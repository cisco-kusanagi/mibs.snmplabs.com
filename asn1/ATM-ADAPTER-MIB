ATM-ADAPTER-MIB DEFINITIONS ::= BEGIN

IMPORTS
     enterprises, Counter       FROM RFC1155-SMI
     DisplayString              FROM RFC1213-MIB
     OBJECT-TYPE                FROM RFC1212;

ibm               OBJECT IDENTIFIER ::= { enterprises 2 }

ibmProd           OBJECT IDENTIFIER ::= { ibm 6 }

     -- a subtree for defining atm adapter MIB object types
atmAdapter        OBJECT IDENTIFIER ::= { ibmProd 29 }

     -- a subtree for defining administrative
     --  object identifiers
atmAdapterAdmin   OBJECT IDENTIFIER ::= { atmAdapter 1 }

     -- a subtree for defining UNI MIB object types
atmAdapterMib  OBJECT IDENTIFIER ::= { atmAdapter 2 }

--        Object Identifier definitions

-- The following values are defined for use as possible values
--  of the atmfPortTransmissionType object.

atmfTrap              OBJECT IDENTIFIER ::= { atmAdapterAdmin 1 }
atmfTransmissionTypes OBJECT IDENTIFIER ::= { atmAdapterAdmin 2 }
atmfMediaTypes        OBJECT IDENTIFIER ::= { atmAdapterAdmin 3 }
atmfTypes             OBJECT IDENTIFIER ::= { atmAdapterAdmin 4 }

     -- unknown transmission type
atmfUnknownType
          OBJECT IDENTIFIER ::= { atmfTransmissionTypes 1 }

     -- Sonet STS-3c physical layer at 155.52 Mbps
atmfSonetSTS3c
          OBJECT IDENTIFIER ::= { atmfTransmissionTypes 2 }

     -- DS3 physical layer at 44.736 Mbps
atmfDs3
          OBJECT IDENTIFIER ::= { atmfTransmissionTypes 3 }

     -- 4B/5B encoding physical layer at 100 Mbps
atmf4B5B
          OBJECT IDENTIFIER ::= { atmfTransmissionTypes 4 }

     -- 8B/10B encoding physical layer at 155.52 Mbps
atmf8B10B
          OBJECT IDENTIFIER ::= { atmfTransmissionTypes 5 }


-- The following values are defined for use as possible values
--  of the atmfPortMediaType object.


     -- unknown media type
atmfMediaUnknownType
          OBJECT IDENTIFIER ::= { atmfMediaTypes 1 }

     -- Coaxial cable
atmfMediaCoaxCable
          OBJECT IDENTIFIER ::= { atmfMediaTypes 2 }

     -- Single Mode fiber
atmfMediaSingleMode
          OBJECT IDENTIFIER ::= { atmfMediaTypes 3 }

     -- Multi Mode fiber
atmfMediaMultiMode
          OBJECT IDENTIFIER ::= { atmfMediaTypes 4 }

     -- Shielded Twisted Pair
atmfMediaStp
          OBJECT IDENTIFIER ::= { atmfMediaTypes 5 }

     -- Unshielded Twisted Pair
atmfMediaUtp
          OBJECT IDENTIFIER ::= { atmfMediaTypes 6 }





     -- unknown adapter type
atmfUnknownAdapterType
          OBJECT IDENTIFIER ::= { atmfTypes 1 }

     -- Turbo ways ATM adapter
atmfTurbowaysATM-100
          OBJECT IDENTIFIER ::= { atmfTypes 2 }






-- atmfTrap              OBJECT IDENTIFIER ::= { atmAdapterAdmin 1 }

muxatmTrap                  OBJECT-TYPE
  SYNTAX                    INTEGER
  ACCESS                    read-only
  STATUS                    mandatory
  DESCRIPTION
   "An enterprise-specific trap is generated when this
   MIB variable is read.  If the trap is generated, the
   value of the MIB variable is 1.  If the trap fails,
   the value of the MIB variable is 0."
  ::= { atmfTrap 1 }


muxatmString                OBJECT-TYPE
  SYNTAX                    DisplayString
  ACCESS                    read-only
  STATUS                    mandatory
  DESCRIPTION
   "A simple string.  It is the title of the ATM MIB."
  ::= { atmfTrap 2 }




--                    The MIB groups

atmfAdapterGroup   OBJECT IDENTIFIER ::= { atmAdapterMib 1 }
atmfAtmLayerGroup  OBJECT IDENTIFIER ::= { atmAdapterMib 2 }
atmfAtmStatsGroup  OBJECT IDENTIFIER ::= { atmAdapterMib 3 }




--         The ATM adapter Group

-- The group is mandatory for all UNI devices.
--
-- The ATM adapter Table

atmfAdapterTable            OBJECT-TYPE
     SYNTAX                 SEQUENCE OF AtmfAdapterEntry
     ACCESS                 not-accessible
     STATUS                 mandatory
     DESCRIPTION
          "A table containing all information about the adapter."
     ::= { atmfAdapterGroup 1 }

atmfAdapterEntry            OBJECT-TYPE
     SYNTAX                 AtmfAdapterEntry
     ACCESS                 not-accessible
     STATUS                 mandatory
     DESCRIPTION
          "An entry in the  table containing information about the adapter."
     INDEX {atmfAdapterIndex}
     ::= { atmfAdapterTable 1 }

AtmfAdapterEntry        ::=
  SEQUENCE   {
     atmfAdapterIndex               INTEGER,
     atmfAdapterSerialNumber        INTEGER,
     atmfAdapterDiagVersion         INTEGER,
     atmfAdapterSoftwareVersion     INTEGER,
     atmfAdapterTransmitBufSize     INTEGER,
     atmfAdapterReceiveBufSize      INTEGER,
     atmfAdapterTransmissionType    OBJECT IDENTIFIER,
     atmfAdapterMediaType           OBJECT IDENTIFIER,
     atmfAdapterOperStatus          OBJECT IDENTIFIER,
     atmfAdapterType                OBJECT IDENTIFIER
             }

atmfAdapterIndex            OBJECT-TYPE
     SYNTAX                 INTEGER
     ACCESS                 read-only
     STATUS                 mandatory
     DESCRIPTION
          "A unique value which identifies this ATM adapter."
     ::= { atmfAdapterEntry 1 }


atmfAdapterSerialNumber     OBJECT-TYPE
     SYNTAX                 INTEGER
     ACCESS                 read-only
     STATUS                 mandatory
     DESCRIPTION
          "The serial number from the VPD of the ATM adapter."
     ::= { atmfAdapterEntry 2 }


atmfAdapterDiagVersion      OBJECT-TYPE
     SYNTAX                 INTEGER
     ACCESS                 read-only
     STATUS                 mandatory
     DESCRIPTION
          "The diagnostic version number from the VPD of the ATM adapter."
     ::= { atmfAdapterEntry 3 }

atmfAdapterSoftwareVersion  OBJECT-TYPE
     SYNTAX                 INTEGER
     ACCESS                 read-only
     STATUS                 mandatory
     DESCRIPTION
          "The software version number from the VPD of the ATM adapter."
     ::= { atmfAdapterEntry 4 }


atmfAdapterTransmitBufSize  OBJECT-TYPE
     SYNTAX                 INTEGER (0 ..9180)
     ACCESS                 read-only
     STATUS                 mandatory
     DESCRIPTION
          "The maximum transmit buffer size in bytes."
     ::= { atmfAdapterEntry 5 }


atmfAdapterReceiveBufSize   OBJECT-TYPE
     SYNTAX                 INTEGER (0 ..9180)
     ACCESS                 read-only
     STATUS                 mandatory
     DESCRIPTION
          "The maximum receive buffer size in bytes."
     ::= { atmfAdapterEntry 6 }


atmfAdapterTransmissionType OBJECT-TYPE
     SYNTAX                 OBJECT IDENTIFIER
     ACCESS                 read-only
     STATUS                 mandatory
     DESCRIPTION
          "The Transmission type of this adapter. For example, for a adapter using
           the Sonet STS-3c physical layer at 155.52 Mbs, this object would have
           the Object Identifier Value:atmfSonetSTS3c. For the Turboways ATM 100
           adapter this value shall be: atmf4B5B."
     ::= { atmfAdapterEntry 7 }

atmfAdapterMediaType        OBJECT-TYPE
     SYNTAX                 OBJECT IDENTIFIER
     ACCESS                 read-only
     STATUS                 mandatory
     DESCRIPTION
          "The type of media used on this port.  For example, for a
           adapter using coaxial cable, this object would have the Object
           Identifier value:  atmfMediaCoaxCable. For the Turboways ATM 100 adapter
           the media type shall be: atmfMediaMultiMode"
     ::= { atmfAdapterEntry 8 }


atmfAdapterOperStatus       OBJECT-TYPE
     SYNTAX                 INTEGER {
                                    other(1),
                                    inService(2),
                                    outOfService(3),
                                    loopBack(4)
                                    }
     ACCESS                 read-only
     STATUS                 mandatory
     DESCRIPTION
          "The operational (i.e., actual) state of this adapter.

          An alarm should not be generated on physical interface when the
          value of this object is outOfService(3).  This capability is
          useful if equipment is to be disconnected, or for trouble
          shooting purposes.

          A value of loopBack(4) indicates that a local loopback is in
          place."
     ::= { atmfAdapterEntry 9 }


atmfAdapterType             OBJECT-TYPE
     SYNTAX                 OBJECT IDENTIFIER
     ACCESS                 read-only
     STATUS                 mandatory
     DESCRIPTION
          "The hardware type of this adapter. For example if the adapter is
           100 Mbits MultiMode fiber adapter, then this object would have the
           Object Identifier value: atmfTurbowaysATM-100"
     ::= { atmfAdapterEntry 10 }

   ---------------------------------------------------------------
   --  ATM layer Group
   -- This group is mandatory for all UNI devices.
   --
   -- ATM-layer specific information for the UNI interface

atmfAtmLayerTable           OBJECT-TYPE
     SYNTAX                 SEQUENCE OF AtmfAtmLayerEntry
     ACCESS                 not-accessible
     STATUS                 mandatory
     DESCRIPTION
          "A table containing ATM layer configuration information"
     ::= { atmfAtmLayerGroup 1 }

atmfAtmLayerEntry           OBJECT-TYPE
     SYNTAX                 AtmfAtmLayerEntry
     ACCESS                 not-accessible
     STATUS                 mandatory
     DESCRIPTION
          "An entry in the  table containing configuration information
           about the adapter."
     INDEX {atmfAtmLayerIndex}
     ::= { atmfAtmLayerTable 1 }

AtmfAtmLayerEntry        ::=
  SEQUENCE   {
     atmfAtmLayerIndex              INTEGER,
     atmfAtmLayerMaxVPCs            INTEGER,
     atmfAtmLayerMaxVCCs            INTEGER,
     atmfAtmLayerConfiguredVPCs     INTEGER,
     atmfAtmLayerConfiguredVCCs     INTEGER,
     atmfAtmLayerMaxVpiBits         INTEGER,
     atmfAtmLayerMaxVciBits         INTEGER,
     atmfAtmLayerUniType            INTEGER
             }

atmfAtmLayerIndex                   OBJECT-TYPE
     SYNTAX                         INTEGER
     ACCESS                         read-only
     STATUS                         mandatory
     DESCRIPTION
          "A unique value which identifies this ATM adapter."
     ::= { atmfAtmLayerEntry 1 }

atmfAtmLayerMaxVPCs                 OBJECT-TYPE
     SYNTAX                         INTEGER  (0 ..255)
     ACCESS                         read-only
     STATUS                         mandatory
     DESCRIPTION
          "The maximum number of VPCs supported on this
           User to Network Interface."
     ::= { atmfAtmLayerEntry 2 }

atmfAtmLayerMaxVCCs                 OBJECT-TYPE
     SYNTAX                         INTEGER (0..16777215)
     ACCESS                         read-only
     STATUS                         mandatory
     DESCRIPTION
          "The maximum number of VCCs supported on this
           User to Network Interface."
     ::= { atmfAtmLayerEntry 3 }

atmfAtmLayerConfiguredVPCs          OBJECT-TYPE
     SYNTAX                         INTEGER (0..255)
     ACCESS                         read-only
     STATUS                         mandatory
     DESCRIPTION
          "The number of VPCs configured for use on this
           User to Network Interface."
     ::= { atmfAtmLayerEntry 4 }

atmfAtmLayerConfiguredVCCs          OBJECT-TYPE
     SYNTAX                         INTEGER (0..16777215)
     ACCESS                         read-only
     STATUS                         mandatory
     DESCRIPTION
          "The number of VCCs configured for use on this
           User to Network Interface."
     ::= { atmfAtmLayerEntry 5 }

atmfAtmLayerMaxVpiBits              OBJECT-TYPE
     SYNTAX                         INTEGER (0..8)
     ACCESS                         read-only
     STATUS                         mandatory
     DESCRIPTION
          "The number of active VPI bits on this interface."
     ::= { atmfAtmLayerEntry 6 }

atmfAtmLayerMaxVciBits              OBJECT-TYPE
     SYNTAX                         INTEGER (0..16)
     ACCESS                         read-only
     STATUS                         mandatory
     DESCRIPTION
          "The number of active VCI bits on this interface."
     ::= { atmfAtmLayerEntry 7 }

atmfAtmLayerUniType OBJECT-TYPE
     SYNTAX                         INTEGER {public(1), private(2) }
     ACCESS                         read-only
     STATUS                         mandatory
     DESCRIPTION
          "The type of the ATM User to Network Interface,
          either public or private."
     ::= { atmfAtmLayerEntry 8 }
------------------------------------------------------------------------

--        The ATM Statistics Group

-- This group is optional. However, if any objects in this group
--  are supported, then all objects in the group must be supported.
--
-- ATM-layer statistics for the UNI interface

atmfAtmStatsTable                   OBJECT-TYPE
     SYNTAX                         SEQUENCE OF AtmfAtmStatsEntry
     ACCESS                         not-accessible
     STATUS                         mandatory
     DESCRIPTION
          "A table containing ATM layer statistics information."
     ::= { atmfAtmStatsGroup 1 }

atmfAtmStatsEntry                   OBJECT-TYPE
     SYNTAX                         AtmfAtmStatsEntry
     ACCESS                         not-accessible
     STATUS                         mandatory
     DESCRIPTION
          "An entry in the  table containing information about statistics."
     INDEX {atmfAtmStatsIndex}
     ::= { atmfAtmStatsTable 1 }

AtmfAtmStatsEntry        ::=
  SEQUENCE   {
     atmfAtmStatsIndex              INTEGER,
     atmfAtmStatsReceivedCells      Counter,
     atmfAtmStatsDroppedPackets     Counter,
     atmfAtmStatsTransmittedCells   Counter
             }

atmfAtmStatsIndex                   OBJECT-TYPE
     SYNTAX                         INTEGER
     ACCESS                         read-only
     STATUS                         mandatory
     DESCRIPTION
          "A unique value which identifies this ATM adapter."
     ::= { atmfAtmStatsEntry 1 }

atmfAtmStatsReceivedCells           OBJECT-TYPE
     SYNTAX                         Counter
     ACCESS                         read-only
     STATUS                         mandatory
     DESCRIPTION
          "The accumulated number of ATM cells received on this
          interface which were assigned and not dropped."
     ::= { atmfAtmStatsEntry 2 }

atmfAtmStatsDroppedPackets          OBJECT-TYPE
     SYNTAX                         Counter
     ACCESS                         read-only
     STATUS                         mandatory
     DESCRIPTION
          "The accumulated number of ATM packets which were dropped due
          to errors in the cell formatting."
     ::= { atmfAtmStatsEntry 3 }

atmfAtmStatsTransmittedCells        OBJECT-TYPE
     SYNTAX                         Counter
     ACCESS                         read-only
     STATUS                         mandatory
     DESCRIPTION
          "The accumulated number of assigned ATM cells which were
          transmitted across this interface."
     ::= { atmfAtmStatsEntry 4 }

END
