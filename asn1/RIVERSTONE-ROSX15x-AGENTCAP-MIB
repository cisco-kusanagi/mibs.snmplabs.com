-- ROSX Firmware Agent Capabilities macro

-- #include "rfc1493.inc"
-- #include "rfc1657.inc"
-- #include "rfc1850a.inc"
-- #include "rfc1850b.inc"
-- #include "rfc2011.inc"
-- #include "rfc2012.inc"
-- #include "rfc2013.inc"
-- #include "rfc2674a.inc"
-- #include "rfc2674b.inc"


-- draft and enterprise mibs
-- #include "rstone-smi-mib.txt"


RIVERSTONE-ROSX15x-AGENTCAP-MIB DEFINITIONS ::= BEGIN

IMPORTS
    MODULE-IDENTITY, Integer32, Unsigned32
       FROM SNMPv2-SMI
    DisplayString
       FROM SNMPv2-TC
    AGENT-CAPABILITIES
       FROM  SNMPv2-CONF
    InetAddress
       FROM INET-ADDRESS-MIB
    riverstoneAgentCapabilities 
       FROM RIVERSTONE-SMI-MIB;

rstoneROSX15xAgentCapabilityMIB MODULE-IDENTITY
   LAST-UPDATED "200505160000Z"  -- May 16, 2005
   ORGANIZATION "Riverstone Networks, Inc"
   CONTACT-INFO
	"Riverstone Networks, Inc
	 5200 Great America Parkway
	 Santa Clara CA USA 95054
	 PHONE:+1 408.878.6500
	 EMAIL: nms-eng@riverstonenet.com
	 WEB: http://www.riverstonenet.com"

   DESCRIPTION
     "This module defines agent capabilities for Riverstone ROSX 
     Software Product version 1.5.x."


    REVISION     "200408280000Z"
    DESCRIPTION
         "Created agent capabilities mib for version 1.5.x of 
          Riverstone ROSX software product."
        ::= { riverstoneAgentCapabilities 150 }


-- this branch is for device specific agent information descriptions via AGENT-CAPABILITIES macro

rosx15xCapability OBJECT IDENTIFIER ::= {  rstoneROSX15xAgentCapabilityMIB 1 }

 rosx1500 AGENT-CAPABILITIES 
  PRODUCT-RELEASE 
     "1.5.0.0"
  STATUS  current
  DESCRIPTION
     "Firmware Release 1.5.0.0 for Riverstone 15000 product line."
  REFERENCE 
     "http://www.riverstonenet.com/products"

     -- RFC 1907
     SUPPORTS SNMPv2-MIB
     INCLUDES { 
         systemGroup,
         snmpGroup, 
         snmpBasicNotificationsGroup,
         --  snmpSetGroup is not implemented, but is needed for SNMPv2-MIB compliance
         -- non mandatory groups
         snmpCommunityGroup,
         -- deprecated/obsolete support
         snmpObsoleteGroup
     }

     -- ********************* ************ ************ *************** ***
     -- RFC 2863
     SUPPORTS IF-MIB
     INCLUDES { 
         ifGeneralInformationGroup, 
         ifStackGroup2,
         ifCounterDiscontinuityGroup,
         -- non mandatory groups
         ifFixedLengthGroup,
         ifHCFixedLengthGroup,
         ifPacketGroup,
         ifHCPacketGroup,
         ifVHCPacketGroup,
     }
     VARIATION ifAlias
     ACCESS read-only
     DESCRIPTION "ifAlias is the same as ifDescr"

     VARIATION ifAdminStatus
     ACCESS read-only
     DESCRIPTION "This object is read only."

     VARIATION ifLinkUpDownTrapEnable
     ACCESS read-only
     DESCRIPTION "This object is read only."

     VARIATION ifStackStatus
     ACCESS read-only
     DESCRIPTION "This object is read only."

     VARIATION ifConnectorPresent
     DESCRIPTION "The value of this object is always true."

     VARIATION ifInUnknownProtos
     DESCRIPTION "The value of this object is always zero."

     VARIATION ifOutOctets
     DESCRIPTION "The value of this object for vlans and ip interfaces is always zero."

     VARIATION ifHCOutOctets
     DESCRIPTION "The value of this object for vlans and ip interfaces is always zero."

     VARIATION ifInErrors
     DESCRIPTION "The value of this object for mpls interfaces and mpls tunnels is always zero."

     VARIATION ifInUcastPkts
     DESCRIPTION "In the case of mpls interfaces and mpls tunnels, this is actually a total packet count."

     VARIATION ifHCInUcastPkts
     DESCRIPTION "In the case of mpls interfaces and mpls tunnels, this is actually a total packet count."

     VARIATION ifInMulticastPkts
     DESCRIPTION "The value of this object for mpls interfaces and mpls tunnels is always zero."

     VARIATION ifHCInMulticastPkts
     DESCRIPTION "The value of this object for mpls interfaces and mpls tunnels is always zero."

     VARIATION ifInBroadcastPkts
     DESCRIPTION "The value of this object for ip interfaces, mpls interfaces and mpls tunnels is always zero."

     VARIATION ifHCInBroadcastPkts
     DESCRIPTION "The value of this object for ip interfaces, mpls interfaces and mpls tunnels is always zero."

     VARIATION ifOutUcastPkts
     DESCRIPTION "The value of this object for ip interfaces is always zero. In the case of vlan interfaces and mpls tunnels, this is actually a total packet count."

     VARIATION ifHCOutUcastPkts
     DESCRIPTION "The value of this object for ip interfaces is always zero. In the case of vlan interfaces and mpls tunnels, this is actually a total packet count."

     VARIATION ifHCOutUcastPkts
     DESCRIPTION "The value of this object for ip interfaces is always zero."

     VARIATION ifOutMulticastPkts
     DESCRIPTION "The value of this object for vlan and ip interfaces is always zero."

     VARIATION ifHCOutMulticastPkts
     DESCRIPTION "The value of this object for vlan and ip interfaces is always zero."

     VARIATION ifPromiscuousMode
     DESCRIPTION "The value of this object is always false."

     VARIATION ifInDiscards
     DESCRIPTION "Only vlan and ip interfaces supply this value."

     VARIATION ifOutDiscards
     DESCRIPTION "For physical and LAG interfaces this value is always zero."

     VARIATION ifSpeed
     DESCRIPTION "For vlan and LAG interfaces this value is always 99999 and for the remaining interfaces is always 0."

     VARIATION ifOperStatus
     DESCRIPTION "For LAG interfaces this value is always down."

     VARIATION ifStackTable
     ACCESS not-implemented
     DESCRIPTION "This table is only partially supported (i.e. not all interfaces are present)."

     VARIATION ifInvStackTable
     ACCESS not-implemented
     DESCRIPTION "This table is not supported"

     VARIATION ifRcvAddressTable
     ACCESS not-implemented
     DESCRIPTION "This table is not supported"


     -- ********************* ************ ************ *************** ***
     -- RFC 2011
     SUPPORTS IP-MIB
     INCLUDES { 
         ipGroup,
         icmpGroup
     }
     VARIATION ipDefaultTTL
     ACCESS read-only
     DESCRIPTION "Command line interface(CLI) is used to change default ttl."

     -- ********************* ************ ************ *************** ***
     -- RFC 2012
     SUPPORTS TCP-MIB
     INCLUDES { 
         tcpGroup         
     }
     VARIATION tcpConnState
     ACCESS read-only
     DESCRIPTION "Command line interface(CLI) is used to kill tcp sessions."

     -- ********************* ************ ************ *************** ***
     -- RFC 2013
     SUPPORTS UDP-MIB
     INCLUDES { 
         udpGroup         
     }

     -- ********************* ************ ************ *************** ***
     --  RFC 1657 
--     SUPPORTS BGP4-MIB
--     INCLUDES { 
--         This is an smiv1 mib, all objects read only. Specify in device config file to enable this mib.
--     }

     VARIATION BGP4PathAttrTable
     ACCESS not-implemented
     DESCRIPTION "This table is not supported"

     -- ********************* ************ ************ *************** ***
     -- RFC 1850    
     -- Specify in device config file to enable this mib.
     SUPPORTS OSPF-MIB
     INCLUDES { 
         ospfBasicGroup,
         ospfAreaGroup,
         ospfStubAreaGroup,
         ospfIfGroup,
         ospfIfMetricGroup,
         ospfVirtIfGroup,
         ospfNbrGroup,
         ospfVirtNbrGroup,
         ospfAreaAggregateGroup
     }
     VARIATION ospfVirtIfTable
     ACCESS not-implemented
     DESCRIPTION "This table is not supported"

     VARIATION ospfRouterId
     ACCESS read-only
     DESCRIPTION "Command line interface(CLI) is used to set router id."

     VARIATION ospfAdminStat
     ACCESS read-only
     DESCRIPTION "Command line interface(CLI) is used to set ospf state."

     VARIATION ospfTOSSupport
     ACCESS read-only
     DESCRIPTION "Command line interface(CLI) is used to set ospf TOS support."

     VARIATION ospfExtLsdbLimit
     ACCESS read-only
     DESCRIPTION "Command line interface(CLI) is used to set ospf Lsdb Limit."

     VARIATION ospfMulticastExtensions
     ACCESS read-only
     DESCRIPTION "Command line interface(CLI) is used to set ospf multicast extensions."

     VARIATION ospfExitOverflowInterval
     ACCESS read-only
     DESCRIPTION "Command line interface(CLI) is used to set ospf exit overflow interval."

     VARIATION ospfDemandExtensions
     ACCESS read-only
     DESCRIPTION "Command line interface(CLI) is used to set ospf demand extensions."

     VARIATION ospfAuthType
     ACCESS read-only
     DESCRIPTION "Command line interface(CLI) is used to set ospf authorisation types."

     VARIATION ospfImportAsExtern
     ACCESS read-only
     DESCRIPTION "Command line interface(CLI) is used to set ospf Import AS external routes."

     VARIATION ospfAreaSummary
     ACCESS read-only
     DESCRIPTION "Command line interface(CLI) is used to set ospf area summary importation."

     VARIATION ospfAreaStatus
     ACCESS read-only
     DESCRIPTION "Command line interface(CLI) is used to create & delete ospf areas."

     VARIATION ospfStubMetric
     ACCESS read-only
     DESCRIPTION "Command line interface(CLI) is used to set ospf area stub metric."

     VARIATION ospfStubStatus
     ACCESS read-only
     DESCRIPTION "Command line interface(CLI) is used to create & delete stub areas."

     VARIATION ospfStubMetricType
     ACCESS read-only
     DESCRIPTION "Command line interface(CLI) is used to set ospf stub metric type."

     VARIATION ospfAreaRangeMask
     ACCESS read-only
     DESCRIPTION "Command line interface(CLI) is used to set ospf area range mask."

     VARIATION ospfAreaRangeStatus
     ACCESS read-only
     DESCRIPTION "Command line interface(CLI) is used to create & delete ranges."

     VARIATION ospfAreaRangeEffect
     ACCESS read-only
     DESCRIPTION "Command line interface(CLI) is used to set area range effect."

     VARIATION ospfHostMetric
     ACCESS read-only
     DESCRIPTION "Command line interface(CLI) is used to set host metric."

     VARIATION ospfHostStatus
     ACCESS read-only
     DESCRIPTION "Command line interface(CLI) is used to create & delete hosts."

     VARIATION ospfIfAreaId
     ACCESS read-only
     DESCRIPTION "Command line interface(CLI) is used to set Interface area id."

     VARIATION ospfIfType
     ACCESS read-only
     DESCRIPTION "Command line interface(CLI) is used to set Interface type."

     VARIATION ospfIfAdminStat
     ACCESS read-only
     DESCRIPTION "Command line interface(CLI) is used to set Interface admin status."

     VARIATION ospfIfRtrPriority
     ACCESS read-only
     DESCRIPTION "Command line interface(CLI) is used to set interface router priority."

     VARIATION ospfIfTransitDelay
     ACCESS read-only
     DESCRIPTION "Command line interface(CLI) is used to set interface transit delay."

     VARIATION ospfIfRetransInterval
     ACCESS read-only
     DESCRIPTION "Command line interface(CLI) is used to set interface retransmission interval."

     VARIATION ospfIfHelloInterval
     ACCESS read-only
     DESCRIPTION "Command line interface(CLI) is used to set hello interval."

     VARIATION ospfIfRtrDeadInterval
     ACCESS read-only
     DESCRIPTION "Command line interface(CLI) is used to set dead interval."

     VARIATION ospfIfPollInterval
     ACCESS read-only
     DESCRIPTION "Command line interface(CLI) is used to set poll interval."

     VARIATION ospfIfAuthKey
     ACCESS read-only
     DESCRIPTION "Command line interface(CLI) is used to set interface auth key."

     VARIATION ospfIfStatus
     ACCESS read-only
     DESCRIPTION "Command line interface(CLI) is used to create & delete interfaces."

     VARIATION ospfIfMulticastForwarding
     ACCESS read-only
     DESCRIPTION "Command line interface(CLI) is used to set multicast fwd."

     VARIATION ospfIfDemand
     ACCESS read-only
     DESCRIPTION "Command line interface(CLI) is used to set this attribute."

     VARIATION ospfIfAuthType
     ACCESS read-only
     DESCRIPTION "Command line interface(CLI) is used to set this feature."

     VARIATION ospfIfMetricValue
     ACCESS read-only
     DESCRIPTION "Command line interface(CLI) is used to set this feature."

     VARIATION ospfVirtIfTransitDelay
     ACCESS read-only
     DESCRIPTION "Command line interface(CLI) is used to set this feature."

     VARIATION ospfVirtIfRetransInterval
     ACCESS read-only
     DESCRIPTION "Command line interface(CLI) is used to set this feature."

     VARIATION ospfVirtIfHelloInterval
     ACCESS read-only
     DESCRIPTION "Command line interface(CLI) is used to set this feature."

     VARIATION ospfVirtIfRtrDeadInterval
     ACCESS read-only
     DESCRIPTION "Command line interface(CLI) is used to set this feature."

     VARIATION ospfVirtIfAuthKey
     ACCESS read-only
     DESCRIPTION "Command line interface(CLI) is used to set this feature."

     VARIATION ospfVirtIfStatus
     ACCESS read-only
     DESCRIPTION "Command line interface(CLI) is used to set this feature."

     VARIATION ospfVirtIfAuthType
     ACCESS read-only
     DESCRIPTION "Command line interface(CLI) is used to set this feature."

     VARIATION ospfNbrPriority
     ACCESS read-only
     DESCRIPTION "Command line interface(CLI) is used to set this feature."

     VARIATION ospfNbmaNbrStatus
     ACCESS read-only
     DESCRIPTION "Command line interface(CLI) is used to set this feature."

     VARIATION ospfAreaAggregateStatus
     ACCESS read-only
     DESCRIPTION "Command line interface(CLI) is used to set this feature."

     VARIATION ospfAreaAggregateEffect
     ACCESS read-only
     DESCRIPTION "Command line interface(CLI) is used to set this feature."

     SUPPORTS OSPF-TRAP-MIB
     INCLUDES { 
         ospfTrapControlGroup
     }

     -- ********************* ************ ************ *************** ***
     -- RFC 1493
--    SUPPORTS BRIDGE-MIB
--    INCLUDES { 
--       smiv1 mib
--    }

     VARIATION dot1dBasePortTable
     ACCESS not-implemented
     DESCRIPTION "This table is not supported"

     VARIATION dot1dStpPortTable
     ACCESS not-implemented
     DESCRIPTION "This table is not supported"

     VARIATION dot1dTpLearnedEntryDiscards
     ACCESS not-implemented
     DESCRIPTION "This object is not supported"



     -- ********************* ************ ************ *************** ***
     -- RFC 2674

     SUPPORTS Q-BRIDGE-MIB
     INCLUDES {
        qBridgeBaseGroup,
        qBridgeVlanGroup,
        qBridgeVlanStaticGroup,
        qBridgeFdbUnicastGroup,
     }     

     VARIATION dot1qNumVlans
     ACCESS not-implemented
     DESCRIPTION "The value of this object is always zero."

     VARIATION dot1qGvrpStatus
     ACCESS not-implemented
     DESCRIPTION "The value of this object is always false."

     VARIATION dot1qVlanFdbId
     ACCESS not-implemented
     DESCRIPTION "This object is not supported"

     VARIATION dot1qVlanCurrentEgressPorts
     ACCESS not-implemented
     DESCRIPTION "This object is not supported"

     VARIATION dot1qVlanCurrentUntaggedPorts
     ACCESS not-implemented
     DESCRIPTION "This object is not supported"

     VARIATION dot1qVlanStatus
     ACCESS not-implemented
     DESCRIPTION "This object is not supported"

     VARIATION dot1qVlanCreationTime
     ACCESS not-implemented
     DESCRIPTION "This object is not supported"

     VARIATION dot1qVlanForbiddenEgressPort
     ACCESS not-implemented
     DESCRIPTION "This object is not supported"



     -- ********************* ************ ************ *************** ***
        -- RFC 2674
        -- The P-BRIDGE-MIB is actually not supported even though it is listed
        -- in the show snmp mibs command.
        --
        -- SUPPORTS P-BRIDGE-MIB *** NOT SUPPORTED ***

     -- ********************* ************ ************ *************** ***
     -- RFC 2737

     SUPPORTS ENTITY-MIB
     INCLUDES {
         entityPhysicalGroup,
         entityMappingGroup,
	 entityGeneralGroup,
	 entityNotificationsGroup,
	 entityPhysical2Group,
	 entityLogical2Group
     }

     VARIATION entLastChangeTime
     ACCESS read-only
     DESCRIPTION 
	 "This object would always be zero unless the notification
	  entConfigChange is enabled."

     VARIATION entPhysicalSerialNum
     ACCESS read-only
     DESCRIPTION 
	 "This object is readable in 9.1. The user can use the CLI to 
	  set this object."

     VARIATION entPhysicalAlias
     ACCESS read-only
     DESCRIPTION 
	 "This object does not return any meaninful value, and
	  it is currently not settable."

     VARIATION entPhysicalAssetID
     ACCESS read-only
     DESCRIPTION
	 "This object does not return any meaninful value, and
	  it is currently not settable."

     VARIATION entLPPhysicalIndex
     ACCESS not-implemented
     DESCRIPTION 
	 "This object is not implemented even though entLogical2Group
	  is implemented."

     VARIATION entAliasLogicalIndexOrZero
     ACCESS read-only
     DESCRIPTION 
	 "This object would always be zero even though entLogical2Group
	  is implemented."

     VARIATION entLogicalTAddress
     ACCESS not-implemented
     DESCRIPTION 
	 "This is not implemented. A meaningless value is returned."

     VARIATION entLogicalTDomain
     ACCESS not-implemented
     DESCRIPTION 
	 "This is not implemented. A meaningless value is returned."


     -- ********************* ************ ************ *************** ***

     SUPPORTS RIVERSTONE-VLAN-EXTENSIONS-MIB
     INCLUDES {
         rsPortVlanStatsGroup,
         rsPortVlanStatsOverflowGroup,
         rsPortVlanHCStatsGroup
     }

     VARIATION rsPortVlanOutOctets
     ACCESS not-implemented
     DESCRIPTION  "The value of this object is always zero.."

     VARIATION rsPortVlanOutOverflowOctets
     ACCESS not-implemented
     DESCRIPTION  "The value of this object is always zero.."

     VARIATION rsPortVlanHCOutOctets
     ACCESS not-implemented
     DESCRIPTION  "The value of this object is always zero.."

     -- ********************* ************ ************ *************** ***
     
     -- RFC 2096
     SUPPORTS IP-FORWARD-MIB
     INCLUDES { 
         ipForwardCidrRouteGroup
     }
     VARIATION ipCidrRouteIfIndex
     ACCESS read-only
     DESCRIPTION "SET operation is not supported."

     VARIATION ipCidrRouteType
     ACCESS read-only
     DESCRIPTION "SET operation is not supported."


     VARIATION ipCidrRouteInfo
     ACCESS read-only
     DESCRIPTION "SET operation is not supported."


     VARIATION ipCidrRouteNextHopAS
     ACCESS read-only
     DESCRIPTION "SET operation is not supported."


     VARIATION ipCidrRouteMetric1
     ACCESS read-only
     DESCRIPTION "SET operation is not supported."


     VARIATION ipCidrRouteMetric2
     ACCESS read-only
     DESCRIPTION "SET operation is not supported."


     VARIATION ipCidrRouteMetric3
     ACCESS read-only
     DESCRIPTION "SET operation is not supported."


     VARIATION ipCidrRouteMetric4
     ACCESS read-only
     DESCRIPTION "SET operation is not supported."


     VARIATION ipCidrRouteMetric5
     ACCESS read-only
     DESCRIPTION "SET operation is not supported."


     VARIATION ipCidrRouteStatus
     ACCESS read-only
     DESCRIPTION "SET operation is not supported."


     -- ********************* ************ ************ *************** ***
     
     SUPPORTS RIVERSTONE-SYSTEM-RESOURCES-MIB
     INCLUDES { 
         rsUtlConfGroupV1
     }

     VARIATION rsUtlSamplingRate 
     ACCESS read-only
     DESCRIPTION "SET operation is not supported."

     -- ********************* ************ ************ *************** ***
     
     -- Note that this MIB module has not yet been assigned a home under mib-2
     -- by IANA. It is hosted under { riverstoneMIBs 100 } for now.
     SUPPORTS ENTITY-STATE-MIB
     INCLUDES { 
         entStateGroup
     }

     VARIATION entStateLastChanged
     ACCESS not-implemented
     DESCRIPTION  "This object is not implemented. It always returns sysUpTime."

     VARIATION entStateUsage
     ACCESS not-implemented
     DESCRIPTION  "This object is not implemented."

     VARIATION entStateAdmin
     ACCESS read-only
     DESCRIPTION "SET operation is not supported."

     -- ********************* ************ ************ *************** ***
     
     -- Draft #7 is supported
     -- No write access
     SUPPORTS MPLS-LSR-MIB

     -- Draft #6 is supported
     -- No write access
     SUPPORTS MPLS-TE-MIB

   ::= { rosx15xCapability 1 }

END
