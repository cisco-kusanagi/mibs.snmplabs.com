--			Ascend mibtacl MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBTACL-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibtaclProfile  OBJECT IDENTIFIER ::= { configuration 128}

	-- The mibtaclProfile table
	--
	-- This table contains parameters for the mibtaclProfile profile
	--

    mibtaclProfileTable	OBJECT-TYPE
	SYNTAX		SEQUENCE OF MibtaclProfileEntry
	ACCESS		not-accessible
	STATUS		mandatory
	DESCRIPTION	"A list of mibtaclProfile profile entries."
	::= { mibtaclProfile 1 }

    mibtaclProfileEntry	OBJECT-TYPE
	SYNTAX		MibtaclProfileEntry
	ACCESS		not-accessible
	STATUS		mandatory
	DESCRIPTION	"A mibtaclProfile entry containing objects that
			 maps to the parameters of mibtaclProfile profile."
	INDEX		{ taclProfile-Index-o }
	::= { mibtaclProfileTable 1 }

    MibtaclProfileEntry ::=
	SEQUENCE {
	    taclProfile-Index-o
		INTEGER,
	    taclProfile-EnablePermit
		INTEGER,
	    taclProfile-Action-o
		INTEGER
	}

    taclProfile-Index-o	OBJECT-TYPE
	SYNTAX	INTEGER
	ACCESS	read-only
	STATUS	mandatory
	DESCRIPTION	""
	::= { mibtaclProfileEntry 1 }

    taclProfile-EnablePermit	OBJECT-TYPE
	SYNTAX	INTEGER {
		    no (1),
		    yes (2)
		}
	ACCESS	read-write
	STATUS	mandatory
	DESCRIPTION	"When TRUE, the permit-list is used, when FALSE, the permit-list is skipped when filtering."
	::= { mibtaclProfileEntry 2 }

    taclProfile-Action-o	OBJECT-TYPE
	SYNTAX	INTEGER {
		    noAction (1),
		    createProfile (2),
		    deleteProfile (3)
		}
	ACCESS	read-write
	STATUS	mandatory
	DESCRIPTION	""
	::= { mibtaclProfileEntry 3 }


	-- The mibtaclProfile__permit_list table
	--
	-- This table contains parameters for the mibtaclProfile__permit_list profile
	--

    mibtaclProfile-PermitListTable	OBJECT-TYPE
	SYNTAX		SEQUENCE OF MibtaclProfile-PermitListEntry
	ACCESS		not-accessible
	STATUS		mandatory
	DESCRIPTION	"A list of mibtaclProfile__permit_list profile entries."
	::= { mibtaclProfile 2 }

    mibtaclProfile-PermitListEntry	OBJECT-TYPE
	SYNTAX		MibtaclProfile-PermitListEntry
	ACCESS		not-accessible
	STATUS		mandatory
	DESCRIPTION	"A mibtaclProfile__permit_list entry containing objects that
			 maps to the parameters of mibtaclProfile__permit_list profile."
	INDEX		{ taclProfile-PermitList-Index-o, taclProfile-PermitList-Index1-o }
	::= { mibtaclProfile-PermitListTable 1 }

    MibtaclProfile-PermitListEntry ::=
	SEQUENCE {
	    taclProfile-PermitList-Index-o
		INTEGER,
	    taclProfile-PermitList-Index1-o
		INTEGER,
	    taclProfile-PermitList-ValidEntry
		INTEGER,
	    taclProfile-PermitList-SourceAddress
		IpAddress,
	    taclProfile-PermitList-SourceAddressMask
		IpAddress
	}

    taclProfile-PermitList-Index-o	OBJECT-TYPE
	SYNTAX	INTEGER
	ACCESS	read-only
	STATUS	mandatory
	DESCRIPTION	""
	::= { mibtaclProfile-PermitListEntry 1 }

    taclProfile-PermitList-Index1-o	OBJECT-TYPE
	SYNTAX	INTEGER
	ACCESS	read-only
	STATUS	mandatory
	DESCRIPTION	""
	::= { mibtaclProfile-PermitListEntry 2 }

    taclProfile-PermitList-ValidEntry	OBJECT-TYPE
	SYNTAX	INTEGER {
		    no (1),
		    yes (2)
		}
	ACCESS	read-write
	STATUS	mandatory
	DESCRIPTION	"When TRUE, this entry is used, when FALSE, this entry is skipped when filtering."
	::= { mibtaclProfile-PermitListEntry 3 }

    taclProfile-PermitList-SourceAddress	OBJECT-TYPE
	SYNTAX	IpAddress
	ACCESS	read-write
	STATUS	mandatory
	DESCRIPTION	"A value to compare with the masked source addresses."
	::= { mibtaclProfile-PermitListEntry 4 }

    taclProfile-PermitList-SourceAddressMask	OBJECT-TYPE
	SYNTAX	IpAddress
	ACCESS	read-write
	STATUS	mandatory
	DESCRIPTION	"A mask to apply to a source address before comparison."
	::= { mibtaclProfile-PermitListEntry 5 }

END
