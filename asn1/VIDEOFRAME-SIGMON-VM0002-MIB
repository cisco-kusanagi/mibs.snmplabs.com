VIDEOFRAME-SIGMON-VM0002-MIB DEFINITIONS ::= BEGIN

	--  Relationship to Other MIBs
	--
	--
	--  The objects defined in this MIB are located under the
	--  private.enterprises subtree as shown below:
	--
	--               iso(1).org(3).dod(6).internet(1)
	--                            |
	--                         private(4)
	--                            |
	--                       enterprises(1)
	--                            |
	--                       videoframe(4596)
	--                            |
	--                      vfProducts(4)
	--							  |
	--						vfSigmonFrame(2)
	--							  |
	--					  vfSigmonFrameModuleTypes(1)
	--							  |
	--					   vm0002AnalogVideo(2)
	--                                 
	--
	--  References
	--
	--  [1]  RFC 1902.  McCloghrie, K., and M. Rose, "Structure 
	--       of Management Information for Version 2 of the Simple
	--       Network Management Protocol (SNMPv2)".  
	--       January, 1996.
	--
	--  [2]  RFC 1903.  McCloghrie, K., and M. Rose, "Textual
	--       Conventions for Version 2 of the Simple Network
	--       Management Protocol (SNMPv2)".  
	--       January, 1996.
	--
	--  [3]  RFC 1904.  McCloghrie, K., and M. Rose, "Conformance
	--       Statements for Version 2 of the Simple Network
	--       Management Protocol (SNMPv2)".  
	--       January, 1996.
	--
	--  [4]  RFC 1907.  McCloghrie, K., and M. Rose, "Management 
	--       Information Base for Version 2 of the Simple Network
	--       Management Protocol (SNMPv2)".  
	--       January, 1996.
	--
	--	[5]  Perkins, David and McGinnis, Evan; "Understanding SNMP
	--		 MIBs".  Prentice Hall, ISBN 0-13-437708-7, 1997.
	--
	--
	--  Object Synopsis
	--  
	--
	--  All objects within this MIB are prefixed with the OBJECT
	--  IDENTIFIER "p", where "p" is:
	--
	--  iso(1).org(3).dod(6).internet(1).private(4).enterprises(1).
	--          videoframe(4596).vfProducts(4).vfSigmonFrame(2).
	--			vfSigmonFrameModuleTypes(1)
	--	
	--  or, 1.3.6.1.4.1.4596.4.2.1
	--
	--
	--  Object Name                               Object Id         
	--  --------------------------------          --------------
	--
	--	vm0002AnalogVideo							p.2
	--		vm0002Table								p.2.1
	--		vm0002TableEntry						p.2.1.1
	--			vm0002SlotNumber					p.2.1.1.1.m	   m = slot #
	--			vm0002Active						p.2.1.1.2.m
	--			vm0002FirmwareRev					p.2.1.1.3.m
	--			vm0002Locate						p.2.1.1.4.m
	--		vm0002SignalTable						p.2.2
	--		vm0002SignalEntry						p.2.2.1
	--			vm0002SignalSlotNumber				p.2.2.1.1.m.n   m = slot #, n = signal #
	--			vm0002SignalNumber					p.2.2.1.2.m.n
	--			vm0002SignalName					p.2.2.1.3.m.n
	--			vm0002SignalDescription				p.2.2.1.4.m.n
	--			vm0002VsyncLossThreshold			p.2.2.1.5.m.n
	--			vm0002VsyncLossPeriod				p.2.2.1.6.m.n
	--			vm0002VsyncLossAlarmState			p.2.2.1.7.m.n
	--			vm0002VsyncLossAlarmAck				p.2.2.1.8.m.n
	--			vm0002VsyncLossTrapEnable			p.2.2.1.9.m.n
	--			vm0002HsyncLossThreshold			p.2.2.1.10.m.n
	--			vm0002HsyncLossPeriod				p.2.2.1.11.m.n
	--			vm0002HsyncLossAlarmState			p.2.2.1.12.m.n
	--			vm0002HsyncLossAlarmAck				p.2.2.1.13.m.n
	--			vm0002HsyncLossTrapEnable			p.2.2.1.14.m.n
	--			vm0002PedestalHighThreshold			p.2.2.1.15.m.n
	--			vm0002PedestalHighPeriod			p.2.2.1.16.m.n
	--			vm0002MeasuredPedestal				p.2.2.1.17.m.n
	--			vm0002PedestalHighAlarmState		p.2.2.1.18.m.n
	--			vm0002PedestalHighAlarmAck			p.2.2.1.19.m.n
	--			vm0002PedestalHighTrapEnable		p.2.2.1.20.m.n
	--			vm0002CurrentAplRaw					p.2.2.1.21.m.n
	--			vm0002n100IRECalibrationSet			p.2.2.1.22.m.n
	--			vm0002n100IRECalibrationValue		p.2.2.1.23.m.n
	--			vm0002AplHighThreshold				p.2.2.1.24.m.n
	--			vm0002AplHighDuration				p.2.2.1.25.m.n
	--			vm0002AplHighAlarmState				p.2.2.1.26.m.n
	--			vm0002AplHighAlarmAck				p.2.2.1.27.m.n
	--			vm0002AplHighTrapEnable				p.2.2.1.28.m.n
	--			vm0002AplLowThreshold				p.2.2.1.29.m.n
	--			vm0002AplLowDuration				p.2.2.1.30.m.n
	--			vm0002AplLowAlarmState				p.2.2.1.31.m.n
	--			vm0002AplLowAlarmAck				p.2.2.1.32.m.n
	--			vm0002AplLowTrapEnable				p.2.2.1.33.m.n
	--			vm0002FrozenImageFilter				p.2.2.1.34.m.n
	--			vm0002MaxFrozenDuration				p.2.2.1.35.m.n
	--			vm0002FrozenAlarmState				p.2.2.1.36.m.n
	--			vm0002FrozenAlarmAck				p.2.2.1.37.m.n
	--			vm0002FrozenTrapEnable				p.2.2.1.38.m.n
	--			vm0002BurstPresent					p.2.2.1.39.m.n
	--		vm0002AnalogVideoEvents					p.2.3
	--			vm0002AnalogVideoEventsV2			p.2.3.0
	--				analogVideoVSyncLossAlarm		p.2.3.0.1
	--				analogVideoHSyncLossAlarm		p.2.3.0.2
	--				analogVideoPedestalHighAlarm	p.2.3.0.3
	--				analogVideoAPLHighAlarm			p.2.3.0.4
	--				analogVideoAPLLowAlarm			p.2.3.0.5
	--				analogVideoFrozenImageAlarm		p.2.3.0.6
	--    

	IMPORTS
		OBJECT-TYPE FROM RFC1155-SMI
		MODULE-IDENTITY, OBJECT-IDENTITY, NOTIFICATION-TYPE,
		IpAddress
			FROM SNMPv2-SMI
		DisplayString, RowStatus
			FROM SNMPv2-TC
		MODULE-COMPLIANCE, OBJECT-GROUP
			FROM SNMPv2-CONF
		vfMIBModules
			FROM VIDEOFRAME-REGISTRATIONS-MIB
		vfBoxId
			FROM VIDEOFRAME-GENERIC-MIB
		vfSigmonFrameModuleTypes, vfProductsVF200Reg, vfFrameSlotNumber
			FROM VIDEOFRAME-SIGMON-MIB;

	videoframeSigmonVm0002MIB MODULE-IDENTITY
		LAST-UPDATED "0108300000Z"
		ORGANIZATION "Videoframe Systems"
		CONTACT-INFO
			"Videoframe Systems
			P.O. Box 1991,
			Grass Valley, CA 95945, USA.

			+1 (530) 477-2000

			http://www.videoframesystems.com"
	DESCRIPTION
		"This MIB describes the device specific objects of the VM0002
		Analog Video Monitoring module,	and augments MIB-2, VF-GENERIC,
		and VF-SIGMON in the identification of this Videoframe Systems
		managed device.

		This module will be extended or modified as required.

		Videoframe Systems reserves the right to
		make changes in specification and other 
		information contained in this document without 
		prior notice. The reader should consult Videoframe Systems
		to determine whether any such changes have been made.

		In no event shall Videoframe Systems be 
		liable for any incidental, indirect, special, 
		or consequential damages whatsoever (including 
		but not limited to lost profits) arising out of 
		or related to this document or the information 
		contained in it.

		Videoframe Systems grants vendors, end users, 
		and other interested parties a non-exclusive 
		license to use this specification in connection 
		with the management of Videoframe Systems products.

		Copyright 2001 Videoframe, Inc."
	REVISION      "0108300000Z"
	DESCRIPTION
		"First release."
	::= { vfMIBModules 5 }

	--
	-- VM0002 product registration. vfProductsVF200Reg is from
	-- vf-sigmon
	--

vfProductsVM0002Reg OBJECT-IDENTITY
		STATUS	current
		DESCRIPTION
			"Videoframe VM0002 Analog Video Monitoring Module."
	::= { vfProductsVF200Reg 2 }

	--
	--  The VM0002 MIB top-level groups
	--

	-- root of this MIB module
vm0002AnalogVideo		OBJECT IDENTIFIER ::= { vfSigmonFrameModuleTypes 2 }

	--
	-- Other signal monitoring modules, whose management information is defined in
	-- other MIB modules.
	--
	--		vm0001AnalogAudio		OBJECT IDENTIFIER ::= { vfSigmonFrameModuleTypes 1 }
	--		vm0003AESEBUAudio		OBJECT IDENTIFIER ::= { vfSigmonFrameModuleTypes 3 }
	--		vm0004SDIVideo			OBJECT IDENTIFIER ::= { vfSigmonFrameModuleTypes 4 }
	--		vm0005SerialIO			OBJECT IDENTIFIER ::= { vfSigmonFrameModuleTypes 5 }
	--		vm0006GPIInterface		OBJECT IDENTIFIER ::= { vfSigmonFrameModuleTypes 6 }
	--		vm0007TransferSwitch	OBJECT IDENTIFIER ::= { vfSigmonFrameModuleTypes 7 }
	--		vm0008CPU				OBJECT IDENTIFIER ::= { vfSigmonFrameModuleTypes 8 }
	--		vm0009DTMFTransceiver	OBJECT IDENTIFIER ::= { vfSigmonFrameModuleTypes 9 }
	--		vm0010GPOInterface		OBJECT IDENTIFIER ::= { vfSigmonFrameModuleTypes 10 }
	--		vm0011GPIOInterface		OBJECT IDENTIFIER ::= { vfSigmonFrameModuleTypes 11 }
	--

vm0002Table	OBJECT-TYPE
	SYNTAX	SEQUENCE OF Vm0002Entry
	MAX-ACCESS	not-accessible
	STATUS	current
	DESCRIPTION
		"Each row contains information about one VM0002 Analog Video
		 module in the managed VF200 frame."

	::=	{ vm0002AnalogVideo 1}


vm0002Entry	OBJECT-TYPE
	SYNTAX	Vm0002Entry
    MAX-ACCESS not-accessible
    STATUS     current
    DESCRIPTION
        "An Analog Video module entry."
	INDEX { vfFrameSlotNumber }
    ::= { vm0002Table 1 } 
		
Vm0002Entry   ::= 
    SEQUENCE	{
		vm0002SlotNumber	INTEGER,
		vm0002Active		INTEGER,
		vm0002FirmwareRev	DisplayString,
		vm0002Locate		INTEGER
				}	

vm0002SlotNumber OBJECT-TYPE
		SYNTAX	INTEGER (1..12)				
		MAX-ACCESS	read-only
		STATUS		current
		DESCRIPTION
			"The slot that this entry represents."
	::= { vm0002Entry 1 }

vm0002Active OBJECT-TYPE
		SYNTAX	INTEGER
					{
						active(1),
						inactive(2)
					}				
		MAX-ACCESS	read-only
		STATUS		current
		DESCRIPTION
			"Indicates whether this entry is active (this module is in
			 this slot)."
	::= { vm0002Entry 2 }

vm0002FirmwareRev OBJECT-TYPE
		SYNTAX		DisplayString (SIZE(0..20))
		MAX-ACCESS	read-only
		STATUS		current
		DESCRIPTION
			"The revision level of the firmware on 
			this module."
	::= { vm0002Entry 3 }

vm0002Locate OBJECT-TYPE
		SYNTAX	INTEGER
					{
						flash(1),
						off(2)
					}				
		MAX-ACCESS	read-write
		STATUS		current
		DESCRIPTION
			"Controls the locate indicator on the module and indicates its
			 current state.  Set to flash (1) to cause the locate LED on the
			 front of the module to begin flashing.  Set to off to stop flashing."
	::= { vm0002Entry 4 }

vm0002SignalTable	OBJECT-TYPE
	SYNTAX	SEQUENCE OF Vm0002SignalEntry
	MAX-ACCESS	not-accessible
	STATUS	current
	DESCRIPTION
		"Each row contains information about one channel of one VM0002 Analog Video
		 module in the managed VF200 frame."

	::=	{ vm0002AnalogVideo 2}


vm0002SignalEntry	OBJECT-TYPE
	SYNTAX	Vm0002SignalEntry
    MAX-ACCESS not-accessible
    STATUS     current
    DESCRIPTION
        "An Analog Video module channel entry."
	INDEX { vfFrameSlotNumber, vm0002SignalNumber }
    ::= { vm0002SignalTable 1 } 
		
Vm0002SignalEntry   ::= 
    SEQUENCE	{
		vm0002SignalSlotNumber			INTEGER,
		vm0002SignalNumber				INTEGER,
		vm0002SignalName				DisplayString,
		vm0002SignalDescription			DisplayString,
		vm0002VSyncLossThreshold		INTEGER,
		vm0002VSyncLossPeriod			INTEGER,
		vm0002VSyncLossAlarmState		INTEGER,
		vm0002VSyncLossAlarmAck			INTEGER,
		vm0002VSyncLossTrapEnable		INTEGER,
		vm0002HSyncLossThreshold		INTEGER,
   		vm0002HSyncLossPeriod			INTEGER,
		vm0002HSyncLossAlarmState		INTEGER,
		vm0002HSyncLossAlarmAck			INTEGER,
		vm0002HSyncLossTrapEnable		INTEGER,
		vm0002PedestalHighThreshold		INTEGER,
		vm0002PedestalHighPeriod		INTEGER,
		vm0002MeasuredPedestal			INTEGER,
		vm0002PedestalHighAlarmState	INTEGER,
		vm0002PedestalHighAlarmAck		INTEGER,
		vm0002PedestalHighTrapEnable	INTEGER,
   		vm0002CurrentAplRaw				INTEGER,
		vm0002n100IRECalibrationSet		INTEGER,
		vm0002n100IRECalibrationValue	INTEGER,
		vm0002AplHighThreshold			INTEGER,
		vm0002AplHighDuration			INTEGER,
		vm0002AplHighAlarmState			INTEGER,
		vm0002AplHighAlarmAck			INTEGER,
		vm0002AplHighTrapEnable			INTEGER,
		vm0002AplLowThreshold			INTEGER,
		vm0002AplLowDuration			INTEGER,
		vm0002AplLowAlarmState			INTEGER,
		vm0002AplLowAlarmAck			INTEGER,
		vm0002AplLowTrapEnable			INTEGER,
		vm0002FrozenImageFilter			INTEGER,
		vm0002MaxFrozenDuration			INTEGER,
		vm0002FrozenAlarmState			INTEGER,
		vm0002FrozenAlarmAck			INTEGER,
		vm0002FrozenTrapEnable			INTEGER,
		vm0002BurstPresent				INTEGER
		}

vm0002SignalSlotNumber OBJECT-TYPE
		SYNTAX	INTEGER (1..12)				
		MAX-ACCESS	read-only
		STATUS		current
		DESCRIPTION
			"The frame slot number that this entry represents."
	::= { vm0002SignalEntry 1 }

vm0002SignalNumber OBJECT-TYPE
		SYNTAX		INTEGER(1..4)
		MAX-ACCESS	read-only
		STATUS		current
		DESCRIPTION
			"The channel within the module to which this signal is connected."
	::= { vm0002SignalEntry 2 }

vm0002SignalName OBJECT-TYPE
		SYNTAX		DisplayString (SIZE(0..20))
		MAX-ACCESS	read-write
		STATUS		current
		DESCRIPTION
			"The name of the signal connected to this channel."
	::= { vm0002SignalEntry 3 }

vm0002SignalDescription OBJECT-TYPE
		SYNTAX		DisplayString (SIZE(0..120))
		MAX-ACCESS	read-write
		STATUS		current
		DESCRIPTION
			"Descriptive identification of the signal connected to this channel."
	::= { vm0002SignalEntry 4 }

vm0002VSyncLossThreshold	OBJECT-TYPE
		SYNTAX	INTEGER(0..65075262)
		MAX-ACCESS	read-write
		STATUS		current
		DESCRIPTION
			"Number of frames with VSync errors to tolerate within the VSyncLossPeriod
			before alarming for this channel."
	::= { vm0002SignalEntry 5 }

vm0002VSyncLossPeriod	OBJECT-TYPE
		SYNTAX	INTEGER(0..2147483647)				
		MAX-ACCESS	read-write
		STATUS		current
		DESCRIPTION
			"The period, in milliseconds, over which vertical sync errors
			 are accumulated for this channel."
	::= { vm0002SignalEntry 6 }

vm0002VSyncLossAlarmState	OBJECT-TYPE
		SYNTAX	INTEGER
				{
					ready(1),
					triggered(2)
				}
		MAX-ACCESS	read-only
		STATUS		current
		DESCRIPTION
			"The current state of the vertical sync loss alarm for
			this channel."
	::= { vm0002SignalEntry 7 }

vm0002VSyncLossAlarmAck	OBJECT-TYPE
		SYNTAX	INTEGER
				{
					idle(1),
					unacknowledged(2),
					acknowledge(3)
				}
		MAX-ACCESS	read-write
		STATUS		current
		DESCRIPTION
			"Set to acknowledge (3) to acknowledge a triggered vertical
			 sync loss alarm for this channel."
	::= { vm0002SignalEntry 8 }

vm0002VSyncLossTrapEnable	OBJECT-TYPE
		SYNTAX	INTEGER
				{
					enabled(1),
					disabled(2)
				}
		MAX-ACCESS	read-write
		STATUS		current
		DESCRIPTION
			"Set to enabled (1) to enable the vertical sync loss alarm trap for
			this channel."
	::= { vm0002SignalEntry 9 }

vm0002HSyncLossThreshold	OBJECT-TYPE
		SYNTAX	INTEGER(0..65075262)
		MAX-ACCESS	read-write
		STATUS		current
		DESCRIPTION
			"Number of frames with horizontal sync errors to tolerate within the HSyncLossPeriod
			before alarming for this channel."
	::= { vm0002SignalEntry 10 }

vm0002HSyncLossPeriod	OBJECT-TYPE
		SYNTAX	INTEGER(0..2147483647)				
		MAX-ACCESS	read-write
		STATUS		current
		DESCRIPTION
			"The period, in milliseconds, over which horizontal sync loss errors
			 are accumulated for this channel."
	::= { vm0002SignalEntry 11 }

vm0002HSyncLossAlarmState	OBJECT-TYPE
		SYNTAX	INTEGER
				{
					ready(1),
					triggered(2)
				}
		MAX-ACCESS	read-only
		STATUS		current
		DESCRIPTION
			"The current state of the horizontal sync loss alarm for
			this channel."
	::= { vm0002SignalEntry 12 }

vm0002HSyncLossAlarmAck	OBJECT-TYPE
		SYNTAX	INTEGER
				{
					idle(1),
					unacknowledged(2),
					acknowledge(3)
				}
		MAX-ACCESS	read-write
		STATUS		current
		DESCRIPTION
			"Set to acknowledge (3) to acknowledge a triggered horizontal
			 sync loss alarm for this channel."
	::= { vm0002SignalEntry 13 }

vm0002HSyncLossTrapEnable	OBJECT-TYPE
		SYNTAX	INTEGER
				{
					enabled(1),
					disabled(2)
				}
		MAX-ACCESS	read-write
		STATUS		current
		DESCRIPTION
			"Set to enabled (1) to enable the horizontal sync loss alarm trap for
			this channel."
	::= { vm0002SignalEntry 14 }

vm0002PedestalHighThreshold	OBJECT-TYPE
		SYNTAX	INTEGER(0..300)
		MAX-ACCESS	read-write
		STATUS		current
		DESCRIPTION
			"Pedestal level above which to alarm for this channel, in units of 1/10th IRE."
	::= { vm0002SignalEntry 15 }

vm0002PedestalHighPeriod	OBJECT-TYPE
		SYNTAX	INTEGER(0..2147483647)				
		MAX-ACCESS	read-write
		STATUS		current
		DESCRIPTION
			"The period, in milliseconds, that the pedestal must remain
			 above the threshold to alarm for this channel."
	::= { vm0002SignalEntry 16 }

vm0002MeasuredPedestal	OBJECT-TYPE
		SYNTAX	INTEGER(0..300)
		MAX-ACCESS	read-write
		STATUS		current
		DESCRIPTION
			"The current measured pedestal level on this channel, in units of 1/10th IRE."
	::= { vm0002SignalEntry 17 }

vm0002PedestalHighAlarmState	OBJECT-TYPE
		SYNTAX	INTEGER
				{
					ready(1),
					triggered(2)
				}
		MAX-ACCESS	read-only
		STATUS		current
		DESCRIPTION
			"The current state of the pedestal high alarm for
			this channel."
	::= { vm0002SignalEntry 18 }

vm0002PedestalHighAlarmAck	OBJECT-TYPE
		SYNTAX	INTEGER
				{
					idle(1),
					unacknowledged(2),
					acknowledge(3)
				}
		MAX-ACCESS	read-write
		STATUS		current
		DESCRIPTION
			"Set to acknowledge (3) to acknowledge a triggered pedestal high
			 alarm for this channel."
	::= { vm0002SignalEntry 19 }

vm0002PedestalHighTrapEnable	OBJECT-TYPE
		SYNTAX	INTEGER
				{
					enabled(1),
					disabled(2)
				}
		MAX-ACCESS	read-write
		STATUS		current
		DESCRIPTION
			"Set to enabled (1) to enable the pedestal high alarm trap for
			this channel."
	::= { vm0002SignalEntry 20 }

vm0002CurrentAplRaw	OBJECT-TYPE
		SYNTAX	INTEGER(0..1023)
		MAX-ACCESS	read-only
		STATUS		current
		DESCRIPTION
			"The current average luminance value on this channel,
			 as a raw 10-bit sample value."
	::= { vm0002SignalEntry 21 }
			  
vm0002n100IRECalibrationSet	OBJECT-TYPE
		SYNTAX	INTEGER
			{
				ready(1),
				go(2),
				notReady(3)
			}
		MAX-ACCESS	read-write
		STATUS		current
		DESCRIPTION
			"Set to 'go' (2) to set the value of the 100 IRE channel
			 calibration to the current average luminance value on
			 this channel."
	::= { vm0002SignalEntry 22 }
			  
vm0002n100IRECalibrationValue	OBJECT-TYPE
		SYNTAX	INTEGER(0..1023)
		MAX-ACCESS	read-only
		STATUS		current
		DESCRIPTION
			"The current raw luminance value used as the 100 IRE
			 reference on this channel."
	::= { vm0002SignalEntry 23 }
			  
vm0002AplHighThreshold OBJECT-TYPE
		SYNTAX	INTEGER(0..150)				
		MAX-ACCESS	read-write
		STATUS		current
		DESCRIPTION
			"The high APL alarm threshold for this
			channel, in IRE."
	::= { vm0002SignalEntry 24 }

vm0002AplHighDuration OBJECT-TYPE
		SYNTAX	INTEGER(0..2147483647)				
		MAX-ACCESS	read-write
		STATUS		current
		DESCRIPTION
			"The high APL duration, in milliseconds, at which to alarm, for
			this channel."
	::= { vm0002SignalEntry 25 }

vm0002AplHighAlarmState	OBJECT-TYPE
		SYNTAX	INTEGER
				{
					ready(1),
					triggered(2)
				}
		MAX-ACCESS	read-only
		STATUS		current
		DESCRIPTION
			"The current state of the high APL alarm for this
			channel."
	::= { vm0002SignalEntry 26 }

vm0002AplHighAlarmAck	OBJECT-TYPE
		SYNTAX	INTEGER
				{
					idle(1),
					unacknowledged(2),
					acknowledge(3)
				}
		MAX-ACCESS	read-write
		STATUS		current
		DESCRIPTION
			"Set to acknowledge (3) to acknowledge a triggered high APL alarm for
			this channel."
	::= { vm0002SignalEntry 27 }

vm0002AplHighTrapEnable OBJECT-TYPE
		SYNTAX	INTEGER
					{
						enabled(1),
						disabled(2)
					}				
		MAX-ACCESS	read-write
		STATUS		current
		DESCRIPTION
			"Set to enabled (1) to enable the high APL alarm trap for
			this channel."
	::= { vm0002SignalEntry 28 }

vm0002AplLowThreshold OBJECT-TYPE
		SYNTAX	INTEGER(0..100)				
		MAX-ACCESS	read-write
		STATUS		current
		DESCRIPTION
			"The low APL alarm threshold for this channel, in IRE."
	::= { vm0002SignalEntry 29 }

vm0002AplLowDuration OBJECT-TYPE
		SYNTAX	INTEGER(0..2147483647)				
		MAX-ACCESS	read-write
		STATUS		current
		DESCRIPTION
			"The low APL duration, in milliseconds, at which to alarm, for
			this channel."
	::= { vm0002SignalEntry 30 }

vm0002AplLowAlarmState	OBJECT-TYPE
		SYNTAX	INTEGER
				{
					ready(1),
					triggered(2)
				}
		MAX-ACCESS	read-only
		STATUS		current
		DESCRIPTION
			"The current state of the low APL alarm for
			this channel."
	::= { vm0002SignalEntry 31 }

vm0002AplLowAlarmAck	OBJECT-TYPE
		SYNTAX	INTEGER
				{
					idle(1),
					unacknowledged(2),
					acknowledge(3)
				}
		MAX-ACCESS	read-write
		STATUS		current
		DESCRIPTION
			"Set to acknowledge (3) to acknowledge a triggered low APL alarm for
			this channel."
	::= { vm0002SignalEntry 32 }

vm0002AplLowTrapEnable OBJECT-TYPE
		SYNTAX	INTEGER				
					{
						enabled(1),
						disabled(2)
					}				
		MAX-ACCESS	read-write
		STATUS		current
		DESCRIPTION
			"Set to enabled (1) to enable the low APL alarm trap for
			this channel."
	::= { vm0002SignalEntry 33 }

vm0002FrozenImageFilter OBJECT-TYPE
		SYNTAX	INTEGER(1..8)				
		MAX-ACCESS	read-write
		STATUS		current
		DESCRIPTION
			"The algorithm to use for the frozen image alarm for this
			channel."
	::= { vm0002SignalEntry 34 }

vm0002MaxFrozenDuration OBJECT-TYPE
		SYNTAX	INTEGER(0..2147483647)				
		MAX-ACCESS	read-write
		STATUS		current
		DESCRIPTION
			"The frozen image duration, in milliseconds, at which to alarm, for
			this channel."
	::= { vm0002SignalEntry 35 }

vm0002FrozenAlarmState	OBJECT-TYPE
		SYNTAX	INTEGER
				{
					ready(1),
					triggered(2)
				}
		MAX-ACCESS	read-only
		STATUS		current
		DESCRIPTION
			"The current state of the frozen image alarm for this
			channel."
	::= { vm0002SignalEntry 36 }

vm0002FrozenAlarmAck	OBJECT-TYPE
		SYNTAX	INTEGER
				{
					idle(1),
					unacknowledged(2),
					acknowledge(3)
				}
		MAX-ACCESS	read-write
		STATUS		current
		DESCRIPTION
			"Set to acknowledge (3) to acknowledge a triggered frozen image alarm for
			this channel."
	::= { vm0002SignalEntry 37 }

vm0002FrozenTrapEnable OBJECT-TYPE
		SYNTAX	INTEGER
					{
						enabled(1),
						disabled(2)
					}				
		MAX-ACCESS	read-write
		STATUS		current
		DESCRIPTION
			"Set to enabled (1) to enable the frozen image alarm trap for
			this channel."
	::= { vm0002SignalEntry 38 }

vm0002BurstPresent	OBJECT-TYPE
		SYNTAX	INTEGER
				{
					present(1),
					notPresent(2)
				}
		MAX-ACCESS	read-write
		STATUS		current
		DESCRIPTION
			"Indicates whether color burst is present on
			this channel."
	::= { vm0002SignalEntry 39 }

	--
	-- VM0002 Events
	--

vm0002AnalogVideoEvents		OBJECT IDENTIFIER ::= { vm0002AnalogVideo 3 }
vm0002AnalogVideoEventsV2	OBJECT IDENTIFIER ::= { vm0002AnalogVideoEvents 0 }

analogVideoVSyncLossAlarm	NOTIFICATION-TYPE
		OBJECTS
			{
				vfBoxId,
				vm0002SlotNumber,
				vm0002SignalNumber,
				vm0002SignalName,
				vm0002SignalDescription
			}
		STATUS	current
		DESCRIPTION
			"An Analog Video vertical sync loss alarm was triggered."
		::= { vm0002AnalogVideoEventsV2 1 }

analogVideoHSyncLossAlarm	NOTIFICATION-TYPE
		OBJECTS
			{
				vfBoxId,
				vm0002SlotNumber,
				vm0002SignalNumber,
				vm0002SignalName,
				vm0002SignalDescription
			}
		STATUS	current
		DESCRIPTION
			"An Analog Video horizontal sync loss alarm was triggered."
		::= { vm0002AnalogVideoEventsV2 2 }

analogVideoPedestalHighAlarm	NOTIFICATION-TYPE
		OBJECTS
			{
				vfBoxId,
				vm0002SlotNumber,
				vm0002SignalNumber,
				vm0002SignalName,
				vm0002SignalDescription
			}
		STATUS	current
		DESCRIPTION
			"An Analog Video pedestal high alarm was triggered."
		::= { vm0002AnalogVideoEventsV2 3 }

analogVideoAPLHighAlarm	NOTIFICATION-TYPE
		OBJECTS
			{
				vfBoxId,
				vm0002SlotNumber,
				vm0002SignalNumber,
				vm0002SignalName,
				vm0002SignalDescription
			}
		STATUS	current
		DESCRIPTION
			"An Analog Video APL high alarm was triggered."
		::= { vm0002AnalogVideoEventsV2 4 }

analogVideoAPLLowAlarm	NOTIFICATION-TYPE
		OBJECTS
			{
				vfBoxId,
				vm0002SlotNumber,
				vm0002SignalNumber,
				vm0002SignalName,
				vm0002SignalDescription
			}
		STATUS	current
		DESCRIPTION
			"An Analog Video APL low alarm was triggered."
		::= { vm0002AnalogVideoEventsV2 5 }

analogVideoFrozenImageAlarm	NOTIFICATION-TYPE
		OBJECTS
			{
				vfBoxId,
				vm0002SlotNumber,
				vm0002SignalNumber,
				vm0002SignalName,
				vm0002SignalDescription
			}
		STATUS	current
		DESCRIPTION
			"An Analog Video frozen image alarm was triggered."
		::= { vm0002AnalogVideoEventsV2 6 }


END
