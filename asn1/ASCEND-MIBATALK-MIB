--			Ascend mibatalk MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBATALK-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibatalkGlobalProfile  OBJECT IDENTIFIER ::= { configuration 36}
    mibatalkInterfaceProfile  OBJECT IDENTIFIER ::= { configuration 35}

	-- The mibatalkGlobalProfile table
	--
	-- This table contains parameters for the mibatalkGlobalProfile profile
	--

    mibatalkGlobalProfileTable	OBJECT-TYPE
	SYNTAX		SEQUENCE OF MibatalkGlobalProfileEntry
	ACCESS		not-accessible
	STATUS		mandatory
	DESCRIPTION	"A list of mibatalkGlobalProfile profile entries."
	::= { mibatalkGlobalProfile 1 }

    mibatalkGlobalProfileEntry	OBJECT-TYPE
	SYNTAX		MibatalkGlobalProfileEntry
	ACCESS		not-accessible
	STATUS		mandatory
	DESCRIPTION	"A mibatalkGlobalProfile entry containing objects that
			 maps to the parameters of mibatalkGlobalProfile profile."
	INDEX		{ atalkGlobalProfile-Index-o }
	::= { mibatalkGlobalProfileTable 1 }

    MibatalkGlobalProfileEntry ::=
	SEQUENCE {
	    atalkGlobalProfile-Index-o
		INTEGER,
	    atalkGlobalProfile-AtalkDialinPoolStart
		INTEGER,
	    atalkGlobalProfile-AtalkDialinPoolEnd
		INTEGER,
	    atalkGlobalProfile-Action-o
		INTEGER
	}

    atalkGlobalProfile-Index-o	OBJECT-TYPE
	SYNTAX	INTEGER
	ACCESS	read-only
	STATUS	mandatory
	DESCRIPTION	""
	::= { mibatalkGlobalProfileEntry 1 }

    atalkGlobalProfile-AtalkDialinPoolStart	OBJECT-TYPE
	SYNTAX	INTEGER
	ACCESS	read-write
	STATUS	mandatory
	DESCRIPTION	"The Net range start of the dialin pool shared by the wan interfaces."
	::= { mibatalkGlobalProfileEntry 2 }

    atalkGlobalProfile-AtalkDialinPoolEnd	OBJECT-TYPE
	SYNTAX	INTEGER
	ACCESS	read-write
	STATUS	mandatory
	DESCRIPTION	"The Net range end of the dialin pool shared by the wan interfaces."
	::= { mibatalkGlobalProfileEntry 3 }

    atalkGlobalProfile-Action-o	OBJECT-TYPE
	SYNTAX	INTEGER {
		    noAction (1),
		    createProfile (2),
		    deleteProfile (3)
		}
	ACCESS	read-write
	STATUS	mandatory
	DESCRIPTION	""
	::= { mibatalkGlobalProfileEntry 4 }


	-- The mibatalkInterfaceProfile table
	--
	-- This table contains parameters for the mibatalkInterfaceProfile profile
	--

    mibatalkInterfaceProfileTable	OBJECT-TYPE
	SYNTAX		SEQUENCE OF MibatalkInterfaceProfileEntry
	ACCESS		not-accessible
	STATUS		mandatory
	DESCRIPTION	"A list of mibatalkInterfaceProfile profile entries."
	::= { mibatalkInterfaceProfile 1 }

    mibatalkInterfaceProfileEntry	OBJECT-TYPE
	SYNTAX		MibatalkInterfaceProfileEntry
	ACCESS		not-accessible
	STATUS		mandatory
	DESCRIPTION	"A mibatalkInterfaceProfile entry containing objects that
			 maps to the parameters of mibatalkInterfaceProfile profile."
	INDEX		{ atalkInterfaceProfile-Shelf-o, atalkInterfaceProfile-Slot-o, atalkInterfaceProfile-Item-o, atalkInterfaceProfile-LogicalItem-o }
	::= { mibatalkInterfaceProfileTable 1 }

    MibatalkInterfaceProfileEntry ::=
	SEQUENCE {
	    atalkInterfaceProfile-Shelf-o
		INTEGER,
	    atalkInterfaceProfile-Slot-o
		INTEGER,
	    atalkInterfaceProfile-Item-o
		INTEGER,
	    atalkInterfaceProfile-LogicalItem-o
		INTEGER,
	    atalkInterfaceProfile-InterfaceAddress-PhysicalAddress-Shelf
		INTEGER,
	    atalkInterfaceProfile-InterfaceAddress-PhysicalAddress-Slot
		INTEGER,
	    atalkInterfaceProfile-InterfaceAddress-PhysicalAddress-ItemNumber
		INTEGER,
	    atalkInterfaceProfile-InterfaceAddress-LogicalItem
		INTEGER,
	    atalkInterfaceProfile-AtalkRoutingEnabled
		INTEGER,
	    atalkInterfaceProfile-HintZone
		DisplayString,
	    atalkInterfaceProfile-AtalkRouter
		INTEGER,
	    atalkInterfaceProfile-AtalkNetStart
		INTEGER,
	    atalkInterfaceProfile-AtalkNetEnd
		INTEGER,
	    atalkInterfaceProfile-Action-o
		INTEGER
	}

    atalkInterfaceProfile-Shelf-o	OBJECT-TYPE
	SYNTAX	INTEGER
	ACCESS	read-only
	STATUS	mandatory
	DESCRIPTION	""
	::= { mibatalkInterfaceProfileEntry 1 }

    atalkInterfaceProfile-Slot-o	OBJECT-TYPE
	SYNTAX	INTEGER
	ACCESS	read-only
	STATUS	mandatory
	DESCRIPTION	""
	::= { mibatalkInterfaceProfileEntry 2 }

    atalkInterfaceProfile-Item-o	OBJECT-TYPE
	SYNTAX	INTEGER
	ACCESS	read-only
	STATUS	mandatory
	DESCRIPTION	""
	::= { mibatalkInterfaceProfileEntry 3 }

    atalkInterfaceProfile-LogicalItem-o	OBJECT-TYPE
	SYNTAX	INTEGER
	ACCESS	read-only
	STATUS	mandatory
	DESCRIPTION	""
	::= { mibatalkInterfaceProfileEntry 4 }

    atalkInterfaceProfile-InterfaceAddress-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibatalkInterfaceProfileEntry 5 }

    atalkInterfaceProfile-InterfaceAddress-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibatalkInterfaceProfileEntry 6 }

    atalkInterfaceProfile-InterfaceAddress-PhysicalAddress-ItemNumber	OBJECT-TYPE
	SYNTAX	INTEGER
	ACCESS	read-write
	STATUS	mandatory
	DESCRIPTION	"A number that specifies an addressable entity within the context of shelf and slot."
	::= { mibatalkInterfaceProfileEntry 7 }

    atalkInterfaceProfile-InterfaceAddress-LogicalItem	OBJECT-TYPE
	SYNTAX	INTEGER
	ACCESS	read-write
	STATUS	mandatory
	DESCRIPTION	"A number that specifies an addressable logical entity within the context of a physical address."
	::= { mibatalkInterfaceProfileEntry 8 }

    atalkInterfaceProfile-AtalkRoutingEnabled	OBJECT-TYPE
	SYNTAX	INTEGER {
		    no (1),
		    yes (2)
		}
	ACCESS	read-write
	STATUS	mandatory
	DESCRIPTION	"Allow Appletalk routing and ARA connections."
	::= { mibatalkInterfaceProfileEntry 9 }

    atalkInterfaceProfile-HintZone	OBJECT-TYPE
	SYNTAX	DisplayString
	ACCESS	read-write
	STATUS	mandatory
	DESCRIPTION	"The default zone that the MAX will come up in."
	::= { mibatalkInterfaceProfileEntry 10 }

    atalkInterfaceProfile-AtalkRouter	OBJECT-TYPE
	SYNTAX	INTEGER {
		    atalkRouterOff (1),
		    atalkRouterSeed (2),
		    atalkRouterNonSeed (3)
		}
	ACCESS	read-write
	STATUS	mandatory
	DESCRIPTION	"The type of AppleTalk Router to enable."
	::= { mibatalkInterfaceProfileEntry 11 }

    atalkInterfaceProfile-AtalkNetStart	OBJECT-TYPE
	SYNTAX	INTEGER
	ACCESS	read-write
	STATUS	mandatory
	DESCRIPTION	"The start of the AppleTalk Net number range."
	::= { mibatalkInterfaceProfileEntry 12 }

    atalkInterfaceProfile-AtalkNetEnd	OBJECT-TYPE
	SYNTAX	INTEGER
	ACCESS	read-write
	STATUS	mandatory
	DESCRIPTION	"The end of the AppleTalk Net number range."
	::= { mibatalkInterfaceProfileEntry 13 }

    atalkInterfaceProfile-Action-o	OBJECT-TYPE
	SYNTAX	INTEGER {
		    noAction (1),
		    createProfile (2),
		    deleteProfile (3)
		}
	ACCESS	read-write
	STATUS	mandatory
	DESCRIPTION	""
	::= { mibatalkInterfaceProfileEntry 14 }


	-- The mibatalkInterfaceProfile__atalk_Zone_List table
	--
	-- This table contains parameters for the mibatalkInterfaceProfile__atalk_Zone_List profile
	--

    mibatalkInterfaceProfile-AtalkZoneListTable	OBJECT-TYPE
	SYNTAX		SEQUENCE OF MibatalkInterfaceProfile-AtalkZoneListEntry
	ACCESS		not-accessible
	STATUS		mandatory
	DESCRIPTION	"A list of mibatalkInterfaceProfile__atalk_Zone_List profile entries."
	::= { mibatalkInterfaceProfile 2 }

    mibatalkInterfaceProfile-AtalkZoneListEntry	OBJECT-TYPE
	SYNTAX		MibatalkInterfaceProfile-AtalkZoneListEntry
	ACCESS		not-accessible
	STATUS		mandatory
	DESCRIPTION	"A mibatalkInterfaceProfile__atalk_Zone_List entry containing objects that
			 maps to the parameters of mibatalkInterfaceProfile__atalk_Zone_List profile."
	INDEX		{ atalkInterfaceProfile-AtalkZoneList-Shelf-o, atalkInterfaceProfile-AtalkZoneList-Slot-o, atalkInterfaceProfile-AtalkZoneList-Item-o, atalkInterfaceProfile-AtalkZoneList-LogicalItem-o, atalkInterfaceProfile-AtalkZoneList-Index-o }
	::= { mibatalkInterfaceProfile-AtalkZoneListTable 1 }

    MibatalkInterfaceProfile-AtalkZoneListEntry ::=
	SEQUENCE {
	    atalkInterfaceProfile-AtalkZoneList-Shelf-o
		INTEGER,
	    atalkInterfaceProfile-AtalkZoneList-Slot-o
		INTEGER,
	    atalkInterfaceProfile-AtalkZoneList-Item-o
		INTEGER,
	    atalkInterfaceProfile-AtalkZoneList-LogicalItem-o
		INTEGER,
	    atalkInterfaceProfile-AtalkZoneList-Index-o
		INTEGER,
	    atalkInterfaceProfile-AtalkZoneList
		DisplayString
	}

    atalkInterfaceProfile-AtalkZoneList-Shelf-o	OBJECT-TYPE
	SYNTAX	INTEGER
	ACCESS	read-only
	STATUS	mandatory
	DESCRIPTION	""
	::= { mibatalkInterfaceProfile-AtalkZoneListEntry 1 }

    atalkInterfaceProfile-AtalkZoneList-Slot-o	OBJECT-TYPE
	SYNTAX	INTEGER
	ACCESS	read-only
	STATUS	mandatory
	DESCRIPTION	""
	::= { mibatalkInterfaceProfile-AtalkZoneListEntry 2 }

    atalkInterfaceProfile-AtalkZoneList-Item-o	OBJECT-TYPE
	SYNTAX	INTEGER
	ACCESS	read-only
	STATUS	mandatory
	DESCRIPTION	""
	::= { mibatalkInterfaceProfile-AtalkZoneListEntry 3 }

    atalkInterfaceProfile-AtalkZoneList-LogicalItem-o	OBJECT-TYPE
	SYNTAX	INTEGER
	ACCESS	read-only
	STATUS	mandatory
	DESCRIPTION	""
	::= { mibatalkInterfaceProfile-AtalkZoneListEntry 4 }

    atalkInterfaceProfile-AtalkZoneList-Index-o	OBJECT-TYPE
	SYNTAX	INTEGER
	ACCESS	read-only
	STATUS	mandatory
	DESCRIPTION	""
	::= { mibatalkInterfaceProfile-AtalkZoneListEntry 5 }

    atalkInterfaceProfile-AtalkZoneList	OBJECT-TYPE
	SYNTAX	DisplayString
	ACCESS	read-write
	STATUS	mandatory
	DESCRIPTION	"The Zone List for an AppleTalk seed router."
	::= { mibatalkInterfaceProfile-AtalkZoneListEntry 6 }

END
