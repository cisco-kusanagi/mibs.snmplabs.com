XYPLEX-CHARACTER1-MIB DEFINITIONS ::= BEGIN
            
                    IMPORTS
                            enterprises, Counter, Gauge, TimeTicks
                                    FROM RFC1155-SMI
                            DisplayString
                                    FROM SNMPv2-TC
                            OBJECT-TYPE
                                    FROM RFC-1212
                            DateTime, AddressType
                                    FROM XYPLEX-SYSTEM-MIB;
            
            xyplex          OBJECT IDENTIFIER ::= { enterprises 33 }
            characterDep    OBJECT IDENTIFIER ::= { xyplex 2 }
            character       OBJECT IDENTIFIER ::= { xyplex 13 }
            
            -- Xyplex Character subgroups
            
            basic           OBJECT IDENTIFIER ::= { character 1 }
            queue           OBJECT IDENTIFIER ::= { character 2 }
            menu            OBJECT IDENTIFIER ::= { character 3 }
            netLogin        OBJECT IDENTIFIER ::= { character 4 }
            dial            OBJECT IDENTIFIER ::= { character 5 }
            sessionLog      OBJECT IDENTIFIER ::= { character 6 }
            
            -- This MIB module uses the extended OBJECT-TYPE macro as
            -- defined in [9]
            
            -- This is a MIB module for all Xyplex systems that
            -- implement physical or logical character stream devices














            
            

            
            
            
            
            -- the Character Basic group
            
            -- Implementation of this group is mandatory for all Xyplex
            -- systems that implement physical or logical character
            -- stream devices
            
            basicBroadcast OBJECT-TYPE
                SYNTAX INTEGER { disabled(1), enabled(2) }
                ACCESS read-write
                STATUS mandatory
                DESCRIPTION
                    "Control for user ability to broadcast messages to 
                    other local ports.  Corresponds directly to SERVER 
                    BROADCAST and the presence of the label 'Broadcast' 
                    following the label 'Enabled Characteristics:' in 
                    the SERVER CHARACTERISTICS display."
                ::= { basic 1 }
            
            basicErrorReport OBJECT-TYPE
                SYNTAX INTEGER { disabled(1), enabled(2) }
                ACCESS read-write
                STATUS mandatory
                DESCRIPTION
                    "Control for server display of an error when the 
                    user gives an unsupported command.  Corresponds 
                    directly to SERVER REPORT ERRORS and the presence of 
                    the label 'Report Errors' following the label 
                    'Enabled Characteristics:' in the SERVER 
                    CHARACTERISTICS display."
                ::= { basic 2 }
            
            basicLock OBJECT-TYPE
                SYNTAX INTEGER { disabled(1), enabled(2) }
                ACCESS read-write
                STATUS mandatory
                DESCRIPTION
                    "Control for user ability to use a password to 
                    protect a logged in terminal from other users.  
                    Corresponds directly to SERVER LOCK and the presence 
                    of the label 'Lock' following the label 'Enabled 
                    Characteristics:' in the SERVER CHARACTERISTICS 
                    display."
                ::= { basic 3 }
            
            basicInactivityTimer OBJECT-TYPE
                SYNTAX INTEGER (1..120)

            
            

            
            
            
            
                ACCESS read-write
                STATUS mandatory
                DESCRIPTION
                    "Number of minutes a terminal may remain logged in 
                    with no sessions, no input or output, and no modem 
                    transitions.  Corresponds directly to SERVER 
                    INACTIVITY TIMER and the value labeled 'Inactivity 
                    Timer:' in the SERVER CHARACTERISTICS display."
                ::= { basic 4 }
            
            basicPasswordRetryLimit OBJECT-TYPE
                SYNTAX INTEGER (0..250)
                ACCESS read-write
                STATUS mandatory
                DESCRIPTION
                    "Number of times the server allows a user to retry 
                    an incorrect password.  Corresponds directly to 
                    SERVER PASSWORD LIMIT and the value labeled 
                    'Password Limit:' in the SERVER CHARACTERISTICS 
                    display."
                ::= { basic 5 }
            
            basicPrivilegedPassword OBJECT-TYPE
                SYNTAX DisplayString (SIZE (1..16))
                ACCESS read-write
                STATUS mandatory
                DESCRIPTION
                    "The password a user must enter to become 
                    privileged.
                    For security reasons, reading this object always 
                    returns a zero-length value.  Corresponds directly 
                    to SERVER PRIVILEGED PASSWORD."
                ::= { basic 6 }
            
            basicLoginPassword OBJECT-TYPE
                SYNTAX DisplayString (SIZE (1..16))
                ACCESS read-write
                STATUS mandatory
                DESCRIPTION
                    "The password a user must enter to be given the 
                    opportunity to log in.  For security reasons, 
                    reading this object always returns a zero-length 
                    value. Corresponds directly to SERVER LOGIN 
                    PASSWORD."
                ::= { basic 7 }
            

            
            

            
            
            
            
            basicLoginPrompt OBJECT-TYPE
                SYNTAX DisplayString (SIZE (1..8))
                ACCESS read-write
                STATUS mandatory
                DESCRIPTION
                    "The text string the server displays to prompt a 
                    user for the login password.  Corresponds directly 
                    to SERVER LOGIN PROMPT."
                ::= { basic 8 }
            
            basicWelcome OBJECT-TYPE
                SYNTAX DisplayString (SIZE (0..80))
                ACCESS read-write
                STATUS mandatory
                DESCRIPTION
                    "The text string the server displays before 
                    attempting to log in a user.  Corresponds directly 
                    to SERVER WELCOME and the value labeled 'Welcome:' 
                    in the SERVER CHARACTERISTICS display."
                ::= { basic 9 }
            
            basicActivePorts OBJECT-TYPE
                SYNTAX Gauge
                ACCESS read-only
                STATUS mandatory
                DESCRIPTION
                    "The number of ports with connected sessions or 
                    logged in users.  Corresponds directly to the value 
                    labeled 'Active Ports:' and 'Cur' in the SERVER 
                    STATUS display."
                ::= { basic 10 }
            
            basicActivePortsHigh OBJECT-TYPE
                SYNTAX Gauge
                ACCESS read-only
                STATUS mandatory
                DESCRIPTION
                    "The highest value of basicActivePorts since system 
                    initialization.  Corresponds directly to the value 
                    labeled 'Active Ports:' and 'High' in the SERVER 
                    STATUS display."
                ::= { basic 11 }
            
            basicActiveUsers OBJECT-TYPE
                SYNTAX Gauge
                ACCESS read-only

            
            

            
            
            
            
                STATUS mandatory
                DESCRIPTION
                    "The number of logged in users.  Corresponds 
                    directly to the value labeled 'Active Users:' and 
                    'Cur' in the SERVER STATUS display."
                ::= { basic 12 }
            
            basicActiveUsersHigh OBJECT-TYPE
                SYNTAX Gauge
                ACCESS read-only
                STATUS mandatory
                DESCRIPTION
                    "The highest value of basicActiveUsers since system 
                    initialization.  Corresponds directly to the value 
                    labeled 'Active Users:' and 'High' in the SERVER 
                    STATUS display."
                ::= { basic 13 }
            
            basicSessions OBJECT-TYPE
                SYNTAX Gauge
                ACCESS read-only
                STATUS mandatory
                DESCRIPTION
                    "The total number of connected sessions.  
                    Corresponds directly to the value labeled 'Connected 
                    Sessions:' and 'Cur' in the SERVER STATUS display."
                ::= { basic 14 }
            
            basicSessionsHigh OBJECT-TYPE
                SYNTAX Gauge
                ACCESS read-only
                STATUS mandatory
                DESCRIPTION
                    "The highest value of basicSessions since system 
                    initialization.  Corresponds directly to the value 
                    labeled 'Connected Sessions:' and 'High' in the 
                    SERVER STATUS display."
                ::= { basic 15 }
            
            basicSessionsLimit OBJECT-TYPE
                SYNTAX INTEGER (-1..64)
                ACCESS read-write
                STATUS mandatory
                DESCRIPTION
                    "The maximum total number of sessions that can 
                    simultaneously be connected to the system.  A value 

            
            

            
            
            
            
                            of -1 indicates no limit up to available dynamic 
                    system memory.  Corresponds directly to SERVER 
                    SESSION LIMIT and the value labeled 'Connected 
                    Sessions:' and 'Max' in the SERVER STATUS display."
                ::= { basic 16 }
            
            -- Additional Basic group parameters follow the port tables







































            
            

            
            
            
            
            -- the Basic Port table
            
            basicPortTable OBJECT-TYPE
                SYNTAX SEQUENCE OF BasicPortEntry
                ACCESS not-accessible
                STATUS mandatory
                DESCRIPTION
                    "A list of basic character port entries."
                ::= { basic 17 }
            
            basicPortEntry OBJECT-TYPE
                SYNTAX BasicPortEntry
                ACCESS not-accessible
                STATUS mandatory
                DESCRIPTION
                    "Basic parameter values for a port."
                INDEX { basicPortIndex }
                ::= { basicPortTable 1 }
            
            BasicPortEntry ::=
                SEQUENCE {
                    basicPortIndex
                        INTEGER,
                    basicPortDefaultDestAction
                        INTEGER,
                    basicPortDefaultDestProtocol
                        INTEGER,
                    basicPortDefaultDestName
                        DisplayString,
                    basicPortDefaultDestLATNodeName
                        DisplayString,
                    basicPortDefaultDestLATPortName
                        DisplayString,
                    basicPortAutoConnect
                        INTEGER,
                    basicPortAutoLogin
                        INTEGER,
                    basicPortBroadcast
                        INTEGER,
                    basicPortConnectResume
                        INTEGER,
                    basicPortDialup
                        INTEGER,
                    basicPortIdleTimeout
                        INTEGER,
                    basicPortInactivityLogout

            
            

            
            
            
            
                        INTEGER,
                    basicPortLossNotification
                        INTEGER,
                    basicPortMessageCodes
                        INTEGER,
                    basicPortMultisessions
                        INTEGER,
                    basicPortDefaultUserName
                        DisplayString,
                    basicPortVerification
                        INTEGER,
                    basicPortDefaultProtocol
                        INTEGER,
                    basicPortLogins
                        Counter,
                    basicPortRemoteSessions
                        Counter,
                    basicPortIdleTimeouts
                        Counter,
                    basicPortStatus
                        INTEGER,
                    basicPortLastInCharacter
                        INTEGER,
                    basicPortLastOutCharacter
                        INTEGER,
                    basicPortActiveUserName
                        DisplayString,
                    basicPortDefaultSessionMode
                        INTEGER,
                    basicPortZero
                        INTEGER,
                    basicPortZeroTime
                        TimeTicks
                }
            
            basicPortIndex OBJECT-TYPE
                SYNTAX INTEGER
                ACCESS read-only
                STATUS mandatory
                DESCRIPTION
                    "An index value that uniquely identifies a port.  
                    The port identified by a particular value of this 
                    index is the same port as identified by 
                    charPortIndex in the Character MIB [12]."
                ::= { basicPortEntry 1 }
            

            
            

            
            
            
            
            basicPortDefaultDestAction OBJECT-TYPE
                SYNTAX INTEGER { dedicated(1), preferred(2) }
                ACCESS read-write
                STATUS mandatory
                DESCRIPTION
                    "The action to take relative to 
                    basicPortDefaultDestName.  Corresponds directly to 
                    PORT DEDICATED/PREFERRED SERVICE and the label 
                    'Dedicated/Preferred Service:' in the PORT 
                    CHARACTERISTICS display."
                ::= { basicPortEntry 2 }
            
            basicPortDefaultDestProtocol OBJECT-TYPE
                SYNTAX INTEGER { lat(1), telnet(2), any(3) }
                ACCESS read-write
                STATUS mandatory
                DESCRIPTION
                    "The session protocol to use with 
                    basicPortDefaultDestName.  Corresponds directly to 
                    LAT/TELNET PORT DEDICATED/PREFERRED SERVICE."
                ::= { basicPortEntry 3 }
            
            basicPortDefaultDestName OBJECT-TYPE
                SYNTAX DisplayString (SIZE (0..50))
                ACCESS read-write
                STATUS mandatory
                DESCRIPTION
                    "The default name to use in forming a connection 
                    when no other name is specified.  Corresponds 
                    directly to PORT DEDICATED/PREFERRED SERVICE and the 
                    value labeled 'Dedicated/Preferred Service:' in the 
                    PORT CHARACTERISTICS display.  If the value of 
                    basicPortDefaultDestProtocol is 'telnet', an 
                    Internet port number may be included on the end of 
                    the name, delimited with a colon (':').  If the 
                    value of basicPortDefaultDestProtocol is not 
                    'telnet', then the maximum length is 16."
                ::= { basicPortEntry 4 }
            
            basicPortDefaultDestLATNodeName OBJECT-TYPE
                SYNTAX DisplayString (SIZE (0..16))
                ACCESS read-write
                STATUS mandatory
                DESCRIPTION
                    "A LAT node name to use with 
                    basicPortDefaultDestName.  Corresponds directly to 

            
            

            
            
            
            
                            PORT DEDICATED/PREFERRED SERVICE NODE and the value 
                    labeled 'Node:' following the label 
                    'Dedicated/Preferred Service:' in the PORT 
                    CHARACTERISTICS display.  This object can have a 
                    non- zero-length value only if the value of 
                    basicPortDefaultDestProtocol is 'lat'."
                ::= { basicPortEntry 5 }
            
            basicPortDefaultDestLATPortName OBJECT-TYPE
                SYNTAX DisplayString (SIZE (0..16))
                ACCESS read-write
                STATUS mandatory
                DESCRIPTION
                    "A LAT port name to use with 
                    basicPortDefaultDestName.  Corresponds directly to 
                    PORT DEDICATED/PREFERRED SERVICE NODE and the value 
                    labeled 'Node:' following the label 
                    'Dedicated/Preferred Service:' in the PORT 
                    CHARACTERISTICS display.  this object can hav a 
                    non-zero-length value only if the value if 
                    basicPortDefaultDestProtocol is 'lat'"
                ::= { basicPortEntry 6 }
            
            basicPortAutoConnect OBJECT-TYPE
                SYNTAX INTEGER { disabled(1), enabled(2) }
                ACCESS read-write
                STATUS mandatory
                DESCRIPTION
                    "Control for automatic session connection.  
                    Corresponds directly to PORT AUTOCONNECT and the 
                    presence of the label 'Autoconnect' following the 
                    label 'Enabled Characteristics:' in the PORT 
                    CHARACTERISTICS display."
                ::= { basicPortEntry 7 }
            
            basicPortAutoLogin OBJECT-TYPE
                SYNTAX INTEGER { disabled(1), enabled(2) }
                ACCESS read-write
                STATUS mandatory
                DESCRIPTION
                    "Control for automatic port login.  Corresponds 
                    directly to PORT AUTODEDICATED and the presence of 
                    the label 'Autodedicated' following the label 
                    'Enabled Characteristics:' in the PORT 
                    CHARACTERISTICS display."
                ::= { basicPortEntry 8 }

            
            

            
            
            
            
            
            basicPortBroadcast OBJECT-TYPE
                SYNTAX INTEGER { disabled(1), enabled(2) }
                ACCESS read-write
                STATUS mandatory
                DESCRIPTION
                    "Control for display of messages sent by users on 
                    other ports.  Corresponds directly to PORT BROADCAST 
                    and the presence of the label 'Broadcast' following 
                    the label 'Enabled Characteristics:' in the PORT 
                    CHARACTERISTICS display."
                ::= { basicPortEntry 9 }
            
            basicPortConnectResume OBJECT-TYPE
                SYNTAX INTEGER { disabled(1), enabled(2) }
                ACCESS read-write
                STATUS mandatory
                DESCRIPTION
                    "Control for behavior of a connection attempt to a 
                    destination where the port already has a connection.  
                    'disabled' causes a new connection.  'enabled' 
                    causes the existing connection to become the active 
                    connection.  Corresponds directly to PORT 
                    CONNECTRESUME and the presence of the label 
                    'Connectresume' following the label 'Enabled 
                    Characteristics:' in the PORT CHARACTERISTICS 
                    display."
                ::= { basicPortEntry 10 }
            
            basicPortDialup OBJECT-TYPE
                SYNTAX INTEGER { disabled(1), enabled(2) }
                ACCESS read-write
                STATUS mandatory
                DESCRIPTION
                    "Defines whether the port should be considered as 
                    connected to a dialup line.  'enabled' means that it 
                    is.  Corresponds directly to PORT DIALUP and the 
                    presence of the label 'Dial Up' following the label 
                    'Enabled Characteristics:' in the PORT 
                    CHARACTERISTICS display."
                ::= { basicPortEntry 11 }
            
            basicPortIdleTimeout OBJECT-TYPE
                SYNTAX INTEGER (-1..255)
                ACCESS read-write
                STATUS mandatory

            
            

            
            
            
            
                DESCRIPTION
                    "The number of minutes the system will allow a 
                    session to have no activity before automatically 
                    disconnecting it.  A value of -1 indicates no 
                    timeout.  Zero is not a valid value.  Corresponds 
                    directly to PORT IDLE TIMEOUT and the value labeled 
                    'Idle Timeout:' in the PORT ALTERNATE 
                    CHARACTERISTICS display."
                ::= { basicPortEntry 12 }
            
            basicPortInactivityLogout OBJECT-TYPE
                SYNTAX INTEGER { disabled(1), enabled(2) }
                ACCESS read-write
                STATUS mandatory
                DESCRIPTION
                    "Control for the system automatically logging the 
                    port out when it has no sessions, no local activity, 
                    and no modem signal changes for the time period 
                    specified by basicInactivityTimer.  Corresponds 
                    directly to PORT INACTIVITY LOGOUT and the presence 
                    of the label 'Inactivity Logout' following the label 
                    'Enabled Characteristics:' in the PORT 
                    CHARACTERISTICS display."
                ::= { basicPortEntry 13 }
            
            basicPortLossNotification OBJECT-TYPE
                SYNTAX INTEGER { disabled(1), enabled(2) }
                ACCESS read-write
                STATUS mandatory
                DESCRIPTION
                    "Control for the system sending a Bell character to 
                    the port when it looses an input character due to an 
                    overrun or data error.  Corresponds directly to PORT 
                    LOSS NOTIFICATION and the presence of the label 
                    'Loss Notification' following the label 'Enabled 
                    Characteristics:' in the PORT CHARACTERISTICS 
                    display."
                ::= { basicPortEntry 14 }
            
            basicPortMessageCodes OBJECT-TYPE
                SYNTAX INTEGER { disabled(1), enabled(2) }
                ACCESS read-write
                STATUS mandatory
                DESCRIPTION
                    "Control for including error numbers in error 
                    messages displayed on the port.  Corresponds 

            
            

            
            
            
            
                            directly to PORT MESSAGE CODES and the presence of 
                    the label 'Message Codes' following the label 
                    'Enabled Characteristics:' in the PORT 
                    CHARACTERISTICS display."
                ::= { basicPortEntry 15 }
            
            basicPortMultisessions OBJECT-TYPE
                SYNTAX INTEGER { disabled(1), enabled(2) }
                ACCESS read-write
                STATUS mandatory
                DESCRIPTION
                    "Control for running the multisession line protocol 
                    between the port and the locally-connected terminal.  
                    Corresponds directly to PORT MULTISESSIONS and the 
                    presence of the label 'Multisessions' following the 
                    label 'Enabled Characteristics:' in the PORT 
                    CHARACTERISTICS display."
                ::= { basicPortEntry 16 }
            
            basicPortDefaultUserName OBJECT-TYPE
                SYNTAX DisplayString (SIZE (0..16))
                ACCESS read-write
                STATUS mandatory
                DESCRIPTION
                    "Default user name to use for automatically logging 
                    in the port.  Corresponds directly to PORT USERNAME 
                    and the value labeled 'Port n:' in the PORT 
                    CHARACTERISTICS display."
                ::= { basicPortEntry 17 }
            
            basicPortVerification OBJECT-TYPE
                SYNTAX INTEGER { disabled(1), enabled(2) }
                ACCESS read-write
                STATUS mandatory
                DESCRIPTION
                    "Control for display of informational messages on 
                    the port when the user connects, disconnects, or 
                    switches a session.  Corresponds directly to PORT 
                    VERIFICATION and the presence of the label 
                    'Verification' following the label 'Enabled 
                    Characteristics:' in the PORT CHARACTERISTICS 
                    display."
                ::= { basicPortEntry 18 }
            
            basicPortDefaultProtocol OBJECT-TYPE
                SYNTAX INTEGER { lat(1), telnet(2), any(3) }

            
            

            
            
            
            
                ACCESS read-write
                STATUS mandatory
                DESCRIPTION
                    "The session protocol to use when not otherwise 
                    specified.  Corresponds directly to PORT RESOLVE 
                    SERVICE and the value labeled 'Resolve Service:' in 
                    the PORT ALTERNATE CHARACTERISTICS display."
                ::= { basicPortEntry 19 }
            
            basicPortLogins OBJECT-TYPE
                SYNTAX Counter
                ACCESS read-only
                STATUS mandatory
                DESCRIPTION
                    "The number of logins on the port since system 
                    initialization.  Corresponds directly to the value 
                    labeled 'Local Accesses:' in the PORT COUNTERS 
                    display."
                ::= { basicPortEntry 20 }
            
            basicPortRemoteSessions OBJECT-TYPE
                SYNTAX Counter
                ACCESS read-only
                STATUS mandatory
                DESCRIPTION
                    "The number of remotely originating sessions to the 
                    port since system initialization.  Corresponds 
                    directly to the value labeled 'Remote Accesses:' in 
                    the PORT COUNTERS display."
                ::= { basicPortEntry 21 }
            
            basicPortIdleTimeouts OBJECT-TYPE
                SYNTAX Counter
                ACCESS read-only
                STATUS mandatory
                DESCRIPTION
                    "The number of session disconnects due to expiration 
                    of basicPortIdleTimeout.  Corresponds directly to 
                    the value labeled 'Idle Timeouts:' in the PORT 
                    COUNTERS display."
                ::= { basicPortEntry 22 }
            
            basicPortStatus OBJECT-TYPE
                SYNTAX INTEGER { idle(1), local(2), waitInput(3),
                                 executingCommand(4), connecting(5),
                                 checkConnect(6), waitOutput(7),

            
            

            
            
            
            
                                 connected(8), disconnecting(9),
                                 disconnect(10), suspended(11),
                                 locked(12), permanent(13),
                                 loginWait(14), retryConnect(15),
                                 connectWait(16), logout(17),
                                 login(18), waitSession(19),
                                 reset(20), testServiceWait(21),
                                 testServiceOut(22), 
            connectPassword(23),
                                 waitLogout(24), waitQueue(25),
                                 cancelQueue(26), autobaud(27),
                                 available(28), checkModem(29),
                                 slip(30), signalWait(31),
                                 scriptSearch(32), scriptLoad(33),
                                 scriptRun(34), dialback1(35),
                                 dialback2(36), dialback3(37),
                                 xremote(38) }
                ACCESS read-only
                STATUS mandatory
                DESCRIPTION
                    "The current operational status of the port.  
                    Corresponds directly to the value labeled 'Status:' 
                    in the PORT STATUS display."
                ::= { basicPortEntry 23 }
            
            basicPortLastInCharacter OBJECT-TYPE
                SYNTAX INTEGER (0..255)
                ACCESS read-only
                STATUS mandatory
                DESCRIPTION
                    "The character that most recently came into the 
                    port.  Corresponds directly to the value labeled 
                    'Last Char Input:' in the PORT STATUS display."
                ::= { basicPortEntry 24 }
            
            basicPortLastOutCharacter OBJECT-TYPE
                SYNTAX INTEGER (0..255)
                ACCESS read-only
                STATUS mandatory
                DESCRIPTION
                    "The character that most recently went out of the 
                    port.  Corresponds directly to the value labeled 
                    'Last Char Output:' in the PORT STATUS display."
                ::= { basicPortEntry 25 }
            
            basicPortActiveUserName OBJECT-TYPE

            
            

            
            
            
            
                SYNTAX DisplayString (SIZE (0..16))
                ACCESS read-only
                STATUS mandatory
                DESCRIPTION
                    "The user name currently logged into the port.  
                    Corresponds directly to the value by the port number 
                    and labeled 'Username' in the USERS display."
                ::= { basicPortEntry 26 }
            
            basicPortDefaultSessionMode OBJECT-TYPE
                SYNTAX INTEGER { interactive(1), binary(2),
                                 binaryWithFlow(3), transparent(4)  }
                ACCESS read-write
                STATUS mandatory
                DESCRIPTION
                    "Data recognition mode when starting a session, 
            with
                    the following meanings:
                    
                    interactive      locally recognize all controls
                    binary           recognize only session protocol
                                     (corresponds to PASSALL)
                    binaryWithFlow   recognize only XON and XOFF
                                     (corresponds to PASTHRU
                    transparent      recognize no data
            
                    Corresponds directly to PORT DEFAULT SESSION MODE 
            and
                    the value labeled 'Default Session Mode:' in the 
            PORT
                    ALTERNATE CHARACTERISTICS display."
                ::= { basicPortEntry 27 }
            
            basicPortZero OBJECT-TYPE
                SYNTAX INTEGER  { ready(1), execute(2) }
                ACCESS read-write
                STATUS mandatory
                DESCRIPTION
                    "Control to zero counters for the port.  In response 
                    to a get-request or get-next-request, the agent 
                    always returns 'ready' for this value.  Setting the 
                    value to 'ready' has no effect.  Setting it to 
                    'execute' causes the port's counters to be zeroed.  
                    Corresponds to the ZERO PORT command."
                ::= { basicPortEntry 28 }
            

            
            

            
            
            
            
            basicPortZeroTime OBJECT-TYPE
                SYNTAX TimeTicks
                ACCESS read-only
                STATUS mandatory
                DESCRIPTION
                    "The number of hundredths of a second since the most 
                    recent zeroing of the port's counters, such as 
                    through execution of basicPortZero.  Corresponds 
                    directly to the value labeled 'Seconds Since 
                    Zeroed:' in the PORT COUNTERS display."
                ::= { basicPortEntry 29 }



































            
            

            
            
            
            
            -- the Basic Serial Port table
            
            basicSerialPortTable OBJECT-TYPE
                SYNTAX SEQUENCE OF BasicSerialPortEntry
                ACCESS not-accessible
                STATUS mandatory
                DESCRIPTION
                    "A list of basic character serial port entries."
                ::= { basic 18 }
            
            basicSerialPortEntry OBJECT-TYPE
                SYNTAX BasicSerialPortEntry
                ACCESS not-accessible
                STATUS mandatory
                DESCRIPTION
                    "Basic parameter values for a serial port."
                INDEX { basicSerialPortIndex }
                ::= { basicSerialPortTable 1 }
            
            BasicSerialPortEntry ::=
                SEQUENCE {
                    basicSerialPortIndex
                        INTEGER,
                    basicSerialPortBreak
                        INTEGER,
                    basicSerialPortInterrupts
                        INTEGER,
                    basicSerialPortNoLoss
                        INTEGER,
                    basicSerialPortPause
                        INTEGER,
                    basicSerialPortPrompt
                        DisplayString,
                    basicSerialPortTerminalType
                        INTEGER,
                    basicSerialPortTypeaheadLimit
                        INTEGER,
                    basicSerialPortBackwardSwitch
                        INTEGER,
                    basicSerialPortForwardSwitch
                        INTEGER,
                    basicSerialPortLocalSwitch
                        INTEGER,
                    basicSerialPortModemControl
                        INTEGER,
                    basicSerialPortSignalCheck

            
            

            
            
            
            
                        INTEGER,
                    basicSerialPortDSRLogout
                        INTEGER,
                    basicSerialPortDSRObserve
                        INTEGER,
                    basicSerialPortDCDTimeout
                        INTEGER,
                    basicSerialPortDTRAssert
                        INTEGER,
                    basicSerialPortLimitedCommands
                        INTEGER,
                    basicSerialPortLimitedView
                        INTEGER,
                    basicSerialPortPassword
                        DisplayString,
                    basicSerialPortLineEditor
                        INTEGER,
                    basicSerialPortLineEditorBackspace
                        INTEGER,
                    basicSerialPortLineEditorBeginning
                        INTEGER,
                    basicSerialPortLineEditorCancel
                        INTEGER,
                    basicSerialPortLineEditorDeleteBeginning
                        INTEGER,
                    basicSerialPortLineEditorDeleteLine
                        INTEGER,
                    basicSerialPortLineEditorEnd
                        INTEGER,
                    basicSerialPortLineEditorForward
                        INTEGER,
                    basicSerialPortLineEditorInsertToggle
                        INTEGER,
                    basicSerialPortLineEditorNextLine
                        INTEGER,
                    basicSerialPortLineEditorPreviousLine
                        INTEGER,
                    basicSerialPortLineEditorQuotingCharacter
                        INTEGER,
                    basicSerialPortLineEditorRedisplay
                        INTEGER
                }
            
            basicSerialPortIndex OBJECT-TYPE
                SYNTAX INTEGER
                ACCESS read-only

            
            

            
            
            
            
                STATUS mandatory
                DESCRIPTION
                    "An index value that uniquely identifies a port.  
                    The port identified by a particular value of this 
                    index is the same port as identified by 
                    charPortIndex in the Character MIB [12]."
                ::= { basicSerialPortEntry 1 }
            
            basicSerialPortBreak OBJECT-TYPE
                SYNTAX INTEGER { ignore(1), localSwitch(2),
                                 sendRemote(3) }
                ACCESS read-write
                STATUS mandatory
                DESCRIPTION
                    "Action to take on a BREAK condition from the port.  
                    Corresponds directly to PORT BREAK and the value 
                    labeled 'Break:' in the PORT CHARACTERISTICS 
                    display."
                ::= { basicSerialPortEntry 2 }
            
            basicSerialPortInterrupts OBJECT-TYPE
                SYNTAX INTEGER { disabled(1), enabled(2) }
                ACCESS read-write
                STATUS mandatory
                DESCRIPTION
                    "Control for recognizing BREAK or local switch to 
                    interrupt a session.  Corresponds directly to PORT 
                    INTERRUPTS and the presence of the label 
                    'Interrupts' following the label 'Enabled 
                    Characteristics:' in the PORT CHARACTERISTICS 
                    display."
                ::= { basicSerialPortEntry 3 }
            
            basicSerialPortNoLoss OBJECT-TYPE
                SYNTAX INTEGER { disabled(1), enabled(2) }
                ACCESS read-write
                STATUS mandatory
                DESCRIPTION
                    "Control for storing port input locally in 
                    anticipation of session startup.  Corresponds 
                    directly to PORT NOLOSS and the presence of the 
                    label 'Noloss' following the label 'Enabled 
                    Characteristics:' in the PORT CHARACTERISTICS 
                    display."
                ::= { basicSerialPortEntry 4 }
            

            
            

            
            
            
            
            basicSerialPortPause OBJECT-TYPE
                SYNTAX INTEGER { disabled(1), enabled(2) }
                ACCESS read-write
                STATUS mandatory
                DESCRIPTION
                    "Control for pausing after each screenful of 
                    locally-originated output to the port.  Corresponds 
                    directly to PORT PAUSE and the presence of the label 
                    'Pause' following the label 'Enabled 
                    Characteristics:' in the PORT CHARACTERISTICS 
                    display."
                ::= { basicSerialPortEntry 5 }
            
            basicSerialPortPrompt OBJECT-TYPE
                SYNTAX DisplayString (SIZE (1..8))
                ACCESS read-write
                STATUS mandatory
                DESCRIPTION
                    "Prompt for the system to use on the port.  
                    Corresponds directly to PORT PROMPT and the value 
                    labeled 'Prompt:' in the PORT ALTERNATE 
                    CHARACTERISTICS display."
                ::= { basicSerialPortEntry 6 }
            
            basicSerialPortTerminalType OBJECT-TYPE
                SYNTAX INTEGER { ansi(1), hardcopy(2), softcopy(3) }
                ACCESS read-write
                STATUS mandatory
                DESCRIPTION
                    "Type of terminal attached to the port, for 
                    formatting local output.  Corresponds directly to 
                    PORT TYPE and the value labeled 'Type:' in the PORT 
                    CHARACTERISTICS display."
                ::= { basicSerialPortEntry 7 }
            
            basicSerialPortTypeaheadLimit OBJECT-TYPE
                SYNTAX INTEGER (80..16384)
                ACCESS read-write
                STATUS mandatory
                DESCRIPTION
                    "Maximum number of input characters to hold pending 
                    tranmission on a session.  Corresponds directly to 
                    PORT TYPEAHEAD SIZE and the value labeled 'Typeahead 
                    Size:' in the PORT ALTERNATE CHARACTERISTICS 
                    display."
                ::= { basicSerialPortEntry 8 }

            
            

            
            
            
            
            
            basicSerialPortBackwardSwitch OBJECT-TYPE
                SYNTAX INTEGER (0..255)
                ACCESS read-write
                STATUS mandatory
                DESCRIPTION
                    "Character input from the character port to cause a 
                    switch to the previous, lower numbered session.  The 
                    value 0 indicates no character has this effect.  
                    Corresponds directly to PORT BACKWARD SWITCH and the 
                    value labeled 'Backwards Switch:' in the PORT 
                    CHARACTERISTICS display."
                ::= { basicSerialPortEntry 9 }
            
            basicSerialPortForwardSwitch OBJECT-TYPE
                SYNTAX INTEGER (0..255)
                ACCESS read-write
                STATUS mandatory
                DESCRIPTION
                    "Character input from the character port to cause a 
                    switch to the next, higher numbered session.  The 
                    value 0 indicates no character has this effect.  
                    Corresponds directly to PORT FORWARD SWITCH and the 
                    value labeled 'Forwards Switch:' in the PORT 
                    CHARACTERISTICS display."
                ::= { basicSerialPortEntry 10 }
            
            basicSerialPortLocalSwitch OBJECT-TYPE
                SYNTAX INTEGER (0..255)
                ACCESS read-write
                STATUS mandatory
                DESCRIPTION
                    "Character input from the character port to cause a 
                    switch to local command mode.  The value 0 indicates 
                    no character has this effect.  Corresponds directly 
                    to PORT LOCAL SWITCH and the value labeled 'Local 
                    Switch:' in the PORT CHARACTERISTICS display."
                ::= { basicSerialPortEntry 11 }
            
            
            
            basicSerialPortModemControl OBJECT-TYPE
                SYNTAX INTEGER { disabled(1), enabled(2) }
                ACCESS read-write
                STATUS mandatory
                DESCRIPTION

            
            

            
            
            
            
                    "Control for observing hardware modem control 
                    signals.  Corresponds directly to PORT MODEM CONTROL 
                    and the value labeled 'Modem Control:' in the PORT 
                    CHARACTERISTICS display."
                ::= { basicSerialPortEntry 12 }
            
            basicSerialPortSignalCheck OBJECT-TYPE
                SYNTAX INTEGER { disabled(1), enabled(2) }
                ACCESS read-write
                STATUS mandatory
                DESCRIPTION
                    "Control for observing DSR and DCD to bound allowing 
                    sessions.  Corresponds directly to PORT SIGNAL CHECK 
                    and the presence of the label 'Signal Check' 
                    following the label 'Enabled Characteristics:' in 
                    the PORT CHARACTERISTICS display."
                ::= { basicSerialPortEntry 13 }
            
            basicSerialPortDSRLogout OBJECT-TYPE
                SYNTAX INTEGER { disabled(1), enabled(2) }
                ACCESS read-write
                STATUS mandatory
                DESCRIPTION
                    "Control for logging out the port when DCD is 
                    deasserted.  Corresponds directly to PORT DSRLOGOUT 
                    and the presence of the label 'DSRlogout' following 
                    the label 'Enabled Characteristics:' in the PORT 
                    CHARACTERISTICS display."
                ::= { basicSerialPortEntry 14 }
            
            basicSerialPortDSRObserve OBJECT-TYPE
                SYNTAX INTEGER { disabled(1), enabled(2) }
                ACCESS read-write
                STATUS mandatory
                DESCRIPTION
                    "Control for beginning the login sequence on the 
                    port when DCD is asserted.  Corresponds directly to 
                    PORT DSRWAIT and the presence of the label 'DSRwait' 
                    following the label 'Enabled Characteristics:' in 
                    the PORT CHARACTERISTICS display."
                ::= { basicSerialPortEntry 15 }
            
            basicSerialPortDCDTimeout OBJECT-TYPE
                SYNTAX INTEGER (0..10000)
                ACCESS read-write
                STATUS mandatory

            
            

            
            
            
            
                DESCRIPTION
                    "The number of milleseconds that DCD may be asserted 
                    before disconnecting the port.  Corresponds directly 
                    to PORT DCD TIMEOUT and the value labeled 'DCD 
                    Timeout:' in the PORT ALTERNATE CHARACTERISTICS 
                    display."
                ::= { basicSerialPortEntry 16 }
            
            basicSerialPortDTRAssert OBJECT-TYPE
                SYNTAX INTEGER { always(1), onConnectionOrRing(2),
                                 onConnection(3), onRing(4) }
                ACCESS read-write
                STATUS mandatory
                DESCRIPTION
                    "Control when the system asserts DTR on the port.
            
                    always               unconditional(DISABLED)
                    onConnectionOrRing   connection formed or RING
                                         asserted(ENABLED)
                    onConnection         connection formed
                                         (FORCONNECTION)
                    onRing               RING asserted (FORRING)
            
                    Corresponds directly to PORT DTRWAIT and the value 
                    labeled 'DTR Wait:' in the PORT ALTERNATE 
                    CHARACTERISTICS display."
                ::= { basicSerialPortEntry 17 }
            
            basicSerialPortLimitedCommands OBJECT-TYPE
                SYNTAX INTEGER { disabled(1), enabled(2) }
                ACCESS read-write
                STATUS mandatory
                DESCRIPTION
                    "Control for limiting the commands available to the 
                    user on the port.  Corresponds directly to PORT 
                    SECURITY and the presence of the label 'Security' 
                    following the label 'Enabled Characteristics:' in 
                    the PORT CHARACTERISTICS display."
                ::= { basicSerialPortEntry 18 }
            
            basicSerialPortLimitedView OBJECT-TYPE
                SYNTAX INTEGER { disabled(1), enabled(2) }
                ACCESS read-write
                STATUS mandatory
                DESCRIPTION
                    "Control for restricting what a user may display.  

            
            

            
            
            
            
                            Corresponds directly to PORT LIMITED VIEW and the 
                    presence of the label 'Limited View' following the 
                    label 'Enabled Characteristics:' in the PORT 
                    CHARACTERISTICS display."
                ::= { basicSerialPortEntry 19 }
            
            basicSerialPortPassword OBJECT-TYPE
                SYNTAX INTEGER { disabled(1), enabled(2) }
                ACCESS read-write
                STATUS mandatory
                DESCRIPTION
                    "Control for requiring the user to supply the login 
                    password to log in on the port.  Corresponds 
                    directly to PORT PASSWORD and the presence of the 
                    label 'Password' following the label 'Enabled 
                    Characteristics:' in the PORT CHARACTERISTICS 
                    display."
                ::= { basicSerialPortEntry 20 }
            
            basicSerialPortLineEditor OBJECT-TYPE
                SYNTAX INTEGER { disabled(1), enabled(2) }
                ACCESS read-write
                STATUS mandatory
                DESCRIPTION
                    "Control for allowing the user to use local mode 
                    command line editing.  Corresponds directly to PORT 
                    LINE EDITOR and the presence of the label 'Line 
                    Editor' following the label 'Enabled 
                    Characteristics:' in the PORT CHARACTERISTICS 
                    display."
                ::= { basicSerialPortEntry 21 }
            
            -- Note that the values for the switching and 
            -- line editing characters are mutally exclusive
            
            basicSerialPortLineEditorBackspace OBJECT-TYPE
                SYNTAX INTEGER (0..255)
                ACCESS read-write
                STATUS mandatory
                DESCRIPTION
                    "Character input from the character port to move the 
                    cursor to the left.  The value 0 indicates no 
                    character has this effect.  Corresponds directly to 
                    PORT LINE EDITOR BACKSPACE and the value labeled 
                    'Backspace Character:' in the PORT ALTERNATE 
                    CHARACTERISTICS display."

            
            

            
            
            
            
                ::= { basicSerialPortEntry 22 }
            
            basicSerialPortLineEditorBeginning OBJECT-TYPE
                SYNTAX INTEGER (0..255)
                ACCESS read-write
                STATUS mandatory
                DESCRIPTION
                    "Character input from the character port to move the 
                    cursor to the beginning of the line.  The value 0 
                    indicates no character has this effect.  Corresponds 
                    directly to PORT LINE EDITOR BEGINNING and the value 
                    labeled 'Begin Line Character:' in the PORT 
                    ALTERNATE CHARACTERISTICS display."
                ::= { basicSerialPortEntry 23 }
            
            basicSerialPortLineEditorCancel OBJECT-TYPE
                SYNTAX INTEGER (0..255)
                ACCESS read-write
                STATUS mandatory
                DESCRIPTION
                    "Character input from the character port to cancel 
                    an interactive dialog or delete the current line.  
                    The value 0 indicates no character has this effect.  
                    Corresponds directly to PORT LINE EDITOR CANCEL and 
                    the value labeled 'Cancel Character:' in the PORT 
                    ALTERNATE CHARACTERISTICS display."
                ::= { basicSerialPortEntry 24 }
            
            basicSerialPortLineEditorDeleteBeginning OBJECT-TYPE
                SYNTAX INTEGER (0..255)
                ACCESS read-write
                STATUS mandatory
                DESCRIPTION
                    "Character input from the character port to delete 
                    the current line from the cursor to the beginning.  
                    The value 0 indicates no character has this effect.  
                    Corresponds directly to PORT LINE EDITOR DELETE 
                    BEGINNING and the value labeled 'Delete Begin 
                    Character:' in the PORT ALTERNATE CHARACTERISTICS 
                    display."
                ::= { basicSerialPortEntry 25 }
            
            basicSerialPortLineEditorDeleteLine OBJECT-TYPE
                SYNTAX INTEGER (0..255)
                ACCESS read-write
                STATUS mandatory

            
            

            
            
            
            
                DESCRIPTION
                    "Character input from the character port to delete 
                    the current line.  The value 0 indicates no 
                    character has this effect.  Corresponds directly to 
                    PORT LINE EDITOR DELETE LINE and the value labeled 
                    'Delete Line Character:' in the PORT ALTERNATE 
                    CHARACTERISTICS display."
                ::= { basicSerialPortEntry 26 }
            
            basicSerialPortLineEditorEnd OBJECT-TYPE
                SYNTAX INTEGER (0..255)
                ACCESS read-write
                STATUS mandatory
                DESCRIPTION
                    "Character input from the character port to move the 
                    cursor to the end of the line.  The value 0 
                    indicates no character has this effect.  Corresponds 
                    directly to PORT LINE EDITOR END and the value 
                    labeled 'End of Line Character:' in the PORT 
                    ALTERNATE CHARACTERISTICS display."
                ::= { basicSerialPortEntry 27 }
            
            basicSerialPortLineEditorForward OBJECT-TYPE
                SYNTAX INTEGER (0..255)
                ACCESS read-write
                STATUS mandatory
                DESCRIPTION
                    "Character input from the character port to move the 
                    cursor to the right.  The value 0 indicates no 
                    character has this effect.  Corresponds directly to 
                    PORT LINE EDITOR FORWARDS and the value labeled 
                    'Forwards Character:' in the PORT ALTERNATE 
                    CHARACTERISTICS display."
                ::= { basicSerialPortEntry 28 }
            
            basicSerialPortLineEditorInsertToggle OBJECT-TYPE
                SYNTAX INTEGER (0..255)
                ACCESS read-write
                STATUS mandatory
                DESCRIPTION
                    "Character input from the character port to toggle 
                    between insert and overwrite modes.  The value 0 
                    indicates no character has this effect.  Corresponds 
                    directly to PORT LINE EDITOR INSERT TOGGLE and the 
                    value labeled 'Insert Character:' in the PORT 
                    ALTERNATE CHARACTERISTICS display."

            
            

            
            
            
            
                ::= { basicSerialPortEntry 29 }
            
            basicSerialPortLineEditorNextLine OBJECT-TYPE
                SYNTAX INTEGER (0..255)
                ACCESS read-write
                STATUS mandatory
                DESCRIPTION
                    "Character input from the character port to recall 
                    the next, newer line in the command history.  The 
                    value -1 indicates no character has this effect.  
                    Corresponds directly to PORT LINE EDITOR NEXT LINE 
                    and the value labeled 'Next Line Character:' in the 
                    PORT ALTERNATE CHARACTERISTICS display."
                ::= { basicSerialPortEntry 30 }
            
            basicSerialPortLineEditorPreviousLine OBJECT-TYPE
                SYNTAX INTEGER (0..255)
                ACCESS read-write
                STATUS mandatory
                DESCRIPTION
                    "Character input from the character port to recall 
                    the previous, older line in the command history.  
                    The value 0 indicates no character has this effect.  
                    Corresponds directly to PORT LINE EDITOR PREVIOUS 
                    LINE and the value labeled 'Previous Line 
                    Character:' in the PORT ALTERNATE CHARACTERISTICS 
                    display."
                ::= { basicSerialPortEntry 31 }
            
            basicSerialPortLineEditorQuotingCharacter OBJECT-TYPE
                SYNTAX INTEGER (0..255)
                ACCESS read-write
                STATUS mandatory
                DESCRIPTION
                    "Character input from the character port to inhibit 
                    interpretation of the next input character.  The 
                    value 0 indicates no character has this effect.  
                    Corresponds directly to PORT LINE EDITOR QUOTING 
                    CHARACTER and the value labeled 'Quoting Character:' 
                    in the PORT ALTERNATE CHARACTERISTICS display."
                ::= { basicSerialPortEntry 32 }
            
            basicSerialPortLineEditorRedisplay OBJECT-TYPE
                SYNTAX INTEGER (0..255)
                ACCESS read-write
                STATUS mandatory

            
            

            
            
            
            
                DESCRIPTION
                    "Character input from the character port to 
                    redisplay the current command line.  The value 0 
                    indicates no character has this effect.  Corresponds 
                    directly to PORT LINE EDITOR REDISPLAY CHARACTER and 
                    the value labeled 'Redisplay Character:' in the PORT 
                    ALTERNATE CHARACTERISTICS display."
                ::= { basicSerialPortEntry 33 }






































            
            

            
            
            
            
            -- the Basic group continued
            
            basicConsoleLogoutDisconnect OBJECT-TYPE
                SYNTAX INTEGER { disabled(1), enabled(2) }
                ACCESS read-write
                STATUS mandatory
                DESCRIPTION
                    "Control for automatic session disconnection when a 
                    console port user logs out.  Corresponds directly to 
                    SERVER CONSOLE LOGOUT and the presence of the label 
                    'Console Logout' following the label 'Enabled 
                    Characteristics:' in the SERVER CHARACTERISTICS 
                    display."
                ::= { basic 19 }
































            
            

            
            
            
            
            -- the Queue group
            
            -- Implementation of this group is mandatory for all Xyplex
            -- systems that implement port queueing
            
            queueLimit OBJECT-TYPE
                SYNTAX INTEGER (-1..100)
                ACCESS read-write
                STATUS mandatory
                DESCRIPTION
                    "The maximum number of entries that can be made in 
                    the Queue table.  The value -1 indicates the imit is 
                    available memory.  Corresponds directly to SERVER 
                    QUEUE LIMIT and the value labeled 'Queue Limit:' in 
                    the SERVER CHARACTERISTICS display."
                ::= { queue 1 }
            
            queueHigh OBJECT-TYPE
                SYNTAX Gauge
                ACCESS read-only
                STATUS mandatory
                DESCRIPTION
                    "The highest value of queueNumber since system 
                    initialization.  Corresponds directly to the value 
                    labeled 'Queue Entries' and 'High' in the SERVER 
                    STATUS display."
                ::= { queue 2 }
            
            queueNumber OBJECT-TYPE
                SYNTAX Gauge
                ACCESS read-only
                STATUS mandatory
                DESCRIPTION
                    "The number of entries in the Queue table.  
                    Corresponds directly to the value labeled 'Queue 
                    Entries' and 'Cur' in the SERVER STATUS display."
                ::= { queue 3 }









            
            

            
            
            
            
            -- The Queue table
            
            queueTable OBJECT-TYPE
                SYNTAX SEQUENCE OF QueueEntry
                ACCESS not-accessible
                STATUS mandatory
                DESCRIPTION
                    "A list of queue entries."
                ::= { queue 4 }
            
            queueEntry OBJECT-TYPE
                SYNTAX QueueEntry
                ACCESS not-accessible
                STATUS mandatory
                DESCRIPTION
                    "Parameter values for a queue entry."
                INDEX { queueJob }
                ::= { queueTable 1 }
            
            QueueEntry ::=
                SEQUENCE {
                    queueJob
                        INTEGER,
                    queueStatus
                        INTEGER,
                    queueSourceName
                        DisplayString,
                    queueServiceName
                        DisplayString,
                    queueServicePortIndex
                        INTEGER,
                    queueServicePortName
                        DisplayString
                }
            
            queueJob OBJECT-TYPE
                SYNTAX INTEGER
                ACCESS read-only
                STATUS mandatory
                DESCRIPTION
                    "The job number of a queued request.  Corresponds 
                    directly to the value labeled 'Entry' in the QUEUE 
                    display."
                ::= { queueEntry 1 }
            
            queueStatus OBJECT-TYPE

            
            

            
            
            
            
                SYNTAX INTEGER { invalid(1), valid(2) }
                ACCESS read-write
                STATUS mandatory
                DESCRIPTION
                    "The status of a queue entry.  Set to 'invalid' to 
                    remove the entry, which corresponds directly to the 
                    REMOVE QUEUE ENTRY command.  Actual removal of the 
                    entry is implementation specific."
                ::= { queueEntry 2 }
            
            queueSourceName OBJECT-TYPE
                SYNTAX DisplayString (SIZE (0..50))
                ACCESS read-only
                STATUS mandatory
                DESCRIPTION
                    "The name of the system that originated the queue 
                    entry.  Corresponds directly to the value labeled 
                    'Source Node' in the QUEUE display."
                ::= { queueEntry 3 }
            
            queueServiceName OBJECT-TYPE
                SYNTAX DisplayString (SIZE (0..16))
                ACCESS read-only
                STATUS mandatory
                DESCRIPTION
                    "The name of the service for which the originator is 
                    waiting.  Corresponds directly to the value labeled 
                    'Service' in the QUEUE display."
                ::= { queueEntry 4 }
            
            queueServicePortIndex OBJECT-TYPE
                SYNTAX INTEGER
                ACCESS read-only
                STATUS mandatory
                DESCRIPTION
                    "The charPortIndex of the port for which the 
                    originator is waiting, if supplied by the 
                    originator.  As defined in the Character MIB [12].  
                    Corresponds indirectly to the port number part of 
                    the value labeled 'Port Name' in the QUEUE 
                    display."
                ::= { queueEntry 5 }
            
            queueServicePortName OBJECT-TYPE
                SYNTAX DisplayString (SIZE (0..16))
                ACCESS read-only

            
            

            
            
            
            
                STATUS mandatory
                DESCRIPTION
                    "The name of the port for which the originator is 
                    waiting, if supplied by the originator.  Corresponds 
                    directly to the port name part of the value labeled 
                    'Port Name' in the SERVER QUEUE display."
                ::= { queueEntry 6 }







































            
            

            
            
            
            
            -- the Queue Port table
            
            queuePortTable OBJECT-TYPE
                SYNTAX SEQUENCE OF QueuePortEntry
                ACCESS not-accessible
                STATUS mandatory
                DESCRIPTION
                    "A list of queuing-related character port entries."
                ::= { queue 5 }
            
            queuePortEntry OBJECT-TYPE
                SYNTAX QueuePortEntry
                ACCESS not-accessible
                STATUS mandatory
                DESCRIPTION
                    "Queuing parameter values for a port."
                INDEX { queuePortIndex }
                ::= { queuePortTable 1 }
            
            QueuePortEntry ::=
                SEQUENCE {
                    queuePortIndex
                        INTEGER,
                    queuePortQueuing
                        INTEGER
                }
            
            queuePortIndex OBJECT-TYPE
                SYNTAX INTEGER
                ACCESS read-only
                STATUS mandatory
                DESCRIPTION
                    "An index value that uniquely identifies a port.  
                    The port identified by a particular value of this 
                    index is the same port as identified by 
                    charPortIndex in the Character MIB [12]."
                ::= { queuePortEntry 1 }
            
            queuePortQueuing OBJECT-TYPE
                SYNTAX INTEGER { disabled(1), enabled(2) }
                ACCESS read-write
                STATUS mandatory
                DESCRIPTION
                    "Control for allowing queued requests for using the 
                    port.  Corresponds directly to PORT QUEUING and the 
                    presence of the label 'Queuing' following the label 

            
            

            
            
            
            
                            'Enabled Characteristics:' in the PORT 
                    CHARACTERISTICS display."
                ::= { queuePortEntry 2 }











































            
            

            
            
            
            
            -- the Menu group
            
            -- Implementation of this group is mandatory for all Xyplex
            -- systems that implement user menus
            
            menuNumber OBJECT-TYPE
                SYNTAX Gauge
                ACCESS read-only
                STATUS mandatory
                DESCRIPTION
                    "The number of entries in the Menu table.  
                    Corresponds indirectly to SERVER MENU display."
                ::= { menu 1 }
            
            menuContinuePrompt OBJECT-TYPE
                SYNTAX DisplayString (SIZE (0..50))
                ACCESS read-write
                STATUS mandatory
                DESCRIPTION
                    "The text to use when prompting a menu user to press 
                    RETURN to continue. Corresponds directly to SERVER 
                    MENU CONTINUE PROMPT and the value labeled 'Menu 
                    Continue Prompt:' in the SERVER MENU display."
                ::= { menu 2 }
            
            menuSelectionPrompt OBJECT-TYPE
                SYNTAX DisplayString (SIZE (0..50))
                ACCESS read-write
                STATUS mandatory
                DESCRIPTION
                    "The text to use when prompting a menu user for a 
                    menu selection. Corresponds directly to SERVER MENU 
                    PROMPT and the value labeled 'Menu Prompt:' in the 
                    SERVER MENU display."
                ::= { menu 3 }











            
            

            
            
            
            
            -- The Menu table
            
            menuTable OBJECT-TYPE
                SYNTAX SEQUENCE OF MenuEntry
                ACCESS not-accessible
                STATUS mandatory
                DESCRIPTION
                    "A list of menu entries."
                ::= { menu 4 }
            
            menuEntry OBJECT-TYPE
                SYNTAX MenuEntry
                ACCESS not-accessible
                STATUS mandatory
                DESCRIPTION
                    "Parameter values for a menu entry."
                INDEX { menuIndex }
                ::= { menuTable 1 }
            
            MenuEntry ::=
                SEQUENCE {
                    menuIndex
                        INTEGER,
                    menuStatus
                        INTEGER,
                    menuText
                        DisplayString,
                    menuCommand
                        DisplayString
                }
            
            menuIndex OBJECT-TYPE
                SYNTAX INTEGER
                ACCESS read-only
                STATUS mandatory
                DESCRIPTION
                    "The index number of a menu entry.  Corresponds 
                    directly to the numbers down the left of the SERVER 
                    MENU display."
                ::= { menuEntry 1 }
            
            menuStatus OBJECT-TYPE
                SYNTAX INTEGER { invalid(1), valid(2) }
                ACCESS read-write
                STATUS mandatory
                DESCRIPTION

            
            

            
            
            
            
                    "The status of a the entry.  Set to 'invalid' to
                    remove the entry, which corresponds directly to the 
                    CLEAR SERVER MENU command.  Actual removal of the 
                    entry is implementation specific."
                DEFVAL { valid }
                ::= { menuEntry 2 }
            
            menuText OBJECT-TYPE
                SYNTAX DisplayString (SIZE (0..30))
                ACCESS read-only
                STATUS mandatory
                DESCRIPTION
                    "The text to be displayed in the menu.  Corresponds 
                    directly to the line next to the entry number in the 
                    SERVER MENU display."
                ::= { menuEntry 3 }
            
            menuCommand OBJECT-TYPE
                SYNTAX DisplayString (SIZE (0..64))
                ACCESS read-only
                STATUS mandatory
                DESCRIPTION
                    "The commands to execute when the user chooses the 
                    menu entry.  Corresponds directly second line 
                    following the entry number in the SERVER MENU 
                    display."
                ::= { menuEntry 4 }



















            
            

            
            
            
            
            -- the Menu Port table
            
            menuPortTable OBJECT-TYPE
                SYNTAX SEQUENCE OF MenuPortEntry
                ACCESS not-accessible
                STATUS mandatory
                DESCRIPTION
                    "A list of menu-related character port entries."
                ::= { menu 5 }
            
            menuPortEntry OBJECT-TYPE
                SYNTAX MenuPortEntry
                ACCESS not-accessible
                STATUS mandatory
                DESCRIPTION
                    "Menu parameter values for a port."
                INDEX { menuPortIndex }
                ::= { menuPortTable 1 }
            
            MenuPortEntry ::=
                SEQUENCE {
                    menuPortIndex
                        INTEGER,
                    menuPortMenuStatus
                        INTEGER
                }
            
            menuPortIndex OBJECT-TYPE
                SYNTAX INTEGER
                ACCESS read-only
                STATUS mandatory
                DESCRIPTION
                    "An index value that uniquely identifies a port.  
                    The port identified by a particular value of this 
                    index is the same port as identified by 
                    charPortIndex in the Character MIB [12]."
                ::= { menuPortEntry 1 }
            
            menuPortMenuStatus OBJECT-TYPE
                SYNTAX INTEGER { disabled(1), enabled(2), privileged(3) }
                ACCESS read-write
                STATUS mandatory
                DESCRIPTION
                    "Control for menu operation on the port.  
                    Corresponds indirectly to PORT MENU and PORT 
                    PRIVILEGED MENU and the presence of the labels 

            
            

            
            
            
            
                            'Menu' and 'Privileged Men' following the label 
                    'Enabled Characteristics:' in the PORT 
                    CHARACTERISTICS display."
                ::= { menuPortEntry 2 }










































            
            

            
            
            
            
            -- the Network Login group
            
            -- Implementation of this group is mandatory for all Xyplex
            -- systems that implement network login
            
            netLoginNumber OBJECT-TYPE
                SYNTAX INTEGER
                ACCESS read-only
                STATUS mandatory
                DESCRIPTION
                    "The number of entries in the Network Login Server 
                    table."
                ::= { netLogin 1 }

































            
            

            
            
            
            
            -- The Network Login Server table
            
            netLoginServerTable OBJECT-TYPE
                SYNTAX SEQUENCE OF NetLoginServerEntry
                ACCESS not-accessible
                STATUS mandatory
                DESCRIPTION
                    "A list of network login server entries."
                ::= { netLogin 2 }
            
            netLoginServerEntry OBJECT-TYPE
                SYNTAX NetLoginServerEntry
                ACCESS not-accessible
                STATUS mandatory
                DESCRIPTION
                    "Network login parameter values for a server 
                    entry."
                INDEX { netLoginServerName }
                ::= { netLoginServerTable 1 }
            
            NetLoginServerEntry ::=
                SEQUENCE {
                    netLoginServerName
                        DisplayString,
                    netLoginServerStatus
                        INTEGER,
                    netLoginServerPath
                        DisplayString
                }
            
            netLoginServerName OBJECT-TYPE
                SYNTAX DisplayString (SIZE (1..50))
                ACCESS read-write
                STATUS mandatory
                DESCRIPTION
                    "The name of a network login server, suitable for 
                    resolution to a network address.  Corresponds 
                    directly to host portion of SERVER SCRIPT SERVER and 
                    the value labeled 'Script Host' in the SERVER 
                    PARAMETER SERVER display."
                ::= { netLoginServerEntry 1 }
            
            netLoginServerStatus OBJECT-TYPE
                SYNTAX INTEGER { invalid(1), valid(2) }
                ACCESS read-write
                STATUS mandatory

            
            

            
            
            
            
                DESCRIPTION
                 "Status of this entry.  Set to 'invalid'to remove the  entry, which 
            corresponds directly to the CLEAR SERVER     SCRIPT SERVER 
            command.  Acutal removal of the entry   is implementation 
            specific."
                DEFVAL { valid }
                ::= { netLoginServerEntry 2 }
            
            netLoginServerPath OBJECT-TYPE
                SYNTAX DisplayString (SIZE (0..40))
                ACCESS read-write
                STATUS mandatory
                DESCRIPTION
                    "The full path name to the script file that is 
                    identified by the user name.  Corresponds directly 
                    to path portion of SERVER SCRIPT SERVER and the 
                    value labeled 'Script Path' in the SERVER PARAMETER 
                    SERVER display."
                ::= { netLoginServerEntry 3 }



























            
            

            
            
            
            
            -- the Network Login Port table
            
            netLoginPortTable OBJECT-TYPE
                SYNTAX SEQUENCE OF NetLoginPortEntry
                ACCESS not-accessible
                STATUS mandatory
                DESCRIPTION
                    "A list of network login character port entries."
                ::= { netLogin 3 }
            
            netLoginPortEntry OBJECT-TYPE
                SYNTAX NetLoginPortEntry
                ACCESS not-accessible
                STATUS mandatory
                DESCRIPTION
                    "Network login parameter values for a port."
                INDEX { netLoginPortIndex }
                ::= { netLoginPortTable 1 }
            
            NetLoginPortEntry ::=
                SEQUENCE {
                    netLoginPortIndex
                        INTEGER,
                    netLoginPortScriptUse
                        INTEGER,
                    netLoginPortScriptEcho
                        INTEGER,
                    netLoginPortLoaderAddressType
                        INTEGER,
                    netLoginPortLoaderAddress
                        OCTET STRING,
                    netLoginPortLoaderFile
                        DisplayString
                }
            
            netLoginPortIndex OBJECT-TYPE
                SYNTAX INTEGER
                ACCESS read-only
                STATUS mandatory
                DESCRIPTION
                    "An index value that uniquely identifies a port.  
                    The port identified by a particular value of this 
                    index is the same port as identified by 
                    charPortIndex in the Character MIB [12]."
                ::= { netLoginPortEntry 1 }
            

            
            

            
            
            
            
            netLoginPortScriptUse OBJECT-TYPE
                SYNTAX INTEGER { disabled(1), enabled(2), required(3) }
                ACCESS read-write
                STATUS mandatory
                DESCRIPTION
                    "Control for the script action taken when a user 
                    logs in on the port.  Corresponds directly to PORT 
                    SCRIPT LOGIN and the value labeled 'Script Login:' 
                    in the PORT ALTERNATE CHARACTERISTICS display."
                ::= { netLoginPortEntry 2 }
            
            netLoginPortScriptEcho OBJECT-TYPE
                SYNTAX INTEGER { disabled(1), enabled(2) }
                ACCESS read-write
                STATUS mandatory
                DESCRIPTION
                    "Control for display of script operation on the port 
                    when running a script.  Corresponds directly to PORT 
                    SCRIPT ECHO and the presence of the label 'Script 
                    Echo' following the label 'Enabled Characteristics:' 
                    in the PORT CHARACTERISTICS display."
                ::= { netLoginPortEntry 3 }
            
            netLoginPortLoaderAddressType OBJECT-TYPE
                SYNTAX AddressType
                ACCESS read-only
                STATUS mandatory
                DESCRIPTION
                    "The type of network address contained in 
                    netLoginPortLoaderAddress.  'unknown' means no 
                    address has been defined.  'other' means no other 
                    type value applies.  'ip' is an Internet IP address.  
                    'ethernet' is an 802.3 MAC address.  Corresponds 
                    indirectly to the address part of the value labeled 
                    'Script Loaded From:' in the PORT STATUS display."
                ::= { netLoginPortEntry 4 }
            
            netLoginPortLoaderAddress OBJECT-TYPE
                SYNTAX OCTET STRING
                ACCESS read-only
                STATUS mandatory
                DESCRIPTION
                    "The network address of the server that provided the 
                    script for the current port login.  Corresponds 
                    directly the address part of the value labeled 
                    'Script Loaded From:' in the PORT STATUS display."

            
            

            
            
            
            
                ::= { netLoginPortEntry 5 }
            
            netLoginPortLoaderFile OBJECT-TYPE
                SYNTAX DisplayString
                ACCESS read-only
                STATUS mandatory
                DESCRIPTION
                    "The path and file name of the script used for the 
                    current port login.  Corresponds directly the file 
                    name  part of the value labeled 'Script Loaded 
                    From:' in the PORT STATUS display."
                ::= { netLoginPortEntry 6 }


































            
            

            
            
            
            
            -- the Dial group
            
            -- Implementation of this group is mandatory for all Xyplex
            -- systems that implement automatic dialing
            
            dialPortTable OBJECT-TYPE
                SYNTAX SEQUENCE OF DialPortEntry
                ACCESS not-accessible
                STATUS mandatory
                DESCRIPTION
                    "A list of dial character port entries."
                ::= { dial 1 }
            
            dialPortEntry OBJECT-TYPE
                SYNTAX DialPortEntry
                ACCESS not-accessible
                STATUS mandatory
                DESCRIPTION
                    "Dial parameter values for a port."
                INDEX { dialPortIndex }
                ::= { dialPortTable 1 }
            
            DialPortEntry ::=
                SEQUENCE {
                    dialPortIndex
                        INTEGER,
                    dialPortDialback
                        INTEGER,
                    dialPortDialbackTimeout
                        INTEGER
                }
            
            dialPortIndex OBJECT-TYPE
                SYNTAX INTEGER
                ACCESS read-only
                STATUS mandatory
                DESCRIPTION
                    "An index value that uniquely identifies a port.  
                    The port identified by a particular value of this 
                    index is the same port as identified by 
                    charPortIndex in the Character MIB [12]."
                ::= { dialPortEntry 1 }
            
            dialPortDialback OBJECT-TYPE
                SYNTAX INTEGER { disabled(1), enabled(2) }
                ACCESS read-write

            
            

            
            
            
            
                STATUS mandatory
                DESCRIPTION
                    "Control for use of dialback when a user logs in on 
                    the port.  Corresponds directly to PORT DIALBACK and 
                    the presence of the label 'Dialback' following the 
                    label 'Enabled Characteristics:' in the PORT 
                    CHARACTERISTICS display."
                ::= { dialPortEntry 2 }
            
            dialPortDialbackTimeout OBJECT-TYPE
                SYNTAX INTEGER (5..60)
                ACCESS read-write
                STATUS mandatory
                DESCRIPTION
                    "The number of seconds to wait for remote modem 
                    response when dialing back.  Corresponds directly to 
                    PORT DIALBACK TIMEOUT and the value labeled 
                    'Dialback Timeout:' in the PORT ALTERNATE 
                    CHARACTERISTICS display."
                ::= { dialPortEntry 3 }


























            
            

            
            
            
            
            -- the Session Log group
            
            -- Implementation of this group is mandatory for all Xyplex
            -- systems that implement logging session information
            
            sessionLogLimit OBJECT-TYPE
                SYNTAX INTEGER (0..1000)
                ACCESS read-write
                STATUS mandatory
                DESCRIPTION
                    "The maximum number of entries allowed in the 
                    Session Log table.  Corresponds directly to SERVER 
                    ACCOUNTING ENTRIES and the value labeled 'Accounting 
                    Entries:' in the SERVER CHARACTERISTICS display."
                ::= { sessionLog 1 }
            






























            
            

            
            
            
            
            -- The Session Log table
            
            sessionLogTable OBJECT-TYPE
                SYNTAX SEQUENCE OF SessionLogEntry
                ACCESS not-accessible
                STATUS mandatory
                DESCRIPTION
                    "A list of session log entries."
                ::= { sessionLog 2 }
            
            sessionLogEntry OBJECT-TYPE
                SYNTAX SessionLogEntry
                ACCESS not-accessible
                STATUS mandatory
                DESCRIPTION
                    "Parameter values for a session log entry."
                INDEX { sessionLogIndex }
                ::= { sessionLogTable 1 }
            
            SessionLogEntry ::=
                SEQUENCE {
                    sessionLogIndex
                        INTEGER,
                    sessionLogConnectionID
                        INTEGER,
                    sessionLogPort
                        INTEGER,
                    sessionLogEvent
                        INTEGER,
                    sessionLogEventDetail
                        INTEGER,
                    sessionLogUserName
                        DisplayString,
                    sessionLogRemoteName
                        DisplayString,
                    sessionLogConnectTime
                        DateTime,
                    sessionLogDisconnectTime
                        DateTime,
                    sessionLogInCharacters
                        Counter,
                    sessionLogOutCharacters
                        Counter
                }
            
            sessionLogIndex OBJECT-TYPE

            
            

            
            
            
            
                SYNTAX INTEGER
                ACCESS read-only
                STATUS mandatory
                DESCRIPTION
                    "The index number of a session log entry.  
                    Corresponds directly to the order of the displayed 
                    records in the SERVER ACCOUNTING display.  The 
                    maximum value is sessionLogLimit."
                ::= { sessionLogEntry 1 }
            
            sessionLogConnectionID OBJECT-TYPE
                SYNTAX INTEGER (1..65535)
                ACCESS read-only
                STATUS mandatory
                DESCRIPTION
                    "An indentifying number for records relating to the 
                    same connection, that is, the connect and disconnect 
                    records, either of which can be missing.  
                    Corresponds directly to value labeled 'Entry' the 
                    SERVER ACCOUNTING display."
                ::= { sessionLogEntry 2 }
            
            sessionLogPort OBJECT-TYPE
                SYNTAX INTEGER
                ACCESS read-only
                STATUS mandatory
                DESCRIPTION
                    "An index value that uniquely identifies the port 
                    where the event took place.  The port identified by 
                    a particular value of this index is the same port as 
                    identified by charPortIndex in the Character MIB 
                    [12].  Corresponds directly to the value labeled 
                    'Port' in the SERVER ACCOUNTING display."
                ::= { sessionLogEntry 3 }
            
            sessionLogEvent OBJECT-TYPE
                SYNTAX INTEGER { login(1), connectLocal(2),
                                 connectRemote(3), disconnect(4) }
                ACCESS read-only
                STATUS mandatory
                DESCRIPTION
                    "The type of event.  Corresponds directly to the 
                    alphabetic part of the value labeled 'Type' in the 
                    SERVER ACCOUNTING display."
                ::= { sessionLogEntry 4 }
            

            
            

            
            
            
            
            sessionLogEventDetail OBJECT-TYPE
                SYNTAX INTEGER { none(1), protocolBadCircuit(2),
                                 protocolBadCredits(3),
                                 protocolBadStartOrRun(4),
                                 protocolBadRange(5),
                                 duplicateQueueID(6), noUsers(7),
                                 noServiceResourced(8),
                                 serviceUserDisconnect(9),
                                 serviceUnavailable(10),
                                 serverUserDisconnect(11),
                                 noNodeResources(12),
                                 systemShutdown(13),
                                 nodeUserdisconnect(14),
                                 badCircuitTimer(15),
                                 badServiceClass(16),
                                 badMessageOrSlot(17),
                                 timeout(18), noProgress(19),
                                 serviceNotOnPort(20), noSuchPort(21),
                                 badPassword(22), serviceBusy(23),
                                 noSuchService(24), 
            serviceDisabled(25),
                                 notInQueue(26), noImmeditatAccess(27),
                                 accessDenied(28),
                                 protocolBadSolicit(29),
                                 protocolBadReasonCode(30),
                                 unsupportedTest(31),
                                 domainTooLong(32),
                                 noSuchNode(33),
                                 noSuchServiceOnNode(34),
                                 rejectService(35),
                                 internetConnectDisabled(36) }
                ACCESS read-only
                STATUS mandatory
                DESCRIPTION
                    "The detailed reason for the event.  Corresponds 
                    directly to the numeric part of the value labeled 
                    'Type' in the SERVER ACCOUNTING display."
                ::= { sessionLogEntry 5 }
            
            sessionLogUserName OBJECT-TYPE
                SYNTAX DisplayString (SIZE (0..16))
                ACCESS read-only
                STATUS mandatory
                DESCRIPTION
                    "The user name logged in on the port when the event 
                    occurred.  Corresponds directly to the value labeled 

            
            

            
            
            
            
                            'Username' in the SERVER ACCOUNTING display."
                ::= { sessionLogEntry 6 }
            
            sessionLogRemoteName OBJECT-TYPE
                SYNTAX DisplayString (SIZE (0..16))
                ACCESS read-only
                STATUS mandatory
                DESCRIPTION
                    "The name of the session remote partner.  
                    Corresponds directly to the value labeled 
                    'Destination' in the SERVER ACCOUNTING display."
                ::= { sessionLogEntry 7 }
            
            sessionLogConnectTime OBJECT-TYPE
                SYNTAX DateTime
                ACCESS read-only
                STATUS mandatory
                DESCRIPTION
                    "The date and time that session connection occurred.  
                    Corresponds directly to the value labeled 'Connect 
                    Time' in the SERVER ACCOUNTING display."
                ::= { sessionLogEntry 8 }
            
            sessionLogDisconnectTime OBJECT-TYPE
                SYNTAX DateTime
                ACCESS read-only
                STATUS mandatory
                DESCRIPTION
                    "The date and time that session disconnection 
                    occurred.  Corresponds directly to the value labeled 
                    'Disconnect Time' in the SERVER ACCOUNTING 
                    display."
                ::= { sessionLogEntry 9 }
            
            sessionLogInCharacters OBJECT-TYPE
                SYNTAX Counter
                ACCESS read-only
                STATUS mandatory
                DESCRIPTION
                    "The number of characters that came into the port 
                    for the session.  Corresponds directly to the value 
                    labeled 'Bytes In' in the SERVER ACCOUNTING 
                    display."
                ::= { sessionLogEntry 10 }
            
            sessionLogOutCharacters OBJECT-TYPE

            
            

            
            
            
            
                SYNTAX Counter
                ACCESS read-only
                STATUS mandatory
                DESCRIPTION
                    "The number of characters that went out of the port 
                    for the session.  Corresponds directly to the value 
                    labeled 'Bytes Out' in the SERVER ACCOUNTING 
                    display."
                ::= { sessionLogEntry 11 }
            
END
