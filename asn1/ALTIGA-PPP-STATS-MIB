-- *------------------------------------------------------------------
-- * ALTIGA-PPP-STATS-MIB.my:  Altiga PPP Statistics MIB.
-- *
-- * Altiga Networks was acquired by Cisco Systems on March 29, 2000
-- *
-- * Copyright (c) 2002 by Cisco Systems, Inc.
-- * All rights reserved.
-- *
-- *------------------------------------------------------------------

ALTIGA-PPP-STATS-MIB DEFINITIONS ::= BEGIN

   IMPORTS
      MODULE-IDENTITY, OBJECT-TYPE, Counter32, Integer32
         FROM SNMPv2-SMI
      TruthValue, RowStatus
         FROM SNMPv2-TC
      OBJECT-GROUP, MODULE-COMPLIANCE
         FROM SNMPv2-CONF
      alStatsPpp, alPppGroup
         FROM ALTIGA-MIB
      alPppMibModule
         FROM ALTIGA-GLOBAL-REG;

   altigaPppStatsMibModule MODULE-IDENTITY
      LAST-UPDATED   "200209051300Z"
      ORGANIZATION   "Cisco Systems, Inc."
      CONTACT-INFO
         "Cisco Systems
          170 W Tasman Drive
          San Jose, CA  95134
          USA

          Tel: +1 800 553-NETS
          E-mail: cs-cvpn3000@cisco.com"

      DESCRIPTION
         "The Altiga PPP Statistics MIB models counters and objects that are
          of management interest for PPP.
         
          Acronyms
          The following acronyms are used in this document:

            MIB:        Management Information Base

            MPPC:       Microsoft Point-to-Point Compression

            MPPE:       Microsoft Point-to-Point Encryption 

            PPP:        Point-to-Point Protocol

         "

        REVISION "200209051300Z"
        DESCRIPTION
                "Added module compliance and range."

        REVISION "200207100000Z"
        DESCRIPTION
                "Updated with new header"

      ::= { alPppMibModule 2 }

-- +++++++++++++++++++++++++++++++++++++++++++++++++++++++
-- MIB Objects
-- +++++++++++++++++++++++++++++++++++++++++++++++++++++++

alStatsPppGlobal  OBJECT IDENTIFIER ::= { alStatsPpp 1 }

-- Any global stuff here...

alPppStatsTable OBJECT-TYPE
   SYNTAX         SEQUENCE OF AlPppStatsEntry
   MAX-ACCESS     not-accessible
   STATUS         current
   DESCRIPTION
      "List of active PPP links."
   ::= { alStatsPpp 2 }

alPppStatsEntry OBJECT-TYPE
   SYNTAX         AlPppStatsEntry
   MAX-ACCESS     not-accessible
   STATUS         current
   DESCRIPTION
      "An entry in the alPppStatsTable."
   INDEX    { alPppStatsIfIndex }
   ::= { alPppStatsTable 1 }

AlPppStatsEntry ::= SEQUENCE {
   alPppStatsRowStatus            RowStatus,
   alPppStatsIfIndex           Integer32,
   alPppStatsOctetsSent           Counter32,
   alPppStatsOctetsRcvd           Counter32,
   alPppStatsPacketsSent             Counter32,
   alPppStatsPacketsRcvd             Counter32,
   alPppStatsMppcStatus              TruthValue,
   alPppStatsMppeStatus              TruthValue,
   alPppStatsMppcMppeReset           Counter32,
   alPppStatsMppcOctSentAfterComp    Counter32,
   alPppStatsMppcOctSentBeforeComp   Counter32,
   alPppStatsMppcOctSentUnComp       Counter32,
   alPppStatsMppcOctRcvdBeforeDeComp Counter32,
   alPppStatsMppcOctRcvdAfterDeComp  Counter32,
   alPppStatsMppcOctRcvdUnComp       Counter32
}

alPppStatsRowStatus OBJECT-TYPE
   SYNTAX         RowStatus
   MAX-ACCESS     read-write
   STATUS         current
   DESCRIPTION
      "The status of this row. Used to terminate the session."
   ::= { alPppStatsEntry 1 }

alPppStatsIfIndex OBJECT-TYPE
   SYNTAX         Integer32(0..2147483647)
   MAX-ACCESS     read-only
   STATUS         current
   DESCRIPTION
      "The index of this row."
   ::= { alPppStatsEntry 2 }

alPppStatsOctetsSent OBJECT-TYPE
   SYNTAX         Counter32
   MAX-ACCESS     read-only
   STATUS         current
   DESCRIPTION
      "The number of octets sent during this session."
   ::= { alPppStatsEntry 3 }

alPppStatsOctetsRcvd OBJECT-TYPE
   SYNTAX         Counter32
   MAX-ACCESS     read-only
   STATUS         current
   DESCRIPTION
      "The number of octets received during this session."
   ::= { alPppStatsEntry 4 }

alPppStatsPacketsSent OBJECT-TYPE
   SYNTAX         Counter32
   MAX-ACCESS     read-only
   STATUS         current
   DESCRIPTION
      "The number of packets sent during this session."
   ::= { alPppStatsEntry 5 }

alPppStatsPacketsRcvd OBJECT-TYPE
   SYNTAX         Counter32
   MAX-ACCESS     read-only
   STATUS         current
   DESCRIPTION
      "The number of packets received during this session."
   ::= { alPppStatsEntry 6 }

alPppStatsMppcStatus OBJECT-TYPE
   SYNTAX         TruthValue
   MAX-ACCESS     read-only
   STATUS         current
   DESCRIPTION
      "The status of the MPPC setting during this session."
   ::= { alPppStatsEntry 7 }

alPppStatsMppeStatus OBJECT-TYPE
   SYNTAX         TruthValue
   MAX-ACCESS     read-only
   STATUS         current
   DESCRIPTION
      "The status of the MPPE setting during this session."
   ::= { alPppStatsEntry 8 }

alPppStatsMppcMppeReset OBJECT-TYPE
   SYNTAX         Counter32
   MAX-ACCESS     read-only
   STATUS         current
   DESCRIPTION
      "The reset MPPC and MPPE counts for this session."
   ::= { alPppStatsEntry 9 }

alPppStatsMppcOctSentAfterComp OBJECT-TYPE
   SYNTAX         Counter32
   MAX-ACCESS     read-only
   STATUS         current
   DESCRIPTION
      "The number of octets sent after compression during this session."
   ::= { alPppStatsEntry 10 }

alPppStatsMppcOctSentBeforeComp OBJECT-TYPE
   SYNTAX         Counter32
   MAX-ACCESS     read-only
   STATUS         current
   DESCRIPTION
      "The number of octets sent before compression during this session."
   ::= { alPppStatsEntry 11 }

alPppStatsMppcOctSentUnComp OBJECT-TYPE
   SYNTAX         Counter32
   MAX-ACCESS     read-only
   STATUS         current
   DESCRIPTION
      "The number of octets sent uncompressed during this session."
   ::= { alPppStatsEntry 12 }

alPppStatsMppcOctRcvdBeforeDeComp OBJECT-TYPE
   SYNTAX         Counter32
   MAX-ACCESS     read-only
   STATUS         current
   DESCRIPTION
      "The number of octets received before decompression during this session."
   ::= { alPppStatsEntry 13 }

alPppStatsMppcOctRcvdAfterDeComp OBJECT-TYPE
   SYNTAX         Counter32
   MAX-ACCESS     read-only
   STATUS         current
   DESCRIPTION
      "The number of octets received after decompression during this session."
   ::= { alPppStatsEntry 14 }

alPppStatsMppcOctRcvdUnComp OBJECT-TYPE
   SYNTAX         Counter32
   MAX-ACCESS     read-only
   STATUS         current
   DESCRIPTION
      "The number of octets received uncompressed during this session."
   ::= { alPppStatsEntry 15 }

-- More Tunnel stuff here.

alStatsPppMppcGlobal OBJECT IDENTIFIER ::= { alStatsPpp 3 }

alPppStatsGlobMppcMppeResetsRcvd OBJECT-TYPE
   SYNTAX         Counter32
   MAX-ACCESS     read-only
   STATUS         current
   DESCRIPTION
      "Reset the number of octets received."
   ::= { alStatsPppMppcGlobal 1 }

alPppStatsGlobMppcMppeResetsSent OBJECT-TYPE
   SYNTAX         Counter32
   MAX-ACCESS     read-only
   STATUS         current
   DESCRIPTION
      "Reset the number of octets sent."
   ::= { alStatsPppMppcGlobal 2 }

alPppStatsGlobMppcOctSentAfterComp OBJECT-TYPE
   SYNTAX         Counter32
   MAX-ACCESS     read-only
   STATUS         current
   DESCRIPTION
      "Total number of octets sent after compression."
   ::= { alStatsPppMppcGlobal 3 }

alPppStatsGlobMppcOctSentBeforeComp OBJECT-TYPE
   SYNTAX         Counter32
   MAX-ACCESS     read-only
   STATUS         current
   DESCRIPTION
      "Total number of octets sent before compression."
   ::= { alStatsPppMppcGlobal 4 }

alPppStatsGlobMppcOctSentUnComp OBJECT-TYPE
   SYNTAX         Counter32
   MAX-ACCESS     read-only
   STATUS         current
   DESCRIPTION
      "Total number of octets sent uncompressed."
   ::= { alStatsPppMppcGlobal 5 }

alPppStatsGlobMppcOctRcvdBeforeDeComp OBJECT-TYPE
   SYNTAX         Counter32
   MAX-ACCESS     read-only
   STATUS         current
   DESCRIPTION
      "Total number of octets received before decompression."
   ::= { alStatsPppMppcGlobal 6 }

alPppStatsGlobMppcOctRcvdAfterDeComp OBJECT-TYPE
   SYNTAX         Counter32
   MAX-ACCESS     read-only
   STATUS         current
   DESCRIPTION
      "Total number of octets received after decompression."
   ::= { alStatsPppMppcGlobal 7 }

alPppStatsGlobMppcOctRcvdUnComp OBJECT-TYPE
   SYNTAX         Counter32
   MAX-ACCESS     read-only
   STATUS         current
   DESCRIPTION
      "Total number of octets received uncompressed."
   ::= { alStatsPppMppcGlobal 8 }

altigaPppStatsMibConformance OBJECT IDENTIFIER ::= { altigaPppStatsMibModule 1 }
altigaPppStatsMibCompliances OBJECT IDENTIFIER ::= { altigaPppStatsMibConformance 1 }

altigaPppStatsMibCompliance MODULE-COMPLIANCE
   STATUS         current
   DESCRIPTION
      "The compliance statement for agents which 
       implement the Altiga PPP Statistics MIB."
   MODULE
   MANDATORY-GROUPS { 
      altigaPppStatsGroup
   }
   ::= { altigaPppStatsMibCompliances 1 }

altigaPppStatsGroup OBJECT-GROUP
   OBJECTS
   {
      alPppStatsRowStatus,
      alPppStatsIfIndex,
      alPppStatsOctetsSent,
      alPppStatsOctetsRcvd,
      alPppStatsPacketsSent,
      alPppStatsPacketsRcvd,
      alPppStatsMppcStatus,
      alPppStatsMppeStatus,
      alPppStatsMppcMppeReset,
      alPppStatsMppcOctSentAfterComp,
      alPppStatsMppcOctSentBeforeComp,
      alPppStatsMppcOctSentUnComp,
      alPppStatsMppcOctRcvdBeforeDeComp,
      alPppStatsMppcOctRcvdAfterDeComp,
      alPppStatsMppcOctRcvdUnComp,
      alPppStatsGlobMppcMppeResetsRcvd,
      alPppStatsGlobMppcMppeResetsSent,
      alPppStatsGlobMppcOctSentAfterComp,
      alPppStatsGlobMppcOctSentBeforeComp,
      alPppStatsGlobMppcOctSentUnComp,
      alPppStatsGlobMppcOctRcvdBeforeDeComp,
      alPppStatsGlobMppcOctRcvdAfterDeComp,
      alPppStatsGlobMppcOctRcvdUnComp
   }
   STATUS   current
   DESCRIPTION
          "The objects for PPP statistics."
   ::= { alPppGroup 2 }

END
