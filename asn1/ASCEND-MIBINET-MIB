--			Ascend mibinet MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBINET-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibinternetProfile  OBJECT IDENTIFIER ::= { configuration 1}

	-- The mibinternetProfile table
	--
	-- This table contains parameters for the mibinternetProfile profile
	--

    mibinternetProfileTable	OBJECT-TYPE
	SYNTAX		SEQUENCE OF MibinternetProfileEntry
	ACCESS		not-accessible
	STATUS		mandatory
	DESCRIPTION	"A list of mibinternetProfile profile entries."
	::= { mibinternetProfile 1 }

    mibinternetProfileEntry	OBJECT-TYPE
	SYNTAX		MibinternetProfileEntry
	ACCESS		not-accessible
	STATUS		mandatory
	DESCRIPTION	"A mibinternetProfile entry containing objects that
			 maps to the parameters of mibinternetProfile profile."
	INDEX		{ internetProfile-Station }
	::= { mibinternetProfileTable 1 }

    MibinternetProfileEntry ::=
	SEQUENCE {
	    internetProfile-Station
		DisplayString,
	    internetProfile-Active
		INTEGER,
	    internetProfile-EncapsulationProtocol
		INTEGER,
	    internetProfile-CalledNumberType
		INTEGER,
	    internetProfile-DialNumber
		DisplayString,
	    internetProfile-SubAddress
		DisplayString,
	    internetProfile-Clid
		DisplayString,
	    internetProfile-AutoProfiles
		INTEGER,
	    internetProfile-IpOptions-IpRoutingEnabled
		INTEGER,
	    internetProfile-IpOptions-VjHeaderPrediction
		INTEGER,
	    internetProfile-IpOptions-RemoteAddress
		IpAddress,
	    internetProfile-IpOptions-NetmaskRemote
		IpAddress,
	    internetProfile-IpOptions-LocalAddress
		IpAddress,
	    internetProfile-IpOptions-NetmaskLocal
		IpAddress,
	    internetProfile-IpOptions-RoutingMetric
		INTEGER,
	    internetProfile-IpOptions-Preference
		INTEGER,
	    internetProfile-IpOptions-DownPreference
		INTEGER,
	    internetProfile-IpOptions-PrivateRoute
		INTEGER,
	    internetProfile-IpOptions-MulticastAllowed
		INTEGER,
	    internetProfile-IpOptions-AddressPool
		INTEGER,
	    internetProfile-IpOptions-IpDirect
		IpAddress,
	    internetProfile-IpOptions-Rip
		INTEGER,
	    internetProfile-IpOptions-RouteFilter
		DisplayString,
	    internetProfile-IpOptions-SourceIpCheck
		INTEGER,
	    internetProfile-IpOptions-OspfOptions-Active
		INTEGER,
	    internetProfile-IpOptions-OspfOptions-Area
		IpAddress,
	    internetProfile-IpOptions-OspfOptions-AreaType
		INTEGER,
	    internetProfile-IpOptions-OspfOptions-HelloInterval
		INTEGER,
	    internetProfile-IpOptions-OspfOptions-DeadInterval
		INTEGER,
	    internetProfile-IpOptions-OspfOptions-Priority
		INTEGER,
	    internetProfile-IpOptions-OspfOptions-AuthenType
		INTEGER,
	    internetProfile-IpOptions-OspfOptions-AuthKey
		DisplayString,
	    internetProfile-IpOptions-OspfOptions-KeyId
		INTEGER,
	    internetProfile-IpOptions-OspfOptions-Cost
		INTEGER,
	    internetProfile-IpOptions-OspfOptions-DownCost
		INTEGER,
	    internetProfile-IpOptions-OspfOptions-AseType
		INTEGER,
	    internetProfile-IpOptions-OspfOptions-AseTag
		DisplayString,
	    internetProfile-IpOptions-OspfOptions-TransitDelay
		INTEGER,
	    internetProfile-IpOptions-OspfOptions-RetransmitInterval
		INTEGER,
	    internetProfile-IpOptions-OspfOptions-NonMulticast
		INTEGER,
	    internetProfile-IpOptions-OspfOptions-NetworkType
		INTEGER,
	    internetProfile-IpOptions-OspfOptions-PollInterval
		INTEGER,
	    internetProfile-IpOptions-OspfOptions-Md5AuthKey
		DisplayString,
	    internetProfile-IpOptions-MulticastRateLimit
		INTEGER,
	    internetProfile-IpOptions-MulticastGroupLeaveDelay
		INTEGER,
	    internetProfile-IpOptions-ClientDnsPrimaryAddr
		IpAddress,
	    internetProfile-IpOptions-ClientDnsSecondaryAddr
		IpAddress,
	    internetProfile-IpOptions-ClientDnsAddrAssign
		INTEGER,
	    internetProfile-IpOptions-ClientDefaultGateway
		IpAddress,
	    internetProfile-IpOptions-TosOptions-Active
		INTEGER,
	    internetProfile-IpOptions-TosOptions-Precedence
		INTEGER,
	    internetProfile-IpOptions-TosOptions-TypeOfService
		INTEGER,
	    internetProfile-IpOptions-TosOptions-ApplyTo
		INTEGER,
	    internetProfile-IpOptions-TosOptions-MarkingType
		INTEGER,
	    internetProfile-IpOptions-TosOptions-Dscp
		DisplayString,
	    internetProfile-IpOptions-TosFilter
		DisplayString,
	    internetProfile-IpOptions-ClientWinsPrimaryAddr
		IpAddress,
	    internetProfile-IpOptions-ClientWinsSecondaryAddr
		IpAddress,
	    internetProfile-IpOptions-ClientWinsAddrAssign
		INTEGER,
	    internetProfile-IpOptions-PrivateRouteTable
		DisplayString,
	    internetProfile-IpOptions-PrivateRouteProfileRequired
		INTEGER,
	    internetProfile-IpOptions-NatProfileName
		DisplayString,
	    internetProfile-IpOptions-AddressRealm
		INTEGER,
	    internetProfile-IpxOptions-IpxRoutingEnabled
		INTEGER,
	    internetProfile-IpxOptions-PeerMode
		INTEGER,
	    internetProfile-IpxOptions-Rip
		INTEGER,
	    internetProfile-IpxOptions-Sap
		INTEGER,
	    internetProfile-IpxOptions-DialQuery
		INTEGER,
	    internetProfile-IpxOptions-NetNumber
		DisplayString,
	    internetProfile-IpxOptions-NetAlias
		DisplayString,
	    internetProfile-IpxOptions-SapFilter
		DisplayString,
	    internetProfile-IpxOptions-IpxSpoofing
		INTEGER,
	    internetProfile-IpxOptions-SpoofingTimeout
		INTEGER,
	    internetProfile-IpxOptions-IpxSapHsProxy
		INTEGER,
	    internetProfile-IpxOptions-IpxHeaderCompression
		INTEGER,
	    internetProfile-BridgingOptions-BridgingGroup
		INTEGER,
	    internetProfile-BridgingOptions-DialOnBroadcast
		INTEGER,
	    internetProfile-BridgingOptions-IpxSpoofing
		INTEGER,
	    internetProfile-BridgingOptions-SpoofingTimeout
		INTEGER,
	    internetProfile-BridgingOptions-Fill2
		INTEGER,
	    internetProfile-BridgingOptions-BridgeType
		INTEGER,
	    internetProfile-BridgingOptions-Egress
		INTEGER,
	    internetProfile-SessionOptions-CallFilter
		DisplayString,
	    internetProfile-SessionOptions-DataFilter
		DisplayString,
	    internetProfile-SessionOptions-FilterPersistence
		INTEGER,
	    internetProfile-SessionOptions-FilterRequired
		INTEGER,
	    internetProfile-SessionOptions-IdleTimer
		INTEGER,
	    internetProfile-SessionOptions-TsIdleMode
		INTEGER,
	    internetProfile-SessionOptions-TsIdleTimer
		INTEGER,
	    internetProfile-SessionOptions-Backup
		DisplayString,
	    internetProfile-SessionOptions-Secondary
		DisplayString,
	    internetProfile-SessionOptions-MaxCallDuration
		INTEGER,
	    internetProfile-SessionOptions-VtpGateway
		INTEGER,
	    internetProfile-SessionOptions-Blockcountlimit
		INTEGER,
	    internetProfile-SessionOptions-Blockduration
		INTEGER,
	    internetProfile-SessionOptions-MaxVtpTunnels
		INTEGER,
	    internetProfile-SessionOptions-RedialDelayLimit
		INTEGER,
	    internetProfile-SessionOptions-SesRateType
		INTEGER,
	    internetProfile-SessionOptions-SesRateMode
		INTEGER,
	    internetProfile-SessionOptions-SesAdslCapUpRate
		INTEGER,
	    internetProfile-SessionOptions-SesAdslCapDownRate
		INTEGER,
	    internetProfile-SessionOptions-SesSdslRate
		INTEGER,
	    internetProfile-SessionOptions-SesAdslDmtUpRate
		INTEGER,
	    internetProfile-SessionOptions-SesAdslDmtDownRate
		INTEGER,
	    internetProfile-SessionOptions-RxDataRateLimit
		INTEGER,
	    internetProfile-SessionOptions-TxDataRateLimit
		INTEGER,
	    internetProfile-SessionOptions-CirTimer
		INTEGER,
	    internetProfile-SessionOptions-TrafficShaper
		INTEGER,
	    internetProfile-SessionOptions-MaxtapLogServer
		DisplayString,
	    internetProfile-SessionOptions-MaxtapDataServer
		DisplayString,
	    internetProfile-SessionOptions-Priority
		INTEGER,
	    internetProfile-TelcoOptions-AnswerOriginate
		INTEGER,
	    internetProfile-TelcoOptions-Callback
		INTEGER,
	    internetProfile-TelcoOptions-CallType
		INTEGER,
	    internetProfile-TelcoOptions-NailedGroups
		DisplayString,
	    internetProfile-TelcoOptions-Ft1Caller
		INTEGER,
	    internetProfile-TelcoOptions-Force56kbps
		INTEGER,
	    internetProfile-TelcoOptions-DataService
		INTEGER,
	    internetProfile-TelcoOptions-CallByCall
		INTEGER,
	    internetProfile-TelcoOptions-BillingNumber
		DisplayString,
	    internetProfile-TelcoOptions-TransitNumber
		DisplayString,
	    internetProfile-TelcoOptions-ExpectCallback
		INTEGER,
	    internetProfile-TelcoOptions-DialoutAllowed
		INTEGER,
	    internetProfile-TelcoOptions-DelayCallback
		INTEGER,
	    internetProfile-TelcoOptions-NasPortType
		INTEGER,
	    internetProfile-PppOptions-SendAuthMode
		INTEGER,
	    internetProfile-PppOptions-PppCircuit
		INTEGER,
	    internetProfile-PppOptions-PppCircuitName
		DisplayString,
	    internetProfile-PppOptions-BiDirectionalAuth
		INTEGER,
	    internetProfile-PppOptions-SendPassword
		DisplayString,
	    internetProfile-PppOptions-SubstituteSendName
		DisplayString,
	    internetProfile-PppOptions-RecvPassword
		DisplayString,
	    internetProfile-PppOptions-SubstituteRecvName
		DisplayString,
	    internetProfile-PppOptions-LinkCompression
		INTEGER,
	    internetProfile-PppOptions-Mru
		INTEGER,
	    internetProfile-PppOptions-Lqm
		INTEGER,
	    internetProfile-PppOptions-LqmMinimumPeriod
		INTEGER,
	    internetProfile-PppOptions-LqmMaximumPeriod
		INTEGER,
	    internetProfile-PppOptions-CbcpEnabled
		INTEGER,
	    internetProfile-PppOptions-ModeCallbackControl
		INTEGER,
	    internetProfile-PppOptions-DelayCallbackControl
		INTEGER,
	    internetProfile-PppOptions-TrunkGroupCallbackControl
		INTEGER,
	    internetProfile-PppOptions-SplitCodeDotUserEnabled
		INTEGER,
	    internetProfile-PppOptions-PppInterfaceType
		INTEGER,
	    internetProfile-PppOptions-Mtu
		INTEGER,
	    internetProfile-MpOptions-BaseChannelCount
		INTEGER,
	    internetProfile-MpOptions-MinimumChannels
		INTEGER,
	    internetProfile-MpOptions-MaximumChannels
		INTEGER,
	    internetProfile-MpOptions-BacpEnable
		INTEGER,
	    internetProfile-MpOptions-BodEnable
		INTEGER,
	    internetProfile-MpOptions-CallbackrequestEnable
		INTEGER,
	    internetProfile-MppOptions-AuxSendPassword
		DisplayString,
	    internetProfile-MppOptions-DynamicAlgorithm
		INTEGER,
	    internetProfile-MppOptions-BandwidthMonitorDirection
		INTEGER,
	    internetProfile-MppOptions-IncrementChannelCount
		INTEGER,
	    internetProfile-MppOptions-DecrementChannelCount
		INTEGER,
	    internetProfile-MppOptions-SecondsHistory
		INTEGER,
	    internetProfile-MppOptions-AddPersistence
		INTEGER,
	    internetProfile-MppOptions-SubPersistence
		INTEGER,
	    internetProfile-MppOptions-TargetUtilization
		INTEGER,
	    internetProfile-MppOptions-X25chanTargetUtilization
		INTEGER,
	    internetProfile-FrOptions-FrameRelayProfile
		DisplayString,
	    internetProfile-FrOptions-CircuitType
		INTEGER,
	    internetProfile-FrOptions-Dlci
		INTEGER,
	    internetProfile-FrOptions-CircuitName
		DisplayString,
	    internetProfile-FrOptions-FrLinkType
		INTEGER,
	    internetProfile-FrOptions-FrDirectEnabled
		INTEGER,
	    internetProfile-FrOptions-FrDirectProfile
		DisplayString,
	    internetProfile-FrOptions-FrDirectDlci
		INTEGER,
	    internetProfile-FrOptions-MfrBundleName
		DisplayString,
	    internetProfile-TcpClearOptions-Host
		DisplayString,
	    internetProfile-TcpClearOptions-Port
		INTEGER,
	    internetProfile-TcpClearOptions-Host2
		DisplayString,
	    internetProfile-TcpClearOptions-Port2
		INTEGER,
	    internetProfile-TcpClearOptions-Host3
		DisplayString,
	    internetProfile-TcpClearOptions-Port3
		INTEGER,
	    internetProfile-TcpClearOptions-Host4
		DisplayString,
	    internetProfile-TcpClearOptions-Port4
		INTEGER,
	    internetProfile-TcpClearOptions-DetectEndOfPacket
		INTEGER,
	    internetProfile-TcpClearOptions-EndOfPacketPattern
		DisplayString,
	    internetProfile-TcpClearOptions-FlushLength
		INTEGER,
	    internetProfile-TcpClearOptions-FlushTime
		INTEGER,
	    internetProfile-AraOptions-RecvPassword
		DisplayString,
	    internetProfile-AraOptions-MaximumConnectTime
		INTEGER,
	    internetProfile-X25Options-X25Profile
		DisplayString,
	    internetProfile-X25Options-Lcn
		INTEGER,
	    internetProfile-X25Options-X3Profile
		INTEGER,
	    internetProfile-X25Options-MaxCalls
		INTEGER,
	    internetProfile-X25Options-VcTimerEnable
		INTEGER,
	    internetProfile-X25Options-X25EncapsType
		INTEGER,
	    internetProfile-X25Options-RemoteX25Address
		DisplayString,
	    internetProfile-X25Options-ReverseCharge
		INTEGER,
	    internetProfile-X25Options-CallMode
		INTEGER,
	    internetProfile-X25Options-AnswerX25Address
		DisplayString,
	    internetProfile-X25Options-InactivityTimer
		INTEGER,
	    internetProfile-X25Options-Windowsize
		INTEGER,
	    internetProfile-X25Options-Packetsize
		INTEGER,
	    internetProfile-X25Options-X25Rpoa
		DisplayString,
	    internetProfile-X25Options-X25CugIndex
		DisplayString,
	    internetProfile-X25Options-X25Nui
		DisplayString,
	    internetProfile-X25Options-PadBanner
		DisplayString,
	    internetProfile-X25Options-PadPrompt
		DisplayString,
	    internetProfile-X25Options-PadNuiPrompt
		DisplayString,
	    internetProfile-X25Options-PadNuiPwPrompt
		DisplayString,
	    internetProfile-X25Options-PadAlias1
		DisplayString,
	    internetProfile-X25Options-PadAlias2
		DisplayString,
	    internetProfile-X25Options-PadAlias3
		DisplayString,
	    internetProfile-X25Options-PadDiagDisp
		INTEGER,
	    internetProfile-X25Options-PadDefaultListen
		DisplayString,
	    internetProfile-X25Options-PadDefaultPw
		DisplayString,
	    internetProfile-X25Options-X121SourceAddress
		DisplayString,
	    internetProfile-X25Options-PosAuth
		INTEGER,
	    internetProfile-EuOptions-DceAddr
		INTEGER,
	    internetProfile-EuOptions-DteAddr
		INTEGER,
	    internetProfile-EuOptions-Mru
		INTEGER,
	    internetProfile-X75Options-KFramesOutstanding
		INTEGER,
	    internetProfile-X75Options-N2Retransmissions
		INTEGER,
	    internetProfile-X75Options-T1RetranTimer
		INTEGER,
	    internetProfile-X75Options-FrameLength
		INTEGER,
	    internetProfile-AppletalkOptions-AtalkRoutingEnabled
		INTEGER,
	    internetProfile-AppletalkOptions-AtalkStaticZoneName
		DisplayString,
	    internetProfile-AppletalkOptions-AtalkStaticNetStart
		INTEGER,
	    internetProfile-AppletalkOptions-AtalkStaticNetEnd
		INTEGER,
	    internetProfile-AppletalkOptions-AtalkPeerMode
		INTEGER,
	    internetProfile-UsrRadOptions-AcctType
		INTEGER,
	    internetProfile-UsrRadOptions-AcctHost
		IpAddress,
	    internetProfile-UsrRadOptions-AcctPort
		INTEGER,
	    internetProfile-UsrRadOptions-AcctKey
		DisplayString,
	    internetProfile-UsrRadOptions-AcctTimeout
		INTEGER,
	    internetProfile-UsrRadOptions-AcctIdBase
		INTEGER,
	    internetProfile-CalledNumber
		DisplayString,
	    internetProfile-DhcpOptions-ReplyEnabled
		INTEGER,
	    internetProfile-DhcpOptions-PoolNumber
		INTEGER,
	    internetProfile-DhcpOptions-MaximumLeases
		INTEGER,
	    internetProfile-SharedProf
		INTEGER,
	    internetProfile-MaxSharedUsers
		INTEGER,
	    internetProfile-T3posOptions-X25Profile
		DisplayString,
	    internetProfile-T3posOptions-MaxCalls
		INTEGER,
	    internetProfile-T3posOptions-AutoCallX121Address
		DisplayString,
	    internetProfile-T3posOptions-ReverseCharge
		INTEGER,
	    internetProfile-T3posOptions-Answer
		DisplayString,
	    internetProfile-T3posOptions-T3PosHostInitMode
		INTEGER,
	    internetProfile-T3posOptions-T3PosDteInitMode
		INTEGER,
	    internetProfile-T3posOptions-T3PosEnqHandling
		INTEGER,
	    internetProfile-T3posOptions-T3PosMaxBlockSize
		INTEGER,
	    internetProfile-T3posOptions-T3PosT1
		INTEGER,
	    internetProfile-T3posOptions-T3PosT2
		INTEGER,
	    internetProfile-T3posOptions-T3PosT3
		INTEGER,
	    internetProfile-T3posOptions-T3PosT4
		INTEGER,
	    internetProfile-T3posOptions-T3PosT5
		INTEGER,
	    internetProfile-T3posOptions-T3PosT6
		INTEGER,
	    internetProfile-T3posOptions-T3PosMethodOfHostNotif
		INTEGER,
	    internetProfile-T3posOptions-T3PosPidSelection
		INTEGER,
	    internetProfile-T3posOptions-T3PosAckSuppression
		INTEGER,
	    internetProfile-T3posOptions-X25Rpoa
		DisplayString,
	    internetProfile-T3posOptions-X25CugIndex
		DisplayString,
	    internetProfile-T3posOptions-X25Nui
		DisplayString,
	    internetProfile-T3posOptions-DataFormat
		INTEGER,
	    internetProfile-T3posOptions-LinkAccessType
		INTEGER,
	    internetProfile-FramedOnly
		INTEGER,
	    internetProfile-AltdialNumber1
		DisplayString,
	    internetProfile-AltdialNumber2
		DisplayString,
	    internetProfile-AltdialNumber3
		DisplayString,
	    internetProfile-X32Options-X32Profile
		DisplayString,
	    internetProfile-X32Options-CallMode
		INTEGER,
	    internetProfile-X32Options-X32ApplMode
		INTEGER,
	    internetProfile-TunnelOptions-ProfileType
		INTEGER,
	    internetProfile-TunnelOptions-TunnelingProtocol
		INTEGER,
	    internetProfile-TunnelOptions-MaxTunnels
		INTEGER,
	    internetProfile-TunnelOptions-AtmpHaRip
		INTEGER,
	    internetProfile-TunnelOptions-PrimaryTunnelServer
		DisplayString,
	    internetProfile-TunnelOptions-SecondaryTunnelServer
		DisplayString,
	    internetProfile-TunnelOptions-UdpPort
		INTEGER,
	    internetProfile-TunnelOptions-Password
		DisplayString,
	    internetProfile-TunnelOptions-HomeNetworkName
		DisplayString,
	    internetProfile-TunnelOptions-ClientAuthId
		DisplayString,
	    internetProfile-TunnelOptions-ServerAuthId
		DisplayString,
	    internetProfile-TunnelOptions-Vrouter
		DisplayString,
	    internetProfile-TunnelOptions-AssignmentId
		DisplayString,
	    internetProfile-TunnelOptions-TosCopying
		INTEGER,
	    internetProfile-IpsecOptions-Enabled
		INTEGER,
	    internetProfile-IpsecOptions-SecurityPolicyDatabase
		DisplayString,
	    internetProfile-PriNumberingPlanId
		INTEGER,
	    internetProfile-Vrouter
		DisplayString,
	    internetProfile-CrossConnectIndex
		INTEGER,
	    internetProfile-AtmOptions-Atm1483type
		INTEGER,
	    internetProfile-AtmOptions-Vpi
		INTEGER,
	    internetProfile-AtmOptions-Vci
		INTEGER,
	    internetProfile-AtmOptions-NailedGroup
		INTEGER,
	    internetProfile-AtmOptions-CastType
		INTEGER,
	    internetProfile-AtmOptions-ConnKind
		INTEGER,
	    internetProfile-AtmOptions-AtmServiceType
		INTEGER,
	    internetProfile-AtmOptions-AtmServiceRate
		INTEGER,
	    internetProfile-AtmOptions-VpSwitching
		INTEGER,
	    internetProfile-AtmOptions-TargetAtmAddress
		DisplayString,
	    internetProfile-AtmOptions-TargetSelect
		INTEGER,
	    internetProfile-AtmOptions-TargetVpi
		INTEGER,
	    internetProfile-AtmOptions-TargetVci
		INTEGER,
	    internetProfile-AtmOptions-SpvcRetryInterval
		INTEGER,
	    internetProfile-AtmOptions-SpvcRetryThreshold
		INTEGER,
	    internetProfile-AtmOptions-SpvcRetryLimit
		INTEGER,
	    internetProfile-AtmOptions-AtmDirectEnabled
		INTEGER,
	    internetProfile-AtmOptions-AtmDirectProfile
		DisplayString,
	    internetProfile-AtmOptions-VcFaultManagement
		INTEGER,
	    internetProfile-AtmOptions-VcMaxLoopbackCellLoss
		INTEGER,
	    internetProfile-AtmOptions-SvcOptions-Enabled
		INTEGER,
	    internetProfile-AtmOptions-SvcOptions-IncomingCallerAddr-NumberingPlan
		INTEGER,
	    internetProfile-AtmOptions-SvcOptions-IncomingCallerAddr-E164NativeAddress
		DisplayString,
	    internetProfile-AtmOptions-SvcOptions-IncomingCallerAddr-AesaAddress-Format
		INTEGER,
	    internetProfile-AtmOptions-SvcOptions-IncomingCallerAddr-AesaAddress-IdpPortion-Afi
		DisplayString,
	    internetProfile-AtmOptions-SvcOptions-IncomingCallerAddr-AesaAddress-IdpPortion-Idi
		DisplayString,
	    internetProfile-AtmOptions-SvcOptions-IncomingCallerAddr-AesaAddress-DspPortion-HoDsp
		DisplayString,
	    internetProfile-AtmOptions-SvcOptions-IncomingCallerAddr-AesaAddress-DspPortion-Esi
		DisplayString,
	    internetProfile-AtmOptions-SvcOptions-IncomingCallerAddr-AesaAddress-DspPortion-Sel
		DisplayString,
	    internetProfile-AtmOptions-SvcOptions-OutgoingCalledAddr-NumberingPlan
		INTEGER,
	    internetProfile-AtmOptions-SvcOptions-OutgoingCalledAddr-E164NativeAddress
		DisplayString,
	    internetProfile-AtmOptions-SvcOptions-OutgoingCalledAddr-AesaAddress-Format
		INTEGER,
	    internetProfile-AtmOptions-SvcOptions-OutgoingCalledAddr-AesaAddress-IdpPortion-Afi
		DisplayString,
	    internetProfile-AtmOptions-SvcOptions-OutgoingCalledAddr-AesaAddress-IdpPortion-Idi
		DisplayString,
	    internetProfile-AtmOptions-SvcOptions-OutgoingCalledAddr-AesaAddress-DspPortion-HoDsp
		DisplayString,
	    internetProfile-AtmOptions-SvcOptions-OutgoingCalledAddr-AesaAddress-DspPortion-Esi
		DisplayString,
	    internetProfile-AtmOptions-SvcOptions-OutgoingCalledAddr-AesaAddress-DspPortion-Sel
		DisplayString,
	    internetProfile-AtmOptions-AtmInverseArp
		INTEGER,
	    internetProfile-AtmOptions-Fr08Mode
		INTEGER,
	    internetProfile-AtmOptions-AtmCircuitProfile
		DisplayString,
	    internetProfile-AtmOptions-OamAisF5
		INTEGER,
	    internetProfile-AtmOptions-OamSupport
		INTEGER,
	    internetProfile-AtmOptions-Mtu
		INTEGER,
	    internetProfile-HdlcNrmOptions-SnrmResponseTimeout
		INTEGER,
	    internetProfile-HdlcNrmOptions-SnrmRetryCounter
		INTEGER,
	    internetProfile-HdlcNrmOptions-PollTimeout
		INTEGER,
	    internetProfile-HdlcNrmOptions-PollRate
		INTEGER,
	    internetProfile-HdlcNrmOptions-PollRetryCount
		INTEGER,
	    internetProfile-HdlcNrmOptions-Primary
		INTEGER,
	    internetProfile-HdlcNrmOptions-AsyncDrop
		INTEGER,
	    internetProfile-HdlcNrmOptions-StationPollAddress
		INTEGER,
	    internetProfile-AtmConnectOptions-Atm1483type
		INTEGER,
	    internetProfile-AtmConnectOptions-Vpi
		INTEGER,
	    internetProfile-AtmConnectOptions-Vci
		INTEGER,
	    internetProfile-AtmConnectOptions-NailedGroup
		INTEGER,
	    internetProfile-AtmConnectOptions-CastType
		INTEGER,
	    internetProfile-AtmConnectOptions-ConnKind
		INTEGER,
	    internetProfile-AtmConnectOptions-AtmServiceType
		INTEGER,
	    internetProfile-AtmConnectOptions-AtmServiceRate
		INTEGER,
	    internetProfile-AtmConnectOptions-VpSwitching
		INTEGER,
	    internetProfile-AtmConnectOptions-TargetAtmAddress
		DisplayString,
	    internetProfile-AtmConnectOptions-TargetSelect
		INTEGER,
	    internetProfile-AtmConnectOptions-TargetVpi
		INTEGER,
	    internetProfile-AtmConnectOptions-TargetVci
		INTEGER,
	    internetProfile-AtmConnectOptions-SpvcRetryInterval
		INTEGER,
	    internetProfile-AtmConnectOptions-SpvcRetryThreshold
		INTEGER,
	    internetProfile-AtmConnectOptions-SpvcRetryLimit
		INTEGER,
	    internetProfile-AtmConnectOptions-AtmDirectEnabled
		INTEGER,
	    internetProfile-AtmConnectOptions-AtmDirectProfile
		DisplayString,
	    internetProfile-AtmConnectOptions-VcFaultManagement
		INTEGER,
	    internetProfile-AtmConnectOptions-VcMaxLoopbackCellLoss
		INTEGER,
	    internetProfile-AtmConnectOptions-SvcOptions-Enabled
		INTEGER,
	    internetProfile-AtmConnectOptions-SvcOptions-IncomingCallerAddr-NumberingPlan
		INTEGER,
	    internetProfile-AtmConnectOptions-SvcOptions-IncomingCallerAddr-E164NativeAddress
		DisplayString,
	    internetProfile-AtmConnectOptions-SvcOptions-IncomingCallerAddr-AesaAddress-Format
		INTEGER,
	    internetProfile-AtmConnectOptions-SvcOptions-IncomingCallerAddr-AesaAddress-IdpPortion-Afi
		DisplayString,
	    internetProfile-AtmConnectOptions-SvcOptions-IncomingCallerAddr-AesaAddress-IdpPortion-Idi
		DisplayString,
	    internetProfile-AtmConnectOptions-SvcOptions-IncomingCallerAddr-AesaAddress-DspPortion-HoDsp
		DisplayString,
	    internetProfile-AtmConnectOptions-SvcOptions-IncomingCallerAddr-AesaAddress-DspPortion-Esi
		DisplayString,
	    internetProfile-AtmConnectOptions-SvcOptions-IncomingCallerAddr-AesaAddress-DspPortion-Sel
		DisplayString,
	    internetProfile-AtmConnectOptions-SvcOptions-OutgoingCalledAddr-NumberingPlan
		INTEGER,
	    internetProfile-AtmConnectOptions-SvcOptions-OutgoingCalledAddr-E164NativeAddress
		DisplayString,
	    internetProfile-AtmConnectOptions-SvcOptions-OutgoingCalledAddr-AesaAddress-Format
		INTEGER,
	    internetProfile-AtmConnectOptions-SvcOptions-OutgoingCalledAddr-AesaAddress-IdpPortion-Afi
		DisplayString,
	    internetProfile-AtmConnectOptions-SvcOptions-OutgoingCalledAddr-AesaAddress-IdpPortion-Idi
		DisplayString,
	    internetProfile-AtmConnectOptions-SvcOptions-OutgoingCalledAddr-AesaAddress-DspPortion-HoDsp
		DisplayString,
	    internetProfile-AtmConnectOptions-SvcOptions-OutgoingCalledAddr-AesaAddress-DspPortion-Esi
		DisplayString,
	    internetProfile-AtmConnectOptions-SvcOptions-OutgoingCalledAddr-AesaAddress-DspPortion-Sel
		DisplayString,
	    internetProfile-AtmConnectOptions-AtmInverseArp
		INTEGER,
	    internetProfile-AtmConnectOptions-Fr08Mode
		INTEGER,
	    internetProfile-AtmConnectOptions-AtmCircuitProfile
		DisplayString,
	    internetProfile-AtmConnectOptions-OamAisF5
		INTEGER,
	    internetProfile-AtmConnectOptions-OamSupport
		INTEGER,
	    internetProfile-AtmConnectOptions-Mtu
		INTEGER,
	    internetProfile-Visa2Options-IdleCharacterDelay
		INTEGER,
	    internetProfile-Visa2Options-FirstDataForwardCharacter
		DisplayString,
	    internetProfile-Visa2Options-SecondDataForwardCharacter
		DisplayString,
	    internetProfile-Visa2Options-ThirdDataForwardCharacter
		DisplayString,
	    internetProfile-Visa2Options-FourthDataForwardCharacter
		DisplayString,
	    internetProfile-Visa2Options-o1CharSequence
		DisplayString,
	    internetProfile-Visa2Options-o2CharSequence
		DisplayString,
	    internetProfile-SdtnPacketsServer
		INTEGER,
	    internetProfile-oATString
		DisplayString,
	    internetProfile-PortRedirectOptions-Protocol
		INTEGER,
	    internetProfile-PortRedirectOptions-PortNumber
		INTEGER,
	    internetProfile-PortRedirectOptions-RedirectAddress
		IpAddress,
	    internetProfile-PppoeOptions-Pppoe
		INTEGER,
	    internetProfile-PppoeOptions-BridgeNonPppoe
		INTEGER,
	    internetProfile-AtmQosOptions-UsrUpStreamContract
		DisplayString,
	    internetProfile-AtmQosOptions-UsrDnStreamContract
		DisplayString,
	    internetProfile-AtmQosOptions-SubtendingHops
		INTEGER,
	    internetProfile-BirOptions-Enable
		INTEGER,
	    internetProfile-BirOptions-ProxyArp
		INTEGER,
	    internetProfile-AtmAalOptions-AalEnabled
		INTEGER,
	    internetProfile-AtmAalOptions-AalType
		INTEGER,
	    internetProfile-AtmAalOptions-TransmitSduSize
		INTEGER,
	    internetProfile-AtmAalOptions-ReceiveSduSize
		INTEGER,
	    internetProfile-ConnUser
		INTEGER,
	    internetProfile-ModemOnHoldTimeout
		INTEGER,
	    internetProfile-PriorityOptions-Enabled
		INTEGER,
	    internetProfile-PriorityOptions-PacketClassification
		INTEGER,
	    internetProfile-PriorityOptions-MaxRtpPacketDelay
		INTEGER,
	    internetProfile-PriorityOptions-MinimumRtpPort
		INTEGER,
	    internetProfile-PriorityOptions-MaximumRtpPort
		INTEGER,
	    internetProfile-PriorityOptions-NoHighPrioPktDuration
		INTEGER,
	    internetProfile-Action-o
		INTEGER
	}

    internetProfile-Station	OBJECT-TYPE
	SYNTAX	DisplayString
	ACCESS	read-only
	STATUS	mandatory
	DESCRIPTION	"The name of the host we will be communicating with. This name is used as part of the authentication process when authentication is being used."
	::= { mibinternetProfileEntry 1 }

    internetProfile-Active	OBJECT-TYPE
	SYNTAX	INTEGER {
		    no (1),
		    yes (2)
		}
	ACCESS	read-write
	STATUS	mandatory
	DESCRIPTION	"A profile can be disabled by setting this field to no. There is no difference between an inactive profile and no profile at all to the remainder of the code."
	::= { mibinternetProfileEntry 2 }

    internetProfile-EncapsulationProtocol	OBJECT-TYPE
	SYNTAX	INTEGER {
		    mpp (1),
		    mp (2),
		    ppp (3),
		    combinet (9),
		    slip (4),
		    cslip (5),
		    frameRelay (6),
		    frameRelayCircuit (10),
		    x25pad (11),
		    euraw (12),
		    euui (13),
		    tcpRaw (7),
		    rfc1356X25 (14),
		    ara (15),
		    t3pos (17),
		    dtpt (8),
		    x32 (18),
		    atm (21),
		    atmFrameRelayCircuit (22),
		    hdlcNrm (23),
		    atmCircuit (24),
		    visa2 (26),
		    atmSvcSig (27),
		    atmIma (28)
		}
	ACCESS	read-write
	STATUS	mandatory
	DESCRIPTION	"The encapsulation protocol to be used when communicating with the named station."
	::= { mibinternetProfileEntry 3 }

    internetProfile-CalledNumberType	OBJECT-TYPE
	SYNTAX	INTEGER {
		    unknown (1),
		    international (2),
		    national (3),
		    networkSpecific (4),
		    local (5),
		    abbrev (7)
		}
	ACCESS	read-write
	STATUS	mandatory
	DESCRIPTION	"Indication of whether national number, international number, etc. is specified."
	::= { mibinternetProfileEntry 4 }

    internetProfile-DialNumber	OBJECT-TYPE
	SYNTAX	DisplayString
	ACCESS	read-write
	STATUS	mandatory
	DESCRIPTION	"The phone number of the named station."
	::= { mibinternetProfileEntry 5 }

    internetProfile-SubAddress	OBJECT-TYPE
	SYNTAX	DisplayString
	ACCESS	read-write
	STATUS	mandatory
	DESCRIPTION	"The sub-address extension to the dialed number of the station."
	::= { mibinternetProfileEntry 292 }

    internetProfile-Clid	OBJECT-TYPE
	SYNTAX	DisplayString
	ACCESS	read-write
	STATUS	mandatory
	DESCRIPTION	"The calling line number for authentication."
	::= { mibinternetProfileEntry 6 }

    internetProfile-AutoProfiles	OBJECT-TYPE
	SYNTAX	INTEGER {
		    no (1),
		    yes (2)
		}
	ACCESS	read-write
	STATUS	mandatory
	DESCRIPTION	"This parameter enables or disables automatic profile creation. Currently only the Stinger IDSL provides this capability for PPP Circuits and Frame Relay Circuits."
	::= { mibinternetProfileEntry 420 }

    internetProfile-IpOptions-IpRoutingEnabled	OBJECT-TYPE
	SYNTAX	INTEGER {
		    no (1),
		    yes (2)
		}
	ACCESS	read-write
	STATUS	mandatory
	DESCRIPTION	"Enable/disable IP routing for this connection."
	::= { mibinternetProfileEntry 7 }

    internetProfile-IpOptions-VjHeaderPrediction	OBJECT-TYPE
	SYNTAX	INTEGER {
		    no (1),
		    yes (2)
		}
	ACCESS	read-write
	STATUS	mandatory
	DESCRIPTION	"Enable/disable Van Jacabson TCP Header prediction processing on this connection if supported by the selected encapsulation protocol."
	::= { mibinternetProfileEntry 8 }

    internetProfile-IpOptions-RemoteAddress	OBJECT-TYPE
	SYNTAX	IpAddress
	ACCESS	read-write
	STATUS	mandatory
	DESCRIPTION	"The remote address with netmask of the named host."
	::= { mibinternetProfileEntry 9 }

    internetProfile-IpOptions-NetmaskRemote	OBJECT-TYPE
	SYNTAX	IpAddress
	ACCESS	read-write
	STATUS	mandatory
	DESCRIPTION	"The netmask of the remote address."
	::= { mibinternetProfileEntry 10 }

    internetProfile-IpOptions-LocalAddress	OBJECT-TYPE
	SYNTAX	IpAddress
	ACCESS	read-write
	STATUS	mandatory
	DESCRIPTION	"The interface address with netmask, if required, of the local end. If left zero the interface is assumed to be an unnumbered interface."
	::= { mibinternetProfileEntry 11 }

    internetProfile-IpOptions-NetmaskLocal	OBJECT-TYPE
	SYNTAX	IpAddress
	ACCESS	read-write
	STATUS	mandatory
	DESCRIPTION	"The netmask of the local interface address."
	::= { mibinternetProfileEntry 12 }

    internetProfile-IpOptions-RoutingMetric	OBJECT-TYPE
	SYNTAX	INTEGER
	ACCESS	read-write
	STATUS	mandatory
	DESCRIPTION	"The routing metric, typically measured in number of hops, to be used in the routing table entry created for this connection when the connection is active."
	::= { mibinternetProfileEntry 13 }

    internetProfile-IpOptions-Preference	OBJECT-TYPE
	SYNTAX	INTEGER
	ACCESS	read-write
	STATUS	mandatory
	DESCRIPTION	"The preference used for comparing this route to other routes. Preference has a higher priority than metric. As with the metric field, the lower the number, the higher the preference."
	::= { mibinternetProfileEntry 14 }

    internetProfile-IpOptions-DownPreference	OBJECT-TYPE
	SYNTAX	INTEGER
	ACCESS	read-write
	STATUS	mandatory
	DESCRIPTION	"The preference used for comparing the down-metric route to other routes. Preference has a higher priority than metric. As with the metric field, the lower the number, the higher the preference."
	::= { mibinternetProfileEntry 15 }

    internetProfile-IpOptions-PrivateRoute	OBJECT-TYPE
	SYNTAX	INTEGER {
		    no (1),
		    yes (2)
		}
	ACCESS	read-write
	STATUS	mandatory
	DESCRIPTION	"Enable/disable distribution of the route created for this connection via routing protocols. Private routes are used internally, but never advertized to the outside world."
	::= { mibinternetProfileEntry 16 }

    internetProfile-IpOptions-MulticastAllowed	OBJECT-TYPE
	SYNTAX	INTEGER {
		    no (1),
		    yes (2)
		}
	ACCESS	read-write
	STATUS	mandatory
	DESCRIPTION	"Enable this connection as a multicast traffic client."
	::= { mibinternetProfileEntry 17 }

    internetProfile-IpOptions-AddressPool	OBJECT-TYPE
	SYNTAX	INTEGER
	ACCESS	read-write
	STATUS	mandatory
	DESCRIPTION	"The number of the address pool from which an address for this host should be obtained when using assigned addresses."
	::= { mibinternetProfileEntry 18 }

    internetProfile-IpOptions-IpDirect	OBJECT-TYPE
	SYNTAX	IpAddress
	ACCESS	read-write
	STATUS	mandatory
	DESCRIPTION	"The address of the next-hop when IP direct routing is used."
	::= { mibinternetProfileEntry 19 }

    internetProfile-IpOptions-Rip	OBJECT-TYPE
	SYNTAX	INTEGER {
		    routingOff (1),
		    routingSendOnly (2),
		    routingRecvOnly (3),
		    routingSendAndRecv (4),
		    routingSendOnlyV2 (5),
		    routingRecvOnlyV2 (6),
		    routingSendAndRecvV2 (7)
		}
	ACCESS	read-write
	STATUS	mandatory
	DESCRIPTION	"Specify if RIP or RIP-2 should be used over this connection and if used in both directions or not."
	::= { mibinternetProfileEntry 20 }

    internetProfile-IpOptions-RouteFilter	OBJECT-TYPE
	SYNTAX	DisplayString
	ACCESS	read-write
	STATUS	mandatory
	DESCRIPTION	"The name of this filter. All filters are referenced by name so a name must be assigned to active filters."
	::= { mibinternetProfileEntry 21 }

    internetProfile-IpOptions-SourceIpCheck	OBJECT-TYPE
	SYNTAX	INTEGER {
		    no (1),
		    yes (2)
		}
	ACCESS	read-write
	STATUS	mandatory
	DESCRIPTION	"Enable/disable source ip checking. Packets with source ip address which doesn't match with negotiated remote ip address will be dropped."
	::= { mibinternetProfileEntry 22 }

    internetProfile-IpOptions-OspfOptions-Active	OBJECT-TYPE
	SYNTAX	INTEGER {
		    no (1),
		    yes (2)
		}
	ACCESS	read-write
	STATUS	mandatory
	DESCRIPTION	"Is OSPF active on this interface."
	::= { mibinternetProfileEntry 23 }

    internetProfile-IpOptions-OspfOptions-Area	OBJECT-TYPE
	SYNTAX	IpAddress
	ACCESS	read-write
	STATUS	mandatory
	DESCRIPTION	"The area that this interface belongs to."
	::= { mibinternetProfileEntry 24 }

    internetProfile-IpOptions-OspfOptions-AreaType	OBJECT-TYPE
	SYNTAX	INTEGER {
		    normal (1),
		    stub (2),
		    nSSA (3)
		}
	ACCESS	read-write
	STATUS	mandatory
	DESCRIPTION	"The type of Area. Normal, Stub, NSSA"
	::= { mibinternetProfileEntry 25 }

    internetProfile-IpOptions-OspfOptions-HelloInterval	OBJECT-TYPE
	SYNTAX	INTEGER
	ACCESS	read-write
	STATUS	mandatory
	DESCRIPTION	"The hello interval (seconds)."
	::= { mibinternetProfileEntry 26 }

    internetProfile-IpOptions-OspfOptions-DeadInterval	OBJECT-TYPE
	SYNTAX	INTEGER
	ACCESS	read-write
	STATUS	mandatory
	DESCRIPTION	"The dead interval (seconds)."
	::= { mibinternetProfileEntry 27 }

    internetProfile-IpOptions-OspfOptions-Priority	OBJECT-TYPE
	SYNTAX	INTEGER
	ACCESS	read-write
	STATUS	mandatory
	DESCRIPTION	"The priority of this router in DR elections."
	::= { mibinternetProfileEntry 28 }

    internetProfile-IpOptions-OspfOptions-AuthenType	OBJECT-TYPE
	SYNTAX	INTEGER {
		    none (1),
		    simple (2),
		    md5 (3)
		}
	ACCESS	read-write
	STATUS	mandatory
	DESCRIPTION	"The type of OSPF authentication in effect."
	::= { mibinternetProfileEntry 29 }

    internetProfile-IpOptions-OspfOptions-AuthKey	OBJECT-TYPE
	SYNTAX	DisplayString
	ACCESS	read-write
	STATUS	mandatory
	DESCRIPTION	"The authentication key."
	::= { mibinternetProfileEntry 30 }

    internetProfile-IpOptions-OspfOptions-KeyId	OBJECT-TYPE
	SYNTAX	INTEGER
	ACCESS	read-write
	STATUS	mandatory
	DESCRIPTION	"The key identifier for MD5 authentication."
	::= { mibinternetProfileEntry 31 }

    internetProfile-IpOptions-OspfOptions-Cost	OBJECT-TYPE
	SYNTAX	INTEGER
	ACCESS	read-write
	STATUS	mandatory
	DESCRIPTION	"The output cost."
	::= { mibinternetProfileEntry 32 }

    internetProfile-IpOptions-OspfOptions-DownCost	OBJECT-TYPE
	SYNTAX	INTEGER
	ACCESS	read-write
	STATUS	mandatory
	DESCRIPTION	"The output cost when the link is physically down but virtually up."
	::= { mibinternetProfileEntry 33 }

    internetProfile-IpOptions-OspfOptions-AseType	OBJECT-TYPE
	SYNTAX	INTEGER {
		    type1 (1),
		    type2 (2)
		}
	ACCESS	read-write
	STATUS	mandatory
	DESCRIPTION	"The OSPF ASE type of this LSA."
	::= { mibinternetProfileEntry 34 }

    internetProfile-IpOptions-OspfOptions-AseTag	OBJECT-TYPE
	SYNTAX	DisplayString
	ACCESS	read-write
	STATUS	mandatory
	DESCRIPTION	"The OSPF ASE tag of this link."
	::= { mibinternetProfileEntry 35 }

    internetProfile-IpOptions-OspfOptions-TransitDelay	OBJECT-TYPE
	SYNTAX	INTEGER
	ACCESS	read-write
	STATUS	mandatory
	DESCRIPTION	"The estimated transit delay (seconds)."
	::= { mibinternetProfileEntry 36 }

    internetProfile-IpOptions-OspfOptions-RetransmitInterval	OBJECT-TYPE
	SYNTAX	INTEGER
	ACCESS	read-write
	STATUS	mandatory
	DESCRIPTION	"The retransmit time (seconds)."
	::= { mibinternetProfileEntry 37 }

    internetProfile-IpOptions-OspfOptions-NonMulticast	OBJECT-TYPE
	SYNTAX	INTEGER {
		    no (1),
		    yes (2)
		}
	ACCESS	read-write
	STATUS	mandatory
	DESCRIPTION	"Use direct addresses instead of multicast addresses."
	::= { mibinternetProfileEntry 38 }

    internetProfile-IpOptions-OspfOptions-NetworkType	OBJECT-TYPE
	SYNTAX	INTEGER {
		    broadcast (2),
		    nonBroadcast (3),
		    pointToPoint (4)
		}
	ACCESS	read-write
	STATUS	mandatory
	DESCRIPTION	"The type of network attachment."
	::= { mibinternetProfileEntry 250 }

    internetProfile-IpOptions-OspfOptions-PollInterval	OBJECT-TYPE
	SYNTAX	INTEGER
	ACCESS	read-write
	STATUS	mandatory
	DESCRIPTION	"The poll interval for non-broadcast multi-access network (seconds)."
	::= { mibinternetProfileEntry 251 }

    internetProfile-IpOptions-OspfOptions-Md5AuthKey	OBJECT-TYPE
	SYNTAX	DisplayString
	ACCESS	read-write
	STATUS	mandatory
	DESCRIPTION	"The MD5 authentication key."
	::= { mibinternetProfileEntry 252 }

    internetProfile-IpOptions-MulticastRateLimit	OBJECT-TYPE
	SYNTAX	INTEGER
	ACCESS	read-write
	STATUS	mandatory
	DESCRIPTION	"The multicast rate limit in seconds."
	::= { mibinternetProfileEntry 39 }

    internetProfile-IpOptions-MulticastGroupLeaveDelay	OBJECT-TYPE
	SYNTAX	INTEGER
	ACCESS	read-write
	STATUS	mandatory
	DESCRIPTION	"The multicast group leave in seconds. This is only for IGMP Version 2"
	::= { mibinternetProfileEntry 40 }

    internetProfile-IpOptions-ClientDnsPrimaryAddr	OBJECT-TYPE
	SYNTAX	IpAddress
	ACCESS	read-write
	STATUS	mandatory
	DESCRIPTION	"User specific DNS Primary Address."
	::= { mibinternetProfileEntry 41 }

    internetProfile-IpOptions-ClientDnsSecondaryAddr	OBJECT-TYPE
	SYNTAX	IpAddress
	ACCESS	read-write
	STATUS	mandatory
	DESCRIPTION	"User specific DNS Secondary Address."
	::= { mibinternetProfileEntry 42 }

    internetProfile-IpOptions-ClientDnsAddrAssign	OBJECT-TYPE
	SYNTAX	INTEGER {
		    no (1),
		    yes (2)
		}
	ACCESS	read-write
	STATUS	mandatory
	DESCRIPTION	"A flag to control assigning user specific DNS Addresses."
	::= { mibinternetProfileEntry 43 }

    internetProfile-IpOptions-ClientDefaultGateway	OBJECT-TYPE
	SYNTAX	IpAddress
	ACCESS	read-write
	STATUS	mandatory
	DESCRIPTION	"The default gateway to be used for traffic from this connection, if no specific route is found in the routing table. If left zero, the system's default route will be used."
	::= { mibinternetProfileEntry 44 }

    internetProfile-IpOptions-TosOptions-Active	OBJECT-TYPE
	SYNTAX	INTEGER {
		    no (1),
		    yes (2)
		}
	ACCESS	read-write
	STATUS	mandatory
	DESCRIPTION	"Activate type of service for this connection."
	::= { mibinternetProfileEntry 45 }

    internetProfile-IpOptions-TosOptions-Precedence	OBJECT-TYPE
	SYNTAX	INTEGER {
		    n-000 (1),
		    n-001 (33),
		    n-010 (65),
		    n-011 (97),
		    n-100 (129),
		    n-101 (161),
		    n-110 (193),
		    n-111 (225)
		}
	ACCESS	read-write
	STATUS	mandatory
	DESCRIPTION	"Tag the precedence bits (priority bits) in the TOS octet of IP datagram header with this value when match occurs."
	::= { mibinternetProfileEntry 46 }

    internetProfile-IpOptions-TosOptions-TypeOfService	OBJECT-TYPE
	SYNTAX	INTEGER {
		    normal (1),
		    cost (3),
		    reliability (5),
		    throughput (9),
		    latency (17)
		}
	ACCESS	read-write
	STATUS	mandatory
	DESCRIPTION	"Tag the type of service field in the TOS octet of IP datagram header with this value when match occurs."
	::= { mibinternetProfileEntry 47 }

    internetProfile-IpOptions-TosOptions-ApplyTo	OBJECT-TYPE
	SYNTAX	INTEGER {
		    incoming (1025),
		    outgoing (2049),
		    both (3073)
		}
	ACCESS	read-write
	STATUS	mandatory
	DESCRIPTION	"Define how the type-of-service applies to data flow for this connection."
	::= { mibinternetProfileEntry 48 }

    internetProfile-IpOptions-TosOptions-MarkingType	OBJECT-TYPE
	SYNTAX	INTEGER {
		    precedenceTos (1),
		    dscp (2)
		}
	ACCESS	read-write
	STATUS	mandatory
	DESCRIPTION	"Select type of packet marking."
	::= { mibinternetProfileEntry 459 }

    internetProfile-IpOptions-TosOptions-Dscp	OBJECT-TYPE
	SYNTAX	DisplayString
	ACCESS	read-write
	STATUS	mandatory
	DESCRIPTION	"DSCP tag to be used in marking of the packets (if marking-type = dscp)."
	::= { mibinternetProfileEntry 460 }

    internetProfile-IpOptions-TosFilter	OBJECT-TYPE
	SYNTAX	DisplayString
	ACCESS	read-write
	STATUS	mandatory
	DESCRIPTION	"The name of type-of-service filter. All filters are referenced by name so a name must be assigned to active filters."
	::= { mibinternetProfileEntry 49 }

    internetProfile-IpOptions-ClientWinsPrimaryAddr	OBJECT-TYPE
	SYNTAX	IpAddress
	ACCESS	read-write
	STATUS	mandatory
	DESCRIPTION	"User specific WINS Primary Address."
	::= { mibinternetProfileEntry 293 }

    internetProfile-IpOptions-ClientWinsSecondaryAddr	OBJECT-TYPE
	SYNTAX	IpAddress
	ACCESS	read-write
	STATUS	mandatory
	DESCRIPTION	"User specific WINS Secondary Address."
	::= { mibinternetProfileEntry 294 }

    internetProfile-IpOptions-ClientWinsAddrAssign	OBJECT-TYPE
	SYNTAX	INTEGER {
		    no (1),
		    yes (2)
		}
	ACCESS	read-write
	STATUS	mandatory
	DESCRIPTION	"A flag to control assigning user specific WINS Addresses."
	::= { mibinternetProfileEntry 295 }

    internetProfile-IpOptions-PrivateRouteTable	OBJECT-TYPE
	SYNTAX	DisplayString
	ACCESS	read-write
	STATUS	mandatory
	DESCRIPTION	"Private route table ID for this connection"
	::= { mibinternetProfileEntry 296 }

    internetProfile-IpOptions-PrivateRouteProfileRequired	OBJECT-TYPE
	SYNTAX	INTEGER {
		    no (1),
		    yes (2)
		}
	ACCESS	read-write
	STATUS	mandatory
	DESCRIPTION	"Parameter to decide default action,if private route table not found. If set to yes, the call will be cleared if the private route profile cannot be found. If set to no, the call will be allowed to complete, even if the private route profile cannot be found."
	::= { mibinternetProfileEntry 297 }

    internetProfile-IpOptions-NatProfileName	OBJECT-TYPE
	SYNTAX	DisplayString
	ACCESS	read-write
	STATUS	mandatory
	DESCRIPTION	"The profile to use for NAT translations on this connection."
	::= { mibinternetProfileEntry 419 }

    internetProfile-IpOptions-AddressRealm	OBJECT-TYPE
	SYNTAX	INTEGER
	ACCESS	read-write
	STATUS	mandatory
	DESCRIPTION	"Used to determine which interfaces and WANs are connected to the same address space--they will have the identical values in this field."
	::= { mibinternetProfileEntry 421 }

    internetProfile-IpxOptions-IpxRoutingEnabled	OBJECT-TYPE
	SYNTAX	INTEGER {
		    no (1),
		    yes (2)
		}
	ACCESS	read-write
	STATUS	mandatory
	DESCRIPTION	"Enable/disable IPX routing for this connection."
	::= { mibinternetProfileEntry 50 }

    internetProfile-IpxOptions-PeerMode	OBJECT-TYPE
	SYNTAX	INTEGER {
		    routerPeer (1),
		    dialinPeer (2)
		}
	ACCESS	read-write
	STATUS	mandatory
	DESCRIPTION	"Enable/disable full routing between peer or use the pool to assign a network number."
	::= { mibinternetProfileEntry 51 }

    internetProfile-IpxOptions-Rip	OBJECT-TYPE
	SYNTAX	INTEGER {
		    both (1),
		    send (2),
		    recv (3),
		    off (4)
		}
	ACCESS	read-write
	STATUS	mandatory
	DESCRIPTION	"This field specifies RIP traffic when peer is a Router."
	::= { mibinternetProfileEntry 52 }

    internetProfile-IpxOptions-Sap	OBJECT-TYPE
	SYNTAX	INTEGER {
		    both (1),
		    send (2),
		    recv (3),
		    off (4)
		}
	ACCESS	read-write
	STATUS	mandatory
	DESCRIPTION	"This field specifies SAP traffic when peer is a Router."
	::= { mibinternetProfileEntry 53 }

    internetProfile-IpxOptions-DialQuery	OBJECT-TYPE
	SYNTAX	INTEGER {
		    no (1),
		    yes (2)
		}
	ACCESS	read-write
	STATUS	mandatory
	DESCRIPTION	"Indicate if we should dial to this connection if our SAP table contains no NetWare file servers, and a workstation makes a get-nearest-server query."
	::= { mibinternetProfileEntry 54 }

    internetProfile-IpxOptions-NetNumber	OBJECT-TYPE
	SYNTAX	DisplayString
	ACCESS	read-write
	STATUS	mandatory
	DESCRIPTION	"The network number of the other router. May be zero, if we don't know what it is."
	::= { mibinternetProfileEntry 55 }

    internetProfile-IpxOptions-NetAlias	OBJECT-TYPE
	SYNTAX	DisplayString
	ACCESS	read-write
	STATUS	mandatory
	DESCRIPTION	"The network number of the point to point link."
	::= { mibinternetProfileEntry 56 }

    internetProfile-IpxOptions-SapFilter	OBJECT-TYPE
	SYNTAX	DisplayString
	ACCESS	read-write
	STATUS	mandatory
	DESCRIPTION	"The name of the IPX SAP filter, if any, to use with this connection."
	::= { mibinternetProfileEntry 57 }

    internetProfile-IpxOptions-IpxSpoofing	OBJECT-TYPE
	SYNTAX	INTEGER {
		    none (1),
		    clientSpoofing (2),
		    serverSpoofing (3)
		}
	ACCESS	read-write
	STATUS	mandatory
	DESCRIPTION	"Selects the IPX spoofing mode when bridging."
	::= { mibinternetProfileEntry 58 }

    internetProfile-IpxOptions-SpoofingTimeout	OBJECT-TYPE
	SYNTAX	INTEGER
	ACCESS	read-write
	STATUS	mandatory
	DESCRIPTION	"IPX NetWare connection timeout value."
	::= { mibinternetProfileEntry 59 }

    internetProfile-IpxOptions-IpxSapHsProxy	OBJECT-TYPE
	SYNTAX	INTEGER {
		    no (1),
		    yes (2)
		}
	ACCESS	read-write
	STATUS	mandatory
	DESCRIPTION	"Use IPX SAP Home Server Proxy."
	::= { mibinternetProfileEntry 60 }

    internetProfile-IpxOptions-IpxHeaderCompression	OBJECT-TYPE
	SYNTAX	INTEGER {
		    no (1),
		    yes (2)
		}
	ACCESS	read-write
	STATUS	mandatory
	DESCRIPTION	"Use IPX header compression if encapsulation supports it."
	::= { mibinternetProfileEntry 61 }

    internetProfile-BridgingOptions-BridgingGroup	OBJECT-TYPE
	SYNTAX	INTEGER
	ACCESS	read-write
	STATUS	mandatory
	DESCRIPTION	"Select the bridging group for this connection. Group 0 disables bridging. All packets not routed will be bridged to interfaces belonging to the same group."
	::= { mibinternetProfileEntry 62 }

    internetProfile-BridgingOptions-DialOnBroadcast	OBJECT-TYPE
	SYNTAX	INTEGER {
		    no (1),
		    yes (2)
		}
	ACCESS	read-write
	STATUS	mandatory
	DESCRIPTION	"Enable/disable outdial when broadcast frames are received."
	::= { mibinternetProfileEntry 63 }

    internetProfile-BridgingOptions-IpxSpoofing	OBJECT-TYPE
	SYNTAX	INTEGER {
		    none (1),
		    clientSpoofing (2),
		    serverSpoofing (3)
		}
	ACCESS	read-write
	STATUS	mandatory
	DESCRIPTION	"Selects the IPX spoofing mode when bridging."
	::= { mibinternetProfileEntry 64 }

    internetProfile-BridgingOptions-SpoofingTimeout	OBJECT-TYPE
	SYNTAX	INTEGER
	ACCESS	read-write
	STATUS	mandatory
	DESCRIPTION	"IPX NetWare connection timeout value."
	::= { mibinternetProfileEntry 65 }

    internetProfile-BridgingOptions-Fill2	OBJECT-TYPE
	SYNTAX	INTEGER
	ACCESS	read-only
	STATUS	mandatory
	DESCRIPTION	"filler to get to 32 bit boundary"
	::= { mibinternetProfileEntry 253 }

    internetProfile-BridgingOptions-BridgeType	OBJECT-TYPE
	SYNTAX	INTEGER {
		    transparentBridging (1),
		    ipxClientBridging (2),
		    noBridging (3)
		}
	ACCESS	read-write
	STATUS	mandatory
	DESCRIPTION	"For the P25 user interface."
	::= { mibinternetProfileEntry 66 }

    internetProfile-BridgingOptions-Egress	OBJECT-TYPE
	SYNTAX	INTEGER {
		    no (1),
		    yes (2)
		}
	ACCESS	read-write
	STATUS	mandatory
	DESCRIPTION	"Enable/disable Egress on this interface. This interface will become the exit path for all packets destined to the network."
	::= { mibinternetProfileEntry 285 }

    internetProfile-SessionOptions-CallFilter	OBJECT-TYPE
	SYNTAX	DisplayString
	ACCESS	read-write
	STATUS	mandatory
	DESCRIPTION	"The name of the filter used to determine if a packet should cause the idle timer to be reset or, when the answer profile is used for connection profile defaults, if a call should be placed."
	::= { mibinternetProfileEntry 67 }

    internetProfile-SessionOptions-DataFilter	OBJECT-TYPE
	SYNTAX	DisplayString
	ACCESS	read-write
	STATUS	mandatory
	DESCRIPTION	"The name of the filter used to determine if packets should be forwarded or dropped."
	::= { mibinternetProfileEntry 68 }

    internetProfile-SessionOptions-FilterPersistence	OBJECT-TYPE
	SYNTAX	INTEGER {
		    no (1),
		    yes (2)
		}
	ACCESS	read-write
	STATUS	mandatory
	DESCRIPTION	"Determines if filters should persist between calls."
	::= { mibinternetProfileEntry 69 }

    internetProfile-SessionOptions-FilterRequired	OBJECT-TYPE
	SYNTAX	INTEGER {
		    no (1),
		    yes (2)
		}
	ACCESS	read-write
	STATUS	mandatory
	DESCRIPTION	"If No, the call will be allowed to come up even if the specified filter was not found either locally, in the cache or in RADIUS. If Yes, then the call will be cleared if the specified filter was not found either locally, in the cache or in RADIUS."
	::= { mibinternetProfileEntry 298 }

    internetProfile-SessionOptions-IdleTimer	OBJECT-TYPE
	SYNTAX	INTEGER
	ACCESS	read-write
	STATUS	mandatory
	DESCRIPTION	"The number of seconds of no activity before a call will be dropped. The value 0 disables the idle timer."
	::= { mibinternetProfileEntry 70 }

    internetProfile-SessionOptions-TsIdleMode	OBJECT-TYPE
	SYNTAX	INTEGER {
		    noIdle (1),
		    inputOnlyIdle (2),
		    inputOutputIdle (3)
		}
	ACCESS	read-write
	STATUS	mandatory
	DESCRIPTION	"The method used to determine when the terminal server idle session timer is reset."
	::= { mibinternetProfileEntry 71 }

    internetProfile-SessionOptions-TsIdleTimer	OBJECT-TYPE
	SYNTAX	INTEGER
	ACCESS	read-write
	STATUS	mandatory
	DESCRIPTION	"The number of seconds of no activity as defined by the idle mode before a session will be terminated."
	::= { mibinternetProfileEntry 72 }

    internetProfile-SessionOptions-Backup	OBJECT-TYPE
	SYNTAX	DisplayString
	ACCESS	read-write
	STATUS	mandatory
	DESCRIPTION	"Name of the backup connection profile."
	::= { mibinternetProfileEntry 73 }

    internetProfile-SessionOptions-Secondary	OBJECT-TYPE
	SYNTAX	DisplayString
	ACCESS	read-write
	STATUS	mandatory
	DESCRIPTION	"A secondary internet profile used for dial back-up support."
	::= { mibinternetProfileEntry 74 }

    internetProfile-SessionOptions-MaxCallDuration	OBJECT-TYPE
	SYNTAX	INTEGER
	ACCESS	read-write
	STATUS	mandatory
	DESCRIPTION	"The number of minutes of connect time before a call will be dropped. The value 0 disables the connection timer."
	::= { mibinternetProfileEntry 76 }

    internetProfile-SessionOptions-VtpGateway	OBJECT-TYPE
	SYNTAX	INTEGER {
		    no (1),
		    yes (2)
		}
	ACCESS	read-write
	STATUS	mandatory
	DESCRIPTION	"This profile is an VTP gateway connection to an mobile client's home network."
	::= { mibinternetProfileEntry 77 }

    internetProfile-SessionOptions-Blockcountlimit	OBJECT-TYPE
	SYNTAX	INTEGER
	ACCESS	read-write
	STATUS	mandatory
	DESCRIPTION	"Maximum number of failed attempts allowed for connection before blocking the call."
	::= { mibinternetProfileEntry 78 }

    internetProfile-SessionOptions-Blockduration	OBJECT-TYPE
	SYNTAX	INTEGER
	ACCESS	read-write
	STATUS	mandatory
	DESCRIPTION	"Number of seconds that connection attempts to non responding network will be blocked before allowing retries."
	::= { mibinternetProfileEntry 79 }

    internetProfile-SessionOptions-MaxVtpTunnels	OBJECT-TYPE
	SYNTAX	INTEGER
	ACCESS	read-write
	STATUS	mandatory
	DESCRIPTION	"If this profile is a VTP gateway, then this parameter specifies the maximum number of VTP tunnels allowed to the VTP home network specified by the name of this profile."
	::= { mibinternetProfileEntry 81 }

    internetProfile-SessionOptions-RedialDelayLimit	OBJECT-TYPE
	SYNTAX	INTEGER
	ACCESS	read-write
	STATUS	mandatory
	DESCRIPTION	"Number of seconds delay before allowing a redial"
	::= { mibinternetProfileEntry 82 }

    internetProfile-SessionOptions-SesRateType	OBJECT-TYPE
	SYNTAX	INTEGER {
		    disabled (1),
		    sdsl (2),
		    adslCap (3),
		    adslCell (4),
		    adslDmt (5)
		}
	ACCESS	read-write
	STATUS	mandatory
	DESCRIPTION	"The per ses rate type."
	::= { mibinternetProfileEntry 83 }

    internetProfile-SessionOptions-SesRateMode	OBJECT-TYPE
	SYNTAX	INTEGER {
		    autobaud (2),
		    singlebaud (3)
		}
	ACCESS	read-write
	STATUS	mandatory
	DESCRIPTION	"The per ses rate mode."
	::= { mibinternetProfileEntry 84 }

    internetProfile-SessionOptions-SesAdslCapUpRate	OBJECT-TYPE
	SYNTAX	INTEGER {
		    n-1088000 (51),
		    n-952000 (52),
		    n-816000 (53),
		    n-680000 (54),
		    n-544000 (55),
		    n-408000 (56),
		    n-272000 (57)
		}
	ACCESS	read-write
	STATUS	mandatory
	DESCRIPTION	"The per session adsl-cap up stream data rate"
	::= { mibinternetProfileEntry 85 }

    internetProfile-SessionOptions-SesAdslCapDownRate	OBJECT-TYPE
	SYNTAX	INTEGER {
		    n-7168000 (1),
		    n-6272000 (2),
		    n-5120000 (3),
		    n-4480000 (4),
		    n-3200000 (5),
		    n-2688000 (6),
		    n-2560000 (7),
		    n-2240000 (8),
		    n-1920000 (9),
		    n-1600000 (10),
		    n-1280000 (11),
		    n-960000 (12),
		    n-640000 (13)
		}
	ACCESS	read-write
	STATUS	mandatory
	DESCRIPTION	"The per session adsl-cap down stream data rate"
	::= { mibinternetProfileEntry 86 }

    internetProfile-SessionOptions-SesSdslRate	OBJECT-TYPE
	SYNTAX	INTEGER {
		    n-144000 (1),
		    n-272000 (2),
		    n-400000 (3),
		    n-528000 (4),
		    n-784000 (5),
		    n-1168000 (6),
		    n-1552000 (7),
		    n-2320000 (8),
		    n-160000 (9),
		    n-192000 (10),
		    n-208000 (11),
		    n-384000 (12),
		    n-416000 (13),
		    n-768000 (14),
		    n-1040000 (15),
		    n-1152000 (16),
		    n-1536000 (17),
		    n-1568000 (18),
		    n-1680000 (19),
		    n-1920000 (20),
		    n-2160000 (21)
		}
	ACCESS	read-write
	STATUS	mandatory
	DESCRIPTION	"The per session symetrical data rate. This parameter does not pertain to the old 16 port sdsl card."
	::= { mibinternetProfileEntry 87 }

    internetProfile-SessionOptions-SesAdslDmtUpRate	OBJECT-TYPE
	SYNTAX	INTEGER {
		    upstrmMegMax (151),
		    n-1088000 (152),
		    n-928000 (153),
		    n-896000 (154),
		    n-800000 (155),
		    n-768000 (156),
		    n-640000 (157),
		    n-512000 (158),
		    n-384000 (159),
		    n-256000 (160),
		    n-128000 (161)
		}
	ACCESS	read-write
	STATUS	mandatory
	DESCRIPTION	"The per session adsl-dmt up stream data rate"
	::= { mibinternetProfileEntry 88 }

    internetProfile-SessionOptions-SesAdslDmtDownRate	OBJECT-TYPE
	SYNTAX	INTEGER {
		    dwnstrmMegMax (101),
		    n-9504000 (102),
		    n-8960000 (103),
		    n-8000000 (104),
		    n-7168000 (105),
		    n-6272000 (106),
		    n-5120000 (107),
		    n-4480000 (108),
		    n-3200000 (109),
		    n-2688000 (110),
		    n-2560000 (111),
		    n-2240000 (112),
		    n-1920000 (113),
		    n-1600000 (114),
		    n-1280000 (115),
		    n-960000 (116),
		    n-768000 (117),
		    n-640000 (118),
		    n-512000 (119),
		    n-384000 (120),
		    n-256000 (121),
		    n-128000 (122)
		}
	ACCESS	read-write
	STATUS	mandatory
	DESCRIPTION	"The per session adsl-dmt down stream data rate"
	::= { mibinternetProfileEntry 89 }

    internetProfile-SessionOptions-RxDataRateLimit	OBJECT-TYPE
	SYNTAX	INTEGER
	ACCESS	read-write
	STATUS	mandatory
	DESCRIPTION	"The maximum information rate to be received from the named station (kbps)."
	::= { mibinternetProfileEntry 90 }

    internetProfile-SessionOptions-TxDataRateLimit	OBJECT-TYPE
	SYNTAX	INTEGER
	ACCESS	read-write
	STATUS	mandatory
	DESCRIPTION	"The maximum information rate to be transmitted to the named station (kbps)."
	::= { mibinternetProfileEntry 91 }

    internetProfile-SessionOptions-CirTimer	OBJECT-TYPE
	SYNTAX	INTEGER
	ACCESS	read-write
	STATUS	mandatory
	DESCRIPTION	"The CIR timer in (milli-sec)."
	::= { mibinternetProfileEntry 414 }

    internetProfile-SessionOptions-TrafficShaper	OBJECT-TYPE
	SYNTAX	INTEGER
	ACCESS	read-write
	STATUS	mandatory
	DESCRIPTION	"The traffic shaper assigned to this profile."
	::= { mibinternetProfileEntry 286 }

    internetProfile-SessionOptions-MaxtapLogServer	OBJECT-TYPE
	SYNTAX	DisplayString
	ACCESS	read-write
	STATUS	mandatory
	DESCRIPTION	"The name or the IP Address of the host to which the MaxTap start/stop notifications has to be sent."
	::= { mibinternetProfileEntry 299 }

    internetProfile-SessionOptions-MaxtapDataServer	OBJECT-TYPE
	SYNTAX	DisplayString
	ACCESS	read-write
	STATUS	mandatory
	DESCRIPTION	"The name or the IP Address of the host to which the tapped data has to be sent."
	::= { mibinternetProfileEntry 300 }

    internetProfile-SessionOptions-Priority	OBJECT-TYPE
	SYNTAX	INTEGER {
		    normal (1),
		    high (2)
		}
	ACCESS	read-write
	STATUS	mandatory
	DESCRIPTION	"Priority of the link"
	::= { mibinternetProfileEntry 415 }

    internetProfile-TelcoOptions-AnswerOriginate	OBJECT-TYPE
	SYNTAX	INTEGER {
		    ansAndOrig (1),
		    answerOnly (2),
		    originateOnly (3)
		}
	ACCESS	read-write
	STATUS	mandatory
	DESCRIPTION	"Specifies if this profile can be used for incoming calls, outgoing calls, or both."
	::= { mibinternetProfileEntry 92 }

    internetProfile-TelcoOptions-Callback	OBJECT-TYPE
	SYNTAX	INTEGER {
		    no (1),
		    yes (2)
		}
	ACCESS	read-write
	STATUS	mandatory
	DESCRIPTION	"When true a call received from the named host requires callback security. The number dialed is the phoneNumber from this connection profile."
	::= { mibinternetProfileEntry 93 }

    internetProfile-TelcoOptions-CallType	OBJECT-TYPE
	SYNTAX	INTEGER {
		    off (1),
		    ft1 (2),
		    ft1Mpp (3),
		    bri (4),
		    ft1Bo (5),
		    dChan (6),
		    aodi (7),
		    megamax (8)
		}
	ACCESS	read-write
	STATUS	mandatory
	DESCRIPTION	"Nailed channel usage for this connection."
	::= { mibinternetProfileEntry 94 }

    internetProfile-TelcoOptions-NailedGroups	OBJECT-TYPE
	SYNTAX	DisplayString
	ACCESS	read-write
	STATUS	mandatory
	DESCRIPTION	"All the nailed groups belonging to a session. MPP supports multiple groups."
	::= { mibinternetProfileEntry 95 }

    internetProfile-TelcoOptions-Ft1Caller	OBJECT-TYPE
	SYNTAX	INTEGER {
		    no (1),
		    yes (2)
		}
	ACCESS	read-write
	STATUS	mandatory
	DESCRIPTION	"Specifies if this side should initiate calls when a mix of nailed and switched calls are being used."
	::= { mibinternetProfileEntry 96 }

    internetProfile-TelcoOptions-Force56kbps	OBJECT-TYPE
	SYNTAX	INTEGER {
		    no (1),
		    yes (2)
		}
	ACCESS	read-write
	STATUS	mandatory
	DESCRIPTION	"If yes then inbound 64 kbps calls are connected at 56 kbps."
	::= { mibinternetProfileEntry 97 }

    internetProfile-TelcoOptions-DataService	OBJECT-TYPE
	SYNTAX	INTEGER {
		    voice (1),
		    n-56kRestricted (2),
		    n-64kClear (3),
		    n-64kRestricted (4),
		    n-56kClear (5),
		    n-384kRestricted (6),
		    n-384kClear (7),
		    n-1536kClear (8),
		    n-1536kRestricted (9),
		    n-128kClear (10),
		    n-192kClear (11),
		    n-256kClear (12),
		    n-320kClear (13),
		    dws384Clear (14),
		    n-448Clear (15),
		    n-512Clear (16),
		    n-576Clear (17),
		    n-640Clear (18),
		    n-704Clear (19),
		    n-768Clear (20),
		    n-832Clear (21),
		    n-896Clear (22),
		    n-960Clear (23),
		    n-1024Clear (24),
		    n-1088Clear (25),
		    n-1152Clear (26),
		    n-1216Clear (27),
		    n-1280Clear (28),
		    n-1344Clear (29),
		    n-1408Clear (30),
		    n-1472Clear (31),
		    n-1600Clear (32),
		    n-1664Clear (33),
		    n-1728Clear (34),
		    n-1792Clear (35),
		    n-1856Clear (36),
		    n-1920Clear (37),
		    x30RestrictedBearer (39),
		    v110ClearBearer (40),
		    n-64kX30Restricted (41),
		    n-56kV110Clear (42),
		    modem (43),
		    atmodem (44),
		    n-2456kV110 (46),
		    n-4856kV110 (47),
		    n-9656kV110 (48),
		    n-19256kV110 (49),
		    n-38456kV110 (50),
		    n-2456krV110 (51),
		    n-4856krV110 (52),
		    n-9656krV110 (53),
		    n-19256krV110 (54),
		    n-38456krV110 (55),
		    n-2464kV110 (56),
		    n-4864kV110 (57),
		    n-9664kV110 (58),
		    n-19264kV110 (59),
		    n-38464kV110 (60),
		    n-2464krV110 (61),
		    n-4864krV110 (62),
		    n-9664krV110 (63),
		    n-19264krV110 (64),
		    n-38464krV110 (65),
		    v32 (66),
		    phs64k (67),
		    voiceOverIp (68),
		    atmSvc (70),
		    frameRelaySvc (71),
		    vpnTunnel (72),
		    wormarq (73),
		    n-14456kV110 (74),
		    n-28856kV110 (75),
		    n-14456krV110 (76),
		    n-28856krV110 (77),
		    n-14464kV110 (78),
		    n-28864kV110 (79),
		    n-14464krV110 (80),
		    n-28864krV110 (81),
		    modem31khzAudio (82),
		    x25Svc (83),
		    n-144kClear (255),
		    iptoip (263)
		}
	ACCESS	read-write
	STATUS	mandatory
	DESCRIPTION	"The type of bearer channel capability to set up for each switched call in the session."
	::= { mibinternetProfileEntry 98 }

    internetProfile-TelcoOptions-CallByCall	OBJECT-TYPE
	SYNTAX	INTEGER
	ACCESS	read-write
	STATUS	mandatory
	DESCRIPTION	"The call-by-call signaling value for PRI lines."
	::= { mibinternetProfileEntry 99 }

    internetProfile-TelcoOptions-BillingNumber	OBJECT-TYPE
	SYNTAX	DisplayString
	ACCESS	read-write
	STATUS	mandatory
	DESCRIPTION	"A number used for billing purposes. This number, if present, is used as either a 'billing suffix' or the 'calling party number'."
	::= { mibinternetProfileEntry 100 }

    internetProfile-TelcoOptions-TransitNumber	OBJECT-TYPE
	SYNTAX	DisplayString
	ACCESS	read-write
	STATUS	mandatory
	DESCRIPTION	"The string for use in the 'transit network IE' for PRI calling when going through a LEC."
	::= { mibinternetProfileEntry 101 }

    internetProfile-TelcoOptions-ExpectCallback	OBJECT-TYPE
	SYNTAX	INTEGER {
		    no (1),
		    yes (2)
		}
	ACCESS	read-write
	STATUS	mandatory
	DESCRIPTION	"When true we expect calls to the named host will result in a callback from that host. This would occur if the remote host were authenticating us based on Caller ID."
	::= { mibinternetProfileEntry 102 }

    internetProfile-TelcoOptions-DialoutAllowed	OBJECT-TYPE
	SYNTAX	INTEGER {
		    no (1),
		    yes (2)
		}
	ACCESS	read-write
	STATUS	mandatory
	DESCRIPTION	"When true, this connection is allowed to use the LAN modems to place outgoing calls."
	::= { mibinternetProfileEntry 103 }

    internetProfile-TelcoOptions-DelayCallback	OBJECT-TYPE
	SYNTAX	INTEGER
	ACCESS	read-write
	STATUS	mandatory
	DESCRIPTION	"Number of seconds to delay before dialing back. Values of 0-3 seconds are treated as 3 seconds."
	::= { mibinternetProfileEntry 104 }

    internetProfile-TelcoOptions-NasPortType	OBJECT-TYPE
	SYNTAX	INTEGER {
		    async (4),
		    sync (5),
		    isdnSync (6),
		    v120IsdnAsync (7),
		    v110IsdnAsync (8),
		    virtual (9),
		    v32IsdnAsync (10),
		    vdspAsyncIsdn (11),
		    arqPdcIsdn (12),
		    any (1),
		    digital (2),
		    analog (3)
		}
	ACCESS	read-write
	STATUS	mandatory
	DESCRIPTION	"Indicates the type of physical port being used."
	::= { mibinternetProfileEntry 254 }

    internetProfile-PppOptions-SendAuthMode	OBJECT-TYPE
	SYNTAX	INTEGER {
		    noPppAuth (1),
		    papPppAuth (2),
		    chapPppAuth (3),
		    anyPppAuth (4),
		    desPapPppAuth (5),
		    tokenPapPppAuth (6),
		    tokenChapPppAuth (7),
		    cacheTokenPppAuth (8),
		    msChapPppAuth (9),
		    papPreferred (10)
		}
	ACCESS	read-write
	STATUS	mandatory
	DESCRIPTION	"The type of PPP authentication to use for this call."
	::= { mibinternetProfileEntry 105 }

    internetProfile-PppOptions-PppCircuit	OBJECT-TYPE
	SYNTAX	INTEGER {
		    none (1),
		    transparent (2)
		}
	ACCESS	read-write
	STATUS	mandatory
	DESCRIPTION	"PPP Circuit. Set to type to enable the PPP Circuit Mode."
	::= { mibinternetProfileEntry 422 }

    internetProfile-PppOptions-PppCircuitName	OBJECT-TYPE
	SYNTAX	DisplayString
	ACCESS	read-write
	STATUS	mandatory
	DESCRIPTION	"The peer datalink identifier for a PPP circuit."
	::= { mibinternetProfileEntry 423 }

    internetProfile-PppOptions-BiDirectionalAuth	OBJECT-TYPE
	SYNTAX	INTEGER {
		    none (1),
		    allowed (2),
		    required (3)
		}
	ACCESS	read-write
	STATUS	mandatory
	DESCRIPTION	"This parameter enables the authentication to be done in both directions. It can be used only with CHAP or MS-CHAP authentication."
	::= { mibinternetProfileEntry 354 }

    internetProfile-PppOptions-SendPassword	OBJECT-TYPE
	SYNTAX	DisplayString
	ACCESS	read-write
	STATUS	mandatory
	DESCRIPTION	"This is the password sent to the far end; used for MPP and PPP PAP and CHAP security."
	::= { mibinternetProfileEntry 106 }

    internetProfile-PppOptions-SubstituteSendName	OBJECT-TYPE
	SYNTAX	DisplayString
	ACCESS	read-write
	STATUS	mandatory
	DESCRIPTION	"Name send to the far end, if different from the global system name."
	::= { mibinternetProfileEntry 107 }

    internetProfile-PppOptions-RecvPassword	OBJECT-TYPE
	SYNTAX	DisplayString
	ACCESS	read-write
	STATUS	mandatory
	DESCRIPTION	"This is the password received from the far end; used for MPP and PPP PAP and CHAP security."
	::= { mibinternetProfileEntry 108 }

    internetProfile-PppOptions-SubstituteRecvName	OBJECT-TYPE
	SYNTAX	DisplayString
	ACCESS	read-write
	STATUS	mandatory
	DESCRIPTION	"Name expected from the far end used during a bi-directional authentication. If it is null the profile name will be used in place. This parameter is used only for outgoing calls."
	::= { mibinternetProfileEntry 355 }

    internetProfile-PppOptions-LinkCompression	OBJECT-TYPE
	SYNTAX	INTEGER {
		    none (1),
		    stac (2),
		    stac9 (3),
		    msStac (4),
		    mppc (5)
		}
	ACCESS	read-write
	STATUS	mandatory
	DESCRIPTION	"The type of link compression to use for PPP, MP, and MPP calls."
	::= { mibinternetProfileEntry 109 }

    internetProfile-PppOptions-Mru	OBJECT-TYPE
	SYNTAX	INTEGER
	ACCESS	read-write
	STATUS	mandatory
	DESCRIPTION	"The Maximum Receive Unit, i.e. the largest frame we will accept."
	::= { mibinternetProfileEntry 110 }

    internetProfile-PppOptions-Lqm	OBJECT-TYPE
	SYNTAX	INTEGER {
		    no (1),
		    yes (2)
		}
	ACCESS	read-write
	STATUS	mandatory
	DESCRIPTION	"Link Quality Monitoring. Set to Yes to enable the PPP LQM protocol."
	::= { mibinternetProfileEntry 111 }

    internetProfile-PppOptions-LqmMinimumPeriod	OBJECT-TYPE
	SYNTAX	INTEGER
	ACCESS	read-write
	STATUS	mandatory
	DESCRIPTION	"The minimum period, in 1/100 of a second, that we will accept/send link quality monitoring packets."
	::= { mibinternetProfileEntry 112 }

    internetProfile-PppOptions-LqmMaximumPeriod	OBJECT-TYPE
	SYNTAX	INTEGER
	ACCESS	read-write
	STATUS	mandatory
	DESCRIPTION	"The maximum period, in 1/100 of a second, that we will accept/send link quality monitoring packets."
	::= { mibinternetProfileEntry 113 }

    internetProfile-PppOptions-CbcpEnabled	OBJECT-TYPE
	SYNTAX	INTEGER {
		    no (1),
		    yes (2)
		}
	ACCESS	read-write
	STATUS	mandatory
	DESCRIPTION	"Enable Microsoft Callback Control Protocol Negotiation."
	::= { mibinternetProfileEntry 114 }

    internetProfile-PppOptions-ModeCallbackControl	OBJECT-TYPE
	SYNTAX	INTEGER {
		    cbcpNoCallback (2),
		    cbcpUserNumber (3),
		    cbcpProfileNum (4),
		    cbcpAll (8)
		}
	ACCESS	read-write
	STATUS	mandatory
	DESCRIPTION	"CBCP operation allowed on to use for this call."
	::= { mibinternetProfileEntry 115 }

    internetProfile-PppOptions-DelayCallbackControl	OBJECT-TYPE
	SYNTAX	INTEGER
	ACCESS	read-write
	STATUS	mandatory
	DESCRIPTION	"Delay to request before callback to us is initiated"
	::= { mibinternetProfileEntry 116 }

    internetProfile-PppOptions-TrunkGroupCallbackControl	OBJECT-TYPE
	SYNTAX	INTEGER
	ACCESS	read-write
	STATUS	mandatory
	DESCRIPTION	"Trunk group to use for the callback."
	::= { mibinternetProfileEntry 117 }

    internetProfile-PppOptions-SplitCodeDotUserEnabled	OBJECT-TYPE
	SYNTAX	INTEGER {
		    no (1),
		    yes (2)
		}
	ACCESS	read-write
	STATUS	mandatory
	DESCRIPTION	"TRUE if local splitting of passwords is desired in CACHE-TOKEN. This feature permits the use of usernames longer than five chars, when using a typical 4 digit pin and 6 digit ACE token code."
	::= { mibinternetProfileEntry 118 }

    internetProfile-PppOptions-PppInterfaceType	OBJECT-TYPE
	SYNTAX	INTEGER {
		    hdlcLike (1),
		    frameRelay (2),
		    aal5 (3),
		    x25 (4)
		}
	ACCESS	read-write
	STATUS	mandatory
	DESCRIPTION	"PPP network interface for this profile."
	::= { mibinternetProfileEntry 119 }

    internetProfile-PppOptions-Mtu	OBJECT-TYPE
	SYNTAX	INTEGER
	ACCESS	read-write
	STATUS	mandatory
	DESCRIPTION	"The Maximum Transmit Unit, i.e. the largest frame we will transmit."
	::= { mibinternetProfileEntry 301 }

    internetProfile-MpOptions-BaseChannelCount	OBJECT-TYPE
	SYNTAX	INTEGER
	ACCESS	read-write
	STATUS	mandatory
	DESCRIPTION	"When the session is initially set up, and if it is a fixed session, the number of channels to be used for the call."
	::= { mibinternetProfileEntry 120 }

    internetProfile-MpOptions-MinimumChannels	OBJECT-TYPE
	SYNTAX	INTEGER
	ACCESS	read-write
	STATUS	mandatory
	DESCRIPTION	"The default value for the minimum number of channels in a multi-channel call."
	::= { mibinternetProfileEntry 121 }

    internetProfile-MpOptions-MaximumChannels	OBJECT-TYPE
	SYNTAX	INTEGER
	ACCESS	read-write
	STATUS	mandatory
	DESCRIPTION	"The default value for the maximum number of channels in a multi-channel call."
	::= { mibinternetProfileEntry 122 }

    internetProfile-MpOptions-BacpEnable	OBJECT-TYPE
	SYNTAX	INTEGER {
		    no (1),
		    yes (2)
		}
	ACCESS	read-write
	STATUS	mandatory
	DESCRIPTION	"Enable Bandwidth Allocation Control Protocol (BACP)."
	::= { mibinternetProfileEntry 123 }

    internetProfile-MpOptions-BodEnable	OBJECT-TYPE
	SYNTAX	INTEGER {
		    no (1),
		    yes (2)
		}
	ACCESS	read-write
	STATUS	mandatory
	DESCRIPTION	"Enable Bandwidth On Demand."
	::= { mibinternetProfileEntry 255 }

    internetProfile-MpOptions-CallbackrequestEnable	OBJECT-TYPE
	SYNTAX	INTEGER {
		    no (1),
		    yes (2)
		}
	ACCESS	read-write
	STATUS	mandatory
	DESCRIPTION	"Allow BAP CallBackRequest."
	::= { mibinternetProfileEntry 284 }

    internetProfile-MppOptions-AuxSendPassword	OBJECT-TYPE
	SYNTAX	DisplayString
	ACCESS	read-write
	STATUS	mandatory
	DESCRIPTION	"This is the password sent to the far end; used for MPP PAP-TOKEN-CHAP security."
	::= { mibinternetProfileEntry 124 }

    internetProfile-MppOptions-DynamicAlgorithm	OBJECT-TYPE
	SYNTAX	INTEGER {
		    constant (1),
		    linear (2),
		    quadratic (3)
		}
	ACCESS	read-write
	STATUS	mandatory
	DESCRIPTION	"The algorithm to use to calculate the average link utilization. Bandwidth changes are performed on the average utilization, not current utilization."
	::= { mibinternetProfileEntry 125 }

    internetProfile-MppOptions-BandwidthMonitorDirection	OBJECT-TYPE
	SYNTAX	INTEGER {
		    transmit (1),
		    transmitRecv (2),
		    none (3)
		}
	ACCESS	read-write
	STATUS	mandatory
	DESCRIPTION	"The direction to monitor link utilization. A unit can monitor transmit, transmit and receive, or turn off monitoring entirely."
	::= { mibinternetProfileEntry 126 }

    internetProfile-MppOptions-IncrementChannelCount	OBJECT-TYPE
	SYNTAX	INTEGER
	ACCESS	read-write
	STATUS	mandatory
	DESCRIPTION	"Number of channels to increment as a block."
	::= { mibinternetProfileEntry 127 }

    internetProfile-MppOptions-DecrementChannelCount	OBJECT-TYPE
	SYNTAX	INTEGER
	ACCESS	read-write
	STATUS	mandatory
	DESCRIPTION	"Number of channels to decrement as a block."
	::= { mibinternetProfileEntry 128 }

    internetProfile-MppOptions-SecondsHistory	OBJECT-TYPE
	SYNTAX	INTEGER
	ACCESS	read-write
	STATUS	mandatory
	DESCRIPTION	"The number of seconds of history that link utilization is averaged over to make bandwidth changes."
	::= { mibinternetProfileEntry 129 }

    internetProfile-MppOptions-AddPersistence	OBJECT-TYPE
	SYNTAX	INTEGER
	ACCESS	read-write
	STATUS	mandatory
	DESCRIPTION	"The number of seconds of that the average line utilization must exceed the target utilization before bandwidth will be added."
	::= { mibinternetProfileEntry 130 }

    internetProfile-MppOptions-SubPersistence	OBJECT-TYPE
	SYNTAX	INTEGER
	ACCESS	read-write
	STATUS	mandatory
	DESCRIPTION	"The number of seconds of that the average line utilization must fall below the target utilization before bandwidth will be reduced. Bandwidth will not be reduced if the reduced bandwidth would exceed the target utilization."
	::= { mibinternetProfileEntry 131 }

    internetProfile-MppOptions-TargetUtilization	OBJECT-TYPE
	SYNTAX	INTEGER
	ACCESS	read-write
	STATUS	mandatory
	DESCRIPTION	"The default value for the target utilization. Bandwidth changes occur when the average utilization exceeds or falls below this value."
	::= { mibinternetProfileEntry 132 }

    internetProfile-MppOptions-X25chanTargetUtilization	OBJECT-TYPE
	SYNTAX	INTEGER
	ACCESS	read-write
	STATUS	mandatory
	DESCRIPTION	"The default value for the X25 channel target utilization. Bandwidth changes occur when the average utilization exceeds or falls below this value."
	::= { mibinternetProfileEntry 380 }

    internetProfile-FrOptions-FrameRelayProfile	OBJECT-TYPE
	SYNTAX	DisplayString
	ACCESS	read-write
	STATUS	mandatory
	DESCRIPTION	"Frame Relay profile name, specifies link over which this circuit is established."
	::= { mibinternetProfileEntry 133 }

    internetProfile-FrOptions-CircuitType	OBJECT-TYPE
	SYNTAX	INTEGER {
		    pvc (1),
		    svc (2)
		}
	ACCESS	read-write
	STATUS	mandatory
	DESCRIPTION	"The type of circuit, permanent (PVC) or switched (SVC)."
	::= { mibinternetProfileEntry 302 }

    internetProfile-FrOptions-Dlci	OBJECT-TYPE
	SYNTAX	INTEGER
	ACCESS	read-write
	STATUS	mandatory
	DESCRIPTION	"The assigned DLCI value for this connection, for PVC."
	::= { mibinternetProfileEntry 134 }

    internetProfile-FrOptions-CircuitName	OBJECT-TYPE
	SYNTAX	DisplayString
	ACCESS	read-write
	STATUS	mandatory
	DESCRIPTION	"The peer frame relay datalink for a FR circuit."
	::= { mibinternetProfileEntry 135 }

    internetProfile-FrOptions-FrLinkType	OBJECT-TYPE
	SYNTAX	INTEGER {
		    transparentLink (1),
		    hostLink (2),
		    trunkLink (3)
		}
	ACCESS	read-write
	STATUS	mandatory
	DESCRIPTION	"The frame relay link type."
	::= { mibinternetProfileEntry 303 }

    internetProfile-FrOptions-FrDirectEnabled	OBJECT-TYPE
	SYNTAX	INTEGER {
		    no (1),
		    yes (2)
		}
	ACCESS	read-write
	STATUS	mandatory
	DESCRIPTION	"Enable the frame relay direct option for this connection."
	::= { mibinternetProfileEntry 136 }

    internetProfile-FrOptions-FrDirectProfile	OBJECT-TYPE
	SYNTAX	DisplayString
	ACCESS	read-write
	STATUS	mandatory
	DESCRIPTION	"Name of the frame relay profile that will be used for frame-relay-direct routing."
	::= { mibinternetProfileEntry 137 }

    internetProfile-FrOptions-FrDirectDlci	OBJECT-TYPE
	SYNTAX	INTEGER
	ACCESS	read-write
	STATUS	mandatory
	DESCRIPTION	"The DLCI of the frame relay direct connection."
	::= { mibinternetProfileEntry 138 }

    internetProfile-FrOptions-MfrBundleName	OBJECT-TYPE
	SYNTAX	DisplayString
	ACCESS	read-write
	STATUS	mandatory
	DESCRIPTION	"Name of the multi-link frame-relay profile."
	::= { mibinternetProfileEntry 287 }

    internetProfile-TcpClearOptions-Host	OBJECT-TYPE
	SYNTAX	DisplayString
	ACCESS	read-write
	STATUS	mandatory
	DESCRIPTION	"The first TCP CLEAR login host."
	::= { mibinternetProfileEntry 139 }

    internetProfile-TcpClearOptions-Port	OBJECT-TYPE
	SYNTAX	INTEGER
	ACCESS	read-write
	STATUS	mandatory
	DESCRIPTION	"The TCP port of the first login-host."
	::= { mibinternetProfileEntry 140 }

    internetProfile-TcpClearOptions-Host2	OBJECT-TYPE
	SYNTAX	DisplayString
	ACCESS	read-write
	STATUS	mandatory
	DESCRIPTION	"The second TCP CLEAR login host."
	::= { mibinternetProfileEntry 141 }

    internetProfile-TcpClearOptions-Port2	OBJECT-TYPE
	SYNTAX	INTEGER
	ACCESS	read-write
	STATUS	mandatory
	DESCRIPTION	"The TCP port of the second login-host."
	::= { mibinternetProfileEntry 142 }

    internetProfile-TcpClearOptions-Host3	OBJECT-TYPE
	SYNTAX	DisplayString
	ACCESS	read-write
	STATUS	mandatory
	DESCRIPTION	"The third TCP CLEAR login host."
	::= { mibinternetProfileEntry 143 }

    internetProfile-TcpClearOptions-Port3	OBJECT-TYPE
	SYNTAX	INTEGER
	ACCESS	read-write
	STATUS	mandatory
	DESCRIPTION	"The TCP port of the third login-host."
	::= { mibinternetProfileEntry 144 }

    internetProfile-TcpClearOptions-Host4	OBJECT-TYPE
	SYNTAX	DisplayString
	ACCESS	read-write
	STATUS	mandatory
	DESCRIPTION	"The fourth TCP CLEAR login host."
	::= { mibinternetProfileEntry 145 }

    internetProfile-TcpClearOptions-Port4	OBJECT-TYPE
	SYNTAX	INTEGER
	ACCESS	read-write
	STATUS	mandatory
	DESCRIPTION	"The TCP port of the fourth login-host."
	::= { mibinternetProfileEntry 146 }

    internetProfile-TcpClearOptions-DetectEndOfPacket	OBJECT-TYPE
	SYNTAX	INTEGER {
		    no (1),
		    yes (2)
		}
	ACCESS	read-write
	STATUS	mandatory
	DESCRIPTION	"Set to yes to attempt packet detection"
	::= { mibinternetProfileEntry 147 }

    internetProfile-TcpClearOptions-EndOfPacketPattern	OBJECT-TYPE
	SYNTAX	DisplayString
	ACCESS	read-write
	STATUS	mandatory
	DESCRIPTION	"End of packet pattern to match"
	::= { mibinternetProfileEntry 148 }

    internetProfile-TcpClearOptions-FlushLength	OBJECT-TYPE
	SYNTAX	INTEGER
	ACCESS	read-write
	STATUS	mandatory
	DESCRIPTION	"Set the maximum packet length before flush"
	::= { mibinternetProfileEntry 149 }

    internetProfile-TcpClearOptions-FlushTime	OBJECT-TYPE
	SYNTAX	INTEGER
	ACCESS	read-write
	STATUS	mandatory
	DESCRIPTION	"Set the maximum packet hold time before flush"
	::= { mibinternetProfileEntry 150 }

    internetProfile-AraOptions-RecvPassword	OBJECT-TYPE
	SYNTAX	DisplayString
	ACCESS	read-write
	STATUS	mandatory
	DESCRIPTION	"The password received from the far end."
	::= { mibinternetProfileEntry 151 }

    internetProfile-AraOptions-MaximumConnectTime	OBJECT-TYPE
	SYNTAX	INTEGER
	ACCESS	read-write
	STATUS	mandatory
	DESCRIPTION	"Maximum time in minutes that an ARA session can stay connected."
	::= { mibinternetProfileEntry 152 }

    internetProfile-X25Options-X25Profile	OBJECT-TYPE
	SYNTAX	DisplayString
	ACCESS	read-write
	STATUS	mandatory
	DESCRIPTION	"Name of the x25 profile that this profile is associated with."
	::= { mibinternetProfileEntry 157 }

    internetProfile-X25Options-Lcn	OBJECT-TYPE
	SYNTAX	INTEGER
	ACCESS	read-write
	STATUS	mandatory
	DESCRIPTION	"The LCN (if any) for this profile (for PVCs)."
	::= { mibinternetProfileEntry 158 }

    internetProfile-X25Options-X3Profile	OBJECT-TYPE
	SYNTAX	INTEGER {
		    crtProfile (1),
		    infonetProfile (2),
		    defaultProfile (3),
		    scenProfile (4),
		    ccSspProfile (5),
		    ccTspProfile (6),
		    hardcopyProfile (7),
		    hdxProfile (8),
		    sharkProfile (9),
		    posProfile (12),
		    nullProfile (10),
		    customProfile (11)
		}
	ACCESS	read-write
	STATUS	mandatory
	DESCRIPTION	"X.3 profile parameter index"
	::= { mibinternetProfileEntry 159 }

    internetProfile-X25Options-MaxCalls	OBJECT-TYPE
	SYNTAX	INTEGER
	ACCESS	read-write
	STATUS	mandatory
	DESCRIPTION	"Max number of unsuccessful calls"
	::= { mibinternetProfileEntry 160 }

    internetProfile-X25Options-VcTimerEnable	OBJECT-TYPE
	SYNTAX	INTEGER {
		    no (1),
		    yes (2)
		}
	ACCESS	read-write
	STATUS	mandatory
	DESCRIPTION	"PAD VCE enable flag"
	::= { mibinternetProfileEntry 161 }

    internetProfile-X25Options-X25EncapsType	OBJECT-TYPE
	SYNTAX	INTEGER {
		    rfc877 (1),
		    snap (2),
		    null (3),
		    ppp (4),
		    aodi (5)
		}
	ACCESS	read-write
	STATUS	mandatory
	DESCRIPTION	"RFC1356 encaps Type: RFC877/SNAP/NULL"
	::= { mibinternetProfileEntry 162 }

    internetProfile-X25Options-RemoteX25Address	OBJECT-TYPE
	SYNTAX	DisplayString
	ACCESS	read-write
	STATUS	mandatory
	DESCRIPTION	"X.25 address of remote station."
	::= { mibinternetProfileEntry 461 }

    internetProfile-X25Options-ReverseCharge	OBJECT-TYPE
	SYNTAX	INTEGER {
		    no (1),
		    yes (2)
		}
	ACCESS	read-write
	STATUS	mandatory
	DESCRIPTION	"Reverse charge request"
	::= { mibinternetProfileEntry 164 }

    internetProfile-X25Options-CallMode	OBJECT-TYPE
	SYNTAX	INTEGER {
		    both (1),
		    outgoing (2),
		    incoming (3)
		}
	ACCESS	read-write
	STATUS	mandatory
	DESCRIPTION	"Call mode for this interface: Both/Outgoing/Incoming"
	::= { mibinternetProfileEntry 165 }

    internetProfile-X25Options-AnswerX25Address	OBJECT-TYPE
	SYNTAX	DisplayString
	ACCESS	read-write
	STATUS	mandatory
	DESCRIPTION	"Answer number: mandatory if call mode is incoming or both."
	::= { mibinternetProfileEntry 462 }

    internetProfile-X25Options-InactivityTimer	OBJECT-TYPE
	SYNTAX	INTEGER
	ACCESS	read-only
	STATUS	mandatory
	DESCRIPTION	"X.25 Inactivity Timer."
	::= { mibinternetProfileEntry 167 }

    internetProfile-X25Options-Windowsize	OBJECT-TYPE
	SYNTAX	INTEGER
	ACCESS	read-write
	STATUS	mandatory
	DESCRIPTION	"Window size requested on outgoing X.25 calls."
	::= { mibinternetProfileEntry 463 }

    internetProfile-X25Options-Packetsize	OBJECT-TYPE
	SYNTAX	INTEGER {
		    n-6 (7),
		    n-7 (8),
		    n-8 (9),
		    n-9 (10),
		    n-10 (11),
		    n-11 (12),
		    n-12 (13)
		}
	ACCESS	read-write
	STATUS	mandatory
	DESCRIPTION	"Packet size requested on outgoing X.25 calls."
	::= { mibinternetProfileEntry 464 }

    internetProfile-X25Options-X25Rpoa	OBJECT-TYPE
	SYNTAX	DisplayString
	ACCESS	read-write
	STATUS	mandatory
	DESCRIPTION	"X.25 RPOA facility."
	::= { mibinternetProfileEntry 169 }

    internetProfile-X25Options-X25CugIndex	OBJECT-TYPE
	SYNTAX	DisplayString
	ACCESS	read-write
	STATUS	mandatory
	DESCRIPTION	"X.25 CUG index. Supplied as a right-justified field e.g. 1 should be 0001"
	::= { mibinternetProfileEntry 170 }

    internetProfile-X25Options-X25Nui	OBJECT-TYPE
	SYNTAX	DisplayString
	ACCESS	read-write
	STATUS	mandatory
	DESCRIPTION	"X.25 NUI facility."
	::= { mibinternetProfileEntry 171 }

    internetProfile-X25Options-PadBanner	OBJECT-TYPE
	SYNTAX	DisplayString
	ACCESS	read-only
	STATUS	mandatory
	DESCRIPTION	"PAD banner message."
	::= { mibinternetProfileEntry 172 }

    internetProfile-X25Options-PadPrompt	OBJECT-TYPE
	SYNTAX	DisplayString
	ACCESS	read-only
	STATUS	mandatory
	DESCRIPTION	"PAD prompt."
	::= { mibinternetProfileEntry 173 }

    internetProfile-X25Options-PadNuiPrompt	OBJECT-TYPE
	SYNTAX	DisplayString
	ACCESS	read-only
	STATUS	mandatory
	DESCRIPTION	"NUI prompt."
	::= { mibinternetProfileEntry 174 }

    internetProfile-X25Options-PadNuiPwPrompt	OBJECT-TYPE
	SYNTAX	DisplayString
	ACCESS	read-only
	STATUS	mandatory
	DESCRIPTION	"NUI password prompt."
	::= { mibinternetProfileEntry 175 }

    internetProfile-X25Options-PadAlias1	OBJECT-TYPE
	SYNTAX	DisplayString
	ACCESS	read-only
	STATUS	mandatory
	DESCRIPTION	"PAD Alias number 1."
	::= { mibinternetProfileEntry 176 }

    internetProfile-X25Options-PadAlias2	OBJECT-TYPE
	SYNTAX	DisplayString
	ACCESS	read-only
	STATUS	mandatory
	DESCRIPTION	"PAD Alias number 2."
	::= { mibinternetProfileEntry 177 }

    internetProfile-X25Options-PadAlias3	OBJECT-TYPE
	SYNTAX	DisplayString
	ACCESS	read-only
	STATUS	mandatory
	DESCRIPTION	"PAD Alias number 3."
	::= { mibinternetProfileEntry 178 }

    internetProfile-X25Options-PadDiagDisp	OBJECT-TYPE
	SYNTAX	INTEGER {
		    no (1),
		    yes (2)
		}
	ACCESS	read-write
	STATUS	mandatory
	DESCRIPTION	"PAD D/B channel Diagnostic display."
	::= { mibinternetProfileEntry 179 }

    internetProfile-X25Options-PadDefaultListen	OBJECT-TYPE
	SYNTAX	DisplayString
	ACCESS	read-write
	STATUS	mandatory
	DESCRIPTION	"PAD diag listen address."
	::= { mibinternetProfileEntry 180 }

    internetProfile-X25Options-PadDefaultPw	OBJECT-TYPE
	SYNTAX	DisplayString
	ACCESS	read-write
	STATUS	mandatory
	DESCRIPTION	"PAD diag password."
	::= { mibinternetProfileEntry 181 }

    internetProfile-X25Options-X121SourceAddress	OBJECT-TYPE
	SYNTAX	DisplayString
	ACCESS	read-write
	STATUS	mandatory
	DESCRIPTION	"X.121 address to use to identify this call"
	::= { mibinternetProfileEntry 471 }

    internetProfile-X25Options-PosAuth	OBJECT-TYPE
	SYNTAX	INTEGER {
		    false (1),
		    true (2)
		}
	ACCESS	read-write
	STATUS	mandatory
	DESCRIPTION	"Use POS Authentication"
	::= { mibinternetProfileEntry 472 }

    internetProfile-EuOptions-DceAddr	OBJECT-TYPE
	SYNTAX	INTEGER
	ACCESS	read-write
	STATUS	mandatory
	DESCRIPTION	"The address of the DCE side of the link when the EUNET UI protocol is used."
	::= { mibinternetProfileEntry 182 }

    internetProfile-EuOptions-DteAddr	OBJECT-TYPE
	SYNTAX	INTEGER
	ACCESS	read-write
	STATUS	mandatory
	DESCRIPTION	"The address of the DTE side of the link when the EUNET UI protocol is used."
	::= { mibinternetProfileEntry 183 }

    internetProfile-EuOptions-Mru	OBJECT-TYPE
	SYNTAX	INTEGER
	ACCESS	read-write
	STATUS	mandatory
	DESCRIPTION	"The MRU used for EUNET protocol connections."
	::= { mibinternetProfileEntry 184 }

    internetProfile-X75Options-KFramesOutstanding	OBJECT-TYPE
	SYNTAX	INTEGER
	ACCESS	read-write
	STATUS	mandatory
	DESCRIPTION	"Number of frames outstanding before we require an ack. Defaults to 7."
	::= { mibinternetProfileEntry 185 }

    internetProfile-X75Options-N2Retransmissions	OBJECT-TYPE
	SYNTAX	INTEGER
	ACCESS	read-write
	STATUS	mandatory
	DESCRIPTION	"Number of retransmissions allowed. Defaults to 10."
	::= { mibinternetProfileEntry 186 }

    internetProfile-X75Options-T1RetranTimer	OBJECT-TYPE
	SYNTAX	INTEGER
	ACCESS	read-write
	STATUS	mandatory
	DESCRIPTION	"Number of milliseconds between retransmissions. Defaults to 1000."
	::= { mibinternetProfileEntry 187 }

    internetProfile-X75Options-FrameLength	OBJECT-TYPE
	SYNTAX	INTEGER
	ACCESS	read-write
	STATUS	mandatory
	DESCRIPTION	"Frame length to use for incoming X.75 connections. Defaults to 1024."
	::= { mibinternetProfileEntry 188 }

    internetProfile-AppletalkOptions-AtalkRoutingEnabled	OBJECT-TYPE
	SYNTAX	INTEGER {
		    no (1),
		    yes (2)
		}
	ACCESS	read-write
	STATUS	mandatory
	DESCRIPTION	"Enable/disable AppleTalk routine for this connection."
	::= { mibinternetProfileEntry 189 }

    internetProfile-AppletalkOptions-AtalkStaticZoneName	OBJECT-TYPE
	SYNTAX	DisplayString
	ACCESS	read-write
	STATUS	mandatory
	DESCRIPTION	"The static Zone Name to show for this route."
	::= { mibinternetProfileEntry 190 }

    internetProfile-AppletalkOptions-AtalkStaticNetStart	OBJECT-TYPE
	SYNTAX	INTEGER
	ACCESS	read-write
	STATUS	mandatory
	DESCRIPTION	"The Net Number start value for this route."
	::= { mibinternetProfileEntry 191 }

    internetProfile-AppletalkOptions-AtalkStaticNetEnd	OBJECT-TYPE
	SYNTAX	INTEGER
	ACCESS	read-write
	STATUS	mandatory
	DESCRIPTION	"The Net Number end value for this route."
	::= { mibinternetProfileEntry 192 }

    internetProfile-AppletalkOptions-AtalkPeerMode	OBJECT-TYPE
	SYNTAX	INTEGER {
		    routerPeer (1),
		    dialinPeer (2)
		}
	ACCESS	read-write
	STATUS	mandatory
	DESCRIPTION	"Enable/disable full routing between peer or using proxy AARP to assign a network address."
	::= { mibinternetProfileEntry 193 }

    internetProfile-UsrRadOptions-AcctType	OBJECT-TYPE
	SYNTAX	INTEGER {
		    global (1),
		    local (2),
		    both (3)
		}
	ACCESS	read-write
	STATUS	mandatory
	DESCRIPTION	"Specify where accounting information for this connection will be sent, either the global server list, a per-user override, or both."
	::= { mibinternetProfileEntry 194 }

    internetProfile-UsrRadOptions-AcctHost	OBJECT-TYPE
	SYNTAX	IpAddress
	ACCESS	read-write
	STATUS	mandatory
	DESCRIPTION	"The IP address of the RADIUS accounting host."
	::= { mibinternetProfileEntry 195 }

    internetProfile-UsrRadOptions-AcctPort	OBJECT-TYPE
	SYNTAX	INTEGER
	ACCESS	read-write
	STATUS	mandatory
	DESCRIPTION	"The UDP port of the RADIUS Accounting server."
	::= { mibinternetProfileEntry 196 }

    internetProfile-UsrRadOptions-AcctKey	OBJECT-TYPE
	SYNTAX	DisplayString
	ACCESS	read-write
	STATUS	mandatory
	DESCRIPTION	"The RADIUS accounting key."
	::= { mibinternetProfileEntry 197 }

    internetProfile-UsrRadOptions-AcctTimeout	OBJECT-TYPE
	SYNTAX	INTEGER
	ACCESS	read-write
	STATUS	mandatory
	DESCRIPTION	"Number of seconds to wait for a response to accounting request."
	::= { mibinternetProfileEntry 198 }

    internetProfile-UsrRadOptions-AcctIdBase	OBJECT-TYPE
	SYNTAX	INTEGER {
		    acctBase10 (1),
		    acctBase16 (2)
		}
	ACCESS	read-write
	STATUS	mandatory
	DESCRIPTION	"The Base to use in reporting the Account ID"
	::= { mibinternetProfileEntry 199 }

    internetProfile-CalledNumber	OBJECT-TYPE
	SYNTAX	DisplayString
	ACCESS	read-write
	STATUS	mandatory
	DESCRIPTION	"The called line number for authentication."
	::= { mibinternetProfileEntry 200 }

    internetProfile-DhcpOptions-ReplyEnabled	OBJECT-TYPE
	SYNTAX	INTEGER {
		    no (1),
		    yes (2)
		}
	ACCESS	read-write
	STATUS	mandatory
	DESCRIPTION	"Set to yes to enable replies to DHCP clients."
	::= { mibinternetProfileEntry 201 }

    internetProfile-DhcpOptions-PoolNumber	OBJECT-TYPE
	SYNTAX	INTEGER
	ACCESS	read-write
	STATUS	mandatory
	DESCRIPTION	"Allocate addresses from this pool."
	::= { mibinternetProfileEntry 202 }

    internetProfile-DhcpOptions-MaximumLeases	OBJECT-TYPE
	SYNTAX	INTEGER
	ACCESS	read-write
	STATUS	mandatory
	DESCRIPTION	"Maximum number of leases allowed on this connection."
	::= { mibinternetProfileEntry 203 }

    internetProfile-SharedProf	OBJECT-TYPE
	SYNTAX	INTEGER {
		    no (1),
		    yes (2)
		}
	ACCESS	read-write
	STATUS	mandatory
	DESCRIPTION	"When TRUE multiple users may share a connection profile, as long as IP addresses are not duplicated."
	::= { mibinternetProfileEntry 283 }

    internetProfile-MaxSharedUsers	OBJECT-TYPE
	SYNTAX	INTEGER
	ACCESS	read-write
	STATUS	mandatory
	DESCRIPTION	"Limits the maximum number of end users allowed to connect using a shared connection profile. The default value is 0 which means there is no limit."
	::= { mibinternetProfileEntry 465 }

    internetProfile-T3posOptions-X25Profile	OBJECT-TYPE
	SYNTAX	DisplayString
	ACCESS	read-write
	STATUS	mandatory
	DESCRIPTION	"Name of the x25 profile that this profile is associated with."
	::= { mibinternetProfileEntry 205 }

    internetProfile-T3posOptions-MaxCalls	OBJECT-TYPE
	SYNTAX	INTEGER
	ACCESS	read-write
	STATUS	mandatory
	DESCRIPTION	"Max number of unsuccessful calls"
	::= { mibinternetProfileEntry 206 }

    internetProfile-T3posOptions-AutoCallX121Address	OBJECT-TYPE
	SYNTAX	DisplayString
	ACCESS	read-only
	STATUS	mandatory
	DESCRIPTION	"X.121 address to auto-call upon session startup."
	::= { mibinternetProfileEntry 207 }

    internetProfile-T3posOptions-ReverseCharge	OBJECT-TYPE
	SYNTAX	INTEGER {
		    no (1),
		    yes (2)
		}
	ACCESS	read-write
	STATUS	mandatory
	DESCRIPTION	"Reverse charge request"
	::= { mibinternetProfileEntry 208 }

    internetProfile-T3posOptions-Answer	OBJECT-TYPE
	SYNTAX	DisplayString
	ACCESS	read-only
	STATUS	mandatory
	DESCRIPTION	"Answer number: mandatory if call mode is incoming or both."
	::= { mibinternetProfileEntry 209 }

    internetProfile-T3posOptions-T3PosHostInitMode	OBJECT-TYPE
	SYNTAX	INTEGER {
		    local (1),
		    binLocal (2),
		    transparent (3),
		    blind (4),
		    unknown (5)
		}
	ACCESS	read-only
	STATUS	mandatory
	DESCRIPTION	"T3POS Host Initialization mode: LOCAL/BIN-LOCAL/TRANSPARENT/BLIND"
	::= { mibinternetProfileEntry 210 }

    internetProfile-T3posOptions-T3PosDteInitMode	OBJECT-TYPE
	SYNTAX	INTEGER {
		    local (1),
		    binLocal (2),
		    transparent (3),
		    blind (4),
		    unknown (5)
		}
	ACCESS	read-only
	STATUS	mandatory
	DESCRIPTION	"T3POS DTE Initialization mode: LOCAL/BIN-LOCAL/TRANSPARENT/BLIND"
	::= { mibinternetProfileEntry 211 }

    internetProfile-T3posOptions-T3PosEnqHandling	OBJECT-TYPE
	SYNTAX	INTEGER {
		    off (1),
		    on (2)
		}
	ACCESS	read-only
	STATUS	mandatory
	DESCRIPTION	"T3POS ENQ handling param"
	::= { mibinternetProfileEntry 212 }

    internetProfile-T3posOptions-T3PosMaxBlockSize	OBJECT-TYPE
	SYNTAX	INTEGER {
		    n-512 (1),
		    n-1024 (2)
		}
	ACCESS	read-only
	STATUS	mandatory
	DESCRIPTION	"T3POS Max block size: 512/1024"
	::= { mibinternetProfileEntry 213 }

    internetProfile-T3posOptions-T3PosT1	OBJECT-TYPE
	SYNTAX	INTEGER
	ACCESS	read-only
	STATUS	mandatory
	DESCRIPTION	"T3POS T1 timer."
	::= { mibinternetProfileEntry 214 }

    internetProfile-T3posOptions-T3PosT2	OBJECT-TYPE
	SYNTAX	INTEGER
	ACCESS	read-only
	STATUS	mandatory
	DESCRIPTION	"T3POS T2 timer."
	::= { mibinternetProfileEntry 215 }

    internetProfile-T3posOptions-T3PosT3	OBJECT-TYPE
	SYNTAX	INTEGER
	ACCESS	read-only
	STATUS	mandatory
	DESCRIPTION	"T3POS T3 timer."
	::= { mibinternetProfileEntry 216 }

    internetProfile-T3posOptions-T3PosT4	OBJECT-TYPE
	SYNTAX	INTEGER
	ACCESS	read-only
	STATUS	mandatory
	DESCRIPTION	"T3POS T4 timer."
	::= { mibinternetProfileEntry 217 }

    internetProfile-T3posOptions-T3PosT5	OBJECT-TYPE
	SYNTAX	INTEGER
	ACCESS	read-only
	STATUS	mandatory
	DESCRIPTION	"T3POS T5 timer."
	::= { mibinternetProfileEntry 218 }

    internetProfile-T3posOptions-T3PosT6	OBJECT-TYPE
	SYNTAX	INTEGER
	ACCESS	read-only
	STATUS	mandatory
	DESCRIPTION	"T3POS T6 timer."
	::= { mibinternetProfileEntry 219 }

    internetProfile-T3posOptions-T3PosMethodOfHostNotif	OBJECT-TYPE
	SYNTAX	INTEGER {
		    none (1),
		    callRequestPacket (2),
		    modeSwitchFrame (3)
		}
	ACCESS	read-only
	STATUS	mandatory
	DESCRIPTION	"T3POS Method of Host Notification."
	::= { mibinternetProfileEntry 220 }

    internetProfile-T3posOptions-T3PosPidSelection	OBJECT-TYPE
	SYNTAX	INTEGER {
		    x29 (1),
		    t3pos (2)
		}
	ACCESS	read-only
	STATUS	mandatory
	DESCRIPTION	"T3POS PID selection: X.29, T3POS."
	::= { mibinternetProfileEntry 221 }

    internetProfile-T3posOptions-T3PosAckSuppression	OBJECT-TYPE
	SYNTAX	INTEGER {
		    off (1),
		    on (2)
		}
	ACCESS	read-only
	STATUS	mandatory
	DESCRIPTION	"T3POS ACK suppression."
	::= { mibinternetProfileEntry 222 }

    internetProfile-T3posOptions-X25Rpoa	OBJECT-TYPE
	SYNTAX	DisplayString
	ACCESS	read-only
	STATUS	mandatory
	DESCRIPTION	"X.25 RPOA facility."
	::= { mibinternetProfileEntry 223 }

    internetProfile-T3posOptions-X25CugIndex	OBJECT-TYPE
	SYNTAX	DisplayString
	ACCESS	read-only
	STATUS	mandatory
	DESCRIPTION	"X.25 CUG index."
	::= { mibinternetProfileEntry 224 }

    internetProfile-T3posOptions-X25Nui	OBJECT-TYPE
	SYNTAX	DisplayString
	ACCESS	read-only
	STATUS	mandatory
	DESCRIPTION	"X.25 NUI facility."
	::= { mibinternetProfileEntry 225 }

    internetProfile-T3posOptions-DataFormat	OBJECT-TYPE
	SYNTAX	INTEGER {
		    dataFormat7e1 (1),
		    dataFormat7o1 (2),
		    dataFormat7m1 (3),
		    dataFormat7s1 (4),
		    dataFormat8n1 (5)
		}
	ACCESS	read-only
	STATUS	mandatory
	DESCRIPTION	"T3POS Open/Local Data Format."
	::= { mibinternetProfileEntry 226 }

    internetProfile-T3posOptions-LinkAccessType	OBJECT-TYPE
	SYNTAX	INTEGER {
		    axtypeDedicated (1),
		    axtypeDialIn (2)
		}
	ACCESS	read-only
	STATUS	mandatory
	DESCRIPTION	"T3POS Link access type."
	::= { mibinternetProfileEntry 227 }

    internetProfile-FramedOnly	OBJECT-TYPE
	SYNTAX	INTEGER {
		    no (1),
		    yes (2)
		}
	ACCESS	read-write
	STATUS	mandatory
	DESCRIPTION	"A profile can be restricted to only doing the framed commands (ppp, mpp, slip, and quit) by setting this to YES"
	::= { mibinternetProfileEntry 228 }

    internetProfile-AltdialNumber1	OBJECT-TYPE
	SYNTAX	DisplayString
	ACCESS	read-write
	STATUS	mandatory
	DESCRIPTION	"The first alternate phone number of the named station."
	::= { mibinternetProfileEntry 229 }

    internetProfile-AltdialNumber2	OBJECT-TYPE
	SYNTAX	DisplayString
	ACCESS	read-write
	STATUS	mandatory
	DESCRIPTION	"The second alternate phone number of the named station."
	::= { mibinternetProfileEntry 230 }

    internetProfile-AltdialNumber3	OBJECT-TYPE
	SYNTAX	DisplayString
	ACCESS	read-write
	STATUS	mandatory
	DESCRIPTION	"The third alternate phone number of the named station."
	::= { mibinternetProfileEntry 231 }

    internetProfile-X32Options-X32Profile	OBJECT-TYPE
	SYNTAX	DisplayString
	ACCESS	read-write
	STATUS	mandatory
	DESCRIPTION	"Name of the x25 profile that this profile is associated with."
	::= { mibinternetProfileEntry 232 }

    internetProfile-X32Options-CallMode	OBJECT-TYPE
	SYNTAX	INTEGER {
		    both (1),
		    outgoing (2),
		    incoming (3)
		}
	ACCESS	read-only
	STATUS	mandatory
	DESCRIPTION	"Call mode for this interface: Incoming"
	::= { mibinternetProfileEntry 233 }

    internetProfile-X32Options-X32ApplMode	OBJECT-TYPE
	SYNTAX	INTEGER {
		    netToNet (1),
		    isdnCircuitMode (2),
		    isdnPacketMode (3),
		    last (4)
		}
	ACCESS	read-write
	STATUS	mandatory
	DESCRIPTION	"Appl mode for this interface"
	::= { mibinternetProfileEntry 424 }

    internetProfile-TunnelOptions-ProfileType	OBJECT-TYPE
	SYNTAX	INTEGER {
		    disabled (1),
		    mobileClient (2),
		    gatewayProfile (3),
		    dialoutProfile (4)
		}
	ACCESS	read-write
	STATUS	mandatory
	DESCRIPTION	"The type of connection this profile describes"
	::= { mibinternetProfileEntry 234 }

    internetProfile-TunnelOptions-TunnelingProtocol	OBJECT-TYPE
	SYNTAX	INTEGER {
		    disabled (1),
		    pptpProtocol (2),
		    l2fProtocol (3),
		    l2tpProtocol (4),
		    atmpProtocol (5),
		    vtpProtocol (6),
		    ipinipProtocol (8)
		}
	ACCESS	read-write
	STATUS	mandatory
	DESCRIPTION	"The protocol used for tunneling, if enabled"
	::= { mibinternetProfileEntry 235 }

    internetProfile-TunnelOptions-MaxTunnels	OBJECT-TYPE
	SYNTAX	INTEGER
	ACCESS	read-write
	STATUS	mandatory
	DESCRIPTION	"If this profile is a tunnel gateway, then this parameter specifies the maximum number of tunnels allowed to the home network specified by the name of this profile."
	::= { mibinternetProfileEntry 236 }

    internetProfile-TunnelOptions-AtmpHaRip	OBJECT-TYPE
	SYNTAX	INTEGER {
		    ripOff (1),
		    ripSendV2 (2)
		}
	ACCESS	read-write
	STATUS	mandatory
	DESCRIPTION	"Allows an ATMP home agent to send routing updates to the home network consisting of the mobile nodes' addresses."
	::= { mibinternetProfileEntry 237 }

    internetProfile-TunnelOptions-PrimaryTunnelServer	OBJECT-TYPE
	SYNTAX	DisplayString
	ACCESS	read-write
	STATUS	mandatory
	DESCRIPTION	"The IP address or hostname of the primary tunnel server if this is a mobile client's profile."
	::= { mibinternetProfileEntry 238 }

    internetProfile-TunnelOptions-SecondaryTunnelServer	OBJECT-TYPE
	SYNTAX	DisplayString
	ACCESS	read-write
	STATUS	mandatory
	DESCRIPTION	"The IP address or hostname of the secondary tunnel server if this is a mobile client's profile."
	::= { mibinternetProfileEntry 239 }

    internetProfile-TunnelOptions-UdpPort	OBJECT-TYPE
	SYNTAX	INTEGER
	ACCESS	read-write
	STATUS	mandatory
	DESCRIPTION	"The default UDP port to use when communicating with the ATMP home agent, if this is a mobile client's profile."
	::= { mibinternetProfileEntry 240 }

    internetProfile-TunnelOptions-Password	OBJECT-TYPE
	SYNTAX	DisplayString
	ACCESS	read-write
	STATUS	mandatory
	DESCRIPTION	"The password required by the tunnel server, if this is a mobile client profile."
	::= { mibinternetProfileEntry 241 }

    internetProfile-TunnelOptions-HomeNetworkName	OBJECT-TYPE
	SYNTAX	DisplayString
	ACCESS	read-write
	STATUS	mandatory
	DESCRIPTION	"The name of the home network if the ATMP home agent is operating in gateway mode. It should be empty if the ATMP home agent is operating in router mode. For L2TP, it indicates the Private Group ID value for a client. Used for ATMP and L2TP mobile client's profiles."
	::= { mibinternetProfileEntry 242 }

    internetProfile-TunnelOptions-ClientAuthId	OBJECT-TYPE
	SYNTAX	DisplayString
	ACCESS	read-write
	STATUS	mandatory
	DESCRIPTION	"The system name used by the Tunnel Initiator during Tunnel establishment for the purposes of tunnel authentication. This is different and independent from user authentication. Used on L2TP and L2F."
	::= { mibinternetProfileEntry 413 }

    internetProfile-TunnelOptions-ServerAuthId	OBJECT-TYPE
	SYNTAX	DisplayString
	ACCESS	read-write
	STATUS	mandatory
	DESCRIPTION	"The system name used by the Tunnel Terminator during Tunnel establishment for the purposes of tunnel authentication. This is different and independent from user authentication. Used on L2TP and L2F."
	::= { mibinternetProfileEntry 417 }

    internetProfile-TunnelOptions-Vrouter	OBJECT-TYPE
	SYNTAX	DisplayString
	ACCESS	read-write
	STATUS	mandatory
	DESCRIPTION	"The name of the virtual router used for the tunnel."
	::= { mibinternetProfileEntry 356 }

    internetProfile-TunnelOptions-AssignmentId	OBJECT-TYPE
	SYNTAX	DisplayString
	ACCESS	read-write
	STATUS	mandatory
	DESCRIPTION	"The identification assigned to tunnels so that sessions could be grouped into different tunnels based on this Id. This Id only has local significance and is not transmited to the remote tunnel-endpoint."
	::= { mibinternetProfileEntry 418 }

    internetProfile-TunnelOptions-TosCopying	OBJECT-TYPE
	SYNTAX	INTEGER {
		    no (1),
		    yes (2)
		}
	ACCESS	read-write
	STATUS	mandatory
	DESCRIPTION	"Control the TOS byte of the outer IP header"
	::= { mibinternetProfileEntry 473 }

    internetProfile-IpsecOptions-Enabled	OBJECT-TYPE
	SYNTAX	INTEGER {
		    no (1),
		    yes (2)
		}
	ACCESS	read-write
	STATUS	mandatory
	DESCRIPTION	"IPSec can be disabled on a profile by setting this field to no."
	::= { mibinternetProfileEntry 474 }

    internetProfile-IpsecOptions-SecurityPolicyDatabase	OBJECT-TYPE
	SYNTAX	DisplayString
	ACCESS	read-write
	STATUS	mandatory
	DESCRIPTION	"The name of the IPSec SPD profile to be used."
	::= { mibinternetProfileEntry 475 }

    internetProfile-PriNumberingPlanId	OBJECT-TYPE
	SYNTAX	INTEGER {
		    unknown (1),
		    iSDN (2),
		    private (10)
		}
	ACCESS	read-write
	STATUS	mandatory
	DESCRIPTION	"PRI Called Party element's Numbering-Plan-ID value for outgoing PRI calls."
	::= { mibinternetProfileEntry 244 }

    internetProfile-Vrouter	OBJECT-TYPE
	SYNTAX	DisplayString
	ACCESS	read-write
	STATUS	mandatory
	DESCRIPTION	"Specifies the VRouter in which this profile belongs."
	::= { mibinternetProfileEntry 245 }

    internetProfile-CrossConnectIndex	OBJECT-TYPE
	SYNTAX	INTEGER
	ACCESS	read-only
	STATUS	mandatory
	DESCRIPTION	"AToM Mib cross connect index."
	::= { mibinternetProfileEntry 425 }

    internetProfile-AtmOptions-Atm1483type	OBJECT-TYPE
	SYNTAX	INTEGER {
		    aal5Llc (1),
		    aal5Vc (2)
		}
	ACCESS	read-write
	STATUS	mandatory
	DESCRIPTION	"The type of AAL5 multiplexing."
	::= { mibinternetProfileEntry 246 }

    internetProfile-AtmOptions-Vpi	OBJECT-TYPE
	SYNTAX	INTEGER
	ACCESS	read-write
	STATUS	mandatory
	DESCRIPTION	"The VPI of this connection."
	::= { mibinternetProfileEntry 247 }

    internetProfile-AtmOptions-Vci	OBJECT-TYPE
	SYNTAX	INTEGER
	ACCESS	read-write
	STATUS	mandatory
	DESCRIPTION	"The VCI of this connection."
	::= { mibinternetProfileEntry 248 }

    internetProfile-AtmOptions-NailedGroup	OBJECT-TYPE
	SYNTAX	INTEGER
	ACCESS	read-write
	STATUS	mandatory
	DESCRIPTION	"A number that identifies the set of lines that makes up a nailed-group."
	::= { mibinternetProfileEntry 256 }

    internetProfile-AtmOptions-CastType	OBJECT-TYPE
	SYNTAX	INTEGER {
		    p2p (2),
		    p2mproot (3),
		    p2mpleaf (4)
		}
	ACCESS	read-write
	STATUS	mandatory
	DESCRIPTION	"The connection topology type."
	::= { mibinternetProfileEntry 426 }

    internetProfile-AtmOptions-ConnKind	OBJECT-TYPE
	SYNTAX	INTEGER {
		    pvc (2),
		    svcIncoming (3),
		    svcOutgoing (4),
		    spvcInitiator (5),
		    spvcTarget (6)
		}
	ACCESS	read-write
	STATUS	mandatory
	DESCRIPTION	"The use of call control."
	::= { mibinternetProfileEntry 427 }

    internetProfile-AtmOptions-AtmServiceType	OBJECT-TYPE
	SYNTAX	INTEGER {
		    atmUbrService (1),
		    atmCbrService (2),
		    atmAbrService (3),
		    atmVbrService (4)
		}
	ACCESS	read-write
	STATUS	mandatory
	DESCRIPTION	"ATM service type."
	::= { mibinternetProfileEntry 257 }

    internetProfile-AtmOptions-AtmServiceRate	OBJECT-TYPE
	SYNTAX	INTEGER
	ACCESS	read-write
	STATUS	mandatory
	DESCRIPTION	"ATM service rate is the minimum bits per second that is required."
	::= { mibinternetProfileEntry 258 }

    internetProfile-AtmOptions-VpSwitching	OBJECT-TYPE
	SYNTAX	INTEGER {
		    no (1),
		    yes (2)
		}
	ACCESS	read-write
	STATUS	mandatory
	DESCRIPTION	"Is this VP switching? VP = 0 is used for VC switching and VP > 0 is used for VP switching."
	::= { mibinternetProfileEntry 304 }

    internetProfile-AtmOptions-TargetAtmAddress	OBJECT-TYPE
	SYNTAX	DisplayString
	ACCESS	read-write
	STATUS	mandatory
	DESCRIPTION	"The target ATM Address of this Soft PVcc or PVpc."
	::= { mibinternetProfileEntry 428 }

    internetProfile-AtmOptions-TargetSelect	OBJECT-TYPE
	SYNTAX	INTEGER {
		    required (2),
		    any (3)
		}
	ACCESS	read-only
	STATUS	mandatory
	DESCRIPTION	"Indicates whether the target VPI/VCI values are to be used at the destination."
	::= { mibinternetProfileEntry 429 }

    internetProfile-AtmOptions-TargetVpi	OBJECT-TYPE
	SYNTAX	INTEGER
	ACCESS	read-write
	STATUS	mandatory
	DESCRIPTION	"Target VPI."
	::= { mibinternetProfileEntry 430 }

    internetProfile-AtmOptions-TargetVci	OBJECT-TYPE
	SYNTAX	INTEGER
	ACCESS	read-write
	STATUS	mandatory
	DESCRIPTION	"Target VCI."
	::= { mibinternetProfileEntry 431 }

    internetProfile-AtmOptions-SpvcRetryInterval	OBJECT-TYPE
	SYNTAX	INTEGER
	ACCESS	read-write
	STATUS	mandatory
	DESCRIPTION	"Period to wait before attempting to establish SPVC after the first SPVC setup failure. 0 indicates no retry"
	::= { mibinternetProfileEntry 448 }

    internetProfile-AtmOptions-SpvcRetryThreshold	OBJECT-TYPE
	SYNTAX	INTEGER
	ACCESS	read-write
	STATUS	mandatory
	DESCRIPTION	"The number of consecutive call setup attempts for the SPVC to fail before the call failure is declared. 0 indicates infinite number of call attempts that means failure is not declared."
	::= { mibinternetProfileEntry 449 }

    internetProfile-AtmOptions-SpvcRetryLimit	OBJECT-TYPE
	SYNTAX	INTEGER
	ACCESS	read-write
	STATUS	mandatory
	DESCRIPTION	"Maximum limit on how many consecutive unsuccessful call setup attempts can be made before stopping the attempt to set up the connection."
	::= { mibinternetProfileEntry 450 }

    internetProfile-AtmOptions-AtmDirectEnabled	OBJECT-TYPE
	SYNTAX	INTEGER {
		    no (1),
		    yes (2)
		}
	ACCESS	read-write
	STATUS	mandatory
	DESCRIPTION	"Enable ATM Direct."
	::= { mibinternetProfileEntry 306 }

    internetProfile-AtmOptions-AtmDirectProfile	OBJECT-TYPE
	SYNTAX	DisplayString
	ACCESS	read-write
	STATUS	mandatory
	DESCRIPTION	"The atm connection profile name to be used for the ATM Direct connection."
	::= { mibinternetProfileEntry 307 }

    internetProfile-AtmOptions-VcFaultManagement	OBJECT-TYPE
	SYNTAX	INTEGER {
		    none (1),
		    segmentLoopback (2),
		    endToEndLoopback (3)
		}
	ACCESS	read-write
	STATUS	mandatory
	DESCRIPTION	"The VC fault management function to be used for this VC."
	::= { mibinternetProfileEntry 357 }

    internetProfile-AtmOptions-VcMaxLoopbackCellLoss	OBJECT-TYPE
	SYNTAX	INTEGER
	ACCESS	read-write
	STATUS	mandatory
	DESCRIPTION	"The maximum number of consecutive cell loopback failures before the call is disconnected."
	::= { mibinternetProfileEntry 358 }

    internetProfile-AtmOptions-SvcOptions-Enabled	OBJECT-TYPE
	SYNTAX	INTEGER {
		    no (1),
		    yes (2)
		}
	ACCESS	read-write
	STATUS	mandatory
	DESCRIPTION	"Enable ATM SVC."
	::= { mibinternetProfileEntry 308 }

    internetProfile-AtmOptions-SvcOptions-IncomingCallerAddr-NumberingPlan	OBJECT-TYPE
	SYNTAX	INTEGER {
		    undefined (1),
		    isdn (2),
		    aesa (3),
		    unknown (5),
		    x121 (9)
		}
	ACCESS	read-write
	STATUS	mandatory
	DESCRIPTION	"Numbering plan for an SVC address"
	::= { mibinternetProfileEntry 381 }

    internetProfile-AtmOptions-SvcOptions-IncomingCallerAddr-E164NativeAddress	OBJECT-TYPE
	SYNTAX	DisplayString
	ACCESS	read-write
	STATUS	mandatory
	DESCRIPTION	"An SVC address in a native E.164 format."
	::= { mibinternetProfileEntry 382 }

    internetProfile-AtmOptions-SvcOptions-IncomingCallerAddr-AesaAddress-Format	OBJECT-TYPE
	SYNTAX	INTEGER {
		    undefined (1),
		    dccAesa (2),
		    icdAesa (6),
		    e164Aesa (4),
		    customAesa (5)
		}
	ACCESS	read-write
	STATUS	mandatory
	DESCRIPTION	"An AESA address format used to define this SVC address."
	::= { mibinternetProfileEntry 383 }

    internetProfile-AtmOptions-SvcOptions-IncomingCallerAddr-AesaAddress-IdpPortion-Afi	OBJECT-TYPE
	SYNTAX	DisplayString
	ACCESS	read-write
	STATUS	mandatory
	DESCRIPTION	"An Authority and Format Identifier(AFI) for AESA address. Must be defined for every AESA address."
	::= { mibinternetProfileEntry 384 }

    internetProfile-AtmOptions-SvcOptions-IncomingCallerAddr-AesaAddress-IdpPortion-Idi	OBJECT-TYPE
	SYNTAX	DisplayString
	ACCESS	read-write
	STATUS	mandatory
	DESCRIPTION	"An Initial Domain Identifier (IDI) portion of the AESA address."
	::= { mibinternetProfileEntry 385 }

    internetProfile-AtmOptions-SvcOptions-IncomingCallerAddr-AesaAddress-DspPortion-HoDsp	OBJECT-TYPE
	SYNTAX	DisplayString
	ACCESS	read-write
	STATUS	mandatory
	DESCRIPTION	"A High-Order Domain-Specific Part of AESA address. The IDP portion determine the format of the HO-DSP."
	::= { mibinternetProfileEntry 386 }

    internetProfile-AtmOptions-SvcOptions-IncomingCallerAddr-AesaAddress-DspPortion-Esi	OBJECT-TYPE
	SYNTAX	DisplayString
	ACCESS	read-write
	STATUS	mandatory
	DESCRIPTION	"An End System Identifier (ESI) which uniquely identifies the end system within the specified subnetwork."
	::= { mibinternetProfileEntry 387 }

    internetProfile-AtmOptions-SvcOptions-IncomingCallerAddr-AesaAddress-DspPortion-Sel	OBJECT-TYPE
	SYNTAX	DisplayString
	ACCESS	read-write
	STATUS	mandatory
	DESCRIPTION	"A selector (SEL) field that may be used by the end system."
	::= { mibinternetProfileEntry 388 }

    internetProfile-AtmOptions-SvcOptions-OutgoingCalledAddr-NumberingPlan	OBJECT-TYPE
	SYNTAX	INTEGER {
		    undefined (1),
		    isdn (2),
		    aesa (3),
		    unknown (5),
		    x121 (9)
		}
	ACCESS	read-write
	STATUS	mandatory
	DESCRIPTION	"Numbering plan for an SVC address"
	::= { mibinternetProfileEntry 389 }

    internetProfile-AtmOptions-SvcOptions-OutgoingCalledAddr-E164NativeAddress	OBJECT-TYPE
	SYNTAX	DisplayString
	ACCESS	read-write
	STATUS	mandatory
	DESCRIPTION	"An SVC address in a native E.164 format."
	::= { mibinternetProfileEntry 390 }

    internetProfile-AtmOptions-SvcOptions-OutgoingCalledAddr-AesaAddress-Format	OBJECT-TYPE
	SYNTAX	INTEGER {
		    undefined (1),
		    dccAesa (2),
		    icdAesa (6),
		    e164Aesa (4),
		    customAesa (5)
		}
	ACCESS	read-write
	STATUS	mandatory
	DESCRIPTION	"An AESA address format used to define this SVC address."
	::= { mibinternetProfileEntry 391 }

    internetProfile-AtmOptions-SvcOptions-OutgoingCalledAddr-AesaAddress-IdpPortion-Afi	OBJECT-TYPE
	SYNTAX	DisplayString
	ACCESS	read-write
	STATUS	mandatory
	DESCRIPTION	"An Authority and Format Identifier(AFI) for AESA address. Must be defined for every AESA address."
	::= { mibinternetProfileEntry 392 }

    internetProfile-AtmOptions-SvcOptions-OutgoingCalledAddr-AesaAddress-IdpPortion-Idi	OBJECT-TYPE
	SYNTAX	DisplayString
	ACCESS	read-write
	STATUS	mandatory
	DESCRIPTION	"An Initial Domain Identifier (IDI) portion of the AESA address."
	::= { mibinternetProfileEntry 393 }

    internetProfile-AtmOptions-SvcOptions-OutgoingCalledAddr-AesaAddress-DspPortion-HoDsp	OBJECT-TYPE
	SYNTAX	DisplayString
	ACCESS	read-write
	STATUS	mandatory
	DESCRIPTION	"A High-Order Domain-Specific Part of AESA address. The IDP portion determine the format of the HO-DSP."
	::= { mibinternetProfileEntry 394 }

    internetProfile-AtmOptions-SvcOptions-OutgoingCalledAddr-AesaAddress-DspPortion-Esi	OBJECT-TYPE
	SYNTAX	DisplayString
	ACCESS	read-write
	STATUS	mandatory
	DESCRIPTION	"An End System Identifier (ESI) which uniquely identifies the end system within the specified subnetwork."
	::= { mibinternetProfileEntry 395 }

    internetProfile-AtmOptions-SvcOptions-OutgoingCalledAddr-AesaAddress-DspPortion-Sel	OBJECT-TYPE
	SYNTAX	DisplayString
	ACCESS	read-write
	STATUS	mandatory
	DESCRIPTION	"A selector (SEL) field that may be used by the end system."
	::= { mibinternetProfileEntry 396 }

    internetProfile-AtmOptions-AtmInverseArp	OBJECT-TYPE
	SYNTAX	INTEGER {
		    no (1),
		    yes (2)
		}
	ACCESS	read-write
	STATUS	mandatory
	DESCRIPTION	"Send Atm Inverse Arp request for this connection."
	::= { mibinternetProfileEntry 327 }

    internetProfile-AtmOptions-Fr08Mode	OBJECT-TYPE
	SYNTAX	INTEGER {
		    translation (1),
		    transparent (2)
		}
	ACCESS	read-write
	STATUS	mandatory
	DESCRIPTION	"The FR-08 transparent mode"
	::= { mibinternetProfileEntry 367 }

    internetProfile-AtmOptions-AtmCircuitProfile	OBJECT-TYPE
	SYNTAX	DisplayString
	ACCESS	read-write
	STATUS	mandatory
	DESCRIPTION	"The atm circuit profile name to be used for this connection."
	::= { mibinternetProfileEntry 432 }

    internetProfile-AtmOptions-OamAisF5	OBJECT-TYPE
	SYNTAX	INTEGER {
		    disable (1),
		    segment (2),
		    endToEnd (3)
		}
	ACCESS	read-write
	STATUS	mandatory
	DESCRIPTION	"Disable/Enable sending OAM AIS F5 cells when pvc is down."
	::= { mibinternetProfileEntry 451 }

    internetProfile-AtmOptions-OamSupport	OBJECT-TYPE
	SYNTAX	INTEGER {
		    no (1),
		    yes (2)
		}
	ACCESS	read-write
	STATUS	mandatory
	DESCRIPTION	"Is F4 OAM supported? It is used only when vp-switching is yes. The Stinger system can only support F4 OAM for 50 VPC segments in total."
	::= { mibinternetProfileEntry 452 }

    internetProfile-AtmOptions-Mtu	OBJECT-TYPE
	SYNTAX	INTEGER
	ACCESS	read-write
	STATUS	mandatory
	DESCRIPTION	"The maximum packet size (excluding LLC encapsulation if used) that can be transmitted to a remote peer without performing fragmentation."
	::= { mibinternetProfileEntry 468 }

    internetProfile-HdlcNrmOptions-SnrmResponseTimeout	OBJECT-TYPE
	SYNTAX	INTEGER
	ACCESS	read-write
	STATUS	mandatory
	DESCRIPTION	"SNRM Response Timeout in milliseconds."
	::= { mibinternetProfileEntry 259 }

    internetProfile-HdlcNrmOptions-SnrmRetryCounter	OBJECT-TYPE
	SYNTAX	INTEGER
	ACCESS	read-write
	STATUS	mandatory
	DESCRIPTION	"SNRM Retry Counter in units."
	::= { mibinternetProfileEntry 260 }

    internetProfile-HdlcNrmOptions-PollTimeout	OBJECT-TYPE
	SYNTAX	INTEGER
	ACCESS	read-write
	STATUS	mandatory
	DESCRIPTION	"HDLC-NRM Poll Reponse Timeout in milliseconds"
	::= { mibinternetProfileEntry 261 }

    internetProfile-HdlcNrmOptions-PollRate	OBJECT-TYPE
	SYNTAX	INTEGER
	ACCESS	read-write
	STATUS	mandatory
	DESCRIPTION	"HDLC-NRM Poll Rate in milliseconds"
	::= { mibinternetProfileEntry 262 }

    internetProfile-HdlcNrmOptions-PollRetryCount	OBJECT-TYPE
	SYNTAX	INTEGER
	ACCESS	read-write
	STATUS	mandatory
	DESCRIPTION	"Poll Response Retry Counter in units"
	::= { mibinternetProfileEntry 263 }

    internetProfile-HdlcNrmOptions-Primary	OBJECT-TYPE
	SYNTAX	INTEGER {
		    no (1),
		    yes (2)
		}
	ACCESS	read-write
	STATUS	mandatory
	DESCRIPTION	"Primary station (Yes) or Secondary station (No)."
	::= { mibinternetProfileEntry 264 }

    internetProfile-HdlcNrmOptions-AsyncDrop	OBJECT-TYPE
	SYNTAX	INTEGER {
		    no (1),
		    yes (2)
		}
	ACCESS	read-write
	STATUS	mandatory
	DESCRIPTION	"Drop Async I-frames (Yes) or process (No)."
	::= { mibinternetProfileEntry 368 }

    internetProfile-HdlcNrmOptions-StationPollAddress	OBJECT-TYPE
	SYNTAX	INTEGER
	ACCESS	read-write
	STATUS	mandatory
	DESCRIPTION	"Secondary station address to use for SNRM polling"
	::= { mibinternetProfileEntry 416 }

    internetProfile-AtmConnectOptions-Atm1483type	OBJECT-TYPE
	SYNTAX	INTEGER {
		    aal5Llc (1),
		    aal5Vc (2)
		}
	ACCESS	read-write
	STATUS	mandatory
	DESCRIPTION	"The type of AAL5 multiplexing."
	::= { mibinternetProfileEntry 265 }

    internetProfile-AtmConnectOptions-Vpi	OBJECT-TYPE
	SYNTAX	INTEGER
	ACCESS	read-write
	STATUS	mandatory
	DESCRIPTION	"The VPI of this connection."
	::= { mibinternetProfileEntry 266 }

    internetProfile-AtmConnectOptions-Vci	OBJECT-TYPE
	SYNTAX	INTEGER
	ACCESS	read-write
	STATUS	mandatory
	DESCRIPTION	"The VCI of this connection."
	::= { mibinternetProfileEntry 267 }

    internetProfile-AtmConnectOptions-NailedGroup	OBJECT-TYPE
	SYNTAX	INTEGER
	ACCESS	read-write
	STATUS	mandatory
	DESCRIPTION	"A number that identifies the set of lines that makes up a nailed-group."
	::= { mibinternetProfileEntry 268 }

    internetProfile-AtmConnectOptions-CastType	OBJECT-TYPE
	SYNTAX	INTEGER {
		    p2p (2),
		    p2mproot (3),
		    p2mpleaf (4)
		}
	ACCESS	read-write
	STATUS	mandatory
	DESCRIPTION	"The connection topology type."
	::= { mibinternetProfileEntry 433 }

    internetProfile-AtmConnectOptions-ConnKind	OBJECT-TYPE
	SYNTAX	INTEGER {
		    pvc (2),
		    svcIncoming (3),
		    svcOutgoing (4),
		    spvcInitiator (5),
		    spvcTarget (6)
		}
	ACCESS	read-write
	STATUS	mandatory
	DESCRIPTION	"The use of call control."
	::= { mibinternetProfileEntry 434 }

    internetProfile-AtmConnectOptions-AtmServiceType	OBJECT-TYPE
	SYNTAX	INTEGER {
		    atmUbrService (1),
		    atmCbrService (2),
		    atmAbrService (3),
		    atmVbrService (4)
		}
	ACCESS	read-write
	STATUS	mandatory
	DESCRIPTION	"ATM service type."
	::= { mibinternetProfileEntry 269 }

    internetProfile-AtmConnectOptions-AtmServiceRate	OBJECT-TYPE
	SYNTAX	INTEGER
	ACCESS	read-write
	STATUS	mandatory
	DESCRIPTION	"ATM service rate is the minimum bits per second that is required."
	::= { mibinternetProfileEntry 270 }

    internetProfile-AtmConnectOptions-VpSwitching	OBJECT-TYPE
	SYNTAX	INTEGER {
		    no (1),
		    yes (2)
		}
	ACCESS	read-write
	STATUS	mandatory
	DESCRIPTION	"Is this VP switching? VP = 0 is used for VC switching and VP > 0 is used for VP switching."
	::= { mibinternetProfileEntry 328 }

    internetProfile-AtmConnectOptions-TargetAtmAddress	OBJECT-TYPE
	SYNTAX	DisplayString
	ACCESS	read-write
	STATUS	mandatory
	DESCRIPTION	"The target ATM Address of this Soft PVcc or PVpc."
	::= { mibinternetProfileEntry 435 }

    internetProfile-AtmConnectOptions-TargetSelect	OBJECT-TYPE
	SYNTAX	INTEGER {
		    required (2),
		    any (3)
		}
	ACCESS	read-only
	STATUS	mandatory
	DESCRIPTION	"Indicates whether the target VPI/VCI values are to be used at the destination."
	::= { mibinternetProfileEntry 436 }

    internetProfile-AtmConnectOptions-TargetVpi	OBJECT-TYPE
	SYNTAX	INTEGER
	ACCESS	read-write
	STATUS	mandatory
	DESCRIPTION	"Target VPI."
	::= { mibinternetProfileEntry 437 }

    internetProfile-AtmConnectOptions-TargetVci	OBJECT-TYPE
	SYNTAX	INTEGER
	ACCESS	read-write
	STATUS	mandatory
	DESCRIPTION	"Target VCI."
	::= { mibinternetProfileEntry 438 }

    internetProfile-AtmConnectOptions-SpvcRetryInterval	OBJECT-TYPE
	SYNTAX	INTEGER
	ACCESS	read-write
	STATUS	mandatory
	DESCRIPTION	"Period to wait before attempting to establish SPVC after the first SPVC setup failure. 0 indicates no retry"
	::= { mibinternetProfileEntry 453 }

    internetProfile-AtmConnectOptions-SpvcRetryThreshold	OBJECT-TYPE
	SYNTAX	INTEGER
	ACCESS	read-write
	STATUS	mandatory
	DESCRIPTION	"The number of consecutive call setup attempts for the SPVC to fail before the call failure is declared. 0 indicates infinite number of call attempts that means failure is not declared."
	::= { mibinternetProfileEntry 454 }

    internetProfile-AtmConnectOptions-SpvcRetryLimit	OBJECT-TYPE
	SYNTAX	INTEGER
	ACCESS	read-write
	STATUS	mandatory
	DESCRIPTION	"Maximum limit on how many consecutive unsuccessful call setup attempts can be made before stopping the attempt to set up the connection."
	::= { mibinternetProfileEntry 455 }

    internetProfile-AtmConnectOptions-AtmDirectEnabled	OBJECT-TYPE
	SYNTAX	INTEGER {
		    no (1),
		    yes (2)
		}
	ACCESS	read-write
	STATUS	mandatory
	DESCRIPTION	"Enable ATM Direct."
	::= { mibinternetProfileEntry 330 }

    internetProfile-AtmConnectOptions-AtmDirectProfile	OBJECT-TYPE
	SYNTAX	DisplayString
	ACCESS	read-write
	STATUS	mandatory
	DESCRIPTION	"The atm connection profile name to be used for the ATM Direct connection."
	::= { mibinternetProfileEntry 331 }

    internetProfile-AtmConnectOptions-VcFaultManagement	OBJECT-TYPE
	SYNTAX	INTEGER {
		    none (1),
		    segmentLoopback (2),
		    endToEndLoopback (3)
		}
	ACCESS	read-write
	STATUS	mandatory
	DESCRIPTION	"The VC fault management function to be used for this VC."
	::= { mibinternetProfileEntry 369 }

    internetProfile-AtmConnectOptions-VcMaxLoopbackCellLoss	OBJECT-TYPE
	SYNTAX	INTEGER
	ACCESS	read-write
	STATUS	mandatory
	DESCRIPTION	"The maximum number of consecutive cell loopback failures before the call is disconnected."
	::= { mibinternetProfileEntry 370 }

    internetProfile-AtmConnectOptions-SvcOptions-Enabled	OBJECT-TYPE
	SYNTAX	INTEGER {
		    no (1),
		    yes (2)
		}
	ACCESS	read-write
	STATUS	mandatory
	DESCRIPTION	"Enable ATM SVC."
	::= { mibinternetProfileEntry 332 }

    internetProfile-AtmConnectOptions-SvcOptions-IncomingCallerAddr-NumberingPlan	OBJECT-TYPE
	SYNTAX	INTEGER {
		    undefined (1),
		    isdn (2),
		    aesa (3),
		    unknown (5),
		    x121 (9)
		}
	ACCESS	read-write
	STATUS	mandatory
	DESCRIPTION	"Numbering plan for an SVC address"
	::= { mibinternetProfileEntry 397 }

    internetProfile-AtmConnectOptions-SvcOptions-IncomingCallerAddr-E164NativeAddress	OBJECT-TYPE
	SYNTAX	DisplayString
	ACCESS	read-write
	STATUS	mandatory
	DESCRIPTION	"An SVC address in a native E.164 format."
	::= { mibinternetProfileEntry 398 }

    internetProfile-AtmConnectOptions-SvcOptions-IncomingCallerAddr-AesaAddress-Format	OBJECT-TYPE
	SYNTAX	INTEGER {
		    undefined (1),
		    dccAesa (2),
		    icdAesa (6),
		    e164Aesa (4),
		    customAesa (5)
		}
	ACCESS	read-write
	STATUS	mandatory
	DESCRIPTION	"An AESA address format used to define this SVC address."
	::= { mibinternetProfileEntry 399 }

    internetProfile-AtmConnectOptions-SvcOptions-IncomingCallerAddr-AesaAddress-IdpPortion-Afi	OBJECT-TYPE
	SYNTAX	DisplayString
	ACCESS	read-write
	STATUS	mandatory
	DESCRIPTION	"An Authority and Format Identifier(AFI) for AESA address. Must be defined for every AESA address."
	::= { mibinternetProfileEntry 400 }

    internetProfile-AtmConnectOptions-SvcOptions-IncomingCallerAddr-AesaAddress-IdpPortion-Idi	OBJECT-TYPE
	SYNTAX	DisplayString
	ACCESS	read-write
	STATUS	mandatory
	DESCRIPTION	"An Initial Domain Identifier (IDI) portion of the AESA address."
	::= { mibinternetProfileEntry 401 }

    internetProfile-AtmConnectOptions-SvcOptions-IncomingCallerAddr-AesaAddress-DspPortion-HoDsp	OBJECT-TYPE
	SYNTAX	DisplayString
	ACCESS	read-write
	STATUS	mandatory
	DESCRIPTION	"A High-Order Domain-Specific Part of AESA address. The IDP portion determine the format of the HO-DSP."
	::= { mibinternetProfileEntry 402 }

    internetProfile-AtmConnectOptions-SvcOptions-IncomingCallerAddr-AesaAddress-DspPortion-Esi	OBJECT-TYPE
	SYNTAX	DisplayString
	ACCESS	read-write
	STATUS	mandatory
	DESCRIPTION	"An End System Identifier (ESI) which uniquely identifies the end system within the specified subnetwork."
	::= { mibinternetProfileEntry 403 }

    internetProfile-AtmConnectOptions-SvcOptions-IncomingCallerAddr-AesaAddress-DspPortion-Sel	OBJECT-TYPE
	SYNTAX	DisplayString
	ACCESS	read-write
	STATUS	mandatory
	DESCRIPTION	"A selector (SEL) field that may be used by the end system."
	::= { mibinternetProfileEntry 404 }

    internetProfile-AtmConnectOptions-SvcOptions-OutgoingCalledAddr-NumberingPlan	OBJECT-TYPE
	SYNTAX	INTEGER {
		    undefined (1),
		    isdn (2),
		    aesa (3),
		    unknown (5),
		    x121 (9)
		}
	ACCESS	read-write
	STATUS	mandatory
	DESCRIPTION	"Numbering plan for an SVC address"
	::= { mibinternetProfileEntry 405 }

    internetProfile-AtmConnectOptions-SvcOptions-OutgoingCalledAddr-E164NativeAddress	OBJECT-TYPE
	SYNTAX	DisplayString
	ACCESS	read-write
	STATUS	mandatory
	DESCRIPTION	"An SVC address in a native E.164 format."
	::= { mibinternetProfileEntry 406 }

    internetProfile-AtmConnectOptions-SvcOptions-OutgoingCalledAddr-AesaAddress-Format	OBJECT-TYPE
	SYNTAX	INTEGER {
		    undefined (1),
		    dccAesa (2),
		    icdAesa (6),
		    e164Aesa (4),
		    customAesa (5)
		}
	ACCESS	read-write
	STATUS	mandatory
	DESCRIPTION	"An AESA address format used to define this SVC address."
	::= { mibinternetProfileEntry 407 }

    internetProfile-AtmConnectOptions-SvcOptions-OutgoingCalledAddr-AesaAddress-IdpPortion-Afi	OBJECT-TYPE
	SYNTAX	DisplayString
	ACCESS	read-write
	STATUS	mandatory
	DESCRIPTION	"An Authority and Format Identifier(AFI) for AESA address. Must be defined for every AESA address."
	::= { mibinternetProfileEntry 408 }

    internetProfile-AtmConnectOptions-SvcOptions-OutgoingCalledAddr-AesaAddress-IdpPortion-Idi	OBJECT-TYPE
	SYNTAX	DisplayString
	ACCESS	read-write
	STATUS	mandatory
	DESCRIPTION	"An Initial Domain Identifier (IDI) portion of the AESA address."
	::= { mibinternetProfileEntry 409 }

    internetProfile-AtmConnectOptions-SvcOptions-OutgoingCalledAddr-AesaAddress-DspPortion-HoDsp	OBJECT-TYPE
	SYNTAX	DisplayString
	ACCESS	read-write
	STATUS	mandatory
	DESCRIPTION	"A High-Order Domain-Specific Part of AESA address. The IDP portion determine the format of the HO-DSP."
	::= { mibinternetProfileEntry 410 }

    internetProfile-AtmConnectOptions-SvcOptions-OutgoingCalledAddr-AesaAddress-DspPortion-Esi	OBJECT-TYPE
	SYNTAX	DisplayString
	ACCESS	read-write
	STATUS	mandatory
	DESCRIPTION	"An End System Identifier (ESI) which uniquely identifies the end system within the specified subnetwork."
	::= { mibinternetProfileEntry 411 }

    internetProfile-AtmConnectOptions-SvcOptions-OutgoingCalledAddr-AesaAddress-DspPortion-Sel	OBJECT-TYPE
	SYNTAX	DisplayString
	ACCESS	read-write
	STATUS	mandatory
	DESCRIPTION	"A selector (SEL) field that may be used by the end system."
	::= { mibinternetProfileEntry 412 }

    internetProfile-AtmConnectOptions-AtmInverseArp	OBJECT-TYPE
	SYNTAX	INTEGER {
		    no (1),
		    yes (2)
		}
	ACCESS	read-write
	STATUS	mandatory
	DESCRIPTION	"Send Atm Inverse Arp request for this connection."
	::= { mibinternetProfileEntry 351 }

    internetProfile-AtmConnectOptions-Fr08Mode	OBJECT-TYPE
	SYNTAX	INTEGER {
		    translation (1),
		    transparent (2)
		}
	ACCESS	read-write
	STATUS	mandatory
	DESCRIPTION	"The FR-08 transparent mode"
	::= { mibinternetProfileEntry 379 }

    internetProfile-AtmConnectOptions-AtmCircuitProfile	OBJECT-TYPE
	SYNTAX	DisplayString
	ACCESS	read-write
	STATUS	mandatory
	DESCRIPTION	"The atm circuit profile name to be used for this connection."
	::= { mibinternetProfileEntry 439 }

    internetProfile-AtmConnectOptions-OamAisF5	OBJECT-TYPE
	SYNTAX	INTEGER {
		    disable (1),
		    segment (2),
		    endToEnd (3)
		}
	ACCESS	read-write
	STATUS	mandatory
	DESCRIPTION	"Disable/Enable sending OAM AIS F5 cells when pvc is down."
	::= { mibinternetProfileEntry 456 }

    internetProfile-AtmConnectOptions-OamSupport	OBJECT-TYPE
	SYNTAX	INTEGER {
		    no (1),
		    yes (2)
		}
	ACCESS	read-write
	STATUS	mandatory
	DESCRIPTION	"Is F4 OAM supported? It is used only when vp-switching is yes. The Stinger system can only support F4 OAM for 50 VPC segments in total."
	::= { mibinternetProfileEntry 457 }

    internetProfile-AtmConnectOptions-Mtu	OBJECT-TYPE
	SYNTAX	INTEGER
	ACCESS	read-write
	STATUS	mandatory
	DESCRIPTION	"The maximum packet size (excluding LLC encapsulation if used) that can be transmitted to a remote peer without performing fragmentation."
	::= { mibinternetProfileEntry 469 }

    internetProfile-Visa2Options-IdleCharacterDelay	OBJECT-TYPE
	SYNTAX	INTEGER
	ACCESS	read-write
	STATUS	mandatory
	DESCRIPTION	"Idle Character Delay in milliseconds."
	::= { mibinternetProfileEntry 271 }

    internetProfile-Visa2Options-FirstDataForwardCharacter	OBJECT-TYPE
	SYNTAX	DisplayString
	ACCESS	read-write
	STATUS	mandatory
	DESCRIPTION	"First Data Forwarding Character. Default is 0x04"
	::= { mibinternetProfileEntry 272 }

    internetProfile-Visa2Options-SecondDataForwardCharacter	OBJECT-TYPE
	SYNTAX	DisplayString
	ACCESS	read-write
	STATUS	mandatory
	DESCRIPTION	"Second Data Forwarding Character. Default is 0x06"
	::= { mibinternetProfileEntry 273 }

    internetProfile-Visa2Options-ThirdDataForwardCharacter	OBJECT-TYPE
	SYNTAX	DisplayString
	ACCESS	read-write
	STATUS	mandatory
	DESCRIPTION	"Third Data Forwarding Character. Default is 0x15"
	::= { mibinternetProfileEntry 274 }

    internetProfile-Visa2Options-FourthDataForwardCharacter	OBJECT-TYPE
	SYNTAX	DisplayString
	ACCESS	read-write
	STATUS	mandatory
	DESCRIPTION	"Fourth Data Forwarding Character. Default is 0x05"
	::= { mibinternetProfileEntry 275 }

    internetProfile-Visa2Options-o1CharSequence	OBJECT-TYPE
	SYNTAX	DisplayString
	ACCESS	read-write
	STATUS	mandatory
	DESCRIPTION	"1 character data forwarding sequence. Default is 0x03"
	::= { mibinternetProfileEntry 276 }

    internetProfile-Visa2Options-o2CharSequence	OBJECT-TYPE
	SYNTAX	DisplayString
	ACCESS	read-write
	STATUS	mandatory
	DESCRIPTION	"2 character data forwarding sequence. Default is 0x00:0x03"
	::= { mibinternetProfileEntry 277 }

    internetProfile-SdtnPacketsServer	OBJECT-TYPE
	SYNTAX	INTEGER {
		    no (1),
		    yes (2)
		}
	ACCESS	read-write
	STATUS	mandatory
	DESCRIPTION	"Decides if this profile Handles sdtn-packets. Note, the Sdtn data packets may still be encapsulated"
	::= { mibinternetProfileEntry 278 }

    internetProfile-oATString	OBJECT-TYPE
	SYNTAX	DisplayString
	ACCESS	read-write
	STATUS	mandatory
	DESCRIPTION	"Allows the user to enter customized AT commands in the modem dial or answer string."
	::= { mibinternetProfileEntry 279 }

    internetProfile-PortRedirectOptions-Protocol	OBJECT-TYPE
	SYNTAX	INTEGER {
		    none (1),
		    tcp (7),
		    udp (18)
		}
	ACCESS	read-write
	STATUS	mandatory
	DESCRIPTION	"The protocol to be redirected."
	::= { mibinternetProfileEntry 280 }

    internetProfile-PortRedirectOptions-PortNumber	OBJECT-TYPE
	SYNTAX	INTEGER
	ACCESS	read-write
	STATUS	mandatory
	DESCRIPTION	"Port number to be redirected."
	::= { mibinternetProfileEntry 281 }

    internetProfile-PortRedirectOptions-RedirectAddress	OBJECT-TYPE
	SYNTAX	IpAddress
	ACCESS	read-write
	STATUS	mandatory
	DESCRIPTION	"IP Address of server to which packet is to be redirected."
	::= { mibinternetProfileEntry 282 }

    internetProfile-PppoeOptions-Pppoe	OBJECT-TYPE
	SYNTAX	INTEGER {
		    no (1),
		    yes (2)
		}
	ACCESS	read-write
	STATUS	mandatory
	DESCRIPTION	"Enable or disable the ability to establish PPP over Ethernet session over this interface."
	::= { mibinternetProfileEntry 288 }

    internetProfile-PppoeOptions-BridgeNonPppoe	OBJECT-TYPE
	SYNTAX	INTEGER {
		    no (1),
		    yes (2)
		}
	ACCESS	read-write
	STATUS	mandatory
	DESCRIPTION	"States wheather to bridge all other protocols except PPPoE on this interface or not."
	::= { mibinternetProfileEntry 289 }

    internetProfile-AtmQosOptions-UsrUpStreamContract	OBJECT-TYPE
	SYNTAX	DisplayString
	ACCESS	read-write
	STATUS	mandatory
	DESCRIPTION	"Quality of Service (QOS) contract for user up stream traffic"
	::= { mibinternetProfileEntry 352 }

    internetProfile-AtmQosOptions-UsrDnStreamContract	OBJECT-TYPE
	SYNTAX	DisplayString
	ACCESS	read-write
	STATUS	mandatory
	DESCRIPTION	"Quality of Service (QOS) contract for user down stream traffic"
	::= { mibinternetProfileEntry 353 }

    internetProfile-AtmQosOptions-SubtendingHops	OBJECT-TYPE
	SYNTAX	INTEGER {
		    n-0Level (1),
		    n-1Level (2),
		    n-2Level (3),
		    n-3Level (4)
		}
	ACCESS	read-write
	STATUS	mandatory
	DESCRIPTION	"Number of hops from which the end-point of this connection originates"
	::= { mibinternetProfileEntry 470 }

    internetProfile-BirOptions-Enable	OBJECT-TYPE
	SYNTAX	INTEGER {
		    no (1),
		    yes (2)
		}
	ACCESS	read-write
	STATUS	mandatory
	DESCRIPTION	"Enable or disable the BIR on this interface."
	::= { mibinternetProfileEntry 290 }

    internetProfile-BirOptions-ProxyArp	OBJECT-TYPE
	SYNTAX	INTEGER {
		    no (1),
		    yes (2)
		}
	ACCESS	read-write
	STATUS	mandatory
	DESCRIPTION	"Specify how proxy arp is to be used on an interface."
	::= { mibinternetProfileEntry 291 }

    internetProfile-AtmAalOptions-AalEnabled	OBJECT-TYPE
	SYNTAX	INTEGER {
		    no (1),
		    yes (2)
		}
	ACCESS	read-only
	STATUS	mandatory
	DESCRIPTION	"Enable the AAl options"
	::= { mibinternetProfileEntry 440 }

    internetProfile-AtmAalOptions-AalType	OBJECT-TYPE
	SYNTAX	INTEGER {
		    aal0 (1),
		    aal5 (2),
		    unspecified (3)
		}
	ACCESS	read-write
	STATUS	mandatory
	DESCRIPTION	"ATM Adaptation Layer type"
	::= { mibinternetProfileEntry 441 }

    internetProfile-AtmAalOptions-TransmitSduSize	OBJECT-TYPE
	SYNTAX	INTEGER
	ACCESS	read-write
	STATUS	mandatory
	DESCRIPTION	"Size of the trasmitt Service Data Unit in octets."
	::= { mibinternetProfileEntry 442 }

    internetProfile-AtmAalOptions-ReceiveSduSize	OBJECT-TYPE
	SYNTAX	INTEGER
	ACCESS	read-write
	STATUS	mandatory
	DESCRIPTION	"Size of the receive Service Data Unit in octets."
	::= { mibinternetProfileEntry 443 }

    internetProfile-ConnUser	OBJECT-TYPE
	SYNTAX	INTEGER {
		    default (1),
		    cpcs (2)
		}
	ACCESS	read-only
	STATUS	mandatory
	DESCRIPTION	"Connetion User type ."
	::= { mibinternetProfileEntry 444 }

    internetProfile-ModemOnHoldTimeout	OBJECT-TYPE
	SYNTAX	INTEGER {
		    mohDisabled (1),
		    n-10SecMohTimeout (2),
		    n-20SecMohTimeout (3),
		    n-30SecMohTimeout (4),
		    n-40SecMohTimeout (5),
		    n-1MinMohTimeout (6),
		    n-2MinMohTimeout (7),
		    n-3MinMohTimeout (8),
		    n-4MinMohTimeout (9),
		    n-6MinMohTimeout (10),
		    n-8MinMohTimeout (11),
		    n-12MinMohTimeout (12),
		    n-16MinMohTimeout (13),
		    noLimitMohTimeout (14),
		    connProfileUseGlobal (15)
		}
	ACCESS	read-write
	STATUS	mandatory
	DESCRIPTION	"The allowable Modem-on-Hold timeout values."
	::= { mibinternetProfileEntry 458 }

    internetProfile-PriorityOptions-Enabled	OBJECT-TYPE
	SYNTAX	INTEGER {
		    no (1),
		    yes (2)
		}
	ACCESS	read-write
	STATUS	mandatory
	DESCRIPTION	"Enable priority classification."
	::= { mibinternetProfileEntry 482 }

    internetProfile-PriorityOptions-PacketClassification	OBJECT-TYPE
	SYNTAX	INTEGER {
		    qosTag (2),
		    udpPortRange (3)
		}
	ACCESS	read-write
	STATUS	mandatory
	DESCRIPTION	"Method used to classify PPP packets."
	::= { mibinternetProfileEntry 477 }

    internetProfile-PriorityOptions-MaxRtpPacketDelay	OBJECT-TYPE
	SYNTAX	INTEGER
	ACCESS	read-write
	STATUS	mandatory
	DESCRIPTION	"Maximum delay for RTP packets in milli-seconds. Used for calculating the fragment size for the non-rtp traffic using the same link."
	::= { mibinternetProfileEntry 478 }

    internetProfile-PriorityOptions-MinimumRtpPort	OBJECT-TYPE
	SYNTAX	INTEGER
	ACCESS	read-write
	STATUS	mandatory
	DESCRIPTION	"Minimum UDP port for prioritization"
	::= { mibinternetProfileEntry 479 }

    internetProfile-PriorityOptions-MaximumRtpPort	OBJECT-TYPE
	SYNTAX	INTEGER
	ACCESS	read-write
	STATUS	mandatory
	DESCRIPTION	"Maximum UDP port for prioritization"
	::= { mibinternetProfileEntry 480 }

    internetProfile-PriorityOptions-NoHighPrioPktDuration	OBJECT-TYPE
	SYNTAX	INTEGER
	ACCESS	read-write
	STATUS	mandatory
	DESCRIPTION	"The number of seconds of no high priority packets before disabling IP fragmentation of low priority packets. The value 0 disables checking duration of no high priority packet."
	::= { mibinternetProfileEntry 481 }

    internetProfile-Action-o	OBJECT-TYPE
	SYNTAX	INTEGER {
		    noAction (1),
		    createProfile (2),
		    deleteProfile (3)
		}
	ACCESS	read-write
	STATUS	mandatory
	DESCRIPTION	""
	::= { mibinternetProfileEntry 249 }


	-- The mibinternetProfile__ipx_options__ipx_sap_hs_proxy_net table
	--
	-- This table contains parameters for the mibinternetProfile__ipx_options__ipx_sap_hs_proxy_net profile
	--

    mibinternetProfile-IpxOptions-IpxSapHsProxyNetTable	OBJECT-TYPE
	SYNTAX		SEQUENCE OF MibinternetProfile-IpxOptions-IpxSapHsProxyNetEntry
	ACCESS		not-accessible
	STATUS		mandatory
	DESCRIPTION	"A list of mibinternetProfile__ipx_options__ipx_sap_hs_proxy_net profile entries."
	::= { mibinternetProfile 2 }

    mibinternetProfile-IpxOptions-IpxSapHsProxyNetEntry	OBJECT-TYPE
	SYNTAX		MibinternetProfile-IpxOptions-IpxSapHsProxyNetEntry
	ACCESS		not-accessible
	STATUS		mandatory
	DESCRIPTION	"A mibinternetProfile__ipx_options__ipx_sap_hs_proxy_net entry containing objects that
			 maps to the parameters of mibinternetProfile__ipx_options__ipx_sap_hs_proxy_net profile."
	INDEX		{ internetProfile-IpxOptions-IpxSapHsProxyNet-Station, internetProfile-IpxOptions-IpxSapHsProxyNet-Index-o }
	::= { mibinternetProfile-IpxOptions-IpxSapHsProxyNetTable 1 }

    MibinternetProfile-IpxOptions-IpxSapHsProxyNetEntry ::=
	SEQUENCE {
	    internetProfile-IpxOptions-IpxSapHsProxyNet-Station
		DisplayString,
	    internetProfile-IpxOptions-IpxSapHsProxyNet-Index-o
		INTEGER,
	    internetProfile-IpxOptions-IpxSapHsProxyNet
		INTEGER
	}

    internetProfile-IpxOptions-IpxSapHsProxyNet-Station	OBJECT-TYPE
	SYNTAX	DisplayString
	ACCESS	read-only
	STATUS	mandatory
	DESCRIPTION	""
	::= { mibinternetProfile-IpxOptions-IpxSapHsProxyNetEntry 1 }

    internetProfile-IpxOptions-IpxSapHsProxyNet-Index-o	OBJECT-TYPE
	SYNTAX	INTEGER
	ACCESS	read-only
	STATUS	mandatory
	DESCRIPTION	""
	::= { mibinternetProfile-IpxOptions-IpxSapHsProxyNetEntry 2 }

    internetProfile-IpxOptions-IpxSapHsProxyNet	OBJECT-TYPE
	SYNTAX	INTEGER
	ACCESS	read-write
	STATUS	mandatory
	DESCRIPTION	"The Network# for IPX SAP Proxy Home Server."
	::= { mibinternetProfile-IpxOptions-IpxSapHsProxyNetEntry 3 }

END
