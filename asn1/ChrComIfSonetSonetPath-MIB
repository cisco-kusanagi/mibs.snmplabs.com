ChrComIfSonetSonetPath-MIB

--FORCE-INCLUDE	<mib.h>
--FORCE-INCLUDE	<snmpdefs.h>
--FORCE-INCLUDE	"mibhand.h"

	DEFINITIONS  ::=  BEGIN

IMPORTS
	OBJECT-TYPE, Counter32			FROM  SNMPv2-SMI
	Integer32, Unsigned32			FROM  SNMPv2-SMI
	chrComIfSonet				FROM  Chromatis-MIB
	ifIndex					FROM  RFC1213-MIB
	STSrates				FROM  SonetTypes-MIB
	CastType				FROM  SonetTypes-MIB
	PathTP					FROM  SonetTypes-MIB
	TPdevice				FROM  SonetTypes-MIB
	TruthValue				FROM  SonetTypes-MIB
	NIMlevel				FROM  SonetTypes-MIB
	TxTrafficType				FROM  SonetTypes-MIB
	TraceType				FROM  SonetTypes-MIB
	EnableDisableType			FROM  SonetTypes-MIB
	DisplayString			FROM  RFC1213-MIB
	PloopbackType				FROM  SonetTypes-MIB
	RowStatus				FROM  SonetTypes-MIB;

-- chrComIfSonetSonetPath Table

chrComIfSonetSonetPathTable		OBJECT-TYPE
	SYNTAX		SEQUENCE OF ChrComIfSonetSonetPathEntry
	MAX-ACCESS	not-accessible
	STATUS		current
	DESCRIPTION
	"The Sonet Line private Table"
	::= { chrComIfSonet 6}

chrComIfSonetSonetPathEntry		OBJECT-TYPE
	SYNTAX		ChrComIfSonetSonetPathEntry
	MAX-ACCESS	not-accessible
	STATUS		current
	DESCRIPTION
	""
	INDEX  {  ifIndex }

--DEFAULT  get-function-async  MNIL_GetRoutine
--DEFAULT  set-function-async  MNIL_SetRoutine
--DEFAULT  next-function-async MNIL_NextRoutine
--DEFAULT  test-function-async MNIL_TestRoutine
--DEFAULT  cookie "SonetPath"
	::= { chrComIfSonetSonetPathTable  1 }

ChrComIfSonetSonetPathEntry  ::=
	SEQUENCE  {
	chrComIfSonetpathRate		STSrates,
	chrComIfSonetSonetPathCastType	CastType,
	chrComIfSonetpathTP			PathTP,
	chrComIfSonetTPdevice		TPdevice,
	chrComIfSonetInbandMng		TruthValue,
	chrComIfSonetNIMlevel		NIMlevel,
	chrComIfSonetpathPeerSetID		Unsigned32	(0..4294967295),
	chrComIfSonetVirtualId		Unsigned32	(0..4294967295),
	chrComIfSonetSonetPathXcID		Unsigned32	(0..4294967295),
	chrComIfSonetTransmitedTraffic	TxTrafficType,
	chrComIfSonetExpectedTraffic		Unsigned32	(0..4294967295),
	chrComIfSonetReceivedTraffic		Unsigned32	(0..4294967295),
	chrComIfSonetPathTrace		TraceType,
	chrComIfSonetPathTraceMatchCheckState EnableDisableType,
	chrComIfSonetTransmittedPathTrace	DisplayString	(SIZE (0..64)),
	chrComIfSonetExpectedPathTrace	DisplayString	(SIZE (0..64)),
	chrComIfSonetReceivedPathTrace	DisplayString	(SIZE (0..64)),
	chrComIfSonetEnhancedRDI		EnableDisableType,
	chrComIfSonetPathLoopback		PloopbackType,
	chrComIfSonetAlarmVector		Integer32	(0..65535),
	chrComIfSonetAlarmSeverityIndex	Unsigned32	(0..4294967295),
	chrComIfSonetrowStatus		RowStatus
}

chrComIfSonetpathRate 	OBJECT-TYPE
	SYNTAX		STSrates
	MAX-ACCESS 	read-write
	STATUS 		current
	DESCRIPTION
	""
	::= { chrComIfSonetSonetPathEntry  1 }

chrComIfSonetSonetPathCastType 	OBJECT-TYPE
	SYNTAX		CastType
	MAX-ACCESS 	read-write
	STATUS 		current
	DESCRIPTION
	""
	::= { chrComIfSonetSonetPathEntry  2 }

chrComIfSonetpathTP 	OBJECT-TYPE
	SYNTAX		PathTP
	MAX-ACCESS 	read-only
	STATUS 		current
	DESCRIPTION
	""
	::= { chrComIfSonetSonetPathEntry  3 }

chrComIfSonetTPdevice 	OBJECT-TYPE
	SYNTAX		TPdevice
	MAX-ACCESS 	read-only
	STATUS 		current
	DESCRIPTION
	""
	::= { chrComIfSonetSonetPathEntry  4 }

chrComIfSonetInbandMng 	OBJECT-TYPE
	SYNTAX		TruthValue
	MAX-ACCESS 	read-only
	STATUS 		current
	DESCRIPTION
	""
	::= { chrComIfSonetSonetPathEntry  5 }

chrComIfSonetNIMlevel 	OBJECT-TYPE
	SYNTAX		NIMlevel
	MAX-ACCESS 	read-write
	STATUS 		current
	DESCRIPTION
	""
	::= { chrComIfSonetSonetPathEntry  6 }

chrComIfSonetpathPeerSetID 	OBJECT-TYPE
	SYNTAX		Unsigned32	(0..4294967295)
	MAX-ACCESS 	read-write
	STATUS 		current
	DESCRIPTION
	""
	::= { chrComIfSonetSonetPathEntry  7 }

chrComIfSonetVirtualId 	OBJECT-TYPE
	SYNTAX		Unsigned32	(0..4294967295)
	MAX-ACCESS 	read-only
	STATUS 		current
	DESCRIPTION
	"IfIndex of virtual interface (VS), which is also an index to the PathProtectionPeerTable.
NullPathPeerID indicates that no Path Protection is configured for the line
"
	::= { chrComIfSonetSonetPathEntry  8 }

chrComIfSonetSonetPathXcID 	OBJECT-TYPE
	SYNTAX		Unsigned32	(0..4294967295)
	MAX-ACCESS 	read-only
	STATUS 		current
	DESCRIPTION
	""
	::= { chrComIfSonetSonetPathEntry  9 }

chrComIfSonetTransmitedTraffic 	OBJECT-TYPE
	SYNTAX		TxTrafficType
	MAX-ACCESS 	read-write
	STATUS 		current
	DESCRIPTION
	"This parameter defines the transmitted signal label in Sonet interfaces"
	::= { chrComIfSonetSonetPathEntry  10 }

chrComIfSonetExpectedTraffic 	OBJECT-TYPE
	SYNTAX		Unsigned32	(0..4294967295)
	MAX-ACCESS 	read-write
	STATUS 		current
	DESCRIPTION
	"This parameter defines the expected signal label in Sonet interfaces"
	::= { chrComIfSonetSonetPathEntry  11 }

chrComIfSonetReceivedTraffic 	OBJECT-TYPE
	SYNTAX		Unsigned32	(0..4294967295)
	MAX-ACCESS 	read-only
	STATUS 		current
	DESCRIPTION
	"This parameter defines the received signal label in Sonet interfaces"
	::= { chrComIfSonetSonetPathEntry  12 }

chrComIfSonetPathTrace 	OBJECT-TYPE
	SYNTAX		TraceType
	MAX-ACCESS 	read-write
	STATUS 		current
	DESCRIPTION
	""
	::= { chrComIfSonetSonetPathEntry  13 }

chrComIfSonetPathTraceMatchCheckState 	OBJECT-TYPE
	SYNTAX		EnableDisableType
	MAX-ACCESS 	read-write
	STATUS 		current
	DESCRIPTION
	"this field is used for enabling and disabling the path trace match check"
	::= { chrComIfSonetSonetPathEntry  14 }

chrComIfSonetTransmittedPathTrace 	OBJECT-TYPE
	SYNTAX		DisplayString	(SIZE (0..64))
	MAX-ACCESS 	read-write
	STATUS 		current
	DESCRIPTION
	"This parameter defines the transmitted path trace"
	::= { chrComIfSonetSonetPathEntry  15 }

chrComIfSonetExpectedPathTrace 	OBJECT-TYPE
	SYNTAX		DisplayString	(SIZE (0..64))
	MAX-ACCESS 	read-write
	STATUS 		current
	DESCRIPTION
	"This parameter defines the expected path trace"
	::= { chrComIfSonetSonetPathEntry  16 }

chrComIfSonetReceivedPathTrace 	OBJECT-TYPE
	SYNTAX		DisplayString	(SIZE (0..64))
	MAX-ACCESS 	read-only
	STATUS 		current
	DESCRIPTION
	"The actual received signal label on sonet signal"
	::= { chrComIfSonetSonetPathEntry  17 }

chrComIfSonetEnhancedRDI 	OBJECT-TYPE
	SYNTAX		EnableDisableType
	MAX-ACCESS 	read-write
	STATUS 		current
	DESCRIPTION
	""
	::= { chrComIfSonetSonetPathEntry  18 }

chrComIfSonetPathLoopback 	OBJECT-TYPE
	SYNTAX		PloopbackType
	MAX-ACCESS 	read-write
	STATUS 		current
	DESCRIPTION
	""
	::= { chrComIfSonetSonetPathEntry  19 }

chrComIfSonetAlarmVector 	OBJECT-TYPE
	SYNTAX		Integer32	(0..65535)
	MAX-ACCESS 	read-only
	STATUS 		current
	DESCRIPTION
	"16 bit field.  the Sonet Section Alarm Vector field. "
	::= { chrComIfSonetSonetPathEntry  20 }

chrComIfSonetAlarmSeverityIndex 	OBJECT-TYPE
	SYNTAX		Unsigned32	(0..4294967295)
	MAX-ACCESS 	read-write
	STATUS 		current
	DESCRIPTION
	""
	::= { chrComIfSonetSonetPathEntry  21 }

chrComIfSonetrowStatus 	OBJECT-TYPE
	SYNTAX		RowStatus
	MAX-ACCESS 	read-write
	STATUS 		current
	DESCRIPTION
	""
	::= { chrComIfSonetSonetPathEntry  22 }


END
