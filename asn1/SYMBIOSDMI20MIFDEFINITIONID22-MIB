-- MIB generated by miftomib version 1.0a

SYMBIOSDMI20MIFDEFINITIONID22-MIB DEFINITIONS ::= BEGIN

-- This file is the Symbios MIF for DMI 2.0

IMPORTS
    OBJECT-TYPE
    FROM RFC-1212
    Counter, enterprises
    FROM RFC1155-SMI
    DisplayString
    FROM RFC1213-MIB
	 TRAP-TYPE FROM RFC-1215;

DmiCounter			::= Counter
DmiInteger			::= INTEGER
DmiInteger64X		::= INTEGER (-18446744073709551615..18446744073709551615)
DmiDisplaystring	::= DisplayString
DmiDateX				::= OCTET STRING (SIZE (28))
DmiComponentIndex	::= INTEGER

symbios               	OBJECT IDENTIFIER ::= {enterprises 1123}
cosprings             	OBJECT IDENTIFIER ::= {symbios 3}
scsi             		OBJECT IDENTIFIER ::= {cosprings 1}
fam8xx             	OBJECT IDENTIFIER ::= {scsi 2}
id22             		OBJECT IDENTIFIER ::= {fam8xx 22}
dmtfGroups          	OBJECT IDENTIFIER ::= {id22 1}

SComponentid ::= SEQUENCE {
	a1Manufacturer                          	DmiDisplaystring,
	a1Product                               	DmiDisplaystring,
	a1Version                               	DmiDisplaystring,
	a1SerialNumber                          	DmiDisplaystring,
	a1Installation                          	DmiDateX,
	a1Verify                                	DmiInteger
}

tComponentid OBJECT-TYPE
	SYNTAX		SEQUENCE OF SComponentid
	ACCESS		not-accessible
	STATUS		mandatory
	DESCRIPTION	"This group defines the attributes common to all components.
This group is required."
	::= {dmtfGroups 1}

eComponentid OBJECT-TYPE
	SYNTAX		SComponentid
	ACCESS		not-accessible
	STATUS		mandatory
	DESCRIPTION	""
	INDEX		{DmiComponentIndex}
	::= {tComponentid 1}

a1Manufacturer OBJECT-TYPE
	SYNTAX		DmiDisplaystring
	ACCESS		read-only
	STATUS		mandatory
	DESCRIPTION	"Manufacturer of this component."
	::= {eComponentid 1}

a1Product OBJECT-TYPE
	SYNTAX		DmiDisplaystring
	ACCESS		read-only
	STATUS		mandatory
	DESCRIPTION	"Product name for this component."
	::= {eComponentid 2}

a1Version OBJECT-TYPE
	SYNTAX		DmiDisplaystring
	ACCESS		read-only
	STATUS		mandatory
	DESCRIPTION	"Version number of this component."
	::= {eComponentid 3}

a1SerialNumber OBJECT-TYPE
	SYNTAX		DmiDisplaystring
	ACCESS		read-only
	STATUS		mandatory
	DESCRIPTION	"Serial number for this component"
	::= {eComponentid 4}

a1Installation OBJECT-TYPE
	SYNTAX		DmiDateX
	ACCESS		read-only
	STATUS		mandatory
	DESCRIPTION	"The installation date and time of this component. The Service
Layer assigns this value, the manufacturer should leave it blank."
	::= {eComponentid 5}

a1Verify OBJECT-TYPE
	SYNTAX		INTEGER {
		vAnErrorOccurredCheckStatusCode         	(0),
		vThisComponentDoesNotExist              	(1),
		vTheVerifyIsNotSupported                	(2),
		vReserved                               	(3),
		vThisComponentExistsButTheFunctionalityI	(4),
		vThisComponentExistsButTheFunctionality1	(5),
		vThisComponentExistsAndIsNotFunctioningC	(6),
		vThisComponentExistsAndIsFunctioningCorr	(7)
	}
	ACCESS		read-only
	STATUS		mandatory
	DESCRIPTION	"A code that provides a level of verification that the component
is still installed and working."
	::= {eComponentid 6}

SSubcomponentSoftware ::= SEQUENCE {
	a2SoftwareIndex                         	DmiInteger,
	a2Type                                  	DmiDisplaystring,
	a2Vendor                                	DmiDisplaystring,
	a2Version                               	DmiDisplaystring,
	a2Description                           	DmiDisplaystring,
	a2IdentificationCode                    	DmiDisplaystring,
	a2LanguageEdition                       	DmiDisplaystring,
	a2InterfaceDescription                  	DmiDisplaystring,
	a2InterfaceVersion                      	DmiDisplaystring
}

tSubcomponentSoftware OBJECT-TYPE
	SYNTAX		SEQUENCE OF SSubcomponentSoftware
	ACCESS		not-accessible
	STATUS		mandatory
	DESCRIPTION	"This group describes the software resources that are used
by a component or subcomponent."
	::= {dmtfGroups 2}

eSubcomponentSoftware OBJECT-TYPE
	SYNTAX		SSubcomponentSoftware
	ACCESS		not-accessible
	STATUS		mandatory
	DESCRIPTION	""
	INDEX		{DmiComponentIndex, a2SoftwareIndex}
	::= {tSubcomponentSoftware 1}

a2SoftwareIndex OBJECT-TYPE
	SYNTAX		DmiInteger
	ACCESS		read-only
	STATUS		mandatory
	DESCRIPTION	"An index into the SubComponent Software table"
	::= {eSubcomponentSoftware 1}

a2Type OBJECT-TYPE
	SYNTAX		DmiDisplaystring
	ACCESS		read-only
	STATUS		mandatory
	DESCRIPTION	"The type of software resource described by this row.  For
example this value would be 'Device Driver', 'INF File', 'Boot ROM',  and
etc."
	::= {eSubcomponentSoftware 2}

a2Vendor OBJECT-TYPE
	SYNTAX		DmiDisplaystring
	ACCESS		read-only
	STATUS		mandatory
	DESCRIPTION	"The name of the vendor who supplied this piece of software."
	::= {eSubcomponentSoftware 3}

a2Version OBJECT-TYPE
	SYNTAX		DmiDisplaystring
	ACCESS		read-only
	STATUS		mandatory
	DESCRIPTION	"The revision level of this piece of software.  For example
the Version Major, Version Minor, Revision, and Build numbers."
	::= {eSubcomponentSoftware 4}

a2Description OBJECT-TYPE
	SYNTAX		DmiDisplaystring
	ACCESS		read-only
	STATUS		mandatory
	DESCRIPTION	"An additional description of this piece of software"
	::= {eSubcomponentSoftware 5}

a2IdentificationCode OBJECT-TYPE
	SYNTAX		DmiDisplaystring
	ACCESS		read-only
	STATUS		mandatory
	DESCRIPTION	"The Stock Keeping Unit (SKU) or Part Number for this piece
of software."
	::= {eSubcomponentSoftware 6}

a2LanguageEdition OBJECT-TYPE
	SYNTAX		DmiDisplaystring
	ACCESS		read-only
	STATUS		mandatory
	DESCRIPTION	"Identifies the language edition of this piece of software."
	::= {eSubcomponentSoftware 7}

a2InterfaceDescription OBJECT-TYPE
	SYNTAX		DmiDisplaystring
	ACCESS		read-only
	STATUS		mandatory
	DESCRIPTION	"This is the specification or operating system to which this
piece of software conforms. (e.g. 'Microsoft NT', 'NetWare', etc.)"
	::= {eSubcomponentSoftware 8}

a2InterfaceVersion OBJECT-TYPE
	SYNTAX		DmiDisplaystring
	ACCESS		read-only
	STATUS		mandatory
	DESCRIPTION	"The specification or operating system version to which this
piece of software conforms. (e.g. '4.0 or higher', '3.xx', etc.)"
	::= {eSubcomponentSoftware 9}

SWorldwideIdentifer ::= SEQUENCE {
	a3WorldwideIdentifierIndex              	DmiInteger,
	a3WorldwideIdentifierType               	DmiInteger,
	a3WorldwideIdentifier                   	DmiDisplaystring
}

tWorldwideIdentifer OBJECT-TYPE
	SYNTAX		SEQUENCE OF SWorldwideIdentifer
	ACCESS		not-accessible
	STATUS		mandatory
	DESCRIPTION	"The Worldwide Identifer"
	::= {dmtfGroups 3}

eWorldwideIdentifer OBJECT-TYPE
	SYNTAX		SWorldwideIdentifer
	ACCESS		not-accessible
	STATUS		mandatory
	DESCRIPTION	""
	INDEX		{DmiComponentIndex, a3WorldwideIdentifierIndex}
	::= {tWorldwideIdentifer 1}

a3WorldwideIdentifierIndex OBJECT-TYPE
	SYNTAX		DmiInteger
	ACCESS		read-only
	STATUS		mandatory
	DESCRIPTION	"An index into the Worldwide Identifier table."
	::= {eWorldwideIdentifer 1}

a3WorldwideIdentifierType OBJECT-TYPE
	SYNTAX		INTEGER {
		vOther                                  	(1),
		vUnknown                                	(2),
		vNone                                   	(3),
		vVendorIdProductIdSerialNumber          	(4),
		vIeeeExtendedUniqueIdentifier64-bit     	(5),
		vFc-ph64-bitName-identifier             	(6),
		vBinary                                 	(7),
		vUnicode                                	(8),
		vLanMacAddress                          	(9),
		vWanAccessAddress                       	(10)
	}
	ACCESS		read-only
	STATUS		mandatory
	DESCRIPTION	"The type of identifier displayed by the Worldwide Identifier
attribute."
	::= {eWorldwideIdentifer 2}

a3WorldwideIdentifier OBJECT-TYPE
	SYNTAX		DmiDisplaystring
	ACCESS		read-only
	STATUS		mandatory
	DESCRIPTION	"The Worldwide identifier for this device."
	::= {eWorldwideIdentifer 3}

SFieldReplaceableUnit ::= SEQUENCE {
	a4FruIndex                              	DmiInteger,
	a4DeviceGroupIndex                      	DmiInteger,
	a4Description                           	DmiDisplaystring,
	a4Manufacturer                          	DmiDisplaystring,
	a4Model                                 	DmiDisplaystring,
	a4PartNumber                            	DmiDisplaystring,
	a4FruSerialNumber                       	DmiDisplaystring,
	a4RevisionLevel                         	DmiDisplaystring,
	a4WarrantyStartDate                     	DmiDateX,
	a4WarrantyDuration                      	DmiInteger,
	a4SupportPhoneNumber                    	DmiDisplaystring,
	a4FruInternetUniformResourceLocator     	DmiDisplaystring
}

tFieldReplaceableUnit OBJECT-TYPE
	SYNTAX		SEQUENCE OF SFieldReplaceableUnit
	ACCESS		not-accessible
	STATUS		mandatory
	DESCRIPTION	"A Field Replaceable Unit (FRU), is defined as a hardware
component which is designed to be separately removable for replacement or
repair. For the purposes of this definition, a motherboard and a fixed hard
disk are FRUs, whereas a fixed hard disk platter or a chip fixed in place
on the motherboard are not FRUs since they are not designed to be separately
removable. Each instance within the FRU table should contain the device group
and instance data for the associated hardware component."
	::= {dmtfGroups 4}

eFieldReplaceableUnit OBJECT-TYPE
	SYNTAX		SFieldReplaceableUnit
	ACCESS		not-accessible
	STATUS		mandatory
	DESCRIPTION	""
	INDEX		{DmiComponentIndex, a4FruIndex}
	::= {tFieldReplaceableUnit 1}

a4FruIndex OBJECT-TYPE
	SYNTAX		DmiInteger
	ACCESS		read-only
	STATUS		mandatory
	DESCRIPTION	"The index into the Field Replaceable Unit table."
	::= {eFieldReplaceableUnit 1}

a4DeviceGroupIndex OBJECT-TYPE
	SYNTAX		DmiInteger
	ACCESS		read-only
	STATUS		mandatory
	DESCRIPTION	"The group ID of the group referencing this Field Replaceable
Unit instance."
	::= {eFieldReplaceableUnit 2}

a4Description OBJECT-TYPE
	SYNTAX		DmiDisplaystring
	ACCESS		read-only
	STATUS		mandatory
	DESCRIPTION	"A clear description of this Field Replaceable Unit."
	::= {eFieldReplaceableUnit 3}

a4Manufacturer OBJECT-TYPE
	SYNTAX		DmiDisplaystring
	ACCESS		read-only
	STATUS		mandatory
	DESCRIPTION	"The name of the company manufacturing or providing this Field
Replaceable Unit."
	::= {eFieldReplaceableUnit 4}

a4Model OBJECT-TYPE
	SYNTAX		DmiDisplaystring
	ACCESS		read-only
	STATUS		mandatory
	DESCRIPTION	"The manufacturer's model number for this Field Replaceable
Unit."
	::= {eFieldReplaceableUnit 5}

a4PartNumber OBJECT-TYPE
	SYNTAX		DmiDisplaystring
	ACCESS		read-only
	STATUS		mandatory
	DESCRIPTION	"A part number by which a replacement part can be ordered
for this Field Replaceable Unit."
	::= {eFieldReplaceableUnit 6}

a4FruSerialNumber OBJECT-TYPE
	SYNTAX		DmiDisplaystring
	ACCESS		read-only
	STATUS		mandatory
	DESCRIPTION	"The manufacturer's serial number for this Field Replaceable
Unit."
	::= {eFieldReplaceableUnit 7}

a4RevisionLevel OBJECT-TYPE
	SYNTAX		DmiDisplaystring
	ACCESS		read-only
	STATUS		mandatory
	DESCRIPTION	"The revision level of this Field Replaceable Unit."
	::= {eFieldReplaceableUnit 8}

a4WarrantyStartDate OBJECT-TYPE
	SYNTAX		DmiDateX
	ACCESS		read-only
	STATUS		mandatory
	DESCRIPTION	"The start date of the service warranty for this Field Replaceabl
 Unit."
	::= {eFieldReplaceableUnit 9}

a4WarrantyDuration OBJECT-TYPE
	SYNTAX		DmiInteger
	ACCESS		read-only
	STATUS		mandatory
	DESCRIPTION	"The total duration of this Field Replaceable Unit warranty
in months."
	::= {eFieldReplaceableUnit 10}

a4SupportPhoneNumber OBJECT-TYPE
	SYNTAX		DmiDisplaystring
	ACCESS		read-only
	STATUS		mandatory
	DESCRIPTION	"The phone number(s) for support for this Field Replaceable
Unit."
	::= {eFieldReplaceableUnit 11}

a4FruInternetUniformResourceLocator OBJECT-TYPE
	SYNTAX		DmiDisplaystring
	ACCESS		read-only
	STATUS		mandatory
	DESCRIPTION	"The Internet Uniform Resource Locator string that can be
used through a World Wide Web browser to obtain further information about
this FRU"
	::= {eFieldReplaceableUnit 12}

SStorageDevices ::= SEQUENCE {
	a5StorageDeviceIndex                    	DmiInteger,
	a5Type                                  	DmiInteger,
	a5TypeDescription                       	DmiDisplaystring,
	a5Sub-identifier                        	DmiDisplaystring,
	a5MediaDataBlockSize                    	DmiInteger,
	a5FormattedMediaCapacity                	DmiInteger64X,
	a5RemovableDevice                       	DmiInteger,
	a5DeviceLoaded                          	DmiInteger,
	a5RemovableMedia                        	DmiInteger,
	a5MediaLoaded                           	DmiInteger,
	a5Compression                           	DmiInteger,
	a5Encryption                            	DmiInteger
}

tStorageDevices OBJECT-TYPE
	SYNTAX		SEQUENCE OF SStorageDevices
	ACCESS		not-accessible
	STATUS		mandatory
	DESCRIPTION	"This group defines the mass storage devices in this system."
	::= {dmtfGroups 5}

eStorageDevices OBJECT-TYPE
	SYNTAX		SStorageDevices
	ACCESS		not-accessible
	STATUS		mandatory
	DESCRIPTION	""
	INDEX		{DmiComponentIndex, a5StorageDeviceIndex}
	::= {tStorageDevices 1}

a5StorageDeviceIndex OBJECT-TYPE
	SYNTAX		DmiInteger
	ACCESS		read-only
	STATUS		mandatory
	DESCRIPTION	"An index into the storage device table."
	::= {eStorageDevices 1}

a5Type OBJECT-TYPE
	SYNTAX		INTEGER {
		vOther                                  	(1),
		vUnknown                                	(2),
		vRigidDiskDrive                         	(3),
		vFlexibleDisketteDrive                  	(4),
		vOpticalWrite-onceread-manyWormDrive    	(6),
		vMagneto-opticalDrive                   	(7),
		vCompactDiskDrive                       	(8),
		vFlashDisk                              	(9),
		vCartridgeRigidDiskDrive                	(10),
		vOpticalFloppyDiskDrive                 	(11),
		vTapeDrive                              	(12),
		vMediaChanger                           	(13),
		vSolidState                             	(14),
		vDigitalVersatileDiskDvdDrive           	(15),
		vDigitalVersatileDiskDvdramRamDrive     	(16)
	}
	ACCESS		read-only
	STATUS		mandatory
	DESCRIPTION	"The type of this mass storage device.  If 'Other' is used,
then the Type Description attribute shall be used."
	::= {eStorageDevices 2}

a5TypeDescription OBJECT-TYPE
	SYNTAX		DmiDisplaystring
	ACCESS		read-only
	STATUS		mandatory
	DESCRIPTION	"A longer description of the storage device.  For example:
 3.5 inch flexible diskette drive using diskettes with a maximum capacity
of 1.44MB.  If 'Other' was specified above, then this field shall be used.
 Otherwise, the contents of this optional field shall not contradict the
Storage Device Type specified above."
	::= {eStorageDevices 3}

a5Sub-identifier OBJECT-TYPE
	SYNTAX		DmiDisplaystring
	ACCESS		read-only
	STATUS		mandatory
	DESCRIPTION	"The sub-identifier for this storage device (e.g., the device's
SCSI logical unit number)."
	::= {eStorageDevices 4}

a5MediaDataBlockSize OBJECT-TYPE
	SYNTAX		DmiInteger
	ACCESS		read-only
	STATUS		mandatory
	DESCRIPTION	"The size in bytes of the data blocks used on the storage
media.  If the media block size is unknown or not consistent across the media,
then this value shall be zero."
	::= {eStorageDevices 5}

a5FormattedMediaCapacity OBJECT-TYPE
	SYNTAX		DmiInteger64X
	ACCESS		read-only
	STATUS		mandatory
	DESCRIPTION	"The total size in bytes of this storage media after it has
been formatted."
	::= {eStorageDevices 6}

a5RemovableDevice OBJECT-TYPE
	SYNTAX		INTEGER {
		vFalse                                  	(0),
		vTrue                                   	(1),
		vUnknown                                	(2)
	}
	ACCESS		read-only
	STATUS		mandatory
	DESCRIPTION	"If true, then this storage device is removable (e.g.:  PCMCIA
device)."
	::= {eStorageDevices 7}

a5DeviceLoaded OBJECT-TYPE
	SYNTAX		INTEGER {
		vFalse                                  	(0),
		vTrue                                   	(1),
		vUnknown                                	(2)
	}
	ACCESS		read-only
	STATUS		mandatory
	DESCRIPTION	"If true, then the storage device is loaded.  If the device
is not removable, then this value shall be 'TRUE'."
	::= {eStorageDevices 8}

a5RemovableMedia OBJECT-TYPE
	SYNTAX		INTEGER {
		vFalse                                  	(0),
		vTrue                                   	(1),
		vUnknown                                	(2)
	}
	ACCESS		read-only
	STATUS		mandatory
	DESCRIPTION	"If true, then the media in this storage device is removable."
	::= {eStorageDevices 9}

a5MediaLoaded OBJECT-TYPE
	SYNTAX		INTEGER {
		vFalse                                  	(0),
		vTrue                                   	(1),
		vUnknown                                	(2)
	}
	ACCESS		read-only
	STATUS		mandatory
	DESCRIPTION	"If true, the media in this storage device is loaded.  If
the media is not removable, then this value shall be 'TRUE' "
	::= {eStorageDevices 10}

a5Compression OBJECT-TYPE
	SYNTAX		INTEGER {
		vFalse                                  	(0),
		vTrue                                   	(1),
		vUnknown                                	(2)
	}
	ACCESS		read-only
	STATUS		mandatory
	DESCRIPTION	"If true, the storage device supports compression."
	::= {eStorageDevices 11}

a5Encryption OBJECT-TYPE
	SYNTAX		INTEGER {
		vFalse                                  	(0),
		vTrue                                   	(1),
		vUnknown                                	(2)
	}
	ACCESS		read-only
	STATUS		mandatory
	DESCRIPTION	"If true, the storage device supports encryption."
	::= {eStorageDevices 12}

SStorageDevicesEvents ::= SEQUENCE {
	a6StorageDevicesEventType               	DmiInteger,
	a6EventSeverity                         	DmiInteger,
	a6EventIsStateBased                     	DmiInteger,
	a6EventStateKey                         	DmiInteger,
	a6AssociatedGroup                       	DmiDisplaystring,
	a6EventSystem                           	DmiInteger,
	a6EventSubsystem                        	DmiInteger,
	a6EventSolution                         	DmiInteger,
	a6InstanceDataPresent                   	DmiInteger,
	a6EventMessage                          	DmiDisplaystring
}

tStorageDevicesEvents OBJECT-TYPE
	SYNTAX		SEQUENCE OF SStorageDevicesEvents
	ACCESS		not-accessible
	STATUS		mandatory
	DESCRIPTION	"Storage Devices events."
	::= {dmtfGroups 6}

eStorageDevicesEvents OBJECT-TYPE
	SYNTAX		SStorageDevicesEvents
	ACCESS		not-accessible
	STATUS		mandatory
	DESCRIPTION	""
	INDEX		{DmiComponentIndex, a6AssociatedGroup}
	::= {tStorageDevicesEvents 1}

a6StorageDevicesEventType OBJECT-TYPE
	SYNTAX		INTEGER {
		vRebuildInProgress                      	(1),
		vStorageDeviceReadying                  	(2),
		vStorageDeviceError                     	(3),
		vSelf-monitoringWarning                 	(4)
	}
	ACCESS		read-only
	STATUS		mandatory
	DESCRIPTION	"The type of Storage Devices event that has occurred."
	::= {eStorageDevicesEvents 1}

a6EventSeverity OBJECT-TYPE
	SYNTAX		INTEGER {
		vMonitor                                	(1),
		vInformation                            	(2),
		vOk                                     	(4),
		vNon-critical                           	(8),
		vCritical                               	(16),
		vNon-recoverable                        	(32)
	}
	ACCESS		read-only
	STATUS		mandatory
	DESCRIPTION	"The severity of this event."
	::= {eStorageDevicesEvents 2}

a6EventIsStateBased OBJECT-TYPE
	SYNTAX		INTEGER {
		vFalse                                  	(0),
		vTrue                                   	(1)
	}
	ACCESS		read-only
	STATUS		mandatory
	DESCRIPTION	"The value of this attribute determined whether the Event
 being reported is a state-based Event or not.  If the value of this attribute
is TRUE then the Event is state-based.  Else the Event is not state-based"
	::= {eStorageDevicesEvents 3}

a6EventStateKey OBJECT-TYPE
	SYNTAX		DmiInteger
	ACCESS		read-only
	STATUS		mandatory
	DESCRIPTION	"This attribute holds the key identifying a row of the Event
State group within the Component in which the event generator group is located.
 The Current State attribute within the row contains the current state of
this state-based event.  The current state can be one of the four severities:
OK, Non-Critical, Critical, and Non-Recoverable."
	::= {eStorageDevicesEvents 4}

a6AssociatedGroup OBJECT-TYPE
	SYNTAX		DmiDisplaystring
	ACCESS		read-only
	STATUS		mandatory
	DESCRIPTION	"The"
	::= {eStorageDevicesEvents 5}

a6EventSystem OBJECT-TYPE
	SYNTAX		INTEGER {
		vOther                                  	(1),
		vUnknown                                	(2),
		vDomainValidation                       	(3),
		vDeviceScan                             	(4),
		vSmart                                  	(5)
	}
	ACCESS		read-only
	STATUS		mandatory
	DESCRIPTION	"The major functional aspect of the product causing the fault."
	::= {eStorageDevicesEvents 6}

a6EventSubsystem OBJECT-TYPE
	SYNTAX		INTEGER {
		vOther                                  	(1),
		vUnknown                                	(2)
	}
	ACCESS		read-only
	STATUS		mandatory
	DESCRIPTION	"The minor functional aspect of the product causing the fault."
	::= {eStorageDevicesEvents 7}

a6EventSolution OBJECT-TYPE
	SYNTAX		INTEGER {
		vOther                                  	(1),
		vUnknown                                	(2),
		v1stCheckCabling2ndPowerCycleDeviceLas		(3),
		vBackupDataFromFailingDeviceAndReplaceTh	(4),
		vRunDiskAdministrator                  	(5),
		vNoActionRequired                       	(6)
	}
	ACCESS		read-only
	STATUS		mandatory
	DESCRIPTION	"A solution to the problem that caused the event."
	::= {eStorageDevicesEvents 8}

a6InstanceDataPresent OBJECT-TYPE
	SYNTAX		INTEGER {
		vFalse                                  	(0),
		vTrue                                   	(1)
	}
	ACCESS		read-only
	STATUS		mandatory
	DESCRIPTION	"Indicates whether the second event block contains instance-speci
ic data."
	::= {eStorageDevicesEvents 9}

a6EventMessage OBJECT-TYPE
	SYNTAX		DmiDisplaystring
	ACCESS		read-only
	STATUS		mandatory
	DESCRIPTION	"Auxiliary information related to the event."
	::= {eStorageDevicesEvents 10}

SStorageController ::= SEQUENCE {
	a7ControllerIndex                       	DmiInteger,
	a7Identification                        	DmiDisplaystring,
	a7ProtectionManagement                  	DmiInteger,
	a7BusMaster                             	DmiInteger,
	a7SecondsSinceLastPower-up              	DmiInteger
}

tStorageController OBJECT-TYPE
	SYNTAX		SEQUENCE OF SStorageController
	ACCESS		not-accessible
	STATUS		mandatory
	DESCRIPTION	"This group defines the storage controller in this system."
	::= {dmtfGroups 7}

eStorageController OBJECT-TYPE
	SYNTAX		SStorageController
	ACCESS		not-accessible
	STATUS		mandatory
	DESCRIPTION	""
	INDEX		{DmiComponentIndex, a7ControllerIndex}
	::= {tStorageController 1}

a7ControllerIndex OBJECT-TYPE
	SYNTAX		DmiInteger
	ACCESS		read-only
	STATUS		mandatory
	DESCRIPTION	"An index into the Storage Controller table."
	::= {eStorageController 1}

a7Identification OBJECT-TYPE
	SYNTAX		DmiDisplaystring
	ACCESS		read-only
	STATUS		mandatory
	DESCRIPTION	"e.g. Name, brand and hardware revision level of the storage
controller."
	::= {eStorageController 2}

a7ProtectionManagement OBJECT-TYPE
	SYNTAX		INTEGER {
		vOther                                  	(1),
		vUnknown                                	(2),
		vUnprotected                            	(3),
		vProtected                              	(4),
		vProtectedThroughScsi-3ControllerCommand	(5),
		vProtectedThroughScsi-3ControllerComman1	(6)
	}
	ACCESS		read-only
	STATUS		mandatory
	DESCRIPTION	"Indicates whether or not the controller provides redundancy
or protection against device failures."
	::= {eStorageController 3}

a7BusMaster OBJECT-TYPE
	SYNTAX		INTEGER {
		vFalse                                  	(0),
		vTrue                                   	(1),
		vUnknown                                	(2)
	}
	ACCESS		read-only
	STATUS		mandatory
	DESCRIPTION	"If true, then this storage controller is the bus master."
	::= {eStorageController 4}

a7SecondsSinceLastPower-up OBJECT-TYPE
	SYNTAX		DmiInteger
	ACCESS		read-only
	STATUS		mandatory
	DESCRIPTION	"The number of seconds that have passed since this controller
was last powered on."
	::= {eStorageController 5}

SStorageControllerEvents ::= SEQUENCE {
	a8StorageControllerEventType            	DmiInteger,
	a8EventSeverity                         	DmiInteger,
	a8EventIsStateBased                     	DmiInteger,
	a8EventStateKey                         	DmiInteger,
	a8AssociatedGroup                       	DmiDisplaystring,
	a8EventSystem                           	DmiInteger,
	a8EventSubsystem                        	DmiInteger,
	a8EventSolution                         	DmiInteger,
	a8InstanceDataPresent                   	DmiInteger,
	a8EventMessage                          	DmiDisplaystring
}

tStorageControllerEvents OBJECT-TYPE
	SYNTAX		SEQUENCE OF SStorageControllerEvents
	ACCESS		not-accessible
	STATUS		mandatory
	DESCRIPTION	"Storage Controller events."
	::= {dmtfGroups 8}

eStorageControllerEvents OBJECT-TYPE
	SYNTAX		SStorageControllerEvents
	ACCESS		not-accessible
	STATUS		mandatory
	DESCRIPTION	""
	INDEX		{DmiComponentIndex, a8AssociatedGroup}
	::= {tStorageControllerEvents 1}

a8StorageControllerEventType OBJECT-TYPE
	SYNTAX		INTEGER {
		vStorageControllerError                 	(1),
		vSelf-monitoringWarning1                	(2)
	}
	ACCESS		read-only
	STATUS		mandatory
	DESCRIPTION	"The type of Storage Controller event that has occurred."
	::= {eStorageControllerEvents 1}

a8EventSeverity OBJECT-TYPE
	SYNTAX		INTEGER {
		vMonitor                                	(1),
		vInformation                            	(2),
		vOk                                     	(4),
		vNon-critical                           	(8),
		vCritical                               	(16),
		vNon-recoverable                        	(32)
	}
	ACCESS		read-only
	STATUS		mandatory
	DESCRIPTION	"The severity of this event."
	::= {eStorageControllerEvents 2}

a8EventIsStateBased OBJECT-TYPE
	SYNTAX		INTEGER {
		vFalse                                  	(0),
		vTrue                                   	(1)
	}
	ACCESS		read-only
	STATUS		mandatory
	DESCRIPTION	"The value of this attribute determined whether the Event
being reported is a state-based Event or not.  If the value of this attribute
is TRUE then the Event is state-based.  Else the Event is not state-based"
	::= {eStorageControllerEvents 3}

a8EventStateKey OBJECT-TYPE
	SYNTAX		DmiInteger
	ACCESS		read-only
	STATUS		mandatory
	DESCRIPTION	"This attribute holds the key identifying a row of the Event
State group within the Component in which the event generator group is located.
 The Current State attribute within the row contains the current state of
this state-based event.  The current state can be one of the four severities:
OK, Non-Critical, Critical, and Non-Recoverable."
	::= {eStorageControllerEvents 4}

a8AssociatedGroup OBJECT-TYPE
	SYNTAX		DmiDisplaystring
	ACCESS		read-only
	STATUS		mandatory
	DESCRIPTION	"The"
	::= {eStorageControllerEvents 5}

a8EventSystem OBJECT-TYPE
	SYNTAX		INTEGER {
		vOther                                  	(1),
		vUnknown                                	(2),
		vDomainValidation                       	(3),
		vControllerScan                         	(4)
	}
	ACCESS		read-only
	STATUS		mandatory
	DESCRIPTION	"The major functional aspect of the product causing the fault."
	::= {eStorageControllerEvents 6}

a8EventSubsystem OBJECT-TYPE
	SYNTAX		INTEGER {
		vOther                                  	(1),
		vUnknown                                	(2)
	}
	ACCESS		read-only
	STATUS		mandatory
	DESCRIPTION	"The minor functional aspect of the product causing the fault."
	::= {eStorageControllerEvents 7}

a8EventSolution OBJECT-TYPE
	SYNTAX		INTEGER {
		vOther                                  	(1),
		vUnknown                                	(2),
		v1stCheckCabling2ndPowerCycleSystemLas	(3),
		vRunDomainValidationOnThisController    	(4)
	}
	ACCESS		read-only
	STATUS		mandatory
	DESCRIPTION	"A solution to the problem that caused the event."
	::= {eStorageControllerEvents 8}

a8InstanceDataPresent OBJECT-TYPE
	SYNTAX		INTEGER {
		vFalse                                  	(0),
		vTrue                                   	(1)
	}
	ACCESS		read-only
	STATUS		mandatory
	DESCRIPTION	"Indicates whether the second event block contains instance-speci
ic data."
	::= {eStorageControllerEvents 9}

a8EventMessage OBJECT-TYPE
	SYNTAX		DmiDisplaystring
	ACCESS		read-only
	STATUS		mandatory
	DESCRIPTION	"Auxiliary information related to the event."
	::= {eStorageControllerEvents 10}

SBusPort ::= SEQUENCE {
	a9BusPortIndex                          	DmiInteger,
	a9Protocol                              	DmiInteger,
	a9ProtocolDescription                   	DmiDisplaystring,
	a9SignalCharacteristics                 	DmiInteger,
	a9AddressDescriptor                     	DmiDisplaystring,
	a9Isochronous                           	DmiInteger,
	a9MaximumWidth                          	DmiInteger,
	a9MaximumTransferRate                   	DmiInteger,
	a9MaximumNumberOfAttachments            	DmiInteger,
	a9ConnectorType                         	DmiInteger,
	a9ConnectorTypeDescription              	DmiDisplaystring,
	a9ConnectorGender                       	DmiInteger
}

tBusPort OBJECT-TYPE
	SYNTAX		SEQUENCE OF SBusPort
	ACCESS		not-accessible
	STATUS		mandatory
	DESCRIPTION	"This global table has one entry for each of the Bus Ports
in this Component."
	::= {dmtfGroups 9}

eBusPort OBJECT-TYPE
	SYNTAX		SBusPort
	ACCESS		not-accessible
	STATUS		mandatory
	DESCRIPTION	""
	INDEX		{DmiComponentIndex, a9BusPortIndex}
	::= {tBusPort 1}

a9BusPortIndex OBJECT-TYPE
	SYNTAX		DmiInteger
	ACCESS		read-only
	STATUS		mandatory
	DESCRIPTION	"An index into the Bus Port table."
	::= {eBusPort 1}

a9Protocol OBJECT-TYPE
	SYNTAX		INTEGER {
		vOther                                  	(1),
		vUnknown                                	(2),
		vEisa                                   	(3),
		vIsa                                    	(4),
		vPci                                    	(5),
		vAtaatapi                               	(6),
		vFlexibleDiskette                       	(7),
		v1496                                   	(8),
		vScsiParallelInterface                  	(9),
		vScsiFibreChannelProtocol               	(10),
		vScsiSerialBusProtocol                  	(11),
		vScsiSerialBusProtocol-21394            	(12),
		vScsiSerialStorageArchitecture          	(13),
		vVesa                                   	(14),
		vPcmcia                                 	(15),
		vUniversalSerialBus                     	(16),
		vParallelPort                           	(17),
		vEscon                                  	(18),
		vDiagnostic                             	(19),
		vI2c                                    	(20),
		vPower                                  	(21),
		vHippi                                  	(22),
		vMultibus                               	(23),
		vVme                                    	(24),
		vIpi                                    	(25),
		vIeee-488                               	(26),
		vRs232                                  	(27),
		vIeee802310base5                        	(28),
		vIeee802310base2                        	(29),
		vIeee80231base5                         	(30),
		vIeee802310broad36                      	(31),
		vIeee8023100basevg                      	(32),
		vIeee8025Token-ring                     	(33),
		vAnsiX3t95Fddi                          	(34),
		vMca                                    	(35)
	}
	ACCESS		read-only
	STATUS		mandatory
	DESCRIPTION	"The protocol describing the electrical characteristic of
the Bus Port.  If 'Other' is used, then the Protocol Description attribute
shall be used."
	::= {eBusPort 2}

a9ProtocolDescription OBJECT-TYPE
	SYNTAX		DmiDisplaystring
	ACCESS		read-only
	STATUS		mandatory
	DESCRIPTION	"Additional description of the protocol described above. 
If 'Other' was specified above, then this field shall be used.  Otherwise,
the contents of this optional field shall not contradict the Protocol specified
above."
	::= {eBusPort 3}

a9SignalCharacteristics OBJECT-TYPE
	SYNTAX		INTEGER {
		vOther                                  	(1),
		vUnknown                                	(2),
		vSingleEnded                            	(3),
		vDifferential                           	(4),
		vLowVoltageDifferential                 	(5),
		vOptical                                	(6)
	}
	ACCESS		read-only
	STATUS		mandatory
	DESCRIPTION	"The signal characteristics of the Bus Port being described."
	::= {eBusPort 4}

a9AddressDescriptor OBJECT-TYPE
	SYNTAX		DmiDisplaystring
	ACCESS		read-only
	STATUS		mandatory
	DESCRIPTION	"The address descriptor of this bus port.  For example, the
SCSI address of this port."
	::= {eBusPort 5}

a9Isochronous OBJECT-TYPE
	SYNTAX		INTEGER {
		vFalse                                  	(0),
		vTrue                                   	(1)
	}
	ACCESS		read-only
	STATUS		mandatory
	DESCRIPTION	"Indicates whether or not this bus port supports isochronous
transfers."
	::= {eBusPort 6}

a9MaximumWidth OBJECT-TYPE
	SYNTAX		DmiInteger
	ACCESS		read-only
	STATUS		mandatory
	DESCRIPTION	"The maximum width, in bits, of this Bus Port's data path.
 A value of 1 should be used for serial."
	::= {eBusPort 7}

a9MaximumTransferRate OBJECT-TYPE
	SYNTAX		DmiInteger
	ACCESS		read-only
	STATUS		mandatory
	DESCRIPTION	"The theoretical maximum transfer rate, in millions of bytes
per second, that this Bus Port is capable of achieving under ideal conditions.
 A value of zero should be used if the transfer rate is less than 1 million
bytes per second.  A value of 0x80000000 should be used if the transfer rate
is unknown."
	::= {eBusPort 8}

a9MaximumNumberOfAttachments OBJECT-TYPE
	SYNTAX		DmiInteger
	ACCESS		read-only
	STATUS		mandatory
	DESCRIPTION	"The maximum number of directly addressable entities supported
by this bus port's protocol.  A value of zero should be used if the number
of attachments is unknown."
	::= {eBusPort 9}

a9ConnectorType OBJECT-TYPE
	SYNTAX		INTEGER {
		vOther                                  	(1),
		vUnknown                                	(2),
		vNone                                   	(3),
		vScsiAHigh-densityShielded50Pins        	(4),
		vScsiAHigh-densityUnshielded50Pins      	(5),
		vScsiALow-densityShielded50Pins         	(6),
		vScsiALow-densityUnshielded50Pins       	(7),
		vScsiPHigh-densityShielded68Pins        	(8),
		vScsiPHigh-densityUnshielded68Pins      	(9),
		vScsiSca-i80Pins                        	(10),
		vScsiSca-ii80Pins                       	(11),
		vScsiFibreChannelDb9Copper              	(12),
		vScsiFibreChannelFibre                  	(13),
		vScsiFibreChannelSca-ii40Pins           	(14),
		vScsiFibreChannelSca-ii20Pins           	(15),
		vScsiFibreChannelBnc                    	(16),
		vAta3-12Inch40Pins                      	(17),
		vAta2-12Inch44Pins                      	(18),
		vSerial9Pin                             	(19),
		vSerial25Pin                            	(20),
		vRs23225Pin                             	(21),
		vRs422                                  	(22),
		vIeee-488                               	(23),
		vAui                                    	(24),
		vUptCategory3                           	(25),
		vUptCategory4                           	(26),
		vUptCategory5                           	(27),
		vBnc                                    	(28),
		vStpRj11                                	(29),
		vStpRj45                                	(30),
		vStpDb9                                 	(31),
		vFiberMic                               	(32),
		vAppleAui                               	(33),
		vPciSlot                                	(34),
		vIsaSlot                                	(35),
		vEisaSlot                               	(36),
		vVesaSlot                               	(37),
		vPcmciaSlot                             	(38),
		vPcCardSlot                             	(39),
		vFloppyDiskette5-14Inch                 	(40),
		vFloppyDiskette3-12Inch                 	(41),
		vHssdc6Pins                             	(42),
		vGbicSocket                             	(43),
		v13946Pins                              	(44),
		vScsiVhdciShielded68Pins                	(45)
	}
	ACCESS		read-only
	STATUS		mandatory
	DESCRIPTION	"Describes how options (cards, devices, etc.) physically connect
to this bus port.  If 'Other' is used, then the Connector Type Description
attribute shall be used."
	::= {eBusPort 10}

a9ConnectorTypeDescription OBJECT-TYPE
	SYNTAX		DmiDisplaystring
	ACCESS		read-only
	STATUS		mandatory
	DESCRIPTION	"An additional text description of the type of connector describe
above.  If 'Other' was specified above, then this field shall be used.  Otherwis
, the contents of this optional field shall not contradict the connector
specified above."
	::= {eBusPort 11}

a9ConnectorGender OBJECT-TYPE
	SYNTAX		INTEGER {
		vOther                                  	(1),
		vUnknown                                	(2),
		vFemale                                 	(3),
		vMale                                   	(4)
	}
	ACCESS		read-only
	STATUS		mandatory
	DESCRIPTION	"Indicates the gender of the connector described above."
	::= {eBusPort 12}

SFibreChannelBusPortExtensions ::= SEQUENCE {
	a10BusPortIndex                         	DmiInteger,
	a10EndToEndCredit                       	DmiInteger,
	a10BufferToBufferCredit                 	DmiInteger,
	a10LinkType                             	DmiInteger,
	a10FlowControlClassType                 	DmiInteger,
	a10FlowControlAcknowledgmentType        	DmiInteger,
	a10FabricTopology                       	DmiInteger
}

tFibreChannelBusPortExtensions OBJECT-TYPE
	SYNTAX		SEQUENCE OF SFibreChannelBusPortExtensions
	ACCESS		not-accessible
	STATUS		mandatory
	DESCRIPTION	"This group extents the Bus Port group with Fibre Channel
specific attributes."
	::= {dmtfGroups 10}

eFibreChannelBusPortExtensions OBJECT-TYPE
	SYNTAX		SFibreChannelBusPortExtensions
	ACCESS		not-accessible
	STATUS		mandatory
	DESCRIPTION	""
	INDEX		{DmiComponentIndex, a10BusPortIndex}
	::= {tFibreChannelBusPortExtensions 1}

a10BusPortIndex OBJECT-TYPE
	SYNTAX		DmiInteger
	ACCESS		read-only
	STATUS		mandatory
	DESCRIPTION	"The index into the Bus Port Table that this Fibre Channel
group is extending."
	::= {eFibreChannelBusPortExtensions 1}

a10EndToEndCredit OBJECT-TYPE
	SYNTAX		DmiInteger
	ACCESS		read-only
	STATUS		mandatory
	DESCRIPTION	"The number of allowable outstanding acknowledgments for a
sequence."
	::= {eFibreChannelBusPortExtensions 2}

a10BufferToBufferCredit OBJECT-TYPE
	SYNTAX		DmiInteger
	ACCESS		read-only
	STATUS		mandatory
	DESCRIPTION	"The number of frames which can be handled by the node before
a wait for the buffer ready is required, and prior to subsequent frame transmiss
ons."
	::= {eFibreChannelBusPortExtensions 3}

a10LinkType OBJECT-TYPE
	SYNTAX		INTEGER {
		vOther                                  	(1),
		vUnknown                                	(2),
		vCopper                                 	(3),
		vFibre-SingleMode1300Nanometers         	(4),
		vFibre-SingleMode1500Nanometers         	(5),
		vFibre-Multimode50-Laser                	(6),
		vFibre-Multimode50-Led                  	(7),
		vFibre-Multimode625-Laser               	(8),
		vFibre-Multimode625-Led                 	(9),
		vFibreLongWave                          	(10),
		vFibreShortWave                         	(11)
	}
	ACCESS		read-only
	STATUS		mandatory
	DESCRIPTION	"Reports whether copper or fibre media is used."
	::= {eFibreChannelBusPortExtensions 4}

a10FlowControlClassType OBJECT-TYPE
	SYNTAX		INTEGER {
		vOther                                  	(1),
		vUnknown                                	(2),
		vClass-1                                	(3),
		vClass-2                                	(4),
		vClass-3                                	(5),
		vClass-1class-2                         	(6)
	}
	ACCESS		read-only
	STATUS		mandatory
	DESCRIPTION	"Identifies the Flow Control Class Type."
	::= {eFibreChannelBusPortExtensions 5}

a10FlowControlAcknowledgmentType OBJECT-TYPE
	SYNTAX		INTEGER {
		vOther                                  	(1),
		vUnknown                                	(2),
		vAck-0                                  	(3),
		vAck-1                                  	(4),
		vAck-n                                  	(5)
	}
	ACCESS		read-only
	STATUS		mandatory
	DESCRIPTION	"Identifies the Flow Control Acknowledgment Type."
	::= {eFibreChannelBusPortExtensions 6}

a10FabricTopology OBJECT-TYPE
	SYNTAX		INTEGER {
		vFalse                                  	(0),
		vTrue                                   	(1),
		vUnknown                                	(2)
	}
	ACCESS		read-only
	STATUS		mandatory
	DESCRIPTION	"If true, a fabric topology exists within the fibre channel
bus port."
	::= {eFibreChannelBusPortExtensions 7}

SMassStorageAssociation ::= SEQUENCE {
	a11AssociationIndex                     	DmiInteger,
	a11Type                                 	DmiDisplaystring,
	a11Reference1                           	DmiDisplaystring,
	a11Reference2                           	DmiDisplaystring
}

tMassStorageAssociation OBJECT-TYPE
	SYNTAX		SEQUENCE OF SMassStorageAssociation
	ACCESS		not-accessible
	STATUS		mandatory
	DESCRIPTION	"Mass storage associations define the relationships between
the various components of the Storage Subsystem."
	::= {dmtfGroups 11}

eMassStorageAssociation OBJECT-TYPE
	SYNTAX		SMassStorageAssociation
	ACCESS		not-accessible
	STATUS		mandatory
	DESCRIPTION	""
	INDEX		{DmiComponentIndex, a11AssociationIndex}
	::= {tMassStorageAssociation 1}

a11AssociationIndex OBJECT-TYPE
	SYNTAX		DmiInteger
	ACCESS		read-only
	STATUS		mandatory
	DESCRIPTION	"An index into the Association table."
	::= {eMassStorageAssociation 1}

a11Type OBJECT-TYPE
	SYNTAX		DmiDisplaystring
	ACCESS		read-only
	STATUS		mandatory
	DESCRIPTION	"This field specifies the type of the association."
	::= {eMassStorageAssociation 2}

a11Reference1 OBJECT-TYPE
	SYNTAX		DmiDisplaystring
	ACCESS		read-only
	STATUS		mandatory
	DESCRIPTION	"A reference to an object."
	::= {eMassStorageAssociation 3}

a11Reference2 OBJECT-TYPE
	SYNTAX		DmiDisplaystring
	ACCESS		read-only
	STATUS		mandatory
	DESCRIPTION	"A reference to an object."
	::= {eMassStorageAssociation 4}

SMassStorageAssociationEvents ::= SEQUENCE {
	a12MassStorageAssociationEventType      	DmiInteger,
	a12EventSeverity                        	DmiInteger,
	a12EventIsStateBased                    	DmiInteger,
	a12EventStateKey                        	DmiInteger,
	a12AssociatedGroup                      	DmiDisplaystring,
	a12EventSystem                          	DmiInteger,
	a12EventSubsystem                       	DmiInteger,
	a12EventSolution                        	DmiInteger,
	a12InstanceDataPresent                  	DmiInteger,
	a12EventMessage                         	DmiDisplaystring
}

tMassStorageAssociationEvents OBJECT-TYPE
	SYNTAX		SEQUENCE OF SMassStorageAssociationEvents
	ACCESS		not-accessible
	STATUS		mandatory
	DESCRIPTION	"Mass Storage Association events."
	::= {dmtfGroups 12}

eMassStorageAssociationEvents OBJECT-TYPE
	SYNTAX		SMassStorageAssociationEvents
	ACCESS		not-accessible
	STATUS		mandatory
	DESCRIPTION	""
	INDEX		{DmiComponentIndex, a12AssociatedGroup}
	::= {tMassStorageAssociationEvents 1}

a12MassStorageAssociationEventType OBJECT-TYPE
	SYNTAX		INTEGER {
		vNewObjectDetected                      	(1),
		vExistingObjectReplaced                 	(2),
		vExistingObjectGone                     	(3)
	}
	ACCESS		read-only
	STATUS		mandatory
	DESCRIPTION	"The type of Mass storage association where a change has occurred
"
	::= {eMassStorageAssociationEvents 1}

a12EventSeverity OBJECT-TYPE
	SYNTAX		INTEGER {
		vMonitor                                	(1),
		vInformation                            	(2),
		vOk                                     	(4),
		vNon-critical                           	(8),
		vCritical                               	(16),
		vNon-recoverable                        	(32)
	}
	ACCESS		read-only
	STATUS		mandatory
	DESCRIPTION	"The severity of this event."
	::= {eMassStorageAssociationEvents 2}

a12EventIsStateBased OBJECT-TYPE
	SYNTAX		INTEGER {
		vFalse                                  	(0),
		vTrue                                   	(1)
	}
	ACCESS		read-only
	STATUS		mandatory
	DESCRIPTION	"The value of this attribute determined whether the Event
being reported is a state-based Event or not.  If the value of this attribute
is TRUE then the Event is state-based.  Else the Event is not state-based"
	::= {eMassStorageAssociationEvents 3}

a12EventStateKey OBJECT-TYPE
	SYNTAX		DmiInteger
	ACCESS		read-only
	STATUS		mandatory
	DESCRIPTION	"This attribute holds the key identifying a row of the Event
State group within the Component in which the event generator group is located.
 The Current State attribute within the row contains the current state of
this state-based event.  The current state can be one of the four severities:
OK, Non-Critical, Critical, and Non-Recoverable."
	::= {eMassStorageAssociationEvents 4}

a12AssociatedGroup OBJECT-TYPE
	SYNTAX		DmiDisplaystring
	ACCESS		read-only
	STATUS		mandatory
	DESCRIPTION	"The class name of the group that is associated with the events
defined in this EventGeneration group."
	::= {eMassStorageAssociationEvents 5}

a12EventSystem OBJECT-TYPE
	SYNTAX		INTEGER {
		vOther                                  	(0),
		vUnknown                                	(1),
		vStorageController                      	(2),
		vStorageDevice                          	(3),
		vBusPort                                	(4),
		vVolumeSet                              	(5),
		vProtectedSpaceExtent                   	(6),
		vAggregateProtectedSpaceExtent          	(7),
		vPhysicalExtent                         	(8),
		vAggregatePhysicalExtent                	(9),
		vRedundancyGroup                        	(10),
		vCache                                  	(11),
		vSoftwareSubcomponent                   	(12)
	}
	ACCESS		read-only
	STATUS		mandatory
	DESCRIPTION	"The mass storage association object type which is causing
a change."
	::= {eMassStorageAssociationEvents 6}

a12EventSubsystem OBJECT-TYPE
	SYNTAX		INTEGER {
		vOther                                  	(1),
		vUnknown                                	(2)
	}
	ACCESS		read-only
	STATUS		mandatory
	DESCRIPTION	"The minor functional aspect of the product causing the fault."
	::= {eMassStorageAssociationEvents 7}

a12EventSolution OBJECT-TYPE
	SYNTAX		INTEGER {
		vOther                                  	(1),
		vUnknown                                	(2),
		vNoActionIsRequired                     	(3)
	}
	ACCESS		read-only
	STATUS		mandatory
	DESCRIPTION	"A solution to the problem that caused the event."
	::= {eMassStorageAssociationEvents 8}

a12InstanceDataPresent OBJECT-TYPE
	SYNTAX		INTEGER {
		vFalse                                  	(0),
		vTrue                                   	(1)
	}
	ACCESS		read-only
	STATUS		mandatory
	DESCRIPTION	"Indicates whether the second event block contains instance-speci
ic data."
	::= {eMassStorageAssociationEvents 9}

a12EventMessage OBJECT-TYPE
	SYNTAX		DmiDisplaystring
	ACCESS		read-only
	STATUS		mandatory
	DESCRIPTION	"Auxiliary information related to the event."
	::= {eMassStorageAssociationEvents 10}

SBusPortAssociation ::= SEQUENCE {
	a13BusPortAssociationIndex              	DmiInteger,
	a13NegotiatedSpeed                      	DmiInteger,
	a13NegotiatedWidth                      	DmiInteger
}

tBusPortAssociation OBJECT-TYPE
	SYNTAX		SEQUENCE OF SBusPortAssociation
	ACCESS		not-accessible
	STATUS		mandatory
	DESCRIPTION	"Bus Port Association "
	::= {dmtfGroups 13}

eBusPortAssociation OBJECT-TYPE
	SYNTAX		SBusPortAssociation
	ACCESS		not-accessible
	STATUS		mandatory
	DESCRIPTION	""
	INDEX		{DmiComponentIndex, a13BusPortAssociationIndex}
	::= {tBusPortAssociation 1}

a13BusPortAssociationIndex OBJECT-TYPE
	SYNTAX		DmiInteger
	ACCESS		read-only
	STATUS		mandatory
	DESCRIPTION	"An index into the Bus Port Association table.  This index
is the same as the index in the Association group that defines the bus port
association."
	::= {eBusPortAssociation 1}

a13NegotiatedSpeed OBJECT-TYPE
	SYNTAX		DmiInteger
	ACCESS		read-only
	STATUS		mandatory
	DESCRIPTION	"The maximum burst transfer rate, in millions of bytes, which
was negotiated between the two associated bus ports."
	::= {eBusPortAssociation 2}

a13NegotiatedWidth OBJECT-TYPE
	SYNTAX		DmiInteger
	ACCESS		read-only
	STATUS		mandatory
	DESCRIPTION	"The width, in bits, of the bus ports data path which was
negotiated between the two associated bus ports."
	::= {eBusPortAssociation 3}

SOperationalState ::= SEQUENCE {
	a14OperationalStateInstanceIndex        	DmiInteger,
	a14DeviceGroupIndex                     	DmiInteger,
	a14OperationalStatus                    	DmiInteger,
	a14UsageState                           	DmiInteger,
	a14AvailabilityStatus                   	DmiInteger,
	a14AdministrativeState                  	DmiInteger,
	a14FatalErrorCount                      	DmiCounter,
	a14MajorErrorCount                      	DmiCounter,
	a14WarningErrorCount                    	DmiCounter,
	a14CurrentErrorStatus                   	DmiInteger,
	a14DevicePredictedFailureStatus         	DmiInteger
}

tOperationalState OBJECT-TYPE
	SYNTAX		SEQUENCE OF SOperationalState
	ACCESS		not-accessible
	STATUS		mandatory
	DESCRIPTION	"This group provides the operational state, usage, and availabili
y status, and administrative state indicators for specific Device Group instance
."
	::= {dmtfGroups 14}

eOperationalState OBJECT-TYPE
	SYNTAX		SOperationalState
	ACCESS		not-accessible
	STATUS		mandatory
	DESCRIPTION	""
	INDEX		{DmiComponentIndex, a14OperationalStateInstanceIndex}
	::= {tOperationalState 1}

a14OperationalStateInstanceIndex OBJECT-TYPE
	SYNTAX		DmiInteger
	ACCESS		read-only
	STATUS		mandatory
	DESCRIPTION	"The Index into the Operational State table."
	::= {eOperationalState 1}

a14DeviceGroupIndex OBJECT-TYPE
	SYNTAX		DmiInteger
	ACCESS		read-only
	STATUS		mandatory
	DESCRIPTION	"The group ID of the group referencing this instance."
	::= {eOperationalState 2}

a14OperationalStatus OBJECT-TYPE
	SYNTAX		INTEGER {
		vOther                                  	(1),
		vUnknown                                	(2),
		vEnabled                                	(3),
		vDisabled                               	(4),
		vNotApplicable                          	(5)
	}
	ACCESS		read-only
	STATUS		mandatory
	DESCRIPTION	"The operational status of the Device Group instance."
	::= {eOperationalState 3}

a14UsageState OBJECT-TYPE
	SYNTAX		INTEGER {
		vOther                                  	(1),
		vUnknown                                	(2),
		vIdle                                   	(3),
		vActive                                 	(4),
		vBusy                                   	(5),
		vNotApplicable                          	(6)
	}
	ACCESS		read-only
	STATUS		mandatory
	DESCRIPTION	"The usage state of the Device Group instance."
	::= {eOperationalState 4}

a14AvailabilityStatus OBJECT-TYPE
	SYNTAX		INTEGER {
		vOther                                  	(1),
		vUnknown                                	(2),
		vRunning                                	(3),
		vWarning                                	(4),
		vInTest                                 	(5),
		vNotApplicable                          	(6),
		vPowerOff                               	(7),
		vOffLine                                	(8),
		vOffDuty                                	(9),
		vDegraded                               	(10),
		vNotInstalled                           	(11),
		vInstallError                           	(12),
		vPowerSave                              	(13)
	}
	ACCESS		read-only
	STATUS		mandatory
	DESCRIPTION	"The availability status of the Device Group instance."
	::= {eOperationalState 5}

a14AdministrativeState OBJECT-TYPE
	SYNTAX		INTEGER {
		vOther                                  	(1),
		vUnknown                                	(2),
		vLocked                                 	(3),
		vUnlocked                               	(4),
		vNotApplicable                          	(5),
		vShuttingDown                           	(6)
	}
	ACCESS		read-only
	STATUS		mandatory
	DESCRIPTION	"The administrative state of the Device Group instance."
	::= {eOperationalState 6}

a14FatalErrorCount OBJECT-TYPE
	SYNTAX		DmiCounter
	ACCESS		read-only
	STATUS		mandatory
	DESCRIPTION	"The accumulated Fatal or Non-recoverable error count for
this Device Group instance."
	::= {eOperationalState 7}

a14MajorErrorCount OBJECT-TYPE
	SYNTAX		DmiCounter
	ACCESS		read-only
	STATUS		mandatory
	DESCRIPTION	"The accumulated Major or Critical error count for this Device
Group instance."
	::= {eOperationalState 8}

a14WarningErrorCount OBJECT-TYPE
	SYNTAX		DmiCounter
	ACCESS		read-only
	STATUS		mandatory
	DESCRIPTION	"The accumulated Warning or Non-Critical error count for this
Device Group instance."
	::= {eOperationalState 9}

a14CurrentErrorStatus OBJECT-TYPE
	SYNTAX		INTEGER {
		vOther                                  	(1),
		vUnknown                                	(2),
		vOk                                     	(3),
		vNon-critical1                          	(4),
		vCritical                               	(5),
		vNon-recoverable1                       	(6)
	}
	ACCESS		read-only
	STATUS		mandatory
	DESCRIPTION	"This attribute presents the current error status for this
Device Group instance. The most critical error status in effect should be
presented. I.e. if a part of the Device Group instance is 'Critical', while
other status is 'Non-critical' then the status 'Critical' should be reported."
	::= {eOperationalState 10}

a14DevicePredictedFailureStatus OBJECT-TYPE
	SYNTAX		INTEGER {
		vOther                                  	(1),
		vUnknown                                	(2),
		vNotSupportedByThisDevice               	(3),
		vNoFailurePredictedByTheDevice          	(4),
		vDeviceFailurePredictedByTheDevice      	(5),
		vMediaFailurePredictedByTheDevice       	(6)
	}
	ACCESS		read-only
	STATUS		mandatory
	DESCRIPTION	"Enumeration describing the current Device Predicted Failure
Status (e.g.: the S.M.A.R.T. status of the device)."
	::= {eOperationalState 11}

SSymbiosEventPolling ::= SEQUENCE {
	a15SymbiosFlag                          	DmiInteger,
	a15SmartEventPolling                    	DmiInteger,
	a15ScanEventPolling                     	DmiInteger,
	a15Saf-teEventPolling                   	DmiInteger,
	a15EventPollingPeriod                   	DmiInteger,
	a15ControlLevelForDomainValidationErrorR	DmiInteger,
	a15ControlLevelForDomainValidationSchedu	DmiInteger
}

tSymbiosEventPolling OBJECT-TYPE
	SYNTAX		SEQUENCE OF SSymbiosEventPolling
	ACCESS		not-accessible
	STATUS		mandatory
	DESCRIPTION	"This group is the Symbios Vendor unique group for dealing
with Event Polling."
	::= {dmtfGroups 15}

eSymbiosEventPolling OBJECT-TYPE
	SYNTAX		SSymbiosEventPolling
	ACCESS		not-accessible
	STATUS		mandatory
	DESCRIPTION	""
	INDEX		{DmiComponentIndex}
	::= {tSymbiosEventPolling 1}

a15SymbiosFlag OBJECT-TYPE
	SYNTAX		DmiInteger
	ACCESS		read-write
	STATUS		mandatory
	DESCRIPTION	"A Symbios Vendor Unique Flag."
	::= {eSymbiosEventPolling 1}

a15SmartEventPolling OBJECT-TYPE
	SYNTAX		INTEGER {
		vDisabled                               	(0),
		vEnabled                                	(1),
		vUnknown                                	(2),
		vNotApplicable                          	(3)
	}
	ACCESS		read-write
	STATUS		mandatory
	DESCRIPTION	"A flag indicating whether or not the CI will poll for SMART
events."
	::= {eSymbiosEventPolling 2}

a15ScanEventPolling OBJECT-TYPE
	SYNTAX		INTEGER {
		vDisabled                               	(0),
		vEnabled                                	(1),
		vUnknown                                	(2),
		vNotApplicable                          	(3)
	}
	ACCESS		read-write
	STATUS		mandatory
	DESCRIPTION	"A flag indicating whether or not the CI will scan for a change
in Devices and Controllers."
	::= {eSymbiosEventPolling 3}

a15Saf-teEventPolling OBJECT-TYPE
	SYNTAX		INTEGER {
		vDisabled                               	(0),
		vEnabled                                	(1),
		vUnknown                                	(2),
		vNotApplicable                          	(3)
	}
	ACCESS		read-write
	STATUS		mandatory
	DESCRIPTION	"A flag indicating whether or not the CI will poll for SAF-TE
events."
	::= {eSymbiosEventPolling 4}

a15EventPollingPeriod OBJECT-TYPE
	SYNTAX		DmiInteger
	ACCESS		read-write
	STATUS		mandatory
	DESCRIPTION	"The event poll period in number of minutes."
	::= {eSymbiosEventPolling 5}

a15ControlLevelForDomainValidationErrorR OBJECT-TYPE
	SYNTAX		INTEGER {
		vNotSupported                           	(0),
		vDisabled                               	(1),
		vReportIfDomainValidationRequired       	(2),
		vWhenDomainValidationRequiredAutoRun    	(3)
	}
	ACCESS		read-write
	STATUS		mandatory
	DESCRIPTION	"This indicates the control level for performing domain validatio
 based on Error Rate."
	::= {eSymbiosEventPolling 6}

a15ControlLevelForDomainValidationSchedu OBJECT-TYPE
	SYNTAX		DmiInteger
	ACCESS		read-write
	STATUS		mandatory
	DESCRIPTION	"This indicates the number of hours between scheduled runs
of domain validation.  Zero indicates that no scheduled run should be performed."
	::= {eSymbiosEventPolling 7}

SSymbiosDevice ::= SEQUENCE {
	a16SymbiosDeviceIndex                   	DmiInteger,
	a16SmartReportingCapability             	DmiInteger,
	a16ControlLevelForDomainValidationMargin	DmiInteger,
	a16ControlLevelForDomainValidationSkewin	DmiInteger,
	a16MaximumAllowedNegotiatedSpeed        	DmiInteger,
	a16MaximumAllowedNegotiatedWidth        	DmiInteger,
	a16DomainValidationNegotiatedSpeed      	DmiInteger,
	a16DomainValidationNegotiatedWidth      	DmiInteger
}

tSymbiosDevice OBJECT-TYPE
	SYNTAX		SEQUENCE OF SSymbiosDevice
	ACCESS		not-accessible
	STATUS		mandatory
	DESCRIPTION	"This group is a Symbios Vendor unique group for dealing with
Devices."
	::= {dmtfGroups 16}

eSymbiosDevice OBJECT-TYPE
	SYNTAX		SSymbiosDevice
	ACCESS		not-accessible
	STATUS		mandatory
	DESCRIPTION	""
	INDEX		{DmiComponentIndex, a16SymbiosDeviceIndex}
	::= {tSymbiosDevice 1}

a16SymbiosDeviceIndex OBJECT-TYPE
	SYNTAX		DmiInteger
	ACCESS		read-only
	STATUS		mandatory
	DESCRIPTION	"An index into the Symbios Vendor Unique Device info table.
This index corresponds to the Storage Device index."
	::= {eSymbiosDevice 1}

a16SmartReportingCapability OBJECT-TYPE
	SYNTAX		INTEGER {
		vDisabled                               	(0),
		vEnabled                                	(1),
		vUnknown                                	(2),
		vNotSupported                           	(3)
	}
	ACCESS		read-write
	STATUS		mandatory
	DESCRIPTION	"A flag indicating the state of a Devices's SMART reporting
capability."
	::= {eSymbiosDevice 2}

a16ControlLevelForDomainValidationMargin OBJECT-TYPE
	SYNTAX		INTEGER {
		vNotSupported                           	(0),
		vAll                                    	(1),
		vNominal                                	(2)
	}
	ACCESS		read-write
	STATUS		mandatory
	DESCRIPTION	"This indicates the control level for margining while performing
domain validation for this device."
	::= {eSymbiosDevice 3}

a16ControlLevelForDomainValidationSkewin OBJECT-TYPE
	SYNTAX		INTEGER {
		vNotSupported                           	(0),
		vAll                                    	(1),
		vNominal                                	(2)
	}
	ACCESS		read-write
	STATUS		mandatory
	DESCRIPTION	"This indicates the control level for skewing while performing
domain validation for this device."
	::= {eSymbiosDevice 4}

a16MaximumAllowedNegotiatedSpeed OBJECT-TYPE
	SYNTAX		INTEGER {
		vNotApplicable                          	(0),
		vMaximumRate                            	(1),
		v160MillionBytesseconds                 	(2),
		v80MillionBytesseconds                  	(3),
		v40MillionBytesseconds                  	(4),
		v20MillionBytesseconds                  	(5),
		v10MillionBytesseconds                  	(6),
		v5MillionBytesseconds                   	(7),
		vAsynchronous                           	(8)
	}
	ACCESS		read-write
	STATUS		mandatory
	DESCRIPTION	"This indicates the maximum allowed negotiated speed while
performing domain validation for this device."
	::= {eSymbiosDevice 5}

a16MaximumAllowedNegotiatedWidth OBJECT-TYPE
	SYNTAX		INTEGER {
		vNotApplicable                          	(0),
		vMaximumWidth                           	(1),
		vWide16Bits                             	(2),
		vNarrow8Bits                            	(3)
	}
	ACCESS		read-write
	STATUS		mandatory
	DESCRIPTION	"This indicates the maximum allowed negotiated width while
performing domain validation for this device."
	::= {eSymbiosDevice 6}

a16DomainValidationNegotiatedSpeed OBJECT-TYPE
	SYNTAX		DmiInteger
	ACCESS		read-only
	STATUS		mandatory
	DESCRIPTION	"This indicates the maximum negotiated speed that was achieved
while performing domain validation for this device.  The speed is indicated
in millions of bytes per second. Typically, a value of zero would represent
asynchronous transfers."
	::= {eSymbiosDevice 7}

a16DomainValidationNegotiatedWidth OBJECT-TYPE
	SYNTAX		DmiInteger
	ACCESS		read-only
	STATUS		mandatory
	DESCRIPTION	"This indicates the maximum negotiated width that was achieved
while performing domain validation for this device.  The width is indicated
in bits.  "
	::= {eSymbiosDevice 8}

SSaf-teProcessor ::= SEQUENCE {
	a17Saf-teProcessorIndex                 	DmiInteger,
	a17StorageControllerIndex               	DmiInteger,
	a17ScsiId                               	DmiInteger64X,
	a17ScsiLun                              	DmiInteger64X,
	a17VendorId                             	DmiDisplaystring,
	a17ProductId                            	DmiDisplaystring,
	a17FirmwareRevisionLevel                	DmiDisplaystring,
	a17EnclosureUniqueIdentifier            	DmiDisplaystring,
	a17Saf-teSpecificationRevisionLevel     	DmiDisplaystring,
	a17HasLocks                             	DmiInteger,
	a17HasSpeakers                          	DmiInteger,
	a17DoorLocked                           	DmiInteger,
	a17SpeakerStatus                        	DmiInteger,
	a17PowerOnMinutes                       	DmiInteger,
	a17PowerOnCycles                        	DmiInteger,
	a17TemperatureOutOfRange                	DmiInteger
}

tSaf-teProcessor OBJECT-TYPE
	SYNTAX		SEQUENCE OF SSaf-teProcessor
	ACCESS		not-accessible
	STATUS		mandatory
	DESCRIPTION	"This group defines a SAF-TE Processor"
	::= {dmtfGroups 17}

eSaf-teProcessor OBJECT-TYPE
	SYNTAX		SSaf-teProcessor
	ACCESS		not-accessible
	STATUS		mandatory
	DESCRIPTION	""
	INDEX		{DmiComponentIndex, a17Saf-teProcessorIndex}
	::= {tSaf-teProcessor 1}

a17Saf-teProcessorIndex OBJECT-TYPE
	SYNTAX		DmiInteger
	ACCESS		read-only
	STATUS		mandatory
	DESCRIPTION	"An index into the SAF-TE processor table."
	::= {eSaf-teProcessor 1}

a17StorageControllerIndex OBJECT-TYPE
	SYNTAX		DmiInteger
	ACCESS		read-only
	STATUS		mandatory
	DESCRIPTION	"An index into the Storage Controller table."
	::= {eSaf-teProcessor 2}

a17ScsiId OBJECT-TYPE
	SYNTAX		DmiInteger64X
	ACCESS		read-only
	STATUS		mandatory
	DESCRIPTION	"The SCSI target/initiator identifier."
	::= {eSaf-teProcessor 3}

a17ScsiLun OBJECT-TYPE
	SYNTAX		DmiInteger64X
	ACCESS		read-only
	STATUS		mandatory
	DESCRIPTION	"The SCSI logical unit number."
	::= {eSaf-teProcessor 4}

a17VendorId OBJECT-TYPE
	SYNTAX		DmiDisplaystring
	ACCESS		read-only
	STATUS		mandatory
	DESCRIPTION	"The vendor ID that is returned in the Inquiry command"
	::= {eSaf-teProcessor 5}

a17ProductId OBJECT-TYPE
	SYNTAX		DmiDisplaystring
	ACCESS		read-only
	STATUS		mandatory
	DESCRIPTION	"The product ID that is returned in the Inquiry command"
	::= {eSaf-teProcessor 6}

a17FirmwareRevisionLevel OBJECT-TYPE
	SYNTAX		DmiDisplaystring
	ACCESS		read-only
	STATUS		mandatory
	DESCRIPTION	"Identifies the current firmware revision of the SAF-TE processor
"
	::= {eSaf-teProcessor 7}

a17EnclosureUniqueIdentifier OBJECT-TYPE
	SYNTAX		DmiDisplaystring
	ACCESS		read-only
	STATUS		mandatory
	DESCRIPTION	"This field specifies the unique unit number for the SAF-TE
processor."
	::= {eSaf-teProcessor 8}

a17Saf-teSpecificationRevisionLevel OBJECT-TYPE
	SYNTAX		DmiDisplaystring
	ACCESS		read-only
	STATUS		mandatory
	DESCRIPTION	"Identifies the revision of the SAF-TE interface specification
to which this device claims compliance."
	::= {eSaf-teProcessor 9}

a17HasLocks OBJECT-TYPE
	SYNTAX		INTEGER {
		vFalse                                  	(0),
		vTrue                                   	(1),
		vUnknown                                	(2)
	}
	ACCESS		read-only
	STATUS		mandatory
	DESCRIPTION	"If true, then this SAF-TE processor is contained within an
enclosure that has locks."
	::= {eSaf-teProcessor 10}

a17HasSpeakers OBJECT-TYPE
	SYNTAX		INTEGER {
		vFalse                                  	(0),
		vTrue                                   	(1),
		vUnknown                                	(2)
	}
	ACCESS		read-only
	STATUS		mandatory
	DESCRIPTION	"If true, then this SAF-TE processor is contained within an
enclosure that has speakers."
	::= {eSaf-teProcessor 11}

a17DoorLocked OBJECT-TYPE
	SYNTAX		INTEGER {
		vFalse                                  	(0),
		vTrue                                   	(1),
		vUnknown                                	(2)
	}
	ACCESS		read-only
	STATUS		mandatory
	DESCRIPTION	"If true, then this SAF-TE processor enclosure is locked."
	::= {eSaf-teProcessor 12}

a17SpeakerStatus OBJECT-TYPE
	SYNTAX		INTEGER {
		vFalse                                  	(0),
		vTrue                                   	(1),
		vUnknown                                	(2)
	}
	ACCESS		read-only
	STATUS		mandatory
	DESCRIPTION	"If true, then this SAF-TE processor enclsoure speakers are
turned on.  If false, then the speakers are off or not installed."
	::= {eSaf-teProcessor 13}

a17PowerOnMinutes OBJECT-TYPE
	SYNTAX		DmiInteger
	ACCESS		read-only
	STATUS		mandatory
	DESCRIPTION	"Total number of power on minutes."
	::= {eSaf-teProcessor 14}

a17PowerOnCycles OBJECT-TYPE
	SYNTAX		DmiInteger
	ACCESS		read-only
	STATUS		mandatory
	DESCRIPTION	"Total number of times the SAF-TE enclosure has been power
on."
	::= {eSaf-teProcessor 15}

a17TemperatureOutOfRange OBJECT-TYPE
	SYNTAX		INTEGER {
		vFalse                                  	(0),
		vTrue                                   	(1),
		vUnknown                                	(2)
	}
	ACCESS		read-only
	STATUS		mandatory
	DESCRIPTION	"If true, then the temperature is out of range."
	::= {eSaf-teProcessor 16}

SSaf-teControlledFan ::= SEQUENCE {
	a18Saf-teControlledFanIndex             	DmiInteger,
	a18Saf-teProcessorIndex                 	DmiInteger,
	a18Status                               	DmiInteger
}

tSaf-teControlledFan OBJECT-TYPE
	SYNTAX		SEQUENCE OF SSaf-teControlledFan
	ACCESS		not-accessible
	STATUS		mandatory
	DESCRIPTION	"This group defines status of a fan controlled by a SAF-TE
Processor"
	::= {dmtfGroups 18}

eSaf-teControlledFan OBJECT-TYPE
	SYNTAX		SSaf-teControlledFan
	ACCESS		not-accessible
	STATUS		mandatory
	DESCRIPTION	""
	INDEX		{DmiComponentIndex, a18Saf-teControlledFanIndex}
	::= {tSaf-teControlledFan 1}

a18Saf-teControlledFanIndex OBJECT-TYPE
	SYNTAX		DmiInteger
	ACCESS		read-only
	STATUS		mandatory
	DESCRIPTION	"An index into the SAF-TE controlled fan table."
	::= {eSaf-teControlledFan 1}

a18Saf-teProcessorIndex OBJECT-TYPE
	SYNTAX		DmiInteger
	ACCESS		read-only
	STATUS		mandatory
	DESCRIPTION	"The Index to the SAF-TE proccessor that is controlling this
fan."
	::= {eSaf-teControlledFan 2}

a18Status OBJECT-TYPE
	SYNTAX		INTEGER {
		vFanIsOperational                       	(0),
		vFanIsMalfunctioning                    	(1),
		vFanIsNotInstalled                      	(2),
		vUnknownStatus                          	(128)
	}
	ACCESS		read-only
	STATUS		mandatory
	DESCRIPTION	"The fan status."
	::= {eSaf-teControlledFan 3}

SSaf-teControlledPowerSupply ::= SEQUENCE {
	a19Saf-teControlledPowerSupplyIndex     	DmiInteger,
	a19Saf-teProcessorIndex                 	DmiInteger,
	a19Status                               	DmiInteger
}

tSaf-teControlledPowerSupply OBJECT-TYPE
	SYNTAX		SEQUENCE OF SSaf-teControlledPowerSupply
	ACCESS		not-accessible
	STATUS		mandatory
	DESCRIPTION	"This group defines status of a Power Supply controlled by
a SAF-TE Processor"
	::= {dmtfGroups 19}

eSaf-teControlledPowerSupply OBJECT-TYPE
	SYNTAX		SSaf-teControlledPowerSupply
	ACCESS		not-accessible
	STATUS		mandatory
	DESCRIPTION	""
	INDEX		{DmiComponentIndex, a19Saf-teControlledPowerSupplyIndex}
	::= {tSaf-teControlledPowerSupply 1}

a19Saf-teControlledPowerSupplyIndex OBJECT-TYPE
	SYNTAX		DmiInteger
	ACCESS		read-only
	STATUS		mandatory
	DESCRIPTION	"An index into the SAF-TE controlled Power Supply table."
	::= {eSaf-teControlledPowerSupply 1}

a19Saf-teProcessorIndex OBJECT-TYPE
	SYNTAX		DmiInteger
	ACCESS		read-only
	STATUS		mandatory
	DESCRIPTION	"The Index to the SAF-TE proccessor that is controlling this
Power Supply."
	::= {eSaf-teControlledPowerSupply 2}

a19Status OBJECT-TYPE
	SYNTAX		INTEGER {
		vPowerSupplyIsOperationalAndOn          	(0),
		vPowerSupplyIsOperationalAndOff         	(1),
		vPowerSupplyIsMalfunctioningAndCommanded	(16),
		vPowerSupplyIsMalfunctioningAndCommande1	(17),
		vPowerSupplyIsNotPresent                	(32),
		vPowerSupplyIsPresent                   	(33),
		vUnknownStatus                          	(128)
	}
	ACCESS		read-only
	STATUS		mandatory
	DESCRIPTION	"The Power Supply status."
	::= {eSaf-teControlledPowerSupply 3}

SSaf-teControlledSlot ::= SEQUENCE {
	a20Saf-teControlledSlotIndex            	DmiInteger,
	a20Saf-teProcessorIndex                 	DmiInteger,
	a20ScsiId                               	DmiInteger64X,
	a20NumberOfInsertions                   	DmiInteger,
	a20State                                	DmiInteger,
	a20Rebuild                              	DmiInteger,
	a20DeviceFault                          	DmiInteger,
	a20InFailedArray                        	DmiInteger,
	a20InCriticalArray                      	DmiInteger,
	a20ParityCheck                          	DmiInteger,
	a20PredictedFault                       	DmiInteger
}

tSaf-teControlledSlot OBJECT-TYPE
	SYNTAX		SEQUENCE OF SSaf-teControlledSlot
	ACCESS		not-accessible
	STATUS		mandatory
	DESCRIPTION	"This group defines status of a Slot controlled by a SAF-TE
Processor"
	::= {dmtfGroups 20}

eSaf-teControlledSlot OBJECT-TYPE
	SYNTAX		SSaf-teControlledSlot
	ACCESS		not-accessible
	STATUS		mandatory
	DESCRIPTION	""
	INDEX		{DmiComponentIndex, a20Saf-teControlledSlotIndex}
	::= {tSaf-teControlledSlot 1}

a20Saf-teControlledSlotIndex OBJECT-TYPE
	SYNTAX		DmiInteger
	ACCESS		read-only
	STATUS		mandatory
	DESCRIPTION	"An index into the SAF-TE controlled Slot table."
	::= {eSaf-teControlledSlot 1}

a20Saf-teProcessorIndex OBJECT-TYPE
	SYNTAX		DmiInteger
	ACCESS		read-only
	STATUS		mandatory
	DESCRIPTION	"The Index to the SAF-TE proccessor table that is controlling
this Slot."
	::= {eSaf-teControlledSlot 2}

a20ScsiId OBJECT-TYPE
	SYNTAX		DmiInteger64X
	ACCESS		read-only
	STATUS		mandatory
	DESCRIPTION	"The SCSI target/initiator identifier for this slot."
	::= {eSaf-teControlledSlot 3}

a20NumberOfInsertions OBJECT-TYPE
	SYNTAX		DmiInteger
	ACCESS		read-only
	STATUS		mandatory
	DESCRIPTION	"The total number of device insertions for this slot while
the enclosure is powered on."
	::= {eSaf-teControlledSlot 4}

a20State OBJECT-TYPE
	SYNTAX		INTEGER {
		vDevicePresent-Ready                    	(1),
		vDevicePresent-NotReady                 	(2),
		vDevicePresent-HotSpare                 	(3),
		vDevicePresent-ReadyForRemoval          	(4),
		vDeviceNotPresent                       	(5),
		vDeviceNotPresent-ReadyForInsertion     	(6),
		vUnconfigured                           	(7),
		vUnknownState                           	(8)
	}
	ACCESS		read-only
	STATUS		mandatory
	DESCRIPTION	"The slot state."
	::= {eSaf-teControlledSlot 5}

a20Rebuild OBJECT-TYPE
	SYNTAX		INTEGER {
		vNotRebuilding                          	(0),
		vRebuildInProcess                       	(1),
		vRebuildStopped                         	(2),
		vUnknownStatus                          	(3)
	}
	ACCESS		read-only
	STATUS		mandatory
	DESCRIPTION	"Rebuild status"
	::= {eSaf-teControlledSlot 6}

a20DeviceFault OBJECT-TYPE
	SYNTAX		INTEGER {
		vFalse                                  	(0),
		vTrue                                   	(1),
		vUnknown                                	(2)
	}
	ACCESS		read-only
	STATUS		mandatory
	DESCRIPTION	"If true, the device has exhibited some hardware or data fault."
	::= {eSaf-teControlledSlot 7}

a20InFailedArray OBJECT-TYPE
	SYNTAX		INTEGER {
		vFalse                                  	(0),
		vTrue                                   	(1),
		vUnknown                                	(2)
	}
	ACCESS		read-only
	STATUS		mandatory
	DESCRIPTION	"If true, the device is in an array and an error has occurred
on any member of the array."
	::= {eSaf-teControlledSlot 8}

a20InCriticalArray OBJECT-TYPE
	SYNTAX		INTEGER {
		vFalse                                  	(0),
		vTrue                                   	(1),
		vUnknown                                	(2)
	}
	ACCESS		read-only
	STATUS		mandatory
	DESCRIPTION	"If true, the device is in an array that is non fault-tolerant."
	::= {eSaf-teControlledSlot 9}

a20ParityCheck OBJECT-TYPE
	SYNTAX		INTEGER {
		vFalse                                  	(0),
		vTrue                                   	(1),
		vUnknown                                	(2)
	}
	ACCESS		read-only
	STATUS		mandatory
	DESCRIPTION	"If true, the device is in an array that is undergoing a parity
check operation."
	::= {eSaf-teControlledSlot 10}

a20PredictedFault OBJECT-TYPE
	SYNTAX		INTEGER {
		vFalse                                  	(0),
		vTrue                                   	(1),
		vUnknown                                	(2)
	}
	ACCESS		read-only
	STATUS		mandatory
	DESCRIPTION	"If true, the device has been tagged by a fault prediction
algorithm as being likely to fail in the near future."
	::= {eSaf-teControlledSlot 11}

SSaf-teControlledTemperatureSensor ::= SEQUENCE {
	a21Saf-teControlledTemperatureSensorInde	DmiInteger,
	a21Saf-teProcessorIndex                 	DmiInteger,
	a21Temperature                          	DmiInteger
}

tSaf-teControlledTemperatureSensor OBJECT-TYPE
	SYNTAX		SEQUENCE OF SSaf-teControlledTemperatureSensor
	ACCESS		not-accessible
	STATUS		mandatory
	DESCRIPTION	"This group defines status of a Temperature sensor controlled
by a SAF-TE Processor"
	::= {dmtfGroups 21}

eSaf-teControlledTemperatureSensor OBJECT-TYPE
	SYNTAX		SSaf-teControlledTemperatureSensor
	ACCESS		not-accessible
	STATUS		mandatory
	DESCRIPTION	""
	INDEX		{DmiComponentIndex, a21Saf-teControlledTemperatureSensorInde}
	::= {tSaf-teControlledTemperatureSensor 1}

a21Saf-teControlledTemperatureSensorInde OBJECT-TYPE
	SYNTAX		DmiInteger
	ACCESS		read-only
	STATUS		mandatory
	DESCRIPTION	"An index into the SAF-TE controlled Temperature sensor table."
	::= {eSaf-teControlledTemperatureSensor 1}

a21Saf-teProcessorIndex OBJECT-TYPE
	SYNTAX		DmiInteger
	ACCESS		read-only
	STATUS		mandatory
	DESCRIPTION	"The Index to the SAF-TE proccessor that is controlling this
Temperature sensor."
	::= {eSaf-teControlledTemperatureSensor 2}

a21Temperature OBJECT-TYPE
	SYNTAX		DmiInteger
	ACCESS		read-only
	STATUS		mandatory
	DESCRIPTION	"The current temperature in degrees Fahrenheit."
	::= {eSaf-teControlledTemperatureSensor 3}

SNetworkAdapter802PortGroup ::= SEQUENCE {
	a22PortIndex                            	DmiInteger,
	a22PermanentNetworkAddress              	DmiDisplaystring,
	a22CurrentNetworkAddress                	DmiDisplaystring,
	a22ConnectorType                        	DmiInteger,
	a22DataRate                             	DmiInteger
}

tNetworkAdapter802PortGroup OBJECT-TYPE
	SYNTAX		SEQUENCE OF SNetworkAdapter802PortGroup
	ACCESS		not-accessible
	STATUS		mandatory
	DESCRIPTION	"Contains objects related to each of the network ports on
the network adapter."
	::= {dmtfGroups 22}

eNetworkAdapter802PortGroup OBJECT-TYPE
	SYNTAX		SNetworkAdapter802PortGroup
	ACCESS		not-accessible
	STATUS		mandatory
	DESCRIPTION	""
	INDEX		{DmiComponentIndex, a22PortIndex}
	::= {tNetworkAdapter802PortGroup 1}

a22PortIndex OBJECT-TYPE
	SYNTAX		DmiInteger
	ACCESS		read-only
	STATUS		mandatory
	DESCRIPTION	"This attribute is the ordinal of the network port within
the network adapter, i.e. the 'port number'."
	::= {eNetworkAdapter802PortGroup 1}

a22PermanentNetworkAddress OBJECT-TYPE
	SYNTAX		DmiDisplaystring
	ACCESS		read-only
	STATUS		mandatory
	DESCRIPTION	"This is the node address stored permanently in the adapter."
	::= {eNetworkAdapter802PortGroup 2}

a22CurrentNetworkAddress OBJECT-TYPE
	SYNTAX		DmiDisplaystring
	ACCESS		read-only
	STATUS		mandatory
	DESCRIPTION	"This is the node address that can be modified by software,
sometimes referred to as the Locally Administered Address (LAA)."
	::= {eNetworkAdapter802PortGroup 3}

a22ConnectorType OBJECT-TYPE
	SYNTAX		INTEGER {
		vUnknown                                	(1),
		vAui                                    	(2),
		vUtpCategory3                           	(3),
		vUtpCategory4                           	(4),
		vUtpCategory5                           	(5),
		vBnc                                    	(6),
		vStpRj45                                	(7),
		vStpDb9                                 	(8),
		vFiberMic                               	(9),
		vAppleAui                               	(10)
	}
	ACCESS		read-only
	STATUS		mandatory
	DESCRIPTION	"This is the type of connector currently being used to physically
attach this port to the LAN."
	::= {eNetworkAdapter802PortGroup 4}

a22DataRate OBJECT-TYPE
	SYNTAX		DmiInteger
	ACCESS		read-only
	STATUS		mandatory
	DESCRIPTION	"This is the rate at which data is transferred over the LAN
in Mbps."
	::= {eNetworkAdapter802PortGroup 5}

SNetworkAdapterHardwareGroup ::= SEQUENCE {
	a23NetworkTopology                      	DmiInteger,
	a23TransmissionCapability               	DmiInteger,
	a23NetworkAdapterRamSize                	DmiInteger,
	a23BusType                              	DmiInteger,
	a23BusWidth                             	DmiInteger,
	a23AdapterHardwareIndex                 	DmiInteger
}

tNetworkAdapterHardwareGroup OBJECT-TYPE
	SYNTAX		SEQUENCE OF SNetworkAdapterHardwareGroup
	ACCESS		not-accessible
	STATUS		mandatory
	DESCRIPTION	"Contains objects related to the network adapter hardware."
	::= {dmtfGroups 23}

eNetworkAdapterHardwareGroup OBJECT-TYPE
	SYNTAX		SNetworkAdapterHardwareGroup
	ACCESS		not-accessible
	STATUS		mandatory
	DESCRIPTION	""
	INDEX		{DmiComponentIndex, a23AdapterHardwareIndex}
	::= {tNetworkAdapterHardwareGroup 1}

a23NetworkTopology OBJECT-TYPE
	SYNTAX		INTEGER {
		vOther                                  	(1),
		v10MbpsEthernet                         	(2),
		v100MbpsEthernet                        	(3),
		v10010MbpsEthernet                      	(4),
		v100MbpsVgAnylan                        	(5),
		v4MbpsToken-ring                        	(6),
		v16MbpsToken-ring                       	(7),
		v164MbpsToken-ring                      	(8),
		v2MbpsArcnet                            	(9),
		v20MbpsArcnet                           	(10),
		vFddi                                   	(11),
		vAtm                                    	(12),
		vAppletalk                              	(13),
		v100mbpsTokenRing                       	(14),
		v1gbpsEthernet                          	(15)
	}
	ACCESS		read-only
	STATUS		mandatory
	DESCRIPTION	"This is the network media access method/topology supported
by this adapter."
	::= {eNetworkAdapterHardwareGroup 1}

a23TransmissionCapability OBJECT-TYPE
	SYNTAX		INTEGER {
		vNormal                                 	(1),
		vFullDuplex                             	(2)
	}
	ACCESS		read-only
	STATUS		mandatory
	DESCRIPTION	"The transmission capabilities of the adapter."
	::= {eNetworkAdapterHardwareGroup 2}

a23NetworkAdapterRamSize OBJECT-TYPE
	SYNTAX		DmiInteger
	ACCESS		read-only
	STATUS		mandatory
	DESCRIPTION	"This is the total size of adapter RAM in Kb."
	::= {eNetworkAdapterHardwareGroup 3}

a23BusType OBJECT-TYPE
	SYNTAX		INTEGER {
		vOther                                  	(1),
		vIsa                                    	(2),
		vEisa                                   	(3),
		vMca                                    	(4),
		vPci                                    	(5),
		vVl                                     	(6),
		vPcmcia                                 	(7),
		vParallel                               	(8),
		vNec98                                  	(9),
		vMotherboard                            	(256)
	}
	ACCESS		read-only
	STATUS		mandatory
	DESCRIPTION	"This is the type of bus used to interface the adapter to
the host."
	::= {eNetworkAdapterHardwareGroup 4}

a23BusWidth OBJECT-TYPE
	SYNTAX		INTEGER {
		vOther                                  	(1),
		vUnknown                                	(2),
		v8BitCard                               	(3),
		v16BitCard                              	(4),
		v32BitCard                              	(5),
		v64BitCard                              	(6),
		v128BitCard                             	(7)
	}
	ACCESS		read-only
	STATUS		mandatory
	DESCRIPTION	"This is the width (in bits) of the data path used to interface
the adapter with the host."
	::= {eNetworkAdapterHardwareGroup 5}

a23AdapterHardwareIndex OBJECT-TYPE
	SYNTAX		DmiInteger
	ACCESS		read-only
	STATUS		mandatory
	DESCRIPTION	"An index into the Network Adapter Hardware table."
	::= {eNetworkAdapterHardwareGroup 6}

SEventGenerationForPowerSupply ::= SEQUENCE {
	a24EventType                            	DmiInteger,
	a24EventSeverity                        	DmiInteger,
	a24IsEventState-based                   	DmiInteger,
	a24EventStateKey                        	DmiInteger,
	a24AssociatedGroup                      	DmiDisplaystring,
	a24EventSystem                          	DmiInteger,
	a24EventSubsystem1                      	DmiInteger,
	a24IsInstanceDataPresent                	DmiInteger,
	a24EventMessage                         	DmiDisplaystring
}

tEventGenerationForPowerSupply OBJECT-TYPE
	SYNTAX		SEQUENCE OF SEventGenerationForPowerSupply
	ACCESS		not-accessible
	STATUS		mandatory
	DESCRIPTION	""
	::= {dmtfGroups 24}

eEventGenerationForPowerSupply OBJECT-TYPE
	SYNTAX		SEventGenerationForPowerSupply
	ACCESS		not-accessible
	STATUS		mandatory
	DESCRIPTION	""
	INDEX		{DmiComponentIndex, a24AssociatedGroup}
	::= {tEventGenerationForPowerSupply 1}

a24EventType OBJECT-TYPE
	SYNTAX		INTEGER {
		vPowerSupplyStatusChange                	(1),
		vPowerControlRequest                    	(2),
		vPowerSupplyFailed                      	(256),
		vPowerSupplyOk                          	(257),
		vPowerSupplyLikelyToFail                	(258)
	}
	ACCESS		read-only
	STATUS		mandatory
	DESCRIPTION	"The type of event that has occurred."
	::= {eEventGenerationForPowerSupply 1}

a24EventSeverity OBJECT-TYPE
	SYNTAX		INTEGER {
		vMonitor                                	(1),
		vInformation                            	(2),
		vOk                                     	(4),
		vNon-critical                           	(8),
		vCritical                               	(16),
		vNon-recoverable                        	(32)
	}
	ACCESS		read-only
	STATUS		mandatory
	DESCRIPTION	"The severity of this event."
	::= {eEventGenerationForPowerSupply 2}

a24IsEventState-based OBJECT-TYPE
	SYNTAX		INTEGER {
		vFalse                                  	(0),
		vTrue                                   	(1)
	}
	ACCESS		read-only
	STATUS		mandatory
	DESCRIPTION	"The value of this attribute determines whether the Event
being reported is a state-based Event or not. If the value of this attribute
is TRUE then the Event is state-based. Otherwise the Event is not state-based."
	::= {eEventGenerationForPowerSupply 3}

a24EventStateKey OBJECT-TYPE
	SYNTAX		DmiInteger
	ACCESS		read-only
	STATUS		mandatory
	DESCRIPTION	"A unique, single integer key into the Event State group if
this is a state-based Event. If this is not a state-based Event then this
this attribute's value is not defined."
	::= {eEventGenerationForPowerSupply 4}

a24AssociatedGroup OBJECT-TYPE
	SYNTAX		DmiDisplaystring
	ACCESS		read-only
	STATUS		mandatory
	DESCRIPTION	"The class name of the group that is associated with the events
defined in this EventGeneration group."
	::= {eEventGenerationForPowerSupply 5}

a24EventSystem OBJECT-TYPE
	SYNTAX		INTEGER {
		vOther                                  	(1),
		vUnknown                                	(2)
	}
	ACCESS		read-only
	STATUS		mandatory
	DESCRIPTION	"The major functional aspect of the product causing the fault."
	::= {eEventGenerationForPowerSupply 6}

a24EventSubsystem OBJECT-TYPE
	SYNTAX		INTEGER {
		vOther                                  	(1),
		vUnknown                                	(2)
	}
	ACCESS		read-only
	STATUS		mandatory
	DESCRIPTION	"The minor functional aspect of the product causing the fault."
	::= {eEventGenerationForPowerSupply 7}

a24IsInstanceDataPresent OBJECT-TYPE
	SYNTAX		INTEGER {
		vFalse                                  	(0),
		vTrue                                   	(1)
	}
	ACCESS		read-only
	STATUS		mandatory
	DESCRIPTION	"Indicates whether the second event block contains instance-speci
ic data."
	::= {eEventGenerationForPowerSupply 8}

a24EventMessage OBJECT-TYPE
	SYNTAX		DmiDisplaystring
	ACCESS		read-only
	STATUS		mandatory
	DESCRIPTION	"Auxillary information releated to the event This text contains
the name of the Probe"
	::= {eEventGenerationForPowerSupply 9}

SEventGenerationForTemperatureProbe ::= SEQUENCE {
	a25EventType                            	DmiInteger,
	a25EventSeverity                        	DmiInteger,
	a25IsEventState-based                   	DmiInteger,
	a25EventStateKey                        	DmiInteger,
	a25AssociatedGroup                      	DmiDisplaystring,
	a25EventSystem                          	DmiInteger,
	a25EventSubsystem                       	DmiInteger,
	a25IsInstanceDataPresent                	DmiInteger,
	a25EventMessage                         	DmiDisplaystring
}

tEventGenerationForTemperatureProbe OBJECT-TYPE
	SYNTAX		SEQUENCE OF SEventGenerationForTemperatureProbe
	ACCESS		not-accessible
	STATUS		mandatory
	DESCRIPTION	""
	::= {dmtfGroups 25}

eEventGenerationForTemperatureProbe OBJECT-TYPE
	SYNTAX		SEventGenerationForTemperatureProbe
	ACCESS		not-accessible
	STATUS		mandatory
	DESCRIPTION	""
	INDEX		{DmiComponentIndex, a25AssociatedGroup}
	::= {tEventGenerationForTemperatureProbe 1}

a25EventType OBJECT-TYPE
	SYNTAX		INTEGER {
		vTemperatureOutOfRange                  	(1)
	}
	ACCESS		read-only
	STATUS		mandatory
	DESCRIPTION	"The type of event that has occurred."
	::= {eEventGenerationForTemperatureProbe 1}

a25EventSeverity OBJECT-TYPE
	SYNTAX		INTEGER {
		vMonitor                                	(1),
		vInformation                            	(2),
		vOk                                     	(4),
		vNon-critical                           	(8),
		vCritical                               	(16),
		vNon-recoverable                        	(32)
	}
	ACCESS		read-only
	STATUS		mandatory
	DESCRIPTION	"The severity of this event."
	::= {eEventGenerationForTemperatureProbe 2}

a25IsEventState-based OBJECT-TYPE
	SYNTAX		INTEGER {
		vFalse                                  	(0),
		vTrue                                   	(1)
	}
	ACCESS		read-only
	STATUS		mandatory
	DESCRIPTION	"The value of this attribute determines whether the Event
being reported is a state-based Event or not. If the value of this attribute
is TRUE then the Event is state-based. Otherwise the Event is not state-based."
	::= {eEventGenerationForTemperatureProbe 3}

a25EventStateKey OBJECT-TYPE
	SYNTAX		DmiInteger
	ACCESS		read-only
	STATUS		mandatory
	DESCRIPTION	"A unique, single integer key into the Event State group if
this is a state-based Event.  If this is not a state-based Event then this
this attribute's value is not defined."
	::= {eEventGenerationForTemperatureProbe 4}

a25AssociatedGroup OBJECT-TYPE
	SYNTAX		DmiDisplaystring
	ACCESS		read-only
	STATUS		mandatory
	DESCRIPTION	"The class name of the group that is associated with the events
defined in this Event Generation group."
	::= {eEventGenerationForTemperatureProbe 5}

a25EventSystem OBJECT-TYPE
	SYNTAX		INTEGER {
		vOther                                  	(1),
		vUnknown                                	(2)
	}
	ACCESS		read-only
	STATUS		mandatory
	DESCRIPTION	"The major functional aspect of the product causing the fault."
	::= {eEventGenerationForTemperatureProbe 6}

a25EventSubsystem OBJECT-TYPE
	SYNTAX		INTEGER {
		vOther                                  	(1),
		vUnknown                                	(2)
	}
	ACCESS		read-only
	STATUS		mandatory
	DESCRIPTION	"The minor functional aspect of the product causing the fault."
	::= {eEventGenerationForTemperatureProbe 7}

a25IsInstanceDataPresent OBJECT-TYPE
	SYNTAX		INTEGER {
		vFalse                                  	(0),
		vTrue                                   	(1)
	}
	ACCESS		read-only
	STATUS		mandatory
	DESCRIPTION	"Indicates whether the second event block contains instance-speci
ic data."
	::= {eEventGenerationForTemperatureProbe 8}

a25EventMessage OBJECT-TYPE
	SYNTAX		DmiDisplaystring
	ACCESS		read-only
	STATUS		mandatory
	DESCRIPTION	"Auxillary information releated to the event This text contains
the name of the Probe"
	::= {eEventGenerationForTemperatureProbe 9}

SEventGenerationForFans ::= SEQUENCE {
	a26EventType                            	DmiInteger,
	a26EventSeverity                        	DmiInteger,
	a26IsEventState-based                   	DmiInteger,
	a26EventStateKey                        	DmiInteger,
	a26AssociatedGroup                      	DmiDisplaystring,
	a26EventSystem                          	DmiInteger,
	a26EventSubsystem                       	DmiInteger,
	a26IsInstanceDataPresent                	DmiInteger,
	a26EventMessage                         	DmiDisplaystring
}

tEventGenerationForFans OBJECT-TYPE
	SYNTAX		SEQUENCE OF SEventGenerationForFans
	ACCESS		not-accessible
	STATUS		mandatory
	DESCRIPTION	""
	::= {dmtfGroups 26}

eEventGenerationForFans OBJECT-TYPE
	SYNTAX		SEventGenerationForFans
	ACCESS		not-accessible
	STATUS		mandatory
	DESCRIPTION	""
	INDEX		{DmiComponentIndex, a26AssociatedGroup}
	::= {tEventGenerationForFans 1}

a26EventType OBJECT-TYPE
	SYNTAX		INTEGER {
		vFanFailure                             	(1)
	}
	ACCESS		read-only
	STATUS		mandatory
	DESCRIPTION	"The type of event that has occurred."
	::= {eEventGenerationForFans 1}

a26EventSeverity OBJECT-TYPE
	SYNTAX		INTEGER {
		vMonitor                                	(1),
		vInformation                            	(2),
		vOk                                     	(4),
		vNon-critical                           	(8),
		vCritical                               	(16),
		vNon-recoverable                        	(32)
	}
	ACCESS		read-only
	STATUS		mandatory
	DESCRIPTION	"The severity of this event."
	::= {eEventGenerationForFans 2}

a26IsEventState-based OBJECT-TYPE
	SYNTAX		INTEGER {
		vFalse                                  	(0),
		vTrue                                   	(1)
	}
	ACCESS		read-only
	STATUS		mandatory
	DESCRIPTION	"The value of this attribute determines whether the Event
being reported is a state-based Event or not. If the value of this attribute
is TRUE then the Event is state-based. Otherwise the Event is not state-based."
	::= {eEventGenerationForFans 3}

a26EventStateKey OBJECT-TYPE
	SYNTAX		DmiInteger
	ACCESS		read-only
	STATUS		mandatory
	DESCRIPTION	"A unique, single integer key into the Event State group if
this is a state-based Event. If this is not a state-based Event then this
this attribute's value is not defined."
	::= {eEventGenerationForFans 4}

a26AssociatedGroup OBJECT-TYPE
	SYNTAX		DmiDisplaystring
	ACCESS		read-only
	STATUS		mandatory
	DESCRIPTION	"The class name of the group that is associated with the events
defined in this Event Generation group."
	::= {eEventGenerationForFans 5}

a26EventSystem OBJECT-TYPE
	SYNTAX		INTEGER {
		vOther                                  	(1),
		vUnknown                                	(2)
	}
	ACCESS		read-only
	STATUS		mandatory
	DESCRIPTION	"The major functional aspect of the product causing the fault."
	::= {eEventGenerationForFans 6}

a26EventSubsystem OBJECT-TYPE
	SYNTAX		INTEGER {
		vOther                                  	(1),
		vUnknown                                	(2)
	}
	ACCESS		read-only
	STATUS		mandatory
	DESCRIPTION	"The minor functional aspect of the product causing the fault."
	::= {eEventGenerationForFans 7}

a26IsInstanceDataPresent OBJECT-TYPE
	SYNTAX		INTEGER {
		vFalse                                  	(0),
		vTrue                                   	(1)
	}
	ACCESS		read-only
	STATUS		mandatory
	DESCRIPTION	"Indicates whether the second event block contains instance-speci
ic data."
	::= {eEventGenerationForFans 8}

a26EventMessage OBJECT-TYPE
	SYNTAX		DmiDisplaystring
	ACCESS		read-only
	STATUS		mandatory
	DESCRIPTION	"Auxillary information releated to the event This text contains
the name of the Probe"
	::= {eEventGenerationForFans 9}

SSymbiosHealth ::= SEQUENCE {
	a27OverallHealthStatus                  	DmiInteger,
	a27OverallControllerHealthStatus        	DmiInteger,
	a27Non-recoverableControllers           	DmiInteger,
	a27DegradedControllers                  	DmiInteger,
	a27OverallDeviceHealthStatus            	DmiInteger,
	a27Non-recoverableDevices               	DmiInteger,
	a27DegradedDevices                      	DmiInteger,
	a27DataValuesTimeStamp                  	DmiDateX,
	a27HardwareTimeStamp                    	DmiDateX
}

tSymbiosHealth OBJECT-TYPE
	SYNTAX		SEQUENCE OF SSymbiosHealth
	ACCESS		not-accessible
	STATUS		mandatory
	DESCRIPTION	"This group is the Symbios Vendor unique group for reporting
the health."
	::= {dmtfGroups 27}

eSymbiosHealth OBJECT-TYPE
	SYNTAX		SSymbiosHealth
	ACCESS		not-accessible
	STATUS		mandatory
	DESCRIPTION	""
	INDEX		{DmiComponentIndex}
	::= {tSymbiosHealth 1}

a27OverallHealthStatus OBJECT-TYPE
	SYNTAX		INTEGER {
		vOther                                  	(1),
		vUnknown                                	(2),
		vOk                                     	(3),
		vDegraded                               	(4),
		vNon-recoverable                        	(5)
	}
	ACCESS		read-only
	STATUS		mandatory
	DESCRIPTION	"Status indicating the overall health."
	::= {eSymbiosHealth 1}

a27OverallControllerHealthStatus OBJECT-TYPE
	SYNTAX		INTEGER {
		vOther                                  	(1),
		vUnknown                                	(2),
		vOk                                     	(3),
		vDegraded                               	(4),
		vNon-recoverable                        	(5)
	}
	ACCESS		read-only
	STATUS		mandatory
	DESCRIPTION	"Status indicating the overall health of the controllers."
	::= {eSymbiosHealth 2}

a27Non-recoverableControllers OBJECT-TYPE
	SYNTAX		DmiInteger
	ACCESS		read-only
	STATUS		mandatory
	DESCRIPTION	"The number of controllers reporting a non-recoverable status."
	::= {eSymbiosHealth 3}

a27DegradedControllers OBJECT-TYPE
	SYNTAX		DmiInteger
	ACCESS		read-only
	STATUS		mandatory
	DESCRIPTION	"The number of controllers reporting a degraded status."
	::= {eSymbiosHealth 4}

a27OverallDeviceHealthStatus OBJECT-TYPE
	SYNTAX		INTEGER {
		vOther                                  	(1),
		vUnknown                                	(2),
		vOk                                     	(3),
		vDegraded                               	(4),
		vNon-recoverable                        	(5)
	}
	ACCESS		read-only
	STATUS		mandatory
	DESCRIPTION	"Status indicating the overall health of the devices."
	::= {eSymbiosHealth 5}

a27Non-recoverableDevices OBJECT-TYPE
	SYNTAX		DmiInteger
	ACCESS		read-only
	STATUS		mandatory
	DESCRIPTION	"The number of devices reporting a non-recoverable status."
	::= {eSymbiosHealth 6}

a27DegradedDevices OBJECT-TYPE
	SYNTAX		DmiInteger
	ACCESS		read-only
	STATUS		mandatory
	DESCRIPTION	"The number of devices reporting a degraded status."
	::= {eSymbiosHealth 7}

a27DataValuesTimeStamp OBJECT-TYPE
	SYNTAX		DmiDateX
	ACCESS		read-only
	STATUS		mandatory
	DESCRIPTION	"The time the data values where last changed."
	::= {eSymbiosHealth 8}

a27HardwareTimeStamp OBJECT-TYPE
	SYNTAX		DmiDateX
	ACCESS		read-only
	STATUS		mandatory
	DESCRIPTION	"The time the hardware recognition was last changed."
	::= {eSymbiosHealth 9}

SSymbiosController ::= SEQUENCE {
	a28SymbiosControllerIndex               	DmiInteger,
	a28LastRunDateForDv                     	DmiDateX,
	a28IoFactorForDvErrorRate               	DmiInteger,
	a28TimeFactorForDvErrorRate             	DmiInteger,
	a28ErrorCountFactorForDvErrorRate       	DmiInteger,
	a28DvStatus                             	DmiInteger
}

tSymbiosController OBJECT-TYPE
	SYNTAX		SEQUENCE OF SSymbiosController
	ACCESS		not-accessible
	STATUS		mandatory
	DESCRIPTION	"This group is a Symbios Vendor unique group for dealing with
Controllers."
	::= {dmtfGroups 28}

eSymbiosController OBJECT-TYPE
	SYNTAX		SSymbiosController
	ACCESS		not-accessible
	STATUS		mandatory
	DESCRIPTION	""
	INDEX		{DmiComponentIndex, a28SymbiosControllerIndex}
	::= {tSymbiosController 1}

a28SymbiosControllerIndex OBJECT-TYPE
	SYNTAX		DmiInteger
	ACCESS		read-only
	STATUS		mandatory
	DESCRIPTION	"An index into the Symbios Vendor Unique Controller table.
 This index corresponds to the Storage Controller index."
	::= {eSymbiosController 1}

a28LastRunDateForDv OBJECT-TYPE
	SYNTAX		DmiDateX
	ACCESS		read-only
	STATUS		mandatory
	DESCRIPTION	"This indicates the date and time of the last time Domain
Validation was completed on this controller."
	::= {eSymbiosController 2}

a28IoFactorForDvErrorRate OBJECT-TYPE
	SYNTAX		DmiInteger
	ACCESS		read-write
	STATUS		mandatory
	DESCRIPTION	"This indicates the I/O factor to use for calculating the
Domain Validation Error Rate."
	::= {eSymbiosController 3}

a28TimeFactorForDvErrorRate OBJECT-TYPE
	SYNTAX		DmiInteger
	ACCESS		read-write
	STATUS		mandatory
	DESCRIPTION	"This indicates the time factor to use for calculating the
Domain Validation Error Rate."
	::= {eSymbiosController 4}

a28ErrorCountFactorForDvErrorRate OBJECT-TYPE
	SYNTAX		DmiInteger
	ACCESS		read-write
	STATUS		mandatory
	DESCRIPTION	"This indicates the error count factor to use for calculating
the Domain Validation Error Rate."
	::= {eSymbiosController 5}

a28DvStatus OBJECT-TYPE
	SYNTAX		INTEGER {
		vNotApplicable                          	(0),
		vDomainValidationCompletedByTheDriver   	(1),
		vDomainValidationCompletedWithNoChanges 	(2),
		vDomainValidationCompletedWithChanges   	(3),
		vDomainValidationCurrentlyRunning       	(4),
		vDomainValidationTerminated             	(5),
		vDomainValidationNeedsToBeRun           	(6)
	}
	ACCESS		read-write
	STATUS		mandatory
	DESCRIPTION	"This indicates the status of Domain Validation for this controll
r.  Writing a value of 4 to this attribute will cause Domain Validation to
be run."
	::= {eSymbiosController 6}

SMiftomib ::= SEQUENCE {
	a99MibName                              	DmiDisplaystring,
	a99MibOid                               	DmiDisplaystring,
	a99DisableTrap                          	DmiInteger
}

tMiftomib OBJECT-TYPE
	SYNTAX		SEQUENCE OF SMiftomib
	ACCESS		not-accessible
	STATUS		mandatory
	DESCRIPTION	"This group defines attributes required for DMI to SNMP translati
n."
	::= {dmtfGroups 99}

eMiftomib OBJECT-TYPE
	SYNTAX		SMiftomib
	ACCESS		not-accessible
	STATUS		mandatory
	DESCRIPTION	""
	INDEX		{DmiComponentIndex}
	::= {tMiftomib 1}

a99MibName OBJECT-TYPE
	SYNTAX		DmiDisplaystring
	ACCESS		read-only
	STATUS		mandatory
	DESCRIPTION	"The MIB name that defines this MIF"
	::= {eMiftomib 1}

a99MibOid OBJECT-TYPE
	SYNTAX		DmiDisplaystring
	ACCESS		read-only
	STATUS		mandatory
	DESCRIPTION	"The MIB OID that corresponds to this MIF"
	::= {eMiftomib 2}

a99DisableTrap OBJECT-TYPE
	SYNTAX		DmiInteger
	ACCESS		read-write
	STATUS		mandatory
	DESCRIPTION	"This attribute can be changed to disable sending oftraps
from this component"
	::= {eMiftomib 3}


--
-- Trap definitions - not generated by MIFTOMIB tool
--

-- DeviceError TRAP-TYPE
trap1forStorageDevices TRAP-TYPE
	ENTERPRISE eStorageDevicesEvents 
	VARIABLES {
       a6StorageDevicesEventType, 
       a6EventSeverity,  
       a6EventIsStateBased,
       a6EventStateKey,  
       a6AssociatedGroup, 
       a6EventSystem,     
       a6EventSubsystem,
       a6EventSolution,
       a6InstanceDataPresent,
       a6EventMessage,
       a5StorageDeviceIndex  
   }

	DESCRIPTION "Self-Monitoring Warning (predictive failure - data recovery possible)"

	::= 1


-- DeviceWarningTrap TRAP-TYPE
trap2forStorageDevices TRAP-TYPE
	ENTERPRISE eStorageDevicesEvents 
	VARIABLES {
	    a6StorageDevicesEventType, 
	    a6EventSeverity,  
	    a6EventIsStateBased,
	    a6EventStateKey,  
	    a6AssociatedGroup, 
	    a6EventSystem,     
	    a6EventSubsystem,
          a6EventSolution,
          a6InstanceDataPresent,
          a6EventMessage,
 	    a5StorageDeviceIndex  
	}

	DESCRIPTION "Self-Monitoring Warning (predictive failure - data recovery questionable)"

	::= 2



-- ErrorControllerTrap TRAP-TYPE
trap3forStorageController TRAP-TYPE
	ENTERPRISE eStorageControllerEvents 
	VARIABLES {
	    a8StorageControllerEventType,
	    a8EventSeverity,  
	    a8EventIsStateBased,
	    a8EventStateKey,
	    a8AssociatedGroup,
	    a8EventSystem,
	    a8EventSubsystem,
          a8EventSolution,
          a8InstanceDataPresent,
          a8EventMessage,
	    a7ControllerIndex
	}

	DESCRIPTION "Storage Controller Error (not responding)"

	::= 3

-- NewStorageControllerTrap TRAP-TYPE
trap4forMassStorageAssociation TRAP-TYPE
	ENTERPRISE eMassStorageAssociationEvents 
	VARIABLES {
	    a12MassStorageAssociationEventType,
	    a12EventSeverity,
	    a12EventIsStateBased,
	    a12EventStateKey,
	    a12AssociatedGroup,
	    a12EventSystem,
	    a12EventSubsystem,
          a12EventSolution,
          a12InstanceDataPresent,
          a12EventMessage,
 	    a11AssociationIndex
	}

	DESCRIPTION "New Storage controller detected"

	::= 4

-- NewDeviceTrap TRAP-TYPE
trap5forMassStorageAssociation TRAP-TYPE
	ENTERPRISE eMassStorageAssociationEvents 
	VARIABLES {
	    a12MassStorageAssociationEventType,
	    a12EventSeverity,
	    a12EventIsStateBased,
	    a12EventStateKey,
	    a12AssociatedGroup,
	    a12EventSystem,
	    a12EventSubsystem,
          a12EventSolution,
          a12InstanceDataPresent,
          a12EventMessage,
	    a11AssociationIndex
	}

	DESCRIPTION "New device detected"

	::= 5

-- ExistingControllerChangedTrap TRAP-TYPE
trap6forMassStorageAssociation TRAP-TYPE
	ENTERPRISE eMassStorageAssociationEvents 
	VARIABLES {
	    a12MassStorageAssociationEventType,
	    a12EventSeverity,
	    a12EventIsStateBased,
	    a12EventStateKey,
	    a12AssociatedGroup,
	    a12EventSystem,
	    a12EventSubsystem,
          a12EventSolution,
          a12InstanceDataPresent,
          a12EventMessage,
	    a11AssociationIndex
	}

	DESCRIPTION "Existing controller changed"

	::=6

-- ExistingDeviceChangedTrap TRAP-TYPE
trap7forMassStorageAssociation TRAP-TYPE
	ENTERPRISE eMassStorageAssociationEvents 
	VARIABLES {
	    a12MassStorageAssociationEventType,
	    a12EventSeverity,
	    a12EventIsStateBased,
	    a12EventStateKey,
	    a12AssociatedGroup,
	    a12EventSystem,
	    a12EventSubsystem,
          a12EventSolution,
          a12InstanceDataPresent,
          a12EventMessage,
	    a11AssociationIndex
	}

	DESCRIPTION "Existing device changed"

	::= 7

END
