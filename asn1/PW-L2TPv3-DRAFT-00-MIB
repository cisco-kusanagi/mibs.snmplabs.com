-- extracted from draft-nadeau-l2tpext-pw-l2tpv3-mib-01.txt
-- at Sat Jun 30 06:08:28 2007

  PW-L2TPv3-DRAFT-00-MIB DEFINITIONS ::= BEGIN

  IMPORTS  
     MODULE-IDENTITY, OBJECT-TYPE, Unsigned32, transmission  
        FROM SNMPv2-SMI                   -- [RFC2578] 

     MODULE-COMPLIANCE, OBJECT-GROUP  
        FROM SNMPv2-CONF                  -- [RFC2580]  

     StorageType, RowStatus  
        FROM SNMPv2-TC                    -- [RFC2579] 

     InterfaceIndexOrZero  
        FROM IF-MIB                       -- [RFC2863] 

     SnmpAdminString
        FROM SNMP-FRAMEWORK-MIB

     pwIndex                               -- [RFCxxxx] 
  -- RFC Editor: Please replace XXXX with RFC number & remove this 
  -- note.  
        FROM PW-STD-MIB  

  ;  

  pwL2tpv3Draft00MIB MODULE-IDENTITY  
     LAST-UPDATED "200610051200Z"  -- 05 Oct 2006 12:00:00 GMT   
     ORGANIZATION    "IETF L2TP Working Group"
     CONTACT-INFO
               "Layer Two Tunneling Protocol Extensions WG
                Working Group Area:        Internet
                Working Group Name:        l2tpext
                General Discussion:        l2tp@l2tp.net"

     DESCRIPTION  
         "This MIB module complements the PW-STD-MIB module for PW   
          operation over L2TPv3.  

         Copyright (C) The Internet Society (2006).  This version  
         of this MIB module is part of RFC yyyy;  see the RFC  
         itself for full legal notices.  
         -- RFC Ed.: replace yyyy with actual RFC number & remove  
         -- this note  
         "        
     -- Revision history.  
      REVISION       "200610051200Z"  -- 05 Oct 2006 12:00:00 GMT
      DESCRIPTION  
          " First published as RFCWXYZ. "  
  -- RFC Editor: Please replace WXYZ with correct # and remove this 
  -- note 

    ::= { transmission XXX } 
  -- RFC Editor: To be assigned by IANA. Please replace XXX 
  -- with the assigned value and remove this note. 

  -- Top-level components of this MIB.  

                     

   -- Notifications  
   pwL2tpv3Notifications OBJECT IDENTIFIER   
                                 ::= { pwL2tpv3Draft00MIB 0 }  

  -- Tables, Scalars  
  pwL2tpv3Objects       OBJECT IDENTIFIER  
                                ::= { pwL2tpv3Draft00MIB 1 }  
  -- Conformance  
  pwL2tpv3Conformance   OBJECT IDENTIFIER   
                                ::= { pwL2tpv3Draft00MIB 2 }  

  -- PW L2TPv3 table  

  pwL2tpv3Table   OBJECT-TYPE  
     SYNTAX        SEQUENCE OF PwL2tpv3Entry  
     MAX-ACCESS    not-accessible  
     STATUS        current  
     DESCRIPTION  
         "This table controls L2TPv3 specific parameters when the PW is  
          going to be carried over L2TPv3."  
     ::= { pwL2tpv3Objects 1 }  

  pwL2tpv3Entry   OBJECT-TYPE  
     SYNTAX        PwL2tpv3Entry  
     MAX-ACCESS    not-accessible  
     STATUS        current  
     DESCRIPTION  
          "A row in this table represents parameters 
           specific to L2TPv3  for a pseudo wire (PW). 

           A row MUST be created automatically by the local agent 
           for every entry in the pwTable if the pwPsnType is   
           l2tp. Each entry is indexed by pwIndex, which uniquely   
           identifies a singular PW.  

           A row can also be created manually in this table.
          "  
     INDEX  { pwIndex }  

-- Ed Note: Do we need to have pwL2tpv3CtrlCfgIfIndex as an index?

        ::= { pwL2tpv3Table 1 }  

  PwL2tpv3Entry ::= SEQUENCE {  
        pwL2tpv3SessionCfgIfIndex       InterfaceIndexOrZero,
        pwL2tpv3CtrlCfgRouterID         SnmpAdminString,
        pwL2tpv3LocalSessionID          Unsigned32,    
        pwL2tpv3RemoteSessionID         Unsigned32,  
        pwL2tpv3OperType                BITS,  
        pwL2tpv3DataSequencing          INTEGER,
        pwL2tpv3AddrResol               INTEGER,
        pwL2tpv3Mtu                     Unsigned32,
        pwL2tpv3StorageType             StorageType,
        pwL2tpv3RowStatus               RowStatus       
     }  

   pwL2tpv3SessionCfgIfIndex    OBJECT-TYPE
           SYNTAX          InterfaceIndexOrZero
           MAX-ACCESS      read-create
           STATUS          current
           DESCRIPTION
               "The interface index for the corresponding L2TP 
                interface to which this PW session is associated.

                The value of this object must correspond to the 
                value of l2tpv3SessionCfgIfIndex in the 
                l2tpv3SessionCfgTable."
     ::= { pwL2tpv3Entry 1 }  


   pwL2tpv3CtrlCfgRouterID   OBJECT-TYPE
           SYNTAX          SnmpAdminString
           MAX-ACCESS      read-create
           STATUS          current
           DESCRIPTION
               "The local router ID of this peer, as communicated via
                the Router ID AVP for this control connection.

                The value of this object corresponds to the 
                value of l2tpv3CtrlCfgRouterID in l2tpv3CtrlCfgTable."
     ::= { pwL2tpv3Entry 2 }  


   pwL2tpv3LocalSessionID OBJECT-TYPE
           SYNTAX          Unsigned32
           MAX-ACCESS      read-create
           STATUS          current
           DESCRIPTION
               "The local L2TPv3 session id for this PW. The value 
                of this object corresponds to the 
                l2tpv3SessionCfgLocalID in l2tpv3SessionCfgTable."
     ::= { pwL2tpv3Entry 3 }  

   pwL2tpv3RemoteSessionID OBJECT-TYPE
           SYNTAX          Unsigned32
           MAX-ACCESS      read-create
           STATUS          current
           DESCRIPTION
               "The remote L2TPv3 session id for this PW. The value 
                of this object corresponds to the 
                l2tpv3SessionCfgRemoteID in l2tpv3SessionCfgTable."
     ::= { pwL2tpv3Entry 4 }  

  pwL2tpv3OperType OBJECT-TYPE   
     SYNTAX   BITS {  
         ifToIf    (0),  
         vcToVc    (1),  
         ifToVc    (2),
         vcToIf    (3)
              }  
     MAX-ACCESS    read-create  
     STATUS        current  
     DESCRIPTION  
          "Set by the operator to indicate the operation type of this  
           PW. "
     REFERENCE  
          "[PW-IP] section 6."  
     ::= { pwL2tpv3Entry 5 }  

  pwL2tpv3DataSequencing OBJECT-TYPE   
     SYNTAX   INTEGER {  
         noSeq            (0),  
         nonIpSeq         (1),  
         allSeq           (2)  
              }  

     MAX-ACCESS    read-create  
     STATUS        current  
     DESCRIPTION  
         "Set by the operator to indicate data sequencing.
           noSeq(0) - No incoming data packets require sequencing.
           nonIpSeq(0)- Only non-IP data packets require sequencing.
           allSeq(2) - All incoming data packets require sequencing."
     REFERENCE  
          "[PW-IP] section 4.2."  
     DEFVAL { allSeq }  
     ::= { pwL2tpv3Entry 6 }  

  pwL2tpv3AddrResol OBJECT-TYPE   
     SYNTAX        INTEGER {  
         static            (0),  
         dynamic           (1)
              } 
     MAX-ACCESS    read-create  
     STATUS        current  
     DESCRIPTION  
          "The value of this object indicates the point-to-point
           address resolution mechanism for this PW."
     REFERENCE  
          "[PW-IP] section 5."  
     DEFVAL { static }  
     ::= { pwL2tpv3Entry 7 }  

  pwL2tpv3Mtu OBJECT-TYPE   
     SYNTAX        Unsigned32
     MAX-ACCESS    read-create  
     STATUS        current  
     DESCRIPTION  
          "Set by the operator to indicate the PW MTU value to be   
           used on the PW."  
     REFERENCE  
          "[PW-IP] section 4.3."  
     DEFVAL { 1500 }  
     ::= { pwL2tpv3Entry 8 }  

  pwL2tpv3StorageType OBJECT-TYPE   
     SYNTAX        StorageType  
     MAX-ACCESS    read-create  
     STATUS        current  
     DESCRIPTION  
         "This variable indicates the storage type for this row.
          Conceptual rows having the value 'permanent'
          need not allow write-access to any columnar
          objects in the row."  
     DEFVAL { volatile }
     ::= { pwL2tpv3Entry 9 }  

  pwL2tpv3RowStatus  OBJECT-TYPE
      SYNTAX        RowStatus
      MAX-ACCESS    read-create
      STATUS        current
      DESCRIPTION
           "This variable is used to create, modify, and/or
             delete a row in this table.  When a row in this
             table is in active(1) state, no objects in that row
             can be modified by the agent except
             pwL2tpv3RowStatus and pwL2tpv3StorageType."
      ::= { pwL2tpv3Entry 10 }

  -- End of PW L2TPv3 table  



  -- conformance information  

  pwL2tpv3Groups      OBJECT IDENTIFIER ::= { pwL2tpv3Conformance 1 }  
  pwL2tpv3Compliances OBJECT IDENTIFIER ::= { pwL2tpv3Conformance 2 }  

  -- Compliance requirement for fully compliant implementations.  

  pwL2tpv3ModuleFullCompliance MODULE-COMPLIANCE  
      STATUS  current  
      DESCRIPTION  
              "The compliance statement for agents that provide full  
               support for PW-L2TP MIB Module. Such devices can  
               then be monitored and also be configured using  
               this MIB module."  

     MODULE  -- this module  
     MANDATORY-GROUPS { pwL2tpv3Group
                       }  

      ::= { pwL2tpv3Compliances 1 }  

  -- Compliance requirement for Read Only compliant implementations.  

  pwL2tpv3ModuleReadOnlyCompliance MODULE-COMPLIANCE  
      STATUS  current  
      DESCRIPTION  
              "The compliance statement for agents that provide read  
               only support for PW-L2TP MIB Module. Such devices can  
               then be monitored but cannot be configured using this  
               MIB module."  

                     

     MODULE  -- this module  
     MANDATORY-GROUPS { pwL2tpv3Group 
                       }  


      ::= { pwL2tpv3Compliances 2 }  

  -- Units of conformance.  

  pwL2tpv3Group OBJECT-GROUP   
     OBJECTS {  
        pwL2tpv3SessionCfgIfIndex, 
        pwL2tpv3CtrlCfgRouterID,
        pwL2tpv3LocalSessionID, 
        pwL2tpv3RemoteSessionID,
        pwL2tpv3OperType,       
        pwL2tpv3DataSequencing, 
        pwL2tpv3AddrResol,      
        pwL2tpv3Mtu,            
        pwL2tpv3StorageType,
        pwL2tpv3RowStatus    
            }  
     STATUS  current  
     DESCRIPTION  
         "Collection of objects needed for PW over L2TPv3 PSN   
          configuration."  
     ::= { pwL2tpv3Groups 1 }  

                     
END

-- 
--    Copyright (C) The IETF Trust (2007).
-- 
--    This document is subject to the rights, licenses and restrictions
--    contained in BCP 78, and except as set forth therein, the authors
--    retain all their rights.
-- 
--    This document and the information contained herein are provided on an
--    "AS IS" basis and THE CONTRIBUTOR, THE ORGANIZATION HE/SHE  
--    REPRESENTS OR IS SPONSORED BY (IF ANY), THE INTERNET SOCIETY, THE
--    IETF TRUST AND THE INTERNET ENGINEERING TASK FORCE DISCLAIM ALL
--    WARRANTIES, EXPRESS OR IMPLIED, INCLUDING BUT NOT LIMITED TO ANY
--    WARRANTY THAT THE USE OF THE INFORMATION HEREIN WILL NOT INFRINGE
--    ANY RIGHTS OR ANY IMPLIED WARRANTIES OF MERCHANTABILITY OR FITNESS
--    FOR A PARTICULAR PURPOSE.
-- 
-- 
-- 12 Intellectual Property Notice 
--    
--    The IETF takes no position regarding the validity or scope of any
--    Intellectual Property Rights or other rights that might be claimed to
--    pertain to the implementation or use of the technology described in
--    this document or the extent to which any license under such rights
--    might or might not be available; nor does it represent that it has
--    made any independent effort to identify any such rights. Information
--    on the procedures with respect to rights in RFC documents can be
--    found in BCP 78 and BCP 79.
--    Copies of IPR disclosures made to the IETF Secretariat and any
--    assurances of licenses to be made available, or the result of an
--    attempt made to obtain a general license or permission for the use 
--    of such proprietary rights by implementers or users of this
--    specification can be obtained from the IETF on-line IPR repository
--    at http://www.ietf.org/ipr.
-- 
--    The IETF invites any interested party to bring to its attention any
--    copyrights, patents or patent applications, or other proprietary
--    rights that may cover technology that may be required to implement
--    this standard. Please address the information to the IETF at ietf-
--    ipr@ietf.org.
-- 
-- Disclaimer of Validity
-- 
--    This document and the information contained herein are provided
--    on an "AS IS" basis and THE CONTRIBUTOR, THE ORGANIZATION HE/SHE
--    REPRESENTS OR IS SPONSORED BY (IF ANY), THE INTERNET SOCIETY, THE
--    IETF TRUST AND THE INTERNET ENGINEERING TASK FORCE DISCLAIM ALL
--    WARRANTIES, EXPRESS OR IMPLIED, INCLUDING BUT NOT LIMITED TO ANY
--    WARRANTY THAT THE USE OF THE INFORMATION HEREIN WILL NOT INFRINGE
--    ANY RIGHTS OR ANY IMPLIED WARRANTIES OF MERCHANTABILITY OR FITNESS
--    FOR A PARTICULAR PURPOSE.
