--
-- This SMIv2 module has been generated by smidump 0.2-cvs. Do not edit.
--

SONUS-DS1-MIB DEFINITIONS ::= BEGIN

IMPORTS
    Integer32, MODULE-IDENTITY, NOTIFICATION-TYPE, OBJECT-TYPE
        FROM SNMPv2-SMI
    DisplayString, RowStatus
        FROM SNMPv2-TC
    sonusDs1Index, sonusDs3Index, sonusEventClass, sonusEventDescription, 
    sonusEventLevel, sonusPortIndex, sonusShelfIndex, sonusSlotIndex
        FROM SONUS-COMMON-MIB
    sonusCircuitMIBs
        FROM SONUS-SMI
    SonusAdminAction, SonusAdminState, SonusName, SonusServiceState
        FROM SONUS-TC;

sonusDsx1MIB MODULE-IDENTITY
    LAST-UPDATED    "200107310000Z"
    ORGANIZATION    
            "Sonus Networks, Inc."
    CONTACT-INFO    
            "   Customer Support    
             Sonus Networks, Inc,
             5 Carlisle Road
             Westford, MA 01886
             USA
             
             Tel: 978-692-8999
             Fax: 978-392-9118
             E-mail: cs.snmp@sonusnet.com"
    DESCRIPTION     
            "The MIB Module for DS1 Management."
    ::= { sonusCircuitMIBs 1 }


sonusDsx1MIBObjects OBJECT IDENTIFIER
    ::= { sonusDsx1MIB 1 }

sonusDsx1Admn OBJECT IDENTIFIER
    ::= { sonusDsx1MIBObjects 1 }

sonusDsx1AdmnNextIndex OBJECT IDENTIFIER
    ::= { sonusDsx1Admn 1 }

sonusDsx1AdmnTable OBJECT-TYPE
    SYNTAX          SEQUENCE OF SonusDsx1AdmnEntry
    MAX-ACCESS      not-accessible
    STATUS          current
    DESCRIPTION     
            "Table of Sonus Enterprise Configurations for all DS1s"
    ::= { sonusDsx1Admn 2 }

sonusDsx1AdmnEntry OBJECT-TYPE
    SYNTAX          SonusDsx1AdmnEntry
    MAX-ACCESS      not-accessible
    STATUS          current
    DESCRIPTION     
            "Entry in Table consisting of the all the Sonus Enterprise DS1 Configurations"
    INDEX           { sonusDsx1AdmnShelfIndex, sonusDsx1AdmnSlotIndex, 
                      sonusDsx1AdmnPortIndex, sonusDsx1AdmnDs3Index, 
                      sonusDsx1AdmnDs1Index }
    ::= { sonusDsx1AdmnTable 1 }

SonusDsx1AdmnEntry ::=
    SEQUENCE {
        sonusDsx1AdmnRowStatus          RowStatus,
        sonusDsx1AdmnName               SonusName,
        sonusDsx1AdmnProfileName        DisplayString,
        sonusDsx1AdmnShelfIndex         Integer32,
        sonusDsx1AdmnSlotIndex          Integer32,
        sonusDsx1AdmnPortIndex          Integer32,
        sonusDsx1AdmnDs3Index           Integer32,
        sonusDsx1AdmnDs1Index           Integer32,
        sonusDsx1AdmnIfIndex            Integer32,
        sonusDsx1AdmnState              SonusAdminState,
        sonusDsx1AdmnLineBuildOut       INTEGER,
        sonusDsx1AdmnTimeout            Integer32,
        sonusDsx1AdmnMode               SonusServiceState,
        sonusDsx1AdmnAction             SonusAdminAction,
        sonusDsx1AdmnIdleCode           Integer32,
        sonusDsx1AdmnAvailChannels      BITS,
        sonusDsx1AdmnType               INTEGER,
        sonusDsx1AdmnESThreshold        Integer32,
        sonusDsx1AdmnSESThreshold       Integer32,
        sonusDsx1AdmnCSSThreshold       Integer32,
        sonusDsx1AdmnDayESThreshold     Integer32,
        sonusDsx1AdmnDaySESThreshold    Integer32,
        sonusDsx1AdmnDayCSSThreshold    Integer32,
        sonusDsx1AdmnFarESThreshold     Integer32,
        sonusDsx1AdmnFarSESThreshold    Integer32,
        sonusDsx1AdmnFarDayESThreshold  Integer32,
        sonusDsx1AdmnFarDaySESThreshold Integer32,
        sonusDsx1AdmnPCVThreshold       Integer32,
        sonusDsx1AdmnLCVThreshold       Integer32,
        sonusDsx1AdmnUASThreshold       Integer32,
        sonusDsx1AdmnFarPCVThreshold    Integer32,
        sonusDsx1AdmnFarLCVThreshold    Integer32,
        sonusDsx1AdmnFarUASThreshold    Integer32,
        sonusDsx1AdmnDayPCVThreshold    Integer32,
        sonusDsx1AdmnDayLCVThreshold    Integer32,
        sonusDsx1AdmnDayUASThreshold    Integer32,
        sonusDsx1AdmnFarDayPCVThreshold Integer32,
        sonusDsx1AdmnFarDayLCVThreshold Integer32,
        sonusDsx1AdmnFarDayUASThreshold Integer32,
        sonusDsx1AdmnInitCounters       SonusAdminState,
        sonusDsx1AdmnEchoProfileName    DisplayString,
        sonusDsx1AdmnEchoCancellorMaxTail INTEGER,
        sonusDsx1AdmnEchoCancellorAudioType   INTEGER,
        sonusDsx1AdmnEchoCancellorSignallingTone        INTEGER,
        sonusDsx1AdmnEchoCancellorNlpDisable    Integer32,
        sonusDsx1AdmnEchoCancellorNlpEnable   Integer32,
        sonusDsx1AdmnEchoCancellorReturnLoss    INTEGER,
        sonusDsx1AdmnEchoCancellorResidualEcho      INTEGER,
        sonusDsx1AdmnEchoCancellorHiLevelComp     INTEGER,
        sonusDsx1AdmnEchoCancellorModemDisable      INTEGER,
        sonusDsx1AdmnZeroSuppression    INTEGER,
        sonusDsx1AdmnCircuitId          DisplayString,
        sonusDsx1AdmnEchoCancellorNarrowbandDetection             INTEGER
    }

sonusDsx1AdmnRowStatus OBJECT-TYPE
    SYNTAX          RowStatus
    MAX-ACCESS      read-write
    STATUS          current
    DESCRIPTION     
            "DS1, Needed for SNMP"
    ::= { sonusDsx1AdmnEntry 1 }

sonusDsx1AdmnName OBJECT-TYPE
    SYNTAX          SonusName
    MAX-ACCESS      read-write
    STATUS          current
    DESCRIPTION     
            "Name of this T1/E1 Span"
    ::= { sonusDsx1AdmnEntry 2 }

sonusDsx1AdmnProfileName OBJECT-TYPE
    SYNTAX          DisplayString (SIZE(1..23))
    MAX-ACCESS      read-write
    STATUS          current
    DESCRIPTION     
            "The name of the profile applied to this T1/E1 Table"
    ::= { sonusDsx1AdmnEntry 3 }

sonusDsx1AdmnShelfIndex OBJECT-TYPE
    SYNTAX          Integer32
    MAX-ACCESS      read-only
    STATUS          current
    DESCRIPTION     
            "Shelf index for this table"
    ::= { sonusDsx1AdmnEntry 4 }

sonusDsx1AdmnSlotIndex OBJECT-TYPE
    SYNTAX          Integer32
    MAX-ACCESS      read-only
    STATUS          current
    DESCRIPTION     
            "Slot index for this table"
    ::= { sonusDsx1AdmnEntry 5 }

sonusDsx1AdmnPortIndex OBJECT-TYPE
    SYNTAX          Integer32
    MAX-ACCESS      read-only
    STATUS          current
    DESCRIPTION     
            "Port Index into this table"
    ::= { sonusDsx1AdmnEntry 6 }

sonusDsx1AdmnDs3Index OBJECT-TYPE
    SYNTAX          Integer32
    MAX-ACCESS      read-only
    STATUS          current
    DESCRIPTION     
            "Ds3 Index into this table"
    ::= { sonusDsx1AdmnEntry 7 }

sonusDsx1AdmnDs1Index OBJECT-TYPE
    SYNTAX          Integer32
    MAX-ACCESS      read-only
    STATUS          current
    DESCRIPTION     
            "Ds1 Index into this table"
    ::= { sonusDsx1AdmnEntry 8 }

sonusDsx1AdmnIfIndex OBJECT-TYPE
    SYNTAX          Integer32
    MAX-ACCESS      read-only
    STATUS          current
    DESCRIPTION     
            "If Index for the corresponding standard MIB table"
    ::= { sonusDsx1AdmnEntry 9 }

sonusDsx1AdmnState OBJECT-TYPE
    SYNTAX          SonusAdminState
    MAX-ACCESS      read-write
    STATUS          current
    DESCRIPTION     
            "State of T1/E1, Enabled/Disabled"
    DEFVAL          { disabled }
    ::= { sonusDsx1AdmnEntry 10 }

sonusDsx1AdmnLineBuildOut OBJECT-TYPE
    SYNTAX          INTEGER { buildOut0to110(1), buildOut110to220(2), 
                        buildOut220to330(3), buildOut330to440(4), 
                        buildOut440to550(5), buildOut550to660(6), 
                        buildOut120Ohms(7), buildOut75Ohms(8) }
    MAX-ACCESS      read-write
    STATUS          current
    DESCRIPTION     
            "Line build out of T1/E1"
    DEFVAL          { buildOut110to220 }
    ::= { sonusDsx1AdmnEntry 11 }

sonusDsx1AdmnTimeout OBJECT-TYPE
    SYNTAX          Integer32 (0..1440)
    MAX-ACCESS      read-write
    STATUS          current
    DESCRIPTION     
            "Max time in minutes before dryup takes place"
    DEFVAL          { 5 }
    ::= { sonusDsx1AdmnEntry 12 }

sonusDsx1AdmnMode OBJECT-TYPE
    SYNTAX          SonusServiceState
    MAX-ACCESS      read-write
    STATUS          current
    DESCRIPTION     
            "T1/E1 span is in service or out of service."
    DEFVAL          { outOfService }
    ::= { sonusDsx1AdmnEntry 13 }

sonusDsx1AdmnAction OBJECT-TYPE
    SYNTAX          SonusAdminAction
    MAX-ACCESS      read-write
    STATUS          current
    DESCRIPTION     
            "Force out of service or wait for dryup"
    DEFVAL          { dryUp }
    ::= { sonusDsx1AdmnEntry 14 }

sonusDsx1AdmnIdleCode OBJECT-TYPE
    SYNTAX          Integer32 (0..255)
    MAX-ACCESS      read-write
    STATUS          current
    DESCRIPTION     
            "Idle code to be applied to the channels"
    DEFVAL          { 127 }
    ::= { sonusDsx1AdmnEntry 15 }

sonusDsx1AdmnAvailChannels OBJECT-TYPE
    SYNTAX          BITS { channel1(0), channel2(1), channel3(2), 
                        channel4(3), channel5(4), channel6(5), 
                        channel7(6), channel8(7), channel9(8), 
                        channel10(9), channel11(10), channel12(11), 
                        channel13(12), channel14(13), channel15(14), 
                        channel16(15), channel17(16), channel18(17), 
                        channel19(18), channel20(19), channel21(20), 
                        channel22(21), channel23(22), channel24(23), 
                        channel25(24), channel26(25), channel27(26), 
                        channel28(27), channel29(28), channel30(29), 
                        channel31(30), channel32(31) }
    MAX-ACCESS      read-write
    STATUS          current
    DESCRIPTION     
            "Bitstring map of channels that are available on this T1/E1 span."
    ::= { sonusDsx1AdmnEntry 16 }

sonusDsx1AdmnType OBJECT-TYPE
    SYNTAX          INTEGER { t1(1), e1(2) }
    MAX-ACCESS      read-write
    STATUS          current
    DESCRIPTION     
            "Type of DSx1. Indicates whether this span is a T1 span or E1 span."
    DEFVAL          { t1 }
    ::= { sonusDsx1AdmnEntry 17 }

sonusDsx1AdmnESThreshold OBJECT-TYPE
    SYNTAX          Integer32 (1..900)
    MAX-ACCESS      read-write
    STATUS          current
    DESCRIPTION     
            "Errored Seconds threshold value for 15 minute interval. This is for near end."
    DEFVAL          { 65 }
    ::= { sonusDsx1AdmnEntry 18 }

sonusDsx1AdmnSESThreshold OBJECT-TYPE
    SYNTAX          Integer32 (1..900)
    MAX-ACCESS      read-write
    STATUS          current
    DESCRIPTION     
            "Severely Errored Seconds threshold value for 15 minute interval. 
             This is for near end."
    DEFVAL          { 10 }
    ::= { sonusDsx1AdmnEntry 19 }

sonusDsx1AdmnCSSThreshold OBJECT-TYPE
    SYNTAX          Integer32 (1..900)
    MAX-ACCESS      read-write
    STATUS          current
    DESCRIPTION     
            "Severely Errored Seconds threshold value for 15 minute interval. 
             This is for near end."
    DEFVAL          { 1 }
    ::= { sonusDsx1AdmnEntry 20 }

sonusDsx1AdmnDayESThreshold OBJECT-TYPE
    SYNTAX          Integer32 (1..65535)
    MAX-ACCESS      read-write
    STATUS          current
    DESCRIPTION     
            "Errored Seconds threshold value for a day. This is for near end."
    DEFVAL          { 648 }
    ::= { sonusDsx1AdmnEntry 21 }

sonusDsx1AdmnDaySESThreshold OBJECT-TYPE
    SYNTAX          Integer32 (1..65535)
    MAX-ACCESS      read-write
    STATUS          current
    DESCRIPTION     
            "Severely Errored Seconds threshold value for a day. This is for near end."
    DEFVAL          { 100 }
    ::= { sonusDsx1AdmnEntry 22 }

sonusDsx1AdmnDayCSSThreshold OBJECT-TYPE
    SYNTAX          Integer32 (1..65535)
    MAX-ACCESS      read-write
    STATUS          current
    DESCRIPTION     
            "Severely Errored Seconds threshold value for a day. This is for near end."
    DEFVAL          { 4 }
    ::= { sonusDsx1AdmnEntry 23 }

sonusDsx1AdmnFarESThreshold OBJECT-TYPE
    SYNTAX          Integer32 (1..900)
    MAX-ACCESS      read-write
    STATUS          current
    DESCRIPTION     
            "Errored Seconds threshold value for 15 minute interval. This is for far end."
    DEFVAL          { 65 }
    ::= { sonusDsx1AdmnEntry 24 }

sonusDsx1AdmnFarSESThreshold OBJECT-TYPE
    SYNTAX          Integer32 (1..900)
    MAX-ACCESS      read-write
    STATUS          current
    DESCRIPTION     
            "Severely Errored Seconds threshold value for 15 minute interval. 
             This is for far end."
    DEFVAL          { 10 }
    ::= { sonusDsx1AdmnEntry 25 }

sonusDsx1AdmnFarDayESThreshold OBJECT-TYPE
    SYNTAX          Integer32 (1..65535)
    MAX-ACCESS      read-write
    STATUS          current
    DESCRIPTION     
            "Errored Seconds threshold value for a day. This is for far end."
    DEFVAL          { 648 }
    ::= { sonusDsx1AdmnEntry 26 }

sonusDsx1AdmnFarDaySESThreshold OBJECT-TYPE
    SYNTAX          Integer32 (1..65535)
    MAX-ACCESS      read-write
    STATUS          current
    DESCRIPTION     
            "Severely Errored Seconds threshold value for a day. This is for far end."
    DEFVAL          { 100 }
    ::= { sonusDsx1AdmnEntry 27 }

sonusDsx1AdmnPCVThreshold OBJECT-TYPE
    SYNTAX          Integer32 (1..16383)
    MAX-ACCESS      read-write
    STATUS          current
    DESCRIPTION     
            "Path Code Violations threshold value for 15 minute interval. This is for near end."
    DEFVAL          { 13296 }
    ::= { sonusDsx1AdmnEntry 28 }

sonusDsx1AdmnLCVThreshold OBJECT-TYPE
    SYNTAX          Integer32 (1..16383)
    MAX-ACCESS      read-write
    STATUS          current
    DESCRIPTION     
            "Line Code Violations threshold value for 15 minute interval. This is for near end."
    DEFVAL          { 13340 }
    ::= { sonusDsx1AdmnEntry 29 }

sonusDsx1AdmnUASThreshold OBJECT-TYPE
    SYNTAX          Integer32 (1..900)
    MAX-ACCESS      read-write
    STATUS          current
    DESCRIPTION     
            "Unavailable Seconds threshold value for 15 minute interval. This is for near end."
    DEFVAL          { 10 }
    ::= { sonusDsx1AdmnEntry 30 }

sonusDsx1AdmnFarPCVThreshold OBJECT-TYPE
    SYNTAX          Integer32 (1..16383)
    MAX-ACCESS      read-write
    STATUS          current
    DESCRIPTION     
            "Path Code Violations threshold value for 15 minute interval. This is for far end."
    DEFVAL          { 72 }
    ::= { sonusDsx1AdmnEntry 31 }

sonusDsx1AdmnFarLCVThreshold OBJECT-TYPE
    SYNTAX          Integer32 (1..16383)
    MAX-ACCESS      read-write
    STATUS          current
    DESCRIPTION     
            "Line Code Violations threshold value for 15 minute interval. This is for far end."
    DEFVAL          { 72 }
    ::= { sonusDsx1AdmnEntry 32 }

sonusDsx1AdmnFarUASThreshold OBJECT-TYPE
    SYNTAX          Integer32 (1..900)
    MAX-ACCESS      read-write
    STATUS          current
    DESCRIPTION     
            "Unavailable Seconds threshold value for 15 minute interval. This is for far end."
    DEFVAL          { 10 }
    ::= { sonusDsx1AdmnEntry 33 }

sonusDsx1AdmnDayPCVThreshold OBJECT-TYPE
    SYNTAX          Integer32 (1..1048575)
    MAX-ACCESS      read-write
    STATUS          current
    DESCRIPTION     
            "Path Code Violations threshold value for a day. This is for near end."
    DEFVAL          { 132960 }
    ::= { sonusDsx1AdmnEntry 34 }

sonusDsx1AdmnDayLCVThreshold OBJECT-TYPE
    SYNTAX          Integer32 (1..1048575)
    MAX-ACCESS      read-write
    STATUS          current
    DESCRIPTION     
            "Line Code Violations threshold value for a day. This is for near end."
    DEFVAL          { 133400 }
    ::= { sonusDsx1AdmnEntry 35 }

sonusDsx1AdmnDayUASThreshold OBJECT-TYPE
    SYNTAX          Integer32 (1..65535)
    MAX-ACCESS      read-write
    STATUS          current
    DESCRIPTION     
            "Unavailable Seconds threshold value for a day. This is for near end."
    DEFVAL          { 100 }
    ::= { sonusDsx1AdmnEntry 36 }

sonusDsx1AdmnFarDayPCVThreshold OBJECT-TYPE
    SYNTAX          Integer32 (1..1048575)
    MAX-ACCESS      read-write
    STATUS          current
    DESCRIPTION     
            "Path Code Violations threshold value for a day. This is for far end."
    DEFVAL          { 691 }
    ::= { sonusDsx1AdmnEntry 37 }

sonusDsx1AdmnFarDayLCVThreshold OBJECT-TYPE
    SYNTAX          Integer32 (1..1048575)
    MAX-ACCESS      read-write
    STATUS          current
    DESCRIPTION     
            "Line Code Violations threshold value for a day. This is for far end."
    DEFVAL          { 691 }
    ::= { sonusDsx1AdmnEntry 38 }

sonusDsx1AdmnFarDayUASThreshold OBJECT-TYPE
    SYNTAX          Integer32 (1..65535)
    MAX-ACCESS      read-write
    STATUS          current
    DESCRIPTION     
            "Unavailable Seconds threshold value for a day. This is for far end."
    DEFVAL          { 100 }
    ::= { sonusDsx1AdmnEntry 39 }

sonusDsx1AdmnInitCounters OBJECT-TYPE
    SYNTAX          SonusAdminState
    MAX-ACCESS      read-write
    STATUS          current
    DESCRIPTION     
            "Used to initialize all counters. Once enabled clears all T1/E1 counters."
    DEFVAL          { disabled }
    ::= { sonusDsx1AdmnEntry 40 }

sonusDsx1AdmnEchoProfileName OBJECT-TYPE
    SYNTAX          DisplayString (SIZE(1..23))
    MAX-ACCESS      read-write
    STATUS          current
    DESCRIPTION     
            "The name of the Echo Canceller profile applied to this T1/E1 Table"
    ::= { sonusDsx1AdmnEntry 41 }

sonusDsx1AdmnEchoCancellorMaxTail OBJECT-TYPE
    SYNTAX          INTEGER { millisec24(1), millisec32(2), 
                        millisec48(3), millisec64(4) }
    MAX-ACCESS      read-only
    STATUS          current
    DESCRIPTION     
            "Maximum Echo canceller tail length"
    DEFVAL          { millisec64 }
    ::= { sonusDsx1AdmnEntry 42 }

sonusDsx1AdmnEchoCancellorAudioType OBJECT-TYPE
    SYNTAX          INTEGER { uLaw(1), aLaw(2) }
    MAX-ACCESS      read-only
    STATUS          current
    DESCRIPTION     
            "Echo Canceller Audio encoding type A-law or U-law"
    DEFVAL          { uLaw }
    ::= { sonusDsx1AdmnEntry 43 }

sonusDsx1AdmnEchoCancellorSignallingTone OBJECT-TYPE
    SYNTAX          INTEGER { none(1), c5(2) }
    MAX-ACCESS      read-only
    STATUS          current
    DESCRIPTION     
            "Echo Cancellation: None, 2400, 2600 or 2101 Hz"
    DEFVAL          { none }
    ::= { sonusDsx1AdmnEntry 44 }

sonusDsx1AdmnEchoCancellorNlpDisable OBJECT-TYPE
    SYNTAX          Integer32 (0..16)
    MAX-ACCESS      read-only
    STATUS          current
    DESCRIPTION     
            "Echo Canceller Non-linear processing control, Disable"
    DEFVAL          { 6 }
    ::= { sonusDsx1AdmnEntry 45 }

sonusDsx1AdmnEchoCancellorNlpEnable OBJECT-TYPE
    SYNTAX          Integer32 (0..80)
    MAX-ACCESS      read-only
    STATUS          current
    DESCRIPTION     
            "Echo canceller Non-linear processing control, Enable"
    DEFVAL          { 75 }
    ::= { sonusDsx1AdmnEntry 46 }

sonusDsx1AdmnEchoCancellorReturnLoss OBJECT-TYPE
    SYNTAX          INTEGER { dB6(1), dB3(2), dB0(3) }
    MAX-ACCESS      read-only
    STATUS          current
    DESCRIPTION     
            "For Network Echo Cancellation, specifies the echo
             return loss in dB's. Default value is 6dB."
    DEFVAL          { dB6 }
    ::= { sonusDsx1AdmnEntry 47 }

sonusDsx1AdmnEchoCancellorResidualEcho OBJECT-TYPE
    SYNTAX          INTEGER { cancelOnly(1), suppressResidual(2), 
                        comfortNoise(4) }
    MAX-ACCESS      read-only
    STATUS          current
    DESCRIPTION     
            "For Network Echo Cancellation, specifies the residual echo
             cancellation."
    DEFVAL          { comfortNoise }
    ::= { sonusDsx1AdmnEntry 48 }

sonusDsx1AdmnEchoCancellorHiLevelComp OBJECT-TYPE
    SYNTAX          INTEGER { none(1), dB6(2) }
    MAX-ACCESS      read-only
    STATUS          current
    DESCRIPTION     
            "For Network Echo Cancellation, the high level compensation
             value. Default value is to attenuate by 6dB."
    DEFVAL          { dB6 }
    ::= { sonusDsx1AdmnEntry 49 }

sonusDsx1AdmnEchoCancellorModemDisable OBJECT-TYPE
    SYNTAX          INTEGER { ignore2100Hz(1), g164(2), g165(4) }
    MAX-ACCESS      read-only
    STATUS          current
    DESCRIPTION     
            "For Network Echo Cancellation, specifies whether to disable
             echo cancellation when a modem tone is detected."
    DEFVAL          { g165 }
    ::= { sonusDsx1AdmnEntry 50 }

sonusDsx1AdmnZeroSuppression OBJECT-TYPE
    SYNTAX          INTEGER { none(1), jamBit8(2), 
                        signalFrameOnlyJamBit8(3), gteZeroSuppression(4), 
                        bellZeroSuppression(5) }
    MAX-ACCESS      read-write
    STATUS          current
    DESCRIPTION     
            "T1 span zero suppression control."
    DEFVAL          { none }
    ::= { sonusDsx1AdmnEntry 51 }

sonusDsx1AdmnCircuitId OBJECT-TYPE
    SYNTAX          DisplayString (SIZE(1..23))
    MAX-ACCESS      read-write
    STATUS          current
    DESCRIPTION     
            "The Circuit Id."
    ::= { sonusDsx1AdmnEntry 52 }

sonusDsx1AdmnEchoCancellorNarrowbandDetection OBJECT-TYPE
    SYNTAX          INTEGER { off(1), on(2) }
    MAX-ACCESS      read-only
    STATUS          current
    DESCRIPTION     
            "For Network Echo Cancellation, narrow band detection is OFF or ON. If set ON
             it narrows the G.164 detection bandwidth in G.165 mode to the G.165 band."
    DEFVAL          { off }
    ::= { sonusDsx1AdmnEntry 53 }

sonusDsx1StatTable OBJECT-TYPE
    SYNTAX          SEQUENCE OF SonusDsx1StatEntry
    MAX-ACCESS      not-accessible
    STATUS          current
    DESCRIPTION     
            "Table of Sonus Enterprise Status for all DS1s"
    ::= { sonusDsx1MIBObjects 2 }

sonusDsx1StatEntry OBJECT-TYPE
    SYNTAX          SonusDsx1StatEntry
    MAX-ACCESS      not-accessible
    STATUS          current
    DESCRIPTION     
            "Entry in Table consisting of the all the Sonus Enterprise DS1 Status"
    INDEX           { sonusDsx1StatShelfIndex, sonusDsx1StatSlotIndex, 
                      sonusDsx1StatPortIndex, sonusDsx1StatDs3Index, 
                      sonusDsx1StatDs1Index }
    ::= { sonusDsx1StatTable 1 }

SonusDsx1StatEntry ::=
    SEQUENCE {
        sonusDsx1StatShelfIndex         Integer32,
        sonusDsx1StatSlotIndex          Integer32,
        sonusDsx1StatPortIndex          Integer32,
        sonusDsx1StatDs3Index           Integer32,
        sonusDsx1StatDs1Index           Integer32,
        sonusDsx1StatValidInt           Integer32,
        sonusDsx1StatRxSlips            Integer32,
        sonusDsx1StatTxSlips            Integer32,
        sonusDsx1StatLOF                Integer32,
        sonusDsx1StatAIS                Integer32,
        sonusDsx1StatRAI                Integer32,
        sonusDsx1StatRED                Integer32,
        sonusDsx1StatCRC                Integer32,
        sonusDsx1StatCOFA               Integer32,
        sonusDsx1StatFBE                Integer32,
        sonusDsx1StatStatus             DisplayString,
        sonusDsx1StatAllocChannels      DisplayString,
        sonusDsx1StatEnabChannels       DisplayString,
        sonusE1StatLOMF                 Integer32,
        sonusE1StatMFError              Integer32,
        sonusE1StatFEBE                 Integer32,
        sonusE1StatOOOF                 Integer32,
        sonusE1StatC2NCIWCK             Integer32,
        sonusE1StatRAIContCRC           Integer32,
        sonusE1StatContFEBE             Integer32,
        sonusE1StatExcessCRC            Integer32,
        sonusE1StatFASErr               Integer32,
        sonusDsx1StatSendPattern        INTEGER,
        sonusDsx1StatStatusCode         INTEGER,
        sonusDsx1StatLoopbackStatus     INTEGER,
        sonusDsx1StatOperStatus         INTEGER
    }

sonusDsx1StatShelfIndex OBJECT-TYPE
    SYNTAX          Integer32
    MAX-ACCESS      read-only
    STATUS          current
    DESCRIPTION     
            "Shelf index into this table"
    ::= { sonusDsx1StatEntry 1 }

sonusDsx1StatSlotIndex OBJECT-TYPE
    SYNTAX          Integer32
    MAX-ACCESS      read-only
    STATUS          current
    DESCRIPTION     
            "Slot index into this table"
    ::= { sonusDsx1StatEntry 2 }

sonusDsx1StatPortIndex OBJECT-TYPE
    SYNTAX          Integer32
    MAX-ACCESS      read-only
    STATUS          current
    DESCRIPTION     
            "Port Index into this table"
    ::= { sonusDsx1StatEntry 3 }

sonusDsx1StatDs3Index OBJECT-TYPE
    SYNTAX          Integer32
    MAX-ACCESS      read-only
    STATUS          current
    DESCRIPTION     
            "Ds3 Index into this table"
    ::= { sonusDsx1StatEntry 4 }

sonusDsx1StatDs1Index OBJECT-TYPE
    SYNTAX          Integer32
    MAX-ACCESS      read-only
    STATUS          current
    DESCRIPTION     
            "Ds1 Index into this table"
    ::= { sonusDsx1StatEntry 5 }

sonusDsx1StatValidInt OBJECT-TYPE
    SYNTAX          Integer32
    MAX-ACCESS      read-only
    STATUS          current
    DESCRIPTION     
            "Number of valid intervals of Performance Monitoring"
    ::= { sonusDsx1StatEntry 6 }

sonusDsx1StatRxSlips OBJECT-TYPE
    SYNTAX          Integer32
    MAX-ACCESS      read-only
    STATUS          current
    DESCRIPTION     
            "Number of frame slips in the receive direction."
    ::= { sonusDsx1StatEntry 7 }

sonusDsx1StatTxSlips OBJECT-TYPE
    SYNTAX          Integer32
    MAX-ACCESS      read-only
    STATUS          current
    DESCRIPTION     
            "Number of frame slips in the transmit direction."
    ::= { sonusDsx1StatEntry 8 }

sonusDsx1StatLOF OBJECT-TYPE
    SYNTAX          Integer32
    MAX-ACCESS      read-only
    STATUS          current
    DESCRIPTION     
            "Number of Loss of Frame defects that have occured."
    ::= { sonusDsx1StatEntry 9 }

sonusDsx1StatAIS OBJECT-TYPE
    SYNTAX          Integer32
    MAX-ACCESS      read-only
    STATUS          current
    DESCRIPTION     
            "Number of AIS alarms that have occured."
    ::= { sonusDsx1StatEntry 10 }

sonusDsx1StatRAI OBJECT-TYPE
    SYNTAX          Integer32
    MAX-ACCESS      read-only
    STATUS          current
    DESCRIPTION     
            "Number of RAI alarms that have occured."
    ::= { sonusDsx1StatEntry 11 }

sonusDsx1StatRED OBJECT-TYPE
    SYNTAX          Integer32
    MAX-ACCESS      read-only
    STATUS          current
    DESCRIPTION     
            "Number of RED alarms that have occured."
    ::= { sonusDsx1StatEntry 12 }

sonusDsx1StatCRC OBJECT-TYPE
    SYNTAX          Integer32
    MAX-ACCESS      read-only
    STATUS          current
    DESCRIPTION     
            "Number T1 CRC framing errors that have occured."
    ::= { sonusDsx1StatEntry 13 }

sonusDsx1StatCOFA OBJECT-TYPE
    SYNTAX          Integer32
    MAX-ACCESS      read-only
    STATUS          current
    DESCRIPTION     
            "Number of Change of Frame Alignments that have occured."
    ::= { sonusDsx1StatEntry 14 }

sonusDsx1StatFBE OBJECT-TYPE
    SYNTAX          Integer32
    MAX-ACCESS      read-only
    STATUS          current
    DESCRIPTION     
            "Number framing bit errors that have occured."
    ::= { sonusDsx1StatEntry 15 }

sonusDsx1StatStatus OBJECT-TYPE
    SYNTAX          DisplayString
    MAX-ACCESS      read-only
    STATUS          deprecated
    DESCRIPTION     
            "T1/E1 span status. Indicates if port in alarm state, loopback state etc."
    ::= { sonusDsx1StatEntry 16 }

sonusDsx1StatAllocChannels OBJECT-TYPE
    SYNTAX          DisplayString
    MAX-ACCESS      read-only
    STATUS          current
    DESCRIPTION     
            "String display showing bitmap of channels that are currently allocated.
             A 1 indicates that the channel is allocated."
    ::= { sonusDsx1StatEntry 17 }

sonusDsx1StatEnabChannels OBJECT-TYPE
    SYNTAX          DisplayString
    MAX-ACCESS      read-only
    STATUS          current
    DESCRIPTION     
            "String display showing bitmap of channels that are currently enabled
             A 1 indicates that the channel is allocated."
    ::= { sonusDsx1StatEntry 18 }

sonusE1StatLOMF OBJECT-TYPE
    SYNTAX          Integer32
    MAX-ACCESS      read-only
    STATUS          current
    DESCRIPTION     
            "Number of Loss of Multiframe alignments that have occured."
    ::= { sonusDsx1StatEntry 19 }

sonusE1StatMFError OBJECT-TYPE
    SYNTAX          Integer32
    MAX-ACCESS      read-only
    STATUS          current
    DESCRIPTION     
            "Number of Multiframe CRC errors that have occured."
    ::= { sonusDsx1StatEntry 20 }

sonusE1StatFEBE OBJECT-TYPE
    SYNTAX          Integer32
    MAX-ACCESS      read-only
    STATUS          current
    DESCRIPTION     
            "Number of Far End Block errors that have occured."
    ::= { sonusDsx1StatEntry 21 }

sonusE1StatOOOF OBJECT-TYPE
    SYNTAX          Integer32
    MAX-ACCESS      read-only
    STATUS          current
    DESCRIPTION     
            "Number of Out of ofline framer errors that have occured."
    ::= { sonusDsx1StatEntry 22 }

sonusE1StatC2NCIWCK OBJECT-TYPE
    SYNTAX          Integer32
    MAX-ACCESS      read-only
    STATUS          current
    DESCRIPTION     
            "Number of CRC 2 Non CRC framing events that have occured."
    ::= { sonusDsx1StatEntry 23 }

sonusE1StatRAIContCRC OBJECT-TYPE
    SYNTAX          Integer32
    MAX-ACCESS      read-only
    STATUS          current
    DESCRIPTION     
            "Number of RAI and Continuous CRC errors that have occured."
    ::= { sonusDsx1StatEntry 24 }

sonusE1StatContFEBE OBJECT-TYPE
    SYNTAX          Integer32
    MAX-ACCESS      read-only
    STATUS          current
    DESCRIPTION     
            "Number of Continuous FEBE errors that have occured."
    ::= { sonusDsx1StatEntry 25 }

sonusE1StatExcessCRC OBJECT-TYPE
    SYNTAX          Integer32
    MAX-ACCESS      read-only
    STATUS          current
    DESCRIPTION     
            "Number of Excessive CRC errors that have occured."
    ::= { sonusDsx1StatEntry 26 }

sonusE1StatFASErr OBJECT-TYPE
    SYNTAX          Integer32
    MAX-ACCESS      read-only
    STATUS          current
    DESCRIPTION     
            "Number of Frame Alignment Sequence Errors."
    ::= { sonusDsx1StatEntry 27 }

sonusDsx1StatSendPattern OBJECT-TYPE
    SYNTAX          INTEGER { dsx1SendNoCode(1), dsx1SendLineCode(2), 
                        dsx1SendPayloadCode(3), dsx1SendResetCode(4), 
                        dsx1SendQRS(5), dsx1Send511Pattern(6), 
                        dsx1Send3in24Pattern(7), 
                        dsx1SendOtherTestPattern(8) }
    MAX-ACCESS      read-only
    STATUS          current
    DESCRIPTION     
            "Indicates status of SendCode variable for PATTERNS ONLY
             - does not include SendCodes that require loopback."
    DEFVAL          { dsx1SendNoCode }
    ::= { sonusDsx1StatEntry 28 }

sonusDsx1StatStatusCode OBJECT-TYPE
    SYNTAX          INTEGER { dsx1StatStatusCodeNoAlarm(1), 
                        dsx1StatStatusCodeRedAlarm(2), 
                        dsx1StatStatusCodeYellowAlarm(3), 
                        dsx1StatStatusCodeAisAlarm(4), 
                        dsx1StatStatusCodeDspFailure(5), 
                        dsx1StatStatusCodeLoopback(6) }
    MAX-ACCESS      read-only
    STATUS          current
    DESCRIPTION     
            "T1/E1 span status. Indicates if port in alarm state, loopback state etc. Integer version of 
             sonusDsx1StatStatus variable."
    DEFVAL          { dsx1StatStatusCodeNoAlarm }
    ::= { sonusDsx1StatEntry 29 }

sonusDsx1StatLoopbackStatus OBJECT-TYPE
    SYNTAX          INTEGER { dsx1StatLoopbackStatusNoLoopback(1), 
                        dsx1StatLoopbackStatusNeLineLoopback(2), 
                        dsx1StatLoopbackStatusNePayloadLoopback(3), 
                        dsx1StatLoopbackStatusNeInwardLoopback(4), 
                        dsx1StatLoopbackStatusNeDualLoopback(5), 
                        dsx1StatLoopbackStatusFeLineLoopback(6), 
                        dsx1StatLoopbackStatusFePayloadLoopback(7) }
    MAX-ACCESS      read-only
    STATUS          current
    DESCRIPTION     
            "T1 loopback status display. Indicates loopback STATUS of T1 port."
    DEFVAL          { dsx1StatLoopbackStatusNoLoopback }
    ::= { sonusDsx1StatEntry 30 }

sonusDsx1StatOperStatus OBJECT-TYPE
    SYNTAX          INTEGER { up(1), down(2), dryingUp(3) }
    MAX-ACCESS      read-only
    STATUS          current
    DESCRIPTION     
            "The actual status of the DS1 interface. Interface is 
             Up if it is administratively in service and there are no
             line failures or hardware failures. Interface is Down if
             it is administratively in service and there are line
             failures or hardware failures, or if it is administratively
             out of service. Interface is DryingUp if it is administratively
             out of service and is drying up (no new	calls, still carrying
             in-progress calls)."
    ::= { sonusDsx1StatEntry 31 }

sonusDs0AdmnTable OBJECT-TYPE
    SYNTAX          SEQUENCE OF SonusDs0AdmnEntry
    MAX-ACCESS      not-accessible
    STATUS          current
    DESCRIPTION     
            "Table of Sonus Enterprise Configuration for DS0s"
    ::= { sonusDsx1MIBObjects 3 }

sonusDs0AdmnEntry OBJECT-TYPE
    SYNTAX          SonusDs0AdmnEntry
    MAX-ACCESS      not-accessible
    STATUS          current
    DESCRIPTION     
            "Entry in Table consisting of the all the Sonus Enterprise Ds0 Configuration"
    INDEX           { sonusDs0AdmnShelfIndex, sonusDs0AdmnSlotIndex, 
                      sonusDs0AdmnPortIndex, sonusDs0AdmnDs3Index, 
                      sonusDs0AdmnDs1Index, sonusDs0AdmnDs0Index }
    ::= { sonusDs0AdmnTable 1 }

SonusDs0AdmnEntry ::=
    SEQUENCE {
        sonusDs0AdmnShelfIndex          Integer32,
        sonusDs0AdmnSlotIndex           Integer32,
        sonusDs0AdmnPortIndex           Integer32,
        sonusDs0AdmnDs3Index            Integer32,
        sonusDs0AdmnDs1Index            Integer32,
        sonusDs0AdmnDs0Index            Integer32,
        sonusDs0AdmnTimeout             Integer32,
        sonusDs0AdmnMode                SonusServiceState,
        sonusDs0AdmnAction              SonusAdminAction,
        sonusDs0AdmnState               INTEGER,
        sonusDs0AdmnIdleCode            Integer32,
        sonusDs0AdmnTone                INTEGER,
        sonusDs0AdmnLoopback            INTEGER
    }

sonusDs0AdmnShelfIndex OBJECT-TYPE
    SYNTAX          Integer32
    MAX-ACCESS      read-only
    STATUS          current
    DESCRIPTION     
            "Shelf Index for this table"
    ::= { sonusDs0AdmnEntry 1 }

sonusDs0AdmnSlotIndex OBJECT-TYPE
    SYNTAX          Integer32
    MAX-ACCESS      read-only
    STATUS          current
    DESCRIPTION     
            "Slot index for this table"
    ::= { sonusDs0AdmnEntry 2 }

sonusDs0AdmnPortIndex OBJECT-TYPE
    SYNTAX          Integer32
    MAX-ACCESS      read-only
    STATUS          current
    DESCRIPTION     
            "Port Index into this table"
    ::= { sonusDs0AdmnEntry 3 }

sonusDs0AdmnDs3Index OBJECT-TYPE
    SYNTAX          Integer32
    MAX-ACCESS      read-only
    STATUS          current
    DESCRIPTION     
            "Ds3 Index into this table"
    ::= { sonusDs0AdmnEntry 4 }

sonusDs0AdmnDs1Index OBJECT-TYPE
    SYNTAX          Integer32
    MAX-ACCESS      read-only
    STATUS          current
    DESCRIPTION     
            "DS1 index for this table"
    ::= { sonusDs0AdmnEntry 5 }

sonusDs0AdmnDs0Index OBJECT-TYPE
    SYNTAX          Integer32
    MAX-ACCESS      read-only
    STATUS          current
    DESCRIPTION     
            "DS0 index for this table"
    ::= { sonusDs0AdmnEntry 6 }

sonusDs0AdmnTimeout OBJECT-TYPE
    SYNTAX          Integer32 (0..1440)
    MAX-ACCESS      read-write
    STATUS          current
    DESCRIPTION     
            "Max time in minutes before channel dryup takes place"
    DEFVAL          { 5 }
    ::= { sonusDs0AdmnEntry 7 }

sonusDs0AdmnMode OBJECT-TYPE
    SYNTAX          SonusServiceState
    MAX-ACCESS      read-write
    STATUS          current
    DESCRIPTION     
            "Channel is in service or out of service."
    DEFVAL          { inService }
    ::= { sonusDs0AdmnEntry 8 }

sonusDs0AdmnAction OBJECT-TYPE
    SYNTAX          SonusAdminAction
    MAX-ACCESS      read-write
    STATUS          current
    DESCRIPTION     
            "Force out of service or wait for dryup"
    DEFVAL          { dryUp }
    ::= { sonusDs0AdmnEntry 9 }

sonusDs0AdmnState OBJECT-TYPE
    SYNTAX          INTEGER { unavailable(1), available(2) }
    MAX-ACCESS      read-write
    STATUS          current
    DESCRIPTION     
            "Channel state, available/unavailable"
    DEFVAL          { available }
    ::= { sonusDs0AdmnEntry 10 }

sonusDs0AdmnIdleCode OBJECT-TYPE
    SYNTAX          Integer32 (0..255)
    MAX-ACCESS      read-write
    STATUS          current
    DESCRIPTION     
            "Channel Idle Code pattern"
    DEFVAL          { 127 }
    ::= { sonusDs0AdmnEntry 11 }

sonusDs0AdmnTone OBJECT-TYPE
    SYNTAX          INTEGER { none(1), dmw(2) }
    MAX-ACCESS      read-write
    STATUS          current
    DESCRIPTION     
            "Insert different tones into channel. Digital milliwatt"
    DEFVAL          { none }
    ::= { sonusDs0AdmnEntry 12 }

sonusDs0AdmnLoopback OBJECT-TYPE
    SYNTAX          INTEGER { disabled(1), enabled(2) }
    MAX-ACCESS      read-write
    STATUS          current
    DESCRIPTION     
            "Put channel in loopback"
    DEFVAL          { disabled }
    ::= { sonusDs0AdmnEntry 13 }

sonusDs1Profile OBJECT IDENTIFIER
    ::= { sonusDsx1MIBObjects 4 }

sonusDs1ProfileNextIndex OBJECT-TYPE
    SYNTAX          Integer32
    MAX-ACCESS      read-only
    STATUS          current
    DESCRIPTION     
            "The next valid index to use when creating an entry in
             the sonusDs1ProfileTable."
    ::= { sonusDs1Profile 1 }

sonusDs1ProfileTable OBJECT-TYPE
    SYNTAX          SEQUENCE OF SonusDs1ProfileEntry
    MAX-ACCESS      not-accessible
    STATUS          current
    DESCRIPTION     
            "Table for T1/E1 profile"
    ::= { sonusDs1Profile 2 }

sonusDs1ProfileEntry OBJECT-TYPE
    SYNTAX          SonusDs1ProfileEntry
    MAX-ACCESS      not-accessible
    STATUS          current
    DESCRIPTION     
            "Entry in Table consisting of T1/E1 profile. The T1/E1 profiles
             have to be created by users and then configured. These profiles
             can then be applied onto any T1/E1 span."
    INDEX           { sonusDs1ProfileIndex }
    ::= { sonusDs1ProfileTable 1 }

SonusDs1ProfileEntry ::=
    SEQUENCE {
        sonusDs1ProfileRowStatus        RowStatus,
        sonusDs1ProfileName             SonusName,
        sonusDs1ProfileIndex            Integer32,
        sonusDs1ProfileState            SonusAdminState,
        sonusDs1ProfileDs1LineBO        INTEGER,
        sonusDs1ProfileDs1LineType      INTEGER,
        sonusDs1ProfileDs1LineCoding    INTEGER,
        sonusDs1ProfileDs1SignalMode    INTEGER,
        sonusDs1ProfileDs1Fdl           INTEGER,
        sonusDs1ProfileDs0IdleCode      Integer32,
        sonusDs1ProfileAvailChannels    BITS,
        sonusDs1ProfileDs1LineBOState   SonusAdminState,
        sonusDs1ProfileDs1LineTypeState SonusAdminState,
        sonusDs1ProfileDs1LineCodingState SonusAdminState,
        sonusDs1ProfileDs1SignalModeState SonusAdminState,
        sonusDs1ProfileDs1FdlState      SonusAdminState,
        sonusDs1ProfileDs0IdleCodeState SonusAdminState,
        sonusDs1ProfileAvailChannelsState SonusAdminState,
        sonusDs1ProfileType             INTEGER,
        sonusDs1ProfileESThreshold      Integer32,
        sonusDs1ProfileSESThreshold     Integer32,
        sonusDs1ProfileCSSThreshold     Integer32,
        sonusDs1ProfileDayESThreshold   Integer32,
        sonusDs1ProfileDaySESThreshold  Integer32,
        sonusDs1ProfileDayCSSThreshold  Integer32,
        sonusDs1ProfileFarESThreshold   Integer32,
        sonusDs1ProfileFarSESThreshold  Integer32,
        sonusDs1ProfileFarDayESThreshold Integer32,
        sonusDs1ProfileFarDaySESThreshold Integer32,
        sonusDs1ProfilePCVThreshold     Integer32,
        sonusDs1ProfileLCVThreshold     Integer32,
        sonusDs1ProfileUASThreshold     Integer32,
        sonusDs1ProfileFarPCVThreshold  Integer32,
        sonusDs1ProfileFarLCVThreshold  Integer32,
        sonusDs1ProfileFarUASThreshold  Integer32,
        sonusDs1ProfileDayPCVThreshold  Integer32,
        sonusDs1ProfileDayLCVThreshold  Integer32,
        sonusDs1ProfileDayUASThreshold  Integer32,
        sonusDs1ProfileFarDayPCVThreshold Integer32,
        sonusDs1ProfileFarDayLCVThreshold Integer32,
        sonusDs1ProfileFarDayUASThreshold Integer32,
        sonusDs1ProfileESThresholdState SonusAdminState,
        sonusDs1ProfileSESThresholdState SonusAdminState,
        sonusDs1ProfileCSSThresholdState SonusAdminState,
        sonusDs1ProfileDayESThresholdState  SonusAdminState,
        sonusDs1ProfileDaySESThresholdState   SonusAdminState,
        sonusDs1ProfileDayCSSThresholdState   SonusAdminState,
        sonusDs1ProfileFarESThresholdState  SonusAdminState,
        sonusDs1ProfileFarSESThresholdState   SonusAdminState,
        sonusDs1ProfileFarDayESThresholdState     SonusAdminState,
        sonusDs1ProfileFarDaySESThresholdState      SonusAdminState,
        sonusDs1ProfilePCVThresholdState SonusAdminState,
        sonusDs1ProfileLCVThresholdState SonusAdminState,
        sonusDs1ProfileUASThresholdState SonusAdminState,
        sonusDs1ProfileFarPCVThresholdState   SonusAdminState,
        sonusDs1ProfileFarLCVThresholdState   SonusAdminState,
        sonusDs1ProfileFarUASThresholdState   SonusAdminState,
        sonusDs1ProfileDayPCVThresholdState   SonusAdminState,
        sonusDs1ProfileDayLCVThresholdState   SonusAdminState,
        sonusDs1ProfileDayUASThresholdState   SonusAdminState,
        sonusDs1ProfileFarDayPCVThresholdState      SonusAdminState,
        sonusDs1ProfileFarDayLCVThresholdState      SonusAdminState,
        sonusDs1ProfileFarDayUASThresholdState      SonusAdminState
    }

sonusDs1ProfileRowStatus OBJECT-TYPE
    SYNTAX          RowStatus
    MAX-ACCESS      read-write
    STATUS          current
    DESCRIPTION     
            "Profile: Row Status Needed for SNMP"
    ::= { sonusDs1ProfileEntry 1 }

sonusDs1ProfileName OBJECT-TYPE
    SYNTAX          SonusName
    MAX-ACCESS      read-write
    STATUS          current
    DESCRIPTION     
            "Name of this Profile"
    ::= { sonusDs1ProfileEntry 2 }

sonusDs1ProfileIndex OBJECT-TYPE
    SYNTAX          Integer32
    MAX-ACCESS      read-only
    STATUS          current
    DESCRIPTION     
            "Index into the profile table"
    ::= { sonusDs1ProfileEntry 3 }

sonusDs1ProfileState OBJECT-TYPE
    SYNTAX          SonusAdminState
    MAX-ACCESS      read-write
    STATUS          current
    DESCRIPTION     
            "Profile: State"
    DEFVAL          { disabled }
    ::= { sonusDs1ProfileEntry 4 }

sonusDs1ProfileDs1LineBO OBJECT-TYPE
    SYNTAX          INTEGER { buildOut0to110(1), buildOut110to220(2), 
                        buildOut220to330(3), buildOut330to440(4), 
                        buildOut440to550(5), buildOut550to660(6), 
                        buildOut120Ohms(7), buildOut75Ohms(8) }
    MAX-ACCESS      read-write
    STATUS          current
    DESCRIPTION     
            "Profile: DS1 Line build out"
    DEFVAL          { buildOut110to220 }
    ::= { sonusDs1ProfileEntry 5 }

sonusDs1ProfileDs1LineType OBJECT-TYPE
    SYNTAX          INTEGER { esf(2), d4(3), e1(4), e1crc(5) }
    MAX-ACCESS      read-write
    STATUS          current
    DESCRIPTION     
            "Profile: T1/E1 Line type"
    DEFVAL          { esf }
    ::= { sonusDs1ProfileEntry 6 }

sonusDs1ProfileDs1LineCoding OBJECT-TYPE
    SYNTAX          INTEGER { b8zs(2), hdb3(3), ami(5) }
    MAX-ACCESS      read-write
    STATUS          current
    DESCRIPTION     
            "Profile: T1/E1 Line Coding, B8ZS, AMI, HDB3"
    DEFVAL          { b8zs }
    ::= { sonusDs1ProfileEntry 7 }

sonusDs1ProfileDs1SignalMode OBJECT-TYPE
    SYNTAX          INTEGER { none(1) }
    MAX-ACCESS      read-write
    STATUS          current
    DESCRIPTION     
            "Profile: T1/E1 Signalling, Robbed Bit or None"
    DEFVAL          { none }
    ::= { sonusDs1ProfileEntry 8 }

sonusDs1ProfileDs1Fdl OBJECT-TYPE
    SYNTAX          INTEGER { ansi(2), none(8) }
    MAX-ACCESS      read-write
    STATUS          current
    DESCRIPTION     
            "Profile: T1 Facilities Data Link type"
    DEFVAL          { ansi }
    ::= { sonusDs1ProfileEntry 9 }

sonusDs1ProfileDs0IdleCode OBJECT-TYPE
    SYNTAX          Integer32 (0..255)
    MAX-ACCESS      read-write
    STATUS          current
    DESCRIPTION     
            "Profile: Idle code to be used on all channels in this T1/E1 span"
    DEFVAL          { 127 }
    ::= { sonusDs1ProfileEntry 10 }

sonusDs1ProfileAvailChannels OBJECT-TYPE
    SYNTAX          BITS { channel1(0), channel2(1), channel3(2), 
                        channel4(3), channel5(4), channel6(5), 
                        channel7(6), channel8(7), channel9(8), 
                        channel10(9), channel11(10), channel12(11), 
                        channel13(12), channel14(13), channel15(14), 
                        channel16(15), channel17(16), channel18(17), 
                        channel19(18), channel20(19), channel21(20), 
                        channel22(21), channel23(22), channel24(23), 
                        channel25(24), channel26(25), channel27(26), 
                        channel28(27), channel29(28), channel30(29), 
                        channel31(30) }
    MAX-ACCESS      read-write
    STATUS          current
    DESCRIPTION     
            "Bitstring map of channels that are available on this T1/E1."
    ::= { sonusDs1ProfileEntry 11 }

sonusDs1ProfileDs1LineBOState OBJECT-TYPE
    SYNTAX          SonusAdminState
    MAX-ACCESS      read-write
    STATUS          current
    DESCRIPTION     
            "Profile: Line Build Out State, used by profile code"
    DEFVAL          { enabled }
    ::= { sonusDs1ProfileEntry 12 }

sonusDs1ProfileDs1LineTypeState OBJECT-TYPE
    SYNTAX          SonusAdminState
    MAX-ACCESS      read-write
    STATUS          current
    DESCRIPTION     
            "Profile: T1/E1 Line type State, used by profile code"
    DEFVAL          { enabled }
    ::= { sonusDs1ProfileEntry 13 }

sonusDs1ProfileDs1LineCodingState OBJECT-TYPE
    SYNTAX          SonusAdminState
    MAX-ACCESS      read-write
    STATUS          current
    DESCRIPTION     
            "Profile: T1/E1 Line coding State, used by profile code"
    DEFVAL          { enabled }
    ::= { sonusDs1ProfileEntry 14 }

sonusDs1ProfileDs1SignalModeState OBJECT-TYPE
    SYNTAX          SonusAdminState
    MAX-ACCESS      read-write
    STATUS          current
    DESCRIPTION     
            "Profile: T1/E1 Signal Mode state, used by profile code"
    DEFVAL          { enabled }
    ::= { sonusDs1ProfileEntry 15 }

sonusDs1ProfileDs1FdlState OBJECT-TYPE
    SYNTAX          SonusAdminState
    MAX-ACCESS      read-write
    STATUS          current
    DESCRIPTION     
            "Profile: T1/E1 FDL State, used by profile code"
    DEFVAL          { enabled }
    ::= { sonusDs1ProfileEntry 16 }

sonusDs1ProfileDs0IdleCodeState OBJECT-TYPE
    SYNTAX          SonusAdminState
    MAX-ACCESS      read-write
    STATUS          current
    DESCRIPTION     
            "Profile: Channel Idle Code State, used by profile"
    DEFVAL          { enabled }
    ::= { sonusDs1ProfileEntry 17 }

sonusDs1ProfileAvailChannelsState OBJECT-TYPE
    SYNTAX          SonusAdminState
    MAX-ACCESS      read-write
    STATUS          current
    DESCRIPTION     
            "Profile: Available channel state, disabled/enabled"
    DEFVAL          { enabled }
    ::= { sonusDs1ProfileEntry 18 }

sonusDs1ProfileType OBJECT-TYPE
    SYNTAX          INTEGER { t1(1), e1(2) }
    MAX-ACCESS      read-write
    STATUS          current
    DESCRIPTION     
            "Type of DSx1. Indicates whether this span is a T1 span or E1 span."
    DEFVAL          { t1 }
    ::= { sonusDs1ProfileEntry 19 }

sonusDs1ProfileESThreshold OBJECT-TYPE
    SYNTAX          Integer32 (1..900)
    MAX-ACCESS      read-write
    STATUS          current
    DESCRIPTION     
            "Errored Seconds threshold value for 15 minute interval. This is for near end."
    DEFVAL          { 65 }
    ::= { sonusDs1ProfileEntry 20 }

sonusDs1ProfileSESThreshold OBJECT-TYPE
    SYNTAX          Integer32 (1..900)
    MAX-ACCESS      read-write
    STATUS          current
    DESCRIPTION     
            "Severely Errored Seconds threshold value for 15 minute interval. 
             This is for near end."
    DEFVAL          { 10 }
    ::= { sonusDs1ProfileEntry 21 }

sonusDs1ProfileCSSThreshold OBJECT-TYPE
    SYNTAX          Integer32 (1..900)
    MAX-ACCESS      read-write
    STATUS          current
    DESCRIPTION     
            "Severely Errored Seconds threshold value for 15 minute interval. 
             This is for near end."
    DEFVAL          { 1 }
    ::= { sonusDs1ProfileEntry 22 }

sonusDs1ProfileDayESThreshold OBJECT-TYPE
    SYNTAX          Integer32 (1..65535)
    MAX-ACCESS      read-write
    STATUS          current
    DESCRIPTION     
            "Errored Seconds threshold value for a day. This is for near end."
    DEFVAL          { 648 }
    ::= { sonusDs1ProfileEntry 23 }

sonusDs1ProfileDaySESThreshold OBJECT-TYPE
    SYNTAX          Integer32 (1..65535)
    MAX-ACCESS      read-write
    STATUS          current
    DESCRIPTION     
            "Severely Errored Seconds threshold value for a day. This is for near end."
    DEFVAL          { 100 }
    ::= { sonusDs1ProfileEntry 24 }

sonusDs1ProfileDayCSSThreshold OBJECT-TYPE
    SYNTAX          Integer32 (1..65535)
    MAX-ACCESS      read-write
    STATUS          current
    DESCRIPTION     
            "Severely Errored Seconds threshold value for a day. This is for near end."
    DEFVAL          { 4 }
    ::= { sonusDs1ProfileEntry 25 }

sonusDs1ProfileFarESThreshold OBJECT-TYPE
    SYNTAX          Integer32 (1..900)
    MAX-ACCESS      read-write
    STATUS          current
    DESCRIPTION     
            "Errored Seconds threshold value for 15 minute interval. This is for far end."
    DEFVAL          { 65 }
    ::= { sonusDs1ProfileEntry 26 }

sonusDs1ProfileFarSESThreshold OBJECT-TYPE
    SYNTAX          Integer32 (1..900)
    MAX-ACCESS      read-write
    STATUS          current
    DESCRIPTION     
            "Severely Errored Seconds threshold value for 15 minute interval. 
             This is for far end."
    DEFVAL          { 10 }
    ::= { sonusDs1ProfileEntry 27 }

sonusDs1ProfileFarDayESThreshold OBJECT-TYPE
    SYNTAX          Integer32 (1..65535)
    MAX-ACCESS      read-write
    STATUS          current
    DESCRIPTION     
            "Errored Seconds threshold value for a day. This is for far end."
    DEFVAL          { 648 }
    ::= { sonusDs1ProfileEntry 28 }

sonusDs1ProfileFarDaySESThreshold OBJECT-TYPE
    SYNTAX          Integer32 (1..65535)
    MAX-ACCESS      read-write
    STATUS          current
    DESCRIPTION     
            "Severely Errored Seconds threshold value for a day. This is for far end."
    DEFVAL          { 100 }
    ::= { sonusDs1ProfileEntry 29 }

sonusDs1ProfilePCVThreshold OBJECT-TYPE
    SYNTAX          Integer32 (1..16383)
    MAX-ACCESS      read-write
    STATUS          current
    DESCRIPTION     
            "Path Code Violations threshold value for 15 minute interval. This is for near end."
    DEFVAL          { 13296 }
    ::= { sonusDs1ProfileEntry 30 }

sonusDs1ProfileLCVThreshold OBJECT-TYPE
    SYNTAX          Integer32 (1..16383)
    MAX-ACCESS      read-write
    STATUS          current
    DESCRIPTION     
            "Line Code Violations threshold value for 15 minute interval. This is for near end."
    DEFVAL          { 13340 }
    ::= { sonusDs1ProfileEntry 31 }

sonusDs1ProfileUASThreshold OBJECT-TYPE
    SYNTAX          Integer32 (1..900)
    MAX-ACCESS      read-write
    STATUS          current
    DESCRIPTION     
            "Unavailable Seconds threshold value for 15 minute interval. This is for near end."
    DEFVAL          { 10 }
    ::= { sonusDs1ProfileEntry 32 }

sonusDs1ProfileFarPCVThreshold OBJECT-TYPE
    SYNTAX          Integer32 (1..16383)
    MAX-ACCESS      read-write
    STATUS          current
    DESCRIPTION     
            "Path Code Violations threshold value for 15 minute interval. This is for far end."
    DEFVAL          { 72 }
    ::= { sonusDs1ProfileEntry 33 }

sonusDs1ProfileFarLCVThreshold OBJECT-TYPE
    SYNTAX          Integer32 (1..16383)
    MAX-ACCESS      read-write
    STATUS          current
    DESCRIPTION     
            "Line Code Violations threshold value for 15 minute interval. This is for far end."
    DEFVAL          { 72 }
    ::= { sonusDs1ProfileEntry 34 }

sonusDs1ProfileFarUASThreshold OBJECT-TYPE
    SYNTAX          Integer32 (1..900)
    MAX-ACCESS      read-write
    STATUS          current
    DESCRIPTION     
            "Unavailable Seconds threshold value for 15 minute interval. This is for far end."
    DEFVAL          { 10 }
    ::= { sonusDs1ProfileEntry 35 }

sonusDs1ProfileDayPCVThreshold OBJECT-TYPE
    SYNTAX          Integer32 (1..1048575)
    MAX-ACCESS      read-write
    STATUS          current
    DESCRIPTION     
            "Path Code Violations threshold value for a day. This is for near end."
    DEFVAL          { 132960 }
    ::= { sonusDs1ProfileEntry 36 }

sonusDs1ProfileDayLCVThreshold OBJECT-TYPE
    SYNTAX          Integer32 (1..1048575)
    MAX-ACCESS      read-write
    STATUS          current
    DESCRIPTION     
            "Line Code Violations threshold value for a day. This is for near end."
    DEFVAL          { 133400 }
    ::= { sonusDs1ProfileEntry 37 }

sonusDs1ProfileDayUASThreshold OBJECT-TYPE
    SYNTAX          Integer32 (1..65535)
    MAX-ACCESS      read-write
    STATUS          current
    DESCRIPTION     
            "Unavailable Seconds threshold value for a day. This is for near end."
    DEFVAL          { 100 }
    ::= { sonusDs1ProfileEntry 38 }

sonusDs1ProfileFarDayPCVThreshold OBJECT-TYPE
    SYNTAX          Integer32 (1..1048575)
    MAX-ACCESS      read-write
    STATUS          current
    DESCRIPTION     
            "Path Code Violations threshold value for a day. This is for far end."
    DEFVAL          { 691 }
    ::= { sonusDs1ProfileEntry 39 }

sonusDs1ProfileFarDayLCVThreshold OBJECT-TYPE
    SYNTAX          Integer32 (1..1048575)
    MAX-ACCESS      read-write
    STATUS          current
    DESCRIPTION     
            "Line Code Violations threshold value for a day. This is for far end."
    DEFVAL          { 691 }
    ::= { sonusDs1ProfileEntry 40 }

sonusDs1ProfileFarDayUASThreshold OBJECT-TYPE
    SYNTAX          Integer32 (1..65535)
    MAX-ACCESS      read-write
    STATUS          current
    DESCRIPTION     
            "Unavailable Seconds threshold value for a day. This is for far end."
    DEFVAL          { 100 }
    ::= { sonusDs1ProfileEntry 41 }

sonusDs1ProfileESThresholdState OBJECT-TYPE
    SYNTAX          SonusAdminState
    MAX-ACCESS      read-write
    STATUS          current
    DESCRIPTION     
            "Errored Seconds threshold profile state."
    DEFVAL          { enabled }
    ::= { sonusDs1ProfileEntry 42 }

sonusDs1ProfileSESThresholdState OBJECT-TYPE
    SYNTAX          SonusAdminState
    MAX-ACCESS      read-write
    STATUS          current
    DESCRIPTION     
            "Severely Errored Seconds profile state."
    DEFVAL          { enabled }
    ::= { sonusDs1ProfileEntry 43 }

sonusDs1ProfileCSSThresholdState OBJECT-TYPE
    SYNTAX          SonusAdminState
    MAX-ACCESS      read-write
    STATUS          current
    DESCRIPTION     
            "Severely Errored Seconds profile state."
    DEFVAL          { enabled }
    ::= { sonusDs1ProfileEntry 44 }

sonusDs1ProfileDayESThresholdState OBJECT-TYPE
    SYNTAX          SonusAdminState
    MAX-ACCESS      read-write
    STATUS          current
    DESCRIPTION     
            "Errored Seconds threshold profile state."
    DEFVAL          { enabled }
    ::= { sonusDs1ProfileEntry 45 }

sonusDs1ProfileDaySESThresholdState OBJECT-TYPE
    SYNTAX          SonusAdminState
    MAX-ACCESS      read-write
    STATUS          current
    DESCRIPTION     
            "Severely Errored Seconds threshold profile state."
    DEFVAL          { enabled }
    ::= { sonusDs1ProfileEntry 46 }

sonusDs1ProfileDayCSSThresholdState OBJECT-TYPE
    SYNTAX          SonusAdminState
    MAX-ACCESS      read-write
    STATUS          current
    DESCRIPTION     
            "Severely Errored Seconds threshold profile state."
    DEFVAL          { enabled }
    ::= { sonusDs1ProfileEntry 47 }

sonusDs1ProfileFarESThresholdState OBJECT-TYPE
    SYNTAX          SonusAdminState
    MAX-ACCESS      read-write
    STATUS          current
    DESCRIPTION     
            "Errored Seconds threshold profile state."
    DEFVAL          { enabled }
    ::= { sonusDs1ProfileEntry 48 }

sonusDs1ProfileFarSESThresholdState OBJECT-TYPE
    SYNTAX          SonusAdminState
    MAX-ACCESS      read-write
    STATUS          current
    DESCRIPTION     
            "Severely Errored Seconds threshold profile state."
    DEFVAL          { enabled }
    ::= { sonusDs1ProfileEntry 49 }

sonusDs1ProfileFarDayESThresholdState OBJECT-TYPE
    SYNTAX          SonusAdminState
    MAX-ACCESS      read-write
    STATUS          current
    DESCRIPTION     
            "Errored Seconds threshold profile state."
    DEFVAL          { enabled }
    ::= { sonusDs1ProfileEntry 50 }

sonusDs1ProfileFarDaySESThresholdState OBJECT-TYPE
    SYNTAX          SonusAdminState
    MAX-ACCESS      read-write
    STATUS          current
    DESCRIPTION     
            "Severely Errored Seconds threshold profile state."
    DEFVAL          { enabled }
    ::= { sonusDs1ProfileEntry 51 }

sonusDs1ProfilePCVThresholdState OBJECT-TYPE
    SYNTAX          SonusAdminState
    MAX-ACCESS      read-write
    STATUS          current
    DESCRIPTION     
            "Path Code Violations threshold profile state."
    DEFVAL          { enabled }
    ::= { sonusDs1ProfileEntry 52 }

sonusDs1ProfileLCVThresholdState OBJECT-TYPE
    SYNTAX          SonusAdminState
    MAX-ACCESS      read-write
    STATUS          current
    DESCRIPTION     
            "Line Code Violations threshold profile state."
    DEFVAL          { enabled }
    ::= { sonusDs1ProfileEntry 53 }

sonusDs1ProfileUASThresholdState OBJECT-TYPE
    SYNTAX          SonusAdminState
    MAX-ACCESS      read-write
    STATUS          current
    DESCRIPTION     
            "Unavailable Seconds threshold profile state."
    DEFVAL          { enabled }
    ::= { sonusDs1ProfileEntry 54 }

sonusDs1ProfileFarPCVThresholdState OBJECT-TYPE
    SYNTAX          SonusAdminState
    MAX-ACCESS      read-write
    STATUS          current
    DESCRIPTION     
            "Path Code Violations threshold profile state."
    DEFVAL          { enabled }
    ::= { sonusDs1ProfileEntry 55 }

sonusDs1ProfileFarLCVThresholdState OBJECT-TYPE
    SYNTAX          SonusAdminState
    MAX-ACCESS      read-write
    STATUS          current
    DESCRIPTION     
            "Line Code Violations threshold profile state."
    DEFVAL          { enabled }
    ::= { sonusDs1ProfileEntry 56 }

sonusDs1ProfileFarUASThresholdState OBJECT-TYPE
    SYNTAX          SonusAdminState
    MAX-ACCESS      read-write
    STATUS          current
    DESCRIPTION     
            "Unavailable Seconds threshold profile state."
    DEFVAL          { enabled }
    ::= { sonusDs1ProfileEntry 57 }

sonusDs1ProfileDayPCVThresholdState OBJECT-TYPE
    SYNTAX          SonusAdminState
    MAX-ACCESS      read-write
    STATUS          current
    DESCRIPTION     
            "Path Code Violations threshold profile state."
    DEFVAL          { enabled }
    ::= { sonusDs1ProfileEntry 58 }

sonusDs1ProfileDayLCVThresholdState OBJECT-TYPE
    SYNTAX          SonusAdminState
    MAX-ACCESS      read-write
    STATUS          current
    DESCRIPTION     
            "Line Code Violations threshold profile state."
    DEFVAL          { enabled }
    ::= { sonusDs1ProfileEntry 59 }

sonusDs1ProfileDayUASThresholdState OBJECT-TYPE
    SYNTAX          SonusAdminState
    MAX-ACCESS      read-write
    STATUS          current
    DESCRIPTION     
            "Unavailable Seconds threshold profile state."
    DEFVAL          { enabled }
    ::= { sonusDs1ProfileEntry 60 }

sonusDs1ProfileFarDayPCVThresholdState OBJECT-TYPE
    SYNTAX          SonusAdminState
    MAX-ACCESS      read-write
    STATUS          current
    DESCRIPTION     
            "Path Code Violations threshold profile state."
    DEFVAL          { enabled }
    ::= { sonusDs1ProfileEntry 61 }

sonusDs1ProfileFarDayLCVThresholdState OBJECT-TYPE
    SYNTAX          SonusAdminState
    MAX-ACCESS      read-write
    STATUS          current
    DESCRIPTION     
            "Line Code Violations threshold state."
    DEFVAL          { enabled }
    ::= { sonusDs1ProfileEntry 62 }

sonusDs1ProfileFarDayUASThresholdState OBJECT-TYPE
    SYNTAX          SonusAdminState
    MAX-ACCESS      read-write
    STATUS          current
    DESCRIPTION     
            "Unavailable Seconds threshold profile state."
    DEFVAL          { enabled }
    ::= { sonusDs1ProfileEntry 63 }

sonusDsx1MIBNotifications OBJECT IDENTIFIER
    ::= { sonusDsx1MIB 2 }

sonusDsx1MIBNotificationsPrefix OBJECT IDENTIFIER
    ::= { sonusDsx1MIBNotifications 0 }

sonusDsx1MIBNotificationsObjects OBJECT IDENTIFIER
    ::= { sonusDsx1MIBNotifications 1 }

sonusDs1OutOfServiceReason OBJECT-TYPE
    SYNTAX          INTEGER { maintenance(1) }
    MAX-ACCESS      read-only
    STATUS          current
    DESCRIPTION     
            "The reason for T1/E1 span going out of service"
    ::= { sonusDsx1MIBNotificationsObjects 1 }

sonusDs1OutOfServiceType OBJECT-TYPE
    SYNTAX          INTEGER { admin(1), hwFailure(2) }
    MAX-ACCESS      read-only
    STATUS          current
    DESCRIPTION     
            "The type of operation which caused T1/E1 span to go out of service"
    ::= { sonusDsx1MIBNotificationsObjects 2 }

sonusDs1ThresholdType OBJECT-TYPE
    SYNTAX          INTEGER { currentLineCodeViolation(1), 
                        currentPathCodeViolation(2), 
                        currentPathCodeViolationFarEnd(3), 
                        currentControlledSlips(4), 
                        currentErroredSeconds(5), 
                        currentSeverelyErrSeconds(6), 
                        currentUnavailableSeconds(7), 
                        totalLineCodeViolation(8), 
                        totalPathCodeViolation(9), 
                        totalPathCodeViolationFarEnd(10), 
                        totalControlledSlips(11), 
                        totalErroredSeconds(12), 
                        totalSeverelyErrSeconds(13), 
                        totalUnavailableSeconds(14), 
                        currentFarEndErroredSeconds(15), 
                        currentFarEndSeverelyErrSeconds(16), 
                        totalFarEndErroredSeconds(17), 
                        totalFarEndCurrentSeverelyErrSeconds(18), 
                        currentFarEndUnavailableSeconds(19), 
                        totalFarEndUnavailableSeconds(20) }
    MAX-ACCESS      read-only
    STATUS          current
    DESCRIPTION     
            "Type of threshold that was crossed which caused a threshold crossing trap"
    ::= { sonusDsx1MIBNotificationsObjects 3 }

sonusDs1LineState OBJECT-TYPE
    SYNTAX          INTEGER { green(1), red(2), yellow(3), ais(4), 
                        hwfailure(5) }
    MAX-ACCESS      read-only
    STATUS          current
    DESCRIPTION     
            "The type of Alarm or failure which caused T1/E1 span to go out of service"
    ::= { sonusDsx1MIBNotificationsObjects 4 }

sonusDs1AdmnState OBJECT-TYPE
    SYNTAX          INTEGER { disabled(1), enabled(2), deleted(3), 
                        inservice(4), dryingUp(5) }
    MAX-ACCESS      read-only
    STATUS          current
    DESCRIPTION     
            "The administrative state of the T1/E1 span."
    ::= { sonusDsx1MIBNotificationsObjects 5 }

sonusDsx1AdminChangeNotification NOTIFICATION-TYPE
    OBJECTS         { sonusShelfIndex, sonusSlotIndex, sonusPortIndex, 
                      sonusDs3Index, sonusDs1Index, sonusDs1AdmnState, 
                      sonusEventDescription, sonusEventClass, 
                      sonusEventLevel }
    STATUS          current
    DESCRIPTION     
            "A sonusDsx1AdminChangeNotification trap indicates the DS1 admin changes. 
             It is used to notify out-of-service, in-service, enabled and
             	 disabled"
    ::= { sonusDsx1MIBNotificationsPrefix 1 }

sonusDsx1OutOfServiceNotification NOTIFICATION-TYPE
    OBJECTS         { sonusShelfIndex, sonusSlotIndex, sonusPortIndex, 
                      sonusDs3Index, sonusDs1Index, 
                      sonusDs1OutOfServiceReason, 
                      sonusDs1OutOfServiceType, sonusEventDescription, 
                      sonusEventClass, sonusEventLevel }
    STATUS          current
    DESCRIPTION     
            "A sonusDsx1OutOfServiceNotification trap indicates that a T1/E1 span
             went out of service. The reason indicates the reason why and
             type indicates the type of failure or alarm."
    ::= { sonusDsx1MIBNotificationsPrefix 2 }

sonusDsx1ThresholdCrossingNotification NOTIFICATION-TYPE
    OBJECTS         { sonusShelfIndex, sonusSlotIndex, sonusPortIndex, 
                      sonusDs3Index, sonusDs1Index, 
                      sonusDs1ThresholdType, sonusEventDescription, 
                      sonusEventClass, sonusEventLevel }
    STATUS          current
    DESCRIPTION     
            "A sonusDsx1ThresholdCrossingNotification trap indicates that a T1/E1 span
             threshold has been crossed. The type indicates the type of threshold."
    ::= { sonusDsx1MIBNotificationsPrefix 3 }

sonusDsx1LineStatusChangeNotification NOTIFICATION-TYPE
    OBJECTS         { sonusShelfIndex, sonusSlotIndex, sonusPortIndex, 
                      sonusDs3Index, sonusDs1Index, sonusDs1LineState, 
                      sonusEventDescription, sonusEventClass, 
                      sonusEventLevel }
    STATUS          current
    DESCRIPTION     
            "A sonusDsx1LineStatusChangeNotification trap indicates the T1/E1 span state changes. 
             It is used to notify T1/E1 span Alarms states"
    ::= { sonusDsx1MIBNotificationsPrefix 4 }

END -- end of module SONUS-DS1-MIB.
