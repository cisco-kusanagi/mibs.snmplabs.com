-- automatically generated by mosy 7.1 #379 (dbc), do not edit!

TCAv2-MIB DEFINITIONS ::= BEGIN


IMPORTS
        DisplayString
                FROM RFC1213-MIB
        OBJECT-TYPE
                FROM RFC-1212
        Counter, enterprises
                FROM RFC1155-SMI
        TimeStamp
                FROM SNMPv2-TC;

bellcore OBJECT IDENTIFIER ::= { enterprises  148 }

requirements OBJECT IDENTIFIER ::= { bellcore  1 }

-- created from tcaMIB (9312101200Z)

tcaMIB OBJECT IDENTIFIER ::= { requirements  5 }

tcaObjects OBJECT IDENTIFIER ::= { tcaMIB  1 }

tcaTable OBJECT-TYPE
    SYNTAX  SEQUENCE OF TcaEntry
    ACCESS  not-accessible
    STATUS  mandatory
    DESCRIPTION
           "The Threshold Crossing Alert table."
    ::= { tcaObjects  1 }

tcaEntry OBJECT-TYPE
    SYNTAX  TcaEntry
    ACCESS  not-accessible
    STATUS  mandatory
    DESCRIPTION
           "An entry in the Threshold Crossing Alert table."
    INDEX   { tcaIfIndex,  tcaIndex }
    ::= { tcaTable  1 }

TcaEntry ::=
    SEQUENCE {
        tcaIfIndex
            INTEGER (-2147483648..2147483647),

        tcaIndex
            INTEGER (-2147483648..2147483647),

        tcaObject
            OBJECT IDENTIFIER,

        tcaObjectDesc
            DisplayString,

        tcaThreshold
            INTEGER (-2147483648..2147483647),

        tcaSampleType
            INTEGER,

        tcaCounts
            Counter,

        tcaTimeStamp
            TimeStamp,

        tcaTrapEnabler
            INTEGER
    }

tcaIfIndex OBJECT-TYPE
    SYNTAX  INTEGER (-2147483648..2147483647)
    ACCESS  not-accessible
    STATUS  mandatory
    DESCRIPTION
           "The value of this object is equal to MIB II's
                      ifIndex value for this interface sublayer
                      (ifEntry)."
    ::= { tcaEntry  1 }

tcaIndex OBJECT-TYPE
    SYNTAX  INTEGER (-2147483648..2147483647)
    ACCESS  not-accessible
    STATUS  mandatory
    DESCRIPTION
           "The value of this object is used as one of the
                      indices for this table.  It is a unique identifier
                      for this row in the table for this interface
                      (ifIndex).  The value of this object can be from 1
                      to N, where N is the number of potential TCAs for
                      this interface sublayer (ifEntry)."
    ::= { tcaEntry  2 }

tcaObject OBJECT-TYPE
    SYNTAX  OBJECT IDENTIFIER
    ACCESS  read-only
    STATUS  mandatory
    DESCRIPTION
           "The value of this object is the OBJECT IDENTIFIER
                      of the counter object being thresholded.  The
                      counter objects being thresholded are defined in
                      other MIB Modules."
    ::= { tcaEntry  3 }

tcaObjectDesc OBJECT-TYPE
    SYNTAX  DisplayString
    ACCESS  read-only
    STATUS  mandatory
    DESCRIPTION
           "The value of this object is a description of the
                      counter object being thresholded.  For example,
                      DS1 Coding Violations."
    ::= { tcaEntry  4 }

tcaThreshold OBJECT-TYPE
    SYNTAX  INTEGER (-2147483648..2147483647)
    ACCESS  read-only
    STATUS  mandatory
    DESCRIPTION
           "The value of this object is the threshold value
                      of the counter object being thresholded."
    ::= { tcaEntry  5 }

tcaSampleType OBJECT-TYPE
    SYNTAX  INTEGER {
    intervalAbsoluteValue(1),
    intervalDeltaValue(2),
    intervalFallingAlarm(3),
    intervalRisingAlarm(4),
    intervalAtValueAlarm(5),
    intervalNotAtValueAlarm(6),
    intervalIncludesValue(7),
    intervalIncludesNotValue(8)
}
    ACCESS  read-only
    STATUS  mandatory
    DESCRIPTION
           "The value of this object is the sample type of
                      the object being thresholded from the
                      perspective of the CNM or XA-OM customer.
                      This object can be used for the following
                      data types:
                      (a) Counters
                      (b) Counters measured over certain intervals,
                          where the Counters are reset to zero at the end
                          of the interval and as a result have the
                          syntax Gauge.
                      (c) Gauges (other than (b))
                      (d) (Enumerated) INTEGER
                      (e) (Enumerated) INTEGER that is used as a bitmap.
                      The enumerated values of this object apply to
                      these data types as follows:

                                          |        possible values        |
                          data type       | 1 | 2 | 3 | 4 | 5 | 6 | 7 | 8 |
                      --------------------+---+---+---+---+---+---+---+---+
                      (a) Counter         |   | X |   |   |   |   |   |   |
                      (b) IntervalCounter | X |   |   |   |   |   |   |   |
                      (c) Gauge           |   |   | X | X |   |   |   |   |
                      (d) Enum INT        |   |   |   |   | X | X |   |   |
                      (e) Enum INT(bitmap)|   |   |   |   |   |   | X | X |
                      --------------------+---+---+---+---+---+---+---+---+

                      (a) Counter values can only rise. An







                          alarm may be triggered when the value has
                          risen a delta amount within a sample period.
                      (b) IntervalCounter values can only rise within an
                          interval and are reset at the end of the
                          interval. An alarm may be triggered when
                          the value has exceeded an absolute value.
                      (c) A Gauge value may rise and fall. An alarm
                          may be triggered when the value has risen or
                          fallen a certain amount.
                      (d) An INTEGER may assume values in any sequence.
                          An alarm may be triggered when the value
                          does equal or doesnot equal a certain
                          specified value.
                      (e) A bitmap may assume values that represent
                          one or more bits to be set. An alarm may be
                          triggered when the value does include or not
                          include the combined value of certain bits.
                          Note that for (c), (d), and (e) only one alarm
                          needs to be generated, i.e., at first detection
                          of this event."
    ::= { tcaEntry  6 }

tcaCounts OBJECT-TYPE
    SYNTAX  Counter
    ACCESS  read-only
    STATUS  mandatory
    DESCRIPTION
           "The value of this object is the number of times
                      the threshold was crossed for this counter object,
                      since sysUpTime was initialized or restarted.
                      This counter is a continuous counter.  It should
                      be noted that as this object has a SYNTAX of
                      Counter, that it does not have a defined initial
                      value.  However, it is recommended that this
                      object be initialized to zero."
    ::= { tcaEntry  7 }

tcaTimeStamp OBJECT-TYPE
    SYNTAX  TimeStamp
    ACCESS  read-only
    STATUS  mandatory
    DESCRIPTION
           "The value of this object is equal to the value of
                      MIB-II's sysUpTime object at which last (latest)
                      threshold was crossed for this counter object.







                      The value of this object is set to zero at
                      (re)initialization."
    ::= { tcaEntry  8 }

tcaTrapEnabler OBJECT-TYPE
    SYNTAX  INTEGER {
    enabled(1),
    disabled(2)
}
    ACCESS  read-write
    STATUS  mandatory
    DESCRIPTION
           "Indicates whether fyiTraps should be generated
                      for this threshold crossing count (tcaObject).
                      The physical layer counters' and gauges' (e.g.,
                      DS1, DS3, SONET, and PLCP) TCAs should have a
                      default value of disabled(2).  The SMDS service
                      violations and higher layer protocol violations
                      counters' TCAs should have a default value of
                      enabled(1).  A fyiTrap, when generated, shall have
                      the following varBind list: tcaObject,
                      tcaObjectDesc, tcaThreshold, and tcaTimeStamp."
    ::= { tcaEntry  9 }

tcaConformance OBJECT IDENTIFIER ::= { tcaMIB  2 }

tcaGroups OBJECT IDENTIFIER ::= { tcaConformance  1 }

tcaCompliances OBJECT IDENTIFIER ::= { tcaConformance  2 }

tcaCompliance OBJECT IDENTIFIER ::= { tcaCompliances  1 }

tcaGroup OBJECT IDENTIFIER ::= { tcaGroups  1 }

END



_/_/_/_/_/_/_/_/_/_/_/_/_/_/_/_/_/_/_/_/_/_/_/_/_/_/_/_/_/_/_/_/_/_/_/_/_/
_/                                                                      _/
_/  Kaj Tesink                                                          _/
_/  Bellcore                                                            _/
_/  - Broadband Data Services & Consulting  vmail (908) 758-5254        _/
_/    331 Newman Springs Rd.                email kaj@cc.bellcore.com   _/
_/    Red Bank, NJ 07701                  faxmail (908) 758-4196        _/
_/                                                                      _/
_/_/_/_/_/_/_/_/_/_/_/_/_/_/_/_/_/_/_/_/_/_/_/_/_/_/_/_/_/_/_/_/_/_/_/_/_/
