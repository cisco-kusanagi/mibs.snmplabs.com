AVICI-PROCESS-MIB DEFINITIONS ::= BEGIN

    IMPORTS
        MODULE-IDENTITY, OBJECT-TYPE, Gauge32
            FROM SNMPv2-SMI
        MODULE-COMPLIANCE, OBJECT-GROUP
            FROM SNMPv2-CONF
        aviciMibs
            FROM AVICI-SMI
        aviciSysInventoryId
            FROM AVICI-SYSTEM-MIB;
    
aviciProcessMIB MODULE-IDENTITY
        LAST-UPDATED "0009071215Z"
        ORGANIZATION "Avici Systems Inc"
        CONTACT-INFO "        
                  Avici Systems, Inc.
                  101 Billerica Avenue
                  North Billerica, MA 01862-1256
 
                  (978) 964-2000
                  (978) 964-2100 (fax)
 
                  snmp@avici.com"
        DESCRIPTION
            "The MIB module to describe Avici CPU statistics."
        REVISION      "000821111500Z"
        DESCRIPTION
            "Changed mib arcs."
        REVISION      "000907121500Z"
        DESCRIPTION
            "Added conformance information."  
        ::= { aviciMibs 7 }

aviciProcessObjects       OBJECT IDENTIFIER ::= { aviciProcessMIB 1 }

-- This MIB displays CPU utilization on the Avici TSR. CPU 
-- utilization will give a general idea of how busy the processor is on a 
-- particular Avici platform. These numbers are an approximation only.

-- Avici CPU Total Table

aviciCPUTotalTable OBJECT-TYPE
        SYNTAX          SEQUENCE OF AviciCPUTotalEntry
        MAX-ACCESS      not-accessible
        STATUS          current
        DESCRIPTION
                "A table of total CPU statistics for an Avici platform. "
        ::= { aviciProcessObjects 1 }

aviciCPUTotalEntry OBJECT-TYPE
        SYNTAX          AviciCPUTotalEntry
        MAX-ACCESS      not-accessible
        STATUS          current
        DESCRIPTION
                "Overall information about the CPU load."
        INDEX   { aviciSysInventoryId }
        ::= { aviciCPUTotalTable 1 }

AviciCPUTotalEntry ::=
        SEQUENCE {
                aviciCPUTotal5sec                 Gauge32,
                aviciCPUTotal1min                 Gauge32,
                aviciCPUTotal5min                 Gauge32
        }

aviciCPUTotal5sec OBJECT-TYPE
        SYNTAX          Gauge32 (0..100)
        MAX-ACCESS      read-only
        STATUS          current
        DESCRIPTION
                "The total CPU busy percentage on this platform in the
                 last 5 second  period."
        ::= { aviciCPUTotalEntry 1 }

aviciCPUTotal1min OBJECT-TYPE
        SYNTAX          Gauge32 (0..100)
        MAX-ACCESS      read-only
        STATUS          current
        DESCRIPTION
                "The total CPU busy percentage on this platform in the
                 last 1 minute period."
        ::= { aviciCPUTotalEntry 2 }

aviciCPUTotal5min OBJECT-TYPE
        SYNTAX          Gauge32 (0..100)
        MAX-ACCESS      read-only
        STATUS          current
        DESCRIPTION
                "The total CPU busy percentage on this platform in the
                 last 5 minute period."
        ::= { aviciCPUTotalEntry 3 }

--
-- Conformance Information
--    

aviciProcessMIBConformance OBJECT IDENTIFIER ::= { aviciProcessMIB 2 }
aviciProcessMIBCompliances OBJECT IDENTIFIER ::= { aviciProcessMIBConformance 1 }
aviciProcessMIBGroups OBJECT IDENTIFIER ::= { aviciProcessMIBConformance 2 }

aviciProcessMIBCompliance MODULE-COMPLIANCE
        STATUS current
        DESCRIPTION
            "The compliance statement for aviciProcess."
        MODULE
        MANDATORY-GROUPS {
            aviciProcessCPUGroup
        }
        ::= { aviciProcessMIBCompliances 1 }

aviciProcessCPUGroup OBJECT-GROUP
        OBJECTS {
            aviciCPUTotal5sec,
            aviciCPUTotal1min,
            aviciCPUTotal5min
        }
        STATUS     current
        DESCRIPTION
            "Objects for CPU statistics."
        ::= { aviciProcessMIBGroups 1 }

END
