Wellfleet-NAME-TABLE-MIB DEFINITIONS ::= BEGIN

    IMPORTS

      OBJECT-TYPE
        FROM RFC-1212
      DisplayString
        FROM RFC1213-MIB
      wfName
        FROM Wellfleet-COMMON-MIB;

    wfNameEntry	OBJECT IDENTIFIER ::= { wfName 1 }

    wfNameDelete OBJECT-TYPE
        SYNTAX	INTEGER {
    		    created(1),
    		    deleted(2)
    		}
        ACCESS	read-write
        STATUS	mandatory
        DESCRIPTION
                "Create or Delete the Object Base Record"
        DEFVAL	{ created }
        ::= { wfNameEntry 1 }

    wfNameName OBJECT-TYPE
        SYNTAX	DisplayString (SIZE(0..64))
        ACCESS	read-write
        STATUS	mandatory
        DESCRIPTION
                "The BCC name of an object"
        ::= { wfNameEntry 2 }

    END  -- Wellfleet-NAME-TABLE-MIB
