-- extracted from draft-ietf-pwe3-pw-tc-mib-04.txt
-- at Tue Feb 17 06:17:14 2004

  PW-TC-DRAFT04-MIB DEFINITIONS ::= BEGIN 
   
  IMPORTS 
     MODULE-IDENTITY, Unsigned32, Integer32, transmission 
        FROM SNMPv2-SMI 
   
     TEXTUAL-CONVENTION 
        FROM SNMPv2-TC; 
   
  pwTCMIB MODULE-IDENTITY 
     LAST-UPDATED "200402031200Z"  -- 3 February 2004 12:00:00 GMT 
     ORGANIZATION "Pseudo Wire Edge to Edge Emulation (PWE3) Working 
                   Group" 
     CONTACT-INFO 
     " Thomas D. Nadeau 
       Postal: Cisco Systems, Inc. 
               250 Apollo Drive 
               Chelmsford, MA 01824 
       Tel:    +1-978-497-3051 
       Email:  tnadeau@cisco.com 
   
       Dave Danenberg 
       Email:  dave_danenberg@yahoo.com 
    
               David Zelig 
       Postal: Corrigent Systems. 
               126, Yigal Alon St. 
               Tel Aviv, ISRAEL 
               Phone: +972-3-6945273 
       E-mail: davidz@corrigent.com 
   
               Andrew G. Malis  
       Postal: Tellabs, Inc.  
               2730 Orchard Parkway  
               San Jose, CA 95134  
       Email:  Andy.Malis@tellabs.com 
          
          The PWE3 Working Group (email distribution pwe3@ietf.org, 
          http://www.ietf.org/html.charters/pwe3-charter.html) 
      " 
                             PWE3 TC MIB                February 2004 



     DESCRIPTION 
         "This MIB Module provides Textual Conventions 
         and OBJECT-IDENTITY Objects to be used in networks 
         implementing PW services. 
   
         Copyright (C) The Internet Society (date).  This version 
         of this MIB module is part of RFC yyyy;  see the RFC 
         itself for full legal notices. 
  -- RFC Ed.: replace yyyy with actual RFC number & remove this note 
         " 
   
   
     -- Revision history. 
   
     REVISION "200402031200Z"  -- 3 February 2004 12:00:00 GMT 
     DESCRIPTION " Changes from previous drats: 
        - Change IANA request text. 
        - Change PwVcRemoteCwStatus to PwVcCwStatus and add two 
          enum so the textual convention will indicate the full 
          status of the CW negotiation including the final result. 
       " 
     REVISION "200311301200Z"  -- 30 November 2003 12:00:00 GMT 
     DESCRIPTION " Changes from previous drats: 
        - Removing non-necessary textual convention. 
        - Adapt description of main clause based on MIB 
          boilerplate. 
       " 
     REVISION "200307281200Z"  -- 28 July 2003 12:00:00 GMT 
     DESCRIPTION "Adding objects to cover new control draft.  
        Adapt VC types for current values in WG documents." 
   
     REVISION "200305011200Z"  -- 1 May 2003 12:00:00 GMT 
     DESCRIPTION "Adding PwVcAttachmentIdentifierType,  
        Adapt VC types for current values in WG documents." 
   
     REVISION "200205281200Z"  -- 28 May 2002 12:00:00 GMT 
     DESCRIPTION "Adding PwVcType, and enhance some descriptions." 
      
     REVISION "200201301200Z"  -- 30 January 2002 12:00:00 GMT 
     DESCRIPTION "Adding PwVcVlanCfg, PwAddressType and  
                  PwOperStatus." 
   
     REVISION "200112201200Z"  -- 20 Dec 2001 12:00:00 GMT 
     DESCRIPTION "Remove PwVcInstance" 
   
     REVISION "200107121200Z"  -- 12 July 2001 12:00:00 GMT 
     DESCRIPTION "Initial version." 
   
   
     -- Please see the IANA Considerations Section. 
     -- The requested pwStdMIB subId is 1, e.g. 
                             PWE3 TC MIB                February 2004 



     --   ::= { pwStdMIB 1 } 
   
     ::= { pwStdMIB 1 }  
   
  pwStdMIB OBJECT IDENTIFIER 
            -- This object identifier needs to be assigned by IANA. 
   
         ::= { transmission XXX }  
   
  PwGroupID ::= TEXTUAL-CONVENTION 
     STATUS      current 
     DESCRIPTION 
          "An administrative identification mechanism for grouping a 
           set of service-specific pseudo-wire services. May only 
           have local significance." 
     SYNTAX  Unsigned32 
   
  PwVcIDType ::= TEXTUAL-CONVENTION 
     STATUS      current 
     DESCRIPTION 
          "Pseudo-Wire Identifier. Used to identify the PW  
           (together with some other fields) in the signaling  
           session. Zero if the PW is set-up manually." 
     SYNTAX  Unsigned32 
   
  PwVcIndexType ::= TEXTUAL-CONVENTION 
     STATUS      current 
     DESCRIPTION 
          "Pseudo Wire Index. Locally unique index for indexing 
           several MIB tables associated with a particular PW." 
     SYNTAX  Unsigned32 
   
  PwVcVlanCfg ::= TEXTUAL-CONVENTION 
     STATUS      current 
     DESCRIPTION 
          "VLAN configuration for Ethernet PW.  
           Values between 0 to 4095 indicate the actual VLAN field 
           value.  
           A value of 4096 indicates that the object refer to  
           untagged frames, i.e. frames without 802.1Q field. 
           A value of 4097 indicates that the object is not  
           relevant." 
     SYNTAX  Integer32 (0..4097) 
   
  PwOperStatus ::= TEXTUAL-CONVENTION 
     STATUS      current 
     DESCRIPTION 
        "Indicate the operational status of the PW. 
         
        - up:             Ready to pass packets.  
        - down:           If PW signaling has not yet finished, or 
                             PWE3 TC MIB                February 2004 



                          indications available at the service  
                          level indicate that the VC is not  
                          passing packets. 
        - testing:        If AdminStatus at the PW level is set to  
                          test. 
        - dormant:        The PW is not available because of the 
                          required resources are occupied PW with  
                          higher priority PWs . 
        - notPresent:     Some component is missing to accomplish  
                          the set up of the PW. 
        - lowerLayerDown: The underlying PSN or outer tunnel is not 
                          in OperStatus 'up'.  
        " 
   SYNTAX   INTEGER { 
       up(1), 
       down(2), 
       testing(3), 
       unknown(4), 
       dormant(5), 
       notPresent(6), 
       lowerLayerDown(7) 
       }       
   
  PwVcType ::= TEXTUAL-CONVENTION 
     STATUS      current 
     DESCRIPTION 
        "Indicate the PW type (i.e. the carried service). 
        " 
   SYNTAX   INTEGER { 
      other(0), 
      frameRelayDlci(1), 
      atmAal5SduVcc(2), 
      atmTransparent(3), 
      ethernetTagged(4), 
      ethernet(5), 
      hdlc(6), 
      ppp(7), 
      cem(8),  -- old format 
      atmCellNto1Vcc(9), 
      atmCellNto1Vpc(10), 
      ipLayer2Transport(11), 
      atmCell1to1Vcc(12), 
      atmCell1to1Vpc(13), 
      atmAal5PduVcc(14), 
      frameRelayPortMode(15), 
      cep(16) 
       }       
   
  PwVcAttachmentIdentifierType ::= TEXTUAL-CONVENTION 
   
     STATUS      current 
                             PWE3 TC MIB                February 2004 



     DESCRIPTION 
        "An octet string used in the generalized FEC element for 
         identifying attachment forwarder and groups. The NULL  
         identifier is of zero length." 
   SYNTAX    OCTET STRING (SIZE (0..255)) 
   
  PwVcCwStatus ::= TEXTUAL-CONVENTION 
   
     STATUS      current 
     DESCRIPTION 
        "Indicate the status of the control word negotiation based on 
         the local configuration and the remote indications.   
          
         waitingForNextMsg indicate that the node is waiting for  
         another label mapping from the remote. 
          
         sentWrongBitErrorCode indicate that the local node has  
         notified the peer about mismatch in the C bit. 
          
         rxWithdrawWithWrongBitErrorCode indicate that a withdraw  
         message has been received with wrong C-bit error code. 
          
         illegalReceivedBit indicate a C bit configuration with 
         the remote which is not compatible with the PW type. 
          
         cwPresent indicate that the CW is present for this PW: if  
         signaling is used - C bit is set and agreed between the 
         peers, and for manual configured PW the local configuration 
         require the use of the CW. 
   
         cwNotPresent indicate that the CW is not present for this  
         PW: if signaling is used - C bit is reset and agreed between 
         the peers, and for manual configured PW the local  
         configuration requires that CW would not be used. 
   
         notYetKnown indicate that a label mapping has not yet  
         received from the peer. 
        " 
   SYNTAX    INTEGER { 
                waitingForNextMsg (1), 
                sentWrongBitErrorCode (2), 
                rxWithdrawWithWrongBitErrorCode (3), 
                illegalReceivedBit (4), 
                cwPresent (5), 
                cwNotPresent (6), 
                notYetKnown(7) 
                } 
   
  PwVcCapabilities ::= TEXTUAL-CONVENTION 
     STATUS      current 
     DESCRIPTION 
                             PWE3 TC MIB                February 2004 



        "Indicate the optional capabilities of the control protocol. 
         A value of zero indicate the basic LDP PW signaling.  
         Values may be added in the future based on  
         new capabilities introduced in IETF documents. 
        " 
   SYNTAX   BITS { 
      pwStatusIndication (0) 
       }       
   
  PwVcStatus ::= TEXTUAL-CONVENTION 
     STATUS      current 
     DESCRIPTION 
        "The status of the PW and the interfaces affecting this PW. 
         If none of the bits are set, it indicate no faults are  
         reported." 
   SYNTAX   BITS { 
      pwNotForwarding (0), 
      customerFacingPwRxFault (1), 
      customerFacingPwTxFault (2), 
      psnFacingPwRxFault  (3), 
      psnFacingPwTxFault  (4) 
       }       
   
  PwVcFragSize ::= TEXTUAL-CONVENTION 
     STATUS      current 
     DESCRIPTION 
        "If set to value other than zero, it indicates desired  
         fragmentation to the value set. If set to zero,  
         fragmentation is not desired for PSN bound packets." 
   SYNTAX   Unsigned32  
   
  PwVcFragStatus ::= TEXTUAL-CONVENTION 
     STATUS      current 
     DESCRIPTION 
        "The status of the fragmentation process based on local  
         configuration and the remote capability. 
   
         noFrag bit indicates that local configuration is for no  
         fragmentation. 
   
         cfgFragGreaterThanPsnMtu bit indicates the local desire to  
         fragment, but the fragmentation size desired is greater  
         than the MTU available at the PSN between peers.  
         Fragmentation is not done in this case. 
   
         cfgFragButRemoteIncapable bit indicates local configuration  
         for fragmentation but the remote is not fragmentation  
         capable. 
   
         remoteFragCapable bit indicates that the remote has  
         advertized it's fragmentation capability. 
                             PWE3 TC MIB                February 2004 



   
         fragEnabled bit indicates that both the local was  
         configured for fragmentation and the remote has the  
         cabability to accept fragmented packets. 
        " 
   SYNTAX   BITS { 
      noFrag (0), 
      cfgFragGreaterThanPsnMtu (1), 
      cfgFragButRemoteIncapable (2), 
      remoteFragCapable (3), 
      fragEnabled (4) 
       }       
   
  END 

-- 
--   Copyright (C) The Internet Society (2000).  All Rights Reserved. 
--   This document and translations of it may be copied and furnished to 
--   others, and derivative works that comment on or otherwise explain 
--   it or assist in its implementation may be prepared, copied, 
--   published and distributed, in whole or in part, without restriction 
--   of any kind, provided that the above copyright notice and this 
--   paragraph are included on all such copies and derivative works.  
--   However, this document itself may not be modified in any way, such 
--   as by removing the copyright notice or references to the Internet 
--   Society or other Internet organizations, except as needed for the 
--   purpose of developing Internet standards in which case the 
--   procedures for copyrights defined in the Internet Standards process 
--   must be followed, or as required to translate it into languages 
--   other than English. 
--   The limited permissions granted above are perpetual and will not be 
--   revoked by the Internet Society or its successors or assigns. This 
--   document and the information contained herein is provided on an "AS 
--   IS" basis and THE INTERNET SOCIETY AND THE INTERNET ENGINEERING 
--   TASK FORCE DISCLAIMS ALL WARRANTIES, EXPRESS OR IMPLIED, INCLUDING 
--   BUT NOT LIMITED TO ANY WARRANTY THAT THE USE OF THE INFORMATION 
--   HEREIN WILL NOT INFRINGE ANY RIGHTS OR ANY IMPLIED WARRANTIES OF 
--   MERCHANTABILITY OR FITNESS FOR A PARTICULAR PURPOSE. 
--    
-- 11 Intellectual Property Notice 
--    
--   The IETF takes no position regarding the validity or scope of any 
--   intellectual property or other rights that might be claimed to 
--   pertain to the implementation or use of the technology described in 
--   this document or the extent to which any license under such rights 
--   might or might not be available; neither does it represent that it 
--   has made any effort to identify any such rights.  Information on 
--   the IETF's procedures with respect to rights in standards-track and 
--   standards-related documentation can be found in BCP-11 [RFC2028]. 
--   Copies of claims of rights made available for publication and any 
--   assurances of licenses to be made available, or the result of an 
--   attempt made to obtain a general license or permission for the use 
--   of such proprietary rights by implementors or users of this 
--   specification can be obtained from the IETF Secretariat. 
--    
--   The IETF invites any interested party to bring to its attention any 
--   copyrights, patents or patent applications, or other proprietary 
--   rights that may cover technology that may be required to practice 
--   this standard.  Please address the information to the IETF 
--   Executive Director.
