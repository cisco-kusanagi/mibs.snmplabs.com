-- |**********************************************************************|
 -- | Copyright 1998 - Sonoma Systems, Inc. Marina del Rey, CA 90292       |
 -- |    Unpublished software - All rights reserved.                       |
 -- |                                                                      |
 -- | The information in this software is subject to change without notice |
 -- | and should not be construed as a commitment by Sonoma Systems, Inc.  |
 -- |                                                                      |
 -- | Sonoma Systems, Inc. assumes no responsibility for the use or        |
 -- | reliability of its software on equipment which is not supplied by    |
 -- | Sonoma Systems, Inc.                                                 |
 -- |                                                                      |
 -- | This software is furnished under a license and may be copied only    |
 -- | under the terms of that license and with the inclusion of this       |
 -- | notice. This software, or any other copies thereof, may not be       |
 -- | provided or otherwise made available to any other person except to   |
 -- | one who agrees to these license terms. Title to and ownership of the |
 -- | software shall at all times remain with Sonoma Systems, Inc.         |
 -- |**********************************************************************|
 --
 -- Sonoma Systems Inc.,
 -- 4640 Admiralty Way, Suite #600,
 -- Marina Del Rey,
 -- California 90292-6695.
 --
 -- Web : www.sonoma-systems.com
 -- Phone:  310.827.8000
 --
 -- NAME        : imamib.def
 --
 -- DESCRIPTION : This is the MIB fro the Sonoma ATM IMA Group.
 --
 -- ARCHIVE : $Archive:   M:\pvcs\pvcsproj\sonoma3\src\mib\imamib.dev  $
 -- REVISION: $Revision:   1.36  $
 -- AUTHOR  : $Author:   EMARCULI  $
 -- DATE    : $Date:   Feb 26 1999 15:12:44  $

      SONOMASYSTEMS-SONOMA-ATM-IMA-MIB
      DEFINITIONS ::= BEGIN

      IMPORTS
        Counter
        FROM RFC1155-SMI
        OBJECT-TYPE
        FROM RFC-1212
        sonomaATM 
        FROM SONOMASYSTEMS-SONOMA-MIB;

    --  This MIB module uses the extended OBJECT-TYPE macro as
    --  defined in [14];
    --
    -- Hierarchy for these groups
    -- enterprises OBJECT IDENTIFIER ::= { private 4 }
    -- sonomaSystems OBJECT IDENTIFIER ::= {  enterprises 2926 }
    -- sonomaSeries OBJECT IDENTIFIER ::= { sonomaSystems 25 }
    -- sonomaATM OBJECT IDENTIFIER ::= { sonomaSeries 7 }
    sonomaImaATMAdapterGroup OBJECT IDENTIFIER ::= { sonomaATM 7 }


    -- Sonoma IMA ATM Adapter Specific Group MIB groups
       atmImaGroupObjects OBJECT IDENTIFIER ::= { sonomaImaATMAdapterGroup 1 }
       atmImaLinkObjects OBJECT IDENTIFIER ::= { sonomaImaATMAdapterGroup 2 }
       atmImaDs1Objects OBJECT IDENTIFIER ::= { sonomaImaATMAdapterGroup 3 }
       atmImaE1Objects OBJECT IDENTIFIER ::= { sonomaImaATMAdapterGroup 4 }

    -----------------------------------------------------------------------

    -- The implementation of this MIB is mandatory for all network devices
    -- which have ATM Inverse Multiplexer network interface module.

    -- atmfImaMib MODULE-IDENTITY
    --
    -- DESCRIPTION
    -- "The MIB module to describe an ATM Inverse Multiplexer interface"
    -- ::= { atmForumNetworkManagement TBD }
	
    --

    -- This MIB consists of the IMA group subtree.
    -- The IMA group subtree consists of the number of IMA groups and a
    -- table of IMA groups. Each entry in the table of IMA groups contains
    -- information (configuration and status) specific to each group.

    -- The IMA Group subtree

    imaGroupNumber OBJECT-TYPE
	SYNTAX INTEGER
	ACCESS read-only
	STATUS mandatory
	DESCRIPTION
	  "The number of IMA groups configured on this system."
	::= { atmImaGroupObjects 1 }

    -- IMA Group Table contains configuration and status information

    imaGroupTable OBJECT-TYPE
	SYNTAX SEQUENCE OF ImaGroupEntry
	ACCESS not-accessible
	STATUS mandatory
	DESCRIPTION
	  "The IMA Group Configuration table."
	::= { atmImaGroupObjects 2 }

    imaGroupEntry OBJECT-TYPE
	SYNTAX ImaGroupEntry
	ACCESS not-accessible
	STATUS mandatory
	DESCRIPTION
	  "An entry in the IMA Group table."
	INDEX { imaGroupIndex }
	::= { imaGroupTable 1 }

    ImaGroupEntry ::= SEQUENCE {
	imaGroupIndex		INTEGER,
	imaGroupRowStatus	INTEGER,
	imaGroupIfIndex		INTEGER,
	imaGroupNeState		INTEGER,
	imaGroupFeState		INTEGER,
	imaGroupFailureStatus	INTEGER,
	imaGroupSymmetry 	INTEGER,
	imaGroupMinNumTxLinks 	INTEGER,
	imaGroupMinNumRxLinks 	INTEGER,
	imaGroupNeTxClkMode 	INTEGER,
	imaGroupFeTxClkMode 	INTEGER,
	imaGroupTxTimingRefLink INTEGER,
	imaGroupRxTimingRefLink INTEGER,
	imaGroupLastChange 	INTEGER,
	imaGroupTxImaId 	INTEGER,
	imaGroupRxImaId 	INTEGER,
	imaGroupTxFrameLength 	INTEGER,
	imaGroupRxFrameLength 	INTEGER,
	imaGroupDiffDelayMax 	INTEGER,
	imaGroupLeastDelayLink 	INTEGER,
	imaGroupDiffDelayMaxObs INTEGER,
	imaGroupAlphaValue 	INTEGER,
	imaGroupBetaValue 	INTEGER,
	imaGroupGammaValue 	INTEGER,
	imaGroupRunningSecs 	INTEGER,
	imaGroupUnavailSecs 	INTEGER,
	imaGroupNeNumFailures 	INTEGER,
	imaGroupFeNumFailures 	INTEGER,
	imaGroupTxAvailCellRate INTEGER,
	imaGroupRxAvailCellRate INTEGER,
	imaGroupNumTxCfgLnks 	INTEGER,
	imaGroupNumRxCfgLnks 	INTEGER,
	imaGroupNumTxActLnks 	INTEGER,
	imaGroupNumRxActLnks 	INTEGER,
	imaGroupTestLinkIfIndex INTEGER,
	imaGroupTestPattern 	INTEGER,
	imaGroupTestProcStatus 	INTEGER
	}

    imaGroupIndex OBJECT-TYPE
	SYNTAX INTEGER
	ACCESS read-only
	STATUS mandatory
	DESCRIPTION
	  "A unique value for the IMA Group."
	::= { imaGroupEntry 1 }

    imaGroupRowStatus OBJECT-TYPE
        SYNTAX  INTEGER { 
                        enabled(1),
                        disabled(2)
                        }
	ACCESS read-write
	STATUS mandatory
	DESCRIPTION
	  "This object identifies the IMA Group's administrative status.
	  It is used to enable and disable a group."
	::= { imaGroupEntry 2 }

    imaGroupIfIndex OBJECT-TYPE
	SYNTAX INTEGER
	ACCESS read-only

	STATUS mandatory
	DESCRIPTION
	  "This object identifies the logical interface number
	  ('ifIndex') assigned to this IMA group, and is used to identify
	  corresponding rows in the Interfaces MIB.

	  Note that re-initialization of the management agent may cause
	  a client's 'imaGroupIfIndex' to change."
	::= { imaGroupEntry 3 }

    imaGroupNeState OBJECT-TYPE
	SYNTAX INTEGER {
	  notConfigured(1),
	  startUp(2),
	  startUpAck(3),
	  configAbortUnsupportedM(4),
	  configAbortIncompatibleSymmetry(5),
	  configAbortOther(6),
	  insufficientLinks(7),
	  blocked(8),
	  operational(9) 
	}
	ACCESS read-only
	STATUS mandatory
	DESCRIPTION
	  "The current operational state of the near-end IMA
	  Group State Machine."
	::= { imaGroupEntry 4 }

    imaGroupFeState OBJECT-TYPE
	SYNTAX INTEGER {
	  notConfigured(1),
	  startUp(2),
	  startUpAck(3),
	  configAbortUnsupportedM(4),
	  configAbortIncompatibleSymmetry(5),
	  configAbortOther(6),
	  insufficientLinks(7),
	  blocked(8),
	  operational(9)
	}
	ACCESS read-only
	STATUS mandatory
	DESCRIPTION
	  "The current operational state of the far-end IMA
	  Group State Machine."
	::= { imaGroupEntry 5 }

    imaGroupFailureStatus OBJECT-TYPE
	SYNTAX INTEGER {
	  noFailure(1), -- unit is up
	  startUpNe(2),
	  startUpFe(3),
	  invalidMValueNe(4),
	  invalidMValueFe(5),
	  failedAssymetricNe(6),
	  failedAssymetricFe(7),
	  insufficientLinksNe(8),
	  insufficientLinksFe(9),
	  blockedNe(10),
	  blockedFe(11),
	  otherFailure(12)
	}
	ACCESS read-only
	STATUS mandatory
	DESCRIPTION
	  "The current failure status of the IMA group (the reason why
	  the GTSM is in the down state."
	::= { imaGroupEntry 6 }

    imaGroupSymmetry OBJECT-TYPE
	SYNTAX INTEGER {
	  symmetricOperation(1),
	  asymmetricOperation(2),
	  asymmetricConfiguration(3)
	}
	ACCESS read-write
	STATUS mandatory
	DESCRIPTION
	  "Symmetry of the IMA group."
	DEFVAL { symmetricOperation }
	::= { imaGroupEntry 7 }

    imaGroupMinNumTxLinks OBJECT-TYPE
	SYNTAX INTEGER (1..32)
	ACCESS read-write
	STATUS mandatory
	DESCRIPTION
	  "Minimum number of transmit links required to be Active for
	  the IMA group to be in the Up state."
	DEFVAL { 2 }
	::= { imaGroupEntry 8 }

    imaGroupMinNumRxLinks OBJECT-TYPE
	SYNTAX INTEGER (1..32)
	ACCESS read-write
	STATUS mandatory
	DESCRIPTION
	  "Minimum number of receive links required to be Active for
	  the IMA group to be in the Up state."
	DEFVAL { 2 }
	::= { imaGroupEntry 9 }

    imaGroupNeTxClkMode OBJECT-TYPE
	SYNTAX INTEGER { 
	  ctc(1), 
	  itc(2) 
	}
	ACCESS read-write
	STATUS mandatory
	DESCRIPTION
	  "Transmit clocking mode used by the near-end IMA group."
	DEFVAL { ctc }
	::= { imaGroupEntry 10 }

    imaGroupFeTxClkMode OBJECT-TYPE
	SYNTAX INTEGER { 
	  ctc(1), 
	  itc(2) 
	}
	ACCESS read-only
	STATUS mandatory
	DESCRIPTION
	  "Transmit clocking mode used by the far-end IMA group."
	::= { imaGroupEntry 11 }

    imaGroupTxTimingRefLink OBJECT-TYPE
	SYNTAX INTEGER (1..8)
	ACCESS read-write
	STATUS mandatory
	DESCRIPTION
	  "The ifIndex of the transmit timing reference link to
	  be used by the near-end for IMA data cell clock recovery from
	  the ATM layer."
	DEFVAL { 1 }
	::= { imaGroupEntry 12 }

    imaGroupRxTimingRefLink OBJECT-TYPE
	SYNTAX INTEGER (1..8)
	ACCESS read-only
	STATUS mandatory
	DESCRIPTION
	  "The ifIndex of the receive timing reference link to be
	  used by near-end for IMA data cell clock recovery toward
	  the ATM layer."
	DEFVAL { 1 }
	::= { imaGroupEntry 13 }

    imaGroupLastChange OBJECT-TYPE
	SYNTAX INTEGER
	ACCESS read-only
	STATUS mandatory
	DESCRIPTION
	  "The time-of-day the IMA group last changed operational
	  state (i.e., value of imaNeGroupState changed)."
	::= { imaGroupEntry 14 }

    imaGroupTxImaId OBJECT-TYPE
	SYNTAX INTEGER (0..255)
	ACCESS read-write
	STATUS mandatory
	DESCRIPTION
	  "The IMA ID currently in use by the near-end IMA function."
	DEFVAL { 100 }
	::= { imaGroupEntry 15 }

    imaGroupRxImaId OBJECT-TYPE
	SYNTAX INTEGER (0..255)
	ACCESS read-only
	STATUS mandatory
	DESCRIPTION
	  "The IMA ID currently in use by the far-end IMA function."
	::= { imaGroupEntry 16 }

    imaGroupTxFrameLength OBJECT-TYPE
	SYNTAX INTEGER {
	  m32(32),
	  m64(64),
	  m128(128),
	  m256(256)
	}
	ACCESS read-write
	STATUS mandatory
	DESCRIPTION
	  "The frame length to be used by the IMA group in the transmit
	  direction. Can only be set when the IMA group is startup."
	DEFVAL { m128 }
	::= { imaGroupEntry 17 }

    imaGroupRxFrameLength OBJECT-TYPE
	SYNTAX INTEGER {
	  m32(32),
	  m64(64),
	  m128(128),
	  m256(256)
	}
	ACCESS read-only
	STATUS mandatory
	DESCRIPTION
	  "Value of IMA frame length as received from remote IMA function."
	::= { imaGroupEntry 18 }

    imaGroupDiffDelayMax OBJECT-TYPE
	SYNTAX INTEGER
	ACCESS read-write
	STATUS mandatory
	DESCRIPTION
	  "The maximum number of milliseconds of delay differential among
	  the links that will be tolerated on this interface."
	DEFVAL { 25 }
	::= { imaGroupEntry 19 }

    imaGroupLeastDelayLink OBJECT-TYPE
	SYNTAX INTEGER
	ACCESS read-only
	STATUS mandatory
	DESCRIPTION
	  "The ifIndex of the link configured in the IMA
	  group which has the smallest link propagation delay. This
	  value has meaning only if at least 1 link has been configured
	  in the IMA group."
	::= { imaGroupEntry 20 }

    imaGroupDiffDelayMaxObs OBJECT-TYPE
	SYNTAX INTEGER
	ACCESS read-only
	STATUS mandatory
	DESCRIPTION
	  "The latest maximum differential delay observed (in
	  milliseconds), i.e. between the links having the least and
	  most link propagation delay, among the receive links that
	  are currently configured in the IMA group."
	::= { imaGroupEntry 21 }

    imaGroupAlphaValue OBJECT-TYPE
	SYNTAX INTEGER (1..2)
	ACCESS read-write
	STATUS mandatory
	DESCRIPTION
	  "This indicates the 'alpha' value used to specify the
	  number of consecutive invalid ICP cells to be detected
	  before moving to the IMA HUNT state."
	DEFVAL { 2 }
	::= { imaGroupEntry 22 }

    imaGroupBetaValue OBJECT-TYPE
	SYNTAX INTEGER (1..5)
	ACCESS read-write
	STATUS mandatory
	DESCRIPTION
	  "This indicates the 'beta' value used to specify the
	  number of consecutive errored ICP cells to be detected
	  before moving to the IMA HUNT state."
	DEFVAL { 2 }
	::= { imaGroupEntry 23 }

    imaGroupGammaValue OBJECT-TYPE
	SYNTAX INTEGER (1..5)
	ACCESS read-write
	STATUS mandatory
	DESCRIPTION
	  "This indicates the 'gamma' value used to specify the
	  number of consecutive valid ICP cells to be detected before
	  moving to the IMA SYNC state from the PRESYNC state."
	DEFVAL { 1 }
	::= { imaGroupEntry 24 }

    imaGroupRunningSecs OBJECT-TYPE
	SYNTAX INTEGER
	ACCESS read-only
	STATUS mandatory
	DESCRIPTION
	  "The amount of time (in seconds) since this IMA group has
	  been in operation (up or down)."
	::= { imaGroupEntry 25 }

    imaGroupUnavailSecs OBJECT-TYPE
	SYNTAX INTEGER
	ACCESS read-only
	STATUS mandatory
	DESCRIPTION
	  "Count of one second intervals where the IMA Group Traffic
	  State Machine is Down."
	::= { imaGroupEntry 26 }

    imaGroupNeNumFailures OBJECT-TYPE
	SYNTAX INTEGER
	ACCESS read-only
	STATUS mandatory
	DESCRIPTION
	  "The number of times a near-end group failure (Config-Abort,
	  Insufficient-Links) has been reported since power-up or reboot."
	::= { imaGroupEntry 27 }

    imaGroupFeNumFailures OBJECT-TYPE
	SYNTAX INTEGER
	ACCESS read-only
	STATUS mandatory
	DESCRIPTION
	  "The number of times a far-end group failure (Config-Abort-FE,
	  Insufficient-Links-FE, Blocked-FE) has been reported since
	  power-up or reboot. This is an optional attribute."
	::= { imaGroupEntry 28 }

    imaGroupTxAvailCellRate OBJECT-TYPE
	SYNTAX INTEGER
	ACCESS read-only
	STATUS mandatory
	DESCRIPTION
	  "The current cell rate (truncated value in cells per second)
	  provided by this IMA group in the transmit direction,
	  considering all the transmit links in the Active state."
	::= { imaGroupEntry 29 }

    imaGroupRxAvailCellRate OBJECT-TYPE
	SYNTAX INTEGER
	ACCESS read-only
	STATUS mandatory
	DESCRIPTION
	  "The current cell rate (truncated value in cells per second)
	  provided by this IMA group in the receive direction,
	  considering all the receive links in the Active state."
	::= { imaGroupEntry 30 }

    --     imaGroupNumTxCfgLnks is used by a network operator to tell how many
    -- links are configured for transmit in the IMA group.

    imaGroupNumTxCfgLnks OBJECT-TYPE
	SYNTAX INTEGER
	ACCESS read-only
	STATUS mandatory
	DESCRIPTION
	  "The number of links that are configured to transmit in this IMA
	  group."
	::= { imaGroupEntry 31 }

    -- imaGroupNumRxCfgLnks is used by a network operator to tell how many
    -- links are configured for receive in the IMA group.

    imaGroupNumRxCfgLnks OBJECT-TYPE
	SYNTAX INTEGER
	ACCESS read-only
	STATUS mandatory
	DESCRIPTION
	  "The number of links that are configured to receive in this IMA
	  group."
	::= { imaGroupEntry 32 }

    -- imaGroupNumTxActLnks is used by a network operator to tell how many
    -- links which are configured for transmit are also Active.

    imaGroupNumTxActLnks OBJECT-TYPE
	SYNTAX INTEGER
	ACCESS read-only
	STATUS mandatory
	DESCRIPTION
	  "The number of links which are configured to transmit and are
	  currently Active in this IMA group."
	::= { imaGroupEntry 33 }

    -- imaGroupNumRxActLnks is used by a network operator to tell how many
    -- links which are configured for receive are also Active.

    imaGroupNumRxActLnks OBJECT-TYPE
	SYNTAX INTEGER
	ACCESS read-only
	STATUS mandatory
	DESCRIPTION
	  "The number of links which are configured to receive and are
	  currently Active in this IMA group."
	::= { imaGroupEntry 34 }

    --
    -- Test Pattern Procedure control objects. These objects are implemented
    -- if the IMA implements the Test Pattern Procedure. In this case all
    -- test pattern procedure related objects must be implemented.
    --  Specifically these are
    --
    -- imaGroupTestLinkIfIndex
    -- imaGroupTestPattern
    -- imaGroupTestProcStatus
    -- imaLinkTestProcStatus
    -- imaLinkRxTestPattern
    --

    imaGroupTestLinkIfIndex OBJECT-TYPE
	SYNTAX INTEGER
	ACCESS read-write
	STATUS mandatory
	DESCRIPTION
	  "This object is used to designate an interface as the Test Link.
	  A value of -1 specifies that the implementation may choose the
	  Test Link. In this case, the implementation may also choose the
	  value of 'imaGroupTestPattern'."
	DEFVAL { -1 }
	::= { imaGroupEntry 35 }

    imaGroupTestPattern OBJECT-TYPE
	SYNTAX INTEGER
	ACCESS read-write
	STATUS mandatory
	DESCRIPTION
	  "The value of this object is used to specify the test pattern
	  in an IMA group loopback operation. A value in the range 0 to
	  255 designates a specific pattern. A value of -1 specifies
	  that the implementation may choose the value. In this case,
	  the implementation may also choose the value of
	  'imaGroupTestLinkIfIndex'."
	DEFVAL { -1 }
	::= { imaGroupEntry 36 }

    imaGroupTestProcStatus OBJECT-TYPE
	SYNTAX INTEGER {
	  disabled(1), 
	  operating(2),
	  linkFail(3)
	}
	ACCESS read-write
	STATUS mandatory
	DESCRIPTION
	  "This object is used to enable or disable the
	  Test Pattern Procedure, and to note whether at least one
	  link failed the test.
	  The test is started by setting operating(2) status. If any
	  link should fail the test, the IMA will set the status to
	  linkfail(3). The linkfail(3) state will persist until
	  either the disabled(1) state is set or until no instance
	  of imaLinkTestProcStatus has the value linkfail(3).
	  Only the values disabled(1) and operating(2) may be written.
	  Writing the operating(2) value will not cause clearing of
	  the linkfail(3) state."
	DEFVAL { disabled }
	::= { imaGroupEntry 37 }

    --
    -- The IMA Group - ifIndex Mapping Table
    -- 
    -- Note that the Group Index is different that the ifIndex.
    --
    -- The "ifIndex Mapping" table allows the Unit Management to
    -- perform easy look-ups (no searches and sorts).

    -- THIS CAUSES SNCOMP TO CRASH - REMOVED
    --
    -- imaGroupMappingTable OBJECT-TYPE
    -- SYNTAX SEQUENCE of ImaGroupMappingEntry
    --  ACCESS not-accessible
    --	STATUS mandatory
    --	DESCRIPTION
    --	  "A table mapping the 'ifIndex' values of 'imaGroupIfIndex'
    --	  to the 'imaGroupIndex' values of the corresponding
    --	  IMA group."
    --	::= { atmImaGroupObjects 3 }

    -- imaGroupMappingEntry OBJECT-TYPE
    --	SYNTAX ImaGroupMappingEntry
    --	ACCESS not-accessible
    --	STATUS mandatory
    --	DESCRIPTION
    --	  "Each row describes one ifIndex ==> imaGroupIndex mapping."
    --	INDEX { ifIndex }
    --	::= { imaGroupMappingTable 1 }

    --  imaGroupMappingIndex ::=
    --	SEQUENCE {
    --	  imaGroupMappingIndex integer
    --	}

    -- imaGroupMappingIndex OBJECT-TYPE
    --	SYNTAX integer
    --	ACCESS read-only
    --	STATUS mandatory
    --	DESCRIPTION
    --	  "The imaGroupIndex of the IMA Group which implements the
    --	  specified interface."
    --	::= { imaGroupMappingEntry 1 }
    --
    -- END OF REMOVED ENTRY

    -- The IMA link status and configuration table
    -- Each entry in the table contains status information about a link
    -- which is part of an IMA group.

    imaLinkTable OBJECT-TYPE
	SYNTAX SEQUENCE OF ImaLinkEntry
	ACCESS not-accessible
	STATUS mandatory
	DESCRIPTION
	  "The IMA group Link Status and Configuration table."
	::= { atmImaLinkObjects 1 }

    imaLinkEntry OBJECT-TYPE
	SYNTAX ImaLinkEntry
	ACCESS not-accessible
	STATUS mandatory
	DESCRIPTION
	  "An entry in the IMA Group Link table."
	INDEX {  imaLinkGroupIndex, imaLinkIfIndex }
	::= { imaLinkTable 1 }

    ImaLinkEntry 	::= SEQUENCE {
	imaLinkIfIndex 		INTEGER,
	imaLinkRowStatus 	INTEGER,
	imaLinkGroupIndex 	INTEGER,	
	imaLinkNeTxState 	INTEGER,
	imaLinkNeRxState 	INTEGER,
	imaLinkFeTxState 	INTEGER,
	imaLinkFeRxState 	INTEGER,
	imaLinkNeRxFailureStatus INTEGER,
	imaLinkFeRxFailureStatus INTEGER,
	imaLinkTxLid 		INTEGER,
	imaLinkRxLid 		INTEGER,
	imaLinkRelDelay 	INTEGER,
	imaLinkImaViolations 	INTEGER,
	imaLinkOifAnomalies 	INTEGER,
	imaLinkNeSevErroredSec 	INTEGER,
	imaLinkFeSevErroredSec 	INTEGER,
	imaLinkNeUnavailSec 	INTEGER,
	imaLinkFeUnavailSec 	INTEGER,
	imaLinkNeTxUnusableSec 	INTEGER,
	imaLinkNeRxUnusableSec 	INTEGER,
	imaLinkFeTxUnusableSec 	INTEGER,
	imaLinkFeRxUnusableSec 	INTEGER,
	imaLinkNeTxNumFailures 	INTEGER,
	imaLinkNeRxNumFailures 	INTEGER,
	imaLinkFeTxNumFailures 	INTEGER,
	imaLinkFeRxNumFailures 	INTEGER,
	imaLinkTxStuffs 	INTEGER,
	imaLinkRxStuffs 	INTEGER,
	imaLinkRxTestPattern 	INTEGER,
	imaLinkTestProcStatus 	INTEGER,
	imaLinkNumber	 	INTEGER
	}

    imaLinkIfIndex OBJECT-TYPE
	SYNTAX INTEGER
	ACCESS read-only
	STATUS mandatory
	DESCRIPTION
	  "This corresponds to the 'ifIndex' of the MIB-II interface
	  on which this link is established. This object also
	  corresponds to the logical number ('ifIndex') assigned to
	  this IMA link."
	::= { imaLinkEntry 1 }

    imaLinkRowStatus OBJECT-TYPE
        SYNTAX  INTEGER { 
                        enabled(1),
                        disabled(2)
                        }
	ACCESS read-write
	STATUS mandatory
	DESCRIPTION
	  "The imaLinkRowStatus object allows create, change and delete
	  operations on imaLinkTable entries.
	  
	  To create a new conceptual row (or instance) of the imaLinkTable,
	  imaLinkRowStatus must be set to 'createAndWait' or 'createAndGo.'
	  A successful set of the object imaLinkGroupIndex must be
	  performed before the RowStatus of this new row can transition
	  to the 'Active' state. The imaLinkGroupIndex provides the
	  association between a physical IMA link to an IMA group.

	  To change (modify) an imaLinkTable entry, the imaLinkRowStatus
	  object must be set to 'notInService'. Only then can the
	  conceptual row be changed. Setting object imaLinkGroupIndex to
	  a different value has the effect of changing the association
	  between a physical IMA link and an IMA group. To place the
	  link 'in group', the imaLinkRowStatus object is set to 'Active'.
	  While the row is not in 'Active' state, both the Transmit and
	  Receive IMA state machines are in the 'Not In Group' state.

	  To remove (delete) an imaLinkTable entry from this table, set
	  this object to 'destroy.'

	  A network manager may elect to perform a delete operation
	  followed immediately by a create operation instead of a
	  modify operation. The net effect of the delete/create is to
	  re-instantiate (reset) agent counters defined in this table."
	::= { imaLinkEntry 2 }

    imaLinkGroupIndex OBJECT-TYPE
	SYNTAX INTEGER {
	  imaGroup-1(1),
	  none(2)
        }
	ACCESS read-write
	STATUS mandatory
	DESCRIPTION
	  "The value which identifies the IMA group (imaGroupIndex)
	  of which this link is a member."
	::= { imaLinkEntry 3 }

    imaLinkNeTxState OBJECT-TYPE
	SYNTAX INTEGER {
	  notInGroup(1),
	  unusableNoGivenReason(2),
	  unusableFault(3),
	  unusableMisconnected(4),
	  unusableBlocked(5),
	  unusableFailed(6),
	  usable(7),
	  active(8)
	}
	ACCESS read-only
	STATUS mandatory
	DESCRIPTION
	  "The current state of the near-end transmit link."
	::= { imaLinkEntry 4 }

    imaLinkNeRxState OBJECT-TYPE
	SYNTAX INTEGER {
	  notInGroup(1),
	  unusableNoGivenReason(2),
	  unusableFault(3),
	  unusableMisconnected(4),
	  unusableBlocked(5),
	  unusableFailed(6),
	  usable(7),
	  active(8)
	}
	ACCESS read-only
	STATUS mandatory
	DESCRIPTION
	  "The current state of the near-end receive link."
	::= { imaLinkEntry 5 }

    imaLinkFeTxState OBJECT-TYPE
	SYNTAX INTEGER {
	  notInGroup(1),
	  unusableNoGivenReason(2),
	  unusableFault(3),
	  unusableMisconnected(4),
	  unusableBlocked(5),
	  unusableFailed(6),
	  usable(7),
	  active(8)
	}
	ACCESS read-only
	STATUS mandatory
	DESCRIPTION
	  "The current state of the far-end transmit link as reported
	  via ICP cells."
	::= { imaLinkEntry 6 }

    imaLinkFeRxState OBJECT-TYPE
	SYNTAX INTEGER {
	  notInGroup(1),
	  unusableNoGivenReason(2),
	  unusableFault(3),
	  unusableMisconnected(4),
	  unusableBlocked(5),
	  unusableFailed(6),
	  usable(7),
	  active(8)
	}
	ACCESS read-only
	STATUS mandatory
	DESCRIPTION
	  "The current state of the far-end receive link as reported
	  via ICP cells."
	::= { imaLinkEntry 7 }

    imaLinkNeRxFailureStatus OBJECT-TYPE
	SYNTAX INTEGER {
	  noFailure(1),
	  imaLinkFailure(2),
	  lifFailure(3),
	  lodsFailure(4),
	  misConnected(5),
	  blocked(6),
	  fault(7),
	  farEndTxLinkUnusable(8),
	  farEndRxLinkUnusable(9)
	}
	ACCESS read-only
	STATUS mandatory
	DESCRIPTION
	  "The current link failure status of the near-end receive link."
	::= { imaLinkEntry 8 }

    imaLinkFeRxFailureStatus OBJECT-TYPE
	SYNTAX INTEGER {
	  noFailure(1),
	  imaLinkFailure(2),
	  lifFailure(3),
	  lodsFailure(4),
	  misConnected(5),
	  blocked(6),
	  fault(7),
	  farEndTxLinkUnusable(8),
	  farEndRxLinkUnusable(9)
	}
	ACCESS read-only
	STATUS mandatory
	DESCRIPTION
	  "The current link failure status of the far-end receive link
	  as reported via ICP cells."
	::= { imaLinkEntry 9 }

    imaLinkTxLid OBJECT-TYPE
	SYNTAX INTEGER (0..31)
	ACCESS read-only
	STATUS mandatory
	DESCRIPTION
	  "The outgoing LID used currently on the link by the local end.
	  This value has meaning only if the link belongs to an IMA group."
	::= { imaLinkEntry 10 }

    imaLinkRxLid OBJECT-TYPE
	SYNTAX INTEGER (0..31)
	ACCESS read-only
	STATUS mandatory
	DESCRIPTION
	  "The incoming LID used currently on the link by the remote
	  end as reported via ICP cells. This value has meaning only
	  if the link belongs to an IMA group."
	::= { imaLinkEntry 11 }

    imaLinkRelDelay OBJECT-TYPE
	SYNTAX INTEGER
	ACCESS read-only
	STATUS mandatory
	DESCRIPTION
	  "The latest measured delay on this link relative to the link, in
	  the same IMA group, with the least delay."
	::= { imaLinkEntry 12 }

    imaLinkImaViolations OBJECT-TYPE
	SYNTAX INTEGER
	ACCESS read-only
	STATUS mandatory
	DESCRIPTION
	  "ICP violations: count of errored, invalid or missing ICP
	  cells during non-SES-IMA condition."
	::= { imaLinkEntry 13 }

    imaLinkOifAnomalies OBJECT-TYPE
	SYNTAX INTEGER
	ACCESS read-only
	STATUS mandatory
	DESCRIPTION
	  "The number of OIF anomalies during non-SES-IMA condition at the
	  near-end. This is an optional attribute."
	::= { imaLinkEntry 14 }

    imaLinkNeSevErroredSec OBJECT-TYPE
	SYNTAX INTEGER
	ACCESS read-only
	STATUS mandatory
	DESCRIPTION
	  "Count of one second intervals containing several IV-IMA, or
	  one or more link defects (e.g., LOS, OOF/LOF, AIS, LCD), LIF, LODS
	  defects during non-UAS-IMA condition."
	::= { imaLinkEntry 15 }

    imaLinkFeSevErroredSec OBJECT-TYPE
	SYNTAX INTEGER
	ACCESS read-only
	STATUS mandatory
	DESCRIPTION
	  "Count of one second intervals containing one or more
	  RDI-IMA defects."
	::= { imaLinkEntry 16 }

    imaLinkNeUnavailSec OBJECT-TYPE
	SYNTAX INTEGER
	ACCESS read-only
	STATUS mandatory
	DESCRIPTION
	  "Count of unavailable seconds at near-end: unavailability begins
	  at the onset of 10 contiguous SES-IMA and ends at the onset
	  of 10 contiguous seconds with no SES-IMA."
	::= { imaLinkEntry 17 }

    imaLinkFeUnavailSec OBJECT-TYPE
	SYNTAX INTEGER
	ACCESS read-only
	STATUS mandatory
	DESCRIPTION
	  "Count of unavailable seconds at far-end: unavailability begins
	  at the onset of 10 contiguous SES-IMA-FE and ends at the onset of
	  10 contiguous seconds with no SES-IMA-FE."
	::= { imaLinkEntry 18 }

    imaLinkNeTxUnusableSec OBJECT-TYPE
	SYNTAX INTEGER
	ACCESS read-only
	STATUS mandatory
	DESCRIPTION
	  "Tx Unusable seconds: count of Unusable seconds at the near
	  end Tx LSM."
	::= { imaLinkEntry 19 }

    imaLinkNeRxUnusableSec OBJECT-TYPE
	SYNTAX INTEGER
	ACCESS read-only
	STATUS mandatory
	DESCRIPTION
	  "Rx Unusable seconds: count of Unusable seconds at the near
	  end Rx LSM."
	::= { imaLinkEntry 20 }

    imaLinkFeTxUnusableSec OBJECT-TYPE
	SYNTAX INTEGER
	ACCESS read-only
	STATUS mandatory
	DESCRIPTION
	  "Tx Unusable seconds at far-end: count of seconds with Unusable
	  indications from the far-end Tx LSM."
	::= { imaLinkEntry 21 }

    imaLinkFeRxUnusableSec OBJECT-TYPE
	SYNTAX INTEGER
	ACCESS read-only
	STATUS mandatory
	DESCRIPTION
	  "Rx Unusable seconds at far-end: count of seconds with Unusable
	  indications from the far-end Rx LSM."
	::= { imaLinkEntry 22 }

    imaLinkNeTxNumFailures OBJECT-TYPE
	SYNTAX INTEGER
	ACCESS read-only
	STATUS mandatory
	DESCRIPTION
	  "The number of times a near-end transmit failure alarm condition
	  has been entered on this link."
	::= { imaLinkEntry 23 }

    imaLinkNeRxNumFailures OBJECT-TYPE
	SYNTAX INTEGER
	ACCESS read-only
	STATUS mandatory
	DESCRIPTION
	  "The number of times a near-end receive failure alarm condition
	  has been entered on this link (i.e., LIF, LODS, Mis-Connected,
	  RDI-IMA)."
	::= { imaLinkEntry 24 }

    imaLinkFeTxNumFailures OBJECT-TYPE
	SYNTAX INTEGER
	ACCESS read-only
	STATUS mandatory
	DESCRIPTION
	  "The number of times a far-end transmit failure alarm condition
	  has been entered on this link. This is an optional attribute."
	::= { imaLinkEntry 25 }

    imaLinkFeRxNumFailures OBJECT-TYPE
	SYNTAX INTEGER
	ACCESS read-only
	STATUS mandatory
	DESCRIPTION
	  "The number of times a far-end receive failure alarm condition
	  has been entered on this link (i.e., LIF, LODS, Mis-Connected, 
	  RDI-IMA).  This is an optional attribute."
	::= { imaLinkEntry 26 }

    imaLinkTxStuffs OBJECT-TYPE
	SYNTAX INTEGER
	ACCESS read-only
	STATUS mandatory
	DESCRIPTION
	  "Counts of stuff events inserted in the transmit direction.
	  This is an optional attribute."
	::= { imaLinkEntry 27 }

    imaLinkRxStuffs OBJECT-TYPE
	SYNTAX INTEGER
	ACCESS read-only
	STATUS mandatory
	DESCRIPTION
	  "Counts of stuff events detected in the receive direction.
	  This is an optional attribute."
	::= { imaLinkEntry 28 }

    imaLinkRxTestPattern OBJECT-TYPE
	SYNTAX INTEGER (0..255)
	ACCESS read-only
	STATUS mandatory
	DESCRIPTION
	  "This object identifies the test pattern received in the
	  ICP Cell (octet 17) on the link during the IMA Test Pattern
	  Procedure.  This value then may be compared to the transmitted
	  test pattern."
	DEFVAL { 0 }
	::= { imaLinkEntry 29 }

    imaLinkTestProcStatus OBJECT-TYPE
	SYNTAX INTEGER {
	  disabled(1), 
	  operating(2),
	  linkFail(3)
	}
	ACCESS read-only
	STATUS mandatory
	DESCRIPTION
	  "This value indicates the current state of the Test Pattern
	  Procedure.  If the value is disabled(1), the test is not
	  running.  A value of operating(2) means the test is running
	  and no error has been found on this interface.  A value of
	  linkfail(3) means an error has been detected o this link
	  during the test.

	  Once an error occurs, the linkfail(3) value is latched until
	  either this object is read or until the imaGroupTestProcStatus
	  is moved to disabled(1).  Once read, if the error no longer
	  persists, a subsequent read will report the value operating(2)."
	DEFVAL { disabled }
	::= { imaLinkEntry 30 }

    imaLinkNumber OBJECT-TYPE
	SYNTAX INTEGER
	ACCESS read-only
	STATUS mandatory
	DESCRIPTION
	  "This corresponds to the link number on the IMA Group."
	::= { imaLinkEntry 31 }

    -- This group contains all informat specificly for
    -- Sonoma Systems DS1 adapter. It includes the configuration and
    -- some statistics information

    --  atmImaDs1Objects

    imaDs1Table  OBJECT-TYPE
        SYNTAX  SEQUENCE OF ImaDs1Entry
        ACCESS  not-accessible
        STATUS  mandatory
        DESCRIPTION
            "A table of physical layer configuration for the DS1
         interface"
        ::= { atmImaDs1Objects 1 }

    imaDs1Entry  OBJECT-TYPE
        SYNTAX  ImaDs1Entry
        ACCESS  not-accessible
        STATUS  mandatory
        DESCRIPTION
          "A entry in the table, containing information about the
           physical layer of a DS1 interface"
        INDEX  { imaDs1GroupIndex, imaDs1Index }
        ::= { imaDs1Table 1 }
    
    ImaDs1Entry ::= SEQUENCE {
	imaDs1Index 		  INTEGER,
	imaDs1GroupIndex 	  INTEGER,
	imaDs1ConfLoopback        INTEGER,
      	imaDs1ConfTxClockSelect   INTEGER,
      	imaDs1ConfLineCode   	  INTEGER,
      	imaDs1ConfFrameFormat     INTEGER,
      	imaDs1ConfCableLength     INTEGER,
	imaDs1ConfTxTimingRefLink INTEGER,
	imaDs1ConfScramble        INTEGER,
      	imaDs1StatsNoSignals      Counter,
      	imaDs1StatsAISDetects     Counter,
      	imaDs1StatsYelAlarmCount  Counter,
      	imaDs1StatsLCVErrors      Counter,
      	imaDs1StatsPCVErrors      Counter,
      	imaDs1StatsMOSErrors      Counter,
      	imaDs1StatsSyncLossCount  Counter,
      	imaDs1StatsHECErrors      Counter,
      	imaDs1StatsSignalLoss     INTEGER,
      	imaDs1StatsAISDetect      INTEGER,
      	imaDs1StatsYellowAlarm    INTEGER,
      	imaDs1StatsSyncLoss       INTEGER,
      	imaDs1StatsTxClockLoss    INTEGER,
      	imaDs1StatsErrSec         Counter,
      	imaDs1StatsLineErrSec     Counter,
      	imaDs1StatsErrFreeSec     Counter,
      	imaDs1StatsBurstErrSec    Counter,
      	imaDs1StatsSevErrSec      Counter,
      	imaDs1StatsConSevErrSec   Counter,
      	imaDs1StatsFailedSignal   Counter,
      	imaDs1StatsUnavailSec     Counter,
      	imaDs1StatsSevErrFramSec  Counter,
      	imaDs1StatsClearCounters  INTEGER,
	imaDs1DebugAddr           INTEGER,
	imaDs1DebugReadValue      INTEGER,
	imaDs1DebugWriteValue     INTEGER,
	imaDs1DebugRead           INTEGER,
	imaDs1PortNumber          INTEGER
    }

    imaDs1Index   OBJECT-TYPE
        SYNTAX  INTEGER
        ACCESS  read-only
        STATUS  mandatory
        DESCRIPTION
            "The physical interface index."
        ::= { imaDs1Entry 1 }

    imaDs1GroupIndex OBJECT-TYPE
        SYNTAX  INTEGER
        ACCESS  read-only
        STATUS  mandatory
        DESCRIPTION
            "The IMA Group's interface index."
        ::= { imaDs1Entry 2 }

    imaDs1ConfLoopback OBJECT-TYPE
        SYNTAX  INTEGER { 
                        none(1),
                        payload(2), 
                        line(3),
			local(4)
                        }
        ACCESS  read-write
        STATUS  mandatory
        DESCRIPTION
	    "This object is used to modify the state of internal 
	    loopback...."
          DEFVAL { none }
        ::= { imaDs1Entry 3 }

    imaDs1ConfTxClockSelect OBJECT-TYPE
        SYNTAX  INTEGER {
                        internal(1), 
                        recovered(2) 
                        }
        ACCESS  read-write
        STATUS  mandatory
        DESCRIPTION
            "Configure the transmit clock."
            DEFVAL { recovered }
        ::= { imaDs1Entry 4 }

    imaDs1ConfLineCode OBJECT-TYPE
        SYNTAX  INTEGER {
                        b8zs(1), 
                        ami(2) 
                        } 
        ACCESS  read-only
        STATUS  mandatory
        DESCRIPTION
            "Configure the line coding method."
            DEFVAL { b8zs }
        ::= { imaDs1Entry 5 }

    imaDs1ConfFrameFormat OBJECT-TYPE
        SYNTAX  INTEGER {
                        sf(1), 
                        esf(2) 
                        } 
        ACCESS  read-only
        STATUS  mandatory
        DESCRIPTION
            "Configure the framing format."
            DEFVAL { esf }
        ::= { imaDs1Entry 6 }

    imaDs1ConfCableLength OBJECT-TYPE
        SYNTAX  INTEGER {
                        short-haul-0-133-FT(1), 
                        short-haul-133-266-FT(2),
                        short-haul-266-399-FT(3),
                        short-haul-399-533-FT(4),
                        short-haul-533-655-FT(5),
                        long-haul-0-0-dB(6),
			long-haul-7-5-dB(7),
			long-haul-15-0-dB(8),
			long-haul-22-5-dB(9)
                        }
        ACCESS  read-write
        STATUS  mandatory
        DESCRIPTION
            "Configure the cable length."
            DEFVAL { short-haul-0-133-FT }
        ::= { imaDs1Entry 7 }

    imaDs1ConfTxTimingRefLink OBJECT-TYPE
	SYNTAX INTEGER
	ACCESS read-only
	STATUS mandatory
	DESCRIPTION
	  "The ifIndex of the transmit timing reference link to
	  be used by the near-end for IMA data cell clock recovery from
	  the ATM layer."
	::= { imaDs1Entry 8 }

    imaDs1ConfScramble OBJECT-TYPE
	SYNTAX INTEGER {
                        on(1), 
                        off(2) 
                        }
	ACCESS read-only
	STATUS mandatory
	DESCRIPTION
	  "The cells are scrambled / de-scrambled on the line."
	  DEFVAL { off }
	::= { imaDs1Entry 9 }

    imaDs1StatsNoSignals  OBJECT-TYPE
        SYNTAX  Counter
        ACCESS  read-only
        STATUS  mandatory
        DESCRIPTION
            "No signal error counter."
        ::= { imaDs1Entry 10 }

    imaDs1StatsAISDetects  OBJECT-TYPE
        SYNTAX  Counter
        ACCESS  read-only
        STATUS  mandatory
        DESCRIPTION
            "AIS Detect counter."
        ::= {imaDs1Entry 11 }
    
    imaDs1StatsYelAlarmCount  OBJECT-TYPE
        SYNTAX  Counter
        ACCESS  read-only
        STATUS  mandatory
        DESCRIPTION
            "A count of the number of Yellow Alarms."
        ::= { imaDs1Entry 12 }

    imaDs1StatsLCVErrors  OBJECT-TYPE
        SYNTAX  Counter
        ACCESS  read-only
        STATUS  mandatory
        DESCRIPTION
            "LCV (Line Code Violation) error counter."
        ::= { imaDs1Entry 13 }

    imaDs1StatsPCVErrors  OBJECT-TYPE
        SYNTAX  Counter
        ACCESS  read-only
        STATUS  mandatory
        DESCRIPTION
            "PCV (Path Code Violation) error counter."
        ::= { imaDs1Entry 14 }

    imaDs1StatsMOSErrors  OBJECT-TYPE
        SYNTAX  Counter
        ACCESS  read-only
        STATUS  mandatory
        DESCRIPTION
            "Multiframe out of sync error counter."
        ::= { imaDs1Entry 15 }

    imaDs1StatsSyncLossCount  OBJECT-TYPE
        SYNTAX  Counter
        ACCESS  read-only
        STATUS  mandatory
        DESCRIPTION
            "Sync Loss counter."
        ::= { imaDs1Entry 16 }

    imaDs1StatsHECErrors  OBJECT-TYPE
        SYNTAX  Counter
        ACCESS  read-only
        STATUS  mandatory
        DESCRIPTION
            "HEC error counter."
        ::= { imaDs1Entry 17 }

    imaDs1StatsSignalLoss  OBJECT-TYPE
        SYNTAX  INTEGER {
                        true (1), 
                        false (2)
                        }
        ACCESS  read-only
        STATUS  mandatory
        DESCRIPTION
            "Signal loss indication."
        ::= { imaDs1Entry 18 }

    imaDs1StatsAISDetect  OBJECT-TYPE
        SYNTAX  INTEGER {
                        true (1), 
                        false (2)
                        }
        ACCESS  read-only
        STATUS  mandatory
        DESCRIPTION
            "AIS indication."
        ::= { imaDs1Entry 19 }

    imaDs1StatsYellowAlarm  OBJECT-TYPE
        SYNTAX  INTEGER {
                        true (1), 
                        false (2)
                        }
        ACCESS  read-only
        STATUS  mandatory
        DESCRIPTION
            "Yellow Alarm indication."
        ::= { imaDs1Entry 20 }

    imaDs1StatsSyncLoss  OBJECT-TYPE
        SYNTAX  INTEGER {
                        true (1), 
                        false (2)
                        }
        ACCESS  read-only
        STATUS  mandatory
        DESCRIPTION
            "Loss of sync indication."
        ::= { imaDs1Entry 21 }

    imaDs1StatsTxClockLoss  OBJECT-TYPE
        SYNTAX  INTEGER {
                        true (1), 
                        false (2)
                        }
        ACCESS  read-only
        STATUS  mandatory
        DESCRIPTION
            "Loss of transmit clock indication."
        ::= { imaDs1Entry 22 }

    imaDs1StatsErrSec  OBJECT-TYPE
        SYNTAX  Counter
        ACCESS  read-only
        STATUS  mandatory
        DESCRIPTION
            "Count of Errored Seconds."
        ::= { imaDs1Entry 23 }

    imaDs1StatsLineErrSec  OBJECT-TYPE
        SYNTAX  Counter
        ACCESS  read-only
        STATUS  mandatory
        DESCRIPTION
            "Count of Line Errored Seconds."
        ::= { imaDs1Entry 24 }

    imaDs1StatsErrFreeSec  OBJECT-TYPE
        SYNTAX  Counter
        ACCESS  read-only
        STATUS  mandatory
        DESCRIPTION
            "Count of Error Free Seconds."
        ::= { imaDs1Entry 25 }

    imaDs1StatsBurstErrSec  OBJECT-TYPE
        SYNTAX  Counter
        ACCESS  read-only
        STATUS  mandatory
        DESCRIPTION
            "Count of Bursty Errored Seconds."
        ::= { imaDs1Entry 26 }

    imaDs1StatsSevErrSec  OBJECT-TYPE
        SYNTAX  Counter
        ACCESS  read-only
        STATUS  mandatory
        DESCRIPTION
            "Count of Severely Errored Seconds."
        ::= { imaDs1Entry 27 }

    imaDs1StatsConSevErrSec  OBJECT-TYPE
        SYNTAX  Counter
        ACCESS  read-only
        STATUS  mandatory
        DESCRIPTION
            "Count of Consecutive Severely Errored Seconds."
        ::= { imaDs1Entry 28 }

    imaDs1StatsFailedSignal  OBJECT-TYPE
        SYNTAX  Counter
        ACCESS  read-only
        STATUS  mandatory
        DESCRIPTION
            "Count of Failed Signal conditions."
        ::= { imaDs1Entry 29 }

    imaDs1StatsUnavailSec  OBJECT-TYPE
        SYNTAX  Counter
        ACCESS  read-only
        STATUS  mandatory
        DESCRIPTION
            "Count of unavailable secondss."
        ::= { imaDs1Entry 30 }

    imaDs1StatsSevErrFramSec  OBJECT-TYPE
        SYNTAX  Counter
        ACCESS  read-only
        STATUS  mandatory
        DESCRIPTION
            "Count of Severely Errored Framing Seconds."
        ::= { imaDs1Entry 31 }

    imaDs1StatsClearCounters  OBJECT-TYPE
        SYNTAX  INTEGER {
                        true (1), 
                        false (2)
                        }
        ACCESS  read-write
        STATUS  mandatory
        DESCRIPTION
            "Clear all counters in this group ONLY."
        DEFVAL { false }
        ::= { imaDs1Entry 32 }

    imaDs1DebugAddr  OBJECT-TYPE
        SYNTAX  INTEGER 
        ACCESS  read-write
        STATUS  mandatory
        DESCRIPTION
            "PCI Phy address for DS1 port register."
        DEFVAL { 0 }
        ::= { imaDs1Entry 33 }

    imaDs1DebugReadValue  OBJECT-TYPE
        SYNTAX  INTEGER 
        ACCESS  read-write
        STATUS  mandatory
        DESCRIPTION
            "Value read from DS1 port register."
        DEFVAL { 0 }
        ::= { imaDs1Entry 34 }

    imaDs1DebugWriteValue  OBJECT-TYPE
        SYNTAX  INTEGER 
        ACCESS  read-write
        STATUS  mandatory
        DESCRIPTION
            "Value written to DS1 port register."
        DEFVAL { 0 }
        ::= { imaDs1Entry 35 }

    imaDs1DebugRead  OBJECT-TYPE
        SYNTAX  INTEGER 
        ACCESS  read-write
        STATUS  mandatory
        DESCRIPTION
            "Read or Write of DS1 port register (TRUE = READ)."
        DEFVAL { 1 }
        ::= { imaDs1Entry 36 }

    imaDs1PortNumber   OBJECT-TYPE
        SYNTAX  INTEGER
        ACCESS  read-only
        STATUS  mandatory
        DESCRIPTION
            "The port number on the IMA."
        ::= { imaDs1Entry 37 }

    -- This group contains all informat specificly for
    -- Sonoma Systems E1 adapter. It includes the configuration and
    -- some statistics information

    --  atmImaE1Objects

    imaE1Table  OBJECT-TYPE
        SYNTAX  SEQUENCE OF ImaE1Entry
        ACCESS  not-accessible
        STATUS  mandatory
        DESCRIPTION
            "A table of physical layer configuration for the E1
         interface"
        ::= { atmImaE1Objects 1 }

    imaE1Entry  OBJECT-TYPE
        SYNTAX  ImaE1Entry
        ACCESS  not-accessible
        STATUS  mandatory
        DESCRIPTION
          "A entry in the table, containing information about the
           physical layer of a E1 interface"
        INDEX  { imaE1GroupIndex, imaE1Index }
        ::= { imaE1Table 1 }
    
    ImaE1Entry ::= SEQUENCE {
	imaE1Index 		 INTEGER,
	imaE1GroupIndex 	 INTEGER,
	imaE1ConfLoopback        INTEGER,
      	imaE1ConfTxClockSelect   INTEGER,
      	imaE1ConfLineCode   	 INTEGER,
      	imaE1ConfFrameFormat     INTEGER,
      	imaE1ConfCableLength     INTEGER,
	imaE1ConfTxTimingRefLink INTEGER,
	imaE1ConfScramble        INTEGER,
      	imaE1StatsNoSignals      Counter,
      	imaE1StatsRAIDetects     Counter,
      	imaE1StatsFASErrors      Counter,
      	imaE1StatsCVErrors       Counter,
      	imaE1StatsCRCErrors      Counter,
      	imaE1StatsEBitErrors     Counter,
      	imaE1StatsSyncLossCount  Counter,
      	imaE1StatsHECErrors      Counter,
      	imaE1StatsSignalLoss     INTEGER,
      	imaE1StatsRAIDetect      INTEGER,
      	imaE1StatsSyncLoss       INTEGER,
      	imaE1StatsTxClockLoss    INTEGER,
      	imaE1StatsErrSec         Counter,
      	imaE1StatsLineErrSec     Counter,
      	imaE1StatsErrFreeSec     Counter,
      	imaE1StatsBurstErrSec    Counter,
      	imaE1StatsSevErrSec      Counter,
      	imaE1StatsConSevErrSec   Counter,
      	imaE1StatsFailedSignal   Counter,
      	imaE1StatsUnavailSec     Counter,
      	imaE1StatsSevErrFramSec  Counter,
      	imaE1StatsClearCounters  INTEGER,
	imaE1DebugAddr           INTEGER,
	imaE1DebugReadValue      INTEGER,
	imaE1DebugWriteValue     INTEGER,
	imaE1DebugRead           INTEGER,
	imaE1PortNumber		 INTEGER
    }

    imaE1Index   OBJECT-TYPE
        SYNTAX  INTEGER
        ACCESS  read-only
        STATUS  mandatory
        DESCRIPTION
            "The physical interface index."
        ::= { imaE1Entry 1 }

    imaE1GroupIndex OBJECT-TYPE
        SYNTAX  INTEGER
        ACCESS  read-only
        STATUS  mandatory
        DESCRIPTION
            "The IMA Group's interface index."
        ::= { imaE1Entry 2 }

    imaE1ConfLoopback OBJECT-TYPE
        SYNTAX  INTEGER { 
                        disabled(1),
                        internal(2), 
                        external(3)
                        }
        ACCESS  read-write
        STATUS  mandatory
        DESCRIPTION
            "This object is used to modify the state of internal
             loopback...."
          DEFVAL { disabled }
        ::= { imaE1Entry 3 }

    imaE1ConfTxClockSelect OBJECT-TYPE
        SYNTAX  INTEGER {
                        internal(1), 
                        recovered(2) 
                        } 
        ACCESS  read-write
        STATUS  mandatory
        DESCRIPTION
            "Configure the transmit clock."
            DEFVAL { internal }
        ::= { imaE1Entry 4 }

    imaE1ConfLineCode OBJECT-TYPE
        SYNTAX  INTEGER {
                        hdb3(1), 
                        ami(2) 
                        } 
        ACCESS  read-only
        STATUS  mandatory
        DESCRIPTION
            "Configure the line coding method."
            DEFVAL { hdb3 }
        ::= { imaE1Entry 5 }

    imaE1ConfFrameFormat OBJECT-TYPE
        SYNTAX  INTEGER {
                        crc4-enabled(1), 
                        crc4-disabled(2) 
                        } 
        ACCESS  read-only
        STATUS  mandatory
        DESCRIPTION
            "Configure the framing format."
            DEFVAL { crc4-enabled }
        ::= { imaE1Entry 6 }

    imaE1ConfCableLength OBJECT-TYPE
        SYNTAX  INTEGER {
                        short-haul(1),
                        long-haul(2), 
                        long-haul-75(3)
                        } 
        ACCESS  read-write
        STATUS  mandatory
        DESCRIPTION
            "Configure Long or Short Haul."
            DEFVAL { short-haul }
        ::= { imaE1Entry 7 }

    imaE1ConfTxTimingRefLink OBJECT-TYPE
	SYNTAX INTEGER
	ACCESS read-only
	STATUS mandatory
	DESCRIPTION
	  "The ifIndex of the transmit timing reference link to
	  be used by the near-end for IMA data cell clock recovery from
	  the ATM layer."
	::= { imaE1Entry 8 }

    imaE1ConfScramble OBJECT-TYPE
	SYNTAX INTEGER {
                        on(1), 
                        off(2) 
                        }
	ACCESS read-only
	STATUS mandatory
	DESCRIPTION
	  "The cells are scrambled / de-scrambled on the line."
            DEFVAL { on }
	::= { imaE1Entry 9 }

    imaE1StatsNoSignals  OBJECT-TYPE
        SYNTAX  Counter
        ACCESS  read-only
        STATUS  mandatory
        DESCRIPTION
            "No signal error counter."
        ::= { imaE1Entry 10 }

    imaE1StatsRAIDetects  OBJECT-TYPE
        SYNTAX  Counter
        ACCESS  read-only
        STATUS  mandatory
        DESCRIPTION
            "RAI Detect counter."
        ::= {imaE1Entry 11 }

    imaE1StatsFASErrors  OBJECT-TYPE
        SYNTAX  Counter
        ACCESS  read-only
        STATUS  mandatory
        DESCRIPTION
            "FAS (Frame Alignment Signal) error counter."
        ::= { imaE1Entry 12 }

    imaE1StatsCVErrors  OBJECT-TYPE
        SYNTAX  Counter
        ACCESS  read-only
        STATUS  mandatory
        DESCRIPTION
            "CV (Code Violation) error counter."
        ::= { imaE1Entry 13 }

    imaE1StatsCRCErrors  OBJECT-TYPE
        SYNTAX  Counter
        ACCESS  read-only
        STATUS  mandatory
        DESCRIPTION
            "CRC4 error counter."
        ::= { imaE1Entry 14 }

    imaE1StatsEBitErrors  OBJECT-TYPE
        SYNTAX  Counter
        ACCESS  read-only
        STATUS  mandatory
        DESCRIPTION
            "E-Bit (FEBE) error counter."
        ::= { imaE1Entry 15 }

    imaE1StatsSyncLossCount  OBJECT-TYPE
        SYNTAX  Counter
        ACCESS  read-only
        STATUS  mandatory
        DESCRIPTION
            "Sync Loss counter."
        ::= { imaE1Entry 16 }

    imaE1StatsHECErrors  OBJECT-TYPE
        SYNTAX  Counter
        ACCESS  read-only
        STATUS  mandatory
        DESCRIPTION
            "HEC error counter."
        ::= { imaE1Entry 17 }

    imaE1StatsSignalLoss  OBJECT-TYPE
        SYNTAX  INTEGER {
                        true (1), 
                        false (2)
                        }
        ACCESS  read-only
        STATUS  mandatory
        DESCRIPTION
            "Signal loss indication."
        ::= { imaE1Entry 18 }

    imaE1StatsRAIDetect  OBJECT-TYPE
        SYNTAX  INTEGER {
                        true (1), 
                        false (2)
                        }
        ACCESS  read-only
        STATUS  mandatory
        DESCRIPTION
            "RAI indication."
        ::= { imaE1Entry 19 }

    imaE1StatsSyncLoss  OBJECT-TYPE
        SYNTAX  INTEGER {
                        true (1), 
                        false (2)
                        }
        ACCESS  read-only
        STATUS  mandatory
        DESCRIPTION
            "Loss of sync indication."
        ::= { imaE1Entry 20 }

    imaE1StatsTxClockLoss  OBJECT-TYPE
        SYNTAX  INTEGER {
                        true (1), 
                        false (2)
                        }
        ACCESS  read-only
        STATUS  mandatory
        DESCRIPTION
            "Loss of transmit clock indication."
        ::= { imaE1Entry 21 }

    imaE1StatsErrSec  OBJECT-TYPE
        SYNTAX  Counter
        ACCESS  read-only
        STATUS  mandatory
        DESCRIPTION
            "Count of Errored Seconds."
        ::= { imaE1Entry 22 }

    imaE1StatsLineErrSec  OBJECT-TYPE
        SYNTAX  Counter
        ACCESS  read-only
        STATUS  mandatory
        DESCRIPTION
            "Count of Line Errored Seconds."
        ::= { imaE1Entry 23 }

    imaE1StatsErrFreeSec  OBJECT-TYPE
        SYNTAX  Counter
        ACCESS  read-only
        STATUS  mandatory
        DESCRIPTION
            "Count of Error Free Seconds."
        ::= { imaE1Entry 24 }

    imaE1StatsBurstErrSec  OBJECT-TYPE
        SYNTAX  Counter
        ACCESS  read-only
        STATUS  mandatory
        DESCRIPTION
            "Count of Bursty Errored Seconds."
        ::= { imaE1Entry 25 }

    imaE1StatsSevErrSec  OBJECT-TYPE
        SYNTAX  Counter
        ACCESS  read-only
        STATUS  mandatory
        DESCRIPTION
            "Count of Severely Errored Seconds."
        ::= { imaE1Entry 26 }

    imaE1StatsConSevErrSec  OBJECT-TYPE
        SYNTAX  Counter
        ACCESS  read-only
        STATUS  mandatory
        DESCRIPTION
            "Count of Consecutive Severely Errored Seconds."
        ::= { imaE1Entry 27 }

    imaE1StatsFailedSignal  OBJECT-TYPE
        SYNTAX  Counter
        ACCESS  read-only
        STATUS  mandatory
        DESCRIPTION
            "Count of Failed Signal conditions."
        ::= { imaE1Entry 28 }

    imaE1StatsUnavailSec  OBJECT-TYPE
        SYNTAX  Counter
        ACCESS  read-only
        STATUS  mandatory
        DESCRIPTION
            "Count of unavailable secondss."
        ::= { imaE1Entry 29 }

    imaE1StatsSevErrFramSec  OBJECT-TYPE
        SYNTAX  Counter
        ACCESS  read-only
        STATUS  mandatory
        DESCRIPTION
            "Count of Severely Errored Framing Seconds."
        ::= { imaE1Entry 30 }

    imaE1StatsClearCounters  OBJECT-TYPE
        SYNTAX  INTEGER {
                        true (1), 
                        false (2)
                        }
        ACCESS  read-write
        STATUS  mandatory
        DESCRIPTION
            "Clear all counters in this group ONLY."
        DEFVAL { false }
        ::= { imaE1Entry 31 }

    imaE1DebugAddr  OBJECT-TYPE
        SYNTAX  INTEGER 
        ACCESS  read-write
        STATUS  mandatory
        DESCRIPTION
            "PCI Phy address for E1 port register."
        DEFVAL { 0 }
        ::= { imaE1Entry 32 }

    imaE1DebugReadValue  OBJECT-TYPE
        SYNTAX  INTEGER 
        ACCESS  read-write
        STATUS  mandatory
        DESCRIPTION
            "Value read from E1 port register."
        DEFVAL { 0 }
        ::= { imaE1Entry 33 }

    imaE1DebugWriteValue  OBJECT-TYPE
        SYNTAX  INTEGER 
        ACCESS  read-write
        STATUS  mandatory
        DESCRIPTION
            "Value written to E1 port register."
        DEFVAL { 0 }
        ::= { imaE1Entry 34 }

    imaE1DebugRead  OBJECT-TYPE
        SYNTAX  INTEGER 
        ACCESS  read-write
        STATUS  mandatory
        DESCRIPTION
            "Read or Write of E1 port register (TRUE = READ)."
        DEFVAL { 1 }
        ::= { imaE1Entry 35 }

    imaE1PortNumber   OBJECT-TYPE
        SYNTAX  INTEGER
        ACCESS  read-only
        STATUS  mandatory
        DESCRIPTION
            "The port number on the IMA."
        ::= { imaE1Entry 36 }

    END
