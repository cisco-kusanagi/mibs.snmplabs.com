-- ****************************************************************************
--
--                 Funk Steel-Belted RADIUS Server Traps
--         Management Information Base for SNMP Network Management
--
--
--      Copyright 1999, Funk Software Inc.
--      All Rights Reserved.
--
--      The SBR Traps MIB defines the contents of the traps that can be issued
--      by the SBR server.
--
--      The Funk Enterprise number is 1411.
--      The ASN.1 prefix to, and including the Funk Enterprise is:
--           1.3.6.1.4.1.1411
--
-- ****************************************************************************

-- Please note, all traps can be suppressed by configuring RADIUS appropriately.
-- Please see the Radius administrator's manual for more details about trap suppression.
--

FNKSBRTR-MIB DEFINITIONS ::= BEGIN

    IMPORTS
        enterprises             FROM RFC1155-SMI
        OBJECT-TYPE             FROM RFC-1212
        SnmpAdminString         FROM SNMP-FRAMEWORK-MIB
        TRAP-TYPE               FROM RFC-1215;


    funk              OBJECT IDENTIFIER ::= { enterprises 1411 }
    funkSbr           OBJECT IDENTIFIER ::= { funk 1 }
    funkSbrTraps      OBJECT IDENTIFIER ::= { funkSbr 1 }
    funkSbrTrapVars   OBJECT IDENTIFIER ::= { funkSbrTraps 1 }


-- ****************************************************************************
--  Trap Variable Definitions
-- ****************************************************************************

    funkSbrTrapVarComp OBJECT-TYPE
        SYNTAX  INTEGER {
            core(1),             -- core SBR infrastructure
            accounting(2),       -- SBR accounting server
            authentication(3)    -- SBR authentication server
            }
        ACCESS  not-accessible
        STATUS  optional
        DESCRIPTION
                "The component within the SBR server that issued the trap."
        ::= { funkSbrTrapVars 1 }

    funkSbrTrapVarSev OBJECT-TYPE
        SYNTAX  INTEGER {
            informational(1),    -- the trap is informational
            warning(2),          -- the trap is a warning
            error(3)             -- the trap is an error
            }
        ACCESS  not-accessible
        STATUS  optional
        DESCRIPTION
                "The severity of the event that caused the trap."
        ::= { funkSbrTrapVars 2 }

    funkSbrTrapVarSWName OBJECT-TYPE
        SYNTAX  SnmpAdminString (SIZE (0..255))
        ACCESS  not-accessible
        STATUS  optional
        DESCRIPTION
                "The identity of the software that is the RADIUS server."
        ::= { funkSbrTrapVars 3 }

    funkSbrTrapVarThreadsAvail OBJECT-TYPE
        SYNTAX  SnmpAdminString (SIZE (0..10))
        ACCESS  not-accessible
        STATUS  optional
        DESCRIPTION
                "The number of threads available in the thread worker pool."
        ::= { funkSbrTrapVars 4 }

    funkSbrTrapVarBytesAvail OBJECT-TYPE
        SYNTAX  SnmpAdminString (SIZE (0..32))
        ACCESS  not-accessible
        STATUS  optional
        DESCRIPTION
                "The number of bytes available in the file system."
        ::= { funkSbrTrapVars 5 }

    funkSbrTrapVarPrivateDir OBJECT-TYPE
        SYNTAX  SnmpAdminString (SIZE (0..255))
        ACCESS  not-accessible
        STATUS  optional
        DESCRIPTION
                "The file system path to the private directory used by the
                 RADIUS server."
        ::= { funkSbrTrapVars 6 }

    funkSbrTrapVarNumberOfOccurrences OBJECT-TYPE
        SYNTAX  SnmpAdminString (SIZE (0..10))
        ACCESS  not-accessible
        STATUS  optional
        DESCRIPTION
                "The dilution factor for the trap. The trap is sent on once for
                 every 'n' occurrences of this event."
        ::= { funkSbrTrapVars 7 }

    funkSbrTrapVarSQLConnects OBJECT-TYPE
        SYNTAX  SnmpAdminString (SIZE (0..10))
        ACCESS  not-accessible
        STATUS  optional
        DESCRIPTION
                "The number of connection attempts to a SQL database."
        ::= { funkSbrTrapVars 8 }

    funkSbrTrapVarSQLDisconnects OBJECT-TYPE
        SYNTAX  SnmpAdminString (SIZE (0..10))
        ACCESS  not-accessible
        STATUS  optional
        DESCRIPTION
                "The number of disconnects from a SQL database (due to an
                 error encountered during an operation)."
        ::= { funkSbrTrapVars 9 }

    funkSbrTrapVarSQLTimeouts OBJECT-TYPE
        SYNTAX  SnmpAdminString (SIZE (0..10))
        ACCESS  not-accessible
        STATUS  optional
        DESCRIPTION
                "The number of timeouts encountered when trying to perform
                 a transaction against a SQL database."
        ::= { funkSbrTrapVars 10 }

    funkSbrTrapVarServiceDispatcherErrCode OBJECT-TYPE
        SYNTAX  SnmpAdminString (SIZE (0..10))
        ACCESS  not-accessible
        STATUS  optional
        DESCRIPTION
                "The error code returned in response to an attempt to start
                 the RADIUS service on Windows NT."
        ::= { funkSbrTrapVars 11 }

    funkSbrTrapVarSetStatusErrCode OBJECT-TYPE
        SYNTAX  SnmpAdminString (SIZE (0..10))
        ACCESS  not-accessible
        STATUS  optional
        DESCRIPTION
                "The error code returned in response to an attempt to inform
                 the service control dispatcher of the status of the RADIUS
                 service on Windows NT."
        ::= { funkSbrTrapVars 12 }

    funkSbrTrapVarGetDiskFreeSpaceErrCode OBJECT-TYPE
        SYNTAX  SnmpAdminString (SIZE (0..10))
        ACCESS  not-accessible
        STATUS  optional
        DESCRIPTION
                "The error code returned in response to an attempt to call
                 GetDiskFreeSpaceEx to determine the amount of free disk space
                 available on Windows NT."
        ::= { funkSbrTrapVars 13 }

    funkSbrTrapVarIniString OBJECT-TYPE
        SYNTAX  SnmpAdminString (SIZE (0..255))
        ACCESS  not-accessible
        STATUS  optional
        DESCRIPTION
                "The INI file setting used to specify a configuration value."
        ::= { funkSbrTrapVars 14 }

    funkSbrTrapVarDbType OBJECT-TYPE
        SYNTAX  SnmpAdminString (SIZE (0..255))
        ACCESS  not-accessible
        STATUS  optional
        DESCRIPTION
                "The type of database being employed by the RADIUS server."
        ::= { funkSbrTrapVars 15 }

    funkSbrTrapVarFailedSystemName OBJECT-TYPE
	SYNTAX  SnmpAdminString (SIZE (0..255))
	ACCESS  not-accessible
	STATUS  optional
	DESCRIPTION
		"The name of the remote system failing 
		 connectivity from the radius server."
	::= {funkSbrTrapVars 16 }

    funkSbrTrapVarUserName OBJECT-TYPE
	SYNTAX  SnmpAdminString (SIZE (0..255))
	ACCESS  not-accessible
	STATUS  optional
	DESCRIPTION
		"The name of the user to whom the trap
                 refers."
	::= {funkSbrTrapVars 17 }

    funkSbrTrapVarPersistStoreName OBJECT-TYPE
	SYNTAX  SnmpAdminString (SIZE (0..255))
	ACCESS  not-accessible
	STATUS  optional
	DESCRIPTION
		"The name of the persistent storage to which the trap refers."
	::= {funkSbrTrapVars 18 }

    funkSbrTrapVarDiagnosticMessage OBJECT-TYPE
	SYNTAX  SnmpAdminString (SIZE (0..255))
	ACCESS  not-accessible
	STATUS  optional
	DESCRIPTION
		"A generic diagnostic message that may be helpful in determining
        and addressing the possible root causes of the trap." 
	::= {funkSbrTrapVars 19 }

    funkSbrTrapVarIPAddrPoolName OBJECT-TYPE
	SYNTAX  SnmpAdminString (SIZE (0..255))
	ACCESS  not-accessible
	STATUS  optional
	DESCRIPTION
		"The name of the IP address pool to which the trap refers."
	::= {funkSbrTrapVars 20 }

    funkSbrTrapVarIPAddrAvail OBJECT-TYPE
	SYNTAX  SnmpAdminString (SIZE (0..255))
	ACCESS  not-accessible
	STATUS  optional
	DESCRIPTION
		"The number of addresses available in the IP address pool."
	::= {funkSbrTrapVars 21 }


-- ****************************************************************************
--  Trap Definitions
-- ****************************************************************************


-- ***************************** Informational ********************************

    funkSbrTrapServiceStarted TRAP-TYPE
        ENTERPRISE funkSbrTraps
        VARIABLES { funkSbrTrapVarComp, funkSbrTrapVarSev, 
                    funkSbrTrapVarSWName }
        DESCRIPTION
            "This trap will be sent when the RADIUS server is started."
        ::= 100

    funkSbrTrapServiceStopped TRAP-TYPE
        ENTERPRISE funkSbrTraps
        VARIABLES { funkSbrTrapVarComp, funkSbrTrapVarSev, 
                    funkSbrTrapVarSWName }
        DESCRIPTION
            "This trap will be sent when the RADIUS server is stopped."
        ::= 101

    funkSbrTrapThreadsNormal TRAP-TYPE
        ENTERPRISE funkSbrTraps
        VARIABLES { funkSbrTrapVarComp, funkSbrTrapVarSev, 
                    funkSbrTrapVarThreadsAvail }
        DESCRIPTION
            "This trap will be sent when the the number of available threads
             in the accounting or authentication server has risen above a
             specified threshold."
        ::= 102

    funkSbrTrapFSNormal TRAP-TYPE
        ENTERPRISE funkSbrTraps
        VARIABLES { funkSbrTrapVarComp, funkSbrTrapVarSev, 
                    funkSbrTrapVarBytesAvail }
        DESCRIPTION
            "This trap will be sent when the the number of bytes available
             in the file system from which the server is running has risen
             above a specified threshold."
        ::= 103

    funkSbrTrapConcurrencyReconnect TRAP-TYPE
        ENTERPRISE funkSbrTraps
        VARIABLES { funkSbrTrapVarComp, funkSbrTrapVarSev, 
                    funkSbrTrapVarFailedSystemName }
        DESCRIPTION
            "This trap will be sent when Radius reconnects to the concurrency 
             server after it has sent a ConcurrencyFailure, ConcurrentyTimeout,
             or ConcurrencyLocalProxyFailure trap."
        ::= 104

    funkSbrTrapSQLReconnect TRAP-TYPE
        ENTERPRISE funkSbrTraps
        VARIABLES { funkSbrTrapVarComp, funkSbrTrapVarSev, 
                    funkSbrTrapVarFailedSystemName }
        DESCRIPTION
            "This trap will be sent when Radius reconnects to the SQL
	     database after it has sent a SQLConnectFail trap."
        ::= 105

    funkSbrTrapLDAPReconnect TRAP-TYPE
        ENTERPRISE funkSbrTraps
        VARIABLES { funkSbrTrapVarComp, funkSbrTrapVarSev, 
                    funkSbrTrapVarFailedSystemName }
        DESCRIPTION
            "This trap will be sent when Radius reconnects to the LDAP
	     server after it has sent a LDAPConnectFail trap."
        ::= 106

    funkSbrTrapUserAccountLocked TRAP-TYPE
        ENTERPRISE funkSbrTraps
        VARIABLES { funkSbrTrapVarComp, funkSbrTrapVarSev,
                    funkSbrTrapVarUserName }
        DESCRIPTION
            "This trap will be sent when a user's account becomes locked out
             due to an excessive number of rejected authentication attempts
             within a defined period of time."
        ::= 107

    funkSbrTrapUserAccountReleased TRAP-TYPE
        ENTERPRISE funkSbrTraps
        VARIABLES { funkSbrTrapVarComp, funkSbrTrapVarSev,
                    funkSbrTrapVarUserName }
        DESCRIPTION
            "This trap will be sent when a user's account, previously locked 
             out due to an excessive number of rejected authentication attempts,
             becomes unlocked."
        ::= 108

    funkSbrTrapProxySpoolReconnect TRAP-TYPE
        ENTERPRISE funkSbrTraps
        VARIABLES { funkSbrTrapVarComp, funkSbrTrapVarSev,
                    funkSbrTrapVarFailedSystemName }
        DESCRIPTION
            "This trap will be sent when the proxy accounting spooler reconnects 
			to the target realm after it has sent a ProxySpoolTimeout trap."
        ::= 109

    funkSbrTrapIPAddrPoolNormal TRAP-TYPE
        ENTERPRISE funkSbrTraps
        VARIABLES { funkSbrTrapVarComp, funkSbrTrapVarSev, 
                    funkSbrTrapVarIPAddrPoolName,
                    funkSbrTrapVarIPAddrAvail }
        DESCRIPTION
            "This trap will be sent when the number of available IP addresses
            in any pool has risen above a specified threshold."
        ::= 110

-- ******************************* Warnings ***********************************

    funkSbrTrapCmdArgBadPrivDir TRAP-TYPE
        ENTERPRISE funkSbrTraps
        VARIABLES { funkSbrTrapVarComp, funkSbrTrapVarSev, 
                    funkSbrTrapVarPrivateDir }
        DESCRIPTION
            "This trap will be sent when an invalid private directory is
             specified on the command line used to launch the RADIUS server.
             The command line option is ignored."
        ::= 5000

    funkSbrTrapLowThreads TRAP-TYPE
        ENTERPRISE funkSbrTraps
        VARIABLES { funkSbrTrapVarComp, funkSbrTrapVarSev, 
                    funkSbrTrapVarThreadsAvail }
        DESCRIPTION
            "This trap will be sent when the count of threads available for the
             accounting or authentication server drops below a configurable
             threshold. An informational trap is sent when the count of
             available threads (at some future point) rises to an acceptable
             level."
        ::= 5001

    funkSbrTrapConcurrencyFailure TRAP-TYPE
        ENTERPRISE funkSbrTraps
        VARIABLES { funkSbrTrapVarComp, funkSbrTrapVarSev, 
                    funkSbrTrapVarNumberOfOccurrences }
        DESCRIPTION
            "This trap will be sent when communications with the RADIUS
             concurrency server fails. The trap is 'diluted', i.e. it is sent
             only once for every 'n' occurrences of the failure."
        ::= 5002

    funkSbrTrapConcurrencyTimeout TRAP-TYPE
        ENTERPRISE funkSbrTraps
        VARIABLES { funkSbrTrapVarComp, funkSbrTrapVarSev, 
                    funkSbrTrapVarNumberOfOccurrences }
        DESCRIPTION
            "This trap will be sent when communications with the RADIUS
             concurrency server times out. The trap is 'diluted', i.e. it is
             sent only once for every 'n' occurrences of the failure."
        ::= 5003

    funkSbrTrapConcurrencyLocalProxyFailure TRAP-TYPE
        ENTERPRISE funkSbrTraps
        VARIABLES { funkSbrTrapVarComp, funkSbrTrapVarSev, 
                    funkSbrTrapVarNumberOfOccurrences }
        DESCRIPTION
            "This trap will be sent when a local error prevents the RADIUS
             server from sending a proxy request to the RADIUS concurrency
             server. The trap is 'diluted', i.e. it is sent only once for
             every 'n' occurrences of the failure."
        ::= 5004

    funkSbrTrapStaticAcctProxyTimeout TRAP-TYPE
        ENTERPRISE funkSbrTraps
        VARIABLES { funkSbrTrapVarComp, funkSbrTrapVarSev, 
                    funkSbrTrapVarNumberOfOccurrences }
        DESCRIPTION
            "This trap will be sent when the RADIUS server times out in an
             attempt to forward an accounting request to the location specified
             by the static proxy option. The trap is 'diluted', i.e. it is sent
             only once for every 'n' occurrences of the failure."
        ::= 5005

    funkSbrTrapStaticAcctProxyLocalFailure TRAP-TYPE
        ENTERPRISE funkSbrTraps
        VARIABLES { funkSbrTrapVarComp, funkSbrTrapVarSev, 
                    funkSbrTrapVarNumberOfOccurrences }
        DESCRIPTION
            "This trap will be sent when the RADIUS server encounters a local
             failure in an attempt to forward an accounting request to the
             location specified by the static proxy option. The trap is
             'diluted', i.e. it is sent only once for every 'n' occurrences of
             the failure."
        ::= 5006

    funkSbrTrapLowFSSpace TRAP-TYPE
        ENTERPRISE funkSbrTraps
        VARIABLES { funkSbrTrapVarComp, funkSbrTrapVarSev, 
                    funkSbrTrapVarBytesAvail }
        DESCRIPTION
            "This trap will be sent when the amount of space available in the
             file system in which the server's private directory resides falls
             below a configurable threshold. An informational trap is sent when
             the amount of available space (at some future point) rises to an
             acceptable level."
        ::= 5007

    funkSbrTrapSQLConnectFail TRAP-TYPE
        ENTERPRISE funkSbrTraps
        VARIABLES { funkSbrTrapVarComp, funkSbrTrapVarSev, 
                    funkSbrTrapVarSQLConnects }
        DESCRIPTION
            "This trap will be sent when the connection to a SQL database
             has failed. The trap is 'diluted', i.e. it is sent only once
             for every 'n' occurrences of the timeout."
        ::= 5008

    funkSbrTrapSQLDisconnect TRAP-TYPE
        ENTERPRISE funkSbrTraps
        VARIABLES { funkSbrTrapVarComp, funkSbrTrapVarSev, 
                    funkSbrTrapVarSQLDisconnects }
        DESCRIPTION
            "This trap will be sent when a disconnect to a SQL database occurs.
			The trap is 'diluted', i.e. it is sent only once for every 'n' 
			occurrences of the disconnect."
        ::= 5009

    funkSbrTrapSQLTimeout TRAP-TYPE
        ENTERPRISE funkSbrTraps
        VARIABLES { funkSbrTrapVarComp, funkSbrTrapVarSev, 
                    funkSbrTrapVarSQLTimeouts }
        DESCRIPTION
            "This trap will be sent when a timeout occurs during an attempt to 
             perform transactions to a SQL database.  The trap is 'diluted', 
			 i.e. it is sent only once for every 'n' occurrences of the timeout."
        ::= 5010

    funkSbrTrapAcctDbTimeout TRAP-TYPE
        ENTERPRISE funkSbrTraps
        VARIABLES { funkSbrTrapVarComp, funkSbrTrapVarSev, 
                    funkSbrTrapVarNumberOfOccurrences }
        DESCRIPTION
            "This trap will be sent when the access to the accounting database
             has timed out. The trap is 'diluted', i.e. it is sent only once
             for every 'n' occurrences of the timeout."
        ::= 5011

    funkSbrTrapAcctDbFailure TRAP-TYPE
        ENTERPRISE funkSbrTraps
        VARIABLES { funkSbrTrapVarComp, funkSbrTrapVarSev, 
                    funkSbrTrapVarNumberOfOccurrences }
        DESCRIPTION
            "This trap will be sent when the access to the accounting database
             has failed. The trap is 'diluted', i.e. it is sent only once for
             every 'n' occurrences of the failure."
        ::= 5012

    funkSbrTrapVerifyServerTimeout TRAP-TYPE
        ENTERPRISE funkSbrTraps
        VARIABLES { funkSbrTrapVarComp, funkSbrTrapVarSev, 
                    funkSbrTrapVarNumberOfOccurrences }
        DESCRIPTION
            "This trap will be sent when an attempt to communicate with the
             Verification Server has timed out. The trap is 'diluted', i.e. it
             is sent only once for every 'n' occurrences of the timeout."
        ::= 5013

    funkSbrTrapVerifyServerFail TRAP-TYPE
        ENTERPRISE funkSbrTraps
        VARIABLES { funkSbrTrapVarComp, funkSbrTrapVarSev, 
                    funkSbrTrapVarNumberOfOccurrences }
        DESCRIPTION
            "This trap will be sent when an attempt to communicate with the
             Verification Server has failed. The trap is 'diluted', i.e. it is
             sent only once for every 'n' occurrences of the failure."
        ::= 5014

    funkSbrTrapLDAPConnectFailure TRAP-TYPE
        ENTERPRISE funkSbrTraps
        VARIABLES { funkSbrTrapVarComp, funkSbrTrapVarSev, 
				    funkSbrTrapVarFailedSystemName }
        DESCRIPTION
            "This trap will be sent when a connect failure takes place to an LDAP server."
        ::= 5015

    funkSbrTrapLDAPConnectFailures TRAP-TYPE
        ENTERPRISE funkSbrTraps
        VARIABLES { funkSbrTrapVarComp, funkSbrTrapVarSev, 
                    funkSbrTrapVarNumberOfOccurrences}
        DESCRIPTION
            "This trap will be sent when an attempt to communicate with the
             LDAP Server has failed. The trap is 'diluted', i.e. it is
             sent only once for every 'n' occurrences of the failure."
        ::= 5016

    funkSbrTrapLDAPDisconnects TRAP-TYPE
        ENTERPRISE funkSbrTraps
        VARIABLES { funkSbrTrapVarComp, funkSbrTrapVarSev, 
                    funkSbrTrapVarNumberOfOccurrences}
        DESCRIPTION
            "This trap will be sent the LDAP Server has Disconnected. 
			 The trap is 'diluted', i.e. it is sent only once for every 
			'n' occurrences of the failure."
        ::= 5017

    funkSbrTrapLDAPRequestTimeouts TRAP-TYPE
        ENTERPRISE funkSbrTraps
        VARIABLES { funkSbrTrapVarComp, funkSbrTrapVarSev,  
				    funkSbrTrapVarNumberOfOccurrences }
        DESCRIPTION
            "This trap will be sent when an request sent to the
             LDAP Server has timed out. The trap is 'diluted', i.e. it is
             sent only once for every 'n' occurrences of the failure."
        ::= 5018

    funkSbrTrapLDAPDisconnect TRAP-TYPE
        ENTERPRISE funkSbrTraps
        VARIABLES { funkSbrTrapVarComp, funkSbrTrapVarSev, 
					funkSbrTrapVarFailedSystemName}
        DESCRIPTION
            "This trap will be sent when a disconnect to a LDAP server occurs."
        ::= 5019

    funkSbrTrapLDAPRequestTimeout TRAP-TYPE
        ENTERPRISE funkSbrTraps
        VARIABLES { funkSbrTrapVarComp, funkSbrTrapVarSev, 
					funkSbrTrapVarFailedSystemName }
        DESCRIPTION
            "This trap will be sent when a request sent to the
             LDAP Server has timed out."
        ::= 5020

    funkSbrTrapProxySpoolTimeout TRAP-TYPE
        ENTERPRISE funkSbrTraps
        VARIABLES { funkSbrTrapVarComp, funkSbrTrapVarSev, 
					funkSbrTrapVarFailedSystemName }
        DESCRIPTION
            "This trap will be sent when a request forwarded by the proxy
			accounting spooler has timed out."
        ::= 5021

    funkSbrTrapProxySpoolTimeouts TRAP-TYPE
        ENTERPRISE funkSbrTraps
        VARIABLES { funkSbrTrapVarComp, funkSbrTrapVarSev, 
					funkSbrTrapVarNumberOfOccurrences }
        DESCRIPTION
            "This trap will be sent when a request forwarded by the proxy
			accounting spooler has timed out.  The trap is 'diluted', i.e. it is
             sent only once for every 'n' occurrences of the timeout."
        ::= 5022
    funkSbrTrapSoftLimitViolation TRAP-TYPE
        ENTERPRISE funkSbrTraps
        VARIABLES { funkSbrTrapVarComp, funkSbrTrapVarSev, 
					funkSbrTrapVarNumberOfOccurrences,
					funkSbrTrapVarFailedSystemName }
        DESCRIPTION
            "This trap will be sent when accepting a concurrency request
			exceeds a realm's soft limit.  The trap is 'diluted', i.e. it is
             sent only once for every 'n' occurrences of all such violations."
        ::= 5023
    funkSbrTrapHardLimitViolation TRAP-TYPE
        ENTERPRISE funkSbrTraps
        VARIABLES { funkSbrTrapVarComp, funkSbrTrapVarSev, 
					funkSbrTrapVarNumberOfOccurrences,
					funkSbrTrapVarFailedSystemName }
        DESCRIPTION
            "This trap will be sent when a concurrency request is rejected because a
			realm's hard limit has been reached.  The trap is 'diluted', 
			i.e. it is sent only once for every 'n' occurrences of all 
			such violations."
        ::= 5024
    funkSbrTrapConcurrencyServerMisconfiguration TRAP-TYPE
        ENTERPRISE funkSbrTraps
        VARIABLES { funkSbrTrapVarComp, funkSbrTrapVarSev, 
					funkSbrTrapVarFailedSystemName }
        DESCRIPTION
            "This trap will be sent when a PAS realm has been misconfigured
			All authentication requests to the named realm will be rejected."
        ::= 5025
    funkSbrTrapACCTWriteFailure TRAP-TYPE
        ENTERPRISE funkSbrTraps
        VARIABLES { funkSbrTrapVarComp, funkSbrTrapVarSev,
                    funkSbrTrapVarNumberOfOccurrences,
                    funkSbrTrapVarPersistStoreName,
                    funkSbrTrapVarDiagnosticMessage }
        DESCRIPTION
            "This trap will be sent when the server is unable to commit accounting
            data to a persistent store such as the file system, database, etc.  The
            trap is 'diluted', i.e. it is sent only once for every 'n' occurrences
            of all such failures."
        ::= 5026
    funkSbrTrapIPAddrPoolLow TRAP-TYPE
        ENTERPRISE funkSbrTraps
        VARIABLES { funkSbrTrapVarComp, funkSbrTrapVarSev, 
                    funkSbrTrapVarIPAddrPoolName,
                    funkSbrTrapVarIPAddrAvail }
        DESCRIPTION
            "This trap will be sent when the number of available IP addresses
            in any pool falls below a configurable threshold.  An informational
            trap is sent when the number of available IP addresses (at some
            future point) rises to an acceptable level."
        ::= 5027
-- ******************************** Errors ************************************

    funkSbrTrapStartServiceError TRAP-TYPE
        ENTERPRISE funkSbrTraps
        VARIABLES { funkSbrTrapVarComp, funkSbrTrapVarSev, 
                    funkSbrTrapVarServiceDispatcherErrCode }
        DESCRIPTION
            "This trap will be sent for an NT version of RADIUS when the
             service control dispatcher returns an error."
        ::= 10000

    funkSbrTrapSetStatusError TRAP-TYPE
        ENTERPRISE funkSbrTraps
        VARIABLES { funkSbrTrapVarComp, funkSbrTrapVarSev, 
                    funkSbrTrapVarSetStatusErrCode }
        DESCRIPTION
            "This trap will be sent for an NT version of RADIUS when the
             attempt to inform the service control dispatcher of the status
             of the RADIUS server encounters an error."
        ::= 10001

    funkSbrTrapBadPrivDir TRAP-TYPE
        ENTERPRISE funkSbrTraps
        VARIABLES { funkSbrTrapVarComp, funkSbrTrapVarSev, 
                    funkSbrTrapVarPrivateDir }
        DESCRIPTION
            "This trap will be sent for an NT version of RADIUS when the
             attempt to inform the service control dispatcher of the status
             of the RADIUS server encounters an error."
        ::= 10002

    funkSbrTrapFailedThreadCreate TRAP-TYPE
        ENTERPRISE funkSbrTraps
        VARIABLES { funkSbrTrapVarComp, funkSbrTrapVarSev }
        DESCRIPTION
            "This trap will be sent when an attempt to create a thread at
             server startup encounters a failure. The server will fail to
             start."
        ::= 10003

    funkSbrTrapFailedMutexCreate TRAP-TYPE
        ENTERPRISE funkSbrTraps
        VARIABLES { funkSbrTrapVarComp, funkSbrTrapVarSev }
        DESCRIPTION
            "This trap will be sent when an attempt to create a mutex at
             server startup encounters a failure. The server will fail to
             start."
        ::= 10004

    funkSbrTrapFailedSignalInit TRAP-TYPE
        ENTERPRISE funkSbrTraps
        VARIABLES { funkSbrTrapVarComp, funkSbrTrapVarSev }
        DESCRIPTION
            "This trap will be sent when an attempt to initialize signal
             handling at server startup encounters a failure. The server
             will fail to start."
        ::= 10005

    funkSbrTrapFailedEventInit TRAP-TYPE
        ENTERPRISE funkSbrTraps
        VARIABLES { funkSbrTrapVarComp, funkSbrTrapVarSev }
        DESCRIPTION
            "This trap will be sent when an attempt to initialize event
             processing at server startup encounters a failure. The server
             will fail to start."
        ::= 10006

    funkSbrTrapFailedLogFile TRAP-TYPE
        ENTERPRISE funkSbrTraps
        VARIABLES { funkSbrTrapVarComp, funkSbrTrapVarSev }
        DESCRIPTION
            "This trap will be sent when an attempt to open or create a log
             file at server startup encounters a failure. The server will
             fail to start."
        ::= 10007

    funkSbrTrapFailedLDAPAdminInit TRAP-TYPE
        ENTERPRISE funkSbrTraps
        VARIABLES { funkSbrTrapVarComp, funkSbrTrapVarSev }
        DESCRIPTION
            "This trap will be sent when an attempt to initialize the LDAP
             administration interface at server startup encounters a failure.
             The server will fail to start."
        ::= 10008

    funkSbrTrapFailedRPCInit TRAP-TYPE
        ENTERPRISE funkSbrTraps
        VARIABLES { funkSbrTrapVarComp, funkSbrTrapVarSev }
        DESCRIPTION
            "This trap will be sent when an attempt to initialize the RPC
             administration interface at server startup encounters a failure.
             The server will fail to start."
        ::= 10009

    funkSbrTrapFailedIPInit TRAP-TYPE
        ENTERPRISE funkSbrTraps
        VARIABLES { funkSbrTrapVarComp, funkSbrTrapVarSev }
        DESCRIPTION
            "This trap will be sent when an attempt to initialize basic TCP/IP
             services at server startup encounters a failure. The server will
             fail to start."
        ::= 10010

    funkSbrTrapFailedCurrentSessionsInit TRAP-TYPE
        ENTERPRISE funkSbrTraps
        VARIABLES { funkSbrTrapVarComp, funkSbrTrapVarSev }
        DESCRIPTION
            "This trap will be sent when an attempt to initialize current
             sessions list processing at server startup encounters a failure.
             The server will fail to start."
        ::= 10011

    funkSbrTrapFailedChallCacheInit TRAP-TYPE
        ENTERPRISE funkSbrTraps
        VARIABLES { funkSbrTrapVarComp, funkSbrTrapVarSev }
        DESCRIPTION
            "This trap will be sent when an attempt to initialize the RADIUS
             challenge continuation cache at server startup encounters a
             failure. The server will fail to start."
        ::= 10012

    funkSbrTrapFailedActiveRASInit TRAP-TYPE
        ENTERPRISE funkSbrTraps
        VARIABLES { funkSbrTrapVarComp, funkSbrTrapVarSev }
        DESCRIPTION
            "This trap will be sent when an attempt to initialize the RAS
             activity monitor at server startup encounters a failure. The
             server will fail to start."
        ::= 10013

    funkSbrTrapFailedDictionaryInit TRAP-TYPE
        ENTERPRISE funkSbrTraps
        VARIABLES { funkSbrTrapVarComp, funkSbrTrapVarSev }
        DESCRIPTION
            "This trap will be sent when an attempt to initialize the
             dictionary processing at server startup encounters a failure.
             The server will fail to start."
        ::= 10014

    funkSbrTrapFailedVendorInit TRAP-TYPE
        ENTERPRISE funkSbrTraps
        VARIABLES { funkSbrTrapVarComp, funkSbrTrapVarSev }
        DESCRIPTION
            "This trap will be sent when an attempt to process the vendor.ini
             file at server startup encounters a failure. The server will fail
             to start."
        ::= 10015

    funkSbrTrapFailedDBInit TRAP-TYPE
        ENTERPRISE funkSbrTraps
        VARIABLES { funkSbrTrapVarComp, funkSbrTrapVarSev,
                    funkSbrTrapVarDbType }
        DESCRIPTION
            "This trap will be sent when an attempt to initialize the internal
             database at server startup encounters a failure. The server will
             fail to start."
        ::= 10016

    funkSbrTrapFailedUnixUserInit TRAP-TYPE
        ENTERPRISE funkSbrTraps
        VARIABLES { funkSbrTrapVarComp, funkSbrTrapVarSev }
        DESCRIPTION
            "This trap will be sent when an attempt to initialize the Unix user
             browsing component at server startup encounters a failure. The
             server will fail to start."
        ::= 10017

    funkSbrTrapFailedAdminRightsInit TRAP-TYPE
        ENTERPRISE funkSbrTraps
        VARIABLES { funkSbrTrapVarComp, funkSbrTrapVarSev }
        DESCRIPTION
            "This trap will be sent when an attempt to initialize the
             administration user rights component at server startup encounters
             a failure. The server will fail to start."
        ::= 10018

    funkSbrTrapFailedDbOpen TRAP-TYPE
        ENTERPRISE funkSbrTraps
        VARIABLES { funkSbrTrapVarComp, funkSbrTrapVarSev,
                    funkSbrTrapVarDbType }
        DESCRIPTION
            "This trap will be sent when an attempt to open the internal
             database at server startup encounters a failure. The server will
             fail to start."
        ::= 10019

    funkSbrTrapFailedDNISLookupInit TRAP-TYPE
        ENTERPRISE funkSbrTraps
        VARIABLES { funkSbrTrapVarComp, funkSbrTrapVarSev }
        DESCRIPTION
            "This trap will be sent when an attempt to initialize the
             tunnel DNIS lookup component at server startup encounters
             a failure. The server will fail to start."
        ::= 10020

    funkSbrTrapFailedConfigCacheInit TRAP-TYPE
        ENTERPRISE funkSbrTraps
        VARIABLES { funkSbrTrapVarComp, funkSbrTrapVarSev }
        DESCRIPTION
            "This trap will be sent when an attempt to initialize the
             configuration caching component at server startup encounters a
             failure. The server will fail to start."
        ::= 10021

    funkSbrTrapFailedDbCacheInit TRAP-TYPE
        ENTERPRISE funkSbrTraps
        VARIABLES { funkSbrTrapVarComp, funkSbrTrapVarSev }
        DESCRIPTION
            "This trap will be sent when an attempt to initialize the
             database caching component at server startup encounters a
             failure. The server will fail to start."
        ::= 10022

    funkSbrTrapFailedLicenseInit TRAP-TYPE
        ENTERPRISE funkSbrTraps
        VARIABLES { funkSbrTrapVarComp, funkSbrTrapVarSev }
        DESCRIPTION
            "This trap will be sent when an attempt to initialize the
             licensing component at server startup encounters a failure. The
             server will fail to start."
        ::= 10023

    funkSbrTrapFailedNDSTrusteeInit TRAP-TYPE
        ENTERPRISE funkSbrTraps
        VARIABLES { funkSbrTrapVarComp, funkSbrTrapVarSev }
        DESCRIPTION
            "This trap will be sent when an attempt to initialize NDS trustee
             processing on NetWare at server startup encounters a failure. The
             server will fail to start."
        ::= 10024

    funkSbrTrapFailedHostLookupInit TRAP-TYPE
        ENTERPRISE funkSbrTraps
        VARIABLES { funkSbrTrapVarComp, funkSbrTrapVarSev }
        DESCRIPTION
            "This trap will be sent when an attempt to initialize host lookup
             processing on NetWare at server startup encounters a failure. The
             server will fail to start."
        ::= 10025

    funkSbrTrapFailedAddrPoolInit TRAP-TYPE
        ENTERPRISE funkSbrTraps
        VARIABLES { funkSbrTrapVarComp, funkSbrTrapVarSev }
        DESCRIPTION
            "This trap will be sent when an attempt to initialize IP/IPX
             address pool resource management at server startup encounters a
             failure. The server will fail to start."
        ::= 10026

    funkSbrTrapFailedLoginLimitInit TRAP-TYPE
        ENTERPRISE funkSbrTraps
        VARIABLES { funkSbrTrapVarComp, funkSbrTrapVarSev }
        DESCRIPTION
            "This trap will be sent when an attempt to initialize user login
             count tracking at server startup encounters a failure. The server
             will fail to start."
        ::= 10027

    funkSbrTrapFailedPersistStoreCreate TRAP-TYPE
        ENTERPRISE funkSbrTraps
        VARIABLES { funkSbrTrapVarComp, funkSbrTrapVarSev }
        DESCRIPTION
            "This trap will be sent when an attempt to create the persistent
             store for current session list processing at server startup
             encounters a failure. The server will fail to start."
        ::= 10028

    funkSbrTrapFailedPersistStoreInit TRAP-TYPE
        ENTERPRISE funkSbrTraps
        VARIABLES { funkSbrTrapVarComp, funkSbrTrapVarSev }
        DESCRIPTION
            "This trap will be sent when an attempt to initialize the
             persistent store for current session list processing at server
             startup encounters a failure. The server will fail to start."
        ::= 10029

    funkSbrTrapFailedPerfMonInit TRAP-TYPE
        ENTERPRISE funkSbrTraps
        VARIABLES { funkSbrTrapVarComp, funkSbrTrapVarSev }
        DESCRIPTION
            "This trap will be sent for an NT version of RADIUS when an 
			attempt to initialize the Windows NT performance monitor 
			interface at server startup encounters a failure. The server 
			will fail to start."
        ::= 10030

    funkSbrTrapFailedLockInit TRAP-TYPE
        ENTERPRISE funkSbrTraps
        VARIABLES { funkSbrTrapVarComp, funkSbrTrapVarSev }
        DESCRIPTION
            "This trap will be sent when an attempt to initialize admin
             locking component at server startup encounters a failure. The
             server will fail to start."
        ::= 10031

    funkSbrTrapFailedPlugInInit TRAP-TYPE
        ENTERPRISE funkSbrTraps
        VARIABLES { funkSbrTrapVarComp, funkSbrTrapVarSev }
        DESCRIPTION
            "This trap will be sent when an attempt to initialize the plug-in
             support component at server startup encounters a failure. The
             server will fail to start."
        ::= 10032

    funkSbrTrapFailedPacketCacheInit TRAP-TYPE
        ENTERPRISE funkSbrTraps
        VARIABLES { funkSbrTrapVarComp, funkSbrTrapVarSev }
        DESCRIPTION
            "This trap will be sent when an attempt to initialize duplicate
             packet request cache at server startup encounters a failure. The
             server will fail to start."
        ::= 10033

    funkSbrTrapFailedNameMangleInit TRAP-TYPE
        ENTERPRISE funkSbrTraps
        VARIABLES { funkSbrTrapVarComp, funkSbrTrapVarSev }
        DESCRIPTION
            "This trap will be sent when an attempt to initialize name mangling
             support at server startup encounters a failure. The server will
             fail to start."
        ::= 10034

    funkSbrTrapFailedNameStripInit TRAP-TYPE
        ENTERPRISE funkSbrTraps
        VARIABLES { funkSbrTrapVarComp, funkSbrTrapVarSev }
        DESCRIPTION
            "This trap will be sent when an attempt to initialize name
             stripping support at server startup encounters a failure. The
             server will fail to start."
        ::= 10035

    funkSbrTrapFailedFSSpaceChecking TRAP-TYPE
        ENTERPRISE funkSbrTraps
        VARIABLES { funkSbrTrapVarComp, funkSbrTrapVarSev, 
                    funkSbrTrapVarGetDiskFreeSpaceErrCode }
        DESCRIPTION
            "This trap will be sent when an attempt to determine the amount
             of free file system space fails. File system space checking
             will be disabled until the server is restarted."
        ::= 10036

    funkSbrTrapFailedNameValidateInit TRAP-TYPE
        ENTERPRISE funkSbrTraps
        VARIABLES { funkSbrTrapVarComp, funkSbrTrapVarSev }
        DESCRIPTION
            "This trap will be sent when an attempt to initialize name
             validation support at server startup encounters a failure. The
             server will fail to start."
        ::= 10037

    funkSbrTrapFailedResourceCheckInit TRAP-TYPE
        ENTERPRISE funkSbrTraps
        VARIABLES { funkSbrTrapVarComp, funkSbrTrapVarSev }
        DESCRIPTION
            "This trap will be sent when an attempt to initialize system
             resource checking at server startup encounters a failure. The
             server will fail to start."
        ::= 10038

    funkSbrTrapFailedSystemStatsInit TRAP-TYPE
        ENTERPRISE funkSbrTraps
        VARIABLES { funkSbrTrapVarComp, funkSbrTrapVarSev }
        DESCRIPTION
            "This trap will be sent when an attempt to initialize statistic
             collection at server startup encounters a failure. The server
             will fail to start."
        ::= 10039

    funkSbrTrapSQLConnectFailure TRAP-TYPE
        ENTERPRISE funkSbrTraps
        VARIABLES { funkSbrTrapVarComp, funkSbrTrapVarSev, 
				    funkSbrTrapVarFailedSystemName }
        DESCRIPTION
            "This trap will be sent when a 
             connection attempt from the SQL authentication or accounting
             plug-in to the specified system has failed."
        ::= 10040

    funkSbrTrapSQLDiscon TRAP-TYPE
        ENTERPRISE funkSbrTraps
        VARIABLES { funkSbrTrapVarComp, funkSbrTrapVarSev, 
                    funkSbrTrapVarFailedSystemName }
        DESCRIPTION
            "This trap will be sent when a disconnect from a SQL database has occurred."
        ::= 10041

    -- 	* 10042 * individual SQL timeout (not sent as a trap)

    funkSbrTrapFailedReserveMemoryAlloc TRAP-TYPE
        ENTERPRISE funkSbrTraps
        VARIABLES { funkSbrTrapVarComp, funkSbrTrapVarSev,
                    funkSbrTrapVarIniString }
        DESCRIPTION
            "This trap will be sent when an attempt to allocate reserved memory
             based on a setting in the radius.ini file fails. The server will
             start without reserved memory, but will be unable to warn of low
             memory conditions."
        ::= 10043

    funkSbrTrapReserveMemoryFreed TRAP-TYPE
        ENTERPRISE funkSbrTraps
        VARIABLES { funkSbrTrapVarComp, funkSbrTrapVarSev,
                    funkSbrTrapVarIniString }
        DESCRIPTION
            "This trap will be sent when an attempt to allocate memory during 
             runtime fails and the block of memory reserved at system startup
             is freed in an attempt to alleviate the low memory condition."
        ::= 10044

    funkSbrTrapMemoryAllocFail TRAP-TYPE
        ENTERPRISE funkSbrTraps
        VARIABLES { funkSbrTrapVarComp, funkSbrTrapVarSev, 
                    funkSbrTrapVarNumberOfOccurrences }
        DESCRIPTION
            "This trap will be sent when an attempt to allocate memory has
             failed. The trap is 'diluted', i.e. it is sent only once for
             every 'n' occurrences of the failure."
        ::= 10045

    -- 	* 10046 * individual accounting database connect failure (not sent as a trap)

    -- 	* 10047 * individual verification server connect failure (not sent as a trap)

    funkSbrTrapFailedMibInfoCollectInit TRAP-TYPE
        ENTERPRISE funkSbrTraps
        VARIABLES { funkSbrTrapVarComp, funkSbrTrapVarSev }
        DESCRIPTION
            "This trap will be sent when an attempt to initialize MIB
             information collection at server startup encounters a failure. The
             server will fail to start."
        ::= 10048

    funkSbrTrapFailedMibInfoAccessInit TRAP-TYPE
        ENTERPRISE funkSbrTraps
        VARIABLES { funkSbrTrapVarComp, funkSbrTrapVarSev }
        DESCRIPTION
            "This trap will be sent when an attempt to initialize MIB access 
             at server startup encounters a failure. The server will fail to
             start."
        ::= 10049

    funkSbrTrapFailedCommonIPInit TRAP-TYPE
        ENTERPRISE funkSbrTraps
        VARIABLES { funkSbrTrapVarComp, funkSbrTrapVarSev }
        DESCRIPTION
            "This trap will be sent when an attempt to initialize common IP 
             services at server startup encounters a failure. The server will
             fail to start."
        ::= 10050
END
