Wellfleet-BB-MIB-MIB DEFINITIONS ::= BEGIN

-- Created by mdl2asn version 3.1
-- Creation date: Wed Aug 30 16:38:20 EDT 1995


    IMPORTS

      IpAddress, Counter, Gauge, TimeTicks, Opaque, enterprises, mgmt
        FROM RFC1155-SMI
      OBJECT-TYPE
        FROM RFC-1212
      TRAP-TYPE
        FROM RFC-1215
      DisplayString, mib-2
        FROM RFC1213-MIB
      wfGameGroup
        FROM Wellfleet-COMMON-MIB;


    wfBackboneTable OBJECT-TYPE
        SYNTAX	SEQUENCE OF WfBackboneEntry
        ACCESS	not-accessible
        STATUS	mandatory
        DESCRIPTION
                "Table of Backbone entries, indexed by slot number"
        ::= { wfGameGroup 4 }

    wfBackboneEntry OBJECT-TYPE
        SYNTAX	WfBackboneEntry
        ACCESS	not-accessible
        STATUS	mandatory
        DESCRIPTION
                "A particular interface"
        INDEX	{ wfBackboneSlot }
        ::= { wfBackboneTable 1 }

    WfBackboneEntry ::= SEQUENCE {
    	    wfBackboneSlot
    		INTEGER,
    	    wfTxDropCtrSlotMask0
    		Counter,
    	    wfTxDropCtrNoGrant
    		Counter,
    	    wfTxDropCtrFlowCtrl
    		Counter,
    	    wfTxDied
    		Counter,
    	    wfTxDramDied
    		Counter,
    	    wfTxIdleErrors
    		Counter,
    	    wfTxNoSomErrors
    		Counter,
    	    wfTxPktSomErrors
    		Counter,
    	    wfTxDropEomErrors
    		Counter,
    	    wfTxOverflowErrors
    		Counter,
    	    wfTxSofErrors
    		Counter,
    	    wfTxDataptrErrors
    		Counter,
    	    wfTxEndptrErrors
    		Counter,
    	    wfTxBoardSpeedMask
    		INTEGER,
    	    wfTxErrorEnableMask
    		INTEGER,
    	    wfTxBusRequestTimeout
    		INTEGER,
    	    wfTxDeadlockTimeout
    		INTEGER,
    	    wfTxIgnoreFlowCtrl
    		INTEGER,
    	    wfTxBackboneSelectMode
    		INTEGER,
    	    wfTxEnableSlotMask0
    		INTEGER,
    	    wfTxFifoSize
    		INTEGER,
    	    wfTxVisControl
    		INTEGER,
    	    wfRxPktNumErrors
    		Counter,
    	    wfRxAddrOvrErrors
    		Counter,
    	    wfRxSomErrors
    		Counter,
    	    wfRxDied
    		Counter,
    	    wfRxUnloadErrors
    		Counter,
    	    wfRxDropCtr
    		Counter,
    	    wfRxSofErrors
    		Counter,
    	    wfRxCrcErrors
    		Counter,
    	    wfRxOvrErrors
    		Counter,
    	    wfRxForceEomErrors
    		Counter,
    	    wfRxMaxEofErrors
    		Counter,
    	    wfRxFifoSize
    		INTEGER,
    	    wfRxReceiveMode
    		INTEGER,
    	    wfRxIgnorePktNum
    		INTEGER,
    	    wfRxVisControl
    		INTEGER,
    	    wfRxErrorEnableMask
    		INTEGER,
    	    wfRxMaxEof
    		INTEGER,
    	    wfRxParitySense
    		INTEGER,
    	    wfRxDeadlockTimeout
    		INTEGER,
    	    wfTxDropWB
    		INTEGER,
    	    wfTxDiedNoPg
    		INTEGER,
    	    wfTxDtbErrors
    		INTEGER,
    	    wfTxPagePtrErrors
    		INTEGER,
    	    wfRxWBCtr
    		INTEGER,
    	    wfRxLinkList0Ctr
    		INTEGER,
    	    wfRxArbErrors
    		INTEGER
        }

    wfBackboneSlot OBJECT-TYPE
        SYNTAX	INTEGER
        ACCESS	read-only
        STATUS	mandatory
        DESCRIPTION
                "The slot number indexes the backbone table"
        ::= { wfBackboneEntry 1 }

    wfTxDropCtrSlotMask0 OBJECT-TYPE
        SYNTAX	Counter
        ACCESS	read-only
        STATUS	mandatory
        DESCRIPTION
                "The number of packets dropped because their slot masks equals zero"
        ::= { wfBackboneEntry 2 }

    wfTxDropCtrNoGrant OBJECT-TYPE
        SYNTAX	Counter
        ACCESS	read-only
        STATUS	mandatory
        DESCRIPTION
                "The number of packets dropped because no bus was granted for TX."
        ::= { wfBackboneEntry 3 }

    wfTxDropCtrFlowCtrl OBJECT-TYPE
        SYNTAX	Counter
        ACCESS	read-only
        STATUS	mandatory
        DESCRIPTION
                "The number of packets dropped because of flow control."
        ::= { wfBackboneEntry 4 }

    wfTxDied OBJECT-TYPE
        SYNTAX	Counter
        ACCESS	read-only
        STATUS	mandatory
        DESCRIPTION
                "The number of times the TX state machine has died."
        ::= { wfBackboneEntry 5 }

    wfTxDramDied OBJECT-TYPE
        SYNTAX	Counter
        ACCESS	read-only
        STATUS	mandatory
        DESCRIPTION
                "The number of times the TX DRAM state machine has died."
        ::= { wfBackboneEntry 6 }

    wfTxIdleErrors OBJECT-TYPE
        SYNTAX	Counter
        ACCESS	read-only
        STATUS	mandatory
        DESCRIPTION
                "The number of times both pipeline state machines were active simultaneously."
        ::= { wfBackboneEntry 7 }

    wfTxNoSomErrors OBJECT-TYPE
        SYNTAX	Counter
        ACCESS	read-only
        STATUS	mandatory
        DESCRIPTION
                "The number of times the state machine left idle without start of message."
        ::= { wfBackboneEntry 8 }

    wfTxPktSomErrors OBJECT-TYPE
        SYNTAX	Counter
        ACCESS	read-only
        STATUS	mandatory
        DESCRIPTION
                "The number of times the TX packet state machine left idle without start of
                message."
        ::= { wfBackboneEntry 9 }

    wfTxDropEomErrors OBJECT-TYPE
        SYNTAX	Counter
        ACCESS	read-only
        STATUS	mandatory
        DESCRIPTION
                "The number of times the TX detected a drop of an end of message."
        ::= { wfBackboneEntry 10 }

    wfTxOverflowErrors OBJECT-TYPE
        SYNTAX	Counter
        ACCESS	read-only
        STATUS	mandatory
        DESCRIPTION
                "The number of times the TX detected an overflow condition."
        ::= { wfBackboneEntry 11 }

    wfTxSofErrors OBJECT-TYPE
        SYNTAX	Counter
        ACCESS	read-only
        STATUS	mandatory
        DESCRIPTION
                "The number of times the TX detected a start offset error condition."
        ::= { wfBackboneEntry 12 }

    wfTxDataptrErrors OBJECT-TYPE
        SYNTAX	Counter
        ACCESS	read-only
        STATUS	mandatory
        DESCRIPTION
                "The number of times the TX detected that an increment on the data pointer
                caused a carry-out error condition."
        ::= { wfBackboneEntry 13 }

    wfTxEndptrErrors OBJECT-TYPE
        SYNTAX	Counter
        ACCESS	read-only
        STATUS	mandatory
        DESCRIPTION
                "The number of times the TX detected that the end pointer wrapped in the
                address space when it was formed from the buf pointer and the end offset."
        ::= { wfBackboneEntry 14 }

    wfTxBoardSpeedMask OBJECT-TYPE
        SYNTAX	INTEGER
        ACCESS	read-only
        STATUS	mandatory
        DESCRIPTION
                "The mask describing the speed setting of all boards in the system."
        ::= { wfBackboneEntry 15 }

    wfTxErrorEnableMask OBJECT-TYPE
        SYNTAX	INTEGER
        ACCESS	read-write
        STATUS	mandatory
        DESCRIPTION
                "The mask describing the set of TX errors that are enabled."
        ::= { wfBackboneEntry 16 }

    wfTxBusRequestTimeout OBJECT-TYPE
        SYNTAX	INTEGER
        ACCESS	read-only
        STATUS	mandatory
        DESCRIPTION
                "The timeout value for the TX bus request."
        ::= { wfBackboneEntry 17 }

    wfTxDeadlockTimeout OBJECT-TYPE
        SYNTAX	INTEGER
        ACCESS	read-only
        STATUS	mandatory
        DESCRIPTION
                "The timeout value for the TX bus deadlock."
        ::= { wfBackboneEntry 18 }

    wfTxIgnoreFlowCtrl OBJECT-TYPE
        SYNTAX	INTEGER
        ACCESS	read-only
        STATUS	mandatory
        DESCRIPTION
                "Indicates whether TX flow control is enabled or not."
        ::= { wfBackboneEntry 19 }

    wfTxBackboneSelectMode OBJECT-TYPE
        SYNTAX	INTEGER
        ACCESS	read-write
        STATUS	mandatory
        DESCRIPTION
                "Indicates the TX backbone selection mode (1 = MRR8, 0 = First available)."
        ::= { wfBackboneEntry 20 }

    wfTxEnableSlotMask0 OBJECT-TYPE
        SYNTAX	INTEGER
        ACCESS	read-only
        STATUS	mandatory
        DESCRIPTION
                "Indicates whether TX will transmit packets with slot mask 0."
        ::= { wfBackboneEntry 21 }

    wfTxFifoSize OBJECT-TYPE
        SYNTAX	INTEGER
        ACCESS	read-only
        STATUS	mandatory
        DESCRIPTION
                "Indicates the size of the TX FIFO."
        ::= { wfBackboneEntry 22 }

    wfTxVisControl OBJECT-TYPE
        SYNTAX	INTEGER
        ACCESS	read-write
        STATUS	mandatory
        DESCRIPTION
                "The read/write value of TX visibility register used for debug."
        ::= { wfBackboneEntry 23 }

    wfRxPktNumErrors OBJECT-TYPE
        SYNTAX	Counter
        ACCESS	read-only
        STATUS	mandatory
        DESCRIPTION
                "The number of times the RX detected a packet numbering error."
        ::= { wfBackboneEntry 24 }

    wfRxAddrOvrErrors OBJECT-TYPE
        SYNTAX	Counter
        ACCESS	read-only
        STATUS	mandatory
        DESCRIPTION
                "The number of times the RX detected a address overrun error."
        ::= { wfBackboneEntry 25 }

    wfRxSomErrors OBJECT-TYPE
        SYNTAX	Counter
        ACCESS	read-only
        STATUS	mandatory
        DESCRIPTION
                "The number of times the RX detected a start of message error."
        ::= { wfBackboneEntry 26 }

    wfRxDied OBJECT-TYPE
        SYNTAX	Counter
        ACCESS	read-only
        STATUS	mandatory
        DESCRIPTION
                "The number of times the RX state machine died."
        ::= { wfBackboneEntry 27 }

    wfRxUnloadErrors OBJECT-TYPE
        SYNTAX	Counter
        ACCESS	read-only
        STATUS	mandatory
        DESCRIPTION
                "The number of times the RX tried to unload an empty FIFO."
        ::= { wfBackboneEntry 28 }

    wfRxDropCtr OBJECT-TYPE
        SYNTAX	Counter
        ACCESS	read-only
        STATUS	mandatory
        DESCRIPTION
                "The number of times the RX dropped a packet."
        ::= { wfBackboneEntry 29 }

    wfRxSofErrors OBJECT-TYPE
        SYNTAX	Counter
        ACCESS	read-only
        STATUS	mandatory
        DESCRIPTION
                "The number of times the RX detected a start offset error."
        ::= { wfBackboneEntry 30 }

    wfRxCrcErrors OBJECT-TYPE
        SYNTAX	Counter
        ACCESS	read-only
        STATUS	mandatory
        DESCRIPTION
                "The number of times the RX detected a CRC error."
        ::= { wfBackboneEntry 31 }

    wfRxOvrErrors OBJECT-TYPE
        SYNTAX	Counter
        ACCESS	read-only
        STATUS	mandatory
        DESCRIPTION
                "The number of times the RX detected an overrun error."
        ::= { wfBackboneEntry 32 }

    wfRxForceEomErrors OBJECT-TYPE
        SYNTAX	Counter
        ACCESS	read-only
        STATUS	mandatory
        DESCRIPTION
                "The number of times the RX detected a force end-of-message error."
        ::= { wfBackboneEntry 33 }

    wfRxMaxEofErrors OBJECT-TYPE
        SYNTAX	Counter
        ACCESS	read-only
        STATUS	mandatory
        DESCRIPTION
                "The number of times the RX detected an end offset error."
        ::= { wfBackboneEntry 34 }

    wfRxFifoSize OBJECT-TYPE
        SYNTAX	INTEGER
        ACCESS	read-only
        STATUS	mandatory
        DESCRIPTION
                "Indicates the size of the RX FIFO."
        ::= { wfBackboneEntry 35 }

    wfRxReceiveMode OBJECT-TYPE
        SYNTAX	INTEGER
        ACCESS	read-write
        STATUS	mandatory
        DESCRIPTION
                "Indicates the receive mode of the RX."
        ::= { wfBackboneEntry 36 }

    wfRxIgnorePktNum OBJECT-TYPE
        SYNTAX	INTEGER
        ACCESS	read-only
        STATUS	mandatory
        DESCRIPTION
                "Indicates whether RX will ignore packet numbering errors."
        ::= { wfBackboneEntry 37 }

    wfRxVisControl OBJECT-TYPE
        SYNTAX	INTEGER
        ACCESS	read-write
        STATUS	mandatory
        DESCRIPTION
                "The read/write value of RX visibility register used for debug."
        ::= { wfBackboneEntry 38 }

    wfRxErrorEnableMask OBJECT-TYPE
        SYNTAX	INTEGER
        ACCESS	read-write
        STATUS	mandatory
        DESCRIPTION
                "The mask describing the set of RX errors that are enabled."
        ::= { wfBackboneEntry 39 }

    wfRxMaxEof OBJECT-TYPE
        SYNTAX	INTEGER
        ACCESS	read-only
        STATUS	mandatory
        DESCRIPTION
                "Indicates the maximum end offset that the RX will allow."
        ::= { wfBackboneEntry 40 }

    wfRxParitySense OBJECT-TYPE
        SYNTAX	INTEGER
        ACCESS	read-only
        STATUS	mandatory
        DESCRIPTION
                "Indicates the parity sense that RX is expecting."
        ::= { wfBackboneEntry 41 }

    wfRxDeadlockTimeout OBJECT-TYPE
        SYNTAX	INTEGER
        ACCESS	read-only
        STATUS	mandatory
        DESCRIPTION
                "The timeout value for the RX bus deadlock."
        ::= { wfBackboneEntry 42 }

    wfTxDropWB OBJECT-TYPE
        SYNTAX	INTEGER
        ACCESS	read-only
        STATUS	mandatory
        DESCRIPTION
                "The number of buffers dropped by a Bluefish style TX because it had a Wastebasket page in it."
        ::= { wfBackboneEntry 43 }

    wfTxDiedNoPg OBJECT-TYPE
        SYNTAX	INTEGER
        ACCESS	read-only
        STATUS	mandatory
        DESCRIPTION
                "The number of times a Bluefish style TX died because it recieved a buffer with no pages in it."
        ::= { wfBackboneEntry 44 }

    wfTxDtbErrors OBJECT-TYPE
        SYNTAX	INTEGER
        ACCESS	read-only
        STATUS	mandatory
        DESCRIPTION
                "The number of times a Bluefish style TX recieved a data-back signal from the VBM when it had no VBM access in progress."
        ::= { wfBackboneEntry 45 }

    wfTxPagePtrErrors OBJECT-TYPE
        SYNTAX	INTEGER
        ACCESS	read-only
        STATUS	mandatory
        DESCRIPTION
                "The number of times the Bluefish style TX page pointer wrapped in the valid address space."
        ::= { wfBackboneEntry 46 }

    wfRxWBCtr OBJECT-TYPE
        SYNTAX	INTEGER
        ACCESS	read-only
        STATUS	mandatory
        DESCRIPTION
                "The number of wastebasket pages the Bluefish style Rx recieved from the VBM."
        ::= { wfBackboneEntry 47 }

    wfRxLinkList0Ctr OBJECT-TYPE
        SYNTAX	INTEGER
        ACCESS	read-only
        STATUS	mandatory
        DESCRIPTION
                "The number of times the Bluefish style Rx recieved a buffer pointer of 0 from the VBM."
        ::= { wfBackboneEntry 48 }

    wfRxArbErrors OBJECT-TYPE
        SYNTAX	INTEGER
        ACCESS	read-only
        STATUS	mandatory
        DESCRIPTION
                "The number of times a Bluefish style Rx had two recievers trying to write to VBM at the same time."
        ::= { wfBackboneEntry 49 }

    END  -- Wellfleet-BB-MIB-MIB
