--
--  This is a SNMPv1 translation of Digital Equipment Corporation's
--  Broadcast and Unknown Server MIB.
--
--  Initial translation was done by the tool
--          SMIC (the next generation) version 1.6.31
--
--  The machine-generated MIB was then modified to remove all remaining
--  SNMP version 2 constructs.
--

DEC-BUS-MIB DEFINITIONS ::= BEGIN

IMPORTS

    Counter, TimeTicks
            FROM RFC1155-SMI
    OBJECT-TYPE
            FROM RFC-1212
    decMIBextension
            FROM DECATM-MIB;

decBusMIB OBJECT IDENTIFIER ::= { decMIBextension 29 }

-- MODULE-IDENTITY
--  LastUpdated
--    9509120000Z
--  OrgName
--    Digital Equipment Corporation
--  ContactInfo
--    
--      Thomas Newton
--      Digital Equipment Corporation
--      550 King Street
--      Littleton, MA  01460
--      United States of America
--      Tel: 508-486-5293
--      E-mail: newton@school.enet.dec.com
--  Descr
--    This module defines a portion of the management 
--     information base (MIB) for managing ATM LAN Emulation
--     Broadcast and Unknown Servers.

decBusMIBObjects OBJECT IDENTIFIER ::= { decBusMIB 1 }
decBusMIBConformance OBJECT IDENTIFIER ::= { decBusMIB 2 }
decBusMIBGroups OBJECT IDENTIFIER ::= { decBusMIBConformance 1 }
decBusMIBCompliances OBJECT IDENTIFIER ::= { decBusMIBConformance 2 }

-- BusLecState ::= INTEGER {
--        other(1),
--        noBusConnect(2),
--        busConnect(3),
--        clientConnect(4),
--        operational(5),
--        deleting(6)
--        }
-- TEXTUAL-CONVENTION
--  Status
--    mandatory
--  Descr
--    Indicates the status of a LAN Emulation Client from
--     the server's perspective.
--    
--         other
--             The LEC state is unknown.
--    
--         noBusConnect
--             The LEC has not initiated a Multicast Send
--             connection to the BUS.
--    
--         busConnect
--             The Multicast Send connection from the LEC
--             to the BUS has been established.  However,
--             the BUS has not set up a Multicast Forward
--             connection.
--    
--         clientConnect
--             The BUS is waiting for a Multicast Forward
--             connection to be established.
--    
--         operational
--             The BUS is forwarding frames to the LEC.
--    
--         deleting
--             The LEC is being disconnected from the BUS.

decBusConfigTable OBJECT-TYPE
    SYNTAX SEQUENCE OF DecBusConfigEntry
    ACCESS not-accessible
    STATUS mandatory
    DESCRIPTION
        "A table which describes all the Broadcast and Unknown
         Server components implemented by this managed device."
    ::= { decBusMIBObjects 1 }

decBusConfigEntry OBJECT-TYPE
    SYNTAX DecBusConfigEntry
    ACCESS not-accessible
    STATUS mandatory
    DESCRIPTION
        "Each row of the table describes a standalone BUS or a
         component of a BUS."
    INDEX { decBusIndex }
    ::= { decBusConfigTable 1 }

DecBusConfigEntry ::= SEQUENCE {
    decBusIndex INTEGER,
    decBusRowStatus INTEGER,
    decBusAdminStatus INTEGER,
    decBusOperStatus INTEGER,
    decBusLastChange TimeTicks,
    decBusAtmAddress OCTET STRING,
    decBusDescription OCTET STRING,
    decBusLanName OCTET STRING,
    decBusLanType INTEGER,
    decBusMaxDataFrameSize INTEGER,
    decBusMaxFrameAge INTEGER,
    decBusMaxForwardingRate INTEGER
    }

decBusIndex OBJECT-TYPE
    SYNTAX INTEGER
    ACCESS read-only
    STATUS mandatory
    DESCRIPTION
        "A unique number greater than zero which identifies
         this table row."
    ::= { decBusConfigEntry 1 }

decBusRowStatus OBJECT-TYPE
    SYNTAX INTEGER {
        active(1),
        notInService(2),
        notReady(3),
        createAndGo(4),
        createAndWait(5),
        destroy(6)
        }
    ACCESS read-write
    STATUS mandatory
    DESCRIPTION
        "This object is used to create and delete Broadcast and
         Unknown Server components.
        
         If this object is writable, it will accept the values
             'createAndGo'
             'destroy'
         under suitable conditions.
        
         Use decBusAdminStatus to enable and disable service."
    ::= { decBusConfigEntry 2 }

decBusAdminStatus OBJECT-TYPE
    SYNTAX INTEGER {
        up(1),
        down(2)
        }
    ACCESS read-write
    STATUS mandatory
    DESCRIPTION
        "The desired state of this BUS component.
        
         When a BUS is distributed, this object controls the
         'local' server component, as opposed to the overall
         state of the BUS.
        
         If a LES is connected to the BUS, enabling/disabling
         either server may affect both of them.  Otherwise it
         is up to the network manager to coordinate the state
         of the servers."
    ::= { decBusConfigEntry 3 }

decBusOperStatus OBJECT-TYPE
    SYNTAX INTEGER {
        up(1),
        down(2),
        disabling(3),
        deleting(4)
        }
    ACCESS read-only
    STATUS mandatory
    DESCRIPTION
        "The operational state of this BUS component.
        
         A BUS component may not become operational until it
         has been configured with values for
        
                 LAN Type
                 Maximum Data Frame Size
                 Maximum Frame Age
        
         When a BUS is in the 'disabling' or 'deleting' state,
         attempts to set decBusAdminStatus to 'up' will fail."
    ::= { decBusConfigEntry 4 }

decBusLastChange OBJECT-TYPE
    SYNTAX TimeTicks
    ACCESS read-only
    STATUS mandatory
    DESCRIPTION
        "The value of sysUpTime at the time that this server
         last entered its current operational state.  If the
         current state was entered prior to the last
         re-initialization of the local network management
         subsystem, then this object contains a zero value."
    ::= { decBusConfigEntry 5 }

decBusAtmAddress OBJECT-TYPE
    SYNTAX OCTET STRING(SIZE(0..20))
    ACCESS read-only
    STATUS mandatory
    DESCRIPTION
        "The ATM address of this Broadcast and Unknown Server,
         or Broadcast and Unknown Server component.
        
         Clients establish Multicast Send VCCs to this address
         as part of the BUS Connect phase of LAN Emulation."
    ::= { decBusConfigEntry 6 }

decBusDescription OBJECT-TYPE
    SYNTAX OCTET STRING(SIZE(0..80))
    ACCESS read-write
    STATUS mandatory
    DESCRIPTION
        "A human-readable string which can contain anything the
         network manager wants."
    ::= { decBusConfigEntry 7 }

decBusLanName OBJECT-TYPE
    SYNTAX OCTET STRING(SIZE(0..32))
    ACCESS read-write
    STATUS mandatory
    DESCRIPTION
        "The name of this emulated LAN.  While not required for
         operational purposes, providing a LAN Name may make it
         easier to keep track of which BUS component is which.
        
         This string is not guaranteed to uniquely identify the
         emulated LAN."
    REFERENCE
        "ATM Forum LAN Emulation Over ATM Specification, V1.0,
         Section 5.1.1"
    ::= { decBusConfigEntry 8 }

decBusLanType OBJECT-TYPE
    SYNTAX INTEGER {
        aflane8023(2),
        aflane8025(3)
        }
    ACCESS read-write
    STATUS mandatory
    DESCRIPTION
        "The data frame format (or LAN-TYPE) for the emulated
         LAN this Broadcast and Unknown Server supports.
        
         In an active emulated LAN, this parameter MUST have a
         consistent value in all of the LES and BUS components
         serving the emulated LAN.  Otherwise, problems may
         result.
        
         This columnar object's value may only be changed when
         'decBus[Admin,Oper]Status' are 'down'."
    REFERENCE
        "ATM Forum LAN Emulation Over ATM Specification, V1.0,
         Section 5.1.2"
    ::= { decBusConfigEntry 9 }

decBusMaxDataFrameSize OBJECT-TYPE
    SYNTAX INTEGER {
        max1516(2),
        max4544(3),
        max9234(4),
        max18190(5)
        }
    ACCESS read-write
    STATUS mandatory
    DESCRIPTION
        "The maximum AAL-5 SDU size for data frames sent over
         this emulated LAN.  This must be one of the standard
         sizes defined in the LAN Emulation specification, in
         other words either 1516, 4544, 9234, or 18190 octets.
        
         In an active emulated LAN, this parameter MUST have a
         consistent value in all of the LES and BUS components
         serving the emulated LAN.  Otherwise, problems may
         result.
        
         This columnar object's value may only be changed when
         'decBus[Admin,Oper]Status' are 'down'."
    REFERENCE
        "ATM Forum LAN Emulation Over ATM Specification, V1.0,
         Section 5.1.2"
    ::= { decBusConfigEntry 10 }

decBusMaxFrameAge OBJECT-TYPE
    SYNTAX INTEGER (1..4)
--  Units
--    seconds
    ACCESS read-write
    STATUS mandatory
    DESCRIPTION
        "The maximum amount of time which this Broadcast and
         Unknown Server can hold a frame before being forced
         to either forward or discard it.
        
         If a BUS is distributed, each of its servers should
         have the same value for this parameter."
    REFERENCE
        "ATM Forum LAN Emulation Over ATM Specification, V1.0,
         Section 5.1.2"
    ::= { decBusConfigEntry 11 }

decBusMaxForwardingRate OBJECT-TYPE
    SYNTAX INTEGER ( 0..2147483647 )
--  Units
--    bits per second
    ACCESS read-write
    STATUS mandatory
    DESCRIPTION
        "The maximum rate at which this Broadcast and Unknown
         Server will forward frames."
    ::= { decBusConfigEntry 12 }

decBusClientStatesTable OBJECT-TYPE
    SYNTAX SEQUENCE OF DecBusClientStatesEntry
    ACCESS not-accessible
    STATUS mandatory
    DESCRIPTION
        "A table describing how many clients are in various
         membership states."
    ::= { decBusMIBObjects 2 }

decBusClientStatesEntry OBJECT-TYPE
    SYNTAX DecBusClientStatesEntry
    ACCESS not-accessible
    STATUS mandatory
    DESCRIPTION
        "Each row contains counters for one BUS component."
    INDEX { decBusIndex }
-- Augments decBusConfigEntry
    ::= { decBusClientStatesTable 1 }

DecBusClientStatesEntry ::= SEQUENCE {
    decBusActiveClients INTEGER,
    decBusMulticastFwdInProgress INTEGER,
    decBusTerminating INTEGER
    }

decBusActiveClients OBJECT-TYPE
    SYNTAX INTEGER
    ACCESS read-only
    STATUS mandatory
    DESCRIPTION
        "The number of active clients of this BUS component.
        
         This count only includes those clients which have
         both Multicast Send and Multicast Forward VCCs."
    ::= { decBusClientStatesEntry 1 }

decBusMulticastFwdInProgress OBJECT-TYPE
    SYNTAX INTEGER
    ACCESS read-only
    STATUS mandatory
    DESCRIPTION
        "The number of clients to which this BUS component
         is currently establishing Multicast Forward VCCs."
    ::= { decBusClientStatesEntry 2 }

decBusTerminating OBJECT-TYPE
    SYNTAX INTEGER
    ACCESS read-only
    STATUS mandatory
    DESCRIPTION
        "The number of clients whose memberships this BUS
         component is in the process of terminating."
    ::= { decBusClientStatesEntry 3 }

decBusTrafficTable OBJECT-TYPE
    SYNTAX SEQUENCE OF DecBusTrafficEntry
    ACCESS not-accessible
    STATUS mandatory
    DESCRIPTION
        "A table of traffic statistics, with one row for each
         Broadcast and Unknown Server."
    ::= { decBusMIBObjects 3 }

decBusTrafficEntry OBJECT-TYPE
    SYNTAX DecBusTrafficEntry
    ACCESS not-accessible
    STATUS mandatory
    DESCRIPTION
        "A set of traffic statistics for one BUS component."
    INDEX { decBusIndex }
    ::= { decBusTrafficTable 1 }

DecBusTrafficEntry ::= SEQUENCE {
    decBusFramesForwarded Counter,
    decBusInvalidFrames Counter,
    decBusFramesAgedOut Counter,
    decBusFramesRateLimited Counter,
    decBusFramesDiscarded Counter
    }

decBusFramesForwarded OBJECT-TYPE
    SYNTAX Counter
    ACCESS read-only
    STATUS mandatory
    DESCRIPTION
        "The number of frames successfully forwarded by this
         Broadcast and Unknown Server."
    ::= { decBusTrafficEntry 1 }

decBusInvalidFrames OBJECT-TYPE
    SYNTAX Counter
    ACCESS read-only
    STATUS mandatory
    DESCRIPTION
        "The number of frames which were discarded because
         of errors (such as invalid frame length)."
    ::= { decBusTrafficEntry 2 }

decBusFramesAgedOut OBJECT-TYPE
    SYNTAX Counter
    ACCESS read-only
    STATUS mandatory
    DESCRIPTION
        "The number of frames which were discarded because
         delay exceeded the Maximum Frame Age."
    ::= { decBusTrafficEntry 3 }

decBusFramesRateLimited OBJECT-TYPE
    SYNTAX Counter
    ACCESS read-only
    STATUS mandatory
    DESCRIPTION
        "The number of frames which were discarded in order
         to enforce 'decBusMaxForwardingRate'."
    ::= { decBusTrafficEntry 4 }

decBusFramesDiscarded OBJECT-TYPE
    SYNTAX Counter
    ACCESS read-only
    STATUS mandatory
    DESCRIPTION
        "The number of frames which could not be forwarded,
         even though no errors had been detected, and the
         frames had not aged out."
    ::= { decBusTrafficEntry 5 }

decBusClientTable OBJECT-TYPE
    SYNTAX SEQUENCE OF DecBusClientEntry
    ACCESS not-accessible
    STATUS mandatory
    DESCRIPTION
        "A table listing clients of the emulated LANs which
         this node serves.
        
         This table reflects the actual membership of each
         emulated LAN, as opposed to the desired membership."
    ::= { decBusMIBObjects 4 }

decBusClientEntry OBJECT-TYPE
    SYNTAX DecBusClientEntry
    ACCESS not-accessible
    STATUS mandatory
    DESCRIPTION
        "Each entry describes an active LAN Emulation Client,
         from the perspective of the BUS."
    INDEX { decBusIndex, decBusClientIndex }
    ::= { decBusClientTable 1 }

DecBusClientEntry ::= SEQUENCE {
    decBusClientIndex INTEGER,
    decBusClientAtmAddress OCTET STRING,
    decBusClientID INTEGER,
    decBusClientUsedSeveralIDs INTEGER,
    decBusClientState INTEGER,
    decBusClientRowStatus INTEGER
    }

decBusClientIndex OBJECT-TYPE
    SYNTAX INTEGER
    ACCESS read-only
    STATUS mandatory
    DESCRIPTION
        "A unique value for each table row.  This value has no
         predefined relation to a client's LECID."
    ::= { decBusClientEntry 1 }

decBusClientAtmAddress OBJECT-TYPE
    SYNTAX OCTET STRING(SIZE(0..20))
    ACCESS read-only
    STATUS mandatory
    DESCRIPTION
        "The primary ATM address of the LAN Emulation Client."
    ::= { decBusClientEntry 2 }

decBusClientID OBJECT-TYPE
    SYNTAX INTEGER(0..65279)
    ACCESS read-only
    STATUS mandatory
    DESCRIPTION
        "Contains the first LECID the appropriate BUS has seen
         for this client, or zero if none has been seen yet."
    ::= { decBusClientEntry 3 }

decBusClientUsedSeveralIDs OBJECT-TYPE
    SYNTAX INTEGER {
        true(1),
        false(2)
        }
    ACCESS read-only
    STATUS mandatory
    DESCRIPTION
        "Indicates whether the appropriate BUS has seen two or
         more non-zero LEC IDs for this client.  This is not a
         normal condition, and it would usually arise due to a
         transmission error in a frame or due to a client that
         was violating the LAN Emulation specification."
    ::= { decBusClientEntry 4 }

decBusClientState OBJECT-TYPE
    SYNTAX INTEGER {
        other(1),
        noBusConnect(2),
        busConnect(3),
        clientConnect(4),
        operational(5),
        deleting(6)
        }
    ACCESS read-only
    STATUS mandatory
    DESCRIPTION
        "Indicates the status of this LEC from the server's
         perspective."
    ::= { decBusClientEntry 5 }

decBusClientRowStatus OBJECT-TYPE
    SYNTAX INTEGER {
        active(1),
        notInService(2),
        notReady(3),
        createAndGo(4),
        createAndWait(5),
        destroy(6)
        }
    ACCESS read-write
    STATUS mandatory
    DESCRIPTION
        "Provides a way to disconnect a LEC from the BUS.
        
         When read, this object has the value 'active'.  When
         written, it only accepts the value 'destroy'.
        
         Because the ability to disconnect clients could lead
         to denial-of-service attacks, support for this
         feature is strictly optional."
    ::= { decBusClientEntry 6 }

decBusLecTable OBJECT-TYPE
    SYNTAX SEQUENCE OF DecBusLecEntry
    ACCESS not-accessible
    STATUS mandatory
    DESCRIPTION
        "A table listing clients which belong to the emulated
         LANs that this node serves."
    ::= { decBusMIBObjects 5 }

decBusLecEntry OBJECT-TYPE
    SYNTAX DecBusLecEntry
    ACCESS not-accessible
    STATUS mandatory
    DESCRIPTION
        "Each entry describes a LAN Emulation Client from the
         perspective of the BUS."
    INDEX { decBusIndex, decBusLecAtmAddress }
    ::= { decBusLecTable 1 }

DecBusLecEntry ::= SEQUENCE {
    decBusLecAtmAddress OCTET STRING,
    decBusLecIndex INTEGER,
    decBusLecID INTEGER,
    decBusLecUsedSeveralIDs INTEGER,
    decBusLecState INTEGER,
    decBusLecRowStatus INTEGER
    }

decBusLecAtmAddress OBJECT-TYPE
    SYNTAX OCTET STRING(SIZE(0..20))
    ACCESS read-only
    STATUS mandatory
    DESCRIPTION
        "The primary ATM address of the LAN Emulation Client."
    ::= { decBusLecEntry 1 }

decBusLecIndex OBJECT-TYPE
    SYNTAX INTEGER
    ACCESS read-only
    STATUS mandatory
    DESCRIPTION
        "The client's index in the 'decBusClientTable'.  Note
         that this value is NOT the client's LEC-ID."
    ::= { decBusLecEntry 2 }

decBusLecID OBJECT-TYPE
    SYNTAX INTEGER(0..65279)
    ACCESS read-only
    STATUS mandatory
    DESCRIPTION
        "Contains the first LECID the appropriate BUS has seen
         for this client, or zero if none has been seen yet."
    ::= { decBusLecEntry 3 }

decBusLecUsedSeveralIDs OBJECT-TYPE
    SYNTAX INTEGER {
        true(1),
        false(2)
        }
    ACCESS read-only
    STATUS mandatory
    DESCRIPTION
        "Indicates whether the appropriate BUS has seen two or
         more non-zero LEC IDs for this client.  This is not a
         normal condition, and it would usually arise due to a
         transmission error in a frame or due to a client that
         was violating the LAN Emulation specification."
    ::= { decBusLecEntry 4 }

decBusLecState OBJECT-TYPE
    SYNTAX INTEGER {
        other(1),
        noBusConnect(2),
        busConnect(3),
        clientConnect(4),
        operational(5),
        deleting(6)
        }
    ACCESS read-only
    STATUS mandatory
    DESCRIPTION
        "Indicates the status of this LEC from the server's
         perspective."
    ::= { decBusLecEntry 5 }

decBusLecRowStatus OBJECT-TYPE
    SYNTAX INTEGER {
        active(1),
        notInService(2),
        notReady(3),
        createAndGo(4),
        createAndWait(5),
        destroy(6)
        }
    ACCESS read-write
    STATUS mandatory
    DESCRIPTION
        "Provides a way to disconnect a LEC from the BUS.
        
         When read, this object has the value 'active'.  When
         written, it only accepts the value 'destroy'.
        
         Because the ability to disconnect clients could lead
         to denial-of-service attacks, support for this
         feature is strictly optional."
    ::= { decBusLecEntry 6 }

decBusMulticastSendTable OBJECT-TYPE
    SYNTAX SEQUENCE OF DecBusMulticastSendEntry
    ACCESS not-accessible
    STATUS mandatory
    DESCRIPTION
        "This optional table identifies Multicast Send VCCs
         at the place where they attach to the BUS.
        
         In a SVC implementation, the objects in this table
         will be read-only.
        
         In a PVC implementation, this table can be used to
         tell the BUS about the creation or the deletion of
         Multicast Send VCCs."
    ::= { decBusMIBObjects 6 }

decBusMulticastSendEntry OBJECT-TYPE
    SYNTAX DecBusMulticastSendEntry
    ACCESS not-accessible
    STATUS mandatory
    DESCRIPTION
        "Each entry describes the circuits going to one LAN
         Emulation Client."
    INDEX { decBusIndex, decBusLecAtmAddress }
-- Augments decBusLecEntry
    ::= { decBusMulticastSendTable 1 }

DecBusMulticastSendEntry ::= SEQUENCE {
    decBusMulticastSendInterface INTEGER,
    decBusMulticastSendVpi INTEGER,
    decBusMulticastSendVci INTEGER,
    decBusMulticastSendRowStatus INTEGER
    }

decBusMulticastSendInterface OBJECT-TYPE
    SYNTAX INTEGER(0..2147483647)
    ACCESS read-write
    STATUS mandatory
    DESCRIPTION
        "If a Multicast Send PVC or SVC exists, this object
         has a value equal to the 'ifIndex' of the ATM port
         which terminates that circuit at the BUS.
        
         Otherwise it has the value 0."
    ::= { decBusMulticastSendEntry 1 }

decBusMulticastSendVpi OBJECT-TYPE
    SYNTAX INTEGER(0..255)
    ACCESS read-write
    STATUS mandatory
    DESCRIPTION
        "If a Multicast Send PVC or SVC exists, this object
         has a value equal to the VPI of the Multicast Send
         VCC at the point where it connects to the BUS.
        
         Otherwise, it has the value 0."
    ::= { decBusMulticastSendEntry 2 }

decBusMulticastSendVci OBJECT-TYPE
    SYNTAX INTEGER(0..65535)
    ACCESS read-write
    STATUS mandatory
    DESCRIPTION
        "If a Multicast Send PVC or SVC exists, this object
         has a value equal to the VCI of the Multicast Send
         VCC at the point where it connects to the BUS.
        
         Otherwise, it has the value 0."
    ::= { decBusMulticastSendEntry 3 }

decBusMulticastSendRowStatus OBJECT-TYPE
    SYNTAX INTEGER {
        active(1),
        notInService(2),
        notReady(3),
        createAndGo(4),
        createAndWait(5),
        destroy(6)
        }
    ACCESS read-write
    STATUS mandatory
    DESCRIPTION
        "Used to create and delete rows in the table."
    ::= { decBusMulticastSendEntry 4 }

decBusMulticastFwdTable OBJECT-TYPE
    SYNTAX SEQUENCE OF DecBusMulticastFwdEntry
    ACCESS not-accessible
    STATUS mandatory
    DESCRIPTION
        "This optional table identifies Multicast Forward
         VCCs at the place where they attach to the BUS.
        
         In a SVC implementation, this table will be read-
         only.
        
         In a PVC implementation, this table can be used to
         tell the BUS about the creation or the deletion of
         Multicast Forward VCCs."
    ::= { decBusMIBObjects 7 }

decBusMulticastFwdEntry OBJECT-TYPE
    SYNTAX DecBusMulticastFwdEntry
    ACCESS not-accessible
    STATUS mandatory
    DESCRIPTION
        "Each entry describes the circuits going to one LAN
         Emulation Client."
    INDEX { decBusIndex, decBusMulticastFwdInterface, decBusMulticastFwdVpi, decBusMulticastFwdVci }
    ::= { decBusMulticastFwdTable 1 }

DecBusMulticastFwdEntry ::= SEQUENCE {
    decBusMulticastFwdInterface INTEGER,
    decBusMulticastFwdVpi INTEGER,
    decBusMulticastFwdVci INTEGER,
    decBusMulticastFwdRowStatus INTEGER
    }

decBusMulticastFwdInterface OBJECT-TYPE
    SYNTAX INTEGER(0..2147483647)
    ACCESS read-only
    STATUS mandatory
    DESCRIPTION
        "The 'ifIndex' of the ATM port which terminates the
         Multicast Forward VCC at the BUS."
    ::= { decBusMulticastFwdEntry 1 }

decBusMulticastFwdVpi OBJECT-TYPE
    SYNTAX INTEGER(0..255)
    ACCESS read-only
    STATUS mandatory
    DESCRIPTION
        "The VPI of the Multicast Forward VCC at the point
         where this VCC connects to the BUS."
    ::= { decBusMulticastFwdEntry 2 }

decBusMulticastFwdVci OBJECT-TYPE
    SYNTAX INTEGER(0..65535)
    ACCESS read-only
    STATUS mandatory
    DESCRIPTION
        "The VCI of the Multicast Forward VCC at the point
         where this VCC connects to the BUS."
    ::= { decBusMulticastFwdEntry 3 }

decBusMulticastFwdRowStatus OBJECT-TYPE
    SYNTAX INTEGER {
        active(1),
        notInService(2),
        notReady(3),
        createAndGo(4),
        createAndWait(5),
        destroy(6)
        }
    ACCESS read-write
    STATUS mandatory
    DESCRIPTION
        "An object provided to satisfy the requirement that
         all tables have at least one accessible object; in
         the future, it may also be extended to provide PVC
         support."
    ::= { decBusMulticastFwdEntry 4 }

decBusCallStatsTable OBJECT-TYPE
    SYNTAX SEQUENCE OF DecBusCallStatsEntry
    ACCESS not-accessible
    STATUS mandatory
    DESCRIPTION
        "This table holds statistics on virtual circuit/leaf
         establishment attempts.
        
         It contains one row for each Broadcast and Unknown
         Server, and acts as an extension to the
         'decBusConfigTable'."
    ::= { decBusMIBObjects 8 }

decBusCallStatsEntry OBJECT-TYPE
    SYNTAX DecBusCallStatsEntry
    ACCESS not-accessible
    STATUS mandatory
    DESCRIPTION
        "Each row contains connection statistics for one
         Broadcast and Unknown Server."
    INDEX { decBusIndex }
    ::= { decBusCallStatsTable 1 }

DecBusCallStatsEntry ::= SEQUENCE {
    decBusMulticastSendCalls Counter,
    decBusMulticastSendFailures Counter,
    decBusMsOutOfResourcesFailures Counter,
    decBusMsInvalidInfoElements Counter,
    decBusMsWrongLanTypes Counter,
    decBusMsWrongMaxFrameSizes Counter,
    decBusMulticastForwardCalls Counter,
    decBusMulticastForwardFailures Counter,
    decBusMfOutOfResourcesFailures Counter,
    decBusMfClientRejects Counter
    }

decBusMulticastSendCalls OBJECT-TYPE
    SYNTAX Counter
    ACCESS read-only
    STATUS mandatory
    DESCRIPTION
        "The total number of Multicast Send establishment
         attempts for this BUS component."
    ::= { decBusCallStatsEntry 1 }

decBusMulticastSendFailures OBJECT-TYPE
    SYNTAX Counter
    ACCESS read-only
    STATUS mandatory
    DESCRIPTION
        "The number of Multicast Send establishment attempts
         for this BUS component which were not accepted.
        
         This includes failures counted in
        
                 decBusMsOutOfResourcesFailures
                 decBusMsInvalidInfoElements
                 decBusMsWrongLanTypes
                 decBusMsWrongMaxFrameSizes
        
          and any miscellaneous failures."
    ::= { decBusCallStatsEntry 2 }

decBusMsOutOfResourcesFailures OBJECT-TYPE
    SYNTAX Counter
    ACCESS read-only
    STATUS mandatory
    DESCRIPTION
        "The number of Multicast Send establishment attempts
         for this BUS component which failed for lack of
         resources."
    ::= { decBusCallStatsEntry 3 }

decBusMsInvalidInfoElements OBJECT-TYPE
    SYNTAX Counter
    ACCESS read-only
    STATUS mandatory
    DESCRIPTION
        "The number of Multicast Send establishment attempts
         for this BUS component which failed because required
         information elements were missing or contained
         invalid information.
        
         The optional Event Log group can help you determine
         which information elements were invalid or missing.
        
         This object does not count call failures included in
         decBusMsWrongLanTypes or decBusMsWrongMaxFrameSizes."
    ::= { decBusCallStatsEntry 4 }

decBusMsWrongLanTypes OBJECT-TYPE
    SYNTAX Counter
    ACCESS read-only
    STATUS mandatory
    DESCRIPTION
        "The number of Multicast Send establishment attempts
         which were rejected because they specified a
         different LAN Type (data frame format) than the
         one configured for this BUS component."
    ::= { decBusCallStatsEntry 5 }

decBusMsWrongMaxFrameSizes OBJECT-TYPE
    SYNTAX Counter
    ACCESS read-only
    STATUS mandatory
    DESCRIPTION
        "The number of Multicast Send establishment attempts
         which were rejected because they specified a
         different maximum AAL-5 SDU size than the one
         configured for this BUS component."
    ::= { decBusCallStatsEntry 6 }

decBusMulticastForwardCalls OBJECT-TYPE
    SYNTAX Counter
    ACCESS read-only
    STATUS mandatory
    DESCRIPTION
        "The number of Multicast Forward connections which
         this BUS tried to establish."
    ::= { decBusCallStatsEntry 7 }

decBusMulticastForwardFailures OBJECT-TYPE
    SYNTAX Counter
    ACCESS read-only
    STATUS mandatory
    DESCRIPTION
        "The number of Multicast Forward connections which
         this BUS was unable to establish.
        
         This includes failures counted in
        
                 decBusMfOutOfResourcesFailures
                 decBusMfClientRejects
        
          and any miscellaneous failures."
    ::= { decBusCallStatsEntry 8 }

decBusMfOutOfResourcesFailures OBJECT-TYPE
    SYNTAX Counter
    ACCESS read-only
    STATUS mandatory
    DESCRIPTION
        "The number of Multicast Forward connections which
         this BUS component could not establish due to lack
         of resources."
    ::= { decBusCallStatsEntry 9 }

decBusMfClientRejects OBJECT-TYPE
    SYNTAX Counter
    ACCESS read-only
    STATUS mandatory
    DESCRIPTION
        "The number of Multicast Forward connections which
         this BUS component's clients refused to accept."
    ::= { decBusCallStatsEntry 10 }

decBusEventLogMaximumSize OBJECT-TYPE
    SYNTAX INTEGER
    ACCESS read-write
    STATUS mandatory
    DESCRIPTION
        "The minimum number of events which the agent should
         remember before purging old log entries to make way
         for new ones."
    ::= { decBusMIBObjects 9 }

decBusEventLogTable OBJECT-TYPE
    SYNTAX SEQUENCE OF DecBusEventLogEntry
    ACCESS not-accessible
    STATUS mandatory
    DESCRIPTION
        "A table of event log entries for the emulated
         LANs that this node serves."
    ::= { decBusMIBObjects 10 }

decBusEventLogEntry OBJECT-TYPE
    SYNTAX DecBusEventLogEntry
    ACCESS not-accessible
    STATUS mandatory
    DESCRIPTION
        "An entry describing a significant event."
    INDEX { decBusEventIndex }
    ::= { decBusEventLogTable 1 }

DecBusEventLogEntry ::= SEQUENCE {
    decBusEventIndex INTEGER,
    decBusEventType INTEGER,
    decBusEventReason INTEGER,
    decBusEventServer INTEGER,
    decBusEventServerAtmAddress OCTET STRING,
    decBusEventClientAtmAddress OCTET STRING,
    decBusEventTimestamp TimeTicks
    }

decBusEventIndex OBJECT-TYPE
    SYNTAX INTEGER
    ACCESS read-only
    STATUS mandatory
    DESCRIPTION
        "A unique number greater than zero which identifies
         this table row."
    ::= { decBusEventLogEntry 1 }

decBusEventType OBJECT-TYPE
    SYNTAX INTEGER {
        joinFailed(1)
        }
    ACCESS read-only
    STATUS mandatory
    DESCRIPTION
        "The event which triggered this log entry.
        
             joinFailed(1) - A client tried to join one of the
                 broadcast domains which this host serves, but
                 the attempt failed.                          "
    ::= { decBusEventLogEntry 2 }

decBusEventReason OBJECT-TYPE
    SYNTAX INTEGER {
        versionNotSupported(1),
        invalidRequestParameters(2),
        duplicateLanDestination(4),
        duplicateAtmAddress(5),
        insufficientResources(6),
        accessDenied(7),
        invalidRequestorId(8),
        invalidLanDestination(9),
        invalidAtmAddress(10),
        wrongLanType(50),
        wrongMaxFrameSize(51),
        wrongJoinMaxFrameSize(52),
        nonDuplicateRequest(53),
        controlDistributeFailure(54),
        multicastForwardFailure(55),
        joinNotCompleted(56),
        joinTimeout(57),
        busConnectTimeout(58),
        clientNotConnectedToLes(59),
        missingInformationElement(70),
        noAalParameters(71),
        noAtmTrafficDescriptor(72),
        noBroadbandBearerCapability(73),
        noBlli(74),
        noCallingPartyNumber(75),
        noCalledPartyNumber(76),
        noConnectionIdentifier(77),
        noQosParameter(78),
        invalidInformationElement(80),
        invalidAalParameters(81),
        invalidAtmTrafficDescriptor(82),
        invalidBroadbandBearerCapability(83),
        invalidBlli(84),
        invalidCallingPartyNumber(85),
        invalidCalledPartyNumber(86),
        invalidConnectionIdentifier(87),
        invalidQosParameter(88),
        invalidAalMode(90),
        invalidAalSccs(91),
        insecureAtmAddress(100),
        unverifiedAtmAddress(101)
        }
    ACCESS read-only
    STATUS mandatory
    DESCRIPTION
        "The cause of the failure."
    ::= { decBusEventLogEntry 3 }

decBusEventServer OBJECT-TYPE
    SYNTAX INTEGER
    ACCESS read-only
    STATUS mandatory
    DESCRIPTION
        "The 'decBusIndex' of the LAN Emulation Server that
         was involved in this incident.
        
         If the value of this object is zero, it indicates
         that the server no longer exists."
    ::= { decBusEventLogEntry 4 }

decBusEventServerAtmAddress OBJECT-TYPE
    SYNTAX OCTET STRING(SIZE(0..20))
    ACCESS read-only
    STATUS mandatory
    DESCRIPTION
        "The ATM address of the Broadcast and Unknown Server
         that was involved in this incident."
    ::= { decBusEventLogEntry 5 }

decBusEventClientAtmAddress OBJECT-TYPE
    SYNTAX OCTET STRING(SIZE(0..20))
    ACCESS read-only
    STATUS mandatory
    DESCRIPTION
        "If known, the ATM address of the LAN Emulation Client
         that was involved in this incident."
    ::= { decBusEventLogEntry 6 }

decBusEventTimestamp OBJECT-TYPE
    SYNTAX TimeTicks
    ACCESS read-only
    STATUS mandatory
    DESCRIPTION
        "The value of sysUpTime at the time that the event
         occurred.  If the event occurred prior to the last
         re-initialization of the local network management
         subsystem, this object contains a zero value."
    ::= { decBusEventLogEntry 7 }

decBusConfigGroup OBJECT IDENTIFIER ::= { decBusMIBGroups 1 }
-- OBJECT-GROUP
--  Status
--    mandatory
--  Descr
--    A collection of objects describing all of the
--     Broadcast and Unknown Server components which
--     this managed device implements.
--  objects
--    decBusRowStatus, decBusAdminStatus, decBusOperStatus, 
--    decBusLastChange, decBusAtmAddress, decBusDescription, 
--    decBusLanName, decBusLanType, decBusMaxDataFrameSize, 
--    decBusMaxFrameAge, decBusMaxForwardingRate

decBusClientStatesGroup OBJECT IDENTIFIER ::= { decBusMIBGroups 2 }
-- OBJECT-GROUP
--  Status
--    mandatory
--  Descr
--    A collection of objects describing how many BUS
--     clients are in various membership states.
--  objects
--    decBusActiveClients, decBusMulticastFwdInProgress, 
--    decBusTerminating

decBusTrafficGroup OBJECT IDENTIFIER ::= { decBusMIBGroups 3 }
-- OBJECT-GROUP
--  Status
--    mandatory
--  Descr
--    A collection of objects describing traffic and
--     packet loss statistics for each BUS component.
--  objects
--    decBusFramesForwarded, decBusInvalidFrames, 
--    decBusFramesAgedOut, decBusFramesRateLimited,
--    decBusFramesDiscarded

decBusClientGroup OBJECT IDENTIFIER ::= { decBusMIBGroups 4 }
-- OBJECT-GROUP
--  Status
--    mandatory
--  Descr
--    A collection of objects describing the clients
--     of each managed BUS component.
--  objects
--    decBusClientAtmAddress, decBusClientID, 
--    decBusClientUsedSeveralIDs, decBusClientState, 
--    decBusClientRowStatus

decBusLecGroup OBJECT IDENTIFIER ::= { decBusMIBGroups 5 }
-- OBJECT-GROUP
--  Status
--    mandatory
--  Descr
--    A collection of objects describing the clients
--     of each managed BUS component.
--  objects
--    decBusLecIndex, decBusLecID, decBusLecUsedSeveralIDs, 
--    decBusLecState, decBusLecRowStatus

decBusCircuitGroup OBJECT IDENTIFIER ::= { decBusMIBGroups 6 }
-- OBJECT-GROUP
--  Status
--    mandatory
--  Descr
--    An optional collection of objects describing
--     Multicast Send and Multicast Forward VCCs.
--  objects
--    decBusMulticastSendInterface, decBusMulticastSendVpi, 
--    decBusMulticastSendVci, decBusMulticastSendRowStatus, 
--    decBusMulticastFwdRowStatus

decBusCallStatsGroup OBJECT IDENTIFIER ::= { decBusMIBGroups 7 }
-- OBJECT-GROUP
--  Status
--    mandatory
--  Descr
--    A collection of BUS statistics concerning SVC
--     establishments.
--  objects
--    decBusMulticastSendCalls, decBusMulticastSendFailures, 
--    decBusMsOutOfResourcesFailures, decBusMsInvalidInfoElements, 
--    decBusMsWrongLanTypes, decBusMsWrongMaxFrameSizes, 
--    decBusMulticastForwardCalls, decBusMulticastForwardFailures, 
--    decBusMfOutOfResourcesFailures, decBusMfClientRejects

decBusEventLogGroup OBJECT IDENTIFIER ::= { decBusMIBGroups 8 }
-- OBJECT-GROUP
--  Status
--    mandatory
--  Descr
--    A collection of objects which provide event
--     logging for Broadcast and Unknown Servers.
--  objects
--    decBusEventLogMaximumSize, decBusEventType, decBusEventReason, 
--    decBusEventServer, decBusEventServerAtmAddress, 
--    decBusEventClientAtmAddress, decBusEventTimestamp

decBusMIBCompliance OBJECT IDENTIFIER ::= { decBusMIBCompliances 1 }
-- MODULE-COMPLIANCE
--  Status
--    mandatory
--  Descr
--    The compliance statement for SNMP entities
--     located in ATM LAN Emulation Servers.
--  Module
--    >>current<<
--   MandGroup
--    decBusConfigGroup
--   MandGroup
--    decBusClientStatesGroup
--   MandGroup
--    decBusTrafficGroup
--   MandGroup
--    decBusClientGroup
--   MandGroup
--    decBusLecGroup
--   MandGroup
--    decBusCallStatsGroup
--   OptGroup
--    decBusCircuitGroup
--   OptGroup
--    decBusEventLogGroup
--   ObjVar
--    decBusRowStatus
--   ObjVar
--    decBusAdminStatus
--   ObjVar
--    decBusDescription
--   ObjVar
--    decBusLanName
--   ObjVar
--    decBusLanType
--   ObjVar
--    decBusMaxDataFrameSize
--   ObjVar
--    decBusMaxFrameAge
--   ObjVar
--    decBusMaxForwardingRate
--   ObjVar
--    decBusClientRowStatus
--   ObjVar
--    decBusLecRowStatus
--   ObjVar
--    decBusEventLogMaximumSize


END
