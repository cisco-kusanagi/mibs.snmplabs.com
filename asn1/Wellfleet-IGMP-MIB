-- @(#)WSCCS h/mibs-igmp.mib 1.5.2.3 12/26/96
Wellfleet-IGMP-MIB DEFINITIONS ::= BEGIN

-- Created by mdl2asn version 3.1
-- Creation date: Wed Aug 30 16:42:48 EDT 1995


    IMPORTS

      IpAddress, Counter
        FROM RFC1155-SMI
      OBJECT-TYPE
        FROM RFC-1212
      wfIgmpGroup
        FROM Wellfleet-COMMON-MIB;


    wfIgmpBase	OBJECT IDENTIFIER ::= { wfIgmpGroup 1 }

    wfIgmpBaseCreate OBJECT-TYPE
        SYNTAX	INTEGER {
    		    created(1),
    		    deleted(2)
    		}
        ACCESS	read-write
        STATUS	mandatory
        DESCRIPTION
                "Create/Delete parameter. Default is created.
                Users perform a set operation on this
                object in order to create/delete IGMP."
        DEFVAL	{ created }
        ::= { wfIgmpBase 1 }

    wfIgmpBaseEnable OBJECT-TYPE
        SYNTAX	INTEGER {
    		    enabled(1),
    		    disabled(2)
    		}
        ACCESS	read-write
        STATUS	mandatory
        DESCRIPTION
                "Enable/Disable Parameter indicates whether
                this IGMP record is enabled or disabled."
        DEFVAL	{ enabled }
        ::= { wfIgmpBase 2 }

    wfIgmpBaseState OBJECT-TYPE
        SYNTAX	INTEGER {
    		    up(1),
    		    down(2),
    		    init(3),
    		    notpres(4)
    		}
        ACCESS	read-only
        STATUS	mandatory
        DESCRIPTION
                "The current state of the entire IGMP."
        DEFVAL	{ notpres }
        ::= { wfIgmpBase 3 }

    wfIgmpBaseEstimatedGroups OBJECT-TYPE
        SYNTAX	INTEGER(5..65535)
        ACCESS	read-write
        STATUS	mandatory
        DESCRIPTION
                "The number of estimated groups that will
                be used through this router."
        DEFVAL	{ 20 }
        ::= { wfIgmpBase 4 }

    wfIgmpBaseVersionThreshold OBJECT-TYPE
        SYNTAX	INTEGER(1..65535)
        ACCESS	read-write
        STATUS	mandatory
        DESCRIPTION
                "The time (in seconds) that will pass after
                the last old style query before we will try
                to become the igmp designated querier"
        DEFVAL	{ 540 }
        ::= { wfIgmpBase 5 }

    wfIgmpBaseDebug OBJECT-TYPE
        SYNTAX	INTEGER
        ACCESS	read-write
        STATUS	mandatory
        DESCRIPTION
                "This is a debug field for IGMP. Setting bits
                cause igmp to gernerate certain log messages.
                This field will NOT restart IGMP.
                The follow bits maybe set in any combination
		(LS stands for least significant):

		0x00000001 for received IGMP protocol (join/leave) packets
                0x00000002 for sent IGMP messages
		0x00000004 for received mcast protocl packets
                0x00000008 for MTRACE related log messages
                0x00000010 for configuration related log messages
                0x00000020 for interaction with mcast protocols
                0x00000040 for interaction with RSVP
                0x00000080 for MTM forwarding cache related log messages
                0x00000100 for IGMP Relay related log messages"

        ::= { wfIgmpBase 6 }

    wfIgmpBaseJoinAckEnable OBJECT-TYPE
        SYNTAX	INTEGER {
    		    enabled(1),
    		    disabled(2)
    		}
        ACCESS	read-write
        STATUS	mandatory
        DESCRIPTION
                "Enable/Disable Parameter indicates whether an immediate
                response is needed for an IGMP report by sending an IGMP
                query to the group of this IGMP report."
        DEFVAL	{ disabled }
        ::= { wfIgmpBase 7 }

    wfIgmpBaseFwdCacheLimit OBJECT-TYPE
        SYNTAX	INTEGER(64..65535)
        ACCESS	read-write
        STATUS	mandatory
        DESCRIPTION
                "Maximum number of MTM forwarding cache entries"
        DEFVAL	{ 512 }
        ::= { wfIgmpBase 8 }

    wfIgmpBaseIgnoreNonLocalReport OBJECT-TYPE
        SYNTAX	INTEGER {
    		    ignore(1),
    		    accept(2)
    		}
        ACCESS	read-write
        STATUS	mandatory
        DESCRIPTION
                "Whether IGMP joins/leaves from a non-local network are
		accepted. For example, if network 10.10.10.0/24 is defined
		on circuit 1 which is connected to a physical wire for
		both 10.10.10.0/24 and 10.10.11.0/24, an IGMP Join
		from the 10.10.11.0/24 network may be ignored on the circuit"

        DEFVAL	{ ignore }
        ::= { wfIgmpBase 9 }

    wfIgmpBaseRelayEnable OBJECT-TYPE
        SYNTAX	INTEGER {
    		    enabled(1),
    		    disabled(2)
    		}
        ACCESS	read-write
        STATUS	mandatory
        DESCRIPTION
                "Enable/Disable Parameter indicates whether
                the IGMP Relay is enabled or disabled."
        DEFVAL	{ disabled }
        ::= { wfIgmpBase 10 }

    wfIgmpBaseRelayTimeoutValue OBJECT-TYPE
        SYNTAX  INTEGER(0..65535)
        ACCESS  read-write
        STATUS  mandatory
        DESCRIPTION
                "The timer value for timing out IGMP-R forward entries."
        DEFVAL  { 60 }
        ::= { wfIgmpBase 11 }

    wfIgmpBaseRelayFwdOptions OBJECT-TYPE
        SYNTAX	INTEGER {
    		    primary(1),
    		    backup(2),
                    both(3)
    		}
        ACCESS	read-write
        STATUS	mandatory
        DESCRIPTION
                "This mib attribute indicates whether multicast data
                 is forwarded to IGMP-R primary upstream circuit, 
                 backup upstream, or both of them."
        DEFVAL	{ primary }
        ::= { wfIgmpBase 12 }

    wfIgmpBaseGroupCount OBJECT-TYPE
        SYNTAX	Counter
        ACCESS	read-only
        STATUS	mandatory
        DESCRIPTION
                "Actual number of groups presented on the router"
        ::= { wfIgmpBase 13 }

    wfIgmpBasePerStreamRedundEnable OBJECT-TYPE
        SYNTAX  INTEGER {
                    enabled(1),
                    disabled(2)
                }
        ACCESS  read-write
        STATUS  mandatory
        DESCRIPTION
                "Enable/Disable Parameter indicates whether
                 the IGMP Relay Per-Stream Redundancy is enabled
                 or disabled.
 
                 Per-Stream Redundancy allows a stream to fail over
                 to backup link if it is not received on the primary
                 link for a period of wfIgmpBaseRelayTimeoutValue,
                 and then fall back if the stream is received on
                 the primary link again.
 
                 To enable this feature, you must enable
                 wfIgmpBaseRelayEnable."
 
        DEFVAL  { disabled }
        ::= { wfIgmpBase 14 }

    wfIgmpIfTable OBJECT-TYPE
        SYNTAX	SEQUENCE OF WfIgmpIfEntry
        ACCESS	not-accessible
        STATUS	mandatory
        DESCRIPTION
                "List of configured IGMP interfaces"
        ::= { wfIgmpGroup 2 }

    wfIgmpIfEntry OBJECT-TYPE
        SYNTAX	WfIgmpIfEntry
        ACCESS	not-accessible
        STATUS	mandatory
        DESCRIPTION
                "A description of an IGMP interface"
        INDEX	{ wfIgmpIfCctno }
        ::= { wfIgmpIfTable 1 }

    WfIgmpIfEntry ::= SEQUENCE {
    	    wfIgmpIfCreate
    		INTEGER,
    	    wfIgmpIfEnable
    		INTEGER,
    	    wfIgmpIfState
    		INTEGER,
    	    wfIgmpDesignatedRouter
    		IpAddress,
    	    wfIgmpIfQueryRate
    		INTEGER,
    	    wfIgmpIfMembershipTimeout
    		INTEGER,
    	    wfIgmpIfDRTimeout
    		INTEGER,
    	    wfIgmpIfLocalIpAddress
    		IpAddress,
    	    wfIgmpIfCctno
    		INTEGER,
    	    wfIgmpIfInDatagrams
    		Counter,
    	    wfIgmpIfOutQueries
    		Counter,
    	    wfIgmpIfInQueries
    		Counter,
    	    wfIgmpIfDiscards
    		Counter,
    	    wfIgmpIfNetVersion
    		INTEGER,
    	    wfIgmpIfMaxHostResponse
    		INTEGER,
            wfIgmpIfRoutingProtocol
                INTEGER,
	    wfIgmpIfDroppedDataPkt
		Counter,
    	    wfIgmpIfMtraceEntryLifetime
    		INTEGER,
    	    wfIgmpIfInMtraceReqs
    		Counter,
    	    wfIgmpIfOutMtraceReqs
    		Counter,
    	    wfIgmpIfInMtraceResps
    		Counter,
    	    wfIgmpIfOutMtraceResps
    		Counter,
    	    wfIgmpIfRelayType
    		INTEGER,
            wfIgmpIfUnsolicitedReportInterval
    		INTEGER,
            wfIgmpIfSuppressQuery
    		INTEGER,
    	    wfIgmpIfGroupCount
    		Counter,
            wfIgmpIfVRRPTriggerState
                INTEGER,
            wfIgmpIfStaticFwdCacheLifeTime
                 INTEGER
        }

    wfIgmpIfCreate OBJECT-TYPE
        SYNTAX	INTEGER {
    		    created(1),
    		    deleted(2)
    		}
        ACCESS	read-write
        STATUS	mandatory
        DESCRIPTION
                "Indicates whether this IGMP If record is to be deleted or created"
        DEFVAL	{ created }
        ::= { wfIgmpIfEntry 1 }

    wfIgmpIfEnable OBJECT-TYPE
        SYNTAX	INTEGER {
    		    enabled(1),
    		    disabled(2)
    		}
        ACCESS	read-write
        STATUS	mandatory
        DESCRIPTION
                "Indicates whether this IGMP intf record is to be enabled or disabled"
        DEFVAL	{ enabled }
        ::= { wfIgmpIfEntry 2 }

    wfIgmpIfState OBJECT-TYPE
        SYNTAX	INTEGER {
    		    up(1),
    		    down(2),
    		    init(3),
    		    invalid(4),
    		    notpres(5)
    		}
        ACCESS	read-only
        STATUS	mandatory
        DESCRIPTION
                "The current state of the IGMP interface. Invalid indicates an error in
                processing the cfg record"
        DEFVAL	{ notpres }
        ::= { wfIgmpIfEntry 3 }

    wfIgmpDesignatedRouter OBJECT-TYPE
        SYNTAX	IpAddress
        ACCESS	read-only
        STATUS	mandatory
        DESCRIPTION
                "The current Igmp Designated Router. If there are multipule
                routers on a multi-access network, this is the router sending
                the igmp host queries."
        ::= { wfIgmpIfEntry 4 }

    wfIgmpIfQueryRate OBJECT-TYPE
        SYNTAX	INTEGER(0..4096)
        ACCESS	read-write
        STATUS	mandatory
        DESCRIPTION
                "Query rate. This value specifies, in seconds, how often a local group
                membership is queried.  If set to 0, no queries will be sent out this
                interface, and it should mean that there are no hosts on that interface
                that want to multicast.  This does not mean no multicast traffic will go
                out this port, as routed mutilcast traffic may use this interface"
        DEFVAL	{ 120 }
        ::= { wfIgmpIfEntry 5 }

    wfIgmpIfMembershipTimeout OBJECT-TYPE
        SYNTAX	INTEGER(30..8192)
        ACCESS	read-write
        STATUS	mandatory
        DESCRIPTION
                "Membership timeout. This value specifies, in seconds, the amount of
                time that a local group membership is valid without confirmation.
                The suggested value is (2*QueryRate)+20"
        DEFVAL	{ 260 }
        ::= { wfIgmpIfEntry 6 }

    wfIgmpIfDRTimeout OBJECT-TYPE
        SYNTAX	INTEGER(10..8192)
        ACCESS	read-write
        STATUS	mandatory
        DESCRIPTION
                "Designated Router Timeout. This value specifies, in seconds, the
                amount of time from the last host query message that will be used
                to determine the loss of the IGMP designated router. "
        DEFVAL	{ 140 }
        ::= { wfIgmpIfEntry 7 }

    wfIgmpIfLocalIpAddress OBJECT-TYPE
        SYNTAX	IpAddress
        ACCESS	read-only
        STATUS	mandatory
        DESCRIPTION
                "IP Address currently in use on this circuit. This is the IP address
                that being used to generate and multicast traffic"
        ::= { wfIgmpIfEntry 8 }

    wfIgmpIfCctno OBJECT-TYPE
        SYNTAX	INTEGER
        ACCESS	read-only
        STATUS	mandatory
        DESCRIPTION
                "The Circuit IGMP should be running on"
        ::= { wfIgmpIfEntry 9 }

    wfIgmpIfInDatagrams OBJECT-TYPE
        SYNTAX	Counter
        ACCESS	read-only
        STATUS	mandatory
        DESCRIPTION
                "The total number of IGMP datagrams received on the interface."
        ::= { wfIgmpIfEntry 10 }

    wfIgmpIfOutQueries OBJECT-TYPE
        SYNTAX	Counter
        ACCESS	read-only
        STATUS	mandatory
        DESCRIPTION
                "The number of Host Membership Query messages sent out of this
                interface."
        ::= { wfIgmpIfEntry 11 }

    wfIgmpIfInQueries OBJECT-TYPE
        SYNTAX	Counter
        ACCESS	read-only
        STATUS	mandatory
        DESCRIPTION
                "The number of Host Membership Query messages that have been
                received on this interface."
        ::= { wfIgmpIfEntry 12 }

    wfIgmpIfDiscards OBJECT-TYPE
        SYNTAX	Counter
        ACCESS	read-only
        STATUS	mandatory
        DESCRIPTION
                "The number of IGMP messages received on this interface that
                were discarded due to bad checksums, illegal message types,
                bad values in fields, etc."
        ::= { wfIgmpIfEntry 13 }

    wfIgmpIfNetVersion OBJECT-TYPE
        SYNTAX	INTEGER
        ACCESS	read-only
        STATUS	mandatory
        DESCRIPTION
                "This is the version of igmp that this router believes is
                running on this network. A value of 1 means IGMPv1 (old
                igmp) and a value of 2 means IGMPv2 (new igmp)."
        ::= { wfIgmpIfEntry 14 }

    wfIgmpIfMaxHostResponse OBJECT-TYPE
        SYNTAX	INTEGER(1..2147483647)
        ACCESS	read-write
        STATUS	mandatory
        DESCRIPTION
                "This is the amount of time in 10th of seconds that a host
                is supposed to take to respond to a query. This will
                value will be placed in the code feild of the igmp
                query packet."
        DEFVAL	{ 100 }
        ::= { wfIgmpIfEntry 15 }

    wfIgmpIfRoutingProtocol OBJECT-TYPE
        SYNTAX	INTEGER {
                     igmp(1),
                     dvmrp(2),
		     pim(3),
                     mospf(4),
                     cbt(5),
	             internal(6),
	             relay(7)
                }
        ACCESS	read-only
        STATUS	mandatory
        DESCRIPTION
                "This has the value of the multicast protocol running
                 on this interface.  A value 'igmp' means there is no
                 multicast protocol up on this interface. Note :
                 type  8 used for static configuration for MTM 
                  for ti display only.Hence is
                  reserved "
        DEFVAL	{ igmp }
        ::= { wfIgmpIfEntry 16 }

    wfIgmpIfDroppedDataPkt OBJECT-TYPE
        SYNTAX	Counter
        ACCESS	read-only
        STATUS	mandatory
        DESCRIPTION
                "Number of data packets that have to be dropped on this
		 outgoing interface due to lack of buffers. If alias flooding
		 is used for some (s, g) and kernel could not allocate
		 buffers for some member gates, those drops are not counted
		 into this counter"
        ::= { wfIgmpIfEntry 17 }

    wfIgmpIfMtraceEntryLifetime OBJECT-TYPE
        SYNTAX	INTEGER(30..8192)
        ACCESS	read-write
        STATUS	mandatory
        DESCRIPTION
                "This is the amount of time in seconds that a router
		 is supposed to keep a forwarding cache entry that
                 was created specifically for mtrace."
        DEFVAL	{ 30 }
        ::= { wfIgmpIfEntry 18 }

    wfIgmpIfInMtraceReqs OBJECT-TYPE
        SYNTAX	Counter
        ACCESS	read-only
        STATUS	mandatory
        DESCRIPTION
                "The total number of Mtrace packets received on the interface."
        ::= { wfIgmpIfEntry 19 }

    wfIgmpIfOutMtraceReqs OBJECT-TYPE
        SYNTAX	Counter
        ACCESS	read-only
        STATUS	mandatory
        DESCRIPTION
                "The total number of Mtrace packets send from the interface."
        ::= { wfIgmpIfEntry 20 }

    wfIgmpIfInMtraceResps OBJECT-TYPE
        SYNTAX	Counter
        ACCESS	read-only
        STATUS	mandatory
        DESCRIPTION
                "The total number of Mtrace packets received on the interface."
        ::= { wfIgmpIfEntry 21 }

    wfIgmpIfOutMtraceResps OBJECT-TYPE
        SYNTAX	Counter
        ACCESS	read-only
        STATUS	mandatory
        DESCRIPTION
                "The total number of Mtrace packets send from the interface."
        ::= { wfIgmpIfEntry 22 }

    wfIgmpIfRelayType OBJECT-TYPE
        SYNTAX	INTEGER {
    		    primary(1),
    		    backup(2),
		    downstream(3)
    		}
        ACCESS	read-write
        STATUS	mandatory
        DESCRIPTION
                "Indicates whether the IGMP circuit is configured as the
                 primary upstream circuit, the backup upstream circuit or
                 a downstream circuit. At most one circuit can be 
                 configured as the primary. At most one circuit can be
                 configured as the backup."
        DEFVAL	{ downstream }
        ::= { wfIgmpIfEntry 23 }

    wfIgmpIfUnsolicitedReportInterval OBJECT-TYPE
        SYNTAX	INTEGER(0..255)
        ACCESS	read-write
        STATUS	mandatory
        DESCRIPTION
                "This mib attribute is the Unsolicited Report Interval, in
                 seconds, which is the time between repetitions of a host's 
                 initial report of membership in a group. If this is zero, 
                 then do not send the report twice."
        DEFVAL	{ 10 }
        ::= { wfIgmpIfEntry 24 }

    wfIgmpIfSuppressQuery OBJECT-TYPE
        SYNTAX	INTEGER {
    		    yes(1),
    		    no(2)
    		}
        ACCESS	read-write
        STATUS	mandatory
        DESCRIPTION
		"Whether IGMP query is suppressed on this interface.

		 In Bay's multicast implementation, configuring 'IGMP'
		 on an interface means two things:

		 1. the interface will be used for forwarding multicast
		    traffic
		 2. IGMP protocol will be running on the interface

		 Therefore, on some interfaces like point-to-point or
		 non-broadcast ones, even though there is no need to
		 run IGMP protocol, 'igmp' must be configured.

		 However, with this attribute we can disable the sending
		 of IGMP queries."
        DEFVAL	{ no }
        ::= { wfIgmpIfEntry 25 }

    wfIgmpIfGroupCount OBJECT-TYPE
        SYNTAX	Counter
        ACCESS	read-only
        STATUS	mandatory
        DESCRIPTION
                "The total number of groups presented on the interface."
        ::= { wfIgmpIfEntry 26 }
 
    wfIgmpIfVRRPTriggerState OBJECT-TYPE
        SYNTAX  INTEGER {
                    enabled(1),
                    disabled(2)
                }
        ACCESS  read-only
        STATUS  mandatory
        DESCRIPTION
                "Indicates whether VRRP subsystem wants this IGMP Intf to
                 be enabled or disabled."
        DEFVAL  { enabled }
        ::= { wfIgmpIfEntry 27 }

     
   wfIgmpIfStaticFwdCacheLifeTime OBJECT-TYPE
        SYNTAX INTEGER (80..7200)
        ACCESS read-write
        STATUS mandatory
        DESCRIPTION " If the IGMPStaticForwarding Policy mode is set to static
                     to dynamic (static inbound and multicast protcol outbound)
                      mode. This value should be set based on which protcols are 
                      planned to be configured on the outbound. Typical values 
                      are for DVMRP(7200), MOSPF(600) and  PIM(210)  so that MTM 
                      cache entries will be alive for the above specified 
                      seconds even if the traffic is not present. 
		      The above value is in seconds. "                  
        DEFVAL  { 216 }
         ::= { wfIgmpIfEntry  28 }
   
    wfIgmpGroupTable OBJECT-TYPE
        SYNTAX	SEQUENCE OF WfIgmpGroupEntry
        ACCESS	not-accessible
        STATUS	mandatory
        DESCRIPTION
                "A table of IGMP groups"
        ::= { wfIgmpGroup 3 }

    wfIgmpGroupEntry OBJECT-TYPE
        SYNTAX	WfIgmpGroupEntry
        ACCESS	not-accessible
        STATUS	mandatory
        DESCRIPTION
                "An IGMP group in the group table"
        INDEX	{ wfIgmpCct,
		  wfIgmpIpifAddress,
    		  wfIgmpGroupAddress }
        ::= { wfIgmpGroupTable 1 }

    WfIgmpGroupEntry ::= SEQUENCE {
    	    wfIgmpGroupAddress
    		IpAddress,
    	    wfIgmpCct
    		INTEGER,
	    wfIgmpIpifAddress
		IpAddress,
    	    wfIgmpTimeLeft
    		INTEGER
        }

    wfIgmpGroupAddress OBJECT-TYPE
        SYNTAX	IpAddress
        ACCESS	read-only
        STATUS	mandatory
        DESCRIPTION
                "the group address"
        ::= { wfIgmpGroupEntry 1 }

    wfIgmpCct OBJECT-TYPE
        SYNTAX	INTEGER
        ACCESS	read-only
        STATUS	mandatory
        DESCRIPTION
                "the circuit for this group"
        ::= { wfIgmpGroupEntry 2 }

    wfIgmpIpifAddress OBJECT-TYPE
        SYNTAX	IpAddress
        ACCESS	read-only
        STATUS	mandatory
        DESCRIPTION
                "the IP interface for this group"
        ::= { wfIgmpGroupEntry 3 }

    wfIgmpTimeLeft OBJECT-TYPE
        SYNTAX	INTEGER
        ACCESS	read-only
        STATUS	mandatory
        DESCRIPTION
                "how long until this group times out."
        ::= { wfIgmpGroupEntry 4 }

    wfIgmpStaticGroupTable OBJECT-TYPE
        SYNTAX	SEQUENCE OF WfIgmpStaticGroupEntry
        ACCESS	not-accessible
        STATUS	mandatory
        DESCRIPTION
                "The list of elements in IGMP Static membership table"
        ::= { wfIgmpGroup 4 }

    wfIgmpStaticGroupEntry OBJECT-TYPE
        SYNTAX	WfIgmpStaticGroupEntry
        ACCESS	not-accessible
        STATUS	mandatory
        DESCRIPTION
                "A Staticly configured group membership"
        INDEX	{ wfIgmpStaticGroupCct,
                  wfIgmpStaticGroupAddress,
	          wfIgmpStaticGroupPrefix }
        ::= { wfIgmpStaticGroupTable 1 }

    WfIgmpStaticGroupEntry ::= SEQUENCE {
            wfIgmpStaticGroupCreate
     		INTEGER,
    	    wfIgmpStaticGroupCct
    		INTEGER,
    	    wfIgmpStaticGroupAddress
    		IpAddress,
     	    wfIgmpStaticGroupPrefix
    		INTEGER
        }

    wfIgmpStaticGroupCreate OBJECT-TYPE
        SYNTAX	INTEGER {
    		    created(1),
    		    deleted(2)
    		}
        ACCESS	read-write
        STATUS	mandatory
        DESCRIPTION
                "Indicates whether this IGMP record is to be deleted or created"
        DEFVAL	{ created }
        ::= { wfIgmpStaticGroupEntry 1 }

    wfIgmpStaticGroupCct OBJECT-TYPE
        SYNTAX	INTEGER
        ACCESS	read-only
        STATUS	mandatory
        DESCRIPTION
                "the circuit for this group"
        ::= { wfIgmpStaticGroupEntry 2 }

    wfIgmpStaticGroupAddress OBJECT-TYPE
        SYNTAX	IpAddress
        ACCESS	read-only
        STATUS	mandatory
        DESCRIPTION
                "the group address"
        ::= { wfIgmpStaticGroupEntry 3 }

    wfIgmpStaticGroupPrefix OBJECT-TYPE
        SYNTAX	INTEGER
        ACCESS	read-only
        STATUS	mandatory
        DESCRIPTION
                "the prefix for this group"
        ::= { wfIgmpStaticGroupEntry 4 }

    wfIgmpBoundaryTable OBJECT-TYPE
        SYNTAX	SEQUENCE OF WfIgmpBoundaryEntry
        ACCESS	not-accessible
        STATUS	mandatory
        DESCRIPTION
                "The list of elements in IGMP Boundary table"
        ::= { wfIgmpGroup 5 }

    wfIgmpBoundaryEntry OBJECT-TYPE
        SYNTAX	WfIgmpBoundaryEntry
        ACCESS	not-accessible
        STATUS	mandatory
        DESCRIPTION
                "For Administratively Scoped Addresses:
		 No group that falls into this group/prefix will be
		 accepted on the specified cct, or forwarded out of the cct"
        INDEX	{ wfIgmpBoundaryGroupAddress,
	          wfIgmpBoundaryGroupPrefix }
        ::= { wfIgmpBoundaryTable 1 }

    WfIgmpBoundaryEntry ::= SEQUENCE {
	    wfIgmpBoundaryCreate
		INTEGER,
	    wfIgmpBoundaryEnable
		INTEGER,
    	    wfIgmpBoundaryGroupAddress
    		IpAddress,
     	    wfIgmpBoundaryGroupPrefix
    		INTEGER,
    	    wfIgmpBoundaryCctList
    		OCTET STRING,
    	    wfIgmpBoundaryTunnelList
    		OCTET STRING
        }

    wfIgmpBoundaryCreate OBJECT-TYPE
        SYNTAX	INTEGER {
    		    created(1),
    		    deleted(2)
    		}
        ACCESS	read-write
        STATUS	mandatory
        DESCRIPTION
                "Indicates whether this record is to be deleted or created"
        DEFVAL	{ created }
        ::= { wfIgmpBoundaryEntry 1 }

    wfIgmpBoundaryEnable OBJECT-TYPE
        SYNTAX	INTEGER {
    		    enabled(1),
    		    disabled(2)
    		}
        ACCESS	read-write
        STATUS	mandatory
        DESCRIPTION
                "Indicates whether this record is enabled or disabled"
        DEFVAL	{ enabled }
        ::= { wfIgmpBoundaryEntry 2 }

    wfIgmpBoundaryGroupAddress OBJECT-TYPE
        SYNTAX	IpAddress
        ACCESS	read-only
        STATUS	mandatory
        DESCRIPTION
                "the group address in concern"
        ::= { wfIgmpBoundaryEntry 3 }

    wfIgmpBoundaryGroupPrefix OBJECT-TYPE
        SYNTAX	INTEGER
        ACCESS	read-only
        STATUS	mandatory
        DESCRIPTION
                "the group prefix length"
        ::= { wfIgmpBoundaryEntry 4 }

    wfIgmpBoundaryCctList OBJECT-TYPE
        SYNTAX	OCTET STRING
        ACCESS	read-write
        STATUS	mandatory
        DESCRIPTION
                "The boundary circuit list. Each circuit takes two octets"
        ::= { wfIgmpBoundaryEntry 5 }

    wfIgmpBoundaryTunnelList OBJECT-TYPE
        SYNTAX	OCTET STRING
        ACCESS	read-write
        STATUS	mandatory
        DESCRIPTION
                "the boundary tunnel list. Each tunnel takes 8 octets,
		 the first 4 of which are for local IP address, and the
		 last 4 are for remote IP address"
        ::= { wfIgmpBoundaryEntry 6 }

    END  -- Wellfleet-IGMP-MIB
