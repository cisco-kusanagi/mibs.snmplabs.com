PDN-ETHER-MIB DEFINITIONS ::= BEGIN

-- Version :  0.1 DRAFT
-- Enterprise ethernet configuration mib
-- Copyright (C) 2000 Paradyne Corporation.

-- Created by : Wayne Jadoo / Prakash Easwar

IMPORTS
OBJECT-TYPE
FROM RFC-1212
pdn-ether
FROM PDN-HEADER-MIB
SwitchState, ManagementType,
ResetStates
FROM PDN-TC
ifIndex
FROM RFC1213-MIB
;

pdnPortConfigMIBObjects  OBJECT IDENTIFIER ::= { pdn-ether 1 }
pdnPortConfigMIBTraps    OBJECT IDENTIFIER ::= { pdn-ether 2 }
pdnPortConfigEthernet    OBJECT IDENTIFIER ::= { pdnPortConfigMIBObjects 1 }

-- Ethernet Type of Configuration
            
        pdnPortConfigEthernetTable OBJECT-TYPE
              SYNTAX  SEQUENCE OF PdnPortConfigEthernetEntry
              ACCESS  not-accessible
              STATUS  mandatory
              DESCRIPTION
                "A Table that contains information about 
                 the Ethernet port configuration"
              ::= { pdnPortConfigEthernet 1 }

        pdnPortConfigEthernetEntry OBJECT-TYPE
              SYNTAX  PdnPortConfigEthernetEntry
              ACCESS  not-accessible
              STATUS  mandatory
              DESCRIPTION
                  "An entry that contains configuration 
                   information about an ethernet Port "
              INDEX  { ifIndex }
              ::= { pdnPortConfigEthernetTable 1 }

        PdnPortConfigEthernetEntry ::=
                SEQUENCE
                {
                   pdnPortConfigEthernetDuplexMode     SwitchState,
                   pdnPortConfigEthernetManageType     ManagementType,
                   pdnPortConfigEthernetResetState     ResetStates
                }

          pdnPortConfigEthernetDuplexMode OBJECT-TYPE
              SYNTAX   SwitchState
              ACCESS   read-write
              STATUS   mandatory
              DESCRIPTION
                      "This object is used to enable or Disable 
                       Duplex Mode on an ethernet Port."
                      
              DEFVAL { disabled } -- Disabled
              ::= { pdnPortConfigEthernetEntry 1  }
        
          pdnPortConfigEthernetManageType OBJECT-TYPE
              SYNTAX   ManagementType
              ACCESS   read-write
              STATUS   mandatory
              DESCRIPTION
                      "This object is used to Enable or 
                       Disable Inband or Outband Management."
                      
              DEFVAL { outband } 
              ::= { pdnPortConfigEthernetEntry 2  }

          pdnPortConfigEthernetResetState OBJECT-TYPE
              SYNTAX   ResetStates
              ACCESS   read-write
              STATUS   mandatory
              DESCRIPTION
                      "This object is used to reset the ethernet port." 

              DEFVAL { noOp } -- No
              ::= { pdnPortConfigEthernetEntry 3  }

        
END
