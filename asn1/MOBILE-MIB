-- extracted from draft-adwankar-netconf-symple-00.txt
-- at Thu Oct 23 06:15:15 2003

       MOBILE-MIB DEFINITIONS ::= BEGIN

          IMPORTS
                  mgmt, NetworkAddress, IpAddress, Counter, Gauge,
                          TimeTicks
                      FROM RFC1155-SMI
                  OBJECT-TYPE
                          FROM RFC-1212;

          mgmt         OBJECT IDENTIFIER ::= { iso org(3) dod(6) internet(1) 
                                               mgmt(2) }
          directory    OBJECT IDENTIFIER ::= { internet 1 }
          experimental OBJECT IDENTIFIER ::= { internet 3 }
          private      OBJECT IDENTIFIER ::= { internet 4 }
          enterprises  OBJECT IDENTIFIER ::= { private 1 }
          Company      OBJECT IDENTIFIER ::= { enterprises xxx }

          -- textual conventions

           DisplayString ::=
               OCTET STRING
          -- This data type is used to model textual information taken
          -- from the NVT ASCII character set.  By convention, objects
          -- with this syntax are declared as having
          --
                (SIZE (0..255))

           PhysAddress ::=
               OCTET STRING
          -- This data type is used to model media addresses.  For many
          -- types of media, this will be in a binary representation.
          -- For example, an ethernet address would be represented as
          -- a string of 6 octets.


          -- groups in MOBILE-MIB

          DevInfo          OBJECT IDENTIFIER ::= { Company 1 }
          DevDetail        OBJECT IDENTIFIER ::= { Company 2 }
          
          Ext              OBJECT IDENTIFIER ::= { DevDetail 1 }
          
          Settings         OBJECT IDENTIFIER ::= { Ext 1 }
          
          WAP              OBJECT IDENTIFIER ::= { Ext 2 }          
          
          Log              OBJECT IDENTIFIER ::= { Ext 3 }                    

          Applications     OBJECT IDENTIFIER ::= { Ext 4 }          
          
          App1             OBJECT IDENTIFIER ::= { Applications 1 }                    

          -- the DevInfo group

	  -- Directory which holds device info

          Man         OBJECT-TYPE
              SYNTAX  DisplayString (SIZE (0..255))
              ACCESS  read-only
              STATUS  mandatory
              DESCRIPTION
                      "Manufacture name."
              ::= { DevInfo 1 }

          Mod         OBJECT-TYPE
              SYNTAX  DisplayString (SIZE (0..255))
              ACCESS  read-only
              STATUS  mandatory
              DESCRIPTION
                      "Model name."
              ::= { DevInfo 2 }

          DevID       OBJECT-TYPE
              SYNTAX  DisplayString (SIZE (0..255))
              ACCESS  read-only
              STATUS  mandatory
              DESCRIPTION
                      "Device serial number."
              ::= { DevInfo 3 }

          Lang        OBJECT-TYPE
              SYNTAX  DisplayString (SIZE (0..255))
              ACCESS  read-write
              STATUS  mandatory
              DESCRIPTION
                      "Device language."
              ::= { DevInfo 4 }

          DmV         OBJECT-TYPE
              SYNTAX  DisplayString (SIZE (0..255))
              ACCESS  read-only
              STATUS  mandatory

            DESCRIPTION
                      "Device version."
              ::= { DevInfo 5 }
              
          -- the DevDetail group
          
          OEM         OBJECT-TYPE
              SYNTAX  DisplayString (SIZE (0..255))
              ACCESS  read-only
              STATUS  mandatory
              DESCRIPTION
                      "Specify OEM of the device (ex, Motorola)."
              ::= { DevDetail 1 }

          FwV         OBJECT-TYPE
              SYNTAX  DisplayString (SIZE (0..255))
              ACCESS  read-only
              STATUS  mandatory
              DESCRIPTION
                      "Firmware version."
              ::= { DevDetail 2 }

          SwV         OBJECT-TYPE
              SYNTAX  DisplayString (SIZE (0..255))
              ACCESS  read-only
              STATUS  mandatory
              DESCRIPTION
                      "Software version."
              ::= { DevDetail 3 }

          HwV         OBJECT-TYPE
              SYNTAX  DisplayString (SIZE (0..255))
              ACCESS  read-only
              STATUS  mandatory
              DESCRIPTION
                      "Hardware version."
              ::= { DevDetail 4 }

          DevTyp      OBJECT-TYPE
              SYNTAX  DisplayString (SIZE (0..255))
              ACCESS  read-only
              STATUS  mandatory
              DESCRIPTION
                      "Device type."
              ::= { DevDetail 5 }

          Bearer      OBJECT-TYPE
              SYNTAX  DisplayString (SIZE (0..255))
              ACCESS  read-only
              STATUS  mandatory
              DESCRIPTION
                      "Bearer."
              ::= { DevDetail 6 }

          EnergyLevel OBJECT-TYPE
              SYNTAX  INTEGER
              ACCESS  read-only
              STATUS  mandatory
              DESCRIPTION
                      "Energy Level. e.g Battery level"
              ::= { DevDetail 7 }
              
          -- the Settings group

          -- Parent Settings directory

          clock       OBJECT-TYPE
              SYNTAX  DisplayString (SIZE (0..255))
              ACCESS  read-write
              STATUS  mandatory
              DESCRIPTION
                      "Set date and time."
              ::= { Settings 1 }

          ActiveRing  OBJECT-TYPE
              SYNTAX  INTEGER
              ACCESS  read-write
              STATUS  mandatory
              DESCRIPTION
                      "Replace active ring tone type setting."
              ::= { Settings 2 }

          ActiveAlert OBJECT-TYPE
              SYNTAX  INTEGER
              ACCESS  read-write
              STATUS  mandatory
              DESCRIPTION
                      "Replace active alert type setting (Silent, Vibrate, 
                                                          Loud, etc)."
              ::= { Settings 3 }

          AlertLevel  OBJECT-TYPE
              SYNTAX  INTEGER
              ACCESS  read-write
              STATUS  mandatory
              DESCRIPTION
                      "Replace alert level setting."
              ::= { Settings 4 }

          DTMF  OBJECT-TYPE
              SYNTAX  INTEGER
              ACCESS  read-write
              STATUS  mandatory
              DESCRIPTION
                      "Replace DTMF settings (Short, Long, Off)."
              ::= { Settings 5 }

          SecurityCode  OBJECT-TYPE
              SYNTAX  DisplayString (SIZE (0..255))
              ACCESS  read-write
              STATUS  mandatory
              DESCRIPTION
                      "Replace the security code."
              ::= { Settings 6 }

          LockState  OBJECT-TYPE
              SYNTAX  INTEGER
              ACCESS  read-write
              STATUS  mandatory
              DESCRIPTION
                      "Security lock state (Locked, Unlocked)."
              ::= { Settings 7 }

               
          -- the WAP group

          -- WAP folder settings

          Defaultwebsession OBJECT-TYPE         
              SYNTAX        DisplayString (SIZE (0..255))
              ACCESS        read-write
              STATUS        optional
              DESCRIPTION
                      "Set default web session on phone."
              ::= { WAP 1 }

          -- the Log group

          -- Directory which holds Log Mgmt Node

          CallProcessing OBJECT-TYPE         
              SYNTAX        DisplayString (SIZE (0..255))
              ACCESS        read-write
              STATUS        optional
              DESCRIPTION
                      "Call Processing Log."
              ::= { Log 1 }

          Location OBJECT-TYPE         
              SYNTAX        DisplayString (SIZE (0..255))
              ACCESS        read-write
              STATUS        optional
              DESCRIPTION
                      "Location Log."
              ::= { Log 2 }

          -- the Applications group

          -- Directory which holds Applications Info

          ExecutionCount OBJECT-TYPE         
              SYNTAX        INTEGER
              ACCESS        read-write
              STATUS        optional
              DESCRIPTION
                      "App1 Execution Count."
              ::= { App1 1 }

          END
