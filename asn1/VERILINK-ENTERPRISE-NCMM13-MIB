VERILINK-ENTERPRISE-NCMM13-MIB

        -- set up MIB-wide defaults
        -- all functions can use %n for object name and
        -- %t for object type, %p for parent name,
        -- %d for name of default-bearing node and %% for %

          DEFINITIONS ::= BEGIN

     IMPORTS
                Gauge
                        FROM RFC1155-SMI
            	DisplayString
                     FROM RFC1213-MIB
        	OBJECT-TYPE
                     FROM RFC-1212
        	ncm-m13
             FROM VERILINK-ENTERPRISE-NCMALARM-MIB;


     --  This MIB module uses the extended OBJECT-TYPE macro as
     --  defined in RFC 1212.
     --  This MIB module uses the TRAP-TYPE macro as
     --  defined in RFC 1215.


     --   verilink                    OBJECT IDENTIFIER ::= { enterprises 321 }
     --   as2000                      OBJECT IDENTIFIER ::= { verilink 1 }
     --   ncm-m13                     OBJECT IDENTIFIER ::= { as2000 3037 }



	--
     --ncm m13 DS3 table
     --  
     ncmm13DS3PortTable OBJECT-TYPE
          SYNTAX SEQUENCE OF Ncmm13DS3PortEntry
          ACCESS not-accessible
          STATUS mandatory
          DESCRIPTION
               "The m13 DS3 Port table."
                --DEFAULT test-function   m13-test
              --DEFAULT set-function    null-set-proc
                --DEFAULT next-function   m13-next
          ::= { ncm-m13 14000 }

     ncmm13DS3PortEntry OBJECT-TYPE
          SYNTAX Ncmm13DS3PortEntry
          ACCESS not-accessible
          STATUS mandatory
          DESCRIPTION
               "An entry in the m13 information table."
          INDEX   { ncmm13DS3PortNIDIndex, ncmm13DS3PortIndex }
          ::= { ncmm13DS3PortTable 1 }

     Ncmm13DS3PortEntry ::= SEQUENCE {
             ncmm13DS3PortNIDIndex
                INTEGER,
             ncmm13DS3PortIndex
                INTEGER,
             ncmm13DS3ModeControl
                INTEGER,
             ncmm13DS3LineType
                INTEGER,
	     ncmm13DS3PerfControl
		INTEGER,
	     ncmm13DS3AlarmControl
		INTEGER,
	     ncmm13DS3FarEndControl
                INTEGER,
	     ncmm13DS3BusType
                INTEGER,
             ncmm13DS3InbandControl
                INTEGER,
	     ncmm13DS3CableLength
		INTEGER,
             ncmm13DS3EquipCode
                 DisplayString,
             ncmm13DS3LocationIDCode
                 DisplayString,
             ncmm13DS3FrameIDCode
                 DisplayString,
             ncmm13DS3UnitCode
                 DisplayString,
             ncmm13DS3FacilityIDCode
                 DisplayString,
             ncmm13DS3PortIdCode
                 DisplayString,
             ncmm13DS3GenIDCode
                 DisplayString
          }


	ncmm13DS3PortNIDIndex OBJECT-TYPE
          SYNTAX  INTEGER (1..'7fffffff'h)
          ACCESS  read-only
          STATUS  mandatory
          DESCRIPTION
                "This variable indicates the node id value of the node."
            ::= { ncmm13DS3PortEntry 1 }
 
     	ncmm13DS3PortIndex OBJECT-TYPE
          SYNTAX  INTEGER (1..65535)
          ACCESS  read-only
          STATUS  mandatory
          DESCRIPTION
               "The index value which uniquely identifies  the
                DS3  interface  to which this entry is applica-
                ble.  The interface identified by a  particular
                value  of  this  index is the same interface as
                identified by the same value as a dsx1LineIndex
                object instance."
            ::= { ncmm13DS3PortEntry 2 }
 
     	ncmm13DS3ModeControl OBJECT-TYPE
          SYNTAX  INTEGER {
                c-bit(1),
                m23-bit(2)
          }
          ACCESS  read-write
          STATUS  mandatory
          DESCRIPTION
                "The Mode Control Bit for M13."
            ::= { ncmm13DS3PortEntry 3 }
 
	 ncmm13DS3LineType  OBJECT-TYPE
          SYNTAX  INTEGER{
                bi-polar(1),
                uni-polar(2)
          }
          ACCESS  read-write
          STATUS  mandatory
          DESCRIPTION
               "The Line Type for M13."
            ::= { ncmm13DS3PortEntry 4 }
 
	 ncmm13DS3PerfControl OBJECT-TYPE
          SYNTAX  INTEGER { 
		disabled (1),
                enabled (2)
          }
          ACCESS  read-write
          STATUS  mandatory
          DESCRIPTION
                "Performance Control Enabled/Disabled for M13."
           ::= { ncmm13DS3PortEntry 5 }


	ncmm13DS3AlarmControl OBJECT-TYPE
	SYNTAX INTEGER { 
		disabled (1),
                enabled (2)
          }
          ACCESS  read-write
          STATUS  mandatory
          DESCRIPTION
                "Alarm Control Enabled/Disabled for M13."
           ::= { ncmm13DS3PortEntry 6 }

	ncmm13DS3FarEndControl OBJECT-TYPE
	SYNTAX INTEGER { 
		disabled (1),
                enabled (2)
          }
          ACCESS  read-write
          STATUS  mandatory
          DESCRIPTION
                "Far End Control Enabled/Disabled for M13."
           ::= { ncmm13DS3PortEntry 7 }

	ncmm13DS3BusType	OBJECT-TYPE
	SYNTAX INTEGER { 
		c-bus (1),
                a-bus(2)
          }
          ACCESS  read-write
          STATUS  mandatory
          DESCRIPTION
                "Inband Control Enabled/Disabled for M13."
           ::= { ncmm13DS3PortEntry 8 }



	
	ncmm13DS3InbandControl	OBJECT-TYPE
	SYNTAX INTEGER { 
		disabled (1),
                enabled (2)
          }
          ACCESS  read-write
          STATUS  mandatory
          DESCRIPTION
                "Inband Control Enabled/Disabled for M13."
           ::= { ncmm13DS3PortEntry 9 }


	
	ncmm13DS3CableLength	OBJECT-TYPE
	SYNTAX INTEGER { 
		short (1),
                long (2)
          }
          ACCESS  read-write
          STATUS  mandatory
          DESCRIPTION
                "Cable length for M13."
           ::= { ncmm13DS3PortEntry 10 }

	 
     ncmm13DS3EquipCode OBJECT-TYPE
          SYNTAX  DisplayString (SIZE (0..10))
          ACCESS  read-write
          STATUS  mandatory
          DESCRIPTION
               "This is the Far End Equipment Identification code
                that describes the specific piece of equipment.
                It is sent within the Path
                Identification Message."
          ::= { ncmm13DS3PortEntry 11 }
 
     ncmm13DS3LocationIDCode OBJECT-TYPE
          SYNTAX  DisplayString (SIZE (0..11))
          ACCESS  read-write
          STATUS  mandatory
          DESCRIPTION
               "This is the Far End Location Identification code
                that describes the specific location of the
                equipment.  It is sent within the Path
                Identification Message."
          ::= { ncmm13DS3PortEntry 12 }
 
     ncmm13DS3FrameIDCode OBJECT-TYPE
          SYNTAX  DisplayString (SIZE (0..10))
          ACCESS  read-write
          STATUS  mandatory
          DESCRIPTION
               "This is the Far End Frame Identification code
                that identifies where the equipment is located
                within a building at a given location.
                It is sent within the Path Identification Message."
          ::= { ncmm13DS3PortEntry 13 }


	ncmm13DS3UnitCode OBJECT-TYPE
          SYNTAX  DisplayString (SIZE (0..6))
          ACCESS  read-write
          STATUS  mandatory
          DESCRIPTION
               "This is the Far End code
                that identifies the equipment location within a bay.
                It is sent within the Path
                Identification Message."

          ::= { ncmm13DS3PortEntry 14 }
 
     ncmm13DS3FacilityIDCode OBJECT-TYPE
          SYNTAX  DisplayString (SIZE (0..38))
          ACCESS  read-write
          STATUS  mandatory
          DESCRIPTION
               "This code identifies a specific Far End DS3 path.
                It is sent within the Path Identification Message."
          ::= { ncmm13DS3PortEntry 15 }
 
     ncmm13DS3PortIdCode OBJECT-TYPE
          SYNTAX  DisplayString (SIZE (0..38))
          ACCESS read-write
          STATUS mandatory
          DESCRIPTION
               "Port ID."
          ::= { ncmm13DS3PortEntry 16 }
 
 
     ncmm13DS3GenIDCode OBJECT-TYPE
          SYNTAX  DisplayString (SIZE (0..38))
          ACCESS read-write
          STATUS mandatory
          DESCRIPTION
               "Test Signal Generator ID."
          ::= { ncmm13DS3PortEntry 17 }


	-- ncm m13 Status Table

 

	ncmm13StatTable OBJECT-TYPE
          SYNTAX SEQUENCE OF Ncmm13StatEntry
          ACCESS not-accessible
          STATUS mandatory
          DESCRIPTION   
               "The m13 Stats."
                --DEFAULT test-function   m13-test
              --DEFAULT set-function    null-set-proc
                --DEFAULT next-function   m13-next
          ::= { ncm-m13 14001 }

     ncmm13StatEntry OBJECT-TYPE
          SYNTAX Ncmm13StatEntry
          ACCESS not-accessible
          STATUS mandatory
          DESCRIPTION   
               "An entry in the m13 stats table."
          INDEX   { ncmm13StatNIDIndex, ncmm13StatIndex }
          ::= { ncmm13StatTable 1 }

     Ncmm13StatEntry ::= SEQUENCE {
             ncmm13StatNIDIndex
                 INTEGER,
             ncmm13StatIndex
                 INTEGER,
             ncmm13StatAIS
                 INTEGER,
             ncmm13StatIdle
                 INTEGER,
             ncmm13StatYellowAlm
                 INTEGER,
             ncmm13StatOOF
                 INTEGER,
             ncmm13StatLOS
                 INTEGER,
             ncmm13DS3NearEndLocalLoopback
                 INTEGER,
             ncmm13DS3NearEndLineLoopback
                 INTEGER,
	     ncmm13DS3FarEndLineLoopback
                 INTEGER,
	     ncmm13T1NearEndLineLoopback
		DisplayString,
	     ncmm13T1FarEndLineLoopback
		DisplayString,
	     ncmm13FarEndAllT1LineLoopback
		INTEGER,
	     ncmm13T1LocalLoopback
	        DisplayString	

                  }


	ncmm13StatNIDIndex OBJECT-TYPE
          SYNTAX  INTEGER (1..'7fffffff'h)
          ACCESS  read-only
          STATUS  mandatory
          DESCRIPTION
                "This variable indicates the node id value of the node."
            ::= { ncmm13StatEntry 1 }
               
     ncmm13StatIndex OBJECT-TYPE
          SYNTAX  INTEGER (1..65535)
          ACCESS  read-only
          STATUS  mandatory
          DESCRIPTION
               "The index value which uniquely identifies  the
                DS1  interface  to which this entry is applica-
                ble.  The interface identified by a  particular
                value  of  this  index is the same interface as
                identified by the same value as a dsx1LineIndex
                object instance."
            ::= { ncmm13StatEntry 2 }
 
     ncmm13StatAIS OBJECT-TYPE
          SYNTAX INTEGER {
                        oFF (1),
                        oN (2)
               }
          ACCESS read-only
          STATUS mandatory
          DESCRIPTION
               "Port Status m13  AIS off/on."
          ::= { ncmm13StatEntry 3 }
 
     ncmm13StatIdle OBJECT-TYPE
          SYNTAX INTEGER {
                        oFF (1),
                        oN (2)
               }
          ACCESS read-only
          STATUS mandatory
          DESCRIPTION
               "port Status m13  Idle off/on."
          ::= { ncmm13StatEntry 4 }
 
     ncmm13StatYellowAlm OBJECT-TYPE
          SYNTAX INTEGER {
                        oFF (1),
                        oN (2)
               }
          ACCESS read-only
          STATUS mandatory
          DESCRIPTION
               "Port Status m13 Yellow Alarm off/on."
          ::= { ncmm13StatEntry 5 }
 
     ncmm13StatOOF OBJECT-TYPE
          SYNTAX INTEGER {
                        oFF (1),
                        oN (2)
               }
          ACCESS read-only
          STATUS mandatory
          DESCRIPTION
               "port status m13 off/on."
          ::= { ncmm13StatEntry 6 }


	ncmm13StatLOS OBJECT-TYPE
          SYNTAX INTEGER {
                        oFF (1),
                        oN (2)
               }
          ACCESS read-only
          STATUS mandatory
          DESCRIPTION
               "Port Status m13 LOS off/on."
          ::= {  ncmm13StatEntry 7 }

	ncmm13DS3NearEndLocalLoopback OBJECT-TYPE 
          SYNTAX INTEGER {
                        oFF (1),
                        oN (2)
               }
          ACCESS read-only
          STATUS mandatory
          DESCRIPTION
               "Port Status m13 Ds3 Local Loopback off/on."
          ::= { ncmm13StatEntry 8 }
 
          ncmm13DS3NearEndLineLoopback OBJECT-TYPE
          SYNTAX INTEGER {
                        oFF (1),
                        oN (2)
               }
          ACCESS read-only
          STATUS mandatory
          DESCRIPTION
               "Port Status m13 ds3 near end Line loopback  off/on."
          ::= { ncmm13StatEntry 9 }
 
           ncmm13DS3FarEndLineLoopback OBJECT-TYPE
          SYNTAX INTEGER {
                        oFF (1),
                        oN (2)
               }
          ACCESS read-only
          STATUS mandatory
          DESCRIPTION
               "Port Status m13 ds3 far end line loopback  off/on."
          ::= { ncmm13StatEntry 10 }
 
           ncmm13T1NearEndLineLoopback OBJECT-TYPE
          SYNTAX DisplayString 
          ACCESS read-only
          STATUS mandatory
          DESCRIPTION
               "Port Status m13 T1 near end line loopback."
          ::= { ncmm13StatEntry 11 }


	ncmm13T1FarEndLineLoopback OBJECT-TYPE
          SYNTAX DisplayString 
          ACCESS read-only
          STATUS mandatory
          DESCRIPTION    
               "Port Status m13 T1 Far end line loopback."
          ::= { ncmm13StatEntry 12 }

 
          ncmm13FarEndAllT1LineLoopback OBJECT-TYPE
          SYNTAX INTEGER {
                        disabled (1),
                        enabled (2)
               }
          ACCESS read-only
          STATUS mandatory
          DESCRIPTION
               "Port Status m13 T1 Far End All T1 Line Loopback."
          ::= { ncmm13StatEntry 13 }


	ncmm13T1LocalLoopback OBJECT-TYPE
          SYNTAX DisplayString
          ACCESS read-only
          STATUS mandatory
          DESCRIPTION  
               "Port Status m13 T1 Local loopback."
          ::= { ncmm13StatEntry 14 }




    	           -- the ncm m13 Current
 
-- The ncm m13 current table contains various statistics being
-- collected for the current 15 minute interval.
 
          ncmm13CurrentTable OBJECT-TYPE
              SYNTAX  SEQUENCE OF Ncmm13CurrentEntry
              ACCESS  not-accessible
              STATUS  mandatory
              DESCRIPTION
                      "The m13 Current table."
                --DEFAULT test-function   m13-test
              --DEFAULT set-function    null-set-proc
                --DEFAULT next-function   m13-next
              ::= { ncm-m13 14002 }
 
          ncmm13CurrentEntry OBJECT-TYPE
              SYNTAX  Ncmm13CurrentEntry
              ACCESS  not-accessible
              STATUS  mandatory
              DESCRIPTION
                      "An entry in the m13 Current table."
              INDEX   { ncmm13CurrentNIDIndex, ncmm13CurrentIndex }
              ::= { ncmm13CurrentTable 1 }
 
          Ncmm13CurrentEntry ::=
              SEQUENCE {
                  ncmm13CurrentNIDIndex
                      INTEGER,
                  ncmm13CurrentIndex
                      INTEGER,
                  ncmm13CurrentCRCStatus
                      INTEGER,
                  ncmm13CurrentTimeStampSecs
                      INTEGER,
                  ncmm13CurrentTimeStampMSecs
                      INTEGER,
                  ncmm13CurrentIntervalSecsElaps
                      INTEGER,
                  ncmm13CurrentFarEndCCV
                      Gauge,
                  ncmm13CurrentFarEndCES
                      Gauge,
                  ncmm13CurrentFarEndCSES
                      Gauge,
                  ncmm13CurrentFarEndLUAS
                      Gauge,
                  ncmm13CurrentLCV
                      Gauge,
                  ncmm13CurrentLES
                      Gauge,
                  ncmm13CurrentLSES
                      Gauge,
	          ncmm13CurrentPCV
		      Gauge,	
                  ncmm13CurrentPES
                      Gauge,
                  ncmm13CurrentPSES
                      Gauge,
                  ncmm13CurrentCCV
                      Gauge,
                  ncmm13CurrentCES
                      Gauge,
                  ncmm13CurrentCSES
                      Gauge,
		  ncmm13CurrentSEFS
                      Gauge,
                  ncmm13CurrentAISS
                      Gauge,
		  ncmm13CurrentLUAS
		      Gauge,
                  ncmm13CurrentLOOS
                      Gauge,
                  ncmm13CurrentLOFS
                      Gauge
              }
 
        ncmm13CurrentNIDIndex OBJECT-TYPE
          SYNTAX  INTEGER (1..'7fffffff'h)
          ACCESS  read-only
          STATUS  mandatory
          DESCRIPTION
                "This variable indicates the node id value of the node."
            ::= { ncmm13CurrentEntry 1 }
               
          ncmm13CurrentIndex OBJECT-TYPE
              SYNTAX  INTEGER (1..65535)
              ACCESS  read-only
              STATUS  mandatory
              DESCRIPTION
                      "The index value which uniquely identifies the
                      m13 interface to which this entry is
                      applicable.  The interface identified by a
                      particular value of this index is the same
                      interface as identified by the same value an
                      ncmhdmLineIndex object instance."
              ::= { ncmm13CurrentEntry 2 }
 
          ncmm13CurrentCRCStatus OBJECT-TYPE
                SYNTAX INTEGER {
                       disabled (1)
               } 
          ACCESS read-only
          STATUS mandatory
          DESCRIPTION
               "Current CRC4 Status."
          ::= { ncmm13CurrentEntry  3  }
 
 
          ncmm13CurrentTimeStampSecs OBJECT-TYPE
              SYNTAX  INTEGER (1..65535)
              ACCESS  read-only
              STATUS  mandatory
              DESCRIPTION
                      "Current Time in seconds."
              ::= { ncmm13CurrentEntry 4 }
 
          ncmm13CurrentTimeStampMSecs OBJECT-TYPE
              SYNTAX  INTEGER (1..65535)
              ACCESS  read-only
              STATUS  mandatory
              DESCRIPTION
                      "Current Time in milliseconds."
              ::= { ncmm13CurrentEntry 5 }


	 ncmm13CurrentIntervalSecsElaps OBJECT-TYPE
              SYNTAX  INTEGER (1..65535)
              ACCESS  read-only
              STATUS  mandatory
              DESCRIPTION
                      "Seconds elapsed in the current interval."
              ::= { ncmm13CurrentEntry 6 }
 
          ncmm13CurrentFarEndCCV OBJECT-TYPE
              SYNTAX  Gauge
              ACCESS  read-only
              STATUS  mandatory
              DESCRIPTION
                      "The counter associated with the number of
                        Far End C-bit Code Violations,
                       in the current 15 minute interval."
              ::= { ncmm13CurrentEntry 7 }
               
          ncmm13CurrentFarEndCES OBJECT-TYPE
              SYNTAX  Gauge
              ACCESS  read-only
              STATUS  mandatory
              DESCRIPTION
                      "The counter associated with the number of
                        Far End C-bit Errored Seconds,
                       in the current 15 minute interval."
              ::= { ncmm13CurrentEntry 8 }
               
          ncmm13CurrentFarEndCSES OBJECT-TYPE
              SYNTAX  Gauge
              ACCESS  read-only
              STATUS  mandatory
              DESCRIPTION
                      "The counter associated with the number of
                        Far End C-bit Severely Errored Seconds,
                       in the current 15 minute interval."
 
              ::= { ncmm13CurrentEntry 9 }
 
          ncmm13CurrentFarEndLUAS OBJECT-TYPE
              SYNTAX  Gauge
              ACCESS  read-only
              STATUS  mandatory
              DESCRIPTION
                      "Far End Line Unavailable Seconds. The counter associated
                      with the number of Seconds the Far End m13 interface
                      was Out Of Service in the current 15 minute interval."
              ::= { ncmm13CurrentEntry 10 }
               
          ncmm13CurrentLCV OBJECT-TYPE
              SYNTAX  Gauge
              ACCESS  read-only
              STATUS  mandatory
              DESCRIPTION
                      "The counter associated with the number of Line
                      Code Violations, a bipolar or excesive zero violation,
                       in the current 15 minute interval."
              ::= { ncmm13CurrentEntry 11 }


	 ncmm13CurrentLES OBJECT-TYPE
              SYNTAX  Gauge
              ACCESS  read-only
              STATUS  mandatory
              DESCRIPTION
                      "Line Errored Second Total.  The counter associated
                      with the number of Seconds of in which one or more
                      LCV occurred in the current 15 minute interval."
              ::= { ncmm13CurrentEntry 12 }
               
          ncmm13CurrentLSES OBJECT-TYPE
              SYNTAX  Gauge
              ACCESS  read-only
              STATUS  mandatory
              DESCRIPTION
                      "The counter associated with the number of
                       Line Severely Errored Seconds (LSES) in
                       the current 15 minute interval."
              ::= { ncmm13CurrentEntry 13 }
               
          ncmm13CurrentPCV OBJECT-TYPE
              SYNTAX  Gauge
              ACCESS  read-only
              STATUS  mandatory
              DESCRIPTION
                      "The counter associated with the number
                      of Parity Code Violations (locally calculated P-bits
                      disagree with those received),
                       in the current 15 minute interval."
              ::= { ncmm13CurrentEntry 14 }
               
          ncmm13CurrentPES OBJECT-TYPE
              SYNTAX  Gauge
              ACCESS  read-only
              STATUS  mandatory
              DESCRIPTION
                      "The counter associated with the number of Seconds
                      having at least one Parity Code Violation,
                       in the current 15 minute interval."
              ::= { ncmm13CurrentEntry 15 }
               
          ncmm13CurrentPSES OBJECT-TYPE
              SYNTAX  Gauge
              ACCESS  read-only
              STATUS  mandatory
              DESCRIPTION
                      "The counter associated with the number of Seconds
                      having 44 or more Parity Code Violations,
                       in the current 15 minute interval."
              ::= { ncmm13CurrentEntry 16 }
               
          ncmm13CurrentCCV OBJECT-TYPE
              SYNTAX  Gauge
              ACCESS  read-only
              STATUS  mandatory
              DESCRIPTION
                      "The counter associated with the number of
                        C-bit Code Violations,
                       in the current 15 minute interval."
              ::= { ncmm13CurrentEntry 17 }


	ncmm13CurrentCES OBJECT-TYPE
              SYNTAX  Gauge
              ACCESS  read-only
              STATUS  mandatory
              DESCRIPTION
                      "The counter associated with the number of
                        C-bit Errored Seconds,
                       in the current 15 minute interval."
              ::= { ncmm13CurrentEntry 18 }
               
          ncmm13CurrentCSES OBJECT-TYPE
              SYNTAX  Gauge
              ACCESS  read-only
              STATUS  mandatory
              DESCRIPTION
                      "The counter associated with the number of
                        C-bit Severely Errored Seconds,
                       in the current 15 minute interval."
              ::= { ncmm13CurrentEntry 19 }
               
          ncmm13CurrentSEFS OBJECT-TYPE
              SYNTAX  Gauge
              ACCESS  read-only
              STATUS  mandatory
              DESCRIPTION
                      "The counter associated with the number of seconds
                      in which one or more Out of Frame occurred
                       in the current 15 minute interval."
              ::= { ncmm13CurrentEntry 20 }
               
          ncmm13CurrentAISS OBJECT-TYPE
              SYNTAX  Gauge
              ACCESS  read-only
              STATUS  mandatory
              DESCRIPTION
                      "The counter associated with the number of Seconds
                      in which one or more incoming AISS was detected
                       in the current 15 minute interval."
              ::= { ncmm13CurrentEntry 21 }

	ncmm13CurrentLUAS OBJECT-TYPE
              SYNTAX  Gauge
              ACCESS  read-only
              STATUS  mandatory
              DESCRIPTION
                      "The counter associated with the number of Seconds
                      in which one or more incoming LUAS was detected
                       in the current 15 minute interval."
              ::= { ncmm13CurrentEntry 22 }

               
          ncmm13CurrentLOOS OBJECT-TYPE
              SYNTAX  Gauge
              ACCESS  read-only
              STATUS  mandatory
              DESCRIPTION
                      "The counter associated with the number of Seconds
                      the m13 interface was Out Of Service
                      in the current 15 minute interval."
              ::= { ncmm13CurrentEntry 23 }
               
          ncmm13CurrentLOFS OBJECT-TYPE
              SYNTAX  Gauge
              ACCESS  read-only
              STATUS  mandatory
              DESCRIPTION
                      "The counter associated with the number of Seconds
                      Of system Loss Of Signal (LOS) in the current
                      15 minute interval."
              ::= { ncmm13CurrentEntry 24 }


	 
     -- ncm m13 Specific Interval table
     -- The m13 Interval table contains various statistics
     -- collected by each m13 Interface over the previous 24 hours of
     -- operation.  The past 24 hours are broken into 96 completed
     -- 15 minute intervals.
 
 
          ncmm13IntervalTable OBJECT-TYPE
              SYNTAX  SEQUENCE OF Ncmm13IntervalEntry
              ACCESS  not-accessible
              STATUS  mandatory
              DESCRIPTION
                      "The DS3/E3 Interval table."
                --DEFAULT test-function   m13-test
              --DEFAULT set-function    null-set-proc
                --DEFAULT next-function   m13interval-next
              ::= { ncm-m13 14003 }
 
          ncmm13IntervalEntry OBJECT-TYPE
              SYNTAX  Ncmm13IntervalEntry
              ACCESS  not-accessible
              STATUS  mandatory
              DESCRIPTION
                      "An entry in the m13 Interval table."
              INDEX   { ncmm13IntervalNIDIndex, ncmm13IntervalIndex, ncmm13IntervalNumber }
              ::= { ncmm13IntervalTable 1 }
 
          Ncmm13IntervalEntry ::=
              SEQUENCE {
                  ncmm13IntervalNIDIndex
                      INTEGER,
                  ncmm13IntervalIndex
                      INTEGER,
                  ncmm13IntervalNumber
                      INTEGER,
                  ncmm13IntervalFarEndCCV
                      Gauge,
                  ncmm13IntervalFarEndCES
                      Gauge,
                  ncmm13IntervalFarEndCSES
                      Gauge,
                  ncmm13IntervalFarEndLUAS
                      Gauge,
                  ncmm13IntervalLCV
                      Gauge,
                  ncmm13IntervalLES
                      Gauge,
                  ncmm13IntervalLSES
                      Gauge,
                  ncmm13IntervalPCV
                      Gauge,
                  ncmm13IntervalPES
                      Gauge,
		  ncmm13IntervalPSES
                      Gauge,
                  ncmm13IntervalCCV
                      Gauge,
                  ncmm13IntervalCES
                      Gauge,
                  ncmm13IntervalCSES
                      Gauge,
                  ncmm13IntervalSEFS
                      Gauge,
                  ncmm13IntervalAISS
                      Gauge,
		  ncmm13IntervalLUAS
                      Gauge,
		  ncmm13IntervalLOSS
		      Gauge,
		  ncmm13IntervalLOFS
		      Gauge

               }
 
        ncmm13IntervalNIDIndex OBJECT-TYPE
          SYNTAX  INTEGER (1..'7fffffff'h)
          ACCESS  read-only
          STATUS  mandatory
          DESCRIPTION
                "This variable indicates the node id value of the node."
            ::= { ncmm13IntervalEntry 1 }
               
 
          ncmm13IntervalIndex OBJECT-TYPE
              SYNTAX  INTEGER (1..65535)
              ACCESS  read-only
              STATUS  mandatory
              DESCRIPTION
                      "The index value which uniquely identifies the
                      m13 interface to which this entry is
                      applicable.  The interface identified by a
                      particular value of this index is the same
                      interface as identified by the same value an
                      ncmhdmLineIndex object instance."
              ::= { ncmm13IntervalEntry 2 }
 
         ncmm13IntervalNumber OBJECT-TYPE
             SYNTAX  INTEGER (1..96)
             ACCESS  read-only
             STATUS  mandatory
             DESCRIPTION
                "A number between 1 and 96, where 1 is the most
                recently completed 15 minute interval and 96 is
                the least recently completed 15 minutes  inter-
                val   (assuming   that  all  96  intervals  are
                valid)."
            ::= { ncmm13IntervalEntry 3 }
 
 
          ncmm13IntervalFarEndCCV OBJECT-TYPE
              SYNTAX  Gauge
              ACCESS  read-only
              STATUS  mandatory
              DESCRIPTION
                      "The counter associated with the number of
                        Far End C-bit Code Violations,
                       in the previous 15 minute interval."
              ::= { ncmm13IntervalEntry 4 }


	ncmm13IntervalFarEndCES OBJECT-TYPE
              SYNTAX  Gauge
              ACCESS  read-only
              STATUS  mandatory
              DESCRIPTION
                      "The counter associated with the number of
                        Far End C-bit Errored Seconds,
                       in the current 15 minute interval."
              ::= { ncmm13IntervalEntry 5 }
               
          ncmm13IntervalFarEndCSES OBJECT-TYPE
              SYNTAX  Gauge
              ACCESS  read-only
              STATUS  mandatory
              DESCRIPTION
                      "The counter associated with the number of
                        Far End C-bit Severely Errored Seconds,
                       in the current 15 minute interval."
 
              ::= { ncmm13IntervalEntry 6 }
 
          ncmm13IntervalFarEndLUAS OBJECT-TYPE
              SYNTAX  Gauge
              ACCESS  read-only
              STATUS  mandatory
              DESCRIPTION
                      "Far End Line Unavailable Seconds. The counter associated
                      with the number of Seconds the Far End m13 interface
                      was Out Of Service in the current 15 minute interval."
              ::= { ncmm13IntervalEntry 7 }
               
          ncmm13IntervalLCV OBJECT-TYPE
              SYNTAX  Gauge
              ACCESS  read-only
              STATUS  mandatory
              DESCRIPTION
                      "The counter associated with the number of Line
                      Code Violations, a bipolar or excesive zero violation,
                       in the current 15 minute interval."
              ::= { ncmm13IntervalEntry 8 }
               
          ncmm13IntervalLES OBJECT-TYPE
              SYNTAX  Gauge
              ACCESS  read-only
              STATUS  mandatory
              DESCRIPTION
                      "Line Errored Second Total.  The counter associated
                      with the number of Seconds of in which one or more
                      LCV occurred in the current 15 minute interval."
              ::= { ncmm13IntervalEntry 9 }
               
          ncmm13IntervalLSES OBJECT-TYPE
              SYNTAX  Gauge
              ACCESS  read-only
              STATUS  mandatory
              DESCRIPTION
                      "The counter associated with the number of
                       Line Severely Errored Seconds (LSES) in
                       the current 15 minute interval."
              ::= { ncmm13IntervalEntry 10 }


	ncmm13IntervalPCV OBJECT-TYPE
              SYNTAX  Gauge
              ACCESS  read-only
              STATUS  mandatory
              DESCRIPTION
                      "The counter associated with the number
                      of Parity Code Violations (locally calculated P-bits
                      disagree with those received),
                       in the current 15 minute interval."
              ::= { ncmm13IntervalEntry 11 }
               
          ncmm13IntervalPES OBJECT-TYPE
              SYNTAX  Gauge
              ACCESS  read-only
              STATUS  mandatory
              DESCRIPTION
                      "The counter associated with the number of Seconds
                      having at least one Parity Code Violation,
                       in the current 15 minute interval."
              ::= { ncmm13IntervalEntry 12 }
               
          ncmm13IntervalPSES OBJECT-TYPE
              SYNTAX  Gauge
              ACCESS  read-only
              STATUS  mandatory
              DESCRIPTION
                      "The counter associated with the number of Seconds
                      having 44 or more Parity Code Violations,
                       in the current 15 minute interval."
              ::= { ncmm13IntervalEntry 13 }
               
          ncmm13IntervalCCV OBJECT-TYPE
              SYNTAX  Gauge
              ACCESS  read-only
              STATUS  mandatory
              DESCRIPTION
                      "The counter associated with the number of
                        C-bit Code Violations,
                       in the current 15 minute interval."
              ::= { ncmm13IntervalEntry 14 }
               
          ncmm13IntervalCES OBJECT-TYPE
              SYNTAX  Gauge
              ACCESS  read-only
              STATUS  mandatory
              DESCRIPTION
                      "The counter associated with the number of
                        C-bit Errored Seconds,
                       in the current 15 minute interval."
              ::= { ncmm13IntervalEntry 15 }
               
          ncmm13IntervalCSES OBJECT-TYPE
              SYNTAX  Gauge
              ACCESS  read-only
              STATUS  mandatory
              DESCRIPTION
                      "The counter associated with the number of
                        C-bit Severely Errored Seconds,
                       in the current 15 minute interval."
              ::= { ncmm13IntervalEntry 16 }


	 ncmm13IntervalSEFS OBJECT-TYPE
              SYNTAX  Gauge
              ACCESS  read-only
              STATUS  mandatory
              DESCRIPTION
                      "The counter associated with the number of seconds
                      in which one or more Out of Frame occurred
                       in the current 15 minute interval."
              ::= { ncmm13IntervalEntry 17 }
               
          ncmm13IntervalAISS OBJECT-TYPE
              SYNTAX  Gauge
              ACCESS  read-only
              STATUS  mandatory
              DESCRIPTION
                      "The counter associated with the number of Seconds
                      in which one or more incoming AIS was detected
                       in the current 15 minute interval."
              ::= { ncmm13IntervalEntry 18 }
               
          ncmm13IntervalLUAS OBJECT-TYPE
              SYNTAX  Gauge
              ACCESS  read-only
              STATUS  mandatory
              DESCRIPTION
                      "The counter associated with the number of Seconds
                      the m13 interface was Out Of Service
                       in the current 15 minute interval."
              ::= { ncmm13IntervalEntry 19 }
               
          ncmm13IntervalLOSS OBJECT-TYPE
              SYNTAX  Gauge
              ACCESS  read-only
              STATUS  mandatory
              DESCRIPTION
                      "The counter associated with the number of Seconds
                      Of system Loss Of Signal (LOS) in the current
                      15 minute interval."
              ::= { ncmm13IntervalEntry 20 }
               
          ncmm13IntervalLOFS OBJECT-TYPE
              SYNTAX  Gauge
              ACCESS  read-only
              STATUS  mandatory
              DESCRIPTION
                      "The counter associated with the number of Seconds
                      Of system Loss Of Frame (LOF) in the current
                      15 minute interval."
                
              ::= { ncmm13IntervalEntry 21 }


	-- the  ncm m13 Total Table
 
          ncmm13TotalTable OBJECT-TYPE
              SYNTAX  SEQUENCE OF Ncmm13TotalEntry
              ACCESS  not-accessible
              STATUS  mandatory
              DESCRIPTION
                      "The m13 Total table."
                --DEFAULT test-function   m13-test
              --DEFAULT set-function    null-set-proc
                --DEFAULT next-function   m13-next
              ::= { ncm-m13 14004 }
 
          ncmm13TotalEntry OBJECT-TYPE
              SYNTAX  Ncmm13TotalEntry
              ACCESS  not-accessible
              STATUS  mandatory
              DESCRIPTION
                      "An entry in the m13 Total table."
              INDEX   { ncmm13TotalNIDIndex, ncmm13TotalIndex }
              ::= { ncmm13TotalTable 1 }
 
 
          Ncmm13TotalEntry ::=
              SEQUENCE {
                  ncmm13TotalNIDIndex
                      INTEGER,
                  ncmm13TotalIndex
                      INTEGER,
                  ncmm13TotalCRCStatus
                      INTEGER,
                  ncmm13TotalValidInterv
                      INTEGER,
                  ncmm13TotalFarEndCCV
                      Gauge,
                  ncmm13TotalFarEndCES
                      Gauge,
                  ncmm13TotalFarEndCSES
                      Gauge,
                  ncmm13TotalFarEndLUAS
                      Gauge,
                  ncmm13TotalLCV
                      Gauge,
                  ncmm13TotalLES
                      Gauge,
                  ncmm13TotalLSES
                      Gauge,
                  ncmm13TotalPCV
                      Gauge,
                  ncmm13TotalPES
                      Gauge,
                  ncmm13TotalPSES
                      Gauge,
                  ncmm13TotalCCV
                      Gauge,
                  ncmm13TotalCES
                      Gauge,
                  ncmm13TotalCSES
                      Gauge,
                  ncmm13TotalSEFS
                      Gauge,
                  ncmm13TotalAISS
                      Gauge,
		  ncmm13TotalLUAS
		      Gauge,
		  ncmm13TotalLOSS
		      Gauge,
		  ncmm13TotalLOFS
		      Gauge
                 }
 
        ncmm13TotalNIDIndex OBJECT-TYPE
          SYNTAX  INTEGER (1..'7fffffff'h)
          ACCESS  read-only
          STATUS  mandatory
          DESCRIPTION
                "This variable indicates the node id value of the node."
            ::= { ncmm13TotalEntry 1 }
               
          ncmm13TotalIndex OBJECT-TYPE
              SYNTAX  INTEGER (1..65535)
              ACCESS  read-only
              STATUS  mandatory
              DESCRIPTION
                      "The index value which uniquely identifies the
                      m13 interface to which this entry is
                      applicable.  The interface identified by a
                      particular value of this index is the same
                      interface as identified by the same value an
                      ncmhdmLineIndex object instance."
              ::= { ncmm13TotalEntry 2 }
 
          ncmm13TotalCRCStatus OBJECT-TYPE
               SYNTAX INTEGER {
                       disabled (1)
               } 
              ACCESS  read-only
              STATUS  mandatory
              DESCRIPTION
                      "CRC4 Status."
              ::= { ncmm13TotalEntry 3 }
 
          ncmm13TotalValidInterv OBJECT-TYPE
              SYNTAX  INTEGER (1..65535)
              ACCESS  read-only
              STATUS  mandatory
              DESCRIPTION
                      "The number of valid intervals."
              ::= { ncmm13TotalEntry 4 }
 
          ncmm13TotalFarEndCCV OBJECT-TYPE
              SYNTAX  Gauge
              ACCESS  read-only
              STATUS  mandatory
              DESCRIPTION
                      "The counter associated with the number of
                        Far End C-bit Code Violations,
                      in the last 24 hour interval."
              ::= { ncmm13TotalEntry 5 }
               
          ncmm13TotalFarEndCES OBJECT-TYPE
              SYNTAX  Gauge
              ACCESS  read-only
              STATUS  mandatory
              DESCRIPTION
                      "The counter associated with the number of
                        Far End C-bit Errored Seconds,
                      in the last 24 hour interval."
              ::= { ncmm13TotalEntry 6 }

	 ncmm13TotalFarEndCSES OBJECT-TYPE
              SYNTAX  Gauge
              ACCESS  read-only
              STATUS  mandatory
              DESCRIPTION
                      "The counter associated with the number of
                        Far End C-bit Severely Errored Seconds,
                      in the last 24 hour interval."
 
              ::= { ncmm13TotalEntry 7 }
 
          ncmm13TotalFarEndLUAS OBJECT-TYPE
              SYNTAX  Gauge
              ACCESS  read-only
              STATUS  mandatory
              DESCRIPTION
                      "Far End Line Unavailable Seconds. The counter associated
                      with the number of Seconds the Far End m13 interface
                      was Out Of Service in the last 24 hour interval."
              ::= { ncmm13TotalEntry 8 }
               
          ncmm13TotalLCV OBJECT-TYPE
              SYNTAX  Gauge
              ACCESS  read-only
              STATUS  mandatory
              DESCRIPTION
                      "The counter associated with the number of Line
                      Code Violations, a bipolar or excesive zero violation,
                      in the last 24 hour interval."
              ::= { ncmm13TotalEntry 9 }
               
          ncmm13TotalLES OBJECT-TYPE
              SYNTAX  Gauge
              ACCESS  read-only
              STATUS  mandatory
              DESCRIPTION
                      "Line Errored Second Total.  The counter associated
                      with the number of Seconds of in which one or more
                      LCV occurred in the last 24 hour interval."
              ::= { ncmm13TotalEntry 10 }
               
          ncmm13TotalLSES OBJECT-TYPE
              SYNTAX  Gauge
              ACCESS  read-only
              STATUS  mandatory
              DESCRIPTION
                      "The counter associated with the number of Seconds
                      Of Line Severely Errored Seconds (LSES) in the last
                      24 hour interval."
              ::= { ncmm13TotalEntry 11 }
               
          ncmm13TotalPCV OBJECT-TYPE
              SYNTAX  Gauge
              ACCESS  read-only
              STATUS  mandatory
              DESCRIPTION
                      "The counter associated with the number
                      of Parity Code Violations (locally calculated P-bits
                      disagree with those received),
                      in the last 24 hour interval."
              ::= { ncmm13TotalEntry 12 }

	 ncmm13TotalPES OBJECT-TYPE
              SYNTAX  Gauge
              ACCESS  read-only
              STATUS  mandatory
              DESCRIPTION
                      "The counter associated with the number of Seconds
                      having at least one Parity Code Violation,
                      in the last 24 hour interval."
              ::= { ncmm13TotalEntry 13 }
               
          ncmm13TotalPSES OBJECT-TYPE
              SYNTAX  Gauge
              ACCESS  read-only
              STATUS  mandatory
              DESCRIPTION
                      "The counter associated with the number of Seconds
                      having 44 or more Parity Code Violations,
                      in the last 24 hour interval."
              ::= { ncmm13TotalEntry 14 }
               
          ncmm13TotalCCV OBJECT-TYPE
              SYNTAX  Gauge
              ACCESS  read-only
              STATUS  mandatory
              DESCRIPTION
                      "The counter associated with the number of
                        C-bit Code Violations,
                      in the last 24 hour interval."
              ::= { ncmm13TotalEntry 15 }
               
          ncmm13TotalCES OBJECT-TYPE
              SYNTAX  Gauge
              ACCESS  read-only
              STATUS  mandatory
              DESCRIPTION
                      "The counter associated with the number of
                        C-bit Errored Seconds,
                      in the last 24 hour interval."
              ::= { ncmm13TotalEntry 16 }
               
          ncmm13TotalCSES OBJECT-TYPE
              SYNTAX  Gauge
              ACCESS  read-only
              STATUS  mandatory
              DESCRIPTION
                      "The counter associated with the number of
                        C-bit Severely Errored Seconds,
                      in the last 24 hour interval."
              ::= { ncmm13TotalEntry 17 }
               
          ncmm13TotalSEFS OBJECT-TYPE
              SYNTAX  Gauge
              ACCESS  read-only
              STATUS  mandatory
              DESCRIPTION
                      "The counter associated with the number of seconds
                      in which one or more Out of Frame occurred
                      in the last 24 hour interval."
              ::= { ncmm13TotalEntry 18 }


	 ncmm13TotalAISS OBJECT-TYPE
              SYNTAX  Gauge
              ACCESS  read-only
              STATUS  mandatory
              DESCRIPTION
                      "The counter associated with the number of Seconds
                      in which one or more incoming AIS was detected
                      in the last 24 hour interval."
              ::= { ncmm13TotalEntry 19 }
               
          ncmm13TotalLUAS OBJECT-TYPE
              SYNTAX  Gauge
              ACCESS  read-only
              STATUS  mandatory
              DESCRIPTION
                      "The counter associated with the number of Seconds
                      the m13 interface was Out Of Service in the last 24
                      hour interval."
              ::= { ncmm13TotalEntry 20 }
               
          ncmm13TotalLOSS OBJECT-TYPE
              SYNTAX  Gauge
              ACCESS  read-only
              STATUS  mandatory
              DESCRIPTION
                      "The counter associated with the number of Seconds
                      Of system Loss Of Signal (LOS) in the last
                      24 hour interval."
              ::= { ncmm13TotalEntry 21 }
               
          ncmm13TotalLOFS OBJECT-TYPE
              SYNTAX  Gauge
              ACCESS  read-only
              STATUS  mandatory
              DESCRIPTION
                      "The counter associated with the number of Seconds
                      Of system Loss Of Frame (LOF) in the last
                      24 hour interval."
                
              ::= { ncmm13TotalEntry 22 }
               
	--  ncm m13 24 Hour SnapShot
 
	-- The m13 24 Hour SnapShot table contains various statistics being
	-- collected for the last 24 Hours.
 
 
         ncmm13PerformanceSnapShotTable OBJECT-TYPE
             SYNTAX  SEQUENCE OF Ncmm13PerformanceSnapShotEntry
             ACCESS  not-accessible
             STATUS  mandatory
                --DEFAULT test-function   m13-test
              --DEFAULT set-function    null-set-proc
                --DEFAULT next-function   m13-next
            ::= { ncm-m13 14005 }
 
 
         ncmm13PerformanceSnapShotEntry OBJECT-TYPE
             SYNTAX  Ncmm13PerformanceSnapShotEntry
             ACCESS  not-accessible
             STATUS  mandatory
             DESCRIPTION
             "An entry in the  m13 Performance Snap Shot Entry table."
             INDEX   { ncmm13SnapShotNIDIndex, ncmm13SnapShotIndex }
            ::= { ncmm13PerformanceSnapShotTable 1 }
 
 
        Ncmm13PerformanceSnapShotEntry ::=
         SEQUENCE {
           ncmm13SnapShotNIDIndex
                INTEGER,
           ncmm13SnapShotIndex
                 INTEGER,
           ncmm13SnapShotCRCStatus
                INTEGER,
           ncmm13SnapShot
                INTEGER,
           ncmm13TimeStampSec
                INTEGER,
           ncmm13TimeStampMilliSec
                 INTEGER,
           ncmm13SnapShotSecs
                 INTEGER,
           ncmm13ResetPerfReg
                 INTEGER
                }
          
          
       ncmm13SnapShotNIDIndex OBJECT-TYPE
             SYNTAX  INTEGER (1..'7fffffff'h)
             ACCESS  read-only
             STATUS  mandatory
             DESCRIPTION
                "The object specifies the node id index of the node."
            ::= { ncmm13PerformanceSnapShotEntry 1 }
 
	
        ncmm13SnapShotIndex OBJECT-TYPE
             SYNTAX  INTEGER (1..'7fffffff'h)
             ACCESS  read-only
             STATUS  mandatory
             DESCRIPTION
                "The index value which uniquely identifies  the
                m13  interface  to which this entry is applica-
                ble.  The interface identified by a  particular
                value  of  this  index is the same interface as
                identified by the same value as a LineIndex
                object instance."
            ::= { ncmm13PerformanceSnapShotEntry 2 }
 
 
          ncmm13SnapShotCRCStatus OBJECT-TYPE
               SYNTAX INTEGER {
                       disabled (1)
               } 
              ACCESS  read-only
              STATUS  mandatory
              DESCRIPTION
                      "CRC4 Status."
              ::= { ncmm13PerformanceSnapShotEntry 3 }
 
        ncmm13SnapShot OBJECT-TYPE
            SYNTAX INTEGER {
                                no(1),
                                yes(2)
                       } 
           ACCESS read-write
           STATUS mandatory
           DESCRIPTION
           "The variable specifies the option to initiate snap shot
               command."
 
            ::= { ncmm13PerformanceSnapShotEntry 4 }
 
        ncmm13TimeStampSec OBJECT-TYPE
           SYNTAX  INTEGER (1..'7fffffff'h)
           ACCESS read-only
           STATUS mandatory
           DESCRIPTION
           "The variable specifies the Time Stamp in Seconds ."
 
           ::= { ncmm13PerformanceSnapShotEntry 5 }
 
 
        ncmm13TimeStampMilliSec OBJECT-TYPE
            SYNTAX  INTEGER (1..65535)
           ACCESS read-only
           STATUS mandatory
           DESCRIPTION
           "The variable specifies the Time Stamp in milli  Seconds ."
 
           ::= { ncmm13PerformanceSnapShotEntry  6 }


	
         ncmm13SnapShotSecs OBJECT-TYPE
            SYNTAX  INTEGER (1..65535)
           ACCESS read-only
            STATUS mandatory
           DESCRIPTION
           "The variable specifies number of seconds in the current interval."
            ::= { ncmm13PerformanceSnapShotEntry 7 }
 
         ncmm13ResetPerfReg OBJECT-TYPE
             SYNTAX  INTEGER {
                         no(1),
                         yes(2)
                     }
             ACCESS  read-write
             STATUS  mandatory
             DESCRIPTION
                "Reset Performance Monitoring registers."
            ::= { ncmm13PerformanceSnapShotEntry 8 }
 
	-- the Quarter-Hour m13 AlertThreshold table
 
          ncmm13TCAQtrTable OBJECT-TYPE
              SYNTAX  SEQUENCE OF Ncmm13TCAQtrEntry
              ACCESS  not-accessible
              STATUS  mandatory
              DESCRIPTION
                      "The quarter hour Alert Threshold Table."
                --DEFAULT test-function   m13-test
              --DEFAULT set-function    null-set-proc
                --DEFAULT next-function   m13-next
              ::= { ncm-m13 14006  }
 
          ncmm13TCAQtrEntry OBJECT-TYPE
              SYNTAX  Ncmm13TCAQtrEntry
              ACCESS  not-accessible
              STATUS  mandatory
              DESCRIPTION
                      "An entry in the m13 table."
              INDEX   { ncmm13TCAQtrNIDIndex, ncmm13TCAQtrIndex }
              ::= { ncmm13TCAQtrTable 1 }
 
          Ncmm13TCAQtrEntry ::=
              SEQUENCE {
                  ncmm13TCAQtrNIDIndex
                      INTEGER,
                  ncmm13TCAQtrIndex
                      INTEGER,
                  ncmm13TCAQtrFarEndCCV
                      INTEGER,
                  ncmm13TCAQtrFarEndCES
                      INTEGER,
                  ncmm13TCAQtrFarEndCSES
                      INTEGER,
                  ncmm13TCAQtrFarEndLUAS
                      INTEGER,
                  ncmm13TCAQtrLCV
                      INTEGER,
                  ncmm13TCAQtrLES
                      INTEGER,
                  ncmm13TCAQtrLSES
                      INTEGER,
                  ncmm13TCAQtrPCV
                      INTEGER,
                  ncmm13TCAQtrPES
                      INTEGER,
                  ncmm13TCAQtrPSES
                      INTEGER,
                  ncmm13TCAQtrCCV
                      INTEGER,
                  ncmm13TCAQtrCES
                      INTEGER,
                  ncmm13TCAQtrCSES
                      INTEGER,
                  ncmm13TCAQtrSEFS
                      INTEGER,
                  ncmm13TCAQtrAISS
                      INTEGER,
                  ncmm13TCAQtrLUAS
                      INTEGER,
                  ncmm13TCAQtrLOSS
                      INTEGER,
                  ncmm13TCAQtrLOFS
                      INTEGER
              }

	ncmm13TCAQtrNIDIndex OBJECT-TYPE
          SYNTAX  INTEGER (1..'7fffffff'h)
          ACCESS  read-only
          STATUS  mandatory
          DESCRIPTION
                "This variable indicates the node id value of the node."
            ::= { ncmm13TCAQtrEntry 1 }
               
          ncmm13TCAQtrIndex OBJECT-TYPE
              SYNTAX  INTEGER (1..65535)
              ACCESS  read-only
              STATUS  mandatory
              DESCRIPTION
                      "The index value which uniquely identifies the
                      alert crossing threshold interface to which
                      this entry is applicable.  The interface
                      identified by a particular value of this
                      index is the same interface as identified
                      by the same value an plcpLineIndex object
                      instance."
              ::= { ncmm13TCAQtrEntry 2 }
               
          ncmm13TCAQtrFarEndCCV OBJECT-TYPE
              SYNTAX  INTEGER (0..4294967295)
              ACCESS  read-write
              STATUS  mandatory
              DESCRIPTION
                      "The performance alert threshold for m13
                        layer Far End C-bit Code Violation in 1/4 hour
                        boundary."
              ::= { ncmm13TCAQtrEntry 3 }
               
          ncmm13TCAQtrFarEndCES OBJECT-TYPE
              SYNTAX  INTEGER (0..4294967295)
              ACCESS  read-write
              STATUS  mandatory
              DESCRIPTION
                      "The performance alert threshold for m13
                        Far End C-bit Errored Seconds,
                        in 1/4 hour boundary."
              ::= { ncmm13TCAQtrEntry 4 }
               
          ncmm13TCAQtrFarEndCSES OBJECT-TYPE
              SYNTAX  INTEGER (0..4294967295)
              ACCESS  read-write
              STATUS  mandatory
              DESCRIPTION
                      "The performance alert threshold for m13
                        Far End C-bit Severely Errored Seconds,
                        in 1/4 hour boundary."
 
              ::= { ncmm13TCAQtrEntry 5 }
 
          ncmm13TCAQtrFarEndLUAS OBJECT-TYPE
              SYNTAX  INTEGER (0..4294967295)
              ACCESS  read-write
              STATUS  mandatory
              DESCRIPTION
                      "The performance alert threshold for m13 layer
                      Far End Line Unavailable Seconds in 1/4 hour
                        boundary."
              ::= { ncmm13TCAQtrEntry 6 }


	ncmm13TCAQtrLCV OBJECT-TYPE
              SYNTAX  INTEGER (0..4294967295)
              ACCESS  read-write
              STATUS  mandatory
              DESCRIPTION
                      "The performance alert threshold for m13
                        layer Line code Violation in 1/4 hour
                        boundary."
              ::= { ncmm13TCAQtrEntry 7 }
               
          ncmm13TCAQtrLES OBJECT-TYPE
              SYNTAX  INTEGER (0..4294967295)
              ACCESS  read-write
              STATUS  mandatory
              DESCRIPTION
                        "The performance alert threshold for m13
                        layer Line Errored Second in 1/4 hour
                        boundary."
 
              ::= { ncmm13TCAQtrEntry 8 }
 
          ncmm13TCAQtrLSES OBJECT-TYPE
              SYNTAX  INTEGER (0..4294967295)
              ACCESS  read-write
              STATUS  mandatory
              DESCRIPTION
                        "The performance alert threshold for m13
                        layer Line Severely Errored Second
                        in 1/4 hour boundary."
              ::= { ncmm13TCAQtrEntry 9 }
               
          ncmm13TCAQtrPCV OBJECT-TYPE
              SYNTAX  INTEGER (0..4294967295)
              ACCESS  read-write
              STATUS  mandatory
              DESCRIPTION
                        "The performance alert threshold for m13
                        layer Parity Code Violation in 1/4 hour boundary."
              ::= { ncmm13TCAQtrEntry 10 }
               
          ncmm13TCAQtrPES OBJECT-TYPE
              SYNTAX  INTEGER (0..4294967295)
              ACCESS  read-write
              STATUS  mandatory
              DESCRIPTION
                        "The performance alert threshold for m13
                        layer Parity Errored Second in 1/4 hour boundary."
              ::= { ncmm13TCAQtrEntry 11 }
               
          ncmm13TCAQtrPSES OBJECT-TYPE
              SYNTAX  INTEGER (0..4294967295)
              ACCESS  read-write
              STATUS  mandatory
              DESCRIPTION
                        "The performance alert threshold for m13
                        layer Parity Severely Errored Second in 1/4 hour
                        boundary."
              ::= { ncmm13TCAQtrEntry 12 }


	 ncmm13TCAQtrCCV OBJECT-TYPE
              SYNTAX  INTEGER (0..4294967295)
              ACCESS  read-write
              STATUS  mandatory
              DESCRIPTION
                        "The performance alert threshold for m13
                        layer C-bit Code Violation in 1/4 hour boundary."
              ::= { ncmm13TCAQtrEntry 13 }
               
          ncmm13TCAQtrCES OBJECT-TYPE
              SYNTAX  INTEGER (0..4294967295)
              ACCESS  read-write
              STATUS  mandatory
              DESCRIPTION
                        "The performance alert threshold for m13
                        Far End C-bit Errored Seconds,
                        layer Errored Second in 1/4 hour boundary."
              ::= { ncmm13TCAQtrEntry 14 }
               
          ncmm13TCAQtrCSES OBJECT-TYPE
              SYNTAX  INTEGER (0..4294967295)
              ACCESS  read-write
              STATUS  mandatory
              DESCRIPTION
                        "The performance alert threshold for m13
                        layer C-bit Severely Errored Second in 1/4 hour
                        boundary."
              ::= { ncmm13TCAQtrEntry 15 }
               
          ncmm13TCAQtrSEFS OBJECT-TYPE
              SYNTAX  INTEGER (0..4294967295)
              ACCESS  read-write
              STATUS  mandatory
              DESCRIPTION
                        "The performance alert threshold for m13
                        layer Severely Errored Framing Seconds
                        in 1/4 hour boundary."
              ::= { ncmm13TCAQtrEntry 16 }
               
          ncmm13TCAQtrAISS OBJECT-TYPE
              SYNTAX  INTEGER (0..4294967295)
              ACCESS  read-write
              STATUS  mandatory
              DESCRIPTION
                        "The performance alert threshold for m13
                        layer Alarm Indication Signal Second
                        in 1/4 hour boundary."
              ::= { ncmm13TCAQtrEntry 17 }
               
          ncmm13TCAQtrLUAS OBJECT-TYPE
              SYNTAX  INTEGER (0..4294967295)
              ACCESS  read-write
              STATUS  mandatory
              DESCRIPTION
                        "The performance alert threshold for m13
                        layer Unavailable Second in 1/4 hour
                        boundary."
              ::= { ncmm13TCAQtrEntry 18 }


	ncmm13TCAQtrLOSS OBJECT-TYPE
              SYNTAX  INTEGER (0..4294967295)
              ACCESS  read-write
              STATUS  mandatory
              DESCRIPTION
                        "The performance alert threshold for m13
                        Loss of Signal (LOS) Seconds in 1/4 hour
                        boundary."
              ::= { ncmm13TCAQtrEntry 19 }
               
          ncmm13TCAQtrLOFS OBJECT-TYPE
              SYNTAX  INTEGER (0..4294967295)
              ACCESS  read-write
              STATUS  mandatory
              DESCRIPTION
                        "The performance alert threshold for m13
                        Loss of Frame (LOF) Seconds in 1/4 hour
                        boundary."
              ::= { ncmm13TCAQtrEntry 20 }
               
	-- the 24-Hour m13 AlertThreshold table
 
          ncmm13TCADayTable OBJECT-TYPE
              SYNTAX  SEQUENCE OF Ncmm13TCADayEntry
              ACCESS  not-accessible
              STATUS  mandatory
              DESCRIPTION
                      "The 24 hour m13 Alert Threshold Table."
                --DEFAULT test-function   m13-test
              --DEFAULT set-function    null-set-proc
                --DEFAULT next-function   m13-next
              ::= { ncm-m13 14007 }
 
          ncmm13TCADayEntry OBJECT-TYPE
              SYNTAX  Ncmm13TCADayEntry
              ACCESS  not-accessible
              STATUS  mandatory
              DESCRIPTION
                      "An entry in the 24 hour m13 Alert Threshold Table."
              INDEX   { ncmm13TCADayNIDIndex,  ncmm13TCADayIndex }
              ::= { ncmm13TCADayTable 1 }
 
          Ncmm13TCADayEntry ::=
              SEQUENCE {
                  ncmm13TCADayNIDIndex
                      INTEGER,
                  ncmm13TCADayIndex
                      INTEGER,
                  ncmm13TCADayFarEndCCV
                      INTEGER,
                  ncmm13TCADayFarEndCES
                      INTEGER,
                  ncmm13TCADayFarEndCSES
                      INTEGER,
                  ncmm13TCADayFarEndLUAS
                      INTEGER,
                  ncmm13TCADayLCV
                      INTEGER,
                  ncmm13TCADayLES
                      INTEGER,
                  ncmm13TCADayLSES
                      INTEGER,
                  ncmm13TCADayPCV
                      INTEGER,
                  ncmm13TCADayPES
                      INTEGER,
                  ncmm13TCADayPSES
                      INTEGER,
                  ncmm13TCADayCCV
                      INTEGER,
                  ncmm13TCADayCES
                      INTEGER,
                  ncmm13TCADayCSES
                      INTEGER,
                  ncmm13TCADaySEFS
                      INTEGER,
                  ncmm13TCADayAISS
                      INTEGER,
                  ncmm13TCADayLUAS
                      INTEGER,
                  ncmm13TCADayLOSS
                      INTEGER,
                  ncmm13TCADayLOFS
                      INTEGER
              }


	ncmm13TCADayNIDIndex OBJECT-TYPE
          SYNTAX  INTEGER (1..'7fffffff'h)
          ACCESS  read-only
          STATUS  mandatory
          DESCRIPTION
                "This variable indicates the node id value of the node."
            ::= { ncmm13TCADayEntry 1 }
               
          ncmm13TCADayIndex OBJECT-TYPE
              SYNTAX  INTEGER (1..65535)
              ACCESS  read-only
              STATUS  mandatory
              DESCRIPTION
                      "The index value which uniquely identifies the
                      alert crossing threshold interface to which
                      this entry is applicable.  The interface
                      identified by a particular value of this
                      index is the same interface as identified
                      by the same value an plcpLineIndex object
                      instance."
              ::= { ncmm13TCADayEntry 2 }
               
 
          ncmm13TCADayFarEndCCV OBJECT-TYPE
              SYNTAX  INTEGER (0..4294967295)
              ACCESS  read-write
              STATUS  mandatory
              DESCRIPTION
                      "The performance alert threshold for m13
                        layer Far End C-bit Code Violation in 24 hour
                        boundary."
              ::= { ncmm13TCADayEntry 3 }
               
          ncmm13TCADayFarEndCES OBJECT-TYPE
              SYNTAX  INTEGER (0..4294967295)
              ACCESS  read-write
              STATUS  mandatory
              DESCRIPTION
                      "The performance alert threshold for m13
                        Far End C-bit Errored Seconds,
                        in 24 hour boundary."
              ::= { ncmm13TCADayEntry 4 }
               
          ncmm13TCADayFarEndCSES OBJECT-TYPE
              SYNTAX  INTEGER (0..4294967295)
              ACCESS  read-write
              STATUS  mandatory
              DESCRIPTION
                      "The performance alert threshold for m13
                        Far End C-bit Severely Errored Seconds,
                        in 24 hour boundary."
 
              ::= { ncmm13TCADayEntry 5 }
 
          ncmm13TCADayFarEndLUAS OBJECT-TYPE
              SYNTAX  INTEGER (0..4294967295)
              ACCESS  read-write
              STATUS  mandatory
              DESCRIPTION
                      "The performance alert threshold for m13 layer
                      Far End Line Unavailable Seconds in 24 hour
                      boundary."
              ::= { ncmm13TCADayEntry 6 }


	 ncmm13TCADayLCV OBJECT-TYPE
              SYNTAX  INTEGER (0..4294967295)
              ACCESS  read-write
              STATUS  mandatory
              DESCRIPTION
                      "The performance alert threshold for m13
                        layer Line code Violation in 24 hour
                        boundary."
              ::= { ncmm13TCADayEntry 7 }
               
          ncmm13TCADayLES OBJECT-TYPE
              SYNTAX  INTEGER (0..4294967295)
              ACCESS  read-write
              STATUS  mandatory
              DESCRIPTION
                        "The performance alert threshold for m13
                        layer Line Errored Second in 24 hour
                        boundary."
 
              ::= { ncmm13TCADayEntry 8 }
 
          ncmm13TCADayLSES OBJECT-TYPE
              SYNTAX  INTEGER (0..4294967295)
              ACCESS  read-write
              STATUS  mandatory
              DESCRIPTION
                        "The performance alert threshold for m13
                        layer Line Severely Errored Second
                        in 24 hour boundary."
              ::= { ncmm13TCADayEntry 9 }
               
          ncmm13TCADayPCV OBJECT-TYPE
              SYNTAX  INTEGER (0..4294967295)
              ACCESS  read-write
              STATUS  mandatory
              DESCRIPTION
                        "The performance alert threshold for m13
                        layer Parity Code Violation in 24 hour boundary."
              ::= { ncmm13TCADayEntry 10 }
               
          ncmm13TCADayPES OBJECT-TYPE
              SYNTAX  INTEGER (0..4294967295)
              ACCESS  read-write
              STATUS  mandatory
              DESCRIPTION
                        "The performance alert threshold for m13
                        layer Parity Errored Second in 24 hour boundary."
              ::= { ncmm13TCADayEntry 11 }
               
          ncmm13TCADayPSES OBJECT-TYPE
              SYNTAX  INTEGER (0..4294967295)
              ACCESS  read-write
              STATUS  mandatory
              DESCRIPTION
                        "The performance alert threshold form 13
                        layer Parity Severely Errored Second in 24 hour
                        boundary."
              ::= { ncmm13TCADayEntry 12 }


	 ncmm13TCADayCCV OBJECT-TYPE
              SYNTAX  INTEGER (0..4294967295)
              ACCESS  read-write
              STATUS  mandatory
              DESCRIPTION
                        "The performance alert threshold for m13
                        layer C-bit Code Violation in 24 hour boundary."
              ::= { ncmm13TCADayEntry 13 }
               
          ncmm13TCADayCES OBJECT-TYPE
              SYNTAX  INTEGER (0..4294967295)
              ACCESS  read-write
              STATUS  mandatory
              DESCRIPTION
                        "The performance alert threshold for m13
                        C-bit Errored Seconds, in 24 hour boundary."
              ::= { ncmm13TCADayEntry 14 }
               
          ncmm13TCADayCSES OBJECT-TYPE
              SYNTAX  INTEGER (0..4294967295)
              ACCESS  read-write
              STATUS  mandatory
              DESCRIPTION
                        "The performance alert threshold for DS3
                        C-bit Severely Errored Seconds, in 24 hour
                        boundary."
              ::= { ncmm13TCADayEntry 15 }
               
          ncmm13TCADaySEFS OBJECT-TYPE
              SYNTAX  INTEGER (0..4294967295)
              ACCESS  read-write
              STATUS  mandatory
              DESCRIPTION
                        "The performance alert threshold for m13
                        layer Severely Errored Framing Seconds
                        in 24 hour boundary."
              ::= { ncmm13TCADayEntry 16 }
               
          ncmm13TCADayAISS OBJECT-TYPE
              SYNTAX  INTEGER (0..4294967295)
              ACCESS  read-write
              STATUS  mandatory
              DESCRIPTION
                        "The performance alert threshold for m13
                        layer Alarm Indication Signal Second
                        in 24 hour boundary."
              ::= { ncmm13TCADayEntry 17 }
               
          ncmm13TCADayLUAS OBJECT-TYPE
              SYNTAX  INTEGER (0..4294967295)
              ACCESS  read-write
              STATUS  mandatory
              DESCRIPTION
                        "The performance alert threshold for m13
                        layer Unavailable Second in 24 hour
                        boundary."
              ::= { ncmm13TCADayEntry 18 }


	ncmm13TCADayLOSS OBJECT-TYPE
              SYNTAX  INTEGER (0..4294967295)
              ACCESS  read-write
              STATUS  mandatory
              DESCRIPTION
                        "The performance alert threshold for m13
                        Loss of Signal (LOS) Seconds in 24 hour
                        boundary."
              ::= { ncmm13TCADayEntry 19 }
               
          ncmm13TCADayLOFS OBJECT-TYPE
              SYNTAX  INTEGER (0..4294967295)
              ACCESS  read-write
              STATUS  mandatory
              DESCRIPTION
                        "The performance alert threshold for m13
                        Loss of Frame (LOF) Seconds in 24 hour
                        boundary."
              ::= { ncmm13TCADayEntry 20 }
               

	 -- m13 Transmit Alarm table
 
          ncmm13TxAlarmTable OBJECT-TYPE
              SYNTAX  SEQUENCE OF Ncmm13TxAlarmEntry
              ACCESS  not-accessible
              STATUS  mandatory
              DESCRIPTION
                "m13 Transmit alarm Table."
                --DEFAULT test-function   m13-test
              --DEFAULT set-function    null-set-proc
                --DEFAULT next-function   m13-next
              ::= { ncm-m13 14008 }
 
          ncmm13TxAlarmEntry OBJECT-TYPE
              SYNTAX  Ncmm13TxAlarmEntry
              ACCESS  not-accessible
              STATUS  mandatory
              DESCRIPTION
                      "An entry in the m13 Transmit Alarm table."
              INDEX   { ncmm13TxAlarmNIDIndex, ncmm13TxAlarmIndex }
              ::= { ncmm13TxAlarmTable 1 }
 
          Ncmm13TxAlarmEntry ::=
              SEQUENCE {
                  ncmm13TxAlarmNIDIndex
                      INTEGER,
                  ncmm13TxAlarmIndex
                      INTEGER,
                  ncmm13TxYellowAlarm
                      INTEGER,
                  ncmm13TxAIS
                      INTEGER,
                  ncmm13TxIdleSignal
                      INTEGER,
                  ncmm13TxFEBE
                      INTEGER,
                  ncmm13TxFEACAlarm
                      INTEGER
              }
 
        ncmm13TxAlarmNIDIndex OBJECT-TYPE
          SYNTAX  INTEGER (1..'7fffffff'h)
          ACCESS  read-only
          STATUS  mandatory
          DESCRIPTION
                "This variable indicates the node id value of the node."
            ::= { ncmm13TxAlarmEntry 1 }


	 ncmm13TxAlarmIndex OBJECT-TYPE
              SYNTAX  INTEGER (1..65535)
              ACCESS  read-only
              STATUS  mandatory
              DESCRIPTION
                      "The index value which uniquely identifies the
                      Transmit Alarm interface to which
                      this entry is applicable.  The interface
                      identified by a particular value of this
                      index is the same interface as identified
                      by the same value an m13 LineIndex object
                      instance."
              ::= { ncmm13TxAlarmEntry 2 }
               
          ncmm13TxYellowAlarm OBJECT-TYPE
              SYNTAX  INTEGER{
                        enable(1),
                        disable(2)
                      }
              ACCESS  read-write
              STATUS  mandatory
              DESCRIPTION
                      "Transmit the near-end yellow alarm for m13."
              ::= { ncmm13TxAlarmEntry 3 }
 
          ncmm13TxAIS   OBJECT-TYPE
              SYNTAX  INTEGER{
                        enable(1),
                        disable(2)
                      }
              ACCESS  read-write
              STATUS  mandatory
              DESCRIPTION
                      "Transmit the near-end AIS alarm for m13."
              ::= { ncmm13TxAlarmEntry 4 }
 
          ncmm13TxIdleSignal OBJECT-TYPE
              SYNTAX  INTEGER{
                        enable(1),
                        disable(2)
                      }
              ACCESS  read-write
              STATUS  mandatory
              DESCRIPTION
                      "Transmit the near-end Idle alarm for m13."
              ::= { ncmm13TxAlarmEntry 5 }
 
          ncmm13TxFEBE OBJECT-TYPE
              SYNTAX  INTEGER{
                        enable(1),
                        disable(2)
                      }
              ACCESS  read-write
              STATUS  mandatory
              DESCRIPTION
                      "Near end unit transmits the FEBE alarm for m13."
              ::= { ncmm13TxAlarmEntry 6 }


	 ncmm13TxFEACAlarm OBJECT-TYPE
              SYNTAX  INTEGER{
                        no-FEAC-Alarm-enabled (1),
                        eqpt-FailureSA-Alarm (2),
                        los-HBER-Alarm (3),
                        oof-Alarm (4),
                        ais-Received-Alarm (5),
                        idle-Received-Alarm (6),
                        eqpt-NSA-Alarm (7),
                        common-Eqpt-NSA-Alarm (8)
                      }
              ACCESS  read-write
              STATUS  mandatory
              DESCRIPTION
                      "This object describes which, if any, FEAC
                        Alarm is enabled. "
              ::= { ncmm13TxAlarmEntry 7 }
               

                 
-- ncm m13 DS3 Line Loopback Activate/Deactivate
 
              ncmm13DS3LPBKTable OBJECT-TYPE
              SYNTAX  SEQUENCE OF Ncmm13DS3LPBKEntry
              ACCESS  not-accessible
              STATUS  mandatory
              DESCRIPTION
                      "The m13 DS3 Loopback table."
                --DEFAULT test-function   m13-test
              --DEFAULT set-function    null-set-proc
                --DEFAULT next-function   m13-next
 
              ::= { ncm-m13 14009 }
 
          ncmm13DS3LPBKEntry OBJECT-TYPE
              SYNTAX  Ncmm13DS3LPBKEntry
              ACCESS  not-accessible
              STATUS  mandatory
              DESCRIPTION
                      "An entry in the m13 Loopback table."
              INDEX   { ncmm13DS3LPBKNIDIndex, ncmm13DS3LPBKIndex }
              ::= { ncmm13DS3LPBKTable 1 }

 	Ncmm13DS3LPBKEntry ::=
              SEQUENCE {
                  ncmm13DS3LPBKNIDIndex
                      INTEGER,
                  ncmm13DS3LPBKIndex
                      INTEGER,
                  ncmm13DS3LPBKAction
                      INTEGER
              }  
 
        ncmm13DS3LPBKNIDIndex OBJECT-TYPE
          SYNTAX  INTEGER (1..'7fffffff'h)
          ACCESS  read-only
          STATUS  mandatory
          DESCRIPTION
                "This variable indicates the node id value of the node."
            ::= { ncmm13DS3LPBKEntry 1 }
         
          ncmm13DS3LPBKIndex OBJECT-TYPE
              SYNTAX  INTEGER (1..65535)
              ACCESS  read-only
              STATUS  mandatory
              DESCRIPTION
                      "The index value which uniquely identifies the
                      m13 interface to which this entry is
                      applicable.  The interface identified by a
                      particular value of this index is the same
                      interface as identified by the same value an
                      ncmm13LineIndex object instance."
              ::= { ncmm13DS3LPBKEntry 2 }

	ncmm13DS3LPBKAction OBJECT-TYPE
          SYNTAX INTEGER {
                        no-Loopback (1),
                        m13-DS3-Activate-Local(2),
                        m13-DS3-Activate-Line(3),
                        m13-DS3-Activate-FEAC-Far-End(4),
                        m13-DS3-Activate-Inband-Far-End(5),
                        m13-DS3-DeActivate-Local (6),
                        m13-DS3-DeActivate-Line (7),
                        m13-DS3-DeActivate-FEAC-Far-End (8),
                        m13-DS3-DeActivate-Inband-Far-End (9)
                          }
          ACCESS read-write
          STATUS mandatory
          DESCRIPTION
               "m13 DS3 Loopback Activation/Deactivation."
          ::= { ncmm13DS3LPBKEntry 3 }



	 -- ncm m13 T1 Loopback Activate/Deactivate
 
              ncmm13T1LPBKTable OBJECT-TYPE
              SYNTAX  SEQUENCE OF Ncmm13T1LPBKEntry
              ACCESS  not-accessible
              STATUS  mandatory
              DESCRIPTION
                      "The m13 Loopback table."
                --DEFAULT test-function   m13loop-test
              --DEFAULT set-function    null-set-proc
                --DEFAULT next-function   m13loop-next
 
              ::= { ncm-m13 14010 }
 
          ncmm13T1LPBKEntry OBJECT-TYPE
              SYNTAX  Ncmm13T1LPBKEntry
              ACCESS  not-accessible
              STATUS  mandatory
              DESCRIPTION
                      "An entry in the m13 Loopback table."
              INDEX   { ncmm13T1LPBKNIDIndex, ncmm13T1LPBKIndex }
              ::= { ncmm13T1LPBKTable 1 }

	Ncmm13T1LPBKEntry ::=
              SEQUENCE {
                  ncmm13T1LPBKNIDIndex
                      INTEGER,
                  ncmm13T1LPBKIndex
                      INTEGER,
                  ncmm13T1LPBKAction
                      INTEGER
              }  
 
        ncmm13T1LPBKNIDIndex OBJECT-TYPE
          SYNTAX  INTEGER (1..'7fffffff'h)
          ACCESS  read-only
          STATUS  mandatory
          DESCRIPTION
                "This variable indicates the node id value of the node."
            ::= { ncmm13T1LPBKEntry 1 }
         
          ncmm13T1LPBKIndex OBJECT-TYPE
              SYNTAX  INTEGER (1..65535)
              ACCESS  read-only
              STATUS  mandatory
              DESCRIPTION
                      "The index value which uniquely identifies the
                      m13 interface to which this entry is
                      applicable.  The interface identified by a
                      particular value of this index is the same
                      interface as identified by the same value an
                      ncmm13LineIndex object instance."
              ::= { ncmm13T1LPBKEntry 2 }

	 ncmm13T1LPBKAction OBJECT-TYPE
          SYNTAX INTEGER {
                        no-Loopback (1),
                        m13-Activate-1-28-T1-Line(10),
                        m13-Activate-All-T1-Line(11),
                        m13-Activate-1-28-T1-Far-End(12),
                        m13-Activate-All-T1-Far-End(13),
                        m13-Activate-1-28-T1-Local(14),
                        m13-Activate-All-T1-Local(15),
                        m13-DeActivate-1-28-T1-Line(16),
                        m13-DeActivate-All-T1-Line(17),
                        m13-DeActivate-1-28-T1-Far-End(18),
                        m13-DeActivate-All-T1-Far-End(19),
                        m13-DeActivate-1-28-T1-Local(20),
                        m13-DeActivate-All-T1-Local(21)
                          }
          ACCESS read-write
          STATUS mandatory
          DESCRIPTION
               "m13 Loopback Activate
                if Line Type = 0 (DS3 Loopback)
                1 No Active
                2 Local Loopback
                3 Line Loopback
                4 FEAC Far End
                5 Inband Far End
 
                if Line Type = 1 (T1 Line Command)
                6 1-28 T1 Line Loopback

		if Line Type = 2(T1 Far End Line)
                7 1-28 T1 Far End Loopback
 
                if Line Type = 3(T1 Local Loopback )
                8 1-28 T1 Local Loopback
 
                m13 Loopback DeActivate
                if Line Type = 0 (DS3 Loopback)
                1 No Active
                9 Local Loopback
                10 Line Loopback
                11 FEAC Far End
                12 Inband Far End
 
                if Line Type = 1 (T1 Line Command)
                13 1-28 T1 Line Loopback
 
                if Line Type = 2(T1 Far End Line)
                14 1-28 T1 Far End Loopback
 
                if Line Type = 3(T1 Local Loopback )
                15 1-28 T1 Local Loopback."
 
          ::= { ncmm13T1LPBKEntry 3 }



	 --   ncm m13 T1 Port Configuration Table


       ncmm13T1ConfigTable OBJECT-TYPE
             SYNTAX  SEQUENCE OF Ncmm13T1ConfigEntry
             ACCESS  not-accessible
             STATUS  mandatory
             --DEFAULT test-function    m13t1-test
             --DEFAULT next-function    m13t1-next


            ::= { ncm-m13 14011 }


       ncmm13T1ConfigEntry OBJECT-TYPE
             SYNTAX  Ncmm13T1ConfigEntry
             ACCESS  not-accessible
             STATUS  mandatory
             DESCRIPTION
                "An entry in the  ncm m13 T1 Configuration table."
            INDEX   { ncmm13T1ConfigNIDIndex, ncmm13T1LineIndex }
            ::= { ncmm13T1ConfigTable 1 }


       Ncmm13T1ConfigEntry ::=
         SEQUENCE {

           ncmm13T1ConfigNIDIndex
                INTEGER,
           ncmm13T1LineIndex
                 INTEGER,  
	   ncmm13T1FramingFormat
		 INTEGER,              
           ncmm13T1LineCoding
                 INTEGER,
           ncmm13T1EnableNetOnesDensity
                INTEGER,
           ncmm13T1DensityPattern
                 INTEGER,
	   ncmm13T1PortService
		 INTEGER
                           }
 
        ncmm13T1ConfigNIDIndex OBJECT-TYPE
             SYNTAX  INTEGER (1..'7fffffff'h)
             ACCESS  read-only
             STATUS  mandatory
             DESCRIPTION
                "This object is the identifier of the node id index."
            ::= { ncmm13T1ConfigEntry 1 }       
 
        ncmm13T1LineIndex OBJECT-TYPE
             SYNTAX  INTEGER (1..'7fffffff'h)
             ACCESS  read-only
             STATUS  mandatory
             DESCRIPTION
                "This object is the identifier of a  Inter-
                f on a managed device.  If there is an ifEn-
                try that is directly associated with  this  and
                only  this  m13  interface,  it should have the
                same value as ifIndex.   Otherwise,  the  value
                exceeds  ifNumber,  and  is a unique identifier
                following this rule: inside  interfaces  (e.g.,
                equipment  side)  with even numbers and outside
                interfaces  (e.g.,  network   side)   with   odd
                numbers."
            ::= { ncmm13T1ConfigEntry 2 }


	 ncmm13T1FramingFormat OBJECT-TYPE
             SYNTAX  INTEGER {
                         sF(1),
                         eSF(2)
                          }    
             ACCESS  read-write
             STATUS  mandatory
             DESCRIPTION
                "This variable indicates  the  variety  of
                Line  implementing  this  circuit.  The type of
                circuit affects the number of bits  per  second
                that  the circuit can reasonably carry, as well
                as the interpretation of the  usage  and  error
                statistics.  The values, in sequence, describe:

                TITLE:          SPECIFICATION:
                ESF             Extended SuperFrame DS1
                SF              Super Frame"

         ::= { ncmm13T1ConfigEntry 3 }

 
 
          ncmm13T1LineCoding OBJECT-TYPE
             SYNTAX  INTEGER {

                         aMI (1),
                         b8ZS (2)
                     }
             ACCESS  read-write
             STATUS  mandatory
             DESCRIPTION
                "This variable describes the  variety  of  Zero
                Code  Suppression  used  on  the link, which in
                turn affects a number of its characteristics.

                B8ZS refers to the use of a specified  pat-
                tern  of  normal  bits  and  bipolar violations
                which are used to replace a  sequence  of  eight
                zero bits.

                AMI refers to a mode wherein no  zero  code
                suppression  is  present  and the line encoding
                does not solve the problem directly.   In  this
                application, the higher layer must provide data
                which meets or exceeds the  pulse  density  re-
                quirements, such as inverting HDLC data."

            ::= { ncmm13T1ConfigEntry 4 }

                  

	   ncmm13T1EnableNetOnesDensity OBJECT-TYPE
             SYNTAX  INTEGER {
                        disabled(1),
                        enabled(2)
                     }
             ACCESS  read-write
             STATUS  mandatory
             DESCRIPTION
          "The variable specifies the Disable/Enable of the Network
               One's Density."
            ::= { ncmm13T1ConfigEntry 5 }
      
        

	   ncmm13T1DensityPattern OBJECT-TYPE
            SYNTAX  INTEGER {
 
                             d80Zeros(1),
                             d15Zeros(2),
                             d12d5c80Zero(3),
                             tR-62411(4)
 
                              }
            ACCESS  read-write
            STATUS  mandatory
            DESCRIPTION
           "This variable indicates what type of density network is
            being sent on the port or line by the device. The values
                mean :
 
           'Disabled' refers to no network ones density exist.
 
           'D80Zeros' refers to send a request for network one's density
            of 80 zeroes density pattern.
 
           'D15Zeros' refers to send a request for network one's density
                of 15 zeroes density pattern.
 
          'D12d5c80Zero'refers to send a request for 12.5% and 80 zeroes
           network one's density pattern.
 
           'TR-62411' refers to sending a request for TR6241
            network density pattern.
 
           'Other' refers to sending a network's density pattern
            other than those described by this object[pvt]**."
           ::= { ncmm13T1ConfigEntry 6 }

 
 	ncmm13T1PortService  OBJECT-TYPE
             SYNTAX  INTEGER {
                        out-of-service(1),
                        in-service(2)
                              }
             ACCESS  read-write
             STATUS  mandatory
             DESCRIPTION
          "The variable specifies whether port state is in service or
               not."
            ::= { ncmm13T1ConfigEntry 7 }

	
        
        
 

 
     END
