-- *****************************************************************
--
-- STN-EXTIF.mib:  
--      Spring Tide Networks Extension Interface MIB file.
--
--
--      Copyright (c) 2000 by Spring Tide Networks, Inc.
--                      ALL RIGHTS RESERVED       
--
-- *****************************************************************

-- MIB Object definitions for Spring Tide Network Extension Interface


STN-EXTIF-MIB DEFINITIONS ::= BEGIN

    IMPORTS
        MODULE-IDENTITY,
        OBJECT-TYPE, 
        NOTIFICATION-TYPE, 
        IpAddress,
        Integer32
                FROM SNMPv2-SMI

        DisplayString
                FROM SNMPv2-TC

        MODULE-COMPLIANCE,
        OBJECT-GROUP
                FROM SNMPv2-CONF

        InterfaceIndex
                FROM IF-MIB

        stnExtensions,
        stnNotification
                FROM SPRING-TIDE-NETWORKS-SMI;


    stnExtIf MODULE-IDENTITY
        LAST-UPDATED    "0002160000Z"
        ORGANIZATION    "Spring Tide Networks, Inc."
        CONTACT-INFO
                "
                Spring Tide Networks, Inc.
                Customer Service
                Postal: 3 Clock Tower Place
                        Maynard, MA 01754
                Tel:    1 888-786-4357
                Email:  stncs@springtidenet.com
                "
        DESCRIPTION     "This MIB module describes managed objects of
                         Spring Tide Networks interface extensions."
        ::= { stnExtensions 1 }


    --
    -- Top Level STN Interface Extensions MIB Objects
    --
    stnExtIfObjects        OBJECT IDENTIFIER ::= { stnExtIf 1 }
    stnExtIfMibConformance OBJECT IDENTIFIER ::= { stnExtIf 2 }
    stnExtIfMibTraps       OBJECT IDENTIFIER ::= { stnExtIf 3 }


    --
    -- STN Interface Name / Layer 2 Table
    --

    stnExtIfL2Table OBJECT-TYPE
        SYNTAX		SEQUENCE OF StnExtIfL2Entry
        MAX-ACCESS	not-accessible
        STATUS		current
        DESCRIPTION	"A list of L2 interface entries."
        ::= { stnExtIfObjects 1 }
 
    stnExtIfL2Entry OBJECT-TYPE
        SYNTAX          StnExtIfL2Entry
        MAX-ACCESS      not-accessible
        STATUS          current
        DESCRIPTION     "Entry contains information about a particular L2
			interface."
        INDEX           { stnExtIfL2IfName }
        ::= { stnExtIfL2Table 1 }
 
    StnExtIfL2Entry ::= SEQUENCE {
        stnExtIfL2IfName	DisplayString,
        stnExtIfL2IfIndex	InterfaceIndex
    }

    stnExtIfL2IfName OBJECT-TYPE
        SYNTAX          DisplayString
        MAX-ACCESS      read-only
        STATUS          current
        DESCRIPTION     "The interface name associated with the L2."
        ::= { stnExtIfL2Entry 1 }

    stnExtIfL2IfIndex OBJECT-TYPE
        SYNTAX          InterfaceIndex
        MAX-ACCESS      read-only
        STATUS          current
        DESCRIPTION     "The interface index number associated with the L2 
			interface name."
        ::= { stnExtIfL2Entry 2 }


    --
    -- STN Interface Name / Layer 3 Table
    --

    stnExtIfL3Table OBJECT-TYPE
        SYNTAX		SEQUENCE OF StnExtIfL3Entry
        MAX-ACCESS	not-accessible
        STATUS		current
        DESCRIPTION	"A list of L3 interface entries."
        ::= { stnExtIfObjects 2 }
 
    stnExtIfL3Entry OBJECT-TYPE
        SYNTAX          StnExtIfL3Entry
        MAX-ACCESS      not-accessible
        STATUS          current
        DESCRIPTION     "Entry contains information about a particular L3
			interface."
        INDEX           { stnExtIfL3IfName }
        ::= { stnExtIfL3Table 1 }
 
    StnExtIfL3Entry ::= SEQUENCE {
        stnExtIfL3IfName		        DisplayString,
        stnExtIfL3IfIndex		        InterfaceIndex,
        stnExtIfL3SubnetIfInstance	    Integer32,
        stnExtIfL3IpAddress		        IpAddress,
        stnExtIfL3IpMask		        IpAddress
    }

    stnExtIfL3IfName OBJECT-TYPE
        SYNTAX          DisplayString
        MAX-ACCESS      read-only
        STATUS          current
        DESCRIPTION     "The interface name associated with the L3."
        ::= { stnExtIfL3Entry 1 }

    stnExtIfL3IfIndex OBJECT-TYPE
        SYNTAX          InterfaceIndex
        MAX-ACCESS      read-only
        STATUS          current
        DESCRIPTION     "The interface index number associated with the L3 
			interface name."
        ::= { stnExtIfL3Entry 2 }

    stnExtIfL3SubnetIfInstance OBJECT-TYPE
        SYNTAX          Integer32
        MAX-ACCESS      read-only
        STATUS          current
        DESCRIPTION     "The subnet interface instance associated with the L3 
			interface name."
        ::= { stnExtIfL3Entry 3 }

    stnExtIfL3IpAddress OBJECT-TYPE
        SYNTAX          IpAddress
        MAX-ACCESS      read-only
        STATUS          current
        DESCRIPTION     "The IP address associated with the L3 interface name."
        ::= { stnExtIfL3Entry 4 }

    stnExtIfL3IpMask OBJECT-TYPE
        SYNTAX          IpAddress
        MAX-ACCESS      read-only
        STATUS          current
        DESCRIPTION     "The IP subnet mask associated with the L3 interface 
			name."
        ::= { stnExtIfL3Entry 5 }


    --
    -- STN IP Address / Layer 3 Table
    --

    stnExtIpAddrL3Table OBJECT-TYPE
        SYNTAX		SEQUENCE OF StnExtIpAddrL3Entry
        MAX-ACCESS	not-accessible
        STATUS		current
        DESCRIPTION	"A list of L3 IP address entries."
        ::= { stnExtIfObjects 3 }
 
    stnExtIpAddrL3Entry OBJECT-TYPE
        SYNTAX          StnExtIpAddrL3Entry
        MAX-ACCESS      not-accessible
        STATUS          current
        DESCRIPTION     "Entry contains information about a particular L3
			interface."
        INDEX           { stnExtIpAddrL3IpAddress }
        ::= { stnExtIpAddrL3Table 1 }
 
    StnExtIpAddrL3Entry ::= SEQUENCE {
        stnExtIpAddrL3IpAddress		        IpAddress,
        stnExtIpAddrL3IfIndex		        InterfaceIndex,
        stnExtIpAddrL3SubnetIfInstance	    Integer32,
        stnExtIpAddrL3IfName		        DisplayString,
        stnExtIpAddrL3IpMask		        IpAddress
    }

    stnExtIpAddrL3IpAddress OBJECT-TYPE
        SYNTAX          IpAddress
        MAX-ACCESS      read-only
        STATUS          current
        DESCRIPTION     "The IP address associated with the L3 interface."
        ::= { stnExtIpAddrL3Entry 1 }

    stnExtIpAddrL3IfIndex OBJECT-TYPE
        SYNTAX          InterfaceIndex
        MAX-ACCESS      read-only
        STATUS          current
        DESCRIPTION     "The interface index number associated with the L3 
			interface."
        ::= { stnExtIpAddrL3Entry 2 }

    stnExtIpAddrL3SubnetIfInstance OBJECT-TYPE
        SYNTAX          Integer32
        MAX-ACCESS      read-only
        STATUS          current
        DESCRIPTION     "The subnet interface instance associated with the L3 
			interface."
        ::= { stnExtIpAddrL3Entry 3 }

    stnExtIpAddrL3IfName OBJECT-TYPE
        SYNTAX          DisplayString
        MAX-ACCESS      read-only
        STATUS          current
        DESCRIPTION     "The interface name associated with the L3 interface."
        ::= { stnExtIpAddrL3Entry 4 }

    stnExtIpAddrL3IpMask OBJECT-TYPE
        SYNTAX          IpAddress
        MAX-ACCESS      read-only
        STATUS          current
        DESCRIPTION     "The IP subnet mask associated with the L3 interface."
        ::= { stnExtIpAddrL3Entry 5 }


    --
    -- STN Subnet Interface Instance / Layer 3 Table
    --

    stnExtSubnetL3Table OBJECT-TYPE
        SYNTAX		SEQUENCE OF StnExtSubnetL3Entry
        MAX-ACCESS	not-accessible
        STATUS		current
        DESCRIPTION	"A list of L3 subnet interface entries."
        ::= { stnExtIfObjects 4 }
 
    stnExtSubnetL3Entry OBJECT-TYPE
        SYNTAX          StnExtSubnetL3Entry
        MAX-ACCESS      not-accessible
        STATUS          current
        DESCRIPTION     "Entry contains information about a particular L3
			subnet interface."
        INDEX           { stnExtSubnetL3SubnetIfInstance }
        ::= { stnExtSubnetL3Table 1 }
 
    StnExtSubnetL3Entry ::= SEQUENCE {
        stnExtSubnetL3SubnetIfInstance	Integer32,
        stnExtSubnetL3IfIndex		    InterfaceIndex,
        stnExtSubnetL3IfName		    DisplayString,
        stnExtSubnetL3IpAddress		    IpAddress,
        stnExtSubnetL3IpMask		    IpAddress
    }

    stnExtSubnetL3SubnetIfInstance OBJECT-TYPE
        SYNTAX          Integer32
        MAX-ACCESS      read-only
        STATUS          current
        DESCRIPTION     "The subnet interface instance associated with the L3 
			interface."
        ::= { stnExtSubnetL3Entry 1 }

    stnExtSubnetL3IfIndex OBJECT-TYPE
        SYNTAX          InterfaceIndex
        MAX-ACCESS      read-only
        STATUS          current
        DESCRIPTION     "The interface index number associated with the L3 
			interface."
        ::= { stnExtSubnetL3Entry 2 }

    stnExtSubnetL3IfName OBJECT-TYPE
        SYNTAX          DisplayString
        MAX-ACCESS      read-only
        STATUS          current
        DESCRIPTION     "The interface name associated with the L3 interface."
        ::= { stnExtSubnetL3Entry 3 }

    stnExtSubnetL3IpAddress OBJECT-TYPE
        SYNTAX          IpAddress
        MAX-ACCESS      read-only
        STATUS          current
        DESCRIPTION     "The IP address associated with the L3 interface."
        ::= { stnExtSubnetL3Entry 4 }

    stnExtSubnetL3IpMask OBJECT-TYPE
        SYNTAX          IpAddress
        MAX-ACCESS      read-only
        STATUS          current
        DESCRIPTION     "The IP subnet mask associated with the L3 interface."
        ::= { stnExtSubnetL3Entry 5 }


    --
    -- STN Traps & Notifications 
    --


    --
    -- Conformance Information
    --


END
