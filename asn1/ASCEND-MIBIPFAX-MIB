--			Ascend mibipfax MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBIPFAX-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibipFaxProfile  OBJECT IDENTIFIER ::= { configuration 84}

	-- The mibipFaxProfile table
	--
	-- This table contains parameters for the mibipFaxProfile profile
	--

    mibipFaxProfileTable	OBJECT-TYPE
	SYNTAX		SEQUENCE OF MibipFaxProfileEntry
	ACCESS		not-accessible
	STATUS		mandatory
	DESCRIPTION	"A list of mibipFaxProfile profile entries."
	::= { mibipFaxProfile 1 }

    mibipFaxProfileEntry	OBJECT-TYPE
	SYNTAX		MibipFaxProfileEntry
	ACCESS		not-accessible
	STATUS		mandatory
	DESCRIPTION	"A mibipFaxProfile entry containing objects that
			 maps to the parameters of mibipFaxProfile profile."
	INDEX		{ ipFaxProfile-Index-o }
	::= { mibipFaxProfileTable 1 }

    MibipFaxProfileEntry ::=
	SEQUENCE {
	    ipFaxProfile-Index-o
		INTEGER,
	    ipFaxProfile-IpFaxEnabled
		INTEGER,
	    ipFaxProfile-OutgoingFaxPort
		INTEGER,
	    ipFaxProfile-ServerLogin
		DisplayString,
	    ipFaxProfile-DialerType
		INTEGER,
	    ipFaxProfile-ServerPassword
		DisplayString,
	    ipFaxProfile-IncomingFaxPort
		INTEGER,
	    ipFaxProfile-AllCallsAreFax
		INTEGER,
	    ipFaxProfile-FaxIncomingCallType
		INTEGER,
	    ipFaxProfile-Action-o
		INTEGER
	}

    ipFaxProfile-Index-o	OBJECT-TYPE
	SYNTAX	INTEGER
	ACCESS	read-only
	STATUS	mandatory
	DESCRIPTION	""
	::= { mibipFaxProfileEntry 1 }

    ipFaxProfile-IpFaxEnabled	OBJECT-TYPE
	SYNTAX	INTEGER {
		    no (1),
		    yes (2)
		}
	ACCESS	read-write
	STATUS	mandatory
	DESCRIPTION	"Enable IP Fax on this box ?"
	::= { mibipFaxProfileEntry 2 }

    ipFaxProfile-OutgoingFaxPort	OBJECT-TYPE
	SYNTAX	INTEGER
	ACCESS	read-write
	STATUS	mandatory
	DESCRIPTION	"TCP Port Number to listen on"
	::= { mibipFaxProfileEntry 3 }

    ipFaxProfile-ServerLogin	OBJECT-TYPE
	SYNTAX	DisplayString
	ACCESS	read-write
	STATUS	mandatory
	DESCRIPTION	"Login name from Fax Server."
	::= { mibipFaxProfileEntry 4 }

    ipFaxProfile-DialerType	OBJECT-TYPE
	SYNTAX	INTEGER {
		    mitel (1),
		    atlas (2)
		}
	ACCESS	read-write
	STATUS	mandatory
	DESCRIPTION	"Set type of dialer use for incoming fax call."
	::= { mibipFaxProfileEntry 5 }

    ipFaxProfile-ServerPassword	OBJECT-TYPE
	SYNTAX	DisplayString
	ACCESS	read-write
	STATUS	mandatory
	DESCRIPTION	"Password from Fax Server."
	::= { mibipFaxProfileEntry 6 }

    ipFaxProfile-IncomingFaxPort	OBJECT-TYPE
	SYNTAX	INTEGER
	ACCESS	read-write
	STATUS	mandatory
	DESCRIPTION	"Port Number for Fax Server."
	::= { mibipFaxProfileEntry 7 }

    ipFaxProfile-AllCallsAreFax	OBJECT-TYPE
	SYNTAX	INTEGER {
		    no (1),
		    yes (2)
		}
	ACCESS	read-write
	STATUS	mandatory
	DESCRIPTION	"Enable IP Fax DNIS on incoming calls."
	::= { mibipFaxProfileEntry 8 }

    ipFaxProfile-FaxIncomingCallType	OBJECT-TYPE
	SYNTAX	INTEGER {
		    redialer (1),
		    did (2)
		}
	ACCESS	read-write
	STATUS	mandatory
	DESCRIPTION	"Set type of incoming fax call."
	::= { mibipFaxProfileEntry 9 }

    ipFaxProfile-Action-o	OBJECT-TYPE
	SYNTAX	INTEGER {
		    noAction (1),
		    createProfile (2),
		    deleteProfile (3)
		}
	ACCESS	read-write
	STATUS	mandatory
	DESCRIPTION	""
	::= { mibipFaxProfileEntry 10 }


	-- The mibipFaxProfile__fax_servers table
	--
	-- This table contains parameters for the mibipFaxProfile__fax_servers profile
	--

    mibipFaxProfile-FaxServersTable	OBJECT-TYPE
	SYNTAX		SEQUENCE OF MibipFaxProfile-FaxServersEntry
	ACCESS		not-accessible
	STATUS		mandatory
	DESCRIPTION	"A list of mibipFaxProfile__fax_servers profile entries."
	::= { mibipFaxProfile 2 }

    mibipFaxProfile-FaxServersEntry	OBJECT-TYPE
	SYNTAX		MibipFaxProfile-FaxServersEntry
	ACCESS		not-accessible
	STATUS		mandatory
	DESCRIPTION	"A mibipFaxProfile__fax_servers entry containing objects that
			 maps to the parameters of mibipFaxProfile__fax_servers profile."
	INDEX		{ ipFaxProfile-FaxServers-Index-o, ipFaxProfile-FaxServers-Index1-o }
	::= { mibipFaxProfile-FaxServersTable 1 }

    MibipFaxProfile-FaxServersEntry ::=
	SEQUENCE {
	    ipFaxProfile-FaxServers-Index-o
		INTEGER,
	    ipFaxProfile-FaxServers-Index1-o
		INTEGER,
	    ipFaxProfile-FaxServers
		IpAddress
	}

    ipFaxProfile-FaxServers-Index-o	OBJECT-TYPE
	SYNTAX	INTEGER
	ACCESS	read-only
	STATUS	mandatory
	DESCRIPTION	""
	::= { mibipFaxProfile-FaxServersEntry 1 }

    ipFaxProfile-FaxServers-Index1-o	OBJECT-TYPE
	SYNTAX	INTEGER
	ACCESS	read-only
	STATUS	mandatory
	DESCRIPTION	""
	::= { mibipFaxProfile-FaxServersEntry 2 }

    ipFaxProfile-FaxServers	OBJECT-TYPE
	SYNTAX	IpAddress
	ACCESS	read-write
	STATUS	mandatory
	DESCRIPTION	"Fax Server addresses"
	::= { mibipFaxProfile-FaxServersEntry 3 }


	-- The mibipFaxProfile__fax_did table
	--
	-- This table contains parameters for the mibipFaxProfile__fax_did profile
	--

    mibipFaxProfile-FaxDidTable	OBJECT-TYPE
	SYNTAX		SEQUENCE OF MibipFaxProfile-FaxDidEntry
	ACCESS		not-accessible
	STATUS		mandatory
	DESCRIPTION	"A list of mibipFaxProfile__fax_did profile entries."
	::= { mibipFaxProfile 3 }

    mibipFaxProfile-FaxDidEntry	OBJECT-TYPE
	SYNTAX		MibipFaxProfile-FaxDidEntry
	ACCESS		not-accessible
	STATUS		mandatory
	DESCRIPTION	"A mibipFaxProfile__fax_did entry containing objects that
			 maps to the parameters of mibipFaxProfile__fax_did profile."
	INDEX		{ ipFaxProfile-FaxDid-Index-o, ipFaxProfile-FaxDid-Index1-o }
	::= { mibipFaxProfile-FaxDidTable 1 }

    MibipFaxProfile-FaxDidEntry ::=
	SEQUENCE {
	    ipFaxProfile-FaxDid-Index-o
		INTEGER,
	    ipFaxProfile-FaxDid-Index1-o
		INTEGER,
	    ipFaxProfile-FaxDid
		DisplayString
	}

    ipFaxProfile-FaxDid-Index-o	OBJECT-TYPE
	SYNTAX	INTEGER
	ACCESS	read-only
	STATUS	mandatory
	DESCRIPTION	""
	::= { mibipFaxProfile-FaxDidEntry 1 }

    ipFaxProfile-FaxDid-Index1-o	OBJECT-TYPE
	SYNTAX	INTEGER
	ACCESS	read-only
	STATUS	mandatory
	DESCRIPTION	""
	::= { mibipFaxProfile-FaxDidEntry 2 }

    ipFaxProfile-FaxDid	OBJECT-TYPE
	SYNTAX	DisplayString
	ACCESS	read-write
	STATUS	mandatory
	DESCRIPTION	"List of DID Numbers for IP Fax facility."
	::= { mibipFaxProfile-FaxDidEntry 3 }


	-- The mibipFaxProfile__fax_dnis table
	--
	-- This table contains parameters for the mibipFaxProfile__fax_dnis profile
	--

    mibipFaxProfile-FaxDnisTable	OBJECT-TYPE
	SYNTAX		SEQUENCE OF MibipFaxProfile-FaxDnisEntry
	ACCESS		not-accessible
	STATUS		mandatory
	DESCRIPTION	"A list of mibipFaxProfile__fax_dnis profile entries."
	::= { mibipFaxProfile 4 }

    mibipFaxProfile-FaxDnisEntry	OBJECT-TYPE
	SYNTAX		MibipFaxProfile-FaxDnisEntry
	ACCESS		not-accessible
	STATUS		mandatory
	DESCRIPTION	"A mibipFaxProfile__fax_dnis entry containing objects that
			 maps to the parameters of mibipFaxProfile__fax_dnis profile."
	INDEX		{ ipFaxProfile-FaxDnis-Index-o, ipFaxProfile-FaxDnis-Index1-o }
	::= { mibipFaxProfile-FaxDnisTable 1 }

    MibipFaxProfile-FaxDnisEntry ::=
	SEQUENCE {
	    ipFaxProfile-FaxDnis-Index-o
		INTEGER,
	    ipFaxProfile-FaxDnis-Index1-o
		INTEGER,
	    ipFaxProfile-FaxDnis
		DisplayString
	}

    ipFaxProfile-FaxDnis-Index-o	OBJECT-TYPE
	SYNTAX	INTEGER
	ACCESS	read-only
	STATUS	mandatory
	DESCRIPTION	""
	::= { mibipFaxProfile-FaxDnisEntry 1 }

    ipFaxProfile-FaxDnis-Index1-o	OBJECT-TYPE
	SYNTAX	INTEGER
	ACCESS	read-only
	STATUS	mandatory
	DESCRIPTION	""
	::= { mibipFaxProfile-FaxDnisEntry 2 }

    ipFaxProfile-FaxDnis	OBJECT-TYPE
	SYNTAX	DisplayString
	ACCESS	read-write
	STATUS	mandatory
	DESCRIPTION	"Dialed Number for IP Fax facility."
	::= { mibipFaxProfile-FaxDnisEntry 3 }

END
