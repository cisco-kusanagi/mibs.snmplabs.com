--
     -- (c) 1996, 1999 VERITAS Software, Corp.  All rights reserved.
     --
     -- SNMP Console support for Backup Exec for NT and NetWare
     --
     -- VERITAS Software: 1.3.6.1.4.1.1302
     --
     -- Note that not all Backup Exec products support all of
     -- the definitions supplied in this MIB.
     --
     -- $Revision:   2.7  $
     -- $Date:   25 Apr 2001 16:31:14  $
     --
     --
     -- 1302 - veritassoftware
     --        .1 - backupExecNetWare
     --        .3 - products
     --             .1 - backupexec
     --                  .1 - beconfig
     --                  .2 - bejobs
     --                  .4 - bemodules
     --                       .1 - labs
     --                       .2 - disasterrecovery
     --                       .3 - openfileoption
     --                  .5 - nonspecifictraps
     --                       .1 - pvldevice
     --                       .2 - pvlmedia
     --                       .3 - catalog
     --                       .4 - tapealert
     --                       .5 - databasemaint
     --                       .6 - softwareupdate
     --                       .7 - install
     --             .2 - devices
     --                  .4 - loader
     --                  .5 - tape
     --             .3 - trapvars
     --
     -- Traps
     -- -----
     -- 1302.1         : #1 Session Blocked
     --                : #2 Error
     --                : #3 Scheduler Offline
     --                : #4 Warning
     --                : #5 Information
     -- 1302.3.1.1.9   : #1 App Start
     --                : #2 App Stop
     --                : #3 System Error
     --                : #4 General Information
     -- 1302.3.1.2.8   : #1 Job Failed
     --                : #2 Job Aborted
     --                : #3 Job Success
     --                : #4 Job Success with exceptions
     --                : #5 Job Started
     --                : #6 Job Completed with no data
     --                : #7 Job Warning
     -- 1302.3.1.4.1.1 : #1 LABS needs multiple tapes
     --                : #2 LABS retried
     -- 1302.3.1.4.2.1 : #1 IDR incomplete
     --                : #2 IDR completed full backup
     -- 1302.3.1.4.3.1 : #1 OFO failed
     --                : #2 OFO Couldn't init
     -- 1302.3.1.5.1.1 : #1 PVL Device Error
	 --				   : #2 PVL Device Warning
	 --				   : #3 PVL Device Information
	 --				   : #4 PVL Device Intervention
     -- 1302.3.1.5.2.1 : #1 PVL Media Error
	 --				   : #2 PVL Media Warning
	 --				   : #3 PVL Media Information
	 --				   : #4 PVL Media Intervention
     -- 1302.3.1.5.3.1 : #1 Catalog Error
     -- 1302.3.1.5.4.1 : #1 Tape Alert Error
	 --				   : #2 Tape Alert Warning
	 --				   : #3 Tape Alert Information
     -- 1302.3.2.5.5.1 : #1 Database Maintenance Error
      --                    : #2 Database Maintenance Warning
     -- 1302.3.2.5.6.1 : #1 Software Update Error
      --                    : #2 Software Update Warning
      --                    : #3 Software Update Information
     -- 1302.3.2.5.7.1 : #1 Software Update Warning
      --                    : #2 Software Update Information

     -- 1302.3.2.4.3   : #3 Loader needs attention
     -- 1302.3.2.5.3   : #3 Tape drive needs attention
     --

     Backup-Exec-MIB DEFINITIONS ::= BEGIN

     IMPORTS
          enterprises
               FROM RFC1155-SMI
          OBJECT-TYPE
               FROM RFC-1212
          TRAP-TYPE
               FROM RFC-1215
          DisplayString
               FROM RFC1213-MIB;
     
     veritassoftware     OBJECT IDENTIFIER ::= { enterprises 1302 }
     backupExecNetWare   OBJECT IDENTIFIER ::= { veritassoftware 1 }
     products            OBJECT IDENTIFIER ::= { veritassoftware 3 }
     backupexec          OBJECT IDENTIFIER ::= { products 1 }
     devices             OBJECT IDENTIFIER ::= { products 2 }
     trapvars            OBJECT IDENTIFIER ::= { products 3 }
     beconfig            OBJECT IDENTIFIER ::= { backupexec 1 }
     bejobs              OBJECT IDENTIFIER ::= { backupexec 2 }
     beinfo              OBJECT IDENTIFIER ::= { backupexec 3 }
     bemodules           OBJECT IDENTIFIER ::= { backupexec 4 }
     nonspecifictraps    OBJECT IDENTIFIER ::= { backupexec 5 }
     loader              OBJECT IDENTIFIER ::= { devices 4 }
     tape                OBJECT IDENTIFIER ::= { devices 5 }
     labs                OBJECT IDENTIFIER ::= { bemodules 1 }
     disasterrecovery    OBJECT IDENTIFIER ::= { bemodules 2 }
     openfileoption      OBJECT IDENTIFIER ::= { bemodules 3 }
     pvldevice           OBJECT IDENTIFIER ::= { nonspecifictraps 1 }
     pvlmedia            OBJECT IDENTIFIER ::= { nonspecifictraps 2 }
	catalog             OBJECT IDENTIFIER ::= { nonspecifictraps 3 }
     tapealert           OBJECT IDENTIFIER ::= { nonspecifictraps 4 }
     databasemaint       OBJECT IDENTIFIER ::= { nonspecifictraps 5 }
     softwareupdate      OBJECT IDENTIFIER ::= { nonspecifictraps 6 }
     install             OBJECT IDENTIFIER ::= { nonspecifictraps 7 }

--
--   Trap Variables Section
--

     serverName     OBJECT-TYPE
          SYNTAX    DisplayString
          ACCESS    read-only
          STATUS    mandatory
          DESCRIPTION
               "Server on which this product is running."
          ::= { trapvars 1 }
     
     appInfo        OBJECT-TYPE
          SYNTAX    DisplayString
          ACCESS    read-only
          STATUS    mandatory
          DESCRIPTION
               "Product name and version information."
          ::= { trapvars 2 }
     
     jobName        OBJECT-TYPE
          SYNTAX    DisplayString
          ACCESS    read-only
          STATUS    mandatory
          DESCRIPTION
               "The name of the job."
          ::= { trapvars 3 }
     
     operatorName   OBJECT-TYPE
          SYNTAX    DisplayString
          ACCESS    read-only
          STATUS    mandatory
          DESCRIPTION
               "User account which caused the event."
          ::= { trapvars 4 }
     
     messageText    OBJECT-TYPE
          SYNTAX    DisplayString
          ACCESS    read-only
          STATUS    mandatory
          DESCRIPTION
               "Description of the event."
          ::= { trapvars 5 }
     
     additionalText OBJECT-TYPE
          SYNTAX    DisplayString
          ACCESS    read-only
          STATUS    mandatory
          DESCRIPTION
               "Additional information about the event, if available." 
          ::= { trapvars 6 }
     

--
--  Backup Exec Section
--

--   Configuration Group
     
     backupExecNTGeneral  OBJECT IDENTIFIER ::= { beconfig 9 }

     beNTLoaded    TRAP-TYPE
          ENTERPRISE     backupExecNTGeneral
          VARIABLES { messageText, serverName, appInfo }
          DESCRIPTION
               "The application has started."
          --#TYPE      "No action required"
          --#SUMMARY   "%s"
          --#ARGUMENTS {0}
          --#SEVERITY  INFORMATIONAL
          --#TIMEINDEX 1        
          --#STATE     OPERATIONAL
          ::= 1

     beNTUnloaded     TRAP-TYPE
          ENTERPRISE     backupExecNTGeneral
          VARIABLES { messageText, serverName, appInfo }
          DESCRIPTION
               "The application has stopped."
          --#TYPE      "User is advised to take action"
          --#SUMMARY   "%s"
          --#ARGUMENTS {0}
          --#SEVERITY  MINOR
          --#TIMEINDEX 1        
          --#STATE     DEGRADED
          ::= 2
     

     beNTSystemError  TRAP-TYPE
          ENTERPRISE     backupExecNTGeneral
          VARIABLES { messageText, serverName, additionalText }
          DESCRIPTION
               "The application has encountered an error."
          --#TYPE      "User is advised to take action"
          --#SUMMARY   "%s %s"
          --#ARGUMENTS {0,2}
          --#SEVERITY  MAJOR
          --#TIMEINDEX 1        
          --#STATE     DEGRADED
          ::= 3
     

     beNTGeneralInfo  TRAP-TYPE
          ENTERPRISE     backupExecNTGeneral
          VARIABLES { messageText, serverName, additionalText }
          DESCRIPTION
               "Information on normal events."
          --#TYPE      "No action required"
          --#SUMMARY   "%s %s"
          --#ARGUMENTS {0,2}
          --#SEVERITY  INFORMATIONAL
          --#TIMEINDEX 1        
          --#STATE     OPERATIONAL
          ::= 4
     

--   Jobs Group

     backupExecNTJobs   OBJECT IDENTIFIER ::= { bejobs 8 }

     jobFailure             TRAP-TYPE
          ENTERPRISE     backupExecNTJobs
          VARIABLES { messageText, serverName, jobName, additionalText }
          DESCRIPTION
               "The Job failed."
          --#TYPE      "User advised to take action"
          --#SUMMARY   "%s Job:%s %s"
          --#ARGUMENTS {0,2,3}
          --#SEVERITY  MINOR
          --#TIMEINDEX 1        
          --#STATE     OPERATIONAL
          ::= 1

     jobAborted              TRAP-TYPE
          ENTERPRISE     backupExecNTJobs
          VARIABLES { messageText, serverName, jobName, operatorName }
          DESCRIPTION
               "The Job was canceled."
          --#TYPE      "User advised of event"
          --#SUMMARY   "%s Job:%s Canceled by:%s"
          --#ARGUMENTS {0,2,3}
          --#SEVERITY  MINOR
          --#TIMEINDEX 1        
          --#STATE     OPERATIONAL
          ::= 2

     jobSuccess            TRAP-TYPE
          ENTERPRISE     backupExecNTJobs
          VARIABLES { messageText, serverName, jobName, additionalText }
          DESCRIPTION
               "The Job succeeded."
          --#TYPE      "No action required"
          --#SUMMARY   "%s Job:%s %s"
          --#ARGUMENTS {0,2,3}
          --#SEVERITY  INFORMATIONAL
          --#TIMEINDEX 1        
          --#STATE     OPERATIONAL
          ::= 3

     jobSuccessExcept      TRAP-TYPE
          ENTERPRISE     backupExecNTJobs
          VARIABLES { messageText, serverName, jobName, additionalText }
          DESCRIPTION
               "The Job succeeded, but there was a problem."
          --#TYPE      "User advised of event"
          --#SUMMARY   "%s Job:%s %s"
          --#ARGUMENTS {0,2,3}
          --#SEVERITY  MINOR
          --#TIMEINDEX 1        
          --#STATE     OPERATIONAL
          ::= 4

     jobStarted         TRAP-TYPE
          ENTERPRISE     backupExecNTJobs
          VARIABLES { messageText, serverName, jobName, additionalText }
          DESCRIPTION
               "The Job has started."
          --#TYPE      "User advised of event"
          --#SUMMARY   "%s Job:%s %s"
          --#ARGUMENTS {0,2,3}
          --#SEVERITY  INFORMATIONAL
          --#TIMEINDEX 1        
          --#STATE     OPERATIONAL
          ::= 5

     jobNoData     TRAP-TYPE
          ENTERPRISE     backupExecNTJobs
          VARIABLES { messageText }
          DESCRIPTION
               "The job succeeded, but there was no data."
          --#TYPE      "No action required"
          --#SUMMARY   "%s"
          --#ARGUMENTS {0}
          --#SEVERITY  INFORMATIONAL
          --#TIMEINDEX 1        
          --#STATE     OPERATIONAL
          ::= 6

     jobWarning    TRAP-TYPE
          ENTERPRISE     backupExecNTJobs
          VARIABLES { messageText }
          DESCRIPTION
               "The job has a warning."
          --#TYPE      "User advised of event"
          --#SUMMARY   "%s"
          --#ARGUMENTS {0}
          --#SEVERITY  MINOR
          --#TIMEINDEX 1        
          --#STATE     OPERATIONAL
          ::= 7

--
--  BE Info Section
--

     beName OBJECT-TYPE
          SYNTAX DisplayString (SIZE (0..255))
          ACCESS read-only
          STATUS mandatory
          DESCRIPTION
                "Backup Exec product name."
          ::= { beinfo 1 }

     revMajor OBJECT-TYPE
          SYNTAX INTEGER (0..255)
          ACCESS read-only
          STATUS mandatory
          DESCRIPTION
                "The Backup Exec major revision level."
          ::= { beinfo 2 }

     revMinor OBJECT-TYPE
          SYNTAX INTEGER (0..255)
          ACCESS read-only
          STATUS mandatory
          DESCRIPTION
                "The Backup Exec minor revision level."
          ::= { beinfo 3 }

     beBuild OBJECT-TYPE
          SYNTAX INTEGER (0..255)
          ACCESS read-only
          STATUS mandatory
          DESCRIPTION
                "The Backup Exec build number."
          ::= { beinfo 4 }

     beSerial OBJECT-TYPE
          SYNTAX DisplayString (SIZE (0..255))
          ACCESS read-only
          STATUS mandatory
          DESCRIPTION
                "Backup Exec serial number."
          ::= { beinfo 5 }

--
--  Modules Section
--

--   LABS Group

     backupExecOptLABS     OBJECT IDENTIFIER ::= { labs 1 }

     multipleTapesNeeded    TRAP-TYPE
          ENTERPRISE     backupExecOptLABS
          VARIABLES { messageText, serverName, jobName, additionalText }
          DESCRIPTION
               "Media for Low Administration Backup jobs will need to be
                replaced more frequently."
          --#TYPE      "User advised of event"
          --#SUMMARY   "%s Job:%s %s"
          --#ARGUMENTS {0,2,3}
          --#SEVERITY  INFORMATIONAL
          --#TIMEINDEX 1        
          --#STATE     OPERATIONAL
          ::= 1

     retriedAutomatically   TRAP-TYPE
          ENTERPRISE     backupExecOptLABS
          VARIABLES { messageText, serverName, jobName, additionalText }
          DESCRIPTION
               "The failed Low Administration Backup job has caused an
                additional medium to be used.  The Low Administration media
                group will need to be replaced sooner than scheduled."
          --#TYPE      "User advised of event"
          --#SUMMARY   "%s Job:%s %s"
          --#ARGUMENTS {0,2,3}
          --#SEVERITY  MINOR
          --#TIMEINDEX 1        
          --#STATE     OPERATIONAL
          ::= 2


--   Disaster Recovery Group

     backupExecOptIDR      OBJECT IDENTIFIER ::= { disasterrecovery 1 }

     copyDRFile    TRAP-TYPE
          ENTERPRISE     backupExecOptIDR
          VARIABLES { messageText, serverName, jobName, additionalText }
          DESCRIPTION
               "Disaster Recovery is not complete.  Update the Disaster
                Recovery diskettes or manually copy Disaster Recovery file,
                (servername).dr, found in the Disaster Recovery directory,
                to the alternate path."
          --#TYPE      "Take action immediately"
          --#SUMMARY   "%s Job:%s %s"
          --#ARGUMENTS {0,2,3}
          --#SEVERITY  MAJOR
          --#TIMEINDEX 1        
          --#STATE     OPERATIONAL
          ::= 1

     fullBackupComplete      TRAP-TYPE
          ENTERPRISE     backupExecOptIDR
          VARIABLES { messageText, serverName, jobName, additionalText }
          DESCRIPTION
               "Disaster Recovery has completed a full backup.  It is necessary
                now to update the disaster recovery disks in order to keep them
                current."
          --#TYPE      "User advised to take action"
          --#SUMMARY   "%s Job:%s %s"
          --#ARGUMENTS {0,2,3}
          --#SEVERITY  INFORMATIONAL
          --#TIMEINDEX 1        
          --#STATE     OPERATIONAL
          ::= 2


--   Open File Option Group

     backupExecOptOFO    OBJECT IDENTIFIER ::= { openfileoption 1 }

     ofoFailed        TRAP-TYPE
          ENTERPRISE     backupExecOptOFO
          VARIABLES { messageText, serverName, jobName, additionalText }
          DESCRIPTION
               "The Advanced Open File Option was unable to backup the selected resource."
          --#TYPE      "User advised to take action"
          --#SUMMARY   "%s Job:%s %s"
          --#ARGUMENTS {0,2,3}
          --#SEVERITY  MAJOR
          --#TIMEINDEX 1        
          --#STATE     OPERATIONAL
          ::= 1

     ofoCouldNotInit        TRAP-TYPE
          ENTERPRISE     backupExecOptOFO
          VARIABLES { messageText, serverName, jobName, additionalText }
          DESCRIPTION
               "The Advanced Open File Option was unable to initialize.  The resource is
                being backed up using normal backup methods."
          --#TYPE      "User advised to take action"
          --#SUMMARY   "%s Job:%s %s"
          --#ARGUMENTS {0,2,3}
          --#SEVERITY  MAJOR
          --#TIMEINDEX 1        
          --#STATE     OPERATIONAL
          ::= 2

--
--  nonspecific traps Section
--

--   pvldevice Group

     backupExecPVLDevice   OBJECT IDENTIFIER ::= { pvldevice 1 }

     pvlDeviceError   TRAP-TYPE
          ENTERPRISE     backupExecPVLDevice
          VARIABLES { messageText }
          DESCRIPTION
               "The device has encountered an error."
          --#TYPE      "User is advised to take action"
          --#SUMMARY   "%s"
          --#ARGUMENTS {0}
          --#SEVERITY  MINOR
          --#TIMEINDEX 1        
          --#STATE     DEGRADED
          ::= 1

     pvlDeviceWarning TRAP-TYPE
          ENTERPRISE     backupExecPVLDevice
          VARIABLES { messageText }
          DESCRIPTION
               "The device has encountered a warning."
          --#TYPE      "User advised of event"
          --#SUMMARY   "%s"
          --#ARGUMENTS {0}
          --#SEVERITY  MINOR
          --#TIMEINDEX 1        
          --#STATE     OPERATIONAL
          ::= 2

     pvlDeviceInfo    TRAP-TYPE
          ENTERPRISE     backupExecPVLDevice
          VARIABLES { messageText }
          DESCRIPTION
               "Normal device information."
          --#TYPE      "No action required"
          --#SUMMARY   "%s"
          --#ARGUMENTS {0}
          --#SEVERITY  INFORMATIONAL
          --#TIMEINDEX 1        
          --#STATE     OPERATIONAL
          ::= 3

     pvlDeviceAttn    TRAP-TYPE
          ENTERPRISE     backupExecPVLDevice
          VARIABLES { messageText }
          DESCRIPTION
               "Device requires attention."
          --#TYPE      "Take action immediately"
          --#SUMMARY   "%s"
          --#ARGUMENTS {0}
          --#SEVERITY  MAJOR
          --#TIMEINDEX 1        
          --#STATE     DEGRADED
          ::= 4


--   pvlmedia Group

     backupExecPVLMedia   OBJECT IDENTIFIER ::= { pvlmedia 1 }

     pvlMediaError    TRAP-TYPE
          ENTERPRISE     backupExecPVLMedia
          VARIABLES { messageText }
          DESCRIPTION
               "There is an error with the media."
          --#TYPE      "User is advised to take action"
          --#SUMMARY   "%s"
          --#ARGUMENTS {0}
          --#SEVERITY  MINOR
          --#TIMEINDEX 1        
          --#STATE     DEGRADED
          ::= 1

     pvlMediaWarning  TRAP-TYPE
          ENTERPRISE     backupExecPVLMedia
          VARIABLES { messageText }
          DESCRIPTION
               "There may be a problem with the media."
          --#TYPE      "User advised of event"
          --#SUMMARY   "%s"
          --#ARGUMENTS {0}
          --#SEVERITY  MINOR
          --#TIMEINDEX 1        
          --#STATE     OPERATIONAL
          ::= 2

     pvlMediaInfo     TRAP-TYPE
          ENTERPRISE     backupExecPVLMedia
          VARIABLES { messageText }
          DESCRIPTION
               "Normal media information."
          --#TYPE      "No action required"
          --#SUMMARY   "%s"
          --#ARGUMENTS {0}
          --#SEVERITY  INFORMATIONAL
          --#TIMEINDEX 1        
          --#STATE     OPERATIONAL
          ::= 3

     pvlMediaAttn     TRAP-TYPE
          ENTERPRISE     backupExecPVLMedia
          VARIABLES { messageText }
          DESCRIPTION
               "Media requires attention."
          --#TYPE      "Take action immediately"
          --#SUMMARY   "%s"
          --#ARGUMENTS {0}
          --#SEVERITY  MAJOR
          --#TIMEINDEX 1        
          --#STATE     DEGRADED
          ::= 4

--   Catalog Group

     backupExecCatalog    OBJECT IDENTIFIER ::= { catalog 1 }

     catalogFailed        TRAP-TYPE
          ENTERPRISE     backupExecCatalog
          VARIABLES { messageText }
          DESCRIPTION
               "There is an error with the catalogs."
          --#TYPE      "User advised to take action"
          --#SUMMARY   "%s"
          --#ARGUMENTS {0}
          --#SEVERITY  MAJOR
          --#TIMEINDEX 1        
          --#STATE     OPERATIONAL
          ::= 1


--
--  TapeAlert Traps
--
--  Note that these are not the actual TapeAlert traps, but
--  centralized traps to denote that specific TapeAlert traps have occurred.
--
     backupExecTapeAlert    OBJECT IDENTIFIER ::= { tapealert 1 }

     tapeAlertError   TRAP-TYPE
          ENTERPRISE     backupExecTapeAlert
          VARIABLES { messageText }
          DESCRIPTION
               "There is a TapeAlert error."
          --#TYPE      "User is advised to take action"
          --#SUMMARY   "%s"
          --#ARGUMENTS {0}
          --#SEVERITY  MINOR
          --#TIMEINDEX 1        
          --#STATE     DEGRADED
          ::= 1

     tapeAlertWarning TRAP-TYPE
          ENTERPRISE     backupExecTapeAlert
          VARIABLES { messageText }
          DESCRIPTION
               "There is a TapeAlert warning."
          --#TYPE      "User advised of event"
          --#SUMMARY   "%s"
          --#ARGUMENTS {0}
          --#SEVERITY  MINOR
          --#TIMEINDEX 1        
          --#STATE     OPERATIONAL
          ::= 2

     tapeAlertInfo    TRAP-TYPE
          ENTERPRISE     backupExecTapeAlert
          VARIABLES { messageText }
          DESCRIPTION
               "Normal TapeAlert information."
          --#TYPE      "No action required"
          --#SUMMARY   "%s"
          --#ARGUMENTS {0}
          --#SEVERITY  INFORMATIONAL
          --#TIMEINDEX 1        
          --#STATE     OPERATIONAL
          ::= 3



--
--  Database Maintenance Traps
--
     backupExecDatabaseMaintenance    OBJECT IDENTIFIER ::= { databasemaint 1 }

     databaseMaintenanceError   TRAP-TYPE
          ENTERPRISE     backupExecDatabaseMaintenance
          VARIABLES { messageText }
          DESCRIPTION
               "There is a database maintenance error."
          --#TYPE      "User is advised to take action"
          --#SUMMARY   "%s"
          --#ARGUMENTS {0}
          --#SEVERITY  MINOR
          --#TIMEINDEX 1        
          --#STATE     DEGRADED
          ::= 1

     databaseMaintenanceInfo    TRAP-TYPE
          ENTERPRISE     backupExecDatabaseMaintenance
          VARIABLES { messageText }
          DESCRIPTION
               "Normal database maintenance information."
          --#TYPE      "No action required"
          --#SUMMARY   "%s"
          --#ARGUMENTS {0}
          --#SEVERITY  INFORMATIONAL
          --#TIMEINDEX 1        
          --#STATE     OPERATIONAL
          ::= 2



--
--  Software Update Traps
--
     backupExecSoftwareUpdate    OBJECT IDENTIFIER ::= { softwareupdate 1 }

     softwareUpdateError   TRAP-TYPE
          ENTERPRISE     backupExecSoftwareUpdate
          VARIABLES { messageText }
          DESCRIPTION
               "There is a software update error."
          --#TYPE      "User is advised to take action"
          --#SUMMARY   "%s"
          --#ARGUMENTS {0}
          --#SEVERITY  MINOR
          --#TIMEINDEX 1        
          --#STATE     DEGRADED
          ::= 1
     
     softwareUpdateWarning TRAP-TYPE
          ENTERPRISE     backupExecSoftwareUpdate
          VARIABLES { messageText }
          DESCRIPTION
               "There is a software update warning."
          --#TYPE      "User advised of event"
          --#SUMMARY   "%s"
          --#ARGUMENTS {0}
          --#SEVERITY  MINOR
          --#TIMEINDEX 1        
          --#STATE     OPERATIONAL
          ::= 2

     softwareUpdateInfo    TRAP-TYPE
          ENTERPRISE     backupExecSoftwareUpdate
          VARIABLES { messageText }
          DESCRIPTION
               "Normal software update information."
          --#TYPE      "No action required"
          --#SUMMARY   "%s"
          --#ARGUMENTS {0}
          --#SEVERITY  INFORMATIONAL
          --#TIMEINDEX 1        
          --#STATE     OPERATIONAL
          ::= 3




--
--  Install Traps
--
     backupExecInstall    OBJECT IDENTIFIER ::= { install 1 }
     
     installWarning TRAP-TYPE
          ENTERPRISE     backupExecInstall
          VARIABLES { messageText }
          DESCRIPTION
               "There is an install warning."
          --#TYPE      "User advised of event"
          --#SUMMARY   "%s"
          --#ARGUMENTS {0}
          --#SEVERITY  MINOR
          --#TIMEINDEX 1        
          --#STATE     OPERATIONAL
          ::= 1

     installInfo    TRAP-TYPE
          ENTERPRISE     backupExecInstall
          VARIABLES { messageText }
          DESCRIPTION
               "Normal install information."
          --#TYPE      "No action required"
          --#SUMMARY   "%s"
          --#ARGUMENTS {0}
          --#SEVERITY  INFORMATIONAL
          --#TIMEINDEX 1        
          --#STATE     OPERATIONAL
          ::= 2


--
--  Devices Section
--

--   Loader Group

     backupExecNTLoader    OBJECT IDENTIFIER ::= { loader 3 }
     
     loaderNeedsAttention  TRAP-TYPE
          ENTERPRISE     backupExecNTLoader
          VARIABLES { messageText, serverName, jobName, additionalText }
          DESCRIPTION
               "Loader needs human intervention."
          --#TYPE      "Take action immediately"
          --#SUMMARY   "%s Job:%s %s"
          --#ARGUMENTS {0,2,3}
          --#SEVERITY  MAJOR
          --#TIMEINDEX 1        
          --#STATE     DEGRADED
          ::= 3

--   Tape Drive Group

     backupExecNTTapeDrive OBJECT IDENTIFIER ::= { tape 3 }
     
     driveNeedsAttention   TRAP-TYPE
          ENTERPRISE     backupExecNTTapeDrive
          VARIABLES { messageText, serverName, jobName, additionalText }
          DESCRIPTION
               "Tape drive needs human intervention."
          --#TYPE      "Take action immediately"
          --#SUMMARY   "%s Job:%s %s"
          --#ARGUMENTS {0,2,3}
          --#SEVERITY  MAJOR
          --#TIMEINDEX 1        
          --#STATE     DEGRADED
          ::= 3


--   Backup Exec for NetWare section

messageobject            OBJECT-TYPE
                         SYNTAX DisplayString (SIZE (0..128))
                         ACCESS read-only
                         STATUS mandatory
                         DESCRIPTION
                                "Buffer for text that the traps send to
                                 explain why the trap occurred."
                         ::= { backupExecNetWare 1 }


blockingerrormsg         TRAP-TYPE
                         ENTERPRISE     backupExecNetWare
                         VARIABLES
                         {
                              messageobject
                         }
                         DESCRIPTION
                              "An error occurred that prevents 1 or more
                               sessions from processing jobs."
                         --#TYPE      "Take action immediately"
                         --#SUMMARY   "Backup Exec - %s"
                         --#ARGUMENTS {0}
                         --#SEVERITY  MAJOR
                         --#TIMEINDEX 1        
                         --#STATE     DEGRADED
                         ::= 1

errormessage             TRAP-TYPE
                         ENTERPRISE     backupExecNetWare
                         VARIABLES
                         {
                              messageobject
                         }
                         DESCRIPTION
                              "An error occurred, but the session can
                               continue to process jobs."
                         --#TYPE      "User advised of event"
                         --#SUMMARY   "Backup Exec - %s"
                         --#ARGUMENTS {0}
                         --#SEVERITY  MINOR
                         --#TIMEINDEX 1        
                         --#STATE     OPERATIONAL     
                         ::= 2

blockingmessage          TRAP-TYPE
                         ENTERPRISE     backupExecNetWare
                         VARIABLES
                         {
                              messageobject
                         }
                         DESCRIPTION
                              "An event occurred that prevents 1 or more
                               sessions from processing jobs."
                         --#TYPE      "Take action immediately"
                         --#SUMMARY   "Backup Exec - %s"
                         --#ARGUMENTS {0}
                         --#SEVERITY  MAJOR
                         --#TIMEINDEX 1        
                         --#STATE     DEGRADED     
                         ::= 3

warningmessage           TRAP-TYPE
                         ENTERPRISE     backupExecNetWare
                         VARIABLES
                         {
                              messageobject
                         }
                         DESCRIPTION
                              "An event occurred that prevents a particular
                               job from running, but does not prevent the
                               session from processing jobs."
                         --#TYPE      "User advised of event"
                         --#SUMMARY   "Backup Exec - %s"
                         --#ARGUMENTS {0}
                         --#SEVERITY  MINOR
                         --#TIMEINDEX 1        
                         --#STATE     OPERATIONAL  
                         ::= 4

informationmessage       TRAP-TYPE
                         ENTERPRISE     backupExecNetWare
                         VARIABLES
                         {
                              messageobject
                         }
                         DESCRIPTION
                              "Information on normal events."
                         --#TYPE      "No action required"
                         --#SUMMARY   "Backup Exec - %s"
                         --#ARGUMENTS {0}
                         --#SEVERITY  INFORMATIONAL
                         --#TIMEINDEX 1        
                         --#STATE     OPERATIONAL  
                         ::= 5
END
