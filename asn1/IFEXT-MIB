IFEXT-MIB

   --FORCE-INCLUDE <mib.h>
   --FORCE-INCLUDE <snmpdefs.h>
   --FORCE-INCLUDE <snmpstat.h>
   --FORCE-INCLUDE "mibproto.h"
 
   DEFINITIONS ::= BEGIN

	IMPORTS
		MODULE-IDENTITY, OBJECT-TYPE, Integer32
			FROM SNMPv2-SMI
		RowStatus
			FROM SNMPv2-TC
		ifExt
			FROM APENT-MIB;


    ifExtMib MODULE-IDENTITY
	   LAST-UPDATED "9801282000Z" -- Wed January 28 20:00:00 EST 1998
	   ORGANIZATION "ArrowPoint Communications Inc."
	   CONTACT-INFO
	   "Postal:               ArrowPoint Communications Inc.
				                 50 Nagog Park
				                 Acton, Massachusetts 01720
	   Tel:                   +1 978-206-3000  option 1
	   E-Mail:                support@arrowpoint.com"
       DESCRIPTION
	"This MIB is not external viewable.  It provides a portion of the
    interface entry table for internal consumption."
      ::= { ifExt 1}


apIfTable OBJECT-TYPE
	SYNTAX      SEQUENCE OF ApIfEntry
	MAX-ACCESS  not-accessible
	STATUS      current
	DESCRIPTION
		"A table of interface entries"
	::= {ifExt 2}

apIfEntry OBJECT-TYPE
	SYNTAX      ApIfEntry
	MAX-ACCESS  not-accessible
	STATUS      current
	DESCRIPTION
	       "ArrowPoint interface record"
	INDEX  { apIfIndex}
	::= {apIfTable 1}

ApIfEntry ::=
	SEQUENCE 
	{
	apIfIndex					Integer32,
	apIfType 	 				INTEGER,
	apIfCategory				INTEGER,
	apIfSlot					Integer32,
	apIfPort					Integer32,
	apIfStatus					RowStatus
	}

apIfIndex OBJECT-TYPE
	SYNTAX      Integer32
	MAX-ACCESS  read-create
	STATUS      current
	DESCRIPTION
	       "The ifIndex of the interface entry"
	::= {apIfEntry 1}

apIfType OBJECT-TYPE
	SYNTAX      INTEGER {
							fe(6),
							ds1(18),
							console(22),
							ppp(23),
							ds3(30),
							fr(32),
							ct(54),
							ds0(81),
							ds0b(82),
							pppmm(108),
              ge(117),
							madlan(1005),
    			    sar(1006)
						}
	MAX-ACCESS  read-create
	STATUS      current
	DESCRIPTION
	       "The ifType of the interface entry"
	::= {apIfEntry 2}

apIfCategory OBJECT-TYPE
	SYNTAX      INTEGER {
							physical(1),
							not-physical(2)
						}
	MAX-ACCESS  read-create
	STATUS      current
	DESCRIPTION
	       "The if category of the interface entry"
	::= {apIfEntry 3}

apIfSlot OBJECT-TYPE
	SYNTAX      Integer32
	MAX-ACCESS  read-create
	STATUS      current
	DESCRIPTION
	       "The slot associated with this interface"
	::= {apIfEntry 4}


apIfPort OBJECT-TYPE
	SYNTAX      Integer32
	MAX-ACCESS  read-create
	STATUS      current
	DESCRIPTION
	       "The physical port associated with this interface"
	::= {apIfEntry 5}

apIfStatus OBJECT-TYPE
	SYNTAX      RowStatus
	MAX-ACCESS  read-create
	STATUS      current
	DESCRIPTION
	       "This status object for this row"
	::= {apIfEntry 6}

apIfCctTable OBJECT-TYPE
	SYNTAX      SEQUENCE OF ApIfCctEntry
	MAX-ACCESS  not-accessible
	STATUS      current
	DESCRIPTION
		"A table of interface entries"
	::= {ifExt 3}

apIfCctEntry OBJECT-TYPE
	SYNTAX      ApIfCctEntry
	MAX-ACCESS  not-accessible
	STATUS      current
	DESCRIPTION
	       "ArrowPoint circuit record"
	INDEX  { apIfCctIfIndex}
	::= {apIfCctTable 1}

ApIfCctEntry ::=
	SEQUENCE 
	{
	apIfCctIfIndex				Integer32,
	apIfCctStatus				RowStatus
	}

apIfCctIfIndex OBJECT-TYPE
	SYNTAX      Integer32
	MAX-ACCESS  read-create
	STATUS      current
	DESCRIPTION
	       "The ifIndex of the circuit"
	::= {apIfCctEntry 1}

apIfCctStatus OBJECT-TYPE
	SYNTAX      RowStatus
	MAX-ACCESS  read-create
	STATUS      current
	DESCRIPTION
	       "This status object for this row"
	::= {apIfCctEntry 2}

apIfRedundantSCM OBJECT-TYPE
	SYNTAX      INTEGER {
						present (1),
						not-present(2)
						}
	MAX-ACCESS  read-create
	STATUS      current
	DESCRIPTION
	       "The presence of the redundant SCM"
	::= {ifExt 4}

END
