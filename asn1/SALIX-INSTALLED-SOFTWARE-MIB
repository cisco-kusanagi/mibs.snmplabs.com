SALIX-INSTALLED-SOFTWARE-MIB DEFINITIONS ::= BEGIN

IMPORTS
   MODULE-IDENTITY, OBJECT-TYPE, IpAddress    FROM SNMPv2-SMI

   MODULE-COMPLIANCE, OBJECT-GROUP            FROM SNMPv2-CONF
         
         DateAndTime, DisplayString                       FROM SNMPv2-TC
         
         hrSWInstalledEntry, 
         hrSWInstalledIndex, hrSWRunEntry    FROM HOST-RESOURCES-MIB         
         
         SalixPlugInUnitType                 FROM SALIX-PRODUCT-PLUGIN-MIB

         salixGeneric                        FROM SALIX-MIB;

salixInstalledSWMIB MODULE-IDENTITY
     LAST-UPDATED "9810130000Z"
     ORGANIZATION "SALIX Technologies"
     CONTACT-INFO "904 Wind River Lane
                   Suite 101
                   Gaithersburg, MD  20878
                   (301)-417-0017"
     DESCRIPTION  "The MIB describing Installed Software objects 
                   for SALIX products"
     ::= { salixGeneric 4 }
     
   salixInstalledSWMIBObjects OBJECT IDENTIFIER ::= { salixInstalledSWMIB 1 }
   salixInstalledSWMIBTraps   OBJECT IDENTIFIER ::= { salixInstalledSWMIB 2 }
   salixInstalledSWMIBCompliance OBJECT IDENTIFIER ::= { salixInstalledSWMIB 3 }       
   salixInstalledSWMIBTrapPrefix OBJECT IDENTIFIER ::= { salixInstalledSWMIBTraps 0}


    -- Installed Software Table

  salixSysHrSWInstalledTable OBJECT-TYPE
       SYNTAX     SEQUENCE OF    SalixSysHrSWInstalledEntry
       MAX-ACCESS not-accessible
       STATUS     current
       DESCRIPTION
            "The  system installed software table.  This table augments
             the hrSWInstalledTable to include additional attributes of 
             the software installed in the table."
       ::= { salixInstalledSWMIBObjects 1 }

  salixSysHrSWInstalledEntry OBJECT-TYPE
       SYNTAX     SalixSysHrSWInstalledEntry
       MAX-ACCESS not-accessible
       STATUS     current
       DESCRIPTION
            "An entry in the salixSysHrSWInstalledTable that describes
             additional attributes of the software installed in the 
             hrSWInstalledTable."
       AUGMENTS { hrSWInstalledEntry }
       ::= { salixSysHrSWInstalledTable 1 }

  SalixSysHrSWInstalledEntry ::= SEQUENCE {
        	salixSysHrSWInstalledFileVersion  OCTET STRING,
	      salixSysHrSWInstalledFileControl  DateAndTime,
        	salixSysHrSWInstalledFileCreation DateAndTime,
        	salixSysHrSWInstalledFilePiuType  SalixPlugInUnitType,
         salixSysHrSWInstalledFileBuilderName OCTET STRING,
         salixSysHrSWInstalledFileReleaseLabel OCTET STRING
       }

  salixSysHrSWInstalledFileVersion OBJECT-TYPE
       SYNTAX     OCTET STRING(SIZE (8))
       MAX-ACCESS read-only
       STATUS     current
       DESCRIPTION
            "The release version of the software file installed in 
             the software table entry."
       ::= { salixSysHrSWInstalledEntry 1 }

  salixSysHrSWInstalledFileControl OBJECT-TYPE
       SYNTAX     DateAndTime
       MAX-ACCESS read-only
       STATUS     current
       DESCRIPTION
            "The date and time configuration and control information
             that uniquely identifies the file in the installed
             software table entry."
       ::= { salixSysHrSWInstalledEntry 2 }

  salixSysHrSWInstalledFileCreation OBJECT-TYPE
       SYNTAX     DateAndTime
       MAX-ACCESS read-only
       STATUS     current
       DESCRIPTION
            "The creation date and time of the file in the installed
             software table entry."
       ::= { salixSysHrSWInstalledEntry 3 }

  salixSysHrSWInstalledFilePiuType OBJECT-TYPE
       SYNTAX     SalixPlugInUnitType
       MAX-ACCESS read-only
       STATUS     current
       DESCRIPTION
            "The type of plugin unit that the installed software
             can operate."
       ::= { salixSysHrSWInstalledEntry 4 }

  salixSysHrSWInstalledFileBuilderName OBJECT-TYPE
       SYNTAX     OCTET STRING(SIZE (32))
       MAX-ACCESS read-only
       STATUS     current
       DESCRIPTION
            "The username of the person who created the file
             in the installed software table entry."
       ::= { salixSysHrSWInstalledEntry 5 }

  salixSysHrSWInstalledFileReleaseLabel OBJECT-TYPE
       SYNTAX     OCTET STRING(SIZE (32))
       MAX-ACCESS read-only
       STATUS     current
       DESCRIPTION
            "The version control release label for the file
             in the installed software table entry ."
       ::= { salixSysHrSWInstalledEntry 6 }

    --  Software Download Table

    -- This table provides a mechanism for installing software 
    -- on the  hard disk by initiating a download request 
	 -- to a specific software entry (bin) in the  software 
    -- download table.  Prior to initiating the download request
	 -- a management entity must first set the following fields
	 -- in this table:
    --      salixSysSwDownloadFilename 
    --      salixSysSwDownloadIpAddress.
    --
    -- When the above fields are valid, the management entity
	 -- can then start the download by sending a request to the 
	 -- SNMP agent with the salixSysSwDownloadRequest field set to 
	 -- 'start' in addition to specifing values for the 
	 -- salixSysSwDownloadUsername and salixSysSwDownloadPassword fields.

    -- It is the responsibility of the management entity to poll the
    -- salixSysSwDownloadState to determine when the download completes.
    -- If the command completes with 'success', then the download to the
    --  was successful and the software is installed into the  
    -- Installed Software Table.

    -- The agent will create the salixSysSwDownloadTable with a fixed number
    -- of entries when the host is booted.  The management entity
    -- can download to any entry in the salixSysSwDownloadTable with the 
    -- exception of entry (bin) zero.  Entry (bin) zero is reserved
    -- to indicate an empty software bin.

    -- A download request to an entry (bin) in the salixSysSwDownloadTable
    -- will overwrite the corresponding entry (bin) in the 
    -- salixSysHrSWInstalledTable.  However, a download request to an entry
    -- (bin) in the salixSysSwDownloadTable will be ignored if a previous
    -- request is still in progress.

  salixSysSwDownloadTable OBJECT-TYPE
       SYNTAX     SEQUENCE OF    SalixSysSwDownloadEntry
       MAX-ACCESS not-accessible
       STATUS     current
       DESCRIPTION
            "The  software download table.  This table provides a
             mechanism for downloading software to the system.  Software 
             that is successfully downloaded is installed on the system
             and occupies an entry in the salixSysHrSWInstalledTable."
       ::= { salixInstalledSWMIBObjects 2 }

  salixSysSwDownloadEntry OBJECT-TYPE
       SYNTAX     SalixSysSwDownloadEntry
       MAX-ACCESS not-accessible
       STATUS     current
       DESCRIPTION
            "An entry in the salixSysSwDownloadTable that identifies 
             the parameters necessary to download software to the system."
       INDEX { hrSWInstalledIndex }
       ::= { salixSysSwDownloadTable 1 }

  SalixSysSwDownloadEntry ::= SEQUENCE {
            salixSysSwDownloadIpAddress      IpAddress,
            salixSysSwDownloadFilename       DisplayString,
            salixSysSwDownloadUsername       DisplayString,
            salixSysSwDownloadPassword       DisplayString,
            salixSysSwDownloadRequest        INTEGER,
            salixSysSwDownloadState          INTEGER,
            salixSysSwDownloadStatusMessage  OCTET STRING
       }

  salixSysSwDownloadIpAddress OBJECT-TYPE
       SYNTAX     IpAddress
       MAX-ACCESS read-write
       STATUS     current
       DESCRIPTION
            "The Ip Address where the salixSysSwDownloadFilename
             object resides."
       ::= { salixSysSwDownloadEntry 1 }

  salixSysSwDownloadFilename OBJECT-TYPE
       SYNTAX     DisplayString (SIZE(0..64))
       MAX-ACCESS read-write
       STATUS     current
       DESCRIPTION
            "The fully qualified filename found at the specified Ip Address
             (salixSysSwDownloadIpAddress) that is to be downloaded
             to the entry in the Table."
       ::= { salixSysSwDownloadEntry 2 }

  salixSysSwDownloadUsername OBJECT-TYPE
       SYNTAX     DisplayString (SIZE(0..64))
       MAX-ACCESS read-write
       STATUS     current
       DESCRIPTION
            "The username to be used when getting a file from the
             computer at the IP address indicated by the 
             salixSysSwDownloadIpAddress attribute.  For security
             reasons, reading this field will return an empty string."
       ::= { salixSysSwDownloadEntry 3 }
     
  salixSysSwDownloadPassword OBJECT-TYPE
       SYNTAX     DisplayString (SIZE(0..64))
       MAX-ACCESS read-write
       STATUS     current
       DESCRIPTION
            "The password to be used when getting a file from the
             computer at the IP address indicated by the 
             salixSysSwDownloadIpAddress attribute.  For security
             reasons, reading this field will return an empty string."
       ::= { salixSysSwDownloadEntry 4 }
       
  salixSysSwDownloadRequest OBJECT-TYPE
       SYNTAX         INTEGER { none(0), start(1) }
       MAX-ACCESS     read-write
       STATUS         current
       DESCRIPTION
            "Setting this attribute to 'start' will cause the download
             request to begin."
       DEFVAL { none }
       ::= { salixSysSwDownloadEntry 5 }

  salixSysSwDownloadState OBJECT-TYPE
       SYNTAX     INTEGER { none(1),
                            inProgress(2),
                            success(3),
                            aborted(4),
                            failed(5),
                            locked(6)
                          }
       MAX-ACCESS read-only
       STATUS     current
       DESCRIPTION
            "The state of the download software request.

             none(1)       - download not started or not supported
             inProgress(2) - download in progress
             success(3)    - download to the installed software table
                             was successful.
             aborted(4)    - download aborted
             failed(5)     - download to at least one plug-in unit failed
             locked(6)     - the filename in the installed software entry
                             is locked by the management processor software."
       DEFVAL { none }
       ::= { salixSysSwDownloadEntry 6 }

  salixSysSwDownloadStatusMessage OBJECT-TYPE
       SYNTAX     OCTET STRING(SIZE (256))
       MAX-ACCESS read-only
       STATUS     current
       DESCRIPTION
            "Status message that describes the current state of the
             download as indicated by the 'salixSysSwDownloadState' 
             attribute."
       ::= { salixSysSwDownloadEntry 7 }
       
    -- Run Software Table

  salixSysHrSWRunTable OBJECT-TYPE
       SYNTAX     SEQUENCE OF    SalixSysHrSWRunEntry
       MAX-ACCESS not-accessible
       STATUS     current
       DESCRIPTION
            "The  system Run software table.  This table augments
             the hrSWRunTable to include additional attributes of 
             the software Run in the table."
       ::= { salixInstalledSWMIBObjects 3 }

  salixSysHrSWRunEntry OBJECT-TYPE
       SYNTAX     SalixSysHrSWRunEntry
       MAX-ACCESS not-accessible
       STATUS     current
       DESCRIPTION
            "An entry in the salixSysHrSWRunTable that describes
             additional attributes of the software Run in the 
             hrSWRunTable."
       AUGMENTS { hrSWRunEntry }
       ::= { salixSysHrSWRunTable 1 }

  SalixSysHrSWRunEntry ::= SEQUENCE {
        	salixSysHrSWRunFileVersion  OCTET STRING,
	      salixSysHrSWRunFileControl  DateAndTime,
        	salixSysHrSWRunFileCreation DateAndTime,
         salixSysHrSWRunFileBuilderName OCTET STRING,
         salixSysHrSWRunFileReleaseLabel OCTET STRING
       }

  salixSysHrSWRunFileVersion OBJECT-TYPE
       SYNTAX     OCTET STRING(SIZE (8))
       MAX-ACCESS read-only
       STATUS     current
       DESCRIPTION
            "The release version of the software file Run in 
             the software table entry."
       ::= { salixSysHrSWRunEntry 1 }

  salixSysHrSWRunFileControl OBJECT-TYPE
       SYNTAX     DateAndTime
       MAX-ACCESS read-only
       STATUS     current
       DESCRIPTION
            "The date and time configuration and control information
             that uniquely identifies the file in the Run
             software table entry."
       ::= { salixSysHrSWRunEntry 2 }

  salixSysHrSWRunFileCreation OBJECT-TYPE
       SYNTAX     DateAndTime
       MAX-ACCESS read-only
       STATUS     current
       DESCRIPTION
            "The creation date and time of the file in the Run
             software table entry."
       ::= { salixSysHrSWRunEntry 3 }
       
  salixSysHrSWRunFileBuilderName OBJECT-TYPE
       SYNTAX     OCTET STRING(SIZE (32))
       MAX-ACCESS read-only
       STATUS     current
       DESCRIPTION
            "The username of the person who created the file
             in the Run software table entry."
       ::= { salixSysHrSWRunEntry 4 }

  salixSysHrSWRunFileReleaseLabel OBJECT-TYPE
       SYNTAX     OCTET STRING(SIZE (32))
       MAX-ACCESS read-only
       STATUS     current
       DESCRIPTION
            "The version control release label for the file
             in the Run software table entry ."
       ::= { salixSysHrSWRunEntry 5 }
       
-- Conformance Statements

salixInstalledSWGroups      OBJECT IDENTIFIER  ::= { salixInstalledSWMIBCompliance 1 }
salixInstalledSWCompliances OBJECT IDENTIFIER  ::= { salixInstalledSWMIBCompliance 2 }

   salixInstalledSWGroup OBJECT-GROUP
      OBJECTS {
         salixSysSwDownloadIpAddress,
         salixSysSwDownloadFilename,
         salixSysSwDownloadUsername,
         salixSysSwDownloadPassword,
         salixSysSwDownloadRequest,
         salixSysSwDownloadState,  
         salixSysSwDownloadStatusMessage
      }
      STATUS         current
      DESCRIPTION    "Salix InstalledSW Objects Group"
      ::= { salixInstalledSWGroups 1}

-- Compliance Statements

salixInstalledSWCompliance MODULE-COMPLIANCE
     STATUS       current
     DESCRIPTION
                  "The basic implementation requirements for the SALIX-INSTALLED-SOFTWARE-MIB."
     MODULE       -- This module
     MANDATORY-GROUPS { salixInstalledSWGroup }
     ::= { salixInstalledSWCompliances 1 }

END
