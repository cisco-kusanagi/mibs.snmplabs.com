--
-- IBM wireless LAN MIB: version 1.0
--

WIRELESS-MIB DEFINITIONS ::= BEGIN

IMPORTS
         enterprises, Counter, Timeticks, Gauge     FROM RFC1155-SMI
         DisplayString                              FROM RFC1213-MIB
         OBJECT-TYPE                                FROM RFC1212;

MacAddress ::= OCTET STRING (SIZE(6))



ibm OBJECT IDENTIFIER ::= { enterprises 2 }

ibmProd OBJECT IDENTIFIER ::= { ibm 6 }

ibmwlan OBJECT IDENTIFIER ::= { ibmProd 10 }

wrBase      OBJECT IDENTIFIER ::= { ibmwlan 1 }

wrRemote    OBJECT IDENTIFIER ::= { ibmwlan 2 }


------------------------------
--The Base Name
------------------------------

baseName         OBJECT-TYPE
                 SYNTAX DisplayString
                 ACCESS read-only
                 STATUS mandatory
                 DESCRIPTION
                 "Name of the Base Station assigned through the Wireless
                 Network Administration Program."
                 ::= { wrBase 1 }

------------------------------
--The Network Name
------------------------------

baseNetworkName        OBJECT-TYPE
                 SYNTAX DisplayString
                 ACCESS read-only
                 STATUS mandatory
                 DESCRIPTION
                 "Name of the Wireless Network containing the Base Station.
                 This name has been assigned through the Wireless Network
                 Administration Program."
                 ::= { wrBase 2 }

------------------------------
--The Wireless Network Administration Console IP Address
------------------------------

baseAdminIPAddr  OBJECT-TYPE
                 SYNTAX IpAddress
                 ACCESS read-only
                 STATUS mandatory
                 DESCRIPTION
                 "IP Address of the station housing the Wireless Network
                  Administration Program."
              ::= { wrBase 3 }


------------------------------
--The Base Station Table
------------------------------

wrBaseTable OBJECT-TYPE
              SYNTAX SEQUENCE OF WrBaseEntry
              ACCESS not-accessible
              STATUS mandatory
              DESCRIPTION
              "This table contains wireless interface parameters and state
               variables, one entry per wireless interface."
              ::= { wrBase 4 }


wrBaseEntry OBJECT-TYPE
              SYNTAX WrBaseEntry
              ACCESS not-accessible
              STATUS mandatory
              DESCRIPTION
              "An entry contains wireless parameters and state
               variables for a particular interface."
              INDEX { baseIfIndex }
              ::= { wrBaseTable 1 }

WrBaseEntry
     ::= SEQUENCE {
             baseIfIndex            INTEGER,
             baseHDLCaddress        INTEGER,
             baseNbOFRemote         INTEGER,
             baseCellIdentifier     INTEGER,
             baseAdapterStatus      INTEGER,
             baseEmittedPower       INTEGER,
             -- Controller Card VPD
             baseControllerCardDesc  DisplayString,
             baseUnivAddress         MacAddress,
             -- Radio VPD
             baseModemDesc           DisplayString,
             -- Topology flag (enum)
             baseTopologyTrapActive  INTEGER
             }

baseIfIndex  OBJECT-TYPE
            SYNTAX INTEGER
            ACCESS read-only
            STATUS mandatory
            DESCRIPTION
              "The value of this object identifies the wireless
               interface for which this entry contains management
               information. The value of this object for a particular
               interface has the same value as the IfIndex object
               defined in MIB-II for the same interface."
            ::= { wrBaseEntry 1 }


baseHDLCaddress OBJECT-TYPE
             SYNTAX OCTET STRING
             ACCESS read-only
             STATUS mandatory
             DESCRIPTION
             "HDLC address of the wireless interface."
            ::= { wrBaseEntry 2 }


baseNbOFRemote   OBJECT-TYPE
                 SYNTAX INTEGER
                 ACCESS read-only
                 STATUS mandatory
                 DESCRIPTION
                 "Number of wireless workstations registered
                  to the wireless interface."
                 ::= { wrBaseEntry 3 }


baseCellIdentifier OBJECT-TYPE
                 SYNTAX INTEGER
                 ACCESS read-only
                 STATUS mandatory
                 DESCRIPTION
                 "Identifier of the cell controlled
                  by the wireless interface."
                 ::= { wrBaseEntry 4 }

baseAdapterStatus  OBJECT-TYPE
                   SYNTAX INTEGER {
                        operational (1),
                        not-operational (2)
                        }
                   ACCESS read-only
                   STATUS mandatory
                   DESCRIPTION
                   "Status of the wireless interface."
                   ::= { wrBaseEntry 5 }

baseEmittedPower   OBJECT-TYPE
                   SYNTAX INTEGER
                   ACCESS read-only
                   STATUS mandatory
                   DESCRIPTION
                   "Emitted power of the wireless interface."
                   ::= { wrBaseEntry 6 }

baseControllerCardDesc  OBJECT-TYPE
               SYNTAX DisplayString
               ACCESS read-only
               STATUS mandatory
               DESCRIPTION
               "Vital Product Data  of the wireless controller card
                performing the wireless interface function."
               ::= { wrBaseEntry 7 }

baseUnivAddress   OBJECT-TYPE
                SYNTAX MacAddress
                ACCESS read-only
                STATUS mandatory
                DESCRIPTION
                "Universal address of the wireless controller card
                 performing the wireless interface function."
                ::= { wrBaseEntry 8 }

baseModemDesc   OBJECT-TYPE
               SYNTAX DisplayString
               ACCESS read-only
               STATUS mandatory
               DESCRIPTION
               "Vital Product Data  of the transceiver
                performing the wireless interface function."
                ::= { wrBaseEntry 9 }

baseTopologyTrapActive   OBJECT-TYPE
               SYNTAX INTEGER {
                    active (1),
                    inactive (2)
                    }
               ACCESS read-write
               STATUS mandatory
               DESCRIPTION
               "Traps will be sent when wireless workstation
                registers to and deregisters from the wireless
                interface only if this object is set to active."
               ::= { wrBaseEntry 10 }



----------------------------------------
--The Base Station Statistics table
----------------------------------------



wrBaseStatsTable  OBJECT-TYPE
                  SYNTAX SEQUENCE OF WrBaseStatsEntry
                  ACCESS not-accessible
                  STATUS mandatory
                  DESCRIPTION
                  "This table contains wireless interface statistics,
                   one entry per wireless interface."
                  ::= { wrBase 5 }

wrBaseStatsEntry OBJECT-TYPE
              SYNTAX WrBaseStatsEntry
              ACCESS not-accessible
              STATUS mandatory
              DESCRIPTION
              "An entry contains wireless statistics for a particular
              interface."
              INDEX { baseStatsIfIndex }
              ::= { wrBaseStatsTable 1 }

WrBaseStatsEntry
        ::=  SEQUENCE
               {
               baseStatsIfIndex        INTEGER,
               -- Adapter Counters
               baseStatsXmit           Counter,
               baseStatsRxmit          Counter,
               baseStatsNegAckRcv      Counter,
               baseStatsRcv            Counter,
               baseStatsLineErrors     Counter,
               baseStatsNegAckXmit     Counter,
               -- Adapter Counters
               baseStatsFramePurged    Counter,
               baseStatsFreqDelete     Counter,
               baseStatsHopAdvance     Counter,
               baseStatsCLineErrors    Counter,
               -- ICR Counters
               baseStatsRcvICRFrame    Counter,
               baseStatsXmitICRFrame   Counter,
               baseStatsNoICRBufferAvail  Counter,
               baseStatsNotRoutedICRFrame Counter,
               -- All base station aggregate Gauges
               baseStatsNbCUserEst     Gauge
               }

baseStatsIfIndex  OBJECT-TYPE
                  SYNTAX  INTEGER
                  ACCESS  read-only
                  STATUS  mandatory
                  DESCRIPTION
                 "The value of this object identifies the wireless
                  interface for which this entry contains management
                  information. The value of this object for a particular
                  interface has the same value as the IfIndex object
                  defined in MIB-II for the same interface."
                  ::= { wrBaseStatsEntry 1 }

baseStatsXmit      OBJECT-TYPE
                      SYNTAX Counter
                      ACCESS read-only
                      STATUS mandatory
                      DESCRIPTION
                      "Number of packets transmitted over the wireless
                      interface."
                      ::= { wrBaseStatsEntry 2 }

baseStatsRxmit     OBJECT-TYPE
                      SYNTAX Counter
                      ACCESS read-only
                      STATUS mandatory
                      DESCRIPTION
                      "Number of packets retransmitted over
                      the wireless interface due to a lack
                      of positive acknowledgement."
                      ::= { wrBaseStatsEntry 3 }

baseStatsNegAckRcv OBJECT-TYPE
                      SYNTAX Counter
                      ACCESS read-only
                      STATUS mandatory
                      DESCRIPTION
                      "Number of negative acknowledgement received over
                      the wireless interface (workstations congestion
                      indicator)."
                      ::= { wrBaseStatsEntry 4 }

baseStatsRcv       OBJECT-TYPE
                      SYNTAX Counter
                      ACCESS read-only
                      STATUS mandatory
                      DESCRIPTION
                      "Number of packets received over the wireless interface."
                      ::= { wrBaseStatsEntry 5 }

baseStatsLineErrors OBJECT-TYPE
                      SYNTAX Counter
                      ACCESS read-only
                      STATUS mandatory
                      DESCRIPTION
                      "Number of slots assigned to wireless workstations
                      that fail to use or that fail to receive (HDLC error)."
                      ::= { wrBaseStatsEntry 6 }

baseStatsNegAckXmit OBJECT-TYPE
                      SYNTAX Counter
                      ACCESS read-only
                      STATUS mandatory
                      DESCRIPTION
                      "Number of negative acknowledgement transmitted over
                      the wireless interface (base congestion indicator)."
                      ::= { wrBaseStatsEntry 7 }


baseStatsFramePurged OBJECT-TYPE
                         SYNTAX Counter
                         ACCESS read-only
                         STATUS mandatory
                         DESCRIPTION
                         "Number of frames that were purged by the wireless
                          interface because they were corrupted during air
                          transmission."
                         ::= { wrBaseStatsEntry 8 }

baseStatsFreqDelete    OBJECT-TYPE
                         SYNTAX Counter
                         ACCESS read-only
                         STATUS mandatory
                         DESCRIPTION
                         "Number of times a single frequency had
                         to be replaced in the frequency hopping
                         pattern because an excessive level of
                         interference was detected for that
                         frequency."
                         ::= { wrBaseStatsEntry 9 }

baseStatsHopAdvance    OBJECT-TYPE
                         SYNTAX Counter
                         ACCESS read-only
                         STATUS mandatory
                         DESCRIPTION
                         "Number of times a hop advance procedure
                          had to be performed because an excessive
                          level of interference was detected for each
                          frequency of the hopping pattern."
                         ::= { wrBaseStatsEntry 10 }

baseStatsCLineErrors OBJECT-TYPE
                         SYNTAX Counter
                         ACCESS read-only
                         STATUS mandatory
                         DESCRIPTION
                         "Number of times the first packet of a frame
                          was received over the wireless interface
                          with an HDLC error."
                          ::= { wrBaseStatsEntry 11 }

baseStatsRcvICRFrame OBJECT-TYPE
                         SYNTAX Counter
                         ACCESS read-only
                         STATUS mandatory
                         DESCRIPTION
                         "Number of frames received by the base station
                          on the wireless interface that must be
                          forwarded to one or more wireless workstations
                          registered to the same wireless interface."
                          ::= { wrBaseStatsEntry 12 }

baseStatsXmitICRFrame OBJECT-TYPE
                           SYNTAX Counter
                           ACCESS read-only
                           STATUS mandatory
                           DESCRIPTION
                          "Number of frames forwarded by the base station
                           from a wireless workstation to another one.
                           This counter may be incremented several times
                           for the same frame if it is a broadcast frame."
                           ::= { wrBaseStatsEntry 13 }

baseStatsNoICRBufferAvail  OBJECT-TYPE
                           SYNTAX Counter
                           ACCESS read-only
                           STATUS mandatory
                           DESCRIPTION
                          "Number of frames received on the wireless
                           interface coming from a wireless
                           workstation and going to another
                           wireless workstation registered to the same
                           wireless interface that had to be discarded
                           due to a lack of resources."
                           ::= { wrBaseStatsEntry 14 }

baseStatsNotRoutedICRFrame OBJECT-TYPE
                           SYNTAX Counter
                           ACCESS read-only
                           STATUS mandatory
                           DESCRIPTION
                          "Number of frames received on the wireless
                           interface coming from a wireless
                           workstation and going to another
                           wireless workstation that were discarded
                           because the target wireless workstation
                           could not be found."
                           ::= { wrBaseStatsEntry 15 }

baseStatsNbCUserEst OBJECT-TYPE
                       SYNTAX Gauge
                       ACCESS read-only
                       STATUS mandatory
                       DESCRIPTION
                       "Number of wireless workstation trying
                        to transmit in C interval."
                       ::= { wrBaseStatsEntry 16 }


------------------------------
--The Remote station table
------------------------------

wrRemoteTable OBJECT-TYPE
              SYNTAX SEQUENCE OF WrRemoteEntry
              ACCESS not-accessible
              STATUS mandatory
              DESCRIPTION
              "This table contains management information
               for the wireless workstations registered to the
               wireless interfaces, one entry per registered
               wireless workstation."
               ::= { wrRemote 1 }

wrRemoteEntry OBJECT-TYPE
              SYNTAX WrRemoteEntry
              ACCESS not-accessible
              STATUS mandatory
              DESCRIPTION
              "An entry contains management information for a particular
               wireless workstation. An object of this type is transient
               in that it ceases to exist when (or soon after) the
               wireless workstation deregisters from the base."
              INDEX { remIfIndex,
                      remIndex}
              ::= { wrRemoteTable 1 }


WrRemoteEntry
     ::= SEQUENCE {
             remIfIndex             INTEGER,
             remIndex               INTEGER,
             remMacAddress          MacAddress,
             remName                DisplayString,
             remControllerCardDesc  DisplayString,
             remUnivAddress         MacAddress,
             -- Radio VPD
             remModemDesc           DisplayString
            }


remIfIndex  OBJECT-TYPE
          SYNTAX INTEGER
          ACCESS read-only
          STATUS mandatory
          DESCRIPTION
          "The value of this object identifies the wireless
           interface to which is registered the workstation for
           which this entry contains management information.
           The value of this object for a particular
           interface has the same value as the IfIndex object
           defined in MIB-II for the same interface."
          ::= { wrRemoteEntry 1 }


remIndex  OBJECT-TYPE
          SYNTAX INTEGER
          ACCESS read-only
          STATUS mandatory
          DESCRIPTION
          "The value of this object identifies the registered wireless
           workstation for which this entry contains management information.
           This value has been dynamically assigned to the wireless
           workstation when it registered to the base."
          ::= { wrRemoteEntry 2 }

remMacAddress   OBJECT-TYPE
                SYNTAX MacAddress
                ACCESS read-only
                STATUS mandatory
                DESCRIPTION
                "MAC address of the wireless workstation."
                ::= { wrRemoteEntry 3 }

remName         OBJECT-TYPE
                SYNTAX DisplayString
                ACCESS read-only
                STATUS mandatory
                DESCRIPTION
                "Name of the wireless workstation."
                ::= { wrRemoteEntry 4 }

remControllerCardDesc  OBJECT-TYPE
               SYNTAX DisplayString
               ACCESS read-only
               STATUS mandatory
               DESCRIPTION
               "Adapter Vital Product Data of the wireless workstation."
               ::= { wrRemoteEntry 5 }

remUnivAddress  OBJECT-TYPE
                SYNTAX MacAddress
                ACCESS read-only
                STATUS mandatory
                DESCRIPTION
                "Universal address of the wireless workstation."
                ::= { wrRemoteEntry 6 }

remModemDesc   OBJECT-TYPE
               SYNTAX DisplayString
               ACCESS read-only
               STATUS mandatory
               DESCRIPTION
               "Transceiver Vital Product Data of the wireless workstation."
               ::= { wrRemoteEntry 7 }

------------------------------
--The Remote stats table
------------------------------

wrRemoteStatsTable OBJECT-TYPE
                   SYNTAX SEQUENCE OF WrRemStatsEntry
                   ACCESS not-accessible
                   STATUS mandatory
                   DESCRIPTION
                  "This table contains statistics information
                   for the wireless workstations registered to the
                   wireless interfaces, one entry per registered
                   wireless workstation."
                   ::= { wrRemote 2 }

wrRemStatsEntry OBJECT-TYPE
                SYNTAX WrRemStatsEntry
                ACCESS not-accessible
                STATUS mandatory
                DESCRIPTION
                "An entry contains statistics information for a particular
                 wireless workstation. An object of this type is transient
                 in that it ceases to exist when (or soon after) the
                 wireless workstation deregisters from the base."
                INDEX { remStatsIfIndex,
                        remStatsIndex}
                ::= { wrRemoteStatsTable 1 }


WrRemStatsEntry
     ::= SEQUENCE {
             remStatsIfIndex    INTEGER,
             remStatsIndex      INTEGER,
             remStatsXmit       Counter,
             remStatsRxmit      Counter,
             remStatsNegAckRcv  Counter,
             remStatsRcv        Counter,
             remStatsLineErrors Counter,
             remStatsNegAckXmit Counter
             }

remStatsIfIndex OBJECT-TYPE
                SYNTAX INTEGER
                ACCESS read-only
                STATUS mandatory
                DESCRIPTION
               "The value of this object identifies the wireless
                interface to which is registered the workstation for
                which this entry contains management information.
                The value of this object for a particular
                interface has the same value as the IfIndex object
                defined in MIB-II for the same interface."
                ::= { wrRemStatsEntry 1 }

remStatsIndex   OBJECT-TYPE
                SYNTAX INTEGER
                ACCESS read-only
                STATUS mandatory
                DESCRIPTION
               "The value of this object identifies the wireless workstation
                for which this entry contains statistics information.
                This value has been dynamically assigned to the wireless
                workstation when it registered to the base."
                ::= { wrRemStatsEntry 2 }

remStatsXmit OBJECT-TYPE
                SYNTAX Counter
                ACCESS read-only
                STATUS mandatory
                DESCRIPTION
                "Number of packets transmitted over the wireless interface
                to this particular wireless workstation."
                ::= { wrRemStatsEntry 3 }

remStatsRxmit OBJECT-TYPE
                 SYNTAX Counter
                 ACCESS read-only
                 STATUS mandatory
                 DESCRIPTION
                "Number of packets retried over the wireless interface
                 due to a lack of positive acknowledgement from
                 this particular wireless workstation."
                 ::= { wrRemStatsEntry 4 }

remStatsNegAckRcv OBJECT-TYPE
                     SYNTAX Counter
                     ACCESS read-only
                     STATUS mandatory
                     DESCRIPTION
                    "Number of Out of Sequences Packets received over
                     the wireless interface from this particular
                     wireless workstation."
                     ::= { wrRemStatsEntry 5 }

remStatsRcv  OBJECT-TYPE
             SYNTAX Counter
             ACCESS read-only
             STATUS mandatory
             DESCRIPTION
             "Number of packets received over the wireless interface
              from this particular wireless workstation."
             ::= { wrRemStatsEntry 6 }

remStatsLineErrors OBJECT-TYPE
                      SYNTAX Counter
                      ACCESS read-only
                      STATUS mandatory
                      DESCRIPTION
                      "Number of slots assigned to this particular wireless
                       workstation that fail to use or that fail to receive
                       (HDLC error)."
                      ::= { wrRemStatsEntry 7 }

remStatsNegAckXmit OBJECT-TYPE
                      SYNTAX Counter
                      ACCESS read-only
                      STATUS mandatory
                      DESCRIPTION
                      "Number of negative acknowledgement transmitted to a
                       given workstation over the wireless interface
                       (base congestion indicator)."
                      ::= { wrRemStatsEntry 8 }


END
