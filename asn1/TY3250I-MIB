-- TyLink Enterprise MIB for 3250                             =
--                                                            =
-- SCCS Information: @(#)ty3250i.mib	3.5  Last Delta-ed on: 11/29/95
--                                                            =
-- This file contains MIB Definitions for extended management =
-- of TyLink 3250 Product (T1 product with integral agent).   =
--
-- This MIB is Copyrighted by TyLink Corporation (1995).
-- Permission is granted to the general public to use this
-- file for management of TyLink Products.
--                                                            =
-- Updates to this Enterprise MIB may be obtained from        =
-- TyLink Customer Service 1-800-828-2780.                    =
--                                                            =

TY3250I-MIB DEFINITIONS ::= BEGIN

   IMPORTS

      DisplayString
	 FROM SNMPv2-TC
      Counter, TimeTicks, enterprises, IpAddress
	 FROM RFC1155-SMI
      Gauge
	 FROM RFC1155-SMI
      TRAP-TYPE
	 FROM RFC-1215
      OBJECT-TYPE
	 FROM RFC-1212;

   --  This MIB module uses the extended OBJECT-TYPE macro.

   tylink  OBJECT IDENTIFIER ::= { enterprises 466 }
   ty3250  OBJECT IDENTIFIER ::= { tylink 4 }


   -- textual conventions

       --DisplayString ::=
       --    OCTET STRING
       -- This data type is used to model textual information taken
       -- from the NVT ASCII character set.  By convention, objects
       -- with this syntax are declared as having
       --
       --      SIZE (0..255)


-- *********************************************************************
--                     TY3250I ENTERPRISE SPECIFIC MIB
-- *********************************************************************


-- ======================================================================
--
--  The 3250 MIB Tree
--      This MIB covers the TyLink 3250, a one port T1 CSU/DSU for dedicated
--      applications.  This product is managed  via an integral agent.
--
--  The 3250 MIB Consists of three groups (plus Traps):
--      The SYSTEM group
--      The CONFIGURATION group
--      The MAINTENANCE group
--
--
--      The SYSTEM group
--          This group provides system level attributes of the node.
--
--          The group consists of the following tables:
--              ty3250SysTable       - System level attributes
--
--      The CONFIGURATION group
--          This group provides for configuration of the node.
--
--          The group consists of the following tables:
--              ty3250CfgAppTable    - Application level configuration
--              ty3250CfgT1Table     - T1 port configuration
--              ty3250CfgDteTable    - DTE port configuration
--              ty3250CfgConnectTable - T1 network bandwidth assignment
--              ty3250CfgCommTable  - Maintenance port configuration
--              ty3250CfgSnmpTable   - SNMP configuration
--              ty3250CfgEventDestTable   - NSMS Event Destination Configuration
--              ty3250CfgSupChan     - NSMS Supervisory Channel Configuration
--
--      The MAINTENANCE group
--          This group provides for run-time control of the node.
--
--          The group consists of the following tables:
--              ty3250DiagT1Table    - T1 Port Diagnostics
--              ty3250DiagDteTable   - DTE port diagnostics
--              ty3250DiagBERTable   - Bit Error Rate Tests
--              ty3250T1PerfCurrent  - T1 Performance (user registers)
--              ty3250T1PerfInterval - T1 Performance History (user registers)
--              ty3250T1PerfTotals   - T1 Performance 24 Hr Totals (user registers)
--              ty3250T1PerfCmd      - provides control over perf. registers
--
--      The MIB also contains enterprise trap information:
--             ty3250Trap
--
-- =======================================================================


-- ========================
-- ==   SYSTEM group     ==
-- ========================
--
--       The ty3250SysTable
--              This table contains the system attributes of the 3250 CSU.
      
ty3250SysTable      OBJECT IDENTIFIER ::= { ty3250 1 }

ty3250SysType       OBJECT-TYPE
	  SYNTAX      DisplayString (SIZE (0..10))
	  ACCESS      read-only
	  STATUS      mandatory
	  DESCRIPTION
	     "A textual description of the system model identifier.
	      for example: TYLINK3250"
	  ::= { ty3250SysTable 1 }

ty3250SysSoftRev    OBJECT-TYPE
	  SYNTAX      DisplayString (SIZE (0..10))
	  ACCESS      read-only
	  STATUS      mandatory
	  DESCRIPTION
	     "Displays the Software Revision installed in this node."
	  ::= { ty3250SysTable 2 }

ty3250SysHardRev    OBJECT-TYPE
	  SYNTAX      DisplayString (SIZE (0..10))
	  ACCESS      read-only
	  STATUS      mandatory
	  DESCRIPTION
	     "Displays the Hardware Revision of the node."
	  ::= { ty3250SysTable 3 }

ty3250SysNumT1Installed    OBJECT-TYPE
	  SYNTAX      INTEGER (0..1)
	  ACCESS      read-only
	  STATUS      mandatory
	  DESCRIPTION
	     "The number of network (T1) ports that are
	      installed.  There is 1 on the 3250."
	  ::= { ty3250SysTable 4 }

ty3250SysNumDteInstalled    OBJECT-TYPE
	  SYNTAX      INTEGER (0..1)
	  ACCESS      read-only
	  STATUS      mandatory
	  DESCRIPTION
	     "The number of channels (DTE) that are
	      installed.  There is 1 on the 3250."
	  ::= { ty3250SysTable 5 }

ty3250SysNumCommInstalled    OBJECT-TYPE
	  SYNTAX      INTEGER (0..2)
	  ACCESS      read-only
	  STATUS      mandatory
	  DESCRIPTION
	     "The number of Maintenance ports that are 
	      installed. The front panel MAINT port is for
	      the user interface, the rear panel COMM port
	      is for Lan(Network) Access."
	  ::= { ty3250SysTable 6 }

ty3250SysName       OBJECT-TYPE
	  SYNTAX      DisplayString (SIZE (0..16))
	  ACCESS      read-write
	  STATUS      mandatory
	  DESCRIPTION
	     "The user supplied name of the node.  This object
	      does not affect operation, but may be useful
	      for network management."
	  ::= { ty3250SysTable 7 }

ty3250SysResetNode    OBJECT-TYPE
	  SYNTAX      INTEGER
	  {
	       reset-node (321)
	  }
	  ACCESS      write-only
	  STATUS      mandatory
	  DESCRIPTION
		"Command to reset the node. NODE WILL BE OFF-LINE AND 
		USER DATA WILL BE INTERRUPTED FOR APPROXIMATELY 15 
		SECONDS. "
	  ::= { ty3250SysTable 8 }


-- =========================
-- == CONFIGURATION group ==
-- =========================
--
--       The Application Configuration Table
--              This table contains the Application (system) Configuration
--              information for the 3250 DDS DSU.

-- ty3250CfgAppTable   OBJECT IDENTIFIER ::= { ty3250 2 }

-- ty3250CfgAppClockSource OBJECT-TYPE
--          SYNTAX      INTEGER
--         {
--               internal (1),
--               network (2),
--               dte     (3)
--          }
--          ACCESS      read-write
--          STATUS      mandatory
--          DESCRIPTION
--             "T1 network interface timing source.  There must be only one
--              source on a T1 line.  Node should typically be network (2) 
--              timed on a point-to-network application. Line Driver and 
--              point-to-point applications typically need one node as 
--              internal (1), one as network (2)."  
--          ::= { ty3250CfgAppTable 2 }


--
--       The T1 Configuration Table
--              This table contains the T1 port Configuration
--              information for the 3250 CSU/DSU.

ty3250CfgT1Table   OBJECT IDENTIFIER ::= { ty3250 3 }   
--        DESCRIPTION
--           "The T1 Port Configuration table contains
--            parameters for the Framed TDM (T1) port on the
--            3250. "
	  

ty3250CfgT1Framing    OBJECT-TYPE
	  SYNTAX      INTEGER 
	  {
		d4              (1),
		esf-54016       (2),
		esf-ansi        (3)
--              esf-nsms        (4)
	  }
	  ACCESS        read-write
	  STATUS        mandatory
	  DESCRIPTION
		"Type of Framing on this T1 Line.  Check with your service 
		 provider to determine value.  D4 is also known as 
		 'SuperFrame', ESF is 'Extended SuperFrame'.  ESF provides 
		 enhanced performance monitoring capabilities. ANSI and 
		 54016 refer to the ESF Facility Data Link (FDL)."
		 
	 ::= { ty3250CfgT1Table 1 }

ty3250CfgT1LineEncoding    OBJECT-TYPE
	  SYNTAX      INTEGER 
	  {
		ami             (1),
		b8zs            (2)
	  }
	  ACCESS        read-write
	  STATUS        mandatory
	  DESCRIPTION
		"T1 interface bipolar encoding scheme.  Check with your 
		service provider to determine value. B8ZS, which inherently 
		provides ample 'ones-density', is recommended. AMI users 
		must pay special attention to the 'ones-density' requirements
		of the servic provider."
	 ::= { ty3250CfgT1Table 2 }

ty3250CfgT1Density    OBJECT-TYPE
	  SYNTAX      INTEGER 
	  {
		no-density              (1),
		twelve-half-percent     (2),
		one-in-16               (3),
		one-in-64               (4)
	  }
	  ACCESS        read-write
	  STATUS        mandatory
	  DESCRIPTION
		"CSU 'ones density' monitor. Defines the maximum number of
		consecutive zeros that can be transmitted to the network. 
		If density monitoring is enabled, the composite signal 
		is guaranteed to meet the selected density threshhold at 
		the expense of user data. No-density (4) should be used 
		if B8ZS Line Encoding is chosen or if Channel Density is 
		bit-7-stuff. This option is not applicable if DSX-1 mode 
		is selected."
	  ::= { ty3250CfgT1Table 3 }


ty3250CfgT1Interface    OBJECT-TYPE
	  SYNTAX      INTEGER 
	  {
		dsx-1           (1),
		csu             (2)  
	  }
	  ACCESS        read-write
	  STATUS        mandatory
	  DESCRIPTION
		"Enables CSU-specific functions if CSU (1) is selected. 
		CSU functions include Line Build-out, density monitoring, 
		and certain diagnostic features. Selecting DSX-1 (2) will
		disable these CSU functions for line driver or external
		CSU applications."
	  ::= { ty3250CfgT1Table 4 }


ty3250CfgT1LboSetting    OBJECT-TYPE
	  SYNTAX      INTEGER 
	  {
		zero-db         (2),
		n7-5-db         (3),
		n15-db          (1)
	  }
	  ACCESS        read-write
	  STATUS        mandatory
	  DESCRIPTION
		"CSU Line Build Out. Consult service provider for proper
		setting; either 0dB (1), -7.5dB (2), or -15dB (3). Not
		applicable if T1Interface = dsx1."
	 ::= { ty3250CfgT1Table 5 }


ty3250CfgT1Timing    OBJECT-TYPE
	  SYNTAX      INTEGER 
	  {
		internal        (1),
		loop            (2)
--              dte             (3)
	  }
	  ACCESS        read-write
	  STATUS        mandatory
	  DESCRIPTION
	     "T1 network interface timing source.  There must be only one
	      source on a T1 line.  Node should typically be network (2) 
	      timed on a point-to-network application. Line Driver and 
	      point-to-point applications typically need one node as 
	      internal (1), one as network (2)."  
	 ::= { ty3250CfgT1Table 6 }

ty3250CfgT1CicuitID OBJECT-TYPE
	  SYNTAX  DisplayString (SIZE (0..255))
	  ACCESS  read-write
	  STATUS  mandatory
	  DESCRIPTION
		 "This variable contains the transmission vendor's 
		 circuit identifier, for the purpose of facilitating 
		 troubleshooting."
	  ::= { ty3250CfgT1Table 7 }


-- ty3250CfgT1Personality    OBJECT-TYPE
--       SYNTAX      INTEGER 
--         {
--               user            (1),
--               network         (2)
--         }
--         ACCESS        read-write
--         STATUS        mandatory
--         DESCRIPTION
--               "TBD"
--        ::= { ty3250CfgT1Table 8 }


--
--       The DTE Configuration Table
--              This table contains the DTE port Configuration
--              information for the 3250 CSU/DSU.

ty3250CfgDteTable   OBJECT IDENTIFIER ::= { ty3250 4 }
--        DESCRIPTION
--           "The Dte Port Configuration table contains
--            parameters for the Serial (DTE) port on the
--            3250. "
	  

ty3250CfgDteLineRate    OBJECT-TYPE
	  SYNTAX      INTEGER  (0..1536000)
	  ACCESS        read-write
	  STATUS        mandatory
	  DESCRIPTION
		"Serial Data Rate in bits-per-second, must be multiple
		of 8000bps. For example enter 768000 for 768Kb/s. Valid
		rates depend upon channel density selection: nX56K for 
		bit-7-stuffing, and nX64K for clear-channel (n is an 
		integer 1-24 inclusive)."
	 ::= { ty3250CfgDteTable 1 }

ty3250CfgDteChannelDensity    OBJECT-TYPE
	  SYNTAX      INTEGER  
		{
		bit-7-stuff     (56),
		clear-channel   (64)
		}
	  ACCESS        read-write
	  STATUS        mandatory
	  DESCRIPTION
		"Packing of serial data into T1 DS0's. Bit-7-stuff (56) 
		allows DTE rates of nX56Kb/s and provides sufficient 
		ones-density on any circuit. Clear-channel (64) 
		allows rates on nX64Kb/s and may require an additional
		means of density enforcement (eg, B8ZS)."
	 ::= { ty3250CfgDteTable 2 }

ty3250CfgDteTiming    OBJECT-TYPE
	  SYNTAX      INTEGER  
		{
		loop-1  (1),
		loop-2  (2)
		}
	  ACCESS        read-write
	  STATUS        mandatory
	  DESCRIPTION
		"Serial DTE Transmit Timing mode. Loop-1 (1) uses the clock  
		returned from the DTE (TT/TCE) to sample tx data, Loop-2 (2) 
		uses the clock (ST/TC) generated by the node to sample tx 
		data."
	 ::= { ty3250CfgDteTable 3 }

ty3250CfgDteClockMode    OBJECT-TYPE
	  SYNTAX      INTEGER  
		{
		clock-normal    (1),
		clock-invert    (2)
		}
	  ACCESS        read-write
	  STATUS        mandatory
	  DESCRIPTION
		"Clock-normal samples data with the rising edge of the 
		selected tx clock, clock-invert samples data with the 
		falling edge of the selected tx clock. The tx clock is 
		selected using CfgDteTiming. This clock invertion is 
		most useful when loop-2 timing is used. Only in rare 
		circumstances will clock-invert (2) be used with loop-1 
		timing."
	 ::= { ty3250CfgDteTable 4 }

ty3250CfgDteDataMode    OBJECT-TYPE
	  SYNTAX      INTEGER  
		{
		data-normal     (1),
		data-invert     (2)
		}
	  ACCESS        read-write
	  STATUS        mandatory
	  DESCRIPTION
		"Inverts data.  Can make some applications, particularly
		HDLC-based protocols, meet density requirements even across
		clear channel DS0s in AMI mode. 
		"
	 ::= { ty3250CfgDteTable 5 }

ty3250CfgDteIntfType    OBJECT-TYPE
	  SYNTAX      INTEGER  
		{
		intf-v35       (3),
		intf-rs449     (4)
		}
	  ACCESS        read-write
	  STATUS        mandatory
	  DESCRIPTION
		"Sets the electrical interface for the DTE port."
	  ::= { ty3250CfgDteTable 6 }


--
--       The Connection Configuration Table
--           The Connection Configuration table contains methods for
--           assigning T1 network bandwidth to ports. In auto entry mode
--           the user provides a starting DS0 and the node assigns
--           sequential, contiguous, DS0s; all of the same type (data or
--           voice). In manual entry the user configures each DS0 
--           seperately. In manual mode the DS0s may be assigned 
--           discontiguously and could be a mix of voice and data 
--           circuits. This table also includes deletion and
--           validation utilities.

ty3250CfgConnectTable  OBJECT IDENTIFIER ::= { ty3250 5 }

ty3250CfgConnAutoAssign OBJECT IDENTIFIER ::= { ty3250CfgConnectTable 1 }
--              "Provides T1 network index, starting DS0 and DTE port number
--              for the node to automatically assign the proper amount of
--              bandwidth. Bandwidth requirements are defined by the DTE 
--              Data Rate and DTE Channel Density selections."


ty3250ConnAutoT1Index OBJECT-TYPE
	  SYNTAX      INTEGER (1..4)
	  ACCESS      read-write
	  STATUS      mandatory
	  DESCRIPTION
		"Index to T1 network port of interest. 3250 supports
		one T1 network port (1)"
	  ::= { ty3250CfgConnAutoAssign 1 }

ty3250ConnStartDS0            OBJECT-TYPE
	  SYNTAX        INTEGER
			{
			ds0-01        (1),
			ds0-02        (2),
			ds0-03        (3),
			ds0-04        (4),
			ds0-05        (5),
			ds0-06        (6),
			ds0-07        (7),
			ds0-08        (8),
			ds0-09        (9),
			ds0-10        (10),
			ds0-11        (11),
			ds0-12        (12),
			ds0-13        (13),
			ds0-14        (14),
			ds0-15        (15),
			ds0-16        (16),
			ds0-17        (17),
			ds0-18        (18),
			ds0-19        (19),
			ds0-20        (20),
			ds0-21        (21),
			ds0-22        (22),
			ds0-23        (23),
			ds0-24        (24),
			no-current-connections (40),
			non-continuous-ds0s (41)
			}
	  ACCESS        read-write
	  STATUS        mandatory
	  DESCRIPTION
		"Port1-t1 includes 24 DS0's. This value is the starting DS0  
		used by the node to allocate DS0s to meet port2-dte's 
		requirements. Sequential, contiguous DS0s are assigned. 
		The number of DS0s required is based upon the DTE Data Rate 
		and DTE Channel Mapping. The node's response to an entry  
		may be gathered by querying ty3250ConnAutoStatus. To assign 
		DS0s in a non-contiguous format, use the CfgEditConnTable."
	  ::= { ty3250CfgConnAutoAssign 2 }

ty3250ConnAutoPort            OBJECT-TYPE
	  SYNTAX        INTEGER
			{
			port1-t1      (1),
			port2-dte     (2),
--                      port3         (3),
--                      port4         (4),
			not-connected (33)
			}
	  ACCESS        read-write
	  STATUS        mandatory
	  DESCRIPTION
		"Selects the port for which DS0s are automatically
		allocated to on the T1 network port. Node software may
		not allow connection of port1-t1 to port1-t1."
	  ::= { ty3250CfgConnAutoAssign 3 }

ty3250ConnAutoType            OBJECT-TYPE
	  SYNTAX        INTEGER
			{
			data (1),
			voice (2)
			}
	  ACCESS        read-write
	  STATUS        mandatory
	  DESCRIPTION
		"Defines the type of traffic being transported. The 3250
		only supports data (1). The selected type will be assigned
		to all DS0s."

	  ::= { ty3250CfgConnAutoAssign 4 }


ty3250ConnDteRate             OBJECT-TYPE
	  SYNTAX        INTEGER (0..1536000)
	  ACCESS        read-only
	  STATUS        mandatory
	  DESCRIPTION
		"Data rate of the 3250's DTE port. Can be changed from
		the CfgDteTable."

	  ::= { ty3250CfgConnAutoAssign 5 }

ty3250ConnDteDensity          OBJECT-TYPE
	  SYNTAX        INTEGER 
			{
			bit-7-stuff     (56),
			clear-channel   (64)
			}
	  ACCESS        read-only
	  STATUS        mandatory
	  DESCRIPTION
		"Channel/DS0 format for the 3250's DTE port. Can be 
		changed from the CfgDteTable."

	  ::= { ty3250CfgConnAutoAssign 6 }

ty3250ConnDs0Required         OBJECT-TYPE
	  SYNTAX        INTEGER (0..24)
	  ACCESS        read-only
	  STATUS        mandatory
	  DESCRIPTION
		"The number of DS0s required by the node's DTE port. 
		This is based upon the DTE data rate and channel density 
		selections."
		
		::= { ty3250CfgConnAutoAssign 7 }


ty3250ConnAutoStatus         OBJECT-TYPE  
	  SYNTAX       INTEGER
			{
			connections-valid (1),
			incorrect-bandwidth (2),
			bandwidth-conflict (3),
			no-current-connections(4)
			}
	  ACCESS       read-only
	  STATUS       mandatory
	  DESCRIPTION
	  "Queries the node's connection status. Cause codes
	  will be returned when a connection set is rejected."
	  ::= { ty3250CfgConnAutoAssign 8 }             


ty3250CfgCurrentConnTable OBJECT-TYPE
	  SYNTAX       SEQUENCE OF Ty3250CfgCurrentConnections
	  ACCESS       not-accessible
	  STATUS       mandatory
	  DESCRIPTION
	     "Retrieves node's active connections assignments for 
	     display only. To edit connections, use CfgConnAutoAssign  
	     or CfgEditConnTable."
	  ::= { ty3250CfgConnectTable 2 }

ty3250CfgCurrentConnections OBJECT-TYPE
	  SYNTAX  Ty3250CfgCurrentConnections
	  ACCESS  not-accessible
	  STATUS      mandatory
	  DESCRIPTION
		"An entry in the Current Connections Table."
	  INDEX { ty3250T1Index, ty3250Ds0 }
	  ::= { ty3250CfgCurrentConnTable 1 }

Ty3250CfgCurrentConnections ::=
	  SEQUENCE 
	  {
		ty3250T1Index        INTEGER,
		ty3250Ds0            INTEGER,
		ty3250DtePort        INTEGER,
		ty3250Type           INTEGER
	  }

ty3250T1Index   OBJECT-TYPE
	  SYNTAX      INTEGER (1..4)
	  ACCESS      read-only
	  STATUS      mandatory
	  DESCRIPTION
		"Index to T1 network port of interest. 3250 only supports
		one T1 network port (1)"
	  ::= { ty3250CfgCurrentConnections 1 }

ty3250Ds0       OBJECT-TYPE
	  SYNTAX        INTEGER (1..24)
	  ACCESS        read-only
	  STATUS        mandatory
	  DESCRIPTION
		"DS0 number 1 through 24 corresponding to the T1 network
		port index"
	  ::= { ty3250CfgCurrentConnections 2 }

ty3250DtePort   OBJECT-TYPE
	  SYNTAX        INTEGER
			{
			port1-t1      (1),
			port2-dte     (2),
--                      port3         (3),
--                      port4         (4),
			not-connected (33)
			}
	  ACCESS        read-only
	  STATUS        mandatory
	  DESCRIPTION
		"DS0 assignment for indexed T1 network port. After 
		making any adjustments to the connections, the 
		ty3250CfgConnUpdateCmd must be sent. Node software 
		may not permit port1-t1 connections to itself."
	  ::= { ty3250CfgCurrentConnections 3 }

ty3250Type                    OBJECT-TYPE
	  SYNTAX        INTEGER
			{
			data (1),
			voice (2)
			}
	  ACCESS        read-only
	  STATUS        mandatory
	  DESCRIPTION
		"Defines the type of traffic being transported. The 3250
		only supports data (1)."

	  ::= { ty3250CfgCurrentConnections 4 }


ty3250CfgEditConnMenu OBJECT IDENTIFIER ::= { ty3250CfgConnectTable 3 }             

ty3250CfgEditConnCopyCurrtoEdit   OBJECT-TYPE
	  SYNTAX        INTEGER
			{
			copy-current (1)
			}
	  ACCESS        write-only
	  STATUS        mandatory
	  DESCRIPTION
		"Fill the edit buffer with the node's current active
		 connections."
	  ::= { ty3250CfgEditConnMenu 1 }             


ty3250CfgEditConnTable OBJECT-TYPE 
	  SYNTAX       SEQUENCE OF Ty3250CfgEditConnEntry
	  ACCESS       not-accessible
	  STATUS       mandatory
	  DESCRIPTION
	     "Edits current DS0 assignment. After making any adjustments 
	     to the connections, the ty3250CfgConnUpdateCmd must be sent."
	  ::= { ty3250CfgEditConnMenu 2 }             

ty3250CfgEditConnEntry OBJECT-TYPE
	  SYNTAX       Ty3250CfgEditConnEntry
	  ACCESS       not-accessible
	  STATUS       mandatory
	  DESCRIPTION
	     "An entry in the Edit Connections table."
	  INDEX { ty3250ConnT1Index, ty3250ConnDS0 }

	  ::= { ty3250CfgEditConnTable 1 }             
	
Ty3250CfgEditConnEntry ::=
	  SEQUENCE 
		{
		ty3250ConnT1Index INTEGER,
		ty3250ConnDS0 INTEGER,
		ty3250ConnDTE INTEGER,
		ty3250ConnType INTEGER
		}

ty3250ConnT1Index OBJECT-TYPE
	  SYNTAX      INTEGER (1..4)
	  ACCESS      read-only
	  STATUS      mandatory
	  DESCRIPTION
		"Index to T1 network port of interest. 3250 only supports
		one T1 network port (1)"
	  ::= { ty3250CfgEditConnEntry 1 }

ty3250ConnDS0        OBJECT-TYPE
	  SYNTAX        INTEGER (1..24)
	  ACCESS        read-only
	  STATUS        mandatory
	  DESCRIPTION
		"DS0 number 1 through 24 corresponding to the T1 network
		port index"
	  ::= { ty3250CfgEditConnEntry 2 }

ty3250ConnDTE        OBJECT-TYPE
	  SYNTAX        INTEGER
			{
			port1-t1      (1),
			port2-dte     (2),
--                      port3         (3),
--                      port4         (4),
			not-connected (33)
			}
	  ACCESS        read-write
	  STATUS        mandatory
	  DESCRIPTION
		"DS0 assignment for indexed T1 network port. After making 
		any adjustments to the connections, the ty3250CfgConnUpdateCmd 
		must be sent. Node software may not permit connections between
		port1-t1 and itself."
	  ::= { ty3250CfgEditConnEntry 3 }

ty3250ConnType       OBJECT-TYPE
	  SYNTAX        INTEGER
			{
			data (1),
			voice (2)
			}
	  ACCESS        read-write
	  STATUS        mandatory
	  DESCRIPTION
		"defines the type of traffic being transported. The 3250
		only supports data (1)."
	  ::= { ty3250CfgEditConnEntry 4 }



ty3250CfgConnUpdate OBJECT IDENTIFIER ::= { ty3250CfgEditConnMenu 3 }             


ty3250CfgConnUpdateCmd        OBJECT-TYPE
	  SYNTAX        INTEGER
			{
			update (1)
			}
	  ACCESS        write-only
	  STATUS        mandatory
	  DESCRIPTION
		"Updates the connections with the edit buffer. The edit buffer
		is comprised of any changes sent (set) from the CfgEditConnTable."
	  ::= { ty3250CfgConnUpdate 1 }             

ty3250CfgConnStatus             OBJECT-TYPE
	  SYNTAX          INTEGER
			  {
			  connections-valid (1),
			  incorrect-bandwidth (2),
			  bandwidth-conflict (3),
			  no-current-connections(4)
			  }
	  ACCESS        read-only
	  STATUS        mandatory
	  DESCRIPTION
		"Displays node status from the last connection update."
	  ::= { ty3250CfgConnUpdate 2 }             

ty3250CfgEditConnClearEditBuff    OBJECT-TYPE
	  SYNTAX        INTEGER
			{
			clear-edit (1)
			}
	  ACCESS        write-only
	  STATUS        mandatory
	  DESCRIPTION
		"Removes all changes from edit buffer. The edit buffer is 
		comprised of any changes sent (set) from the CfgEditConnTable."
	  ::= { ty3250CfgEditConnMenu 4 }             


--
--       The COMM PORT Configuration Table
--              This table contains the configuration options for 
--              the asynchronous RS232 ports. A typical set-up 
--              uses one port for an ASCII terminal User Interface 
--              and one for Lan(Network) access functions.


ty3250CfgCommTable OBJECT IDENTIFIER ::= { ty3250 6}
--        DESCRIPTION   
--           "The Communication Ports Configuration table contains
--            parameters for the RS232/RJ48 ports on the
--            3250.  The User Interface (ASCII) Port is Index=1; 
--            the Lan(Network) access port is 2"



ty3250CfgCommFormat OBJECT-TYPE
	  SYNTAX SEQUENCE OF Ty3250CfgCommIntf
	  ACCESS        not-accessible
	  STATUS        mandatory
	  ::= { ty3250CfgCommTable 1 }


ty3250CfgCommIntf     OBJECT-TYPE
	  SYNTAX      Ty3250CfgCommIntf
	  ACCESS      not-accessible
	  STATUS      mandatory
	  DESCRIPTION
	     "Configuration of electrical interface and character 
	     format of the communications ports."
	  INDEX { ty3250CfgCommIndex }
	  ::= { ty3250CfgCommFormat 1 }

Ty3250CfgCommIntf ::=
	  SEQUENCE
	  {
	       ty3250CfgCommIndex    INTEGER,
	       ty3250CfgCommBaud     INTEGER,
	       ty3250CfgCommDataBits INTEGER,
	       ty3250CfgCommStopBits INTEGER,
	       ty3250CfgCommParity   INTEGER,
	       ty3250CfgCommFlowCtrl INTEGER
	  } 

ty3250CfgCommIndex  OBJECT-TYPE
	  SYNTAX INTEGER
		 {    
		 comm (1),
		 maint (2)
		 }
	  ACCESS      read-only
	  STATUS      mandatory
	  DESCRIPTION
		"The comm (1) is at the rear and the maint (2) is at 
		the front of the box."
	  ::= { ty3250CfgCommIntf 1 }


ty3250CfgCommBaud OBJECT-TYPE
	  SYNTAX      INTEGER
	  {
	      baud-1200 (1),
	      baud-2400 (2),
	      baud-4800 (3),
	      baud-9600 (4),
	      baud-19200 (5),
	      baud-38400 (6)
	  }
	  ACCESS      read-write
	  STATUS      mandatory
	  DESCRIPTION
	     "Baud rate for this Communication port.  Values are
	      baud-1200 (1), baud-2400 (2), baud-4800 (3),
	      baud-9600 (4), baud-19200 (5), baud-38400 (6)."
	  ::= { ty3250CfgCommIntf 2 }


ty3250CfgCommDataBits OBJECT-TYPE
	  SYNTAX      INTEGER
	  {
	      databits-7 (1),
	      databits-8 (2)
	  }
	  ACCESS      read-write
	  STATUS      mandatory
	  DESCRIPTION
	     "Databits for this Communication port.  Values
	      are databits-7 (1) and databits-8 (2)."
	  ::= { ty3250CfgCommIntf 3 }

ty3250CfgCommStopBits OBJECT-TYPE
	  SYNTAX      INTEGER
	  {
	      stopbits-1 (1),
	      stopbits-1-5 (2),
	      stopbits-2 (3)
	  }
	  ACCESS      read-write
	  STATUS      mandatory
	  DESCRIPTION
	     "Number of Stopbits for this Communication port.
	      Values are stopbits-1 (1), stopbits-1-5 (2),
	      and stopbits-2 (3)."
	  ::= { ty3250CfgCommIntf 4 }


ty3250CfgCommParity OBJECT-TYPE
	  SYNTAX      INTEGER
	  {
	      no-parity   (1),
	      odd-parity  (2),
	      even-parity (3)
	  }
	  ACCESS      read-write
	  STATUS      mandatory
	  DESCRIPTION
	     "Parity for this Communication port.  Values are
	      no-parity (1), odd-parity (2), even-parity (3)."
	  ::= { ty3250CfgCommIntf 5 }



ty3250CfgCommFlowCtrl OBJECT-TYPE
	  SYNTAX      INTEGER
	  {
	      no-flow-control (1),
	      software-flow-control  (2),
	      hardware-flow-control  (3)
	  }
	  ACCESS      read-write
	  STATUS      mandatory
	  DESCRIPTION
	     "Flow Control for this Communication port.  Values
	      are off-flow-control (1) and on-flow-control (2)."
	  ::= { ty3250CfgCommIntf 6 }


ty3250CfgCommModeTable  OBJECT-TYPE
	  SYNTAX        SEQUENCE OF Ty3250CfgCommMode
	  ACCESS        not-accessible
	  STATUS        mandatory
	  ::= { ty3250CfgCommTable 2 }


ty3250CfgCommModeEntry  OBJECT-TYPE
	  SYNTAX      Ty3250CfgCommMode
	  ACCESS      not-accessible
	  STATUS      mandatory
	  DESCRIPTION
		"Ascii communication port configuration."
	  INDEX { ty3250CfgCommModeIndex }
	  ::= { ty3250CfgCommModeTable 1 }

Ty3250CfgCommMode ::=
	  SEQUENCE
	  {
	       ty3250CfgCommModeIndex    INTEGER,
	       ty3250CfgCommMode         INTEGER,
	       ty3250CfgCommMyIP     IpAddress,
	       ty3250CfgCommPeerIP   IpAddress,
	       ty3250CfgCommMask     IpAddress,
	       ty3250CfgCommMaxMTU   INTEGER
	  } 

ty3250CfgCommModeIndex  OBJECT-TYPE
	  SYNTAX INTEGER
		 {    
		 comm (1),
		 maint (2)
		 }
	  ACCESS read-write
	  STATUS mandatory
	  DESCRIPTION
		"Communication port configured as user interface. 
		The comm (1) is at the rear and the maint (2) is 
		at the front of the box. The 3250 may require that
		the maint (2) port be used for user interface only."
	  ::= { ty3250CfgCommModeEntry 1}  

ty3250CfgCommMode  OBJECT-TYPE
	  SYNTAX INTEGER
		 {    
		 user-interface-vt100 (1),
		 slip (2),
         ethernet (3),
         token-ring (4)
		 }
	  ACCESS read-write
	  STATUS mandatory
	  DESCRIPTION
	     "Defines mode of operation of the selected communication 
	     port. The 3250 may require that the user-interface be 
	     assigned to the Maint port and a Network access type be 
         assigned to the COMM port."
	  ::= { ty3250CfgCommModeEntry 2}

ty3250CfgCommMyIP   OBJECT-TYPE
	  SYNTAX      IpAddress
	  ACCESS      read-write
	  STATUS      mandatory
	  DESCRIPTION
	     "The IP address for this node's network access port."
	  ::= { ty3250CfgCommModeEntry 3 }
 
ty3250CfgCommPeerIP   OBJECT-TYPE
	  SYNTAX      IpAddress
	  ACCESS      read-write
	  STATUS      mandatory
	  DESCRIPTION
	     "The IP address for other end of network access connection."
	  ::= { ty3250CfgCommModeEntry 4 }
 
ty3250CfgCommMask   OBJECT-TYPE
	  SYNTAX      IpAddress
	  ACCESS      read-write
	  STATUS      mandatory
	  DESCRIPTION
	     "The IP Network Mask (eg 255.255.255.0) for the
	      network access link."
	  ::= { ty3250CfgCommModeEntry 5 }
 
ty3250CfgCommMaxMTU OBJECT-TYPE
	  SYNTAX      INTEGER  (1..2048)
	  ACCESS      read-write
	  STATUS      mandatory
	  DESCRIPTION
	     "The Maximum Transmission Unit is the size of the
	      largest IP packet supported.  This value should
	      be set to the lowest value supported by any
	      equipment in the transmission path."  
	  ::= { ty3250CfgCommModeEntry 6 }


--
--       The SNMP Configuration Table
--              This table contains the SNMP Configuration
--              information for the 3250 CSU/DSU.
--
ty3250CfgSnmpTable OBJECT-TYPE 
	  SYNTAX        SEQUENCE OF Ty3250SnmpEntry
	  ACCESS        not-accessible
	  STATUS        mandatory
	  DESCRIPTION
	  "IP addresses and corresponding trap filters."

	  ::= { ty3250 7}

 
ty3250SnmpEntry OBJECT-TYPE
	  SYNTAX        Ty3250SnmpEntry
	  ACCESS        not-accessible
	  STATUS        mandatory
	  DESCRIPTION
	  "entry of IP addresses and corresponding trap filters."
	  INDEX { ty3250SnmpIndex }
	  ::= { ty3250CfgSnmpTable 1 }

Ty3250SnmpEntry ::=

	  SEQUENCE
	  {
	  ty3250SnmpIndex INTEGER (1..6),
	  ty3250SnmpManagerIP IpAddress
--        ty3250SnmpTrapFilterTable
	  }

ty3250SnmpIndex   OBJECT-TYPE
	  SYNTAX      INTEGER (1..6)
	  ACCESS      read-write
	  STATUS      mandatory
	  DESCRIPTION
	  "The index to one of the SNMP manager's address and filter
	  configurations."
	  ::= { ty3250SnmpEntry 1 }


ty3250SnmpManagerIP   OBJECT-TYPE
	  SYNTAX      IpAddress
	  ACCESS      read-write
	  STATUS      mandatory
	  DESCRIPTION
	     "The IP address for the SNMP manager to receive
	      this node's TRAPs."
	  ::= { ty3250SnmpEntry 2 }


-- ty3250SnmpTrapFilterTable  OBJECT-TYPE
--        SYNTAX      SEQUENCE OF Ty3250SnmpTrapFilter
--        ACCESS      read-write
--        STATUS      mandatory
--        DESCRIPTION
--           "The trap filter for this SNMP manager."
--        ::= { ty3250SnmpEntry 3 }    

-- 
-- ty3250SnmpTrapFilterEntry  OBJECT-TYPE
--        SYNTAX      ty3250SnmpTrapFilterEntry
--        ACCESS      read-write
--        STATUS      mandatory
--        DESCRIPTION
--           "The trap filter for this SNMP manager."
--        INDEX { 
--            
--        ::= { ty3250SnmpTrapFilterTable 1 }
-- 


-- Ty3250SnmpTrapFilterEntry ::=
-- 
--        SEQUENCE
--        {
--             ty3250NoTraps INTEGER,
--             ty3250AllTraps INTEGER, 
--             ty3250TrapColdStart INTEGER, 
--             ty3250TrapAuthentication INTEGER, 
--             ty3250TrapT1CarrierLoss INTEGER,
--             ty3250TrapT1CarrierDetect INTEGER,
--             ty3250TrapT1SyncLossDeclare INTEGER,
--             ty3250TrapT1SyncAcquire INTEGER, 
--             ty3250TrapT1RedAlarmDeclare INTEGER,
--             ty3250TrapT1RedAlarmClear INTEGER, 
--             ty3250TrapT1YellowAlarmDetect INTEGER,
--             ty3250TrapT1YellowAlarmClear INTEGER, 
--             ty3250TrapT1AisDetect INTEGER,
--             ty3250TrapT1AisClear INTEGER, 
--             ty3250TrapT1ControlledSlip INTEGER,
--             ty3250TrapSysConfigurationUpdate INTEGER,
--             ty3250TrapSysDiagnosticState INTEGER, 
--             ty3250TrapSysDiagnosticClear INTEGER
--        }
-- 
-- ty3250NoTraps   OBJECT-TYPE
--        SYNTAX      INTEGER 
--                    {
--                    disble-traps (0),
--                    enable-traps (1)
--                    }
--        ACCESS      read-write
--        STATUS      mandatory
--        DESCRIPTION
--        "globally disables all traps to associated IP address or
--        enables traps on one or more events."
--        ::= { ty3250SnmpTrapFilter 1 }
-- 
-- ty3250AllTraps  OBJECT-TYPE
--        SYNTAX      INTEGER 
--                    {
--                    all-traps (0),
--                    custom (1)
--                    }
--        ACCESS      read-write
--        STATUS      mandatory
--        DESCRIPTION
--        "Allows either the enabling of all traps (0) or the 
--        filtering of  individual trap events from the manager (1)."
--        ::= { ty3250SnmpTrapFilter 2 }
-- 
-- ty3250TrapColdStart  OBJECT-TYPE
--        SYNTAX      INTEGER 
--                    {
--                    disable-event (0),
--                    enable-event (1)
--                    }
--        ACCESS      read-write
--        STATUS      mandatory
--        DESCRIPTION
--        "Disables (0) or enables (1) this trap event to the manager."
--        
--        ::= { ty3250SnmpTrapFilter 3 }
-- 
-- ty3250TrapAuthentication  OBJECT-TYPE
--        SYNTAX      INTEGER 
--                    {
--                    disable-event (0),
--                    enable-event (1)
--                    }
--        ACCESS      read-write
--        STATUS      mandatory
--        DESCRIPTION
--        "Disables (0) or enables (1) this trap event to the manager."
--        
--        ::= { ty3250SnmpTrapFilter 4 }
-- 
-- ty3250TrapT1CarrierLoss  OBJECT-TYPE
--        SYNTAX      INTEGER 
--                    {
--                    disable-event (0),
--                    enable-event (1)
--                    }
--        ACCESS      read-write
--        STATUS      mandatory
--        DESCRIPTION
--        "Disables (0) or enables (1) this trap event to the manager."
--        
--        ::= { ty3250SnmpTrapFilter 5 }
-- 
-- ty3250TrapT1CarrierDetect  OBJECT-TYPE
--        SYNTAX      INTEGER 
--                    {
--                    disable-event (0),
--                    enable-event (1)
--                    }
--        ACCESS      read-write
--        STATUS      mandatory
--        DESCRIPTION
--        "Disables (0) or enables (1) this trap event to the manager."
--        
--        ::= { ty3250SnmpTrapFilter 6 }
-- 
-- ty3250TrapT1SyncLossDeclare  OBJECT-TYPE
--        SYNTAX      INTEGER 
--                    {
--                    disable-event (0),
--                    enable-event (1)
--                    }
--        ACCESS      read-write
--                STATUS      mandatory
--                DESCRIPTION
--                "Disables (0) or enables (1) this trap event to the manager."
--                
--                ::= { ty3250SnmpTrapFilter 7 }
--      
--      ty3250TrapT1SyncAcquire  OBJECT-TYPE
--        SYNTAX      INTEGER 
--                    {
--                    disable-event (0),
--                    enable-event (1)
--                    }
--        ACCESS      read-write
--        STATUS      mandatory
--        DESCRIPTION
--        "Disables (0) or enables (1) this trap event to the manager."
--        
--        ::= { ty3250SnmpTrapFilter 8 }
-- 
-- ty3250TrapT1RedAlarmDeclare  OBJECT-TYPE
--        SYNTAX      INTEGER 
--                    {
--                    disable-event (0),
--                    enable-event (1)
--                    }
--        ACCESS      read-write
--        STATUS      mandatory
--        DESCRIPTION
--        "Disables (0) or enables (1) this trap event to the manager."
--        
--        ::= { ty3250SnmpTrapFilter 9 }
-- 
-- ty3250TrapT1RedAlarmClear  OBJECT-TYPE
--        SYNTAX      INTEGER 
--                    {
--                    disable-event (0),
--                    enable-event (1)
--                    }
--        ACCESS      read-write
--        STATUS      mandatory
--        DESCRIPTION
--        "Disables (0) or enables (1) this trap event to the manager."
--        
--        ::= { ty3250SnmpTrapFilter 10 }
-- 
-- ty3250TrapT1YellowAlarmDetect  OBJECT-TYPE
--        SYNTAX      INTEGER 
--                    {
--                    disable-event (0),
--                    enable-event (1)
--                    }
--        ACCESS      read-write
--        STATUS      mandatory
--        DESCRIPTION
--        "Disables (0) or enables (1) this trap event to the manager."
--                
--                ::= { ty3250SnmpTrapFilter 11 }
--      
--      ty3250TrapT1YellowAlarmClear  OBJECT-TYPE
--                SYNTAX      INTEGER 
--                            {
--                            disable-event (0),
--                    enable-event (1)
--                    }
--        ACCESS      read-write
--        STATUS      mandatory
--        DESCRIPTION
--        "Disables (0) or enables (1) this trap event to the manager."
--        
--        ::= { ty3250SnmpTrapFilter 12 }
-- 
-- ty3250TrapT1AisDetect  OBJECT-TYPE
--        SYNTAX      INTEGER 
--                    {
--                    disable-event (0),
--                    enable-event (1)
--                    }
--        ACCESS      read-write
--        STATUS      mandatory
--        DESCRIPTION
--        "Disables (0) or enables (1) this trap event to the manager."
--        
--        ::= { ty3250SnmpTrapFilter 13 }
-- 
-- ty3250TrapT1AisClear  OBJECT-TYPE
--        SYNTAX      INTEGER 
--                    {
--                    disable-event (0),
--                    enable-event (1)
--                    }
--        ACCESS      read-write
--        STATUS      mandatory
--        DESCRIPTION
--        "Disables (0) or enables (1) this trap event to the manager."
--        
--        ::= { ty3250SnmpTrapFilter 14 }
-- 
-- ty3250TrapT1ControlledSlip  OBJECT-TYPE
--        SYNTAX      INTEGER 
--                    {
--                    disable-event (0),
--                    enable-event (1)
--                    }
--        ACCESS      read-write
--        STATUS      mandatory
--        DESCRIPTION
--        "Disables (0) or enables (1) this trap event to the manager."
--        
--        ::= { ty3250SnmpTrapFilter 15 }
-- 
--      ty3250TrapSysConfigurationUpdate  OBJECT-TYPE
--                SYNTAX      INTEGER 
--                            {
--                            disable-event (0),
--                            enable-event (1)
--                            }
--                ACCESS      read-write
--        STATUS      mandatory
--        DESCRIPTION
--        "Disables (0) or enables (1) this trap event to the manager."
--        
--        ::= { ty3250SnmpTrapFilter 16 }
--
-- ty3250TrapSysDiagnosticState  OBJECT-TYPE
--        SYNTAX      INTEGER 
--                    {
--                    disable-event (0),
--                    enable-event (1)
--                    }
--        ACCESS      read-write
--        STATUS      mandatory
--        DESCRIPTION
--        "Disables (0) or enables (1) this trap event to the manager."
--        
--        ::= { ty3250SnmpTrapFilter 17 }
--      
--      ty3250TrapSysDiagnosticClear  OBJECT-TYPE
--                SYNTAX      INTEGER 
--                            {
--                            disable-event (0),
--                            enable-event (1)
--                            }
--                ACCESS      read-write
--                STATUS      mandatory
--                DESCRIPTION
--                "Disables (0) or enables (1) this trap event to the manager."
--                
--                ::= { ty3250SnmpTrapFilter 18 }
--      
--



--
--       The Event Destination Configuration Table
--              This table contains the Event Destination Configuration
--              information for the TYVIEW MODE 3250 CSU/DSU.

-- ty3250CfgEventDestTableTable   OBJECT-TYPE   
--           SYNTAX      SEQUENCE OF Ty3250CfgEventDestEntry
--           ACCESS      not-accessible
--           STATUS      mandatory
--           DESCRIPTION
--              "The Event Destination Configuration table contains
--              ... for the TyLink 3250. "
--           ::= { ty3250 8 }


--
--       The Supervisory Channel Configuration Table
--              This table contains the NSMS Mode Supervisory Channel Configuration
--              information for the 3250 CSU/DSU.

-- ty3250CfgSupChanTable   OBJECT-TYPE   
--           SYNTAX      SEQUENCE OF Ty3250CfgSupChanEntry
--           ACCESS      not-accessible
--           STATUS      mandatory
--           DESCRIPTION
--              "The Supervisory Channel Configuration table contains
--               ... for the TyLink 3250. "
--           ::= { ty3250 9 }




-- ========================
-- ==   MAINTENANCE group    ==
-- ========================
--
--       The ty3250DiagT1Table
--              This table contains the T1 level diagnostics of the 3250 CSU.
--

ty3250DiagT1Table   OBJECT IDENTIFIER ::= { ty3250 10 }
--        DESCRIPTION
--           "Network (T1) Diagnostics for the TyLink 3250. "
	  

ty3250DiagT1LocLineLpbk OBJECT-TYPE
	  SYNTAX      INTEGER
		{
		line-lpbk-disable       (1),
		line-lpbk-enable        (2)
		}
	  ACCESS      read-write
	  STATUS      mandatory
	  DESCRIPTION
	     "Local Line Loopback on the T1 network port. Data and 
	     framing received from the network is transmitted back 
	     to the network"
	  ::= { ty3250DiagT1Table 1 }

ty3250DiagT1LocPylLpbk OBJECT-TYPE
	  SYNTAX      INTEGER
		{
		pyl-lpbk-disable        (1),
		pyl-lpbk-enable         (2)
		}
	  ACCESS      read-write
	  STATUS      mandatory
	  DESCRIPTION
	     "Local Payload Loopback on the T1 network port. Data 
	     (NOT framing) received from the network is reframed 
	     and transmitted back to the network. "
	  ::= { ty3250DiagT1Table 2 }

ty3250DiagT1LocAggrLpbk OBJECT-TYPE
	  SYNTAX      INTEGER
		{
		aggr-lpbk-disable       (1),
		aggr-lpbk-enable        (2)
		}
	  ACCESS      read-write
	  STATUS      mandatory
	  DESCRIPTION
	     "Local Aggregate Loopback on the T1 network port. Data 
	     from the DTE is framed for transmission and looped back 
	     through the network receiver towards the DTE."
	  ::= { ty3250DiagT1Table 3 }

ty3250DiagT1RmtLpbkStatus OBJECT-TYPE
	  SYNTAX      INTEGER
		{
		no-remote-lpbks         (1),
		csu-lpbk-from-remote    (2),
		dsu-lpbk-from-remote    (3),
		pyl-lpbk-from-remote    (4),
		csu-lpbk-sent-to-remote      (5),
		dsu-lpbk-sent-to-remote      (6)
		}
	  ACCESS      read-only
	  STATUS      mandatory
	  DESCRIPTION
	     "Status of Remote Loopbacks received from the T1 network port.
	       csu-lpbk-from-remote (1) indicates the node is in a Network Line
	       Loopback state due to the reception of the CSU Loop-up pattern
	       from the network.
	       dsu-lpbk-from-remote (2) indicates the node is in a Network Line
	       Loopback state due to the reception of the TyLink proprietary 
	       Loop-up pattern a remote node.
	       pyl-lpbk-from-remote (3) indicates the node is in a Payload 
	       Loopback state due to the reception of the Facility Data Link's 
	       Loop-up pattern from the network (ESF only).
	       csu-lpbk-sent-to-remote (4) indicates the node sent a csu loop up
	       pattern to the remote. The node doesn't know if the loopback was
	       accepted by the remote unit.
	       dsu-lpbk-sent-to-remote (5) indicates the node sent a dsu loop up
	       pattern to the remote. The node doesn't know if the loopback was
	       accepted by the remote unit."

	  ::= { ty3250DiagT1Table 4 }

ty3250DiagT1RmtLpbkCmd OBJECT-TYPE
	  SYNTAX      INTEGER
		{
		rmt-csu-lpbk-loopup     (1),
		rmt-csu-lpbk-loopdown   (2),
		rmt-dsu-lpbk-loopup     (3),
		rmt-dsu-lpbk-loopdown   (4)
		}
	  ACCESS      write-only
	  STATUS      mandatory
	  DESCRIPTION
	     "Remote loopbacks that can be transmitted out the T1 network port.
		rmt-csu-lpbk-loopup (1) sends standard CSU loop up code into
		the network.
		rmt-csu-lpbk-loopdown (2) sends standard CSU loop down code 
		into the network.
		rmt-dsu-lpbk-loopup (3) sends TyLink proprietary loop up code 
		into the network.
		rmt-dsu-lpbk-loopdown (4) sends TyLink proprietary loop up 
		code into the network."
	  ::= { ty3250DiagT1Table 5 }


--
--       The ty3250DiagDteTable
--              This table contains the DTE level diagnostics of the 3250 CSU.
--

ty3250DiagDteTable   OBJECT IDENTIFIER ::= { ty3250 11 }
--        DESCRIPTION
--           "DTE Diagnostics for the TyLink 3250. "
	  

ty3250DiagDteLocBidirLpbk OBJECT-TYPE
	  SYNTAX      INTEGER
		{
		bidir-lpbk-disable      (1),
		bidir-lpbk-enable       (2)
		}
	  ACCESS      read-write
	  STATUS      mandatory
	  DESCRIPTION
	     "Local Bi-directional Loopback on the DTE port. Loops the clock 
	     and data back to the DTE at the interface on the 3250; also 
	     loops the DTE's network bandwidth back to the network."
	  ::= { ty3250DiagDteTable 1 }

ty3250DiagDteRmtLpbkStatus OBJECT-TYPE
	  SYNTAX      INTEGER
		{
		no-remote-lpbks         (1),
		bidir-lpbk-from-remote  (2),
		bidir-lpbk-sent-to-remote (3)
		}
	  ACCESS      read-only
	  STATUS      mandatory
	  DESCRIPTION
	     "Status of Remote Loopbacks received for the DTE port. 
	       bidir-lpbk-from-remote indictaes that either a proprietary
	       or V54 loop up pattern was received on the DTE's network
	       bandwidth.
	       bidir-lpbk-sent-to-remote indiactes that either a 
	       proprietary or V54 loop up pattern was sent to the remote 
	       DTE. "
	  ::= { ty3250DiagDteTable 2 }

ty3250DiagDteRmtLpbkCmd OBJECT-TYPE
	  SYNTAX      INTEGER
		{
		rmt-bidir-lpbk-loopup-tyl   (1),
		rmt-bidir-lpbk-loopdown-tyl (2),
		rmt-bidir-lpbk-loopup-v54   (3),
		rmt-bidir-lpbk-loopdown-v54 (4)
		}
	  ACCESS      write-only
	  STATUS      mandatory
	  DESCRIPTION
	     "Remote loopbacks that can be transmitted to a remote DTE port
		rmt-bidir-lpbk-loopup-tyl (1) sends the TyLink proprietary             
		loop up pattern to a remote TyLink DTE. When detected by the
		remote unit, a DTE Bidirectional Loopback is put up.
		rmt-bidir-lpbk-loopdown-tyl (2) sends the TyLink proprietary             
		loop down pattern to a remote TyLink DTE. When detected by the
		remote unit, a DTE Bidirectional Loopback is torn down.
		rmt-bidir-lpbk-loopup-V54 (3) sends the standard V.54             
		loop up pattern to a remote, V54-compatible DTE. When 
		detected by the remote unit, a DTE Bidirectional Loopback 
		is put up.
		rmt-bidir-lpbk-loopdown-V54 (4) sends the standard V.54             
		loop down pattern to a remote, V54-compatible DTE. When 
		detected by the remote unit, a DTE Bidirectional Loopback 
		is torn down."
	  ::= { ty3250DiagDteTable 3 }


--
--       The ty3250DiagBerTable
--              This table contains the internal Bit Error Rate test diagnostics
--              of the 3250 CSU.
--

ty3250DiagBerTable   OBJECT IDENTIFIER ::= { ty3250 12 }
--        DESCRIPTION
--           "Internal Bit Error Rate Tester for the TyLink 3250. "
	  


ty3250DiagBerPattrn   OBJECT-TYPE
	  SYNTAX      INTEGER
	  {
	       pattrn-511  (1),
	       pattrn-qrss  (2)
	  }
	  ACCESS      read-write
	  STATUS      mandatory
	  DESCRIPTION
	     "selects pseudorandom pattern for bit error rate test"
	  ::= { ty3250DiagBerTable 1 }

ty3250DiagBerState   OBJECT-TYPE
	  SYNTAX      INTEGER
	  {
	       enable-t1-bert-on-full-bw (1),
	       enable-t1-bert-on-DTE-bw (2),
	       disable-bert-test (3),
	       inject-error-bert-test (4),
	       clear-error-bert-test (5)
	  }
	  ACCESS      write-only
	  STATUS      mandatory
	  DESCRIPTION
	     "BERT test related actions:
	     a: Starts a BERT test on selected bandwidth,
	     b: Stops a BERT test on selected bandwidth,
	     c: Inject Errors while the BERT test is running,
	     d: Clears BERT test errors."
	  ::= { ty3250DiagBerTable 2 }

ty3250DiagBerStatus  OBJECT-TYPE
	  SYNTAX      INTEGER 
	  {
	       bert-off         (1),
	       bert-full-bw-out-of-sync (2),
	       bert-DTE-bw-out-of-sync (3),
	       bert-full-bw-in-sync (4),
	       bert-DTE-bw-in-sync (5)
	  }
	  ACCESS      read-only
	  STATUS      mandatory
	  DESCRIPTION
	     "Displays the current BERT test sync status."
	  ::= { ty3250DiagBerTable 3 }

ty3250DiagBerErrors   OBJECT-TYPE
	  SYNTAX      Counter
	  ACCESS      read-only
	  STATUS      mandatory
	  DESCRIPTION
	     "Displays the number of errors detected in Bert Test."
	  ::= { ty3250DiagBerTable 4 }

ty3250DiagBerTimeElaps OBJECT-TYPE
	  SYNTAX      TimeTicks
	  ACCESS      read-only
	  STATUS      mandatory
	  DESCRIPTION
	     "Elapsed time since BERT test was started or cleared."
	  ::= { ty3250DiagBerTable 5 }



--
--      Interface Status 
--
--         The current status of an indexed port. This section is intended
--         to be roughly equivalent to the front-panel LED indictors at 
--         the 3250 node.
--

ty3250PortStatusTable OBJECT-TYPE
	  SYNTAX  SEQUENCE OF Ty3250PortStatus
	  ACCESS  not-accessible
	  STATUS  mandatory
	  DESCRIPTION
	     "Status of a T1 or DTE port."
	  ::= { ty3250 13 }

ty3250PortStatus OBJECT-TYPE
	  SYNTAX  Ty3250PortStatus
	  ACCESS  not-accessible
	  STATUS  mandatory
	  DESCRIPTION
	     "An entry in the DS1 Interval table."
	  INDEX   { ty3250IntfIndex }
	  ::= { ty3250PortStatusTable 1 }

Ty3250PortStatus ::=
	  SEQUENCE 
	  {
		ty3250IntfIndex         INTEGER,
		ty3250IntfType          INTEGER,
		ty3250IntfMode          INTEGER,
		ty3250IntfStatus        INTEGER,
		ty3250IntfAlarms        INTEGER
	   }

ty3250IntfIndex   OBJECT-TYPE
	  SYNTAX  INTEGER (1..4)
	  ACCESS  read-only
	  STATUS  mandatory
	  DESCRIPTION
	     "The index value which uniquely identifies  the
	     interface to which this entry is applicable. "
	  ::= { ty3250PortStatus 1 }

ty3250IntfType   OBJECT-TYPE
	  SYNTAX  INTEGER
	  {
		t1-port (1),
		dte-port (2)
--              comm-port (3)
	  }
	  ACCESS  read-only
	  STATUS  mandatory
	  DESCRIPTION
		"Port type."
	  ::= { ty3250PortStatus 2 }

ty3250IntfMode   OBJECT-TYPE
	  SYNTAX  INTEGER
	  {
		inactive (1),
		active (2),
		test-mode (3)
	  }
	  ACCESS  read-only
	  STATUS  mandatory
	  DESCRIPTION
		"Status of the indexed port. Inactive (1) indicates
		the port has no connections. Active (2) indicates 
		connections and data mode. Test-mode (3) indicates
		connections and diagnostic state for that port."
	  ::= { ty3250PortStatus 3 }

ty3250IntfStatus   OBJECT-TYPE
	  SYNTAX  INTEGER
	  {
		t1-frame-sync-okay (1),
		t1-frame-sync-with-errors (2),
		signal-present-without-frame-sync (3),
		signal-not-present (4), 
		not-applicable (5)
	  }
	  ACCESS  read-only
	  STATUS  mandatory
	  DESCRIPTION
		"Status of the indexed port."
	  ::= { ty3250PortStatus 4 }

ty3250IntfAlarms   OBJECT-TYPE
	  SYNTAX  INTEGER
	  {
		no-alarms (1),
		red-alarm-declared (2), 
		yellow-alarm-detected (3),
		unframed-all-ones-detected (4)
	  }
	  ACCESS  read-only
	  STATUS  mandatory
	  DESCRIPTION
		"Alarms present at the indexed port. The node software 
		may not support DTE alarm conditions."
	  ::= { ty3250PortStatus 5 }


--
--      T1 Current Performance Table

--       The T1 current performance table contains various statistics 
--       being collected for the current 15 minute interval.

ty3250PerfT1CurrentTable OBJECT-TYPE
	  SYNTAX  SEQUENCE OF Ty3250T1CurrentEntry
	  ACCESS  not-accessible
	  STATUS  mandatory
	  DESCRIPTION
	     "The T1 performance numbers for the current  
	     15 minute interval."
	  ::= { ty3250 14 }


ty3250T1CurrentEntry OBJECT-TYPE
	  SYNTAX  Ty3250T1CurrentEntry
	  ACCESS  not-accessible
	  STATUS  mandatory
	  DESCRIPTION
	     "An entry in the T1 Current Perf table."
	  INDEX   { ty3250T1CurrentIndex }
	  ::= { ty3250PerfT1CurrentTable 1 }

Ty3250T1CurrentEntry ::=
	  SEQUENCE {
	     ty3250T1CurrentIndex       INTEGER,
	     ty3250T1CurrentCrc6Events  Gauge,
	     ty3250T1CurrentOofEvents   Gauge,
	     ty3250T1CurrentESs         Gauge,
	     ty3250T1CurrentSESs        Gauge,
	     ty3250T1CurrentSEFSs       Gauge,
	     ty3250T1CurrentUASs        Gauge,
	     ty3250T1CurrentCSSs        Gauge,
	     ty3250T1CurrentBESs        Gauge,
	     ty3250T1CurrentLCVs        Gauge
		   }
ty3250T1CurrentIndex OBJECT-TYPE
	  SYNTAX  INTEGER (1..4)
	  ACCESS  read-only
	  STATUS  mandatory
	  DESCRIPTION
	     "The index value which uniquely identifies  the
	     T1 interface to which this entry is applica-
	     ble. "
	  ::= { ty3250T1CurrentEntry 1 }

ty3250T1CurrentCrc6Events OBJECT-TYPE
	  SYNTAX  Gauge
	  ACCESS  read-only
	  STATUS  mandatory
	  DESCRIPTION
	     "Count of CRC errors detected on an ESF framed circuit.
	     In ESF framing a CRC is generated at the source, based upon 
	     the composite data. A CRC error indicates the presence of
	     at least one bit error in an ESF superframe. This field is 
	     a free-running accumulation of CRC errors and IS NOT reset 
	     when the current 15 minute interval expires. It can be reset 
	     with the performance command ty3250T1PerfClearEvents. 
	     Not applicable if D4/SF framing is selcted."
	  ::= { ty3250T1CurrentEntry 2 }

ty3250T1CurrentOofEvents OBJECT-TYPE
	  SYNTAX  Gauge
	  ACCESS  read-only
	  STATUS  mandatory
	  DESCRIPTION
	     "Count of Out-of-Frame events on a T1 circuit. An out-of-
	     frame event occurs when the frame synchronization criteria
	     is lost and a resynchronization must occur. Data is interrupted
	     during frame resynchronization. This field is a free-running 
	     accumulation of OOF transitions and IS NOT reset when the 
	     current 15 minute interval expires. It can be reset with the 
	     performance command ty3250T1PerfClearEvents." 
	  ::= { ty3250T1CurrentEntry 3 }


ty3250T1CurrentESs OBJECT-TYPE
	  SYNTAX  Gauge
	  ACCESS  read-only
	  STATUS  mandatory
	  DESCRIPTION
	     "The number of Errored Seconds, encountered  by
	     a T1 interface in the current 15 minute inter-
	     val. An errored second is a one-second interval with
	     CRC errors or a loss of frame sync occurred."
	  ::= { ty3250T1CurrentEntry 4 }

ty3250T1CurrentSESs OBJECT-TYPE
	  SYNTAX  Gauge
	  ACCESS  read-only
	  STATUS  mandatory
	  DESCRIPTION
	     "The number of Severely Errored Seconds encoun-
	     tered  by  a  t1 interface  in the current 15
	     minute interval. A severely errored second is a one
	     second interval with more than 320 CRC errors or
	     one or more frame sync losses."
	  ::= { ty3250T1CurrentEntry 5 }

ty3250T1CurrentSEFSs OBJECT-TYPE
	  SYNTAX  Gauge
	  ACCESS  read-only
	  STATUS  mandatory
	  DESCRIPTION
	     "The number of Severely Errored Framing Seconds
	     encountered  by a t1 interface in the current
	     15 minute interval. A SEFS is a one second interval
	     with one or more frame sync losses."
	  ::= { ty3250T1CurrentEntry 6 }

ty3250T1CurrentUASs OBJECT-TYPE
	  SYNTAX  Gauge
	  ACCESS  read-only
	  STATUS  mandatory
	  DESCRIPTION
	     "The number of Unavailable Seconds  encountered
	     by a t1 interface in the current 15 minute in-
	     terval. A UAS is a one second interval during which 
	     the received signal is classified as 'unavailable due
	     to excessive errors'. A signal is unavailable after
	     receiving ten consective severely errored seconds and
	     stays unavailable until ten seconds without a severely
	     errored second occur."
	  ::= { ty3250T1CurrentEntry 7 }

ty3250T1CurrentCSSs OBJECT-TYPE
	  SYNTAX  Gauge
	  ACCESS  read-only
	  STATUS  mandatory
	  DESCRIPTION
	     "The number of Controlled Slip Seconds encoun-
	     tered by a t1 interface in the current 15
	     minute interval. A controlled slip is the 
	     replication or deletion of a T1 frame at the receiver.
	     These events often indicate a T1 network timing 
	     problem."
	  ::= { ty3250T1CurrentEntry 8 }

ty3250T1CurrentBESs OBJECT-TYPE
	  SYNTAX Gauge
	  ACCESS read-only
	  STATUS mandatory
	  DESCRIPTION
	     "The number of Bursty  Errored  Seconds  (BESs)
	     encountered  by  a DS1 interface in the current
	     15 minute interval. A BES is a one second interval
	     with more than one and less than 320 CRC errors."
	  ::= {ty3250T1CurrentEntry 9 }

ty3250T1CurrentLCVs OBJECT-TYPE
	  SYNTAX Gauge
	  ACCESS read-only
	  STATUS mandatory
	  DESCRIPTION
	     "The number of Line Code Violations (LCVs)  en-
	     countered  by a DS1 interface in the current 15
	     minute interval. LCVs are non-B8ZS related
	     violations of the alternate mark inversion protocol.
	     An excessive count usually indicates a B8ZS/AMI
	     configuration mismatch in the T1 network."
	  ::= {ty3250T1CurrentEntry 10 }


--      T1 Performance Intervals

--      The T1 Interval Table contains various statistics
--      collected by each T1 Interface over the previous 24 hours of
--      operation.  The past 24 hours are broken into 96 completed
--      15 minute intervals.

ty3250PerfT1IntervalTable OBJECT-TYPE
	  SYNTAX  SEQUENCE OF Ty3250T1IntervalEntry
	  ACCESS  not-accessible
	  STATUS  mandatory
	  DESCRIPTION
	     "The DS1 Interval table."
	  ::= { ty3250 15 }


ty3250T1IntervalEntry OBJECT-TYPE
	  SYNTAX  Ty3250T1IntervalEntry
	  ACCESS  not-accessible
	  STATUS  mandatory
	  DESCRIPTION
	     "An entry in the DS1 Interval table."
	  INDEX   { ty3250T1IntervalIndex, ty3250T1IntervalNumber }
	  ::= { ty3250PerfT1IntervalTable 1 }

Ty3250T1IntervalEntry ::=
	  SEQUENCE {
		   ty3250T1IntervalIndex  INTEGER,
		   ty3250T1IntervalNumber INTEGER,
		   ty3250T1IntervalESs    Gauge,
		   ty3250T1IntervalSESs   Gauge,
		   ty3250T1IntervalSEFSs  Gauge,
		   ty3250T1IntervalUASs   Gauge,
		   ty3250T1IntervalCSSs   Gauge,
		   ty3250T1IntervalBESs   Gauge,
		   ty3250T1IntervalLCVs   Gauge
		   }
		
ty3250T1IntervalIndex OBJECT-TYPE
	  SYNTAX  INTEGER (1..4)
	  ACCESS  read-only
	  STATUS  mandatory
	  DESCRIPTION
	     "The index value which uniquely identifies  the
	     t1  interface  to which this entry is applica-
	     ble.  The interface identified by a  particular
	     value  of  this  index is the same interface as
	     identified by the same value as a NetwLineIndex
	     object instance."
	  ::= { ty3250T1IntervalEntry 1 }


ty3250T1IntervalNumber OBJECT-TYPE
	  SYNTAX  INTEGER (1..96)
	  ACCESS  read-only
	  STATUS  mandatory
	  DESCRIPTION
	     "A number between 1 and 96, where 1 is the most
	     recently completed 15 minute interval and 96 is
	     the least recently completed 15 minutes  inter-
	     val   (assuming   that  all  96  intervals  are
	     valid)."
	  ::= { ty3250T1IntervalEntry 2 }

ty3250T1IntervalESs OBJECT-TYPE
	  SYNTAX  Gauge
	  ACCESS  read-only
	  STATUS  mandatory
	  DESCRIPTION
	     "The number of Errored Seconds encountered by a
	     t1 interface in one of the previous 96, indi-
	     vidual 15 minute, intervals. An errored second is 
	     a one-second interval with CRC errors or a loss 
	     of frame sync occurred."
	  ::= { ty3250T1IntervalEntry 3 }


ty3250T1IntervalSESs OBJECT-TYPE
	  SYNTAX  Gauge
	  ACCESS  read-only
	  STATUS  mandatory
	  DESCRIPTION
	     "The number of Severely Errored Seconds encoun-
	     tered by a t1 interface in one of the previous
	     96, individual 15 minute, intervals. A severely 
	     errored second is a one second interval with more 
	     than 320 CRC errors or one or more frame sync losses."
	  ::= { ty3250T1IntervalEntry 4 }


ty3250T1IntervalSEFSs OBJECT-TYPE
	  SYNTAX  Gauge
	  ACCESS  read-only
	  STATUS  mandatory
	  DESCRIPTION
	     "The number of Severely Errored Framing Seconds
	     encountered  by  a  t1 interface in one of the
	     previous 96, individual 15 minute, intervals.
	     A SEFS is a one second interval with one or more 
	     frame sync losses."
	  ::= { ty3250T1IntervalEntry 5 }


ty3250T1IntervalUASs OBJECT-TYPE
	  SYNTAX  Gauge
	  ACCESS  read-only
	  STATUS  mandatory
	  DESCRIPTION
	     "The number of Unavailable Seconds  encountered
	     by  a  t1 interface in one of the previous 96,
	     individual 15 minute, intervals. A UAS is a one second 
	     interval during which the received signal is classified 
	     as 'unavailable due to excessive errors'. A signal is 
	     unavailable after receiving ten consective severely 
	     errored seconds and stays unavailable until ten seconds 
	     without a severely errored second occur."
	  ::= { ty3250T1IntervalEntry 6 }


ty3250T1IntervalCSSs OBJECT-TYPE
	  SYNTAX  Gauge
	  ACCESS  read-only
	  STATUS  mandatory
	  DESCRIPTION
	     "The number of Controlled Slip Seconds  encoun-
	     tered by a t1 interface in one of the previous
	     96, individual 15 minute, intervals. A controlled 
	     slip is the replication or deletion of a T1 frame 
	     at the receiver. These events often indicate a T1 
	     network timing problem."
	  ::= { ty3250T1IntervalEntry 7 }

ty3250T1IntervalBESs OBJECT-TYPE
	  SYNTAX Gauge
	  ACCESS read-only
	  STATUS mandatory
	  DESCRIPTION
	     "The number of Bursty  Errored  Seconds  (BESs)
	     encountered  by  a  t1 interface in one of the
	     previous 96, individual 15 minute, intervals.
	     A BES is a one second interval with more than one 
	     and less than 320 CRC errors."
	  ::= {ty3250T1IntervalEntry 8 }


ty3250T1IntervalLCVs OBJECT-TYPE
	  SYNTAX Gauge
	  ACCESS read-only
	  STATUS mandatory
	  DESCRIPTION
	     "The number of Line Code Violations (LCVs)  en-
	     countered  by a DS1 interface in the current 15
	     minute interval. LCVs are non-B8ZS related
	     violations of the alternate mark inversion protocol.
	     An excessive count usually indicates a B8ZS/AMI
	     configuration mismatch in the T1 network."
	  ::= {ty3250T1IntervalEntry 9 }



--      T1 Performance 24 Hour Totals

--       The T1 Totals Table contains the cumulative sum of the
--       various statistics for the 24 hour period preceding the
--       current interval.

ty3250PerfT1TotalTable OBJECT-TYPE
	  SYNTAX  SEQUENCE OF Ty3250T1TotalEntry
	  ACCESS  not-accessible
	  STATUS  mandatory
	  DESCRIPTION
	     "The T1 Total table.  24 hour interval."
	  ::= { ty3250 16 }


ty3250T1TotalEntry OBJECT-TYPE
	  SYNTAX  Ty3250T1TotalEntry
	  ACCESS  not-accessible
	  STATUS  mandatory
	  DESCRIPTION
	     "An entry in the T1 Total table."
	  INDEX   { ty3250T1TotalIndex }
	  ::= { ty3250PerfT1TotalTable 1 }

Ty3250T1TotalEntry ::=
	  SEQUENCE {
	     ty3250T1TotalIndex INTEGER, 
	     ty3250T1TotalESs   Gauge,
	     ty3250T1TotalSESs  Gauge,
	     ty3250T1TotalSEFSs Gauge,
	     ty3250T1TotalUASs  Gauge,
	     ty3250T1TotalCSSs  Gauge,
	     ty3250T1TotalBESs  Gauge,
	     ty3250T1TotalLCVs  Gauge
		   }

ty3250T1TotalIndex OBJECT-TYPE
	  SYNTAX  INTEGER (1..4)
	  ACCESS  read-only
	  STATUS  mandatory
	  DESCRIPTION
	     "The index value which uniquely identifies  the
	     t1  interface  to which this entry is applica-
	     ble.  The interface identified by a  particular
	     value  of  this  index is the same interface as
	     identified by the same value as a NetwLineIndex
	     object instance."
	  ::= { ty3250T1TotalEntry 1 }


ty3250T1TotalESs OBJECT-TYPE
	  SYNTAX  Gauge
	  ACCESS  read-only
	  STATUS  mandatory
	  DESCRIPTION
	     "The number of Errored Seconds encountered by a
	     t1 interface in the previous 24 hour interval.
	     An errored second is a one-second interval with 
	     CRC errors or a loss of frame sync occurred."
	  ::= { ty3250T1TotalEntry 2 }


ty3250T1TotalSESs OBJECT-TYPE
	  SYNTAX  Gauge
	  ACCESS  read-only
	  STATUS  mandatory
	  DESCRIPTION
	     "The number of Severely Errored Seconds encoun-
	     tered  by  a  t1  interface in the previous 24
	     hour interval. A severely errored second is a one 
	     second interval with more than 320 CRC errors or 
	     one or more frame sync losses."
	  ::= { ty3250T1TotalEntry 3 }


ty3250T1TotalSEFSs OBJECT-TYPE
	  SYNTAX  Gauge
	  ACCESS  read-only
	  STATUS  mandatory
	  DESCRIPTION
	     "The number of Severely Errored Framing Seconds
	     24 hour interval. A SEFS is a one second interval 
	     with one or more frame sync losses."
	  ::= { ty3250T1TotalEntry 4 }


ty3250T1TotalUASs OBJECT-TYPE
	  SYNTAX  Gauge
	  ACCESS  read-only
	  STATUS  mandatory
	  DESCRIPTION
	     "The number of Unavailable Seconds  encountered
	     by  a t1 interface in the previous 24 hour in-
	     terval. A UAS is a one second interval during which 
	     the received signal is classified as 'unavailable 
	     due to excessive errors'. A signal is unavailable 
	     after receiving ten consective severely errored 
	     seconds and stays unavailable until ten seconds 
	     without a severely errored second occur."
	  ::= { ty3250T1TotalEntry 5 }


ty3250T1TotalCSSs OBJECT-TYPE
	  SYNTAX  Gauge
	  ACCESS  read-only
	  STATUS  mandatory
	  DESCRIPTION
	     "The number of Controlled Slip Seconds  encoun-
	     tered  by  a  t1  interface in the previous 24
	     hour interval. A controlled slip is the replication 
	     or deletion of a T1 frame at the receiver. These 
	     events often indicate a T1 network timing problem."
	  ::= { ty3250T1TotalEntry 6 }


ty3250T1TotalBESs OBJECT-TYPE
	  SYNTAX Gauge
	  ACCESS read-only
	  STATUS mandatory
	  DESCRIPTION
	     "The number of Bursty  Errored  Seconds  (BESs)
	     encountered  by a t1 interface in the previous
	     24 hour interval. A BES is a one second interval 
	     with more than one and less than 320 CRC errors."
	  ::= { ty3250T1TotalEntry 7 }


ty3250T1TotalLCVs OBJECT-TYPE
	  SYNTAX Gauge
	  ACCESS read-only
	  STATUS mandatory
	  DESCRIPTION
	     "The number of Line Code Violations (LCVs)  en-
	     countered  by a t1 interface in the current 15
	     minute interval. LCVs are non-B8ZS related
	     violations of the alternate mark inversion protocol.
	     An excessive count usually indicates a B8ZS/AMI
	     configuration mismatch in the T1 network."
	  ::= {ty3250T1TotalEntry 8 }


--      T1 Performance Commands

--      A set of commands that affect the (user) bank of T1 performance 
--      registers         


ty3250T1PerfCmdTypeTable OBJECT-TYPE
	  SYNTAX  SEQUENCE OF Ty3250T1PerfCmdType
	  ACCESS  not-accessible
	  STATUS  mandatory
	  DESCRIPTION
	     "An entry in the DS1 Interval table."
	  ::= { ty3250 17 }

ty3250T1PerfCmdType OBJECT-TYPE
	  SYNTAX  Ty3250T1PerfCmdType
	  ACCESS  not-accessible
	  STATUS  mandatory
	  DESCRIPTION
	     "An entry in the DS1 Interval table."
	  INDEX   { ty3250T1CommandIndex }
	  ::= { ty3250T1PerfCmdTypeTable 1 }

Ty3250T1PerfCmdType ::=
	  SEQUENCE {
		   ty3250T1CommandIndex    INTEGER,
		   ty3250T1PerfFreezeState INTEGER,
		   ty3250T1PerfClearEvents INTEGER,
		   ty3250T1PerfClearAll    INTEGER
		   }
		
ty3250T1CommandIndex OBJECT-TYPE
	  SYNTAX  INTEGER (1..4)
	  ACCESS  write-only
	  STATUS  mandatory
	  DESCRIPTION
	     "The index value which uniquely identifies  the
	     t1  interface  to which this command is applica-
	     ble."  
	  ::= { ty3250T1PerfCmdType 1 }
	 
ty3250T1PerfFreezeState OBJECT-TYPE
	  SYNTAX      INTEGER
		{
		freeze-reg (1),
		unfreeze-reg (2)
		}
	  ACCESS  read-write
	  STATUS  mandatory
	  DESCRIPTION
	     "This command halts the node's performance monitoring
	     and freezes the current, interval, and total performance
	     register values."
	     ::= { ty3250T1PerfCmdType 2 }

ty3250T1PerfClearEvents OBJECT-TYPE
	  SYNTAX      INTEGER
		{
		clear-events (1)
		}
	  ACCESS  write-only
	  STATUS  mandatory
	  DESCRIPTION
	     "This command resets all of the (user's) error event 
	     registers. This includes the CRC6 and Out-of-Frame
	     counts. It does not affect the interval or 24 hour
	     performance totals."
	  ::= { ty3250T1PerfCmdType 3 }

ty3250T1PerfClearAll OBJECT-TYPE
	  SYNTAX      INTEGER
		{
		clear-all (1)
		}
	  ACCESS  write-only
	  STATUS  mandatory
	  DESCRIPTION
	     "This command resets all of the (user's) performance 
	     registers."
	  ::= { ty3250T1PerfCmdType 4}





-- =========================
-- ==        TRAPS        ==
-- =========================
--
--       The Alarm (Trap) table for the 3250.
--              This table contains definitions for enterprise specific traps
--              associated with the 3250 T1 DSU/CSU.
ty3250AlarmType     OBJECT-TYPE
	  SYNTAX      INTEGER
	  {
	       cold-start (1),
	       authentication (2),
	       t1-netw-carrier-loss (3),
	       t1-netw-carrier-detect (4),
	       t1-netw-sync-loss-declare (5),
	       t1-netw-sync-acquire (6),
	       t1-netw-red-alarm-declare (7),
	       t1-netw-red-alarm-clear (8),
	       t1-netw-yellow-alarm-detect (9),
	       t1-netw-yellow-alarm-clear (10),
	       t1-netw-ais-detect (11),
	       t1-netw-ais-clear (12),
	       t1-controlled-slip (13),
	       configuration-update (14),
	       diagnostic-state (15),
	       diagnostic-clear (16)
	  }
	  ACCESS      read-only
	  STATUS      mandatory
	  DESCRIPTION
	     "The type of alarms that are generated on the node"
	  ::= { ty3250 18 }

ty3250Trap          TRAP-TYPE
	  ENTERPRISE  ty3250
	  VARIABLES   
	  { 
	       ty3250AlarmType
	  }
	  DESCRIPTION
	     "A ty3250Trap trap signifies that the
	     sending node had its `ty3250AlarmType`
	     variable modified."
	  ::= 0



ty3250coldstart          TRAP-TYPE
          ENTERPRISE  ty3250
	  VARIABLES   
	  { 
	       ty3250AlarmType
	  }
          DESCRIPTION
             "cold-start."
          ::= 1

ty3250authentication          TRAP-TYPE
          ENTERPRISE  ty3250
	  VARIABLES   
	  { 
	       ty3250AlarmType
	  }
          DESCRIPTION
             "authentication."
          ::= 2

ty3250t1netwcarrierloss          TRAP-TYPE
          ENTERPRISE  ty3250
	  VARIABLES   
	  { 
	       ty3250AlarmType
	  }
          DESCRIPTION
             "t1-netw-carrier-loss."
          ::= 3

ty3250t1netwcarrierdetect          TRAP-TYPE
          ENTERPRISE  ty3250
	  VARIABLES   
	  { 
	       ty3250AlarmType
	  }
          DESCRIPTION
             "t1-netw-carrier-detect."
          ::= 4

ty3250t1netwsynclossdeclare          TRAP-TYPE
          ENTERPRISE  ty3250
	  VARIABLES   
	  { 
	       ty3250AlarmType
	  }
          DESCRIPTION
             "t1-netw-sync-loss-declare."
          ::= 5

ty3250t1netwsyncacquire          TRAP-TYPE
          ENTERPRISE  ty3250
	  VARIABLES   
	  { 
	       ty3250AlarmType
	  }
          DESCRIPTION
             "t1-netw-sync-acquire."
          ::= 6

ty3250t1netwredalarmdeclare          TRAP-TYPE
          ENTERPRISE  ty3250
	  VARIABLES   
	  { 
	       ty3250AlarmType
	  }
          DESCRIPTION
             "t1-netw-red-alarm-declare."
          ::= 7

ty3250t1netwredalarmclear          TRAP-TYPE
          ENTERPRISE  ty3250
	  VARIABLES   
	  { 
	       ty3250AlarmType
	  }
          DESCRIPTION
             "t1-netw-red-alarm-clear."
          ::= 8

ty3250t1netwyellowalarmdetect          TRAP-TYPE
          ENTERPRISE  ty3250
	  VARIABLES   
	  { 
	       ty3250AlarmType
	  }
          DESCRIPTION
             "t1-netw-yellow-alarm-detect."
          ::= 9

ty3250t1netwyellowalarmclear          TRAP-TYPE
          ENTERPRISE  ty3250
	  VARIABLES   
	  { 
	       ty3250AlarmType
	  }
          DESCRIPTION
             "."
          ::= 10

ty3250t1netwaisdetect          TRAP-TYPE
          ENTERPRISE  ty3250
	  VARIABLES   
	  { 
	       ty3250AlarmType
	  }
          DESCRIPTION
             "t1-netw-ais-detect."
          ::= 11

ty3250t1netwaisclear          TRAP-TYPE
          ENTERPRISE  ty3250
	  VARIABLES   
	  { 
	       ty3250AlarmType
	  }
          DESCRIPTION
             "t1-netw-ais-clear."
          ::= 12

ty3250t1controlledslip          TRAP-TYPE
          ENTERPRISE  ty3250
	  VARIABLES   
	  { 
	       ty3250AlarmType
	  }
          DESCRIPTION
             "t1-controlled-slip."
          ::= 13

ty3250configurationupdate          TRAP-TYPE
          ENTERPRISE  ty3250
	  VARIABLES   
	  { 
	       ty3250AlarmType
	  }
          DESCRIPTION
             "configuration-update."
          ::= 14

ty3250diagnosticstate          TRAP-TYPE
          ENTERPRISE  ty3250
	  VARIABLES   
	  { 
	       ty3250AlarmType
	  }
          DESCRIPTION
             "diagnostic-state."
          ::= 15

ty3250diagnosticclear          TRAP-TYPE
          ENTERPRISE  ty3250
	  VARIABLES   
	  { 
	       ty3250AlarmType
	  }
          DESCRIPTION
             "diagnostic-clear."
          ::= 16


END
