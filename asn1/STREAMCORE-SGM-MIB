STREAMCORE-SGM-MIB DEFINITIONS ::= BEGIN

-- ==========================================================================
-- Copyright (c) 2001, 2007 Streamcore System
--
-- Nom   : STREAMCORE-SGM-MIB.txt
--
-- ==========================================================================

IMPORTS
   MODULE-IDENTITY, OBJECT-TYPE, IpAddress, Unsigned32
		FROM SNMPv2-SMI
   DisplayString
		FROM SNMPv2-TC
	scMibs, StreamGroomerId
		FROM STREAMCORE-MIB
;

  

sgmMIB MODULE-IDENTITY
    LAST-UPDATED "2007111900003"
    ORGANIZATION "StreamCore"
    CONTACT-INFO
            "        
             Postal: StreamCore
                     11-15 quai de Dion-Bouton
                     92800 Puteaux
                     France

             Phone:  +33 (0)1 47 86 83 10
             Email:  support@streamcore.com"
    DESCRIPTION
            "The MIB module for managing Streamcore SGM."
    REVISION     "2007111900003"
    DESCRIPTION
	       "Initial revision."
    ::= { scMibs 1 }

--
-- Database table
--

dbTable OBJECT-TYPE
    SYNTAX      SEQUENCE OF DbEntry
    MAX-ACCESS  not-accessible
    STATUS      current
    DESCRIPTION
	   "Table contains the list of databases configured ont this SGM."
    ::= { sgmMIB 1 }

dbEntry OBJECT-TYPE
    SYNTAX      DbEntry
    MAX-ACCESS  not-accessible
    STATUS      current
    DESCRIPTION
	   ""
    INDEX { dbIndex }
    ::= { dbTable 1 }

DbEntry ::= SEQUENCE {
    dbIndex      Unsigned32,
    dbName       DisplayString
}

dbIndex OBJECT-TYPE
    SYNTAX      Unsigned32
    MAX-ACCESS  not-accessible
    STATUS      current
    DESCRIPTION
	   ""
    ::= { dbEntry 1 }

dbName OBJECT-TYPE
    SYNTAX      DisplayString
    MAX-ACCESS  read-only
    STATUS      current
    DESCRIPTION
	   ""
    ::= { dbEntry 2 }

--
-- Sg table
--

sgTable OBJECT-TYPE
    SYNTAX      SEQUENCE OF SgEntry
    MAX-ACCESS  not-accessible
    STATUS      current
    DESCRIPTION
	   ""
    ::= { sgmMIB 2 }

sgEntry OBJECT-TYPE
    SYNTAX      SgEntry
    MAX-ACCESS  not-accessible
    STATUS      current
    DESCRIPTION
	   ""
    INDEX { dbIndex, sgId }
    ::= { sgTable 1 }

SgEntry ::= SEQUENCE {
    sgId           StreamGroomerId,
    sgName         DisplayString,
    sgIpAddress    IpAddress
}

sgId OBJECT-TYPE
    SYNTAX      StreamGroomerId
    MAX-ACCESS  not-accessible
    STATUS      current
    DESCRIPTION
	   ""
    ::= { sgEntry 1 }

sgName OBJECT-TYPE
    SYNTAX      DisplayString
    MAX-ACCESS  read-only
    STATUS      current
    DESCRIPTION
	   ""
    ::= { sgEntry 2 }

sgIpAddress OBJECT-TYPE
    SYNTAX      IpAddress
    MAX-ACCESS  read-only
    STATUS      current
    DESCRIPTION
	   ""
    ::= { sgEntry 3 }
    

END

--
-- END STREAMCORE-SGM-MIB
--
