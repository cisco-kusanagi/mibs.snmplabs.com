-- *****************************************************************
--
-- stn-version.mib:  
--      Spring Tide Networks Versions MIB file.
--
--
--      Copyright (c) 1999, 2000 by Spring Tide Networks, Inc.
--                      ALL RIGHTS RESERVED       
--
-- *****************************************************************

-- MIB Object definitions for Spring Tide Network hardware and
-- software versions

STN-VERSION-MIB DEFINITIONS ::= BEGIN

    IMPORTS
        MODULE-IDENTITY,
        OBJECT-TYPE,
        NOTIFICATION-TYPE, 
        Integer32
                FROM SNMPv2-SMI

        DisplayString
                FROM SNMPv2-TC

        MODULE-COMPLIANCE
                FROM SNMPv2-CONF

        stnSystems,
        stnNotification
                FROM SPRING-TIDE-NETWORKS-SMI

        StnHardwareModuleType
                FROM SPRING-TIDE-NETWORKS-TC

        stnEngineIndex, 
        stnEngineSlot,
        stnEngineCpu
                FROM STN-CHASSIS-MIB;


    stnVersion       MODULE-IDENTITY
        LAST-UPDATED    "0002160000Z"
        ORGANIZATION    "Spring Tide Networks, Inc."
        CONTACT-INFO
                "
                Spring Tide Networks, Inc.
                Customer Service
                Postal: 3 Clock Tower Place
                        Maynard, MA 01754
                Tel:    1 888-786-4357
                Email:  stncs@springtidenet.com
                "
        DESCRIPTION     "This MIB module describes the Spring Tide Networks 
                         software and hardware versions."
        ::= { stnSystems 2 }


    --
    -- Top Level STN Version MIB Objects
    --
    stnVersionObjects		OBJECT IDENTIFIER ::= { stnVersion 1 }
    stnVersionMibConformance	OBJECT IDENTIFIER ::= { stnVersion 2 }

    stnSwVersions       OBJECT IDENTIFIER ::= { stnVersionObjects 1 }
    stnHwVersions       OBJECT IDENTIFIER ::= { stnVersionObjects 2 }


    -- STN Software Version Table

    stnSwVersionTable OBJECT-TYPE
        SYNTAX        SEQUENCE OF StnSwVersionEntry
        MAX-ACCESS    not-accessible
        STATUS        current
        DESCRIPTION   "A list of system software and gateware version entries."
        ::= { stnSwVersions 1 }
 
    stnSwVersionEntry OBJECT-TYPE
        SYNTAX          StnSwVersionEntry
        MAX-ACCESS      not-accessible
        STATUS          current
        DESCRIPTION     "Entry contains information about a particular 
                         system software or gateware version."
        INDEX           { stnSwImage }
        ::= { stnSwVersionTable 1 }
 
    StnSwVersionEntry ::= SEQUENCE {
                stnSwImage                  INTEGER,
                stnSwVersionPrefix          DisplayString,
                stnSwMajorVersion           Integer32,
                stnSwMinorVersion           Integer32,
                stnSwMaintenanceVersion     Integer32,
                stnSwPatchVersion           Integer32,
                stnSwVersionDescr           DisplayString
                }

    stnSwImage OBJECT-TYPE     
        SYNTAX          INTEGER { 
                                bootstrap(1),           -- Bootstrap
                                cpmSwitch(2),           -- Central Processor Module Operational
                                cpmRoute(3),            --
                                tsmECF(4),              -- Tunnel Switching Module Operational
                                cpmSwitchRecv(5),       -- Central Processor Module Recovery
                                cpmRouteRecv(6),        --
                                tsmECFRecv(7),          -- Tunnel Switching Module Recovery
                                cpmKing(8),             -- 
                                cpmBlue(9),             -- 
                                cpmHermit(10),          -- 
                                cpmSwcPipeline(11),     -- 
                                cpmRpePipeline(12),     -- 
                                cpmSpider(13),          -- 
                                cpmSand(14),            -- 
                                tsmBlue(15),            --
                                tsmHermit(16),          --
                                tsmPipeline(17),        --
                                tsmBridge(18),          --
                                tsmSoldier(19),         --
                                swfmHorseshoe(20),      -- Switch Fabric Module
                                atmOC3Stone(21),        -- ATM OC3 Line Card
                                enetMud(22),            -- Ethernet Line Card
                                rmFiddler(23),          -- Resource Module
                                atmOC12Golden(24),      -- ATM OC12 Line Card
                                ds3Green(25)            -- DS3 Line Card

                                }
        MAX-ACCESS      read-only
        STATUS          current
        DESCRIPTION     "Indicates the software image type."
        ::= { stnSwVersionEntry  1 }

    stnSwVersionPrefix OBJECT-TYPE
        SYNTAX          DisplayString (SIZE(1))
        MAX-ACCESS      read-only
        STATUS          current
        DESCRIPTION     "The software image version prefix."
        ::= { stnSwVersionEntry  2 }

    stnSwMajorVersion OBJECT-TYPE
        SYNTAX          Integer32
        MAX-ACCESS      read-only
        STATUS          current
        DESCRIPTION     "The software image major version."
        ::= { stnSwVersionEntry  3 }

    stnSwMinorVersion OBJECT-TYPE
        SYNTAX          Integer32
        MAX-ACCESS      read-only
        STATUS          current
        DESCRIPTION     "The software image minor version."
        ::= { stnSwVersionEntry  4 }

    stnSwMaintenanceVersion OBJECT-TYPE
        SYNTAX          Integer32
        MAX-ACCESS      read-only
        STATUS          current
        DESCRIPTION     "The software image maintenance version."
        ::= { stnSwVersionEntry  5 }

    stnSwPatchVersion OBJECT-TYPE
        SYNTAX          Integer32
        MAX-ACCESS      read-only
        STATUS          current
        DESCRIPTION     "The software image patch version."
        ::= { stnSwVersionEntry  6 }


    stnSwVersionDescr   OBJECT-TYPE
        SYNTAX          DisplayString
        MAX-ACCESS      read-only
        STATUS          current
        DESCRIPTION     "A descriptive string used to describe 
                        the software type and version."
        ::= { stnSwVersionEntry  7 }


    -- STN Hardware Version Table

    stnHwVersionTable OBJECT-TYPE
        SYNTAX        SEQUENCE OF StnHwVersionEntry
        MAX-ACCESS    not-accessible
        STATUS        current
        DESCRIPTION   "A list of system hardware version entries."
        ::= { stnHwVersions 1 }
 
    stnHwVersionEntry OBJECT-TYPE
        SYNTAX          StnHwVersionEntry
        MAX-ACCESS      not-accessible
        STATUS          current
        DESCRIPTION     "Entry contains information about all 
                        hardware versions and identification information."
        INDEX           { stnHwSlotIndex }
        ::= { stnHwVersionTable 1 }
 
    StnHwVersionEntry ::= SEQUENCE {
                stnHwSlotIndex          Integer32,
                stnHwType               StnHardwareModuleType,
                stnHwMajorVersion       Integer32,
                stnHwMinorVersion       Integer32,
                stnHwVersionDescr       DisplayString,
                stnHwSerialNumber       DisplayString
                }

    stnHwSlotIndex OBJECT-TYPE
        SYNTAX          Integer32
        MAX-ACCESS      not-accessible
        STATUS          current
        DESCRIPTION     "A sequence number that identifies a particular slot
                        in the chassis."
        ::= { stnHwVersionEntry 1 }

    stnHwType OBJECT-TYPE     
        SYNTAX          StnHardwareModuleType
        MAX-ACCESS      read-only
        STATUS          current
        DESCRIPTION     "Indicates the hardware type located in the specific slot."
        ::= { stnHwVersionEntry  2 }

    stnHwMajorVersion OBJECT-TYPE
        SYNTAX          Integer32
        MAX-ACCESS      read-only
        STATUS          current
        DESCRIPTION     "The hardware major version of the module."
        ::= { stnHwVersionEntry  3 }

    stnHwMinorVersion OBJECT-TYPE
        SYNTAX          Integer32
        MAX-ACCESS      read-only
        STATUS          current
        DESCRIPTION     "The hardware minor version of the module."
        ::= { stnHwVersionEntry  4 }

    stnHwVersionDescr OBJECT-TYPE
        SYNTAX          DisplayString
        MAX-ACCESS      read-only
        STATUS          current
        DESCRIPTION     "A descriptive string used to describe 
                        the hardware type and version."
        ::= { stnHwVersionEntry  5 }

    stnHwSerialNumber OBJECT-TYPE
        SYNTAX          DisplayString
        MAX-ACCESS      read-only
        STATUS          current
        DESCRIPTION     "The serial number of the hardware module."
        ::= { stnHwVersionEntry  6 }


    --
    -- STN Traps & Notifications 
    --
    stnSwImageUpgraded NOTIFICATION-TYPE
        OBJECTS         { stnSwImage }
        STATUS          current
        DESCRIPTION     "A stnSwImageUpgraded trap signifies that the agent 
                        entity has detected that the indicated software
                        image has been successfully upgraded to all
                        appropriate engines.
                        The generation of this trap can be controlled by the
                        SwUpgradeTraps configuration object."
        ::= { stnNotification 51 }

    stnSwImageUpgradeFailure NOTIFICATION-TYPE
        OBJECTS         { stnSwImage,       stnEngineIndex, 
                          stnEngineSlot,    stnEngineCpu}
        STATUS          current
        DESCRIPTION     "A stnSwImageUpgradeFailure trap signifies that the 
                        agent entity has detected that the indicated software
                        image has failed to load into all appropriate engines.
                        The generation of this trap can be controlled by the
                        SwUpgradeTraps configuration object."
        ::= { stnNotification 52 }


    stnSwImageNotFound NOTIFICATION-TYPE
        OBJECTS         { stnSwImage }
        STATUS          current
        DESCRIPTION     "A stnSwImageNotFound trap signifies that the 
                        agent entity has detected that the indicated software
                        image cannot be found.
                        The generation of this trap can be controlled by the
                        SwUpgradeTraps configuration object."
        ::= { stnNotification 53 }


    stnSwImageAutoDowngraded NOTIFICATION-TYPE
        OBJECTS         { stnSwImage, stnSwVersionDescr, stnSwVersionDescr }
        STATUS          current
        DESCRIPTION     "A stnSwImageAutoDowngraded trap signifies that the 
                        agent entity has detected that the indicated software
                        image cannot successfully execute on the system and
                        has been automatically downgraded.
                        The first stnSwVersionDescr associated with this 
                        notification is the current operational image, 
                        while the second stnSwVersionDescr is the failed image.
                        The generation of this trap can be controlled by the
                        SwUpgradeTraps configuration object."
        ::= { stnNotification 54 }

END
