-- 	$Id: shiva-filters.asn,v 1.3 1996/01/16 16:40:12 dfox Exp $

--
-- 	Copyright 1992, 1993, 1994, 1995, 1996 Shiva Corporation
--

--	Shiva systems filter MIB

SHIVA-FILTER-MIB DEFINITIONS ::= BEGIN

IMPORTS
    	OBJECT-TYPE
    		FROM RFC-1212		-- Concise MIB Definitions
    	tFilters
    		FROM SHIVA-MIB;

	tAppleTalkFilters    OBJECT IDENTIFIER ::= { tFilters 1 }
	tNBPFilters    	     OBJECT IDENTIFIER ::= { tAppleTalkFilters 1 }
	tZoneFilters   	     OBJECT IDENTIFIER ::= { tAppleTalkFilters 2 }

    tNBPFilterConfig	OBJECT-TYPE
	SYNTAX	INTEGER { 
		unconfigured(1), 
		configured(2),
		reinitialize(3)
	}
	ACCESS	read-write
	STATUS	mandatory
	DESCRIPTION
		"This integer indicates the state of NBP filtering in
		this device, which is either configured or unconfigured.  
		Setting this object to 'reinitialize' (3) causes the
		device to reinitialize NBP filtering."
	::= { tNBPFilters 1 }

    tZoneFilterConfig	OBJECT-TYPE
	SYNTAX	INTEGER { 
		unconfigured(1), 
		configured(2),
		reinitialize(3)
	}
	ACCESS	read-write
	STATUS	mandatory
	DESCRIPTION
		"This integer indicates the state of zone filtering in
		this device, which is either configured or unconfigured.  
		Setting this object to 'reinitialize' (3) causes the
		device to reinitialize zone filtering."
	::= { tZoneFilters 1 }

END
