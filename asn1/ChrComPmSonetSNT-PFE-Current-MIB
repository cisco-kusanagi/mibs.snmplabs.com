ChrComPmSonetSNT-PFE-Current-MIB

--FORCE-INCLUDE	<mib.h>
--FORCE-INCLUDE	<snmpdefs.h>
--FORCE-INCLUDE	"mibhand.h"

	DEFINITIONS  ::=  BEGIN

IMPORTS
	OBJECT-TYPE, Counter32			FROM  SNMPv2-SMI
	Integer32, Unsigned32			FROM  SNMPv2-SMI
	chrComPmSonet				FROM  Chromatis-MIB
	chrComIfifIndex					FROM  ChrComIfifTable-MIB
	TruthValue				FROM  ChrTyp-MIB
	Gauge32				FROM  SNMPv2-SMI;

-- chrComPmSonetSNT-PFE-Current Table

chrComPmSonetSNT-PFE-CurrentTable		OBJECT-TYPE
	SYNTAX		SEQUENCE OF ChrComPmSonetSNT-PFE-CurrentEntry
	MAX-ACCESS	not-accessible
	STATUS		current
	DESCRIPTION
	""
	::= { chrComPmSonet 13}

chrComPmSonetSNT-PFE-CurrentEntry		OBJECT-TYPE
	SYNTAX		ChrComPmSonetSNT-PFE-CurrentEntry
	MAX-ACCESS	not-accessible
	STATUS		current
	DESCRIPTION
	""
	INDEX  {  chrComIfifIndex }

--DEFAULT  get-function-async  MNIL_GetRoutine
--DEFAULT  set-function-async  MNIL_SetRoutine
--DEFAULT  next-function-async MNIL_NextRoutine
--DEFAULT  test-function-async MNIL_TestRoutine
--DEFAULT  cookie "SNT-PFE-Current"
	::= { chrComPmSonetSNT-PFE-CurrentTable  1 }

ChrComPmSonetSNT-PFE-CurrentEntry  ::=
	SEQUENCE  {
	chrComPmSonetSuspectedInterval	TruthValue,
	chrComPmSonetElapsedTime		Unsigned32	(0..4294967295),
	chrComPmSonetSuppressedIntrvls	Gauge32			(0..4294967295),
	chrComPmSonetStatus			Gauge32			(0..4294967295),
	chrComPmSonetES			Gauge32			(0..4294967295),
	chrComPmSonetSES			Gauge32			(0..4294967295),
	chrComPmSonetCV			Gauge32			(0..4294967295),
	chrComPmSonetUAS			Gauge32			(0..4294967295),
	chrComPmSonetThresholdProfIndex	Unsigned32	(0..4294967295),
	chrComPmSonetResetPmCountersAction	TruthValue
}

chrComPmSonetSuspectedInterval 	OBJECT-TYPE
	SYNTAX		TruthValue
	MAX-ACCESS 	read-only
	STATUS 		current
	DESCRIPTION
	""
	::= { chrComPmSonetSNT-PFE-CurrentEntry  1 }

chrComPmSonetElapsedTime 	OBJECT-TYPE
	SYNTAX		Unsigned32	(0..4294967295)
	MAX-ACCESS 	read-only
	STATUS 		current
	DESCRIPTION
	""
	::= { chrComPmSonetSNT-PFE-CurrentEntry  2 }

chrComPmSonetSuppressedIntrvls 	OBJECT-TYPE
	SYNTAX		Gauge32			(0..4294967295)
	MAX-ACCESS 	read-only
	STATUS 		current
	DESCRIPTION
	""
	::= { chrComPmSonetSNT-PFE-CurrentEntry  3 }

chrComPmSonetStatus 	OBJECT-TYPE
	SYNTAX		Gauge32			(0..4294967295)
	MAX-ACCESS 	read-only
	STATUS 		current
	DESCRIPTION
	""
	::= { chrComPmSonetSNT-PFE-CurrentEntry  4 }

chrComPmSonetES 	OBJECT-TYPE
	SYNTAX		Gauge32			(0..4294967295)
	MAX-ACCESS 	read-only
	STATUS 		current
	DESCRIPTION
	""
	::= { chrComPmSonetSNT-PFE-CurrentEntry  5 }

chrComPmSonetSES 	OBJECT-TYPE
	SYNTAX		Gauge32			(0..4294967295)
	MAX-ACCESS 	read-only
	STATUS 		current
	DESCRIPTION
	""
	::= { chrComPmSonetSNT-PFE-CurrentEntry  6 }

chrComPmSonetCV 	OBJECT-TYPE
	SYNTAX		Gauge32			(0..4294967295)
	MAX-ACCESS 	read-only
	STATUS 		current
	DESCRIPTION
	""
	::= { chrComPmSonetSNT-PFE-CurrentEntry  7 }

chrComPmSonetUAS 	OBJECT-TYPE
	SYNTAX		Gauge32			(0..4294967295)
	MAX-ACCESS 	read-only
	STATUS 		current
	DESCRIPTION
	""
	::= { chrComPmSonetSNT-PFE-CurrentEntry  8 }

chrComPmSonetThresholdProfIndex 	OBJECT-TYPE
	SYNTAX		Unsigned32	(0..4294967295)
	MAX-ACCESS 	read-only
	STATUS 		current
	DESCRIPTION
	""
	::= { chrComPmSonetSNT-PFE-CurrentEntry  9 }

chrComPmSonetResetPmCountersAction 	OBJECT-TYPE
	SYNTAX		TruthValue
	MAX-ACCESS 	read-write
	STATUS 		current
	DESCRIPTION
	""
	::= { chrComPmSonetSNT-PFE-CurrentEntry  10 }


END
