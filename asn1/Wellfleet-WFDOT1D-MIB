Wellfleet-WFDOT1D-MIB DEFINITIONS ::= BEGIN

-- Created by mdl2asn version 3.1
-- Creation date: Wed Aug 30 16:50:03 EDT 1995


    IMPORTS

      IpAddress, Counter, Gauge, TimeTicks, Opaque, enterprises, mgmt
        FROM RFC1155-SMI
      OBJECT-TYPE
        FROM RFC-1212
      TRAP-TYPE
        FROM RFC-1215
      DisplayString, mib-2
        FROM RFC1213-MIB
      wfBridgeGroup
        FROM Wellfleet-COMMON-MIB;


    wfDot1d		OBJECT IDENTIFIER ::= { wfBridgeGroup 6 }
    wfDot1dBaseGroup	OBJECT IDENTIFIER ::= { wfDot1d 1 }
    wfDot1dStaticGroup  OBJECT IDENTIFIER ::= { wfDot1d 5 }


    wfDot1dBaseBridgeAddress OBJECT-TYPE
        SYNTAX	OCTET STRING
        ACCESS	read-only
        STATUS	mandatory
        DESCRIPTION
                "The MAC address used by this bridge when it must
                be referred to in a unique fashion.   It is
                recommended that this be the numerically smallest
                MAC address of all ports that belong to this
                bridge.  However it is only required to be unique.
                When concatenated with dot1dStpPriority a unique
                BridgeIdentifier is formed which is used in the
                Spanning Tree Protocol."
        ::= { wfDot1dBaseGroup 1 }

    wfDot1dBaseNumPorts OBJECT-TYPE
        SYNTAX	INTEGER
        ACCESS	read-only
        STATUS	mandatory
        DESCRIPTION
                "The number of ports controlled by this bridging
                entity."
        ::= { wfDot1dBaseGroup 2 }

    wfDot1dBaseType OBJECT-TYPE
        SYNTAX	INTEGER {
    		    unk(1),
    		    only(2),
    		    sr(3),
    		    srt(4)
    		}
        ACCESS	read-only
        STATUS	mandatory
        DESCRIPTION
                "Indicates what type of bridging this bridge can
                perform.  If a bridge is actually performing a
                certain type of bridging this will be indicated by
                entries in the port table for the given type."
        DEFVAL	{ only }
        ::= { wfDot1dBaseGroup 3 }

    wfDot1dStaticTable OBJECT-TYPE
        SYNTAX	SEQUENCE OF WfDot1dStaticTableEntry
        ACCESS	not-accessible
        STATUS	mandatory
        DESCRIPTION
                "'A table containing filtering information
                configured into the bridge by (local or network)
                management specifying the set of ports to which
                frames received from specific ports and containing
                specific destination addresses are allowed to be
                forwarded.  The value of zero in this table as the
                port number from which frames with a specific
                destination address are received, is used to
                specify all ports for which there is no specific
                entry in this table for that particular
                destination address.  Entries are valid for
                unicast and for group/broadcast addresses.'"
        ::= { wfDot1dStaticGroup 1 }

    wfDot1dStaticTableEntry OBJECT-TYPE
        SYNTAX	WfDot1dStaticTableEntry
        ACCESS	not-accessible
        STATUS	mandatory
        DESCRIPTION
                "'Filtering information configured into the bridge
                 by (local or network) management specifying the
                 set of ports to which frames received from a
                 specific port and containing a specific
                 destination address are allowed to be forwarded.'"
        INDEX	{ wfDot1dStaticAddress,
    		  wfDot1dStaticReceivePort }
        ::= { wfDot1dStaticTable 1 }

    WfDot1dStaticTableEntry ::= SEQUENCE {
    	    wfDot1dStaticAddress
    		OCTET STRING,
    	    wfDot1dStaticReceivePort
    		INTEGER,
    	    wfDot1dStaticAllowedToGoTo
    		OCTET STRING,
    	    wfDot1dStaticStatus
    		INTEGER
        }

    wfDot1dStaticAddress OBJECT-TYPE
        SYNTAX	OCTET STRING (SIZE (6))
        ACCESS	read-write
        STATUS	mandatory
        DESCRIPTION
                "'The destination MAC address in a frame to which
                this entry's filtering information applies.  This
                object can take the value of a unicast address, a
                group address or the broadcast address.'"
        ::= { wfDot1dStaticTableEntry 1 }

    wfDot1dStaticReceivePort OBJECT-TYPE
        SYNTAX	INTEGER
        ACCESS	read-write
        STATUS	mandatory
        DESCRIPTION
                "'Either the value '0', or the port number of the
                port from which a frame must be received in order
                for this entry's filtering information to apply.
                A value of zero indicates that this entry applies
                on all ports of the bridge for which there is no
                other applicable entry.'"
        ::= { wfDot1dStaticTableEntry 2 }

    wfDot1dStaticAllowedToGoTo OBJECT-TYPE
        SYNTAX	OCTET STRING
        ACCESS	read-write
        STATUS	mandatory
        DESCRIPTION
                "'The set of ports to which frames received from a
                specific port and destined for a specific MAC
                address, are allowed to be forwarded.  Each octet
                within the value of this object specifies a set of
                eight ports, with the first octet specifying ports
                1 through 8, the second octet specifying ports 9
                through 16, etc.  Within each octet, the most
                significant bit represents the lowest numbered
                port, and the least significant bit represents the
                highest numbered port.  Thus, each port of the
                bridge is represented by a single bit within the
                value of this object.  If that bit has a value of
                '1' then that port is included in the set of
                ports; the port is not included if its bit has a
                value of '0'.  (Note that the setting of the bit
                corresponding to the port from which a frame is
                received is irrelevant.)'"
        ::= { wfDot1dStaticTableEntry 3 }

    wfDot1dStaticStatus OBJECT-TYPE
        SYNTAX	INTEGER {
    		    other(1),
    		    invalid(2),
    		    permanent(3),
    		    reset(4),
    		    timeout(5)
    		}
        ACCESS	read-write
        STATUS	mandatory
        DESCRIPTION
                "'This object indicates the status of this entry.
                     other(1) - this entry is currently in use but
                          the conditions under which it will
                          remain so are different from each of the
                          following values.
                     invalid(2) - writing this value to the object
                          removes the corresponding entry.
                     permanent(3) - this entry is currently in use
                          and will remain so after the next reset
                          of the bridge.
                     deleteOnReset(4) - this entry is currently in
                          use and will remain so until the next
                          reset of the bridge.
                     deleteOnTimeout(5) - this entry is currently
                          in use and will remain so until it is
                          aged out.'"
        DEFVAL	{ invalid }
        ::= { wfDot1dStaticTableEntry 4 }

    END  -- Wellfleet-WFDOT1D-MIB
