XYLAN-XIP-MIB DEFINITIONS ::= BEGIN

     --  xylan-xip.mib
     --  Revision: 1.0
     --  Date: September 1998

     --  Alcatel Internetworking, Inc.
     --  26801 W. Agoura Road
     --  Calabasas, CA 91301
     --  (818) 880-3500
     --  support@ind.alcatel.com

     --  This module provides authoritative definitions for Alcatel Internetworking, Inc.
     --  enterprise-specific XIP (Xylan Interswitch Protocol).

     --  This module will be extended, as needed.


     --  Alcatel Internetworking, Inc. reserves the right to make changes in 
     --  specification and other information contained in this document 
     --  without prior notice.  The reader should consult Alcatel Internetworking,
     --  Inc. to determine whether any such changes have been made.
     --  Current MIBs are availible from the following URLs:
     --			ftp://ftp.ind.alcatel.com/pub/products/mibs
     --			http://www.ind.alcatel.com

     --  In no event shall Alcatel Internetworking, Inc. be liable for any incidental, 
     --  indirect, special, or consequential damages whatsoever (including 
     --  but not limited to lost profits) arising out of or related to this
     --  document or the information contained in it, even if Alcatel Internetworking,
     --  Inc. has been advised of, known, or should have known, the 
     --  possibility of such damages.
     --  Alcatel Internetworking, Inc. grants vendors, end-users, and other interested
     --  parties a non-exclusive license to use this Specification in connection
     --  with the management of Alcatel Internetworking, Inc. products.

     --  Copyright (C) 1998, Alcatel Internetworking, Inc. All Rights Reserved.

     
     	IMPORTS
		OBJECT-TYPE
			FROM RFC-1212
		IpAddress 
			FROM RFC1155-SMI
	        xylanXIPArch
			FROM XYLAN-BASE-MIB 
		MacAddress
			FROM BRIDGE-MIB
			;


xylanXIPGMAPconfig OBJECT IDENTIFIER ::= { xylanXIPArch 1 }
xylanXIPXMAPconfig OBJECT IDENTIFIER ::= { xylanXIPArch 2 }

-- GMAP Configuration *********************

xylanXIPGMAPstate OBJECT-TYPE
	SYNTAX  INTEGER {
		inactive (0),
		active   (1)
	}
	ACCESS  read-write
	STATUS  mandatory
	DESCRIPTION "Current state of the GMAP functionality."
	::= { xylanXIPGMAPconfig 1 }

xylanXIPGMAPgaptime OBJECT-TYPE
	SYNTAX INTEGER (0..65535)
	ACCESS read-write
	STATUS mandatory
	DESCRIPTION "The time in milliseconds for gaps between successive GMAP 
		     protocol packets."
	::= { xylanXIPGMAPconfig 2 }

xylanXIPGMAPupdatetime OBJECT-TYPE
	SYNTAX INTEGER (1..65535)
	ACCESS read-write
	STATUS mandatory
	DESCRIPTION "The time in seconds between GMAP update packet generation."
	::= { xylanXIPGMAPconfig 3 }

xylanXIPGMAPholdtime OBJECT-TYPE
	SYNTAX INTEGER (1..65535)
	ACCESS read-write
	STATUS mandatory
	DESCRIPTION "The time in minutes that the switch will remember 
		     information received in GMAP update packets."
	::= { xylanXIPGMAPconfig 4 }


-- GMAP Trap *********************

xylanXIPGMAPLastTrapReason OBJECT-TYPE
	SYNTAX  INTEGER {
		no-trap-sent (0),
		authenticated-group (1),
		conflicting-binding-rule (2),
		same-proto-different-groups-conflict (3),
		same-group-different-protocols-conflict (4),
		non-mobile-group (5)
	}
	ACCESS  read-only
	STATUS  mandatory
	DESCRIPTION "Reason for last GMAP update to not be applied.  Valid
                     reasons are: 

		       0 - No trap has been sent
		       1 - Target group is an authenticated group
		       2 - Update would conflict with a binding rule
		       3 - Update would create two different group entries
		           for the same protocol
		       4 - Update would create two different protocol entries
		           for the same group
		       5 - Target group is not mobile"

	::= { xylanXIPGMAPconfig 5 }

xylanXIPGMAPLastTrapPort OBJECT-TYPE
	SYNTAX  INTEGER 
	ACCESS  read-only
	STATUS  mandatory
	DESCRIPTION "The virtual port number of the last port on which the 
		     GMAP change was not applied because of a conflict."
	::= { xylanXIPGMAPconfig 6 }

xylanXIPGMAPLastTrapMac OBJECT-TYPE
	SYNTAX  MacAddress
	ACCESS  read-only
	STATUS  mandatory
	DESCRIPTION "The last MAC address for which a GMAP change was not
		     applied because of a conflict."
	::= { xylanXIPGMAPconfig 7 }

xylanXIPGMAPLastTrapProtocol OBJECT-TYPE
	SYNTAX  INTEGER 
	ACCESS  read-only
	STATUS  mandatory
	DESCRIPTION "The protocol identifier of the last GMAP change that
		     was not applied because of a conflict."
	::= { xylanXIPGMAPconfig 8 }

xylanXIPGMAPLastTrapGroup OBJECT-TYPE
	SYNTAX  INTEGER 
	ACCESS  read-only
	STATUS  mandatory
	DESCRIPTION "The group identifier of the last GMAP change that was 
		     not applied because of a conflict."
	::= { xylanXIPGMAPconfig 9 }

-- GMAP Table *****************************

xylanXIPGMAPTable OBJECT-TYPE
	SYNTAX  SEQUENCE OF XylanXIPGMAPTableEntry
	ACCESS  not-accessible
	STATUS  mandatory
	DESCRIPTION "GMAP MAC address list."
	::= { xylanXIPGMAPconfig 10 }

xylanXIPGMAPTableEntry OBJECT-TYPE
	SYNTAX  XylanXIPGMAPTableEntry
	ACCESS  not-accessible
	STATUS  mandatory
	DESCRIPTION "GMAP MAC address list."
	INDEX { xylanXIPGMAPMacAddr, xylanXIPGMAPProtocol }
	::= { xylanXIPGMAPTable 1 }

XylanXIPGMAPTableEntry ::= SEQUENCE {
	xylanXIPGMAPMacAddr MacAddress,
	xylanXIPGMAPProtocol INTEGER,
	xylanXIPGMAPGroup INTEGER,
	xylanXIPGMAPSrcSwitch MacAddress,
	xylanXIPGMAPFlags OCTET STRING (SIZE(4)),
	xylanXIPGMAPTimeout INTEGER
	} 

xylanXIPGMAPMacAddr OBJECT-TYPE
	SYNTAX  MacAddress
	ACCESS  read-only
	STATUS  mandatory
	DESCRIPTION "The MAC address of a GMAP entry."
	::= { xylanXIPGMAPTableEntry 1 }

xylanXIPGMAPProtocol OBJECT-TYPE
	SYNTAX  INTEGER 
	ACCESS  read-only
	STATUS  mandatory
	DESCRIPTION "The protocol identifier for a GMAP entry."
	::= { xylanXIPGMAPTableEntry 2 }

xylanXIPGMAPGroup OBJECT-TYPE
	SYNTAX  INTEGER 
	ACCESS  read-only
	STATUS  mandatory
	DESCRIPTION "The group identifier for a GMAP entry."
	::= { xylanXIPGMAPTableEntry 3 }

xylanXIPGMAPSrcSwitch OBJECT-TYPE
	SYNTAX  MacAddress
	ACCESS  read-only
	STATUS  mandatory
	DESCRIPTION "The MAC address of the switch that provided the
	             information for a GMAP entry."
	::= { xylanXIPGMAPTableEntry 4 }

xylanXIPGMAPFlags OBJECT-TYPE
	SYNTAX  OCTET STRING (SIZE(4)) 
	ACCESS  read-only
	STATUS  mandatory
	DESCRIPTION "The flags for a GMAP entry.  The least significant byte
	             holds the router flags.  The next byte contains the flags
	             from auto-tracker.  The most significant 2 bytes are not
	             currently used."
	::= { xylanXIPGMAPTableEntry 5 }

xylanXIPGMAPTimeout OBJECT-TYPE
	SYNTAX  INTEGER 
	ACCESS  read-only
	STATUS  mandatory
	DESCRIPTION "Seconds remaining before this entry will age out."
	::= { xylanXIPGMAPTableEntry 6 }

-- XMAP Configuration *********************

xylanXIPXMAPstate OBJECT-TYPE
	SYNTAX  INTEGER {
		inactive (0),
		active   (1)
	}
	ACCESS  read-write
	STATUS  mandatory
	DESCRIPTION "Current state of the XMAP agent."
	::= { xylanXIPXMAPconfig 1 }

xylanXIPXMAPdisctime OBJECT-TYPE
	SYNTAX INTEGER (1..65535)
	ACCESS read-write
	STATUS mandatory
	DESCRIPTION "The time in seconds for interval betweeen hello
		     packets in the initial discovery phase
		     of the XMAP protocol."
	::= { xylanXIPXMAPconfig 2 }

xylanXIPXMAPcommontime OBJECT-TYPE
	SYNTAX INTEGER (1..65535)
	ACCESS read-write
	STATUS mandatory
	DESCRIPTION "The time in seconds for the interval between hello
		     packets at other than the discovery phase."
	::= { xylanXIPXMAPconfig 3 }

-- XMAP Trap *********************

xylanXIPXMAPLastTrapReason OBJECT-TYPE
	SYNTAX  INTEGER {
		no-trap-sent (0),
		add (1),
		change (2),
		remove (3)
	}
	ACCESS  read-only
	STATUS  mandatory
	DESCRIPTION "Reason for last change of port status.  Valid
                     reasons are: 
		       0 - no trap has been sent
		       1 - port added 
		       2 - change of information on existing port
		       3 - port deleted"
	::= { xylanXIPXMAPconfig 4 }

xylanXIPXMAPLastTrapPort OBJECT-TYPE
	SYNTAX  INTEGER
	ACCESS  read-only
	STATUS  mandatory
	DESCRIPTION "The virtual port number of the port that most recently 
                     changed."
	::= { xylanXIPXMAPconfig 5 }

-- XMAP Adjacency Tables *********************

xylanXIPXMAPports OBJECT-TYPE
	SYNTAX  SEQUENCE OF XylanXIPXMAPPortEntry
	ACCESS  not-accessible
	STATUS  mandatory
	DESCRIPTION "XMAP adjacent switch, remote port, and group information."
	::= { xylanXIPXMAPconfig 6 }

xylanXIPXMAPPortentry OBJECT-TYPE
	SYNTAX  XylanXIPXMAPPortEntry
	ACCESS  not-accessible
	STATUS  mandatory
	DESCRIPTION "XMAP adjacent switch, remote port, and group information."
	INDEX { xylanXIPXMAPAdjPort, xylanXIPXMAPRemMac,
		xylanXIPXMAPRemPort }
	::= { xylanXIPXMAPports 1 }

XylanXIPXMAPPortEntry ::= SEQUENCE {
	xylanXIPXMAPAdjPort INTEGER,
	xylanXIPXMAPRemMac MacAddress,
	xylanXIPXMAPRemPort INTEGER,
	xylanXIPXMAPRemGroup INTEGER
	} 

xylanXIPXMAPAdjPort OBJECT-TYPE
	SYNTAX  INTEGER 
	ACCESS  read-only
	STATUS  mandatory
	DESCRIPTION "The local virtual port number which has an adjacent 
		     switch connected."
	::= { xylanXIPXMAPPortentry 1 }

xylanXIPXMAPRemMac OBJECT-TYPE
	SYNTAX  MacAddress
	ACCESS  read-only
	STATUS  mandatory
	DESCRIPTION "The MAC Address of the MPM in the adjacent switch."
	::= { xylanXIPXMAPPortentry 2 }

xylanXIPXMAPRemPort OBJECT-TYPE
	SYNTAX  INTEGER
	ACCESS  read-only
	STATUS  mandatory
	DESCRIPTION "The remote virtual port number in the adjacent switch."
	::= { xylanXIPXMAPPortentry 3 }

xylanXIPXMAPRemGroup OBJECT-TYPE
	SYNTAX  INTEGER
	ACCESS  read-only
	STATUS  mandatory
	DESCRIPTION "The remote group for the virtual port in the adjacent 
		     switch."
	::= { xylanXIPXMAPPortentry 4 }

xylanXIPXMAPhosts OBJECT-TYPE
	SYNTAX  SEQUENCE OF XylanXIPXMAPHostEntry
	ACCESS  not-accessible
	STATUS  mandatory
	DESCRIPTION "XMAP adjacent switch IP address information."
	::= { xylanXIPXMAPconfig 7 }

xylanXIPXMAPHostentry OBJECT-TYPE
	SYNTAX  XylanXIPXMAPHostEntry
	ACCESS  not-accessible
	STATUS mandatory
	DESCRIPTION "XMAP adjacent switch IP address information."
	INDEX { xylanXIPXMAPHostMac,
		xylanXIPXMAPIpAddr }
	::= { xylanXIPXMAPhosts 1 }

XylanXIPXMAPHostEntry ::= SEQUENCE {
	xylanXIPXMAPHostMac  MacAddress,
	xylanXIPXMAPIpAddr   IpAddress
	} 

xylanXIPXMAPHostMac OBJECT-TYPE
	SYNTAX  MacAddress
	ACCESS  read-only
	STATUS  mandatory
	DESCRIPTION "The MAC Address of the MPM in the adjacent switch."
	::= { xylanXIPXMAPHostentry 1 }

xylanXIPXMAPIpAddr OBJECT-TYPE
	SYNTAX  IpAddress
	ACCESS  read-only
	STATUS  mandatory
       	DESCRIPTION "An IP address of the adjacent switch."
	::= { xylanXIPXMAPHostentry 2 }

-- XMAP configuration end *********************

END
