CHASSISMGREXT-MIB

   --FORCE-INCLUDE <mib.h>
   --FORCE-INCLUDE <snmpdefs.h>
   --FORCE-INCLUDE <snmpstat.h>
   --FORCE-INCLUDE "mibproto.h"
 
	DEFINITIONS ::= BEGIN

	IMPORTS
	    MODULE-IDENTITY, OBJECT-TYPE, IpAddress, Integer32
			FROM SNMPv2-SMI
		DisplayString
			FROM SNMPv2-TC
		chassisMgrExt
			FROM APENT-MIB;

--  chassisMgrExt MIB

chassisMgrExtMib MODULE-IDENTITY
	LAST-UPDATED "9707202000Z" -- Wed July 20 20:00:00 EST 1997
	ORGANIZATION "ArrowPoint Communications Inc."
	CONTACT-INFO
	"
	Postal:               ArrowPoint Communications Inc.
				                 50 Nagog Park
				                 Acton, Massachusetts 01720
	   Tel:                   +1 978-206-3000  option 1
	   E-Mail:                support@arrowpoint.com"
	DESCRIPTION
		"This MIB module describes the ArrowPoint Communications
		enterprise MIB for the High Speed Serial Interface (HSSI)
		module."
	::= { chassisMgrExt 1 }

--- chassisMgrExt scalars

apChassisMgrExtChassisType OBJECT-TYPE
	SYNTAX INTEGER {
		ws100(0),
		ws800(1),
		ws150(2),
		ws50(3),
		unknown(4)
	} 
	MAX-ACCESS read-only
	STATUS current
	DESCRIPTION
		"This object specifies the type of chassis."
	--DEFAULT apjam-group apChassisGroupInst, apChassisMgrExtChassisName
	--DEFAULT apjam-popup-def apChassisGroupInst, Properties, local
	--DEFAULT ap-display-name Chassis Type
	--DEFAULT apjam-popup-ref apChassisGroupInst, Properties
	::= { chassisMgrExt 2 }

apChassisMgrExtChassisName OBJECT-TYPE
	SYNTAX DisplayString ( SIZE ( 0..16 ) )
	MAX-ACCESS read-only
	STATUS current
	DESCRIPTION
		"This object specifies the name of the chassis."
	--DEFAULT ap-display-name Chassis Name
	--DEFAULT apjam-popup-ref apChassisGroupInst, Properties
	::= { chassisMgrExt 3 }

apChassisMgrExtChassisSerialNumber OBJECT-TYPE
	SYNTAX DisplayString ( SIZE( 0..255 ) )
	MAX-ACCESS read-only
	STATUS current
	DESCRIPTION
		"This object specifies the serial number of the chassis."
	--DEFAULT ap-display-name Serial #
	--DEFAULT apjam-popup-ref apChassisGroupInst, Properties
	::= { chassisMgrExt 4 }

apChassisMgrExtNumberSlots OBJECT-TYPE
	SYNTAX INTEGER (0..14)
	MAX-ACCESS read-only
	STATUS current
	DESCRIPTION
		"This object specifies the number of slots in the chassis."
	--DEFAULT ap-display-name Number of Slots
	--DEFAULT apjam-popup-ref apChassisGroupInst, Properties
	::= { chassisMgrExt 5 }

apChassisMgrExtNumberModules OBJECT-TYPE
	SYNTAX INTEGER
	MAX-ACCESS read-only
	STATUS current
	DESCRIPTION
		"This object specifies the number of modules in the chassis."
	--DEFAULT ap-display-name Number of Modules
	--DEFAULT apjam-popup-ref apChassisGroupInst, Properties
	::= { chassisMgrExt 6 }

apChassisMgrExtNumberPowerSupplies OBJECT-TYPE
	SYNTAX INTEGER (1..2)
	MAX-ACCESS read-only
	STATUS current
	DESCRIPTION
		"This object specifies the number of power supplies in
		the chassis."
	--DEFAULT ap-display-name Number of Pwer Supplies
	--DEFAULT apjam-popup-ref apChassisGroupInst, Properties
	::= { chassisMgrExt 7 }

apChassisMgrExtNumberFans OBJECT-TYPE
	SYNTAX INTEGER (1..4)
	MAX-ACCESS read-only
	STATUS current
	DESCRIPTION
		"This object specifies the number of fans in the chassis."
	--DEFAULT ap-display-name Number of Fans
	--DEFAULT apjam-popup-ref apChassisGroupInst, Properties
	::= { chassisMgrExt 8 }

apChassisMgrExtSoftwareVersionNumber OBJECT-TYPE
	SYNTAX DisplayString ( SIZE ( 0..4 ) )
	MAX-ACCESS read-only
	STATUS current
	DESCRIPTION
		"This object specifies the version number of the running
		software in the chassis."
	--DEFAULT ap-display-name Software version
	--DEFAULT apjam-popup-ref apChassisGroupInst, Properties
	::= { chassisMgrExt 9 }

apChassisMgrExtBootpState OBJECT-TYPE
	SYNTAX INTEGER  {
		bootp-disabled(0),
		bootp-enabled(1)
	}
	MAX-ACCESS read-only
	STATUS current
	DESCRIPTION
		"This object specifies the state of the BOOTP services at chassis
		boot time."
	--DEFAULT ap-display-name Bootp State
	--DEFAULT apjam-popup-ref apChassisGroupInst, Properties
	::= { chassisMgrExt 10 }

apChassisMgrExtMgmtPortIpAddress OBJECT-TYPE
	SYNTAX IpAddress
	MAX-ACCESS read-only
	STATUS current
	DESCRIPTION
		"This object specifies the Ip Address of the management port on
		the chassis."
	--DEFAULT ap-display-name Mgmt Port Ip Addr
	--DEFAULT apjam-popup-ref apChassisGroupInst, Properties
	::= { chassisMgrExt 11 }

apChassisMgrExtBaseEthernetAddress OBJECT-TYPE
	SYNTAX DisplayString ( SIZE ( 0..18 ) )
	MAX-ACCESS read-only
	STATUS current
	DESCRIPTION
		"This object specifies the base ethernet address the unit."
	--DEFAULT ap-display-name Ethernet
	--DEFAULT apjam-popup-ref apChassisGroupInst, Properties
	::= { chassisMgrExt 12 }

apChassisMgrExtCpuUtilization OBJECT-TYPE
	SYNTAX INTEGER
	MAX-ACCESS read-only
	STATUS current
	DESCRIPTION
		"This object has been DEPRECATED.  Use:
		  apChassisMgrExtSubModuleCPUInstantaneous or
		  apChassisMgrExtSubModuleCPUAverage"
	--DEFAULT ap-display-name Cpu Utilization
	--DEFAULT apjam-popup-ref apChassisGroupInst, Properties
	::= { chassisMgrExt 13 }

apChassisMgrExtMajorHwVersion OBJECT-TYPE
	SYNTAX DisplayString ( SIZE( 0..255 ) )
	MAX-ACCESS read-only
	STATUS current
	DESCRIPTION
		"This object specifies the major hardware version of the chassis."
	--DEFAULT ap-display-name Hw Major Version
	--DEFAULT apjam-popup-ref apChassisGroupInst, Properties
	::= { chassisMgrExt 14 }

apChassisMgrExtMinorHwVersion OBJECT-TYPE
	SYNTAX DisplayString ( SIZE( 0..255 ) )
	MAX-ACCESS read-only
	STATUS current
	DESCRIPTION
		"This object specifies the minor hardware version of the chassis."
	--DEFAULT ap-display-name Hw Minor Version
	--DEFAULT apjam-popup-ref apChassisGroupInst, Properties
	::= { chassisMgrExt 15 }

--- chassisMgrExt : Chassis Module Table

apChassisMgrExtModuleTable OBJECT-TYPE
	SYNTAX  SEQUENCE OF ApChassisMgrExtModuleEntry
	MAX-ACCESS  not-accessible
	STATUS  current
	DESCRIPTION
		"The Module Table for a given slot in the chassis."
	::= { chassisMgrExt 16 }

apChassisMgrExtModuleEntry OBJECT-TYPE
	SYNTAX  ApChassisMgrExtModuleEntry
    MAX-ACCESS  not-accessible
	STATUS  current
    DESCRIPTION
		"An entry in the Chassis Module Table."
	INDEX { apChassisMgrExtModuleSlotNumber }
	--DEFAULT apjam-group apChassisModuleInst, apChassisMgrExtModuleType
	--DEFAULT apjam-popup-def apChassisModuleInst, Properties, local
	::= { apChassisMgrExtModuleTable 1 }

	ApChassisMgrExtModuleEntry ::=
		SEQUENCE {
			apChassisMgrExtModuleSlotNumber
				INTEGER,
			apChassisMgrExtModuleType
				INTEGER,
			apChassisMgrExtModuleName
				DisplayString,
			apChassisMgrExtModuleSerialNumber
				DisplayString,
			apChassisMgrExtModuleMajorHwVersion
				DisplayString,
			apChassisMgrExtModuleMinorHwVersion
				DisplayString,
			apChassisMgrExtModuleOpStatus
				INTEGER,				
			apChassisMgrExtModuleNumSubModules
				INTEGER
		}

apChassisMgrExtModuleSlotNumber OBJECT-TYPE
	SYNTAX INTEGER (1..14)
	MAX-ACCESS read-only
	STATUS current
	DESCRIPTION
		"This object specifies slot number of this module within the chassis."
	--DEFAULT ap-display-name Slot Number
	--DEFAULT apjam-popup-ref apChassisModuleInst, Properties
	::= { apChassisMgrExtModuleEntry 2 }

apChassisMgrExtModuleType OBJECT-TYPE
	SYNTAX INTEGER {
		scm(0),
		sfm(1),
		scfm(2),
		fem-t1(3),
		dual-hssi(4),
		fem(5),
		fenic(6),
		genic(7),
		gem(8),
		unknown(9)
	}		
	MAX-ACCESS read-only
	STATUS current
	DESCRIPTION
		"This object specifies module type within the chassis."
	--DEFAULT ap-display-name Type
	--DEFAULT apjam-popup-ref apChassisModuleInst, Properties
	::= { apChassisMgrExtModuleEntry 3 }

apChassisMgrExtModuleName OBJECT-TYPE
	SYNTAX DisplayString( SIZE( 0..255 ) )
	MAX-ACCESS read-only
	STATUS current
	DESCRIPTION
		"This object specifies module name within the chassis."
	--DEFAULT ap-display-name Name
	--DEFAULT apjam-popup-ref apChassisModuleInst, Properties
	::= { apChassisMgrExtModuleEntry 4 }

apChassisMgrExtModuleSerialNumber OBJECT-TYPE
	SYNTAX DisplayString ( SIZE( 0..255 ) )
	MAX-ACCESS read-only
	STATUS current
	DESCRIPTION
		"This object specifies the serial number of the module
		within the chassis."
	--DEFAULT ap-display-name Serial Number
	--DEFAULT apjam-popup-ref apChassisModuleInst, Properties
	::= { apChassisMgrExtModuleEntry 5 }

apChassisMgrExtModuleOpStatus OBJECT-TYPE
	SYNTAX INTEGER {
		powered-off(0),
		powered-on(1),
		primary(2),
		backup(3),
		bad(4),
		unknown(5)
	}
	MAX-ACCESS read-only
	STATUS current
	DESCRIPTION
		"This object specifies the module's operational status
		within the chassis."
	--DEFAULT ap-display-name Operational Status
	--DEFAULT apjam-popup-ref apChassisModuleInst, Properties
	::= { apChassisMgrExtModuleEntry 6 }

apChassisMgrExtModuleNumSubModules OBJECT-TYPE
	SYNTAX INTEGER (0..8)
	MAX-ACCESS read-only
	STATUS current
	DESCRIPTION
		"This object specifies the number of sub-modules on this module within
		the chassis."
	::= { apChassisMgrExtModuleEntry 7 }

apChassisMgrExtModuleMajorHwVersion OBJECT-TYPE
	SYNTAX DisplayString ( SIZE( 0..255 ) )
	MAX-ACCESS read-only
	STATUS current
	DESCRIPTION
		"This object specifies the hardware major version of the module
		within the chassis."
	--DEFAULT ap-display-name HW Major Version
	--DEFAULT apjam-popup-ref apChassisModuleInst, Properties
	::= { apChassisMgrExtModuleEntry 8 }

apChassisMgrExtModuleMinorHwVersion OBJECT-TYPE
	SYNTAX DisplayString ( SIZE( 0..255 ) )
	MAX-ACCESS read-only
	STATUS current
	DESCRIPTION
		"This object specifies the minor hardware version of the module
		within the chassis."
	--DEFAULT ap-display-name HW Minor Version
	--DEFAULT apjam-popup-ref apChassisModuleInst, Properties
	::= { apChassisMgrExtModuleEntry 9 }

-- chassisMgrExt : SubModule Table

apChassisMgrExtSubModuleTable OBJECT-TYPE
	SYNTAX  SEQUENCE OF ApChassisMgrExtSubModuleEntry
	MAX-ACCESS  not-accessible
	STATUS  current
	DESCRIPTION
		"The table describes sub-module(s) associated with a module
		in a slot in the chassis."
	::= { chassisMgrExt 17 }

apChassisMgrExtSubModuleEntry OBJECT-TYPE
	SYNTAX  ApChassisMgrExtSubModuleEntry
    MAX-ACCESS  not-accessible
	STATUS  current
    DESCRIPTION
		"An entry in the sub-module table."
	INDEX { apChassisMgrExtSubModuleSlot, apChassisMgrExtSubModuleSubSlot }
	--DEFAULT apjam-group apChassisSubModuleInst, apChassisMgrExtSubModuleType
	--DEFAULT apjam-popup-def apChassisSubModuleInst, Properties, local
	::= { apChassisMgrExtSubModuleTable 1 }

	ApChassisMgrExtSubModuleEntry ::=
		SEQUENCE {
			apChassisMgrExtSubModuleSlot
				INTEGER,
			apChassisMgrExtSubModuleSubSlot
				INTEGER,
			apChassisMgrExtSubModuleType
				INTEGER,
			apChassisMgrExtSubModuleName
				DisplayString,
			apChassisMgrExtSubModuleOpStatus
				INTEGER,										
			apChassisMgrExtSubModuleSsCardType
				INTEGER,										
			apChassisMgrExtSubModuleSsCardOpStatus
				INTEGER,
			apChassisMgrExtSubModulePortName
				DisplayString,
			apChassisMgrExtSubModulePortNumber
				INTEGER,
			apChassisMgrExtSubModuleSystemHeapFree
				Integer32,
			apChassisMgrExtSubModuleSystemHeapChainDepth
				Integer32,
			apChassisMgrExtSubModuleInstalledMemory
				Integer32,
			apChassisMgrExtSubModuleCPUInstantaneous
				Integer32,
			apChassisMgrExtSubModuleCPUAverage
				Integer32
		}

apChassisMgrExtSubModuleSlot OBJECT-TYPE
	SYNTAX INTEGER (1..14)
	MAX-ACCESS read-only
	STATUS current
	DESCRIPTION
		"This object specifies the slot number associated with this sub-module
		within the chassis."
	--DEFAULT ap-display-name Slot
	--DEFAULT apjam-popup-ref apChassisSubModuleInst, Properties
	::= { apChassisMgrExtSubModuleEntry 1 }

apChassisMgrExtSubModuleSubSlot OBJECT-TYPE
	SYNTAX INTEGER (1..8)
	MAX-ACCESS read-only
	STATUS current
	DESCRIPTION
		"This object specifies sub-slot associated with this sub-module within
		the chassis."
	--DEFAULT ap-display-name Sub Slot
	--DEFAULT apjam-popup-ref apChassisSubModuleInst, Properties
	::= { apChassisMgrExtSubModuleEntry 2 }

apChassisMgrExtSubModuleType OBJECT-TYPE
	SYNTAX INTEGER {
		scm-submodule(0),
		sfm-submodule(1),
		scfm-submodule(2),
		t1-submodule(3),
		hssi-submodule(4),
		epif-submodule(5),
		v35-submodule(6),
		xpif-submodule(7),
		sfm2-submodule(8),
		scfm2-submodule(9),
		genic-2port-submodule(10),
		genic-1port-submodule(11),
		unknown-submodule(12)
	}		
	MAX-ACCESS read-only
	STATUS current
	DESCRIPTION
		"This object specifies the type of sub-module."
	--DEFAULT ap-display-name Type
	--DEFAULT apjam-popup-ref apChassisSubModuleInst, Properties
	::= { apChassisMgrExtSubModuleEntry 3 }

apChassisMgrExtSubModuleName OBJECT-TYPE
	SYNTAX DisplayString ( SIZE ( 0..16 ) )
	MAX-ACCESS read-only
	STATUS current
	DESCRIPTION
		"This object specifies the name of the sub-module."
	--DEFAULT ap-display-name Name
	--DEFAULT apjam-popup-ref apChassisSubModuleInst, Properties
	::= { apChassisMgrExtSubModuleEntry 4 }

apChassisMgrExtSubModuleOpStatus OBJECT-TYPE
	SYNTAX INTEGER {
		offline-ok(0),
		offline-bad(1),
		online(2),
		bad(3),
		going-online(4),
		going-offline(5),
		inserted(6),
		post(7),
		post-ok(8),
		post-fail(9),
		post-bad-comm(10),
		any(11),
		unknown-state(12)
	}
	MAX-ACCESS read-only
	STATUS current
	DESCRIPTION
		"This object specifies the sub-module's operational status
		within the chassis."
	--DEFAULT ap-display-name Operational Status
	--DEFAULT apjam-popup-ref apChassisSubModuleInst, Properties
	::= { apChassisMgrExtSubModuleEntry 5 }
	
apChassisMgrExtSubModuleSsCardType OBJECT-TYPE
	SYNTAX INTEGER {
		hifen-t1(0),
		hifen-hssi(1),
		unknown(2)
	}
	MAX-ACCESS read-only
	STATUS current
	DESCRIPTION
		"This object specifies the type of Special Services card for this 
		sub-module within the chassis."
	--DEFAULT ap-display-name Special Services Card
	--DEFAULT apjam-popup-ref apChassisSubModuleInst, Properties
	::= { apChassisMgrExtSubModuleEntry 6 }

apChassisMgrExtSubModuleSsCardOpStatus OBJECT-TYPE
	SYNTAX INTEGER {
		offline-ok(0),
		offline-bad(1),
		online(2),
		unknown-state(3)
	}
	MAX-ACCESS read-only
	STATUS current
	DESCRIPTION
		"This object specifies the operational status of the Special Services card 
		for this sub-module within the chassis."
	--DEFAULT ap-display-name Special Service Status
	--DEFAULT apjam-popup-ref apChassisSubModuleInst, Properties
	::= { apChassisMgrExtSubModuleEntry 7 }

apChassisMgrExtSubModulePortName OBJECT-TYPE
	SYNTAX DisplayString ( SIZE ( 0..255 ) )
	MAX-ACCESS read-only
	STATUS current
	DESCRIPTION
		"This object specifies the user visible port name."
	--DEFAULT ap-display-name Port Name
	--DEFAULT apjam-popup-ref apChassisSubModuleInst, Properties
	::= { apChassisMgrExtSubModuleEntry 8 }

apChassisMgrExtSubModulePortNumber OBJECT-TYPE
	SYNTAX INTEGER (1..12)
	MAX-ACCESS read-only
	STATUS current
	DESCRIPTION
		"This object specifies the external port number of this sub-slot 
		associated with this sub-module within the chassis."
	--DEFAULT ap-display-name Port Number
	--DEFAULT apjam-popup-ref apChassisSubModuleInst, Properties
	::= { apChassisMgrExtSubModuleEntry 9 }

apChassisMgrExtSubModuleSystemHeapFree OBJECT-TYPE
	SYNTAX Integer32
	MAX-ACCESS read-only
	STATUS current
	DESCRIPTION
		"This object identifes the amount of available system heap memory."
	::= { apChassisMgrExtSubModuleEntry 10 }

apChassisMgrExtSubModuleSystemHeapChainDepth OBJECT-TYPE
	SYNTAX Integer32
	MAX-ACCESS read-only
	STATUS current
	DESCRIPTION
		"This object specifies the chain depth of the system heap."
	::= { apChassisMgrExtSubModuleEntry 11 }

apChassisMgrExtSubModuleInstalledMemory OBJECT-TYPE
	SYNTAX Integer32
	MAX-ACCESS read-only
	STATUS current
	DESCRIPTION
		"This object specifies the amount of memory present on the
		 submodule."
	::= { apChassisMgrExtSubModuleEntry 12 }

apChassisMgrExtSubModuleCPUInstantaneous OBJECT-TYPE
	SYNTAX Integer32 (0..100)
	MAX-ACCESS read-only
	STATUS current
	DESCRIPTION
		"This object specifies the instantaneous CPU utilization"
	::= { apChassisMgrExtSubModuleEntry 13 }

apChassisMgrExtSubModuleCPUAverage OBJECT-TYPE
	SYNTAX Integer32 (0..100)
	MAX-ACCESS read-only
	STATUS current
	DESCRIPTION
		"This object specifies the average CPU utilization" 
	::= { apChassisMgrExtSubModuleEntry 14 }

apChassisMgrExtSubModuleBufferTable OBJECT-TYPE
	SYNTAX  SEQUENCE OF ApChassisMgrExtSubModuleBufferEntry
	MAX-ACCESS  not-accessible
	STATUS  current
	DESCRIPTION
		"The table describes buffers for sub-module(s) associated with a module
		in a slot in the chassis."
	::= { chassisMgrExt 18 }

apChassisMgrExtSubModuleBufferEntry OBJECT-TYPE
	SYNTAX  ApChassisMgrExtSubModuleBufferEntry
    MAX-ACCESS  not-accessible
	STATUS  current
    DESCRIPTION
		"An entry in the sub-module buffer table."
	INDEX { apChassisMgrExtSubModuleBufferPool,apChassisMgrExtSubModuleBufferSlot, apChassisMgrExtSubModuleBufferSubSlot }
	::= { apChassisMgrExtSubModuleBufferTable 1 }

	ApChassisMgrExtSubModuleBufferEntry ::=
		SEQUENCE {
			apChassisMgrExtSubModuleBufferPool
				INTEGER,
			apChassisMgrExtSubModuleBufferSlot
				INTEGER,
			apChassisMgrExtSubModuleBufferSubSlot
				INTEGER,
			apChassisMgrExtSubModuleBufferSize
				Integer32,
			apChassisMgrExtSubModuleBufferCount
				Integer32,
			apChassisMgrExtSubModuleBufferAvailable
				Integer32,
			apChassisMgrExtSubModuleBufferFailures
				Integer32,
			apChassisMgrExtSubModuleBufferLowBufferCount
				Integer32
		}

apChassisMgrExtSubModuleBufferPool OBJECT-TYPE
	SYNTAX INTEGER (0..1)
	MAX-ACCESS read-only
	STATUS current
	DESCRIPTION
		"This object specifies buffer pool associated with this sub-module 
		within the chassis."
	::= { apChassisMgrExtSubModuleBufferEntry 1 }

apChassisMgrExtSubModuleBufferSlot OBJECT-TYPE
	SYNTAX INTEGER (1..14)
	MAX-ACCESS read-only
	STATUS current
	DESCRIPTION
		"This object specifies the slot number associated with this sub-module
		within the chassis."
	::= { apChassisMgrExtSubModuleBufferEntry 2 }

apChassisMgrExtSubModuleBufferSubSlot OBJECT-TYPE
	SYNTAX INTEGER (1..8)
	MAX-ACCESS read-only
	STATUS current
	DESCRIPTION
		"This object specifies sub-slot associated with this sub-module within
		the chassis."
	::= { apChassisMgrExtSubModuleBufferEntry 3 }

apChassisMgrExtSubModuleBufferSize OBJECT-TYPE
	SYNTAX Integer32
	MAX-ACCESS read-only
	STATUS current
	DESCRIPTION
		"This object specifies the buffer pool size."
	::= { apChassisMgrExtSubModuleBufferEntry 4 }

apChassisMgrExtSubModuleBufferCount OBJECT-TYPE
	SYNTAX Integer32
	MAX-ACCESS read-only
	STATUS current
	DESCRIPTION
		"This object specifies the buffer pool count."
	::= { apChassisMgrExtSubModuleBufferEntry 5 }

apChassisMgrExtSubModuleBufferAvailable OBJECT-TYPE
	SYNTAX Integer32
	MAX-ACCESS read-only
	STATUS current
	DESCRIPTION
		"This object specifies the number of available buffers in the buffer pool."
	::= { apChassisMgrExtSubModuleBufferEntry 6 }

apChassisMgrExtSubModuleBufferFailures OBJECT-TYPE
	SYNTAX Integer32
	MAX-ACCESS read-only
	STATUS current
	DESCRIPTION
		"This object specifies the number of buffer pool failures."
	::= { apChassisMgrExtSubModuleBufferEntry 7 }

apChassisMgrExtSubModuleBufferLowBufferCount OBJECT-TYPE
	SYNTAX Integer32
	MAX-ACCESS read-only
	STATUS current
	DESCRIPTION
		"This object specifies the buffer low threshold count."
	::= { apChassisMgrExtSubModuleBufferEntry 8 }

END
