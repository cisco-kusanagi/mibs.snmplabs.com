CXModuleHardware-MIB DEFINITIONS ::= BEGIN

IMPORTS
	TimeTicks               FROM RFC1155-SMI
	OBJECT-TYPE             FROM RFC-1212
	DisplayString           FROM RFC1213-MIB

--  Proprietary Imports

	cxModuleHardware, Alias 
				FROM CXProduct-SMI;

cxModuleHwAlias OBJECT-TYPE
	SYNTAX  Alias
	ACCESS  read-write
	STATUS  mandatory
	DESCRIPTION
"Determines the name the network administrator assigns to the CPU card.
When you configure via the local console, this name is the command prompt.

The setting of this object is dynamic. The system immediately implements
the name you choose.

Range of Values: From 1 to 32 alphanumeric characters. You can use any 
combination of lettersor numbers; however, you cannot use blank spaces. 
Use a dash or underscore as a delimiter.

Default value:  
- CX900 architecture: CX900

- CX1000 architecture: CX1000

Configuration Changed: Operative"

	::= { cxModuleHardware 1 }

cxModuleHwRevAssemblyAndEco OBJECT-TYPE
	SYNTAX  INTEGER
	ACCESS  read-only
	STATUS  mandatory
	DESCRIPTION
"Displays the hardware revision of the device.
You cannot modify this object. It is a display that the software provides.

Range of Values: 7 numeric bits

Default Value: None "

	::= { cxModuleHardware 2 }

cxModuleHwPhysSlot OBJECT-TYPE
	SYNTAX  INTEGER
	ACCESS  read-only
	STATUS  mandatory
	DESCRIPTION
"Displays the number of the physical slot where the CPU card resides.
You cannot modify this object. It is a display that the software provides.

Note: THE CX 900 DOES NOT SUPPORT THIS OBJECT.

Range of values:
- CX900 architechture: Not supported

- CX1000 architechture: From 1 to 16

Default value: None "

	::= { cxModuleHardware 3 }


cxModuleHwCpuClockSpeed OBJECT-TYPE
	SYNTAX  INTEGER
	ACCESS  read-only
	STATUS  mandatory
	DESCRIPTION
"Displays the CPU clock rate in Khz.
You cannot modify this object. It is a display that the software provides.

Range of Values: None. The value is hardcoded on the CPU.

Default Value:  25000"

	::= { cxModuleHardware 4 }

cxModuleHwLedsDisplay OBJECT-TYPE
	SYNTAX  INTEGER
	ACCESS  read-only
	STATUS  mandatory
	DESCRIPTION
"Displays the status of the error LED. 
You cannot modify this object. It is a display that the software provides.

Options:
on: Error LED is on.

off: Error LED is off.

Default Value: None"

	::= { cxModuleHardware 5 }


cxModuleHwFlashEpromSize OBJECT-TYPE
	SYNTAX  INTEGER
	ACCESS  read-only
	STATUS  mandatory
	DESCRIPTION
"Dispays the size, in Kbytes, of the Flash EPROM.
You cannot modify this object. It is a display that the software provides.

Range of Values: A maximum of 4 digits from 1024 to 6144

Default Value: None "

	::= { cxModuleHardware 7 }

cxModuleHwPrivateDramSize OBJECT-TYPE
	SYNTAX  INTEGER
	ACCESS  read-only
	STATUS  mandatory
	DESCRIPTION
"Displays the size, in Kbytes, of the System DRAM.
You cannot modify this object. It is a display that the software provides.

Range of Values: A maximum of 5 digits from 512 to 33792

Default Value: None"

	::= { cxModuleHardware 8 }

cxModuleHwSharedDramSize OBJECT-TYPE
	SYNTAX  INTEGER
	ACCESS  read-only
	STATUS  mandatory
	DESCRIPTION
"Displays the size, in Kbytes, of the Data Buffer DRAM.
You cannot modify this object. It is a display that the software provides.
Range of Values:
-A maximum of 5 digits from 512 to 33792
Default Value: None"

	::= { cxModuleHardware 9 }

cxModuleHwUpTimeTicks OBJECT-TYPE
	SYNTAX  TimeTicks
	ACCESS  read-only
	STATUS  mandatory
	DESCRIPTION
"Displays the number of time ticks,in 10msec increments, since power up.
You cannot modify this object. It is a display that the software provides.

Range of Values: 0 to 4,294,967,295

Default Value: 0 "

	::= { cxModuleHardware 12 }

cxModuleHwResetTimeOut OBJECT-TYPE
	SYNTAX   INTEGER
	ACCESS   read-write
	STATUS   mandatory
	DESCRIPTION
"Determines the length of delay, in seconds before next scheduled card
reset. This type of reset saves the configuration before resetting.

The setting of this object is dynamic. The system immediately begins
reducing the value you enter.

Range of Values: A maximum of 10 digits from 0 to 4,294,967,295

Default Value:  0

Configuration Changed:  Operative "

	::= { cxModuleHardware 13 }

cxModuleHwSwVersion OBJECT-TYPE
	SYNTAX   DisplayString
	ACCESS   read-only
	STATUS   mandatory
	DESCRIPTION
"Displays the textual string which identifies the software currently
running on the device.

You cannot modify this object. It is a display that the software provides."

     ::= { cxModuleHardware 14 }


cxModuleHwNodeId   OBJECT-TYPE
	SYNTAX   INTEGER (0..65535)
	ACCESS   read-write
	STATUS   mandatory
	DESCRIPTION
"Identifies this system with an ID number. This parameter is used only for
SKYDATA's connection management.

Range of Values: 0 to 65,535

Default Value:  None "

	::= { cxModuleHardware 15 }


END
