XIPMROUTE-MIB DEFINITIONS ::= BEGIN

IMPORTS
    MODULE-IDENTITY, OBJECT-TYPE, experimental,
    Integer32, Counter32, Counter64,
    IpAddress, TimeTicks             FROM SNMPv2-SMI
    DisplayString, RowStatus         FROM SNMPv2-TC
    MODULE-COMPLIANCE, OBJECT-GROUP  FROM SNMPv2-CONF
    xediaMibs
        FROM XEDIA-REG
    InterfaceIndex, InterfaceIndexOrZero
	 FROM IF-MIB;

xipMRouteMIB MODULE-IDENTITY
    LAST-UPDATED "9903120000Z" 
    ORGANIZATION "Xedia Corp."
    CONTACT-INFO
            "support@xedia.com"
    DESCRIPTION
            "The MIB module for management of IP Multicast routing, but
            independent of the specific multicast routing protocol in
            use. XXX "
    ::= { xediaMibs 29 }


xipMRouteMIBObjects OBJECT IDENTIFIER ::= { xipMRouteMIB 1 }

xipMRoute      OBJECT IDENTIFIER ::= { xipMRouteMIBObjects 1 }


-- the Xedia IP Multicast Routing MIB-Group
--
-- a collection of objects providing information about
-- IP Multicast Groups


--
--  The Multicast Routing Interface Table
--

xipMRouteInterfaceTable OBJECT-TYPE
    SYNTAX     SEQUENCE OF XipMRouteInterfaceEntry
    MAX-ACCESS not-accessible
    STATUS     current
    DESCRIPTION
            "The (conceptual) table containg multicast routing
            information specific to interfaces."
    ::= { xipMRoute 1 }

xipMRouteInterfaceEntry OBJECT-TYPE
    SYNTAX     XipMRouteInterfaceEntry
    MAX-ACCESS not-accessible
    STATUS     current
    DESCRIPTION
            "An entry (conceptual row) containing the multicast routing
            information for a particular interface."
    INDEX      { xipMRouteInterfaceIfIndex }
    ::= { xipMRouteInterfaceTable 1 }

XipMRouteInterfaceEntry ::= SEQUENCE {
    xipMRouteInterfaceIfIndex		InterfaceIndex,
    xipMRouteInterfaceProtocol		INTEGER,
    xipMRouteInterfaceAdminStatus	INTEGER,
    xipMRouteInterfaceAddress		IpAddress
}

xipMRouteInterfaceIfIndex OBJECT-TYPE
    SYNTAX     InterfaceIndex
    MAX-ACCESS not-accessible
    STATUS     current
    DESCRIPTION
            "The ifIndex value of the interface for which this entry
            contains information."
    ::= { xipMRouteInterfaceEntry 1 }

xipMRouteInterfaceProtocol OBJECT-TYPE
    SYNTAX     INTEGER {
	           none(0),
--                 other(1),
--                 local(2), 
--                 netmgmt(3),
                   dvmrp(4),
--                 mospf(5),
--                 pimSparseDense(6),
--                 cbt(7),
--                 pimSparseMode(8),
                   pimDenseMode(9)
--                 igmpOnly(10)
               }
    MAX-ACCESS read-create
    STATUS     current
    DESCRIPTION
            "The routing protocol running on this interface."
    DEFVAL	{ none }
    ::= { xipMRouteInterfaceEntry 2 }

xipMRouteInterfaceAdminStatus OBJECT-TYPE
    SYNTAX      INTEGER {
                    enabled(1),
                    disabled(2)
                }
    MAX-ACCESS read-create
    STATUS     current
    DESCRIPTION
            "The status of this entry.  Creating the entry enables multicast
            on the virtual interface; destroying the entry or setting it
            to notInService disables multicast on the virtual interface."
    DEFVAL	{ disabled }
    ::= { xipMRouteInterfaceEntry 3 }

xipMRouteInterfaceAddress OBJECT-TYPE
    SYNTAX      IpAddress
    MAX-ACCESS read-create
    STATUS     current
    DESCRIPTION
            "Interface address associated with the multicast protocol.  
	     When not specified (0.0.0.0), multicast protocols will be
	     associated with the first address started on the interface."
    DEFVAL	{ '00000000'H }		-- 0.0.0.0
    ::= { xipMRouteInterfaceEntry 4 }

END
