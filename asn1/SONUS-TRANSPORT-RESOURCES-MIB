--
-- This SMIv2 module has been generated by smidump 0.2-cvs. Do not edit.
--

SONUS-TRANSPORT-RESOURCES-MIB DEFINITIONS ::= BEGIN

IMPORTS
    Integer32, MODULE-IDENTITY, OBJECT-TYPE
        FROM SNMPv2-SMI
    RowStatus
        FROM SNMPv2-TC
    sonusResourcesMIBs
        FROM SONUS-SMI;

sonusTransportResourcesMIB MODULE-IDENTITY
    LAST-UPDATED    "200102030000Z"
    ORGANIZATION    
            "Sonus Networks, Inc."
    CONTACT-INFO    
            "   Customer Support    
             Sonus Networks, Inc,
             5 carlisle Road
             Westford, MA 01886
             USA
             
             Tel: 978-692-8999
             Fax: 978-392-9118
             E-mail: cs.snmp@sonusnet.com"
    DESCRIPTION     
            "The MIB Module for Transport Reources Management."
    ::= { sonusResourcesMIBs 4 }


sonusTransportResourcesMIBObjects OBJECT IDENTIFIER
    ::= { sonusTransportResourcesMIB 1 }

sonusNifStatTable OBJECT-TYPE
    SYNTAX          SEQUENCE OF SonusNifStatEntry
    MAX-ACCESS      not-accessible
    STATUS          current
    DESCRIPTION     
            "This table contains status information about each NIF"
    ::= { sonusTransportResourcesMIBObjects 1 }

sonusNifStatEntry OBJECT-TYPE
    SYNTAX          SonusNifStatEntry
    MAX-ACCESS      not-accessible
    STATUS          current
    DESCRIPTION     
            "This table describes the NIF status"
    INDEX           { sonusNifStatNifIndex }
    ::= { sonusNifStatTable 1 }

SonusNifStatEntry ::=
    SEQUENCE {
        sonusNifStatNifIndex            Integer32,
        sonusNifStatState               INTEGER,
        sonusNifStatCallNum             Integer32,
        sonusNifStatResNum              Integer32,
        sonusNifStatSpeedCur            Integer32,
        sonusNifStatSpeedMax            Integer32,
        sonusNifStatSpeedActual         Integer32,
        sonusNifStatSpeedDeviation      Integer32
    }

sonusNifStatNifIndex OBJECT-TYPE
    SYNTAX          Integer32
    MAX-ACCESS      read-only
    STATUS          current
    DESCRIPTION     
            "Nif's ifIndex that identifies the NIF"
    ::= { sonusNifStatEntry 1 }

sonusNifStatState OBJECT-TYPE
    SYNTAX          INTEGER { outOfService(1), inService(2), dryUp(3) }
    MAX-ACCESS      read-only
    STATUS          current
    DESCRIPTION     
            "The state of this NIF"
    ::= { sonusNifStatEntry 2 }

sonusNifStatCallNum OBJECT-TYPE
    SYNTAX          Integer32
    MAX-ACCESS      read-only
    STATUS          current
    DESCRIPTION     
            "The number of calls on this NIF"
    ::= { sonusNifStatEntry 3 }

sonusNifStatResNum OBJECT-TYPE
    SYNTAX          Integer32
    MAX-ACCESS      read-only
    STATUS          current
    DESCRIPTION     
            "The number of xres allocated on this NIF"
    ::= { sonusNifStatEntry 4 }

sonusNifStatSpeedCur OBJECT-TYPE
    SYNTAX          Integer32
    MAX-ACCESS      read-only
    STATUS          current
    DESCRIPTION     
            "The current speed(bandwidth) allocated on this NIF"
    ::= { sonusNifStatEntry 5 }

sonusNifStatSpeedMax OBJECT-TYPE
    SYNTAX          Integer32
    MAX-ACCESS      read-only
    STATUS          current
    DESCRIPTION     
            "The maximum speed allowed on this NIF"
    ::= { sonusNifStatEntry 6 }

sonusNifStatSpeedActual OBJECT-TYPE
    SYNTAX          Integer32
    MAX-ACCESS      read-only
    STATUS          current
    DESCRIPTION     
            "The actual speed(bandwidth) on this NIF"
    ::= { sonusNifStatEntry 7 }

sonusNifStatSpeedDeviation OBJECT-TYPE
    SYNTAX          Integer32
    MAX-ACCESS      read-only
    STATUS          current
    DESCRIPTION     
            "The actual speed(bandwidth) deviation on this NIF"
    ::= { sonusNifStatEntry 8 }

sonusPnsAdmnTable OBJECT-TYPE
    SYNTAX          SEQUENCE OF SonusPnsAdmnEntry
    MAX-ACCESS      not-accessible
    STATUS          current
    DESCRIPTION     
            "This table contains admin information about each PNS"
    ::= { sonusTransportResourcesMIBObjects 2 }

sonusPnsAdmnEntry OBJECT-TYPE
    SYNTAX          SonusPnsAdmnEntry
    MAX-ACCESS      not-accessible
    STATUS          current
    DESCRIPTION     
            "This table describes the PNS admin objects"
    INDEX           { sonusPnsAdmnShelf, sonusPnsAdmnSlot }
    ::= { sonusPnsAdmnTable 1 }

SonusPnsAdmnEntry ::=
    SEQUENCE {
        sonusPnsAdmnShelf               Integer32,
        sonusPnsAdmnSlot                Integer32,
        sonusPnsAdmnReservedUdpPorts    Integer32,
        sonusPnsAdmnRowStatus           RowStatus
    }

sonusPnsAdmnShelf OBJECT-TYPE
    SYNTAX          Integer32 (1..6)
    MAX-ACCESS      read-only
    STATUS          current
    DESCRIPTION     
            "A 32-bit integer identifying the shelf of the PNS"
    ::= { sonusPnsAdmnEntry 1 }

sonusPnsAdmnSlot OBJECT-TYPE
    SYNTAX          Integer32 (1..16)
    MAX-ACCESS      read-only
    STATUS          current
    DESCRIPTION     
            "A 32-bit integer identifying the slot of the PNS"
    ::= { sonusPnsAdmnEntry 2 }

sonusPnsAdmnReservedUdpPorts OBJECT-TYPE
    SYNTAX          Integer32 (1..65535)
    MAX-ACCESS      read-write
    STATUS          current
    DESCRIPTION     
            "The number UDP ports on this PNS are reserved for IPDC or MGSG usage"
    DEFVAL          { 5120 }
    ::= { sonusPnsAdmnEntry 3 }

sonusPnsAdmnRowStatus OBJECT-TYPE
    SYNTAX          RowStatus
    MAX-ACCESS      read-write
    STATUS          current
    DESCRIPTION     
            ""
    ::= { sonusPnsAdmnEntry 4 }

END -- end of module SONUS-TRANSPORT-RESOURCES-MIB.
