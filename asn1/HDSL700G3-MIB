-- Copyright 1994 General DataComm Inc., Inc. All Rights Reserved.
--
-- Reproduction of this document is authorized on condition that the
-- foregoing copyright notice is included. This General DataComm, GDC,
-- SNMP Management Information Base Specification embodies GDCs'
-- confidential and proprietary intellectual property. GDC retains all
-- title and ownership in the Specification, including any revisions.
--
-- It is GDCs intent to encourage the widespread use of this Specification
-- in connection with the management of GDC's products. GDC grants vendors,
-- end-users, and other interested parties a non-exclusive license to use
-- this Specification in connection with the management of GDC's products.
--
-- This Specification is supplied "AS IS," and GDC makes no warranty,
-- either expressed or implied, as to the use operation, condition, or
-- performance of the Specification.

-- Revision History
-- Version   Date	Name		Description
-- 1.00A     10-Feb-95  E. Moreno-Leon  Initial Revision
-- 1.00B     05-Apr-95  E. Moreno-Leon  Change alarm hdsl700G3ResponseAlm
--					to hdsl700G3NoResponseAlm
-- 1.00C     01-Sep-95	C. Amorossi	Added Interface Comments
-- 1.00D     13-Mar-96	E. Moreno-Leon	Added Major and Minor BER Alarms

HDSL700G3-MIB DEFINITIONS ::= BEGIN

IMPORTS
	OBJECT-TYPE			FROM RFC-1212
	DisplayString			FROM RFC1213-MIB
	hdsl700G3                       FROM GDCHDSL-MIB;

hdsl700G3System          OBJECT IDENTIFIER ::= { hdsl700G3 1 }
hdsl700G3Version         OBJECT IDENTIFIER ::= { hdsl700G3System 1 }

-- This mib is a subset of the HDSL mib for the 700G3 product.

-- ***************************************************************************
-- The interfaces are defined as follows:
--	Unit	0
--	E1	1
--	Loop1	2
--	Loop2	3
--	Loop3   4
-- ***************************************************************************

gdc700G3SystemMIBversion OBJECT-TYPE
     	SYNTAX DisplayString (SIZE (5))
     	ACCESS read-only
     	STATUS mandatory
     	DESCRIPTION
     		"Identifies the version of the MIB. The format of the version
     		is x.yzT, where 'x' identifies the major revision number, 'y'
     		identifies the minor revision number, 'z' identifies the
     		typographical revision, and T identifies the test revision.
     		Acceptable values for the individual revision components are
     		as follows:
 
     		x: 1 - 9
     		y: 0 - 9
     		z: 0 - 9
     		T: A - Z
 
     		Upon formal release, no designation for the test revision will
     		be present."
     	::= { hdsl700G3Version 1 }

-- ********************************************************************
-- GDC Hdsl Alarm Object Identifier Definitions
-- ********************************************************************
hdsl700G3Alarms          OBJECT IDENTIFIER ::= { hdsl700G3 2 }

hdsl700G3NoResponseAlm		OBJECT IDENTIFIER ::= { hdsl700G3Alarms 1 }
hdsl700G3DiagRxErrAlm		OBJECT IDENTIFIER ::= { hdsl700G3Alarms 2 }
hdsl700G3PowerUpAlm		OBJECT IDENTIFIER ::= { hdsl700G3Alarms 3 }
hdsl700G3UnitFailure            OBJECT IDENTIFIER ::= { hdsl700G3Alarms 4 }
hdsl700G3ChecksumCorrupt        OBJECT IDENTIFIER ::= { hdsl700G3Alarms 5 }
hdsl700G3LossofSignal		OBJECT IDENTIFIER ::= { hdsl700G3Alarms 6 }
hdsl700G3UnavailableSec		OBJECT IDENTIFIER ::= { hdsl700G3Alarms 7 }
hdsl700G3ErrorSec		OBJECT IDENTIFIER ::= { hdsl700G3Alarms 8 }
hdsl700G3LossofSyncWord		OBJECT IDENTIFIER ::= { hdsl700G3Alarms 9 }
hdsl700G3LossofFrameAlign	OBJECT IDENTIFIER ::= { hdsl700G3Alarms 10 }
hdsl700G3AllOnes		OBJECT IDENTIFIER ::= { hdsl700G3Alarms 11 }
hdsl700G3RemoteLossofSig	OBJECT IDENTIFIER ::= { hdsl700G3Alarms 12 }
hdsl700G3RemoteAlarmInd		OBJECT IDENTIFIER ::= { hdsl700G3Alarms 13 }
hdsl700G3MajorBER 		OBJECT IDENTIFIER ::= { hdsl700G3Alarms 14 }
hdsl700G3MinorBER 		OBJECT IDENTIFIER ::= { hdsl700G3Alarms 15 }
 
 
-- ALARM			Maskable	Valid Interfaces
--===============================================================
--hdslNoResponseAlm		No		Unit
--hdslDiagRxErrAlm              No              Unit
--hdslPowerUpAlm		No		Unit
--hdslUnitFailure               No              Unit
--hdslChecksumCorrupt           No              Unit
--hdslLossofSignal		Yes		E1, L1, L2, L3 
--hdslUnavailableSec		Yes		E1, L1, L2, L3
--hdslErrorSec			Yes		E1, L1, L2, L3
--hdslLossofSyncWord		Yes		L1, L2, L3
--hdslLossofFrameAlign		Yes		E1
--hdslAllOnes			Yes		E1
--hdslRemoteLossofSig		Yes		E1
--hdslRemoteAlarmInd		Yes		E1 
--hdsl700G3MajorBER		Yes		L1, L2, L3
--hdsl700G3MinorBER		Yes		L1, L2, L3






END
