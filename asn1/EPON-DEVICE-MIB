-- extracted from draft-ietf-hubmib-efm-epon-mib-03.txt
-- at Sat Mar 12 06:25:43 2005

        EPON-DEVICE-MIB DEFINITIONS ::= BEGIN


       IMPORTS
           MODULE-IDENTITY, mib-2, OBJECT-TYPE, Counter32,
           Unsigned32, Integer32, zeroDotZero
               FROM SNMPv2-SMI
           TruthValue, RowStatus, MacAddress
               FROM SNMPv2-TC
           ifIndex
               FROM IF-MIB
           MODULE-COMPLIANCE, OBJECT-GROUP
               FROM SNMPv2-CONF
            SnmpAdminString
               FROM SNMP-FRAMEWORK-MIB
       ;

   eponDeviceMIB MODULE-IDENTITY
       LAST-UPDATED "200503100000Z"  -- March 10, 2005
       ORGANIZATION "IETF Ethernet Interfaces and Hub MIB Working
                     Group"
       CONTACT-INFO
                    "WG charter:
                  http://www.ietf.org/html.charters/hubmib-charter.html
                     Mailing Lists:
                       General Discussion: hubmib@ietf.org
                       To Subscribe: hubmib-request@ietf.org
                       In Body: subscribe your_email_address
                     Chair: Dan Romascanu
                     Postal: Avaya
                             Atidim Technology Park, Bldg. 3
                             Tel Aviv 61131
                             Israel
                        Tel: +972-3-645-8414
                     E-mail: dromasca@avaya.com

                     Editor: Lior Khermosh
                     Postal: Passave Technologies Inc.
                             Kohav Hertzelia bldg,
                             4 Hasadnaot St.
                             Hertzliya Pituach 46120,
                             ISRAEL

                     P.O.Box 2089 Hertzliya Pituach 46120 Israel
                     Tel:    +972-9-9628000 Ext: 302
                     E-mail: lior.khermosh@passave.com"
       DESCRIPTION
               "The objects in this MIB module are used to manage
                Ethernet Passive Optical Network (EPON) devices which
                are based on the Ethernet in the First Mile (EFM) PON
                as defined in IEEE P802.3 clause 64,65.

                The following reference is used throughout this MIB
                module:
              [802.3] refers to:
                IEEE Draft P802.3: 'Information technology -
                Telecommunications and information exchange between
                systems - Local and metropolitan area networks -
                Specific requirements -
                Part 3: Carrier sense multiple access with collision
                detection (CSMA/CD) access method and physical layer
                specifications - Media Access Control Parameters,
                Physical Layers and Management Parameters for
                subscriber access networks', 8 December 2004.
                Of particular interest are Clause 64(MPCP) 65(P2mP RS)
                and 60 (PON PMDs). Clause 30, 'Management', and Clause
                45,'Management Data Input/Output (MDIO) Interface'.

                Copyright (C) The Internet Society (2005).  This version
                of this MIB module is part of XXXX see the RFC itself
                for full legal notices."

             -- Editor's Note: Replace XXXX with the actual RFC number
             -- assigned by RFC Editor and remove this note

             REVISION    "200503100000Z"  -- March 10, 2005
             DESCRIPTION "Initial version, published as RFC XXXX."

       ::= { mib-2 XXX }

             -- Editor's Note: Replace XXX with a real OID once it is
             -- assigned by IANA and remove this note.

   eponDeviceObjectMIB OBJECT IDENTIFIER ::= { eponDeviceMIB 1}

   eponDeviceObjects OBJECT IDENTIFIER ::= { eponDeviceObjectMIB  1}

   eponDeviceConformance OBJECT IDENTIFIER ::= { eponDeviceObjectMIB  2}

   eponDeviceControlObjects OBJECT IDENTIFIER ::= { eponDeviceObjects 1}
   eponDeviceStatObjects OBJECT IDENTIFIER ::= { eponDeviceObjects 2}

   eponDeviceEventObjects OBJECT IDENTIFIER ::= { eponDeviceObjects 3}


   eponDeviceControlTable OBJECT-TYPE
       SYNTAX  SEQUENCE OF EponDeviceControlEntry
       MAX-ACCESS  not-accessible
       STATUS  current
       DESCRIPTION
               "Table for EPON device MIB modules."
       ::= { eponDeviceControlObjects 1 }

   eponDeviceControlEntry OBJECT-TYPE
       SYNTAX  EponDeviceControlEntry
       MAX-ACCESS  not-accessible
       STATUS  current
       DESCRIPTION
               "An entry in the EPON device Control table."
       INDEX  { ifIndex }
       ::= { eponDeviceControlTable 1 }

   EponDeviceControlEntry ::=
       SEQUENCE {
        eponDeviceObjectReset                       INTEGER,
        eponDeviceObjectModes                       INTEGER,
        eponDeviceObjectFecEnabled                  INTEGER,
        eponDeviceObjectDeviceReadyMode             INTEGER,
        eponDeviceObjectPowerDown                   TruthValue,
        eponDeviceObjectNumberOfLLIDs               Integer32,
        eponDeviceObjectReportNumThreshold           Integer32,
        eponDeviceObjectReportThreshold             Integer32,
        eponDeviceObjectReportMaximumNumThreshold   Integer32,
        eponDeviceObjectReportMaximumNumQueues      Integer32,
        eponDeviceRemoteMACAddressLLIDControl       INTEGER
       }


   eponDeviceObjectReset OBJECT-TYPE
       SYNTAX  INTEGER {
               running(1),
               reset(2)
       }
       MAX-ACCESS  read-write
       STATUS  current
       DESCRIPTION
               "This variable is used to reset the EPON device. The
                interface may be unavailable while the reset occurs and
                data may be lost. During reading operation it returns
                the state of the EPON device. running(1) indicates and
                operates normal operation, reset(2) indicates and
                operates reset mode. Writing can be done all the time."
       DEFVAL { 1 }
       ::= { eponDeviceControlEntry 1 }

   eponDeviceObjectModes OBJECT-TYPE
       SYNTAX  INTEGER {
               olt(1),
               onu(2)
       }
       MAX-ACCESS  read-only
       STATUS  current
       DESCRIPTION
               "This variable defines the mode of the EPON device. When
                an olt(1) it is an Optical Line Terminal device (server)
                and when an onu(2) and Optical Network Unit device
                (client)"
       ::= { eponDeviceControlEntry 2 }

   eponDeviceObjectFecEnabled OBJECT-TYPE
       SYNTAX  INTEGER {
               noFecEnabled (1),
               fecTxEnabled (2),
               fecRxEnabled (3),
               fecTxRxEnabled (4)
       }
       MAX-ACCESS  read-write
       STATUS  current
       DESCRIPTION
             "This variable defines and provides information whether the
              EPON device uses FEC as defined in the [802.3] clause
              65.2 for EPON. When noFECEnabled(1) the device does not
              support FEC mode. When fecTxEnabled(2) the device supports
              the FEC transmission mode. When fecRxEnabled(3) the device
              supports the FEC Receive mode. When fecTxRxEnabled(4) the
              device supports the FEC transmission and receive mode.
              Writing can be done all the time.
              This attribute is relevant for an OLT and an ONU."
       DEFVAL { 1 }
       ::= { eponDeviceControlEntry 3 }


   eponDeviceObjectDeviceReadyMode     OBJECT-TYPE
       SYNTAX  INTEGER {
               notReady (1),
               inProcess (2),
               ready (3)
       }
       MAX-ACCESS  read-write
       STATUS  current
       DESCRIPTION
               "This variable defines the mode of an EPON device and
                provides information on the mode in initialization -
                ready for registration as defined by the [802.3]
                clause 64.
                When notReady(1) the device is not ready for operation.
                When inProcess(2) the device is in initialization
                process.
                When ready(3) the device is ready for registration.
                Writing can be done all the time.
                This attribute is relevant for an OLT and an ONU."
       DEFVAL { 1 }
       ::= { eponDeviceControlEntry 4 }

   eponDeviceObjectPowerDown OBJECT-TYPE
       SYNTAX  TruthValue
       MAX-ACCESS  read-write
       STATUS  current
       DESCRIPTION
               "Setting this variable to True(1) will cause Device to be
                entered into Power down mode. Setting this variable to
                False(0) will cause the device to go out of power down
                mode. When getting True(1) the device is in power down.
                when getting False(0) the device is not in power down.
                Writing can be done all the time.
                This attribute is relevant for an OLT and an ONU."
       DEFVAL { false }
       ::= { eponDeviceControlEntry 5 }


   eponDeviceObjectNumberOfLLIDs OBJECT-TYPE
       SYNTAX  Integer32
       MAX-ACCESS  read-only
       STATUS  current
       DESCRIPTION
               "A read only variable which defines the number of
                registered LLIDs (as defined by the [802.3] clause 65)
                in a EPON network for an OLT and an ONU. Initialization
                value is 0.
                This attribute is relevant for an OLT and an ONU."
       ::= { eponDeviceControlEntry 6 }

   eponDeviceObjectReportNumThreshold OBJECT-TYPE
       SYNTAX  Integer32
       MAX-ACCESS  read-write
       STATUS  current
       DESCRIPTION
               "A set of 8 integers, for each LLID, that defines the
                number of thresholds for each Queue in the REPORT
                message, as defined in [802.3] 64. Each Queue set
                reporting will provide information on the queue
                occupancy of frames below the matching Threshold.
                Writing can be done all the time.
                This attribute is relevant for an OLT and an ONU."
       DEFVAL { 0 }
       ::= { eponDeviceControlEntry 7 }

       eponDeviceObjectReportThreshold OBJECT-TYPE
       SYNTAX  Integer32
       UNITS       "TQ (16nsec)"
       MAX-ACCESS  read-write
       STATUS  current
       DESCRIPTION
               "A multiple set of 8 integers, for each LLID, that
                defines the thresholds reporting for each Queue in the
                REPORT message, as defined in [802.3] 64. The number
                of sets is eponDeviceObjectReportNumThreshold. Each
                Queue set reporting will provide information on the
                queue occupancy of frames below the matching Threshold.
                The value returned shall be in Time quanta (TQ) which
                is 16nsec or 2 octets increments.
                Writing can be done all the time.
                This attribute is relevant for an OLT and an ONU."
       DEFVAL { 0 }
       ::= { eponDeviceControlEntry 8 }


   eponDeviceObjectReportMaximumNumThreshold OBJECT-TYPE
       SYNTAX  Integer32
       MAX-ACCESS  read-only
       STATUS  current
       DESCRIPTION
               "A set of 8 integers, for each LLID, that defines the
                maximal number of thresholds for each Queue in the
                REPORT message, as defined in [802.3] 64. Each Queue
                set reporting will provide information on the queue
                occupancy of frames below the matching Threshold.
                This attribute is relevant for an ONU and an OLT."
       DEFVAL { 0 }
       ::= { eponDeviceControlEntry 9 }

   eponDeviceObjectReportMaximumNumQueues OBJECT-TYPE
       SYNTAX  Integer32
       MAX-ACCESS  read-only
       STATUS  current
       DESCRIPTION
               "A set of 8 integers, for each LLID, that defines the
                maximal number of queues in the REPORT message, as
                defined in [802.3] 64.
                This attribute is relevant for an ONU and an OLT."
       DEFVAL { 0 }
       ::= { eponDeviceControlEntry 10 }


   eponDeviceRemoteMACAddressLLIDControl OBJECT-TYPE
       SYNTAX INTEGER {
               none(1),
               resetLog(2),
               useDefaultReporting(3)
       }
       MAX-ACCESS  read-write
       STATUS      current
       DESCRIPTION
               "Indicates and controls the resetting of the LLID MAC
                address log. Setting this object to none(1) has no
                action resetLog(2) empties the LLID MAC address log. All
                data is deleted. Setting it to useDefaultReporting(3)
                returns all entries priorities to their factory-default
                reporting. Reading this object always returns
                useDefaultReporting(3)."
       DEFVAL { 3 }
       ::= { eponDeviceControlEntry 11 }

   eponDeviceRemoteMACAddressLLIDTable OBJECT-TYPE
       SYNTAX      SEQUENCE OF EponDeviceRemoteMACAddressLLIDEntry
       MAX-ACCESS  not-accessible
       STATUS      current
       DESCRIPTION
               "A read-only table of objects that identifies the source
                MacAddress and LLIDs parameter of the remote devices in
                the network.
                This MacAddress value, as defined in [802.3],
                30.3.5.1.5, is updated on reception of a valid frame
                with:
                (1) a unicast destination Field or a destination Field
                equal to the reserved multicast address for MAC Control
                specified in [802.3] Annex 31A.
                (2) lengthOrType field value equal to the reserved
                Type for MAC Control as specified in [802.3] Annex
                31A.
                (3)an MPCP subtype value equal to the subtype reserved
                for MPCP as specified in [802.3] Annex 31A,
                and an LLID as allocated by the OLT.
                This table is denoted as 'Remote MAC address - LLID'
                (RMadL) table.
                The table is relevant only for an OLT device."
       ::= { eponDeviceControlObjects 2 }


   eponDeviceRemoteMACAddressLLIDEntry OBJECT-TYPE
       SYNTAX      EponDeviceRemoteMACAddressLLIDEntry
       MAX-ACCESS  not-accessible
       STATUS      current
       DESCRIPTION
               "A group of entries.  Applications create and delete
                entries using eponDeviceRMadlEntryStatus.
                When adding objects to an LLID they are added in the
                persistent order of their index in this table."
       INDEX       {ifIndex }
       ::= { eponDeviceRemoteMACAddressLLIDTable 1 }

       EponDeviceRemoteMACAddressLLIDEntry ::=
       SEQUENCE {
               eponDeviceRemoteMACAddressLLIDName    SnmpAdminString,
               eponDeviceRMadlLLID                   Unsigned32,
               eponDeviceRMadlLogID                  OBJECT IDENTIFIER,
               eponDeviceRMadlRemoteAddress          MacAddress,
               eponDeviceRMadlType                   INTEGER,
               eponDeviceRMadlAction                 INTEGER,
               eponDeviceRMadlEntryStatus            RowStatus
       }

   eponDeviceRemoteMACAddressLLIDName OBJECT-TYPE
       SYNTAX      SnmpAdminString (SIZE (1..32))
       MAX-ACCESS  not-accessible
       STATUS      current
       DESCRIPTION
               "A locally-unique, administratively assigned name for a
                group of entries."
       ::= { eponDeviceRemoteMACAddressLLIDEntry 1 }

   eponDeviceRMadlLLID OBJECT-TYPE
       SYNTAX      Unsigned32 (1..4294967295)
       MAX-ACCESS  read-write
       STATUS      current
       DESCRIPTION
               "An arbitrary integer for the purpose of identifying the
                LLID. Writing can be done all the time."

       DEFVAL { 1 }
       ::= { eponDeviceRemoteMACAddressLLIDEntry 2 }


   eponDeviceRMadlLogID OBJECT-TYPE
       SYNTAX      OBJECT IDENTIFIER
       MAX-ACCESS  read-create
       STATUS      current
       DESCRIPTION
               "The object identifier of a MIB module object to add to
                an entry, indicating the entry ID in the table. Writing
                can be done all the time."
       DEFVAL { zeroDotZero }
       ::= { eponDeviceRemoteMACAddressLLIDEntry 3 }

   eponDeviceRMadlRemoteAddress OBJECT-TYPE
       SYNTAX     MacAddress
       MAX-ACCESS  read-create
       STATUS      current
       DESCRIPTION
               "The remote MAC address of the LLID.
                Writing can be done all the time."
       ::= { eponDeviceRemoteMACAddressLLIDEntry 4 }


   eponDeviceRMadlType OBJECT-TYPE
       SYNTAX  INTEGER {
               notRegister (1),
               registered (2)
       }
       MAX-ACCESS  read-write
       STATUS  current
       DESCRIPTION
               "A list of types for entries - LLIDs. Indicates and
                defines the state of registration. notRegister(1) marks
                a non registered LID, registered(2) marks a registered
                LLID.  Writing can be done all the time."
       DEFVAL { 1 }
       ::= { eponDeviceRemoteMACAddressLLIDEntry 5 }

   eponDeviceRMadlAction OBJECT-TYPE
       SYNTAX  INTEGER {
               none (1),
               register (2),
               deregister (3),
               reregister (4)
       }
       MAX-ACCESS  read-write
       STATUS  current
       DESCRIPTION
               "A list of actions for an entry - LLID.  Indicates and
                defines the state of registration for the remote device.
                none(1) marks no action, register(2) marks to register
                an LLID, deregister(3) marks to deregister an LLID,
                reregister(4) marks reregistered LLID.
                Writing can be done all the time."
       DEFVAL { 1 }
       ::= { eponDeviceRemoteMACAddressLLIDEntry 6 }


   eponDeviceRMadlEntryStatus OBJECT-TYPE
       SYNTAX      RowStatus
       MAX-ACCESS  read-create
       STATUS      current
       DESCRIPTION
               "The control that allows creation and deletion of
                entries. Once made active an entry MAY not be modified
                except to delete it."
      ::= { eponDeviceRemoteMACAddressLLIDEntry 7 }




   --Statistics tables

   eponDeviceStatTable OBJECT-TYPE
       SYNTAX     SEQUENCE OF EponDeviceStatEntry
       MAX-ACCESS not-accessible
       STATUS     current
       DESCRIPTION
               "This table defines the list of statistics counters of
                EPON devices. The attributes are relevant for an OLT and
                an ONU."
       ::= { eponDeviceStatObjects 1}

   eponDeviceStatEntry OBJECT-TYPE
       SYNTAX     EponDeviceStatEntry
       MAX-ACCESS not-accessible
       STATUS     current
       DESCRIPTION
               "Table entries for Table of statistics counters of EPON
                devices."
       INDEX       { ifIndex }
       ::= { eponDeviceStatTable 1 }

   EponDeviceStatEntry::=
       SEQUENCE {
               eponDeviceStatTxFramesQueue0            Counter32,
               eponDeviceStatTxFramesQueue1            Counter32,
               eponDeviceStatTxFramesQueue2            Counter32,
               eponDeviceStatTxFramesQueue3            Counter32,
               eponDeviceStatTxFramesQueue4            Counter32,
               eponDeviceStatTxFramesQueue5            Counter32,
               eponDeviceStatTxFramesQueue6            Counter32,
               eponDeviceStatTxFramesQueue7            Counter32,
               eponDeviceStatRxFramesQueue0            Counter32,
               eponDeviceStatRxFramesQueue1            Counter32,
               eponDeviceStatRxFramesQueue2            Counter32,
               eponDeviceStatRxFramesQueue3            Counter32,
               eponDeviceStatRxFramesQueue4            Counter32,
               eponDeviceStatRxFramesQueue5            Counter32,
               eponDeviceStatRxFramesQueue6            Counter32,
               eponDeviceStatRxFramesQueue7            Counter32,
               eponDeviceStatDroppedFramesQueue0       Counter32,
               eponDeviceStatDroppedFramesQueue1       Counter32,
               eponDeviceStatDroppedFramesQueue2       Counter32,
               eponDeviceStatDroppedFramesQueue3       Counter32,
               eponDeviceStatDroppedFramesQueue4       Counter32,
               eponDeviceStatDroppedFramesQueue5       Counter32,
               eponDeviceStatDroppedFramesQueue6       Counter32,
               eponDeviceStatDroppedFramesQueue7       Counter32
       }

     eponDeviceStatTxFramesQueue0 OBJECT-TYPE
       SYNTAX  Counter32
       UNITS      "frames"
       MAX-ACCESS  read-only
       STATUS  current
       DESCRIPTION
               "A count of the number of times a -Queue-0- frames
                transmission occurs. Increment the counter by one for
                each frame transmitted which is an output of -Queue-0-.
                The -Queue-0- marking matched the REPORT MPCP message
                Queue-0 field, as defined in [802.3] clause 64. This
                counter is mandatory for an ONU."
       ::= { eponDeviceStatEntry 1}

   eponDeviceStatTxFramesQueue1 OBJECT-TYPE
       SYNTAX  Counter32
       UNITS      "frames"
       MAX-ACCESS  read-only
       STATUS  current
       DESCRIPTION
               "A count of the number of times a -Queue-1- frames
                transmission occurs. Increment the counter by one for
                each frame transmitted which is an output of -Queue-1-.
                The -Queue-1- marking matched the REPORT MPCP message
                Queue-1 field, as defined in [802.3] clause 64. This
                counter is mandatory for an ONU."
       ::= { eponDeviceStatEntry 2}

   eponDeviceStatTxFramesQueue2 OBJECT-TYPE
       SYNTAX  Counter32
       UNITS      "frames"
       MAX-ACCESS  read-only
       STATUS  current
       DESCRIPTION
               "A count of the number of times a -Queue-2- frames
                transmission occurs. Increment the counter by one for
                each frame transmitted which is an output of -Queue-2-.
                The -Queue-2- marking matched the REPORT MPCP message
                Queue-2 field, as defined in [802.3] clause 64. This
                counter is mandatory for an ONU."
       ::= { eponDeviceStatEntry 3}

   eponDeviceStatTxFramesQueue3 OBJECT-TYPE
       SYNTAX  Counter32
       UNITS      "frames"
       MAX-ACCESS  read-only
       STATUS  current
       DESCRIPTION
               "A count of the number of times a -Queue-3- frames
                transmission occurs. Increment the counter by one for
                each frame transmitted which is an output of -Queue-3-.
                The -Queue-3- marking matched the REPORT MPCP message
                Queue-3 field, as defined in [802.3] clause 64.
                This counter is mandatory for an ONU."
           ::= { eponDeviceStatEntry 4}

   eponDeviceStatTxFramesQueue4 OBJECT-TYPE
       SYNTAX  Counter32
       UNITS      "frames"
       MAX-ACCESS  read-only
       STATUS  current
       DESCRIPTION
               "A count of the number of times a -Queue-4- frames
                transmission occurs. Increment the counter by one for
                each frame transmitted which is an output of -Queue-4-.
                The -Queue-4- marking matched the REPORT MPCP message
                Queue-4 field, as defined in [802.3] clause 64.
                This counter is mandatory for an ONU."
       ::= { eponDeviceStatEntry 5}

   eponDeviceStatTxFramesQueue5 OBJECT-TYPE
       SYNTAX  Counter32
       UNITS      "frames"
       MAX-ACCESS  read-only
       STATUS  current
       DESCRIPTION
               "A count of the number of times a -Queue-5- frames
                transmission occurs. Increment the counter by one for
                each frame transmitted which is an output of -Queue-5-.
                The -Queue-5- marking matched the REPORT MPCP message
                Queue-5 field, as defined in [802.3] clause 64.
                This counter is mandatory for an ONU."
       ::= { eponDeviceStatEntry 6}

   eponDeviceStatTxFramesQueue6 OBJECT-TYPE
       SYNTAX  Counter32
       UNITS      "frames"
       MAX-ACCESS  read-only
       STATUS  current
       DESCRIPTION
               "A count of the number of times a -Queue-6- frames
                transmission occurs. Increment the counter by one for
                each frame transmitted which is an output of -Queue-6-.
                The -Queue-6- marking matched the REPORT MPCP message
                Queue-6 field, as defined in [802.3] clause 64.
                This counter is mandatory for an ONU."
       ::= { eponDeviceStatEntry 7}

   eponDeviceStatTxFramesQueue7 OBJECT-TYPE
       SYNTAX  Counter32
       UNITS      "frames"
       MAX-ACCESS  read-only
          STATUS  current
          DESCRIPTION
               "A count of the number of times a -Queue-7- frames
                transmission occurs. Increment the counter by one for
                each frame transmitted which is an output of -Queue-7-.
                The -Queue-7- marking matched the REPORT MPCP message
                Queue-7 field, as defined in [802.3] clause 64.
                This counter is mandatory for an ONU."
       ::= { eponDeviceStatEntry 8}

   eponDeviceStatRxFramesQueue0 OBJECT-TYPE
       SYNTAX  Counter32
       UNITS      "frames"
       MAX-ACCESS  read-only
       STATUS  current
       DESCRIPTION
               "A count of the number of times a -Queue-0- frames
                reception occurs. Increment the counter by one for each
                frame received, which is an output of -Queue-0-. The
                -Queue-0- marking matched the REPORT MPCP message
                Queue-0 field, as defined in [802.3] clause 64.
                This counter is mandatory for an ONU."
       ::= { eponDeviceStatEntry 9}

   eponDeviceStatRxFramesQueue1 OBJECT-TYPE
       SYNTAX  Counter32
       UNITS      "frames"
       MAX-ACCESS  read-only
       STATUS  current
       DESCRIPTION
               "A count of the number of times a -Queue-1- frames
                reception occurs. Increment the counter by one for each
                frame received, which is an output of -Queue-1-. The
                -Queue-1- marking matched the REPORT MPCP message
                Queue-1 field, as defined in [802.3] clause 64.
                This counter is mandatory for an ONU."
       ::= { eponDeviceStatEntry 10}

   eponDeviceStatRxFramesQueue2 OBJECT-TYPE
       SYNTAX  Counter32
       UNITS      "frames"
       MAX-ACCESS  read-only
       STATUS  current
       DESCRIPTION
               "A count of the number of times a -Queue-2- frames
                reception occurs. Increment the counter by one for each
                frame received, which is an output of -Queue-2-. The
                -Queue-2- marking matched the REPORT MPCP message
                Queue-2 field, as defined in [802.3] clause 64.
                This counter is mandatory for an ONU."
       ::= { eponDeviceStatEntry 11}

   eponDeviceStatRxFramesQueue3 OBJECT-TYPE
       SYNTAX  Counter32
       UNITS      "frames"
       MAX-ACCESS  read-only
       STATUS  current
       DESCRIPTION
               "A count of the number of times a -Queue-3- frames
                reception occurs. Increment the counter by one for each
                frame received, which is an output of -Queue-3-. The
                -Queue-3- marking matched the REPORT MPCP message
                Queue-3 field, as defined in [802.3] clause 64.
                This counter is mandatory for an ONU."
       ::= { eponDeviceStatEntry 12}

   eponDeviceStatRxFramesQueue4 OBJECT-TYPE
       SYNTAX  Counter32
       UNITS      "frames"
       MAX-ACCESS  read-only
       STATUS  current
       DESCRIPTION
               "A count of the number of times a -Queue-4- frames
                reception occurs. Increment the counter by one for each
                frame received, which is an output of -Queue-4-. The
                -Queue-4- marking matched the REPORT MPCP message
                Queue-4 field, as defined in [802.3] clause 64.
                This counter is mandatory for an ONU."
       ::= { eponDeviceStatEntry 13}

   eponDeviceStatRxFramesQueue5 OBJECT-TYPE
       SYNTAX  Counter32
       UNITS      "frames"
       MAX-ACCESS  read-only
       STATUS  current
       DESCRIPTION
               "A count of the number of times a -Queue-5- frames
                reception occurs. Increment the counter by one for each
                frame received, which is an output of -Queue-5-. The
                -Queue-5- marking matched the REPORT MPCP message
                Queue-5 field, as defined in [802.3] clause 64.
                This counter is mandatory for an ONU."
       ::= { eponDeviceStatEntry 14}

   eponDeviceStatRxFramesQueue6 OBJECT-TYPE
       SYNTAX  Counter32
       UNITS      "frames"
       MAX-ACCESS  read-only
       STATUS  current
       DESCRIPTION
               "A count of the number of times a -Queue-6- frames
                reception occurs. Increment the counter by one for each
                frame received, which is an output of -Queue-6-. The
                -Queue-6- marking matched the REPORT MPCP message
                Queue-6 field, as defined in [802.3] clause 64.
                This counter is mandatory for an ONU."
       ::= { eponDeviceStatEntry 15}

   eponDeviceStatRxFramesQueue7 OBJECT-TYPE
       SYNTAX  Counter32
       UNITS      "frames"
       MAX-ACCESS  read-only
       STATUS  current
       DESCRIPTION
               "A count of the number of times a -Queue-7- frames
                reception occurs. Increment the counter by one for each
                frame received, which is an output of -Queue-7-. The
                -Queue-7- marking matched the REPORT MPCP message
                Queue-7 field, as defined in [802.3] clause 64.
                This counter is mandatory for an ONU."
       ::= { eponDeviceStatEntry 16}

   eponDeviceStatDroppedFramesQueue0 OBJECT-TYPE
       SYNTAX  Counter32
       UNITS      "frames"
       MAX-ACCESS  read-only
       STATUS  current
       DESCRIPTION
               "A count of the number of times a -Queue-0- frames drops
                occurs. Increment the counter by one for each frame
                dropped from -Queue-0-. The -Queue-0- marking matched
                the REPORT MPCP message Queue-0 field, as defined in
                [802.3] clause 64.
                This counter is mandatory for an ONU."
       ::= { eponDeviceStatEntry 17}

   eponDeviceStatDroppedFramesQueue1 OBJECT-TYPE
       SYNTAX  Counter32
       UNITS      "frames"
       MAX-ACCESS  read-only
       STATUS  current
       DESCRIPTION
               "A count of the number of times a -Queue-1- frames drops
                occurs. Increment the counter by one for each frame
                dropped from -Queue-1-. The -Queue-1- marking matched
                the REPORT MPCP message Queue-1 field, as defined in
                [802.3] clause 64.
                This counter is mandatory for an ONU."
       ::= { eponDeviceStatEntry 18}

   eponDeviceStatDroppedFramesQueue2 OBJECT-TYPE
       SYNTAX  Counter32
       UNITS      "frames"
       MAX-ACCESS  read-only
       STATUS  current
       DESCRIPTION
               "A count of the number of times a -Queue-2- frames drops
                occurs. Increment the counter by one for each frame
                dropped from -Queue-2-. The -Queue-2- marking matched
                the REPORT MPCP message Queue-2 field, as defined in
                [802.3] clause 64.
                This counter is mandatory for an ONU."
       ::= { eponDeviceStatEntry 19}

   eponDeviceStatDroppedFramesQueue3 OBJECT-TYPE
       SYNTAX  Counter32
       UNITS      "frames"
       MAX-ACCESS  read-only
       STATUS  current
       DESCRIPTION
               "A count of the number of times a -Queue-3- frames drops
                occurs. Increment the counter by one for each frame
                dropped from -Queue-3-. The -Queue-3- marking matched
                the REPORT MPCP message Queue-3 field, as defined in
                [802.3] clause 64.
                This counter is mandatory for an ONU."
       ::= { eponDeviceStatEntry 20}

   eponDeviceStatDroppedFramesQueue4 OBJECT-TYPE
       SYNTAX  Counter32
       UNITS      "frames"
       MAX-ACCESS  read-only
       STATUS  current
       DESCRIPTION
               "A count of the number of times a -Queue-4- frames drops
                occurs. Increment the counter by one for each frame
                dropped from -Queue-4-. The -Queue-4- marking matched
                the REPORT MPCP message Queue-4 field, as defined in
                [802.3] clause 64.
                This counter is mandatory for an ONU."
       ::= { eponDeviceStatEntry 21}

   eponDeviceStatDroppedFramesQueue5 OBJECT-TYPE
       SYNTAX  Counter32
       UNITS      "frames"
       MAX-ACCESS  read-only
       STATUS  current
       DESCRIPTION
               "A count of the number of times a -Queue-5- frames drops
                occurs. Increment the counter by one for each frame
                dropped from -Queue-5-. The -Queue-5- marking matched
                the REPORT MPCP message Queue-5 field, as defined in
                [802.3] clause 64.
                This counter is mandatory for an ONU."
       ::= { eponDeviceStatEntry 22}

   eponDeviceStatDroppedFramesQueue6 OBJECT-TYPE
       SYNTAX  Counter32
       UNITS      "frames"
       MAX-ACCESS  read-only
       STATUS  current
       DESCRIPTION
               "A count of the number of times a -Queue-6- frames drops
                occurs. Increment the counter by one for each frame
                dropped from -Queue-6-. The -Queue-6- marking matched
                the REPORT MPCP message Queue-6 field, as defined in
                [802.3] clause 64.
                This counter is mandatory for an ONU."
       ::= { eponDeviceStatEntry 23}

   eponDeviceStatDroppedFramesQueue7 OBJECT-TYPE
       SYNTAX  Counter32
       UNITS      "frames"
       MAX-ACCESS  read-only
       STATUS  current
       DESCRIPTION
               "A count of the number of times a -Queue-7- frames drops
                occurs. Increment the counter by one for each frame
                dropped from -Queue-7-. The -Queue-7- marking matched
                the REPORT MPCP message Queue-7 field, as defined in
                [802.3] clause 64.
                This counter is mandatory for an ONU."
       ::= { eponDeviceStatEntry 24}

   --Editor's Note use reference to event MIB modules [RFC2981] and
   --docsis MIB modules [RFC2669]




        -- Conformance Statements

   -- Conformance Groups

   eponDeviceGroups OBJECT IDENTIFIER ::={ eponDeviceConformance 1}

   eponDeviceGroupControl OBJECT-GROUP
       OBJECTS {
               eponDeviceObjectReset,
               eponDeviceObjectModes,
               eponDeviceObjectFecEnabled,
               eponDeviceObjectDeviceReadyMode,
               eponDeviceObjectPowerDown,
               eponDeviceObjectNumberOfLLIDs,
               eponDeviceObjectReportNumThreshold,
               eponDeviceObjectReportThreshold,
               eponDeviceObjectReportMaximumNumThreshold,
               eponDeviceObjectReportMaximumNumQueues,
               eponDeviceRemoteMACAddressLLIDControl
       }
       STATUS  current
       DESCRIPTION
               "A collection of objects of eponDevice control
                definition."
       ::= { eponDeviceGroups 1 }


   eponDeviceGroupRMadLTable OBJECT-GROUP
       OBJECTS {
               eponDeviceRMadlLLID,
               eponDeviceRMadlLogID,
               eponDeviceRMadlRemoteAddress,
               eponDeviceRMadlType,
               eponDeviceRMadlAction,
               eponDeviceRMadlEntryStatus
       }
       STATUS  current
       DESCRIPTION
               "A collection of objects of eponDevice remote Mac address
                to LLID table."
       ::= { eponDeviceGroups 2 }


   eponDeviceGroupStat OBJECT-GROUP
       OBJECTS {
               eponDeviceStatTxFramesQueue0,
               eponDeviceStatTxFramesQueue1,
               eponDeviceStatTxFramesQueue2,
               eponDeviceStatTxFramesQueue3,
               eponDeviceStatTxFramesQueue4,
               eponDeviceStatTxFramesQueue5,
               eponDeviceStatTxFramesQueue6,
               eponDeviceStatTxFramesQueue7,
               eponDeviceStatRxFramesQueue0,
               eponDeviceStatRxFramesQueue1,
               eponDeviceStatRxFramesQueue2,
               eponDeviceStatRxFramesQueue3,
               eponDeviceStatRxFramesQueue4,
               eponDeviceStatRxFramesQueue5,
               eponDeviceStatRxFramesQueue6,
               eponDeviceStatRxFramesQueue7,
               eponDeviceStatDroppedFramesQueue0,
               eponDeviceStatDroppedFramesQueue1,
               eponDeviceStatDroppedFramesQueue2,
               eponDeviceStatDroppedFramesQueue3,
               eponDeviceStatDroppedFramesQueue4,
               eponDeviceStatDroppedFramesQueue5,
               eponDeviceStatDroppedFramesQueue6,
               eponDeviceStatDroppedFramesQueue7
       }
       STATUS  current
       DESCRIPTION
               "A collection of objects of EPON device Statistics"
       ::= { eponDeviceGroups 3 }



   -- Compliance

   eponDeviceCompliances OBJECT IDENTIFIER ::= {eponDeviceConformance 2}

   eponDeviceCompliance MODULE-COMPLIANCE
       STATUS      current
       DESCRIPTION "The compliance statement for EPON Devices."
       MODULE  -- this module
       MANDATORY-GROUPS { eponDeviceGroupControl }

       GROUP       eponDeviceGroupRMadLTable
       DESCRIPTION " This group is mandatory for all
                              OLT EPON devices supporting LLID-MAC
                              address table."

       GROUP       eponDeviceGroupStat
       DESCRIPTION "This group is mandatory for all EPON devices
                    supporting interfaces for Statistics collection."


       ::= { eponDeviceCompliances 1}



   END

-- 
--    Copyright (C) The Internet Society (2005).  This document is subject
--    to the rights, licenses and restrictions contained in BCP 78, and
--    except as set forth therein, the authors retain all their rights.
-- Acknowledgment
-- 
--    Funding for the RFC Editor function is currently provided by the
--    Internet Society.
