-- *****************************************************************
--
-- SPRING-TIDE-NETWORKS-TC.mib:  
--      Spring Tide Networks MIB Textual Conventions
--
--
--      Copyright (c) 1999, 2000 by Spring Tide Networks, Inc.
--                      ALL RIGHTS RESERVED       
-- 
-- *****************************************************************


SPRING-TIDE-NETWORKS-TC DEFINITIONS ::= BEGIN

    IMPORTS
        MODULE-IDENTITY
                FROM SNMPv2-SMI
        TEXTUAL-CONVENTION
                FROM SNMPv2-TC
        stnMibModules
                FROM SPRING-TIDE-NETWORKS-SMI;

    stnTextualConventions MODULE-IDENTITY
        LAST-UPDATED    "0002160000Z"
        ORGANIZATION    "Spring Tide Networks, Inc."
        CONTACT-INFO
                "
                Spring Tide Networks, Inc.
                Customer Service
                Postal: 3 Clock Tower Place
                        Maynard, MA 01754
                Tel:    1 888-786-4357
                Email:  stncs@springtidenet.com
                "
        DESCRIPTION     
                "This MIB module defines textual conventions used 
                throughout the Spring Tide Networks enterprise MIBs."
        ::= { stnMibModules 1 }


--  Network Service Access Point (NSAP) Address
    NSAPAddress ::= TEXTUAL-CONVENTION
        STATUS      current
        DESCRIPTION "Network Service Access Point Address"
        SYNTAX      OCTET STRING (SIZE (20))

    CountryCode ::= TEXTUAL-CONVENTION
        DISPLAY-HINT "2a"
        STATUS       current
        DESCRIPTION
             "Represents a case-insensitive 2-letter country code taken from
              ISO-3166. Unrecognized countries are represented as empty string.
             "
        SYNTAX       OCTET STRING (SIZE (0 | 2))

    StnHardwareModuleType ::= TEXTUAL-CONVENTION
        STATUS      current
        DESCRIPTION "SpringTide Networks module types."
        SYNTAX      INTEGER { 
            unknown(1),         -- not applicable or other
            empty(2),           -- empty slot
            cpm(3),             -- Central Processor Module
            tsm(4),             -- Tunnel Switching Module
            swfm-5G(5),         -- 5G Switch Fabric Module
            rim(6),             -- Resource Module
            fcc(7),             -- Connector Module
            fan(8),             -- Fan Module
            powersupply(9),     -- Power Supply Module
            midplane(10),       -- Midplane Module
            e100BT-4(11),       -- 100 BaseT Ethernet 4 port Module
            e100BT-FX-4(12),    -- 100 BaseT Ethernet Fiber 4 port Module
            e100BT-8(13),       -- 100 BaseT Ethernet 8 port Module
            e100BT-FX-8(14),    -- 100 BaseT Ethernet Fiber 8 port Module
            atmOC3-SMF-4(15),   -- ATM OC3/STM1 SMF 4 port Module
            atmOC3-MMF-4(16),   -- ATM OC3/STM1 MMF 4 port Module
            atmOC12-SMF-1(17),  -- ATM OC12/STM4 SMF 1 port Module
            atmOC12-MMF-1(18),  -- ATM OC12/STM4 MMF 1 port Module
            posOC12-SMF-2(19),  -- POS OC12/STM4 SMF 2 port Module
            atmDS3-12(20),      -- ATM DES3/E3 12 port Module
            tsm2(21),           -- Tunnel Switching Module II
            sfx-5G(22),         -- 5G Switch Fabric Module with Serial Crossbar
            gigE-1-e100BT-4(23), -- Gigabit Ethernet 1 port with 100 BaseT Ethernet 4 port Module
            gigE-1-e100BT-FX-4(24), -- Gigabit Ethernet 1 port with 100 BaseT Ethernet Fiber 4 port Module
            fan2(25)            -- 500-3010 Fan Module
        }

    StnHardwareSubModuleType ::= TEXTUAL-CONVENTION
        STATUS      current
        DESCRIPTION "SpringTide Networks sub-module types."
        SYNTAX      INTEGER { 
                unknown(1),         -- not applicable or other
                empty(2),           -- empty slot
                encryption(3)       -- 
            }

    StnModuleAdminStatus ::= TEXTUAL-CONVENTION
        STATUS          current
        DESCRIPTION     "Administrative status of a module."
        SYNTAX          INTEGER {    
                            unknown(1),         -- none of the following
                            not-present(2),     -- 
                            down(3),            -- 
                            booting(4),         -- 
                            testing(5),         -- 
                            up-standalone(6),   -- 
                            up-standby(7),      -- 
                            up-primary(8)       -- 
                        }

    StnModuleOperStatus ::= TEXTUAL-CONVENTION
        STATUS          current
        DESCRIPTION     "Operational status of a module."
        SYNTAX          INTEGER {    
                            unknown(1),       -- none of the following
                            not-present(2),   -- 
                            down(3),          -- 
                            booting(4),       -- 
                            testing(5),       -- 
                            up-standalone(6), -- 
                            up-standby(7),    -- 
                            up-primary(8)     -- 
                        }


    StnEngineAdminStatus ::= TEXTUAL-CONVENTION
        STATUS          current
        DESCRIPTION     "Administrative status of an engine."
        SYNTAX          INTEGER {    
                            unknown(1),         -- none of the following
                            not-present(2),     -- 
                            down(3),            --
                            detected(4),        --
                            configured(5),      -- 
                            up-standalone(6),   -- 
                            up-standby(7),      -- 
                            up-primary(8)       -- 
                        }

    StnEngineOperStatus ::= TEXTUAL-CONVENTION
        STATUS          current
        DESCRIPTION     "Operational status of an engine."
        SYNTAX          INTEGER {    
                            unknown(1),         -- none of the following
                            not-present(2),     --
                            down(3),            --
                            detected(4),        --
                            configured(5),      -- 
                            up-standalone(6),   -- 
                            up-standby(7),      -- 
                            up-primary(8)       -- 
                        }

    StnLedStatus ::= TEXTUAL-CONVENTION
        STATUS          current
        DESCRIPTION     "Current LED status."
        SYNTAX          INTEGER {    
                unknown(1),         -- none of the following 
                off(2),             -- 
                on(3),              -- on, but not one of the following
                green(4),           -- 
                yellow(5),          -- 
                red(6),             -- 
                orange(7),          -- 
                blink-green(8),     -- 
                blink-yellow(9),    -- 
                blink-red(10),      -- 
                blink-orange(11)    -- 
            }

    StnPowerStatus ::= TEXTUAL-CONVENTION
        STATUS          current
        DESCRIPTION     "Status of the power supply."
        SYNTAX          INTEGER {    
                unknown(1),         -- none of the following 
                present(2),         -- power is connected
                not-present(3)      -- power is not connected
            }


    StnBatteryStatus ::= TEXTUAL-CONVENTION
        STATUS          current
        DESCRIPTION     "Status of the battery."
        SYNTAX          INTEGER {    
                unknown(1),         -- none of the following 
                ok(2),              -- battery power is within the acceptable range
                low(3)              -- battery power is below the recommended range
            }

    StnFlashStatus ::= TEXTUAL-CONVENTION
        STATUS          current
        DESCRIPTION     "Status of the flash."
        SYNTAX          INTEGER {    
                general-failure(1), -- none of the following 
                ok(2),              -- flash is operational
                not-present(3),     -- flash is not present
                full(4),            -- flash is full
                cannot-write(5)     -- flash is cannot be written
            }

    StnResourceStatus ::= TEXTUAL-CONVENTION
        STATUS          current
        DESCRIPTION     "Status of the system resources."
        SYNTAX          INTEGER {    
                unknown(1),                 -- none of the following 
                ok(2),                      -- all system resources available  
                low-memory(3),              -- low memory
                no-semaphores-available(4), -- no system semaphores available
                no-buffers-available(5),    -- no system buffers available
                no-sockets-available(6)     -- no system sockets available
            }

    StnUserFailureType ::= TEXTUAL-CONVENTION
        STATUS          current
        DESCRIPTION     "Types of user failures."
        SYNTAX          INTEGER {    
                authentication-failure(1),  -- authentication
                authorization-failure(2),   -- authorization  
                resource-failure(3)         -- resource
            }

    StnConfigFailureType ::= TEXTUAL-CONVENTION
        STATUS          current
        DESCRIPTION     "Types of configuration failures."
        SYNTAX          INTEGER {    
                access-failure(1),      -- access
                unexpected-change(2)    -- unexpected change  
            }


    StnDomainMapType ::= TEXTUAL-CONVENTION
	STATUS		current
	DESCRIPTION	"SpringTide Networks Domain Map types."
	SYNTAX		INTEGER {
		mapip(1), -- Domain Identifier for an IP Subnet
		mapatm(2) -- Domain Identifier for an ATM circuit
    }

END
