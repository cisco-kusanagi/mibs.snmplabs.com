--			Ascend mibcadslnet MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBCADSLNET-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibcadslNetworkProfile  OBJECT IDENTIFIER ::= { configuration 6}

	-- The mibcadslNetworkProfile table
	--
	-- This table contains parameters for the mibcadslNetworkProfile profile
	--

    mibcadslNetworkProfileTable	OBJECT-TYPE
	SYNTAX		SEQUENCE OF MibcadslNetworkProfileEntry
	ACCESS		not-accessible
	STATUS		mandatory
	DESCRIPTION	"A list of mibcadslNetworkProfile profile entries."
	::= { mibcadslNetworkProfile 1 }

    mibcadslNetworkProfileEntry	OBJECT-TYPE
	SYNTAX		MibcadslNetworkProfileEntry
	ACCESS		not-accessible
	STATUS		mandatory
	DESCRIPTION	"A mibcadslNetworkProfile entry containing objects that
			 maps to the parameters of mibcadslNetworkProfile profile."
	INDEX		{ cadslNetworkProfile-Shelf-o, cadslNetworkProfile-Slot-o, cadslNetworkProfile-Item-o }
	::= { mibcadslNetworkProfileTable 1 }

    MibcadslNetworkProfileEntry ::=
	SEQUENCE {
	    cadslNetworkProfile-Shelf-o
		INTEGER,
	    cadslNetworkProfile-Slot-o
		INTEGER,
	    cadslNetworkProfile-Item-o
		INTEGER,
	    cadslNetworkProfile-Name
		DisplayString,
	    cadslNetworkProfile-PhysicalAddress-Shelf
		INTEGER,
	    cadslNetworkProfile-PhysicalAddress-Slot
		INTEGER,
	    cadslNetworkProfile-PhysicalAddress-ItemNumber
		INTEGER,
	    cadslNetworkProfile-Enabled
		INTEGER,
	    cadslNetworkProfile-ProfileNumber
		INTEGER,
	    cadslNetworkProfile-LineConfig-TrunkGroup
		INTEGER,
	    cadslNetworkProfile-LineConfig-NailedGroup
		INTEGER,
	    cadslNetworkProfile-LineConfig-RoutePort-SlotNumber-SlotNumber
		INTEGER,
	    cadslNetworkProfile-LineConfig-RoutePort-SlotNumber-ShelfNumber
		INTEGER,
	    cadslNetworkProfile-LineConfig-RoutePort-RelativePortNumber-RelativePortNumber
		INTEGER,
	    cadslNetworkProfile-LineConfig-Activation
		INTEGER,
	    cadslNetworkProfile-LineConfig-DataRateMode
		INTEGER,
	    cadslNetworkProfile-LineConfig-MaxUpStreamRate
		INTEGER,
	    cadslNetworkProfile-LineConfig-MaxDownStreamRate
		INTEGER,
	    cadslNetworkProfile-LineConfig-LoopBack
		INTEGER,
	    cadslNetworkProfile-Action-o
		INTEGER
	}

    cadslNetworkProfile-Shelf-o	OBJECT-TYPE
	SYNTAX	INTEGER
	ACCESS	read-only
	STATUS	mandatory
	DESCRIPTION	""
	::= { mibcadslNetworkProfileEntry 1 }

    cadslNetworkProfile-Slot-o	OBJECT-TYPE
	SYNTAX	INTEGER
	ACCESS	read-only
	STATUS	mandatory
	DESCRIPTION	""
	::= { mibcadslNetworkProfileEntry 2 }

    cadslNetworkProfile-Item-o	OBJECT-TYPE
	SYNTAX	INTEGER
	ACCESS	read-only
	STATUS	mandatory
	DESCRIPTION	""
	::= { mibcadslNetworkProfileEntry 3 }

    cadslNetworkProfile-Name	OBJECT-TYPE
	SYNTAX	DisplayString
	ACCESS	read-write
	STATUS	mandatory
	DESCRIPTION	"For future use. The current design does not use the name field but instead references Cap adsl lines by the physical address; we may in the future support referencing Cap adsl lines by name as well as by address. The name consists of a null terminated ascii string supplied by the user; it defaults to the ascii form of the Cap adsl line physical address."
	::= { mibcadslNetworkProfileEntry 4 }

    cadslNetworkProfile-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibcadslNetworkProfileEntry 5 }

    cadslNetworkProfile-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibcadslNetworkProfileEntry 6 }

    cadslNetworkProfile-PhysicalAddress-ItemNumber	OBJECT-TYPE
	SYNTAX	INTEGER
	ACCESS	read-write
	STATUS	mandatory
	DESCRIPTION	"A number that specifies an addressable entity within the context of shelf and slot."
	::= { mibcadslNetworkProfileEntry 7 }

    cadslNetworkProfile-Enabled	OBJECT-TYPE
	SYNTAX	INTEGER {
		    no (1),
		    yes (2)
		}
	ACCESS	read-write
	STATUS	mandatory
	DESCRIPTION	"TRUE if the line is enabled, otherwise FALSE."
	::= { mibcadslNetworkProfileEntry 8 }

    cadslNetworkProfile-ProfileNumber	OBJECT-TYPE
	SYNTAX	INTEGER
	ACCESS	read-write
	STATUS	mandatory
	DESCRIPTION	"For potential backwards compatibility. The current design consists of one line profile numbered 0."
	::= { mibcadslNetworkProfileEntry 9 }

    cadslNetworkProfile-LineConfig-TrunkGroup	OBJECT-TYPE
	SYNTAX	INTEGER
	ACCESS	read-write
	STATUS	mandatory
	DESCRIPTION	"The trunk group to which this line is assigned. 0 means this line is not part of a trunk group."
	::= { mibcadslNetworkProfileEntry 10 }

    cadslNetworkProfile-LineConfig-NailedGroup	OBJECT-TYPE
	SYNTAX	INTEGER
	ACCESS	read-write
	STATUS	mandatory
	DESCRIPTION	"A number that identifies the set of lines that makes up a nailed group. 0 means this line is not part of a nailed group."
	::= { mibcadslNetworkProfileEntry 11 }

    cadslNetworkProfile-LineConfig-RoutePort-SlotNumber-SlotNumber	OBJECT-TYPE
	SYNTAX	INTEGER
	ACCESS	read-write
	STATUS	mandatory
	DESCRIPTION	""
	::= { mibcadslNetworkProfileEntry 12 }

    cadslNetworkProfile-LineConfig-RoutePort-SlotNumber-ShelfNumber	OBJECT-TYPE
	SYNTAX	INTEGER
	ACCESS	read-write
	STATUS	mandatory
	DESCRIPTION	"TNT is a multi shelf system. To minimise the changes required to existing code the shelf number is added to this structure as it will almost always be needed when a slot number is needed."
	::= { mibcadslNetworkProfileEntry 13 }

    cadslNetworkProfile-LineConfig-RoutePort-RelativePortNumber-RelativePortNumber	OBJECT-TYPE
	SYNTAX	INTEGER
	ACCESS	read-write
	STATUS	mandatory
	DESCRIPTION	""
	::= { mibcadslNetworkProfileEntry 14 }

    cadslNetworkProfile-LineConfig-Activation	OBJECT-TYPE
	SYNTAX	INTEGER {
		    static (1),
		    dsrActive (2),
		    dcdDsrActive (3)
		}
	ACCESS	read-write
	STATUS	mandatory
	DESCRIPTION	"Line activation mode."
	::= { mibcadslNetworkProfileEntry 15 }

    cadslNetworkProfile-LineConfig-DataRateMode	OBJECT-TYPE
	SYNTAX	INTEGER {
		    autobaud (2),
		    singlebaud (3)
		}
	ACCESS	read-only
	STATUS	mandatory
	DESCRIPTION	"The data rate mode define the mode for modem training"
	::= { mibcadslNetworkProfileEntry 19 }

    cadslNetworkProfile-LineConfig-MaxUpStreamRate	OBJECT-TYPE
	SYNTAX	INTEGER {
		    n-1088000 (51),
		    n-952000 (52),
		    n-816000 (53),
		    n-680000 (54),
		    n-544000 (55),
		    n-408000 (56),
		    n-272000 (57)
		}
	ACCESS	read-write
	STATUS	mandatory
	DESCRIPTION	"The up stream max rate defines the maximum rate from the coe to the cpe."
	::= { mibcadslNetworkProfileEntry 20 }

    cadslNetworkProfile-LineConfig-MaxDownStreamRate	OBJECT-TYPE
	SYNTAX	INTEGER {
		    n-7168000 (1),
		    n-6272000 (2),
		    n-5120000 (3),
		    n-4480000 (4),
		    n-3200000 (5),
		    n-2688000 (6),
		    n-2560000 (7),
		    n-2240000 (8),
		    n-1920000 (9),
		    n-1600000 (10),
		    n-1280000 (11),
		    n-960000 (12),
		    n-640000 (13)
		}
	ACCESS	read-write
	STATUS	mandatory
	DESCRIPTION	"The down stream max rate defines the maximum rate from the coe to the cpe."
	::= { mibcadslNetworkProfileEntry 21 }

    cadslNetworkProfile-LineConfig-LoopBack	OBJECT-TYPE
	SYNTAX	INTEGER {
		    none (1),
		    analog (2),
		    digital (3)
		}
	ACCESS	read-write
	STATUS	mandatory
	DESCRIPTION	"Configuration of different modem loopbacks."
	::= { mibcadslNetworkProfileEntry 23 }

    cadslNetworkProfile-Action-o	OBJECT-TYPE
	SYNTAX	INTEGER {
		    noAction (1),
		    createProfile (2),
		    deleteProfile (3)
		}
	ACCESS	read-write
	STATUS	mandatory
	DESCRIPTION	""
	::= { mibcadslNetworkProfileEntry 22 }

END
