CXAtmDxi-MIB DEFINITIONS ::= BEGIN

--#CURRENT_VERSION 1

IMPORTS
Counter,TimeTicks		FROM RFC1155-SMI
OBJECT-TYPE 		FROM RFC-1212
ifIndex			FROM RFC1213-MIB
	cxAtmDxi,Alias		FROM CXProduct-SMI;


-- Proprietary Data Types
PSapIndex		::= INTEGER (0..0)
SubRef		::= INTEGER (0..255)
Dfa		::= INTEGER (0..1023)
DfaX		::= INTEGER (0..16777216)
Vpi		::= INTEGER (0..255)
Vci		::= INTEGER (0..65535)


-- This MIB consists of the following:
-- (1) Global group
-- (2) Public Service Access Point group
-- (3) Service Access Point group
-- (4) Route group
-- (5) Route Statistics group



--  Global group

--  The group consisting of parameters which are layer-wide in scope.
--
--  The first four objects within the group are used to perform translations between DXI circuit DFAs and ATM
--  circuit VPI/VCIs.
--
--  The first object identifies the supported MIB module version.
--
--  The next four objects provide a calculator-like functionality and do not impose configuration or storage of 
--  any sort.
--
--  Dxi Frame Address (DFA) is the mechanism used to identify a DXI circuit, and must be unique per port.
--
--  The combination of Virtual Path Identifier (VPI) and Virtual Channel identifier (VCI) is the mechanism
--  used to identify an ATM circuit, and must be unique per port.


atmDxiMibLevel OBJECT-TYPE
	SYNTAX  INTEGER
	ACCESS  read-only
	STATUS  mandatory
	DESCRIPTION
  "Used to determine current MIB module release supported by agent.  Object is in decimal."
	DEFVAL  { 0 }
	--#STARTING_VERSION 1
	::= { cxAtmDxi 1 }


atmDxiTranslationDfa OBJECT-TYPE
	SYNTAX  DfaX
	ACCESS  read-write
	STATUS  mandatory
	DESCRIPTION
  "Its specification implies a translation request to the corresponding VPI/VCI pair, according to the translation mode specified by atmDxiTranslationMode.  The result can be read from objects atmDxiTranslationVpi & atmDXiTranslationVci. "
	::= { cxAtmDxi 2 }


atmDxiTranslationVpi OBJECT-TYPE
	SYNTAX  Vpi
	ACCESS  read-write
	STATUS  mandatory
	DESCRIPTION
  "Its specification implies a translation request between the pair (VPI,VCI) into the corresponding DFA, according to the translation mode specified by atmDxiTranslationMode.  The result can be read from object atmDxiTranslationDfa. "
	::= { cxAtmDxi 3 }


atmDxiTranslationVci OBJECT-TYPE
	SYNTAX  Vci
	ACCESS  read-write
	STATUS  mandatory
	DESCRIPTION
  "Its specification implies a translation request between the pair (VPI,VCI) into the corresponding DFA, according to the translation mode specified by atmDxiTranslationMode.  The result can be read from object atmDxiTranslationDfa. "
	::= { cxAtmDxi 4 }


atmDxiTranslationMode OBJECT-TYPE
	SYNTAX  INTEGER {
twobytes	(1),
fourbytes	(2)
}
	ACCESS  read-write
	STATUS  mandatory
	DESCRIPTION
  "Defines the mode used for translation between DFAs and the pair (VPI,VCI).  The mode determines how many bytes are used to encode/decode DFAs or (VPI/VCI) pairs at their respective interface."
	DEFVAL { twobytes }
	::= { cxAtmDxi 5 }



--  Public Service Access Point group

--  The group containing configuration and statistical information associated
--  with public service access points (PSAPs) at the ATM DXI layer.
--  PSAPs always associate with convergence interfaces, and in the case of 
--  the ATM DXI layer, terminates at the ATM layer.
--  PSAPs are not removable!


atmDxiPSapTable OBJECT-TYPE
	SYNTAX  SEQUENCE OF AtmDxiPSapEntry
	ACCESS  not-accessible
	STATUS  mandatory
	DESCRIPTION
  "A table containing information pertaining to one public service access point (PSAP)."
	::= { cxAtmDxi 10 }


atmDxiPSapEntry OBJECT-TYPE
	SYNTAX  AtmDxiPSapEntry
	ACCESS  not-accessible
	STATUS  mandatory
	DESCRIPTION
  "Defines an entry in the Public Service Access Point group."
	INDEX { atmDxiPSapNumber }
	::= { atmDxiPSapTable 1 }


AtmDxiPSapEntry ::=
	SEQUENCE {
-- Parameters
atmDxiPSapNumber			PSapIndex,		-- 1
atmDxiPSapConnectTimer		INTEGER,		-- 5
-- Control
atmDxiPSapControl			INTEGER,		--10
-- Status
atmDxiPSapState			INTEGER,		--15
-- Statistics
atmDxiPSapTxFrames		Counter,			--20
atmDxiPSapRxFrames		Counter,			--21
atmDxiPSapTxOctets			Counter,			--22
atmDxiPSapRxOctets			Counter,			--23
atmDxiPSapOutSuccessfullConnects	Counter,			--24
atmDxiPSapOutUnsuccessfullConnects	Counter,			--25
atmDxiPSapInConnectsReceived		Counter,			--26
atmDxiPSapTxResets			Counter,			--27
atmDxiPSapRxResets			Counter,			--28
atmDxiPSapNoServiceDiscards		Counter,			--35
atmDxiPSapCongestionDiscards		Counter			--36
	}


atmDxiPSapNumber OBJECT-TYPE
	SYNTAX  PSapIndex
	ACCESS  read-only
	STATUS  mandatory
	DESCRIPTION
  "Identifies this PSAP (public service access point) with a numerical value. Values are unique per public service access point.

Value 0 is reserved for the PSAP and is non removable."
	::= { atmDxiPSapEntry 1 }


atmDxiPSapConnectTimer OBJECT-TYPE
	SYNTAX  INTEGER (3..600)
	ACCESS  read-write
	STATUS  mandatory
	DESCRIPTION
  "Determines the number of seconds between attempts to establish a connection for a DXI to ATM circuit mapping.  A connection is attempted only for defined non-connected routes. "
	DEFVAL {10 }
	::= { atmDxiPSapEntry 5 }


atmDxiPSapControl OBJECT-TYPE
	SYNTAX  INTEGER {
clearStats	(1)
}
	ACCESS  write-only
	STATUS  mandatory
	DESCRIPTION
  "Permits control of a specific PSAP (public service access point).

Options:
  clearStats (1): Clear all statistics stored by statistics objects."
	::= { atmDxiPSapEntry 10 }


atmDxiPSapState OBJECT-TYPE
	SYNTAX  INTEGER {
offline		(1),
connected		(4)
}
	ACCESS  read-only
	STATUS  mandatory
	DESCRIPTION
  "Indicates the current state of this PSAP (public service access point).

Options:
  offline (1): Indicates a newly created public service access point whose configuration has not yet been sent to the ATM DXI layer.
  connected (4): PSAP is connected and data flow can proceed."
	DEFVAL { offline }
	::= { atmDxiPSapEntry 15 }


atmDxiPSapTxFrames OBJECT-TYPE
	SYNTAX  Counter
	ACCESS  read-only
	STATUS  mandatory
	DESCRIPTION
 "Indicates the number of frames transmitted by this public service access point."
	::= { atmDxiPSapEntry 20 }


atmDxiPSapRxFrames OBJECT-TYPE
	SYNTAX  Counter
	ACCESS  read-only
	STATUS  mandatory
	DESCRIPTION
  "Indicates the number of frames received by this public service access point."
	::= { atmDxiPSapEntry 21 }


atmDxiPSapTxOctets OBJECT-TYPE
	SYNTAX  Counter
	ACCESS  read-only
	STATUS  mandatory
	DESCRIPTION
  "Indicates the number of octets transmitted by this public service access point."
	::= { atmDxiPSapEntry 22 }


atmDxiPSapRxOctets OBJECT-TYPE
	SYNTAX  Counter
	ACCESS  read-only
	STATUS  mandatory
	DESCRIPTION
  "Indicates the number of octets received by this public service access point."
	::= { atmDxiPSapEntry 23 }


atmDxiPSapOutSuccessfullConnects OBJECT-TYPE
	SYNTAX  Counter
	ACCESS  read-only
	STATUS  mandatory
	DESCRIPTION
  "Indicates the number of successful outgoing connections established by this PSAP (public service access point). An outgoing connection is always attempted from the ATM DXI to the Inter-Application Module (IAM)."
	::= { atmDxiPSapEntry 24 }


atmDxiPSapOutUnsuccessfullConnects OBJECT-TYPE
	SYNTAX  Counter
	ACCESS  read-only
	STATUS  mandatory
	DESCRIPTION
  "Indicates the number of unsuccessful outgoing connections attempted by this PSAP (public service access point). An outgoing connection is always attempted from the ATM DXI to the Inter-Application Module (IAM)."
	::= { atmDxiPSapEntry 25 }


atmDxiPSapInConnectsReceived OBJECT-TYPE
	SYNTAX  Counter
	ACCESS  read-only
	STATUS  mandatory
	DESCRIPTION
  "Indicates the number of connect attempts received at this PSAP (public service access point). An incoming connection is always attempted from the Inter-Application Module (IAM) to ATM DXI.

The ATM DXI layer will always refuse such connection attempts."
	::= { atmDxiPSapEntry 26 }


atmDxiPSapTxResets OBJECT-TYPE
	SYNTAX  Counter
	ACCESS  read-only
	STATUS  mandatory
	DESCRIPTION
  "Indicates the number of reset frames sent by this PSAP (public service access point)."
	::= { atmDxiPSapEntry 27 }


atmDxiPSapRxResets OBJECT-TYPE
	SYNTAX  Counter
	ACCESS  read-only
	STATUS  mandatory
	DESCRIPTION
  "Indicates the number of reset frames received by this PSAP (public service access point)."
	::= { atmDxiPSapEntry 28 }


atmDxiPSapNoServiceDiscards OBJECT-TYPE
	SYNTAX  Counter
	ACCESS  read-only
	STATUS  mandatory
	DESCRIPTION
  "Indicates the number of frames received from the ATM protocol stack which have been discarded by this PSAP (public service access point) because:

     - the DXI port is down."
	::= { atmDxiPSapEntry 35 }


atmDxiPSapCongestionDiscards OBJECT-TYPE
	SYNTAX  Counter
	ACCESS  read-only
	STATUS  mandatory
	DESCRIPTION
  "Indicates the number of received frames discarded due to system congestion."
	::= { atmDxiPSapEntry 36 }



--  Service Access Point group

--  The group containing configuration and statistical  information associated with interfaces at the ATM
--  DXI layer.
--
--  Interface at the ATM DXI layer are supported by service access points(SAPs).
--
--  Interface creation/removal is controlled via the Chassis Logical Interface Administration Table.
--
--  Common statistical information for this layer, such as packet and octet counters, can be located within
--  the Interface Table entry identified by the requested interface ifIndex.


atmDxiSapTable OBJECT-TYPE
	SYNTAX  SEQUENCE OF AtmDxiSapEntry
	ACCESS  not-accessible
	STATUS  mandatory
	DESCRIPTION
  "A table containing information pertaining to one service access point (interface)."
	::= { cxAtmDxi 11 }


atmDxiSapEntry OBJECT-TYPE
	SYNTAX  AtmDxiSapEntry
	ACCESS  not-accessible
	STATUS  mandatory
	DESCRIPTION
  "Defines an entry in the Service Access Point group."
	INDEX { ifIndex }
	::= { atmDxiSapTable 1 }


AtmDxiSapEntry ::=
	SEQUENCE {
-- Parameters
atmDxiSapMode				INTEGER,	-- 5
atmDxiSapTransparentDfa			Dfa,		-- 6
-- Control
atmDxiSapControl				INTEGER,	--10
-- Status
-- Statistics
atmDxiSapRxLmiFrames			Counter,		--20
atmDxiSapNoRouteDiscards			Counter,		--21
atmDxiSapRxInvalidDiscards			Counter,		--22
atmDxiSapCongestionDiscards			Counter,		--23
atmDxiSapFlowControlDiscards			Counter		--24
}


atmDxiSapMode OBJECT-TYPE
	SYNTAX  INTEGER {
mode-1a		(1),
mode-1b		(2),	--future use
mode-2		(3),	--future use
modeTransparent	(4),
modeLoopback	(5)
}
	ACCESS  read-write
	STATUS  mandatory
	DESCRIPTION
  "Defines the DXI operating mode to be used at the service access point."
	DEFVAL { mode-1a }
	::= { atmDxiSapEntry 5 }


atmDxiSapTransparentDfa OBJECT-TYPE
	SYNTAX  Dfa
	ACCESS  read-write
	STATUS  mandatory
	DESCRIPTION
  "Identifies the DXI frame address to use when the associated sap is configured for the transparent mode of operation (object atmDxiSapMode, value 'modeTransparent')."
	::= { atmDxiSapEntry 6 }


atmDxiSapControl OBJECT-TYPE
	SYNTAX  INTEGER {
clearStats	(1)
}
	ACCESS  write-only
	STATUS  mandatory
	DESCRIPTION
  "Permits control of this SAP (service access point).

Options:
  clearStats (1): Clear all statistics stored by statistics objects maintained within the service access point table."
	::= { atmDxiSapEntry 10 }


atmDxiSapRxLmiFrames OBJECT-TYPE
	SYNTAX  Counter
	ACCESS  read-only
	STATUS  mandatory
	DESCRIPTION
  "Indicates the number of DXI LMI (link management interface) frames received by this SAP."
	::= { atmDxiSapEntry 20 }


atmDxiSapNoRouteDiscards OBJECT-TYPE
	SYNTAX  Counter
	ACCESS  read-only
	STATUS  mandatory
	DESCRIPTION
  "Indicates the number of frames received from a DXI port which have been discarded by this SAP (service access point) because:

     - no route was associated with the frame
     - the frame was destined for a route that is not connected
     - the associated ATM circuit is down."
	::= { atmDxiSapEntry 21 }


atmDxiSapRxInvalidDiscards OBJECT-TYPE
	SYNTAX  Counter
	ACCESS  read-only
	STATUS  mandatory
	DESCRIPTION
  "Indicates the following:

     - number of incorrectly formatted DXI frames received by this SAP
     - number of frames received whose length is less than the minimum acceptable
     - number of frames received in error, as signaled by the lower layer.  Such errors include:
     - aborted frames
     - frames with a bad CRC
     - overrun frames
     - frames with a non-integral number of bits
     - frames that are longer than the lower layer is configured to accept.
     - number of frames received while port is down."
	::= { atmDxiSapEntry 22 }


atmDxiSapCongestionDiscards OBJECT-TYPE
	SYNTAX  Counter
	ACCESS  read-only
	STATUS  mandatory
	DESCRIPTION
  "Indicates the number of received frames discarded at this SAP (service access point) due to system congestion."
	::= { atmDxiSapEntry 23 }


atmDxiSapFlowControlDiscards OBJECT-TYPE
	SYNTAX  Counter
	ACCESS  read-only
	STATUS  mandatory
	DESCRIPTION
  "Indicates the number of frames received from a DXI port which have been discarded by this SAP (service access point) because the associated route was flow controlled from the remote."
	::= { atmDxiSapEntry 24 }



--  Route group

--  The group containing associations between DXI circuits at an ATM DXI port and ATM circuits at
--  a UNI port.

--  Each association is established via an entry in this table, and is commonly referred to as a route.

--  Routes identify DXI circuits via their DXI Frame Addresses (DFAs).  Each DXI circuit is also
--  identified to exists at a specified DXI port.  Associations of DXI circuits to ATM circuits are
--  made via the use of "alias", which are textual identifications of ATM circuits.  Each "alias"
--  identifies a unique ATM circuit and its assigned VPI/VCI.


atmDxiSysRouteTable OBJECT-TYPE
	SYNTAX  SEQUENCE OF AtmDxiSysRouteEntry
	ACCESS  not-accessible
	STATUS  mandatory
	DESCRIPTION
  "A table containing associations between ATM DXI circuits at DXI ports, and ATM circuits at a UNI port.

Associations (routes) permit interconnectivity between the two types of circuits."
	::= { cxAtmDxi 12 }


atmDxiSysRouteEntry OBJECT-TYPE
	SYNTAX  AtmDxiSysRouteEntry
	ACCESS  not-accessible
	STATUS  mandatory
	DESCRIPTION
  "Defines an entry in the Route group."
	INDEX {	ifIndex,
atmDxiSRDxiFrameAddress }
	::= { atmDxiSysRouteTable 1 }


AtmDxiSysRouteEntry ::=
	SEQUENCE {
-- Parameters
atmDxiSRDxiFrameAddress			Dfa,		-- 1
atmDxiSRRowStatus				INTEGER,	-- 2
atmDxiSRDestAlias				Alias,		-- 3
atmDxiSRSubRef				SubRef,		-- 4
-- Status
atmDxiSRRouteState				INTEGER,	--10
atmDxiSRFailureReason			INTEGER		--11
}


atmDxiSRDxiFrameAddress OBJECT-TYPE
	SYNTAX  Dfa
	ACCESS  read-only
	STATUS  mandatory
	DESCRIPTION
  "Identifies the DXI frame address which when combined with the ifIndex, uniquely identifies a DXI circuit."
	::= { atmDxiSysRouteEntry 1 }


atmDxiSRRowStatus OBJECT-TYPE
	SYNTAX  INTEGER {
invalid	(1),
valid	(2)
}
	ACCESS  read-write
	STATUS  mandatory
	DESCRIPTION
  "Determines the status of the objects in this row.

Options:
  invalid (1):  The row is deleted from the table immediately, however, values are still in effect until the next reset.

  valid (2):  Use this value to add a new row to the table, or modify an existing row."
	::= { atmDxiSysRouteEntry 2 }


atmDxiSRDestAlias OBJECT-TYPE
	SYNTAX  Alias
	ACCESS  read-write
	STATUS  mandatory
	DESCRIPTION
  "Determines the textual name of the destination service this route  connects to. When attempting a DXI circuit connection to an ATM circuit, this object specifies the name of the circuit at the ATM layer.

ATM DXI connections between 2 DXI cards within the same chassis is not provisioned for.

Range of Values: 1 -16 characters (first  character must be a letter)."
		::= { atmDxiSysRouteEntry 3 }


atmDxiSRSubRef OBJECT-TYPE
	SYNTAX  SubRef
	ACCESS  read-write
	STATUS  mandatory
	DESCRIPTION
  "Specifies a reference number that is used by layers supporting circuit consolidation, such as the FRIM, and must be unique for all routes sharing the same destination circuit at such layers.

The implementation of circuit consolidation onto a single ATM circuit is anticipated within the ATM Adaptation Layer  (AAL5).

Range of Values: 1 - 255 (when connecting to a service supporting circuit consolidation)

0 (when not using circuit consolidation, or when connecting to a service that does not support its use.)"
	DEFVAL { 0 }
	::= { atmDxiSysRouteEntry 4 }


atmDxiSRRouteState OBJECT-TYPE
	SYNTAX  INTEGER {
offLine		(1),
notConnected	(2),
inProgress		(3),
connected		(4),
connectedFlowOff	(5)
}
	ACCESS  read-only
	STATUS  mandatory
	DESCRIPTION
  "Indicates the status of this route.

Options:
  offLine (1): Indicates that the ATM DXI SAP this route is associated with does not exist or is offline.

  notConnected (2): Indicates that the remote destination does not exist, or has refused the connection.

  inProgress (3): Indicates that the connection is in the process of being established. This is a transient state.

  connected (4): Indicates that the connection is established and is ready for data transfer.

  connectedFlowOff (5): Indicates that the connections is established but data flow has been stopped."
	::= { atmDxiSysRouteEntry 10 }


atmDxiSRFailureReason OBJECT-TYPE
	SYNTAX  INTEGER {
noFailure			(1),
internalError		(2),
localAllocFailure		(3),
remoteAllocFailure		(4),
localNoAccess		(5),
remoteNoAccess		(6),
remotePvcDown		(8),
remotePvcBusy		(10),
localFcnFailure		(11),
remoteFcnFailure		(12),
localDsnFailure		(13),
remoteAliasNotFound		(15),
remoteNoPvcService		(16),
mpeInvalidSubref		(17),
routeStalled		(18)
}
	ACCESS  read-only
	STATUS  mandatory
	DESCRIPTION
  "Indicates the status of a failed connection. The value of this object is only valid between attempts to establish the route connection atmDxiSRRouteState = notConnected), and may or may not change after successive failed attempts.

Options:
  noFailure (1): Once a system route has been successfully connected, this value is maintained for the duration of the connection.

  internalError (2): An internal error has occurred.

  localAllocFailure (3): There is insufficient memory available for ATM DXI to establish this connection.

  remoteAllocFailure (4): There is insufficient memory available for the destination protocol layer to establish this connection.

  localNoAccess (5): This route is associated with a SAP that does not exist.

  remoteNoAccess (6): This route is associated with a SAP that does not exist at the destination layer.

  remotePvcDown (8): The PVC at the destination protocol layer is down.

  remotePvcBusy (10): The destination associated with this route is already connected. This typically occurs when the route is a non-MPE (PVC consolidating) circuit.

  localFcnFailure (11): Flow control negotiation failed.

  remoteFcnFailure (12): Flow control negotiation failed at the destination protocol layer.

  localDsnFailure (13): Data size negotiation failed.

  remoteAliasNotFound (15): The destination alias (atmDxiSRDestAlias) does not exist.

  remoteNoPvcService (16): The destination protocol layer does not support PVC service.

  mpeInvalidSubref (17): The value of atmDxiSRSubRef is invalid at the destination protocol layer. (i.e., atmDxiSRSubRef is set to '0' and the destination circuit is configured for PVC consolidation).

  routeStalled (18): An invalid control packet exchange has occurred during the route setup procedure.  The route is temporarily stalled but will recover within 5 seconds."
	::= { atmDxiSysRouteEntry 11 }



--  Route Statistics group

--  The group containing statistics for established routes in the route table.


atmDxiSysRouteStatsTable OBJECT-TYPE
	SYNTAX  SEQUENCE OF AtmDxiSysRouteStatsEntry
	ACCESS  not-accessible
	STATUS  mandatory
	DESCRIPTION
  "A table containing statistics for established routes in the route table."
	::= { cxAtmDxi 13 }


atmDxiSysRouteStatsEntry OBJECT-TYPE
	SYNTAX  AtmDxiSysRouteStatsEntry
	ACCESS  not-accessible
	STATUS  mandatory
	DESCRIPTION
  "Defines an entry in the Route Statistics group."
	INDEX {	ifIndex,
atmDxiSRStatsDxiFrameAddress }
	::= { atmDxiSysRouteStatsTable 1 }


AtmDxiSysRouteStatsEntry ::=
	SEQUENCE {
-- Parameters
atmDxiSRStatsDxiFrameAddress		Dfa,		-- 1
atmDxiSRStatsCreationTime			TimeTicks,	-- 2
atmDxiSRStatsNegotiatedDataSize		INTEGER,	-- 3
atmDxiSRStatsTxFrames			Counter,		-- 4
atmDxiSRStatsRxFrames			Counter,		-- 5
atmDxiSRStatsTxOctets			Counter,		-- 6
atmDxiSRStatsRxOctets			Counter,		-- 7
atmDxiSRStatsFlowControlDiscards		Counter		-- 8
}


atmDxiSRStatsDxiFrameAddress OBJECT-TYPE
	SYNTAX  Dfa
	ACCESS  read-only
	STATUS  mandatory
	DESCRIPTION
  "Identifies the DXI frame address, which when combined with the ifIndex, uniquely identifies a DXI circuit."
	::= { atmDxiSysRouteStatsEntry 1 }


atmDxiSRStatsCreationTime OBJECT-TYPE
	SYNTAX  TimeTicks
	ACCESS  read-only
	STATUS  mandatory
	DESCRIPTION
  "Indicates the system clock's time at which this connection was created."
	::= { atmDxiSysRouteStatsEntry 2 }


atmDxiSRStatsNegotiatedDataSize OBJECT-TYPE
	SYNTAX  INTEGER (0..65535)
	ACCESS  read-only
	STATUS  mandatory
	DESCRIPTION
  "Indicates the data size of a frame negotiated at connection. "
	::= { atmDxiSysRouteStatsEntry 3 }


atmDxiSRStatsTxFrames OBJECT-TYPE
	SYNTAX  Counter
	ACCESS  read-only
	STATUS  mandatory
	DESCRIPTION
  "Indicates the number of frames transmitted by this connection."
	::= { atmDxiSysRouteStatsEntry 4 }


atmDxiSRStatsRxFrames OBJECT-TYPE
	SYNTAX  Counter
	ACCESS  read-only
	STATUS  mandatory
	DESCRIPTION
  "Indicates the number of frames received by this connection."
	::= { atmDxiSysRouteStatsEntry 5 }


atmDxiSRStatsTxOctets OBJECT-TYPE
	SYNTAX  Counter
	ACCESS  read-only
	STATUS  mandatory
	DESCRIPTION
  "Indicates the number of octets transmitted by this connection."
	::= { atmDxiSysRouteStatsEntry 6 }


atmDxiSRStatsRxOctets OBJECT-TYPE
	SYNTAX  Counter
	ACCESS  read-only
	STATUS  mandatory
	DESCRIPTION
  "Indicates the number of octets received by this connection."
	::= { atmDxiSysRouteStatsEntry 7 }


atmDxiSRStatsFlowControlDiscards OBJECT-TYPE
	SYNTAX  Counter
	ACCESS  read-only
	STATUS  mandatory
	DESCRIPTION
  "Indicates the number of frames which were destined for this route but were discarded due to flow control from the remote."
	::= { atmDxiSysRouteStatsEntry 8 }

END
