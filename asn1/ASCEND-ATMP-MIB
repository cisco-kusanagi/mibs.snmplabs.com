--			Ascend ATMP Mib
--
--			Ascend Communications, Inc
--			1701 Harbor Bay Pkwy
--			Alameda, CA 94502
--			+1 510 769 6001
--			info@ascend.com
--
--		Copyright (c) 1993-1998 Ascend Communications, Inc.
--		All rights reserved.
--
-- $Id: atmp.mib,v 29.1 1998/07/08 04:40:17 njuthani Exp $
--
-- 1 July 1998 	Initially created
--
ASCEND-ATMP-MIB DEFINITIONS ::= BEGIN

    IMPORTS
	atmpGroup
	    FROM ASCEND-MIB
	DisplayString
	    FROM ASCEND-MIB
	IpAddress,
	Counter
	    FROM RFC1155-SMI
	OBJECT-TYPE
	    FROM RFC-1212;

				
	-- The atmpGroup contains information pertaining to ATMP tunnels.
	-- The following abbreviations are used: 
	-- 	FA:		Foreign Agent
	-- 	HA:		Home Agent
	-- 	MN:		mobile node
	-- 	HN:		Home network


    atmpAgentMode OBJECT-TYPE
	SYNTAX	INTEGER {
		    atmp-disabled(1),	-- atmp is disabled
		    home-agent( 2 ),	-- configured to be home agent
		    foreign-agent( 3 ),	-- configured to be foreign agent
		    both-agent( 4 )	-- configured for foreign and home agent
		}
	ACCESS	read-only
	STATUS	mandatory
	DESCRIPTION
	    "The type of ATMP Agent."
	::= { atmpGroup 1 }

    atmpAgentType OBJECT-TYPE
	SYNTAX	INTEGER {
		    ha-router( 1 ),	-- home agent routes tunnel data
		    ha-gateway( 2 ),	-- home agent delivers tunneled data 
					-- without routing
		    ha-notapp( 3 ) 	-- not applicable
		}
	ACCESS	read-only
	STATUS	mandatory
	DESCRIPTION
	    "The type of ATMP HA Agent. ha-router means the HA will route
	     the tunneled data to other networks. ha-gateway means the
	     HA delivers tunneled data to other networks without
	     routing anything. A ha-notapp will be returned for FA and if
	     ATMP is disabled."
	::= { atmpGroup 2 }

    atmpAgentUDPPort OBJECT-TYPE
	SYNTAX	INTEGER
	ACCESS	read-only
	STATUS	mandatory
	DESCRIPTION
	    "UDP port number to be used for ATMP."
	::= { atmpGroup 3 }

    atmpAgentGreMtu OBJECT-TYPE
	SYNTAX	INTEGER
	ACCESS	read-only
	STATUS	mandatory
	DESCRIPTION
	    "The maximum IP packet size that can be transmitted to a peer
	     agent without performing fragmentation. The value 0 means
	     this feature is disabled."
	DEFVAL { 0 }
	::= { atmpGroup 4 }

    atmpAgentForceFragmentation OBJECT-TYPE
	SYNTAX	INTEGER {
		    enabled(1),		-- turn on option
		    disabled(2)		-- disable the option
		}
	ACCESS	read-only
	STATUS	mandatory
	DESCRIPTION
	    "To force fragmentation of large IP frames before they are sent
	     to the peer agent even if the packet has the DF bit set. NOTE:
	     this behavior is not standard and prevents MTU discovery 
	     mechanisms. This works in conjunction with atmpAgentGreMtu."
	DEFVAL { disabled }
	::= { atmpGroup 5 }

    atmpAgentHAIdleLimit OBJECT-TYPE
	SYNTAX	INTEGER 
	ACCESS	read-only
	STATUS	mandatory
	DESCRIPTION
	    "Time in minutes that the HA will allow a tunnel to have no traffic
	     before tearing it down. The value 0 means this option is
	     disabled."
	::= { atmpGroup 6 }

    atmpLastErrorGenerated OBJECT-TYPE
	SYNTAX	INTEGER {
		   no-error( 1 ),	  -- no error. also clears field
		   fa-auth-failed( 2 ),	  -- authentication of fa failed. 
		   ha-atmp-disabled( 3 ), -- ha is not configured to run atmp
		   too-many-tunnel( 4 ),  -- too many tunnels, out of resource.
		   err-parameter( 5 ),	  -- atmp message field is invalid
		   bad-tunnel( 6 ),	  -- atmp tunnel number is invalid. this
					  -- usually indicates one side reset.
		   err-timeout( 7 ),	  -- no response from agent
		   hn-unreachable( 8 ),	  -- hn connection profile is not up.
		   dns-failed( 9 ),	  -- dns lookup of the ha failed.
		   err-general( 10 )	  -- the favorite general error
		}
	ACCESS	read-write
	STATUS	mandatory
	DESCRIPTION
	    "This is the last error at the Agent level or Tunnel creation
	     that was generated by the Agent. To clear the field and
	     atmpAgentSentErrorTo do a set with the value no-error(1)" 
	::= { atmpGroup 7 }

    atmpAgentSentErrorTo OBJECT-TYPE
	SYNTAX	IpAddress
	ACCESS	read-only
	STATUS	mandatory
	DESCRIPTION
	    "The IP Address of the agent that the generated was sent to.
	     Clearing atmpLastErrorGenerated also clears this field."
	::= { atmpGroup 8 }

    atmpLastErrorRecv OBJECT-TYPE
	SYNTAX	INTEGER {
		   no-error( 1 ),	  -- no error. also clears field
		   fa-auth-failed( 2 ),	  -- authentication of fa failed. 
		   ha-atmp-disabled( 3 ), -- ha is not configured to run atmp
		   too-many-tunnel( 4 ),  -- too many tunnels, out of resource.
		   err-parameter( 5 ),	  -- atmp message field is invalid
		   bad-tunnel( 6 ),	  -- atmp tunnel number is invalid. this
					  -- usually indicates one side reset.
		   err-timeout( 7 ),	  -- no response from agent
		   hn-unreachable( 8 )	  -- hn connection profile is not up.
		}
	ACCESS	read-write
	STATUS	mandatory
	DESCRIPTION
	    "This is the last error at the Agent level or Tunnel creation
	     that was received from the Peer Agent. To clear the field and
	     atmpAgentRecvErrorFrom do a set with the value no-error(1)" 
	::= { atmpGroup 9 }

    atmpAgentRecvErrorFrom OBJECT-TYPE
	SYNTAX	IpAddress
	ACCESS	read-only
	STATUS	mandatory
	DESCRIPTION
	    "The IP Address of the agent that the last error received was
	    from.  Clearing atmpLastErrorRecv also clears this field."
	::= { atmpGroup 10 }

    atmpEnableAtmpTraps OBJECT-TYPE
	SYNTAX	INTEGER {
		    enabled( 1 ),	-- turn on atmp traps
		    disabled( 2 )	-- turn off atmp traps
		}
	ACCESS	read-write
	STATUS	mandatory
	DESCRIPTION
	    "Enable the atmp traps."
	DEFVAL { disabled }
	::= { atmpGroup 11 }

    atmpAgentNumberFATunnels OBJECT-TYPE
	SYNTAX	INTEGER
	ACCESS	read-only
	STATUS	mandatory
	DESCRIPTION
	    "The number of FA tunnels."
	::= { atmpGroup 12 }

    atmpAgentNumberHATunnels OBJECT-TYPE
	SYNTAX	INTEGER
	ACCESS	read-only
	STATUS	mandatory
	DESCRIPTION
	    "The number of HA tunnels."
	::= { atmpGroup 13 }


    atmpAgentNumberLocalTunnels OBJECT-TYPE
	SYNTAX	INTEGER
	ACCESS	read-only
	STATUS	mandatory
	DESCRIPTION
	    "The number of Local client mode tunnels."
	::= { atmpGroup 14 }

    atmpAgentTunnelHighWater OBJECT-TYPE
	SYNTAX	INTEGER
	ACCESS	read-only
	STATUS	mandatory
	DESCRIPTION
	    "The high water mark on created ATMP tunnels."
	::= { atmpGroup 15 }

	-- The Atmp Tunnel Table
	-- 
	-- The tunnel table is indexed by unique (local to the agent) ID. 
	-- To match tunnels from multiple agents use the HA address, 
	-- FA address and the tunnel ID of the tunnels.


    atmpTunnelTable	OBJECT-TYPE
	SYNTAX		SEQUENCE OF AtmpTunnelEntry
  	ACCESS		not-accessible
	STATUS		mandatory
	DESCRIPTION	"A list of ATMP tunnel entries."
	::= { atmpGroup 16 }

    atmpTunnelEntry	OBJECT-TYPE
	SYNTAX		AtmpTunnelEntry
	ACCESS		not-accessible
	STATUS		mandatory
    	DESCRIPTION	"A ATMP tunnel entry."
	INDEX		{ atmpTunnelIndex }
     	::= { atmpTunnelTable 1 }

    AtmpTunnelEntry ::=
	SEQUENCE {
	    atmpTunnelIndex
		INTEGER,
	    atmpTunnelId
		INTEGER,
	    atmpHAIpAddress
		IpAddress,
	    atmpFAIpAddress
		IpAddress,
	    atmpTunneledProtocol
		INTEGER,
	    atmpTunnelType
		INTEGER,
	    atmpTunnelState
		INTEGER,
	    atmpMnIpAddress
		IpAddress,
	    atmpMnNetmask
		IpAddress,
	    atmpMnIpxNetAddress
		OCTET STRING,
	    atmpMnIpxNodeAddress
		OCTET STRING,
	    atmpHNProfileName
		DisplayString,
	    atmpHNMaxTunnels
		INTEGER,
	    atmpFAPrimaryHAAddress
		DisplayString,
	    atmpFASecondaryHAAddress
		DisplayString,
    	    atmpFASsnStatusIndex
		INTEGER,
    	    atmpFAUserName
		DisplayString,
	    atmpInPkts
		Counter,
	    atmpInOctets
		Counter,
	    atmpInErrPkts
		Counter,
	    atmpOutPkts
		Counter,
	    atmpOutOctets
		Counter,
	    atmpOutErrPkts
		Counter,
    	    atmpPktsForcedToFragment
		Counter,
    	    atmpPktsFailedFragment
		Counter
	}

    atmpTunnelIndex OBJECT-TYPE
	SYNTAX	INTEGER (1..'7fffffff'h)
	ACCESS	read-only
	STATUS	mandatory
	DESCRIPTION
	    "A unique index assigned to this tunnel."
	::= { atmpTunnelEntry 1 }

    atmpTunnelId OBJECT-TYPE
	SYNTAX	INTEGER (0.. 65535)
	ACCESS	read-only
	STATUS	mandatory
	DESCRIPTION
	    "The tunnel ID assigned to this tunnel. This number is assigned
	     by the HA. NOTE: this number does *not* uniquely identify
	     a tunnel."
	::= { atmpTunnelEntry 2 }

    atmpHAIpAddress OBJECT-TYPE
	SYNTAX	IpAddress
	ACCESS	read-only
	STATUS	mandatory
	DESCRIPTION
	    "The IP Address of this tunnel's  HA."
	::= { atmpTunnelEntry 3 }

    atmpFAIpAddress OBJECT-TYPE
	SYNTAX	IpAddress
	ACCESS	read-only
	STATUS	mandatory
	DESCRIPTION
	    "The IP Address of this tunnel's  FA."
	::= { atmpTunnelEntry 4 }

    atmpTunneledProtocol OBJECT-TYPE
	SYNTAX	INTEGER {
		    ip( 1 ),	-- supports ip
		    ipx( 2 )	-- supports ipx
		}
	ACCESS	read-only
	STATUS	mandatory
	DESCRIPTION
	    "This value indicates the protocol(s) that the tunnel supports.
	     The value is a sum. The sum initially takes the value zero.
	     Then for each protocol that is supported, the value of the 
	     protocol is or'ed to the sum. Example: 3 means ip and ipx."
	::= { atmpTunnelEntry 5 }

    atmpTunnelType OBJECT-TYPE
	SYNTAX	INTEGER {
		    ha( 1 ),	-- ha tunnel
		    fa( 2 ),	-- fa tunnel
		    both( 3)	-- both ha and fa. local client mode
		}
	ACCESS	read-only
	STATUS	mandatory
	DESCRIPTION
	    "The type of tunnel this is."
	::= { atmpTunnelEntry 6 }

    atmpTunnelState OBJECT-TYPE
	SYNTAX	INTEGER {
		    registering( 1 ),	-- registering with the HA
		    up( 2 ),		-- tunnel is up
		    down( 3 )		-- tunnel is going down.
		}
	ACCESS	read-only
	STATUS	mandatory
	DESCRIPTION
	    "These are the states  the tunnel can be in. "
	::= { atmpTunnelEntry 7 }

    atmpMnIpAddress OBJECT-TYPE
	SYNTAX	IpAddress
	ACCESS	read-only
	STATUS	mandatory
	DESCRIPTION
	    "The IP Address of the Mobile Node."
	::= { atmpTunnelEntry 8 }

    atmpMnNetmask OBJECT-TYPE
	SYNTAX	IpAddress
	ACCESS	read-only
	STATUS	mandatory
	DESCRIPTION
	    "The netmask of the Mobile Node."
	::= { atmpTunnelEntry 9 }

    atmpMnIpxNetAddress OBJECT-TYPE
	SYNTAX	OCTET STRING (SIZE (4))
	ACCESS	read-only
	STATUS	mandatory
	DESCRIPTION
	    "The IPX network address of the Mobile Node."
	::= { atmpTunnelEntry 10 }


    atmpMnIpxNodeAddress OBJECT-TYPE
	SYNTAX	OCTET STRING (SIZE (6))
	ACCESS	read-only
	STATUS	mandatory
	DESCRIPTION
	    "The IPX node address of the Mobile Node."
	::= { atmpTunnelEntry 11 }

    atmpHNProfileName OBJECT-TYPE
	SYNTAX	DisplayString
	ACCESS	read-only
	STATUS	mandatory
	DESCRIPTION
	    "The name of the home network profile which will be used to
	     forward all packets received by the HA. This may be NULL if the
	     HA is in router mode." 
	::= { atmpTunnelEntry 12 }

    atmpHNMaxTunnels OBJECT-TYPE
	SYNTAX	INTEGER
	ACCESS	read-only
	STATUS	mandatory
	DESCRIPTION
	    "The maximum number of tunnels allowed to this HN."
	::= { atmpTunnelEntry 13 }

    atmpFAPrimaryHAAddress OBJECT-TYPE
	SYNTAX	DisplayString
	ACCESS	read-only
	STATUS	mandatory
	DESCRIPTION
	    "The Address of the Primary HA. This is known on the FA
	    and will be NULL if the tunnel is on the HA."
	::= { atmpTunnelEntry 14 }

    atmpFASecondaryHAAddress OBJECT-TYPE
	SYNTAX	DisplayString
	ACCESS	read-only
	STATUS	mandatory
	DESCRIPTION
	    "The  Address of the secondary HA. This is known only on the FA
	    and will be NULL if the tunnel is on the HA."
	::= { atmpTunnelEntry 15 }

    atmpFASsnStatusIndex OBJECT-TYPE
	SYNTAX	INTEGER
	ACCESS	read-only
	STATUS	mandatory
	DESCRIPTION
	    "The session status entry index. This is used to tie in the tunnel
	     with a mobile node. It is the same as ssnStatusIndex. This
	     is only known on the FA and will be 0 if the tunnel is on the HA."
	::= { atmpTunnelEntry 16 }

    atmpFAUserName OBJECT-TYPE
	SYNTAX	DisplayString
	ACCESS	read-only
	STATUS	mandatory
	DESCRIPTION
	    "The name of the mobile node. This is only known on the FA
	    and will be NULL if the tunnel is on the HA."
	::= { atmpTunnelEntry 17 }


    atmpInPkts OBJECT-TYPE
	SYNTAX	Counter
	ACCESS	read-only
	STATUS	mandatory
	DESCRIPTION
	    "The number of packets received on this tunnel from the peer
	    Agent.  Not valid for tunnels in local client mode. "
	::= { atmpTunnelEntry 18 }

    atmpInOctets OBJECT-TYPE
	SYNTAX	Counter
	ACCESS	read-only
	STATUS	mandatory
	DESCRIPTION
	    "The number of octets received on this tunnel from the peer
	    Agent.  Not valid for tunnels in local client mode. "
	::= { atmpTunnelEntry 19 }

    atmpInErrPkts OBJECT-TYPE
	SYNTAX	Counter
	ACCESS	read-only
	STATUS	mandatory
	DESCRIPTION
	    "The number of packets received on this tunnel from the peer
	    Agent that were dropped. Not valid for tunnels in local 
	    client mode. "
	::= { atmpTunnelEntry 20 }

    atmpOutPkts OBJECT-TYPE
	SYNTAX	Counter
	ACCESS	read-only
	STATUS	mandatory
	DESCRIPTION
	    "The number of packets sent on this tunnel to the peer Agent. Not
	    valid for tunnels in local client mode. "
	::= { atmpTunnelEntry 21 }

    atmpOutOctets OBJECT-TYPE
	SYNTAX	Counter
	ACCESS	read-only
	STATUS	mandatory
	DESCRIPTION
	    "The number of octets sent on this tunnel to the peer Agent. Not
	    valid for tunnels in local client mode. "
	::= { atmpTunnelEntry 22 }

    atmpOutErrPkts OBJECT-TYPE
	SYNTAX	Counter
	ACCESS	read-only
	STATUS	mandatory
	DESCRIPTION
	    "The number of packets dropped on this tunnel before sending
	    to peer Agent.  Not valid for tunnels in local client mode. "
	::= { atmpTunnelEntry 23 }

    atmpPktsForcedToFragment OBJECT-TYPE
	SYNTAX	Counter
	ACCESS	read-only
	STATUS	mandatory
	DESCRIPTION
	    "The number of packets forced to pre-fragment despite the DF
	    bit. Not valid for tunnels in local client mode. "
	::= { atmpTunnelEntry 24 }

    atmpPktsFailedFragment OBJECT-TYPE
	SYNTAX	Counter
	ACCESS	read-only
	STATUS	mandatory
	DESCRIPTION
	    "The number of packets that required to be fragmented but
	    were dropped because atmpAgentForceFragemtnation was disable 
	    and the DF bit was set. Not valid for tunnels in local client 
	    mode."
	::= { atmpTunnelEntry 25 }

END
