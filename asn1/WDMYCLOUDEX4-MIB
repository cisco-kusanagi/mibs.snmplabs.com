--
-- WDMYCLOUDEX4.mib
--

-- Copyright (c) 2013 WD Inc.,
-- Module Name: WDMYCLOUDEX4.mib
-- Abstract:
-- Defines the WDMYCLOUDEX4 MIBs .
--

	WDMYCLOUDEX4-MIB DEFINITIONS ::= BEGIN

	IMPORTS
		enterprises
			FROM RFC1155-SMI
		Integer32
			FROM SNMPv2-SMI
		OBJECT-TYPE
			FROM RFC-1212
		NOTIFICATION-TYPE
			FROM SNMPv2-SMI
		DisplayString
			FROM SNMPv2-TC;

--
--  OID definitions
--

	wd			OBJECT IDENTIFIER ::= { enterprises 5127 }
	productID	OBJECT IDENTIFIER ::= { wd 1 }
	projectID	OBJECT IDENTIFIER ::= { productID 1 }
	modelID 	OBJECT IDENTIFIER ::= { projectID 1 }
	submodelID	OBJECT IDENTIFIER ::= { modelID 1 }
	nasAgent	OBJECT IDENTIFIER ::= { submodelID 1 }


--
-- Node definitions
--
			wdmycloudex4AgentVer OBJECT-TYPE
				SYNTAX DisplayString
				MAX-ACCESS read-only
				STATUS current
				DESCRIPTION
					"Version information for the agent of SNMP of WDMYCLOUDEX4."
				::= { nasAgent 1 }

-- ============================================================================

--
-- system information definitions
--
			wdmycloudex4SoftwareVersion OBJECT-TYPE
				SYNTAX DisplayString
				MAX-ACCESS read-only
				STATUS current
				DESCRIPTION
					"The device software version."
				::= { nasAgent 2 }

			wdmycloudex4HostName OBJECT-TYPE
				SYNTAX DisplayString
				MAX-ACCESS read-only
				STATUS current
				DESCRIPTION
					"The device host name."
				::= { nasAgent 3 }


			wdmycloudex4FTPServer OBJECT-TYPE
				SYNTAX DisplayString
				MAX-ACCESS read-only
				STATUS current
				DESCRIPTION
					"Ftp Server status.
					1 : enable
					0 : disable
					"
				::= { nasAgent 5 }

			wdmycloudex4NetType OBJECT-TYPE
				SYNTAX DisplayString
				MAX-ACCESS read-only
				STATUS current
				DESCRIPTION
					"The Network type.
					0 : Workgroup
					1 : Active Directory"
				::= { nasAgent 6 }

			wdmycloudex4Temperature OBJECT-TYPE
				SYNTAX DisplayString
				MAX-ACCESS read-only
				STATUS current
				DESCRIPTION
					"The temperature of the system."
				::= { nasAgent 7 }

			wdmycloudex4FanStatus OBJECT-TYPE
				SYNTAX DisplayString
				MAX-ACCESS read-only
				STATUS current
				DESCRIPTION
					"The status of the fan0 & fan1."
				::= { nasAgent 8 }

-- ============================================================================

			wdmycloudex4VolumeTable OBJECT-TYPE
			SYNTAX SEQUENCE OF Wdmycloudex4VolumeEntry
			MAX-ACCESS not-accessible
			STATUS current
			DESCRIPTION
				"A table of active volumes on the NAS device."
			::= { nasAgent 9 }

			wdmycloudex4VolumeEntry OBJECT-TYPE
			SYNTAX Wdmycloudex4VolumeEntry
			MAX-ACCESS not-accessible
			STATUS current
			DESCRIPTION
				"An entry in the volume table."
			INDEX { wdmycloudex4VolumeNum }
			::= { wdmycloudex4VolumeTable 1 }

			Wdmycloudex4VolumeEntry ::=
			SEQUENCE {
				wdmycloudex4VolumeNum
					Integer32,
				wdmycloudex4VolumeName
					DisplayString,
				wdmycloudex4VolumeFsType
					DisplayString,
				wdmycloudex4VolumeRaidLevel
					DisplayString,
				wdmycloudex4VolumeSize
					DisplayString,
				wdmycloudex4VolumeFreeSpace
					DisplayString
			 }

			wdmycloudex4VolumeNum OBJECT-TYPE
			SYNTAX Integer32
			MAX-ACCESS read-only
			STATUS current
			DESCRIPTION
				"Instance number of the volume entry."
			::= { wdmycloudex4VolumeEntry 1 }

			wdmycloudex4VolumeName OBJECT-TYPE
			SYNTAX DisplayString
			MAX-ACCESS read-only
			STATUS current
			DESCRIPTION
				"The name of the volume."
			::= { wdmycloudex4VolumeEntry 2 }

			wdmycloudex4VolumeFsType OBJECT-TYPE
			SYNTAX DisplayString
			MAX-ACCESS read-only
			STATUS current
			DESCRIPTION
				"The type of file system of the volume.
				Example : ext3 or ext4"
			::= { wdmycloudex4VolumeEntry 3 }

			wdmycloudex4VolumeRaidLevel OBJECT-TYPE
			SYNTAX DisplayString
			MAX-ACCESS read-only
			STATUS current
			DESCRIPTION
				"The RAID level of the volume. (STANDARD LINEAR RAID0 RAID1 RAID5 RAID10 RAID5+SPARE)"
			::= { wdmycloudex4VolumeEntry 4 }

			wdmycloudex4VolumeSize OBJECT-TYPE
			SYNTAX DisplayString
			MAX-ACCESS read-only
			STATUS current
			DESCRIPTION
				"The size of the volume in bytes."
			::= { wdmycloudex4VolumeEntry 5 }

			wdmycloudex4VolumeFreeSpace OBJECT-TYPE
			SYNTAX DisplayString
			MAX-ACCESS read-only
			STATUS current
			DESCRIPTION
				"Free space on the volume in bytes."
			::= { wdmycloudex4VolumeEntry 6 }

-- ============================================================================

		wdmycloudex4DiskTable OBJECT-TYPE
			SYNTAX SEQUENCE OF Wdmycloudex4DiskEntry
			MAX-ACCESS not-accessible
			STATUS current
			DESCRIPTION
				"A table of physical disks attached to the NAS device."
			::= { nasAgent 10 }

		wdmycloudex4DiskEntry OBJECT-TYPE
			SYNTAX Wdmycloudex4DiskEntry
			MAX-ACCESS not-accessible
			STATUS current
			DESCRIPTION
				"An entry in the physical disk table."
			INDEX { wdmycloudex4DiskNum }
			::= { wdmycloudex4DiskTable 1 }

		Wdmycloudex4DiskEntry ::=
			SEQUENCE {
				wdmycloudex4DiskNum
					Integer32,
				wdmycloudex4DiskVendor
					DisplayString,
				wdmycloudex4DiskModel
					DisplayString,
				wdmycloudex4DiskSerialNumber
					DisplayString,
        		wdmycloudex4DiskTemperature
					DisplayString,
				wdmycloudex4DiskCapacity
					DisplayString
			 }

		wdmycloudex4DiskNum OBJECT-TYPE
			SYNTAX Integer32
			MAX-ACCESS read-only
			STATUS current
			DESCRIPTION
				"Instance number of the disk entry."
			::= { wdmycloudex4DiskEntry 1 }

		wdmycloudex4DiskVendor OBJECT-TYPE
			SYNTAX DisplayString
			MAX-ACCESS read-only
			STATUS current
			DESCRIPTION
				"The vendor of the disk drive."
			::= { wdmycloudex4DiskEntry 2 }

		wdmycloudex4DiskModel OBJECT-TYPE
			SYNTAX DisplayString
			MAX-ACCESS read-only
			STATUS current
			DESCRIPTION
				"The disk drive's model name."
			::= { wdmycloudex4DiskEntry 3 }

		wdmycloudex4DiskSerialNumber OBJECT-TYPE
			SYNTAX DisplayString
			MAX-ACCESS read-only
			STATUS current
			DESCRIPTION
				"The disk drive's serial number."
			::= { wdmycloudex4DiskEntry 4 }

		wdmycloudex4DiskTemperature OBJECT-TYPE
			SYNTAX DisplayString
			MAX-ACCESS read-only
			STATUS current
			DESCRIPTION
				"The centigrade temperature of this disk."
			::= { wdmycloudex4DiskEntry 5 }

		wdmycloudex4DiskCapacity OBJECT-TYPE
			SYNTAX DisplayString
			MAX-ACCESS read-only
			STATUS current
			DESCRIPTION
				"The capacity of the disk in GB."
			::= { wdmycloudex4DiskEntry 6 }


-- ============================================================================

		wdmycloudex4UPSTable OBJECT-TYPE
			SYNTAX SEQUENCE OF Wdmycloudex4UPSEntry
			MAX-ACCESS not-accessible
			STATUS current
			DESCRIPTION
				"A table of UPS attached to the NAS device."
			::= { nasAgent 11 }

		wdmycloudex4UPSEntry OBJECT-TYPE
			SYNTAX Wdmycloudex4UPSEntry
			MAX-ACCESS not-accessible
			STATUS current
			DESCRIPTION
				"An entry in the UPS table."
			INDEX { wdmycloudex4UPSNum }
			::= { wdmycloudex4UPSTable 1 }

		Wdmycloudex4UPSEntry ::=
			SEQUENCE {
				wdmycloudex4UPSNum
					Integer32,
				wdmycloudex4UPSMode
					DisplayString,
				wdmycloudex4UPSManufacturer
					DisplayString,
				wdmycloudex4UPSProduct
					DisplayString,
				wdmycloudex4UPSBatteryCharge
					DisplayString,
				wdmycloudex4UPSStatus
					DisplayString
			 }

		wdmycloudex4UPSNum OBJECT-TYPE
			SYNTAX Integer32
			MAX-ACCESS read-only
			STATUS current
			DESCRIPTION
				"Instance number of the UPS entry."
			::= { wdmycloudex4UPSEntry 1 }

		wdmycloudex4UPSMode OBJECT-TYPE
			SYNTAX DisplayString
			MAX-ACCESS read-only
			STATUS current
			DESCRIPTION
				"The mode of the UPS "
			::= { wdmycloudex4UPSEntry 2 }

		wdmycloudex4UPSManufacturer OBJECT-TYPE
			SYNTAX DisplayString
			MAX-ACCESS read-only
			STATUS current
			DESCRIPTION
				"The manufacturer of the UPS."
			::= { wdmycloudex4UPSEntry 3 }

		wdmycloudex4UPSProduct OBJECT-TYPE
			SYNTAX DisplayString
			MAX-ACCESS read-only
			STATUS current
			DESCRIPTION
				"The product name of the UPS."
			::= { wdmycloudex4UPSEntry 4 }

		wdmycloudex4UPSBatteryCharge OBJECT-TYPE
			SYNTAX DisplayString
			MAX-ACCESS read-only
			STATUS current
			DESCRIPTION
				"The battery charge of the UPS."
			::= { wdmycloudex4UPSEntry 5 }

		wdmycloudex4UPSStatus OBJECT-TYPE
			SYNTAX DisplayString
			MAX-ACCESS read-only
			STATUS current
			DESCRIPTION
				"The status of this UPS."
			::= { wdmycloudex4UPSEntry 6 }



-- ============================================================================
--
--  Notifications
--

	notifyEvts OBJECT IDENTIFIER ::= { nasAgent 200 }

	notifyPasswdChanged        NOTIFICATION-TYPE
    STATUS      current
    DESCRIPTION
        "An indication that the Administrator's password has been changed."
    ::= { notifyEvts 1 }

    notifyFirmwareUpgraded     NOTIFICATION-TYPE
    STATUS      current
    DESCRIPTION
        "An indication that firmware has been upgraded."
    ::= { notifyEvts 2 }

    notifyNetworkChanged        NOTIFICATION-TYPE
    STATUS      current
    DESCRIPTION
        "An indication that the network settings has been changed."
    ::= { notifyEvts 3 }

    notifyTemperatureExceeded        NOTIFICATION-TYPE
    STATUS      current
    DESCRIPTION
        "An indication that system temperature has exceeded."
    ::= { notifyEvts 4 }







--              ******************************************************

--              ******************************************************


	END

--
-- WDMYCLOUDEX4.mib
--
