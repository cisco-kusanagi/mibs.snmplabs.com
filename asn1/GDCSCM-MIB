-- Copyright 1993-1996 General DataComm Ind., Inc. All Rights Reserved.
--
-- Reproduction of this document is authorized on condition that the
-- foregoing copyright notice is included. This General DataComm, GDC,
-- SNMP Management Information Base Specification embodies GDCs'
-- confidential and proprietary intellectual property. GDC retains all
-- title and ownership in the Specification, including any revisions.
--
-- It is GDCs intent to encourage the widespread use of this Specification
-- in connection with the management of GDC's products. GDC grants vendors,
-- end-users, and other interested parties a non-exclusive license to use
-- this Specification in connection with the management of GDC's products.
--
-- This Specification is supplied "AS IS," and GDC makes no warranty,
-- either expressed or implied, as to the use operation, condition, or
-- performance of the Specification.

-- Revision History
-- Version   Date	Name		Description
-- 1.00      02-Jun-94  S. Zezima	Initial Revision  
-- 2.00A     18-Aug-94  S. Zezima       Added MIB variables scmReset
--					and scmDefaultConfig. Completely
--					removed scmSerialNumber and
--					scmOwnSlot, they were commented
--					out of the previous version
--					because the SCM is now in the 
--					scmNodeTable and that information
--					can be retrieved there. Added ltu(2)
--					to the scmNodeType MIB variable.
-- 2.00B     19-Aug-94  S. Zezima       Changed the IMPORTS
-- 2.00C     23-Aug-94  S. Zezima       Changed scmDefaultConfig to not
--					support factoryReset and changed
--					the name of the appl default 
--					configuration.  Also changed the 
--					range for scmSlotNumber from 1-32
-- 2.00D     26-Aug-94  S. Zezima       The scmReset and scmDefaultConfig
--					descriptions updated to indicate
--					that the reset is a hard reset.
-- 2.00E     09-Nov-94  M. Cyr          Added NEs to scmNodeType variable
-- 2.00F     09-Dec-94  W. Richards	Changed scmPowerStatus to scmPowerAvail,
--					added scmPowerConsum.
-- 2.00G     31-Mar-95  E. Moreno-Leon  Change product name from 720d1 to 720g1 and 720d2 to 720g2
-- 2.00H     22-Jun-95  E. Moreno-Leon  Added 702g2 product
-- 2.00I     24-Jul-95  C. Amorossi     Added nms510 to scmNodeType Enums
-- 2.00J     15-Nov-95  C. Amorossi     Added 4 to scmNodeLevel enums
-- 2.00K     21-Nov-95  E. Moreno-Leon  Added sc5034 and dualV34 to scmnodeType Enums
-- 2.00L     16-Jan-96  E. Moreno-Leon  Added SC613 support
-- 2.00M     02-Jan-96  C. Amorossi     Added sc5553 to scmNodeType Enums
-- 2.00N     31-Jan-96  E. Moreno-Leon  Added SC611 and DC621 and NMS553 support
-- 2.00P     05-Feb-96  W. Meltzer      Added scmPowerSupplyTrap
-- 2.00R     21-Feb-96  E. Moreno-Leon  Added HDSL710D2 and HDSL700G2RP support
-- 2.00S     13-Mar-96  E. Moreno-Leon  Added HDSL710D2RP, HDSL720G2RP and HDSL730D2RP support
-- 2.00T     28-May-96  C. Amorossi     Added mp7002 and mp7616 to scmNodeType Enums
--					Added scmCannedConfig
--           14-Jun-96  D. Baylis       Changed name mp7616(30) enum tp uas7616(30) [ver. still 2.00T] 
-- 2.00U     14-Jun-96  D. Baylis       Changed name mp7616(30) enum tp uas7616(30) 
--                                      Added sc521, sc5002, dc610NZ enum to scmnodeType and 
--                                      corrected description on scmNodeLevel
-- 2.00V     18-Jul-96  C. Amorossi     Added mp7001 to scmNodeType Enums and 
--					scmSetNetworkElementRealTime
-- 2.00W     28-Aug-96  D. Baylis       Updated Description on object scmNodeAlarmScan
--                      D. Baylis       Added scmDownLoadCode object
-- 3.00A     29-Aug-96  M. Cyr		Added scmOperatingMode,scmAliveTrapInterval,
--					scmRedundantTimeout and scmAliveTrap all for Redundancy.
--					Added scmRedundancyTable containing just ip address for now
--                                      (objects based on scinstance)
-- 3.00B     11-Oct-96  C. Amorossi     Added scmTelnet object
-- 3.00C     07-Nov-96  D. Baylis       Added T1 hdsl products to scmNodeType Enums  
-- 3.00D     07-Nov-96  M. Cyr          Added scmRedundancySwitch to scmredundancy table.
-- 3.00E     20-Nov-96  D. Baylis       Added mfs7616(44) and uas7616(45) to scmNodeType
--					Chagned uas7616(30) to nz7616(30)
-- 3.00F     21-Nov-96  D. Baylis       Changed enum names to uas7616NZ(30), uas7616TA(44)
-- 3.00G     05-Dec-96  C. Amorossi     Added scmConfigChksumTrap
-- 3.00H     07-Jan-97  D. Baylis       Added product sc553(46) to scmNodeType
-- 3.00J     09-May-97  D. Baylis       Added notlocallymanaged(47)
-- 3.00K     22-Oct-97  D. Baylis       Changed scmMasterTimeout range to 15-100
-- 3.00M     23-Oct-97  C. Amorossi     Added scmTextAlarmTraps, scmAlarmText, scmAlarmTextTrap
-- 3.00N     06-Jan-98  C. Amorossi     Added product uas7624(48) to scmNodeType
-- 3.00P     27-Jan-98  C. Amorossi     Added product hdsl700AG2, hdsl700AG2NZ, uas7626 to scmNodeType
-- 3.00Q     02-Feb-98  C. Amorossi     Added product ntu2m to scmNodeType
-- 3.00R     09-Mar-98  C. Amorossi     Added product uas7022, gt128, gt128NZ to scmNodeType
-- 3.00S     11-May-98  C. Amorossi     Added product sc5034Exp, gt1000, gt2000, scT3 to scmNodeType
-- 3.00T     29-Jul-98  C. Amorossi     Added product uas7722 to scmNodeType and changed gt1000 to
--					gt1030 and gt2000 to gt2030
-- 3.00U     17-Sep-98  C. Amorossi     Changed enum sc5034Exp tp sc5090
-- 3.00V     12-Oct-98  C. Amorossi     Added product sc5034A to scmNodeType
-- 3.00W     16-Oct-98  C. Amorossi     Added products gt1020 and gt2020 to scmNodeType
-- 3.10A     26-Oct-98  C. Amorossi     Added product sc711D2(64) to scmNodeType and changed
--					scT3 to sc800T3
-- 3.10B     14-Dec-98  C. Amorossi     Made scmDate and scmTime obsolete
-- 3.10C     13-Jan-99  C. Amorossi     Added product sc202(65) to scmNodeType
-- 3.10D     03-Feb-99  J. Bassett      Added product sc521A(66) to scmNodeType
-- 3.10E     02-May-00  J. Bassett      Added product uas7722xr(67) and gt1030xr(68) 
--                                      to scmNodeType
-- 3.10F     21-Nov-00  J. Bassett      Added product uas780g2(69) and gt1830(70) to scmNodeType
-- 3.10G     27-Mar-01  V. Yuschuk      Added product sc5506(71) to scmNodeType
-- 3.10H     6/7/2001   V. Yuschuk      Added product sc5516(72) to scmNodeType

GDCSCM-MIB DEFINITIONS ::= BEGIN

IMPORTS
	enterprises,Gauge,IpAddress	FROM RFC1155-SMI
	TRAP-TYPE			FROM RFC-1215
	OBJECT-TYPE			FROM RFC-1212
	DisplayString			FROM RFC1213-MIB
	SCinstance			FROM GDCMACRO-MIB;



gdc		OBJECT IDENTIFIER ::= { enterprises 498 }
sc              OBJECT IDENTIFIER ::= { gdc 3 }
scmSystem	OBJECT IDENTIFIER ::= { sc 6 }


-- groups in the SCM MIB module

scmVersion   	OBJECT IDENTIFIER ::= { scmSystem 1 }
scmMaster	OBJECT IDENTIFIER ::= { scmSystem 2 }
scmNode		OBJECT IDENTIFIER ::= { scmSystem 3 }
scmShelf	OBJECT IDENTIFIER ::= { scmSystem 4 }
scmAlmTrap	OBJECT IDENTIFIER ::= { scmSystem 5 }
scmRedundancy	OBJECT IDENTIFIER ::= { scmSystem 6 }

--
-- The Version group
--	Implementation of this group is mandatory for all systems.
--	The information in this group provides the version information
--      for the MIB.  
--

scmMIBVersion		OBJECT-TYPE
	SYNTAX	DisplayString (SIZE (5))
	ACCESS	read-only
	STATUS  mandatory
	DESCRIPTION
		"The version number of the MIB, to allow products to 
		know which MIB is being supported.  The version number
		will be x.yzT where x is a major revision (1-9), y is a minor
		revision(0-9), z is a typo revision (0-9) and T indicates the
		MIB is still a test revision(A-Z).  When a release is complete
		no T should exist."
	::= { scmVersion 1 }

scmBootVersion          OBJECT-TYPE
	SYNTAX	DisplayString (SIZE (5))
	ACCESS	read-only
	STATUS  mandatory
	DESCRIPTION
		"The version number of the Boot Software, to allow products to 
		know which Boot Software is being supported.  The version number
		will be x.yzT where x is a major revision (1-9), y is a minor
		revision(0-9), z is a typo revision (0-9) and T indicates the
		Boot Software is still a test revision(A-Z).  When a release 
		is complete no T should exist."
	::= { scmVersion 2 }

scmApplVersion          OBJECT-TYPE
	SYNTAX	DisplayString (SIZE (5))
	ACCESS	read-only
	STATUS  mandatory
	DESCRIPTION
		"The version number of the Application Software, to allow 
		products to know which Software is being supported.  The 
		version number will be x.yzT where x is a major revision (1-9),
		 y is a minor revision(0-9), z is a typo revision (0-9) and T 
		indicates the Software is still a test revision(A-Z).  
		When a release is complete no T should exist."
	::= { scmVersion 3 }

--
-- The Master group
--	Implementation of this group is mandatory for all systems.
--	The information in this group must be entered by the network
--	manager on the SNMP management station.
--

scmMasterTimeout	OBJECT-TYPE
	SYNTAX	INTEGER (15..100)
	ACCESS	read-write
	STATUS	mandatory
	DESCRIPTION
		"The Management bus timeout defined as the time 
		between the last character being transmitted
		to the Network Element and the first character
		being received.  This variable is defined in
		milliSeconds.
		The default timeout is 50.0 mS."
	::= { scmMaster 1 }

scmAlarmScan		OBJECT-TYPE
	SYNTAX	INTEGER {
			alarmScanOn(1),
			alarmScanOff(2)
		}
	ACCESS	read-write
	STATUS	mandatory
	DESCRIPTION
		"This is used to turn on and off the alarm scan feature
		to the Network Elements connected off of this SCM. If the alarm 
		scan is turned off no Network Elements will be scanned for
		alarms and therefore no alarms will be sent to the controller.
		If alarms occur when the scan is off, they will be discarded."
	::= { scmMaster 2 }

scmTime			OBJECT-TYPE
	SYNTAX	DisplayString (SIZE (8))
	ACCESS  read-write
	STATUS  obsolete
	DESCRIPTION
		"This is used to read or set the time of the real-time
		clock in the SCM.  The format of the time will be
		hh:mm:ss.  Where hh is the hour (01-24) in 24 hour
		format, mm is minutes (00-59) and  ss is seconds (00-59)"
	::= { scmMaster 3 }

scmDate			OBJECT-TYPE
	SYNTAX	DisplayString (SIZE (8))
	ACCESS  read-write
	STATUS  obsolete
	DESCRIPTION
		"This is used to read or set the date of the real-time
		clock in the SCM.  The format of the date will be
		mm-dd-yy.  Where mm is month (01-12), dd is the day (01-31),
		and yy is the year (00-99)."
	::= { scmMaster 4 }

scmRedundant		OBJECT-TYPE
	SYNTAX	INTEGER {
			redundant(1),
			primary(2)
		}
	ACCESS	read-only
	STATUS  mandatory
	DESCRIPTION
		"This is used to read the current state of a SCM"
	::= { scmMaster 5 }

scmShelfNumber		OBJECT-TYPE
	SYNTAX	INTEGER {
			oneShelf(1),
			twoShelf(2)
		}
	ACCESS  read-only
	STATUS  mandatory
	DESCRIPTION
		"This indicates the number of shelves in the system.  If it
		is a one shelf system, then a maximum of 16 Network Elements
		(including any SCM's). If it is a two shelf system, then a 
		maximum	of 32 Network Elements (including any SCM's) can exist."
	::= { scmMaster 6 }

scmReset		OBJECT-TYPE
	SYNTAX	INTEGER {
			normal(1),
			reset(2)
		}
	ACCESS	read-write
	STATUS	mandatory
	DESCRIPTION
		"This is used to reset the SCM card in the shelf.  The SCM will
		respond to the command and then perform the reset.  During the
		time the SCM resets, the SCM will not respond.  The SCM reset 
		is a hard reset, therefore a coldStart TRAP will be received.

		normal - This is the value that will be returned whenever this
		variable is read.

		reset - This value can be set to perform the reset."
	::= { scmMaster 7 }

scmPowerAvail		OBJECT-TYPE
	SYNTAX	Gauge
	ACCESS	read-only
	STATUS	mandatory
	DESCRIPTION
		"This is used to determine the total amount of power available to the
		 shelves."
	::= { scmMaster 8 }

scmDefaultConfig	OBJECT-TYPE
	SYNTAX	INTEGER {
			normal(1),
			factoryApplDefault(2)
		}
	ACCESS	read-write
	STATUS	mandatory
	DESCRIPTION
		"This is used to allow the NonVolatile Configuration to 
		be set to a factory default state.  The SCM will perform
		a reset to make the default configuration take affect. 
		The SCM reset is a hard reset, therefore a coldStart TRAP
		will be received.

		factoryApplDefault - This is used to clear all of Non-Volatile
		memory associated with the application.  If this option is 
		selected the Node table will be emptied and the Community
		Name Table will only contain 'public' as readOnly and the Trap
		Table will be empty."
	::= { scmMaster 9 }

scmPowerConsum		OBJECT-TYPE
	SYNTAX	Gauge
	ACCESS	read-only
	STATUS	mandatory
	DESCRIPTION
		"This is used to determine the amount of power consumed by all the 
		 managed network elements in the shelves managed by this SCM."
	::= { scmMaster 10 }

scmCannedConfig		OBJECT-TYPE
	SYNTAX	INTEGER {
			cannedConfigNone(1),
			cannedConfig1(2),
			cannedConfig2(3),
			cannedConfig3(4),
			cannedConfig4(5),
			cannedConfig5(6),
			cannedConfig6(7),
			cannedConfig7(8)
		}
	ACCESS	read-only
	STATUS  mandatory
	DESCRIPTION
		"This reads the dip switches and reports the current
		 canned configuration setting."
	::= { scmMaster 11 }


scmSetNetworkElementRealTime   OBJECT-TYPE
	SYNTAX  INTEGER (1..2147483647)
	ACCESS  read-write
	STATUS  mandatory
	DESCRIPTION
		"Number of seconds from midnight Dec 31, 1969.
		 A set of this object will be broadcasted to every
		 network element in the shelf.
		 A get of this object will always return a 1."
	::= { scmMaster 12 }

scmDownLoadCode	OBJECT-TYPE
	SYNTAX	INTEGER {
			enable(1),
			disable(2)
		}
	ACCESS	read-write
	STATUS  mandatory
	DESCRIPTION
		"This object determines if TFTP (Trivial File Transfer Protocol)
		code downloading to the SCM or any NEs is permitted.  
		When management sets disable(2) any attempt to place the SCM
		in boot mode or download code to NEs will result in an TFTP
		error response indicating that the download request has been denied.
		The factory default is enable(1). "
	::= { scmMaster 13 }

scmOperatingMode	OBJECT-TYPE
	SYNTAX	INTEGER {
			active(1),
			standby(2),
			sleep(3)
		}
	ACCESS	read-write
	STATUS	mandatory
	DESCRIPTION
		"This object determines the operating mode of an SCM as it pertains to the management
		 buss.  
			Active - indicates the SCM is to possess full control of the shelf and its
			elements.  This is the default for a primary SCM.
			Standby - indicates the SCM is operationg in redundant mode.  This state applies
			only to an SCM whose dip switch is set to redundant.
			Sleep - indicates the primary SCM has been forced off the management buss.
			This value can never be set by network management and only pertains to an
			SCM whose dip switch is set to primary."
	::= { scmMaster 14 }

scmAliveTrapInterval	OBJECT-TYPE
	SYNTAX INTEGER	(0..60)
	ACCESS read-write
	STATUS mandatory
	DESCRIPTION
		"This object is used to set the time period, represented in minutes, in which the 
		 SCM will send an SNMP TRAP to the manager to indicate that it is alive.  No trap is sent
		 if the value is zero or if the scmOperatingMode is set to Sleep.  The default value
		 is zero for this object."	
	::= { scmMaster 15 }
  
scmRedundantTimeOut	OBJECT-TYPE
	SYNTAX INTEGER (0..300)
	ACCESS read-write
	STATUS mandatory
	DESCRIPTION
		"This object is used to set the time period, represented in seconds, in which the
		 redundant SCM will wait after not receiving express polls from the primary SCM before 
		 it takes contol of the management buss.  When set to zero, the redundant SCM will 
		 ignore the loss of express polls.  The default is zero."
	::= { scmMaster 16 }
	
scmTelnet	OBJECT-TYPE
	SYNTAX	INTEGER {
			enable(1),
			disable(2)
		}
	ACCESS	read-write
	STATUS  mandatory
	DESCRIPTION
		"This object determines if telnet to the SCM is permitted.
		When management sets disable(2) all attempts to telnet to the
		SCM will be rejected.
		The factory default is enable(1). "
	::= { scmMaster 17 }

scmTextAlarmTraps OBJECT-TYPE
	SYNTAX	INTEGER {
			disable(1),
			enable(2)
		}
	ACCESS	read-write
	STATUS  mandatory
	DESCRIPTION
		"This object changes the format of alarm traps from the
		managed network elements.  If this object is set to
		disable then the SCM sends cmnAlarmStatusTrap traps. If
		this is set to enable and the network element supports
		text-style traps then the SCM sends scmAlarmTextTrap traps.
		The factory default is disable(1). "
	::= { scmMaster 18 }


--
-- The Node group
--     Implementation of this group is mandatory for all systems.
--     The information in this group must be entered by the network
--     manager on the SNMP management station.
--

scmNodeTable	OBJECT-TYPE
	SYNTAX	SEQUENCE OF ScmNodeEntry
	ACCESS	not-accessible
	STATUS	mandatory
	DESCRIPTION
		"A table that contains information about the nodes in
		the system.  

		The SCM node is a special node in the table.  The SCM
		itself adds the node to the table and it cannot be 
		deleted by setting the status to invalid.  The configuration
		checksum of the SCM is this node table (minus the SCM's
		configuration checksum), the community name table, the 
		trap table and any ip addresses that are inputed through
		the terminal interface."
	::= { scmNode 2 }


scmNodeEntry	OBJECT-TYPE
	SYNTAX	ScmNodeEntry
	ACCESS	not-accessible
	STATUS	mandatory
	DESCRIPTION
		"A list of information for each node in the system.  To create
		an entry, must give the type field. "
	INDEX	{ scmNodeIndex }
	::= { scmNodeTable 1 }


ScmNodeEntry ::=
	SEQUENCE {
		scmNodeIndex
			SCinstance,
		scmNodeType
			INTEGER,
		scmNodeConfigCs
			OCTET STRING,
		scmNodeStatus
			INTEGER,
		scmNodeAlarmScan
			INTEGER,
		scmNodeLevel
			INTEGER,
		scmNodeConfigChecksumStatus
			INTEGER,
		scmNodeCurrentAlarms
			OCTET STRING,
		scmNodeSerialNumber
			DisplayString,
		scmNodeAdminStatus
			INTEGER,
		scmNodeOperStatus
			INTEGER
	}


scmNodeIndex	OBJECT-TYPE
	SYNTAX	SCinstance
	ACCESS	read-only
	STATUS	mandatory
	DESCRIPTION
		"The value indicates the node number for which this
		entry contains management information.  The Node Index
		is based off of the IFindex in MIB-II.  The Node Index
		value is used to indicate the slot, line and drop of 
		the node that is being addressed.  
		
		The index is defined as: ssllddxx
		where ss is from 1-32, ll from 1-128 and dd from 0-31.  The
		xx is always zero in the Node table, but can be used by a 
		network element type in their MIB."
	::= { scmNodeEntry 1 }


scmNodeType	OBJECT-TYPE
	SYNTAX	INTEGER {
			vf288(1),
			sc5001(2),
			sc5520(3),
			datx2011(4),
			nms520(5),
			sc700G2(6),
			sc700G3(7),
			dc730D1(8),
			dc730D2(9),
			dc720G1(10),
			dc720G2(11),
			sc616(12),
			dc610(13),
			dc612(14),
			sc702G2(15),
			nms510(16),
			sc5034(17),
			scdualV34(18),
			sc613(19),
			sc5553(20),
			sc611(21),
			dc621(22),
			sc710d2(23),
			sc700g2RP(24),
			nms553(25),
			sc710d2rp(26),
			dc720g2rp(27),
			dc730d2rp(28),
                        mp7002(29), 
                        uas7616NZ(30),	 
			scm(31),			
			sc521(32),
			sc5002(33),			
			dc610NZ(34),
			mp7001(35),
			sc701T2(36),
			sc701T2RP(37),
			dc721T1(38),
			dc721T2(39),
			dc721T2RP(40),
			dc731D1(41),
			dc731D2(42),
			dc731D2RP(43),
                        uas7616TA(44),  -- Terminal Adaptor 
                        uas7616(45),	-- Standard
			sc553(46),	
			notlocallymanaged(47),	
			uas7624(48),
			hdsl700AG2(49),
			hdsl700AG2NZ(50),
			uas7626(51),
			ntu2m(52),
			uas7022(53),
			gt128(54),
			gt128NZ(55),
			sc5090(56),
			gt1030(57),
			gt2030(58),
			sc800T3(59),
			uas7722(60),
			sc5034A(61),
			gt1020(62),
			gt2020(63),	
			sc711D2(64),
			sc202(65),
                        sc521A(66),
                        uas7722xr(67),
                        gt1030xr(68),
			uas780g2(69),
			gt1830(70),
                        sc5506(71),
                        sc5516(72)
		}
	ACCESS	read-write
	STATUS	mandatory
	DESCRIPTION
		"The value indicates the type of node located at the Node
		index."
	::= { scmNodeEntry 2 }

scmNodeConfigCs	OBJECT-TYPE
	SYNTAX	OCTET STRING (SIZE(2))
	ACCESS	read-only
	STATUS	mandatory
	DESCRIPTION
		"The value indicates the configuration checksum of the node.  It
		is not a required value when adding an entry to a table.  A 
		default value of 0(zero) will be used when the checksum is 
		unknown. "
	::= { scmNodeEntry 3 }

scmNodeStatus  OBJECT-TYPE
	SYNTAX  INTEGER {
			valid(1),
			invalid(2)
	}
	ACCESS  read-write
	STATUS  mandatory
	DESCRIPTION
		"The status of the entry.  If read and the entry
		exists, valid(1) will always be returned.

		Invalid entries will be removed from the table."
	::= { scmNodeEntry 4 }

scmNodeAlarmScan	OBJECT-TYPE
	SYNTAX	INTEGER {
			on(1),
			off(2)
		}
	ACCESS	read-write
	STATUS	mandatory
	DESCRIPTION
		"This is used to turn on and off the alarm scan feature
		for a particular Network Element connected off of this SCM. If the alarm 
		scan is turned off the Network Element will not be scanned for
		alarms and therefore no alarms will be sent to the controller for that NE.
		If alarms occur when the scan is off, they will be discarded."
	::= { scmNodeEntry 5 }

scmNodeLevel	OBJECT-TYPE
	SYNTAX	INTEGER (1..4)
	ACCESS	read-write
	STATUS	mandatory
	DESCRIPTION
		"The value indicates the level that the node exists at.  Nodes
		that are located in the shelf are usually defined as level 1.
		
		The level is used to determine the time the SCM allows for the
		node to respond.  The higher the level the longer the timeout.
		
		The timeout is defined as follows:
			2 * (level - 1) + 2 Second"
	::= { scmNodeEntry 6 }

scmNodeConfigChecksumStatus	OBJECT-TYPE
	SYNTAX	INTEGER {
			correct (1),
			incorrect (2)
			}
	ACCESS	read-only
	STATUS	mandatory
	DESCRIPTION
		"The value indicates whether the checksum in the NE matches that
                 in the table the last time the information was received from
		 a NE. The NE will send this information on power-up."
	::= { scmNodeEntry 7 }

scmNodeCurrentAlarms OBJECT-TYPE
	SYNTAX	  OCTET STRING (SIZE (1..255))
	ACCESS	  read-only
	STATUS	  mandatory
	DESCRIPTION   
		"Reads the alarm information current in the network element. 
		 The number of bytes in the alarm data is dependent on the 
		 type of network element that is being addressed."
	::= { scmNodeEntry 8 }

scmNodeSerialNumber OBJECT-TYPE
	SYNTAX	  DisplayString (SIZE (16))
	ACCESS	  read-write
	STATUS	  mandatory
	DESCRIPTION
		"This is used to get the serial number of the network
		 element.  This is also used to set the address of the unit 
		 by it's serial number in the case of remote units." 
	::= { scmNodeEntry 9 }

scmNodeAdminStatus  OBJECT-TYPE
	SYNTAX	  INTEGER	{
				up(1),
				down(2)
	}
	ACCESS	  read-write
	STATUS	  mandatory
	DESCRIPTION
		"This is used to set the desired state of the network element."
	::= { scmNodeEntry 10 }

scmNodeOperStatus  OBJECT-TYPE
	SYNTAX	  INTEGER	{
				up(1),
				down(2)
	}
	ACCESS	  read-only
	STATUS	  mandatory
	DESCRIPTION
		"The current operational statue of the network element."
	::= { scmNodeEntry 11 }

--
-- The Express Poll group
--     Implementation of this group is mandatory for all systems.
--     The information in this group is read by the management station
--     to know where elements exist in a shelf.
--

scmSlotTable	OBJECT-TYPE
	SYNTAX	SEQUENCE OF ScmSlotEntry
	ACCESS	not-accessible
	STATUS	mandatory
	DESCRIPTION
		"A table that contains information about the state of
		the Network Elements in the shelf."
	::= { scmShelf 1 }


scmSlotEntry	OBJECT-TYPE
	SYNTAX	ScmSlotEntry
	ACCESS	not-accessible
	STATUS	mandatory
	DESCRIPTION
		"A list of information for each Network Element in the
		shelf."
	INDEX	{ scmSlotNumber }
	::= { scmSlotTable 1 }


ScmSlotEntry ::=
	SEQUENCE {
		scmSlotNumber
		INTEGER,
		scmSlotState
		INTEGER
	}


scmSlotNumber	OBJECT-TYPE
	SYNTAX	INTEGER (1..32)
	ACCESS	read-only
	STATUS	mandatory
	DESCRIPTION
		"The value indicates the slot from which to read the current
		state."
	::= { scmSlotEntry 1 }

scmSlotState	OBJECT-TYPE
	SYNTAX	INTEGER {
			activestate(1),
			inactivestate(2),
			activeerrorstate(3)
		}
	ACCESS	read-only
	STATUS	mandatory
	DESCRIPTION
		"The state of the Network Element in the shelf. Active means
		that all commands to and from the Network Element have had
		correct responses with no communication errors.  Inactive 
		means that the Network Element does not respond to any commands.
		Active with Errors means that responses are received, but
		communication errors are occuring."
	::= { scmSlotEntry 2 }



scmAlarmText    OBJECT-TYPE
	SYNTAX	DisplayString (SIZE (100))
	ACCESS	read-only
	STATUS  mandatory
	DESCRIPTION
		"The variable associated with scmAlarmTextTrap.  A get
		 will always return a null string."
	::= { scmSystem 7 } 

scmAlarmTrap	TRAP-TYPE
	ENTERPRISE	scmSystem
	VARIABLES	{ scmNodeCurrentAlarms }
	DESCRIPTION
		"This is the Alarm Trap. This trap is sent whenever a network 
		 element detects a change in its alarm information."
	::= 1
		
scmExpressPollTrap	TRAP-TYPE
	ENTERPRISE	scmSystem
	VARIABLES	{ scmSlotState }
	DESCRIPTION
		"This is the Express Poll Trap.  It will be used to indicate 
		 a state change in a slot in the shelf."
	::= 2
		
scmPowerSupplyTrap      TRAP-TYPE
        ENTERPRISE      scmSystem
        VARIABLES       { scmPowerAvail }
        DESCRIPTION
                "This is the Power Supply Trap.  It will be used to indicate
                 a change in the amount of power available to the shelf.
                 This change will occur when a power supply card has either
                 failed or has been physically replaced."
        ::= 3

scmAliveTrap		TRAP-TYPE
	ENTERPRISE	scmSystem
	VARIABLES	{ scmOperatingMode,scmAliveTrapInterval }
	DESCRIPTION
		"This is the SCM Alive Trap.  It is used to notify the manager every N minutes that it 
		 is still alive."
	::= 4

scmConfigChksumTrap	TRAP-TYPE
	ENTERPRISE	scmSystem
	VARIABLES	{ scmNodeIndex }
	DESCRIPTION
		"This is the configuration checksum change trap.  When the 
		 configuration checksum of a network element changes then
		 the SCM sends this trap to notify the manager of the
		 change."
	::= 5


scmAlarmTextTrap TRAP-TYPE
	ENTERPRISE scmSystem
    	VARIABLES { scmAlarmText }
    	DESCRIPTION
        	"This trap is sent when an alarm is received from a
                 network element and scmTextAlarmTraps is set to 
                 enable and the network element supports text-style
                 traps.  The variable is scmAlarmText which is a display
		 string of the form: NNN: Slot x Line y Drop z alarm name
                 is Active (or Inactive), where NNN is the network element
	         name which corresponds to scmNodeType. Example:
	
  		 SC553: Slot 2 Line 1 Drop 0 DCD Loss Alarm is Active"
    	::= 6


--
--	The Redundancy group
--		Implementation of this group is mandatory for all systems. The information in this group
--		provides information about the SCM as it pertains to redundancy.
--

scmRedundancyTable	OBJECT-TYPE
	SYNTAX		SEQUENCE OF ScmRedundancyEntry
	ACCESS		not-accessible
	STATUS		mandatory
	DESCRIPTION
			"A table that contains information about the SCM's in the system as they pertain
			 to redundancy."
	::= { scmRedundancy 2 }

scmRedundancyEntry	OBJECT-TYPE
	SYNTAX		ScmRedundancyEntry
	ACCESS		not-accessible
	STATUS		mandatory
	DESCRIPTION
		"A list of information for each SCM in the shelf as it pertains to redundancy."
	INDEX		{ scmRedundancyIndex }
	::= { scmRedundancyTable 1 }

ScmRedundancyEntry ::= 
	SEQUENCE {
			scmRedundancyIndex	SCinstance,
			scmEtherIPAddress	IpAddress,
			scmPPPIPAddress		IpAddress,
			scmRedundancySwitch	INTEGER
		}

scmRedundancyIndex	OBJECT-TYPE
	SYNTAX		SCinstance
	ACCESS		read-only
	STATUS		mandatory
	DESCRIPTION
			"The value indicates the addressing/indexing method of accessing the objects in 
			 this table.  The SCinstance represents the shelf's Slot, Line, Drop and 
			 interface address. Drop and interface will always be zero for an SCM."
	::= { scmRedundancyEntry 1 }

scmEtherIPAddress	OBJECT-TYPE
	SYNTAX		IpAddress
	ACCESS		read-only
	STATUS		mandatory
	DESCRIPTION	
			"This object is used to obtain the Ethernet IP Address of the SCM in ###.###.###.###
			 format."
	::= { scmRedundancyEntry 2 }

scmPPPIPAddress	OBJECT-TYPE
	SYNTAX		IpAddress
	ACCESS		read-only
	STATUS		mandatory
	DESCRIPTION	
			"This object is used to obtain the PPP IP Address of the SCM in ###.###.###.###
			 format."
	::= { scmRedundancyEntry 3 }

scmRedundancySwitch	OBJECT-TYPE
	SYNTAX	INTEGER {
			redundant(1),
			primary(2)
		}
	ACCESS	read-only
	STATUS		mandatory
	DESCRIPTION	
		"This is used to read the current state of the redundant switch on a SCM."
	::= { scmRedundancyEntry 4 }





END
