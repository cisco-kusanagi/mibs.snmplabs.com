ACC-MIB DEFINITIONS ::= BEGIN
-- Title: ACC MIB 
-- Edition: "8.0.3 : August 22, 1995" 
-- By: The ACC MIB group (mib@acc.com)
--   MIB to manage ACC Bridge/Routers up to and including
--   Software Release 8.0.3
-- 
-- 
-- This is the archival version of the enterprises MIB for
-- all products produced by Advanced Computer Communications
-- (ACC).  In this version several enumerated INTEGERs have
-- been converted to plain INTEGER because they use zero as
-- an enumeration.  Some MIB compilers (such as SunNet
-- Manager) complain about this use of zero, but will use the
-- information anyway.  If you would like to obtain a copy of
-- this mib with enumerated values of zero, then contact ACC
-- directly at (805) 685-4455 and ask for customer service.
-- 
-- This mib has been tested with HP OpenView and SunNet Manager.
-- 
-- 
	    IMPORTS 
           enterprises, Counter, Gauge, IpAddress,
           NetworkAddress, TimeTicks
	           FROM RFC1155-SMI
            ifIndex, ipRouteDest, ipAdEntAddr, egpNeighAddr
	           FROM RFC1213-MIB
            atportIndex
               FROM RFC1243-MIB
            OBJECT-TYPE
               FROM RFC-1212;
DisplayString ::= OCTET STRING
--OBJECT DEFINTIONS:  ACC PRIVATE MIB
            acc			OBJECT IDENTIFIER ::= { enterprises 5 }
                accSBAR		OBJECT IDENTIFIER ::= { acc 1 }
                    accBRG		OBJECT IDENTIFIER ::= { accSBAR 1 }
-- System Group
      accSystem         OBJECT IDENTIFIER ::= { accBRG 1 }
	accSysInfo	OBJECT IDENTIFIER ::= { accSystem 1 }
	  accUnitName	OBJECT-TYPE   
			SYNTAX  DisplayString	
			ACCESS	read-write
			STATUS	mandatory
			DESCRIPTION
                " A printable ASCII string up to 32 octets long that is
                 used to refer to a physical unit. This name is used
                 in the prompt displayed at the maintenance terminal."
			::= { accSysInfo 1 }
	  accRomId	OBJECT-TYPE   
			SYNTAX  DisplayString	
			ACCESS	read-only
			STATUS	mandatory
			DESCRIPTION
		 " A printable ASCII string that contains information about
		   the hardware and the firmware (NOT the software). "
			::= { accSysInfo 2 }
	  accSwVersion	OBJECT-TYPE   
			SYNTAX  DisplayString	
			ACCESS	read-only
			STATUS	mandatory
			DESCRIPTION
                   " A printable ASCII string representing the software
                     version number of the running code."
			::= { accSysInfo 3 }
	  accReset	OBJECT-TYPE   
			SYNTAX	INTEGER
			ACCESS	read-write
			STATUS	mandatory
			DESCRIPTION
                 " A Set  command on this object will cause an immediate reset
		   of the unit."
			::= { accSysInfo 4 }
		AccMemBlkEnt ::= SEQUENCE {
			accMemBlkEntSize		INTEGER,
	    		accMemBlkEntTotal		INTEGER,
	    		accMemBlkEntMax 		Gauge,
	    		accMemBlkEntInUse		Gauge,
	    		accMemBlkEntFails		Counter,
			accMemBlkEntType		INTEGER,
	    		accMemBlkEntAllocs		Counter
			}
	  accMemStatTbl    OBJECT-TYPE
			SYNTAX AccMemBlkEnt
			ACCESS not-accessible
			STATUS mandatory
			DESCRIPTION
                    " Information about data buffer pools.
                      Instance is pool number."
		      INDEX { INTEGER }       -- (1 - 7 is D RAM, 8 is M RAM, 9 - is C RAM)
			::= { accSysInfo 5 }
	    accMemBlkEntSize   OBJECT-TYPE  
			SYNTAX	INTEGER
			ACCESS	read-only
			STATUS	mandatory
			DESCRIPTION
                      " Size (bytes) of these buffers"
			::=  { accMemStatTbl 1 }
	    accMemBlkEntTotal	OBJECT-TYPE  
			SYNTAX	INTEGER
			ACCESS	read-only
			STATUS	mandatory
			DESCRIPTION
                       " Total number of these buffers in pool, whether
                         or not they are in use"
			::=  { accMemStatTbl 2 }
	    accMemBlkEntMax   OBJECT-TYPE  
			SYNTAX	Gauge
			ACCESS	read-only
			STATUS	mandatory
			DESCRIPTION
                        " High water mark of usage of buffers"
			::=  { accMemStatTbl 3 }
	    accMemBlkEntInUse	OBJECT-TYPE  
			SYNTAX	Gauge
			ACCESS	read-only
			STATUS	mandatory
			DESCRIPTION
                        " Number of buffers currently in use."
			::=  { accMemStatTbl 4 }
	    accMemBlkEntFails	OBJECT-TYPE  
			SYNTAX	Counter
			ACCESS	read-only
			STATUS	mandatory
			DESCRIPTION
                       " Number of times requests were made for a buffer
                         of this size that failed because none were avaliable."
			::=  { accMemStatTbl 5 }
	    accMemBlkEntType   OBJECT-TYPE  
                SYNTAX  INTEGER 
			ACCESS	read-only
			STATUS	mandatory
			DESCRIPTION
                      " Numeric classification of the buffer."
			::=  { accMemStatTbl 6 }
	    accMemBlkEntAllocs   OBJECT-TYPE  
			SYNTAX	Counter
			ACCESS	read-only
			STATUS	mandatory
			DESCRIPTION
                      " Number of times a request was made for a buffer
			of this size."
			::=  { accMemStatTbl 7 }
	accSessionCtrl	OBJECT IDENTIFIER ::= { accSystem 2 }
	  accLogin	OBJECT-TYPE   
			SYNTAX  DisplayString	
			ACCESS	read-write
			STATUS	mandatory
			DESCRIPTION
                 " A read attempt of this object is interpreted as a request
                  for login to the unit. The instance is an ASCII string
                  with the following (case sensitive) format:
                          CommunityString:Password
                  The GetResponse-PDU will return the accUnitName of the unit.
                  A write attempt is interpreted as a request to change
                  the password.
                  A GetNextRequest will not acknowledge the presence
                   of this object."
			::= { accSessionCtrl 1 }
	  accLogout	OBJECT-TYPE   
			SYNTAX  DisplayString	
			ACCESS	read-only
			STATUS	mandatory
			DESCRIPTION
                 " A read attempt of this object is interpreted as a request
                  for logout to the unit. The instance is an ASCII string
                  with the following format:
                          CommunityString:Password
                  A GetNextRequest will not acknowledge the presence
                   of this object."
			::= { accSessionCtrl 2 }
	  accLoginTimeout  OBJECT-TYPE	
			SYNTAX TimeTicks 
			ACCESS read-write
			STATUS mandatory
			DESCRIPTION
			 " Session inactivity timer.
			   Zero disables timer (no timeout)
			   Default value is zero
			   Range is 0-86400 seconds"
			::= { accSessionCtrl 3 }
	accTrapTable	OBJECT-TYPE 
			SYNTAX	SEQUENCE OF AccTrapEntry
			ACCESS	not-accessible
			STATUS	mandatory
			DESCRIPTION
                   " A table of systems to which Trap Messages generated
                     by this unit shall be sent.
                     To delete an entry, a SetRequest-PDU for the specific
                     instance of accTrapAddr with a NULL value encoding is
                     used."
			::= { accSystem 3 }
	  accTrapEntry	OBJECT-TYPE
			SYNTAX	AccTrapEntry
			ACCESS	not-accessible
			STATUS	mandatory
			DESCRIPTION
                            " A Trap Table entry "
                        INDEX { accTrapAddr }
			::= { accTrapTable 1 }
	  AccTrapEntry	::= SEQUENCE {
			accTrapAddr	 IpAddress,
			accTrapSeverity	 INTEGER
			} 
	    accTrapAddr OBJECT-TYPE   
			SYNTAX	IpAddress
			ACCESS	read-write
			STATUS	mandatory
			DESCRIPTION
                " An IP address to which SNMP traps generated by the unit
                  are sent."
			::= { accTrapEntry 1 }
	    accTrapSeverity	OBJECT-TYPE   
			SYNTAX	INTEGER (1..7)
			ACCESS	read-write
			STATUS	mandatory
			DESCRIPTION
                 " severity level of the traps to be sent 
                   ACC products generate enterprise specific traps for which
                   different severity levels from 1 through 7 are assigned.
                   Level 1 refers to Only SNMP traps. Level 2 are
                   specific traps of highest urgency, and thus progressively
                   each level get more verbose. The normal operational level
                   is expected to be 3 or 4. Higher levels (i.e., 5-7) are
                   expected to generate many events which may be helpful
                   in identifying/isolating configuration related problems,
                   but may affect the performance of the unit."
			::= { accTrapEntry 2 }
	accClock	OBJECT IDENTIFIER ::= { accSystem 4 }
	  accDate	OBJECT-TYPE   
			SYNTAX	OCTET STRING
			ACCESS	read-write
			STATUS	mandatory
			DESCRIPTION
                 " The octet string of six bytes representing the date
                  and time has the following format:
                  YYMMDDHHMMSS
                  where the valid range of values for each of the bytes
                  is as follows:
                          YY      0..99
                          MM      1..12
                          DD      1..31
                          HH      0..23
                          MM      0..59
                          SS      0..59"
			::= { accClock 1 }
	  accUToffset	OBJECT-TYPE   
			SYNTAX	OCTET STRING
			ACCESS	read-write
			STATUS	mandatory
			DESCRIPTION
			 " 3-byte date string, HH MM SS"
			::= { accClock 2 }
	  accSysBootTime  OBJECT-TYPE	
			SYNTAX	OCTET STRING
			ACCESS	read-only
			STATUS	mandatory
			DESCRIPTION
			 " 3-byte date string, HH MM SS"
			::= { accClock 3 }
	  accSysCpuAvgShort  OBJECT-TYPE	
			SYNTAX	INTEGER
			ACCESS	read-only
			STATUS	mandatory
			DESCRIPTION
			 " percentage CPU used over the last minute "
			::= { accClock 4 }
	  accSysCpuAvgLong  OBJECT-TYPE	
			SYNTAX	INTEGER
			ACCESS	read-only
			STATUS	mandatory
			DESCRIPTION
			 " percentage CPU used over the last 5 minutes "
			::= { accClock 5 }
        accAccessTable	OBJECT-TYPE
			SYNTAX	SEQUENCE OF  AccAccessEntry
			ACCESS	not-accessible
			STATUS	mandatory
			DESCRIPTION
                   " A table of users authorized to log in to this unit.
                     To delete an entry, a SetRequest-PDU for the specific
                     instance of accAccessAddr with a NULL value encoding is
                     used."
			::= { accSystem 6 }
	 accAccessEntry	OBJECT-TYPE
		SYNTAX	AccAccessEntry
		ACCESS	not-accessible
		STATUS	mandatory
		DESCRIPTION
                    " An entry of information about an authorized user."
                INDEX { accAccessAddr, accAccessNetMask, accAccessUdpPort }     
		::= { accAccessTable 1 }
	 	AccAccessEntry	::= SEQUENCE {
			      accAccessCmty	 DisplayString,
			      accAccessAddr	 IpAddress,
			      accAccessNetMask	 IpAddress,
			      accAccessUdpPort	 INTEGER
			      }
	   accAccessCmty	OBJECT-TYPE   
			SYNTAX  DisplayString	
			ACCESS	read-write
			STATUS	mandatory
			DESCRIPTION
                 " Access community"
			::= { accAccessEntry 1 }
	   accAccessAddr	OBJECT-TYPE   
		SYNTAX	IpAddress
		ACCESS	read-write
		STATUS	mandatory
		DESCRIPTION
                 " IP address from which a login request is honored."
		::= { accAccessEntry 2 }
	   accAccessNetMask	OBJECT-TYPE   
		SYNTAX	IpAddress
		ACCESS	read-write
		STATUS	mandatory
		DESCRIPTION
                        " Subnet mask used to validate login requests."
		::= { accAccessEntry 3 }  
	   accAccessUdpPort	OBJECT-TYPE   
		SYNTAX	INTEGER
		ACCESS	read-write
		STATUS	mandatory
		DESCRIPTION
                 " UDP port number of the SNMP application. "
			::= { accAccessEntry 4 }
	  accReload	OBJECT-TYPE   
			SYNTAX	TimeTicks
			ACCESS	read-write
			STATUS	mandatory
			DESCRIPTION
			 " Time until system reload shall occur.
			   Upon expiry of the timer, the system will load
			   and execute a new image of the application code.
			   The load file will come from diskette, local
			   EPROM, or over the network, depending on the
			   configuration of the unit."
			::= { accSystem 7 }
        accIfNames  OBJECT IDENTIFIER  ::= { accSystem 8 }
           accIfNumNames  OBJECT-TYPE
                  SYNTAX  INTEGER
                  ACCESS  read-only
                  STATUS  mandatory
                  DESCRIPTION
                     "Number of interfaces (physical and logical).
                      There are this many entries in the Name table."
                   ::= { accIfNames 1 }
	  accIfNameTable	OBJECT-TYPE 
			SYNTAX	SEQUENCE OF AccIfNameEntry
			ACCESS	not-accessible
			STATUS	mandatory
			DESCRIPTION
                   " A table of of mnemonic 'names' for physical and
                     logical interfaces"
			::= { accIfNames 2 }
	     accIfNameEntry	OBJECT-TYPE
			SYNTAX	AccIfNameEntry
			ACCESS	not-accessible
			STATUS	mandatory
			DESCRIPTION
                            " An entry in the Interface Name table "
                        INDEX { accIfNameIndex }
			::= { accIfNameTable 1 }
		  AccIfNameEntry	::= SEQUENCE {
			accIfNameIndex	 INTEGER,
			accIfName  	 DisplayString 
			} 
	      accIfNameIndex OBJECT-TYPE   
			SYNTAX	INTEGER
			ACCESS	read-only
			STATUS	mandatory
			DESCRIPTION
                " Interface number "
			::= { accIfNameEntry 1 }
	       accIfName	OBJECT-TYPE   
			SYNTAX	DisplayString --(SIZE (5)) 
			ACCESS	read-write
			STATUS	mandatory
			DESCRIPTION
                 " Mnemonic name for this interface" 
			::= { accIfNameEntry 2 }
	    accIfGroupTable OBJECT-TYPE
		SYNTAX	SEQUENCE OF  AccIfGroupEntry
		ACCESS	not-accessible
		STATUS	mandatory
		DESCRIPTION
			" A table of interface group descriptors supported by
			this unit.  Interface groups may be populated by 
			physical or logical interfaces, or combinations of
			the two."
		::= { accSystem 9 }
	accIfGroupEntry	OBJECT-TYPE
		SYNTAX	AccIfGroupEntry
		ACCESS	not-accessible
		STATUS	mandatory
		DESCRIPTION
			" An entry of information about a interface group."
		INDEX { accIFGroupIndex }
		::= { accIfGroupTable 1 }
	AccIfGroupEntry	::= SEQUENCE {
		accIFGroupIndex		INTEGER,
		accIFGroupName		DisplayString,
		accIFGroupType		INTEGER,
		accIFGroupIndexBase	INTEGER,
		accIFGroupIndexMax	INTEGER
		}
	accIFGroupIndex	OBJECT-TYPE   
		SYNTAX	INTEGER 
		ACCESS	read-only
		STATUS	mandatory
		DESCRIPTION
			" Index for the accIfGroupTable."
		::= { accIfGroupEntry 1 }
	accIFGroupName	OBJECT-TYPE   
		SYNTAX  DisplayString	
		ACCESS	read-only
		STATUS	mandatory
		DESCRIPTION
			" If accIFGroupIndexBase and accIFGroupIndexMax
			are equal then this object provides the full
			name of the port, else this object has the prefix
			of the port name.  If this is a prefix then the
			suffix is a numeric value from 1 to
			(accIFGroupIndexMax - accIFGroupIndexBase + 1). "
		::= { accIfGroupEntry 2 }
	accIFGroupType	OBJECT-TYPE   
		SYNTAX	INTEGER {
			physical-port(1),
			bridge-port(2),
			dial-port(3),
			multi-link(4)
			}
		ACCESS	read-only
		STATUS	mandatory
		DESCRIPTION
			" Type of port group"
		::= { accIfGroupEntry 3 }
	accIFGroupIndexBase	OBJECT-TYPE   
		SYNTAX	INTEGER
		ACCESS	read-only
		STATUS	mandatory
		DESCRIPTION
			" Lowest IFIndex in this IFGroup"
		::= { accIfGroupEntry 4 }
	accIFGroupIndexMax	OBJECT-TYPE   
		SYNTAX	INTEGER
		ACCESS	read-only
		STATUS	mandatory
		DESCRIPTION
			" The number of interfaces supported in this 
			IFGroup"
		::= { accIfGroupEntry 5 }
accNvm	OBJECT IDENTIFIER ::= { accSysInfo 6 }
        accNvmTotalBlks OBJECT-TYPE
                SYNTAX  INTEGER
                ACCESS  read-only
                STATUS  mandatory
                DESCRIPTION
                        " Total number of NVM blocks."
                ::= { accNvm 1 }
        accNvmBlkSize   OBJECT-TYPE 
                SYNTAX  INTEGER 
                ACCESS  read-only 
                STATUS  mandatory 
                DESCRIPTION 
                        " NVM block size in bytes." 
                ::= { accNvm 2 }
        accNvmDirSize   OBJECT-TYPE 
                SYNTAX  INTEGER 
                ACCESS  read-only 
                STATUS  mandatory 
                DESCRIPTION 
                        " The NVM directory size." 
                ::= { accNvm 3 }
        accNvmFreeBlks  OBJECT-TYPE 
                SYNTAX  INTEGER 
                ACCESS  read-only 
                STATUS  mandatory 
                DESCRIPTION 
                        " The number of free NVM blocks." 
                ::= { accNvm 4 }
        accNvmFileNumber OBJECT-TYPE 
                SYNTAX  INTEGER 
                ACCESS  read-only 
                STATUS  mandatory 
                DESCRIPTION 
                        " The NVM file number." 
                ::= { accNvm 5 }
        accNvmFileName   OBJECT-TYPE 
                SYNTAX  OCTET STRING 
                ACCESS  read-only 
                STATUS  mandatory 
                DESCRIPTION 
                        " The NVM file name." 
                ::= { accNvm 6 }
        accNvmFileSize  OBJECT-TYPE 
                SYNTAX  INTEGER 
                ACCESS  read-only 
                STATUS  mandatory 
                DESCRIPTION 
                        " The NVM file size in bytes." 
                ::= { accNvm 7 }
accSysConfigInfo OBJECT IDENTIFIER ::= { accSysInfo 7 }
     accConfiguration   OBJECT-TYPE
                        SYNTAX  INTEGER {
                                save(1),  -- Save Configuration to NVM
                                load(2),  -- Load Configuration from NVM
                                default(3)  -- Set Configuration to default
                                }
                        ACCESS  read-write
                        STATUS  mandatory
                        DESCRIPTION
                 " Set the action to perform on the active configuration.
                   A set to load or default will immediately reset the unit.
                   On the restart the new configuration (either a previously
                   saved one or the default configuration) will be used."
                        ::= { accSysConfigInfo 1 }
accConfigurationStatus      OBJECT-TYPE
                        SYNTAX  INTEGER {
                                saved(1),
                                changed(2)
                                }
                        ACCESS  read-only
                        STATUS  mandatory
                        DESCRIPTION
                 " The current state of the active configuration.  The value
                   changed indicates that the active configuration has
                   changed since the last time it was saved to NVM."
                        ::= { accSysConfigInfo 2 }
          accScriptHalt OBJECT-TYPE
                        SYNTAX  INTEGER
                        ACCESS  read-write
                        STATUS  mandatory
                        DESCRIPTION
                 " A Set  command on this object will cause an immediate
                   halt to any existing configuration script execution."
                        ::= { accSysInfo 8 }
	accScriptCont	OBJECT IDENTIFIER  ::= { accSysInfo 9 }
          accScriptContServer	 OBJECT-TYPE
                        SYNTAX  IpAddress
                        ACCESS  read-write
                        STATUS  mandatory
                        DESCRIPTION
			" The IP address of the server holding the 
			  configuration script to be downloaded and executed
			  following the next reset."
                        ::= { accScriptCont 1 }
          accScriptContFile	 OBJECT-TYPE
                        SYNTAX  DisplayString
                        ACCESS  read-write
                        STATUS  mandatory
                        DESCRIPTION
			" The filename (with complete pathname) of the  
			  configuration script to be downloaded and executed
			  following the next reset."
                        ::= { accScriptCont 2 }
	  accGifnoc	OBJECT-TYPE   
			SYNTAX	OCTET STRING
			ACCESS	read-only
			STATUS	mandatory
			DESCRIPTION
		 " Reserved number for GIFNOC (S. Froyd, 20-August, 1994)"
			::= { accSysInfo 10 }
        accSysHWType  OBJECT-TYPE
                SYNTAX  INTEGER 
                ACCESS  read-only
                STATUS  mandatory
                DESCRIPTION
                        " The hardware platform product name"
                ::= { accSysInfo 11 }
        accSysProcType  OBJECT-TYPE
                SYNTAX  INTEGER 
                ACCESS  read-only
                STATUS  mandatory
                DESCRIPTION
                        " Type of processor on this platform"
                ::= { accSysInfo 12 }
          accSysLocalRam OBJECT-TYPE
                SYNTAX  INTEGER
                ACCESS  read-only
                STATUS  mandatory
                DESCRIPTION
			" The amount of local RAM installed in the system 
			  in kilobytes"
               ::= { accSysInfo 13 }
          accSysGlobalRam OBJECT-TYPE
                SYNTAX  INTEGER
                ACCESS  read-only
                STATUS  mandatory
                DESCRIPTION
                        " The amount of global RAM installed in the system 
                          in kilobytes"
                ::= { accSysInfo 14 }
        accSysPowerSupply  OBJECT-TYPE
                SYNTAX  INTEGER {
                        single(1),
                        dual-both-operational(2),
                        dual-one-malfunctioning(3)
                        }
                ACCESS  read-only
                STATUS  mandatory
                DESCRIPTION
                        " Type of processor on this platform"
                ::= { accSysInfo 15 }
	accMemPoolTable    OBJECT-TYPE
		SYNTAX	SEQUENCE OF  AccMemPoolEntry
		ACCESS	not-accessible
		STATUS	mandatory
		DESCRIPTION
			" A table of memory pools supported by this unit.
			Each pool describes a physical memory resource."
		::= { accSysInfo 16 }
	accMemPoolEntry	OBJECT-TYPE
		SYNTAX	AccMemPoolEntry
		ACCESS	not-accessible
		STATUS	mandatory
		DESCRIPTION
			" An entry of information about a memory pool."
		INDEX { accMemPoolName }
		::= { accMemPoolTable 1 }
	  AccMemPoolEntry	::= SEQUENCE {
			accMemPoolName			DisplayString,
			accMemPoolMaximum		Gauge,
                        accMemPoolBytes			Gauge,
                        accMemPoolFrags			Gauge,
                        accMemPoolAlign			INTEGER,
                        accMemPoolAllocs		Counter,
                        accMemPoolFails			Counter
			} 
        accMemPoolName  OBJECT-TYPE
                SYNTAX  DisplayString
                ACCESS  read-only
                STATUS  mandatory
                DESCRIPTION
                        "A printable ASCII string describing this
			 memory pool."
                ::= { accMemPoolEntry 1 }
        accMemPoolMaximum OBJECT-TYPE
                SYNTAX  Gauge
                ACCESS  read-only
                STATUS  mandatory
                DESCRIPTION
			"The maximum amount of memory in this memory pool."
               ::= { accMemPoolEntry 2 }
        accMemPoolBytes OBJECT-TYPE
                SYNTAX  Gauge
                ACCESS  read-only
                STATUS  mandatory
                DESCRIPTION
			"The amount of memory currently available
                         in this memory pool."
               ::= { accMemPoolEntry 3 }
        accMemPoolFrags OBJECT-TYPE
                SYNTAX  Gauge
                ACCESS  read-only
                STATUS  mandatory
                DESCRIPTION
			"The number of times this memory pool has been
                         fragmented."
               ::= { accMemPoolEntry 4 }
        accMemPoolAlign OBJECT-TYPE
                SYNTAX  INTEGER
                ACCESS  read-only
                STATUS  mandatory
                DESCRIPTION
			"The alignment this memory pool maintains.  For
			 example, a 4 in this field means memory from this
			 pool is aligned on 32-bit boundaries."
               ::= { accMemPoolEntry 5 }
        accMemPoolAllocs OBJECT-TYPE
                SYNTAX  Counter
                ACCESS  read-only
                STATUS  mandatory
                DESCRIPTION
			"The number of allocation requests addressed to
			 this memory pool."
               ::= { accMemPoolEntry 6 }
        accMemPoolFails OBJECT-TYPE
                SYNTAX  Counter
                ACCESS  read-only
                STATUS  mandatory
                DESCRIPTION
			"The number of times an allocation request addressed
			 to this memory could not be satisfied."
               ::= { accMemPoolEntry 7 }
-- Spanning Tree Protocol Group
    accStp   OBJECT IDENTIFIER ::= { accBRG 2 }
	accStpPriority	OBJECT-TYPE   
			SYNTAX	INTEGER (0..255)
			ACCESS	read-write
			STATUS	mandatory
			DESCRIPTION
                " Among all devices participating in spanning tree, the
                   one with the highest priority (numerically lowest
                   value of this parameter) is elected as the Root
                   of the spanning tree."
			::= { accStp 1 } 
	accStpId	OBJECT-TYPE   
			SYNTAX	OCTET STRING
			ACCESS	read-only
			STATUS	mandatory
			DESCRIPTION
                " Unique bridge identifier of this bridge.  This object
                   comprises two parts, one of which is the MAC address,
                   and the other of which is the brStpPriority and is the
                   more significant part in priority comparisons."
			::= { accStp 2 } 
	accStpBrAddr	OBJECT-TYPE   
			SYNTAX	OCTET STRING
			ACCESS	read-only
			STATUS	mandatory
			DESCRIPTION
             " MAC address of this bridge."
			::= { accStp 3 }    
	accStpMode	OBJECT-TYPE   
			SYNTAX	INTEGER {
				on(1),
				off(2)
				}
			ACCESS	read-write
			STATUS	mandatory
			DESCRIPTION
                " State of this Bridge's participation in Spanning Tree.
                  Spanning Tree  takes care of network connectivity changes
                   caused by addition/removal/failure of links.
                   It avoids loops when any two networks have redundant
                   connections between them."
			::= { accStp 4 } 
	accStpFilterTime	OBJECT-TYPE   
			SYNTAX	TimeTicks
			ACCESS	read-only
			STATUS	mandatory
			DESCRIPTION
                 " Minimum time period elapsing between the
                   transmission of Hello frames through a given Bridge Port.
                   No more than two Hello frames shall be transmitted in any
                   brStpFilterTime period."
			::= { accStp 5 }
	accStpMcastAddr		OBJECT-TYPE   
			SYNTAX	OCTET STRING
			ACCESS	read-write
			STATUS	mandatory
			DESCRIPTION
                 " A unique MAC group address, recognised by all the Bridges
                   within the Bridged Local Area Network."
			::= { accStp 6 } 
	accStpTopChangeDet	OBJECT-TYPE   
			SYNTAX	INTEGER (0..1)
			ACCESS	read-only
			STATUS	mandatory
			DESCRIPTION
                " Indicates if this unit has detected the Topology
                  change indication in the hello BPDU.
				no(0),
				yes(1)
		"
			::= { accStp 7 } 
	accStpTopChange		OBJECT-TYPE   
			SYNTAX	INTEGER (0..1)
			ACCESS	read-only
			STATUS	mandatory
			DESCRIPTION
                " Indicates if the STP topology of a network is in
                   process of changing.
				no(0),
				yes(1)
		"
			::= { accStp 8 } 
	accStpTopChangeTimer	OBJECT-TYPE   
			SYNTAX	TimeTicks
			ACCESS	read-only
			STATUS	mandatory
			DESCRIPTION
                 " This timer serves to determine the time period for
                    which hello frames are transmitted with the
                   Topology Change flag parameter set by the Bridge when
                   it is the Root following the detection of a topology
                   change."
			::= { accStp 9 }
	accStpDesRoot	OBJECT-TYPE   
			SYNTAX	OCTET STRING
			ACCESS	read-only
			STATUS	mandatory
			DESCRIPTION
               "  The Bridge Identifier  of the device currently
                   assumed by this unit to be the Root."
			::= { accStp 10 } 
	accStpRootPathCost	OBJECT-TYPE   
			SYNTAX	INTEGER
			ACCESS	read-only
			STATUS	mandatory
			DESCRIPTION
                " Current path cost to the Root Bridge."
			::= { accStp 11 }
	accStpRootPort	OBJECT-TYPE   
			SYNTAX	OCTET STRING
			ACCESS	read-only
			STATUS	mandatory
			DESCRIPTION
               " Port Number of the one Port in the direction of the Root.
                  (Value is meaningless if this unit is the Root)."
			::= { accStp 12 } 
	accStpMaxAge	OBJECT-TYPE   
			SYNTAX	INTEGER (4..3600)
			ACCESS	read-write
			STATUS	mandatory
			DESCRIPTION
                 " The value of the Max Age parameter when the Bridge is the
                  Root or attempting to become the Root.
                  The Max Age parameter is conveyed to ensure that each Bridge
                  in a Bridged Local Area Network has a consistent value
                  against which to test the age of stored protocol information."
			::= { accStp 13 }
	accStpHelloTime		OBJECT-TYPE   
			SYNTAX	INTEGER (2..1800)
			ACCESS	read-write
			STATUS	mandatory
			DESCRIPTION
                 " Interval between Hello frames that this
                  Bridge will initiate when it is Root or is attempting
                  to be Root."
			::= { accStp 14 }
	accStpForwardDelay	OBJECT-TYPE   
			SYNTAX	INTEGER (5..3600)
			ACCESS	read-write
			STATUS	mandatory
			DESCRIPTION
                 " The time  (seconds) spent in the Listening state while
                   moving from the Blocking state to the Learning state.
                   The time  (seconds) spent in the Learning state while
                   moving from the Listening state to the Forwarding state.
                   The value  (seconds) used for the ageing time of dynamic 
                   entries in the Forwarding Database table wile the Topology
                   Change flag is set in protocol messages received from
                   the Root."
			::= { accStp 15 }
	accStpUpTime	OBJECT-TYPE   
			SYNTAX	TimeTicks
			ACCESS	read-only
			STATUS	mandatory
			DESCRIPTION
                 " "
			::= { accStp 16 }
	accStpTopChangeCnts	OBJECT-TYPE   
			SYNTAX	Counter
			ACCESS	read-only
			STATUS	mandatory
			DESCRIPTION
                   " "
			::= { accStp 17 }
-- Bridge Port Group
      accBrPort  OBJECT IDENTIFIER ::= { accBRG 3 }
	accBrPortInfo	OBJECT IDENTIFIER ::= { accBrPort 1 }
	  accBrPortStats OBJECT IDENTIFIER ::= { accBrPortInfo 1 }
	    accBrPortInNUcastPkts	OBJECT-TYPE   
			SYNTAX	Counter
			ACCESS	read-only
			STATUS	mandatory
			DESCRIPTION
                          " Number of non-unicast packets received"
			::= { accBrPortStats 1 }
	    accBrPortInUcastPkts	OBJECT-TYPE   
			SYNTAX	Counter
			ACCESS	read-only
			STATUS	mandatory
			DESCRIPTION
                         " Number of unicast packets received"
			::= { accBrPortStats 2 }
	    accBrPortInDupPkts	OBJECT-TYPE   
			SYNTAX	Counter
			ACCESS	read-only
			STATUS	mandatory
			DESCRIPTION
                         " Number of in packets duplicated"
			::= { accBrPortStats 3 }
	    accBrPortOutNUcastPkts	OBJECT-TYPE   
			SYNTAX	Counter
			ACCESS	read-only
			STATUS	mandatory
			DESCRIPTION
                         " Number of non-unicast packets sent"
			::= { accBrPortStats 4 }
	    accBrPortOutUcastPkts	OBJECT-TYPE   
			SYNTAX	Counter
			ACCESS	read-only
			STATUS	mandatory
			DESCRIPTION
                         " Number of unicast packets sent"
			::= { accBrPortStats 5 }
	    accBrPortStpInPkts	OBJECT-TYPE   
			SYNTAX	Counter
			ACCESS	read-only
			STATUS	mandatory
			DESCRIPTION
                         " Number of spanning tree packets recieved"
			::= { accBrPortStats 6 }
	    accBrPortStpOutPkts		OBJECT-TYPE   
			SYNTAX	Counter
			ACCESS	read-only
			STATUS	mandatory
			DESCRIPTION
                         " Number of spanning tree packets sent"
			::= { accBrPortStats 7 }
	    accBrPortOutDelayDiscPkts	OBJECT-TYPE   
			SYNTAX	Counter
			ACCESS	read-only
			STATUS	mandatory
			DESCRIPTION
                         " Number of output packets dropped because
                           they were held in queue too long"
			::= { accBrPortStats 8 }
	    accBrPortOutPrioDiscPkts	OBJECT-TYPE   
			SYNTAX	Counter
			ACCESS	read-only
			STATUS	mandatory
			DESCRIPTION
                         " Packets discarded on ouput by the
                           protocol priority filter mechanism"
			::= { accBrPortStats 9 }
	    accBrPortOutQLen	OBJECT-TYPE   
			SYNTAX	Gauge
			ACCESS	read-only
			STATUS	mandatory
			DESCRIPTION
                         " Length of port output queue"
			::= { accBrPortStats 10 }
	    accBrPortInDiscPkts		OBJECT-TYPE   
			SYNTAX	Counter
			ACCESS	read-only
			STATUS	mandatory
			DESCRIPTION
                         " Number of bridge packets discarded
                           at input"
			::= { accBrPortStats 11 }
	  accBrPortStpPriority	OBJECT-TYPE   
			SYNTAX	INTEGER (0..255)
			ACCESS	read-write
			STATUS	mandatory
			DESCRIPTION
                         " Relative STP priority of this port"
			::= { accBrPortInfo 2 }
	  accBrPortId	OBJECT-TYPE   
			SYNTAX	OCTET STRING
			ACCESS	read-only
			STATUS	mandatory
			DESCRIPTION
                         " Port ID"
			::= { accBrPortInfo 3 }
	  accBrPortState	OBJECT-TYPE   
			SYNTAX	INTEGER (0..4)
			ACCESS	read-write
			STATUS	mandatory
			DESCRIPTION
			 " accBrPortState reports the operational status
			   of the port; it is writable for backward
			   compatibility (writes also update
			   accBrPortAdminStatus).
				disabled(0),
				blocking(1),
				listening(2),
				learning(3),
				forwarding(4)
			   "
			::= { accBrPortInfo 5 }
	  accBrPortStpPathCost	OBJECT-TYPE   
			SYNTAX	INTEGER (0..65535)
			ACCESS	read-write
			STATUS	mandatory
			DESCRIPTION
                         " Path cost"
			::= { accBrPortInfo 6 }
	  accBrPortStpDesRoot	OBJECT-TYPE   
			SYNTAX	OCTET STRING
			ACCESS	read-only
			STATUS	mandatory
			DESCRIPTION
                         " Designated root"
			::= { accBrPortInfo 7 }
	  accBrPortStpDesCost	OBJECT-TYPE   
			SYNTAX	INTEGER (0..65535)
			ACCESS	read-only
			STATUS	mandatory
			DESCRIPTION
                         " Cost to designated root"
			::= { accBrPortInfo 8 }
	  accBrPortStpDesBridge		OBJECT-TYPE   
			SYNTAX	OCTET STRING
			ACCESS	read-only
			STATUS	mandatory
			DESCRIPTION
                         " Designated bridge"
			::= { accBrPortInfo 9 }
	  accBrPortStpDesPort	OBJECT-TYPE   
			SYNTAX	OCTET STRING
			ACCESS	read-only
			STATUS	mandatory
			DESCRIPTION
                         " Designated port"
			::= { accBrPortInfo 10 }
	  accBrPortAdminStatus OBJECT-TYPE   
			SYNTAX	INTEGER {
				enabled(1),
				disabled(2)
				}
			ACCESS	read-write
			STATUS	mandatory
			DESCRIPTION
			 " accBrPortAdminStatus reports the administrative
			   status of the port; an update to this variable
			   is effective immediately.  Note that the
			   operational status may be disabled even though
			   accBrPortAdminStatus is enabled, if the bridge
			   port's protocol type is incompatible with the
			   associated physical port protocol type."
			::= { accBrPortInfo 11 }
	  accBrPortLine OBJECT-TYPE	
			SYNTAX	INTEGER
			ACCESS	read-write
			STATUS	mandatory
			DESCRIPTION
			 " Index of physical port associated with this bridge
			   port."
			::= { accBrPortInfo 12 }
	  accBrPortProtocol	OBJECT-TYPE	
			SYNTAX	INTEGER {
				enet(1),
				x25(2),
				lapb(3),
				ffr(4),
				other(5)
				}
			ACCESS	read-write
			STATUS	mandatory
			DESCRIPTION
			 " note that these enumerated values match those in
			   accSlotProtocol; the current implementation will
			   not permit accBrPortProtocol to be set to x25."
			::= { accBrPortInfo 13 }
	  accBrPortFrDlci	OBJECT-TYPE	
			SYNTAX	INTEGER
			ACCESS	read-write
			STATUS	mandatory
			DESCRIPTION
                         " Frame Relay DLCI for this port"
			::= { accBrPortInfo 14 }
	  accBrPortIndex	OBJECT-TYPE
			SYNTAX	INTEGER
			ACCESS	read-only
			STATUS	mandatory
			DESCRIPTION
                         " Bridge Port Index"
			::= { accBrPortInfo 15 }
	  accBrPortXBridgeStatus	OBJECT-TYPE
			SYNTAX	INTEGER {
				enabled(1),
				disabled(2)
				}
			ACCESS	read-only
			STATUS	mandatory
			DESCRIPTION
                         " Bridge Port translating bridge status"
			::= { accBrPortInfo 16 }
-- Bridge FDB Group
      accBridge OBJECT IDENTIFIER ::= { accBRG 4 }
	accBrFdbTimeout		OBJECT-TYPE   
			SYNTAX	INTEGER (10..65535)
			ACCESS	read-write
			STATUS	mandatory
			DESCRIPTION
                 " Time (seconds) for which a learned Forwarding Database
                   entry is valid before being deleted if it has not been seen."
			::= { accBridge 1 }  
	accBrFdbLearnMode	OBJECT-TYPE   
			SYNTAX	INTEGER {
				on(1),
				off(2)
				}
			ACCESS	read-write
			STATUS	mandatory
			DESCRIPTION
                " When Learning Mode is active, Bridges update their
                  Forwarding Database with dynamic entries learned by
                  inspection of the Source MAC Address of received frames.
                  When learning mode is off, Bridges discard packets which
                  are not indicated as forward in their Forwarding Database.
		"
			::= { accBridge 2 }
	accBrFdbRamCurrSize	OBJECT-TYPE   
			SYNTAX	INTEGER
			ACCESS	read-only
			STATUS	mandatory
			DESCRIPTION
                 " The number of entries in the RAM FDB table that contains
                   static as well as dynamic entries."
			::= { accBridge 3 }
	accBrFdbRamMaxSize	OBJECT-TYPE   
			SYNTAX	INTEGER (64..1024)
			ACCESS	read-write
			STATUS	mandatory
			DESCRIPTION
                 " The maximum number of entries configured for the RAM
                   FDB table."
			::= { accBridge 5 }
	accBrFdbNvmMaxSize	OBJECT-TYPE   
			SYNTAX	INTEGER
			ACCESS	read-only
			STATUS	mandatory
			DESCRIPTION
                 " Number of static FDB entries that can be saved
                   in the NVM RAM."
			::= { accBridge 6 }
	accBrFdbTable	OBJECT-TYPE
			SYNTAX SEQUENCE OF AccBrFdbEntry
			ACCESS not-accessible
			STATUS mandatory
			 DESCRIPTION
                 " A list of Forwarding Database entries. Entries may be
                   added/deleted either through learning or explicit
                   management action."
			 ::= { accBridge 7 }
	  accBrFdbEntry OBJECT-TYPE
			SYNTAX AccBrFdbEntry
			ACCESS not-accessible
			STATUS mandatory
			DESCRIPTION
                " A Forwarding Database entry which defines Bridge action
                  to be taken based upon the destination MAC Address of
                  received frames."
                        INDEX { accBrFdbEntMacAddr }
			::= { accBrFdbTable 1 }
	  AccBrFdbEntry  ::= SEQUENCE {
	    	accBrFdbEntMacAddr	OCTET STRING, -- (SIZE(6))
	    	accBrFdbEntDisp		INTEGER,
	    	accBrFdbEntPort		INTEGER,
	    	accBrFdbEntTimer	INTEGER
		}
	    accBrFdbEntMacAddr	OBJECT-TYPE   
			SYNTAX	OCTET STRING -- (SIZE(6))
			ACCESS	read-write
			STATUS	mandatory
			DESCRIPTION
                " MAC Address of the Forwarding Database Entry.
	          Set this object to NULL to delete entry."
			::= { accBrFdbEntry 1 }
	    accBrFdbEntDisp	OBJECT-TYPE   
			SYNTAX	INTEGER (0..2)
			ACCESS	read-write
			STATUS	mandatory
			DESCRIPTION
                 " Disposition of received Frame. Note that a Frame is
                   never sent back out on the Port on which it was received.
				forward(0),
				flood(1),
				discard(2)
		   "
			::= { accBrFdbEntry 2 }
	    accBrFdbEntPort	OBJECT-TYPE   
			SYNTAX	INTEGER
			ACCESS	read-write
			STATUS	mandatory
			DESCRIPTION
                " Port to which frame is to be relayed for frame to be
                  forwarded.  Has no meaning for other dispositions."
			::= { accBrFdbEntry 3 }
	    accBrFdbEntTimer	OBJECT-TYPE   
			SYNTAX	INTEGER
			ACCESS	read-only
			STATUS	mandatory
			DESCRIPTION
                 " Age of Forwarding Database Entry.  A value of
                  zero indicates a static entry."
			::= { accBrFdbEntry 4 }
	accBrFpTable	OBJECT-TYPE
			SYNTAX SEQUENCE OF AccBrFpEntry
			ACCESS not-accessible
			STATUS mandatory
			DESCRIPTION
                 " A list of Forwarding Priority Entries.
		   Entries are added/deleted via management action."
			::= { accBridge 8 }
	  accBrFpEntry	OBJECT-TYPE
			SYNTAX  AccBrFpEntry
			ACCESS not-accessible
			STATUS mandatory
			DESCRIPTION
                   " Relative Priority between frames to be forwarded
                     on a Bridge Port. "
                        INDEX { accBrFpIndex }
			::= { accBrFpTable 1 }
             AccBrFpEntry ::= SEQUENCE {
	    	accBrFpIndex 	INTEGER,
	    	accBrFpProt	INTEGER,
	    	accBrFpPrio	INTEGER
		}
	    accBrFpIndex OBJECT-TYPE   
			SYNTAX	INTEGER 
			ACCESS	read-write
			STATUS	mandatory
			DESCRIPTION
			 " Port number "
			::= { accBrFpEntry 1 }
	    accBrFpProt OBJECT-TYPE   
			SYNTAX	INTEGER (0..65535)
			ACCESS	read-write
			STATUS	mandatory
			DESCRIPTION
			 " protocol type.
			   Set this object to NULL to delete the entry."
			::= { accBrFpEntry 2 }
	    accBrFpPrio OBJECT-TYPE   
			SYNTAX	INTEGER (0..3)
			ACCESS	read-write
			STATUS	mandatory
			DESCRIPTION
                  " Relative forwarding priority assigned to protocol.
				discard(0),
				low(1),
				normal(2),
				high(3)
		"
			::= { accBrFpEntry 3 }
	accBrFpPriDefault	OBJECT-TYPE   
			SYNTAX	INTEGER (0..3)
			ACCESS	read-write
			STATUS	mandatory
			DESCRIPTION
                " Default priority to use for protocol types not specifically
                  enumerated in table.
				discard(0),
				low(1),
				normal(2),
				high(3)
		"
			::= { accBridge 9 }
	accBrNumPorts	OBJECT-TYPE	
			SYNTAX	INTEGER (2..16)
			ACCESS	read-write
			STATUS	mandatory
			DESCRIPTION
                 " Number of physical ports of unit."
			::= { accBridge 10 }
	accBrCompress	OBJECT-TYPE	
			SYNTAX	INTEGER {
			       on(1),
			       off(2)
			       }
			ACCESS	read-write
			STATUS	mandatory
			DESCRIPTION
                 " Bridge frame compression mode."
			::= { accBridge 11 }
        accBrPortX25Table       OBJECT IDENTIFIER ::= { accBridge 14 }
        accBrPortX25Entry       OBJECT IDENTIFIER ::= { accBrPortX25Table 1 }
        accBrPortX25FacIndex  OBJECT-TYPE
                      SYNTAX  INTEGER (0..255)
                      ACCESS  read-write
                      STATUS  mandatory
                      DESCRIPTION
                           " Index of optional facility string or 0."
                      DEFVAL  { 0 }
                      ::= { accBrPortX25Entry 7 }
	accBrMode	OBJECT-TYPE
			SYNTAX	INTEGER {
				bridging(1),	-- bridging is enabled
				off(2), -- bridging is disabled
				passive(3) -- forwarding is disabled
				}
			ACCESS	read-write
			STATUS	mandatory
			DESCRIPTION
		" Bridge mode.  When the mode is set to 'passive',
		  internally generated traffic is forwarded or flooded
		  as appropriate; external traffic is not forwarded to
		  other external ports."
			::= { accBridge 15 }
-- Bridge Filter Group
	accBrFilterMode	OBJECT-TYPE   
			SYNTAX	INTEGER {
				on	(1),
				off	(2)
				}
			ACCESS	read-write
			STATUS	mandatory
			DESCRIPTION
                " When Filter Mode is on, entries in the Filtering table
		  are used to determine the disposition of each frame.
                  When Filter mode is off, no filtering is done."
			::= { accBridge 16 }
	accBrFilterDefault	OBJECT-TYPE   
			SYNTAX	INTEGER {
				forward	(1),
				discard	(2)
				}
			ACCESS	read-write
			STATUS	mandatory
			DESCRIPTION
                 " The default disposition for all received frames when
		   filter mode is ON. Note: When filtering is ON, and the
		   bridge filter table search does NOT provide a match,
		   the default action will be performed."
			::= { accBridge 17 }
	accBrFilterTable	OBJECT-TYPE
			SYNTAX SEQUENCE OF AccBrFilterEntry
			ACCESS not-accessible
			STATUS deprecated
			DESCRIPTION
                 " A list of Filtering entries."
			 ::= { accBridge 18 }
	  accBrFilterEntry OBJECT-TYPE
			SYNTAX AccBrFilterEntry
			ACCESS not-accessible
			STATUS deprecated
			DESCRIPTION
                " A Filtering entry which defines Bridge action
                  to be taken based upon the destination AND source
		  MAC Addresses, port number, port protocol and logic op of
		  received frames."
                        INDEX {	accBrFilterEntDstMacAddr,
				accBrFilterEntSrcMacAddr,
				accBrFilterEntPort,
				accBrFilterEntLogicalOp,
				accBrFilterEntProtocol}
			::= { accBrFilterTable 1 }
	  AccBrFilterEntry  ::= SEQUENCE {
	    	accBrFilterEntDstMacAddr	OCTET STRING,
	    	accBrFilterEntSrcMacAddr	OCTET STRING,
	    	accBrFilterEntPort		INTEGER,
	    	accBrFilterEntLogicalOp		INTEGER,
	    	accBrFilterEntProtocol		OCTET STRING,
	    	accBrFilterEntDisp		INTEGER,
-- The following two items are not actually part of the SEQUENCE but were
-- defined as such. They have been placed in the SEQUENCE definition to avoid
-- MIB compiler problems.
		accBrFilterDiscards		INTEGER,
		accBrFilterEntries		INTEGER
		}
	    accBrFilterEntDstMacAddr	OBJECT-TYPE   
			SYNTAX	OCTET STRING -- (SIZE(6))
			ACCESS	read-write
			STATUS	deprecated
			DESCRIPTION
                " Destination MAC Address of the Filtering entry."
			::= { accBrFilterEntry 1 }
	    accBrFilterEntSrcMacAddr	OBJECT-TYPE   
			SYNTAX	OCTET STRING -- (SIZE(6))
			ACCESS	read-write
			STATUS	deprecated
			DESCRIPTION
                " Source MAC Address of the Filtering entry."
			::= { accBrFilterEntry 2 }
	    accBrFilterEntDisp	OBJECT-TYPE   
			SYNTAX	INTEGER {
				forward	(1),
				discard	(2)
				}
			ACCESS	read-write
			STATUS	deprecated
			DESCRIPTION
                 " Disposition of received Frame. Note that a Frame is
                   never sent back out on the Port on which it was received."
			::= { accBrFilterEntry 3 }
	    accBrFilterEntPort	OBJECT-TYPE   
			SYNTAX	INTEGER
			ACCESS	read-write
			STATUS	deprecated
			DESCRIPTION
                " In all cases, the destination port of the received 
                  frame."
			::= { accBrFilterEntry 4 }
	    accBrFilterEntLogicalOp	OBJECT-TYPE   
			SYNTAX	INTEGER {
				any		(1),
				equal		(2),
				notequal	(3)
				}
			ACCESS	read-write
			STATUS	deprecated
			DESCRIPTION
                 " Logical operation to be performed in conjunction with
		   specified protocol. This is an optional parameter."
			::= { accBrFilterEntry 5 }
	    accBrFilterEntProtocol	OBJECT-TYPE   
			SYNTAX  OCTET STRING -- (SIZE(2))	
			ACCESS	read-write
			STATUS	deprecated
			DESCRIPTION
                 " Protocol to be used in conjunction with logical operation
		   to determine the disposition of all received packets."
			::= { accBrFilterEntry 6 }
-- This unfortunate arrangement is done to make the object id's in the MIB
-- align with those that are implemented. This will produce an error message
-- in smic.
	    accBrFilterDiscards	OBJECT-TYPE   
			SYNTAX	INTEGER
			ACCESS	read-only
			STATUS	deprecated
			DESCRIPTION
                 " The number of packets discarded as a result of bridge
		   filtering. Maintained globally for all ports."
			::= { accBrFilterEntry 7 }
	    accBrFilterEntries	OBJECT-TYPE   
			SYNTAX	INTEGER
			ACCESS	read-only
			STATUS	deprecated
			DESCRIPTION
                 " The number of entries currently in the bridge filtering
		   table. The maximum number of entries is 50."
			::= { accBrFilterEntry 8 }
-- Extensions to the original Bridge filter group
	accBrFiltIITable	OBJECT-TYPE
			SYNTAX SEQUENCE OF AccBrFiltIIEntry
			ACCESS not-accessible
			STATUS mandatory
			DESCRIPTION
                 " A list of Filtering entries."
			 ::= { accBridge 19 }
	  accBrFiltIIEntry OBJECT-TYPE
			SYNTAX AccBrFiltIIEntry
			ACCESS not-accessible
			STATUS mandatory
			DESCRIPTION
                " A Filtering entry which defines the SR action
                  to be taken based upon the destination AND source
                  MAC Addresses AFTER applying the address masks,
                  port number, port protocol and logic op of received frames."
                        INDEX {	accBrFiltIIEntDstMacAddr,
				accBrFiltIIEntDstMacAddrMask,
				accBrFiltIIEntSrcMacAddr,
				accBrFiltIIEntSrcMacAddrMask,
				accBrFiltIIEntPort,
				accBrFiltIIEntLogicalOp,
				accBrFiltIIEntProtocol}
			::= { accBrFiltIITable 1 }
	  AccBrFiltIIEntry  ::= SEQUENCE {
	    	accBrFiltIIEntDstMacAddr	OCTET STRING,
	    	accBrFiltIIEntDstMacAddrMask	OCTET STRING,
	    	accBrFiltIIEntSrcMacAddr	OCTET STRING,
	    	accBrFiltIIEntSrcMacAddrMask	OCTET STRING,
	    	accBrFiltIIEntPort		INTEGER,
	    	accBrFiltIIEntLogicalOp		INTEGER,
	    	accBrFiltIIEntProtocol		OCTET STRING,
	    	accBrFiltIIEntDisp		INTEGER,
	    	accBrFiltIIEntStatus		INTEGER
		}
	    accBrFiltIIEntDstMacAddr	OBJECT-TYPE   
			SYNTAX	OCTET STRING (SIZE(6))
			ACCESS	read-write
			STATUS	mandatory
			DESCRIPTION
                " Destination MAC Address of the Filtering entry."
			::= { accBrFiltIIEntry 1 }
	    accBrFiltIIEntSrcMacAddr	OBJECT-TYPE   
			SYNTAX	OCTET STRING (SIZE(6))
			ACCESS	read-write
			STATUS	mandatory
			DESCRIPTION
                " Source MAC Address of the Filtering entry."
			::= { accBrFiltIIEntry 2 }
	    accBrFiltIIEntDisp	OBJECT-TYPE   
			SYNTAX	INTEGER {
				forward	(1),
				discard	(2)
				}
			ACCESS	read-write
			STATUS	mandatory
			DESCRIPTION
                 " Disposition of received Frame. Note that a Frame is
                   never sent back out on the Port on which it was received."
			::= { accBrFiltIIEntry 3 }
	    accBrFiltIIEntPort	OBJECT-TYPE   
			SYNTAX	INTEGER
			ACCESS	read-write
			STATUS	mandatory
			DESCRIPTION
                " In all cases, the destination port of the received 
                  frame."
			::= { accBrFiltIIEntry 4 }
	    accBrFiltIIEntLogicalOp	OBJECT-TYPE   
			SYNTAX	INTEGER {
				any		(1),
				equal		(2),
				notequal	(3)
				}
			ACCESS	read-write
			STATUS	mandatory
			DESCRIPTION
                 " Logical operation to be performed in conjunction with
		   specified protocol. This is an optional parameter."
			::= { accBrFiltIIEntry 5 }
	    accBrFiltIIEntProtocol	OBJECT-TYPE   
			SYNTAX  OCTET STRING (SIZE(2))	
			ACCESS	read-write
			STATUS	mandatory
			DESCRIPTION
                 " Protocol to be used in conjunction with logical operation
		   to determine the disposition of all received packets."
			::= { accBrFiltIIEntry 6 }
	    accBrFiltIIEntDstMacAddrMask	OBJECT-TYPE   
			SYNTAX	OCTET STRING (SIZE(6))
			ACCESS	read-write
			STATUS	mandatory
			DESCRIPTION
                " Destination MAC Address Mask for the Filtering entry.
                  The mask is ANDed with the Destination address to
                  determine that part of the MAC address which is used in
                  the filtering decision."
			::= { accBrFiltIIEntry 7 }
	    accBrFiltIIEntSrcMacAddrMask	OBJECT-TYPE   
			SYNTAX	OCTET STRING (SIZE(6))
			ACCESS	read-write
			STATUS	mandatory
			DESCRIPTION
                " Source MAC Address Mask for the Filtering entry.
                  The mask is ANDed with the Source address to
                  determine that part of the MAC address which is used in
                  the filtering decision."
			::= { accBrFiltIIEntry 8 }
	    accBrFiltIIEntStatus	OBJECT-TYPE   
			SYNTAX	INTEGER
			ACCESS	read-write
			STATUS	mandatory
			DESCRIPTION
                " 0 indicates that the entry is invalid,
		  1 indicates that the entry is valid."
			::= { accBrFiltIIEntry 9 }
	    accBrFiltIIDiscards	OBJECT-TYPE   
			SYNTAX	INTEGER
			ACCESS	read-only
			STATUS	mandatory
			DESCRIPTION
                 " The number of packets discarded as a result of bridge
		   filtering. Maintained globally for all ports."
			::= { accBridge 20 }
	    accBrFiltIIEntries	OBJECT-TYPE   
			SYNTAX	INTEGER
			ACCESS	read-only
			STATUS	mandatory
			DESCRIPTION
                 " The number of entries currently in the bridge filtering
		   table. The maximum number of entries is 150."
			::= { accBridge 21 }
	    accFdbWhichAddr	OBJECT-TYPE   
                        SYNTAX  INTEGER {
                                destination      (1),
                                source           (2)
                                }
			ACCESS	read-write
			STATUS	mandatory
			DESCRIPTION
                 " Selects whether the MAC address in the forwarding
                   database is to be compared to the destination
                   or source MAC address in the traffic packets."
			::= { accBridge 22 }
-- Slot Group
     accSlot   OBJECT IDENTIFIER  ::= { accBRG 5 }
	accSlotTable	OBJECT-TYPE
			SYNTAX SEQUENCE OF AccSlotEntry
			ACCESS not-accessible
			STATUS mandatory
			DESCRIPTION
                 " A list of physical port entries.  The number of entries is
                   given by the value of accSlotNum."
			::= { accSlot 2 }
		AccSlotEntry ::= SEQUENCE {
	    		accSlotLastChange	OCTET STRING,
	    		accSlotInPkts		Counter,
	    		accSlotOutPkts		Counter,
	    		accSlotNumChanges	Counter,
	    		accSlotProtocol		INTEGER,
			accSlotClockMode	INTEGER,
			accSlotQueueMode	INTEGER,
	    		accSlotDialProcedure	INTEGER,
                        accSlotResyncMode	INTEGER,
                        accSlotCompressMode	INTEGER,
                      --accSlotCompressLength	INTEGER,
                        accSlotCompressV42bisP1	INTEGER,
                        accSlotCompressV42bisP2	INTEGER,
			accSlotCompressDcs221P1	INTEGER,
			accSlotSevereCongPct	INTEGER,
			accSlotDialAddress	DisplayString,
			accSlotCompressRevision INTEGER,
			accSlotCompressMaxStreams INTEGER,
			accSlotCompressMessageLevel INTEGER,
			accSlotIfType		 INTEGER
			}
	  accSlotEntry	OBJECT-TYPE
			SYNTAX AccSlotEntry
			ACCESS not-accessible
			STATUS mandatory
			DESCRIPTION
                 " A table entry providing information about a specific
                   physical port. "
                        INDEX { ifIndex }
			::= { accSlotTable 1 }
	    accSlotLastChange	OBJECT-TYPE   
			SYNTAX	OCTET STRING
			ACCESS	read-only
			STATUS	mandatory
			DESCRIPTION
                 " Time when a state change was last detected on this
                   physical port."
			::= { accSlotEntry 9 }
	    accSlotInPkts	OBJECT-TYPE   
			SYNTAX	Counter
			ACCESS	read-only
			STATUS	mandatory
			DESCRIPTION
                " Number of packets received on this physical interface."
			::= { accSlotEntry 11 }
	    accSlotOutPkts	OBJECT-TYPE   
			SYNTAX	Counter
			ACCESS	read-only
			STATUS	mandatory
			DESCRIPTION
                 " Number of  packets transmitted on this physical interface."
			::= { accSlotEntry 17 }
	    accSlotNumChanges	OBJECT-TYPE   
			SYNTAX	Counter
			ACCESS	read-only
			STATUS	mandatory
			DESCRIPTION
                 " Number of times that this interface has changed state
                   (either up-to-down or down-to-up)."
			::= { accSlotEntry 21 }
	    accSlotProtocol	OBJECT-TYPE   
			SYNTAX	INTEGER	 {
				enet(1),
				x25(2),
				lapb(3),
 				ffr(4),
				other(5),
				token-ring(6),
				smds(7),
				ppp(8),
				fddi(9),
				dial(10),
				multilink(11)
				}
			ACCESS	read-write
			STATUS	mandatory
			DESCRIPTION
			 " Protocol used on this slot.
 			   note that these enumerated values match those
 			   in accBrPortProtocol."
			::= { accSlotEntry 22 }
	    accSlotClockMode	OBJECT-TYPE   
			SYNTAX	INTEGER	 {
				unknown(1),
				ext1(2),
				pp(3),
 				ext2(4),
 				int(5),
 				slave(6)
				}
			ACCESS	read-write
			STATUS	mandatory
			DESCRIPTION
 			 " Clock mode of this port"
			::= { accSlotEntry 23 }
	    accSlotQueueMode	OBJECT-TYPE   
			SYNTAX	INTEGER	 {
				express(1),
				precedence(2)
				}
			ACCESS	read-write
			STATUS	mandatory
			DESCRIPTION
			 " Queuing mode for this slot
			   Fair queuing provides per-conversation
			    bandwidth allocation, with additional
			   bandwidth allocated to higher priority traffic.
			   Precedence queueing gives first-in-first-out
			   service amongst priority queues."
			::= { accSlotEntry 24 }
	    accSlotDialProcedure	OBJECT-TYPE
			SYNTAX  INTEGER  {
				lan(1),
				direct(2),
				x21(3),
				dtr(4),
				isdn(5),
				v25(6),
				hayes(7)
				}
			ACCESS  read-write
			STATUS  mandatory
			DESCRIPTION
			"Dial Procedure."
			::= { accSlotEntry 25 }
	    accSlotResyncMode	OBJECT-TYPE   
			SYNTAX	INTEGER	 {
				on(1),
				off(2)
				}
			ACCESS	read-write
			STATUS	mandatory
			DESCRIPTION
			 " Establishes operational mode of the
                           Resync function for crypto gear. 
                           When active, a link-down condition
                           intitiates resynchronization, which is
                           manifested by setting the DTR (RTS)
                           signal active (low) for 10 milliseconds."
			::= { accSlotEntry 26 }
	    accSlotCompressMode	OBJECT-TYPE   
			SYNTAX	INTEGER	 {
				off(1),
				on(2)
				}
			ACCESS	read-write
			STATUS	mandatory
			DESCRIPTION
			 " Establishes operational mode of Data
                           Compression.  This functionality is
                           appropriate for serial lines. "
			::= { accSlotEntry 27 }
	-- Not implemented yet.
	--  accSlotCompressLength	OBJECT-TYPE   
	--		SYNTAX	INTEGER	
	--		ACCESS	read-only
	--		STATUS	mandatory
	--		DESCRIPTION
	--		 " Minimum length of packet to compress "
	--		::= { accSlotEntry 28 }
	    accSlotCompressV42bisP1	OBJECT-TYPE   
			SYNTAX	INTEGER
			ACCESS	read-only
			STATUS	mandatory
			DESCRIPTION
			 " Number of codewords "
			::= { accSlotEntry 29 }
	    accSlotCompressV42bisP2	OBJECT-TYPE   
			SYNTAX	INTEGER	
			ACCESS	read-only
			STATUS	mandatory
			DESCRIPTION
			 " Maximum string size "
			::= { accSlotEntry 30 }
		accSlotCompressDcs221P1	OBJECT-TYPE
			SYNTAX	INTEGER (0..4)
			ACCESS  read-write
			STATUS  mandatory
			DESCRIPTION
			"Compression Mode"
			::= { accSlotEntry 31 }
		accSlotSevereCongPct	OBJECT-TYPE
			SYNTAX  INTEGER (1..100)
			ACCESS  read-write
			STATUS  mandatory
			DESCRIPTION
			"Percent Congested"
			::= { accSlotEntry 32 }
		accSlotDialAddress	OBJECT-TYPE
			SYNTAX  DisplayString 
			ACCESS  read-write
			STATUS  mandatory
			DESCRIPTION
			"Dial Address."
			::= { accSlotEntry 33 }
		accSlotCompressRevision OBJECT-TYPE
			SYNTAX INTEGER {
				old(1),
				new(2)
				}
			ACCESS  read-write
			STATUS  mandatory
			DESCRIPTION
				"Indicates which data compression algorithm
			should be used for this physical port. If the confi
			gured protocol is Frame Relay, X.25 or PPP, the com
			pression mode must be new. If the configured protocol
			is LAPB, OLD indicates that the neighbor is running
			a release which predates 7.2 and the old compression
			algorithm should be used."
			DEFVAL { new }
			::= { accSlotEntry 34 }
		accSlotCompressMaxStreams OBJECT-TYPE
			SYNTAX INTEGER
			ACCESS read-write
			STATUS mandatory
			DESCRIPTION
				" The maximum number of independent data
			streams for this physical port. This object determines
			the size of the history buffer pool."
			DEFVAL { 1 }
			::= { accSlotEntry 35 }
		accSlotCompressMessageLevel OBJECT-TYPE
			SYNTAX INTEGER
			ACCESS read-write
			STATUS mandatory
			DESCRIPTION
			"."
			::= { accSlotEntry 36 }
                accSlotIfType OBJECT-TYPE
                        SYNTAX INTEGER (0..44)
                        ACCESS read-write
                        STATUS mandatory
                        DESCRIPTION
                        "."
                        ::= { accSlotEntry 37 }
-- COMPRESSION Group
		accCompress OBJECT IDENTIFIER ::= { accBRG 6 }
		accCompressDialNeighborTable OBJECT-TYPE
			SYNTAX SEQUENCE OF AccCompressDialNeighborEntry
			ACCESS not-accessible
			STATUS mandatory
			DESCRIPTION
				"Data compression neighbor exception table
				for dial ports containing data compression
				parameters for selected neighbors."
			::= { accCompress 1 }
		accCompressDialNeighborEntry OBJECT-TYPE
			SYNTAX AccCompressDialNeighborEntry
			ACCESS not-accessible
			STATUS mandatory
			DESCRIPTION
				"Data compression neighbor exception table
				entry containing data compression parameters
				for a particular dial port neighbor."
			INDEX { accCompressDialNeighborIfIndex,
			accCompressDialNeighborCallAddress
			}
			::= { accCompressDialNeighborTable 1 }
		AccCompressDialNeighborEntry ::= SEQUENCE {
			accCompressDialNeighborIfIndex INTEGER,
			accCompressDialNeighborCallAddress DisplayString,
			accCompressDialNeighborStatus INTEGER
			}
		accCompressDialNeighborIfIndex OBJECT-TYPE
			SYNTAX INTEGER
			ACCESS read-only
			STATUS mandatory
			DESCRIPTION
				"The ifindex of the dial port via which the
				neighbor is accessed or connected."
			::= { accCompressDialNeighborEntry 1 }
		accCompressDialNeighborCallAddress OBJECT-TYPE
			SYNTAX DisplayString 
			ACCESS read-only
			STATUS mandatory
			DESCRIPTION
				"The call address of the neighbor to which
				the dial port is accessed or connected."
			::= { accCompressDialNeighborEntry 2 }
		accCompressDialNeighborStatus OBJECT-TYPE
			SYNTAX INTEGER {
				on(1),
				off(2),
				invalid(128)
			}
			ACCESS read-write
			STATUS mandatory
			DESCRIPTION
				"The administrative status of data
				compression for this dial neighbor.  ON
				enables data compression and OFF disables it.
				Setting the status to INVALID permanently
				removes the entry from the table."
			DEFVAL { off }
			::= { accCompressDialNeighborEntry 3 }
		accCompressFfrNeighborTable OBJECT-TYPE
			SYNTAX SEQUENCE OF AccCompressFfrNeighborEntry
			ACCESS not-accessible
			STATUS mandatory
			DESCRIPTION
				"Data compression neighbor exception table
				for frame relay circuits containing data
				compression parameters for selected
				neighbors."
			::= { accCompress 2 }
		accCompressFfrNeighborEntry OBJECT-TYPE
			SYNTAX AccCompressFfrNeighborEntry
			ACCESS not-accessible
			STATUS mandatory
			DESCRIPTION
				"Data compression neighbor exception table
				entry containing data compression parameters
				for a particular frame relay neighbor."
			INDEX { accCompressFfrNeighborIfIndex,
			accCompressFfrNeighborDlci }
			::= { accCompressFfrNeighborTable 1 }
		AccCompressFfrNeighborEntry ::= SEQUENCE {
			accCompressFfrNeighborIfIndex INTEGER,
			accCompressFfrNeighborDlci INTEGER,
			accCompressFfrNeighborStatus INTEGER }
		accCompressFfrNeighborIfIndex OBJECT-TYPE
			SYNTAX INTEGER
			ACCESS read-only
			STATUS mandatory
			DESCRIPTION
				"The physical port index via which the
				neighbor is accessed or connected."
			::= { accCompressFfrNeighborEntry 1 }
		accCompressFfrNeighborDlci OBJECT-TYPE
			SYNTAX INTEGER
			ACCESS read-only
			STATUS mandatory
			DESCRIPTION
				"A unique identifier for the neighbor.  In
				this case it is the local DLCI."
			::= { accCompressFfrNeighborEntry 2 }
		accCompressFfrNeighborStatus OBJECT-TYPE
			SYNTAX INTEGER {
				off(1),
				on(2),
				invalid(128)
			}
			ACCESS read-write
			STATUS mandatory
			DESCRIPTION
				"The administrative status of data
				compression for this neighbor.  ON enables
				data compression and OFF disables it.
				Setting the status to INVALID permanently
				removes the entry from the table."
			DEFVAL { off }
			::= { accCompressFfrNeighborEntry 3 }
		accCompressX25NeighborTable OBJECT-TYPE
			SYNTAX SEQUENCE OF AccCompressX25NeighborEntry
			ACCESS not-accessible
			STATUS mandatory
			DESCRIPTION
				"Data compression neighbor exception table
				for X25 circuits containing data compression
				parameters for selected neighbors."
			::= { accCompress 3 }
		accCompressX25NeighborEntry OBJECT-TYPE
			SYNTAX AccCompressX25NeighborEntry
			ACCESS not-accessible
			STATUS mandatory
			DESCRIPTION
				"Data compression neighbor exception table
				entry containing data compression parameters
				for a particular X.25 neighbor."
			INDEX { accCompressX25NeighborIfIndex,
			accCompressX25NeighborAddress }
			::= { accCompressX25NeighborTable 1 }
		AccCompressX25NeighborEntry ::= SEQUENCE {
			accCompressX25NeighborIfIndex INTEGER,
			accCompressX25NeighborAddress DisplayString,
			accCompressX25NeighborStatus INTEGER }
		accCompressX25NeighborIfIndex OBJECT-TYPE
			SYNTAX INTEGER
			ACCESS read-only
			STATUS mandatory
			DESCRIPTION
				"The physical port index via which the
				neighbor is accessed or connected."
			::= { accCompressX25NeighborEntry 1 }
		accCompressX25NeighborAddress OBJECT-TYPE
			SYNTAX  DisplayString 
			ACCESS read-only
			STATUS mandatory
			DESCRIPTION
				"A unique identifier for the neighbor.  This
				is the neighbor's DTE address"
			::= { accCompressX25NeighborEntry 2 }
		accCompressX25NeighborStatus OBJECT-TYPE
			SYNTAX INTEGER {
				off(1),
				on(2),
				invalid(128)
			}
			ACCESS read-write
			STATUS mandatory
			DESCRIPTION
				"The administrative status of data
				compression for this neighbor.  ON enables
				data compression and OFF disables it.
				Setting the status to INVALID permanently
				removes the entry from the table."
			DEFVAL { off }
			::= { accCompressX25NeighborEntry 3 }
--		Data Compression Statistics Table
		accCompressDialStatTable OBJECT-TYPE
			SYNTAX SEQUENCE OF AccCompressDialStatEntry
			ACCESS not-accessible
			STATUS mandatory
			DESCRIPTION
				"Data compression statistics table for dial
				ports containing data compression statistics
				for all active dial port neighbors."
			::= { accCompress 4 }
		accCompressDialStatEntry OBJECT-TYPE
			SYNTAX AccCompressDialStatEntry
			ACCESS not-accessible
			STATUS mandatory
			DESCRIPTION
				"Data compression dial port statistics table
				entry containing data compression statistics
				for a particular dial port neighbor."
			INDEX { accCompressDialStatIfIndex }
			::= { accCompressDialStatTable 1 }
		AccCompressDialStatEntry ::= SEQUENCE {
			accCompressDialStatIfIndex INTEGER,
			accCompressDialStatCallAddress OCTET STRING,
			accCompressDialStatStatus INTEGER,
			accCompressDialStatOctetsIns Counter,
			accCompressDialStatOctetsOuts Counter,
			accCompressDialStatPacketsIns Counter,
			accCompressDialStatPacketsOuts Counter,
			accCompressDialStatUnCompIns Counter,
			accCompressDialStatUnCompOuts Counter,
			accCompressDialStatAvgCompIn Gauge,
			accCompressDialStatAvgCompOut Gauge,
			accCompressDialStatHdrErrors Counter,
			accCompressDialStatResyncs Counter,
			accCompressDialStatNoEndMarks Counter,
			accCompressDialStatNoBufAvails Counter}
		accCompressDialStatIfIndex OBJECT-TYPE
			SYNTAX INTEGER
			ACCESS read-only
			STATUS mandatory
			DESCRIPTION
				"The interface index of the dial port via
				which the neighbor is accessed or connected."
			::= { accCompressDialStatEntry 1 }
		accCompressDialStatCallAddress OBJECT-TYPE
			SYNTAX OCTET STRING
			ACCESS read-only
			STATUS mandatory
			DESCRIPTION
				"The call address of the neighbor to which
				the dial port is currently connected."
			::= { accCompressDialStatEntry 2 }
		accCompressDialStatStatus OBJECT-TYPE
			SYNTAX INTEGER {
				disc(1),
				conn(2),
				sync(3),
				resync(4)
			}
			ACCESS read-only
			STATUS mandatory
			DESCRIPTION
				"The operational status of the neighbor."
			::= { accCompressDialStatEntry 3 }
		accCompressDialStatOctetsIns OBJECT-TYPE
			SYNTAX Counter
			ACCESS read-only
			STATUS mandatory
			DESCRIPTION
				"The total number of compressed octets
				presented for decompression."
			::= { accCompressDialStatEntry 4 }
		accCompressDialStatOctetsOuts OBJECT-TYPE
			SYNTAX Counter
			ACCESS read-only
			STATUS mandatory
			DESCRIPTION
				"The total number of compressed octets
				generated after compression."
			::= { accCompressDialStatEntry 5 }
		accCompressDialStatPacketsIns OBJECT-TYPE
			SYNTAX Counter
			ACCESS read-only
			STATUS mandatory
			DESCRIPTION
				"The total number of uncompressed packets
				generated by decompression."
			::= { accCompressDialStatEntry 6 }
		accCompressDialStatPacketsOuts OBJECT-TYPE
			SYNTAX Counter
			ACCESS read-only
			STATUS mandatory
			DESCRIPTION
				"The total number of uncompressed packets
				presented for compression."
			::= { accCompressDialStatEntry 7 }
		accCompressDialStatUnCompIns OBJECT-TYPE
			SYNTAX Counter
			ACCESS read-only
			STATUS mandatory
			DESCRIPTION
				"The total number of uncompressed packets
				presented for decompression (i.e., packets
				which could not be compressed and were
				therefore received in their uncompressed
				form)."
			::= { accCompressDialStatEntry 8 }
		accCompressDialStatUnCompOuts OBJECT-TYPE
			SYNTAX Counter
			ACCESS read-only
			STATUS mandatory
			DESCRIPTION
				"The total number of uncompressed packets
				presented for compression which could not be
				compressed (i.e., the packet expanded).
				These packets are transmitted in their
				uncompressed form."
			::= { accCompressDialStatEntry 9 }
		accCompressDialStatAvgCompIn OBJECT-TYPE
			SYNTAX Gauge
			ACCESS read-only
			STATUS mandatory
			DESCRIPTION
				"The average compression rate of packets
				presented for decompression expressed as a
				percentage between 0 and 100.  100% is the
				unattainable rate which could only be
				achieved by compressing all packets to zero
				bits."
			::= { accCompressDialStatEntry 10 }
		accCompressDialStatAvgCompOut OBJECT-TYPE
			SYNTAX Gauge
			ACCESS read-only
			STATUS mandatory
			DESCRIPTION
				"The average compression rate of packets
				presented for compression expressed as a
				percentage between 0 and 100.  100% is the
				unattainable rate which could only be
				achieved by compressing all packets to zero
				bits."
			::= { accCompressDialStatEntry 11 }
		accCompressDialStatHdrErrors OBJECT-TYPE
			SYNTAX Counter
			ACCESS read-only
			STATUS mandatory
			DESCRIPTION
				"The number of packets received with invalid
				compression headers.  A header error requires
				a resynchronization of the history buffers at
				each end of the link."
			::= { accCompressDialStatEntry 12 }
		accCompressDialStatResyncs OBJECT-TYPE
			SYNTAX Counter
			ACCESS read-only
			STATUS mandatory
			DESCRIPTION
				"The number of resynchronizations."
			::= { accCompressDialStatEntry 13 }
		accCompressDialStatNoEndMarks OBJECT-TYPE
		SYNTAX Counter
			ACCESS read-only
			STATUS mandatory
			DESCRIPTION
				"The number of packets received with no end
				marker.  Missing end markers require a
				resynchronization of the history buffers at
				each end of the link."
			::= { accCompressDialStatEntry 14 }
		accCompressDialStatNoBufAvails OBJECT-TYPE
			SYNTAX Counter
			ACCESS read-only
			STATUS mandatory
			DESCRIPTION
				"The number of times the neighbor was
				connected and no history buffer could be
				allocated."
			::= { accCompressDialStatEntry 15 }
		accCompressFfrStatTable OBJECT-TYPE
			SYNTAX SEQUENCE OF AccCompressFfrStatEntry
			ACCESS not-accessible
			STATUS mandatory
			DESCRIPTION
				"Data compression statistics table containing
				data compression statistics for all active
				frame relay neighbors."
			::= { accCompress 5 }
		accCompressFfrStatEntry OBJECT-TYPE
			SYNTAX AccCompressFfrStatEntry
			ACCESS not-accessible
			STATUS mandatory
			DESCRIPTION
				"Data compression statistics table entry
				containing data compression statistics for a
				particular frame relay neighbor."
			INDEX { accCompressFfrStatIfIndex,
			accCompressFfrStatDlci }
			::= { accCompressFfrStatTable 1 }
		AccCompressFfrStatEntry ::= SEQUENCE {
			accCompressFfrStatIfIndex INTEGER,
			accCompressFfrStatDlci INTEGER,
			accCompressFfrStatStatus INTEGER,
			accCompressFfrStatOctetsIns Counter,
			accCompressFfrStatOctetsOuts Counter,
			accCompressFfrStatPacketsIns Counter,
			accCompressFfrStatPacketsOuts Counter,
			accCompressFfrStatUnCompIns Counter,
			accCompressFfrStatUnCompOuts Counter,
			accCompressFfrStatAvgCompIn Gauge,
			accCompressFfrStatAvgCompOut Gauge,
			accCompressFfrStatHdrErrors Counter,
			accCompressFfrStatResyncs Counter,
			accCompressFfrStatNoEndMarks Counter,
			accCompressFfrStatNoBufAvails Counter}
		accCompressFfrStatIfIndex OBJECT-TYPE
			SYNTAX INTEGER
			ACCESS read-only
			STATUS mandatory
			DESCRIPTION
				"The physical port index of the port via
				which the neighbor is accessed or connected."
			::= { accCompressFfrStatEntry 1 }
		accCompressFfrStatDlci OBJECT-TYPE
			SYNTAX INTEGER
			ACCESS read-only
			STATUS mandatory
			DESCRIPTION
				"This is the local DLCI for the frame relay
				neighbor."
			::= { accCompressFfrStatEntry 2 }
		accCompressFfrStatStatus OBJECT-TYPE
			SYNTAX INTEGER {
				disc(1),
				conn(2),
				sync(3),
				resync(4)
			}
			ACCESS read-only
			STATUS mandatory
			DESCRIPTION
				"The operational status of the neighbor."
			::= { accCompressFfrStatEntry 3 }
		accCompressFfrStatOctetsIns OBJECT-TYPE
			SYNTAX Counter
			ACCESS read-only
			STATUS mandatory
			DESCRIPTION
				"The total number of compressed octets
				presented for decompression."
			::= { accCompressFfrStatEntry 4 }
		accCompressFfrStatOctetsOuts OBJECT-TYPE
			SYNTAX Counter
			ACCESS read-only
			STATUS mandatory
			DESCRIPTION
				"The total number of compressed octets
				generated after compression."
			::= { accCompressFfrStatEntry 5 }
		accCompressFfrStatPacketsIns OBJECT-TYPE
			SYNTAX Counter
			ACCESS read-only
			STATUS mandatory
			DESCRIPTION
				"The total number of uncompressed packets
				generated by decompression."
			::= { accCompressFfrStatEntry 6 }
		accCompressFfrStatPacketsOuts OBJECT-TYPE
			SYNTAX Counter
			ACCESS read-only
			STATUS mandatory
			DESCRIPTION
				"The total number of uncompressed packets
				presented for compression."
			::= { accCompressFfrStatEntry 7 }
		accCompressFfrStatUnCompIns OBJECT-TYPE
			SYNTAX Counter
			ACCESS read-only
			STATUS mandatory
			DESCRIPTION
				"The total number of uncompressed packets
				presented for decompression (i.e., packets
				which could not be compressed and were
				therefore received in their uncompressed
				form)."
			::= { accCompressFfrStatEntry 8 }
		accCompressFfrStatUnCompOuts OBJECT-TYPE
			SYNTAX Counter
			ACCESS read-only
			STATUS mandatory
			DESCRIPTION
				"The total number of uncompressed packets
				presented for compression which could not be
				compressed (i.e., the packet expanded).
				These packets are transmitted in their
				uncompressed form."
			::= { accCompressFfrStatEntry 9 }
		accCompressFfrStatAvgCompIn OBJECT-TYPE
			SYNTAX Gauge
			ACCESS read-only
			STATUS mandatory
			DESCRIPTION
				"The average compression rate of packets
				presented for decompression expressed as a
				percentage between 0 and 100.  100% is the
				unattainable rate which could only be
				achieved by compressing all packets to zero
				bits."
			::= { accCompressFfrStatEntry 10 }
		accCompressFfrStatAvgCompOut OBJECT-TYPE
			SYNTAX Gauge
			ACCESS read-only
			STATUS mandatory
			DESCRIPTION
				"The average compression rate of packets
				presented for compression expressed as a
				percentage between 0 and 100.  100% is the
				unattainable rate which could only be
				achieved by compressing all packets to zero
				bits."
			::= { accCompressFfrStatEntry 11 }
		accCompressFfrStatHdrErrors OBJECT-TYPE
			SYNTAX Counter
			ACCESS read-only
			STATUS mandatory
			DESCRIPTION
				"The number of packets received with invalid
				compression headers.  A header error requires
				a resynchronization of the history buffers at
				each end of the link."
			::= { accCompressFfrStatEntry 12 }
		accCompressFfrStatResyncs OBJECT-TYPE
			SYNTAX Counter
			ACCESS read-only
			STATUS mandatory
			DESCRIPTION
				"The number of resynchronizations."
			::= { accCompressFfrStatEntry 13 }
		accCompressFfrStatNoEndMarks OBJECT-TYPE
			SYNTAX Counter
			ACCESS read-only
			STATUS mandatory
			DESCRIPTION
				"The number of packets received with no end
				marker.  Missing end markers require a
				resynchronization of the history buffers at
				each end of the link."
			::= { accCompressFfrStatEntry 14 }
		accCompressFfrStatNoBufAvails OBJECT-TYPE
			SYNTAX Counter
			ACCESS read-only
			STATUS mandatory
			DESCRIPTION
				"The number of times the neighbor was
				connected and no history buffer could be
				allocated."
			::= { accCompressFfrStatEntry 15 }
		accCompressX25StatTable OBJECT-TYPE
		SYNTAX SEQUENCE OF AccCompressX25StatEntry
			ACCESS not-accessible
			STATUS mandatory
			DESCRIPTION
				"Data compression statistics table containing
				data compression statistics for all active
				X.25 neighbors."
			::= { accCompress 6 }
		accCompressX25StatEntry OBJECT-TYPE
			SYNTAX AccCompressX25StatEntry
			ACCESS not-accessible
			STATUS mandatory
			DESCRIPTION
				"Data compression statistics table entry
				containing data compression statistics for a
				particular X.25 neighbor."
			INDEX { accCompressX25StatIfIndex, 
				accCompressX25StatAddress }
			::= { accCompressX25StatTable 1 }
		AccCompressX25StatEntry ::= SEQUENCE {
			accCompressX25StatIfIndex INTEGER,
			accCompressX25StatAddress OCTET STRING,
			accCompressX25StatStatus INTEGER,
			accCompressX25StatOctetsIns Counter,
			accCompressX25StatOctetsOuts Counter,
			accCompressX25StatPacketsIns Counter,
			accCompressX25StatPacketsOuts Counter,
			accCompressX25StatUnCompIns Counter,
			accCompressX25StatUnCompOuts Counter,
			accCompressX25StatAvgCompIn Gauge,
			accCompressX25StatAvgCompOut Gauge,
			accCompressX25StatHdrErrors Counter,
			accCompressX25StatResyncs Counter,
			accCompressX25StatNoEndMarks Counter,
			accCompressX25StatNoBufAvails Counter}
		accCompressX25StatIfIndex OBJECT-TYPE
			SYNTAX INTEGER
			ACCESS read-only
			STATUS mandatory
			DESCRIPTION
				"The physical port index of the port via
				which the neighbor is accessed or connected."
			::= { accCompressX25StatEntry 1 }
		accCompressX25StatAddress OBJECT-TYPE
			SYNTAX OCTET STRING
			ACCESS read-only
			STATUS mandatory
			DESCRIPTION
				"DTE address for the X.25 neighbor."
			::= { accCompressX25StatEntry 2 }
		accCompressX25StatStatus OBJECT-TYPE
			SYNTAX INTEGER {
				disc(1),
				conn(2),
				sync(3),
				resync(4)
			}
			ACCESS read-only
			STATUS mandatory
			DESCRIPTION
				"The operational status of the neighbor."
			::= { accCompressX25StatEntry 3 }
		accCompressX25StatOctetsIns OBJECT-TYPE
			SYNTAX Counter
			ACCESS read-only
			STATUS mandatory
			DESCRIPTION
				"The total number of compressed octets
				presented for decompression."
			::= { accCompressX25StatEntry 4 }
		accCompressX25StatOctetsOuts OBJECT-TYPE
			SYNTAX Counter
			ACCESS read-only
			STATUS mandatory
			DESCRIPTION
				"The total number of compressed octets
				generated after compression."
			::= { accCompressX25StatEntry 5 }
		accCompressX25StatPacketsIns OBJECT-TYPE
			SYNTAX Counter
			ACCESS read-only
			STATUS mandatory
			DESCRIPTION
				"The total number of uncompressed packets
				generated by decompression."
			::= { accCompressX25StatEntry 6 }
		accCompressX25StatPacketsOuts OBJECT-TYPE
			SYNTAX Counter
			ACCESS read-only
			STATUS mandatory
			DESCRIPTION
				"The total number of uncompressed packets
				presented for compression."
			::= { accCompressX25StatEntry 7 }
		accCompressX25StatUnCompIns OBJECT-TYPE
			SYNTAX Counter
			ACCESS read-only
			STATUS mandatory
			DESCRIPTION
				"The total number of uncompressed packets
				presented for decompression (i.e., packets
				which could not be compressed and were
				therefore received in their uncompressed
				form)."
			::= { accCompressX25StatEntry 8 }
		accCompressX25StatUnCompOuts OBJECT-TYPE
			SYNTAX Counter
			ACCESS read-only
			STATUS mandatory
			DESCRIPTION
				"The total number of uncompressed packets
				presented for compression which could not be
				compressed (i.e., the packet expanded).
				These packets are transmitted in their
				uncompressed form."
			::= { accCompressX25StatEntry 9 }
		accCompressX25StatAvgCompIn OBJECT-TYPE
			SYNTAX Gauge
			ACCESS read-only
			STATUS mandatory
			DESCRIPTION
				"The average compression rate of packets
				presented for decompression expressed as a
				percentage between 0 and 100.  100% is the
				unattainable rate which could only be
				achieved by compressing all packets to zero
				bits."
			::= { accCompressX25StatEntry 10 }
		accCompressX25StatAvgCompOut OBJECT-TYPE
			SYNTAX Gauge
			ACCESS read-only
			STATUS mandatory
			DESCRIPTION
				"The average compression rate of packets
				presented for compression expressed as a
				percentage between 0 and 100.  100% is the
				unattainable rate which could only be
				achieved by compressing all packets to zero
				bits."
			::= { accCompressX25StatEntry 11 }
		accCompressX25StatHdrErrors OBJECT-TYPE
			SYNTAX Counter
			ACCESS read-only
			STATUS mandatory
			DESCRIPTION
				"The number of packets received with invalid
				compression headers.  A header error requires
				a resynchronization of the history buffers at
				each end of the link."
			::= { accCompressX25StatEntry 12 }
		accCompressX25StatResyncs OBJECT-TYPE
			SYNTAX Counter
			ACCESS read-only
			STATUS mandatory
			DESCRIPTION
				"The number of resynchronizations."
			::= { accCompressX25StatEntry 13 }
		accCompressX25StatNoEndMarks OBJECT-TYPE
			SYNTAX Counter
			ACCESS read-only
			STATUS mandatory
			DESCRIPTION
				"The number of packets received with no end
				marker.  Missing end markers require a
				resynchronization of the history buffers at
				each end of the link."
			::= { accCompressX25StatEntry 14 }
		accCompressX25StatNoBufAvails OBJECT-TYPE
			SYNTAX Counter
			ACCESS read-only
			STATUS mandatory
			DESCRIPTION
				"The number of times the neighbor was
				connected and no history buffer could be
				allocated."
			::= { accCompressX25StatEntry 15 }
		accCompressPhysStatTable OBJECT-TYPE
			SYNTAX SEQUENCE OF AccCompressPhysStatEntry
			ACCESS not-accessible
			STATUS mandatory
			DESCRIPTION
				"Data compression statistics table for
				physical ports containing aggregate data
				compression statistics for all active and
				inactive neighbors."
			::= { accCompress 7 }
		accCompressPhysStatEntry OBJECT-TYPE
			SYNTAX AccCompressPhysStatEntry
			ACCESS not-accessible
			STATUS mandatory
			DESCRIPTION
				"Data compression statistics table entry
				containing aggregate data compression
				statistics for all neighbors through a
				particular physical port."
			INDEX { accCompressPhysStatIfIndex }
			::= { accCompressPhysStatTable 1 }
		AccCompressPhysStatEntry ::= SEQUENCE {
			accCompressPhysStatIfIndex INTEGER,
			accCompressPhysStatStatus INTEGER,
			accCompressPhysStatOctetsIns Counter,
			accCompressPhysStatOctetsOuts Counter,
			accCompressPhysStatPacketsIns Counter,
			accCompressPhysStatPacketsOuts Counter,
			accCompressPhysStatUnCompIns Counter,
			accCompressPhysStatUnCompOuts Counter,
			accCompressPhysStatAvgCompIn Gauge,
			accCompressPhysStatAvgCompOut Gauge,
			accCompressPhysStatHdrErrors Counter,
			accCompressPhysStatResyncs Counter,
			accCompressPhysStatNoEndMarks Counter,
			accCompressPhysStatNoBufAvails Counter}
		accCompressPhysStatIfIndex OBJECT-TYPE
			SYNTAX INTEGER
			ACCESS read-only
			STATUS mandatory
			DESCRIPTION
				"The index of the physical port via which the
				neighbor(s) is(are) accessed or connected."
			::= { accCompressPhysStatEntry 1 }
		accCompressPhysStatStatus OBJECT-TYPE
			SYNTAX INTEGER {
				disc(1),
				conn(2),
				sync(3),
				resync(4)
			}
			ACCESS read-only
			STATUS mandatory
			DESCRIPTION
				"The operational status of the neighbor. For
				X.25 and Frame Relay ports, as there can be
				more than one neighbor, this is the superior
				status."
			::= { accCompressPhysStatEntry 2 }
		accCompressPhysStatOctetsIns OBJECT-TYPE
			SYNTAX Counter
			ACCESS read-only
			STATUS mandatory
			DESCRIPTION
				"The total number of compressed octets
				presented for decompression."
			::= { accCompressPhysStatEntry 3 }
		accCompressPhysStatOctetsOuts OBJECT-TYPE
			SYNTAX Counter
			ACCESS read-only
			STATUS mandatory
			DESCRIPTION
				"The total number of compressed octets
				generated after compression."
			::= { accCompressPhysStatEntry 4 }
		accCompressPhysStatPacketsIns OBJECT-TYPE
			SYNTAX Counter
			ACCESS read-only
			STATUS mandatory
			DESCRIPTION
				"The total number of uncompressed packets
				generated by decompression."
			::= { accCompressPhysStatEntry 5 }
		accCompressPhysStatPacketsOuts OBJECT-TYPE
			SYNTAX Counter
			ACCESS read-only
			STATUS mandatory
			DESCRIPTION
				"The total number of uncompressed packets
				presented for compression."
			::= { accCompressPhysStatEntry 6 }
		accCompressPhysStatUnCompIns OBJECT-TYPE
			SYNTAX Counter
			ACCESS read-only
			STATUS mandatory
			DESCRIPTION
				"The total number of uncompressed packets
				presented for decompression (i.e., packets
				which could not be compressed and were
				therefore received in their uncompressed
				form)."
			::= { accCompressPhysStatEntry 7 }
		accCompressPhysStatUnCompOuts OBJECT-TYPE
			SYNTAX Counter
			ACCESS read-only
			STATUS mandatory
			DESCRIPTION
				"The total number of uncompressed packets
				presented for compression which could not be
				compressed (i.e., the packet expanded).
				These packets are transmitted in their
				uncompressed form."
			::= { accCompressPhysStatEntry 8 }
		accCompressPhysStatAvgCompIn OBJECT-TYPE
			SYNTAX Gauge
			ACCESS read-only
			STATUS mandatory
			DESCRIPTION
				"The average compression rate of packets
				presented for decompression expressed as a
				percentage between 0 and 100.  100% is the
				unattainable rate which could only be
				achieved by compressing all packets to zero
				bits."
			::= { accCompressPhysStatEntry 9 }
		accCompressPhysStatAvgCompOut OBJECT-TYPE
			SYNTAX Gauge
			ACCESS read-only
			STATUS mandatory
			DESCRIPTION
				"The average compression rate of packets
				presented for compression expressed as a
				percentage between 0 and 100.  100% is the
				unattainable rate which could only be
				achieved by compressing all packets to zero
				bits."
			::= { accCompressPhysStatEntry 10 }
		accCompressPhysStatHdrErrors OBJECT-TYPE
			SYNTAX Counter
			ACCESS read-only
			STATUS mandatory
			DESCRIPTION
				"The number of packets received with invalid
				compression headers.  A header error requires
				a resynchronization of the history buffers at
				each end of the link."
			::= { accCompressPhysStatEntry 11 }
		accCompressPhysStatResyncs OBJECT-TYPE
			SYNTAX Counter
			ACCESS read-only
			STATUS mandatory
			DESCRIPTION
				"The number of resynchronizations."
			::= { accCompressPhysStatEntry 12 }
		accCompressPhysStatNoEndMarks OBJECT-TYPE
			SYNTAX Counter
			ACCESS read-only
			STATUS mandatory
			DESCRIPTION
				"The number of packets received with no end
				marker.  Missing end markers require a
				resynchronization of the history buffers at
				each end of the link."
			::= { accCompressPhysStatEntry 13 }
		accCompressPhysStatNoBufAvails OBJECT-TYPE
			SYNTAX Counter
			ACCESS read-only
			STATUS mandatory
			DESCRIPTION
				"The number of times the neighbor was
				connected and no history buffer could be
				allocated."
			::= { accCompressPhysStatEntry 14 }
-- LAPB Group
      accLapb    OBJECT IDENTIFIER ::= { accBRG 7 }
	accLapbNum	OBJECT-TYPE   
			SYNTAX	INTEGER
			ACCESS	read-only
			STATUS	mandatory
			DESCRIPTION
			 " Number of HDLC ports"
			::= { accLapb 1 }
	accLapbParmTable	OBJECT-TYPE
			SYNTAX	SEQUENCE OF AccLapbParmEntry
			ACCESS	not-accessible
			STATUS	mandatory
			DESCRIPTION
			 " HDLC LAPB port parameters"
			::= { accLapb 2 }
          accLapbParmEntry      OBJECT-TYPE
                        SYNTAX  AccLapbParmEntry
                        ACCESS  not-accessible
                        STATUS  mandatory
                        DESCRIPTION
                         " LAPB parameters for a port."
                        INDEX { accLapbIndex }
                        ::= { accLapbParmTable 1 }
			AccLapbParmEntry ::= SEQUENCE {
			    accLapbIndex	INTEGER,
			    accLapbType		INTEGER,
			    accLapbT1Timer	INTEGER,
			    accLapbN2Count	INTEGER,
			    accLapbFrameWindow	INTEGER,
			    accLapbFlags	INTEGER,
			    accHdlcRrPolling	INTEGER,
			    accHdlcFCS		INTEGER
			    }
	    accLapbIndex	OBJECT-TYPE   
			SYNTAX	INTEGER
			ACCESS	read-only
			STATUS	mandatory
			DESCRIPTION
			 " Physical port number of this interface."
			::= { accLapbParmEntry 1 }
	    accLapbType		OBJECT-TYPE   
			SYNTAX	INTEGER (0..1)
			ACCESS	read-write
			STATUS	mandatory
			DESCRIPTION
			 " LAPB station type for this interface.
				dte(0),
				dce(1)
			"
			::= { accLapbParmEntry 2 }
	    accLapbT1Timer	OBJECT-TYPE   
			SYNTAX	INTEGER (1..32000)
			ACCESS	read-write
			STATUS	mandatory
			DESCRIPTION
			 " T1 timer value (in milliseconds) for this
			   interface."
                        DEFVAL { 3000 }
			::= { accLapbParmEntry 3 }
	    accLapbN2Count	OBJECT-TYPE   
			SYNTAX	INTEGER (2..20)
			ACCESS	read-write
			STATUS	mandatory
			DESCRIPTION
			 " N2 counter (retry counter) for this interface."
                        DEFVAL { 20 }
			::= { accLapbParmEntry 4 }
	    accLapbFrameWindow	OBJECT-TYPE   
			SYNTAX	INTEGER (1..127)
			ACCESS	read-write
			STATUS	mandatory
			DESCRIPTION
			 " LAPB frame window.  If a value greater than
			   7 is specified, modulo-128 sequencing is used
			   instead of modulo-8 sequencing."
                        DEFVAL { 7 }
			::= { accLapbParmEntry 5 }
	    accLapbFlags	OBJECT-TYPE   
			SYNTAX	INTEGER (1..32)
			ACCESS	read-write
			STATUS	mandatory
			DESCRIPTION
			 " Number of flags to insert between frames
			   on transmission."
                        DEFVAL { 2 }
			::= { accLapbParmEntry 6 }
	    accHdlcRrPolling	OBJECT-TYPE
			SYNTAX  INTEGER (1..32000)
			ACCESS	read-write
			STATUS	mandatory
			DESCRIPTION
			"T3 Timer."
			::= { accLapbParmEntry 7 }
	    accHdlcFCS	OBJECT-TYPE
			SYNTAX  INTEGER  {
				ccitt-16(1),
				ccitt-32(2)
				}
			ACCESS	read-write
			STATUS	mandatory
			DESCRIPTION
			"FCS Mode."
			::= { accLapbParmEntry 8 }
	accLapbStatTable    OBJECT-TYPE
			SYNTAX SEQUENCE OF AccLapbStatEntry
			ACCESS not-accessible
			STATUS mandatory
			DESCRIPTION
                          " A list of statistics for serial ports
                            configured for LABP protocol."
			::= { accLapb 3 }
          accLapbStatEntry  OBJECT-TYPE
                        SYNTAX AccLapbStatEntry
                        ACCESS not-accessible
                        STATUS mandatory
                        DESCRIPTION
                          " LAPB statistics for a specific port."
                        INDEX { accLapbStatIndex }
                        ::= { accLapbStatTable 1 }
		AccLapbStatEntry ::= SEQUENCE {
	    		accLapbStatIndex	INTEGER,
	    		accLapbStatBadFCSIns	Counter,
	    		accLapbStatFRMRIns	Counter,
	    		accLapbStatT1Timeouts 	Counter,
	    		accLapbStatREJIns 	Counter,
	    		accLapbStatREJOuts	Counter,
	    		accLapbStatShortIns	Counter
			}
	    accLapbStatIndex  OBJECT-TYPE    
			SYNTAX	INTEGER
			ACCESS	read-only
			STATUS	mandatory
			DESCRIPTION
                          " Port number for this LAPB serial port"
			::= { accLapbStatEntry 1 }
	    accLapbStatBadFCSIns  OBJECT-TYPE  
			SYNTAX	Counter
			ACCESS	read-only
			STATUS	mandatory
			DESCRIPTION
                          " Number of LAPB frames received with bad
                            frame checksum (FCS)."
			::= { accLapbStatEntry 2 }
	    accLapbStatFRMRIns	OBJECT-TYPE  
			SYNTAX	Counter
			ACCESS	read-only
			STATUS	mandatory
			DESCRIPTION
                          " Number of LAPB frames received with
                            framing errors"
			::= { accLapbStatEntry 3 }
	    accLapbStatT1Timeouts  OBJECT-TYPE	
			SYNTAX	Counter
			ACCESS	read-only
			STATUS	mandatory
			DESCRIPTION
                          " Number of T1 timeouts detected on this port"
			::= { accLapbStatEntry 4 }
	    accLapbStatREJIns  OBJECT-TYPE  
			SYNTAX	Counter
			ACCESS	read-only
			STATUS	mandatory
			DESCRIPTION
                          " number of REJECT LAPB frames received"
			::= { accLapbStatEntry 5 }
	    accLapbStatREJOuts	OBJECT-TYPE  
			SYNTAX	Counter
			ACCESS	read-only
			STATUS	mandatory
			DESCRIPTION
                          " Number of LAPB REJECT frames transmitted"
			::= { accLapbStatEntry 6 }
	    accLapbStatShortIns	 OBJECT-TYPE  
			SYNTAX	Counter
			ACCESS	read-only
			STATUS	mandatory
			DESCRIPTION
                          " Number of short LAPB frames received"
			::= { accLapbStatEntry 7 }
-- Ethernet Group
     accEnet   OBJECT IDENTIFIER  ::= { accBRG 8 }
	accEnetNum	OBJECT-TYPE   
			SYNTAX	INTEGER
			ACCESS	read-only
			STATUS	mandatory
			DESCRIPTION
               		 " Number of Ethernet ports on this unit."
			::= { accEnet 1 }
	accEnetParmTable	OBJECT-TYPE
			SYNTAX SEQUENCE OF AccEnetParmEntry
			ACCESS not-accessible
			STATUS mandatory
			 DESCRIPTION
                          " A table of parameters of Ethernet ports
                            The number of table entries is accEnetNum."
			 ::= { accEnet 2 }
	  accEnetParmEntry  OBJECT-TYPE
			SYNTAX AccEnetParmEntry
			ACCESS not-accessible
			STATUS mandatory
			DESCRIPTION
                           " Parameters relative to a specific Ethernet port."
                        INDEX { accEnetPortNo }
			::= { accEnetParmTable 1 }
             AccEnetParmEntry ::= SEQUENCE {
			accEnetPortNo      INTEGER
			}
	    accEnetPortNo  OBJECT-TYPE   
			SYNTAX	INTEGER
			ACCESS	read-only
			STATUS	mandatory
			DESCRIPTION
                         " Number of this ethernet port."
			::= { accEnetParmEntry 1 }
	accEnetStatTable  OBJECT-TYPE
			SYNTAX SEQUENCE OF AccEnetStatEntry
			ACCESS not-accessible
			STATUS mandatory
			DESCRIPTION
                         " A list of per-port statistics for ports
                           configured as Ethernet LANs."
			::= { accEnet 3 }
	  accEnetStatEntry  OBJECT-TYPE
			SYNTAX AccEnetStatEntry
			ACCESS not-accessible
			STATUS mandatory
			DESCRIPTION
                         " Statistics for specific ethernet ports."
                        INDEX { accEnetIndex }
			::= { accEnetStatTable 1 }
		AccEnetStatEntry ::= SEQUENCE {
	    		accEnetIndex			INTEGER,
	    		accEnetStatCRCErrs		Counter,
	    		accEnetStatAlignErrs 		Counter,
	    		accEnetStatOutColls		Counter,
	    		accEnetStatJabberConds 		Counter,
	    		accEnetStatCarrierLosts 	Counter,
	    		accEnetStatHeartbeatErrs 	Counter,
	    		accEnetStatGiants 		Counter,
	    		accEnetStatOneRetrys 		Counter,
	    		accEnetStatMultRetrys 		Counter,
	    		accEnetStatLateColls 		Counter,
	    		accEnetChipCrashes 		Counter
			}
	    accEnetIndex	OBJECT-TYPE   
			SYNTAX	INTEGER
			ACCESS	read-only
			STATUS	mandatory
			DESCRIPTION
                          " Port number of this entry"
			::= { accEnetStatEntry 1 }
	    accEnetStatCRCErrs	OBJECT-TYPE 
			SYNTAX	Counter
			ACCESS	read-only
			STATUS	mandatory
			DESCRIPTION
                          " Number of CRC (Checksum) errors detected on this
                            port."
			::= { accEnetStatEntry 2 }
	    accEnetStatAlignErrs  OBJECT-TYPE 
			SYNTAX	Counter
			ACCESS	read-only
			STATUS	mandatory
			DESCRIPTION
                          " Number of alignment errors detected."
			::= { accEnetStatEntry 3 }
	    accEnetStatOutColls	 OBJECT-TYPE 
			SYNTAX	Counter
			ACCESS	read-only
			STATUS	mandatory
			DESCRIPTION
                          " Number of collisions detected on output."
			::= { accEnetStatEntry 4 }
	    accEnetStatJabberConds  OBJECT-TYPE 
			SYNTAX	Counter
			ACCESS	read-only
			STATUS	mandatory
			DESCRIPTION
                          " Number of jabber conditions detected."
			::= { accEnetStatEntry 5 }
	    accEnetStatCarrierLosts  OBJECT-TYPE 
			SYNTAX	Counter
			ACCESS	read-only
			STATUS	mandatory
			DESCRIPTION
                          " Number of losses of carrier detected."
			::= { accEnetStatEntry 6 }
	    accEnetStatHeartbeatErrs  OBJECT-TYPE 
			SYNTAX	Counter
			ACCESS	read-only
			STATUS	mandatory
			DESCRIPTION
                          " Number of heartbeat errors detected."
			::= { accEnetStatEntry 7 }
	    accEnetStatGiants  OBJECT-TYPE 
			SYNTAX	Counter
			ACCESS	read-only
			STATUS	mandatory
			DESCRIPTION
                          " Number of giant frames detected."
			::= { accEnetStatEntry 8 }
	    accEnetStatOneRetrys  OBJECT-TYPE 
			SYNTAX	Counter
			ACCESS	read-only
			STATUS	mandatory
			DESCRIPTION
                          " Number of times a retry condition was detected."
			::= { accEnetStatEntry 9 }
	    accEnetStatMultRetrys  OBJECT-TYPE 
			SYNTAX	Counter
			ACCESS	read-only
			STATUS	mandatory
			DESCRIPTION
                           " Total number of retries."
			::= { accEnetStatEntry 10 }
	    accEnetStatLateColls  OBJECT-TYPE 
			SYNTAX	Counter
			ACCESS	read-only
			STATUS	mandatory
			DESCRIPTION
                          " Number of late collisions detected."
			::= { accEnetStatEntry 11 }
	    accEnetChipCrashes  OBJECT-TYPE 
			SYNTAX	Counter
			ACCESS	read-only
			STATUS	mandatory
			DESCRIPTION
                          " Number of times aberrant behaviour
			    was detected in Ethernet chip"
			::= { accEnetStatEntry 12 }
-- Multilink Group
      accMultilink      OBJECT IDENTIFIER ::= { accBRG 9 }
accMultilinkParameterTable OBJECT-TYPE
	SYNTAX SEQUENCE OF AccMultilinkParameterEntry
	ACCESS not-accessible
	STATUS mandatory
	DESCRIPTION
		" "
      ::= { accMultilink 1 }
accMultilinkParameterEntry OBJECT-TYPE
	SYNTAX AccMultilinkParameterEntry
	ACCESS not-accessible
	STATUS mandatory
	DESCRIPTION
		" "
	INDEX { accMultilinkParameterIndex }
      ::= { accMultilinkParameterTable 1 }
AccMultilinkParameterEntry ::= SEQUENCE {
	accMultilinkParameterIndex		INTEGER,
	accMultilinkParameterIfIndex		INTEGER,
	accMultilinkParameterMessageLevel	INTEGER,
	accMultilinkParameterPhysicalPort	DisplayString,
	accMultilinkParameterAdminState		INTEGER,
	accMultilinkParameterOperState		INTEGER,
        accMultilinkParameterEncapsulation      INTEGER
	}
accMultilinkParameterIndex OBJECT-TYPE
	SYNTAX INTEGER
	ACCESS read-write
	STATUS mandatory
	DESCRIPTION
		"An integer that uniquely identifies this multilink
		group."
      ::= { accMultilinkParameterEntry 1 }
accMultilinkParameterIfIndex OBJECT-TYPE
	SYNTAX INTEGER
	ACCESS read-write
	STATUS mandatory
	DESCRIPTION
		"An integer that identifies the row of the
		systemwide interfaces table associated with this
		multilink group."
      ::= { accMultilinkParameterEntry 2 }
accMultilinkParameterMessageLevel OBJECT-TYPE
	SYNTAX INTEGER (1..7)
	ACCESS read-write
	STATUS mandatory
	DESCRIPTION
		"How verbose the multilink port will be
		when reporting state changes, errors, and
		warnings.  Level 1 is the least verbose, 
		level 7 the most.  The message levels
		are broken down as follows:
		1 - Error messages.
		2 - Unused + 1.
		3 - Warning messages + 2.
		4 - Unused + 3. 
		5 - Multilink activity + 4.
		6 - Unused + 5.
		7 - Multilink port state changes + 6."
	DEFVAL { 1 }
      ::= { accMultilinkParameterEntry 3 }
accMultilinkParameterPhysicalPort OBJECT-TYPE
	SYNTAX DisplayString
	ACCESS read-only
	STATUS mandatory
	DESCRIPTION
		"A text string listing all physical ports
		associated with this multilink port."
      ::= { accMultilinkParameterEntry 9 } -- was 4 but returned wrong value
accMultilinkParameterAdminState OBJECT-TYPE
	SYNTAX INTEGER {
		enabled(1),
		disabled(2)
	}
	ACCESS read-write
	STATUS mandatory
	DESCRIPTION
		"An integer that specifies the administrative enabling or
		disabling of this multilink group."
      ::= { accMultilinkParameterEntry 5 }
accMultilinkParameterOperState OBJECT-TYPE
	SYNTAX INTEGER {
		down(1),
		starting(2),
		seq-received-ok(3),
		seq-send-ok(4),
		up(5),
		disabled(6)
	}
	ACCESS read-only
	STATUS mandatory
	DESCRIPTION
		"An integer that specifies the operational state
		of this multilink group."
      ::= { accMultilinkParameterEntry 6 }
accMultilinkParameterEncapsulation OBJECT-TYPE
        SYNTAX INTEGER {
                acc(1),
                ietf-ppp(2),
                acc-new(3)
        }
        ACCESS read-write
        STATUS mandatory
        DESCRIPTION
                "If set to ietf-ppp, a multilink group of PPP links will
		follow the standard PPP multilink operations methods. 
		The value acc-new is reserved for future use.  The value
		acc is reserved for compatibility with past offerings."
        DEFVAL { ietf-ppp }
      ::= { accMultilinkParameterEntry 7 }
	accMlTable	OBJECT-TYPE
			SYNTAX SEQUENCE OF AccMlEntry
			ACCESS not-accessible
			STATUS mandatory
			 DESCRIPTION
                  "  A table of Multilink (load-sharing) groups."
			 ::= { accMultilink 2 }
		AccMlEntry ::= SEQUENCE {
			accMlAdminStatus	INTEGER
			}
	  accMlEntry	OBJECT-TYPE
			SYNTAX AccMlEntry
			ACCESS not-accessible
			STATUS mandatory
			DESCRIPTION
                          " Info on specific multilink group "
                        INDEX { ifIndex }
			::= { accMlTable 1 }
	    accMlAdminStatus	OBJECT-TYPE   
			SYNTAX	INTEGER {
				on(1),
				off(2),
				undefined(3)
				}
			ACCESS	read-write
			STATUS	mandatory
			DESCRIPTION
                 " Status of  load sharing capability.  In those systems
                   which support the accSlotProtocol object, the protocol
                   must be set to HDLC for both ports."
			::= { accMlEntry 7 }
accMultilinkStatTable OBJECT-TYPE
	SYNTAX SEQUENCE OF AccMultilinkStatEntry
	ACCESS not-accessible
	STATUS mandatory
	DESCRIPTION
		" "
      ::= { accMultilink 3 }
accMultilinkStatEntry OBJECT-TYPE
	SYNTAX AccMultilinkStatEntry
	ACCESS not-accessible
	STATUS mandatory
	DESCRIPTION
		" "
	INDEX { accMultilinkStatIndex }
      ::= { accMultilinkStatTable 1 }
AccMultilinkStatEntry ::= SEQUENCE {
	accMultilinkStatIndex		INTEGER,
        accMultilinkStatRcvInSeqs	Counter,
        accMultilinkStatRcvOutSeqs	Counter,
        accMultilinkStatRcvOutWindows	Counter,
        accMultilinkStatRcvSeqBreaks	Counter,
        accMultilinkStatRcvPendings	Counter,
	accMultilinkStatRcvRingColls	Counter,
	accMultilinkStatRcvWrongEncaps	Counter,
	accMultilinkStatSendEncapFails	Counter
	}
accMultilinkStatIndex OBJECT-TYPE
	SYNTAX INTEGER
	ACCESS read-only
	STATUS mandatory
	DESCRIPTION
		"An integer that uniquely identifies this
		multilink group."
      ::= { accMultilinkStatEntry 1 }
accMultilinkStatRcvInSeqs OBJECT-TYPE
	SYNTAX Counter
	ACCESS read-only
	STATUS mandatory
	DESCRIPTION
		"The number of messages received over all 
		physical ports associated with this multilink 
		group whose multilink sequence number matched
		what the receiver expected."
      ::= { accMultilinkStatEntry 2 }
accMultilinkStatRcvOutSeqs OBJECT-TYPE
	SYNTAX Counter
	ACCESS read-only
	STATUS mandatory
	DESCRIPTION
		"The number of messages received over all 
		physical ports associated with this multilink 
		group whose multilink sequence number did not
		match what the receiver expected."
      ::= { accMultilinkStatEntry 3 }
accMultilinkStatRcvOutWindows OBJECT-TYPE
	SYNTAX Counter
	ACCESS read-only
	STATUS mandatory
	DESCRIPTION
		"The number of messages received over all 
		physical ports associated with this multilink 
		group whose multilink sequence number did not
		fall within the receiver's window of acceptable 
		sequence numbers."
      ::= { accMultilinkStatEntry 4 }
accMultilinkStatRcvSeqBreaks OBJECT-TYPE
	SYNTAX Counter
	ACCESS read-only
	STATUS mandatory
	DESCRIPTION
		"The number of times the receiver has declared
		that a break in sequence numbers has occurred."
      ::= { accMultilinkStatEntry 5 }
accMultilinkStatRcvWrongEncaps OBJECT-TYPE
	SYNTAX Counter
	ACCESS read-only
	STATUS mandatory
	DESCRIPTION
		"The number of messages received over all 
		physical ports associated with this multilink 
		group that did not bear the expected multilink
		header."
      ::= { accMultilinkStatEntry 6 }
accMultilinkStatRcvPendings OBJECT-TYPE
	SYNTAX Counter
	ACCESS read-only
	STATUS mandatory
	DESCRIPTION
		"The number of messages received over all 
		physical ports associated with this multilink 
		group that are currently being held pending the
		arrival of a message with an earlier sequence
		number."
      ::= { accMultilinkStatEntry 7 }
accMultilinkStatRcvRingColls OBJECT-TYPE
	SYNTAX Counter
	ACCESS read-only
	STATUS mandatory
	DESCRIPTION
		"The number of messages received over all 
		physical ports associated with this multilink 
		group that would have occupied the same storage
		as another message being held pending the
		arrival of a message with an earlier sequence
		number."
      ::= { accMultilinkStatEntry 8 }
accMultilinkStatSendEncapFails OBJECT-TYPE
	SYNTAX Counter
	ACCESS read-only
	STATUS mandatory
	DESCRIPTION
		"The number of times the multilink group was
		unable to encapsulate an outgoing message."
      ::= { accMultilinkStatEntry 9 }
accMultilinkStackTable OBJECT-TYPE
	SYNTAX SEQUENCE OF AccMultilinkStackEntry
	ACCESS not-accessible
	STATUS mandatory
	DESCRIPTION
		" "
      ::= { accMultilink 4 }
accMultilinkStackEntry OBJECT-TYPE
	SYNTAX AccMultilinkStackEntry
	ACCESS not-accessible
	STATUS mandatory
	DESCRIPTION
		" "
	INDEX { accMultilinkStackGroup, accMultilinkStackInterface }
      ::= { accMultilinkStackTable 1 }
AccMultilinkStackEntry ::= SEQUENCE {
	accMultilinkStackGroup		INTEGER,
	accMultilinkStackInterface	INTEGER
	}
accMultilinkStackGroup OBJECT-TYPE
	SYNTAX INTEGER
	ACCESS read-write
	STATUS mandatory
	DESCRIPTION
		"An integer identifying the row of the ifTable 
		 containing information about a multilink group."
      ::= { accMultilinkStackEntry 1 }
accMultilinkStackInterface OBJECT-TYPE
	SYNTAX INTEGER
	ACCESS read-write
	STATUS mandatory
	DESCRIPTION
		"An integer identifying the row of the systemwide
		interfaces table containing information about a
		physical port or dial port associated with a
		multilink group."
      ::= { accMultilinkStackEntry 2 }
-- Async Port (Console) Group
      accAsPort         OBJECT IDENTIFIER ::= { accBRG 10 }
        accConsole      OBJECT IDENTIFIER ::= { accAsPort 2 }
          accConsoleParms  OBJECT IDENTIFIER ::= { accConsole 1 }
	  accConsoleSpeed	OBJECT-TYPE   
			SYNTAX	INTEGER
			ACCESS	read-write
			STATUS	mandatory
			DESCRIPTION
                          " Baud rate for this port;
                            {1200, 2400, 4800, 7200, 9600 } are permitted."
			::= { accConsoleParms 5 }
-- ARP Group
      accArp     OBJECT IDENTIFIER ::=   { accBRG 11 }
	accArpTimeout	OBJECT-TYPE   
			SYNTAX	INTEGER (1..1440)
			ACCESS	read-write
			STATUS	mandatory
			DESCRIPTION
                 " Aging timer value (in minutes) for ARP table entries."
			::= { accArp 1 }
	accArpTable	OBJECT-TYPE
			SYNTAX SEQUENCE OF AccArpEntry
			ACCESS not-accessible
			STATUS mandatory
			DESCRIPTION
                   " The ARP (Address Resolution Protocol) table.
                     This is an alternate view of the atTable."
			::= { accArp 2 }
	  accArpEntry	OBJECT-TYPE
			SYNTAX AccArpEntry
			ACCESS not-accessible
			STATUS mandatory
			DESCRIPTION
                            " A correspondence between logical (IP) 
                              and physical (MAC) addresses."
                        INDEX { accArpNetAddress }
			::= { accArpTable 1 }
		AccArpEntry  ::= SEQUENCE {
			accArpPhysAddress	OCTET STRING,
			accArpNetAddress	IpAddress,
			accArpEntStatus		INTEGER
			}
	    accArpPhysAddress	OBJECT-TYPE   
			SYNTAX	OCTET STRING (SIZE(6))
			ACCESS	read-only
			STATUS	mandatory
			DESCRIPTION
                	 " The Ethernet address of the ARP table entry."
			::= { accArpEntry 1  }
	    accArpNetAddress	OBJECT-TYPE   
			SYNTAX	IpAddress
			ACCESS	read-only
			STATUS	mandatory
			DESCRIPTION
                	 " IP address of this entry.
			   Set this object to NULL to delete an entry."
			::= { accArpEntry 2 }
	    accArpEntStatus	OBJECT-TYPE   
			SYNTAX	INTEGER {
				pending(1),
				dynamic(2),
                                ourbox(4),
				permanent(8),
                                apepending(16),
                                stepending(32),
                                confirmpending(64),
                                confirmsrpending(128)
				}
			ACCESS	read-only
			STATUS	mandatory
			DESCRIPTION
                	 " Status of the ARP table entry."
                        DEFVAL { ourbox }
			::= { accArpEntry 3 }
	accArpType	OBJECT-TYPE   
			SYNTAX	INTEGER (0..2)
			ACCESS	read-write
			STATUS	mandatory
			DESCRIPTION
               		 " State of proxy ARP capability.
				normal(0),
				proxy(2)
			"
			::= { accArp 3 }
	accArpReqRcvds	OBJECT-TYPE   
			SYNTAX	Counter
			ACCESS	read-only
			STATUS	mandatory
			DESCRIPTION
             		 "  Number of ARP Requests received."
			::= { accArp 4 }
	accArpReqSents	OBJECT-TYPE   
			SYNTAX	Counter
			ACCESS	read-only
			STATUS	mandatory
			DESCRIPTION
             		 "  Number of ARP Requests sent."
			::= { accArp 5 }
	accArpRspRcvds	OBJECT-TYPE   
			SYNTAX	Counter
			ACCESS	read-only
			STATUS	mandatory
			DESCRIPTION
              		 " Number of ARP Responses received."
			::= { accArp 6 }
	accArpRspSents	OBJECT-TYPE   
			SYNTAX	Counter
			ACCESS	read-only
			STATUS	mandatory
			DESCRIPTION
              		 " Number of ARP Responses sent."
			::= { accArp 7 }
	accArpInErrs	OBJECT-TYPE   
			SYNTAX	Counter
			ACCESS	read-only
			STATUS	mandatory
			DESCRIPTION
              		 " Number of ARP input errors encountered."
			::= { accArp 8 }
	accArpOutErrs	OBJECT-TYPE   
			SYNTAX	Counter
			ACCESS	read-only
			STATUS	mandatory
			DESCRIPTION
             		 "  Number of ARP output errors encountered."
			::= { accArp 9 }
	accArpUnknownProtos	OBJECT-TYPE   
			SYNTAX	Counter
			ACCESS	read-only
			STATUS	mandatory
			DESCRIPTION
              		 " Number of address resolution requests for which
              		   this ARP implementation did not recognize the protocol."
			::= { accArp 10 }
	accArpPromiscuous	OBJECT-TYPE   
			SYNTAX	INTEGER {
				promiscuous(1),
				nonpromiscuous(2)
				}
			ACCESS	read-write
			STATUS	mandatory
			DESCRIPTION
               		 " When operating promiscuously, the device will
                           learn ARP information from all ARP packets
                           received.  When non-promiscuous, the device
                           will learn information only from ARP packets
                           addressed to the IP address of the device.
			"
			::= { accArp 11 }
	accArpRefresh	OBJECT-TYPE   
			SYNTAX	INTEGER {
				refresh(1),
				norefresh(2)
				}
			ACCESS	read-write
			STATUS	mandatory
			DESCRIPTION
               		 " When operating in refresh mode, when it is
                           time for an entry to age out, the device
                           will refresh the entry by ARPing for it
                           again.  Devices will thus stay in the ARP
                           table until disconnected, even if they are
                           not communicating via the router.  In norefresh 
                           mode, the entry will simply be aged out, and
                           refreshed only if traffic warrants. 
			"
			::= { accArp 12 }
-- IP Routing Group
     accIpRoutingTable  OBJECT-TYPE
			SYNTAX SEQUENCE OF AccIpRoutingEntry
			ACCESS not-accessible
			STATUS mandatory
			DESCRIPTION
			 " Widening of standard IP routing table
			   Entries are added/deleted in conjunction with
			      operations on the standard routing table."
			::= { accBRG 12 }
		AccIpRoutingEntry ::= SEQUENCE {
			accIpRouteDestSubnet	IpAddress
			}
	accIpRoutingEntry OBJECT-TYPE
			SYNTAX AccIpRoutingEntry
			ACCESS not-accessible
			STATUS mandatory
			DESCRIPTION
			 " Additional information about a route."
                        INDEX { ipRouteDest }
			::= { accIpRoutingTable 1 }
	  accIpRouteDestSubnet	OBJECT-TYPE   
			SYNTAX	IpAddress
			ACCESS	read-write
			STATUS	mandatory
			DESCRIPTION
                         " Subnet mask of destination "
			::= { accIpRoutingEntry 2 }
-- Probe Group
     accProbe           OBJECT IDENTIFIER  ::= { accBRG 13 }
	accProbeAddr	OBJECT-TYPE   
			SYNTAX	OCTET STRING
			ACCESS	read-write
			STATUS	mandatory
			DESCRIPTION
               		 " Hexadecimal representation of the memory 
			   address of the long-word whose content we seek."
			::= { accProbe 1 }
	accProbeData	OBJECT-TYPE   
			SYNTAX	INTEGER
			ACCESS	read-only
			STATUS	mandatory
			DESCRIPTION
              		 " Contents (long word) of memory location 
			   of accProbeAddr."
			::= { accProbe 2 }
-- IP Address Group
     accIpAddrTable     OBJECT-TYPE
			SYNTAX SEQUENCE OF AccIpAddrEntry
			ACCESS not-accessible
			STATUS mandatory
			DESCRIPTION
			 " IP Address translation table extension"
			::= { accBRG 14 }
	     AccIpAddrEntry ::= SEQUENCE {
	  		accIpAddrMtu			INTEGER,
	  		accIpAddrSecurityType		INTEGER,
	  		accIpAddrSecurityClass		INTEGER,
	  		accIpAddrSecurityAuth		OCTET STRING,
	  		accIpAddrBcastAddr		IpAddress,
	  		accIpAdEntMetric		INTEGER,
			accIpAdEntPreference		INTEGER
		}
	accIpAddrEntry	OBJECT-TYPE
			SYNTAX AccIpAddrEntry
			ACCESS not-accessible
			STATUS mandatory
			DESCRIPTION
                   " Adds additional information to the ipAddrTable."
                        INDEX { ipAdEntAddr }
			::= { accIpAddrTable 1 }
	  accIpAddrMtu	OBJECT-TYPE   
			SYNTAX	INTEGER
			ACCESS	read-write
			STATUS	mandatory
			DESCRIPTION
               "  Maximum Transmission Unit size for this entry.
                            (46..1500) for Ethernet ports,
                            (128..2048) for HDLC or X25 ports
		   Object will be set to default value if not present
		       in entry-adding SET PDU."
			::= { accIpAddrEntry 1 }
	  accIpAddrSecurityType OBJECT-TYPE   
			SYNTAX	INTEGER {
				none(1),
				basic(2),
				strip(3)
				}
			ACCESS	read-write
			STATUS	mandatory
			DESCRIPTION
		         "  Type of security for this entry."
                        DEFVAL { none }
			::= { accIpAddrEntry 2 }
	  accIpAddrSecurityClass OBJECT-TYPE   
			SYNTAX	INTEGER
			ACCESS	read-write
			STATUS	mandatory
			DESCRIPTION
                " Security classification for this entry.
		   Object will be set to default value if not present
		       in entry-adding SET PDU."
			::= { accIpAddrEntry 3 }
	  accIpAddrSecurityAuth OBJECT-TYPE   
			SYNTAX	OCTET STRING
			ACCESS	read-write
			STATUS	mandatory
			DESCRIPTION
               "  Security authorization for this entry."
			::= { accIpAddrEntry 4 }
	  accIpAddrBcastAddr	OBJECT-TYPE   
			SYNTAX	IpAddress
			ACCESS	read-write
			STATUS	mandatory
			DESCRIPTION
               " IP Broadcast address associated with this entry.
		   Object will be set to default value if not present
		       in entry-adding SET PDU."
			::= { accIpAddrEntry 5 }
	  accIpAdEntMetric	OBJECT-TYPE   
			SYNTAX	INTEGER (0..16)
			ACCESS	read-write
			STATUS	mandatory
			DESCRIPTION
		           " Metric "
                        DEFVAL { 0 }
			::= { accIpAddrEntry 6 }
	  accIpAdEntPreference	OBJECT-TYPE   
			SYNTAX	INTEGER {
				secondary(1),
				primary(2)
			}
			ACCESS	read-write
			STATUS	mandatory
			DESCRIPTION
		           " An entry with a Primary designation will be
			     selected over one with a Secondary designation
			     when a choice amongst otherwise equal entries 
			     is required."
                        DEFVAL { secondary }
			::= { accIpAddrEntry 7 }
-- EGP Neighbor Group
      accEgp    OBJECT IDENTIFIER  ::=  { accBRG 15 }
	accEgpNeighTable OBJECT-TYPE
			SYNTAX SEQUENCE OF AccEgpNeighEntry
			ACCESS not-accessible
			STATUS mandatory
			DESCRIPTION
                   " This table is an extension (widening) of the
                     egpNeighTable."
			::= { accEgp 1 }
	       AccEgpNeighEntry ::= SEQUENCE {
	    		accEgpUptime	TimeTicks,
	    		accEgpFAS	INTEGER,
	    		accEgpSndSeqs	Counter,
	    		accEgpRcvSeqs	Counter
			}
	  accEgpNeighEntry OBJECT-TYPE
			SYNTAX AccEgpNeighEntry
			ACCESS not-accessible
			STATUS mandatory
			DESCRIPTION
                   " Additional information about an EGP neighbor."
                        INDEX { egpNeighAddr }
			::= { accEgpNeighTable 1 }
	    accEgpUptime OBJECT-TYPE   
			SYNTAX	TimeTicks
			ACCESS	read-only
			STATUS	mandatory
			DESCRIPTION
              		 "  Uptime of EGP neighbor"
			::= { accEgpNeighEntry 1 }
	    accEgpFAS	OBJECT-TYPE   
			SYNTAX	INTEGER
			ACCESS	read-only
			STATUS	mandatory
			DESCRIPTION
              		 "  Foreign Autonomous System number"
			::= { accEgpNeighEntry 2 }
	    accEgpSndSeqs	OBJECT-TYPE   
			SYNTAX	Counter
			ACCESS	read-only
			STATUS	mandatory
			DESCRIPTION
              		 " Number of sequences sent to this egp neighbor."
			::= { accEgpNeighEntry 3 }
	    accEgpRcvSeqs	OBJECT-TYPE   
			SYNTAX	Counter
			ACCESS	read-only
			STATUS	mandatory
			DESCRIPTION
               		 " Number of sequences received from this EGP neighbor."
			::= { accEgpNeighEntry 4 }
	accEgpAdminStatus	OBJECT-TYPE   
			SYNTAX	INTEGER {
				on(1),
				off(2)
				}
			ACCESS	read-write
			STATUS	mandatory
			DESCRIPTION
              		 " Administrative status of EGP protocol."
			::= { accEgp 2 }
	accEgpASNumber	OBJECT-TYPE   
			SYNTAX	INTEGER (0..65535)
			ACCESS	read-write
			STATUS	mandatory
			DESCRIPTION
              		 " Autonomous System number, assigned by central
               		   administrative authority."
			::= { accEgp 3 }
	accEgpMetric	OBJECT-TYPE   
			SYNTAX	INTEGER (0..255)
			ACCESS	read-write
			STATUS	mandatory
			DESCRIPTION
                	 " Relative route cost."
			::= { accEgp 4 }
	accEgpInErrMsgs		OBJECT-TYPE   
			SYNTAX	Counter
			ACCESS	read-only
			STATUS	mandatory
			DESCRIPTION
               		 " Number of erroneous EGP messages received"
			::= { accEgp 5 }
	accEgpOutErrMsgs	OBJECT-TYPE   
			SYNTAX	Counter
			ACCESS	read-only
			STATUS	mandatory
			DESCRIPTION
              		 " Number of errors encountered during EGP 
			   message generation."
			::= { accEgp 6 }
	accEgpStateChanges	OBJECT-TYPE   
			SYNTAX	Counter
			ACCESS	read-only
			STATUS	mandatory
			DESCRIPTION
               		 " Number of EGP state changes."
			::= { accEgp 7 }
	accEgpLastChange	OBJECT-TYPE   
			SYNTAX  TimeTicks	
			ACCESS	read-only
			STATUS	mandatory
			DESCRIPTION
             		 " Timestamp of last EGP state change."
			::= { accEgp 8 }
-- RIP Group
     accRip    OBJECT IDENTIFIER  ::= { accBRG 16 }
	accRipAdminStatus	OBJECT-TYPE   
			SYNTAX	INTEGER {
				on(1),
				off(2),
				extended(3)
				}
			ACCESS	read-write
			STATUS	mandatory
			DESCRIPTION
               "  Adminstrative status of RIP protocol.
	          Extended causes subnet mask information to be included in
	          RIP packets, permitting variable-length subnet masking."
			::= { accRip 1 }
	accRipUpdateTimer	OBJECT-TYPE   
			SYNTAX	TimeTicks
			ACCESS	read-write
			STATUS	mandatory
			DESCRIPTION
                " This unit will send updates to its neighbors at the interval
                  established by this timer.  Note that all other RIP timers
                  are scaled off this value."
			::= { accRip 2 }
	accRipGateway	OBJECT-TYPE   
			SYNTAX	INTEGER {
				on(1),
				off(2),
				extended(3)
				}
			ACCESS	read-write
			STATUS	mandatory
			DESCRIPTION
                " Declares if the unit is the gateway unit for an AS.
                  Indicates if the unit does or does not advertise that
                  it is the default route.
	          Extended mode causes EGP-derived information to be
	          included in RIP packets."
			::= { accRip 3 }
	accRipMetric	OBJECT-TYPE   
			SYNTAX	INTEGER (0..15)
			ACCESS	read-write
			STATUS	mandatory
			DESCRIPTION
                " Metric used with the default route in routing updates
                  when this unit is acting as a gateway.
                  Unit is hopcount; 16 represents infinity."
			::= { accRip 4 }
	accRipNeighborList OBJECT IDENTIFIER ::= { accRip 5 }
                -- A list of RIP neighbors.
                -- The instance of an entry is its IP address.
                -- To add an element, the VarBind of a SetRequest PDU will
                -- have both an object instance and value of accRipNeighbor.
                -- To delete an element, a SetRequest-PDU for the specific
                -- instance of accRipNeighbor with a NULL value encoding is
                -- used.
	  accRipNeighbor	OBJECT-TYPE   
			SYNTAX	IpAddress
			ACCESS	read-write
			STATUS	mandatory
			DESCRIPTION
                 " A neighbor to whom routing updates are sent,
                   and from whom updates are accepted.
                   RIP neighbors must be on the local network.
                   In the case of an unnumbered link this object
                   indicates the ifIndex of the link the neighbor
                   is connected to."
			::= { accRipNeighborList 1 }
           accRipNeighborIfindex        OBJECT-TYPE
                        SYNTAX  INTEGER
                        ACCESS  read-only
                        STATUS  mandatory
                        DESCRIPTION
                 " The ifIndex of the port this RIP neighbor is conected
                   to. It is derived from the IP network table
                   (accIpAddrTable). "
                    ::= { accRipNeighborList 2 }
	accRipInCmdCnts	OBJECT-TYPE   
			SYNTAX	Counter
			ACCESS	read-only
			STATUS	mandatory
			DESCRIPTION
                "  Number of RIP command packets successfully received."
			::= { accRip 6 }
	accRipInRspCnts	OBJECT-TYPE   
			SYNTAX	Counter
			ACCESS	read-only
			STATUS	mandatory
			DESCRIPTION
                 " Number of RIP response packets successfully received."
			::= { accRip 7 }
	accRipInErrors	OBJECT-TYPE   
			SYNTAX	Counter
			ACCESS	read-only
			STATUS	mandatory
			DESCRIPTION
                 " Number of RIP response and command packets received with 
                   errors.  Also includes count of packets that could 
                   not be handled due to internal errors."
			::= { accRip 8 }
	accRipOutCmdCnts OBJECT-TYPE   
			SYNTAX	Counter
			ACCESS	read-only
			STATUS	mandatory
			DESCRIPTION
                 " Number of RIP command packets successfully transmitted."
			::= { accRip 9 }
	accRipOutRspCounts	OBJECT-TYPE   
			SYNTAX	Counter
			ACCESS	read-only
			STATUS	mandatory
			DESCRIPTION
                "  Number of RIP response packets successfully transmitted."
			::= { accRip 10 }
-- X.25 Group
-- X.25 addresses are represented as variable-length 
-- ASCII strings (length is between 0 and 15, inclusive).
      accX25      OBJECT IDENTIFIER  ::= { accBRG 17 }
	accX25AtTable	OBJECT-TYPE
			SYNTAX	SEQUENCE OF AccX25AtEntry
			ACCESS	not-accessible
			STATUS	mandatory
			DESCRIPTION
			 " Address translation table for X.25 interfaces.
			   This is a superset of the standard address
			   translation table.
			   Entries are added/deleted via management action."
			::= { accX25 1	}
	  accX25AtEntry OBJECT-TYPE
			SYNTAX	AccX25AtEntry
			ACCESS	not-accessible
			STATUS	mandatory
			DESCRIPTION
			 " Address translation entry for X.25 interfaces."
                        INDEX { accX25AtIfIndex, 
                                accX25AtIpAddress }
			::= { accX25AtTable 1 }
		AccX25AtEntry ::= SEQUENCE {
			    accX25AtIfIndex	INTEGER,
			    accX25AtIpAddress	NetworkAddress,
			    accX25AtNetInOutAddr	DisplayString,
			    accX25AtNetInAddr	DisplayString,
			    accX25AtNetFacIndex INTEGER
			    }
	  accX25AtIfIndex	OBJECT-TYPE   
			SYNTAX	INTEGER
			ACCESS	read-write
			STATUS	mandatory
			DESCRIPTION
			 " Interface number (ifIndex) for which this 
			   translation entry is valid."
			::= { accX25AtEntry 1 }
	  accX25AtIpAddress OBJECT-TYPE	  
			SYNTAX	NetworkAddress
			ACCESS	read-write
			STATUS	mandatory
			DESCRIPTION
                         " IP Address of this entry
			   Set this object to NULL to delete entry."
			::= { accX25AtEntry 2 }
	  accX25AtNetInOutAddr OBJECT-TYPE   
			SYNTAX  DisplayString	
			ACCESS	read-write
			STATUS	mandatory
			DESCRIPTION
			 " X.25 address to use when calling this destination.
			   (both X.25 addresses are checked when mapping an
			   X.25 address to an IP address)
			   Object required in entry-adding SET PDU."
			::= { accX25AtEntry 3 }
	  accX25AtNetInAddr OBJECT-TYPE   
			SYNTAX  DisplayString	
			ACCESS	read-write
			STATUS	mandatory
			DESCRIPTION
			 " Alternate X.25 address to check when mapping an
			   X.25 address to an IP address
			   Object will be set to default value if not present
			       in entry-adding SET PDU."
			::= { accX25AtEntry 4 }
        accX25AtNetFacIndex OBJECT-TYPE
                      SYNTAX  INTEGER (0..255)
                      ACCESS  read-write
                      STATUS  mandatory
                      DESCRIPTION
                           " Index of optional facility string or 0."
                      DEFVAL  { 0 }
                      ::= { accX25AtEntry 5 }
	accX25SubnetParmTable	OBJECT-TYPE
			SYNTAX	SEQUENCE OF AccX25SubnetParmEntry
			ACCESS	not-accessible
			STATUS	mandatory
			DESCRIPTION
			 " Per-network parameters for IP networks attached
			   via X.25 interface.
			   Entries added/deleted via management action."
			::= { accX25 2 }
	  accX25SubnetParmEntry OBJECT-TYPE
			SYNTAX	AccX25SubnetParmEntry
			ACCESS	not-accessible
			STATUS	mandatory
			DESCRIPTION
			 " X.25-specific parameters for this IP network"
                        INDEX { accX25SubnetAddr }
			::= { accX25SubnetParmTable 1 }
		AccX25SubnetParmEntry ::= SEQUENCE {
			    accX25SubnetAddr	IpAddress,
			    accX25Facility	INTEGER,
			    accX25PktNegot	INTEGER,
			    accX25WindowNegot	INTEGER
			    }
	    accX25SubnetAddr	OBJECT-TYPE   
			SYNTAX	IpAddress
			ACCESS	read-write
			STATUS	mandatory
			DESCRIPTION
			 " Network/subnet number of IP network
			   Set this object to NULL to delete entry."
			::= { accX25SubnetParmEntry 1 }
	    accX25Facility	OBJECT-TYPE   
			SYNTAX	INTEGER {
				none(1),
				std(2)
				}
			ACCESS	read-write
			STATUS	mandatory
			DESCRIPTION
			 " selects whether DDN Standard Mode facility is
			   included in call requests. "
                        DEFVAL { none }
			::= { accX25SubnetParmEntry 2 }
	    accX25PktNegot	OBJECT-TYPE   
			SYNTAX	INTEGER
			ACCESS	read-write
			STATUS	mandatory
			DESCRIPTION
			 " specifies value for Packet Size Negotiation Facility
			   (power of 2 between 16 and 1024), or zero if Packet
			   Size Negotiation Facility is not to be used."
                        DEFVAL { 0 }
			::= { accX25SubnetParmEntry 3 }
	    accX25WindowNegot	OBJECT-TYPE   
			SYNTAX	INTEGER
			ACCESS	read-write
			STATUS	mandatory
			DESCRIPTION
			 " specifies value for Window Size Negotiation Facility
			   (between 1 and 127 inclusive), or zero if Window
			   Size Negotiation Facility is not to be used."
                        DEFVAL { 0 }
			::= { accX25SubnetParmEntry 4 }
	accX25PortParmTable	OBJECT-TYPE
			SYNTAX	SEQUENCE OF AccX25PortParmEntry
			ACCESS	not-accessible
			STATUS	mandatory
			DESCRIPTION
			 " Per-port parameters for X.25 interfaces."
			::= { accX25 3 }
          accX25PortParmEntry   OBJECT-TYPE
                        SYNTAX  AccX25PortParmEntry
                        ACCESS  not-accessible
                        STATUS  mandatory
                        DESCRIPTION
                         " X25 parameters of a specific port."
                        INDEX { accX25PortParmIndex }
                        ::= { accX25PortParmTable 1 }
			AccX25PortParmEntry ::= SEQUENCE {
			    accX25PortParmIndex INTEGER,
			    accX25AddrMode	INTEGER,
			    accX25PktSize	INTEGER,
			    accX25PktWind	INTEGER,
			    accX25SvcNumber	INTEGER,
			    accX25SvcBase	INTEGER,
			    accX25ExtendClr	INTEGER,
			    accX25ExtendSeq	INTEGER,
			    accX25IdleMin	TimeTicks,
			    accX25IdleMax	TimeTicks,
			    accX25IdleScale	TimeTicks,
			    accX25SvcMax	INTEGER,
			    accX25SvcLimit	INTEGER,
			    accX25OpenThresh 	INTEGER,
			    accX25SvcMin	INTEGER,
			    accX25SvcDelay	INTEGER,
			    accX25InitBackoff	INTEGER,
			    accX25MaxBackoff	INTEGER,
			    accX25OurAddress	DisplayString,
			    accX25PvcBase	INTEGER,
			    accX25PvcNumber	INTEGER,
			    accX25Tx0Timer	TimeTicks,
			    accX25Tx1Timer	TimeTicks,
			    accX25Tx2Timer	TimeTicks,
			    accX25Tx3Timer	TimeTicks
			    }
	    accX25PortParmIndex		OBJECT-TYPE   
			SYNTAX	INTEGER
			ACCESS	read-only
			STATUS	mandatory
			DESCRIPTION
			 " Port number"
			::= { accX25PortParmEntry 1 }
	    accX25AddrMode	OBJECT-TYPE   
			SYNTAX	INTEGER {
				table(1),	-- use translation table
						-- (accX25AtTable)
				ddn(2),		-- use DDN mapping algorithm
				bfe(3)		-- use Blacker algorithm
				}
			ACCESS	read-write
			STATUS	mandatory
			DESCRIPTION
			 " specifies address translation technique."
                        DEFVAL { table }
			::= { accX25PortParmEntry 2 }
	    accX25PktSize	OBJECT-TYPE   
			SYNTAX	INTEGER
			ACCESS	read-write
			STATUS	mandatory
			DESCRIPTION
			 " specifies default data packet size for this port."
                        DEFVAL { 128 }
			::= { accX25PortParmEntry 3 }
	    accX25PktWind	OBJECT-TYPE   
			SYNTAX	INTEGER
			ACCESS	read-write
			STATUS	mandatory
			DESCRIPTION
			 " specifies default packet window size for this port."
                        DEFVAL { 2 }
			::= { accX25PortParmEntry 4 }
	    accX25SvcNumber	OBJECT-TYPE   
			SYNTAX	INTEGER
			ACCESS	read-write
			STATUS	mandatory
			DESCRIPTION
			 " specifies maximum number of switched virtual
			   circuits to be used on this port."
                        DEFVAL { 256 }
			::= { accX25PortParmEntry 5 }
	    accX25SvcBase	OBJECT-TYPE   
			SYNTAX	INTEGER
			ACCESS	read-write
			STATUS	mandatory
			DESCRIPTION
			 " specifies lowest Logical Channel Identifier
			   to be used for switched virtual circuits."
                        DEFVAL { 1 }
			::= { accX25PortParmEntry 6 }
	    accX25ExtendClr	OBJECT-TYPE   
			SYNTAX	INTEGER {
				on(1),	-- use/accept extended clear format
				off(2)	-- disallow extended clear format
				}
			ACCESS	read-write
			STATUS	mandatory
			DESCRIPTION
			 " specifies whether extended format for call clearing
			   packets (as defined by X.25-1984) is permitted"
                        DEFVAL { off }
			::= { accX25PortParmEntry 7 }
	    accX25ExtendSeq	OBJECT-TYPE   
			SYNTAX	INTEGER {
				normal(1),	-- modulo-8 sequence numbers
				extended(2)	-- modulo-128 sequence numbers
				}
			ACCESS	read-write
			STATUS	mandatory
			DESCRIPTION
			 " Use of extended sequence numbers"
                        DEFVAL { normal }
			::= { accX25PortParmEntry 8 }
	    accX25IdleMin	OBJECT-TYPE   
			SYNTAX	TimeTicks
			ACCESS	read-write
			STATUS	mandatory
			DESCRIPTION
			 " minimum idle time for closing circuits; a circuit
			   will not be cleared until it has been idle (no data
			   has been sent or received) for at least this amount
			   of time."
                        DEFVAL { 30000 }
			::= { accX25PortParmEntry 9 }
	    accX25IdleMax	OBJECT-TYPE   
			SYNTAX	TimeTicks
			ACCESS	read-write
			STATUS	mandatory
			DESCRIPTION
			 " maximum idle time for closing circuits; a circuit
			   will be cleared when its idle time exceeds this
			   value."
                        DEFVAL { 180000 }
			::= { accX25PortParmEntry 10 }
	    accX25IdleScale	OBJECT-TYPE   
			SYNTAX	TimeTicks
			ACCESS	read-write
			STATUS	mandatory
			DESCRIPTION
			 " scale factor for idle timeout: a circuit will
			   be cleared when it has been idle for accX25IdleMin
			   plus accX25IdleScale times the number of available
			   circuits."
                        DEFVAL { 1000 }
			::= { accX25PortParmEntry 11 }
	    accX25SvcMax	OBJECT-TYPE
			SYNTAX	INTEGER
			ACCESS	read-write
			STATUS	mandatory
			DESCRIPTION
			 " Maximum number of virtual circuits which can be 
			   opened to a single destination."
                        DEFVAL { 1 }
			::= { accX25PortParmEntry 12 }
	    accX25SvcLimit	OBJECT-TYPE
			SYNTAX	INTEGER
			ACCESS	read-write
			STATUS	mandatory
			DESCRIPTION
			 " Maximum number of switched virtual circuits that
			   IP can use.  The value must not exceed the total
			   number of logical channels available on this
			   trunk."
                        DEFVAL { 256 }
			::= { accX25PortParmEntry 13 }
	    accX25OpenThresh	OBJECT-TYPE
			SYNTAX	INTEGER
			ACCESS	read-write
			STATUS	mandatory
			DESCRIPTION
			 " Threshold (number of IP datagrams queued per circuit)
			   at which an additional virtual circuit will be
			   opened."
                        DEFVAL { 3 }
			::= { accX25PortParmEntry 14 }
	    accX25SvcMin	OBJECT-TYPE
			SYNTAX	INTEGER
			ACCESS	read-write
			STATUS	mandatory
			DESCRIPTION
			 " The minimum number of virtual circuits which IP
			   will leave available for first circuits
			   to other destinations"
                        DEFVAL { 0 }
			::= { accX25PortParmEntry 15 }
	    accX25SvcDelay	OBJECT-TYPE
			SYNTAX	INTEGER
			ACCESS	read-write
			STATUS	mandatory
			DESCRIPTION
			 " Delay (seconds) between opening of 
			   successive virtual circuits to same destination."
                        DEFVAL { 5 }
			::= { accX25PortParmEntry 16 }
	    accX25InitBackoff	OBJECT-TYPE
			SYNTAX	INTEGER
			ACCESS	read-write
			STATUS	mandatory
			DESCRIPTION
			 " Initial backoff time (seconds) to delay before 
			   next attempt to open an additional virtual circuit
			   to the same destination when an attempt to do so
			   has failed.  "
                        DEFVAL { 15 }
			::= { accX25PortParmEntry 17 }
	    accX25MaxBackoff	OBJECT-TYPE
			SYNTAX	INTEGER
			ACCESS	read-write
			STATUS	mandatory
			DESCRIPTION
			 " Maximum backoff time (seconds) to delay between
			   subsequent attempts to open additional virtual
			   circuits to the same destination.  The actual
			   delay is varied exponentially from 
			   accX25InitBackoff up to this value."
                        DEFVAL { 86400 }
			::= { accX25PortParmEntry 18 }
	    accX25OurAddress	OBJECT-TYPE
			SYNTAX  DisplayString --(SIZE(15))	
			ACCESS	read-write
			STATUS	mandatory
			DESCRIPTION
			 " Our X25 address (put in outbound packets)"
                        DEFVAL { '0'h }
			::= { accX25PortParmEntry 19 }
        accX25PvcBase       OBJECT-TYPE
                 SYNTAX  INTEGER
                 ACCESS  read-write
                 STATUS  mandatory
                 DESCRIPTION
                     " Lowest LCID to be used for PVCs."
                 DEFVAL  { 0 }
                 ::= { accX25PortParmEntry 20 }
        accX25PvcNumber     OBJECT-TYPE
                  SYNTAX  INTEGER
                  ACCESS  read-write
                  STATUS  mandatory
                  DESCRIPTION
                      " Maximum number of PVCs."
                  DEFVAL  { 0 }
                  ::= { accX25PortParmEntry 21 }
        accX25Tx0Timer      OBJECT-TYPE
                   SYNTAX  TimeTicks
                   ACCESS  read-write
                   STATUS  mandatory
                   DESCRIPTION
                       " Value for T10 (DCE) or T20 (DTE) timer."
                   DEFVAL  { 18000 } -- 180 sec (DTE)
                   ::= { accX25PortParmEntry 22 }
        accX25Tx1Timer      OBJECT-TYPE
                   SYNTAX  TimeTicks
                   ACCESS  read-write
                   STATUS  mandatory
                   DESCRIPTION
                       " Value for T11 (DCE) or T21 (DTE) timer."
                   DEFVAL  { 20000 } -- 200 sec (DTE)
                   ::= { accX25PortParmEntry 23 }
        accX25Tx2Timer      OBJECT-TYPE
                   SYNTAX  TimeTicks
                   ACCESS  read-write
                   STATUS  mandatory
                   DESCRIPTION
                       " Value for T12 (DCE) or T22 (DTE) timer."
                   DEFVAL  { 18000 } -- 180 sec (DTE)
                   ::= { accX25PortParmEntry 24 }
        accX25Tx3Timer      OBJECT-TYPE
                   SYNTAX  TimeTicks
                   ACCESS  read-write
                   STATUS  mandatory
                   DESCRIPTION
                       " Value for T13 (DCE) or T23 (DTE) timer."
                   DEFVAL  { 18000 } -- 180 sec (DTE)
		   ::= { accX25PortParmEntry 25 }
	accX25PktStatTable	OBJECT-TYPE
			SYNTAX	SEQUENCE OF AccX25PktStatEntry
			ACCESS	not-accessible
			STATUS	mandatory
			DESCRIPTION
			 " Per-port packet statistics for X.25 interfaces."
			::= { accX25 4 }
          accX25PktStatEntry    OBJECT-TYPE
                        SYNTAX  AccX25PktStatEntry
                        ACCESS  not-accessible
                        STATUS  mandatory
                        DESCRIPTION
                         " X.25 packet level statistics for an X.25 interface."
                        INDEX { accX25PktIndex }
                        ::= { accX25PktStatTable 1 }
			AccX25PktStatEntry ::= SEQUENCE {
			    accX25PktIndex	INTEGER,
			    accX25RcvDiags	Counter,
			    accX25RcvRestartReqs Counter,
			    accX25RcvRestartConfs Counter,
			    accX25RcvCallReqs	Counter,
			    accX25RcvCallAccs	Counter,
			    accX25RcvClrReqs	Counter,
			    accX25RcvClrConfs	Counter,
			    accX25RcvResetReqs	Counter,
			    accX25RcvResetConfs	Counter,
			    accX25RcvInts	Counter,
			    accX25RcvIntConfs	Counter,
			    accX25RcvRRs		Counter,
			    accX25RcvRNRs	Counter,
			    accX25RcvDatas	Counter,
			    accX25XmtDiags	Counter,
			    accX25XmtRestartReqs Counter,
			    accX25XmtRestartConfs Counter,
			    accX25XmtCallReqs	Counter,
			    accX25XmtCallAccs	Counter,
			    accX25XmtClrReqs	Counter,
			    accX25XmtClrConfs	Counter,
			    accX25XmtResetReqs	Counter,
			    accX25XmtResetConfs	Counter,
			    accX25XmtInts	Counter,
			    accX25XmtIntConfs	Counter,
			    accX25XmtRRs	Counter,
			    accX25XmtRNRs	Counter,
			    accX25XmtDatas	Counter,
			    accX25OpenSvcCounts	Counter
			    }
	    accX25PktIndex	OBJECT-TYPE   
			SYNTAX	INTEGER
			ACCESS	read-only
			STATUS	mandatory
			DESCRIPTION
			 " Port number of this X.25 interface."
			::= { accX25PktStatEntry 1 }
	    accX25RcvDiags	OBJECT-TYPE   
			SYNTAX	Counter
			ACCESS	read-only
			STATUS	mandatory
			DESCRIPTION
			 " Number of Diagnostic packets received on this port."
			::= { accX25PktStatEntry 2 }
	    accX25RcvRestartReqs		OBJECT-TYPE   
			SYNTAX	Counter
			ACCESS	read-only
			STATUS	mandatory
			DESCRIPTION
			 " Number of Restart Request (Restart Indication)
			   packets received on this port."
			::= { accX25PktStatEntry 3 }
	    accX25RcvRestartConfs	OBJECT-TYPE   
			SYNTAX	Counter
			ACCESS	read-only
			STATUS	mandatory
			DESCRIPTION
			 " Number of Restart Confirmation packets received
			   on this port."
			::= { accX25PktStatEntry 4 }
	    accX25RcvCallReqs	OBJECT-TYPE   
			SYNTAX	Counter
			ACCESS	read-only
			STATUS	mandatory
			DESCRIPTION
			 " Number of Call Request (Incoming Call) packets
			   received on this port."
			::= { accX25PktStatEntry 5 }
	    accX25RcvCallAccs	OBJECT-TYPE   
			SYNTAX	Counter
			ACCESS	read-only
			STATUS	mandatory
			DESCRIPTION
			 " Number of Call Accepted (Call Connected) packets
			   received on this port."
			::= { accX25PktStatEntry 6 }
	    accX25RcvClrReqs	OBJECT-TYPE   
			SYNTAX	Counter
			ACCESS	read-only
			STATUS	mandatory
			DESCRIPTION
			 " Number of Clear Request (Clear Indication) packets
			   received on this port."
			::= { accX25PktStatEntry 7 }
	    accX25RcvClrConfs	OBJECT-TYPE   
			SYNTAX	Counter
			ACCESS	read-only
			STATUS	mandatory
			DESCRIPTION
			 " Number of Clear Confirmation packets received on
			   this port."
			::= { accX25PktStatEntry 8 }
	    accX25RcvResetReqs	OBJECT-TYPE   
			SYNTAX	Counter
			ACCESS	read-only
			STATUS	mandatory
			DESCRIPTION
			 " Number of Reset Request (Reset Indication) packets
			   received on this port."
			::= { accX25PktStatEntry 9 }
	    accX25RcvResetConfs	OBJECT-TYPE   
			SYNTAX	Counter
			ACCESS	read-only
			STATUS	mandatory
			DESCRIPTION
			 " Number of Reset Confirmation packets received on
			   this port."
			::= { accX25PktStatEntry 10 }
	    accX25RcvInts	OBJECT-TYPE   
			SYNTAX	Counter
			ACCESS	read-only
			STATUS	mandatory
			DESCRIPTION
			 " Number of Interrupt packets received on this port."
			::= { accX25PktStatEntry 11 }
	    accX25RcvIntConfs	OBJECT-TYPE   
			SYNTAX	Counter
			ACCESS	read-only
			STATUS	mandatory
			DESCRIPTION
			 " Number of Interrupt Confirmation packets received
			   on this port."
			::= { accX25PktStatEntry 12 }
	    accX25RcvRRs		OBJECT-TYPE   
			SYNTAX	Counter
			ACCESS	read-only
			STATUS	mandatory
			DESCRIPTION
			 " Number of RR [Receive Ready] packets received on
			   this port."
			::= { accX25PktStatEntry 13 }
	    accX25RcvRNRs	OBJECT-TYPE   
			SYNTAX	Counter
			ACCESS	read-only
			STATUS	mandatory
			DESCRIPTION
			 " Number of RNR [Receive Not Ready] packets received
			   on this port."
			::= { accX25PktStatEntry 14 }
	    accX25RcvDatas	OBJECT-TYPE   
			SYNTAX	Counter
			ACCESS	read-only
			STATUS	mandatory
			DESCRIPTION
			 " Number of Data packets received on this port."
			::= { accX25PktStatEntry 15 }
	    accX25XmtDiags	OBJECT-TYPE   
			SYNTAX	Counter
			ACCESS	read-only
			STATUS	mandatory
			DESCRIPTION
			 " Number of Diagnostic packets transmitted on this
			   port."
			::= { accX25PktStatEntry 16 }
	    accX25XmtRestartReqs		OBJECT-TYPE   
			SYNTAX	Counter
			ACCESS	read-only
			STATUS	mandatory
			DESCRIPTION
			 " Number of Restart Request (Restart Indication)
			   packets transmitted on this port."
			::= { accX25PktStatEntry 17 }
	    accX25XmtRestartConfs	OBJECT-TYPE   
			SYNTAX	Counter
			ACCESS	read-only
			STATUS	mandatory
			DESCRIPTION
			 " Number of Restart Confirmation packets transmitted
			   on this port."
			::= { accX25PktStatEntry 18 }
	    accX25XmtCallReqs	OBJECT-TYPE   
			SYNTAX	Counter
			ACCESS	read-only
			STATUS	mandatory
			DESCRIPTION
			 " Number of Call Request (Incoming Call) packets
			   transmitted on this port."
			::= { accX25PktStatEntry 19 }
	    accX25XmtCallAccs	OBJECT-TYPE   
			SYNTAX	Counter
			ACCESS	read-only
			STATUS	mandatory
			DESCRIPTION
			 " Number of Call Accepted (Call Connected) packets
			   transmitted on this port."
			::= { accX25PktStatEntry 20 }
	    accX25XmtClrReqs	OBJECT-TYPE   
			SYNTAX	Counter
			ACCESS	read-only
			STATUS	mandatory
			DESCRIPTION
			 " Number of Clear Request (Clear Indication) packets
			   transmitted on this port."
			::= { accX25PktStatEntry 21 }
	    accX25XmtClrConfs	OBJECT-TYPE   
			SYNTAX	Counter
			ACCESS	read-only
			STATUS	mandatory
			DESCRIPTION
			 " Number of Clear Confirmation packets transmitted
			   on this port."
			::= { accX25PktStatEntry 22 }
	    accX25XmtResetReqs	OBJECT-TYPE   
			SYNTAX	Counter
			ACCESS	read-only
			STATUS	mandatory
			DESCRIPTION
			 " Number of Reset Request (Reset Indication) packets
			   transmitted on this port."
			::= { accX25PktStatEntry 23 }
	    accX25XmtResetConfs	OBJECT-TYPE   
			SYNTAX	Counter
			ACCESS	read-only
			STATUS	mandatory
			DESCRIPTION
			 " Number of Reset Confirmation packets transmitted
			   on this port."
			::= { accX25PktStatEntry 24 }
	    accX25XmtInts	OBJECT-TYPE   
			SYNTAX	Counter
			ACCESS	read-only
			STATUS	mandatory
			DESCRIPTION
			 " Number of Interrupt packets transmitted on this
			   port."
			::= { accX25PktStatEntry 25 }
	    accX25XmtIntConfs	OBJECT-TYPE   
			SYNTAX	Counter
			ACCESS	read-only
			STATUS	mandatory
			DESCRIPTION
			 " Number of Interrupt Confirmation packets
			   transmitted on this port."
			::= { accX25PktStatEntry 26 }
	    accX25XmtRRs		OBJECT-TYPE   
			SYNTAX	Counter
			ACCESS	read-only
			STATUS	mandatory
			DESCRIPTION
			 " Number of RR [Receive Ready] packets transmitted
			   on this port."
			::= { accX25PktStatEntry 27 }
	    accX25XmtRNRs	OBJECT-TYPE   
			SYNTAX	Counter
			ACCESS	read-only
			STATUS	mandatory
			DESCRIPTION
			 " Number of RNR [Receive Not Ready] packets
			   transmitted on this port."
			::= { accX25PktStatEntry 28 }
	    accX25XmtDatas	OBJECT-TYPE   
			SYNTAX	Counter
			ACCESS	read-only
			STATUS	mandatory
			DESCRIPTION
			 " Number of Data packets transmitted on this port."
			::= { accX25PktStatEntry 29 }
	accX25OpenSvcCounts  OBJECT-TYPE
	            SYNTAX  Counter
	            ACCESS  read-only
	            STATUS  mandatory
	            DESCRIPTION
	                  " Count of SVCs open on this port."
	            ::= { accX25PktStatEntry 30 }
-- X25 Enhanced Group
       accX25OptFacTable       OBJECT-TYPE
                    SYNTAX  SEQUENCE OF AccX25OptFacEntry
                    ACCESS  not-accessible
                    STATUS  mandatory
                    DESCRIPTION
                      " Optional facility string table."
                    ::= { accX25 5 }
       accX25OptFacEntry     OBJECT-TYPE
                    SYNTAX  AccX25OptFacEntry
                    ACCESS  not-accessible
                    STATUS  mandatory
                    DESCRIPTION
                      " A single optional facility entry."
                    INDEX { accX25OptFacIndex }
                    ::= { accX25OptFacTable 1 }
       AccX25OptFacEntry ::= SEQUENCE {
                    accX25OptFacIndex   INTEGER,
                    accX25OptFacString  OCTET STRING
                    }
       accX25OptFacIndex   OBJECT-TYPE
                    SYNTAX  INTEGER
                    ACCESS  read-write
                    STATUS  mandatory
                    DESCRIPTION
                       " Index of this entry in table [1..n]."
                    ::= { accX25OptFacEntry 1 }
       accX25OptFacString  OBJECT-TYPE
                    SYNTAX  OCTET STRING
                    ACCESS  read-write
                    STATUS  mandatory
                    DESCRIPTION
                      " facility string to be added when placing calls."
                    ::= { accX25OptFacEntry 2 }
        accX25PvcAddrTable      OBJECT-TYPE
                    SYNTAX  SEQUENCE OF AccX25PvcAddrEntry
                    ACCESS  not-accessible
                    STATUS  mandatory
                    DESCRIPTION
                       " PVC to X.25 address mapping table."
                    ::= { accX25 6 }
        accX25PvcAddrEntry    OBJECT-TYPE
                     SYNTAX  AccX25PvcAddrEntry
                     ACCESS  not-accessible
                     STATUS  mandatory
                     DESCRIPTION
                       " A single PVC to X.25 address mapping entry."
                     INDEX { accX25PvcLine,
                             accX25PvcAddrLcid
                           }
                     ::= { accX25PvcAddrTable 1 }
	AccX25PvcAddrEntry ::= SEQUENCE {
                     accX25PvcLine       INTEGER,
                     accX25PvcAddrLcid   INTEGER,
                     accX25PvcAddrString DisplayString,
                     accX25PvcProtocol   INTEGER
                     }
        accX25PvcLine       OBJECT-TYPE
                     SYNTAX  INTEGER
                     ACCESS  read-write
                     STATUS  mandatory
                     DESCRIPTION
                        " Physical port for which this entry applies.
			Same is ifIndex."
                     ::= { accX25PvcAddrEntry 1 }
	accX25PvcAddrLcid       OBJECT-TYPE
                     SYNTAX  INTEGER
                     ACCESS  read-write
                     STATUS  mandatory
                     DESCRIPTION
                       " PVC logical channel ID ."
                     ::= { accX25PvcAddrEntry 2 }
        accX25PvcAddrString    OBJECT-TYPE
                     SYNTAX  DisplayString 
                     ACCESS  read-write
                     STATUS  mandatory
                     DESCRIPTION
                        " X.25 address to associate with this PVC."
                     ::= { accX25PvcAddrEntry 3 }
	accX25PvcProtocol       OBJECT-TYPE
                     SYNTAX  INTEGER {
			     ip(1),
			     appletalk(2),
			     decnet(3),
			     idp(4),
			     ipx(5),
			     bridging(6),
			     sourcerouting(7)
			     }
                     ACCESS  read-write
                     STATUS  mandatory
                     DESCRIPTION
                       " PVC Protocol Associated with this line and the LCID ."
                     ::= { accX25PvcAddrEntry 4 }
       accX25ErrorTable        OBJECT-TYPE
                    SYNTAX  SEQUENCE OF AccX25ErrorEntry
                    ACCESS  not-accessible
                    STATUS  mandatory
                    DESCRIPTION
                       " Error and exception logging table."
                    ::= { accX25 7 }
	accX25ErrorEntry      OBJECT-TYPE
                    SYNTAX  AccX25ErrorEntry
                    ACCESS  not-accessible
                    STATUS  mandatory
                    DESCRIPTION
                      " A single error or exception item."
                    INDEX { accX25ErrorLine,
                            accX25ErrorUpTime,
                            accX25ErrorSeq
                          }
                    ::= { accX25ErrorTable 1 }
       AccX25ErrorEntry ::= SEQUENCE {
                    accX25ErrorLine     INTEGER,
                    accX25ErrorUpTime   TimeTicks,
                    accX25ErrorSeq      INTEGER,
                    accX25ErrorState    INTEGER,
                    accX25ErrorProtocol INTEGER,
                    accX25ErrorCause    INTEGER,
                    accX25ErrorDiag     INTEGER,
                    accX25ErrorPacket   OCTET STRING
                    }
        accX25ErrorLine     OBJECT-TYPE
                    SYNTAX  INTEGER
                    ACCESS  read-only
                    STATUS  mandatory
                    DESCRIPTION
                       " Physical port which encountered the error."
                    ::= { accX25ErrorEntry 1 }
	accX25ErrorUpTime   OBJECT-TYPE
                    SYNTAX  TimeTicks
                    ACCESS  read-only
                    STATUS  mandatory
                    DESCRIPTION
                      " SysUpTime when error occurred."
                    ::= { accX25ErrorEntry 2 }
        accX25ErrorSeq      OBJECT-TYPE
                    SYNTAX  INTEGER
                    ACCESS  read-only
                    STATUS  mandatory
                    DESCRIPTION
                       " Unique cutter (for duplicate date/time)."
                    ::= { accX25ErrorEntry 3 }
        accX25ErrorState    OBJECT-TYPE
                    SYNTAX  INTEGER {
                             valid (1),
                            invalid (2) -- to delete entry
                            }
                    ACCESS  read-write
                    STATUS  mandatory
                    DESCRIPTION
                       " Etnry status. "
                    ::= { accX25ErrorEntry 4 }
        accX25ErrorProtocol OBJECT-TYPE
                    SYNTAX  INTEGER
                    ACCESS  read-only
                    STATUS  mandatory
                    DESCRIPTION
                      " Protocol which encountered the error."
                    ::= { accX25ErrorEntry 5 }
        accX25ErrorCause    OBJECT-TYPE
                    SYNTAX  INTEGER
                    ACCESS  read-only
                    STATUS  mandatory
                    DESCRIPTION
                      " Cause octet from close packet."
                    ::= { accX25ErrorEntry 6 }
        accX25ErrorDiag     OBJECT-TYPE
                    SYNTAX  INTEGER
                    ACCESS  read-only
                    STATUS  mandatory
                    DESCRIPTION
                       " Diagnostic octet from close packet."
                    ::= { accX25ErrorEntry 7 }
        accX25ErrorPacket   OBJECT-TYPE
                    SYNTAX  OCTET STRING
                    ACCESS  read-only
                    STATUS  mandatory
                    DESCRIPTION
                        " Packet that triggered the log entry (if available)."
                    ::= { accX25ErrorEntry 8 }
-- X25 Switch Group
	accX25Switch    OBJECT IDENTIFIER  ::= { accX25 8  }
		accX25SwitchStatus  OBJECT-TYPE
			SYNTAX INTEGER {
			       enabled(1),
			       disabled(2)
			       }
			ACCESS read-write
			STATUS mandatory
			DESCRIPTION
				" This Object controls whether X.25 switching 
			is enabled or disabled."
			::= { accX25Switch 1 }
		accX25SwitchConnections  OBJECT-TYPE
			SYNTAX Gauge 
         		ACCESS read-only       
			STATUS mandatory        
			DESCRIPTION
				" This Object indicates the current number of
			X.25 connections that are being switched through this 
			router."
			::= { accX25Switch 2 }
		accX25SwitchCallSucceeds  OBJECT-TYPE
			SYNTAX Counter 
         		ACCESS read-only       
			STATUS mandatory        
			DESCRIPTION
				" This Object indicates the total number of
			X.25 calls that have been switched by this router."
			::= { accX25Switch 3 }
		accX25SwitchCallFails  OBJECT-TYPE
			SYNTAX Counter 
         		ACCESS read-only       
			STATUS mandatory        
			DESCRIPTION
				" This Object indicates the total number of
			X.25 calls that this router has been unable to switch."
			::= { accX25Switch 4 }
		accX25SwitchConnTable OBJECT-TYPE
			SYNTAX SEQUENCE OF AccX25SwitchConnEntry
			ACCESS not-accessible
			STATUS mandatory
			DESCRIPTION
				" This Table contains objects which report
		 	information about the X.25 calls currently being
			switched through this router."
			::= { accX25Switch 5 }
		accX25SwitchConnEntry OBJECT-TYPE
			SYNTAX AccX25SwitchConnEntry
			ACCESS not-accessible
			STATUS mandatory
			DESCRIPTION
				" The entry part of accX25SwitchConnTable."
			INDEX { accX25SwitchConnCallingIfIndex,
				accX25SwitchConnCallingIndex }
			::= { accX25SwitchConnTable 1 }
		AccX25SwitchConnEntry ::= SEQUENCE {
			accX25SwitchConnCallingIfIndex	INTEGER,
			accX25SwitchConnCallingIndex	INTEGER,
			accX25SwitchConnCallingType     INTEGER,
			accX25SwitchConnCallingX121Addr	OCTET STRING,
			accX25SwitchConnCallingPkts	Counter,
			accX25SwitchConnCallingOctets	Counter,
			accX25SwitchConnCalledIfIndex	INTEGER,
			accX25SwitchConnCalledIndex	INTEGER,
			accX25SwitchConnCalledType      INTEGER,
			accX25SwitchConnCalledX121Addr	OCTET STRING,
			accX25SwitchConnCalledPkts	Counter,
			accX25SwitchConnCalledOctets	Counter,
			accX25SwitchConnState		INTEGER
			}
		accX25SwitchConnCallingIfIndex OBJECT-TYPE
			SYNTAX INTEGER
			ACCESS read-only
			STATUS mandatory
			DESCRIPTION
				" An Integer that identifies the row of the
			system wide interfaces table associated with the X.25
			interface which initiated the connection."
			::= { accX25SwitchConnEntry 1 }
		accX25SwitchConnCallingIndex OBJECT-TYPE
			SYNTAX INTEGER
			ACCESS read-only
			STATUS mandatory
			DESCRIPTION
				" An Integer that uniquely identifies the 
			virtual circuit for the initiating interface. For
			X.25 ports, this will be the LCN. For the TCP ports,
			this will be the remote port number."
			::= { accX25SwitchConnEntry 2 }
		accX25SwitchConnCallingType OBJECT-TYPE
			SYNTAX INTEGER {
			       other(1),
			       x25(2),
			       tcp(3)
			       }
			ACCESS read-only
			STATUS mandatory
			DESCRIPTION
				" An integer that indicates the calling type."
			::= { accX25SwitchConnEntry 3 }
		accX25SwitchConnCallingX121Addr OBJECT-TYPE
			SYNTAX OCTET STRING
			ACCESS read-only
			STATUS mandatory
			DESCRIPTION
				" A string that contains the Calling X.121
			address that initiated the connection."
			::= { accX25SwitchConnEntry 4 }
		accX25SwitchConnCallingPkts OBJECT-TYPE
			SYNTAX Counter
			ACCESS read-only
			STATUS mandatory
			DESCRIPTION
				" A counter which keeps track of the number of
			packets sent from the calling to the called port."
			::= { accX25SwitchConnEntry 5 }
		accX25SwitchConnCallingOctets OBJECT-TYPE
			SYNTAX Counter
			ACCESS read-only
			STATUS mandatory
			DESCRIPTION
				" A counter which keeps track of the number of
			octets sent from the calling to the called port."
			::= { accX25SwitchConnEntry 6 }
		accX25SwitchConnCalledIfIndex OBJECT-TYPE
			SYNTAX INTEGER
			ACCESS read-only
			STATUS mandatory
			DESCRIPTION
				" An Integer that identifies the row of the
			system wide interfaces table associated with the X.25
			interface which propagated the connection."
			::= { accX25SwitchConnEntry 7 }
		accX25SwitchConnCalledIndex OBJECT-TYPE
			SYNTAX INTEGER
			ACCESS read-only
			STATUS mandatory
			DESCRIPTION
				" An Integer that uniquely identifies the 
			virtual circuit for the outgoing interface. For
			X.25 ports, this will be the LCN. For the TCP ports,
			this will be the local port number."
			::= { accX25SwitchConnEntry 8 }
		accX25SwitchConnCalledType OBJECT-TYPE
			SYNTAX INTEGER {
			       other(1),
			       x25(2),
			       tcp(3)
			       }
			ACCESS read-only
			STATUS mandatory
			DESCRIPTION
				" An integer that indicates the called type."
			::= { accX25SwitchConnEntry 9 }
		accX25SwitchConnCalledX121Addr OBJECT-TYPE
			SYNTAX OCTET STRING
			ACCESS read-only
			STATUS mandatory
			DESCRIPTION
				" A string that contains the Called X.121
			address that initiated the connection."
			::= { accX25SwitchConnEntry 10 }
		accX25SwitchConnCalledPkts OBJECT-TYPE
			SYNTAX Counter
			ACCESS read-only
			STATUS mandatory
			DESCRIPTION
				" A counter which keeps track of the number of
			packets sent from the calling to the called port."
			::= { accX25SwitchConnEntry 11 }
		accX25SwitchConnCalledOctets OBJECT-TYPE
			SYNTAX Counter
			ACCESS read-only
			STATUS mandatory
			DESCRIPTION
				" A counter which keeps track of the number of
			octets sent from the calling to the called port."
			::= { accX25SwitchConnEntry 12 }
		accX25SwitchConnState OBJECT-TYPE
			SYNTAX INTEGER {
			       open(1),
			       calling(2),
			       clearing(3),
			       resetting(4)
			       }
			ACCESS read-only
			STATUS mandatory
			DESCRIPTION
				" An integer that indicates the state of the
			switched X.25 circuit."
			::= { accX25SwitchConnEntry 13 }
		accX25SwitchAddrTransTable OBJECT-TYPE
			SYNTAX SEQUENCE OF AccX25SwitchAddrTransEntry
			ACCESS not-accessible
			STATUS mandatory
			DESCRIPTION
				" This Table contains objects which control
			the translation of X.121 addresses."
			::= { accX25Switch 6 }
		accX25SwitchAddrTransEntry OBJECT-TYPE
			SYNTAX AccX25SwitchAddrTransEntry
			ACCESS not-accessible
			STATUS mandatory
			DESCRIPTION
				" The entry part for the AddrTrans Table."
			INDEX { accX25SwitchAddrTransIfIndex,
				accX25SwitchAddrTransDir,
				accX25SwitchAddrTransType,
				accX25SwitchAddrTransPattern
			      }
			::= { accX25SwitchAddrTransTable 1 }
		AccX25SwitchAddrTransEntry ::= SEQUENCE {
			accX25SwitchAddrTransIfIndex	INTEGER,      
			accX25SwitchAddrTransDir	INTEGER, 
			accX25SwitchAddrTransType	INTEGER,
			accX25SwitchAddrTransPattern	DisplayString,
			accX25SwitchAddrTransReplace	DisplayString,
			accX25SwitchAddrTransStatus	INTEGER
			}
		accX25SwitchAddrTransIfIndex OBJECT-TYPE
		SYNTAX INTEGER
		ACCESS read-write
		STATUS mandatory
		DESCRIPTION
			" An Integer that identifies the row of the system
		wide interfaces table associated with the X.25 interface
		that receives the call request."
		::= { accX25SwitchAddrTransEntry 1 }
		accX25SwitchAddrTransDir OBJECT-TYPE
		SYNTAX INTEGER {
		       inbound(1),
		       outbound(2)
		       }
		ACCESS read-write
		STATUS mandatory
		DESCRIPTION
			" An Integer that identifies whether this entry applies
		to inbound or to outbound switched X.25 calls."
		::= { accX25SwitchAddrTransEntry 2 }
		accX25SwitchAddrTransType OBJECT-TYPE
		SYNTAX INTEGER {
		       called(1),
		       calling(2)
		       }
		ACCESS read-write
		STATUS mandatory
		DESCRIPTION
			" An Integer that identifies whether this entry applies
		to called or to calling X.121 addresses."
		::= { accX25SwitchAddrTransEntry 3 }
		accX25SwitchAddrTransPattern OBJECT-TYPE
		SYNTAX DisplayString
		ACCESS read-write
		STATUS mandatory
		DESCRIPTION
			" A character string which defines the matching pattern
		for incoming called X.121 addresses."	
		::= { accX25SwitchAddrTransEntry 4 }
		accX25SwitchAddrTransReplace OBJECT-TYPE
		SYNTAX DisplayString
		ACCESS read-write
		STATUS mandatory
		DESCRIPTION
			" A character string which defines the replacement
		pattern for incoming called X.121 addresses."	
		::= { accX25SwitchAddrTransEntry 5 }
		accX25SwitchAddrTransStatus OBJECT-TYPE
		SYNTAX INTEGER {
		       valid(1),
		       invalid(2)
		       }
		ACCESS read-write
		STATUS mandatory
		DESCRIPTION
			" An Integer that defines the status of the table row."
		::= { accX25SwitchAddrTransEntry 6 }
		accX25SwitchRouteTable OBJECT-TYPE
			SYNTAX SEQUENCE OF AccX25SwitchRouteEntry
			ACCESS not-accessible
			STATUS mandatory
			DESCRIPTION
				" This Table contains objects which determine
			the switching of incoming X.25 calls."
			::= { accX25Switch 7 }
		accX25SwitchRouteEntry OBJECT-TYPE
			SYNTAX AccX25SwitchRouteEntry
			ACCESS not-accessible
			STATUS mandatory
			DESCRIPTION
				" The entry part for the Route Table."
			INDEX { accX25SwitchRoutePattern}
			::= { accX25SwitchRouteTable 1 }
		AccX25SwitchRouteEntry ::= SEQUENCE {
			accX25SwitchRoutePattern	OCTET STRING,
			accX25SwitchRouteIfIndex	INTEGER,
			accX25SwitchRouteStatus		INTEGER
			}
		accX25SwitchRoutePattern OBJECT-TYPE
			SYNTAX OCTET STRING
			ACCESS read-write
			STATUS mandatory
			DESCRIPTION
				" A character string which defines the
			matching pattern for the incoming called X.121
			addresses."
			::= { accX25SwitchRouteEntry 1 }
		accX25SwitchRouteIfIndex OBJECT-TYPE
			SYNTAX INTEGER
			ACCESS read-write
			STATUS mandatory
			DESCRIPTION
				" An Integer that identifies the row of the
			system wide interfaces table associated with the X.25
			interface which receives the call request."
			::= { accX25SwitchRouteEntry 2 }
		accX25SwitchRouteStatus OBJECT-TYPE
		SYNTAX INTEGER {
		       valid(1),
		       invalid(2)
		       }
		ACCESS read-write
		STATUS mandatory
		DESCRIPTION
			" An Integer that defines the status of the table row."
		::= { accX25SwitchRouteEntry 3 }
		accX25SwitchExtRtTable OBJECT-TYPE
			SYNTAX SEQUENCE OF AccX25SwitchExtRtEntry
			ACCESS not-accessible
			STATUS mandatory
			DESCRIPTION
				" This Table contains an extended set
			of objects which determine the switching of
			incoming X.25 calls."
			::= { accX25Switch 8 }
		accX25SwitchExtRtEntry OBJECT-TYPE
			SYNTAX AccX25SwitchExtRtEntry
			ACCESS not-accessible
			STATUS mandatory
			DESCRIPTION
				" The entry part for the Extended Route Table."
			INDEX { accX25SwitchExtRtIndex}
			::= { accX25SwitchExtRtTable 1 }
		AccX25SwitchExtRtEntry ::= SEQUENCE {
			accX25SwitchExtRtIndex		INTEGER,
			accX25SwitchExtRtIfIn		INTEGER,
			accX25SwitchExtRtAddr		OCTET STRING,
			accX25SwitchExtRtCUD		OCTET STRING,
			accX25SwitchExtRtDisp		INTEGER,
			accX25SwitchExtRtIfOut		INTEGER,
			accX25SwitchExtRtStatus		INTEGER
			}
		accX25SwitchExtRtIndex OBJECT-TYPE
			SYNTAX INTEGER
			ACCESS read-write
			STATUS mandatory
			DESCRIPTION
				" An Integer that uniquely identifies
			this row of the Extended Switching Table."
			::= { accX25SwitchExtRtEntry 1 }
		accX25SwitchExtRtIfIn OBJECT-TYPE
			SYNTAX INTEGER
			ACCESS read-write
			STATUS mandatory
			DESCRIPTION
				" An Integer that identifies the row of the
			system wide interfaces table associated with the X.25
			interface which receives the call request.  This column
			must match the interface that the call is received on
			before a match can be made.  A value of zero will match
			calls received from any interface."
			::= { accX25SwitchExtRtEntry 2 }
		accX25SwitchExtRtAddr OBJECT-TYPE
			SYNTAX OCTET STRING
			ACCESS read-write
			STATUS mandatory
			DESCRIPTION
				" A character string which defines the
			matching pattern for the incoming called X.121
			addresses."
			::= { accX25SwitchExtRtEntry 3 }
		accX25SwitchExtRtCUD OBJECT-TYPE
			SYNTAX OCTET STRING
			ACCESS read-write
			STATUS mandatory
			DESCRIPTION
				" A octet string which defines the matching
				pattern for the incoming Call User Data.  A
				zero length octet string matches any Call
				User Data contents (including none)."
			::= { accX25SwitchExtRtEntry 4 }
		accX25SwitchExtRtDisp OBJECT-TYPE
			SYNTAX INTEGER {
				switch(1),
				local(2),
				reject(3)
				}
			ACCESS read-write
			STATUS mandatory
			DESCRIPTION
				" An Integer that specifies the disposition
			of incoming calls that match this table entry.  A
			value of 'switch' causes matching calls to be switched
			out the interface specified by accX25SwitchExtRtIfOut.
			A value of 'local' causes the call to be processed for
			local call termination.  A value of 'reject' causes the
			call to be cleared."
			::= { accX25SwitchExtRtEntry 5 }
		accX25SwitchExtRtIfOut OBJECT-TYPE
			SYNTAX INTEGER
			ACCESS read-write
			STATUS mandatory
			DESCRIPTION
				" An Integer that identifies the row of the
			system wide interfaces table associated with the X.25
			interface to which the call will be switched.  This
			column is only significant when the disposition is
			'switch'."
			::= { accX25SwitchExtRtEntry 6 }
		accX25SwitchExtRtStatus OBJECT-TYPE
		SYNTAX INTEGER {
		       valid(1),
		       invalid(2)
		       }
		ACCESS read-write
		STATUS mandatory
		DESCRIPTION
			" An Integer that defines the status of the table row."
		::= { accX25SwitchExtRtEntry 7 }
-- IP Filter Group
      accIpFilter   OBJECT IDENTIFIER  ::= { accBRG 18 }
	accIpSrcRouting	 OBJECT-TYPE   
			SYNTAX	INTEGER {
			   on(1),  --
			   off(2)  -- Discard source-routed IP packets
			}
			ACCESS read-write
			STATUS	mandatory
			DESCRIPTION
                         " Source Routing mode"
			::= { accIpFilter 1 }
-- This filter table is being deprecated in favor of the one that follows.
-- The new table represents extended IP filtering capability added in 
-- version 7.3.8 of the router application.
	accIpFiltTable	OBJECT-TYPE
			SYNTAX SEQUENCE OF AccIpFiltEntry
			ACCESS not-accessible
			STATUS deprecated
			DESCRIPTION
			 " List of IP filters
			   Entries added/deleted by management action.
			   Setting any object to NULL deletes the entry"
			::= { accIpFilter 2 }
	  accIpFiltEntry  OBJECT-TYPE
			SYNTAX AccIpFiltEntry
			ACCESS not-accessible
			STATUS deprecated
			DESCRIPTION
			 " Specific IP filter"
                        INDEX { accIpFiltDAddr,
	    		        accIpFiltDNetMask,
	    		        accIpFiltSAddr,
	    		        accIpFiltSNetMask,
	    		        accIpFiltParm,
                                accIpFiltDisp }
			::= { accIpFiltTable 1 }
		AccIpFiltEntry ::= SEQUENCE {
	    		accIpFiltDAddr 		IpAddress,
	    		accIpFiltDNetMask	IpAddress,
	    		accIpFiltSAddr		IpAddress,
	    		accIpFiltSNetMask	IpAddress,
	    		accIpFiltParm		OCTET STRING,
	    		accIpFiltDisp		INTEGER
			}
	    accIpFiltDAddr  OBJECT-TYPE	 
			SYNTAX	IpAddress
			ACCESS	read-write
			STATUS	deprecated
			DESCRIPTION
			 " Destination Address "
			::= { accIpFiltEntry 1 }
	    accIpFiltDNetMask  OBJECT-TYPE  
			SYNTAX	IpAddress
			ACCESS	read-write
			STATUS	deprecated
			DESCRIPTION
			 " Destination Network Mask"
			::= { accIpFiltEntry 2 }
	    accIpFiltSAddr  OBJECT-TYPE	 
			SYNTAX	IpAddress
			ACCESS	read-write
			STATUS	deprecated
			DESCRIPTION
			 " Source Address "
			::= { accIpFiltEntry 3 }
	    accIpFiltSNetMask  OBJECT-TYPE  
			SYNTAX	IpAddress
			ACCESS	read-write
			STATUS	deprecated
			DESCRIPTION
			 " Source Network Mask "
			::= { accIpFiltEntry 4 }
	    accIpFiltParm  OBJECT-TYPE	
			SYNTAX	OCTET STRING
			ACCESS	read-write
			STATUS	deprecated
			DESCRIPTION
			 " Filter parameters;
			     Byte 0 is Operation 1
			        [0,1,2] = [None, !,=]
			    Bytes 1,2 is Protocol
			    Byte 3 is Operation 2
			        [0	     = none
			        [1,2,3,4]    = both [!, <, >, =]
			        [5,6,7,8]    = destination [!, <, >, =]
			        [9,10,11,12] = source [!, <, >, =]
			     Bytes 4,5 is UDP/TCP port number"
			::= { accIpFiltEntry 5 }
	    accIpFiltDisp  OBJECT-TYPE	
			SYNTAX	INTEGER (0..3)
			ACCESS	read-write
			STATUS	deprecated
			DESCRIPTION
			 " Disposition of  packets meeting the
                           filter criteria.  Packets not discarded
                           will be output with the selected relative
                           transmission priority.
				 normalPriority(0),
				 discard(1),
				 lowPriority(2),
				 highPriority(3)
			"
			::= { accIpFiltEntry 6 }
-- { accIpFilter  3 } Is being used by an SMDS IP table not yet documented
-- as of 01/26/95.
           oIpSubDirBcast     OBJECT-TYPE   
                         SYNTAX  INTEGER {
                                 bcast(1),
                                 nobcast(2)
                                 }
                       ACCESS  read-write
                       STATUS  mandatory
                       DESCRIPTION
                  "Packets with an all-ones host portion of the
                   destination IP address are called Subnet Directed
                   Broadcast (or Limited Broadcast) packets.  This
                   object selects if these packets are to be broadcast
                   onto the destination subnet."
                       ::= { accIpFilter  4 }
-- This table is only used for the display of current filters. 
-- The table that follows this one is used for editing the filter database.
-- These changes added with version 7.3.8 of the router application.
	accIpIfFiltDispTable	OBJECT-TYPE
			SYNTAX SEQUENCE OF AccIpIfFiltDispEntry
			ACCESS not-accessible
			STATUS mandatory
			DESCRIPTION
			 " List of revised IP filters which add support for
			   filtering by source or destination interface."
			::= { accIpFilter 5 }
	  accIpIfFiltDispEntry  OBJECT-TYPE
			SYNTAX AccIpIfFiltDispEntry
			ACCESS not-accessible
			STATUS mandatory
			DESCRIPTION
			 " An entry in the revised IP filter table."
                        INDEX { accIpIfFiltDispIfIndex,
				accIpIfFiltDispPktDir,
				accIpIfFiltDispSeqNum
				}
			::= { accIpIfFiltDispTable 1 }
		AccIpIfFiltDispEntry ::= SEQUENCE {
			accIpIfFiltDispIfIndex		INTEGER,
			accIpIfFiltDispPktDir		INTEGER,
			accIpIfFiltDispSeqNum		INTEGER,
	    		accIpIfFiltDispDAddr 		IpAddress,
	    		accIpIfFiltDispDNetMask		IpAddress,
	    		accIpIfFiltDispSAddr		IpAddress,
	    		accIpIfFiltDispSNetMask		IpAddress,
	    		accIpIfFiltDispOp1		INTEGER,
	    		accIpIfFiltDispProtocol		INTEGER,
	    		accIpIfFiltDispOp2		INTEGER,
	    		accIpIfFiltDispUDPTCPPort	INTEGER,
	    		accIpIfFiltDispDispos		INTEGER,
			accIpIfFiltDispMatches		Counter,
			accIpIfFiltDispLastMatchTime 	TimeTicks,
			accIpIfFiltDispMatchPkt OCTET STRING
			}
	    accIpIfFiltDispIfIndex  OBJECT-TYPE	 
			SYNTAX	INTEGER
			ACCESS	read-only
			STATUS	mandatory
			DESCRIPTION
			 " Interface index to which this filter applies, or
			   zero for global filters.
			   This integer identifies the row of the system wide 
                           interfaces table associated with the particular 
                           interface."
			::= { accIpIfFiltDispEntry 1 }
	    accIpIfFiltDispPktDir  OBJECT-TYPE	 
			SYNTAX	INTEGER {
				input(1),
				output(2),
				global(3)
				}
			ACCESS	read-only
			STATUS	mandatory
			DESCRIPTION
			 "Stream direction to which filter is applied.
			  Input and Output require an interface to
			  be specified. Global indicates all interfaces
			  and both directions. Input and Global filters are 
                          applied prior to Output filters.
                          NOTE: a packet originating in the router may not
                          pass through the filter logic."
			::= { accIpIfFiltDispEntry 2 }
	    accIpIfFiltDispSeqNum  OBJECT-TYPE	 
			SYNTAX	INTEGER
			ACCESS	read-only
			STATUS	mandatory
			DESCRIPTION
                          " An internally generated sequence number used to
			    allow the Filter display table to be retruned in
                            the order the filters are applied (most specific
                            to least specific) without violating SNMP ordering
                            rules. Sequence numbers for all filters may change
                            with a single addition or modification of a filter.
                            Sequence numbers, once assigned, are not assigned
                            again. This number has no intrinsic meaning." 
			::= { accIpIfFiltDispEntry 3 }
	    accIpIfFiltDispDAddr  OBJECT-TYPE	 
			SYNTAX	IpAddress
			ACCESS	read-only
			STATUS	mandatory
			DESCRIPTION
			 " Destination Address "
			::= { accIpIfFiltDispEntry 4 }
	    accIpIfFiltDispDNetMask  OBJECT-TYPE  
			SYNTAX	IpAddress
			ACCESS	read-only
			STATUS	mandatory
			DESCRIPTION
			 " Destination Network Mask"
			::= { accIpIfFiltDispEntry 5 }
	    accIpIfFiltDispSAddr  OBJECT-TYPE	 
			SYNTAX	IpAddress
			ACCESS	read-only
			STATUS	mandatory
			DESCRIPTION
			 " Source Address "
			::= { accIpIfFiltDispEntry 6 }
	    accIpIfFiltDispSNetMask  OBJECT-TYPE  
			SYNTAX	IpAddress
			ACCESS	read-only
			STATUS	mandatory
			DESCRIPTION
			 " Source Network Mask "
			::= { accIpIfFiltDispEntry 7 }
	    accIpIfFiltDispOp1  OBJECT-TYPE	
			SYNTAX	INTEGER {
                                none(1),
                                not-equal(2),
                                equal(3)
				}
			ACCESS	read-only
			STATUS	mandatory
			DESCRIPTION
			 " Logical operation to be performed on the next
                           object/parameter (protocol). If 'none', the 
			   filter will match any protocol."
			::= { accIpIfFiltDispEntry 8 }
	    accIpIfFiltDispProtocol  OBJECT-TYPE	
			SYNTAX	INTEGER (0..255)
			ACCESS	read-only
			STATUS	mandatory
			DESCRIPTION
			 " Ip protocol on which to filter."
			REFERENCE
			 " Assigned numbers document."
			::= { accIpIfFiltDispEntry 9 }
	    accIpIfFiltDispOp2  OBJECT-TYPE	
			SYNTAX	INTEGER {
                                none(1),
                                not-equal(2),
                                less-than(3),
                                greater-than(4),
                                equal(5),
				src-not-equal(6),
				src-less-than(7),
				src-greater-than(8),
				src-equal(9),
				dst-not-equal(10),
				dst-less-than(11),
				dst-greater-than(12),
				dst-equal(13)
				}
			ACCESS	read-only
			STATUS	mandatory
			DESCRIPTION
                         " Logical operation to be performed on the next
                           object/parameter (port)."
			::= { accIpIfFiltDispEntry 10 }
	    accIpIfFiltDispUDPTCPPort  OBJECT-TYPE	
			SYNTAX	INTEGER (1..65535)
			ACCESS	read-only
			STATUS	mandatory
			DESCRIPTION
			 " The UDP or TCP port number to which the previous
			   logical operation is to apply."
			::= { accIpIfFiltDispEntry 11 }
	    accIpIfFiltDispDispos  OBJECT-TYPE	
			SYNTAX	INTEGER {
				 discard(1),
				 log(2),
				 normalPriority(3),
				 lowPriority(4),
				 highPriority(5)
				}
			ACCESS	read-only
			STATUS	mandatory
			DESCRIPTION
			 " Disposition of packets meeting the
                           filter criteria. Packets not discarded
                           will be output with the selected relative
                           transmission priority. The log option causes a
			   rate selected trap to be generated."
			::= { accIpIfFiltDispEntry 12 }
            accIpIfFiltDispMatches  OBJECT-TYPE
                        SYNTAX  Counter
                        ACCESS  read-only
                        STATUS  mandatory
                        DESCRIPTION
                         "The number of times this filter criteria has been
			  applied."
                        ::= { accIpIfFiltDispEntry 13 }
            accIpIfFiltDispLastMatchTime  OBJECT-TYPE
                        SYNTAX  TimeTicks
                        ACCESS  read-only
                        STATUS  mandatory
                        DESCRIPTION
                         " The value of sysUpTime the last time this filter
                           was applied."
                        ::= { accIpIfFiltDispEntry 14 }
            accIpIfFiltDispMatchPkt  OBJECT-TYPE
                        SYNTAX  OCTET STRING -- (SIZE (64))
                        ACCESS  read-only
                        STATUS  mandatory
                        DESCRIPTION
                         " This object is used exclusivley for returning
                           information in a trap about the last packet that was 
                           filtered. A query of this object will return an
                           octet string of length zero."
                        ::= { accIpIfFiltDispEntry 15 }
-- This table is only used for editing the filter database.
	accIpIfFiltEditTable	OBJECT-TYPE
			SYNTAX SEQUENCE OF AccIpIfFiltEditEntry
			ACCESS not-accessible
			STATUS mandatory
			DESCRIPTION
			 " A transient table which is used to create/delete
                           /modify an entry in the IP filter database."
			::= { accIpFilter 6 }
	  accIpIfFiltEditEntry  OBJECT-TYPE
			SYNTAX AccIpIfFiltEditEntry
			ACCESS not-accessible
			STATUS mandatory
			DESCRIPTION
			 " An entry in the revised IP filter table."
                        INDEX { accIpIfFiltEditIndex }
			::= { accIpIfFiltEditTable 1 }
		AccIpIfFiltEditEntry ::= SEQUENCE {
			accIpIfFiltEditIndex		INTEGER,
	    		accIpIfFiltEditAction		INTEGER,
			accIpIfFiltEditIfIndex		INTEGER,
			accIpIfFiltEditPktDir		INTEGER,
	    		accIpIfFiltEditDAddr 		IpAddress,
	    		accIpIfFiltEditDNetMask		IpAddress,
	    		accIpIfFiltEditSAddr		IpAddress,
	    		accIpIfFiltEditSNetMask		IpAddress,
	    		accIpIfFiltEditOp1		INTEGER,
	    		accIpIfFiltEditProtocol		INTEGER,
	    		accIpIfFiltEditOp2		INTEGER,
	    		accIpIfFiltEditUDPTCPPort	INTEGER,
	    		accIpIfFiltEditDispos		INTEGER
			}
	    accIpIfFiltEditIndex  OBJECT-TYPE	 
			SYNTAX	INTEGER
			ACCESS	read-only
			STATUS	mandatory
			DESCRIPTION
			 "An arbitrary number assigned to the record that
                          is currently being edited."
			::= { accIpIfFiltEditEntry 1 }
	    accIpIfFiltEditAction  OBJECT-TYPE	 
			SYNTAX	INTEGER {
				add(1),
				delete(2)
				}
			ACCESS	read-write
			STATUS	mandatory
			DESCRIPTION
			 " The action to be performed with this record. In the
                          future the field 'pending' may be added."
			::= { accIpIfFiltEditEntry 2 }
	    accIpIfFiltEditIfIndex  OBJECT-TYPE	 
			SYNTAX	INTEGER
			ACCESS	read-write
			STATUS	mandatory
			DESCRIPTION
			 " Interface index to which this filter applies, or
			   zero for global filters.
			   This integer identifies the row of the system wide 
                           interfaces table associated with the particular 
                           interface."
			::= { accIpIfFiltEditEntry 3 }
	    accIpIfFiltEditPktDir  OBJECT-TYPE	 
			SYNTAX	INTEGER {
				input(1),
				output(2),
				global(3)
				}
			ACCESS	read-write
			STATUS	mandatory
			DESCRIPTION
                         "Stream direction to which filter is applied.
                          Input and Output require an interface to
                          be specified. Global indicates all interfaces
                          and both directions. Input and Global filters are
                          applied prior to Output filters.
                          NOTE: a packet originating in the router may not
                          pass through the filter logic."
			::= { accIpIfFiltEditEntry 4 }
	    accIpIfFiltEditDAddr  OBJECT-TYPE	 
			SYNTAX	IpAddress
			ACCESS	read-write
			STATUS	mandatory
			DESCRIPTION
			 " Destination Address "
			::= { accIpIfFiltEditEntry 5 }
	    accIpIfFiltEditDNetMask  OBJECT-TYPE  
			SYNTAX	IpAddress
			ACCESS	read-write
			STATUS	mandatory
			DESCRIPTION
			 " Destination Network Mask"
			::= { accIpIfFiltEditEntry 6 }
	    accIpIfFiltEditSAddr  OBJECT-TYPE	 
			SYNTAX	IpAddress
			ACCESS	read-write
			STATUS	mandatory
			DESCRIPTION
			 " Source Address "
			::= { accIpIfFiltEditEntry 7 }
	    accIpIfFiltEditSNetMask  OBJECT-TYPE  
			SYNTAX	IpAddress
			ACCESS	read-write
			STATUS	mandatory
			DESCRIPTION
			 " Source Network Mask "
			::= { accIpIfFiltEditEntry 8 }
	    accIpIfFiltEditOp1  OBJECT-TYPE	
			SYNTAX	INTEGER {
                                none(1),
                                equal(2),
                                not-equal(3)
				}
			ACCESS	read-write
			STATUS	mandatory
			DESCRIPTION
			 " Logical operation to be performed on the next
                           object/parameter (protocol). If 'none', the 
			   filter will match any protocol."
			::= { accIpIfFiltEditEntry 9 }
	    accIpIfFiltEditProtocol  OBJECT-TYPE	
			SYNTAX	INTEGER (0..255)
			ACCESS	read-write
			STATUS	mandatory
			DESCRIPTION
			 " Ip protocol on which to filter."
			REFERENCE
			 " Assigned numbers document."
			::= { accIpIfFiltEditEntry 10 }
	    accIpIfFiltEditOp2  OBJECT-TYPE	
			SYNTAX	INTEGER {
                                none(1),
                                equal(2),
                                not-equal(3),
                                less-than(4),
                                greater-than(5),
				dst-equal(6),
				dst-not-equal(7),
				dst-less-than(8),
				dst-greater-than(9),
				src-equal(10),
				src-not-equal(11),
				src-less-than(12),
				src-greater-than(13)
				}
			ACCESS	read-write
			STATUS	mandatory
			DESCRIPTION
                         " Logical operation to be performed on the next
                           object/parameter (port)."
			::= { accIpIfFiltEditEntry 11 }
	    accIpIfFiltEditUDPTCPPort  OBJECT-TYPE	
			SYNTAX	INTEGER (1..65535)
			ACCESS	read-write
			STATUS	mandatory
			DESCRIPTION
			 " The UDP or TCP port number to which the previous
			   logical operation is to apply."
			::= { accIpIfFiltEditEntry 12 }
	    accIpIfFiltEditDispos  OBJECT-TYPE	
			SYNTAX	INTEGER {
				 discard(1),
				 log(2),
				 normalPriority(3),
				 lowPriority(4),
				 highPriority(5)
				}
			ACCESS	read-write
			STATUS	mandatory
			DESCRIPTION
			 " Disposition of packets meeting the
                           filter criteria. Packets not discarded
                           will be output with the selected relative
                           transmission priority. The log option causes a
			   rate sensitive trap to be generated."
			::= { accIpIfFiltEditEntry 13 }
-- DECnet Group
      accDn        OBJECT IDENTIFIER  ::= { accBRG 19 }
	accDnNumber	OBJECT-TYPE  
			SYNTAX	INTEGER
			ACCESS read-only
			STATUS mandatory
			DESCRIPTION
			 " Number of DECNET circuits"
			::= { accDn 1 }
	accDnID		OBJECT-TYPE  
			SYNTAX	INTEGER
			ACCESS read-write
			STATUS mandatory
			DESCRIPTION
			 " Node ID;  Least 10 bits identify the node,
			   six bits above that identify the area."
			::= { accDn 2 }
	accDnMaxNode	OBJECT-TYPE  
			SYNTAX	INTEGER (1..1023)
			ACCESS read-write
			STATUS mandatory
			DESCRIPTION
			 " Maximum node number permitted in the local area"
			::= { accDn 3 }
	accDnMaxArea	OBJECT-TYPE  
			SYNTAX	INTEGER (1..63)
			ACCESS read-write
			STATUS mandatory
			DESCRIPTION
			 " Maximum area number permitted"
			::= { accDn 4 }
	accDnMaxAdjRtr	OBJECT-TYPE  
			SYNTAX	INTEGER (1..64)
			ACCESS read-write
			STATUS mandatory
			DESCRIPTION
			 " Maximum number of adjacent routers "
			::= { accDn 5 }
	accDnMaxEndNode OBJECT-TYPE  
			SYNTAX	INTEGER (1..1023)
			ACCESS read-write
			STATUS mandatory
			DESCRIPTION
			 " Maximum number of broadcast endnode adjacencies"
			::= { accDn 6 }
	accDnMaxLocHop	OBJECT-TYPE  
			SYNTAX	INTEGER (1..30)
			ACCESS read-write
			STATUS mandatory
			DESCRIPTION
			 " Maximum number of hops allowed within this area"
			::= { accDn 7 }
	accDnMaxLocCost OBJECT-TYPE  
			SYNTAX	INTEGER (1..1022)
			ACCESS read-write
			STATUS mandatory
			DESCRIPTION
			 " Maximum cost allowed on a path within this area"
			::= { accDn 8 }
	accDnMaxVisit	OBJECT-TYPE  
			SYNTAX	INTEGER (1..63)
			ACCESS read-write
			STATUS mandatory
			DESCRIPTION
			 " Maximum number of node visits allowed for a packet"
			::= { accDn 9 }
	accDnMaxForHop	OBJECT-TYPE  
			SYNTAX	INTEGER (1..30)
			ACCESS read-write
			STATUS mandatory
			DESCRIPTION
			 " Maximum number of hops allowed to another area"
			::= { accDn 10 }
	accDnMaxForCost OBJECT-TYPE  
			SYNTAX	INTEGER (1..1022)
			ACCESS read-write
			STATUS mandatory
			DESCRIPTION
			 " Maximum cost allowed on a path to another area"
			::= { accDn 11 }
	accDnBCT1		OBJECT-TYPE  
			SYNTAX	TimeTicks
			ACCESS read-write
			STATUS mandatory
			DESCRIPTION
			 " Interval between retranmissions of routing
			   database updates on Broadcast Address"
			::= { accDn 12 }
	accDnT1		OBJECT-TYPE  
			SYNTAX	TimeTicks
			ACCESS read-write
			STATUS mandatory
			DESCRIPTION
			 " Interval between retranmissions of routing
			   database updates  non-broadcast"
			::= { accDn 13 }
	accDnMsgLev	OBJECT-TYPE  
			SYNTAX	INTEGER (1..7)
			ACCESS read-write
			STATUS mandatory
			DESCRIPTION
			 " Message level for generation of trap messages
			   describing DECNET operational phenonomena
			   See Trap level for description"
			::= { accDn 14 }
	accDnNodeState	OBJECT-TYPE  
			SYNTAX	INTEGER {
			off(1),
			level1(2),
			level2(3)
			}
			ACCESS read-write
			STATUS mandatory
			DESCRIPTION
			 " Operational state of the node "
			::= { accDn 15 }
	accDnUnreachs	OBJECT-TYPE  
			SYNTAX	Counter
			ACCESS read-only
			STATUS mandatory
			DESCRIPTION
			 " Packets dropped due to node unreachable"
			::= { accDn 16 }
	accDnVisitXcds	OBJECT-TYPE  
			SYNTAX	Counter
			ACCESS read-only
			STATUS mandatory
			DESCRIPTION
			 " Packets dropped due to visits exceeded"
			::= { accDn 17 }
	accDnBadNodes	OBJECT-TYPE  
			SYNTAX	Counter
			ACCESS read-only
			STATUS mandatory
			DESCRIPTION
			 " Packets dropped due to illegal node number"
			::= { accDn 18 }
	accDnPktOsizes OBJECT-TYPE  
			SYNTAX	Counter
			ACCESS read-only
			STATUS mandatory
			DESCRIPTION
			 " Packets dropped due to oversize packet"
			::= { accDn 19 }
	accDnFmtErrs	OBJECT-TYPE  
			SYNTAX	Counter
			ACCESS read-only
			STATUS mandatory
			DESCRIPTION
			 " Packets dropped due to packet format error"
			::= { accDn 20 }
	accDnCktTable  OBJECT-TYPE
			SYNTAX  SEQUENCE OF AccDnCktEntry
			ACCESS not-accessible
			STATUS mandatory
			DESCRIPTION
                         " DECnet circuit table
			   Entries are added/deleted via management action."
			::= { accDn 21 }
	  accDnCktEntry	 OBJECT-TYPE
			SYNTAX AccDnCktEntry
			ACCESS not-accessible
			STATUS mandatory
	  		DESCRIPTION
			 " The instance of an entry is the circuit number.
			   Existing entries can be modified."
                        INDEX { accDnCktIndex }
	  		::= { accDnCktTable 1 }
	    AccDnCktEntry ::= SEQUENCE {
			accDnCktIndex		INTEGER,
			accDnCktStatus		INTEGER,
			accDnCktState		INTEGER,
			accDnCktCost		INTEGER,
			accDnMaxRtr		INTEGER,
			accDnHelloInt		TimeTicks,
			accDnRtrPriority	INTEGER,
			accDnDesRtrId		OCTET STRING,
			accDnDesRtrPrio		INTEGER,
			accDnTrnPktRecs		Counter,
			accDnTrnPktSnds		Counter,
			accDnEndNodePktRecs	Counter,
			accDnEndNodePktSnds	Counter,
			accDnCktDowns		Counter,
			accDnCktType		INTEGER,
			accDnCktPort		INTEGER,
			accDnX25InOutAddr	DisplayString,
			accDnX25InAddr		DisplayString,
			accDnX25Idle		TimeTicks,
			accDnX25PktVal		INTEGER,
			accDnX25PktWin		INTEGER,
			accDnEntryStatus	INTEGER,
			accDnX25FacIndex	INTEGER
		    	}
	    accDnCktIndex  OBJECT-TYPE	
			SYNTAX	INTEGER
			ACCESS	read-write
			STATUS	mandatory
			DESCRIPTION
			 " Circuit number "
			::= { accDnCktEntry 1 }
	    accDnCktStatus  OBJECT-TYPE	 
			SYNTAX	INTEGER {
				on(1),
				off(2)
			}
			ACCESS	read-write
			STATUS	mandatory
			DESCRIPTION
			 " Administrative DECNET state of this circuit"
                        DEFVAL { off }
			::= { accDnCktEntry 2 }
	    accDnCktState  OBJECT-TYPE	
			SYNTAX	INTEGER {
				up(1),
				down(2),
				shut(3),
				start(4),
				test(5)
			   }
			ACCESS	read-only
			STATUS	mandatory
			DESCRIPTION
			 " Operational DECNET state of this circuit"
			::= { accDnCktEntry 3 }
	    accDnCktCost  OBJECT-TYPE  
			SYNTAX	INTEGER (1..1022)
			ACCESS	read-write
			STATUS	mandatory
			DESCRIPTION
			 " Administrative circuit cost
			   Object will be set to a circuit-type
                           dependent value if not present
			      in entry-adding SET PDU."
			::= { accDnCktEntry 4 }
	    accDnMaxRtr	 OBJECT-TYPE  
			SYNTAX	INTEGER (1..32)
			ACCESS	read-write
			STATUS	mandatory
			DESCRIPTION
			 " Maximum number of routers that can be
			   communicated with over this circuit"
                        DEFVAL { 4 }
			::= { accDnCktEntry 5 }
	    accDnHelloInt  OBJECT-TYPE	
			SYNTAX	TimeTicks
			ACCESS	read-write
			STATUS	mandatory
			DESCRIPTION
			 " Interval between transmission of Router Hello
			   messages to other DECNET routers on this circuit"
                        DEFVAL { 15 }
			::= { accDnCktEntry 6 }
	    accDnRtrPriority  OBJECT-TYPE  
			SYNTAX	INTEGER (0..255)
			ACCESS	read-write
			STATUS	mandatory
			DESCRIPTION
			 " Priority of this Decnet router to become
			   designated router on this circuit."
                        DEFVAL { 15 }
			::= { accDnCktEntry 7 }
	    accDnDesRtrId  OBJECT-TYPE	
			SYNTAX  OCTET STRING -- (SIZE(3))	
			ACCESS	read-only
			STATUS	mandatory
			DESCRIPTION
			 " ID of router which is designated router on
			   this circuit.  Lower 10 bits is node number,
			   six bits above that are area number."
			::= { accDnCktEntry 8 }
	    accDnDesRtrPrio  OBJECT-TYPE  
			SYNTAX	INTEGER (0..255)
			ACCESS	read-only
			STATUS	mandatory
			DESCRIPTION
			 " Priority of router which is designated router on
			   this circuit.  "
			::= { accDnCktEntry 9 }
	    accDnTrnPktRecs  OBJECT-TYPE	 
			SYNTAX	Counter
			ACCESS	read-only
			STATUS	mandatory
			DESCRIPTION
			 " Number of transit packets received on
			   this circuit."
			::= { accDnCktEntry 10 }
	    accDnTrnPktSnds  OBJECT-TYPE	 
			SYNTAX	Counter
			ACCESS	read-only
			STATUS	mandatory
			DESCRIPTION
			 " Number of transit packets sent on
			   this circuit."
			::= { accDnCktEntry 11 }
	    accDnEndNodePktRecs	OBJECT-TYPE  
			SYNTAX	Counter
			ACCESS	read-only
			STATUS	mandatory
			DESCRIPTION
			 " Number of end-node packets received on
			   this circuit."
			::= { accDnCktEntry 12 }
	    accDnEndNodePktSnds	OBJECT-TYPE  
			SYNTAX	Counter
			ACCESS	read-only
			STATUS	mandatory
			DESCRIPTION
			 " Number of end-node packets sent on
			   this circuit."
			::= { accDnCktEntry 13 }
	    accDnCktDowns  OBJECT-TYPE  
			SYNTAX	Counter
			ACCESS	read-only
			STATUS	mandatory
			DESCRIPTION
			 " Number of circuit down events noted on
			   this circuit."
			::= { accDnCktEntry 14 }
	    accDnCktType  OBJECT-TYPE  
			SYNTAX	INTEGER {
				enet(6),
				trn(9),
				lapb(16),
				mlink(129),
				x25(130),
				fr(131)
			    }
			ACCESS	read-write
			STATUS	mandatory
			DESCRIPTION
			 " Circuit type
			   Object required in entry-adding SET PDU."
			::= { accDnCktEntry 15 }
	    accDnCktPort  OBJECT-TYPE  
			SYNTAX	INTEGER {
				j1(1),
				j2(2),
				j3(3)
			    }
			ACCESS	read-write
			STATUS	mandatory
			DESCRIPTION
			 " Physical port that this circuit is on
			   Object required in entry-adding SET PDU."
			::= { accDnCktEntry 16 }
	    accDnX25InOutAddr  OBJECT-TYPE  
			SYNTAX  DisplayString	
			ACCESS	read-write
			STATUS	mandatory
			DESCRIPTION
			 " X25 address for other end of circuit; we'll
			   send to this address and will accept packets from
			   this address for this circuit.
			   Object required in entry-adding SET PDU if
			      circuit type is X.25"
			::= { accDnCktEntry 17 }
	    accDnX25InAddr  OBJECT-TYPE  
			SYNTAX  DisplayString	
			ACCESS	read-write
			STATUS	mandatory
			DESCRIPTION
			 "  Packets from this address are accepted 
			   on this circuit.
			   Object will be set to default value if not present
			       in entry-adding SET PDU."
			::= { accDnCktEntry 18 }
	    accDnX25Idle  OBJECT-TYPE  
			SYNTAX	TimeTicks
			ACCESS	read-write
			STATUS	mandatory
			DESCRIPTION
			 " Maximum idle time before this circuit is 
			   considered unused.
			   Object will be set to default value if not present
			       in entry-adding SET PDU."
			::= { accDnCktEntry 19 }
	    accDnX25PktVal  OBJECT-TYPE  
			SYNTAX	INTEGER (0..1024)
			ACCESS	read-write
			STATUS	mandatory
			DESCRIPTION
			 " Maximum X25 packet size
			   Object will be set to default value if not present
			       in entry-adding SET PDU."
			::= { accDnCktEntry 20 }
	    accDnX25PktWin  OBJECT-TYPE  
			SYNTAX	INTEGER (0..127)
			ACCESS	read-write
			STATUS	mandatory
			DESCRIPTION
			 " X25 packet window
			   Object will be set to default value if not present
			       in entry-adding SET PDU."
			::= { accDnCktEntry 21 }
	    accDnEntryStatus  OBJECT-TYPE  
			SYNTAX	INTEGER {
				other(1),
				invalid(2)
			    }
			ACCESS	read-write
			STATUS	mandatory
			DESCRIPTION
			 " Setting this object to invalid deletes entry"
			::= { accDnCktEntry 22 }
	accDnX25FacIndex  OBJECT-TYPE
	           SYNTAX  INTEGER (0..255)
	           ACCESS  read-write
	           STATUS  mandatory
	           DESCRIPTION
	                " Index of optional facility string or 0."
	           DEFVAL { 0 }
	           ::= { accDnCktEntry 23 }
	accDnRtTable  OBJECT-TYPE
			SYNTAX  SEQUENCE OF AccDnRtEntry
			ACCESS not-accessible
			STATUS mandatory
			DESCRIPTION
			 " DECnet routing table"
			::= { accDn 22 }
	  accDnRtEntry	OBJECT-TYPE
			SYNTAX AccDnRtEntry
			ACCESS not-accessible
			STATUS mandatory
	  		DESCRIPTION
		            " Detail on specific route "
                        INDEX { accDnRtNode }
	  		::= { accDnRtTable 1 }
             AccDnRtEntry ::= SEQUENCE {
			accDnRtNode		INTEGER,
			accDnRtHops		INTEGER,
			accDnRtCost		INTEGER,
			accDnRtCkt		INTEGER,
			accDnRtNextHop		INTEGER
			}
	    accDnRtNode	 OBJECT-TYPE  
			SYNTAX	INTEGER
			ACCESS	read-only
			STATUS	mandatory
			DESCRIPTION
			 " Destination node"
			::= { accDnRtEntry 1 }
	    accDnRtHops	 OBJECT-TYPE  
			SYNTAX	INTEGER
			ACCESS	read-only
			STATUS	mandatory
			DESCRIPTION
			 " Number of hops to destination"
			::= { accDnRtEntry 2 }
	    accDnRtCost	 OBJECT-TYPE  
			SYNTAX	INTEGER
			ACCESS	read-only
			STATUS	mandatory
			DESCRIPTION
			 " Cost to destination"
			::= { accDnRtEntry 3 }
	    accDnRtCkt	OBJECT-TYPE  
			SYNTAX	INTEGER
			ACCESS	read-only
			STATUS	mandatory
			DESCRIPTION
			 " Circuit number to use to get to destination"
			::= { accDnRtEntry 4 }
	    accDnRtNextHop  OBJECT-TYPE	 
			SYNTAX	INTEGER
			ACCESS	read-only
			STATUS	mandatory
			DESCRIPTION
			 " Next router along the way to destination"
			::= { accDnRtEntry 5 }
	accDnAreaTable	OBJECT-TYPE
			SYNTAX SEQUENCE OF AccDnAreaEntry
			ACCESS not-accessible
			STATUS mandatory
			DESCRIPTION
			 " DECnet area table."
			::= { accDn 23 }
	  accDnAreaEntry  OBJECT-TYPE
			SYNTAX  AccDnAreaEntry
			ACCESS not-accessible
			STATUS mandatory
			DESCRIPTION
		        " Details on specific area "
                        INDEX { accDnAreaArea }
			::= { accDnAreaTable 1 }
	      AccDnAreaEntry ::= SEQUENCE {
			accDnAreaArea		INTEGER,
			accDnAreaHops		INTEGER,
			accDnAreaCost		INTEGER,
			accDnAreaCkt		INTEGER,
			accDnAreaNextHop	INTEGER
			}
	    accDnAreaArea  OBJECT-TYPE	
			SYNTAX	INTEGER
			ACCESS	read-only
			STATUS	mandatory
			DESCRIPTION
			 " Remote area"
			::= { accDnAreaEntry 1 }
	    accDnAreaHops  OBJECT-TYPE	
			SYNTAX	INTEGER
			ACCESS	read-only
			STATUS	mandatory
			DESCRIPTION
			 " Hops to Remote area"
			::= { accDnAreaEntry 2 }
	    accDnAreaCost  OBJECT-TYPE	
			SYNTAX	INTEGER
			ACCESS	read-only
			STATUS	mandatory
			DESCRIPTION
			 " Cost to Remote area"
			::= { accDnAreaEntry 3 }
	    accDnAreaCkt  OBJECT-TYPE  
			SYNTAX	INTEGER
			ACCESS	read-only
			STATUS	mandatory
			DESCRIPTION
			 " Circuit over which remote area can be reached."
			::= { accDnAreaEntry 4 }
	    accDnAreaNextHop  OBJECT-TYPE  
			SYNTAX	INTEGER
			ACCESS	read-only
			STATUS	mandatory
			DESCRIPTION
			 " Next hop to remote area."
			::= { accDnAreaEntry 5 }
     --  DECNET IV Route Filters are used to suppress acceptance of
     --  advertisements of level 1 and level 2 routes.
     accDnRouteFilterTable OBJECT-TYPE
         SYNTAX   SEQUENCE OF AccDnRouteFilterEntry
         ACCESS   not-accessible
         STATUS   mandatory
         DESCRIPTION
             " The DECNET IV Routes that the Network Manager wants to
               be careful about."
         ::= { accDn 24 }
       accDnRouteFilterEntry OBJECT-TYPE
           SYNTAX   AccDnRouteFilterEntry
           ACCESS   not-accessible
           STATUS   mandatory
           DESCRIPTION
               " A single controlled DECNET Route."
           INDEX { accDnRouteFilterAdj, accDnRouteFilterNode }
           ::= { accDnRouteFilterTable 1 }
       AccDnRouteFilterEntry ::=
           SEQUENCE {
               accDnRouteFilterAdj
                   INTEGER,
               accDnRouteFilterNode
                   INTEGER,
               accDnRouteFilterDisposition
                   INTEGER,
               accDnRouteFilterEntStat
                   INTEGER
       }
         accDnRouteFilterAdj OBJECT-TYPE
             SYNTAX   INTEGER (0..65535)
             ACCESS   read-write
             STATUS   mandatory
            DESCRIPTION
                 " If 0, all adjacent systems.
                   If a DECNET Area with host id 0,  all  adjacent
                   systems in that area.
                   If a DECNET Host ID, that adjacent system."
            ::= { accDnRouteFilterEntry 1 }
         accDnRouteFilterNode OBJECT-TYPE
             SYNTAX   INTEGER (0..65535)
             ACCESS   read-write
             STATUS   mandatory
            DESCRIPTION
                 " If 0, all routing information.
                   If a DECNET Area with Host ID 0, relevant level
                   2 routing information.
                   If a DECNET Host ID, level 1  routing  informa-
                   tion for that host."
            ::= { accDnRouteFilterEntry 2 }
         accDnRouteFilterDisposition OBJECT-TYPE
             SYNTAX   INTEGER {
                         accept(1),
                         reject(2)
                      }
             ACCESS   read-write
             STATUS   mandatory
            DESCRIPTION
                 " This variable indicates what to  do  with  the
                   indicated  routing information.  Where overlaps
                   occur ('accept no routing information from area
                   3.0 except from router 3.27'), the most specif-
                   ic match applies."
            ::= { accDnRouteFilterEntry 3 }
         accDnRouteFilterEntStat OBJECT-TYPE
             SYNTAX   INTEGER {
                         invalid(1),
                         valid(2)
                      }
             ACCESS   read-write
             STATUS   mandatory
            DESCRIPTION
                 " setting this variable to 'invalid' has the ef-
                   fect  of  invalidating it as of the next system
                   reset."
            ::= { accDnRouteFilterEntry 4 }
     --  DECNET Forwarding Filter Table
     --  DECNET Forwarding Filter indicates routes from source
     --  to destination.  Traffic on those routes is affected.
     accDnForwardFilterTable OBJECT-TYPE
         SYNTAX   SEQUENCE OF AccDnForwardFilterEntry
         ACCESS   not-accessible
         STATUS   mandatory
         DESCRIPTION
             " The DECNET traffic that the Network Manager wants
               selectively treated."
         ::= { accDn 25 }
     accDnForwardFilterEntry OBJECT-TYPE
         SYNTAX   AccDnForwardFilterEntry
         ACCESS   not-accessible
         STATUS   mandatory
         DESCRIPTION
             " A single set of messages that the Network Manager
               wants selectively treated."
         INDEX { accDnForwardFilterDest, 
                 accDnForwardFilterSource }
         ::= { accDnForwardFilterTable 1 }
     AccDnForwardFilterEntry ::=
         SEQUENCE {
             accDnForwardFilterDest
                 INTEGER,
             accDnForwardFilterSource
                 INTEGER,
             accDnForwardFilterDisposition
                 INTEGER,
             accDnForwardFilterEntStat
                 INTEGER
     }
         accDnForwardFilterDest OBJECT-TYPE
             SYNTAX   INTEGER (0..65535)
             ACCESS   read-write
             STATUS   mandatory
            DESCRIPTION
                 " If 0, all DECNET Addresses.
                   If an Area with Host Part  0,  all  traffic  to
                   that Area.
                   If a DECNET Host ID, all traffic to that Host."
            ::= { accDnForwardFilterEntry 1 }
         accDnForwardFilterSource OBJECT-TYPE
             SYNTAX   INTEGER (0..65535)
             ACCESS   read-write
             STATUS   mandatory
            DESCRIPTION
                 " If 0, all DECNET Traffic.
                   If an Area with Host Part 0, all  traffic  from
                   that Area.
                   If a DECNET Host  ID,  all  traffic  from  that
                   Host."
            ::= { accDnForwardFilterEntry 2 }
         accDnForwardFilterDisposition OBJECT-TYPE
             SYNTAX   INTEGER (0..3)
             ACCESS   read-write
             STATUS   mandatory
            DESCRIPTION
                 " This variable indicates what  is  to  be  done
                   with  traffic  from accDnForwardFilterSource to
                   accDnForwardFilterDest.   When  overlaps  occur
                   ('discard all traffic from Area 4.0 to Anywhere
                   except traffic  from  Host  4.123'),  the  most
                   specific match applies.
                         discard(0),
                         lowPriority(1),
                         normalPriority(2),
                         highPriority(3)
		"
            ::= { accDnForwardFilterEntry 3 }
         accDnForwardFilterEntStat OBJECT-TYPE
             SYNTAX   INTEGER {
                         invalid(1),
                         valid(2)
                      }
             ACCESS   read-write
             STATUS   mandatory
            DESCRIPTION
                 " setting accDnForwardFilterEntStat  to  invalid
                   has  the  effect  of removing the filter on the
                   next system reset."
            ::= { accDnForwardFilterEntry 4 }
     --  DECNET Adjacent System Table
     --  This table displays all systems maintaining current DECNET
     --  adjacencies with the system being queried.
     accDnAdjTable OBJECT-TYPE
         SYNTAX   SEQUENCE OF AccDnAdjEntry
         ACCESS   not-accessible
         STATUS   mandatory
         DESCRIPTION
             " The set of systems adjacent to this router."
         ::= { accDn 26 }
     accDnAdjEntry OBJECT-TYPE
         SYNTAX   AccDnAdjEntry
         ACCESS   not-accessible
         STATUS   mandatory
         DESCRIPTION
             " One of the systems adjacent to this router."
         INDEX { accDnAdjNode }
         ::= { accDnAdjTable 1 }
     AccDnAdjEntry ::=
         SEQUENCE {
             accDnAdjNode
                 INTEGER,
             accDnAdjType
                 INTEGER,
             accDnAdjCircuit
                 INTEGER,
             accDnAdjState
                 INTEGER
     }
         accDnAdjNode OBJECT-TYPE
             SYNTAX   INTEGER (0..65535)
             ACCESS   read-only
             STATUS   mandatory
            DESCRIPTION
                 " The Host Identifier of the adjacent node."
            ::= { accDnAdjEntry 1 }
         accDnAdjType OBJECT-TYPE
             SYNTAX   INTEGER {
                         level2Only(1),
                         level2(2),
                         level1(3),
                         endNode(4)
                      }
             ACCESS   read-only
             STATUS   mandatory
            DESCRIPTION
                 " The type of DECNET adjacency being sustained."
            ::= { accDnAdjEntry 2 }
         accDnAdjCircuit OBJECT-TYPE
             SYNTAX   INTEGER
             ACCESS   read-only
             STATUS   mandatory
            DESCRIPTION
                 " The DECNET Circuit Number."
            ::= { accDnAdjEntry 3 }
         accDnAdjState OBJECT-TYPE
             SYNTAX   INTEGER {
                         up(1),
                         initializing(2),
                         circuitFailed(3),
                         timedOut(4)
                      }
             ACCESS   read-only
             STATUS   mandatory
            DESCRIPTION
                 " The state of the adjacency."
            ::= { accDnAdjEntry 4 }
-- Frame Relay Group
-- Frame Relay addresses (Data Link Connection Identifiers, or DLCIs) are
-- represented as octet strings of length 2.
      accFr     OBJECT IDENTIFIER  ::= { accBRG 20 }
	accFrAtTable	OBJECT-TYPE
			SYNTAX	SEQUENCE OF AccFrAtEntry
			ACCESS	not-accessible
			STATUS	mandatory
			DESCRIPTION
			 " Internet address translation table for Frame
			   Relay interfaces.
			   Entries are added/deleted via management action."
			::= { accFr 1	}
	  accFrAtEntry OBJECT-TYPE
			SYNTAX	AccFrAtEntry
			ACCESS	not-accessible
			STATUS	mandatory
			DESCRIPTION
			 " Internet address translation entry for Frame Relay
			   interfaces."
                        INDEX { accFrAtIfIndex,
                                accFrIpAddress }
			::= { accFrAtTable 1 }
			AccFrAtEntry ::= SEQUENCE {
			    accFrAtIfIndex	INTEGER,
			    accFrIpAddress	IpAddress,
			    accFrDLCI		INTEGER,
			    accFrStatus		INTEGER   
			    }
	  accFrAtIfIndex	OBJECT-TYPE	
			SYNTAX	INTEGER
			ACCESS	read-write
			STATUS	mandatory
			DESCRIPTION
			 " Interface number (ifIndex) for which this 
			   translation entry is valid.
			   Object required in entry-adding SET PDU."
			::= { accFrAtEntry 1 }
	  accFrIpAddress	OBJECT-TYPE	
			SYNTAX	IpAddress
			ACCESS	read-write
			STATUS	mandatory
			DESCRIPTION
			 " IP Address
			   Object required in entry-adding SET PDU."
			::= { accFrAtEntry 2 }
	  accFrDLCI	OBJECT-TYPE	
			SYNTAX	INTEGER
			ACCESS	read-write
			STATUS	mandatory
			DESCRIPTION
			 " Frame Relay DLCI to use for the specified host
			   Object required in entry-adding SET PDU."
			::= { accFrAtEntry 3 }
	  accFrStatus	OBJECT-TYPE	
			SYNTAX	INTEGER {
                                permanent(1),  -- Manually added
				dynamic(2),    -- Learned by Inverse ARP
				confirm-pending(3), -- Learning
				not-connected(4)   -- Manually entered, but
				}
			ACCESS	read-write
			STATUS	mandatory
			DESCRIPTION
			 " Status of this entry
			   Object required in entry-adding SET PDU."
			::= { accFrAtEntry 4 }
	accFrStatTable	OBJECT-TYPE
			SYNTAX	SEQUENCE OF AccFrStatEntry
			ACCESS	not-accessible
			STATUS	mandatory
			DESCRIPTION
			 " Per-line statistics for Frame Relay interfaces"
			::= { accFr 2 }
	  accFrStatEntry	OBJECT-TYPE
			SYNTAX	AccFrStatEntry
			ACCESS	not-accessible
			STATUS	mandatory
			DESCRIPTION
			 " Frame Relay statistics"
                        INDEX { accFrIndex }
			::= { accFrStatTable 1 }
			AccFrStatEntry ::= SEQUENCE {
			    accFrIndex		INTEGER,
			    accFrStatRcvDrops	Counter,
			    accFrStatShorts	Counter,
			    accFrStatIllDlcis	Counter,
			    accFrStatUnkDlcis	Counter,
			    accFrStatUnkProtos	Counter,
			    accFrStatRsrvDlcis	Counter,
			    accFrStatXmtDrops	Counter,
			    accFrStatErrTime	TimeTicks,
			    accFrStatErrType	INTEGER,
			    accFrStatErrDlci	INTEGER,
			    accFrStatErrProto	INTEGER,
			    accFrLinkState	INTEGER,
			    accFrStatUnks	Counter,
			    accFrStatRcvLongs	Counter,
                            accFrStatIlgDlcis	Counter,
			    accFrStatProtoErrs	Counter,
                            accFrStatUnkIes	Counter,
			    accFrStatSeqErrs	Counter,
			    accFrStatUnkRpts	Counter
			    }
	    accFrIndex	OBJECT-TYPE   
			SYNTAX	INTEGER
			ACCESS	read-only
			STATUS	mandatory
			DESCRIPTION
			 " Physical Port number of this Frame Relay interface."
			::= { accFrStatEntry 1 }
	    accFrStatRcvDrops	OBJECT-TYPE   
			SYNTAX	Counter
			ACCESS	read-only
			STATUS	mandatory
			DESCRIPTION
			 " Number of received frames that were discarded due
			   to lack of resources."
			::= { accFrStatEntry 2 }
	    accFrStatShorts		OBJECT-TYPE   
			SYNTAX	Counter
			ACCESS	read-only
			STATUS	mandatory
			DESCRIPTION
			 " Number of received frames that were discarded
			   because they were too short (DLCI and/or
			   protocol field missing)."
			::= { accFrStatEntry 3 }
	    accFrStatIllDlcis	OBJECT-TYPE   
			SYNTAX	Counter
			ACCESS	read-only
			STATUS	mandatory
			DESCRIPTION
			 " Number of received frames that were discarded
			   because the DLCI was badly formed."
			::= { accFrStatEntry 4 }
	    accFrStatUnkDlcis	OBJECT-TYPE   
			SYNTAX	Counter
			ACCESS	read-only
			STATUS	mandatory
			DESCRIPTION
			 " Number of received frames that were discarded
			   because the DLCI did not match any configured
			   value."
			::= { accFrStatEntry 5 }
	    accFrStatUnkProtos	OBJECT-TYPE   
			SYNTAX	Counter
			ACCESS	read-only
			STATUS	mandatory
			DESCRIPTION
			 " Number of received frames that were discarded
			   because the protocol field did not match any
			   protocol configured for the specified DLCI."
			::= { accFrStatEntry 6 }
	    accFrStatRsrvDlcis	OBJECT-TYPE   
			SYNTAX	Counter
			ACCESS	read-only
			STATUS	mandatory
			DESCRIPTION
			 " Number of received frames whose DLCI had the
			   reserved bit set.  (The frame was not discarded;
			   the frame was processed as though the reserved
			   bit were clear)."
			::= { accFrStatEntry 7 }
	    accFrStatXmtDrops	OBJECT-TYPE   
			SYNTAX	Counter
			ACCESS	read-only
			STATUS	mandatory
			DESCRIPTION
			 " Number of frames that could not be transmitted
			   due to lack of resources."
			::= { accFrStatEntry 8 }
	    accFrStatErrTime	OBJECT-TYPE   
			SYNTAX	TimeTicks
			ACCESS	read-only
			STATUS	mandatory
			DESCRIPTION
			 " System uptime when the last Frame Relay error was
			   detected."
			::= { accFrStatEntry 9 }
	    accFrStatErrType	OBJECT-TYPE   
			SYNTAX	INTEGER {
				rcvDrop(1),
				short(2),
				illDlci(3),
				unkDlci(4),
				unkProto(5),
				rsrvDlci(6),
				xmtDrop(7),
	   			 unknownError(8),
	   			 receiveLong(9),
	   			 illegalDLCI(10),
	   			 dlcmiProtoErr(11),
	   			 dlcmiUnknownIE(12),
	   			 dlcmiSequenceErr(13),
	   			 dlcmiUnknownRpt(14)
				}
			ACCESS	read-only
			STATUS	mandatory
			DESCRIPTION
			 " Type of last detected Frame Relay error."
			::= { accFrStatEntry 10 }
	    accFrStatErrDlci	OBJECT-TYPE   
			SYNTAX	INTEGER
			ACCESS	read-only
			STATUS	mandatory
			DESCRIPTION
			 " Value of DLCI field from last detected Frame Relay
			   error (00 00 if no DLCI was associated with the
			   last error)."
			::= { accFrStatEntry 11 }
	    accFrStatErrProto	OBJECT-TYPE   
			SYNTAX	INTEGER
			ACCESS	read-only
			STATUS	mandatory
			DESCRIPTION
			 " Value of protocol field from last detected Frame
			   Relay error (0 if no protocol field was associated
			   with the last error)."
			::= { accFrStatEntry 12 }
	    accFrLinkState	OBJECT-TYPE   
			SYNTAX	INTEGER {
                                down(1),
                                up(2),
                                idle(3)
                                 }
			ACCESS	read-only
			STATUS	mandatory
			DESCRIPTION
			 " State of this Frame Relay link"
			::= { accFrStatEntry 13 }
	    accFrStatUnks	OBJECT-TYPE   
			SYNTAX	Counter
			ACCESS	read-only
			STATUS	mandatory
			DESCRIPTION
			 " Unused object"
			::= { accFrStatEntry 14 }
	    accFrStatRcvLongs	OBJECT-TYPE   
			SYNTAX	Counter
			ACCESS	read-only
			STATUS	mandatory
			DESCRIPTION
			 " Number of received dlcmi frames longer than expected."
			::= { accFrStatEntry 15 }
	    accFrStatIlgDlcis	OBJECT-TYPE   
			SYNTAX	Counter
			ACCESS	read-only
			STATUS	mandatory
			DESCRIPTION
			 " Unused object"
			::= { accFrStatEntry 16 }
	    accFrStatProtoErrs	OBJECT-TYPE   
			SYNTAX	Counter
			ACCESS	read-only
			STATUS	mandatory
			DESCRIPTION
			 " Number of received frames with a protocol violation."
			::= { accFrStatEntry 17 }
	    accFrStatUnkIes	OBJECT-TYPE   
			SYNTAX	Counter
			ACCESS	read-only
			STATUS	mandatory
			DESCRIPTION
			 " Number of dlcmi frames received with an 
                           unknown Information element."
			::= { accFrStatEntry 18 }
	    accFrStatSeqErrs	OBJECT-TYPE   
			SYNTAX	Counter
			ACCESS	read-only
			STATUS	mandatory
			DESCRIPTION
			 " Number of dlcmi frames received with a
                           sequence error."
			::= { accFrStatEntry 19 }
	    accFrStatUnkRpts	OBJECT-TYPE   
			SYNTAX	Counter
			ACCESS	read-only
			STATUS	mandatory
			DESCRIPTION
			 " Unused object"
			::= { accFrStatEntry 20 }
	accFrParmTable	OBJECT-TYPE
			SYNTAX	SEQUENCE OF AccFrParmEntry
			ACCESS	not-accessible
			STATUS	mandatory
			DESCRIPTION
                         " Frame Relay parameter table"
			::= { accFr 3 }
	  accFrParmEntry	OBJECT-TYPE
			SYNTAX	AccFrParmEntry
			ACCESS	not-accessible
			STATUS	mandatory
			DESCRIPTION
                         " Frame Relay parameter entry"
                        INDEX { accFrParmIndex }
			::= { accFrParmTable 1 }
			AccFrParmEntry ::= SEQUENCE {
			    accFrParmIndex	INTEGER,
			    accFrParmAddrFmt	INTEGER,
			    accFrParmAddrLen	INTEGER,
			    accFrParmEncap	INTEGER,
			    accFrDlcmiState	INTEGER,
			    accFrDlcmiPollInt   INTEGER,
			    accFrDlcmiFullStatEnq	INTEGER,
			    accFrDlcmiErrThres	INTEGER,
			    accFrDlcmiMonEvents	INTEGER,
			    accFrDlcmiType	INTEGER,
			    accFrDlcmiIdleTimer	INTEGER
			    }
	    accFrParmIndex	OBJECT-TYPE
			SYNTAX	INTEGER
			ACCESS	read-only
			STATUS	mandatory
			DESCRIPTION
			  " Interface number"
			::= { accFrParmEntry 1 }
	    accFrParmAddrFmt	OBJECT-TYPE
			SYNTAX	INTEGER {
				q921(1),
				draft-q922(2),
				q922(3)
				}
			ACCESS	read-write
			STATUS	mandatory
			DESCRIPTION
			 " Addressing format used.
			     Q.921 per spec.  Ignores length parameter
			     draft-Q922  per March, 1990 draft of Q.922
			     q922 per October, 1990 Q.922 specification"
			::= { accFrParmEntry 2 }
	    accFrParmAddrLen	OBJECT-TYPE
			SYNTAX	INTEGER (2..4)
			ACCESS	read-write
			STATUS	mandatory
			DESCRIPTION
			 " Length of address on serial line"
			::= { accFrParmEntry 3 }
	    accFrParmEncap	OBJECT-TYPE
			SYNTAX	INTEGER {
				early(1),
				ietf(2)
				}
			ACCESS	read-write
			STATUS	mandatory
			DESCRIPTION
			 " Type of encapsulation used on serial line"
			::= { accFrParmEntry 4 }
	    accFrDlcmiState	OBJECT-TYPE
			SYNTAX	INTEGER {
				off(1),
				lmi(2),
				annexd(3)
				}
			ACCESS	read-write
			STATUS	mandatory
			DESCRIPTION
	                 " This variable states which Data Link Connection
	                   Management scheme is active (and by implication,
	                   what DLCI it uses) on the Frame Relay interface."
			::= { accFrParmEntry 5 }
	    accFrDlcmiPollInt	OBJECT-TYPE
			SYNTAX	INTEGER (5..30)
			ACCESS	read-write
			STATUS	mandatory
			DESCRIPTION
	    		 " the number of seconds between successive
			   status enquiry messages."
			::= { accFrParmEntry 6 }
	    accFrDlcmiFullStatEnq	OBJECT-TYPE
			SYNTAX	INTEGER (1..255)
			ACCESS	read-write
			STATUS	mandatory
			DESCRIPTION
			 " Number of status enquiry intervals that pass
			   before issuance of a full status enquiry message."
			::= { accFrParmEntry 7 }
	    accFrDlcmiErrThres	OBJECT-TYPE
			SYNTAX	INTEGER (1..10)
			ACCESS	read-write
			STATUS	mandatory
			DESCRIPTION
			 "  Maximum number of unanswered
			   Status Enquiries the equipmemt shall accept before
			   declaring the interface down."
			::= { accFrParmEntry 8 }
	    accFrDlcmiMonEvents	OBJECT-TYPE
			SYNTAX	INTEGER (5..30)
			ACCESS	read-write
			STATUS	mandatory
			DESCRIPTION
			 " Maximum number of responses to
			   FULL STATUS or LINK INTEGRITY VERIFICATION
			   messages missed before the device will mark the
			   interface down."
			::= { accFrParmEntry 9 }
	    accFrDlcmiType	OBJECT-TYPE
			SYNTAX	INTEGER {
			     user(1),
			     network(2)
			     }
			ACCESS	read-write
			STATUS	mandatory
			DESCRIPTION
			 " Link Maintenance is assymmetrical, so
			   one end must be user, the other network.
			   Normally the bridge/router is user."
			::= { accFrParmEntry 10 }
	    accFrDlcmiIdleTimer	OBJECT-TYPE
			SYNTAX	INTEGER (0..255) 
			ACCESS	read-write
			STATUS	mandatory
			DESCRIPTION
			 " Number of minutes without receiving any
			   non-dlcmi frames before declaring the link idle.
			   Setting the timer to 0 will disable it."
			::= { accFrParmEntry 11 }
	accFrCktTable	OBJECT-TYPE
			SYNTAX	SEQUENCE OF AccFrCktEntry
			ACCESS	not-accessible
			STATUS	mandatory
			DESCRIPTION
                         " Frame Relay circuit table"
			::= { accFr 4 }
	  accFrCktEntry	OBJECT-TYPE
			SYNTAX	AccFrCktEntry
			ACCESS	not-accessible
			STATUS	mandatory
			DESCRIPTION
                         " Frame Relay circuit table entry"
                        INDEX { accFrCktIfIndex }
			::= { accFrCktTable 1 }
			AccFrCktEntry ::= SEQUENCE {
			    accFrCktIfIndex	INTEGER,
			    accFrCktDlci	INTEGER,
			    accFrCktState	INTEGER,
			    accFrCktFECNrcvds	Counter,
			    accFrCktBECNrcvds	Counter,
			    accFrCktFrameXmts	Counter,
			    accFrCktOctetXmts	Counter,
			    accFrCktFrameRcvs	Counter,
			    accFrCktOctetRcvs	Counter,
			    accFrCktCreateTime	TimeTicks,
			    accFrCktChangeTime	TimeTicks,
	                    accFfrCktLoop INTEGER
			    }
	    accFrCktIfIndex	OBJECT-TYPE
			SYNTAX	INTEGER
			ACCESS	read-only
			STATUS	mandatory
			DESCRIPTION
			  " Interface on which this circuit exists"
			::= { accFrCktEntry 1 }
	    accFrCktDlci	OBJECT-TYPE
			SYNTAX	INTEGER
			ACCESS	read-only
			STATUS	mandatory
			DESCRIPTION
			 " Data Link Connection Identifier for this
			   circuit."
			::= { accFrCktEntry 2 }
	    accFrCktState	OBJECT-TYPE
			SYNTAX	INTEGER {
				invalid(1),
				active(2),
				inactive(3)
				}
			ACCESS	read-only
			STATUS	mandatory
			DESCRIPTION
			 " Indicates whether the particular circuit is
			   operational."
			::= { accFrCktEntry 3 }
	    accFrCktFECNrcvds	OBJECT-TYPE
			SYNTAX	Counter
			ACCESS	read-only
			STATUS	mandatory
			DESCRIPTION
			 " Number of frames received from the network in-
			   dicating forward congestion since the circuit
			   was created.		 "
			::= { accFrCktEntry 4 }
	    accFrCktBECNrcvds	OBJECT-TYPE
			SYNTAX	Counter
			ACCESS	read-only
			STATUS	mandatory
			DESCRIPTION
			 " Number of frames received from the network in-
			   dicating backward congestion since the circuit
			   was created.		 "
			::= { accFrCktEntry 5 }
	    accFrCktFrameXmts	OBJECT-TYPE
			SYNTAX	Counter
			ACCESS	read-only
			STATUS	mandatory
			DESCRIPTION
			 " Number of frames sent from this circuit 
			   since it was created.	 "
			::= { accFrCktEntry 6 }
	    accFrCktOctetXmts	OBJECT-TYPE
			SYNTAX	Counter
			ACCESS	read-only
			STATUS	mandatory
			DESCRIPTION
			 " Number of octets sent from this circuit 
			   since it was created.	 "
			::= { accFrCktEntry 7 }
	    accFrCktFrameRcvs	OBJECT-TYPE
			SYNTAX	Counter
			ACCESS	read-only
			STATUS	mandatory
			DESCRIPTION
			 " Number of frames received by this circuit 
			   since it was created.	 "
			::= { accFrCktEntry 8 }
	    accFrCktOctetRcvs	OBJECT-TYPE
			SYNTAX	Counter
			ACCESS	read-only
			STATUS	mandatory
			DESCRIPTION
			 " Number of octets received by this circuit 
			   since it was created.	 "
			::= { accFrCktEntry 9 }
	    accFrCktCreateTime	OBJECT-TYPE
			SYNTAX	TimeTicks
			ACCESS	read-only
			STATUS	mandatory
			DESCRIPTION
			 " The value of sysUpTime when the circuit was
			   created."
			::= { accFrCktEntry 10 }
	    accFrCktChangeTime	OBJECT-TYPE
			SYNTAX	TimeTicks
			ACCESS	read-only
			STATUS	mandatory
			DESCRIPTION
			 " The value of sysUpTime when last there was a
			   change in the circuit state."
			::= { accFrCktEntry 11 }
	    accFfrCktLoop OBJECT-TYPE
			SYNTAX	INTEGER {
				normal (1),
				loop (2)
				}
			ACCESS	read-write
			STATUS	mandatory
			DESCRIPTION
			"Indicates the loopback state of the virtual circuit.
			 The object is normally 'normal', indicating that the
			 circuit is in its normal operational state. If set
			 to 'loop', any messages received on the circuit will
			 be returned unmodified and the circuit will always be
			 viewed as 'down' by higher layer protocols.
			 The state of any circuit reverts to 'normal' after
			 a reset."
			::= { accFrCktEntry 12 }
-- The objects for Frame Relay Switching
		accFfrSwitchParameterTable	OBJECT-TYPE
			SYNTAX SEQUENCE OF AccFfrSwitchParameterEntry
			ACCESS not-accessible
			STATUS mandatory
			DESCRIPTION
			"Frame Relay Switch Parameter table"
		::= { accFr 5 }
		accFfrSwitchParameterEntry	OBJECT-TYPE
			SYNTAX AccFfrSwitchParameterEntry
			ACCESS not-accessible
                        STATUS mandatory
                        DESCRIPTION
			"An entry in Frame Relay Switch Parameter table"
			INDEX {accFfrSwitchIfindex1,accFfrSwitchDlci1}
		::= { accFfrSwitchParameterTable 1 }
		AccFfrSwitchParameterEntry ::= SEQUENCE {
			accFfrSwitchIfindex1	INTEGER,
			accFfrSwitchDlci1	INTEGER,
			accFfrSwitchIfindex2	INTEGER,
			accFfrSwitchDlci2	INTEGER,
			accFfrSwitchStatus	INTEGER
			}
		accFfrSwitchIfindex1		OBJECT-TYPE
			SYNTAX INTEGER
			ACCESS read-write
			STATUS mandatory
                        DESCRIPTION
                        "The first interface index in the entry"
		::= { accFfrSwitchParameterEntry 1 }
		accFfrSwitchDlci1		OBJECT-TYPE
			SYNTAX INTEGER
			ACCESS read-write
			STATUS mandatory
                        DESCRIPTION
                        "The first Frame Relay DLCI in the entry"
		::= { accFfrSwitchParameterEntry 2 }
		accFfrSwitchIfindex2		OBJECT-TYPE
			SYNTAX INTEGER
			ACCESS read-write
			STATUS mandatory
                        DESCRIPTION
                        "The second interface index in the entry"
		::= { accFfrSwitchParameterEntry 3 }
		accFfrSwitchDlci2		OBJECT-TYPE
			SYNTAX INTEGER
			ACCESS read-write
			STATUS mandatory
                        DESCRIPTION
                        "The second Frame Relay DLCI in the entry"
		::= { accFfrSwitchParameterEntry 4 }
		accFfrSwitchStatus		OBJECT-TYPE
			SYNTAX INTEGER {
			       enable(1),	-- Switching Enabled
			       disable(2), 	-- Switching Disabled
			       deleted(128)	-- Entry Deleted
			       }
			ACCESS read-write
			STATUS mandatory
                        DESCRIPTION
                        "The Status tells whether the traffic will be switched
			as per the entry. This object also is usedin the delete
			command"
		::= { accFfrSwitchParameterEntry 5 }
-- XNS Group
   accXns         OBJECT IDENTIFIER ::= { accBRG 21 }
     accXnsParms	OBJECT IDENTIFIER ::= { accXns 1 }
       accXnsAdStat  OBJECT-TYPE   
			SYNTAX	INTEGER {
				on(1),
				off(2)
			}
			ACCESS	read-write
			STATUS	mandatory
			DESCRIPTION
                " Administrative status of XNS routing protocol"
			::= { accXnsParms 1 }
	  accXnsCkSum  OBJECT-TYPE   
			SYNTAX	INTEGER {
				off(1),
				packet(2),
				header(3)
			}
			ACCESS	read-write
			STATUS	mandatory
			DESCRIPTION
                " Checksumming of XNS protocol"
			::= { accXnsParms 2 }
	  accXnsSpltHorz  OBJECT-TYPE   
			SYNTAX	INTEGER {
				off(1),
				simple(2),
				poison(3)
			}
			ACCESS	read-write
			STATUS	mandatory
			DESCRIPTION
                " Split horizon mode of XNS protocol"
			::= { accXnsParms 3 }
	  accXnsAllNets  OBJECT-TYPE   
			SYNTAX	INTEGER {
				on(1),
				off(2)
			}
			ACCESS	read-write
			STATUS	mandatory
			DESCRIPTION
                " All nets mode"
			::= { accXnsParms 4 }
	  accXnsMode  OBJECT-TYPE   
			SYNTAX	INTEGER {
				xns(1),
				ub(2)
			}
			ACCESS	read-write
			STATUS	mandatory
			DESCRIPTION
                " RIP protocol type to use"
			::= { accXnsParms 5 }
     accXnsNetTable  OBJECT-TYPE   
			SYNTAX	SEQUENCE OF AccXnsNetEntry
			ACCESS	not-accessible
			STATUS	mandatory
			DESCRIPTION
                " List of XNS Networks.
	          Entries added/deleted by management action."
			::= { accXns 2 }
	  accXnsNetEntry  OBJECT-TYPE   
			SYNTAX	AccXnsNetEntry
			ACCESS	not-accessible
			STATUS	mandatory
			DESCRIPTION
                           " Information on specific network"
                        INDEX { accXnsNetPort }
			::= { accXnsNetTable 1 }
        AccXnsNetEntry ::= SEQUENCE {
			accXnsNetPort		INTEGER,
			accXnsNetNumber		OCTET STRING,
			accXnsNetType		INTEGER,
			accXnsNetEncap		INTEGER,
			accXnsNetSlot		INTEGER,
			accXnsNetAdStat		INTEGER,
			accXnsNetMtu		INTEGER,
			accXnsNetUpdate		TimeTicks,
			accXnsNetHops		INTEGER,
			accXnsNetCost		INTEGER,
			accXnsNetX25InOutAddr	DisplayString,
			accXnsNetX25InAddr	DisplayString,
			accXnsNetX25Idle	TimeTicks,
			accXnsNetX25PktVal	INTEGER,
			accXnsNetX25PktWin	INTEGER,
			accXnsNetEntryStat	INTEGER,
			accXnsNetUbUpdate	TimeTicks,
			accXnsNetUbTtl		TimeTicks,
			accXnsNetUbQT1		TimeTicks,
			accXnsNetUbQT2		TimeTicks,
                        accXnsNetFncAddr	OCTET STRING,
                        accXnsNetSrMode		INTEGER,
			accXnsNetX25FacIndex	INTEGER,
			accXnsNetDlci		INTEGER
 			}
	  accXnsNetPort  OBJECT-TYPE   
			SYNTAX	INTEGER
			ACCESS	read-write
			STATUS	mandatory
			DESCRIPTION
                " XNS logical port number "
			::= { accXnsNetEntry 1 }
	  accXnsNetNumber  OBJECT-TYPE   
			SYNTAX	OCTET STRING
			ACCESS	read-write
			STATUS	mandatory
			DESCRIPTION
                " XNS network number "
			::= { accXnsNetEntry 2 }
	  accXnsNetType  OBJECT-TYPE   
			SYNTAX	INTEGER {
				enet(1),
				token-ring(2),
				lapb(3),
				x25(4),
				ffr(5)
			}
			ACCESS	read-write
			STATUS	mandatory
			DESCRIPTION
                           " Type of network "
			::= { accXnsNetEntry 3 }
	  accXnsNetEncap  OBJECT-TYPE   
			SYNTAX	INTEGER (0..4)
			ACCESS	read-write
			STATUS	mandatory
			DESCRIPTION
                " LAN Encapsulation used (Ethernet).
				none(0),
				v2(1),
				raw(2),
				llc(3),
				snap(4)
		"
			::= { accXnsNetEntry 4 }
	  accXnsNetSlot  OBJECT-TYPE   
			SYNTAX	INTEGER {
				j1(1),
				j2(2),
				j3(3),
				b1(4)
			}
			ACCESS	read-write
			STATUS	mandatory
			DESCRIPTION
                " Slot to which the network is attached "
			::= { accXnsNetEntry 5 }
	  accXnsNetAdStat  OBJECT-TYPE   
			SYNTAX	INTEGER {
				on(1),
				off(2)
			}
			ACCESS	read-write
			STATUS	mandatory
			DESCRIPTION
	                  " Administrative status of network "
                        DEFVAL { on }
			::= { accXnsNetEntry 6 }
	  accXnsNetMtu  OBJECT-TYPE   
			SYNTAX	INTEGER (576..65535)
			ACCESS	read-write
			STATUS	mandatory
			DESCRIPTION
	        " Maximum packet size.
	          Object will be defaulted to a network type 
                  dependent value if missing in set PDU which
	          adds entries."
			::= { accXnsNetEntry 7 }
	  accXnsNetUpdate  OBJECT-TYPE   
			SYNTAX	TimeTicks
			ACCESS	read-write
			STATUS	mandatory
			DESCRIPTION
	        " Update interval "
                        DEFVAL { 1500 }
			::= { accXnsNetEntry 8 }
	  accXnsNetHops  OBJECT-TYPE   
			SYNTAX	INTEGER
			ACCESS	read-write
			STATUS	mandatory
			DESCRIPTION
	                    " Hop count"
                        DEFVAL { 1 }
			::= { accXnsNetEntry 9 }
	  accXnsNetCost  OBJECT-TYPE   
			SYNTAX	INTEGER
			ACCESS	read-write
			STATUS	mandatory
			DESCRIPTION
	        " Cost metric
	          Object will be defaulted to network type dependent
                  value if missing in set PDU which
	          adds entries."
			::= { accXnsNetEntry 10 }
	  accXnsNetX25InOutAddr  OBJECT-TYPE   
			SYNTAX  DisplayString	
			ACCESS	read-write
			STATUS	mandatory
			DESCRIPTION
	        " X25 address to send to and to receive packets from."
			::= { accXnsNetEntry 11 }
	  accXnsNetX25InAddr  OBJECT-TYPE   
			SYNTAX  DisplayString	
			ACCESS	read-write
			STATUS	mandatory
			DESCRIPTION
	        " Receive-only X25 address
	          Object not required in set PDU (defaults to In/Out address)"
			::= { accXnsNetEntry 12 }
	  accXnsNetX25Idle  OBJECT-TYPE   
			SYNTAX	TimeTicks 
			ACCESS	read-write
			STATUS	mandatory
			DESCRIPTION
	        " Time X25 connection can be idle before it is 
	          determined to be not busy."
                        DEFVAL { 30000 }
			::= { accXnsNetEntry 13 }
	  accXnsNetX25PktVal  OBJECT-TYPE   
			SYNTAX	INTEGER (0..1024)
			ACCESS	read-write
			STATUS	mandatory
			DESCRIPTION
	        " X25 packet size
	          Object will be defaulted if missing in set PDU which
	          adds entries."
                        DEFVAL { 0 }
			::= { accXnsNetEntry 14 }
	  accXnsNetX25PktWin  OBJECT-TYPE   
			SYNTAX	INTEGER (0..127)
			ACCESS	read-write
			STATUS	mandatory
			DESCRIPTION
	        " X25 packet window "
                        DEFVAL { 0 }
			::= { accXnsNetEntry 15 }
	  accXnsNetEntryStat  OBJECT-TYPE   
			SYNTAX	INTEGER {
				other(1),
				invalid(2)
			    }
			ACCESS	read-write
			STATUS	mandatory
			DESCRIPTION
	        " Status of this table entry
	          Set this object to invalid to remove entry from table"
                        DEFVAL { other }
			::= { accXnsNetEntry 16 }
	  accXnsNetUbUpdate  OBJECT-TYPE   
			SYNTAX	TimeTicks
			ACCESS	read-write
			STATUS	mandatory
			DESCRIPTION
	        " Ungermann-Bass update interval
	          Object will be defaulted if missing in set PDU which
	          adds entries."
			::= { accXnsNetEntry 17 }
	  accXnsNetUbTtl  OBJECT-TYPE   
			SYNTAX	TimeTicks
			ACCESS	read-write
			STATUS	mandatory
			DESCRIPTION
	        " Ungermann-Bass time-to-live
	          Object will be defaulted if missing in set PDU which
	          adds entries."
                        DEFVAL { 1500 }
			::= { accXnsNetEntry 18 }
	  accXnsNetUbQT1  OBJECT-TYPE   
			SYNTAX	TimeTicks
			ACCESS	read-write
			STATUS	mandatory
			DESCRIPTION
	        " Ungermann-Bass QT1 timer
	          Object will be defaulted to a network type
                  dependent value if missing in set PDU which
	          adds entries."
			::= { accXnsNetEntry 19 }
	  accXnsNetUbQT2  OBJECT-TYPE   
			SYNTAX	TimeTicks 
			ACCESS	read-write
			STATUS	mandatory
			DESCRIPTION
	        " Ungermann-Bass QT2 timer
	          Object will be defaulted to a network type
                  dependent value if missing in set PDU which
	          adds entries.
	          This object may be individually adjusted"
			::= { accXnsNetEntry 20 }
	accXnsNetFncAddr OBJECT-TYPE
	    SYNTAX	OCTET STRING  -- (SIZE(6))
	    ACCESS	read-write
	    STATUS	mandatory
		DESCRIPTION
		 " The MAC-layer functional address for sending and
		   receiving multicasts."
		::= { accXnsNetEntry 21 }
	accXnsNetSrMode OBJECT-TYPE
	    SYNTAX	INTEGER { 
			off(1), 
			ape(2), 
			spe(3) 
			}
	    ACCESS	read-write
	    STATUS	mandatory
		DESCRIPTION
		 " The source-routing mode for token-ring networks."
		::= { accXnsNetEntry 22 }
        accXnsNetX25FacIndex OBJECT-TYPE
	           SYNTAX      INTEGER (0..255)
       		   ACCESS      read-write
         	   STATUS      mandatory
           	   DESCRIPTION
            		" Index of optional facility string or 0."
           	   DEFVAL      { 0 }
           	   ::= { accXnsNetEntry 23 }
       accXnsNetDlci       OBJECT-TYPE
                   SYNTAX  INTEGER
                   ACCESS  read-write
                   STATUS  mandatory
                   DESCRIPTION
                   " Frame Relay DLCI for this port"
                   ::= { accXnsNetEntry 24 }
     accXnsRouteTable  OBJECT-TYPE   
			SYNTAX	SEQUENCE OF AccXnsRouteEntry
			ACCESS	not-accessible
			STATUS	mandatory
			DESCRIPTION
                " List of routes to other XNS networks"
			::= { accXns 3 }
        accXnsRouteEntry  OBJECT-TYPE   
			SYNTAX	AccXnsRouteEntry
			ACCESS	not-accessible
			STATUS	mandatory
			DESCRIPTION
                          " Information on route to destination network"
                        INDEX { accXnsRtDest }
			::= { accXnsRouteTable 1 }
        AccXnsRouteEntry ::= SEQUENCE {
			accXnsRtDest		OCTET STRING,
			accXnsRtNxtNet		OCTET STRING,
			accXnsRtRouter		OCTET STRING,
			accXnsRtHops		INTEGER,
			accXnsRtCost		INTEGER,
			accXnsRtType		INTEGER,
			accXnsRtOwner		INTEGER,
			accXnsRtAge		TimeTicks,
			accXnsRtPort		INTEGER
 			}
	  accXnsRtDest  OBJECT-TYPE   
			SYNTAX	OCTET STRING 
			ACCESS	read-only
			STATUS	mandatory
			DESCRIPTION
	        " Destination network."
			::= { accXnsRouteEntry 1 }
	  accXnsRtNxtNet  OBJECT-TYPE   
			SYNTAX	OCTET STRING
			ACCESS	read-only
			STATUS	mandatory
			DESCRIPTION
		 " The next network along the way
		   to the destination network."
			::= { accXnsRouteEntry 2 }
	  accXnsRtRouter  OBJECT-TYPE   
			SYNTAX	OCTET STRING 
			ACCESS	read-only
			STATUS	mandatory
			DESCRIPTION
	        " Router on next XNS network on route"
			::= { accXnsRouteEntry 3 }
	  accXnsRtHops  OBJECT-TYPE   
			SYNTAX	INTEGER
			ACCESS	read-only
			STATUS	mandatory
			DESCRIPTION
	        " Number of hops to remote network"
			::= { accXnsRouteEntry 4 }
	  accXnsRtCost  OBJECT-TYPE   
			SYNTAX	INTEGER
			ACCESS	read-only
			STATUS	mandatory
			DESCRIPTION
	        " Cost to remote network"
			::= { accXnsRouteEntry 5 }
	  accXnsRtType  OBJECT-TYPE   
			SYNTAX	INTEGER {
				public(1),
				direct(2),
				static(3)
			    }
			ACCESS	read-only
			STATUS	mandatory
			DESCRIPTION
	        " Type of route"
			::= { accXnsRouteEntry 6 }
	  accXnsRtOwner  OBJECT-TYPE   
			SYNTAX	INTEGER {
				lli(1),
				nms(2),
				rip(3)
			    }
			ACCESS	read-only
			STATUS	mandatory
			DESCRIPTION
	        " Source of route"
			::= { accXnsRouteEntry 7 }
	  accXnsRtAge  OBJECT-TYPE   
			SYNTAX	TimeTicks
			ACCESS	read-only
			STATUS	mandatory
			DESCRIPTION
	        " Age of route"
			::= { accXnsRouteEntry 8 }
	  accXnsRtPort  OBJECT-TYPE   
			SYNTAX	INTEGER
			ACCESS	read-only
			STATUS	mandatory
			DESCRIPTION
		 " The logical port number through which packets will be
		   forwarded to the destination network."
			::= { accXnsRouteEntry 9 }
    accXnsRipStat   OBJECT IDENTIFIER ::= { accXns 4 }
           accXnsRipReqIns OBJECT-TYPE   
			SYNTAX	Counter
			ACCESS	read-only
			STATUS	mandatory
			DESCRIPTION
	        " XNS RIP requests received"
			::= { accXnsRipStat 1 }
           accXnsRipRespIns OBJECT-TYPE   
			SYNTAX	Counter
			ACCESS	read-only
			STATUS	mandatory
			DESCRIPTION
	        " XNS RIP responses received"
			::= { accXnsRipStat 2 }
           accXnsRipReqOuts OBJECT-TYPE   
			SYNTAX	Counter
			ACCESS	read-only
			STATUS	mandatory
			DESCRIPTION
	        " XNS RIP requests transmitted"
			::= { accXnsRipStat 3 }
           accXnsRipRespOuts OBJECT-TYPE   
			SYNTAX	Counter
			ACCESS	read-only
			STATUS	mandatory
			DESCRIPTION
	        " XNS RIP responses transmitted"
			::= { accXnsRipStat 4 }
           accXnsRipInErrs OBJECT-TYPE   
			SYNTAX	Counter
			ACCESS	read-only
			STATUS	mandatory
			DESCRIPTION
	        " XNS RIP packets received with errors"
			::= { accXnsRipStat 5 }
           accXnsRipOutErrs OBJECT-TYPE   
			SYNTAX	Counter
			ACCESS	read-only
			STATUS	mandatory
			DESCRIPTION
	        " XNS RIP responses transmitted with errors."
			::= { accXnsRipStat 6 }
      accXnsNodeStat  OBJECT IDENTIFIER  ::= { accXns 5 }
           accXnsLocalIns OBJECT-TYPE   
			SYNTAX	Counter
			ACCESS	read-only
			STATUS	mandatory
			DESCRIPTION
	        " Packets received for local usage"
			::= { accXnsNodeStat 1 }
           accXnsLocalOuts OBJECT-TYPE   
			SYNTAX	Counter
			ACCESS	read-only
			STATUS	mandatory
			DESCRIPTION
	        " Locally generated packets"
			::= { accXnsNodeStat 2 }
           accXnsNoSockets OBJECT-TYPE   
			SYNTAX	Counter
			ACCESS	read-only
			STATUS	mandatory
			DESCRIPTION
	        " Packets received for which there was no socket"
			::= { accXnsNodeStat 3 }
           accXnsNoRoutes OBJECT-TYPE   
			SYNTAX	Counter
			ACCESS	read-only
			STATUS	mandatory
			DESCRIPTION
	        " Packets for which no route was found"
			::= { accXnsNodeStat 4 }
           accXnsNodeInErrs OBJECT-TYPE   
			SYNTAX	Counter
			ACCESS	read-only
			STATUS	mandatory
			DESCRIPTION
	        " The number of input packets discarded by this node because
	          of some unspecified internal error."
			::= { accXnsNodeStat 5 }
           accXnsOutErrs OBJECT-TYPE   
			SYNTAX	Counter
			ACCESS	read-only
			STATUS	mandatory
			DESCRIPTION
	        " Output errors"
			::= { accXnsNodeStat 6 }
           accXnsAllNetsIns OBJECT-TYPE   
			SYNTAX	Counter
			ACCESS	read-only
			STATUS	mandatory
			DESCRIPTION
	        " All-nets packets received"
			::= { accXnsNodeStat 7 }
           accXnsAllNetsOuts OBJECT-TYPE   
			SYNTAX	Counter
			ACCESS	read-only
			STATUS	mandatory
			DESCRIPTION
	        " All-nets packets transmitted"
			::= { accXnsNodeStat 8 }
           accXnsAllNetsErrs OBJECT-TYPE   
			SYNTAX	Counter
			ACCESS	read-only
			STATUS	mandatory
			DESCRIPTION
	        " Erroneous All-Nets packets encountered"
			::= { accXnsNodeStat 9 }
     accXnsPortStatTable  OBJECT-TYPE   
			SYNTAX	SEQUENCE OF AccXnsPortStatEntry
			ACCESS	not-accessible
			STATUS	mandatory
			DESCRIPTION
                " XNS Port statistics table"
			::= { accXns 6 }
        accXnsPortStatEntry  OBJECT-TYPE   
			SYNTAX	AccXnsPortStatEntry
			ACCESS	not-accessible
			STATUS	mandatory
			DESCRIPTION
                           " Per-port statistics"
		        INDEX { accXnsPortNumber }
			::= { accXnsPortStatTable 1 }
        AccXnsPortStatEntry ::= SEQUENCE {
			accXnsPortNumber		INTEGER,
			accXnsPortTotalIns		Counter,
			accXnsPorFwdReqIns		Counter,
			accXnsPortNoFwdRts		Counter,
			accXnsPortTotalOuts		Counter,
			accXnsPortHopCnts		Counter,
			accXnsPortNotForMes		Counter,
			accXnsPortFwdReqOuts		Counter,
			accXnsPortFwdErrs		Counter,
			accXnsPortInErrs		Counter,
			accXnsPortTooShorts		Counter,
			accXnsPortCkSums		Counter,
			accXnsPortTooLongs		Counter,
			accXnsPortOutErrs		Counter,
			accXnsPortOpState		INTEGER
 			}
	  accXnsPortNumber  OBJECT-TYPE   
			SYNTAX	INTEGER
			ACCESS	read-only
			STATUS	mandatory
			DESCRIPTION
	        " Port number"
			::= { accXnsPortStatEntry 1 }
	  accXnsPortTotalIns  OBJECT-TYPE   
			SYNTAX	Counter
			ACCESS	read-only
			STATUS	mandatory
			DESCRIPTION
	        " Total number of XNS  Packets received"
			::= { accXnsPortStatEntry 2 }
	  accXnsPorFwdReqIns  OBJECT-TYPE   
			SYNTAX	Counter
			ACCESS	read-only
			STATUS	mandatory
			DESCRIPTION
		  " The number of input packets not addressed to the receiving
		    port, as a result of which an attempt was made to find a
		    route to forward them to the final destination."
			::= { accXnsPortStatEntry 3 }
	  accXnsPortNoFwdRts  OBJECT-TYPE   
			SYNTAX	Counter
			ACCESS	read-only
			STATUS	mandatory
			DESCRIPTION
	        " The number of packets received on this port for which no
	          route to the destination network could be found."
			::= { accXnsPortStatEntry 4 }
	  accXnsPortTotalOuts  OBJECT-TYPE   
			SYNTAX	Counter
			ACCESS	read-only
			STATUS	mandatory
			DESCRIPTION
	        " Total XNS packets transmitted"
			::= { accXnsPortStatEntry 5 }
	  accXnsPortHopCnts  OBJECT-TYPE   
			SYNTAX	Counter
			ACCESS	read-only
			STATUS	mandatory
			DESCRIPTION
		 " The number of packets received on this port whose hop
		   count had reached the maximum value."
			::= { accXnsPortStatEntry 6 }
	  accXnsPortNotForMes  OBJECT-TYPE   
			SYNTAX	Counter
			ACCESS	read-only
			STATUS	mandatory
			DESCRIPTION
		 " The number of packets received on this port which were
		   addressed to another node on the same network."
			::= { accXnsPortStatEntry 7 }
	  accXnsPortFwdReqOuts  OBJECT-TYPE   
			SYNTAX	Counter
			ACCESS	read-only
			STATUS	mandatory
			DESCRIPTION
		 " The number of packets received on this port which were
		   successfully forwarded to another port."
			::= { accXnsPortStatEntry 8 }
	  accXnsPortFwdErrs  OBJECT-TYPE   
			SYNTAX	Counter
			ACCESS	read-only
			STATUS	mandatory
			DESCRIPTION
		 " The number of packets received on this port which could
		   not be forwarded, either because there were transmitted
		   via a MAC-layer broadcast, or because their source or
		   destination network number were unknown."
			::= { accXnsPortStatEntry 9 }
	  accXnsPortInErrs  OBJECT-TYPE   
			SYNTAX	Counter
			ACCESS	read-only
			STATUS	mandatory
			DESCRIPTION
	        " The number of packets received on this port which were
	          discarded because of some unspecified internal error."
			::= { accXnsPortStatEntry 10 }
	  accXnsPortTooShorts  OBJECT-TYPE   
			SYNTAX	Counter
			ACCESS	read-only
			STATUS	mandatory
			DESCRIPTION
		 " The number of packets received on this port which were
		   discarded because they were too short."
			::= { accXnsPortStatEntry 11 }
	  accXnsPortCkSums  OBJECT-TYPE   
			SYNTAX	Counter
			ACCESS	read-only
			STATUS	mandatory
			DESCRIPTION
	        " XNS packet checksum errors detected"
			::= { accXnsPortStatEntry 12 }
	  accXnsPortTooLongs  OBJECT-TYPE   
			SYNTAX	Counter
			ACCESS	read-only
			STATUS	mandatory
			DESCRIPTION
		 " The number of packets received on this port which were
		   discarded because they were too long."
			::= { accXnsPortStatEntry 13 }
	  accXnsPortOutErrs  OBJECT-TYPE   
			SYNTAX	Counter
			ACCESS	read-only
			STATUS	mandatory
			DESCRIPTION
	        " XNS packet output errors detected"
			::= { accXnsPortStatEntry 14 }
	  accXnsPortOpState  OBJECT-TYPE   
			SYNTAX	INTEGER (0..4)
			ACCESS	read-only
			STATUS	mandatory
			DESCRIPTION
	        " Operational status of this port.
				off(0),
				down(1),
				start(2),
				stop(3),
				up(4)
		"
			::= { accXnsPortStatEntry 15 }
     accXnsUbNbrTable  OBJECT-TYPE   
			SYNTAX	SEQUENCE OF AccXnsUbNbrEntry
			ACCESS	not-accessible
			STATUS	mandatory
			DESCRIPTION
                " XNS Neighbor table (Ungermann-Bass)"
			::= { accXns 7 }
        accXnsUbNbrEntry  OBJECT-TYPE   
			SYNTAX	AccXnsUbNbrEntry
			ACCESS	not-accessible
			STATUS	mandatory
			DESCRIPTION
                          "  Information on specific neighbor."
                        INDEX { accXnsUbnRmtNet,
		                accXnsUbnLclNet,
		                accXnsUbnRouter }
			::= { accXnsUbNbrTable 1 }
        AccXnsUbNbrEntry ::= SEQUENCE {
			accXnsUbnRmtNet		OCTET STRING,
			accXnsUbnLclNet		OCTET STRING,
			accXnsUbnRouter		OCTET STRING,
			accXnsUbnHops		INTEGER,
			accXnsUbnCost		INTEGER,
			accXnsUbnState		INTEGER,
			accXnsUbnTtl		TimeTicks
 			}
	  accXnsUbnRmtNet  OBJECT-TYPE   
			SYNTAX	OCTET STRING
			ACCESS	read-only
			STATUS	mandatory
			DESCRIPTION
	        " Remote network"
			::= { accXnsUbNbrEntry 1 }
	  accXnsUbnLclNet  OBJECT-TYPE   
			SYNTAX	OCTET STRING
			ACCESS	read-only
			STATUS	mandatory
			DESCRIPTION
	        " Local network"
			::= { accXnsUbNbrEntry 2 }
	  accXnsUbnRouter  OBJECT-TYPE   
			SYNTAX	OCTET STRING
			ACCESS	read-only
			STATUS	mandatory
			DESCRIPTION
	        " Router"
			::= { accXnsUbNbrEntry 3 }
	  accXnsUbnHops  OBJECT-TYPE   
			SYNTAX	INTEGER
			ACCESS	read-only
			STATUS	mandatory
			DESCRIPTION
	        " Hop count to neighbor"
			::= { accXnsUbNbrEntry 4 }
	  accXnsUbnCost  OBJECT-TYPE   
			SYNTAX	INTEGER
			ACCESS	read-only
			STATUS	mandatory
			DESCRIPTION
	        " Cost to neighbor"
			::= { accXnsUbNbrEntry 5 }
	  accXnsUbnState  OBJECT-TYPE   
			SYNTAX	INTEGER (0..3)
			ACCESS	read-only
			STATUS	mandatory
			DESCRIPTION
	        " State of neighbor.
				local(0),
				congested(1),
				uncongested(2),
				keepalive(3)
		"
			::= { accXnsUbNbrEntry 6 }
	  accXnsUbnTtl  OBJECT-TYPE   
			SYNTAX	TimeTicks
			ACCESS	read-only
			STATUS	mandatory
			DESCRIPTION
	        " Time to live"
			::= { accXnsUbNbrEntry 7 }
      accXnsUbRip   OBJECT IDENTIFIER ::= { accXns 8 }
	  accXnsUbRipRespIns  OBJECT-TYPE   
			SYNTAX	Counter
			ACCESS	read-only
			STATUS	mandatory
			DESCRIPTION
	        " U-B RIP Responses received"
			::= { accXnsUbRip 1 }
	  accXnsUbRipHelloIns  OBJECT-TYPE   
			SYNTAX	Counter
			ACCESS	read-only
			STATUS	mandatory
			DESCRIPTION
	        " U-B RIP Hello packets received"
			::= { accXnsUbRip 2 }
	  accXnsUbRipConHelIns  OBJECT-TYPE   
			SYNTAX	Counter
			ACCESS	read-only
			STATUS	mandatory
			DESCRIPTION
	        " U-B RIP (congested) Hello packets received"
			::= { accXnsUbRip 3 }
	  accXnsUbRipUnConHelIns  OBJECT-TYPE   
			SYNTAX	Counter
			ACCESS	read-only
			STATUS	mandatory
			DESCRIPTION
	        " U-B RIP (uncongested) Hello packets received"
			::= { accXnsUbRip 4 }
	  accXnsUbRipRedirIns  OBJECT-TYPE   
			SYNTAX	Counter
			ACCESS	read-only
			STATUS	mandatory
			DESCRIPTION
	        " U-B RIP redirect  packets received"
			::= { accXnsUbRip 5 }
	  accXnsUbRipRespOuts  OBJECT-TYPE   
			SYNTAX	Counter
			ACCESS	read-only
			STATUS	mandatory
			DESCRIPTION
	        " U-B RIP responses transmitted"
			::= { accXnsUbRip 6 }
	  accXnsUbRipHelloOuts  OBJECT-TYPE   
			SYNTAX	Counter
			ACCESS	read-only
			STATUS	mandatory
			DESCRIPTION
	        " U-B hello packets transmitted"
			::= { accXnsUbRip 7 }
	  accXnsUbRipConHelOuts  OBJECT-TYPE   
			SYNTAX	Counter
			ACCESS	read-only
			STATUS	mandatory
			DESCRIPTION
	        " U-B (congested) hello packets transmitted"
			::= { accXnsUbRip 8 }
	  accXnsUbRipUnConHelOuts  OBJECT-TYPE   
			SYNTAX	Counter
			ACCESS	read-only
			STATUS	mandatory
			DESCRIPTION
	        " U-B (uncongested) hello packets transmitted"
			::= { accXnsUbRip 9 }
	  accXnsUbRipRedirOuts  OBJECT-TYPE   
			SYNTAX	Counter
			ACCESS	read-only
			STATUS	mandatory
			DESCRIPTION
	        " U-B redirect packets transmitted"
			::= { accXnsUbRip 10 }
	  accXnsUbNoRoutes  OBJECT-TYPE   
			SYNTAX	Counter
			ACCESS	read-only
			STATUS	mandatory
			DESCRIPTION
	        " U-B unreachable network"
			::= { accXnsUbRip 11 }
	  accXnsUbInErrs  OBJECT-TYPE   
			SYNTAX	Counter
			ACCESS	read-only
			STATUS	mandatory
			DESCRIPTION
	        " U-B total input errors"
			::= { accXnsUbRip 12 }
	  accXnsUbOutErrs  OBJECT-TYPE   
			SYNTAX	Counter
			ACCESS	read-only
			STATUS	mandatory
			DESCRIPTION
	        " U-B total output errors"
			::= { accXnsUbRip 13 }
   accXnsRouteFilters OBJECT IDENTIFIER ::= { accXns 9 }
     accXnsRteFltrDefaultAction OBJECT-TYPE
         SYNTAX   INTEGER { 
		     accept(1), 
		     reject(2) 
		     }
         ACCESS   read-write
         STATUS   mandatory
         DESCRIPTION
     " The action taken on route updates from unconfigured neighbors."
         ::= { accXnsRouteFilters 1 }
     accXnsRteNbrTable OBJECT-TYPE
         SYNTAX   SEQUENCE OF AccXnsRteNbrEntry
         ACCESS   not-accessible
         STATUS   mandatory
         DESCRIPTION
            " A list of Host Identifiers for Routing Neighbors."
         ::= { accXnsRouteFilters 2 }
        accXnsRteNbrEntry OBJECT-TYPE
           SYNTAX   AccXnsRteNbrEntry
           ACCESS   not-accessible
           STATUS   mandatory
           DESCRIPTION
              " The host identifier for an individual routing neighbor."
           INDEX { accXnsRteNbrId }
           ::= { accXnsRteNbrTable 1 }
        AccXnsRteNbrEntry ::=
            SEQUENCE {
                accXnsRteNbrId
                    OCTET STRING,
                accXnsRteNbrAction
                    INTEGER,
                accXnsRteNbrStatus
                    INTEGER
                }
           accXnsRteNbrId OBJECT-TYPE
               SYNTAX   OCTET STRING -- (SIZE(6))
               ACCESS   read-write
               STATUS   mandatory
               DESCRIPTION
                 " The Host Identifier of a potential routing neighbor."
               ::= { accXnsRteNbrEntry 1 }
           accXnsRteNbrAction OBJECT-TYPE
               SYNTAX   INTEGER { 
			accept(1), 
			reject(2) 
			}
               ACCESS   read-write
               STATUS   mandatory
               DESCRIPTION
         " The action to be taken on advertisements from this routing neighbor,
           unless overridden by a route filter."
               ::= { accXnsRteNbrEntry 2 }
           accXnsRteNbrStatus OBJECT-TYPE
               SYNTAX   INTEGER {
                invalid(1), 
                valid(2) 
                }
               ACCESS   read-write
               STATUS   mandatory
               DESCRIPTION
          " Writing 'invalid' has the effect of deleting this routing neighbor
            and making its associated route filters of no effect."
               ::= { accXnsRteNbrEntry 3 }
     accXnsRteFltrTable OBJECT-TYPE
         SYNTAX   SEQUENCE OF AccXnsRteFltrEntry
         ACCESS   not-accessible
         STATUS   mandatory
         DESCRIPTION
         " A list of special advertisements that a given neighbor might offer.
           Route Advertisements defaults are overridden using this table"
         ::= { accXnsRouteFilters 3 }
       accXnsRteFltrEntry OBJECT-TYPE
           SYNTAX   AccXnsRteFltrEntry
           ACCESS   not-accessible
           STATUS   mandatory
           DESCRIPTION
          " A single potential advertisement, with information 
            as to its disposition."
           INDEX { accXnsRteFltrNeighbor, 
                   accXnsRteFltrNetwork }
           ::= { accXnsRteFltrTable 1 }
       AccXnsRteFltrEntry ::=
           SEQUENCE {
               accXnsRteFltrNeighbor
                   OCTET STRING,
               accXnsRteFltrNetwork
                   OCTET STRING,
               accXnsRteFltrAction
                   INTEGER,
               accXnsRteFltrStatus
                   INTEGER
	       }
         accXnsRteFltrNeighbor OBJECT-TYPE
             SYNTAX   OCTET STRING -- (SIZE(6))
             ACCESS   read-write 
             STATUS   mandatory
             DESCRIPTION
          " The Host Identifier of the Routing Neighbor that might 
            offer this advertsiement."
             ::= { accXnsRteFltrEntry 1 }
         accXnsRteFltrNetwork OBJECT-TYPE
             SYNTAX   OCTET STRING  -- (SIZE (4))
             ACCESS   read-write
             STATUS   mandatory
             DESCRIPTION
         " The Network Number the neighbor might advertise."
             ::= { accXnsRteFltrEntry 2 }
         accXnsRteFltrAction OBJECT-TYPE
             SYNTAX   INTEGER { 
		         accept(1), 
		         reject(2) 
		         }
             ACCESS   read-write
             STATUS   mandatory
             DESCRIPTION
                   " What is to be done with such an advertisement."
             ::= { accXnsRteFltrEntry 3 }
         accXnsRteFltrStatus OBJECT-TYPE
             SYNTAX   INTEGER {
                         invalid(1), 
                         valid(2) 
                         }
             ACCESS   read-write
             STATUS   mandatory
             DESCRIPTION
                  " Writing 'invalid' has the effect of deleting this filter."
             ::= { accXnsRteFltrEntry 4 }
--	The Network Filter permits traffic to be prioritized based
--      on souce/destination networks and socket numbers and packet type.
   accXnsNetworkFilters OBJECT IDENTIFIER ::= { accXns 10 }
     accXnsNetFltrDefaultAction OBJECT-TYPE
         SYNTAX   INTEGER (0..3)
         ACCESS   read-write
         STATUS   mandatory
         DESCRIPTION
             " The action taken on messages not matched.
                        discard(0),
                        lowPriority(1),
                        normalPriority(2),
                        highPriority(3)
		"
         ::= { accXnsNetworkFilters 1 }
--	The following network filter table is deprecated in
--      favor of the expanded table immediately subsequent
     oldXnsNetFltrTable OBJECT-TYPE
         SYNTAX   SEQUENCE OF OldXnsNetFltrEntry
         ACCESS   not-accessible
         STATUS   deprecated
         DESCRIPTION
                 " A list of network pairs to specially act on."
         ::= { accXnsNetworkFilters 2 }
     oldXnsNetFltrEntry OBJECT-TYPE
         SYNTAX   OldXnsNetFltrEntry
         ACCESS   not-accessible
         STATUS   deprecated
         DESCRIPTION
                 " A single Network Number pair to be matched."
         INDEX { oldXnsNetFltrDestination, 
                 oldXnsNetFltrSource }
         ::= { oldXnsNetFltrTable 1 }
     OldXnsNetFltrEntry ::=
         SEQUENCE {
             oldXnsNetFltrDestination
                 OCTET STRING,
             oldXnsNetFltrSource
                 OCTET STRING,
             oldXnsNetFltrAction
                 INTEGER,
             oldXnsNetFltrStatus
                 INTEGER
	     }
        oldXnsNetFltrDestination OBJECT-TYPE
            SYNTAX   OCTET STRING   -- (SIZE (4))
            ACCESS   read-write
            STATUS   deprecated
            DESCRIPTION
                " The value to be found in the Destination Network 
                  Field, or 0x00000000."
            ::= { oldXnsNetFltrEntry 1 }
        oldXnsNetFltrSource OBJECT-TYPE
            SYNTAX   OCTET STRING   -- (SIZE (4))
            ACCESS   read-write
            STATUS   deprecated
            DESCRIPTION
        " The value to be found in the Source Network Field, or 0x00000000."
            ::= { oldXnsNetFltrEntry 2 }
        oldXnsNetFltrAction OBJECT-TYPE
            SYNTAX   INTEGER (0..3)
            ACCESS   read-write
            STATUS   deprecated
            DESCRIPTION
         " The action to be taken on matching messages.
                        discard(0),
                        lowPriority(1),
                        normalPriority(2),
                        highPriority(3)
	"
            ::= { oldXnsNetFltrEntry 3 }
        oldXnsNetFltrStatus OBJECT-TYPE
            SYNTAX   INTEGER {
                invalid(1), 
                valid(2) 
                }
            ACCESS   read-write
            STATUS   deprecated
            DESCRIPTION
            " Writing 'invalid' has the effect of removing this filter entry."
            ::= { oldXnsNetFltrEntry 4 }
--	The Network Filter permits the remote network routing
--	routine to determine whether traffic from or to a
--	particular network/socket of a particular packet type
--      is to be prioritized.
--	A zero value in a field is a wildcard.
     accXnsNetFltrTable OBJECT-TYPE
         SYNTAX   SEQUENCE OF AccXnsNetFltrEntry
         ACCESS   not-accessible
         STATUS   mandatory
         DESCRIPTION
                 " A list of network filters to specially act on."
         ::= { accXnsNetworkFilters 3 }
     accXnsNetFltrEntry OBJECT-TYPE
         SYNTAX   AccXnsNetFltrEntry
         ACCESS   not-accessible
         STATUS   mandatory
         DESCRIPTION
                 " A single Network filter to be matched."
         INDEX { accXnsNetFltrDestination, 
                 accXnsNetFltrSource,
                 accXnsNetFltrDestSkt,
                 accXnsNetFltrSrcSkt,
                 accXnsNetFltrPktType }
         ::= { accXnsNetFltrTable 1 }
     AccXnsNetFltrEntry ::=
         SEQUENCE {
             accXnsNetFltrDestination
                 OCTET STRING,
             accXnsNetFltrSource
                 OCTET STRING,
             accXnsNetFltrAction
                 INTEGER,
             accXnsNetFltrStatus
                 INTEGER,
             accXnsNetFltrDestSkt
                 OCTET STRING,
             accXnsNetFltrSrcSkt
                 OCTET STRING,
             accXnsNetFltrPktType
                 INTEGER
	     }
        accXnsNetFltrDestination OBJECT-TYPE
            SYNTAX   OCTET STRING   -- (SIZE (4))
            ACCESS   read-write
            STATUS   mandatory
            DESCRIPTION
                " The value to be found in the Destination Network 
                  Field, or 0x00000000."
            ::= { accXnsNetFltrEntry 1 }
        accXnsNetFltrSource OBJECT-TYPE
            SYNTAX   OCTET STRING   -- (SIZE (4))
            ACCESS   read-write
            STATUS   mandatory
            DESCRIPTION
        " The value to be found in the Source Network Field, or 0x00000000."
            ::= { accXnsNetFltrEntry 2 }
        accXnsNetFltrAction OBJECT-TYPE
            SYNTAX   INTEGER (0..3)
            ACCESS   read-write
            STATUS   mandatory
            DESCRIPTION
         " The action to be taken on matching messages.
                        discard(0),
                        lowPriority(1),
                        normalPriority(2),
                        highPriority(3)
	"
            ::= { accXnsNetFltrEntry 3 }
        accXnsNetFltrStatus OBJECT-TYPE
            SYNTAX   INTEGER {
                invalid(1), 
                valid(2) 
                }
            ACCESS   read-write
            STATUS   mandatory
            DESCRIPTION
            " Writing 'invalid' has the effect of removing this filter entry."
            ::= { accXnsNetFltrEntry 4 }
        accXnsNetFltrDestSkt OBJECT-TYPE
            SYNTAX   OCTET STRING   -- (SIZE (2))
            ACCESS   read-write
            STATUS   mandatory
            DESCRIPTION
                " The value to be found in the Destination Socket 
                  Field, or 0x0000."
            ::= { accXnsNetFltrEntry 5 }
        accXnsNetFltrSrcSkt OBJECT-TYPE
            SYNTAX   OCTET STRING  -- (SIZE (2))
            ACCESS   read-write
            STATUS   mandatory
            DESCRIPTION
        " The value to be found in the Source Socket Field, or 0x0000."
            ::= { accXnsNetFltrEntry 6 }
        accXnsNetFltrPktType OBJECT-TYPE
            SYNTAX   INTEGER 
            ACCESS   read-write
            STATUS   mandatory
            DESCRIPTION
         " Packet type, or zero "
            ::= { accXnsNetFltrEntry 7 }
--  XNS Host Filters
--	The Host Filter indicates what is to be done with traffic
--	originated or destined locally.
--
--	The value 0x000000000000 is used to mean 'any host'
   accXnsHostFilters OBJECT IDENTIFIER ::= { accXns 11 }
      accXnsHostFltrDefaultAction OBJECT-TYPE
            SYNTAX   INTEGER (0..3)
          ACCESS   read-write
          STATUS   mandatory
          DESCRIPTION
          " The action taken on hosts not listed.
                        discard(0),
                        lowPriority(1),
                        normalPriority(2),
                        highPriority(3)
	"
          ::= { accXnsHostFilters 1 }
--  XNS Local Host Table
--	The Local Host List indicates what is to be done with traffic
--	to or from local hosts
      accXnsHostFltrTable OBJECT-TYPE
          SYNTAX   SEQUENCE OF AccXnsHostFltrEntry
          ACCESS   not-accessible
          STATUS   mandatory
          DESCRIPTION
             " A list of XNS Hosts to be handled specially."
          ::= { accXnsHostFilters 2 }
         accXnsHostFltrEntry OBJECT-TYPE
             SYNTAX   AccXnsHostFltrEntry
             ACCESS   not-accessible
             STATUS   mandatory
             DESCRIPTION
                   " A single Host Identifier."
             INDEX { accXnsHostFltrId, 
                     accXnsHostFltrSocket, 
                     accXnsHostFltrPepClient }
             ::= { accXnsHostFltrTable 1 }
         AccXnsHostFltrEntry ::=
             SEQUENCE {
                 accXnsHostFltrId
                     OCTET STRING,
	         accXnsHostFltrSocket
	             OCTET STRING,
	         accXnsHostFltrPepClient
	             OCTET STRING,
                 accXnsHostFltrAction
                     INTEGER,
                 accXnsHostFltrStatus
                     INTEGER
                }
           accXnsHostFltrId OBJECT-TYPE
               SYNTAX   OCTET STRING  -- (SIZE(6))
               ACCESS   read-write
               STATUS   mandatory
               DESCRIPTION
                " Host Identifier "
               ::= { accXnsHostFltrEntry 1 }
           accXnsHostFltrSocket OBJECT-TYPE
               SYNTAX   OCTET STRING  -- (SIZE (2))
               ACCESS   read-write
               STATUS   mandatory
               DESCRIPTION
                " The affected socket number, or zero for 'any socket'."
               ::= { accXnsHostFltrEntry 2 }
           accXnsHostFltrPepClient OBJECT-TYPE
               SYNTAX   OCTET STRING  -- (SIZE(2))
               ACCESS   read-write
               STATUS   mandatory
               DESCRIPTION
                    " On PEP traffic, the affected Client Type, 
                      or zero for all IDP traffic."
               ::= { accXnsHostFltrEntry 3 }
           accXnsHostFltrAction OBJECT-TYPE
            SYNTAX   INTEGER (0..3)
               ACCESS   read-write
               STATUS   mandatory
               DESCRIPTION
                       " The action to be taken on matching messages.
                        discard(0),
                        lowPriority(1),
                        normalPriority(2),
                        highPriority(3)
	"
               ::= { accXnsHostFltrEntry 4 }
           accXnsHostFltrStatus OBJECT-TYPE
               SYNTAX   INTEGER {
                invalid(1), 
                valid(2) 
                }
               ACCESS   read-write
               STATUS   mandatory
               DESCRIPTION
           " Writing 'invalid' has the effect of deleting the entry."
               ::= { accXnsHostFltrEntry 5 }
-- IPX Group
   accIpx         OBJECT IDENTIFIER ::= { accBRG 22 }
     accIpxParms	OBJECT IDENTIFIER ::= { accIpx 1 }
       accIpxAdStat  OBJECT-TYPE   
			SYNTAX	INTEGER {
				on(1),
				off(2)
			}
			ACCESS	read-write
			STATUS	mandatory
			DESCRIPTION
                " Administrative status of IPX routing protocol"
			::= { accIpxParms 1 }
	  accIpxCkSum  OBJECT-TYPE   
			SYNTAX	INTEGER {
				off(1),
				packet(2),
				header(3)
			}
			ACCESS	read-write
			STATUS	mandatory
			DESCRIPTION
                " Checksumming of IPX protocol"
			::= { accIpxParms 2 }
	  accIpxSpltHorz  OBJECT-TYPE   
			SYNTAX	INTEGER {
				off(1),
				simple(2),
				poison(3)
			}
			ACCESS	read-write
			STATUS	mandatory
			DESCRIPTION
                " Split horizon mode of IPX protocol"
			::= { accIpxParms 3 }
	  accIpxAllNets  OBJECT-TYPE   
			SYNTAX	INTEGER {
				on(1),
				off(2)
			}
			ACCESS	read-write
			STATUS	mandatory
			DESCRIPTION
                " All nets mode"
			::= { accIpxParms 4 }
	  accIpxMode  OBJECT-TYPE   
			SYNTAX	INTEGER {
				ipx(1),
				ub(2),
				repeat(3)
			}
			ACCESS	read-write
			STATUS	mandatory
			DESCRIPTION
                " RIP protocol type to use"
			::= { accIpxParms 5 }
	  accIpxWdFilter  OBJECT-TYPE   
			SYNTAX	INTEGER {
				disable(1),
				enable(2)
			}
			ACCESS	read-write
			STATUS	mandatory
			DESCRIPTION
                " Switch to enable/disable a dial originate filter
		of the IPX file server watchdog (Keep Alive) packet."
			::= { accIpxParms 6 }
     accIpxNetTable  OBJECT-TYPE   
			SYNTAX	SEQUENCE OF AccIpxNetEntry
			ACCESS	not-accessible
			STATUS	mandatory
			DESCRIPTION
                " List of IPX Networks.
	          Entries are added/deleted via management action."
			::= { accIpx 2 }
	  accIpxNetEntry  OBJECT-TYPE   
			SYNTAX	AccIpxNetEntry
			ACCESS	not-accessible
			STATUS	mandatory
			DESCRIPTION
                " Information on specific network entry. "
                        INDEX { accIpxNetPort }
			::= { accIpxNetTable 1 }
        AccIpxNetEntry ::= SEQUENCE {
			accIpxNetPort		INTEGER,
			accIpxNetNumber		OCTET STRING,
			accIpxNetType		INTEGER,
			accIpxNetEncap		INTEGER,
			accIpxNetSlot		INTEGER,
			accIpxNetAdStat		INTEGER,
			accIpxNetMtu		INTEGER,
			accIpxNetUpdate		TimeTicks,
			accIpxNetHops		INTEGER,
			accIpxNetCost		INTEGER,
			accIpxNetX25InOutAddr	DisplayString,
			accIpxNetX25InAddr	DisplayString,
			accIpxNetX25Idle	TimeTicks,
			accIpxNetX25PktVal	INTEGER,
			accIpxNetX25PktWin	INTEGER,
			accIpxNetEntryStat	INTEGER,
                        accIpxNetFncAddr	OCTET STRING,
                        accIpxNetSrMode		INTEGER,
			accIpxNetX25FacIndex	INTEGER,
			accIpxNetDlci		INTEGER,
			accIpxNetWdState	INTEGER
 			}
	  accIpxNetPort  OBJECT-TYPE   
			SYNTAX	INTEGER
			ACCESS	read-write
			STATUS	mandatory
			DESCRIPTION
                           " IPX logical port number "
			::= { accIpxNetEntry 1 }
	  accIpxNetNumber  OBJECT-TYPE   
			SYNTAX	OCTET STRING
			ACCESS	read-write
			STATUS	mandatory
			DESCRIPTION
                            " IPX network number "
			::= { accIpxNetEntry 2 }
	  accIpxNetType  OBJECT-TYPE   
			SYNTAX	INTEGER {
				enet(1),
				token-ring(2),
				lapb(3),
				x25(4),
				frame-relay(5),
				ppp(6),
				fddi(7),
				dial(8),
				multilink(9)
			}
			ACCESS	read-write
			STATUS	mandatory
			DESCRIPTION
                " Type of network "
			::= { accIpxNetEntry 3 }
	  accIpxNetEncap  OBJECT-TYPE   
			SYNTAX	INTEGER (0..4)
			ACCESS	read-write
			STATUS	mandatory
			DESCRIPTION
                " LAN Encapsulation used for Ethernets.
				none(0),
				v2(1),
				raw(2),
				llc(3),
				snap(4)
		"
			::= { accIpxNetEntry 4 }
	  accIpxNetSlot  OBJECT-TYPE   
			SYNTAX	INTEGER {
				j1(1),
				j2(2),
				j3(3),
				b1(4)
			}
			ACCESS	read-write
			STATUS	mandatory
			DESCRIPTION
                " Slot to which the network is attached "
			::= { accIpxNetEntry 5 }
	  accIpxNetAdStat  OBJECT-TYPE   
			SYNTAX	INTEGER {
				on(1),
				off(2)
			}
			ACCESS	read-write
			STATUS	mandatory
			DESCRIPTION
	        " Administrative status of network
	          Object will be defaulted if missing in set PDU which
	          adds entries."
			::= { accIpxNetEntry 6 }
	  accIpxNetMtu  OBJECT-TYPE   
			SYNTAX	INTEGER (576..65535)
			ACCESS	read-write
			STATUS	mandatory
			DESCRIPTION
	        " Maximum packet size
	          Object will be defaulted if missing in set PDU which
	          adds entries."
			::= { accIpxNetEntry 7 }
	  accIpxNetUpdate  OBJECT-TYPE   
			SYNTAX	TimeTicks
			ACCESS	read-write
			STATUS	mandatory
			DESCRIPTION
	                    " Update interval "
                        DEFVAL { 1500 }
			::= { accIpxNetEntry 8 }
	  accIpxNetHops  OBJECT-TYPE   
			SYNTAX	INTEGER
			ACCESS	read-write
			STATUS	mandatory
			DESCRIPTION
	                     " Hop count "
                        DEFVAL { 1 }
			::= { accIpxNetEntry 9 }
	  accIpxNetCost  OBJECT-TYPE   
			SYNTAX	INTEGER
			ACCESS	read-write
			STATUS	mandatory
			DESCRIPTION
	                   " Cost metric "
                        DEFVAL { 1 }
			::= { accIpxNetEntry 10 }
	  accIpxNetX25InOutAddr  OBJECT-TYPE   
			SYNTAX  DisplayString	
			ACCESS	read-write
			STATUS	mandatory
			DESCRIPTION
	        " X25 address to send to and to receive packets from.
	          Object required in set PDU adding X25-type circuit"
			::= { accIpxNetEntry 11 }
	  accIpxNetX25InAddr  OBJECT-TYPE   
			SYNTAX  DisplayString	
			ACCESS	read-write
			STATUS	mandatory
			DESCRIPTION
	        " Receive-only X25 address
	          Object not required in set PDU (defaults to In/Out address)"
			::= { accIpxNetEntry 12 }
	  accIpxNetX25Idle  OBJECT-TYPE   
			SYNTAX	TimeTicks 
			ACCESS	read-write
			STATUS	mandatory
			DESCRIPTION
	                   " Time X25 connection can be idle before it is 
	                     determined to be not busy."
                        DEFVAL { 30000 }
			::= { accIpxNetEntry 13 }
	  accIpxNetX25PktVal  OBJECT-TYPE   
			SYNTAX	INTEGER (0..1024)
			ACCESS	read-write
			STATUS	mandatory
			DESCRIPTION
	                    " X25 packet size "
                        DEFVAL { 0 }
			::= { accIpxNetEntry 14 }
	  accIpxNetX25PktWin  OBJECT-TYPE   
			SYNTAX	INTEGER (0..127)
			ACCESS	read-write
			STATUS	mandatory
			DESCRIPTION
	                   " X25 packet window "
                        DEFVAL { 0 }
			::= { accIpxNetEntry 15 }
	  accIpxNetEntryStat  OBJECT-TYPE   
			SYNTAX	INTEGER {
				other(1),
				invalid(2)
			    }
			ACCESS	read-write
			STATUS	mandatory
			DESCRIPTION
	                     " Status of this table entry
		               Set this object to invalid to delete entry."
                        DEFVAL { other }
			::= { accIpxNetEntry 16 }
	accIpxNetFncAddr OBJECT-TYPE
	    SYNTAX	OCTET STRING  -- (SIZE (6))
	    ACCESS	read-write
	    STATUS	mandatory
	    DESCRIPTION
		 " The MAC-layer functional address for sending and
		   receiving multicasts."
	    ::= { accIpxNetEntry 17 }
	accIpxNetSrMode OBJECT-TYPE
	    SYNTAX	INTEGER (0..2)
	    ACCESS	read-write
	    STATUS	mandatory
            DESCRIPTION
		 " The source-routing mode for token-ring networks."
            ::= { accIpxNetEntry 18 }
        accIpxNetX25FacIndex OBJECT-TYPE
                   SYNTAX      INTEGER (0..255)
                   ACCESS      read-write
                   STATUS      mandatory
                   DESCRIPTION
                   " Index of optional facility string or 0."
                   DEFVAL { 0 }
                   ::= { accIpxNetEntry 19 }
        accIpxNetDlci       OBJECT-TYPE
                   SYNTAX  INTEGER
                   ACCESS  read-write
                   STATUS  mandatory
                   DESCRIPTION
                   " Frame Relay DLCI for this port"
                   ::= { accIpxNetEntry 20 }
        accIpxNetWdState   OBJECT-TYPE
                   SYNTAX  INTEGER {
			allow(1),
			discard(2),
			proxy(3)
			}
                   ACCESS  read-write
                   STATUS  mandatory
                   DESCRIPTION
                   " Determines the IPX watchdog state on a specific logical
                     port. The default is ALLOW for LAN/DEDICATED WAN type,
                     PROXY for X.21/FFR/Dial type."
                   ::= { accIpxNetEntry 21 }
     accIpxRtTable  OBJECT-TYPE   
			SYNTAX	SEQUENCE OF AccIpxRtEntry
			ACCESS	not-accessible
			STATUS	mandatory
			DESCRIPTION
                " List of routes to other IPX networks"
			::= { accIpx 3 }
        accIpxRtEntry  OBJECT-TYPE   
			SYNTAX	AccIpxRtEntry
			ACCESS	not-accessible
			STATUS	mandatory
			DESCRIPTION
                " Information on route to destination network"
		        INDEX { accIpxRtDest }
			::= { accIpxRtTable 1 }
        AccIpxRtEntry ::= SEQUENCE {
			accIpxRtDest		OCTET STRING,
			accIpxRtNxtNet		OCTET STRING,
			accIpxRtRouter		OCTET STRING,
			accIpxRtHops		INTEGER,
			accIpxRtCost		INTEGER,
			accIpxRtType		INTEGER,
			accIpxRtOwner		INTEGER,
			accIpxRtAge		TimeTicks,
			accIpxRtPort		INTEGER
 			}
	  accIpxRtDest  OBJECT-TYPE   
			SYNTAX	OCTET STRING  -- (SIZE (4))
			ACCESS	read-only
			STATUS	mandatory
			DESCRIPTION
	        " Destination network."
			::= { accIpxRtEntry 1 }
	  accIpxRtNxtNet  OBJECT-TYPE
			SYNTAX	OCTET STRING
			ACCESS	read-only
			STATUS	mandatory
			DESCRIPTION
		 " The next network along the way 
		   to the destination network."
			::= { accIpxRtEntry 2 }
	  accIpxRtRouter  OBJECT-TYPE   
			SYNTAX	OCTET STRING 
			ACCESS	read-only
			STATUS	mandatory
			DESCRIPTION
	        " Router on next IPX network on route"
			::= { accIpxRtEntry 3 }
	  accIpxRtHops  OBJECT-TYPE   
			SYNTAX	INTEGER
			ACCESS	read-only
			STATUS	mandatory
			DESCRIPTION
	        " Number of hops to remote network"
			::= { accIpxRtEntry 4 }
	  accIpxRtCost  OBJECT-TYPE   
			SYNTAX	INTEGER
			ACCESS	read-only
			STATUS	mandatory
			DESCRIPTION
	        " Cost to remote network"
			::= { accIpxRtEntry 5 }
	  accIpxRtType  OBJECT-TYPE   
			SYNTAX	INTEGER {
				public(1),
				direct(2),
				static(3)
			    }
			ACCESS	read-only
			STATUS	mandatory
			DESCRIPTION
	        " Type of route"
			::= { accIpxRtEntry 6 }
	  accIpxRtOwner  OBJECT-TYPE   
			SYNTAX	INTEGER {
				lli(1),
				nms(2),
				rip(3)
			    }
			ACCESS	read-only
			STATUS	mandatory
			DESCRIPTION
	        " Source of route"
			::= { accIpxRtEntry 7 }
	  accIpxRtAge  OBJECT-TYPE   
			SYNTAX	TimeTicks
			ACCESS	read-only
			STATUS	mandatory
			DESCRIPTION
	        " Age of route"
			::= { accIpxRtEntry 8 }
	  accIpxRtPort  OBJECT-TYPE
			SYNTAX	INTEGER
			ACCESS	read-only
			STATUS	mandatory
			DESCRIPTION
		 " The logical port number through which packets will be
		   forwarded to the destination network."
			::= { accIpxRtEntry 9 }
    accIpxRipStat   OBJECT IDENTIFIER ::= { accIpx 4 }
           accIpxRipReqIns OBJECT-TYPE   
			SYNTAX	Counter
			ACCESS	read-only
			STATUS	mandatory
			DESCRIPTION
	        " IPX RIP requests received"
			::= { accIpxRipStat 1 }
           accIpxRipRespIns OBJECT-TYPE   
			SYNTAX	Counter
			ACCESS	read-only
			STATUS	mandatory
			DESCRIPTION
	        " IPX RIP responses received"
			::= { accIpxRipStat 2 }
           accIpxRipReqOuts OBJECT-TYPE   
			SYNTAX	Counter
			ACCESS	read-only
			STATUS	mandatory
			DESCRIPTION
	        " IPX RIP requests transmitted"
			::= { accIpxRipStat 3 }
           accIpxRipRespOuts OBJECT-TYPE   
			SYNTAX	Counter
			ACCESS	read-only
			STATUS	mandatory
			DESCRIPTION
	        " IPX RIP responses transmitted"
			::= { accIpxRipStat 4 }
           accIpxRipErrIns OBJECT-TYPE   
			SYNTAX	Counter
			ACCESS	read-only
			STATUS	mandatory
			DESCRIPTION
	        " IPX RIP responses recevied with errors."
			::= { accIpxRipStat 5 }
           accIpxRipErrOuts OBJECT-TYPE   
			SYNTAX	Counter
			ACCESS	read-only
			STATUS	mandatory
			DESCRIPTION
	        " IPX RIP responses transmitted with errors."
			::= { accIpxRipStat 6 }
      accIpxNodeStat  OBJECT IDENTIFIER  ::= { accIpx 5 }
           accIpxLocalIns OBJECT-TYPE   
			SYNTAX	Counter
			ACCESS	read-only
			STATUS	mandatory
			DESCRIPTION
	        " Packets received for local usage"
			::= { accIpxNodeStat 1 }
           accIpxLocalOuts OBJECT-TYPE   
			SYNTAX	Counter
			ACCESS	read-only
			STATUS	mandatory
			DESCRIPTION
	        " Locally generated packets"
			::= { accIpxNodeStat 2 }
           accIpxNoSockets OBJECT-TYPE   
			SYNTAX	Counter
			ACCESS	read-only
			STATUS	mandatory
			DESCRIPTION
	        " Packets received for which there was no socket"
			::= { accIpxNodeStat 3 }
           accIpxNoRoutes OBJECT-TYPE   
			SYNTAX	Counter
			ACCESS	read-only
			STATUS	mandatory
			DESCRIPTION
	        " Packets for which no route was found"
			::= { accIpxNodeStat 4 }
           accIpxNodeInErrs OBJECT-TYPE   
			SYNTAX	Counter
			ACCESS	read-only
			STATUS	mandatory
			DESCRIPTION
	        " The number of input packets discarded by this node because
	          of some unspecified internal error."
			::= { accIpxNodeStat 5 }
           accIpxOutErrs OBJECT-TYPE   
			SYNTAX	Counter
			ACCESS	read-only
			STATUS	mandatory
			DESCRIPTION
	        " Output errors"
			::= { accIpxNodeStat 6 }
           accIpxAllNetsIns OBJECT-TYPE   
			SYNTAX	Counter
			ACCESS	read-only
			STATUS	mandatory
			DESCRIPTION
	        " All-nets packets received"
			::= { accIpxNodeStat 7 }
           accIpxAllNetsOuts OBJECT-TYPE   
			SYNTAX	Counter
			ACCESS	read-only
			STATUS	mandatory
			DESCRIPTION
	        " All-nets packets transmitted"
			::= { accIpxNodeStat 8 }
           accIpxAllNetsErrs OBJECT-TYPE   
			SYNTAX	Counter
			ACCESS	read-only
			STATUS	mandatory
			DESCRIPTION
	        " Erroneous All-Nets packets encountered"
			::= { accIpxNodeStat 9 }
     accIpxPortStatTable  OBJECT-TYPE   
			SYNTAX	SEQUENCE OF AccIpxPortStatEntry
			ACCESS	not-accessible
			STATUS	mandatory
			DESCRIPTION
                " IPX Port statistics table"
			::= { accIpx 6 }
        accIpxPortStatEntry  OBJECT-TYPE   
			SYNTAX	AccIpxPortStatEntry
			ACCESS	not-accessible
			STATUS	mandatory
			DESCRIPTION
                " Per-port statistics "
		        INDEX { accIpxPortNumber }
			::= { accIpxPortStatTable 1 }
        AccIpxPortStatEntry ::= SEQUENCE {
			accIpxPortNumber		INTEGER,
			accIpxPortTotalIns		Counter,
			accIpxPorFwdReqIns		Counter,
			accIpxPortNoFwdRts		Counter,
			accIpxPortTotalOuts		Counter,
			accIpxPortHopCnts		Counter,
			accIpxPortNotForMes		Counter,
			accIpxPortFwdReqOuts		Counter,
			accIpxPortFwdErrs		Counter,
			accIpxPortInErrs		Counter,
			accIpxPortTooShorts		Counter,
			accIpxPortCkSums		Counter,
			accIpxPortTooLongs		Counter,
			accIpxPortOutErrs		Counter,
			accIpxPortOpState		INTEGER
 			}
	  accIpxPortNumber  OBJECT-TYPE   
			SYNTAX	INTEGER
			ACCESS	read-only
			STATUS	mandatory
			DESCRIPTION
	        " Port number"
			::= { accIpxPortStatEntry 1 }
	  accIpxPortTotalIns  OBJECT-TYPE   
			SYNTAX	Counter
			ACCESS	read-only
			STATUS	mandatory
			DESCRIPTION
	        " Total number of IPX  Packets received"
			::= { accIpxPortStatEntry 2 }
	  accIpxPorFwdReqIns  OBJECT-TYPE   
			SYNTAX	Counter
			ACCESS	read-only
			STATUS	mandatory
			DESCRIPTION
		  " The number of input packets not addressed to the receiving
		    port, as a result of which an attempt was made to find a
		    route to forward them to the final destination."
			::= { accIpxPortStatEntry 3 }
	  accIpxPortNoFwdRts  OBJECT-TYPE   
			SYNTAX	Counter
			ACCESS	read-only
			STATUS	mandatory
			DESCRIPTION
	        " The number of packets received on this port for which no
	          route to the destination network could be found."
			::= { accIpxPortStatEntry 4 }
	  accIpxPortTotalOuts  OBJECT-TYPE   
			SYNTAX	Counter
			ACCESS	read-only
			STATUS	mandatory
			DESCRIPTION
	        " Total IPX packets transmitted"
			::= { accIpxPortStatEntry 5 }
	  accIpxPortHopCnts  OBJECT-TYPE   
			SYNTAX	Counter
			ACCESS	read-only
			STATUS	mandatory
			DESCRIPTION
		 " The number of packets received on this port whose hop
		   count had reached the maximum value."
			::= { accIpxPortStatEntry 6 }
	  accIpxPortNotForMes  OBJECT-TYPE   
			SYNTAX	Counter
			ACCESS	read-only
			STATUS	mandatory
			DESCRIPTION
		 " The number of packets received on this port which were
		   addressed to another node on the same network."
			::= { accIpxPortStatEntry 7 }
	  accIpxPortFwdReqOuts  OBJECT-TYPE   
			SYNTAX	Counter
			ACCESS	read-only
			STATUS	mandatory
			DESCRIPTION
		 " The number of packets received on this port which were
		   successfully forwarded to another port."
			::= { accIpxPortStatEntry 8 }
	  accIpxPortFwdErrs  OBJECT-TYPE   
			SYNTAX	Counter
			ACCESS	read-only
			STATUS	mandatory
			DESCRIPTION
		 " The number of packets received on this port which could
		   not be forwarded, either because there were transmitted
		   via a MAC-layer broadcast, or because their source or
		   destination network number were unknown."
			::= { accIpxPortStatEntry 9 }
	  accIpxPortInErrs  OBJECT-TYPE   
			SYNTAX	Counter
			ACCESS	read-only
			STATUS	mandatory
			DESCRIPTION
	        " The number of packets received on this port which were
	          discarded because of some unspecified internal error."
			::= { accIpxPortStatEntry 10 }
	  accIpxPortTooShorts  OBJECT-TYPE   
			SYNTAX	Counter
			ACCESS	read-only
			STATUS	mandatory
			DESCRIPTION
		 " The number of packets received on this port which were
		   discarded because they were too short."
			::= { accIpxPortStatEntry 11 }
	  accIpxPortCkSums  OBJECT-TYPE   
			SYNTAX	Counter
			ACCESS	read-only
			STATUS	mandatory
			DESCRIPTION
	        " IPX packet checksum errors detected"
			::= { accIpxPortStatEntry 12 }
	  accIpxPortTooLongs  OBJECT-TYPE   
			SYNTAX	Counter
			ACCESS	read-only
			STATUS	mandatory
			DESCRIPTION
		 " The number of packets received on this port which were
		   discarded because they were too long."
			::= { accIpxPortStatEntry 13 }
	  accIpxPortOutErrs  OBJECT-TYPE   
			SYNTAX	Counter
			ACCESS	read-only
			STATUS	mandatory
			DESCRIPTION
	        " IPX packet output errors detected"
			::= { accIpxPortStatEntry 14 }
	  accIpxPortOpState  OBJECT-TYPE   
			SYNTAX	INTEGER (0..4)
			ACCESS	read-only
			STATUS	mandatory
			DESCRIPTION
	        " Operational status of this port.
				off(0),
				down(1),
				start(2),
				stop(3),
				up(4)
		"
			::= { accIpxPortStatEntry 15 }
     accIpxSapStat  OBJECT IDENTIFIER ::= { accIpx 7 }
	  accIpxSapReqIns  OBJECT-TYPE   
			SYNTAX	Counter
			ACCESS	read-only
			STATUS	mandatory
			DESCRIPTION
	        " IPX SAP requests received"
			::= { accIpxSapStat 1 }
	  accIpxSapReqOuts  OBJECT-TYPE   
			SYNTAX	Counter
			ACCESS	read-only
			STATUS	mandatory
			DESCRIPTION
	        " IPX SAP requests transmitted"
			::= { accIpxSapStat 2 }
	  accIpxSapRespIns  OBJECT-TYPE   
			SYNTAX	Counter
			ACCESS	read-only
			STATUS	mandatory
			DESCRIPTION
	        " IPX SAP responses received"
			::= { accIpxSapStat 3 }
	  accIpxSapRespOuts  OBJECT-TYPE   
			SYNTAX	Counter
			ACCESS	read-only
			STATUS	mandatory
			DESCRIPTION
	        " IPX SAP responses transmitted"
			::= { accIpxSapStat 4 }
	  accIpxSapGetNearIns  OBJECT-TYPE   
			SYNTAX	Counter
			ACCESS	read-only
			STATUS	mandatory
			DESCRIPTION
	        " Get nearest requests received"
			::= { accIpxSapStat 5 }
	  accIpxSapGetNearOuts  OBJECT-TYPE   
			SYNTAX	Counter
			ACCESS	read-only
			STATUS	mandatory
			DESCRIPTION
	        " Get nearest requests transmitted"
			::= { accIpxSapStat 6 }
	  accIpxSapNoRoutes  OBJECT-TYPE   
			SYNTAX	Counter
			ACCESS	read-only
			STATUS	mandatory
			DESCRIPTION
	        " IPX SAP packets for unreachable net"
			::= { accIpxSapStat 7 }
	  accIpxSapNotBests  OBJECT-TYPE   
			SYNTAX	Counter
			ACCESS	read-only
			STATUS	mandatory
			DESCRIPTION
	        " IPX SAP packet which we know there is a better route for"
			::= { accIpxSapStat 8 }
	  accIpxSapNoServers  OBJECT-TYPE   
			SYNTAX	Counter
			ACCESS	read-only
			STATUS	mandatory
			DESCRIPTION
	        " No server available"
			::= { accIpxSapStat 9 }
	  accIpxSapInErrs  OBJECT-TYPE   
			SYNTAX	Counter
			ACCESS	read-only
			STATUS	mandatory
			DESCRIPTION
	        " Bad IPX SAP packets received"
			::= { accIpxSapStat 10 }
	  accIpxSapOutErrs  OBJECT-TYPE   
			SYNTAX	Counter
			ACCESS	read-only
			STATUS	mandatory
			DESCRIPTION
	        " Bad IPX SAP packets transmitted"
			::= { accIpxSapStat 11 }
     accIpxSrvTable  OBJECT-TYPE   
			SYNTAX	SEQUENCE OF AccIpxSrvEntry
			ACCESS	not-accessible
			STATUS	mandatory
			DESCRIPTION
                " IPX server table"
			::= { accIpx 8 }
        accIpxSrvEntry  OBJECT-TYPE   
			SYNTAX	AccIpxSrvEntry
			ACCESS	not-accessible
			STATUS	mandatory
			DESCRIPTION
                           " Specific IPX server information"
                        INDEX { accIpxSrvType,
	                        accIpxSrvName }
			::= { accIpxSrvTable 1 }
        AccIpxSrvEntry ::= SEQUENCE {
			accIpxSrvName		DisplayString,
			accIpxSrvType		OCTET STRING,
			accIpxSrvHost		OCTET STRING,
			accIpxSrvHops		INTEGER,
			accIpxSrvOwner		INTEGER,
			accIpxSrvAge		TimeTicks
 			}
	  accIpxSrvName  OBJECT-TYPE   
			SYNTAX  DisplayString	
			ACCESS	read-only
			STATUS	mandatory
			DESCRIPTION
	        " Name of server"
			::= { accIpxSrvEntry 1 }
	  accIpxSrvType  OBJECT-TYPE   
			SYNTAX	OCTET STRING -- (SIZE(2))
			ACCESS	read-only
			STATUS	mandatory
			DESCRIPTION
	        " Type of server"
			::= { accIpxSrvEntry 2 }
	  accIpxSrvHost  OBJECT-TYPE   
			SYNTAX	OCTET STRING
			ACCESS	read-only
			STATUS	mandatory
			DESCRIPTION
	        " Host"
			::= { accIpxSrvEntry 3 }
	  accIpxSrvHops  OBJECT-TYPE   
			SYNTAX	INTEGER
			ACCESS	read-only
			STATUS	mandatory
			DESCRIPTION
	        " Hop counter"
			::= { accIpxSrvEntry 4 }
	  accIpxSrvOwner  OBJECT-TYPE   
			SYNTAX	INTEGER {
				nms(1),
				sap(2)
				}
			ACCESS	read-only
			STATUS	mandatory
			DESCRIPTION
	        " Source of route"
			::= { accIpxSrvEntry 5 }
	  accIpxSrvAge  OBJECT-TYPE   
			SYNTAX	TimeTicks 
			ACCESS	read-only
			STATUS	mandatory
			DESCRIPTION
	        " Age of route"
			::= { accIpxSrvEntry 6 }
   accIpxRouteFilters OBJECT IDENTIFIER ::= { accIpx 9 }
     accIpxRteFltrDefaultAction OBJECT-TYPE
         SYNTAX   INTEGER { 
		     accept(1), 
		     reject(2) 
		     }
         ACCESS   read-write
         STATUS   mandatory
         DESCRIPTION
          " The action taken on route updates from unconfigured neighbors."
         ::= { accIpxRouteFilters 1 }
      accIpxRteNbrTable OBJECT-TYPE
          SYNTAX   SEQUENCE OF AccIpxRteNbrEntry
          ACCESS   not-accessible
          STATUS   mandatory
          DESCRIPTION
             " A list of Host Identifiers for Routing Neighbors."
          ::= { accIpxRouteFilters 2 }
         accIpxRteNbrEntry OBJECT-TYPE
            SYNTAX   AccIpxRteNbrEntry
            ACCESS   not-accessible
            STATUS   mandatory
            DESCRIPTION
               " The host identifier for an individual routing neighbor."
            INDEX { accIpxRteNbrId }
            ::= { accIpxRteNbrTable 1 }
         AccIpxRteNbrEntry ::=
             SEQUENCE {
                 accIpxRteNbrId
                     OCTET STRING,
                 accIpxRteNbrAction
                     INTEGER,
                 accIpxRteNbrStatus
                     INTEGER
                 }
            accIpxRteNbrId OBJECT-TYPE
                SYNTAX   OCTET STRING -- (SIZE(6))
                ACCESS   read-write
                STATUS   mandatory
                DESCRIPTION
                  " The Host Identifier of a potential routing neighbor."
                ::= { accIpxRteNbrEntry 1 }
            accIpxRteNbrAction OBJECT-TYPE
                SYNTAX   INTEGER { 
			accept(1), 
			reject(2) 
			}
                ACCESS   read-write
                STATUS   mandatory
                DESCRIPTION
         " The action to be taken on advertisements from this routing neighbor,
           unless overridden by a route filter."
                ::= { accIpxRteNbrEntry 2 }
            accIpxRteNbrStatus OBJECT-TYPE
                SYNTAX   INTEGER {
                            invalid(1), 
                            valid(2) 
                            }
                ACCESS   read-write
                STATUS   mandatory
                DESCRIPTION
          " Writing 'invalid' has the effect of deleting this routing neighbor
            and making its associated route filters of no effect."
                ::= { accIpxRteNbrEntry 3 }
     accIpxRteFltrTable OBJECT-TYPE
         SYNTAX   SEQUENCE OF AccIpxRteFltrEntry
         ACCESS   not-accessible
         STATUS   mandatory
         DESCRIPTION
         " A list of special advertisements that a given neighbor might offer.
           Route Advertisements defaults are overridden using this table"
         ::= { accIpxRouteFilters 3 }
        accIpxRteFltrEntry OBJECT-TYPE
            SYNTAX   AccIpxRteFltrEntry
            ACCESS   not-accessible
            STATUS   mandatory
            DESCRIPTION
                  " A single potential advertisement, with information 
                    as to its disposition."
            INDEX { accIpxRteFltrNeighbor, 
                    accIpxRteFltrNetwork }
            ::= { accIpxRteFltrTable 1 }
        AccIpxRteFltrEntry ::=
            SEQUENCE {
                accIpxRteFltrNeighbor
                    OCTET STRING,
                accIpxRteFltrNetwork
                    OCTET STRING,
                accIpxRteFltrAction
                    INTEGER,
                accIpxRteFltrStatus
                    INTEGER
	        }
            accIpxRteFltrNeighbor OBJECT-TYPE
                SYNTAX   OCTET STRING
                ACCESS   read-write
                STATUS   mandatory
                DESCRIPTION
                      " The Host Identifier of the Routing Neighbor that might 
                        offer this advertsiement."
                ::= { accIpxRteFltrEntry 1 }
            accIpxRteFltrNetwork OBJECT-TYPE
                SYNTAX   OCTET STRING  -- (SIZE (4))
                ACCESS   read-write
                STATUS   mandatory
                DESCRIPTION
                     " The Network Number the neighbor might advertise."
                ::= { accIpxRteFltrEntry 2 }
            accIpxRteFltrAction OBJECT-TYPE
                SYNTAX   INTEGER { 
		            accept(1), 
		            reject(2) 
		            }
                ACCESS   read-write
                STATUS   mandatory
                DESCRIPTION
                      " What is to be done with such an advertisement."
                ::= { accIpxRteFltrEntry 3 }
            accIpxRteFltrStatus OBJECT-TYPE
                SYNTAX   INTEGER {
                            invalid(1), 
                            valid(2) 
                            }
                ACCESS   read-write
                STATUS   mandatory
                DESCRIPTION
                     " Writing 'invalid' has the effect of deleting this filter."
                ::= { accIpxRteFltrEntry 4 }
     accIpxNetworkFilters OBJECT IDENTIFIER ::= { accIpx 10 }
         accIpxNetFltrDefaultAction OBJECT-TYPE
             SYNTAX   INTEGER  (0..3)
             ACCESS   read-write
             STATUS   mandatory
             DESCRIPTION
             " The action taken on messages not matched.
                        discard(0),
                        lowPriority(1),
                        normalPriority(2),
                        highPriority(3)
		"
             ::= { accIpxNetworkFilters 1 }
--    The following network filter table has been deprecated in
--    deference to the new table immediately subsequent.
        oldIpxNetFltrTable OBJECT-TYPE
            SYNTAX   SEQUENCE OF OldIpxNetFltrEntry
            ACCESS   not-accessible
            STATUS   deprecated
            DESCRIPTION
                    " A list of network pairs to specially act on."
            ::= { accIpxNetworkFilters 2 }
           oldIpxNetFltrEntry OBJECT-TYPE
               SYNTAX   OldIpxNetFltrEntry
               ACCESS   not-accessible
               STATUS   deprecated
               DESCRIPTION
                       " A single Network Number pair to be matched."
               INDEX { oldIpxNetFltrDestination, 
                       oldIpxNetFltrSource }
               ::= { oldIpxNetFltrTable 1 }
           OldIpxNetFltrEntry ::=
               SEQUENCE {
                   oldIpxNetFltrDestination
                       OCTET STRING,
                   oldIpxNetFltrSource
                       OCTET STRING,
                   oldIpxNetFltrAction
                       INTEGER,
                   oldIpxNetFltrStatus
                       INTEGER
	           }
             oldIpxNetFltrDestination OBJECT-TYPE
                 SYNTAX   OCTET STRING  -- (SIZE (4))
                 ACCESS   read-write
                 STATUS   deprecated
                 DESCRIPTION
        " The value to be found in the Destination Network Field, or 0x00000000."
                 ::= { oldIpxNetFltrEntry 1 }
             oldIpxNetFltrSource OBJECT-TYPE
                 SYNTAX   OCTET STRING  -- (SIZE (4))
                 ACCESS   read-write
                 STATUS   deprecated
                 DESCRIPTION
        " The value to be found in the Source Network Field, or 0x00000000."
                 ::= { oldIpxNetFltrEntry 2 }
             oldIpxNetFltrAction OBJECT-TYPE
             SYNTAX   INTEGER  (0..3)
                 ACCESS   read-write
                 STATUS   deprecated
                 DESCRIPTION
                      " The action to be taken on matching messages.
                        discard(0),
                        lowPriority(1),
                        normalPriority(2),
                        highPriority(3)
		"
                 ::= { oldIpxNetFltrEntry 3 }
             oldIpxNetFltrStatus OBJECT-TYPE
                 SYNTAX   INTEGER {
                             invalid(1), 
                             valid(2) 
                             }
                 ACCESS   read-write
                 STATUS   deprecated
                 DESCRIPTION
            " Writing 'invalid' has the effect of removing this filter entry."
                 ::= { oldIpxNetFltrEntry 4 }
--	The Network Filter permits the filtering of specific
--      traffic based on source and destination network,
--      source and destination socket, and packet type.
--	A value of zero in a field is a wildcard.
        accIpxNetFltrTable OBJECT-TYPE
            SYNTAX   SEQUENCE OF AccIpxNetFltrEntry
            ACCESS   not-accessible
            STATUS   mandatory
            DESCRIPTION
                    " A list of network filters to specially act on."
            ::= { accIpxNetworkFilters 3 }
           accIpxNetFltrEntry OBJECT-TYPE
               SYNTAX   AccIpxNetFltrEntry
               ACCESS   not-accessible
               STATUS   mandatory
               DESCRIPTION
                       " A single Network  filter to be matched."
               INDEX { accIpxNetFltrDestination, 
                       accIpxNetFltrSource,
                       accIpxNetFltrDestSkt,
                       accIpxNetFltrSrcSkt,
                       accIpxNetFltrPktType }
               ::= { accIpxNetFltrTable 1 }
           AccIpxNetFltrEntry ::=
               SEQUENCE {
                   accIpxNetFltrDestination
                       OCTET STRING,
                   accIpxNetFltrSource
                       OCTET STRING,
                   accIpxNetFltrAction
                       INTEGER,
                   accIpxNetFltrStatus
                       INTEGER,
                   accIpxNetFltrDestSkt
                       OCTET STRING,
                   accIpxNetFltrSrcSkt
                       OCTET STRING,
                   accIpxNetFltrPktType
                       INTEGER
	           }
             accIpxNetFltrDestination OBJECT-TYPE
                 SYNTAX   OCTET STRING  -- (SIZE (4))
                 ACCESS   read-write
                 STATUS   mandatory
                 DESCRIPTION
        " The value to be found in the Destination Network Field, or 0x00000000."
                 ::= { accIpxNetFltrEntry 1 }
             accIpxNetFltrSource OBJECT-TYPE
                 SYNTAX   OCTET STRING  -- (SIZE (4))
                 ACCESS   read-write
                 STATUS   mandatory
                 DESCRIPTION
        " The value to be found in the Source Network Field, or 0x00000000."
                 ::= { accIpxNetFltrEntry 2 }
             accIpxNetFltrAction OBJECT-TYPE
             SYNTAX   INTEGER  (0..3)
                 ACCESS   read-write
                 STATUS   mandatory
                 DESCRIPTION
                      " The action to be taken on matching messages.
                        discard(0),
                        lowPriority(1),
                        normalPriority(2),
                        highPriority(3)
		"
                 ::= { accIpxNetFltrEntry 3 }
             accIpxNetFltrStatus OBJECT-TYPE
                 SYNTAX   INTEGER {
                             invalid(1), 
                             valid(2) 
                             }
                 ACCESS   read-write
                 STATUS   mandatory
                 DESCRIPTION
            " Writing 'invalid' has the effect of removing this filter entry."
                 ::= { accIpxNetFltrEntry 4 }
             accIpxNetFltrDestSkt OBJECT-TYPE
                 SYNTAX   OCTET STRING  -- (SIZE (2))
                 ACCESS   read-write
                 STATUS   mandatory
                 DESCRIPTION
        " The value to be found in the Destination Socket field, or 0x0000."
                 ::= { accIpxNetFltrEntry 5 }
             accIpxNetFltrSrcSkt OBJECT-TYPE
                 SYNTAX   OCTET STRING  -- (SIZE (2))
                 ACCESS   read-write
                 STATUS   mandatory
                 DESCRIPTION
        " The value to be found in the Source Socket Field, or 0x0000."
                 ::= { accIpxNetFltrEntry 6 }
             accIpxNetFltrPktType OBJECT-TYPE
                 SYNTAX   INTEGER 
                 ACCESS   read-write
                 STATUS   mandatory
                 DESCRIPTION
            " Packet type or zero"
                 ::= { accIpxNetFltrEntry 7 }
--  IPX Host Filters
--	The Host Filter indicates what is to be done with traffic
--	originated or destined locally.
--
--	The value 0x000000000000 is used to mean 'any host'
     accIpxHostFilters OBJECT IDENTIFIER ::= { accIpx 11 }
        accIpxHostFltrDefaultAction OBJECT-TYPE
             SYNTAX   INTEGER  (0..3)
            ACCESS   read-write
            STATUS   mandatory
            DESCRIPTION
                  " The action taken on hosts not listed.
                        discard(0),
                        lowPriority(1),
                        normalPriority(2),
                        highPriority(3)
		"
            ::= { accIpxHostFilters 1 }
--  IPX Local Host Table
--	The Local Host List indicates what is to be done with traffic
--	to or from local hosts
        accIpxHostFltrTable OBJECT-TYPE
            SYNTAX   SEQUENCE OF AccIpxHostFltrEntry
            ACCESS   not-accessible
            STATUS   mandatory
            DESCRIPTION
                     " A list of IPX Hosts to be handled specially."
            ::= { accIpxHostFilters 2 }
           accIpxHostFltrEntry OBJECT-TYPE
               SYNTAX   AccIpxHostFltrEntry
               ACCESS   not-accessible
               STATUS   mandatory
               DESCRIPTION
                     " A single Host Identifier."
               INDEX { accIpxHostFltrId, 
                       accIpxHostFltrSocket, 
                       accIpxHostFltrPepClient }
               ::= { accIpxHostFltrTable 1 }
           AccIpxHostFltrEntry ::=
               SEQUENCE {
                   accIpxHostFltrId
                       OCTET STRING,
	           accIpxHostFltrSocket
	               OCTET STRING,
	           accIpxHostFltrPepClient
	               OCTET STRING,
                   accIpxHostFltrAction
                       INTEGER,
                   accIpxHostFltrStatus
                       INTEGER
                  }
             accIpxHostFltrId OBJECT-TYPE
                 SYNTAX   OCTET STRING  -- (SIZE(6))
                 ACCESS   read-write
                 STATUS   mandatory
                 DESCRIPTION
                  " Host Identifier "
                 ::= { accIpxHostFltrEntry 1 }
             accIpxHostFltrSocket OBJECT-TYPE
                 SYNTAX   OCTET STRING -- (SIZE (2))
                 ACCESS   read-write
                 STATUS   mandatory
                 DESCRIPTION
                  " The affected socket number, or zero for 'any socket'."
                 ::= { accIpxHostFltrEntry 2 }
             accIpxHostFltrPepClient OBJECT-TYPE
                 SYNTAX   OCTET STRING -- (SIZE(2))
                 ACCESS   read-write
                 STATUS   mandatory
                 DESCRIPTION
                      " On PEP traffic, the affected Client Type, 
                        or zero for all IDP traffic."
                 ::= { accIpxHostFltrEntry 3 }
             accIpxHostFltrAction OBJECT-TYPE
             SYNTAX   INTEGER  (0..3)
                 ACCESS   read-write
                 STATUS   mandatory
                 DESCRIPTION
                         " The action to be taken on matching messages.
                        discard(0),
                        lowPriority(1),
                        normalPriority(2),
                        highPriority(3)
		"
                 ::= { accIpxHostFltrEntry 4 }
             accIpxHostFltrStatus OBJECT-TYPE
                 SYNTAX   INTEGER {
                             invalid(1), 
                             valid(2) 
                             }
                 ACCESS   read-write
                 STATUS   mandatory
                 DESCRIPTION
           " Writing 'invalid' has the effect of deleting the entry."
                 ::= { accIpxHostFltrEntry 5 }
--  NetWare Service Advertising Protocol Filters 
--	Service Advertisement Protocol Filter Entries indicate
--	what service names are or not to be advertised through the
--	network.
     accIpxSapFilters OBJECT IDENTIFIER ::= { accIpx 12 }
        accIpxSapFltrDefault OBJECT-TYPE
            SYNTAX   INTEGER {
                        accept(1), 
                        reject(2) 
                        }
            ACCESS   read-write
            STATUS   mandatory
            DESCRIPTION
           " The default behavior taken on locally originated (hop count <= 2)
             Service Advertisements.
             Remote advertisements must be identified individually."
            ::= { accIpxSapFilters 1 }
--  NetWare Service Advertising Protocol Filter Table
--	NetWare Service Names to include or exclude
--	from the SAP database
        accIpxSapFltrTable OBJECT-TYPE
            SYNTAX   SEQUENCE OF AccIpxSapFltrEntry
            ACCESS   not-accessible
            STATUS   mandatory
            DESCRIPTION
           " A list of Service Names to be handled Specially."
            ::= { accIpxSapFilters 2 }
          accIpxSapFltrEntry OBJECT-TYPE
              SYNTAX   AccIpxSapFltrEntry
              ACCESS   not-accessible
              STATUS   mandatory
              DESCRIPTION
           " A single Service name and its intended disposition."
              INDEX { accIpxSapFltrSrvType, 
                      accIpxSapFltrSrvName }
              ::= { accIpxSapFltrTable 1 }
          AccIpxSapFltrEntry ::=
              SEQUENCE {
                  accIpxSapFltrSrvType
                      OCTET STRING,
                  accIpxSapFltrSrvName
                      OCTET STRING,
                  accIpxSapFltrAction
                      INTEGER,
                  accIpxSapFltrStatus
                      INTEGER
	          }
              accIpxSapFltrSrvType OBJECT-TYPE
                  SYNTAX   OCTET STRING -- (SIZE(2))
	    	  ACCESS   read-write
                  STATUS   mandatory
                  DESCRIPTION
                          " The Service Type of the affected SAP Entry.
                            Zero indicates all services."
                  ::= { accIpxSapFltrEntry 1 }
              accIpxSapFltrSrvName OBJECT-TYPE
                  SYNTAX   OCTET STRING
                  ACCESS   read-write
                  STATUS   mandatory
                  DESCRIPTION
                       " The name of the affected service.  
                         An Octet String of length zero indicates all services.
                         Name may be up to 48 octets"
                  ::= { accIpxSapFltrEntry 2 }
              accIpxSapFltrAction OBJECT-TYPE
                  SYNTAX   INTEGER {
                              accept(1), 
                              reject(2) 
                              }
                  ACCESS   read-write
                  STATUS   mandatory
                  DESCRIPTION
                       " The action to be taken upon a match."
                  ::= { accIpxSapFltrEntry 3 }
              accIpxSapFltrStatus OBJECT-TYPE
                  SYNTAX   INTEGER {
                              invalid(1), 
                              valid(2) 
                              }
                  ACCESS   read-write
                  STATUS   mandatory
                  DESCRIPTION
                       " Writing 'invalid' has the effect of removing the entry."
                  ::= { accIpxSapFltrEntry 4 }
--      IPX watchdog parameters
	accIpxNetWdParms OBJECT IDENTIFIER ::= { accIpx 13 }
	accIpxWdProxyDuration OBJECT-TYPE
		SYNTAX INTEGER (0..86400)
		ACCESS read-write
		STATUS mandatory
		DESCRIPTION
			"IPX Watchdog proxy duration 
			Value is 0 to proxy for forever
			& the proxy duration can be set 
			to 0 - 86400"
		DEFVAL { 86400 }
		::= { accIpxNetWdParms 1 }
	accIpxWdHoldPeriod OBJECT-TYPE
		SYNTAX INTEGER (960..60600)
		ACCESS read-write
		STATUS mandatory
		DESCRIPTION
			"ACC IPX Watchdog hold period
	 		Default value is 960 minutes, 
	 		Hold period range is 960 - 60600"
		DEFVAL { 960 }
		::= { accIpxNetWdParms 2 }
	accIpxWdMaxSessions OBJECT-TYPE
		SYNTAX INTEGER (1..4096)
		ACCESS read-write
		STATUS mandatory
		DESCRIPTION
			"ACC IPX Watchdog Max Sessions
	 		Default value is 1024, 
			Valid range is 1- 4096"
		DEFVAL { 1024 }
		::= { accIpxNetWdParms 3 }
	accIpxWdDiagLevel OBJECT-TYPE
		SYNTAX INTEGER (1..7)
		ACCESS read-write
		STATUS mandatory
		DESCRIPTION
			"ACC IPX Watchdog Diagnostics Level 
	 		Default value is 1, 
		Valid range is 1- 7"
		DEFVAL { 1 }
		::= { accIpxNetWdParms 4 }
--  MultiPath IP Forwarding Table
         ipMultiPathTable OBJECT-TYPE
             SYNTAX   SEQUENCE OF IpMultiPathEntry
             ACCESS   not-accessible
             STATUS   mandatory
           DESCRIPTION
                 " This entity's IP Routing table."
           ::= { accBRG 23 }
         ipMultiPathEntry OBJECT-TYPE
             SYNTAX   IpMultiPathEntry
             ACCESS   not-accessible
             STATUS   mandatory
             DESCRIPTION
                 " A particular route to  a  particular  destina-
                   tion, under a particular policy."
             INDEX { ipMultiPathDest, 
                     ipMultiPathPolicy, 
                     ipMultiPathNextHop }
             ::= { ipMultiPathTable 1 }
         IpMultiPathEntry ::=
             SEQUENCE {
                 ipMultiPathDest
                     IpAddress,
                 ipMultiPathPolicy
                     INTEGER,
                 ipMultiPathIfIndex
                     INTEGER,
                 ipMultiPathMask
                     IpAddress,
                 ipMultiPathNextHop
                     IpAddress,
                 ipMultiPathMetric
                     INTEGER,
                 ipMultiPathType
                     INTEGER,
                 ipMultiPathProto
                     INTEGER,
                 ipMultiPathAge
                     INTEGER
             }
         ipMultiPathDest OBJECT-TYPE
             SYNTAX   IpAddress
             ACCESS   read-write
             STATUS   mandatory
            DESCRIPTION
                 " The destination IP address of this route.   An
                   entry  with  a value of 0.0.0.0 is considered a
                   default route."
            ::= { ipMultiPathEntry 1 }
         ipMultiPathPolicy OBJECT-TYPE
             SYNTAX   INTEGER
             ACCESS   read-write
             STATUS   mandatory
             DESCRIPTION
                 " An instantiator for the relevant policy table. "
            ::= { ipMultiPathEntry 2 }
         ipMultiPathIfIndex OBJECT-TYPE
             SYNTAX   INTEGER
             ACCESS   read-write
             STATUS   mandatory
            DESCRIPTION
                 " The index value which uniquely identifies  the
                   local  interface  through which the next hop of
                   this route should be  reached.   The  interface
                   identified  by a particular value of this index
                   is the same interface as identified by the same
                   value of ifIndex."
            ::= { ipMultiPathEntry 3 }
         ipMultiPathMask OBJECT-TYPE
             SYNTAX   IpAddress
             ACCESS   read-write
             STATUS   mandatory
            DESCRIPTION
                 " Indicate the mask to be logical-ANDed with the
                   destination  address  before  being compared to
                   the value  in  the  ipMultiPathDest  field.   For
                   those  systems  that  do  not support arbitrary
                   subnet masks, an agent constructs the value  of
                   the  ipMultiPathMask  by  determining whether the
                   value of the correspondent ipMultiPathDest  field
                   belong  to a class-A, B, or C network, and then
                   using one of:
                   mask           network
                   255.0.0.0      class-A
                   255.255.0.0    class-B
                   255.255.255.0  class-C
                   If the value of the ipMultiPathDest is 0.0.0.0(a
                   default  route),  then  the  mask value is also
                   0.0.0.0.  It should be noted that all IP  rout-
                   ing subsystems implicitly use this mechanism."
            ::= { ipMultiPathEntry 4 }
         ipMultiPathNextHop OBJECT-TYPE
             SYNTAX   IpAddress
             ACCESS   read-write
             STATUS   mandatory
            DESCRIPTION
                 " The IP address of the next hop of this  route.
                  (In  the  case of a route bound to an interface
                   which is realized via a  broadcast  media,  the
                   value  of  this field is the agent's IP address
                   on that interface.)"
            ::= { ipMultiPathEntry 5 }
         ipMultiPathMetric OBJECT-TYPE
             SYNTAX   INTEGER
             ACCESS   read-write
             STATUS   mandatory
            DESCRIPTION
                 " The primary routing  metric  for  this  route.
                   The  semantics of this metric are determined by
                   the routing-protocol specified in  the  route's
                   ipMultiPathProto  value."
            ::= { ipMultiPathEntry 6 }
         ipMultiPathType OBJECT-TYPE
             SYNTAX   INTEGER {
                         other(1),   -- not specified by this MIB
                         invalid(2),   -- logically deleted
                         direct(3),   -- local interface
                         indirect(4)    -- remote destination
                      }
             ACCESS   read-write
             STATUS   mandatory
            DESCRIPTION
                 " The type  of  route.   Note  that  the  values
                   direct(3)  and  indirect(4) refer to the notion
                   of direct and indirect routing in the IP archi-
                   tecture.   Setting this object to the value in-
                   valid(2) has the  effect  of  invalidating  the
                   corresponding  entry  in the ipMultiPathTable ob-
                   ject.  That is,  it  effectively  dissasociates
                   the destination identified with said entry from
                   the route identified with said entry.  It is an
                   implementation-specific  matter  as  to whether
                   the agent removes an invalidated entry from the
                   table.   Accordingly,  management stations must
                   be prepared to receive tabular information from
                   agents that corresponds to entries not current-
                   ly in use.  Proper interpretation of  such  en-
                   tries  requires examination of the relevant ip-
                   ForwardType object."
            ::= { ipMultiPathEntry 7 }
         ipMultiPathProto OBJECT-TYPE
             SYNTAX   INTEGER {
                         other(1),  -- not specified
                         local(2),  -- local interface
                         netmgmt(3),  -- static route
                         icmp(4),  -- result of ICMP Redirect
                                 -- the following are all dynamic
                                 -- routing protocols
                         egp(5),
                         rip(8),
                         ospf(13)
                      }
             ACCESS   read-write
             STATUS   mandatory
            DESCRIPTION
                 " The routing mechanism via which this route was
                   learned."
            ::= { ipMultiPathEntry 8 }
         ipMultiPathAge OBJECT-TYPE
             SYNTAX   INTEGER
             ACCESS   read-write
             STATUS   mandatory
            DESCRIPTION
                 " The number of seconds  since  this  route  was
                   last  updated  or  otherwise  determined  to be
                   correct.  Note that no semantics of  `too  old'
                   can  be implied except through knowledge of the
                   routing  protocol  by  which  the   route   was
                   learned."
            ::= { ipMultiPathEntry 9 }
-- Unnumbered IP Interface Group {accBRG 40}
        accUnNumIP      OBJECT IDENTIFIER ::= { accBRG 40 }
        accIpNetSrcAddrTable OBJECT-TYPE
                SYNTAX SEQUENCE OF AccIpNetSrcAddrEntry
                ACCESS not-accessible
                STATUS mandatory
                DESCRIPTION
                        " Unnumbered IP Interface Table. "
                ::= { accUnNumIP 1 }
        accIpNetSrcAddrEntry OBJECT-TYPE
                SYNTAX AccIpNetSrcAddrEntry
                ACCESS not-accessible
                STATUS mandatory
                DESCRIPTION
                        " An entry in the Unnumbered IP Interface Table. "
                INDEX { IpAddress }
                ::= { accIpNetSrcAddrTable 1 }
        AccIpNetSrcAddrEntry ::= SEQUENCE {
                accIpNetSrcIfIndex      INTEGER,
                accIpNetSrcAddress      IpAddress
                }
        accIpNetSrcIfIndex OBJECT-TYPE
                SYNTAX INTEGER
                ACCESS read-write
                STATUS mandatory
                DESCRIPTION
                        " The ifIndex of the unnumbered interface. "
                ::= { accIpNetSrcAddrEntry 1 }
        accIpNetSrcAddress OBJECT-TYPE
                SYNTAX IpAddress
                ACCESS read-write
                STATUS mandatory
                DESCRIPTION
                        " The IP Address this system will use as a source
                        address on this unnumbered interface.  By default,
                        it is the smallest IP Address configured for the
                        router. "
                ::= { accIpNetSrcAddrEntry 2 }
-- Token Ring Group
      accTr         OBJECT IDENTIFIER ::= { accBRG 24 }
	accTrNumber OBJECT-TYPE
			SYNTAX INTEGER
			ACCESS read-only
			STATUS mandatory
			DESCRIPTION
			 " Number of token-ring interfaces"
			::= { accTr 1 }
	accTrTable OBJECT-TYPE
			SYNTAX SEQUENCE OF AccTrEntry
			ACCESS not-accessible
			STATUS mandatory
			DESCRIPTION
                         " Token Ring table"
			::= { accTr 2 }
		AccTrEntry ::= SEQUENCE {
			accTrEarlyRelease	INTEGER,
			accTrMACAddr		OCTET STRING,
			accTrDefaultRingId	INTEGER,
			accTrActiveRingId	INTEGER,
			accTrRingSrvStatus	INTEGER
			}
	accTrEntry   OBJECT-TYPE
		SYNTAX AccTrEntry
		ACCESS not-accessible
		STATUS mandatory
		DESCRIPTION
		      " Additional information about Token Ring
		        interfaces."
		INDEX { ifIndex }
		::= { accTrTable 1 }
		accTrEarlyRelease  OBJECT-TYPE
			SYNTAX INTEGER {
				on(1),
				off(2)
			    }
			ACCESS read-write
			STATUS mandatory
			DESCRIPTION
				 " If on, the device will pass the token
				   immediately after transmitting a frame,
				   rather than awaiting the message to transit
				   the ring."
                        DEFVAL { on }
			::= { accTrEntry 2 }
		accTrMACAddr  OBJECT-TYPE
			SYNTAX OCTET STRING
			ACCESS read-write
			STATUS mandatory
			DESCRIPTION
				 " Locally-administered MAC address of this
				   interface.  If zero, an algorithmically
				   determined address is used."
			::= { accTrEntry 3 }
		accTrDefaultRingId  OBJECT-TYPE
			SYNTAX INTEGER
			ACCESS read-write
			STATUS mandatory
			DESCRIPTION
				 " Ring ID that interface will use if one is
				   not provided by a ring server."
			::= { accTrEntry 4 }
		accTrActiveRingId  OBJECT-TYPE
			SYNTAX INTEGER
			ACCESS read-only
			STATUS mandatory
			DESCRIPTION
				 " ID of ring that this interface
				   participates on"
			::= { accTrEntry 5 }
		accTrRingSrvStatus  OBJECT-TYPE
			SYNTAX INTEGER {
				found(1),
				not-found(2)
				}
			ACCESS read-only
			STATUS mandatory
			DESCRIPTION
				 " Indicates if a ring server was
				   found."
			::= { accTrEntry 6 }
-- Source-Routing Bridge Group
      accSr         OBJECT IDENTIFIER ::= { accBRG 25 }
	accSrBridge	OBJECT IDENTIFIER ::= { accSr 1 }
	  accSrBridgeId	OBJECT-TYPE   
		SYNTAX	INTEGER
		ACCESS	read-write
		STATUS	mandatory
		DESCRIPTION
				 " ID of this bridge"
		::= { accSrBridge 1 }
	 accSrVirRingId  OBJECT-TYPE
		SYNTAX INTEGER
		ACCESS read-write
		STATUS mandatory
		DESCRIPTION
			 " Ring number used by bridges on a WAN"
		::= { accSrBridge 2 }
	accSrHopLimit  OBJECT-TYPE
		SYNTAX INTEGER
		ACCESS read-write
		STATUS mandatory
		DESCRIPTION
			 " This bridge will discard a broadcast packet
			   which has transited this many bridges
			   en route."
		::= { accSrBridge 3 }
	accSrSingleRtBcast  OBJECT-TYPE
		SYNTAX INTEGER {
			on(1),
			off(2)
			}
		ACCESS read-write
		STATUS mandatory
		DESCRIPTION
			 " If off, this bridge will not forward
			   single-route broadcast packets."
		::= { accSrBridge 4 }
        accSrNumPorts   OBJECT-TYPE
                        SYNTAX  INTEGER (2..16)
                        ACCESS  read-write
                        STATUS  mandatory
                        DESCRIPTION
                 " Number of physical ports of unit."
                        ::= { accSrBridge 5 }
        accSrRifTimer   OBJECT-TYPE
                        SYNTAX  INTEGER
                        ACCESS  read-write
                        STATUS  mandatory
                        DESCRIPTION
                 " "
                        ::= { accSrBridge 6 }
        accSrSdsInterval   OBJECT-TYPE
                        SYNTAX  TimeTicks
                        ACCESS  read-write
                        STATUS  mandatory
                        DESCRIPTION
                 " Interval between transmissions of 
                   SDS protocol packets "
                        ::= { accSrBridge 7 }
	accSrPortParmTable   OBJECT-TYPE
		SYNTAX SEQUENCE OF AccSrPortParmEntry
		ACCESS not-accessible
		STATUS mandatory
		DESCRIPTION
			 " This table contains per-port parameters
			   for source-routed bridge ports."
		::= { accSr 2 }
	accSrPortParmEntry  OBJECT-TYPE
		SYNTAX AccSrPortParmEntry
		ACCESS not-accessible
		STATUS mandatory
		DESCRIPTION
			 " Parameters for this bridge port"
                INDEX { accSrParmsIndex }
		::= { accSrPortParmTable 1 }
		AccSrPortParmEntry ::= SEQUENCE {
			accSrParmsIndex		INTEGER,
			accSrAdminStatus	INTEGER,
			accSrOperStatus		INTEGER,
                        accSrPortProtocol       INTEGER,
                        accSrPortLine		INTEGER,
                        accSrPortFrDlci		INTEGER,
            		accSrPortXBridgeStatus  INTEGER,
                        accSrPortVirRingId      INTEGER,
                        accSrPortSrMethod       INTEGER
			}
		accSrParmsIndex  OBJECT-TYPE
			SYNTAX INTEGER
			ACCESS read-only
			STATUS mandatory
			DESCRIPTION
				 " Bridge port number"
			::= { accSrPortParmEntry 1 }
		accSrAdminStatus  OBJECT-TYPE
			SYNTAX INTEGER {
				enabled(1),
				disabled(2)
				}
			ACCESS read-write
			STATUS mandatory
			DESCRIPTION
				 " Administrative status of this 
				   bridge port.  If down, source-routing
				   bridging will not occur."
			::= { accSrPortParmEntry 2 }
		accSrOperStatus  OBJECT-TYPE
			SYNTAX INTEGER {
				forwarding(1),
				disabled(2)
				}
			ACCESS read-only
			STATUS mandatory
			DESCRIPTION
				 " Operational (is) status of this
				   bridge port."
			::= { accSrPortParmEntry 3 }
          accSrPortProtocol     OBJECT-TYPE
                        SYNTAX  INTEGER {
                                enet(1),
                                x25(2),
                                lapb(3),
                                ffr(4),
				other(5),
				token-ring(6),
				smds(7),
				ppp(8),
				fddi(9),
				dial(10),
				multilink(11)
                                }
                        ACCESS  read-write
                        STATUS  mandatory
                        DESCRIPTION
                         " Protocol"
                        ::= { accSrPortParmEntry 4 }
          accSrPortLine OBJECT-TYPE
                        SYNTAX  INTEGER
                        ACCESS  read-write
                        STATUS  mandatory
                        DESCRIPTION
                         " Index of physical port associated with this 
                           Source-Routing port."
                        ::= { accSrPortParmEntry 5 }
          accSrPortFrDlci       OBJECT-TYPE
                        SYNTAX  INTEGER
                        ACCESS  read-write
                        STATUS  mandatory
                        DESCRIPTION
                          " Frame Relay DLCI for this port"
                        ::= { accSrPortParmEntry 6 }
          accSrPortXBridgeStatus	OBJECT-TYPE
                        SYNTAX	INTEGER {
                            enabled(1),
                            disabled(2)
                        }
                        ACCESS	read-write
                        STATUS	mandatory
                        DESCRIPTION
                        " Translation bridge status for this port."
                        ::= { accSrPortParmEntry 7 }
        accSrPortVirRingId      OBJECT-TYPE
                        SYNTAX  INTEGER
                        ACCESS  read-write
                        STATUS  mandatory
                        DESCRIPTION
                                " Port Virtual Ring Id"
                        ::= { accSrPortParmEntry 8 }
        accSrPortSrMethod       OBJECT-TYPE
                        SYNTAX  INTEGER {
                                sr1(1),
                                sr2(2)
                                }
                        ACCESS  read-write
                        STATUS  mandatory
                        DESCRIPTION
                                " Port Source Routing Method"
                        ::= { accSrPortParmEntry 9 }
	accSrPortStatsTable  OBJECT-TYPE
		SYNTAX SEQUENCE OF AccSrPortStatsEntry
		ACCESS not-accessible
		STATUS mandatory
		DESCRIPTION
				 " Statistical information on bridge
				   ports."
		::= { accSr 3 }
	accSrPortStatsEntry  OBJECT-TYPE
		SYNTAX AccSrPortStatsEntry
		ACCESS not-accessible
		STATUS mandatory
		DESCRIPTION
			 " Statistics for a single bridge port"
                INDEX { accStatsIndex }
		::= { accSrPortStatsTable 1 }
		AccSrPortStatsEntry ::= SEQUENCE {
			accStatsIndex		INTEGER,
			accInBcastPkts		Counter,
			accInUcastPkts		Counter,
			accOutBcastPkts		Counter,
			accOutUcastPkts		Counter,
			accInSDSPkts		Counter,
			accInAPEPkts		Counter,
			accOutSDSPkts		Counter,
			accOutAPEPkts		Counter,
			accInDiscPkts		Counter,
			accOutDelayDiscPkts	Counter,
			accOutPrioDiscPkts	Counter,
			accInMcastPkts		Counter,
			accOutMcastPkts		Counter
			}
		accStatsIndex  OBJECT-TYPE
			SYNTAX INTEGER
			ACCESS read-only
			STATUS mandatory
			DESCRIPTION
				 " Bridge port number"
			::= { accSrPortStatsEntry 1 }
		accInBcastPkts  OBJECT-TYPE
			SYNTAX Counter
			ACCESS read-only
			STATUS mandatory
			DESCRIPTION
				 " All-stations broadcast packets received"
			::= { accSrPortStatsEntry 2 }
		accInUcastPkts  OBJECT-TYPE
			SYNTAX Counter
			ACCESS read-only
			STATUS mandatory
			DESCRIPTION
				 " Unicast packets received"
			::= { accSrPortStatsEntry 3 }
		accOutBcastPkts  OBJECT-TYPE
			SYNTAX Counter
			ACCESS read-only
			STATUS mandatory
			DESCRIPTION
				 "  All-stations broadcast packets transmitted"
			::= { accSrPortStatsEntry 4 }
		accOutUcastPkts  OBJECT-TYPE
			SYNTAX Counter
			ACCESS read-only
			STATUS mandatory
			DESCRIPTION
				 "  Non-unicast packets received"
			::= { accSrPortStatsEntry 5 }
		accInSDSPkts  OBJECT-TYPE
			SYNTAX Counter
			ACCESS read-only
			STATUS mandatory
			DESCRIPTION
				 " Serial Discovery Sequence packets
				   received.  These packets are a component
				   of a proprietary ACC protocol used when
				   a serial link is established between a
				   pair of ACC units."
			::= { accSrPortStatsEntry 6 }
		accInAPEPkts  OBJECT-TYPE
			SYNTAX Counter
			ACCESS read-only
			STATUS mandatory
			DESCRIPTION
				 " All-path explorer packets received"
			::= { accSrPortStatsEntry 7 }
		accOutSDSPkts  OBJECT-TYPE
			SYNTAX Counter
			ACCESS read-only
			STATUS mandatory
			DESCRIPTION
			 " Serial Discovery Sequence packets transmitted."
			::= { accSrPortStatsEntry 8 }
		accOutAPEPkts  OBJECT-TYPE
			SYNTAX Counter
			ACCESS read-only
			STATUS mandatory
			DESCRIPTION
				 " All-Path Explorer Packets transmitted"
			::= { accSrPortStatsEntry 9 }
		accInDiscPkts  OBJECT-TYPE
			SYNTAX Counter
			ACCESS read-only
			STATUS mandatory
			DESCRIPTION
				 " Packets discarded due to address
				   filtering."
			::= { accSrPortStatsEntry 10 }
		accOutDelayDiscPkts  OBJECT-TYPE
			SYNTAX Counter
			ACCESS read-only
			STATUS mandatory
			DESCRIPTION
				 " Packets discarded because they were too
				   long on the output queue."
			::= { accSrPortStatsEntry 11 }
		accOutPrioDiscPkts  OBJECT-TYPE
			SYNTAX Counter
			ACCESS read-only
			STATUS mandatory
			DESCRIPTION
				 " Packets discarded due to protocol
				   prioritization."
			::= { accSrPortStatsEntry 12 }
		accInMcastPkts	  OBJECT-TYPE
			SYNTAX Counter
			ACCESS read-only
			STATUS mandatory
			DESCRIPTION
				 " Multicast packets received."
			::= { accSrPortStatsEntry 13 }
		accOutMcastPkts	  OBJECT-TYPE
			SYNTAX Counter
			ACCESS read-only
			STATUS mandatory
			DESCRIPTION
				 " Multicast packets transmitted."
			::= { accSrPortStatsEntry 14 }
	accSrRouteTable   OBJECT-TYPE
		SYNTAX SEQUENCE OF AccSrRouteEntry
		ACCESS not-accessible
		STATUS mandatory
		DESCRIPTION
			 " Table of source-routing routes"
		::= { accSr 4 }
	accSrRouteEntry  OBJECT-TYPE
		SYNTAX AccSrRouteEntry
		ACCESS not-accessible
		STATUS mandatory
		DESCRIPTION
			 " Information on a specific route"
                INDEX { accSrRtDest }
		::= { accSrRouteTable 1 }
		AccSrRouteEntry ::= SEQUENCE {
			accSrRtDest	OCTET STRING,
			accSrRtControl	INTEGER,
			accSrRtDesc	OCTET STRING,
			accSrRtIfIndex	INTEGER
			}
		accSrRtDest  OBJECT-TYPE
			SYNTAX OCTET STRING   -- (SIZE (6))
			ACCESS read-only
			STATUS mandatory
			DESCRIPTION
				 " Destination for which route is intended"
			::= { accSrRouteEntry 1 }
		accSrRtControl  OBJECT-TYPE
			SYNTAX INTEGER
			ACCESS read-only
			STATUS mandatory
			DESCRIPTION
				 " Control bytes in routing field"
			::= { accSrRouteEntry 2 }
		accSrRtDesc  OBJECT-TYPE
			SYNTAX OCTET STRING
			ACCESS read-only
			STATUS mandatory
			DESCRIPTION
				 " Route description; sequence of
				   bridge and ring ID's."
			::= { accSrRouteEntry 3 }
		accSrRtIfIndex  OBJECT-TYPE
			SYNTAX INTEGER
			ACCESS read-only
			STATUS mandatory
			DESCRIPTION
				 " "
			::= { accSrRouteEntry 4 }
	accSrFilterTable   OBJECT-TYPE
		SYNTAX SEQUENCE OF AccSrFilterEntry
		ACCESS not-accessible
		STATUS deprecated
		DESCRIPTION
				 " Table of filters to permit forwarding
				   or dropping of frames on per-station-pair
				   basis 
				   Records can be deleted by setting either
				   the source or destination to the NULL
				   type for the instance of interest."
		::= { accSr 5 }
	accSrFilterEntry  OBJECT-TYPE
		SYNTAX AccSrFilterEntry
		ACCESS not-accessible
		STATUS deprecated
		DESCRIPTION
				 " A specific filter"
                INDEX { accSrFilterDest,
                        accSrFilterSrc }
		::= { accSrFilterTable 1 }
		AccSrFilterEntry ::= SEQUENCE {
			accSrFilterDest		OCTET STRING,
			accSrFilterSrc		OCTET STRING,
			accSrFilterAction	INTEGER
			}
		accSrFilterDest  OBJECT-TYPE
			SYNTAX OCTET STRING   -- (SIZE (6))
			ACCESS read-write
			STATUS deprecated
			DESCRIPTION
				 " Destination MAC address of packet to
				   be filtered. Zero address matches all."
			::= { accSrFilterEntry 1 }
		accSrFilterSrc  OBJECT-TYPE
			SYNTAX OCTET STRING   -- (SIZE (6))
			ACCESS read-write
			STATUS deprecated
			DESCRIPTION
				 " Source MAC address of packet to be filtered
				   Zero address matches all."
			::= { accSrFilterEntry 2 }
		accSrFilterAction OBJECT-TYPE
			SYNTAX	INTEGER (0..1)
			ACCESS read-write
			STATUS deprecated
			DESCRIPTION
				 " Action to take packets satisfying filter
				   criteria.
				forward(0),
				discard(1)
				"
			::= { accSrFilterEntry 3 }
	accSrFpTable	OBJECT-TYPE
			SYNTAX SEQUENCE OF AccSrFpEntry
			ACCESS not-accessible
			STATUS mandatory
			DESCRIPTION
                 " A list of Forwarding Priority Entries.
		   Entries are added/deleted via management action."
			::= { accSr 6 }
	  accSrFpEntry	OBJECT-TYPE
			SYNTAX  AccSrFpEntry
			ACCESS not-accessible
			STATUS mandatory
			DESCRIPTION
                   " Relative Priority between frames to be forwarded
                     on a Bridge Port."
                        INDEX { accSrFpIndex }
			::= { accSrFpTable 1 }
             AccSrFpEntry ::= SEQUENCE {
	    	accSrFpIndex 	INTEGER,
	    	accSrFpProt	INTEGER,
	    	accSrFpPrio	INTEGER
		}
	    accSrFpIndex OBJECT-TYPE   
			SYNTAX	INTEGER 
			ACCESS	read-write
			STATUS	mandatory
			DESCRIPTION
			 " Port number"
			::= { accSrFpEntry 1 }
	    accSrFpProt OBJECT-TYPE   
			SYNTAX	INTEGER (0..65535)
			ACCESS	read-write
			STATUS	mandatory
			DESCRIPTION
			 " protocol type
			   Set this object to NULL to delete the entry."
			::= { accSrFpEntry 2 }
	    accSrFpPrio OBJECT-TYPE  
			SYNTAX	INTEGER (0..3)
			ACCESS	read-write
			STATUS	mandatory
			DESCRIPTION
                  " Relative forwarding priority assigned to protocol.
			discard(0),
			low(1),
			normal(2),
			high(3)
		"
			::= { accSrFpEntry 3 }
        accSrFpDefaults         OBJECT IDENTIFIER ::= { accSr 7 }
	accSrFpPriDefault	OBJECT-TYPE  
			SYNTAX	INTEGER (0..3)
			ACCESS	read-write
			STATUS	mandatory
			DESCRIPTION
                	"
			discard(0),
			low(1),
			normal(2),
			high(3)
			"
			::= { accSrFpDefaults 1 }
	accSrPortFRTable OBJECT-TYPE
		SYNTAX SEQUENCE OF AccSrPortFREntry
		ACCESS not-accessible
		STATUS mandatory
		DESCRIPTION
			 " "
		::= { accSr 9 }
	accSrPortFREntry  OBJECT-TYPE
		SYNTAX AccSrPortFREntry
		ACCESS not-accessible
		STATUS mandatory
		DESCRIPTION
			 " "
                INDEX { accSrPortFRport }
		::= { accSrPortFRTable 1 }
		AccSrPortFREntry ::= SEQUENCE {
			accSrPortFRport		INTEGER,
			accSrPortFRdlci		INTEGER,
                        accSrPortFRencap        INTEGER
			}
		accSrPortFRport  OBJECT-TYPE
			SYNTAX INTEGER
			ACCESS read-only
			STATUS mandatory
			DESCRIPTION
				 " "
			::= { accSrPortFREntry 1 }
		accSrPortFRdlci  OBJECT-TYPE
			SYNTAX INTEGER
			ACCESS read-write
			STATUS mandatory
			DESCRIPTION
				 " "
			::= { accSrPortFREntry 2 }
                accSrPortFRencap        OBJECT-TYPE
                        SYNTAX  INTEGER {
                                en1(1),
                                en2(2)
                                }
                        ACCESS  read-write
                        STATUS  mandatory
                        DESCRIPTION
                                " Frame Relay Encapsulation Method"
                        ::= { accSrPortFREntry 3 }
	accSrPortX25Table OBJECT-TYPE
		SYNTAX SEQUENCE OF AccSrPortX25Entry
		ACCESS not-accessible
		STATUS mandatory
		DESCRIPTION
			 " "
		::= { accSr 10 }
	accSrPortX25Entry  OBJECT-TYPE
		SYNTAX AccSrPortX25Entry
		ACCESS not-accessible
		STATUS mandatory
		DESCRIPTION
			 " "
                INDEX { accSrPortX25port }
		::= { accSrPortX25Table 1 }
		AccSrPortX25Entry ::= SEQUENCE {
			accSrPortX25port	INTEGER,
			accSrPortX25addr1	INTEGER,
			accSrPortX25addr2	INTEGER,
			accSrPortX25idleTime	INTEGER,
			accSrPortX25pktNegot	INTEGER,
			accSrPortX25windowNegot	INTEGER,
			accSrPortX25FacIndex	INTEGER
			}
		accSrPortX25port  OBJECT-TYPE
			SYNTAX INTEGER
			ACCESS read-only
			STATUS mandatory
			DESCRIPTION
				 " "
			::= { accSrPortX25Entry 1 }
		accSrPortX25addr1  OBJECT-TYPE
			SYNTAX INTEGER
			ACCESS read-write
			STATUS mandatory
			DESCRIPTION
				 " "
			::= { accSrPortX25Entry 2 }
		accSrPortX25addr2  OBJECT-TYPE
			SYNTAX INTEGER
			ACCESS read-write
			STATUS mandatory
			DESCRIPTION
				 " "
			::= { accSrPortX25Entry 3 }
		accSrPortX25idleTime  OBJECT-TYPE
			SYNTAX INTEGER
			ACCESS read-write
			STATUS mandatory
			DESCRIPTION
				 " "
			::= { accSrPortX25Entry 4 }
		accSrPortX25pktNegot  OBJECT-TYPE
			SYNTAX INTEGER
			ACCESS read-write
			STATUS mandatory
			DESCRIPTION
				 " "
			::= { accSrPortX25Entry 5 }
		accSrPortX25windowNegot  OBJECT-TYPE
			SYNTAX INTEGER
			ACCESS read-write
			STATUS mandatory
			DESCRIPTION
				 " "
			::= { accSrPortX25Entry 6 }
	accSrPortX25FacIndex OBJECT-TYPE
	               SYNTAX  INTEGER (0..255)
	               ACCESS  read-write
	               STATUS  mandatory
	               DESCRIPTION
	                " Index of optional facility string or zero."
	                 DEFVAL { 0 }
	               ::= { accSrPortX25Entry 7 }
-- SR Spanning Tree Protocol Group
    accSrStp   OBJECT IDENTIFIER ::= { accSr 11 }
	accSrStpBridge     OBJECT IDENTIFIER ::= { accSrStp 1 }
	accSrStpPriority	OBJECT-TYPE   
			SYNTAX	INTEGER (0..255)
			ACCESS	read-write
			STATUS	mandatory
			DESCRIPTION
                " Among all devices participating in the sr spanning tree, the
                   one with the highest priority (numerically lowest
                   value of this parameter) is elected as the Root
                   of the spanning tree."
			::= { accSrStpBridge 1 } 
	accSrStpId	OBJECT-TYPE   
			SYNTAX	OCTET STRING
			ACCESS	read-only
			STATUS	mandatory
			DESCRIPTION
                " Unique bridge identifier of this bridge.  This object
                   comprises two parts, one of which is the MAC address,
                   and the other of which is the SrStpPriority and is the
                   more significant part in priority comparisons."
			::= { accSrStpBridge 2 } 
	accSrStpBrAddr	OBJECT-TYPE   
			SYNTAX	OCTET STRING
			ACCESS	read-only
			STATUS	mandatory
			DESCRIPTION
             " MAC address of preferred port for this bridge."
			::= { accSrStpBridge 3 }    
	accSrStpMode	OBJECT-TYPE   
			SYNTAX	INTEGER {
				ieee(1),
				manual(2),
				blue(3)
				}
			ACCESS	read-write
			STATUS	mandatory
			DESCRIPTION
                " Style of this Bridge's participation in Spanning Tree.
                   Ieee follows 802.1d recommendations, manual is a static
		   assignment (no bpdus are sent, received bpdus are ignore),
		   blue is nearly ieee, with some minor exceptions for
		   interoperability with certain SR bridges."
			::= { accSrStpBridge 4 } 
	accSrStpFilterTime	OBJECT-TYPE   
			SYNTAX	TimeTicks
			ACCESS	read-only
			STATUS	mandatory
			DESCRIPTION
                 " Minimum time period elapsing between the
                   transmission of Hello frames through a given Bridge Port.
                   No more than two Hello frames shall be transmitted in any
                   SrStpFilterTime period."
			::= { accSrStpBridge 5 }
	accSrStpMcastAddr		OBJECT-TYPE   
			SYNTAX	OCTET STRING
			ACCESS	read-write
			STATUS	mandatory
			DESCRIPTION
                 " A unique MAC group address, recognised by all the Bridges
                   within the Bridged Local Area Network."
			::= { accSrStpBridge 6 } 
	accSrStpTopChangeDet	OBJECT-TYPE   
			SYNTAX	INTEGER 
			--	{
			--	no(0),
			--	yes(1)
			--	}
			ACCESS	read-only
			STATUS	mandatory
			DESCRIPTION
                " Indicates if this unit has detected the Topology
                  change indication in the hello BPDU."
			::= { accSrStpBridge 7 } 
	accSrStpTopChange		OBJECT-TYPE   
			SYNTAX	INTEGER 
			--	{
			--	no(0),
			--	yes(1)
			--	}
			ACCESS	read-only
			STATUS	mandatory
			DESCRIPTION
                " Indicates if the STP topology of a network is in
                   process of changing."
			::= { accSrStpBridge 8 } 
	accSrStpTopChangeTimer	OBJECT-TYPE   
			SYNTAX	TimeTicks
			ACCESS	read-only
			STATUS	mandatory
			DESCRIPTION
                 " This timer serves to determine the time period for
                    which hello frames are transmitted with the
                   Topology Change flag parameter set by the Bridge when
                   it is the Root following the detection of a topology
                   change."
			::= { accSrStpBridge 9 }
	accSrStpDesRoot	OBJECT-TYPE   
			SYNTAX	OCTET STRING
			ACCESS	read-only
			STATUS	mandatory
			DESCRIPTION
               "  The Bridge Identifier  of the device currently
                   assumed by this unit to be the Root."
			::= { accSrStpBridge 10 } 
	accSrStpRootPathCost	OBJECT-TYPE   
			SYNTAX	INTEGER
			ACCESS	read-only
			STATUS	mandatory
			DESCRIPTION
                " Current path cost to the Root Bridge."
			::= { accSrStpBridge 11 }
	accSrStpRootPort	OBJECT-TYPE   
			SYNTAX	OCTET STRING
			ACCESS	read-only
			STATUS	mandatory
			DESCRIPTION
               " Port Number of the one Port in the direction of the Root.
                  (Value is meaningless if this unit is the Root)."
			::= { accSrStpBridge 12 } 
	accSrStpMaxAge	OBJECT-TYPE   
			SYNTAX	INTEGER (4..3600)
			ACCESS	read-write
			STATUS	mandatory
			DESCRIPTION
                 " The value of the Max Age parameter when the Bridge is the
                  Root or attempting to become the Root.
                  The Max Age parameter is conveyed to ensure that each Bridge
                  in a Bridged Local Area Network has a consistent value
                  against which to test the age of stored protocol information."
			::= { accSrStpBridge 13 }
	accSrStpHelloTime		OBJECT-TYPE   
			SYNTAX	INTEGER (2..1800)
			ACCESS	read-write
			STATUS	mandatory
			DESCRIPTION
                 " Interval between Hello frames that this
                  Bridge will initiate when it is Root or is attempting
                  to be Root."
			::= { accSrStpBridge 14 }
	accSrStpForwardDelay	OBJECT-TYPE   
			SYNTAX	INTEGER (5..3600)
			ACCESS	read-write
			STATUS	mandatory
			DESCRIPTION
                 " The time  (seconds) spent in the Listening state while
                   moving from the Blocking state to the Learning state.
                   The time  (seconds) spent in the Learning state while
                   moving from the Listening state to the Forwarding state.
                   The value  (seconds) used for the ageing time of dynamic 
                   entries in the Forwarding Database table wile the Topology
                   Change flag is set in protocol messages received from
                   the Root.  This object only has an effect if SRT
		   bridging is enabled"
			::= { accSrStpBridge 15 }
	accSrStpUpTime	OBJECT-TYPE   
			SYNTAX	TimeTicks
			ACCESS	read-only
			STATUS	mandatory
			DESCRIPTION
                 " "
			::= { accSrStpBridge 16 }
	accSrStpTopChangeCnts	OBJECT-TYPE   
			SYNTAX	Counter
			ACCESS	read-only
			STATUS	mandatory
			DESCRIPTION
                   " "
			::= { accSrStpBridge 17 }
-- NEEDS REVIEW 
	accSrStpPortParms     OBJECT IDENTIFIER ::= { accSrStp 2 }
	  accSrStpPortState	OBJECT-TYPE   
			SYNTAX	INTEGER 
			--	{
				--disabled(0),
				--blocking(1),
				--listening(2),
				--learning(3),
				--forwarding(4)
				--}
			ACCESS	read-only
			STATUS	mandatory
			DESCRIPTION
			 " accSrStpPortState reports the operational status
			   of the port.  The learning state will only be
			   reported if SRT bridging is enabled"
			::= { accSrStpPortParms 1 }
	  accSrStpPortPathCost	OBJECT-TYPE   
			SYNTAX	INTEGER (0..65535)
			ACCESS	read-write
			STATUS	mandatory
			DESCRIPTION
                         " Path cost"
			::= { accSrStpPortParms 2 }
	  accSrStpPortDesRoot	OBJECT-TYPE   
			SYNTAX	OCTET STRING
			ACCESS	read-only
			STATUS	mandatory
			DESCRIPTION
                         " Designated root"
			::= { accSrStpPortParms 3 }
	  accSrStpPortDesCost	OBJECT-TYPE   
			SYNTAX	INTEGER (0..65535)
			ACCESS	read-only
			STATUS	mandatory
			DESCRIPTION
                         " Cost to designated root"
			::= { accSrStpPortParms 4 }
	  accSrStpPortDesBridge		OBJECT-TYPE   
			SYNTAX	OCTET STRING
			ACCESS	read-only
			STATUS	mandatory
			DESCRIPTION
                         " Designated bridge"
			::= { accSrStpPortParms 5 }
	  accSrStpPortDesPort	OBJECT-TYPE   
			SYNTAX	OCTET STRING
			ACCESS	read-only
			STATUS	mandatory
			DESCRIPTION
                         " Designated port"
			::= { accSrStpPortParms 6 }
	  accSrStpPortPriority	OBJECT-TYPE   
			SYNTAX	INTEGER (0..255)
			ACCESS	read-write
			STATUS	mandatory
			DESCRIPTION
                         " Relative STP priority of this port"
			::= { accSrStpPortParms 7 }
	    accSrStpPortInPkts	OBJECT-TYPE   
			SYNTAX	Counter
			ACCESS	read-only
			STATUS	mandatory
			DESCRIPTION
                         " Number of spanning tree packets recieved"
			::= { accSrStpPortParms 8 }
	    accSrStpPortOutPkts		OBJECT-TYPE   
			SYNTAX	Counter
			ACCESS	read-only
			STATUS	mandatory
			DESCRIPTION
                         " Number of spanning tree packets sent"
			::= { accSrStpPortParms 9 }
	  accSrStpPortAdmin OBJECT-TYPE   
			SYNTAX	INTEGER {
				enabled(1),
				disabled(2)
				}
			ACCESS	read-write
			STATUS	mandatory
			DESCRIPTION
			 " accSrStpPortAdminStatus reports the administrative
			   status of the STP port; an update to this variable
			   requires a reset.  
			   When the STP mode is manual, the 
			   accSrStpPortAdminStatus determines whether the port
			   is part of the active spanning tree or not."
			::= { accSrStpPortParms 10 }
        accSrRingTable OBJECT-TYPE
                SYNTAX SEQUENCE OF AccSrRingEntry
                ACCESS not-accessible
                STATUS mandatory
                DESCRIPTION
                         " "
                ::= { accSr 12 }
        accSrRingEntry  OBJECT-TYPE
                SYNTAX AccSrRingEntry
                ACCESS not-accessible
                STATUS mandatory
                DESCRIPTION
                         " "
                INDEX { accSrRingTblRingID,
                        accSrRingTblBridgeID}
                ::= { accSrRingTable 1 }
                AccSrRingEntry ::= SEQUENCE {
                        accSrRingTblRingID      INTEGER,
                        accSrRingTblBridgeID    INTEGER,
                        accSrRingTblPortIndex   INTEGER,
                        accSrRingTblMetric      INTEGER,
                        accSrRingTblAge         INTEGER,
                        accSrRingTblNbrMacAddr  OCTET STRING
                        }
               accSrRingTblRingID OBJECT-TYPE
                        SYNTAX INTEGER (0..4095)
                        ACCESS read-only
                        STATUS mandatory
                        DESCRIPTION
                                " The ring number of a Token Ring
                                  reachable across the Virtual Ring."
                        ::= { accSrRingEntry 1 }
                accSrRingTblBridgeID OBJECT-TYPE
                        SYNTAX INTEGER (0..15)
                        ACCESS read-write
                        STATUS mandatory
                        DESCRIPTION
                                " The bridge ID used to reach a Token
                                  Ring across the Virtual Ring."
                        ::= { accSrRingEntry 2 }
                accSrRingTblPortIndex OBJECT-TYPE
                        SYNTAX INTEGER
                        ACCESS read-write
                        STATUS mandatory
                        DESCRIPTION
                                 " The SR bridge port used to forward
                                   packets on the Virtual Ring."
                        ::= { accSrRingEntry 3 }
                accSrRingTblMetric OBJECT-TYPE
                        SYNTAX INTEGER
                        ACCESS read-write
                        STATUS mandatory
                        DESCRIPTION
                                 " The number of hops to reach a Token Ring
                                   across the Virtual Ring."
                        ::= { accSrRingEntry 4 }
                accSrRingTblAge OBJECT-TYPE
                        SYNTAX INTEGER
                        ACCESS read-write
                        STATUS mandatory
                        DESCRIPTION
                                " The age, in seconds of this ring information."
                        ::= { accSrRingEntry 5 }
                accSrRingTblNbrMacAddr OBJECT-TYPE
                        SYNTAX OCTET STRING  -- (SIZE (6))
                        ACCESS read-write
                        STATUS mandatory
                        DESCRIPTION
                                 " The MAC address of the neighbor on the
                                   Virtual Ring used to reach a remote Token
                                   Ring.  (currently only used for Ethernets)"
                        ::= { accSrRingEntry 6 }
-- Extensions to the original SR  filter group
	accSrFiltIITable	OBJECT-TYPE
			SYNTAX SEQUENCE OF AccSrFiltIIEntry
			ACCESS not-accessible
			STATUS mandatory
			DESCRIPTION
                 " A list of Filtering entries."
			 ::= { accSr 13 }
	  accSrFiltIIEntry OBJECT-TYPE
			SYNTAX AccSrFiltIIEntry
			ACCESS not-accessible
			STATUS mandatory
			DESCRIPTION
                " A Filtering entry which defines the SR action
                  to be taken based upon the destination AND source
		  MAC Addresses AFTER applying the address masks,
                  port number, port protocol and logic op of received frames."
                        INDEX {	accSrFiltIIEntDstMacAddr,
				accSrFiltIIEntDstMacAddrMask,
				accSrFiltIIEntSrcMacAddr,
				accSrFiltIIEntSrcMacAddrMask,
				accSrFiltIIEntPort,
				accSrFiltIIEntLogicalOp,
				accSrFiltIIEntProtocol}
			::= { accSrFiltIITable 1 }
	  AccSrFiltIIEntry  ::= SEQUENCE {
	    	accSrFiltIIEntDstMacAddr	OCTET STRING,
	    	accSrFiltIIEntDstMacAddrMask	OCTET STRING,
	    	accSrFiltIIEntSrcMacAddr	OCTET STRING,
	    	accSrFiltIIEntSrcMacAddrMask	OCTET STRING,
	    	accSrFiltIIEntPort		INTEGER,
	    	accSrFiltIIEntLogicalOp		INTEGER,
	    	accSrFiltIIEntProtocol		OCTET STRING,
	    	accSrFiltIIEntDisp		INTEGER
		}
	    accSrFiltIIEntDstMacAddr	OBJECT-TYPE   
			SYNTAX	OCTET STRING (SIZE(6))
			ACCESS	read-write
			STATUS	mandatory
			DESCRIPTION
                " Destination MAC Address of the Filtering entry."
			::= { accSrFiltIIEntry 1 }
	    accSrFiltIIEntSrcMacAddr	OBJECT-TYPE   
			SYNTAX	OCTET STRING (SIZE(6))
			ACCESS	read-write
			STATUS	mandatory
			DESCRIPTION
                " Source MAC Address of the Filtering entry."
			::= { accSrFiltIIEntry 2 }
	    accSrFiltIIEntDisp	OBJECT-TYPE   
			SYNTAX	INTEGER {
				forward	(1),
				discard	(2)
				}
			ACCESS	read-write
			STATUS	mandatory
			DESCRIPTION
                 " Disposition of received Frame. Note that a Frame is
                   never sent back out on the Port on which it was received."
			::= { accSrFiltIIEntry 3 }
	    accSrFiltIIEntPort	OBJECT-TYPE   
			SYNTAX	INTEGER
			ACCESS	read-write
			STATUS	mandatory
			DESCRIPTION
                " In all cases, the destination port of the received 
                  frame."
			::= { accSrFiltIIEntry 4 }
	    accSrFiltIIEntLogicalOp	OBJECT-TYPE   
			SYNTAX	INTEGER {
				any		(1),
				equal		(2),
				notequal	(3)
				}
			ACCESS	read-write
			STATUS	mandatory
			DESCRIPTION
                 " Logical operation to be performed in conjunction with
		   specified protocol. This is an optional parameter."
			::= { accSrFiltIIEntry 5 }
	    accSrFiltIIEntProtocol	OBJECT-TYPE   
			SYNTAX  OCTET STRING (SIZE(2))	
			ACCESS	read-write
			STATUS	mandatory
			DESCRIPTION
                 " Protocol to be used in conjunction with logical operation
		   to determine the disposition of all received packets."
			::= { accSrFiltIIEntry 6 }
	    accSrFiltIIEntDstMacAddrMask	OBJECT-TYPE   
			SYNTAX	OCTET STRING (SIZE(6))
			ACCESS	read-write
			STATUS	mandatory
			DESCRIPTION
                " Destination MAC Address Mask for the Filtering entry.
                  The mask is ANDed with the Destination address to 
                  determine that part of the MAC address which is used in 
                  the filtering decision."
			::= { accSrFiltIIEntry 7 }
	    accSrFiltIIEntSrcMacAddrMask	OBJECT-TYPE   
			SYNTAX	OCTET STRING (SIZE(6))
			ACCESS	read-write
			STATUS	mandatory
			DESCRIPTION
                " Source MAC Address Mask for the Filtering entry.
                  The mask is ANDed with the Source address to
                  determine that part of the MAC address which is used in
                  the filtering decision."
			::= { accSrFiltIIEntry 8 }
	    accSrFiltIIDiscards	OBJECT-TYPE   
			SYNTAX	INTEGER
			ACCESS	read-only
			STATUS	mandatory
			DESCRIPTION
                 " The number of packets discarded as a result of bridge
		   filtering. Maintained globally for all ports."
			::= { accSr 14 }
	    accSrFiltIIEntries	OBJECT-TYPE   
			SYNTAX	INTEGER
			ACCESS	read-only
			STATUS	mandatory
			DESCRIPTION
                 " The number of entries currently in the bridge filtering
		   table. The maximum number of entries is 150."
			::= { accSr 15 }
-- SMDS Group
      accSMDS         OBJECT IDENTIFIER ::= { accBRG 26 }
               SmdsAddress ::= OCTET STRING  (SIZE (8))
               -- the 60-bit SMDS address, preceded by 4 bits with the
               -- following values:
               -- "1100" when representing an individual address
               -- "1110" when representing a group address
               -- The SMDS Port group
               accSmdsPortTable  OBJECT-TYPE
                   SYNTAX  SEQUENCE OF AccSmdsPortEntry
                   ACCESS  not-accessible
                   STATUS  mandatory
                   DESCRIPTION
                           "This table contains SMDS port parameters and
                           state variables, one entry per SMDS port."
                  ::= { accSMDS 1 }
              accSmdsPortEntry  OBJECT-TYPE
                  SYNTAX  AccSmdsPortEntry
                  ACCESS  not-accessible
                  STATUS  mandatory
                  DESCRIPTION
                          "This list contains SMDS port parameters and
                          state variables."
                 INDEX   { accSmdsPortIndex }
                 ::= { accSmdsPortTable 1 }
             AccSmdsPortEntry  ::= SEQUENCE {
                 accSmdsPortIndex
                     INTEGER,
                 accSmdsPortIA
                     SmdsAddress
                 }
             accSmdsPortIndex  OBJECT-TYPE
                 SYNTAX  INTEGER (1..65535)
                 ACCESS  read-only
                 STATUS  mandatory
                 DESCRIPTION
                         "The value of this object identifies the SIP
                         port interface for which this entry contains
                         management information.  The value of this
                         object for a particular interface has the same
                         value as the ifIndex object, defined in RFC
                         1156 and RFC 1213, for the same interface."
                ::= { accSmdsPortEntry 1 }
             accSmdsPortIA  OBJECT-TYPE
                 SYNTAX  SmdsAddress
                 ACCESS  read-write
                 STATUS  mandatory
                 DESCRIPTION
                         "The value of this object specifies the SNI
			 Individual address configured for this SIP
			 interface port."
                ::= { accSmdsPortEntry 2 }
               -- The SIP Level 3 group
               -- Implementation of the SIP Level 3 group is mandatory
               -- for all systems implementing SIP Level 3.
               accSipL3Table  OBJECT-TYPE
                   SYNTAX  SEQUENCE OF AccSipL3Entry
                   ACCESS  not-accessible
                   STATUS  mandatory
                   DESCRIPTION
                           "This table contains SIP L3 parameters and
                           state variables, one entry per SIP port."
                  ::= { accSMDS 2 }
              accSipL3Entry  OBJECT-TYPE
                  SYNTAX  AccSipL3Entry
                  ACCESS  not-accessible
                  STATUS  mandatory
                  DESCRIPTION
                          "This list contains SIP L3 parameters and
                          state variables."
                 INDEX   { accSipL3Index }
                 ::= { accSipL3Table 1 }
             AccSipL3Entry  ::= SEQUENCE {
                 accSipL3Index
                     INTEGER,
                 accSipL3RcvIAs
                     Counter,
                 accSipL3RcvGAs
                     Counter,
                 accSipL3UnkIAs
                     Counter,
                 accSipL3UnkGAs
                     Counter,
                 accSipL3SndIAs
                     Counter,
                 accSipL3SndGAs
                     Counter,
                 accSipL3Errors
                     Counter,
                 accSipL3InvAddrs
                     Counter
                 }
             accSipL3Index  OBJECT-TYPE
                 SYNTAX  INTEGER (1..65535)
                 ACCESS  read-only
                 STATUS  mandatory
                 DESCRIPTION
                         "The value of this object identifies the SIP
                         port interface for which this entry contains
                         management information.  The value of this
                         object for a particular interface has the same
                         value as the ifIndex object, defined in RFC
                         1156 and RFC 1213, for the same interface."
                ::= { accSipL3Entry 1 }
            accSipL3RcvIAs OBJECT-TYPE
                SYNTAX  Counter
                ACCESS  read-only
                STATUS  mandatory
                DESCRIPTION
                        "The total number of individually addressed SIP
                        Level 3 PDUs received from the remote system
                        across the SNI.  The total includes only
                        unerrored L3PDUs."
               ::= { accSipL3Entry 2 }
           accSipL3RcvGAs OBJECT-TYPE
               SYNTAX  Counter
               ACCESS  read-only
               STATUS  mandatory
               DESCRIPTION
                       "The total number of group addressed SIP Level 3
                       PDUs received from the remote system across the
                       SNI.  The total includes only unerrored L3PDUs."
              ::= { accSipL3Entry 3 }
          accSipL3UnkIAs OBJECT-TYPE
              SYNTAX  Counter
              ACCESS  read-only
              STATUS  mandatory
              DESCRIPTION
                      "The number of SIP Level 3 PDUs received from the
                      remote system with invalid or unknown individual
                      destination addresses (Destination Address
                      Screening violations are not included).  See SMDS
                      Subscription MIB module."
              ::= { accSipL3Entry 4 }
          accSipL3UnkGAs OBJECT-TYPE
              SYNTAX  Counter
              ACCESS  read-only
              STATUS  mandatory
              DESCRIPTION
                      "The number of SIP Level 3 PDUs received from the
                      remote system with invalid or unknown group
                      addresses.  (Destination Address Screening
                      violations are not included).  See SMDS
                      Subscription MIB module."
              ::= { accSipL3Entry 5 }
          accSipL3SndIAs OBJECT-TYPE
              SYNTAX  Counter
              ACCESS  read-only
              STATUS  mandatory
              DESCRIPTION
                      "The number of individually addressed SIP Level 3
                      PDUs that have been sent by this system across the
                      SNI."
              ::= { accSipL3Entry 6 }
          accSipL3SndGAs OBJECT-TYPE
              SYNTAX  Counter
              ACCESS  read-only
              STATUS  mandatory
              DESCRIPTION
                      "The number of group addressed SIP L3PDUs that
                      have been sent by this system across the SNI."
              ::= { accSipL3Entry 7 }
          -- The total number of SIP L3PDU errors can be calculated as
          -- (Syntactic errors + Semantic Service errors )
          -- Syntactic errors include:
          --    accSipL3Errors
          -- Latest occurrences of syntactic error types are logged in
          --    accSipL3PDUErrorTable.
          -- Semantic Service errors include:
          --    accSipL3UnkIAs
          --    accSipL3UnkGAs
          --    accSipL3InvAddrs
          -- Note that public networks supporting SMDS may discard
          -- SIP L3PDUs due to subscription violations.  Related
          -- managed objects are defined in Definitions of Managed
          -- Objects for SMDS Subscription.
          accSipL3Errors OBJECT-TYPE
              SYNTAX  Counter
              ACCESS  read-only
              STATUS  mandatory
              DESCRIPTION
                      "The total number of SIP Level 3 PDUs received
                      from the remote system that were discovered to
                      have errors (including protocol processing and bit
                      errors but excluding addressing-related errors)
                      and were discarded.  Includes both group addressed
                      L3PDUs and L3PDUs containing an individual
                      destination address."
              ::= { accSipL3Entry 8 }
          accSipL3InvAddrs OBJECT-TYPE
              SYNTAX  Counter
              ACCESS  read-only
              STATUS  mandatory
              DESCRIPTION
                      "The number of SIP Level 3 PDUs received from the
                      remote system that had the Source or Destination
                      Address_Type subfields, (the four most significant
                      bits of the 64 bit address field), not equal to
                      the value 1100 or 1110.  Also, an error is
                      considered to have occurred if the Address_Type
                      field for a Source Address, the four most
                      significant bits of the 64 bits, is equal to 1110
                      (a group address)."
              ::= { accSipL3Entry 9 }
-- Remote Loader Group
      accRload         OBJECT IDENTIFIER ::= { accBRG 27 }
	accRlSourceTable	OBJECT-TYPE
			SYNTAX SEQUENCE OF AccRlSourceEntry
			ACCESS not-accessible
			STATUS mandatory
			DESCRIPTION
			 " Table of host/filenames for remote
			   loading of system application code.
			   To delete an entry, set the value of accRlPriority
			    to NULL for the desired instance.
			   Existing entries may be modified (overwritten)."
			::= { accRload 1 }
	accRlSourceEntry OBJECT-TYPE
			SYNTAX AccRlSourceEntry
			ACCESS not-accessible
			STATUS mandatory
			DESCRIPTION
			 " Specific host/filename information "
                        INDEX { accRlPriority }
			::= { accRlSourceTable 1 }
		AccRlSourceEntry ::= SEQUENCE {
			accRlHostAddr		IpAddress,
			accRlFilename		DisplayString,
			accRlPriority		INTEGER
			}
		accRlHostAddr  OBJECT-TYPE
			SYNTAX IpAddress
			ACCESS read-write
			STATUS mandatory
			DESCRIPTION
			 " IP address of host which contains the
			     application file to be remote-loaded."
			::= { accRlSourceEntry 1 }
		accRlFilename  OBJECT-TYPE
			SYNTAX  DisplayString 
			ACCESS read-write
			STATUS mandatory
			DESCRIPTION
			 " ASCII filename of application file to
			    be remote-loaded to unit."
			::= { accRlSourceEntry 2 }
		accRlPriority  OBJECT-TYPE
			SYNTAX INTEGER 
			ACCESS read-write
			STATUS mandatory
			DESCRIPTION
			 " Priority of this entry. Attempts will be made
			   to download from host/filename with lowest
			   numerical value of priority first, then next
			   lowest, etc.  Range is limited to number of
			   entries in the table."
			::= { accRlSourceEntry 3 }
	accNetload  OBJECT-TYPE
		SYNTAX INTEGER {
			initiate(1),
			other(2)
			}
		ACCESS read-write
		STATUS mandatory
		DESCRIPTION
		 " Setting this object to initiate causes the unit
		   to attempt to load application code into local
		   (execution) memory  from a file in the accRlSourceTable.
		   This code will then be immediately executed."
		::= { accRload 2 }
	accDownload  OBJECT-TYPE
		SYNTAX INTEGER {
			initiate(1),
			other(2)
			}
		ACCESS read-write
		STATUS mandatory
		DESCRIPTION
		 " Setting this object to initiate causes the unit
		   to load local EPROM with application code
		   brought over the network from a file in the 
		   accRlSourceTable."
		::= { accRload 3 }
	accPromload  OBJECT-TYPE
		SYNTAX INTEGER {
			initiate(1),
			other(2)
			}
		ACCESS read-write
		STATUS mandatory
		DESCRIPTION
		 " Setting this object to initiate causes the unit
		   to load local EPROM with diagnostics and the
		   remote loader application brought over the network 
		   from a file called PROMLOAD from a host in the
		   accRlSourceTable."
		::= { accRload 4 }
	accCfgLoad	OBJECT IDENTIFIER ::= { accRload 5 }
	accCfgHost  OBJECT-TYPE
		SYNTAX  IpAddress
		ACCESS  read-write
		STATUS  mandatory
		DESCRIPTION
		 " The IP address of the TFTP server to attempt a
		   download from.  This object is used in conjunction
		   with accCfgFile & accCfgDisp to download configurations."
		::= { accCfgLoad 1 }
	accCfgFile  OBJECT-TYPE
		SYNTAX  DisplayString
		ACCESS	read-write
		STATUS	mandatory
		DESCRIPTION
		 " The filename (include pathname) of the file on the
		   TFTP server to download.  This object is used in
		   conjunction with accCfgHost & accCfgDisp to download
		   configurations."
		::= { accCfgLoad 2 }
	accCfgDisp  OBJECT-TYPE
		SYNTAX	INTEGER {
			reset(1),
			reload(2),
			execute(3)
			}
		ACCESS	read-write
		STATUS	mandatory
		DESCRIPTION
		 " The action to take following the successful TFTP
		   download of a file.  
		   reset specifies that the downloaded file is a binary 
		   configuration file.  The configuration is overwritten 
		   with the downloaded file, and the unit resets, using 
		   the downloaded configuration on restart.
		   reload specifies that the downloaded file is a binary 
		   configuration file.  The configuration is overwritten 
		   with the downloaded file, and the unit reloads, using 
		   the downloaded configuration on restart.
		   execute specifies that the downloaded file is a
		   configuration script containing client commands.
		   On download the script is parsed and the commands executed."
		::= { accCfgLoad 3 }
	accTftpStat	OBJECT IDENTIFIER ::= { accRload 6 }
	accTftpStatus  OBJECT-TYPE
		SYNTAX	INTEGER {
			uploading(1),
			downloading(2),
			idle(3)
			}
		ACCESS	read-only
		STATUS	mandatory
		DESCRIPTION
		 " The state of the remote loader (client of TFTP)."
		::= { accTftpStat 1 }
	accTftpLocalFile  OBJECT-TYPE
		SYNTAX	DisplayString
		ACCESS	read-only
		STATUS	mandatory
		DESCRIPTION
		 " The local filename used in the last upload/download."
		::= { accTftpStat 2 }
	accTftpRemoteFile  OBJECT-TYPE
		SYNTAX	DisplayString
		ACCESS	read-only
		STATUS	mandatory
		DESCRIPTION
		 " The remote filename used in the last download."
		::= { accTftpStat 3 }
	accTftpOctetsTransferred  OBJECT-TYPE
		SYNTAX	INTEGER
		ACCESS	read-only
		STATUS	mandatory
		DESCRIPTION
		 " The number of octets transferred in the last/current
		   upload/download."
		::= { accTftpStat 4 }
	accTftpLastMsg  OBJECT-TYPE
		SYNTAX	DisplayString
		ACCESS	read-only
		STATUS	mandatory
		DESCRIPTION
		 " The contents of the last trap message generated by the
		   remote loader."
		::= { accTftpStat 5 }
-- TFTP command group
        accTftpCmd      OBJECT IDENTIFIER ::= { accRload 7 }
        accTftpCmdReq  OBJECT-TYPE
                SYNTAX  INTEGER {
                        get(1)
                        }
                ACCESS  read-only
                STATUS  mandatory
		DESCRIPTION
		" TFTP command request."
                ::= { accTftpCmd 1 }
        accTftpCmdHost  OBJECT-TYPE
                SYNTAX  IpAddress
                ACCESS  read-only
                STATUS  mandatory
		DESCRIPTION
		" TFTP command host."
                ::= { accTftpCmd 2 }
        accTftpCmdRemote  OBJECT-TYPE
                SYNTAX  DisplayString
                ACCESS  read-only
                STATUS  mandatory
		DESCRIPTION
		" TFTP remote file name."
                ::= { accTftpCmd 3 }
        accTftpCmdLocal  OBJECT-TYPE
                SYNTAX  DisplayString
                ACCESS  read-only
                STATUS  mandatory
		DESCRIPTION
		" TFTP local file name."
                ::= { accTftpCmd 4 }
-- AppleTalk Group
     accAt OBJECT IDENTIFIER ::= { accBRG 28 }
     -- The AtNode Group
     accAtNode OBJECT IDENTIFIER ::= { accAt 1 }
		-- Configuration or operational parameters maintained
		-- and reported on a per-node basis.
     accAtNodeAdState OBJECT-TYPE
		SYNTAX	INTEGER {
			on(1),
			off(3)
		}
		ACCESS	read-write
		STATUS	mandatory
		DESCRIPTION
		 " The administrative state of the AppleTalk router.  If
		   set to on(1), AppleTalk packets will be routed on ports
		   which have been administratively enabled.  If set to
		   off(3), AppleTalk packets will be bridged."
		::= { accAtNode 1 }
     accAtNodeChecksum OBJECT-TYPE
		SYNTAX	INTEGER {
			on(1),
			off(2)
		}
		ACCESS	read-write
		STATUS	mandatory
		DESCRIPTION
		 " The AppleTalk checksum mode.  If set to on(1), output
		   packets will be generated with the standard AppleTalk
		   checksum.  If set to off(2), output packets will be
		   generated with a null checksum.  Checksum verification
		   is performed on input if and only if a DDP checksum is
		   present."
		::= { accAtNode 2 }
     accAtNodeAarpExpire OBJECT-TYPE
		SYNTAX	TimeTicks -- (6000..1800000)
		ACCESS	read-write
		STATUS	mandatory
		DESCRIPTION
		 " The AARP database expiration interval.  AARP database
		   entries which are not updated within this interval of
		   time are deleted from the database.  The default value
		   is 360000 (1 hour)."
		::= { accAtNode 3 }
     -- The AtAarpTable Group
     accAtAarpTable OBJECT-TYPE
		SYNTAX	SEQUENCE OF AccAtAarpEntry
		ACCESS	not-accessible
		STATUS	mandatory
		DESCRIPTION
		 " The AARP database containing AppleTalk protocol to
		   hardware address mappings.  This view of the AARP
		   database differs from the standard view as seen from
		   the experimental branch of the MIB."
		::= { accAt 2 }
     accAtAarpEntry OBJECT-TYPE
		SYNTAX	AccAtAarpEntry
		ACCESS	not-accessible
		STATUS	mandatory
		DESCRIPTION
		 " An AARP database entry which maps a particular AppleTalk
		   protocol address into a MAC-layer hardware address. "
		INDEX { accAtAarpTabPort,
		        accAtAarpTabNetAddr }
		::= { accAtAarpTable 1 }
     AccAtAarpEntry ::= SEQUENCE {
		accAtAarpTabPort		INTEGER,
		accAtAarpTabMacAddr		OCTET STRING,
		accAtAarpTabNetAddr		OCTET STRING,
		accAtAarpTabStatus		INTEGER
     }
     accAtAarpTabPort OBJECT-TYPE
		SYNTAX	INTEGER (1..255)
		ACCESS	read-only
		STATUS	mandatory
		DESCRIPTION
		 " The logical port number of a directly-connected
		   AppleTalk network."
		::= { accAtAarpEntry 1 }
     accAtAarpTabMacAddr OBJECT-TYPE
		SYNTAX	OCTET STRING
		ACCESS	read-only
		STATUS	mandatory
		DESCRIPTION
		 " The 48-bit Ethernet or Token Ring MAC-layer address
		   which corresponds to the AppleTalk network address."
		::= { accAtAarpEntry 2 }
     accAtAarpTabNetAddr OBJECT-TYPE
		SYNTAX  OCTET STRING -- (SIZE(3))	
		ACCESS	read-only
		STATUS	mandatory
		DESCRIPTION
		 " The 24-bit AppleTalk network address consisting of a
		   16-bit network number and 8-bit node id."
		::= { accAtAarpEntry 3 }
     accAtAarpTabStatus OBJECT-TYPE
		SYNTAX	INTEGER {
			dynamic(1),
			static(2),
			pending(3)
		}
		ACCESS	read-only
		STATUS	mandatory
		DESCRIPTION
		 " The status of the entry.  A status of dynamic(1)
		   indicates the entry can be deleted when the expiration
		   interval expires, a status of static(1) indicates the
		   entry contains the address of a local port, and a status
		   of pending(3) indicates the entry is not complete (i.e.,
		   the hardware or protocol address is unknown)."
		::= { accAtAarpEntry 4 }
     -- The AtAarpStatsTable Group
     accAtAarpStatsTable OBJECT-TYPE
		SYNTAX	SEQUENCE OF AccAtAarpStatsEntry
		ACCESS	not-accessible
		STATUS	mandatory
		DESCRIPTION
		 " AppleTalk Address Resolution Protocol (AARP) statistics
		   maintained and reported on a per-port basis."
		::= { accAt 3 }
     accAtAarpStatsEntry OBJECT-TYPE
		SYNTAX	AccAtAarpStatsEntry
		ACCESS	not-accessible
		STATUS	mandatory
		DESCRIPTION
		 " The AARP statistics for a particular logical port.  If
		   the port is not connected to an AppleTalk network which
		   uses AARP, all statistics will be reported with a zero
		   value. "
                INDEX { accAtPortTabIndex }
		::= { accAtAarpStatsTable 1 }
     AccAtAarpStatsEntry ::= SEQUENCE {
		accAtAarpStatsInRequests	Counter,
		accAtAarpStatsInResponses	Counter,
		accAtAarpStatsInProbes		Counter,
		accAtAarpStatsOutRequests	Counter,
		accAtAarpStatsOutResponses	Counter,
		accAtAarpStatsOutProbes		Counter,
		accAtAarpStatsNoReplys		Counter,
		accAtAarpStatsExpires		Counter,
		accAtAarpStatsDiscards		Counter,
		accAtAarpStatsInErrors		Counter,
		accAtAarpStatsOutErrors		Counter
     }
     accAtAarpStatsInRequests OBJECT-TYPE
		SYNTAX	Counter
		ACCESS	read-only
		STATUS	mandatory
		DESCRIPTION
		 " The number of AARP request packets received."
		::= { accAtAarpStatsEntry 1 }
     accAtAarpStatsInResponses OBJECT-TYPE
		SYNTAX	Counter
		ACCESS	read-only
		STATUS	mandatory
		DESCRIPTION
		 " The number of AARP response packets received."
		::= { accAtAarpStatsEntry 2 }
     accAtAarpStatsInProbes OBJECT-TYPE
		SYNTAX	Counter
		ACCESS	read-only
		STATUS	mandatory
		DESCRIPTION
		 " The number of AARP probe packets received."
		::= { accAtAarpStatsEntry 3 }
     accAtAarpStatsOutRequests OBJECT-TYPE
		SYNTAX	Counter
		ACCESS	read-only
		STATUS	mandatory
		DESCRIPTION
		 " The number of AARP request packets sent."
		::= { accAtAarpStatsEntry 4 }
     accAtAarpStatsOutResponses OBJECT-TYPE
		SYNTAX	Counter
		ACCESS	read-only
		STATUS	mandatory
		DESCRIPTION
		 " The number of AARP response packets sent."
		::= { accAtAarpStatsEntry 5 }
     accAtAarpStatsOutProbes OBJECT-TYPE
		SYNTAX	Counter
		ACCESS	read-only
		STATUS	mandatory
		DESCRIPTION
		 " The number of AARP probe packets sent."
		::= { accAtAarpStatsEntry 6 }
     accAtAarpStatsNoReplys OBJECT-TYPE
		SYNTAX	Counter
		ACCESS	read-only
		STATUS	mandatory
		DESCRIPTION
		 " The number of times an AARP request packet and its
		   subsequent retransmissions received no response."
		::= { accAtAarpStatsEntry 7 }
     accAtAarpStatsExpires OBJECT-TYPE
		SYNTAX	Counter
		ACCESS	read-only
		STATUS	mandatory
		DESCRIPTION
		 " The number of times an entry was deleted from the AARP
		   database because the expiration interval had expired."
		::= { accAtAarpStatsEntry 8 }
     accAtAarpStatsDiscards OBJECT-TYPE
		SYNTAX	Counter
		ACCESS	read-only
		STATUS	mandatory
		DESCRIPTION
		 " The number of queued output packets discarded because
		   of an unanswered AARP request."
		::= { accAtAarpStatsEntry 9 }
     accAtAarpStatsInErrors OBJECT-TYPE
		SYNTAX	Counter
		ACCESS	read-only
		STATUS	mandatory
		DESCRIPTION
		 " The number of AARP packets received which were invalid
		   or which could not be processed because of some internal
		   error."
		::= { accAtAarpStatsEntry 10 }
     accAtAarpStatsOutErrors OBJECT-TYPE
		SYNTAX	Counter
		ACCESS	read-only
		STATUS	mandatory
		DESCRIPTION
		 " The number of AARP packets which could not be sent
		   because of some internal error."
		::= { accAtAarpStatsEntry 11 }
     -- The AtAdbStats Group
     accAtAdbStats OBJECT IDENTIFIER ::= { accAt 4 }
		-- AARP database statistics maintained and reported on a
		-- per-node basis.
     accAtAdbStatsCacheds OBJECT-TYPE
		SYNTAX	Counter
		ACCESS	read-only
		STATUS	mandatory
		DESCRIPTION
		 " The number of times the desired database entry was the
		   first entry in the hash bucket (i.e., it had already
		   been rotated to the beginning of the list of entries
		   with the same hash value)."
		::= { accAtAdbStats 1 }
     accAtAdbStatsRotates OBJECT-TYPE
		SYNTAX	Counter
		ACCESS	read-only
		STATUS	mandatory
		DESCRIPTION
		 " The number of times the desired database entry was not
		   the first entry in the hash bucket and had to be rotated
		   to the beginning of the list."
		::= { accAtAdbStats 2 }
     accAtAdbStatsNoEntries OBJECT-TYPE
		SYNTAX	Counter
		ACCESS	read-only
		STATUS	mandatory
		DESCRIPTION
		 " The number of times the desired entry was not in the
		   AARP database."
		::= { accAtAdbStats 3 }
     accAtAdbStatsAdds OBJECT-TYPE
		SYNTAX	Counter
		ACCESS	read-only
		STATUS	mandatory
		DESCRIPTION
		 " The number of times a new entry was added to the AARP
		   database."
		::= { accAtAdbStats 4 }
     accAtAdbStatsUpdates OBJECT-TYPE
		SYNTAX	Counter
		ACCESS	read-only
		STATUS	mandatory
		DESCRIPTION
		 " The number of times an existing entry was updated."
		::= { accAtAdbStats 5 }
     accAtAdbStatsDeletes OBJECT-TYPE
		SYNTAX	Counter
		ACCESS	read-only
		STATUS	mandatory
		DESCRIPTION
		 " The number of times an entry was deleted from the AARP
		   database."
		::= { accAtAdbStats 6 }
     accAtAdbStatsTrims OBJECT-TYPE
		SYNTAX	Counter
		ACCESS	read-only
		STATUS	mandatory
		DESCRIPTION
		 " The number of times the AARP database was trimmed to
		   make room for a new entry."
		::= { accAtAdbStats 7 }
     accAtAdbStatsDiscards OBJECT-TYPE
		SYNTAX	Counter
		ACCESS	read-only
		STATUS	mandatory
		DESCRIPTION
		 " The number of queued output packets discarded because
		   the anchoring database entry was deleted."
		::= { accAtAdbStats 8 }
     -- The AtDdpStats Group
     accAtDdpStats OBJECT IDENTIFIER ::= { accAt 5 }
		-- Datagram Delivery Protocol (DDP) statistics maintained
		-- and reported on a per-node basis.  These statistics
		-- supplement the standard DDP statistics defined in the
		-- experimental branch of the MIB.
     accAtDdpStatsNoOutRoutes OBJECT-TYPE
		SYNTAX	Counter
		ACCESS	read-only
		STATUS	mandatory
		DESCRIPTION
		 " The number of output packets generated by local protocol
		   handlers for which there was not route to the destination
		   network."
		::= { accAtDdpStats 1 }
     accAtDdpStatsInErrors OBJECT-TYPE
		SYNTAX	Counter
		ACCESS	read-only
		STATUS	mandatory
		DESCRIPTION
		 " The number of packets received which could not be
		   delivered because of some internal error."
		::= { accAtDdpStats 2 }
     accAtDdpStatsOutErrors OBJECT-TYPE
		SYNTAX	Counter
		ACCESS	read-only
		STATUS	mandatory
		DESCRIPTION
		 " The number of packets locally generated which could
		   not be sent because of some internal error."
		::= { accAtDdpStats 3 }
     -- The AtNetTable Group
     accAtNetTable OBJECT-TYPE
		SYNTAX	SEQUENCE OF AccAtNetEntry
		ACCESS	not-accessible
		STATUS	mandatory
		DESCRIPTION
		 " AppleTalk network configuration table stored in NVM."
		::= { accAt 6 }
     accAtNetEntry OBJECT-TYPE
		SYNTAX	AccAtNetEntry
		ACCESS	not-accessible
		STATUS	mandatory
		DESCRIPTION
		 " The information stored in NVM which defines an AppleTalk
		   network or half-router serial port.  This information
		   supplements standard configuration parameters defined
		   in the experimental branch of the MIB."
                INDEX { atportIndex }
		::= { accAtNetTable 1 }
     AccAtNetEntry ::= SEQUENCE {
		accAtNetTabProtocol		INTEGER,
		accAtNetTabRtmpIncr		INTEGER,
		accAtNetTabRtmpSend		TimeTicks,
		accAtNetTabX25Addr1		OCTET STRING,
		accAtNetTabX25Addr2		OCTET STRING,
		accAtNetTabX25Idle		TimeTicks,
		accAtNetTabX25PktSize		INTEGER,
		accAtNetTabX25WinSize		INTEGER,
		accAtNetTabX25FacIndex		INTEGER
     }
     accAtNetTabProtocol OBJECT-TYPE
		SYNTAX	INTEGER {
			ethertalk1(1),
			ethertalk2(2),
			tokentalk(3),
			lapb(4),
			x25(5),
			framerelay(6),
			ppp(7),
			fddi(8),
			dial(11),
			multilinkgroup(12)
		}
		ACCESS	read-write
		STATUS	mandatory
		DESCRIPTION
		 " The type of data-link protocol used.  These types
		   augment the standard definitions in the experimental
		   branch of the MIB and are used to maintain conformity
		   with ACC management commands.  Setting this object
		   will cause all other objects associated with this
		   entry to be reset to their default values."
		::= { accAtNetEntry 1 }
     accAtNetTabRtmpIncr OBJECT-TYPE
		SYNTAX	INTEGER (1..15)
		ACCESS	read-write
		STATUS	mandatory
		DESCRIPTION
		 " The RTMP hop-count increment to be applied to packets
		   forwarded via this port or routing tuples received
		   received on this port."
                DEFVAL { 1 }
		::= { accAtNetEntry 2 }
     accAtNetTabRtmpSend OBJECT-TYPE
		SYNTAX	TimeTicks -- (1000..30000)
		ACCESS	read-write
		STATUS	mandatory
		DESCRIPTION
		 " The RTMP send interval for routing updates sent via
		   this port. The RTMP send interval may be
		   set to a higher value on serial ports to limit the
		   amount of bandwidth consumed by routing updates."
                DEFVAL { 1000 }
		::= { accAtNetEntry 3 }
     accAtNetTabX25Addr1 OBJECT-TYPE
		SYNTAX	OCTET STRING
		ACCESS	read-write
		STATUS	mandatory
		DESCRIPTION
		 " The normal DTE address to use for sending or receiving
		   packets via an X.25 virtual circuit."
		::= { accAtNetEntry 4 }
     accAtNetTabX25Addr2 OBJECT-TYPE
		SYNTAX	OCTET STRING
		ACCESS	read-write
		STATUS	mandatory
		DESCRIPTION
		 " An alternate DTE address to use for receiving packets
		   via an X.25 virtual circuit."
		::= { accAtNetEntry 5 }
     accAtNetTabX25Idle OBJECT-TYPE
		SYNTAX	TimeTicks -- (6000..6480000)
		ACCESS	read-write
		STATUS	mandatory
		DESCRIPTION
		 " The interval which governs how long an X.25 circuit
		   can be idle before it is cleared. "
                DEFVAL { 30000 }
		::= { accAtNetEntry 6 }
     accAtNetTabX25PktSize OBJECT-TYPE
		SYNTAX	INTEGER 
		ACCESS	read-write
		STATUS	mandatory
		DESCRIPTION
		 " The desired packet size to be negotiated during X.25
		   call establishment.
			pktsize1(0),
			pktsize2(16),
			pktsize3(32),
			pktsize4(64),
			pktsize5(128),
			pktsize6(256),
			pktsize7(512),
			pktsize8(1024)
		   "
                DEFVAL { 0 }
		::= { accAtNetEntry 7 }
     accAtNetTabX25WinSize OBJECT-TYPE
		SYNTAX	INTEGER (0..127)
		ACCESS	read-write
		STATUS	mandatory
		DESCRIPTION
		 " The desired window size to be negotiated during X.25
		   call establishment."
                DEFVAL { 127 }
		::= { accAtNetEntry 8 }
	accAtNetTabX25FacIndex OBJECT-TYPE
	               SYNTAX  INTEGER (0..255)
	               ACCESS  read-write
	               STATUS  mandatory
	               DESCRIPTION
	                " Index of optional facility string or zero."
	                 DEFVAL { 0 }
	               ::= { accAtNetEntry 9 }
     -- The AtPortTable Group
     accAtPortTable OBJECT-TYPE
		SYNTAX	SEQUENCE OF AccAtPortEntry
		ACCESS	not-accessible
		STATUS	mandatory
		DESCRIPTION
		 " The AppleTalk port table stored in RAM.  For each
		   valid network table entry configured in NVM when
		   the port table is initialized (after system reset)
		   there is a corresponding port table entry in RAM."
		::= { accAt 7 }
     accAtPortEntry OBJECT-TYPE
		SYNTAX	AccAtPortEntry
		ACCESS	not-accessible
		STATUS	mandatory
		DESCRIPTION
		 " The information maintained in RAM for a particular
		   logical port." 
                INDEX { accAtPortTabIndex }
		::= { accAtPortTable 1 }
     AccAtPortEntry ::= SEQUENCE {
		accAtPortTabIndex		INTEGER,
		accAtPortTabNetAddr		OCTET STRING,
		accAtPortTabState		INTEGER,
		accAtPortTabDescr		DisplayString,
		accAtPortTabErrCode		INTEGER,
		accAtPortTabErrTime		TimeTicks,
		accAtPortTabErrAddr		OCTET STRING,
		accAtPortTabErrDescr		DisplayString,
		accAtPortTabErrCount		INTEGER
     }
     accAtPortTabIndex OBJECT-TYPE
		SYNTAX	INTEGER (1..255)
		ACCESS	read-only
		STATUS	mandatory
		DESCRIPTION
		 " The logical port number.  Only ports which were defined
		   prior to the last system reset and whose configuration
		   entries contained valid parameters are initialized and
		   stored in RAM."
		::= { accAtPortEntry 1 }
     accAtPortTabNetAddr OBJECT-TYPE
		SYNTAX	OCTET STRING
		ACCESS	read-only
		STATUS	mandatory
		DESCRIPTION
		 " The ports DDP network address consisting of a 16-bit
		   AppleTalk network number and 8-bit node id.  This
		   address is determined dynamically during port start
		   up and may change after a system reset."
		::= { accAtPortEntry 2 }
     accAtPortTabState OBJECT-TYPE
		SYNTAX	INTEGER {
			down(1),
			start1(2),
			probe1(3),
			start2(4),
			up(5),
			probe2(6),
			query(7),
			ready(8),
			stop2(9),
			stop1(10),
			error(11)
		}
		ACCESS	read-only
		STATUS	mandatory
		DESCRIPTION
		 " The operational state of the port."
		::= { accAtPortEntry 3 }
     accAtPortTabDescr OBJECT-TYPE
		SYNTAX  DisplayString
		ACCESS	read-only
		STATUS	mandatory
		DESCRIPTION
		 " Displayable text describing the type of logical port."
		::= { accAtPortEntry 4 }
     accAtPortTabErrCode OBJECT-TYPE
		SYNTAX	INTEGER
		ACCESS	read-only
		STATUS	mandatory
		DESCRIPTION
		 " An error code indicating why the logical port has been
		   disabled.  This value is set when the operational state
		   (accAtPortTabState) of a port is set to error(11) due
		   to some condition which may prevent continued operation."
		::= { accAtPortEntry 5 }
     accAtPortTabErrTime OBJECT-TYPE
		SYNTAX	TimeTicks
		ACCESS	read-only
		STATUS	mandatory
		DESCRIPTION
		 " The time (relative to the last system reset) at which
		   the port became disabled."
		::= { accAtPortEntry 6 }
     accAtPortTabErrAddr OBJECT-TYPE
		SYNTAX	OCTET STRING
		ACCESS	read-only
		STATUS	mandatory
		DESCRIPTION
		 " The DDP network address of a neighboring router or
		   AppleTalk node which was the source of information
		   causing the port to become disabled.  The DDP address
		   consists of a 16-bit AppleTalk network number and
		   8-bit node id."
		::= { accAtPortEntry 7 }
     accAtPortTabErrDescr OBJECT-TYPE
		SYNTAX  DisplayString	
		ACCESS	read-only
		STATUS	mandatory
		DESCRIPTION
		 " Displayable text which describes why the port has been
		   disabled."
		::= { accAtPortEntry 8 }
     accAtPortTabErrCount OBJECT-TYPE
		SYNTAX	INTEGER
		ACCESS	read-only
		STATUS	mandatory
		DESCRIPTION
		 " The number of subsequent errors which have been detected
		   while a port is disabled."
		::= { accAtPortEntry 9 }
     -- The AtPortStatsTable Group
     accAtPortStatsTable OBJECT-TYPE
		SYNTAX	SEQUENCE OF AccAtPortStatsEntry
		ACCESS	not-accessible
		STATUS	mandatory
		DESCRIPTION
		 " Datagram Delivery Protocol (DDP) statistics maintained
		   and reported on a per-port basis."
		::= { accAt 8 }
     accAtPortStatsEntry OBJECT-TYPE
		SYNTAX	AccAtPortStatsEntry
		ACCESS	not-accessible
		STATUS	mandatory
		DESCRIPTION
		 " The DDP statistics maintained for a particular logical
		   port."
                INDEX { accAtPortTabIndex }
		::= { accAtPortStatsTable 1 }
     AccAtPortStatsEntry ::= SEQUENCE {
		accAtPortStatsInTotals		Counter,
		accAtPortStatsInShorts		Counter,
		accAtPortStatsNotForMes		Counter,
		accAtPortStatsTooShorts		Counter,
		accAtPortStatsTooLongs		Counter,
		accAtPortStatsChksums		Counter,
		accAtPortStatsNotMyNets		Counter,
		accAtPortStatsInFwdReqs		Counter,
		accAtPortStatsFwdBcasts		Counter,
		accAtPortStatsNoFwdRoutes	Counter,
		accAtPortStatsHopCounts		Counter,
		accAtPortStatsReflects		Counter,
		accAtPortStatsOutTotals		Counter,
		accAtPortStatsOutShorts		Counter,
		accAtPortStatsOutFwdReqs	Counter,
		accAtPortStatsInErrors		Counter,
		accAtPortStatsOutErrors		Counter
     }
     accAtPortStatsInTotals OBJECT-TYPE
		SYNTAX	Counter
		ACCESS	read-only
		STATUS	mandatory
		DESCRIPTION
		 " The total number of DDP packets received via the port."
		::= { accAtPortStatsEntry 1 }
     accAtPortStatsInShorts OBJECT-TYPE
		SYNTAX	Counter
		ACCESS	read-only
		STATUS	mandatory
		DESCRIPTION
		 " The total number of DDP packets received with short
		   headers."
		::= { accAtPortStatsEntry 2 }
     accAtPortStatsNotForMes OBJECT-TYPE
		SYNTAX	Counter
		ACCESS	read-only
		STATUS	mandatory
		DESCRIPTION
		 " The number of Phase 1 unicast packets received with a
		   LLAP header whose destination node id did not match
		   that of the receiving port."
		::= { accAtPortStatsEntry 3 }
     accAtPortStatsTooShorts OBJECT-TYPE
		SYNTAX	Counter
		ACCESS	read-only
		STATUS	mandatory
		DESCRIPTION
		 " The number of DDP packets received whose length was
		   less than that of a DDP header or whose physical length
		   was less than the logical length."
		::= { accAtPortStatsEntry 4 }
     accAtPortStatsTooLongs OBJECT-TYPE
		SYNTAX	Counter
		ACCESS	read-only
		STATUS	mandatory
		DESCRIPTION
		 " The number of of DDP packets received whose length
		   exceeded the maximum datagram size or whose physical
		   length was greater than the logical length."
		::= { accAtPortStatsEntry 5 }
     accAtPortStatsChksums OBJECT-TYPE
		SYNTAX	Counter
		ACCESS	read-only
		STATUS	mandatory
		DESCRIPTION
		 " The number of DDP packets received with an invalid
		   checksum."
		::= { accAtPortStatsEntry 6 }
     accAtPortStatsNotMyNets OBJECT-TYPE
		SYNTAX	Counter
		ACCESS	read-only
		STATUS	mandatory
		DESCRIPTION
		 " The number of DDP broadcast packets received whose
		   destination network number was within the range of the
		   connected network but which did not match the network
		   number assigned to the port."
		::= { accAtPortStatsEntry 7 }
     accAtPortStatsInFwdReqs OBJECT-TYPE
		SYNTAX	Counter
		ACCESS	read-only
		STATUS	mandatory
		DESCRIPTION
		 " The number of DDP packets received which were not
		   addressed to the receiving port (although some may
		   have been addressed to another port on the same
		   router)."
		::= { accAtPortStatsEntry 8 }
     accAtPortStatsFwdBcasts OBJECT-TYPE
		SYNTAX	Counter
		ACCESS	read-only
		STATUS	mandatory
		DESCRIPTION
		 " The number of DDP broadcast packets receive whose
		   destination network number was not within the range
		   of the connected network."
		::= { accAtPortStatsEntry 9 }
     accAtPortStatsNoFwdRoutes OBJECT-TYPE
		SYNTAX	Counter
		ACCESS	read-only
		STATUS	mandatory
		DESCRIPTION
		 " The number of DDP packets received for which no route
		   to the destination network existed."
		::= { accAtPortStatsEntry 10 }
     accAtPortStatsHopCounts OBJECT-TYPE
		SYNTAX	Counter
		ACCESS	read-only
		STATUS	mandatory
		DESCRIPTION
		 " The number of DDP packets received which were discarded
		   because the hop count had exceeded the maximum value."
		::= { accAtPortStatsEntry 11 }
     accAtPortStatsReflects OBJECT-TYPE
		SYNTAX	Counter
		ACCESS	read-only
		STATUS	mandatory
		DESCRIPTION
		 " The number of DDP packets received which were addressed
		   to another node on the same network."
		::= { accAtPortStatsEntry 12 }
     accAtPortStatsOutTotals OBJECT-TYPE
		SYNTAX	Counter
		ACCESS	read-only
		STATUS	mandatory
		DESCRIPTION
		 " The total number of DDP packets sent via the port."
		::= { accAtPortStatsEntry 13 }
     accAtPortStatsOutShorts OBJECT-TYPE
		SYNTAX	Counter
		ACCESS	read-only
		STATUS	mandatory
		DESCRIPTION
		 " The number of DDP packets send with short headers."
		::= { accAtPortStatsEntry 14 }
     accAtPortStatsOutFwdReqs OBJECT-TYPE
		SYNTAX	Counter
		ACCESS	read-only
		STATUS	mandatory
		DESCRIPTION
		 " The number of DDP packets forwarded to this port from
		   all other ports."
		::= { accAtPortStatsEntry 15 }
     accAtPortStatsInErrors OBJECT-TYPE
		SYNTAX	Counter
		ACCESS	read-only
		STATUS	mandatory
		DESCRIPTION
		 " The number of DDP packets received which could not be
		   processed because of some internal error."
		::= { accAtPortStatsEntry 16 }
     accAtPortStatsOutErrors OBJECT-TYPE
		SYNTAX	Counter
		ACCESS	read-only
		STATUS	mandatory
		DESCRIPTION
		 " The number of DDP packets which could not be sent
		   because of some internal error."
		::= { accAtPortStatsEntry 17 }
     -- The AtRtmpStats Group
     accAtRtmpStats OBJECT IDENTIFIER ::= { accAt 9 }
		-- Routing Table Maintenance Protocol (RTMP) statistics
		-- maintained and reported on a per-node basis.
     accAtRtmpStatsInRequests OBJECT-TYPE
		SYNTAX	Counter
		ACCESS	read-only
		STATUS	mandatory
		DESCRIPTION
		 " The number of RTMP request packets received."
		::= { accAtRtmpStats 1 }
     accAtRtmpStatsInDataReqs OBJECT-TYPE
		SYNTAX	Counter
		ACCESS	read-only
		STATUS	mandatory
		DESCRIPTION
		 " The number of RTMP route data request packets received."
		::= { accAtRtmpStats 2 }
     accAtRtmpStatsInResponses OBJECT-TYPE
		SYNTAX	Counter
		ACCESS	read-only
		STATUS	mandatory
		DESCRIPTION
		 " The number of RTMP response packets received."
		::= { accAtRtmpStats 3 }
     accAtRtmpStatsInDataResps OBJECT-TYPE
		SYNTAX	Counter
		ACCESS	read-only
		STATUS	mandatory
		DESCRIPTION
		 " The number of RTMP route data response packets received."
		::= { accAtRtmpStats 4 }
     accAtRtmpStatsOutRequests OBJECT-TYPE
		SYNTAX	Counter
		ACCESS	read-only
		STATUS	mandatory
		DESCRIPTION
		 " The number of RTMP request packets sent."
		::= { accAtRtmpStats 5 }
     accAtRtmpStatsOutDataReqs OBJECT-TYPE
		SYNTAX	Counter
		ACCESS	read-only
		STATUS	mandatory
		DESCRIPTION
		 " The number of RTMP route data request packets sent."
		::= { accAtRtmpStats 6 }
     accAtRtmpStatsOutResponses OBJECT-TYPE
		SYNTAX	Counter
		ACCESS	read-only
		STATUS	mandatory
		DESCRIPTION
		 " The number of RTMP response packets sent."
		::= { accAtRtmpStats 7 }
     accAtRtmpStatsOutDataResps OBJECT-TYPE
		SYNTAX	Counter
		ACCESS	read-only
		STATUS	mandatory
		DESCRIPTION
		 " The number of RTMP route data response packets sent."
		::= { accAtRtmpStats 8 }
     accAtRtmpStatsNetConflicts OBJECT-TYPE
		SYNTAX	Counter
		ACCESS	read-only
		STATUS	mandatory
		DESCRIPTION
		 " The number of RTMP packets received which conflicted
		   with the network number range configured for the
		   receiving port or garnered from another router."
		::= { accAtRtmpStats 9 }
     accAtRtmpStatsInErrors OBJECT-TYPE
		SYNTAX	Counter
		ACCESS	read-only
		STATUS	mandatory
		DESCRIPTION
		 " The number of RTMP packets received containing a
		   format error or which could not be processed because
		   of some internal error."
		::= { accAtRtmpStats 10 }
     accAtRtmpStatsOutErrors OBJECT-TYPE
		SYNTAX	Counter
		ACCESS	read-only
		STATUS	mandatory
		DESCRIPTION
		 " The number of RTMP packets which could not be sent
		   because of some internal error."
		::= { accAtRtmpStats 11 }
     -- The AtRdbStats Group
     accAtRdbStats OBJECT IDENTIFIER ::= { accAt 10 }
		-- Routing database statistics maintained and reported
		-- on a per-node basis.
     accAtRdbStatsCacheds OBJECT-TYPE
		SYNTAX	Counter
		ACCESS	read-only
		STATUS	mandatory
		DESCRIPTION
		 " The number of times the desired route was already
		   cached."
		::= { accAtRdbStats 1 }
     accAtRdbStatsSearchs OBJECT-TYPE
		SYNTAX	Counter
		ACCESS	read-only
		STATUS	mandatory
		DESCRIPTION
		 " The number of times the desired route was not cached
		   and the routing database had to be searched."
		::= { accAtRdbStats 2 }
     accAtRdbStatsNoRoutes OBJECT-TYPE
		SYNTAX	Counter
		ACCESS	read-only
		STATUS	mandatory
		DESCRIPTION
		 " The number of times no route could be found to the
		   destination network."
		::= { accAtRdbStats 3 }
     accAtRdbStatsAdds OBJECT-TYPE
		SYNTAX	Counter
		ACCESS	read-only
		STATUS	mandatory
		DESCRIPTION
		 " The number of times a new network was added to the
		   routing database."
		::= { accAtRdbStats 4 }
     accAtRdbStatsUpdates OBJECT-TYPE
		SYNTAX	Counter
		ACCESS	read-only
		STATUS	mandatory
		DESCRIPTION
		 " The number of times an existing route was updated."
		::= { accAtRdbStats 5 }
     accAtRdbStatsDeletes OBJECT-TYPE
		SYNTAX	Counter
		ACCESS	read-only
		STATUS	mandatory
		DESCRIPTION
		 " The number of times a route was deleted from the
		   routing database."
		::= { accAtRdbStats 6 }
     -- The AtNbpStats Group
     accAtNbpStats OBJECT IDENTIFIER ::= { accAt 11 }
		-- Name Binding Protocol (NBP) statistics maintained and
		-- reported on a per-node basis.
     accAtNbpStatsInBrReqs OBJECT-TYPE
		SYNTAX	Counter
		ACCESS	read-only
		STATUS	mandatory
		DESCRIPTION
		 " The number of NBP broadcast request packets received."
		::= { accAtNbpStats 1 }
     accAtNbpStatsInLkUpReqs OBJECT-TYPE
		SYNTAX	Counter
		ACCESS	read-only
		STATUS	mandatory
		DESCRIPTION
		 " The number of NBP lookup request packets received."
		::= { accAtNbpStats 2 }
     accAtNbpStatsInLkUpResps OBJECT-TYPE
		SYNTAX	Counter
		ACCESS	read-only
		STATUS	mandatory
		DESCRIPTION
		 " The number of NBP lookup response packets received."
		::= { accAtNbpStats 3 }
     accAtNbpStatsInFwdReqs OBJECT-TYPE
		SYNTAX	Counter
		ACCESS	read-only
		STATUS	mandatory
		DESCRIPTION
		 " The number of NBP forward request packets received."
		::= { accAtNbpStats 4 }
     accAtNbpStatsOutBrReqs OBJECT-TYPE
		SYNTAX	Counter
		ACCESS	read-only
		STATUS	mandatory
		DESCRIPTION
		 " The number of NBP broadcast request packets sent."
		::= { accAtNbpStats 5 }
     accAtNbpStatsOutLkUpReqs OBJECT-TYPE
		SYNTAX	Counter
		ACCESS	read-only
		STATUS	mandatory
		DESCRIPTION
		 " The number of NBP lookup request packets sent."
		::= { accAtNbpStats 6 }
     accAtNbpStatsOutLkUpResps OBJECT-TYPE
		SYNTAX	Counter
		ACCESS	read-only
		STATUS	mandatory
		DESCRIPTION
		 " The number of NBP lookup response packets sent."
		::= { accAtNbpStats 7 }
     accAtNbpStatsOutFwdReqs OBJECT-TYPE
		SYNTAX	Counter
		ACCESS	read-only
		STATUS	mandatory
		DESCRIPTION
		 " The number of NBP forward request packets sent."
		::= { accAtNbpStats 8 }
     accAtNbpStatsNoZones OBJECT-TYPE
		SYNTAX	Counter
		ACCESS	read-only
		STATUS	mandatory
		DESCRIPTION
		 " The number of NBP request packets received which
		   referenced a zone name which was not in the zone
		   database."
		::= { accAtNbpStats 9 }
     accAtNbpStatsInErrors OBJECT-TYPE
		SYNTAX	Counter
		ACCESS	read-only
		STATUS	mandatory
		DESCRIPTION
		 " The number of NBP packets received which were invalid
		   or which could not be processed because of some internal
		   error."
		::= { accAtNbpStats 10 }
     accAtNbpStatsOutErrors OBJECT-TYPE
		SYNTAX	Counter
		ACCESS	read-only
		STATUS	mandatory
		DESCRIPTION
		 " The number of NBP packets which could not be sent
		   because of some internal error."
		::= { accAtNbpStats 11 }
     -- The AtZipStats Group
     accAtZipStats OBJECT IDENTIFIER ::= { accAt 12 }
		-- Zone Information Protocol (ZIP) statistics maintained
		-- and reported on a per-node basis.
     accAtZipStatsInQuerys OBJECT-TYPE
		SYNTAX	Counter
		ACCESS	read-only
		STATUS	mandatory
		DESCRIPTION
		 " The number of ZIP zone-list-query packets received."
		::= { accAtZipStats 1 }
     accAtZipStatsInReplies OBJECT-TYPE
		SYNTAX	Counter
		ACCESS	read-only
		STATUS	mandatory
		DESCRIPTION
		 " The number of ZIP zone-list-reply packets received."
		::= { accAtZipStats 2 }
     accAtZipStatsInExtReplies OBJECT-TYPE
		SYNTAX	Counter
		ACCESS	read-only
		STATUS	mandatory
		DESCRIPTION
		 " The number of ZIP extended zone-list-reply packets
		   received."
		::= { accAtZipStats 3 }
     accAtZipStatsInInfoReqs OBJECT-TYPE
		SYNTAX	Counter
		ACCESS	read-only
		STATUS	mandatory
		DESCRIPTION
		 " The number of ZIP get-network-information request
		   packets received."
		::= { accAtZipStats 4 }
     accAtZipStatsInInfoReps OBJECT-TYPE
		SYNTAX	Counter
		ACCESS	read-only
		STATUS	mandatory
		DESCRIPTION
		 " The number of ZIP get-network-information reply
		   packets received."
		::= { accAtZipStats 5 }
     accAtZipStatsInTakeDowns OBJECT-TYPE
		SYNTAX	Counter
		ACCESS	read-only
		STATUS	mandatory
		DESCRIPTION
		 " The number of ZIP take-down request packets received."
		::= { accAtZipStats 6 }
     accAtZipStatsInBringUps OBJECT-TYPE
		SYNTAX	Counter
		ACCESS	read-only
		STATUS	mandatory
		DESCRIPTION
		 " The number of ZIP bring-up request packets received."
		::= { accAtZipStats 7 }
     accAtZipStatsInNotifies OBJECT-TYPE
		SYNTAX	Counter
		ACCESS	read-only
		STATUS	mandatory
		DESCRIPTION
		 " The number of ZIP notify request packets received."
		::= { accAtZipStats 8 }
     accAtZipStatsInGetZLReqs OBJECT-TYPE
		SYNTAX	Counter
		ACCESS	read-only
		STATUS	mandatory
		DESCRIPTION
		 " The number of ZIP get-zone-list request packets
		   received."
		::= { accAtZipStats 9 }
     accAtZipStatsInGetLZReqs OBJECT-TYPE
		SYNTAX	Counter
		ACCESS	read-only
		STATUS	mandatory
		DESCRIPTION
		 " The number of ZIP get-local-zones request packets
		   received."
		::= { accAtZipStats 10 }
     accAtZipStatsInGetMZReqs OBJECT-TYPE
		SYNTAX	Counter
		ACCESS	read-only
		STATUS	mandatory
		DESCRIPTION
		 " The number of ZIP get-my-zone request packets received."
		::= { accAtZipStats 11 }
     accAtZipStatsOutQueries OBJECT-TYPE
		SYNTAX	Counter
		ACCESS	read-only
		STATUS	mandatory
		DESCRIPTION
		 " The number of ZIP zone-list-query packets sent."
		::= { accAtZipStats 12 }
     accAtZipStatsOutReplies OBJECT-TYPE
		SYNTAX	Counter
		ACCESS	read-only
		STATUS	mandatory
		DESCRIPTION
		 " The number of ZIP zone-list-reply packets sent."
		::= { accAtZipStats 13 }
     accAtZipStatsOutExtReplies OBJECT-TYPE
		SYNTAX	Counter
		ACCESS	read-only
		STATUS	mandatory
		DESCRIPTION
		 " The number of ZIP extended zone-list-reply packets
		   sent."
		::= { accAtZipStats 14 }
     accAtZipStatsOutInfoReqs OBJECT-TYPE
		SYNTAX	Counter
		ACCESS	read-only
		STATUS	mandatory
		DESCRIPTION
		 " The number of ZIP get-network-information request
		   packets sent."
		::= { accAtZipStats 15 }
     accAtZipStatsOutInfoReps OBJECT-TYPE
		SYNTAX	Counter
		ACCESS	read-only
		STATUS	mandatory
		DESCRIPTION
		 " The number of ZIP get-network-information reply
		   packets sent."
		::= { accAtZipStats 16 }
     accAtZipStatsOutGetZLReps OBJECT-TYPE
		SYNTAX	Counter
		ACCESS	read-only
		STATUS	mandatory
		DESCRIPTION
		 " The number of get-zone-list reply packets sent."
		::= { accAtZipStats 17 }
     accAtZipStatsOutGetLZReps OBJECT-TYPE
		SYNTAX	Counter
		ACCESS	read-only
		STATUS	mandatory
		DESCRIPTION
		 " The number of get-local-zones reply packets sent."
		::= { accAtZipStats 18 }
     accAtZipStatsOutGetMZReps OBJECT-TYPE
		SYNTAX	Counter
		ACCESS	read-only
		STATUS	mandatory
		DESCRIPTION
		 " The number of get-my-zone reply packets sent."
		::= { accAtZipStats 19 }
     accAtZipStatsZoneConflicts OBJECT-TYPE
		SYNTAX	Counter
		ACCESS	read-only
		STATUS	mandatory
		DESCRIPTION
		 " The number of ZIP packets received which conflicted
		   with zone list or default zone information configured
		   for the receiving port or garnered from another router."
		::= { accAtZipStats 20 }
     accAtZipStatsInErrors OBJECT-TYPE
		SYNTAX	Counter
		ACCESS	read-only
		STATUS	mandatory
		DESCRIPTION
		 " The number of ZIP packets received containing a
		   formatting error or which could not be processed
		   because of some internal error."
		::= { accAtZipStats 21 }
     accAtZipStatsOutErrors OBJECT-TYPE
		SYNTAX	Counter
		ACCESS	read-only
		STATUS	mandatory
		DESCRIPTION
		 " The number of ZIP packets which could not be sent
		   because of some internal error."
		::= { accAtZipStats 22 }
     -- The AtAepStats Group
     accAtAepStats OBJECT IDENTIFIER ::= { accAt 13 }
		-- AppleTalk Echo Protocol (AEP) statistics maintained
		-- and reported on a per-node basis.
     accAtAepStatsInErrors OBJECT-TYPE
		SYNTAX	Counter
		ACCESS	read-only
		STATUS	mandatory
		DESCRIPTION
		 " The number of AEP packets received which were invalid
		   or which could not be processed because of some internal
		   error."
		::= { accAtAepStats 1 }
     accAtAepStatsOutErrors OBJECT-TYPE
		SYNTAX	Counter
		ACCESS	read-only
		STATUS	mandatory
		DESCRIPTION
		 " The number of AEP packets which could not be sent
		   because of some internal error."
		::= { accAtAepStats 2 }
     -- The AtZoneListTable Group
     accAtZoneListTable OBJECT-TYPE
		SYNTAX	SEQUENCE OF AccAtZoneListEntry
		ACCESS	not-accessible
		STATUS	mandatory
		DESCRIPTION
		 " The zones list table for directly-connected AppleTalk
		   networks.  AppleTalk networks which are configured in
		   the network table have their zones list configured
		   here.  Zone names for individual networks are inter-
		   mingled in this table. "
		::= { accAt 14 }
     accAtZoneListEntry OBJECT-TYPE
		SYNTAX	AccAtZoneListEntry
		ACCESS	not-accessible
		STATUS	mandatory
		DESCRIPTION
		 " An entry defining a zone name for some directly
		   connected AppleTalk network."
                INDEX { accAtZoneListPort,
                            accAtZoneListName }
		::= { accAtZoneListTable 1 }
     AccAtZoneListEntry ::= SEQUENCE {
		accAtZoneListPort		INTEGER,
		accAtZoneListStatus		INTEGER,
		accAtZoneListName		DisplayString	
     }
     accAtZoneListPort OBJECT-TYPE
		SYNTAX	INTEGER (1..255)
		ACCESS	read-only
		STATUS	mandatory
		DESCRIPTION
		 " The logical port number."
		::= { accAtZoneListEntry 1 }
     accAtZoneListStatus OBJECT-TYPE
		SYNTAX	INTEGER {
			configured(1),
			default(2),
			invalid(3)
		}
		ACCESS	read-write
		STATUS	mandatory
		DESCRIPTION
		 " The status of the zone list entry.  If set to
		   default(2), the entry defines the default zone.
		   Entries are deleted by setting the entry status
		   to invalid(3)."
		::= { accAtZoneListEntry 2 }
     accAtZoneListName OBJECT-TYPE
		SYNTAX  DisplayString	
		ACCESS	read-only
		STATUS	mandatory
		DESCRIPTION
		 " The zone name.  Zone names can contain up to 32
		   case-insensitive characters from the Apple Macintosh
		   character set."
		::= { accAtZoneListEntry 3 }
     -- The AtZoneBynameTable Group
     accAtZoneBynameTable OBJECT-TYPE
		SYNTAX	SEQUENCE OF AccAtZoneBynameEntry
		ACCESS	not-accessible
		STATUS	mandatory
		DESCRIPTION
		 " Used to display entries in the Zone Information
		   Table (ZIT) which are associated with a particular
		   zone name."
		::= { accAt 15 }
     accAtZoneBynameEntry OBJECT-TYPE
		SYNTAX	AccAtZoneBynameEntry
		ACCESS	not-accessible
		STATUS	mandatory
		DESCRIPTION
		 " An entry in the zone information table (ZIT) with a
		   given zone name."
                INDEX { accAtZoneBynameNetMin,
		            accAtZoneBynameName }
		::= { accAtZoneBynameTable 1 }
     AccAtZoneBynameEntry ::= SEQUENCE {
		accAtZoneBynameNetMin		OCTET STRING,
		accAtZoneBynameNetMax		OCTET STRING,
		accAtZoneBynameName		DisplayString	
     }
     accAtZoneBynameNetMin OBJECT-TYPE
		SYNTAX	OCTET STRING
		ACCESS	read-only
		STATUS	mandatory
		DESCRIPTION
		 " The 16-bit range start value for an AppleTalk network."
		::= { accAtZoneBynameEntry 1 }
     accAtZoneBynameNetMax OBJECT-TYPE
		SYNTAX	OCTET STRING
		ACCESS	read-only
		STATUS	mandatory
		DESCRIPTION
		 " The 16-bit range end value for an AppleTalk network."
		::= { accAtZoneBynameEntry 2 }
     accAtZoneBynameName OBJECT-TYPE
		SYNTAX  DisplayString	
		ACCESS	read-only
		STATUS	mandatory
		DESCRIPTION
		 " The AppleTalk zone name."
		::= { accAtZoneBynameEntry 3 }
     -- The AtZoneBynetTable Group
     accAtZoneBynetTable OBJECT-TYPE
		SYNTAX	SEQUENCE OF AccAtZoneBynetEntry
		ACCESS	not-accessible
		STATUS	mandatory
		DESCRIPTION
		 " Used to display entries in the Zone Information
		   Table (ZIT) which are associated with a particular
		   AppleTalk network."
		::= { accAt 16 }
     accAtZoneBynetEntry OBJECT-TYPE
		SYNTAX	AccAtZoneBynetEntry
		ACCESS	not-accessible
		STATUS	mandatory
		DESCRIPTION
		 " An entry in the zone information table (ZIT) associated
		   with a given AppleTalk network."
                INDEX { accAtZoneBynameNetMin,
		            accAtZoneBynameName }
		::= { accAtZoneBynetTable 1 }
     AccAtZoneBynetEntry ::= SEQUENCE {
		accAtZoneBynetNetMin		OCTET STRING,
		accAtZoneBynetNetMax		OCTET STRING,
		accAtZoneBynetName		DisplayString	
     }
     accAtZoneBynetNetMin OBJECT-TYPE
		SYNTAX	OCTET STRING
		ACCESS	read-only
		STATUS	mandatory
		DESCRIPTION
		 " The 16-bit range start value for an AppleTalk network."
		::= { accAtZoneBynetEntry 1 }
     accAtZoneBynetNetMax OBJECT-TYPE
		SYNTAX	OCTET STRING
		ACCESS	read-only
		STATUS	mandatory
		DESCRIPTION
		 " The 16-bit range end value for an AppleTalk network."
		::= { accAtZoneBynetEntry 2 }
     accAtZoneBynetName OBJECT-TYPE
		SYNTAX  DisplayString	
		ACCESS	read-only
		STATUS	mandatory
		DESCRIPTION
		 " The AppleTalk zone name."
		::= { accAtZoneBynetEntry 3 }
--  AppleTalk Forwarding Filter Table
--	AppleTalk Filters are of the form:
--
--	if message is within
--		to-address-range
--		from-address-range
--		socket-range
--		AppleTalk Application
--	then
--		{DISCARD | LOW | NORMAL | HIGH}
     accAtForwardFilterTable OBJECT-TYPE
         SYNTAX   SEQUENCE OF AccAtForwardFilterEntry
         ACCESS   not-accessible
         STATUS   mandatory
         DESCRIPTION
              " A list of descriptions of specific AppleTalk Filters."
         ::= { accAt 17 }
        accAtForwardFilterEntry OBJECT-TYPE
            SYNTAX   AccAtForwardFilterEntry
            ACCESS   not-accessible
            STATUS   mandatory
            DESCRIPTION
                  " The parameters for a single AppleTalk Filter."
            INDEX { accAtForwardFilterToMin, 
                accAtForwardFilterToMax,
	        accAtForwardFilterFromMin, 
                accAtForwardFilterFromMax,
	        accAtForwardFilterSocketMin, 
                accAtForwardFilterSocketMax,
	        accAtForwardFilterType }
            ::= { accAtForwardFilterTable 1 }
        AccAtForwardFilterEntry ::=
            SEQUENCE {
                accAtForwardFilterToMin
                    OCTET STRING,
                accAtForwardFilterToMax
                    OCTET STRING,
                accAtForwardFilterFromMin
                    OCTET STRING,
                accAtForwardFilterFromMax
                    OCTET STRING,
                accAtForwardFilterSocketMin
                    INTEGER,
                accAtForwardFilterSocketMax
                    INTEGER,
                accAtForwardFilterType
                    INTEGER,
                accAtForwardFilterDisposition
                    INTEGER,
                accAtForwardFilterStatus
                    INTEGER
	        }
           accAtForwardFilterToMin OBJECT-TYPE
               SYNTAX   OCTET STRING -- (SIZE(2))
               ACCESS   read-write
               STATUS   mandatory
               DESCRIPTION
                   "  The least value in the destination network address range."
               ::= { accAtForwardFilterEntry 1 }
           accAtForwardFilterToMax OBJECT-TYPE
               SYNTAX   OCTET STRING  -- (SIZE(2))
               ACCESS   read-write
               STATUS   mandatory
               DESCRIPTION
                     " The greatest value in the destination network address range."
               ::= { accAtForwardFilterEntry 2 }
           accAtForwardFilterFromMin OBJECT-TYPE
               SYNTAX   OCTET STRING  -- (SIZE(2))
               ACCESS   read-write
               STATUS   mandatory
               DESCRIPTION
                     " The least value in the source network address range."
               ::= { accAtForwardFilterEntry 3 }
           accAtForwardFilterFromMax OBJECT-TYPE
               SYNTAX   OCTET STRING  -- (SIZE(2))
               ACCESS   read-write
               STATUS   mandatory
               DESCRIPTION
                    " The greatest value in the source network address range."
               ::= { accAtForwardFilterEntry 4 }
           accAtForwardFilterSocketMin OBJECT-TYPE
               SYNTAX   INTEGER (0..255)
               ACCESS   read-write
               STATUS   mandatory
               DESCRIPTION
                    " The least value in the range of affected sockets."
               ::= { accAtForwardFilterEntry 5 }
           accAtForwardFilterSocketMax OBJECT-TYPE
               SYNTAX   INTEGER (0..255)
               ACCESS   read-write
               STATUS   mandatory
               DESCRIPTION
                    " The greatest value in the range of affected sockets."
               ::= { accAtForwardFilterEntry 6 }
           accAtForwardFilterType OBJECT-TYPE
               SYNTAX   INTEGER {
                           any(1),	-- all traffic
                           nbp(2),	-- Name Binding Protocol
                           atp(3),	-- Transaction Protocol
                           aep(4),	-- Echo Protocol
                           rtmp(5),	-- Routing Table Management Protocol
				-- request/response (type 5) or
				-- update (type 1)
                           zip(6),	-- Zone Information Protocol
		           adsp(7),	-- Data Stream Protocol
                           nbpBroadcast(8),
                           nbpRequest(9),	
                           nbpResponse(10),
                           nbpForwardRequest(11)
                        }
               ACCESS   read-write
               STATUS   mandatory
               DESCRIPTION
                       " The affected message types.
                         Name Binding Protocol messages are called out separately,
                         as some applications call for selective discrimination."
               ::= { accAtForwardFilterEntry 7 }
           accAtForwardFilterDisposition OBJECT-TYPE
               SYNTAX   INTEGER (0..3)
               ACCESS   read-write
               STATUS   mandatory
               DESCRIPTION
                      " Upon a filter match, this specifies the action taken.
                           discard(0),
                           lowPriority(1),
                           normalPriority(2),
                           highPriority(3)
			"
               ::= { accAtForwardFilterEntry 8 }
           accAtForwardFilterStatus OBJECT-TYPE
               SYNTAX   INTEGER {
                           invalid(1),
                           valid(2)
                        }
               ACCESS   read-write
               STATUS   mandatory
               DESCRIPTION
                     " Writing 'invalid' deletes the filter table entry."
               ::= { accAtForwardFilterEntry 9 }
--  AppleTalk Route Filter
--	AppleTalk Route Filters are of the form:
--
--	if an update is received from someone in the range
--		router-address-range
--	and it advertises an address range
--		address-range
--	then
--		{ ACCEPT | REJECT } the range
--
--	it is expected that neighboring routers may advertise
--	ranges that don't exactly overlap.  It is expected that
--	advertised ranges that include both rejected and accepted
--	subranges will be treated as a succession of more limited
--	advertisements, each entirely accepted or rejected.
     accAtRouteFilterTable OBJECT-TYPE
         SYNTAX   SEQUENCE OF AccAtRouteFilterEntry
         ACCESS   not-accessible
         STATUS   mandatory
         DESCRIPTION
             "  A list of Route Filters."
         ::= { accAt 18 }
        accAtRouteFilterEntry OBJECT-TYPE
            SYNTAX   AccAtRouteFilterEntry
            ACCESS   not-accessible
            STATUS   mandatory
            DESCRIPTION
                 " A single Route Filter."
            INDEX { accAtRouteFilterRouterMin, 
                accAtRouteFilterRouterMax,
	        accAtRouteFilterRangeMin, 
                accAtRouteFilterRangeMax }
            ::= { accAtRouteFilterTable 1 }
        AccAtRouteFilterEntry ::=
            SEQUENCE {
                accAtRouteFilterRouterMin
                    OCTET STRING,
                accAtRouteFilterRouterMax
                    OCTET STRING,
                accAtRouteFilterRangeMin
                    OCTET STRING,
                accAtRouteFilterRangeMax
                    OCTET STRING,
                accAtRouteFilterDisposition
                    INTEGER,
                accAtRouteFilterStatus
                    INTEGER
	        }
           accAtRouteFilterRouterMin OBJECT-TYPE
               SYNTAX   OCTET STRING  -- (SIZE(2))
               ACCESS   read-write
               STATUS   mandatory
               DESCRIPTION
                    " The least affected Router's Network Address."
               ::= { accAtRouteFilterEntry 1 }
           accAtRouteFilterRouterMax OBJECT-TYPE
               SYNTAX   OCTET STRING  -- (SIZE(2))
               ACCESS   read-write
               STATUS   mandatory
               DESCRIPTION
                 " The greatest affected Router's Network Address."
               ::= { accAtRouteFilterEntry 2 }
           accAtRouteFilterRangeMin OBJECT-TYPE
               SYNTAX   OCTET STRING  -- (SIZE(2))
               ACCESS   read-write
               STATUS   mandatory
               DESCRIPTION
                  " The least Network Address in this range."
               ::= { accAtRouteFilterEntry 3 }
           accAtRouteFilterRangeMax OBJECT-TYPE
               SYNTAX   OCTET STRING  -- (SIZE(2))
               ACCESS   read-write
               STATUS   mandatory
               DESCRIPTION
                    " The greatest Network Address in this range."
               ::= { accAtRouteFilterEntry 4 }
           accAtRouteFilterDisposition OBJECT-TYPE
               SYNTAX   INTEGER {
                           accept(1),
                           reject(2)
                        }
               ACCESS   read-write
               STATUS   mandatory
               DESCRIPTION
                     " What is to be done with matching advertisements."
               ::= { accAtRouteFilterEntry 5 }
           accAtRouteFilterStatus OBJECT-TYPE
               SYNTAX   INTEGER {
                           invalid(1),
                           valid(2)
                        }
               ACCESS   read-write
               STATUS   mandatory
               DESCRIPTION
                   " Writing 'invalid' has the effect of deleting the filter."
               ::= { accAtRouteFilterEntry 6 }
-- Bootp Group
accBootp        OBJECT IDENTIFIER ::= { accBRG 29 }
-- These objects are being deprecated because they were improperly defined
-- when first implemented.
accBootServerOld OBJECT IDENTIFIER ::= { accBootp 1 }
            accBootpServerOld   OBJECT-TYPE   
                        SYNTAX  IpAddress
                        ACCESS  read-only
                        STATUS  mandatory
                        DESCRIPTION
                 " IP address of the Bootp Server."
                        ::= { accBootServerOld 1 }
-- end of deprecated objects
	accBootMode		OBJECT-TYPE
			SYNTAX	 INTEGER {
				automatic(1),
				forced(2),
				off(3),
				default(4)
				}
			 ACCESS  read-only
			 STATUS  mandatory
			 DESCRIPTION
		" Mode of operation on unit boot-up.
		  Automatic - stored configuration information is ignored and
		  configuration is sought from the last known server or via
		  BOOTP if no previous server information is known.
		  Forced - stored configuration information is ignored and
		  configuration information is sought via BOOTP.
		  Off - stored configuration information is used."
			::= { accBootp 2}
	accBootState		OBJECT-TYPE
			SYNTAX INTEGER {
				initial(1),
				disabled(2),
				requesting(3),
				waiting(4),
				configuring(5),
				complete(6),
				failed(7)
				}
			ACCESS  read-only
			STATUS  mandatory
			DESCRIPTION
		"The state of Bootp client operation:
		 initial - client initializing after start-up.
		 disabled - client operation is disabled (Boot Mode Off).
		 requesting - BootP requests are being generated.
		 waiting - waiting between request generation phases.
		 configuring - Bootp response has been received and a
	 	 configuration is being downloaded and executed.
		 complete - configuration is complete.
		 failed - configuration download or execution has failed."
			 ::= { accBootp 3}
	accBootyiaddr		OBJECT-TYPE
			SYNTAX IpAddress
			ACCESS	read-only
			STATUS	mandatory
			DESCRIPTION
		"The value of yiaddr returned in the last Bootp reply
		 processed.  This is the address used by the unit
		 as its address in the TFTP download of a configuration
		 script file."
			 ::= { accBootp 4}
	accBootsiaddr		OBJECT-TYPE
			SYNTAX IpAddress
			ACCESS	read-only
			STATUS	mandatory
			DESCRIPTION
		"The value of siaddr returned in the last Bootp reply
		 processed.  This is the address used by the unit
		 as the server address from which the TFTP download of 
		 a configuration script file is attempted."
			 ::= { accBootp 5}
	accBootsname		OBJECT-TYPE
			SYNTAX	DisplayString
			ACCESS	read-only
			STATUS	mandatory
			DESCRIPTION
		"The value of siaddr returned in the last Bootp reply
		 processed.  This is the name of the Bootp server."
			 ::= { accBootp 6}
-- This object is being replaced by the three gateway addresses below
	accBootgiaddr		OBJECT-TYPE
			SYNTAX IpAddress
			ACCESS	read-only
			STATUS	deprecated
			DESCRIPTION
		"The value of giaddr returned in the last Bootp reply
		 processed.  This is the address used by the unit
		 as the address of any intermediate gateway between
		 the unit and the Bootp server during the download
		 of the configuration script file."
			 ::= { accBootp 7}
	accBootfile		OBJECT-TYPE
			SYNTAX	DisplayString
			ACCESS	read-only
			STATUS	mandatory
			DESCRIPTION
		"The value of file returned in the last Bootp reply
		 processed.  This is the name of the file to download
		 as a configuration script."
			 ::= { accBootp 8}
	accBootInterface	OBJECT-TYPE
			SYNTAX  INTEGER
			ACCESS  read-only
			STATUS  mandatory
			DESCRIPTION
		"The interface index for the interface the last valid
		Bootp reply frame processed was received on."
			 ::= { accBootp 9}
	accBootSentRequests	OBJECT-TYPE
			SYNTAX	Counter
			ACCESS	read-only
			STATUS	mandatory
			DESCRIPTION
		"The number of Bootp requests sent."
			 ::= { accBootp 10}
	accBootReceivedReplies	OBJECT-TYPE
			SYNTAX	Counter
			ACCESS	read-only
			STATUS	mandatory
			DESCRIPTION
		"The number of valid Bootp replies received."
			 ::= { accBootp 11}
	accBootDiscardedReplies	OBJECT-TYPE
			SYNTAX	Counter
			ACCESS	read-only
			STATUS	mandatory
			DESCRIPTION
		"The number of Bootp replies discarded due to
		 insufficient data in reply."
			 ::= { accBootp 12}
        accBootServerTable      OBJECT-TYPE
                        SYNTAX  SEQUENCE OF AccBootServerEntry
                        ACCESS  not-accessible
                        STATUS  mandatory
                        DESCRIPTION
                " A table of Bootpstrap protocol servers that this unit
                 will forward Bootp requests to."
                        ::= { accBootp 13}
        accBootServerEntry      OBJECT-TYPE
                        SYNTAX AccBootServerEntry
                        ACCESS not-accessible
                        STATUS mandatory
                        DESCRIPTION
                " A Boot server table entry. "
                        INDEX { IpAddress }
                        ::= { accBootServerTable 1 }
        AccBootServerEntry ::= SEQUENCE {
                                accBootServerIPAddr     IpAddress
                                }
        accBootServerIPAddr     OBJECT-TYPE
                        SYNTAX  IpAddress
                        ACCESS  read-write
                        STATUS  mandatory
                        DESCRIPTION
                " An IP address of a Bootstrap protocol server to be
                 supported by Boot Helper."
                        ::= { accBootServerEntry 1 }
        accBootg1iaddr           OBJECT-TYPE
                        SYNTAX IpAddress
                        ACCESS  read-only
                        STATUS  mandatory
                        DESCRIPTION
                "The value of first giaddr returned in the last Bootp reply
                 processed.  This is the first address used by the unit
                 as the address of any intermediate gateway between
                 the unit and the Bootp server during the download
                 of the configuration script file."
                         ::= { accBootp 14}
        accBootg2iaddr           OBJECT-TYPE
                        SYNTAX IpAddress
                        ACCESS  read-only
                        STATUS  mandatory
                        DESCRIPTION
                "The value of second giaddr returned in the last Bootp reply
                 processed.  This is the second address used by the unit
                 as the address of any intermediate gateway between
                 the unit and the Bootp server during the download
                 of the configuration script file."
                         ::= { accBootp 15}
        accBootg3iaddr           OBJECT-TYPE
                        SYNTAX IpAddress
                        ACCESS  read-only
                        STATUS  mandatory
                        DESCRIPTION
                "The value of third giaddr returned in the last Bootp reply
                 processed.  This is the third address used by the unit
                 as the address of any intermediate gateway between
                 the unit and the Bootp server during the download
                 of the configuration script file."
                         ::= { accBootp 16}
-- Ping Group
      accPing         OBJECT IDENTIFIER ::= { accBRG 30 }
         accPingDest	OBJECT-TYPE 
			SYNTAX  IpAddress
			ACCESS read-write
			STATUS mandatory
			DESCRIPTION
		" IP address of the  destination
		  for generated Ping packets."
			::= { accPing 1 }
         accPingReqCnt	OBJECT-TYPE 
			SYNTAX  INTEGER (0..1000)
			ACCESS read-write
			STATUS mandatory
			DESCRIPTION
		" Count of Ping packets left to be
		  generated.  Setting this variable to a nonzero value
		  causes the Ping generator to be (re)started.  Setting
		  this variable to zero causes the Ping generator to be
		  stopped. "
			::= { accPing 2 }
         accPingDataMin	OBJECT-TYPE 
			SYNTAX  INTEGER (4..1500)
			ACCESS read-write
			STATUS mandatory
			DESCRIPTION
		" Minimum number of data bytes
		  included in the Ping packet.  The first four bytes
		  of data always carry a timestamp, the remaining
		  data is an incrementing byte data pattern. "
			::= { accPing 3 }
         accPingDataMax	OBJECT-TYPE 
			SYNTAX  INTEGER (4..1500)
			ACCESS read-write
			STATUS mandatory
			DESCRIPTION
		" Maximum number of data bytes
		  included in the Ping packet.  If this value is
		  greater than accPingDataMin, the data field length
		  of the Ping packet is a random value between accPingDataMin
		  and accPingDataMax.  Otherwise the data field length
		  is fixed and specified by accPingDataMin. "
			::= { accPing 4 }
         accPingTimeMin	OBJECT-TYPE 
			SYNTAX  INTEGER (0..15)
			ACCESS read-write
			STATUS mandatory
			DESCRIPTION
		" Time (seconds) to delay before
		  generating the next Ping packet, after correctly
		  receiving the expected Ping response for the previously
		  generated Ping packet. "
			::= { accPing 5 }
         accPingTimeMax	OBJECT-TYPE 
			SYNTAX  INTEGER (1..60)
			ACCESS read-write
			STATUS mandatory
			DESCRIPTION
		" Time (seconds) to wait for a
		  correct Ping response before giving up and generating
		  the next Ping packet. "
			::= { accPing 6 }
         accPingSndPkts	OBJECT-TYPE 
			SYNTAX  Counter
			ACCESS read-only
			STATUS mandatory
			DESCRIPTION
		" Number of Ping packets
		  generated since the current Ping activity was initiated. "
			::= { accPing 7 }
         accPingSndBytes	OBJECT-TYPE 
			SYNTAX  Counter
			ACCESS read-only
			STATUS mandatory
			DESCRIPTION
		" Number of Ping data bytes
		  generated since the current Ping activity was initiated. "
			::= { accPing 8 }
         accPingRcvPkts	OBJECT-TYPE 
			SYNTAX  Counter
			ACCESS read-only
			STATUS mandatory
			DESCRIPTION
		" Number of Ping responses
		  received since the current Ping activity was initiated. "
			::= { accPing 9 }
         accPingRcvBytes	OBJECT-TYPE 
			SYNTAX  Counter
			ACCESS read-only
			STATUS mandatory
			DESCRIPTION
		" Number of Ping data bytes
		  received since the current Ping activity was initiated. "
			::= { accPing 10 }
         accPingRcvOKs	OBJECT-TYPE 
			SYNTAX  Counter
			ACCESS read-only
			STATUS mandatory
			DESCRIPTION
		" Number of correct Ping
		  responses received since the current Ping activity was
		  initiated. "
			::= { accPing 11 }
         accPingRcvBads	OBJECT-TYPE 
			SYNTAX  Counter
			ACCESS read-only
			STATUS mandatory
			DESCRIPTION
		" Number of incorrect Ping
		  responses received since the current Ping activity was
		  initiated. "
			::= { accPing 12 }
         accPingDelayMin	OBJECT-TYPE 
			SYNTAX  INTEGER
			ACCESS read-only
			STATUS mandatory
			DESCRIPTION
		" Minimum round trip delay, in
		  milliseconds, experienced by the Ping packet and
		  the Ping response. "
			::= { accPing 13 }
         accPingDelayMax	OBJECT-TYPE 
			SYNTAX  INTEGER
			ACCESS read-only
			STATUS mandatory
			DESCRIPTION
		" Maximum round trip delay, in
		  milliseconds, experienced by the Ping packet and
		  the Ping response. "
			::= { accPing 14 }
         accPingDelayAvg	OBJECT-TYPE 
			SYNTAX  INTEGER
			ACCESS read-only
			STATUS mandatory
			DESCRIPTION
		" Average round trip delay, in
		  milliseconds, experienced by the Ping packet and
		  the Ping response. "
			::= { accPing 15 }
-- Dial Group
      accDial         OBJECT IDENTIFIER ::= { accBRG 31 }
     --  Dial Control MIB
     CallAddress ::= DisplayString (SIZE (0..128))
     --  Objects of this type are physical ports, identified by
     --  ifIndex value, which back up other physical ports,
     --  by ifIndex value.
     --
     BackupPort ::= INTEGER          -- 1..ifNumber
     --  Objects of this type are physical ports
     --
     PhysicalPort ::= INTEGER        -- 1..ifNumber
     --  Dial Backup Table
     -- The Dial Backup Table specifies which physical ports
     -- backup which other physical ports, and under what circumstances
     -- will be activated or de-activated.
     accDialBackupTable OBJECT-TYPE
         SYNTAX   SEQUENCE OF AccDialBackupEntry
         ACCESS   not-accessible
         STATUS   mandatory
         DESCRIPTION
            "A list of associations between physical ports."
         REFERENCE
            "Dial Control Procedure   "
         ::= { accDial 1 }
     accDialBackupEntry OBJECT-TYPE
         SYNTAX   AccDialBackupEntry
         ACCESS   not-accessible
         STATUS   mandatory
         DESCRIPTION
            "An association between two ports."
         INDEX { accDialBackupPrimary }
         ::= { accDialBackupTable 1 }
     AccDialBackupEntry ::=
         SEQUENCE {
             accDialBackupPort
                 BackupPort,
             accDialBackupPrimary
                 PhysicalPort,
             accDialBackupControl
                 INTEGER,
             accDialBackupRetry
                 INTEGER,
             accDialBackupDamp
                 INTEGER,
             accDialBackupCallCongestion
                 INTEGER,
             accDialBackupClearCongestion
                 INTEGER,
             accDialBackupCallError
                 INTEGER,
             accDialBackupCallAddress
                 CallAddress,
             accDialBackupStatus
                 INTEGER,
             accDialBackupState
                 INTEGER
     }
         accDialBackupPort OBJECT-TYPE
             SYNTAX   BackupPort
             ACCESS   read-write
             STATUS   mandatory
             DESCRIPTION
                "The ifIndex value of the port backing  up  the
                primary port."
            ::= { accDialBackupEntry 1 }
         accDialBackupPrimary OBJECT-TYPE
             SYNTAX   PhysicalPort
             ACCESS   read-only
             STATUS   mandatory
             DESCRIPTION
                "The ifIndex value of the port backed up."
            ::= { accDialBackupEntry 2 }
         accDialBackupControl OBJECT-TYPE
             SYNTAX  INTEGER {
                             master (1),     -- This system calls
                             slave (2),      -- this system is called
                             demand (3)      -- this system does either
                         }
             ACCESS   read-write
             STATUS   mandatory
             DESCRIPTION
                "Backup Control indicates under what conditions
                a call is placed or accepted."
            DEFVAL { demand }
            ::= { accDialBackupEntry 3 }
         accDialBackupRetry OBJECT-TYPE
             SYNTAX   INTEGER (0..3600)
             ACCESS   read-write
             STATUS   mandatory
             DESCRIPTION
                "The number of seconds the system will wait be-
                fore retrying a failed call."
            DEFVAL { 10 }
            ::= { accDialBackupEntry 4 }
         accDialBackupDamp OBJECT-TYPE
             SYNTAX   INTEGER
             ACCESS   read-write
             STATUS   mandatory
             DESCRIPTION
                "Damping factor."
            DEFVAL { 3 }
            ::= { accDialBackupEntry 5 }
         accDialBackupCallCongestion OBJECT-TYPE
             SYNTAX   INTEGER (0..101)
             ACCESS   read-write
             STATUS   mandatory
             DESCRIPTION
                "If the average octet rate transmitted (or,  on
                a  master,  received)  exceeds  this percentage
                times the ifSpeed of the primary link,  a  call
                will be placed."
            DEFVAL { 80 }
            ::= { accDialBackupEntry 6 }
         accDialBackupClearCongestion OBJECT-TYPE
             SYNTAX   INTEGER (0..101)
             ACCESS   read-write
             STATUS   mandatory
             DESCRIPTION
                "If the sum of the primary  and  backup  link's
                average  octet rates (transmitted or, on a mas-
                ter,  received)  falls  below  this  percentage
                times  the ifSpeed of the primary link, an out-
                standing call will be cleared.
                If ClearCongestion >= CallCongestion, the entry
                will  not  be  acted upon by software, but will
                result in a trap at system startup."
            DEFVAL { 50 }
            ::= { accDialBackupEntry 7 }
         accDialBackupCallError OBJECT-TYPE
             SYNTAX   INTEGER
             ACCESS   read-write
             STATUS   mandatory
             DESCRIPTION
                "If the average sum  of  ifInDiscards,  ifInEr-
                rors,  ifOutDiscards, ifOutErrors, accLapbStat-
                BadFCSIns,  accLapbStatT1Timeouts,  accLapbSta-
                tREJIns,  and  accLapbStatREJOuts  exceeds this
                value, a call will be placed.
                The call will be cleared when the  average  be-
                comes zero."
            DEFVAL { 5 }
            ::= { accDialBackupEntry 8 }
         accDialBackupCallAddress OBJECT-TYPE
             SYNTAX   CallAddress
             ACCESS   read-write
             STATUS   mandatory
             DESCRIPTION
                "The address to be called, in ASCII.
                No validation is performed on this variable."
            ::= { accDialBackupEntry 9 }
         accDialBackupStatus OBJECT-TYPE
             SYNTAX  INTEGER {
                     valid (1),
                     invalid (2)
                     }
             ACCESS   read-write
             STATUS   mandatory
             DESCRIPTION
                "If this object is set to 'invalid', the  entry
                is deleted."
            DEFVAL { valid }
            ::= { accDialBackupEntry 10 }
         accDialBackupState OBJECT-TYPE
             SYNTAX   INTEGER {
                         congestOut (1), -- call due to transmit congestion
                         congestIn  (2), -- call due to receive congestion
                         errors     (3), -- call due to errors on link
                         backup     (4), -- call due to primary link failure
                         manual     (5), -- call administratively placed
                         clear      (6)  -- no call active
                      }
             ACCESS   read-write
             STATUS   mandatory
             DESCRIPTION
                "The current call state from the primary link's
                perspective.   The  only values acceptable on a
                SET are 'manual' and 'clear'.  If  'manual'  is
                SET,  the backup link will place a call immedi-
                ately or when it next  becomes  available.   If
                'clear'  is SET when a call is administratively
                placed, either the call will be cleared, or the
                call  will  continue  for  another  reason.  If
                'clear' is set when no call is administratively
                placed, there is no effect."
            DEFVAL { clear }
            ::= { accDialBackupEntry 11 }
	accDialPortTable OBJECT-TYPE
		SYNTAX SEQUENCE OF AccDialPortEntry
		ACCESS not-accessible
		STATUS mandatory
		DESCRIPTION
			" A table containing DOD-port specific variables
			for this DOD implementation."
		::= { accDial 2 }
	accDialPortEntry OBJECT-TYPE
		SYNTAX AccDialPortEntry
		ACCESS not-accessible
		STATUS mandatory
		DESCRIPTION
			" Management information about a particular DOD Port."
		INDEX { accDialPortIndex }
		::= { accDialPortTable 1 }
	AccDialPortEntry ::= SEQUENCE {
		accDialPortIndex		INTEGER,
		accDialPortContents		INTEGER,
		accDialPortStationType		INTEGER,
		accDialPortAdminState		INTEGER,
		accDialPortCallState		INTEGER,
		accDialPortRetryInterval	TimeTicks,
		accDialPortRetryCount		INTEGER,
		accDialPortClearingInterv	TimeTicks,
		accDialPortMessageLevel		INTEGER,
		accDialPortPhysicalPort		INTEGER,
		accDialPortCallAddress		OCTET STRING,
		accDialPortPhysicalPortStr	OCTET STRING,
		accDialPortCallAddressStr	OCTET STRING,
		accDialPortPassword		OCTET STRING,
		accDialPortName			OCTET STRING
		}
	accDialPortIndex	OBJECT-TYPE
		SYNTAX	INTEGER
		ACCESS	read-only
		STATUS	mandatory
		DESCRIPTION
			" Dial port number"
		::= { accDialPortEntry 1 }
	accDialPortContents	OBJECT-TYPE
		SYNTAX	INTEGER {
			other(1),
			invalid(2)
		}
		ACCESS	read-only
		STATUS	mandatory
		DESCRIPTION
			" Setting this object to invalid deletes dial port
			or call address or physical port."
		::= { accDialPortEntry 2 }
	accDialPortStationType	OBJECT-TYPE
		SYNTAX	INTEGER {
			master(1),
			slave(2),
			demand(3)
		}
		ACCESS	read-write
		STATUS	mandatory
		DESCRIPTION
			" Type of station for this dial port. Master can
			place calls, slave can accept calls, demand can
			do both."
		::= { accDialPortEntry 3 }
	accDialPortAdminState	OBJECT-TYPE
		SYNTAX	INTEGER {
			down(1),
			up(2)
		}
		ACCESS	read-write
		STATUS	mandatory
		DESCRIPTION
			" The administrative state of this dial port."
		::= { accDialPortEntry 4 }
	accDialPortCallState	OBJECT-TYPE
		SYNTAX	INTEGER {
			clear(1),
			call(2)
		}
		ACCESS	read-write
		STATUS	mandatory
		DESCRIPTION
			" The dial state of this dial port. This is more
			of a operator request than a state. Depending on
			the current state of the dial port the command that
			sets the value of this object may or may not be
			acted immediately."
		::= { accDialPortEntry 5 }
	accDialPortRetryInterval	OBJECT-TYPE
		SYNTAX	TimeTicks
		ACCESS	read-write
		STATUS	mandatory
		DESCRIPTION
			" Number of seconds allowed to elapse between two 
			dial attempts."
		::= { accDialPortEntry 6 }
	accDialPortRetryCount	OBJECT-TYPE
		SYNTAX	INTEGER
		ACCESS	read-write
		STATUS	mandatory
		DESCRIPTION
			" Total number of dial attempts."
		::= { accDialPortEntry 7 }
	accDialPortClearingInterv	OBJECT-TYPE
		SYNTAX	TimeTicks
		ACCESS	read-write
		STATUS	mandatory
		DESCRIPTION
			" Number of seconds to wait with no traffic
			to hangup this dial session."
		::= { accDialPortEntry 8 }
	accDialPortMessageLevel	OBJECT-TYPE
		SYNTAX	INTEGER
		ACCESS	read-write
		STATUS	mandatory
		DESCRIPTION
			" Current message level for how much to display
			for this dial port.
			1 - Error messages.
			2 - Unused + 1.
			3 - Warning messages + 2.
			4 - Unused + 3. 
			5 - Dial activity + 4.
			6 - Unused + 5.
			7 - Dial port state changes + 6."
		::= { accDialPortEntry 9 }
	accDialPortPhysicalPort	OBJECT-TYPE
		SYNTAX	INTEGER
		ACCESS	write-only
		STATUS	mandatory
		DESCRIPTION
			" One of the possible physical ports this dial
			port may associate."
		::= { accDialPortEntry 10 }
	accDialPortCallAddress	OBJECT-TYPE
		SYNTAX	OCTET STRING
		ACCESS	write-only
		STATUS	mandatory
		DESCRIPTION
			" One of the possible call addresses this dial
			port may call."
		::= { accDialPortEntry 11 }
	accDialPortPhysicalPortStr	OBJECT-TYPE
		SYNTAX	OCTET STRING
		ACCESS	read-only
		STATUS	mandatory
		DESCRIPTION
			" The concatenated string of all physical ports
			associated with this dial port."
		::= { accDialPortEntry 12 }
	accDialPortCallAddressStr	OBJECT-TYPE
		SYNTAX	OCTET STRING
		ACCESS	read-only
		STATUS	mandatory
		DESCRIPTION
			" The concatenated string of all call address/name
			entries associated with this dial port."
		::= { accDialPortEntry 13 }
	accDialPortPassword	OBJECT-TYPE
		SYNTAX	OCTET STRING
		ACCESS	write-only
		STATUS	mandatory
		DESCRIPTION
			" The password associated with the call address."
		::= { accDialPortEntry 14 }
	accDialPortName	OBJECT-TYPE
		SYNTAX	OCTET STRING
		ACCESS	write-only
		STATUS	mandatory
		DESCRIPTION
			" The name associated with the call address. 
			The combination of name and password is used for
			the outbound PAP negotiation."
		::= { accDialPortEntry 15 }
	accDialPortStatTable	OBJECT-TYPE
		SYNTAX	SEQUENCE OF AccDialPortStatEntry
		ACCESS	not-accessible
		STATUS	mandatory
		DESCRIPTION
			" A table containing the operational parameters 
			for this dial port."
		::= { accDial 3 }
	accDialPortStatEntry	OBJECT-TYPE
		SYNTAX	AccDialPortStatEntry
		ACCESS	not-accessible
		STATUS	mandatory
		DESCRIPTION
			" Current status for this dial port."
		INDEX	{ accDialPortStatIndex }
		::= { accDialPortStatTable 1 }
	AccDialPortStatEntry ::= SEQUENCE {
		accDialPortStatIndex		INTEGER,
		accDialPortStatActPhysPort	INTEGER,
		accDialPortStatState		INTEGER,
		accDialPortStatTrigFwdr		INTEGER,
		accDialPortStatElapsedTime	TimeTicks,
		accDialPortStatTrigSrcAddr	OCTET STRING,
		accDialPortStatTrigCallAddr	OCTET STRING,
		accDialPortStatSuccessOut	INTEGER,
		accDialPortStatUnsuccessOut	INTEGER,
		accDialPortStatSuccessIn	INTEGER,
		accDialPortStatUnsuccessIn	INTEGER
		}
	accDialPortStatIndex	OBJECT-TYPE
		SYNTAX	INTEGER
		ACCESS	read-only
		STATUS	mandatory
		DESCRIPTION
			" Dial port number."
		::= { accDialPortStatEntry 1 }
	accDialPortStatActPhysPort 	OBJECT-TYPE
		SYNTAX 	INTEGER
		ACCESS 	read-only
		STATUS 	mandatory
		DESCRIPTION
			" The physical port currently connected with
			or recently connected with."
		::= { accDialPortStatEntry 2 }
	accDialPortStatState 	OBJECT-TYPE
		SYNTAX 	INTEGER
		ACCESS 	read-write
		STATUS 	mandatory
		DESCRIPTION
			" The current state of this dial port.
			The following is a list of valid states:
			down(0),
			disconnected(1),
			queued(2),
			answering(3),
			dialing(4),
			connected(5) "
		::= { accDialPortStatEntry 3 }
	accDialPortStatTrigFwdr 	OBJECT-TYPE
		SYNTAX 	INTEGER
		ACCESS 	read-only
		STATUS 	mandatory
		DESCRIPTION
			" Application which started this dial session.
			The following is a list of applications:
			none(0),
			management(1),
			inbound(2),
			ip(33),
			idp(37),
			decnet(39),
			appletalk(41),
			ipx(43),
			bridging(177),
			sr(179)"
		::= { accDialPortStatEntry 4 }
	accDialPortStatElapsedTime 	OBJECT-TYPE
		SYNTAX 	TimeTicks
		ACCESS 	read-only
		STATUS 	mandatory
		DESCRIPTION
			" Number of seconds that this dial port has
			been in the current state."
		::= { accDialPortStatEntry 5 }
	accDialPortStatTrigSrcAddr 	OBJECT-TYPE
		SYNTAX 	OCTET STRING
		ACCESS 	read-only
		STATUS 	mandatory
		DESCRIPTION
			" Source address of forwarder message that 
			started this dial session. "
		::= { accDialPortStatEntry 6 }
	accDialPortStatTrigCallAddr 	OBJECT-TYPE
		SYNTAX 	OCTET STRING
		ACCESS 	read-only
		STATUS 	mandatory
		DESCRIPTION
			" Phone number connected to during this dial
			session or the last dial session."
		::= { accDialPortStatEntry 7 }
	accDialPortStatSuccessOut 	OBJECT-TYPE
		SYNTAX 	INTEGER
		ACCESS 	read-only
		STATUS 	mandatory
		DESCRIPTION
			" Number of successfull outgoing calls on
			this dial port."
		::= { accDialPortStatEntry 8 }
	accDialPortStatUnsuccessOut 	OBJECT-TYPE
		SYNTAX 	INTEGER
		ACCESS 	read-only
		STATUS 	mandatory
		DESCRIPTION
			" Number of unsuccessfull call attempts on
			this dial port."
		::= { accDialPortStatEntry 9 }
	accDialPortStatSuccessIn 	OBJECT-TYPE
		SYNTAX 	INTEGER
		ACCESS 	read-only
		STATUS 	mandatory
		DESCRIPTION
			" Number of successfull incoming calls on
			this dial port."
		::= { accDialPortStatEntry 10 }
	accDialPortStatUnsuccessIn 	OBJECT-TYPE
		SYNTAX 	INTEGER
		ACCESS 	read-only
		STATUS 	mandatory
		DESCRIPTION
			" Total number of unsuccessfull incoming calls."
		::= { accDialPortStatEntry 11 }
-- Dial Originate databases
-- Appletalk
  accDialOrigAtTable OBJECT-TYPE
		SYNTAX	SEQUENCE OF AccDialOrigAtEntry
		ACCESS	not-accessible
		STATUS	mandatory
		DESCRIPTION
			" A table containing dial originate database
			 for Appletalk."
		::= { accDial 4 }
	accDialOrigAtEntry	OBJECT-TYPE
		SYNTAX AccDialOrigAtEntry
		ACCESS not-accessible
		STATUS mandatory
		DESCRIPTION
			" Dial originate information entry for Appletalk."
		INDEX { accDialOrigAtDestStart,
			accDialOrigAtDestEnd,
			accDialOrigAtSourceStart,
			accDialOrigAtSourceEnd }
		::= { accDialOrigAtTable 1 }
	AccDialOrigAtEntry ::= SEQUENCE {
		accDialOrigAtStatus		INTEGER,
		accDialOrigAtDestStart		OCTET STRING,
		accDialOrigAtDestEnd		OCTET STRING,
		accDialOrigAtSourceStart	OCTET STRING,
		accDialOrigAtSourceEnd		OCTET STRING,
		accDialOrigAtTraffic		INTEGER,
		accDialOrigAtAction		INTEGER
		}
	accDialOrigAtStatus	OBJECT-TYPE
		SYNTAX	INTEGER {
				other(1),
				invalid(2)
			}
		ACCESS	write-only
		STATUS	mandatory
		DESCRIPTION
			" Writing 'invalid' deletes the filter table entry."
		::= { accDialOrigAtEntry 1 }
	accDialOrigAtDestStart	OBJECT-TYPE
		SYNTAX	OCTET STRING  -- (SIZE(2))
		ACCESS	read-write
		STATUS	mandatory
		DESCRIPTION
			" Destination range start for this Appletalk entry 
			 in the dial originate database."
		::= { accDialOrigAtEntry 2 }
	accDialOrigAtDestEnd	OBJECT-TYPE
		SYNTAX	OCTET STRING  -- (SIZE(2))
		ACCESS	read-write
		STATUS	mandatory
		DESCRIPTION
			" Destination range end for this Appletalk entry 
			 in the dial originate database."
		::= { accDialOrigAtEntry 3 }
	accDialOrigAtSourceStart	OBJECT-TYPE
		SYNTAX	OCTET STRING  -- (SIZE(2))
		ACCESS	read-write
		STATUS	mandatory
		DESCRIPTION
			" Source range start for this Appletalk entry 
			 in the dial originate database."
		::= { accDialOrigAtEntry 4 }
	accDialOrigAtSourceEnd	OBJECT-TYPE
		SYNTAX	OCTET STRING  -- (SIZE(2))
		ACCESS	read-write
		STATUS	mandatory
		DESCRIPTION
			" Source range end for this Appletalk entry 
			 in the dial originate database."
		::= { accDialOrigAtEntry 5 }
	accDialOrigAtTraffic	OBJECT-TYPE
		SYNTAX	INTEGER {
			 any(1),
			 nbp(2),
			 atp(3),
			 aep(4),
			 rtmp(5),
			 zip(6),
			 adsp(7),
			 nbpbroadcast(8),
			 nbplookup(9),
			 nbpreply(10),
			 nbpforwardreq(11)
			}
		ACCESS	read-write
		STATUS	mandatory
		DESCRIPTION
			" Traffic info for this Appletalk entry 
			 in the dial originate database."
		::= { accDialOrigAtEntry 6 }
	accDialOrigAtAction	OBJECT-TYPE
		SYNTAX	INTEGER {
			 allow(1),
			 disallow(2)
			}
		ACCESS	read-write
		STATUS	mandatory
		DESCRIPTION
			" Allow-disallow info for this Appletalk entry 
			 in the dial originate database."
		::= { accDialOrigAtEntry 7 }
-- Decnet
	accDialOrigDnTable	OBJECT-TYPE
		SYNTAX	SEQUENCE OF AccDialOrigDnEntry
		ACCESS	not-accessible
		STATUS	mandatory
		DESCRIPTION
			" A table containing dial originate database
			 for Decnet."
		::= { accDial 5 }
	accDialOrigDnEntry	OBJECT-TYPE
		SYNTAX AccDialOrigDnEntry
		ACCESS not-accessible
		STATUS mandatory
		DESCRIPTION
			" Dial originate information entry for Decnet."
		INDEX { accDialOrigDnDestAddr,
			accDialOrigDnSourceAddr }
		::= { accDialOrigDnTable 1 }
	AccDialOrigDnEntry ::= SEQUENCE {
		accDialOrigDnStatus		INTEGER,
		accDialOrigDnDestAddr		INTEGER,
		accDialOrigDnSourceAddr		INTEGER,
		accDialOrigDnAction		INTEGER
		}
	accDialOrigDnStatus	OBJECT-TYPE
		SYNTAX	INTEGER {
				other(1),
				invalid(2)
			}
		ACCESS	write-only
		STATUS	mandatory
		DESCRIPTION
			" Writing 'invalid' deletes the filter table entry."
		::= { accDialOrigDnEntry 1 }
	accDialOrigDnDestAddr	OBJECT-TYPE
		SYNTAX	INTEGER	(0..65535)
		ACCESS	read-write
		STATUS	mandatory
		DESCRIPTION
			" Destination address for this Decnet entry 
			 in the dial originate database."
		::= { accDialOrigDnEntry 2 }
	accDialOrigDnSourceAddr	OBJECT-TYPE
		SYNTAX	INTEGER	(0..65535)
		ACCESS	read-write
		STATUS	mandatory
		DESCRIPTION
			" Source address for this Decnet entry 
			 in the dial originate database."
		::= { accDialOrigDnEntry 3 }
	accDialOrigDnAction	OBJECT-TYPE
		SYNTAX	INTEGER {
			 allow(1),
			 disallow(2)
			}
		ACCESS	read-write
		STATUS	mandatory
		DESCRIPTION
			" Allow-disallow info for this Decnet entry 
			 in the dial originate database."
		::= { accDialOrigDnEntry 4 }
-- Bridge
	accDialOrigBrTable	OBJECT-TYPE
		SYNTAX	SEQUENCE OF AccDialOrigBrEntry
		ACCESS	not-accessible
		STATUS	mandatory
		DESCRIPTION
			" A table containing dial originate database
			 for Bridge."
		::= { accDial 6 }
	accDialOrigBrEntry	OBJECT-TYPE
		SYNTAX AccDialOrigBrEntry
		ACCESS not-accessible
		STATUS mandatory
		DESCRIPTION
			" Dial originate information entry for Bridge."
		INDEX { accDialOrigBrDestMacAddr,
			accDialOrigBrSourceMacAddr }
		::= { accDialOrigBrTable 1 }
	AccDialOrigBrEntry ::= SEQUENCE {
		accDialOrigBrStatus		INTEGER,
		accDialOrigBrDestMacAddr	OCTET STRING,
		accDialOrigBrSourceMacAddr	OCTET STRING,
		accDialOrigBrAction		INTEGER
		}
	accDialOrigBrStatus	OBJECT-TYPE
		SYNTAX	INTEGER {
				other(1),
				invalid(2)
			}
		ACCESS	write-only
		STATUS	mandatory
		DESCRIPTION
			" Writing 'invalid' deletes the filter table entry."
		::= { accDialOrigBrEntry 1 }
	accDialOrigBrDestMacAddr	OBJECT-TYPE
		SYNTAX	OCTET STRING -- (SIZE(6))
		ACCESS	read-write
		STATUS	mandatory
		DESCRIPTION
			" Destination mac address start for this Bridge entry 
			 in the dial originate database."
		::= { accDialOrigBrEntry 2 }
	accDialOrigBrSourceMacAddr	OBJECT-TYPE
		SYNTAX	OCTET STRING
		ACCESS	read-write
		STATUS	mandatory
		DESCRIPTION
			" Source mac address for this Bridge entry 
			 in the dial originate database."
		::= { accDialOrigBrEntry 3 }
	accDialOrigBrAction	OBJECT-TYPE
		SYNTAX	INTEGER {
			 allow(1),
			 disallow(2)
			}
		ACCESS	read-write
		STATUS	mandatory
		DESCRIPTION
			" Allow-disallow info for this Bridge entry 
			 in the dial originate database."
		::= { accDialOrigBrEntry 4 }
-- Idp
	accDialOrigIdpTable	OBJECT-TYPE
		SYNTAX	SEQUENCE OF AccDialOrigIdpEntry
		ACCESS	not-accessible
		STATUS	mandatory
		DESCRIPTION
			" A table containing dial originate database
			 for Idp."
		::= { accDial 7 }
	accDialOrigIdpEntry	OBJECT-TYPE
		SYNTAX AccDialOrigIdpEntry
		ACCESS not-accessible
		STATUS mandatory
		DESCRIPTION
			" Dial originate information entry for Idp."
		INDEX { accDialOrigIdpDestNet,
			accDialOrigIdpSourceNet }
		::= { accDialOrigIdpTable 1 }
	AccDialOrigIdpEntry ::= SEQUENCE {
		accDialOrigIdpStatus	INTEGER,
		accDialOrigIdpDestNet	OCTET STRING,
		accDialOrigIdpSourceNet	OCTET STRING,
		accDialOrigIdpAction	INTEGER
		}
	accDialOrigIdpStatus	OBJECT-TYPE
		SYNTAX	INTEGER {
				other(1),
				invalid(2)
			}
		ACCESS	write-only
		STATUS	mandatory
		DESCRIPTION
			" Writing 'invalid' deletes the filter table entry."
		::= { accDialOrigIdpEntry 1 }
	accDialOrigIdpDestNet	OBJECT-TYPE
		SYNTAX	OCTET STRING -- (SIZE(4))
		ACCESS	read-write
		STATUS	mandatory
		DESCRIPTION
			" Destination network for this Idp entry 
			 in the dial originate database."
		::= { accDialOrigIdpEntry 2 }
	accDialOrigIdpSourceNet	OBJECT-TYPE
		SYNTAX	OCTET STRING -- (SIZE(4))
		ACCESS	read-write
		STATUS	mandatory
		DESCRIPTION
			" Source network for this Idp entry 
			 in the dial originate database."
		::= { accDialOrigIdpEntry 3 }
	accDialOrigIdpAction	OBJECT-TYPE
		SYNTAX	INTEGER {
			 allow(1),
			 disallow(2)
			}
		ACCESS	read-write
		STATUS	mandatory
		DESCRIPTION
			" Allow-disallow info for this Idp entry 
			 in the dial originate database."
		::= { accDialOrigIdpEntry 4 }
-- Ip
	accDialOrigIpTable	OBJECT-TYPE
		SYNTAX	SEQUENCE OF AccDialOrigIpEntry
		ACCESS	not-accessible
		STATUS	mandatory
		DESCRIPTION
			" A table containing dial originate database for Ip."
		::= { accDial 8 }
	accDialOrigIpEntry	OBJECT-TYPE
		SYNTAX AccDialOrigIpEntry
		ACCESS not-accessible
		STATUS mandatory
		DESCRIPTION
			" Dial originate information entry for Ip."
		INDEX { accDialOrigIpDestAddr,
			accDialOrigIpDestMask,
			accDialOrigIpSourceAddr,
			accDialOrigIpSourceMask,
			accDialOrigIpParm }
		::= { accDialOrigIpTable 1 }
	AccDialOrigIpEntry ::= SEQUENCE {
		accDialOrigIpStatus	INTEGER,
		accDialOrigIpDestAddr	IpAddress,
		accDialOrigIpDestMask	IpAddress,
		accDialOrigIpSourceAddr	IpAddress,
		accDialOrigIpSourceMask	IpAddress,
		accDialOrigIpParm	OCTET STRING,
		accDialOrigIpAction	INTEGER
		}
	accDialOrigIpStatus	OBJECT-TYPE
		SYNTAX	INTEGER {
				other(1),
				invalid(2)
			}
		ACCESS	write-only
		STATUS	mandatory
		DESCRIPTION
			" Writing 'invalid' deletes the filter table entry."
		::= { accDialOrigIpEntry 1 }
	accDialOrigIpDestAddr	OBJECT-TYPE
		SYNTAX	IpAddress
		ACCESS	read-write
		STATUS	mandatory
		DESCRIPTION
			" Destination address for this Ip entry 
			 in the dial originate database."
		::= { accDialOrigIpEntry 2 }
	accDialOrigIpDestMask	OBJECT-TYPE
		SYNTAX	IpAddress
		ACCESS	read-write
		STATUS	mandatory
		DESCRIPTION
			" Destination mask for this Ip entry 
			 in the dial originate database."
		::= { accDialOrigIpEntry 3 }
	accDialOrigIpSourceAddr	OBJECT-TYPE
		SYNTAX	IpAddress
		ACCESS	read-write
		STATUS	mandatory
		DESCRIPTION
			" Source address for this Ip entry 
			 in the dial originate database."
		::= { accDialOrigIpEntry 4 }
	accDialOrigIpSourceMask	OBJECT-TYPE
		SYNTAX	IpAddress
		ACCESS	read-write
		STATUS	mandatory
		DESCRIPTION
			" Source mask for this Ip entry 
			 in the dial originate database."
		::= { accDialOrigIpEntry 5 }
	accDialOrigIpParm	OBJECT-TYPE
		 SYNTAX OCTET STRING
		 ACCESS read-write
		 STATUS mandatory
		 DESCRIPTION
			" Filter parameters;
			 Byte 0 is Operation 1
				[0,1,2] = [None, !,=]
			 Bytes 1,2 is Protocol
			 Byte 3 is Operation 2
				[0  = none
				[1,2,3,4] = both [!, <, >, =]
				[5,6,7,8] = destination [!, <, >, =]
				[9,10,11,12] = source [!, <, >, =]
			 Bytes 4,5 is UDP/TCP port number"
		::= { accDialOrigIpEntry 6 }
	accDialOrigIpAction	OBJECT-TYPE
		SYNTAX	INTEGER {
			 allow(1),
			 disallow(2)
			}
		ACCESS	read-write
		STATUS	mandatory
		DESCRIPTION
			" Allow-disallow info for this Ip entry 
			 in the dial originate database."
		::= { accDialOrigIpEntry 7 }
-- Ipx
	accDialOrigIpxTable	OBJECT-TYPE
		SYNTAX	SEQUENCE OF AccDialOrigIpxEntry
		ACCESS	not-accessible
		STATUS	mandatory
		DESCRIPTION
			" A table containing dial originate database for Ipx."
		::= { accDial 9 }
	accDialOrigIpxEntry	OBJECT-TYPE
		SYNTAX AccDialOrigIpxEntry
		ACCESS not-accessible
		STATUS mandatory
		DESCRIPTION
			" Dial originate information entry for Ipx."
		INDEX { accDialOrigIpxDestNet,
			accDialOrigIpxSourceNet }
		::= { accDialOrigIpxTable 1 }
	AccDialOrigIpxEntry ::= SEQUENCE {
		accDialOrigIpxStatus	INTEGER,
		accDialOrigIpxDestNet	OCTET STRING,
		accDialOrigIpxSourceNet	OCTET STRING,
		accDialOrigIpxAction	INTEGER
		}
	accDialOrigIpxStatus	OBJECT-TYPE
		SYNTAX	INTEGER {
				other(1),
				invalid(2)
			}
		ACCESS	write-only
		STATUS	mandatory
		DESCRIPTION
			" Writing 'invalid' deletes the filter table entry."
		::= { accDialOrigIpxEntry 1 }
	accDialOrigIpxDestNet	OBJECT-TYPE
		SYNTAX	OCTET STRING -- (SIZE(4))
		ACCESS	read-write
		STATUS	mandatory
		DESCRIPTION
			" Destination network for this Ipx entry 
			 in the dial originate database."
		::= { accDialOrigIpxEntry 2 }
	accDialOrigIpxSourceNet	OBJECT-TYPE
		SYNTAX	OCTET STRING -- (SIZE(4))
		ACCESS	read-write
		STATUS	mandatory
		DESCRIPTION
			" Source network for this Ipx entry 
			 in the dial originate database."
		::= { accDialOrigIpxEntry 3 }
	accDialOrigIpxAction	OBJECT-TYPE
		SYNTAX	INTEGER {
			 allow(1),
			 disallow(2)
			}
		ACCESS	read-write
		STATUS	mandatory
		DESCRIPTION
			" Allow-disallow info for this Ipx entry 
			 in the dial originate database."
		::= { accDialOrigIpxEntry 4 }
-- Sr
	accDialOrigSrTable	OBJECT-TYPE
		SYNTAX	SEQUENCE OF AccDialOrigSrEntry
		ACCESS	not-accessible
		STATUS	mandatory
		DESCRIPTION
			" A table containing dial originate database for Sr."
		::= { accDial 10 }
	accDialOrigSrEntry	OBJECT-TYPE
		SYNTAX AccDialOrigSrEntry
		ACCESS not-accessible
		STATUS mandatory
		DESCRIPTION
			" Dial originate information entry for Sr."
		INDEX { accDialOrigSrDestMacAddr,
			accDialOrigSrSourceMacAddr }
		::= { accDialOrigSrTable 1 }
	AccDialOrigSrEntry ::= SEQUENCE {
		accDialOrigSrStatus		INTEGER,
		accDialOrigSrDestMacAddr	OCTET STRING,
		accDialOrigSrSourceMacAddr	OCTET STRING,
		accDialOrigSrAction		INTEGER
		}
	accDialOrigSrStatus	OBJECT-TYPE
		SYNTAX	INTEGER {
				other(1),
				invalid(2)
			}
		ACCESS	write-only
		STATUS	mandatory
		DESCRIPTION
			"Writing 'invalid' deletes the filter table entry."
		::= { accDialOrigSrEntry 1 }
	accDialOrigSrDestMacAddr	OBJECT-TYPE
		SYNTAX	OCTET STRING -- (SIZE(6))
		ACCESS	read-write
		STATUS	mandatory
		DESCRIPTION
			" Destination mac address for this Sr entry 
			 in the dial originate database."
		::= { accDialOrigSrEntry 2 }
	accDialOrigSrSourceMacAddr	OBJECT-TYPE
		SYNTAX	OCTET STRING -- (SIZE(6))
		ACCESS	read-write
		STATUS	mandatory
		DESCRIPTION
			" Source mac address for this Sr entry 
			 in the dial originate database."
		::= { accDialOrigSrEntry 3 }
	accDialOrigSrAction	OBJECT-TYPE
		SYNTAX	INTEGER {
			 allow(1),
			 disallow(2)
			}
		ACCESS	read-write
		STATUS	mandatory
		DESCRIPTION
			" Allow-disallow info for this Sr entry 
			 in the dial originate database."
		::= { accDialOrigSrEntry 4 }
	 -- RESERVED 
-- Point-to-Point Protocol Group
      accPpp         OBJECT IDENTIFIER ::= { accBRG 32 }
          accPppLinkTable   OBJECT-TYPE
               SYNTAX    SEQUENCE OF AccPppLinkEntry
               ACCESS    not-accessible
               STATUS    mandatory
               DESCRIPTION
                         "A table containing PPP-link specific variables
                         for this PPP implementation."
               ::= { accPpp 1 }
          accPppLinkEntry   OBJECT-TYPE
               SYNTAX    AccPppLinkEntry
               ACCESS    not-accessible
               STATUS    mandatory
               DESCRIPTION
                         "Management information about a particular PPP
                         Link."
               INDEX     { accPppLinkIndex }
               ::= { accPppLinkTable 1 }
          AccPppLinkEntry ::= SEQUENCE {
               accPppLinkIndex			INTEGER,
	       accPppLinkPhysicalIndex		INTEGER,
               accPppLinkBadAddresses		Counter,
               accPppLinkBadControls		Counter,
               accPppLinkPacketTooLongs		Counter,
               accPppLinkBadFCSs		Counter,
               accPppLinkLocalMRU		INTEGER,
               accPppLinkRemoteMRU		INTEGER,
	       accPppLinkLocalToPeerACCMap	OCTET STRING,
	       accPppLinkPeerToLocalACCMap	OCTET STRING,
	       accPppLinkLocalToRemotePC	INTEGER,
	       accPppLinkRemoteToLocalPC	INTEGER,
	       accPppLinkLocalToRemoteAC	INTEGER,
	       accPppLinkRemoteToLocalAC	INTEGER,
	       accPppLinkTransmit32BitFcs	INTEGER,
	       accPppLinkReceive32BitFcs	INTEGER,
	       accPppLinkOperStatus		INTEGER,
	       accPppLinkPacketTooShorts	Counter,
	       accPppLinkUnknownProtocols	Counter,
	       accPppLinkPacketInDiscards	Counter,
	       accPppLinkPacketOutDiscards	Counter
               }
          accPppLinkIndex   OBJECT-TYPE
               SYNTAX    INTEGER
               ACCESS    read-only
               STATUS    mandatory
               DESCRIPTION
                         "Interface number"
               ::= { accPppLinkEntry 1 }
	  accPppLinkPhysicalIndex   OBJECT-TYPE
               SYNTAX    INTEGER
               ACCESS    read-only
               STATUS    mandatory
               DESCRIPTION
			 " "
               ::= { accPppLinkEntry 2 }
          accPppLinkBadAddresses   OBJECT-TYPE
               SYNTAX    Counter
               ACCESS    read-only
               STATUS    mandatory
               DESCRIPTION
                         "The number of packets received with an
                         incorrect Address Field. " 
               ::= { accPppLinkEntry 3 }
          accPppLinkBadControls   OBJECT-TYPE
               SYNTAX    Counter
               ACCESS    read-only
               STATUS    mandatory
               DESCRIPTION
                         "The number of packets received on this link
                         with an incorrect Control Field. "
               ::= { accPppLinkEntry 4 }
          accPppLinkPacketTooLongs   OBJECT-TYPE
               SYNTAX    Counter
               ACCESS    read-only
               STATUS    mandatory
               DESCRIPTION
                         "The number of received packets that have been
                         discarded because their length exceeded the MRU."
               ::= { accPppLinkEntry 5 }
          accPppLinkBadFCSs    OBJECT-TYPE
               SYNTAX    Counter
               ACCESS    read-only
               STATUS    mandatory
               DESCRIPTION
			 " "
               ::= { accPppLinkEntry 6 }
          accPppLinkLocalMRU    OBJECT-TYPE
               SYNTAX    INTEGER
               ACCESS    read-only
               STATUS    mandatory
               DESCRIPTION
                         "The final negotiated MRU value for the local
                         PPP Entity. This value is the MRU that the
                         remote entity has accepted for the local PPP
                         entity."
               ::= { accPppLinkEntry 7 }
          accPppLinkRemoteMRU    OBJECT-TYPE
               SYNTAX    INTEGER
               ACCESS    read-only
               STATUS    mandatory
               DESCRIPTION
                         "The final negotiated MRU value for the remote
                         PPP Entity."
               ::= { accPppLinkEntry 8 }
	  accPppLinkLocalToPeerACCMap	OBJECT-TYPE
               SYNTAX    OCTET STRING
               ACCESS    read-only
               STATUS    mandatory
               DESCRIPTION
                         ""
               ::= { accPppLinkEntry 9 }
	  accPppLinkPeerToLocalACCMap	OBJECT-TYPE
               SYNTAX    OCTET STRING
               ACCESS    read-only
               STATUS    mandatory
               DESCRIPTION
                         ""
               ::= { accPppLinkEntry 10 }
	  accPppLinkLocalToRemotePC	OBJECT-TYPE
               SYNTAX    INTEGER
               ACCESS    read-only
               STATUS    mandatory
               DESCRIPTION
                         ""
               ::= { accPppLinkEntry 11 }
	  accPppLinkRemoteToLocalPC	OBJECT-TYPE
               SYNTAX    INTEGER
               ACCESS    read-only
               STATUS    mandatory
               DESCRIPTION
                         ""
               ::= { accPppLinkEntry 12 }
	  accPppLinkLocalToRemoteAC	OBJECT-TYPE
               SYNTAX    INTEGER
               ACCESS    read-only
               STATUS    mandatory
               DESCRIPTION
                         ""
               ::= { accPppLinkEntry 13 }
	  accPppLinkRemoteToLocalAC	OBJECT-TYPE
               SYNTAX    INTEGER
               ACCESS    read-only
               STATUS    mandatory
               DESCRIPTION
                         ""
               ::= { accPppLinkEntry 14 }
	  accPppLinkTransmit32BitFcs	OBJECT-TYPE
               SYNTAX    INTEGER
               ACCESS    read-only
               STATUS    mandatory
               DESCRIPTION
                         ""
               ::= { accPppLinkEntry 15 }
	  accPppLinkReceive32BitFcs	OBJECT-TYPE
               SYNTAX    INTEGER
               ACCESS    read-only
               STATUS    mandatory
               DESCRIPTION
                         ""
               ::= { accPppLinkEntry 16 }
	  accPppLinkOperStatus	OBJECT-TYPE
               SYNTAX    INTEGER {
			initial(1),
			starting(2),
			closed(3),
			stopped(4),
			closing(5),
			stopping(6),
			req-sent(7),
			ack-rcvd(8),
			ack-sent(9),
			opened(10)
			}
               ACCESS    read-only
               STATUS    mandatory
               DESCRIPTION
                         ""
               ::= { accPppLinkEntry 17 }
	  accPppLinkPacketTooShorts	OBJECT-TYPE
               SYNTAX    Counter
               ACCESS    read-only
               STATUS    mandatory
               DESCRIPTION
                         ""
               ::= { accPppLinkEntry 18 }
	  accPppLinkUnknownProtocols	OBJECT-TYPE
               SYNTAX    Counter
               ACCESS    read-only
               STATUS    mandatory
               DESCRIPTION
                         ""
               ::= { accPppLinkEntry 19 }
	  accPppLinkPacketInDiscards	OBJECT-TYPE
               SYNTAX    Counter
               ACCESS    read-only
               STATUS    mandatory
               DESCRIPTION
                         ""
               ::= { accPppLinkEntry 20 }
	  accPppLinkPacketOutDiscards	OBJECT-TYPE
               SYNTAX    Counter
               ACCESS    read-only
               STATUS    mandatory
               DESCRIPTION
                         ""
               ::= { accPppLinkEntry 21 }
          accPppLcpConfigTable   OBJECT-TYPE
               SYNTAX    SEQUENCE OF AccPppLcpConfigEntry
               ACCESS    not-accessible
               STATUS    mandatory
               DESCRIPTION
                         "A table containing the LCP configuration
                         parameters for this PPP Link. These variables
                         represent the initial configuration of the PPP
                         Link. The actual values of the parameters may
                         be changed when the link is brought up via the
                         LCP options negotiation mechanism."
               ::= { accPpp 2 }
          accPppLcpConfigEntry   OBJECT-TYPE
               SYNTAX    AccPppLcpConfigEntry
               ACCESS    not-accessible
               STATUS    mandatory
               DESCRIPTION
                         "Configuration information about a particular
                         PPP Link."
               INDEX     { accPppLcpConfigIndex }
               ::= { accPppLcpConfigTable 1 }
          AccPppLcpConfigEntry ::= SEQUENCE {
               accPppLcpConfigIndex
                    INTEGER,
               accPppLcpConfigInitialMRU
                    INTEGER,
	       accPppLcpConfigReceiveACCMap
                    OCTET STRING,
	       accPppLinkConfigXmitACCMap
		    OCTET STRING,
               accPppLcpConfigMagicNumber
                    INTEGER,
               accPppLcpConfig32BitFCS
                    INTEGER,
	       accPppLcpRestartTimer
                    INTEGER,
	       accPppLcpMaxTerminate
                    INTEGER,
	       accPppLcpMaxConfigure
                    INTEGER,
	       accPppLcpMaxFailure
		    INTEGER,
   	       accPppLcpMonInterval
		    INTEGER,
   	       accPppLcpMonEvents
		    INTEGER,
   	       accPppLcpMonThreshold
		    INTEGER,
   	       accPppLcpAdminStatus
                    INTEGER
               }
          accPppLcpConfigIndex   OBJECT-TYPE
               SYNTAX    INTEGER
               ACCESS    read-only
               STATUS    mandatory
               DESCRIPTION
                         "Interface number"
               ::= { accPppLcpConfigEntry 1 }
          accPppLcpConfigInitialMRU   OBJECT-TYPE
               SYNTAX    INTEGER
               ACCESS    read-only
               STATUS    mandatory
               DESCRIPTION
                         "The initial Maximum Receive Unit (MRU) that
                         the local PPP entity will advertise to the
                         remote entity. If the value of this variable is
                         0 then the local PPP entity will not advertise
                         any MRU to the remote entity and the default
                         MRU will be assumed. Changing this object will
                         have effect when the link is next restarted."
               DEFVAL    { 1500 }
               ::= { accPppLcpConfigEntry 2 }
	  accPppLcpConfigReceiveACCMap   OBJECT-TYPE
	       SYNTAX    OCTET STRING
               ACCESS    read-only
               STATUS    mandatory
               DESCRIPTION
			 " "
               ::= { accPppLcpConfigEntry 3 }
	  accPppLinkConfigXmitACCMap	OBJECT-TYPE
	       SYNTAX    OCTET STRING
               ACCESS    read-only
               STATUS    mandatory
               DESCRIPTION
			 " "
               ::= { accPppLcpConfigEntry 4 }
          accPppLcpConfigMagicNumber   OBJECT-TYPE
               SYNTAX    INTEGER { false (1), true (2) }
               ACCESS    read-only
               STATUS    mandatory
               DESCRIPTION
                         "If true(2) then the local node will attempt to
                         perform Magic Number negotiation with the
                         remote node. If false(1) then this negotiation
                         is not performed. In any event, the local node
                         will comply with any magic number negotiations
                         attempted by the remote node, per the PPP
                         specification. Changing this object will have
                         effect when the link is next restarted."
               DEFVAL    { false }
               ::= { accPppLcpConfigEntry 5 }
          accPppLcpConfig32BitFCS   OBJECT-TYPE
	       SYNTAX    INTEGER
               ACCESS    read-only
               STATUS    mandatory
               DESCRIPTION
			 " "
               ::= { accPppLcpConfigEntry 6 }
          accPppLcpRestartTimer   OBJECT-TYPE
               SYNTAX    INTEGER (1..3600)
               ACCESS    read-write
               STATUS    mandatory
               DESCRIPTION
                         " "
               DEFVAL    { 3 }
               ::= { accPppLcpConfigEntry 7 }
          accPppLcpMaxTerminate   OBJECT-TYPE
               SYNTAX    INTEGER (1..255)
               ACCESS    read-write
               STATUS    mandatory
               DESCRIPTION
                         " "
               DEFVAL    { 2 }
               ::= { accPppLcpConfigEntry 8 }
          accPppLcpMaxConfigure   OBJECT-TYPE
               SYNTAX    INTEGER (1..255)
               ACCESS    read-write
               STATUS    mandatory
               DESCRIPTION
                         " "
               DEFVAL    { 10 }
               ::= { accPppLcpConfigEntry 9 }
          accPppLcpMaxFailure   OBJECT-TYPE
               SYNTAX    INTEGER (1..255)
               ACCESS    read-write
               STATUS    mandatory
               DESCRIPTION
                         " "
               DEFVAL    { 10 }
               ::= { accPppLcpConfigEntry 10 }
   	  accPppLcpMonInterval	OBJECT-TYPE
               SYNTAX    INTEGER (0..3600)
               ACCESS    read-write
               STATUS    mandatory
               DESCRIPTION
                         " "
               DEFVAL    { 10 }
               ::= { accPppLcpConfigEntry 11 }
   	  accPppLcpMonEvents	OBJECT-TYPE
               SYNTAX    INTEGER (1..10)
               ACCESS    read-write
               STATUS    mandatory
               DESCRIPTION
                         " "
               DEFVAL    { 5 }
               ::= { accPppLcpConfigEntry 12 }
   	  accPppLcpMonThreshold	OBJECT-TYPE
               SYNTAX    INTEGER (1..10)
               ACCESS    read-write
               STATUS    mandatory
               DESCRIPTION
                         " "
               DEFVAL    { 3 }
               ::= { accPppLcpConfigEntry 13 }
   	  accPppLcpAdminStatus	OBJECT-TYPE
               SYNTAX   INTEGER {
		   	enabled(1),
		       	disabled(2)
			}
               ACCESS    read-write
               STATUS    mandatory
               DESCRIPTION
                         " "
               ::= { accPppLcpConfigEntry 14 }
          accPppLqrTable   OBJECT-TYPE
               SYNTAX    SEQUENCE OF AccPppLqrEntry
               ACCESS    not-accessible
               STATUS    mandatory
               DESCRIPTION
                         "Table containing the LQR parameters and
                         statistics for the local PPP entity."
               ::= { accPpp 3 }
          accPppLqrEntry   OBJECT-TYPE
               SYNTAX    AccPppLqrEntry
               ACCESS    not-accessible
               STATUS    mandatory
               DESCRIPTION
                         "LQR information for a particular PPP link. A
                         PPP link will have an entry in this table if
                         and only if LQR Quality Monitoring has been
                         successfully negotiated for said link."
               INDEX     { accPppLqrIndex }
               ::= { accPppLqrTable 1 }
          AccPppLqrEntry ::= SEQUENCE {
               accPppLqrIndex
                    INTEGER,
               accPppLqrQuality
                    INTEGER,
               accPppLqrInGoodOctets
                    Counter,
               accPppLqrLocalPeriod
                    INTEGER,
               accPppLqrRemotePeriod
                    INTEGER,
               accPppLqrOutLQRs
                    Counter,
               accPppLqrInLQRs
                    Counter
          }
          accPppLqrIndex   OBJECT-TYPE
               SYNTAX    INTEGER 
               ACCESS    read-only
               STATUS    mandatory
               DESCRIPTION
                         "Interface number"
               ::= { accPppLqrEntry 1 }
          accPppLqrQuality   OBJECT-TYPE
               SYNTAX    INTEGER {
                         good(1),
                         bad(2)
                    }
               ACCESS    read-only
               STATUS    mandatory
               DESCRIPTION
                         "The current quality of the link as declared by
                         the local PPP entity's Link-Quality Management
                         modules. No effort is made to define good or
                         bad, nor the policy used to determine it."
               ::= { accPppLqrEntry 2 }
          accPppLqrInGoodOctets   OBJECT-TYPE
               SYNTAX    Counter
               ACCESS    read-only
               STATUS    mandatory
               DESCRIPTION
                         "The LQR InGoodOctets counter for this link."
               ::= { accPppLqrEntry 3 }
          accPppLqrLocalPeriod   OBJECT-TYPE
               SYNTAX    INTEGER
               ACCESS    read-only
               STATUS    mandatory
               DESCRIPTION
                         "The LQR reporting period that is in effect for
                         the local PPP entity. The local entity received
                         a configure-ack for this value from the remote
                         PPP entity."
               ::= { accPppLqrEntry 4 }
          accPppLqrRemotePeriod   OBJECT-TYPE
               SYNTAX    INTEGER
               ACCESS    read-only
               STATUS    mandatory
               DESCRIPTION
                         "The LQR reporting period that is in effect for
                         the remote PPP entity. The local entity sent a
                         configure-ack for this value in response to the
                         configure-req from the remote PPP entity."
               ::= { accPppLqrEntry 5 }
          accPppLqrOutLQRs   OBJECT-TYPE
               SYNTAX    Counter
               ACCESS    read-only
               STATUS    mandatory
               DESCRIPTION
                         "The value of the OutLQRs counter on the local
                         node for the link identified by
                         accPppLqrLinkIndex."
               ::= { accPppLqrEntry 6 }
          accPppLqrInLQRs   OBJECT-TYPE
               SYNTAX    Counter
               ACCESS    read-only
               STATUS    mandatory
               DESCRIPTION
                         "The value of the InLQRs counter on the local
                         node for the link identified by
                         accPppLqrLinkIndex."
               ::= { accPppLqrEntry 7 }
          accPppLqrConfigTable   OBJECT-TYPE
               SYNTAX    SEQUENCE OF AccPppLqrConfigEntry
               ACCESS    not-accessible
               STATUS    mandatory
               DESCRIPTION
                         "Table containing the LQR Configuration
                         parameters for the local PPP entity."
               ::= { accPpp 4 }
          accPppLqrConfigEntry   OBJECT-TYPE
               SYNTAX    AccPppLqrConfigEntry
               ACCESS    not-accessible
               STATUS    mandatory
               DESCRIPTION
                         "LQR configuration information for a particular
                         PPP link."
               INDEX     { accPppLqrConfigIndex }
               ::= { accPppLqrConfigTable 1 }
          AccPppLqrConfigEntry ::= SEQUENCE {
               accPppLqrConfigIndex
                    INTEGER,
               accPppLqrConfigPeriod
                    INTEGER,
               accPppLqrConfigStatus
                    INTEGER
          }
          accPppLqrConfigIndex   OBJECT-TYPE
               SYNTAX    INTEGER
               ACCESS    read-only
               STATUS    mandatory
               DESCRIPTION
                         "Interface number"
               ::= { accPppLqrConfigEntry 1 }
          accPppLqrConfigPeriod   OBJECT-TYPE
               SYNTAX    INTEGER(0..2147483648)
               ACCESS    read-write
               STATUS    mandatory
               DESCRIPTION
                         "The LQR Reporting Period that the local PPP
                         entity will attempt to negotiate with the
                         remote entity, in units of seconds. Changing
                         this object will have effect when the link is
                         next restarted."
               DEFVAL    { 10 }
               ::= { accPppLqrConfigEntry 2 }
          accPppLqrConfigStatus   OBJECT-TYPE
               SYNTAX    INTEGER { disabled (1), enabled (2) }
               ACCESS    read-write
               STATUS    mandatory
               DESCRIPTION
                         "If enabled(2) then the local node will attempt
                         to perform LQR negotiation with the remote
                         node. If disabled(1) then this negotiation is
                         not performed. In any event, the local node
                         will comply with any magic number negotiations
                         attempted by the remote node, per the PPP
                         specification. Changing this object will have
                         effect when the link is next restarted.
                         Setting this object to the value disabled(1)
                         has the effect of invalidating the
                         corresponding entry in the accPppLqrConfigTable
                         object. It is an implementation-specific matter
                         as to whether the agent removes an invalidated
                         entry from the table. Accordingly, management
                         stations must be prepared to receive tabular
                         information from agents that corresponds to
                         entries not currently in use."
               DEFVAL    { enabled }
               ::= { accPppLqrConfigEntry 3 }
          accPppIpcpTable   OBJECT-TYPE
               SYNTAX    SEQUENCE OF AccPppIpcpEntry
               ACCESS    not-accessible
               STATUS    mandatory
               DESCRIPTION
                         "Table containing the IPCP parameters and
                         statistics for the local PPP entity."
               ::= { accPpp 5 }
          accPppIpcpEntry   OBJECT-TYPE
               SYNTAX    AccPppIpcpEntry
               ACCESS    not-accessible
               STATUS    mandatory
               DESCRIPTION
                         "IPCP information for a particular PPP link. A
                         PPP link will have an entry in this table if
                         and only if running IP over the PPP link  has
                         been successfully negotiated for said link."
               INDEX     { accPppIpcpIndex }
               ::= { accPppIpcpTable 1 }
          AccPppIpcpEntry ::= SEQUENCE {
               accPppIpcpIndex
                    INTEGER,
               accPppIpcpLocalToRemoteCompressionProtocol
                    INTEGER,
               accPppIpcpRemoteToLocalCompressionProtocol
                    INTEGER,
               accPppIpcpRemoteMaxSlotId
                    INTEGER,
               accPppIpcpLocalMaxSlotId
                    INTEGER,
   	       accPppIpOperStatus
                    INTEGER
          }
          accPppIpcpIndex   OBJECT-TYPE
               SYNTAX    INTEGER
               ACCESS    read-only
               STATUS    mandatory
               DESCRIPTION
                         "Interface number"
               ::= { accPppIpcpEntry 1 }
          accPppIpcpLocalToRemoteCompressionProtocol   OBJECT-TYPE
               SYNTAX    INTEGER {
                         none(1),
                         vj-tcp(2)
                    }
               ACCESS    read-only
               STATUS    mandatory
               DESCRIPTION
                         "The IP compression protocol that the local
                         PPP-IP entity uses when sending packets to the
                         remote PPP-IP entity."
               ::= { accPppIpcpEntry 2 }
          accPppIpcpRemoteToLocalCompressionProtocol   OBJECT-TYPE
               SYNTAX    INTEGER {
                         none(1),
                         vj-tcp(2)
                    }
               ACCESS    read-only
               STATUS    mandatory
               DESCRIPTION
                         "The IP compression protocol that the remote
                         PPP-IP entity uses when sending packets to the
                         local PPP-IP entity."
               ::= { accPppIpcpEntry 3 }
          accPppIpcpRemoteMaxSlotId   OBJECT-TYPE
               SYNTAX    INTEGER (0..255)
               ACCESS    read-only
               STATUS    mandatory
               DESCRIPTION
                         "The Max-Slot-Id parameter that the remote node
                         has advertised and that is in use on the link."
               ::= { accPppIpcpEntry 4 }
          accPppIpcpLocalMaxSlotId   OBJECT-TYPE
               SYNTAX    INTEGER(0..255)
               ACCESS    read-only
               STATUS    mandatory
               DESCRIPTION
                         "The Max-Slot-Id parameter that the local node
                         has advertised and that is in use on the link."
               ::= { accPppIpcpEntry 5 }
          accPppIpOperStatus   OBJECT-TYPE
               SYNTAX    INTEGER {
			initial(1),
			starting(2),
			closed(3),
			stopped(4),
			closing(5),
			stopping(6),
			req-sent(7),
			ack-rcvd(8),
			ack-sent(9),
			opened(10)
			}
               ACCESS    read-only
               STATUS    mandatory
               DESCRIPTION
			" "
               ::= { accPppIpcpEntry 6 }
          accPppIpcpConfigTable   OBJECT-TYPE
               SYNTAX    SEQUENCE OF AccPppIpcpConfigEntry
               ACCESS    not-accessible
               STATUS    mandatory
               DESCRIPTION
                         "Table containing the IPCP parameters and
                         statistics for the local PPP entity."
               ::= { accPpp 6 }
          accPppIpcpConfigEntry   OBJECT-TYPE
               SYNTAX    AccPppIpcpConfigEntry
               ACCESS    not-accessible
               STATUS    mandatory
               DESCRIPTION
                         "IPCP information for a particular PPP link. A
                         PPP link will have an entry in this table if
                         and only if running IP over the PPP link  has
                         been successfully negotiated for said link."
               INDEX     { accPppIpcpConfigIndex }
               ::= { accPppIpcpConfigTable 1 }
          AccPppIpcpConfigEntry ::= SEQUENCE {
               accPppIpcpConfigIndex
                    INTEGER,
               accPppIpcpConfigCompression
                    INTEGER,
               accPppIpcpConfigStatus
                    INTEGER
          }
          accPppIpcpConfigIndex   OBJECT-TYPE
               SYNTAX    INTEGER
               ACCESS    read-only
               STATUS    mandatory
               DESCRIPTION
                         "The value of ifIndex that identifies the entry
                         in the ifTable that is associated with the
                         local IPCP entity."
               ::= { accPppIpcpConfigEntry 1 }
          accPppIpcpConfigCompression   OBJECT-TYPE
               SYNTAX    INTEGER {
                         none(1),
                         vj-tcp(2)
                    }
               ACCESS    read-write
               STATUS    mandatory
               DESCRIPTION
                         "If none(1) then the local node will not
                         attempt to negotiate any IP Compression option.
                         Otherwise, the local node will attempt to
                         negotiate compression mode indicated by the
                         enumerated value Changing this object will have
                         effect when the link is next restarted."
               DEFVAL    { none }
               ::= { accPppIpcpConfigEntry 2 }
          accPppIpcpConfigStatus   OBJECT-TYPE
               SYNTAX    INTEGER {
                         disabled(1),
                         enabled(2)
                    }
               ACCESS    read-write
               STATUS    mandatory
               DESCRIPTION
                         "If enabled(2) then the local node will allow
                         IP traffic to flow across the link. If
                         disabled(1) then IP traffic will not be allowed
                         to flow across the link.  Setting this object
                         to the value disabled(1) has the effect of
                         invalidating the corresponding entry in the
                         accPppIpcpConfigTable object. It is an
                         implementation-specific matter as to whether
                         the agent removes an invalidated entry from the
                         table. Accordingly, management stations must be
                         prepared to receive tabular information from
                         agents that corresponds to entries not
                         currently in use."
               DEFVAL    { enabled }
               ::= { accPppIpcpConfigEntry 3 }
          accPppBncpTable   OBJECT-TYPE
               SYNTAX    SEQUENCE OF AccPppBncpEntry
               ACCESS    not-accessible
               STATUS    mandatory
               DESCRIPTION
                         "Table containing the parameters and statistics
                         for the local PPP entity that are related to
                         the operation of Bridging over the PPP."
               ::= { accPpp 7 }
          accPppBncpEntry   OBJECT-TYPE
               SYNTAX    AccPppBncpEntry
               ACCESS    not-accessible
               STATUS    mandatory
               DESCRIPTION
                         "Bridging NCP information for a particular PPP
                         link. A PPP link will have an entry in this
                         table if and only if Bridging over PPP has been
                         successfully negotiated for said link."
               INDEX     { accPppBncpIndex }
               ::= { accPppBncpTable 1 }
          AccPppBncpEntry ::= SEQUENCE {
               accPppBncpIndex
                    INTEGER,
               accPppBncpLocalToRemoteTinygramCompression
                    INTEGER,
               accPppBncpRemoteToLocalTinygramCompression
                    INTEGER,
               accPppBncpLocalToRemoteLanId
                    INTEGER,
               accPppBncpRemoteToLocalLanId
                    INTEGER
          }
          accPppBncpIndex   OBJECT-TYPE
               SYNTAX    INTEGER
               ACCESS    read-only
               STATUS    mandatory
               DESCRIPTION
                         "Interface number"
               ::= { accPppBncpEntry 1 }
          accPppBncpLocalToRemoteTinygramCompression   OBJECT-TYPE
               SYNTAX    INTEGER { false(1), true(2) }
               ACCESS    read-only
               STATUS    mandatory
               DESCRIPTION
                         "Indicates whether the local node will perform
                         Tinygram Compression when sending packets to
                         the remote entity. If false then the local
                         entity will not perform Tinygram Compression.
                         If true then the local entity will perform
                         Tinygram Compression."
               ::= { accPppBncpEntry 2 }
          accPppBncpRemoteToLocalTinygramCompression   OBJECT-TYPE
               SYNTAX    INTEGER { false(1), true(2) }
               ACCESS    read-only
               STATUS    mandatory
               DESCRIPTION
                         "Indicates what the local node believes to be
                         the remote node will perform Tinygram
                         Compression when sending packets to the local
                         node. If false then the remote entity is not
                         expected to perform Tinygram Compression. If
                         true then the remote entity is expected to
                         perform Tinygram Compression."
               ::= { accPppBncpEntry 3 }
          accPppBncpLocalToRemoteLanId   OBJECT-TYPE
               SYNTAX    INTEGER { false(1), true(2) }
               ACCESS    read-only
               STATUS    mandatory
               DESCRIPTION
                         "Indicates whether the local node will include
                         the LAN Identification field in transmitted
                         packets or not. If false(1) then the local node
                         will not transmit this field, true(2) means
                         that the field will be transmitted."
               ::= { accPppBncpEntry 4 }
          accPppBncpRemoteToLocalLanId   OBJECT-TYPE
               SYNTAX    INTEGER { false(1), true(2) }
               ACCESS    read-only
               STATUS    mandatory
               DESCRIPTION
                         "Indicates whether the remote node has
                         indicated that it will include the LAN
                         Identification field in transmitted packets or
                         not. If false(1) then the field will not be
                         transmitted, if true(2) then the field will be
                         transmitted."
               ::= { accPppBncpEntry 5 }
          accPppBncpConfigTable   OBJECT-TYPE
               SYNTAX    SEQUENCE OF AccPppBncpConfigEntry
               ACCESS    not-accessible
               STATUS    mandatory
               DESCRIPTION
                         "Table containing the parameters and statistics
                         for the local PPP entity that are related to
                         the operation of Bridging over the PPP."
               ::= { accPpp 8 }
          accPppBncpConfigEntry   OBJECT-TYPE
               SYNTAX    AccPppBncpConfigEntry
               ACCESS    not-accessible
               STATUS    mandatory
               DESCRIPTION
                         "Bridging NCP information for a particular PPP
                         link. A PPP link will have an entry in this
                         table if and only if Bridging over PPP has been
                         successfully negotiated for said link."
               INDEX     { accPppBncpConfigIndex }
               ::= { accPppBncpConfigTable 1 }
          AccPppBncpConfigEntry ::= SEQUENCE {
               accPppBncpConfigIndex
                    INTEGER,
               accPppBncpConfigTinygram
                    INTEGER,
               accPppBncpConfigRingId
                    INTEGER,
               accPppBncpConfigLineId
                    INTEGER,
               accPppBncpConfigLanId
                    INTEGER,
   	       accPppBncpConfigAdminStatus
                    INTEGER
          }
          accPppBncpConfigIndex   OBJECT-TYPE
               SYNTAX    INTEGER
               ACCESS    read-only
               STATUS    mandatory
               DESCRIPTION
                         "The value of ifIndex that identifies the entry
                         in the interface table that is associated with
                         the local PPP Bridging NCP entity."
               ::= { accPppBncpConfigEntry 1 }
          accPppBncpConfigTinygram   OBJECT-TYPE
               SYNTAX    INTEGER { false(1), true(2) }
               ACCESS    read-write
               STATUS    mandatory
               DESCRIPTION
                         "If false then the local BNCP entity will not
                         initiate the Tinygram Compression Option
                         Negotiation. If true then the local BNCP entity
                         will initiate negotiation of this option."
               DEFVAL    { true }
               ::= { accPppBncpConfigEntry 2 }
          accPppBncpConfigRingId   OBJECT-TYPE
               SYNTAX    INTEGER { false(1), true(2) }
               ACCESS    read-write
               STATUS    mandatory
               DESCRIPTION
                         "If false then the local PPP Entity will not
                         initiate a Remote Ring Identification Option
                         negotiation. If true then the local PPP entity
                         will intiate this negotiation. This MIB object
                         is relevant only if the interface is for 802.5
                         Token Ring bridging."
               DEFVAL    { false }
               ::= { accPppBncpConfigEntry 3 }
          accPppBncpConfigLineId   OBJECT-TYPE
               SYNTAX    INTEGER { false(1), true(2) }
               ACCESS    read-write
               STATUS    mandatory
               DESCRIPTION
                         "If false then the local PPP Entity is not to
                         initiate a Line Identification Option
                         negotiation. If true then the local PPP entity
                         will intiate this negotiation. This MIB object
                         is relevant only if the interface is for 802.5
                         Token Ring bridging."
               DEFVAL    { false }
               ::= { accPppBncpConfigEntry 4 }
          accPppBncpConfigLanId   OBJECT-TYPE
               SYNTAX    INTEGER { false(1), true(2) }
               ACCESS    read-write
               STATUS    mandatory
               DESCRIPTION
                         "If false then the local BNCP entity will not
                         initiate the LAN Identification Option
                         Negotiation. If true then the local BNCP entity
                         will initiate negotiation of this option."
               DEFVAL    { false }
               ::= { accPppBncpConfigEntry 5 }
   	  accPppBncpConfigAdminStatus OBJECT-TYPE
               SYNTAX    INTEGER {
                         disabled(1),
                         enabled(2)
                    }
               ACCESS    read-write
               STATUS    mandatory
               DESCRIPTION
			" "
               ::= { accPppBncpConfigEntry 6 }
          accPppXnsTable   OBJECT-TYPE
               SYNTAX    SEQUENCE OF AccPppXnsEntry
               ACCESS    not-accessible
               STATUS    mandatory
               DESCRIPTION
                         " "
               ::= { accPpp 9 }
          accPppXnsEntry   OBJECT-TYPE
               SYNTAX    AccPppXnsEntry
               ACCESS    not-accessible
               STATUS    mandatory
               DESCRIPTION
                         " "
               INDEX     { accPppXnsIndex }
               ::= { accPppXnsTable 1 }
          AccPppXnsEntry ::= SEQUENCE {
		accPppXnsIndex
                    INTEGER,
		accPppXnsOperStatus
                    INTEGER
          }
          accPppXnsIndex   OBJECT-TYPE
               SYNTAX    INTEGER
               ACCESS    read-only
               STATUS    mandatory
               DESCRIPTION
			"Same as ifIndex."
               ::= { accPppXnsEntry 1 }
          accPppXnsOperStatus   OBJECT-TYPE
               SYNTAX    INTEGER {
			initial(1),
			starting(2),
			closed(3),
			stopped(4),
			closing(5),
			stopping(6),
			req-sent(7),
			ack-rcvd(8),
			ack-sent(9),
			opened(10)
			}
               ACCESS    read-only
               STATUS    mandatory
               DESCRIPTION
			" "
               ::= { accPppXnsEntry 2 }
          accPppXnsConfigTable   OBJECT-TYPE
               SYNTAX    SEQUENCE OF AccPppXnsConfigEntry
               ACCESS    not-accessible
               STATUS    mandatory
               DESCRIPTION
                         " "
               ::= { accPpp 10 }
          accPppXnsConfigEntry   OBJECT-TYPE
               SYNTAX    AccPppXnsConfigEntry
               ACCESS    not-accessible
               STATUS    mandatory
               DESCRIPTION
                         " "
               INDEX     { accPppXnsConfigIndex }
               ::= { accPppXnsConfigTable 1 }
          AccPppXnsConfigEntry ::= SEQUENCE {
		accPppXnsConfigIndex
                    INTEGER,
		accPppXnsConfigAdminStatus
                    INTEGER
          }
          accPppXnsConfigIndex   OBJECT-TYPE
               SYNTAX    INTEGER
               ACCESS    read-only
               STATUS    mandatory
               DESCRIPTION
			"Same as ifIndex."
               ::= { accPppXnsConfigEntry 1 }
          accPppXnsConfigAdminStatus   OBJECT-TYPE
               SYNTAX    INTEGER {
                         disabled(1),
                         enabled(2)
                    }
               ACCESS    read-write
               STATUS    mandatory
               DESCRIPTION
			" "
               ::= { accPppXnsConfigEntry 3 }
          accPppIpxTable   OBJECT-TYPE
               SYNTAX    SEQUENCE OF AccPppIpxEntry
               ACCESS    not-accessible
               STATUS    mandatory
               DESCRIPTION
                         " "
               ::= { accPpp 11 }
          accPppIpxEntry   OBJECT-TYPE
               SYNTAX    AccPppIpxEntry
               ACCESS    not-accessible
               STATUS    mandatory
               DESCRIPTION
                         " "
               INDEX     { accPppIpxIndex }
               ::= { accPppIpxTable 1 }
          AccPppIpxEntry ::= SEQUENCE {
		accPppIpxIndex
                    INTEGER,
		accPppIpxOperStatus
                    INTEGER
          }
          accPppIpxIndex   OBJECT-TYPE
               SYNTAX    INTEGER
               ACCESS    read-only
               STATUS    mandatory
               DESCRIPTION
			"Same as ifIndex."
               ::= { accPppIpxEntry 1 }
          accPppIpxOperStatus   OBJECT-TYPE
               SYNTAX    INTEGER {
			initial(1),
			starting(2),
			closed(3),
			stopped(4),
			closing(5),
			stopping(6),
			req-sent(7),
			ack-rcvd(8),
			ack-sent(9),
			opened(10)
			}
               ACCESS    read-only
               STATUS    mandatory
               DESCRIPTION
			" "
               ::= { accPppIpxEntry 2 }
          accPppIpxConfigTable   OBJECT-TYPE
               SYNTAX    SEQUENCE OF AccPppIpxConfigEntry
               ACCESS    not-accessible
               STATUS    mandatory
               DESCRIPTION
                         " "
               ::= { accPpp 12 }
          accPppIpxConfigEntry   OBJECT-TYPE
               SYNTAX    AccPppIpxConfigEntry
               ACCESS    not-accessible
               STATUS    mandatory
               DESCRIPTION
                         " "
               INDEX     { accPppIpxConfigIndex }
               ::= { accPppIpxConfigTable 1 }
          AccPppIpxConfigEntry ::= SEQUENCE {
		accPppIpxConfigIndex
                    INTEGER,
		accPppIpxConfigAdminStatus
                    INTEGER
          }
          accPppIpxConfigIndex   OBJECT-TYPE
               SYNTAX    INTEGER
               ACCESS    read-only
               STATUS    mandatory
               DESCRIPTION
			"Same as ifIndex."
               ::= { accPppIpxConfigEntry 1 }
          accPppIpxConfigAdminStatus   OBJECT-TYPE
               SYNTAX    INTEGER {
                         disabled(1),
                         enabled(2)
                    }
               ACCESS    read-write
               STATUS    mandatory
               DESCRIPTION
			" "
               ::= { accPppIpxConfigEntry 3 }
          accPppAppleTable   OBJECT-TYPE
               SYNTAX    SEQUENCE OF AccPppAppleEntry
               ACCESS    not-accessible
               STATUS    mandatory
               DESCRIPTION
                         " "
               ::= { accPpp 13 }
          accPppAppleEntry   OBJECT-TYPE
               SYNTAX    AccPppAppleEntry
               ACCESS    not-accessible
               STATUS    mandatory
               DESCRIPTION
                         " "
               INDEX     { accPppAppleIndex }
               ::= { accPppAppleTable 1 }
          AccPppAppleEntry ::= SEQUENCE {
		accPppAppleIndex
                    INTEGER,
		accPppAppleOperStatus
                    INTEGER
          }
          accPppAppleIndex   OBJECT-TYPE
               SYNTAX    INTEGER
               ACCESS    read-only
               STATUS    mandatory
               DESCRIPTION
			"Same as ifIndex."
               ::= { accPppAppleEntry 1 }
          accPppAppleOperStatus   OBJECT-TYPE
               SYNTAX    INTEGER {
			initial(1),
			starting(2),
			closed(3),
			stopped(4),
			closing(5),
			stopping(6),
			req-sent(7),
			ack-rcvd(8),
			ack-sent(9),
			opened(10)
			}
               ACCESS    read-only
               STATUS    mandatory
               DESCRIPTION
			" "
               ::= { accPppAppleEntry 2 }
          accPppAppleConfigTable   OBJECT-TYPE
               SYNTAX    SEQUENCE OF AccPppAppleConfigEntry
               ACCESS    not-accessible
               STATUS    mandatory
               DESCRIPTION
                         " "
               ::= { accPpp 14 }
          accPppAppleConfigEntry   OBJECT-TYPE
               SYNTAX    AccPppAppleConfigEntry
               ACCESS    not-accessible
               STATUS    mandatory
               DESCRIPTION
                         " "
               INDEX     { accPppAppleConfigIndex }
               ::= { accPppAppleConfigTable 1 }
          AccPppAppleConfigEntry ::= SEQUENCE {
		accPppAppleConfigIndex
                    INTEGER,
		accPppAppleConfigAdminStatus
                    INTEGER
          }
          accPppAppleConfigIndex   OBJECT-TYPE
               SYNTAX    INTEGER
               ACCESS    read-only
               STATUS    mandatory
               DESCRIPTION
			"Same as ifIndex."
               ::= { accPppAppleConfigEntry 1 }
          accPppAppleConfigAdminStatus   OBJECT-TYPE
               SYNTAX    INTEGER {
                         disabled(1),
                         enabled(2)
                    }
               ACCESS    read-write
               STATUS    mandatory
               DESCRIPTION
			" "
               ::= { accPppAppleConfigEntry 3 }
          accPppDecTable   OBJECT-TYPE
               SYNTAX    SEQUENCE OF AccPppDecEntry
               ACCESS    not-accessible
               STATUS    mandatory
               DESCRIPTION
                         " "
               ::= { accPpp 15 }
          accPppDecEntry   OBJECT-TYPE
               SYNTAX    AccPppDecEntry
               ACCESS    not-accessible
               STATUS    mandatory
               DESCRIPTION
                         " "
               INDEX     { accPppDecIndex }
               ::= { accPppDecTable 1 }
          AccPppDecEntry ::= SEQUENCE {
		accPppDecIndex
                    INTEGER,
		accPppDecOperStatus
                    INTEGER
          }
          accPppDecIndex   OBJECT-TYPE
               SYNTAX    INTEGER
               ACCESS    read-only
               STATUS    mandatory
               DESCRIPTION
			"Same as ifIndex."
               ::= { accPppDecEntry 1 }
          accPppDecOperStatus   OBJECT-TYPE
               SYNTAX    INTEGER {
			initial(1),
			starting(2),
			closed(3),
			stopped(4),
			closing(5),
			stopping(6),
			req-sent(7),
			ack-rcvd(8),
			ack-sent(9),
			opened(10)
			}
               ACCESS    read-only
               STATUS    mandatory
               DESCRIPTION
			" "
               ::= { accPppDecEntry 2 }
          accPppDecConfigTable   OBJECT-TYPE
               SYNTAX    SEQUENCE OF AccPppDecConfigEntry
               ACCESS    not-accessible
               STATUS    mandatory
               DESCRIPTION
                         " "
               ::= { accPpp 16 }
          accPppDecConfigEntry   OBJECT-TYPE
               SYNTAX    AccPppDecConfigEntry
               ACCESS    not-accessible
               STATUS    mandatory
               DESCRIPTION
                         " "
               INDEX     { accPppDecConfigIndex }
               ::= { accPppDecConfigTable 1 }
          AccPppDecConfigEntry ::= SEQUENCE {
		accPppDecConfigIndex
                    INTEGER,
		accPppDecConfigAdminStatus
                    INTEGER
          }
          accPppDecConfigIndex   OBJECT-TYPE
               SYNTAX    INTEGER
               ACCESS    read-only
               STATUS    mandatory
               DESCRIPTION
			"Same as ifIndex."
               ::= { accPppDecConfigEntry 1 }
          accPppDecConfigAdminStatus   OBJECT-TYPE
               SYNTAX    INTEGER {
                         disabled(1),
                         enabled(2)
                    }
               ACCESS    read-write
               STATUS    mandatory
               DESCRIPTION
			" "
               ::= { accPppDecConfigEntry 3 }
          accPppProtocolTable   OBJECT-TYPE
               SYNTAX    SEQUENCE OF AccPppProtocolEntry
               ACCESS    not-accessible
               STATUS    mandatory
               DESCRIPTION
                         " "
               ::= { accPpp 17 }
          accPppProtocolEntry   OBJECT-TYPE
               SYNTAX    AccPppProtocolEntry
               ACCESS    not-accessible
               STATUS    mandatory
               DESCRIPTION
                         " "
               INDEX     { accPppProtocolIndex }
               ::= { accPppProtocolTable 1 }
          AccPppProtocolEntry ::= SEQUENCE {
		accPppProtocolIndex
                    INTEGER,
		accPppProtocolProtocol
                    INTEGER,
		accPppProtocolAdminStatus
                    INTEGER,
		accPppProtocolOperStatus
                    INTEGER
          }
          accPppProtocolIndex   OBJECT-TYPE
               SYNTAX    INTEGER
               ACCESS    read-only
               STATUS    mandatory
               DESCRIPTION
			" "
               ::= { accPppProtocolEntry 1 }
          accPppProtocolProtocol   OBJECT-TYPE
               SYNTAX    INTEGER {
		        ip(33),
		        osi(35),
		        idp(37),
		        decnet(39),
		        appletalk(41),
		        ipx(43),
		        bridge(49),
		        vines(53),
		        multilink(61),
		        ccp(253)
			}
               ACCESS    read-only
               STATUS    mandatory
               DESCRIPTION
			" "
               ::= { accPppProtocolEntry 2 }
          accPppProtocolAdminStatus   OBJECT-TYPE
               SYNTAX    INTEGER {
                         enabled(1),
                         disabled(2)
                    }
               ACCESS    read-only
               STATUS    mandatory
               DESCRIPTION
			" "
               ::= { accPppProtocolEntry 3 }
          accPppProtocolOperStatus   OBJECT-TYPE
               SYNTAX    INTEGER {
			initial(1),
			starting(2),
			closed(3),
			stopped(4),
			closing(5),
			stopping(6),
			req-sent(7),
			ack-rcvd(8),
			ack-sent(9),
			opened(10)
			}
               ACCESS    read-only
               STATUS    mandatory
               DESCRIPTION
			" "
               ::= { accPppProtocolEntry 4 }
          accPppMsg   OBJECT IDENTIFIER ::= { accPpp 18 }
          accPppMsgLevel   OBJECT-TYPE
               SYNTAX    INTEGER (1..7)
               ACCESS    read-write
               STATUS    mandatory
               DESCRIPTION
			" "
               ::= { accPppMsg 1 }
-- Flash Memory Group
   accFlash         OBJECT IDENTIFIER ::= { accBRG 33 }
          accFlashTable   OBJECT-TYPE
               SYNTAX    SEQUENCE OF AccFlashEntry
               ACCESS    not-accessible
               STATUS    mandatory
               DESCRIPTION
                         " "
               ::= { accFlash 1 }
          accFlashEntry   OBJECT-TYPE
               SYNTAX    AccFlashEntry
               ACCESS    not-accessible
               STATUS    mandatory
               DESCRIPTION
                         " "
               INDEX     { accFlashIndex }
               ::= { accFlashTable 1 }
          AccFlashEntry ::= SEQUENCE {
		accFlashIndex
                    INTEGER,
		accFlashFiDisp
                    INTEGER,
		accFlashCksum
                    INTEGER,
		accFlashLength
                    INTEGER
          }
          accFlashIndex   OBJECT-TYPE
               SYNTAX    INTEGER
               ACCESS    read-only
               STATUS    mandatory
               DESCRIPTION
			" "
               ::= { accFlashEntry 1 }
          accFlashFiDisp   OBJECT-TYPE
               SYNTAX    INTEGER {
		       boot-rom(1),
		       boot-flash(2),
		       valid(3),
		       invalid(4)
		       }
               ACCESS    read-only
               STATUS    mandatory
               DESCRIPTION
			" "
               ::= { accFlashEntry 2 }
          accFlashCksum   OBJECT-TYPE
               SYNTAX    INTEGER
               ACCESS    read-only
               STATUS    mandatory
               DESCRIPTION
			" "
               ::= { accFlashEntry 3 }
          accFlashLength   OBJECT-TYPE
               SYNTAX    INTEGER
               ACCESS    read-only
               STATUS    mandatory
               DESCRIPTION
			" "
               ::= { accFlashEntry 4 }
-- Translation Bridging Group
   accXBr         OBJECT IDENTIFIER ::= { accBRG 34 }
	accXBridge	OBJECT IDENTIFIER ::= { accXBr 1 }
	  accXBridgeStatus	OBJECT-TYPE   
		SYNTAX INTEGER {
			enabled(1),
			disabled(2)
			}
		ACCESS	read-write
		STATUS	mandatory
		DESCRIPTION
				 " Status of translation bridging."
		::= { accXBridge 1 }
	  accXBridgeRingId	OBJECT-TYPE   
        SYNTAX INTEGER
		ACCESS	read-write
		STATUS	mandatory
		DESCRIPTION
				 " Translation bridging ring ID."
		::= { accXBridge 2 }
-- Protocol Import Group
   accExtProtImp         OBJECT IDENTIFIER ::= { accBRG 35 }
          accExtProtImpTable   OBJECT-TYPE
               SYNTAX    SEQUENCE OF AccExtProtImpEntry
               ACCESS    not-accessible
               STATUS    mandatory
               DESCRIPTION
                         " "
               ::= { accExtProtImp 1 }
          accExtProtImpEntry   OBJECT-TYPE
               SYNTAX    AccExtProtImpEntry
               ACCESS    not-accessible
               STATUS    mandatory
               DESCRIPTION
                         " "
               INDEX     { accExtProtImpProtocol }
               ::= { accExtProtImpTable 1 }
          AccExtProtImpEntry ::= SEQUENCE {
   		accExtProtImpProtocol
                    INTEGER,
   		accExtProtImpAllowed
                    INTEGER
          }
          accExtProtImpProtocol   OBJECT-TYPE
               SYNTAX    INTEGER {
			rip(1),
			egp(2),
			static(3)
			}
               ACCESS    read-only
               STATUS    mandatory
               DESCRIPTION
			" "
               ::= { accExtProtImpEntry 1 }
          accExtProtImpAllowed   OBJECT-TYPE
               SYNTAX    INTEGER {
		       yes(1),
		       no(2)
		       }
               ACCESS    read-write
               STATUS    mandatory
               DESCRIPTION
			" "
               ::= { accExtProtImpEntry 2 }
-- Basic Rate ISDN Group
    accIsdn OBJECT IDENTIFIER ::= { accBRG 36 }
	-- The IsdnDsl Group
        accIsdnDsl OBJECT IDENTIFIER ::= { accIsdn 1 }
	    -- Configuration and operational parameters maintained and 
	    -- reported on a per-terminal (bridge/router) basis.
            accIsdnDslIndex OBJECT-TYPE
		SYNTAX INTEGER (1..255)
		ACCESS read-only
		STATUS deprecated
		DESCRIPTION
		  " An index instantiating a particular digital subscriber
		    loop interface on this bridge/router terminal."
		::= { accIsdnDsl 1 }
	-- The IsdnSub Group
	-- Configuration and operational parameters maintained and
	-- reported on a per-subscriber interface basis.
            accIsdnSubTable OBJECT-TYPE
		SYNTAX SEQUENCE OF AccIsdnSubEntry
		ACCESS not-accessible
		STATUS deprecated
		DESCRIPTION
		  " ISDN subscriber table containing configuration and
		    operational parameters for all ISDN subscriber
		    interfaces on this bridge/router terminal."
		::= { accIsdn 2 }
            accIsdnSubEntry OBJECT-TYPE
		SYNTAX AccIsdnSubEntry
		ACCESS not-accessible
		STATUS deprecated
		DESCRIPTION
		  " Configuration and operational parameters for a
		    particular ISDN subscriber interface."
		INDEX { accIsdnDslIndex }
		::= { accIsdnSubTable 1 }
            AccIsdnSubEntry ::= SEQUENCE {
                accIsdnDslIndex		INTEGER,
                accIsdnSubSwitchType	INTEGER,
                accIsdnSubChannelMode	INTEGER,
                accIsdnSubAdminStatus	INTEGER,
                accIsdnSubDiagLevel	INTEGER,
                accIsdnSubManualTei	INTEGER
		}
            accIsdnSubSwitchType OBJECT-TYPE
		SYNTAX INTEGER {
		    bri-net3(1),
		    bri-5ess(2),
		    bri-dms100(3),
		    bri-vn2(4),
		    bri-vn3(5),
		    bri-kdd(6),
		    bri-ntt(7),
		    bri-1tr6(8),
		    bri-ni1(9),
		    bri-ccitt(10)
		    }
		ACCESS read-write
		STATUS deprecated
		DESCRIPTION
		  " The particular type of central-office switch
		    providing access to the ISDN network and to
		    which this subscriber interface is connected."
		::= { accIsdnSubEntry 1 }
            accIsdnSubChannelMode OBJECT-TYPE
		SYNTAX INTEGER {
		    cm-1b-plus-d(1),
		    cm-2b-plus-d(2),
		    cm-1h-plus-d(3)
		    }
		ACCESS read-write
		STATUS deprecated
		DESCRIPTION
		  " The ISDN channel configuration mode."
		::= { accIsdnSubEntry 2 }
            accIsdnSubAdminStatus OBJECT-TYPE
		SYNTAX INTEGER {
		    enabled (1),
		    disabled (2)
		    }
		ACCESS read-write
		STATUS deprecated
		DESCRIPTION
		  " The administrative status of this subscriber
		    interface."
		::= { accIsdnSubEntry 3 }
            accIsdnSubDiagLevel OBJECT-TYPE
		SYNTAX INTEGER (0..5)
		ACCESS read-write
		STATUS deprecated
		DESCRIPTION
		  " The current diagnostic message level for this
		    subscriber interface."
		::= { accIsdnSubEntry 4 }
            accIsdnSubManualTei OBJECT-TYPE
		SYNTAX INTEGER (0..63) -- 127
		ACCESS read-write
		STATUS deprecated
		DESCRIPTION
		  " The TEI (terminal endpoint identifier) when manual
		    TEI assignment is required.  Setting this value
		    between 0 and 63 (inclusive) specifies manual TEI
		    assignment using the indicated value.  Setting 
		    this value to 127 (the broadcast TEI) specifies
		    automatic TEI assignment."
		::= { accIsdnSubEntry 5 }
	-- The IsdnStat Group
	-- Statistics and operational status maintained and
	-- reported on a per-subscriber interface basis.
            accIsdnStatTable OBJECT-TYPE
		SYNTAX SEQUENCE OF AccIsdnStatEntry
		ACCESS not-accessible
		STATUS deprecated
		DESCRIPTION
		  " Statistics and operational status maintained for all
		    ISDN subscriber interfaces on this bridge/router
		    terminal."
		::= { accIsdn 3 }
            accIsdnStatEntry OBJECT-TYPE
		SYNTAX AccIsdnStatEntry
		ACCESS not-accessible
		STATUS deprecated
		DESCRIPTION
		  " Statistics and operational status for a particular
		    ISDN subscriber interface."
		INDEX { accIsdnDslIndex }
		::= { accIsdnStatTable 1 }
            AccIsdnStatEntry ::= SEQUENCE {
                accIsdnDslIndex 	    INTEGER,
                accIsdnStatHdlcInPackets    Counter,
                accIsdnStatHdlcInOctets	    Counter,
                accIsdnStatHdlcInErrors	    Counter,
                accIsdnStatHdlcInDiscs	    Counter,
                accIsdnStatHdlcOutPackets   Counter,
                accIsdnStatHdlcOutOctets    Counter,
                accIsdnStatHdlcOutErrors    Counter,
                accIsdnStatHdlcOutDiscs	    Counter,
                accIsdnStatLapdUnsolicResps Counter,
                accIsdnStatLapdPeerSabmes   Counter,
                accIsdnStatLapdN200Errors   Counter,
                accIsdnStatLapdNrSeqErrors  Counter,
                accIsdnStatLapdRecvdFrmrs   Counter,
                accIsdnStatLapdCntlErrors   Counter,
                accIsdnStatLapdInfoErrors   Counter,
                accIsdnStatLapdWrongSizes   Counter,
                accIsdnStatLapdN201Errors   Counter,
                accIsdnStatCallsOriginateds Counter,
                accIsdnStatCallsOfferreds   Counter,
                accIsdnStatCallsAnswereds   Counter,
                accIsdnStatCallsAccepteds   Counter,
                accIsdnStatCallsCompleteds  Counter,
                accIsdnStatCallsCleareds    Counter,
                accIsdnStatDslOperStatus    INTEGER,
                accIsdnStatLastCauses	    INTEGER
		}
            accIsdnStatHdlcInPackets OBJECT-TYPE
		SYNTAX Counter
		ACCESS read-only
		STATUS deprecated
		DESCRIPTION
		  " The number of packets received on the D-channel
		    of this subscriber interface."
		::= { accIsdnStatEntry 1 }
            accIsdnStatHdlcInOctets OBJECT-TYPE
		SYNTAX Counter
		ACCESS read-only
		STATUS deprecated
		DESCRIPTION
		  " The number of octets received on the D-channel
		    of this subscriber interface."
		::= { accIsdnStatEntry 2 }
            accIsdnStatHdlcInErrors OBJECT-TYPE
		SYNTAX Counter
		ACCESS read-only
		STATUS deprecated
		DESCRIPTION
		  " The number of input hardware errors counted by
		    the D-channel input/output driver."
		::= { accIsdnStatEntry 3 }
            accIsdnStatHdlcInDiscs OBJECT-TYPE
		SYNTAX Counter
		ACCESS read-only
		STATUS deprecated
		DESCRIPTION
		  " The number of input packets discarded by the
		    D-channel input/output driver."
		::= { accIsdnStatEntry 4 }
            accIsdnStatHdlcOutPackets OBJECT-TYPE
		SYNTAX Counter
		ACCESS read-only
		STATUS deprecated
		DESCRIPTION
		  " The number of packets transmitted on the D-channel
		    of this subscriber interface."
		::= { accIsdnStatEntry 5 }
            accIsdnStatHdlcOutOctets OBJECT-TYPE
		SYNTAX Counter
		ACCESS read-only
		STATUS deprecated
		DESCRIPTION
		  " The number of octets transmitted on the D-channel
		    of this subscriber interface."
		::= { accIsdnStatEntry 6 }
            accIsdnStatHdlcOutErrors OBJECT-TYPE
		SYNTAX Counter
		ACCESS read-only
		STATUS deprecated
		DESCRIPTION
		  " The number of output hardware errors counted by
		    the D-channel input/output driver."
		::= { accIsdnStatEntry 7 }
            accIsdnStatHdlcOutDiscs OBJECT-TYPE
		SYNTAX Counter
		ACCESS read-only
		STATUS deprecated
		DESCRIPTION
		  " The number of output packets discarded by the
		    D-channel input/output driver."
		::= { accIsdnStatEntry 8 }
            accIsdnStatLapdUnsolicResps OBJECT-TYPE
		SYNTAX Counter
		ACCESS read-only
		STATUS deprecated
		DESCRIPTION
		  " The number of unsolicited LAPD response frames
		    received on all data links associated with the
		    D-channel of this subscriber interface."
		::= { accIsdnStatEntry 9 }
            accIsdnStatLapdPeerSabmes OBJECT-TYPE
		SYNTAX Counter
		ACCESS read-only
		STATUS deprecated
		DESCRIPTION
		  " The number of peer SABME frames received on all
		    data links associated with the D-channel of this
		    subscriber interface."
		::= { accIsdnStatEntry 10 }
            accIsdnStatLapdN200Errors OBJECT-TYPE
		SYNTAX Counter
		ACCESS read-only
		STATUS deprecated
		DESCRIPTION
		  " The number of unsuccessful T200 timer recoveries
		    after a frame has been retransmitted N200 times."
		::= { accIsdnStatEntry 11 }
            accIsdnStatLapdNrSeqErrors OBJECT-TYPE
		SYNTAX Counter
		ACCESS read-only
		STATUS deprecated
		DESCRIPTION
		  " The number of N(R) sequence errors."
		::= { accIsdnStatEntry 12 }
            accIsdnStatLapdRecvdFrmrs OBJECT-TYPE
		SYNTAX Counter
		ACCESS read-only
		STATUS deprecated
		DESCRIPTION
		  " The number of LAPD FRMR response frames received."
		::= { accIsdnStatEntry 13 }
            accIsdnStatLapdCntlErrors OBJECT-TYPE
		SYNTAX Counter
		ACCESS read-only
		STATUS deprecated
		DESCRIPTION
		  " The number of LAPD frames received with an invalid
		    or non-implemented control field."
		::= { accIsdnStatEntry 14 }
            accIsdnStatLapdInfoErrors OBJECT-TYPE
		SYNTAX Counter
		ACCESS read-only
		STATUS deprecated
		DESCRIPTION
		  " The number of LAPD frames received with a
		    non-permitted information (I) field."
		::= { accIsdnStatEntry 15 }
            accIsdnStatLapdWrongSizes OBJECT-TYPE
		SYNTAX Counter
		ACCESS read-only
		STATUS deprecated
		DESCRIPTION
		  " The number of LAPD frames received which were the
		    wrong size."
		::= { accIsdnStatEntry 16 }
            accIsdnStatLapdN201Errors OBJECT-TYPE
		SYNTAX Counter
		ACCESS read-only
		STATUS deprecated
		DESCRIPTION
		  " The number of LAPD frames received which contained
		    and information field which exceeded N201."
		::= { accIsdnStatEntry 17 }
            accIsdnStatCallsOriginateds OBJECT-TYPE
		SYNTAX Counter
		ACCESS read-only
		STATUS deprecated
		DESCRIPTION
		  " The number of outgoing calls originated on this
		    subscriber interface."
		::= { accIsdnStatEntry 18 }
            accIsdnStatCallsOfferreds OBJECT-TYPE
		SYNTAX Counter
		ACCESS read-only
		STATUS deprecated
		DESCRIPTION
		  " The number of incoming calls offerred on this
		    subscriber interface."
		::= { accIsdnStatEntry 19 }
            accIsdnStatCallsAnswereds OBJECT-TYPE
		SYNTAX Counter
		ACCESS read-only
		STATUS deprecated
		DESCRIPTION
		  " The number of outgoing calls originated on this
		    subscriber interface which were answered by the
		    destination."
		::= { accIsdnStatEntry 20 }
            accIsdnStatCallsAccepteds OBJECT-TYPE
		SYNTAX Counter
		ACCESS read-only
		STATUS deprecated
		DESCRIPTION
		  " The number of incoming calls offerred on this
		    subscriber interface which were accepted for
		    connection."
		::= { accIsdnStatEntry 21 }
            accIsdnStatCallsCompleteds OBJECT-TYPE
		SYNTAX Counter
		ACCESS read-only
		STATUS deprecated
		DESCRIPTION
		  " The number of outgoing and incoming calls
		    completed (that is, the number of calls which
		    were successfully connected)."
		::= { accIsdnStatEntry 22 }
            accIsdnStatCallsCleareds OBJECT-TYPE
		SYNTAX Counter
		ACCESS read-only
		STATUS deprecated
		DESCRIPTION
		  " The number of outgoing and incoming calls
		    cleared."
		::= { accIsdnStatEntry 23 }
            accIsdnStatDslOperStatus OBJECT-TYPE
		SYNTAX INTEGER {
		    inactive(1),	-- layer-1 deactivated
		    waiting(2),		-- awaiting activation
		    activated(3),	-- layer-1 activated
		    established(4)	-- multi-frame established
		    }
		ACCESS read-only
		STATUS deprecated
		DESCRIPTION
		  " The operation status of this interface."
		::= { accIsdnStatEntry 24 }
            accIsdnStatLastCauses OBJECT-TYPE
		SYNTAX INTEGER (0..255)
		ACCESS read-only
		STATUS deprecated
		DESCRIPTION
		  " The last cause value sent or received on this
		    subscriber interface."
		::= { accIsdnStatEntry 25 }
	-- The IsdnCall Group
	-- Parameters and operational status maintained and
	-- reported on a per-call basis.
            accIsdnCallTable OBJECT-TYPE
		SYNTAX SEQUENCE OF AccIsdnCallEntry
		ACCESS not-accessible
		STATUS deprecated
		DESCRIPTION
		  " Parameters and operational status for ISDN calls
		    active on this bridge/router terminal."
		::= { accIsdn 4 }
            accIsdnCallEntry OBJECT-TYPE
		SYNTAX AccIsdnCallEntry
		ACCESS not-accessible
		STATUS deprecated
		DESCRIPTION
		  " Parameters and operational status for a particular
		    ISDN call which is presently active or is in the
		    process of being established or cleared."
		INDEX { accIsdnCallDslIndex, accIsdnCallIdentifier }
		::= { accIsdnCallTable 1 }
            AccIsdnCallEntry ::= SEQUENCE {
                accIsdnCallIdentifier	INTEGER,
                accIsdnCallReference	INTEGER,
                accIsdnCallChannelId	INTEGER,
                accIsdnCallIfIndex	INTEGER,
                accIsdnCallInfoRate	INTEGER,
                accIsdnCallState	INTEGER,
                accIsdnCallCause	INTEGER,
                accIsdnCallOrigin	INTEGER,
                accIsdnCallAddress	OCTET STRING,
                accIsdnCallDslIndex	INTEGER
		}
            accIsdnCallIdentifier OBJECT-TYPE
		SYNTAX INTEGER (0..65536)
		ACCESS read-only
		STATUS deprecated
		DESCRIPTION
		  " The internal call control identifier for this call."
		::= { accIsdnCallEntry 1 }
            accIsdnCallReference OBJECT-TYPE
		SYNTAX INTEGER (1..32767)
		ACCESS read-only
		STATUS deprecated
		DESCRIPTION
		  " The Q.931 call reference value for this call."
		::= { accIsdnCallEntry 2 }
            accIsdnCallChannelId OBJECT-TYPE
		SYNTAX INTEGER {
		    none(1),		-- no channel allocated
		    b1(2),		-- B1
		    b2(3),		-- B2
		    h0(4)		-- hyperchannel (B1 + B2)
		    }
		ACCESS read-only
		STATUS deprecated
		DESCRIPTION
		  " The bearer channel interface ID allocated for this
		    call."
		::= { accIsdnCallEntry 3 }
            accIsdnCallIfIndex OBJECT-TYPE
		SYNTAX INTEGER {
		    j1(1),		-- J1
		    j2(2)		-- J2
		    }
		ACCESS read-only
		STATUS deprecated
		DESCRIPTION
		  " The interface index of the physical port connected
		    by the bearer channel."
		::= { accIsdnCallEntry 4 }
            accIsdnCallInfoRate OBJECT-TYPE
		SYNTAX INTEGER {
		    packet(1),
		    r-64k(17),
		    r-2x64k(18),
		    r-384k(20),
		    r-1536k(22),
		    r-1920k(24)
		    }
		ACCESS read-only
		STATUS deprecated
		DESCRIPTION
		  " The information transfer rate."
		::= { accIsdnCallEntry 5 }
            accIsdnCallState OBJECT-TYPE
		SYNTAX INTEGER {
		    disconnected(1),
		    incoming(2),
		    outgoing(3),
		    routing(4),
		    releaseing(5),
		    connected(6)
		    }
		ACCESS read-only
		STATUS deprecated
		DESCRIPTION
		  " The current call control state (not Q.931)."
		::= { accIsdnCallEntry 6 }
            accIsdnCallCause OBJECT-TYPE
		SYNTAX INTEGER (0..255)
		ACCESS read-only
		STATUS deprecated
		DESCRIPTION
		  " The last cause value associated with this call."
		::= { accIsdnCallEntry 7 }
            accIsdnCallOrigin OBJECT-TYPE
		SYNTAX INTEGER {
		    none(1),		-- not yet originated
		    terminal(2),	-- outgoing (TE-to-NT)
		    network(3)		-- incoming (NT-to_TE)
		    }
		ACCESS read-only
		STATUS deprecated
		DESCRIPTION
		  " The originator of the call."
		::= { accIsdnCallEntry 8 }
            accIsdnCallAddress OBJECT-TYPE
		SYNTAX OCTET STRING
		ACCESS read-only
		STATUS deprecated
		DESCRIPTION
		  " The remote call address associated with this call.
		    For incoming calls, this is the calling ISDN address.
		    For outgoing calls, this is the called ISDN address."
		::= { accIsdnCallEntry 9 }
            accIsdnCallDslIndex OBJECT-TYPE
		SYNTAX INTEGER (1..255)
		ACCESS read-only
		STATUS deprecated
		DESCRIPTION
		  " The interface index for the digital subscriber loop."
		::= { accIsdnCallEntry 10 }
	-- ISDN Interface Group
	--
	-- Implementation of the ISDN interface group is mandatory for all
	-- systems that implement a basic rate or primary rate ISDN
	-- interface.  The ISDN interface group consists of three tables:
	--	ISDN Subscriber Table
	--	ISDN Statistics Table
	--	ISDN Call Table
	-- These tables are indexed by a digital subscriber loop (DSL)
	-- index which has the same value as the ifIndex for the ISDN
	-- interface.  Prior to Release 8.0, the DSL index was a
	-- sequential integer index assigned independently of ifIndex.
	-- Due to the change in how ISDN tables are indexed, as well as
	-- other flaws in the ACC ISDN MIB definition, the following
	-- branches are being deprecated, and have been replaced by new
	-- branches:
	--	accIsdnDsl OBJECT IDENTIFIER ::= { accIsdn 1 }
	--	accIsdnSub OBJECT IDENTIFIER ::= { accIsdn 2 }
	--	accIsdnStat OBJECT IDENTIFIER ::= { accIsdn 3 }
	--	accIsdnCall OBJECT IDENTIFIER ::= { accIsdn 4 }
	-- ISDN Subscriber Table
	-- The ISDN Subscriber Table contains one entry for each BRI or
	-- PRI subscriber connection.  Only ISDN interfaces with a D
	-- channel have an entry in this table.  NFAS interfaces are not
	-- represented in this table.
            accIsdnxSubTable OBJECT-TYPE
		SYNTAX SEQUENCE OF AccIsdnxSubEntry
		ACCESS not-accessible
		STATUS mandatory
		DESCRIPTION
		  " ISDN subscriber table containing configuration and
		    operational parameters for all ISDN subscriber
		    interfaces on this bridge/router terminal."
		::= { accIsdn 6 }
            accIsdnxSubEntry OBJECT-TYPE
		SYNTAX AccIsdnxSubEntry
		ACCESS not-accessible
		STATUS mandatory
		DESCRIPTION
		  "An entry in the ISDN Subscriber Table"
		INDEX { accIsdnxSubDslIndex }
		::= { accIsdnxSubTable 1 }
            AccIsdnxSubEntry ::= SEQUENCE {
		accIsdnxSubDslIndex INTEGER,
		accIsdnxSubSwitchType INTEGER,
		accIsdnxSubChanConfig INTEGER,
		accIsdnxSubAdminStatus INTEGER,
		accIsdnxSubDiagLevel INTEGER,
		accIsdnxSubManualTei INTEGER,
		accIsdnxSubOperStatus INTEGER,
		accIsdnxSubNumNfas INTEGER ,
		accIsdnxSubLastCause INTEGER
		}
            accIsdnxSubDslIndex OBJECT-TYPE
		SYNTAX INTEGER (1..'7fffffff'h)
		ACCESS read-only
		STATUS mandatory
		DESCRIPTION
		  " The ifIndex of an ISDN BRI, DBRI, PRI/T1 or PRI/E1
		    interface on this managed device."
		::= { accIsdnxSubEntry 1 }
            accIsdnxSubSwitchType OBJECT-TYPE
                SYNTAX  INTEGER (1..23)
		ACCESS read-write
		STATUS mandatory
		DESCRIPTION
		  " The particular type of central-office switch
		    providing access to the ISDN network and to which
		    this subscriber interface is connected."
		::= { accIsdnxSubEntry 2 }
            accIsdnxSubChanConfig OBJECT-TYPE
		SYNTAX INTEGER (1..255)
		ACCESS read-write
		STATUS mandatory
		DESCRIPTION
		  " The ISDN channel configuration mode.  Beginning with
		    release 8.0, this is the number of bearer channels
		    managed by the D channel.  This object is normally
		    read-only.  It can be written only when changing the
		    channel configuration from 2B+D to 1B+D on a Nile
		    configured with a BRI in J1."
		::= { accIsdnxSubEntry 3 }
            accIsdnxSubAdminStatus OBJECT-TYPE
                SYNTAX  INTEGER (1..3)
		ACCESS read-write
		STATUS mandatory
		DESCRIPTION
		  "  The administrative status of this subscriber interface."
		::= { accIsdnxSubEntry 4 }
            accIsdnxSubDiagLevel OBJECT-TYPE
		SYNTAX INTEGER (0..6)
		ACCESS read-write
		STATUS mandatory
		DESCRIPTION
		  " The current diagnostic message level for this
		    subscriber interface."
		::= { accIsdnxSubEntry 5 }
            accIsdnxSubManualTei OBJECT-TYPE
		SYNTAX INTEGER (0..63) -- 127
		ACCESS read-write
		STATUS mandatory
		DESCRIPTION
		" The TEI (terminal endpoint identifier) when manual
		  TEI assignment is required.  Setting this value
		  between 0 and 63 (inclusive) specifies manual TEI
		  assignment using the indicated value.  Setting this
		  value to 127 (the broadcast TEI) specifies automatic
		  TEI assignment.  This object is writable only for BRI
		  subscribers.  For PRI subscribers, the value read is
		  always 0"
		::= { accIsdnxSubEntry 6 }
            accIsdnxSubOperStatus OBJECT-TYPE
                SYNTAX  INTEGER (1..4)
		ACCESS read-write
		STATUS mandatory
		DESCRIPTION
		" The operational status of this subscriber interface."
		::= { accIsdnxSubEntry 7 }
            accIsdnxSubNumNfas OBJECT-TYPE
		SYNTAX INTEGER (0..255)
		ACCESS read-only
		STATUS mandatory
		DESCRIPTION
		" Indicates the number of NFAS trunks managed by this D
		  channel."
		::= { accIsdnxSubEntry 8 }
            accIsdnxSubLastCause OBJECT-TYPE
		SYNTAX INTEGER (0..255)
		ACCESS read-only
		STATUS mandatory
		DESCRIPTION
		" The last clearing cause for a call associated with
		  this interface."
		::= { accIsdnxSubEntry 9 }
	-- ISDN Statistics Table
	--
	-- The ISDN statistics table contains one entry for each BRI or
	-- PRI subscriber loop connection.
	-- In the case of PRI subscribers, an entry exists only for PRI
	-- interfaces enabled for common  channel signaling (i.e.,
	-- interfaces containing a D channel).
	-- No statistics are maintained for NFAS-enabled subscriber loops.
            accIsdnxStatTable OBJECT-TYPE
		SYNTAX SEQUENCE OF AccIsdnxStatEntry
		ACCESS not-accessible
		STATUS mandatory
		DESCRIPTION
		" Statistics and operational status maintained for all
		  ISDN subscriber interfaces on this bridge/router
		  terminal."
		::= { accIsdn 7 }
            accIsdnxStatEntry OBJECT-TYPE
		SYNTAX AccIsdnxStatEntry
		ACCESS not-accessible
		STATUS mandatory
		DESCRIPTION
		" An entry in the ISDN Statistics Table."
		INDEX { accIsdnxStatDslIndex }
		::= { accIsdnxStatTable 1 }
            AccIsdnxStatEntry ::= SEQUENCE {
		accIsdnxStatDslIndex INTEGER,
		accIsdnxStatHdlcInPackets Counter,
		accIsdnxStatHdlcInOctets Counter,
		accIsdnxStatHdlcInErrors Counter,
		accIsdnxStatHdlcInDiscards Counter,
		accIsdnxStatHdlcOutPackets Counter,
		accIsdnxStatHdlcOutOctets Counter,
		accIsdnxStatHdlcOutErrors Counter,
		accIsdnxStatHdlcOutDiscards Counter,
		accIsdnxStatLapdUnsolicResps Counter,
		accIsdnxStatLapdPeerSabmes Counter,
		accIsdnxStatLapdN200Errors Counter,
		accIsdnxStatLapdNrSeqErrors Counter,
		accIsdnxStatLapdRecvdFrmrs Counter,
		accIsdnxStatLapdCntlErrors Counter,
		accIsdnxStatLapdInfoErrors Counter,
		accIsdnxStatLapdWrongSizes Counter,
		accIsdnxStatLapdN201Errors Counter,
		accIsdnxStatCallOriginateds Counter,
		accIsdnxStatCallOfferreds Counter,
		accIsdnxStatCallRouteds Counter,
		accIsdnxStatCallAccepteds Counter,
		accIsdnxStatCallCompleteds Counter,
		accIsdnxStatCallCleareds Counter }
            accIsdnxStatDslIndex OBJECT-TYPE
		SYNTAX INTEGER (1..'7fffffff'h)
		ACCESS read-only
		STATUS mandatory
		DESCRIPTION
		" The ifIndex of an ISDN BRI, DBRI, PRI/T1 or PRI/E1
		  interface on this managed device."
		::= { accIsdnxStatEntry 1 }
            accIsdnxStatHdlcInPackets OBJECT-TYPE
		SYNTAX Counter
		ACCESS read-only
		STATUS mandatory
		DESCRIPTION
		" The number of packets received on the D-channel of
		  this ISDN interface."
		::= { accIsdnxStatEntry 2 }
            accIsdnxStatHdlcInOctets OBJECT-TYPE
		SYNTAX Counter
		ACCESS read-only
		STATUS mandatory
		DESCRIPTION
		" The number of octets received on the D-channel of
		  this ISDN interface."
		::= { accIsdnxStatEntry 3 }
            accIsdnxStatHdlcInErrors OBJECT-TYPE
		SYNTAX Counter
		ACCESS read-only
		STATUS mandatory
		DESCRIPTION
		" The number of input hardware errors counted by the
		  D-channel HDLC driver."
		::= { accIsdnxStatEntry 4 }
            accIsdnxStatHdlcInDiscards OBJECT-TYPE
		SYNTAX Counter
		ACCESS read-only
		STATUS mandatory
		DESCRIPTION
		" The number of input packets discarded by the
		  D-channel HDLC driver."
		::= { accIsdnxStatEntry 5 }
            accIsdnxStatHdlcOutPackets OBJECT-TYPE
		SYNTAX Counter
		ACCESS read-only
		STATUS mandatory
		DESCRIPTION
		" The number of packets transmitted on the D-channel of
		  this ISDN interface."
		::= { accIsdnxStatEntry 6 }
            accIsdnxStatHdlcOutOctets OBJECT-TYPE
		SYNTAX Counter
		ACCESS read-only
		STATUS mandatory
		DESCRIPTION
		" The number of octets transmitted on the D-channel of
		  this ISDN interface."
		::= { accIsdnxStatEntry 7 }
            accIsdnxStatHdlcOutErrors OBJECT-TYPE
		SYNTAX Counter
		ACCESS read-only
		STATUS mandatory
		DESCRIPTION
		" The number of output hardware errors counted by the
		  D-channel HDLC driver."
		::= { accIsdnxStatEntry 8 }
            accIsdnxStatHdlcOutDiscards OBJECT-TYPE
		SYNTAX Counter
		ACCESS read-only
		STATUS mandatory
		DESCRIPTION
		" The number of output packets discarded by the
		  D-channel HDLC driver."
		::= { accIsdnxStatEntry 9 }
            accIsdnxStatLapdUnsolicResps OBJECT-TYPE
		SYNTAX Counter
		ACCESS read-only
		STATUS mandatory
		DESCRIPTION
		" The number of unsolicited LAPD response frames
		  received on all data links associated with the
		  D-channel of this ISDN interface."
		::= { accIsdnxStatEntry 10 }
            accIsdnxStatLapdPeerSabmes OBJECT-TYPE
		SYNTAX Counter
		ACCESS read-only
		STATUS mandatory
		DESCRIPTION
		" The number of peer SABME frames received on all data
		  links associated with the D-channel of this ISDN
		  interface."
		::= { accIsdnxStatEntry 11 }
            accIsdnxStatLapdN200Errors OBJECT-TYPE
		SYNTAX Counter
		ACCESS read-only
		STATUS mandatory
		DESCRIPTION
		" The number of unsuccessful T200 timer recoveries
		  after a frame has been retransmitted N200 times."
		::= { accIsdnxStatEntry 12 }
            accIsdnxStatLapdNrSeqErrors OBJECT-TYPE
		SYNTAX Counter
		ACCESS read-only
		STATUS mandatory
		DESCRIPTION
		" The number of N(R) sequence errors."
		::= { accIsdnxStatEntry 13 }
            accIsdnxStatLapdRecvdFrmrs OBJECT-TYPE
		SYNTAX Counter
		ACCESS read-only
		STATUS mandatory
		DESCRIPTION
		" The number of LAPD FRMR response frames received."
		::= { accIsdnxStatEntry 14 }
            accIsdnxStatLapdCntlErrors OBJECT-TYPE
		SYNTAX Counter
		ACCESS read-only
		STATUS mandatory
		DESCRIPTION
		" The number of LAPD frames received with an invalid or
		  non-implemented control field."
		::= { accIsdnxStatEntry 15 }
            accIsdnxStatLapdInfoErrors OBJECT-TYPE
		SYNTAX Counter
		ACCESS read-only
		STATUS mandatory
		DESCRIPTION
		" The number of LAPD frames received with a
		  non-permitted information (I) field."
		::= { accIsdnxStatEntry 16 }
            accIsdnxStatLapdWrongSizes OBJECT-TYPE
		SYNTAX Counter
		ACCESS read-only
		STATUS mandatory
		DESCRIPTION
		" The number of LAPD frames received which were the
		  wrong size."
		::= { accIsdnxStatEntry 17 }
            accIsdnxStatLapdN201Errors OBJECT-TYPE
		SYNTAX Counter
		ACCESS read-only
		STATUS mandatory
		DESCRIPTION
		" The number of LAPD frames received which contained
		  and information field which exceeded N201."
		::= { accIsdnxStatEntry 18 }
            accIsdnxStatCallOriginateds OBJECT-TYPE
		SYNTAX Counter
		ACCESS read-only
		STATUS mandatory
		DESCRIPTION
		" The number of outgoing calls originated on this ISDN
		  interface."
		::= { accIsdnxStatEntry 19 }
            accIsdnxStatCallOfferreds OBJECT-TYPE
		SYNTAX Counter
		ACCESS read-only
		STATUS mandatory
		DESCRIPTION
		" The number of incoming calls offered on this ISDN
		  interface."
		::= { accIsdnxStatEntry 20 }
            accIsdnxStatCallRouteds OBJECT-TYPE
		SYNTAX Counter
		ACCESS read-only
		STATUS mandatory
		DESCRIPTION
		" The number of outgoing calls originated on this ISDN
		  interface which were routed by the network."
		::= { accIsdnxStatEntry 21 }
            accIsdnxStatCallAccepteds OBJECT-TYPE
		SYNTAX Counter
		ACCESS read-only
		STATUS mandatory
		DESCRIPTION
		" The number of incoming calls offered on this ISDN
		  interface which were accepted for connection."
		::= { accIsdnxStatEntry 22 }
            accIsdnxStatCallCompleteds OBJECT-TYPE
		SYNTAX Counter
		ACCESS read-only
		STATUS mandatory
		DESCRIPTION
		" The number of outgoing and incoming calls completed
		  (that is, the number of calls which were successfully
		  connected)."
		::= { accIsdnxStatEntry 23 }
            accIsdnxStatCallCleareds OBJECT-TYPE
		SYNTAX Counter
		ACCESS read-only
		STATUS mandatory
		DESCRIPTION
		" The number of outgoing and incoming calls cleared."
		::= { accIsdnxStatEntry 24 }
	-- ISDN Call Table
	-- The ISDN call table contains an entry for each call in
	-- progress. A call is in progress if its call state is
	-- non-zero (i.e., not IDLE). All calls on all ISDN interfaces
	-- are co-mingled in the same table.
            accIsdnxCallTable OBJECT-TYPE
		SYNTAX SEQUENCE OF AccIsdnxCallEntry
		ACCESS not-accessible
		STATUS mandatory
		DESCRIPTION
		" Parameters and operational status for ISDN calls in
		  progress on this bridge/router terminal."
		::= { accIsdn 8 }
            accIsdnxCallEntry OBJECT-TYPE
		SYNTAX AccIsdnxCallEntry
		ACCESS not-accessible
		STATUS mandatory
		DESCRIPTION
		" An entry in the ISDN Call Table."
		INDEX { accIsdnxCallDslIndex, accIsdnxCallReference, accIsdnxCallOrigin }
		::= { accIsdnxCallTable 1 }
            AccIsdnxCallEntry ::= SEQUENCE {
		accIsdnxCallDslIndex INTEGER,
		accIsdnxCallReference INTEGER,
		accIsdnxCallOrigin INTEGER,
		 accIsdnxCallCircuitIndex INTEGER,
		accIsdnxCallInfoRate INTEGER,
		accIsdnxCallState INTEGER,
		accIsdnxCallCause INTEGER,
		accIsdnxCallAddress OCTET STRING,
		accIsdnxCallInfoType INTEGER,
		accIsdnxCallSlotMap INTEGER
		}
            accIsdnxCallDslIndex OBJECT-TYPE
		SYNTAX INTEGER (1..'7fffffff'h)
		ACCESS read-only
		STATUS mandatory
		DESCRIPTION
		" The ifIndex of an ISDN BRI, DBRI, PRI/T1 or PRI/E1
		  interface on this managed device."
		::= { accIsdnxCallEntry 1 }
            accIsdnxCallReference OBJECT-TYPE
		SYNTAX INTEGER (1..32767)
		ACCESS read-only
		STATUS mandatory
		DESCRIPTION
		" The Q.931 call reference value for this call."
		::= { accIsdnxCallEntry 2 }
            accIsdnxCallOrigin OBJECT-TYPE
                SYNTAX  INTEGER (1..3)
		ACCESS read-only
		STATUS mandatory
		DESCRIPTION
		" The originator of the call."
		::= { accIsdnxCallEntry 3 }
            accIsdnxCallCircuitIndex OBJECT-TYPE
		SYNTAX INTEGER (1..'7fffffff'h)
		ACCESS read-only
		STATUS mandatory
		DESCRIPTION
		" The ifIndex for the circuit associated with this call."
		::= { accIsdnxCallEntry 4 }
            accIsdnxCallInfoRate OBJECT-TYPE
                SYNTAX  INTEGER (1..33)
		ACCESS read-only
		STATUS mandatory
		DESCRIPTION
		" The information transfer rate."
		::= { accIsdnxCallEntry 5 }
            accIsdnxCallState OBJECT-TYPE
                SYNTAX  INTEGER (1..16)
		ACCESS read-only
		STATUS mandatory
		DESCRIPTION
		" The Q.931 call control state."
		::= { accIsdnxCallEntry 6 }
            accIsdnxCallCause OBJECT-TYPE
		SYNTAX INTEGER (0..255)
		ACCESS read-only
		STATUS mandatory
		DESCRIPTION
		" The last cause value associated with this call."
		::= { accIsdnxCallEntry 7 }
            accIsdnxCallAddress OBJECT-TYPE
		SYNTAX OCTET STRING
		ACCESS read-only
		STATUS mandatory
		DESCRIPTION
		" The remote call address associated with this call.
		  For incoming calls, this is the calling ISDN
		  address.  For outgoing calls, this is the called ISDN
		  address."
		::= { accIsdnxCallEntry 8 }
            accIsdnxCallInfoType OBJECT-TYPE
                SYNTAX  INTEGER (1..3)
		ACCESS read-only
		STATUS mandatory
		DESCRIPTION
		" The information transfer type:
		  info-type-cmd		circuit mode data, clear channel
		  			64 kbits/s
		  info-type-cm56	circuit mode data, rate-adapted
		  			to 56 kbits/s
		  info-type-cmv		circuit mode data over voice circuit"
		::= { accIsdnxCallEntry 9 }
            accIsdnxCallSlotMap OBJECT-TYPE
		SYNTAX INTEGER
		ACCESS read-only
		STATUS mandatory
		DESCRIPTION
		" A 31-bit mask which identifies the time-slots forming
		  a hyperchannel."
		::= { accIsdnxCallEntry 10 }
	-- The IsdnTest Group
        accIsdnTest OBJECT IDENTIFIER ::= { accIsdn 5 }
	    -- Parameters and commands maintained and reported on a
	    -- per-terminal basis used for controlling homologation
	    -- testing.
            accIsdnTestIfIndex OBJECT-TYPE
		SYNTAX INTEGER {
		    j1(1),		-- J1
		    j2(2)		-- J2
		    }
		ACCESS read-write
		STATUS mandatory
		DESCRIPTION
		  " The interface index for the physical port from
		    which a call will be made."
		::= { accIsdnTest 1 }
            accIsdnTestAddress OBJECT-TYPE
		SYNTAX OCTET STRING
		ACCESS read-write
		STATUS mandatory
		DESCRIPTION
		  " The ISDN destination call address."
		::= { accIsdnTest 2 }
            accIsdnTestCommand OBJECT-TYPE
		SYNTAX INTEGER {
		    normal(1),
		    accept(2),
		    reject(3),
		    ignore(4),
		    call(5),
		    clear(6),
		    disconnect(7),
		    loop(8),
		    unloop(9),
		    activate(10),
		    deactivate(11),
		    display(12)
		    }
		ACCESS read-write
		STATUS mandatory
		DESCRIPTION
		  " The action to be performed."
		::= { accIsdnTest 3 }
            accIsdnTestProceed OBJECT-TYPE
		SYNTAX INTEGER {
		    normal(1),
		    accept(2),
		    reject(3),
		    ignore(4)
		    }
		ACCESS read-only
		STATUS mandatory
		DESCRIPTION
		  " The action to be performed for incoming calls."
		::= { accIsdnTest 4 }
            accIsdnTestRegName OBJECT-TYPE
		SYNTAX INTEGER (0..31)
		ACCESS read-write
		STATUS mandatory
		DESCRIPTION
		  " The name of the MC145474 register to write.
		    nr0(0),
		    nr1(1),
		    nr2(2),
		    nr3(3),
		    nr4(4),
		    nr5(5),
		    nr6(6),
		    br0(16),
		    br1(17),
		    br2(18),
		    br3(19),
		    br4(20),
		    br5(21),
		    br6(22),
		    br7(23),
		    br8(24),
		    br9(25),
		    br10(26),
		    br11(27),
		    br12(28),
		    br13(29),
		    br14(30),
		    br15(31)
		"
		::= { accIsdnTest 5 }
            accIsdnTestRegValue OBJECT-TYPE
		SYNTAX INTEGER (0..255)
		ACCESS read-write
		STATUS mandatory
		DESCRIPTION
		  " The value to write to the MC145474 register."
		::= { accIsdnTest 6 }
-- ISDN SPID group
        accIsdnSpidTable OBJECT-TYPE
                SYNTAX SEQUENCE OF AccIsdnSpidEntry
                ACCESS not-accessible
                STATUS mandatory
                DESCRIPTION
                        " Valid SPIDs currently Registered with the
                          CO, required for placing/accepting calls."
                ::= { accIsdn 9 }
        accIsdnSpidEntry OBJECT-TYPE
                SYNTAX AccIsdnSpidEntry
                ACCESS not-accessible
                STATUS mandatory
                DESCRIPTION
                        " SPID information entry in the SPID Table."
                INDEX { accIsdnSpidIndex }
                ::= { accIsdnSpidTable 1 }
        AccIsdnSpidEntry ::= SEQUENCE {
		accIsdnSpidIndex INTEGER,
                accIsdnSpidValue DisplayString
		}
        accIsdnSpidIndex OBJECT-TYPE
                SYNTAX INTEGER
                ACCESS not-accessible
                STATUS mandatory
                DESCRIPTION
                        " An Index to Ports of B-channels."
                ::= { accIsdnSpidEntry 1 }
        accIsdnSpidValue OBJECT-TYPE
                SYNTAX DisplayString
                ACCESS read-write
                STATUS mandatory
                DESCRIPTION
                        " Value of SPID,Required for the terminal to be
                          active on the S/T bus."
                ::= { accIsdnSpidEntry 2 }
-- V25Bis Group
	accV25  OBJECT IDENTIFIER ::= { accBRG 37 }
		accV25StatTable OBJECT-TYPE
			SYNTAX SEQUENCE OF AccV25StatEntry
			ACCESS not-accessible
			STATUS mandatory
			DESCRIPTION
				" A list of Physical Port Entries that are 
			doing V25Bis Dialing."
		::= { accV25 1 }
		accV25StatEntry OBJECT-TYPE
			SYNTAX AccV25StatEntry
			ACCESS not-accessible 
			STATUS mandatory
			DESCRIPTION
				" A table entry providing information about
			a specific port that is using V25Bis as the dialing
			procedure."
			INDEX { accV25IntIndex }
		::= { accV25StatTable 1 }
		AccV25StatEntry ::= SEQUENCE {
			 	accV25IntIndex		INTEGER,
			 	accV25CurState		INTEGER,
			 	accV25DTRSignal		INTEGER,
			 	accV25DSRSignal		INTEGER,
			 	accV25CTSSignal		INTEGER,
			 	accV25CallAttempts	INTEGER,
			  	accV25CallSuccess	INTEGER
			}
		accV25IntIndex  OBJECT-TYPE
			SYNTAX INTEGER
			ACCESS read-only
			STATUS  mandatory
			DESCRIPTION
			" This is the port which is currently doing the
			V25 Bis dialing."
			::= { accV25StatEntry 1 }
		accV25CurState  OBJECT-TYPE
			SYNTAX INTEGER {
			       dte-not-ready(1),
			       dialogue-pending(2),
			       dialogue(3),
			       handshaking(4),
			       call-connected(5),
			       data-transfer(6),
			       clear-by-dte(7)
			       }
			ACCESS read-only
			STATUS  mandatory
			DESCRIPTION
			" This is the current state of the state machine."
			::= { accV25StatEntry 2 }
		accV25DTRSignal  OBJECT-TYPE
			SYNTAX  INTEGER  {
				on(1),
				off(2)
				}
			ACCESS read-only
			STATUS  mandatory
			DESCRIPTION
			" This is the current state of the 108/2 circuit."
			::= { accV25StatEntry 3 }
		accV25DSRSignal  OBJECT-TYPE
			SYNTAX  INTEGER  {
				on(1),
				off(2)
				}
			ACCESS read-only
			STATUS  mandatory
			DESCRIPTION
			" This is the current state of the 107 circuit."
			::= { accV25StatEntry 4 }
		accV25CTSSignal  OBJECT-TYPE
			SYNTAX  INTEGER  {
				on(1),
				off(2)
				}
			ACCESS read-only
			STATUS  mandatory
			DESCRIPTION
			" This is the current state of the 106 circuit."
			::= { accV25StatEntry 5 }
		accV25CallAttempts  OBJECT-TYPE
			SYNTAX INTEGER
			ACCESS read-only
			STATUS  mandatory
			DESCRIPTION
			" The number of Call Attempts made for the current
			destination."
			::= { accV25StatEntry 6 }
		accV25CallSuccess  OBJECT-TYPE
			SYNTAX INTEGER
			ACCESS read-only
			STATUS  mandatory
			DESCRIPTION
			" The number of Call Attempts which were successful
			for the current destination."
			::= { accV25StatEntry 7 }
-- Hub Group
      accEnetHub	OBJECT IDENTIFIER ::= { accBRG 39 }
	accEnetHubStatTable	OBJECT-TYPE
				SYNTAX SEQUENCE OF AccEnetHubStatEntry
				ACCESS  not-accessible
				STATUS mandatory
				DESCRIPTION
				"A List of Ethernet Hub Port statistics."
				::=   { accEnetHub 1 }
	AccEnetHubStatEntry ::=  SEQUENCE {
			accEnetPortIndex		INTEGER,		
			accEnetHubIndex			INTEGER,
			accEnetHubAdStatus		INTEGER,
			accEnetHubOpStatus		INTEGER,
			accEnetHubBitError		INTEGER,
			accEnetHubLinkTest		INTEGER
			}
	accEnetHubStatEntry	OBJECT-TYPE
			SYNTAX  AccEnetHubStatEntry
			ACCESS  not-accessible
			STATUS mandatory
			DESCRIPTION
			" A table entry providing information about Ethernet
			Hub ports."
			INDEX   { accEnetPortIndex, accEnetHubIndex }
			::=  { accEnetHubStatTable	1 }
	accEnetPortIndex	OBJECT-TYPE
			SYNTAX  INTEGER
			ACCESS   read-only
			STATUS mandatory
			DESCRIPTION
			" This is the Ethernet Physical Port starting with 1"
			::=  { accEnetHubStatEntry	1 }
	accEnetHubIndex	OBJECT-TYPE
			SYNTAX  INTEGER
			ACCESS   read-only
			STATUS mandatory
			DESCRIPTION
			" This is the Ethernet Hub Port index 1-8"
			::=  { accEnetHubStatEntry	2 }
	accEnetHubAdStatus	OBJECT-TYPE
			SYNTAX  INTEGER {
			enabled(1),
			disabled(2)
						}
			ACCESS   read-write
			STATUS mandatory
			DESCRIPTION
			"This is the current administrative status of the
			Ethernet Hub Port."
			::=  { accEnetHubStatEntry	3 }
	accEnetHubOpStatus	  OBJECT-TYPE
			SYNTAX  INTEGER {
				connected (1),
				partitioned (2),
				disabled (3)
				}
			ACCESS   read-only
			STATUS mandatory
			DESCRIPTION
			" This shows the Operational State of the Ethernet
			Hub Port"
			::=  { accEnetHubStatEntry	4 }
	accEnetHubBitError	 OBJECT-TYPE
			SYNTAX  INTEGER {
				yes (1),
				no (2)
				}
			ACCESS   read-only
			STATUS mandatory
			DESCRIPTION
			" This shows whether a bit-error has occurred"
			::=  { accEnetHubStatEntry	5 }
	accEnetHubLinkTest	 OBJECT-TYPE
			SYNTAX  INTEGER {
				pass (1),
				fail (2)
				}
			ACCESS   read-only
			STATUS mandatory
			DESCRIPTION
			" This shows whether a link test has occurred"
			::=  { accEnetHubStatEntry	6 }
END
