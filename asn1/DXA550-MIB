------------------------------------------------------------------------
--
-- MIB ASN.1 for the DXA-550, version 1.0
--
-- Standard groups and tables that are not implemented in the dxa550
-- are in here, but commented out.
--
------------------------------------------------------------------------


DXA550-MIB DEFINITIONS ::= BEGIN
	IMPORTS
			mgmt, NetworkAddress, IpAddress, Counter, Gauge, TimeTicks
		FROM RFC1155-SMI
			OBJECT-TYPE
		FROM RFC-1212;

	-- nullSpecific OBJECT IDENTIFIER ::= { 0 0 }

	internet     OBJECT IDENTIFIER ::= { iso org(3) dod(6) 1 }
	directory    OBJECT IDENTIFIER ::= { internet 1 }
	mgmt         OBJECT IDENTIFIER ::= { internet 2 }
	experimental OBJECT IDENTIFIER ::= { internet 3 }
	private      OBJECT IDENTIFIER ::= { internet 4 }
	enterprises  OBJECT IDENTIFIER ::= { private 1 }

	mib-2      OBJECT IDENTIFIER ::= { mgmt 1 }

	system       OBJECT IDENTIFIER ::= { mib-2 1 }
	interfaces   OBJECT IDENTIFIER ::= { mib-2 2 }
	-- at           OBJECT IDENTIFIER ::= { mib-2 3 }
	ip			OBJECT IDENTIFIER ::= { mib-2 4 }
	icmp		OBJECT IDENTIFIER ::= { mib-2 5 }
	-- tcp          OBJECT IDENTIFIER ::= { mib-2 6 }
	udp          OBJECT IDENTIFIER ::= { mib-2 7 }
	-- transmission OBJECT IDENTIFIER ::= { mib-2 10 }
	snmp         OBJECT IDENTIFIER ::= { mib-2 11 }

	-- Our private tree space.

	datability	OBJECT IDENTIFIER ::= { enterprises 187 }

	-- Put Internet Experimental MIBS under cExper
	cExper			OBJECT IDENTIFIER ::= { datability 1 }
	dot3			OBJECT IDENTIFIER ::= { cExper 3 }
	ifExtensions	OBJECT IDENTIFIER ::= { cExper 6 }
	dot1dBridge		OBJECT IDENTIFIER ::= { cExper 14 }

	-- Product Registration Hierarchy
	cProducts		OBJECT IDENTIFIER ::= { datability 2 }
	cdxa560			OBJECT IDENTIFIER ::= { cProducts 1 }
	cdxa550			OBJECT IDENTIFIER ::= { cProducts 2 }

	--
	-- Subtree to contain proprietary extensions to the standard MIB-II
	-- Groups.
	--

	cStdExtensions	OBJECT IDENTIFIER ::= { datability 3 }

	-- Each extension subtree's OID is similar tothe OID of the
	-- related group in MIB-II in that if the MIB-II group's OID
	-- is defined as { mib-2 n } then the extension subtree's
	-- OID is defined as { cStdExtensions n }.
	--
	-- These subtrees contain extensions to the standard mibs that
	-- are common across all DXA-500 Series Products.
	--

--	cSystem			OBJECT IDENTIFIER ::= { cStdExtensions 1 }
--	cInterfaces		OBJECT IDENTIFIER ::= { cStdExtensions 2 }
	cIp				OBJECT IDENTIFIER ::= { cStdExtensions 4 }
	cIcmp			OBJECT IDENTIFIER ::= { cStdExtensions 5 }
--	cTcp			OBJECT IDENTIFIER ::= { cStdExtensions 6 }
	cUdp			OBJECT IDENTIFIER ::= { cStdExtensions 7 }
	cTransmission	OBJECT IDENTIFIER ::= { cStdExtensions 10 }
	cDot3			OBJECT IDENTIFIER ::= { cTransmission 3 }
--	cSnmp			OBJECT IDENTIFIER ::= { cStdExtensions 11 }

	--
	-- This subtree contains MIB Objects that are specific to the
	-- DXA-550.
	--
	dDXA550	OBJECT IDENTIFIER ::= { datability 4 }

	--
	-- Textual Conventions
	--

	DisplayString ::= OCTET STRING 
	PhysAddress ::= OCTET STRING 

	sysDescr OBJECT-TYPE
		SYNTAX	DisplayString (SIZE (0..255))
		ACCESS	read-only
		STATUS	mandatory
		DESCRIPTION
			"A textual description of the entity.  This value
			should include the full name and version
			identification of the system's hardware type,
			software operating-system, and networking
			software.  It is mandatory that this only contain
			printable ASCII characters."
		::= { system 1 }

	sysObjectID OBJECT-TYPE
		SYNTAX	OBJECT IDENTIFIER
		ACCESS	read-only
		STATUS	mandatory
		DESCRIPTION
			"The vendor's authoritative identification of the
			network management subsystem contained in the
			entity.  This value is allocated within the SMI
			enterprises subtree (1.3.6.1.4.1) and provides an
			easy and unambiguous means for determining `what
			kind of box' is being managed.  For example, if
			vendor `Flintstones, Inc.' was assigned the
			subtree 1.3.6.1.4.1.4242, it could assign the
			identifier 1.3.6.1.4.1.4242.1.1 to its `Fred
			Router'."
		::= { system 2 }

	sysUpTime OBJECT-TYPE
		SYNTAX	TimeTicks
		ACCESS	read-only
		STATUS	mandatory
		DESCRIPTION
			"The time (in hundredths of a second) since the
			network management portion of the system was last
			re-initialized."
		::= { system 3 }

	sysContact OBJECT-TYPE
		SYNTAX	DisplayString (SIZE (0..255))
		ACCESS	read-write
		STATUS	mandatory
		DESCRIPTION
			"The textual identification of the contact person
			for this managed node, together with information
			on how to contact this person."
		::= { system 4 }

	sysName OBJECT-TYPE
		SYNTAX	DisplayString (SIZE (0..255))
		ACCESS	read-write
		STATUS	mandatory
		DESCRIPTION
			"An administratively-assigned name for this
			managed node.  By convention, this is the node's
			fully-qualified domain name."
		::= { system 5 }

	sysLocation OBJECT-TYPE
		SYNTAX	DisplayString (SIZE (0..255))
		ACCESS	read-write
		STATUS	mandatory
		DESCRIPTION
			"The physical location of this node (e.g.,
			`telephone closet, 3rd floor')."
		::= { system 6 }

	sysServices OBJECT-TYPE
		SYNTAX	INTEGER (0..127)
		ACCESS	read-only
		STATUS	mandatory
		DESCRIPTION
			"A value which indicates the set of services that
			this entity primarily offers.

			The value is a sum.  This sum initially takes the
			value zero, Then, for each layer, L, in the range
			1 through 7, that this node performs transactions
			for, 2 raised to (L - 1) is added to the sum.  For
			example, a node which performs primarily routing
			functions would have a value of 4 (2^(3-1)).  In
			contrast, a node which is a host offering
			application services would have a value of 72
			(2^(4-1) + 2^(7-1)).  Note that in the context of
			the Internet suite of protocols, values should be
			calculated accordingly:

			layer  functionality
			1  physical (e.g., repeaters)
			2  datalink/subnetwork (e.g., bridges)
			3  internet (e.g., IP gateways)
			4  end-to-end  (e.g., IP hosts)
			7  applications (e.g., mail relays)

			For systems including OSI protocols, layers 5 and
			6 may also be counted."
		::= { system 7 }

	-- the Interfaces group

	-- Implementation of the Interfaces group is mandatory for
	-- all systems.

	ifNumber OBJECT-TYPE
		SYNTAX	INTEGER
		ACCESS	read-only
		STATUS	mandatory
		DESCRIPTION
			"The number of network interfaces (regardless of
			their current state) present on this system."
		::= { interfaces 1 }


-- the Interfaces table

-- The Interfaces table contains information on the entity's
-- interfaces.  Each interface is thought of as being
-- attached to a `subnetwork'.  Note that this term should
-- not be confused with `subnet' which refers to an
-- addressing partitioning scheme used in the Internet suite
-- of protocols.

	ifTable OBJECT-TYPE
		SYNTAX	SEQUENCE OF IfEntry
		ACCESS	not-accessible
		STATUS	mandatory
		DESCRIPTION
			"A list of interface entries.  The number of
			entries is given by the value of ifNumber."
		::= { interfaces 2 }

	ifEntry OBJECT-TYPE
		SYNTAX	IfEntry
		ACCESS	not-accessible
		STATUS	mandatory
		DESCRIPTION
			"An interface entry containing objects at the
			subnetwork layer and below for a particular
			interface."
		INDEX	{ ifIndex }
		::= { ifTable 1 }

	IfEntry ::= SEQUENCE {
		ifIndex				INTEGER,
		ifDescr				DisplayString,
		ifType				INTEGER,
		ifMtu				INTEGER,
		ifSpeed				Gauge,
		ifPhysAddress		PhysAddress,
		ifAdminStatus		INTEGER,
		ifOperStatus		INTEGER,
		ifLastChange		TimeTicks,
		ifInOctets			Counter,
		ifInUcastPkts		Counter,
		ifInNUcastPkts		Counter,
		ifInDiscards		Counter,
		ifInErrors			Counter,
		ifInUnknownProtos	Counter,
		ifOutOctets			Counter,
		ifOutUcastPkts		Counter,
		ifOutNUcastPkts		Counter,
		ifOutDiscards		Counter,
		ifOutErrors			Counter,
		ifOutQLen			Gauge,
		ifSpecific			OBJECT IDENTIFIER
		}

	ifIndex OBJECT-TYPE
		SYNTAX	INTEGER
		ACCESS	read-only
		STATUS	mandatory
		DESCRIPTION
			"A unique value for each interface.  Its value
			ranges between 1 and the value of ifNumber.  The
			value for each interface must remain constant at
			least from one re-initialization of the entity's
			network management system to the next re-
			initialization."
		::= { ifEntry 1 }

	ifDescr OBJECT-TYPE
		SYNTAX	DisplayString (SIZE (0..255))
		ACCESS	read-only
		STATUS	mandatory
		DESCRIPTION
			"A textual string containing information about the
			interface.  This string should include the name of
			the manufacturer, the product name and the version
			of the hardware interface."
		::= { ifEntry 2 }

	ifType OBJECT-TYPE
		SYNTAX	INTEGER {
				other(1),			-- none of the following
				regular1822(2),
				hdh1822(3),
				ddn-x25(4),
				rfc877-x25(5),
				ethernet-csmacd(6),
				iso88023-csmacd(7),
				iso88024-tokenBus(8),
				iso88025-tokenRing(9),
				iso88026-man(10),
				starLan(11),
				proteon-10Mbit(12),
				proteon-80Mbit(13),
				hyperchannel(14),
				fddi(15),
				lapb(16),
				sdlc(17),
				ds1(18),			-- T-1
				e1(19),				-- european equiv. of T-1
				basicISDN(20),
				primaryISDN(21),	-- proprietary serial
				propPointToPointSerial(22),
				ppp(23),
				softwareLoopback(24),
				eon(25),			-- CLNP over IP [11]
				ethernet-3Mbit(26),
				nsip(27),			-- XNS over IP
				slip(28),			-- generic SLIP
				ultra(29),			-- ULTRA technologies
				ds3(30),			-- T-3
				sip(31),			-- SMDS
				frame-relay(32)
			}
		ACCESS	read-only
		STATUS	mandatory
		DESCRIPTION
			"The type of interface, distinguished according to
			the physical/link protocol(s) immediately `below'
			the network layer in the protocol stack."
		::= { ifEntry 3 }

	ifMtu OBJECT-TYPE
		SYNTAX	INTEGER
		ACCESS	read-only
		STATUS	mandatory
		DESCRIPTION
			"The size of the largest datagram which can be
			sent/received on the interface, specified in
			octets.  For interfaces that are used for
			transmitting network datagrams, this is the size
			of the largest network datagram that can be sent
			on the interface."
		::= { ifEntry 4 }

	ifSpeed OBJECT-TYPE
		SYNTAX	Gauge
		ACCESS	read-only
		STATUS	mandatory
		DESCRIPTION
			"An estimate of the interface's current bandwidth
			in bits per second.  For interfaces which do not
			vary in bandwidth or for those where no accurate
			estimation can be made, this object should contain
			the nominal bandwidth."
		::= { ifEntry 5 }

	ifPhysAddress OBJECT-TYPE
--		SYNTAX	PhysAddress
		SYNTAX	OCTET STRING
		ACCESS	read-only
		STATUS	mandatory
		DESCRIPTION
			"The interface's address at the protocol layer
			immediately `below' the network layer in the
			protocol stack.  For interfaces which do not have
			such an address (e.g., a serial line), this object
			should contain an octet string of zero length."
		::= { ifEntry 6 }

	ifAdminStatus OBJECT-TYPE
		SYNTAX	INTEGER {
				up(1),
				down(2),
				testing(3)
			}
		ACCESS	read-write
		STATUS	mandatory
		DESCRIPTION
			"The desired state of the interface.  The
			testing(3) state indicates that no operational
			packets can be passed."
		::= { ifEntry 7 }

	ifOperStatus OBJECT-TYPE
		SYNTAX	INTEGER {
				up(1),
				down(2),
				testing(3)
			}
		ACCESS	read-only
		STATUS	mandatory
		DESCRIPTION
			"The current operational state of the interface.
			The testing(3) state indicates that no operational
			packets can be passed."
		::= { ifEntry 8 }

	ifLastChange OBJECT-TYPE
		SYNTAX	TimeTicks
		ACCESS	read-only
		STATUS	mandatory
		DESCRIPTION
			"The value of sysUpTime at the time the interface
			entered its current operational state.  If the
			current state was entered prior to the last re-
			initialization of the local network management
			subsystem, then this object contains a zero
			value."
		::= { ifEntry 9 }

	ifInOctets OBJECT-TYPE
		SYNTAX	Counter
		ACCESS	read-only
		STATUS	mandatory
		DESCRIPTION
			"The total number of octets received on the
			interface, including framing characters."
		::= { ifEntry 10 }

	ifInUcastPkts OBJECT-TYPE
		SYNTAX	Counter
		ACCESS	read-only
		STATUS	mandatory
		DESCRIPTION
			"The number of subnetwork-unicast packets
			delivered to a higher-layer protocol."
		::= { ifEntry 11 }

	ifInNUcastPkts OBJECT-TYPE
		SYNTAX	Counter
		ACCESS	read-only
		STATUS	mandatory
		DESCRIPTION
			"The number of non-unicast (i.e., subnetwork-
			broadcast or subnetwork-multicast) packets
			delivered to a higher-layer protocol."
		::= { ifEntry 12 }

	ifInDiscards OBJECT-TYPE
		SYNTAX	Counter
		ACCESS	read-only
		STATUS	mandatory
		DESCRIPTION
			"The number of inbound packets which were chosen
			to be discarded even though no errors had been
			detected to prevent their being deliverable to a
			higher-layer protocol.  One possible reason for
			discarding such a packet could be to free up
			buffer space."
		::= { ifEntry 13 }

	ifInErrors OBJECT-TYPE
		SYNTAX	Counter
		ACCESS	read-only
		STATUS	mandatory
		DESCRIPTION
			"The number of inbound packets that contained
			errors preventing them from being deliverable to a
			higher-layer protocol."
		::= { ifEntry 14 }

	ifInUnknownProtos OBJECT-TYPE
		SYNTAX	Counter
		ACCESS	read-only
		STATUS	mandatory
		DESCRIPTION
			"The number of packets received via the interface
			which were discarded because of an unknown or
			unsupported protocol."
		::= { ifEntry 15 }

	ifOutOctets OBJECT-TYPE
		SYNTAX	Counter
		ACCESS	read-only
		STATUS	mandatory
		DESCRIPTION
			"The total number of octets transmitted out of the
			interface, including framing characters."
		::= { ifEntry 16 }

	ifOutUcastPkts OBJECT-TYPE
		SYNTAX	Counter
		ACCESS	read-only
		STATUS	mandatory
		DESCRIPTION
			"The total number of packets that higher-level
			protocols requested be transmitted to a
			subnetwork-unicast address, including those that
			were discarded or not sent."
		::= { ifEntry 17 }

	ifOutNUcastPkts OBJECT-TYPE
		SYNTAX	Counter
		ACCESS	read-only
		STATUS	mandatory
		DESCRIPTION
			"The total number of packets that higher-level
			protocols requested be transmitted to a non-
			unicast (i.e., a subnetwork-broadcast or
			subnetwork-multicast) address, including those
			that were discarded or not sent."
		::= { ifEntry 18 }

	ifOutDiscards OBJECT-TYPE
		SYNTAX	Counter
		ACCESS	read-only
		STATUS	mandatory
		DESCRIPTION
			"The number of outbound packets which were chosen
			to be discarded even though no errors had been
			detected to prevent their being transmitted.  One
			possible reason for discarding such a packet could
			be to free up buffer space."
		::= { ifEntry 19 }

	ifOutErrors OBJECT-TYPE
		SYNTAX	Counter
		ACCESS	read-only
		STATUS	mandatory
		DESCRIPTION
			"The number of outbound packets that could not be
			transmitted because of errors."
		::= { ifEntry 20 }

	ifOutQLen OBJECT-TYPE
		SYNTAX	Gauge
		ACCESS	read-only
		STATUS	mandatory
		DESCRIPTION
			"The length of the output packet queue (in
			packets)."
		::= { ifEntry 21 }

	ifSpecific OBJECT-TYPE
		SYNTAX	OBJECT IDENTIFIER
		ACCESS	read-only
		STATUS	mandatory
		DESCRIPTION
			"A reference to MIB definitions specific to the
			particular media being used to realize the
			interface.  For example, if the interface is
			realized by an ethernet, then the value of this
			object refers to a document defining objects
			specific to ethernet.  If an agent is not
			configured to have a value for any of these
			variables, the object identifier

				nullSpecific OBJECT IDENTIFIER ::= { 0 0 }

			is returned.  Note that `nullSpecific' is a
			syntatically valid object identifier, and any
			conformant implementation of ASN.1 and BER must be
			able to generate and recognize this value."
		::= { ifEntry 22 }


-- the Address Translation group

-- Implementation of the Address Translation group is
-- mandatory for all systems.  Note however that this group
-- is deprecated by MIB-II. That is, it is being included
-- solely for compatibility with MIB-I nodes, and will most
-- likely be excluded from MIB-III nodes.  From MIB-II and
-- onwards, each network protocol group contains its own
-- address translation tables.

-- The Address Translation group contains one table which is
-- the union across all interfaces of the translation tables
-- for converting a NetworkAddress (e.g., an IP address) into
-- a subnetwork-specific address.  For lack of a better term,
-- this document refers to such a subnetwork-specific address
-- as a `physical' address.

-- Examples of such translation tables are: for broadcast
-- media where ARP is in use, the translation table is
-- equivalent to the ARP cache; or, on an X.25 network where
-- non-algorithmic translation to X.121 addresses is
-- required, the translation table contains the
-- NetworkAddress to X.121 address equivalences.

--        atTable OBJECT-TYPE
--            SYNTAX	SEQUENCE OF AtEntry
--            ACCESS	not-accessible
--            STATUS	deprecated
--            DESCRIPTION
--                    "The Address Translation tables contain the
--                    NetworkAddress to `physical' address equivalences.
--                    Some interfaces do not use translation tables for
--                    determining address equivalences (e.g., DDN-X.25
--                    has an algorithmic method); if all interfaces are
--                    of this type, then the Address Translation table
--                    is empty, i.e., has zero entries."
--            ::= { at 1 }

--        atEntry OBJECT-TYPE
--            SYNTAX	AtEntry
--            ACCESS	not-accessible
--            STATUS	deprecated
--            DESCRIPTION
--                    "Each entry contains one NetworkAddress to
--                    `physical' address equivalence."
--            INDEX   { atIfIndex,
--                      atNetAddress }
--            ::= { atTable 1 }

--        AtEntry ::=
--            SEQUENCE {
--                atIfIndex
--                    INTEGER,
--                atPhysAddress
--                    PhysAddress,
--                atNetAddress
--                    NetworkAddress
--            }

--        atIfIndex OBJECT-TYPE
--            SYNTAX	INTEGER
--            ACCESS	read-write
--            STATUS	deprecated
--            DESCRIPTION
--                    "The interface on which this entry's equivalence
--                    is effective.  The interface identified by a
--                    particular value of this index is the same
--                    interface as identified by the same value of
--                    ifIndex."
--            ::= { atEntry 1 }

--        atPhysAddress OBJECT-TYPE
--            SYNTAX	PhysAddress
--            ACCESS	read-write
--            STATUS	deprecated
--            DESCRIPTION
--                    "The media-dependent `physical' address.

--                    Setting this object to a null string (one of zero
--                    length) has the effect of invaliding the
--                    corresponding entry in the atTable object.  That
--                    is, it effectively dissasociates the interface
--                    identified with said entry from the mapping
--                    identified with said entry.  It is an
--                    implementation-specific matter as to whether the
--                    agent removes an invalidated entry from the table.
--                    Accordingly, management stations must be prepared
--                    to receive tabular information from agents that
--                    corresponds to entries not currently in use.
--                    Proper interpretation of such entries requires
--                    examination of the relevant atPhysAddress object."
--            ::= { atEntry 2 }

--        atNetAddress OBJECT-TYPE
--            SYNTAX	NetworkAddress
--            ACCESS	read-write
--            STATUS	deprecated
--            DESCRIPTION
--                    "The NetworkAddress (e.g., the IP address)
--                    corresponding to the media-dependent `physical'
--                    address."
--            ::= { atEntry 3 }

-- the IP group

-- Implementation of the IP group is mandatory for all
-- systems.

	ipForwarding OBJECT-TYPE
		SYNTAX	INTEGER {
				forwarding(1),		-- acting as a gateway
				not-forwarding(2)	-- NOT acting as a gateway
			}
		ACCESS	read-write
		STATUS	mandatory
		DESCRIPTION
			"The indication of whether this entity is acting
			as an IP gateway in respect to the forwarding of
			datagrams received by, but not addressed to, this
			entity.  IP gateways forward datagrams.  IP hosts
			do not (except those source-routed via the host).

			Note that for some managed nodes, this object may
			take on only a subset of the values possible.
			Accordingly, it is appropriate for an agent to
			return a `badValue' response if a management
			station attempts to change this object to an
			inappropriate value."
		::= { ip 1 }

	ipDefaultTTL OBJECT-TYPE
		SYNTAX	INTEGER
		ACCESS	read-write
		STATUS	mandatory
		DESCRIPTION
			"The default value inserted into the Time-To-Live
			field of the IP header of datagrams originated at
			this entity, whenever a TTL value is not supplied
			by the transport layer protocol."
		::= { ip 2 }

	ipInReceives OBJECT-TYPE
		SYNTAX	Counter
		ACCESS	read-only
		STATUS	mandatory
		DESCRIPTION
			"The total number of input datagrams received from
			interfaces, including those received in error."
		::= { ip 3 }

	ipInHdrErrors OBJECT-TYPE
		SYNTAX	Counter
		ACCESS	read-only
		STATUS	mandatory
		DESCRIPTION
			"The number of input datagrams discarded due to
			errors in their IP headers, including bad
			checksums, version number mismatch, other format
			errors, time-to-live exceeded, errors discovered
			in processing their IP options, etc."
		::= { ip 4 }

	ipInAddrErrors OBJECT-TYPE
		SYNTAX	Counter
		ACCESS	read-only
		STATUS	mandatory
		DESCRIPTION
			"The number of input datagrams discarded because
			the IP address in their IP header's destination
			field was not a valid address to be received at
			this entity.  This count includes invalid
			addresses (e.g., 0.0.0.0) and addresses of
			unsupported Classes (e.g., Class E).  For entities
			which are not IP Gateways and therefore do not
			forward datagrams, this counter includes datagrams
			discarded because the destination address was not
			a local address."
		::= { ip 5 }

	ipForwDatagrams OBJECT-TYPE
		SYNTAX	Counter
		ACCESS	read-only
		STATUS	mandatory
		DESCRIPTION
			"The number of input datagrams for which this
			entity was not their final IP destination, as a
			result of which an attempt was made to find a
			route to forward them to that final destination.
			In entities which do not act as IP Gateways, this
			counter will include only those packets which were
			Source-Routed via this entity, and the Source-
			Route option processing was successful."
		::= { ip 6 }

	ipInUnknownProtos OBJECT-TYPE
		SYNTAX	Counter
		ACCESS	read-only
		STATUS	mandatory
		DESCRIPTION
			"The number of locally-addressed datagrams
			received successfully but discarded because of an
			unknown or unsupported protocol."
		::= { ip 7 }

	ipInDiscards OBJECT-TYPE
		SYNTAX	Counter
		ACCESS	read-only
		STATUS	mandatory
		DESCRIPTION
			"The number of input IP datagrams for which no
			problems were encountered to prevent their
			continued processing, but which were discarded
			(e.g., for lack of buffer space).  Note that this
			counter does not include any datagrams discarded
			while awaiting re-assembly."
		::= { ip 8 }

	ipInDelivers OBJECT-TYPE
		SYNTAX	Counter
		ACCESS	read-only
		STATUS	mandatory
		DESCRIPTION
			"The total number of input datagrams successfully
			delivered to IP user-protocols (including ICMP)."
		::= { ip 9 }

	--
	-- datability IP extensions. A couple of counters
	-- that are extensions on the ipInHdrErrors object.
	-- All of these counters are included within the
	-- ipInHdrErrors object.
	--
	cIpInLenErrors OBJECT-TYPE
		SYNTAX	Counter
		ACCESS	read-only
		STATUS	mandatory
		DESCRIPTION
			"Number of packets received with an inconsistant
			Header/Packet length"
		::= { cIp 1 }

	cIpInVersionErrors OBJECT-TYPE
		SYNTAX	Counter
		ACCESS	read-only
		STATUS	mandatory
		DESCRIPTION
			"Number of packets received with an incorrect
			IP version number."
		::= { cIp 2 }

	cIpInCSErrors OBJECT-TYPE
		SYNTAX	Counter
		ACCESS	read-only
		STATUS	mandatory
		DESCRIPTION
			"Number of packets received with an incorrect
			IP checksum."
		::= { cIp 3 }

	cIpTTLZero OBJECT-TYPE
		SYNTAX	Counter
		ACCESS	read-only
		STATUS	mandatory
		DESCRIPTION
			"Number of packets that would have been forwarded
			but their TTL went to 0."
		::= { cIp 4 }

	ipOutRequests OBJECT-TYPE
		SYNTAX	Counter
		ACCESS	read-only
		STATUS	mandatory
		DESCRIPTION
			"The total number of IP datagrams which local IP
			user-protocols (including ICMP) supplied to IP in
			requests for transmission.  Note that this counter
			does not include any datagrams counted in
			ipForwDatagrams."
		::= { ip 10 }

	ipOutDiscards OBJECT-TYPE
		SYNTAX	Counter
		ACCESS	read-only
		STATUS	mandatory
		DESCRIPTION
			"The number of output IP datagrams for which no
			problem was encountered to prevent their
			transmission to their destination, but which were
			discarded (e.g., for lack of buffer space).  Note
			that this counter would include datagrams counted
			in ipForwDatagrams if any such packets met this
			(discretionary) discard criterion."
		::= { ip 11 }

	ipOutNoRoutes OBJECT-TYPE
		SYNTAX	Counter
		ACCESS	read-only
		STATUS	mandatory
		DESCRIPTION
			"The number of IP datagrams discarded because no
			route could be found to transmit them to their
			destination.  Note that this counter includes any
			packets counted in ipForwDatagrams which meet this
			`no-route' criterion.  Note that this includes any
			datagarms which a host cannot route because all of
			its default gateways are down."
		::= { ip 12 }

	ipReasmTimeout OBJECT-TYPE
		SYNTAX	INTEGER
		ACCESS	read-only
		STATUS	mandatory
		DESCRIPTION
			"The maximum number of seconds which received
			fragments are held while they are awaiting
			reassembly at this entity."
		::= { ip 13 }

	ipReasmReqds OBJECT-TYPE
		SYNTAX	Counter
		ACCESS	read-only
		STATUS	mandatory
		DESCRIPTION
			"The number of IP fragments received which needed
			to be reassembled at this entity."
		::= { ip 14 }

	ipReasmOKs OBJECT-TYPE
		SYNTAX	Counter
		ACCESS	read-only
		STATUS	mandatory
		DESCRIPTION
			"The number of IP datagrams successfully re-
			assembled."
		::= { ip 15 }

	ipReasmFails OBJECT-TYPE
		SYNTAX	Counter
		ACCESS	read-only
		STATUS	mandatory
		DESCRIPTION
			"The number of failures detected by the IP re-
			assembly algorithm (for whatever reason: timed
			out, errors, etc).  Note that this is not
			necessarily a count of discarded IP fragments
			since some algorithms (notably the algorithm in
			RFC 815) can lose track of the number of fragments
			by combining them as they are received."
		::= { ip 16 }

	cIpReasmTimeOuts OBJECT-TYPE
		SYNTAX	Counter
		ACCESS	read-only
		STATUS	mandatory
		DESCRIPTION
			"Number of reassmebly timeouts. This is included inthe
			ipReasmFails object."
		::= { cIp 5 }

	ipFragOKs OBJECT-TYPE
		SYNTAX	Counter
		ACCESS	read-only
		STATUS	mandatory
		DESCRIPTION
			"The number of IP datagrams that have been
			successfully fragmented at this entity."
		::= { ip 17 }

	ipFragFails OBJECT-TYPE
		SYNTAX	Counter
		ACCESS	read-only
		STATUS	mandatory
		DESCRIPTION
			"The number of IP datagrams that have been
			discarded because they needed to be fragmented at
			this entity but could not be, e.g., because their
			Don't Fragment flag was set."
		::= { ip 18 }

	ipFragCreates OBJECT-TYPE
		SYNTAX	Counter
		ACCESS	read-only
		STATUS	mandatory
		DESCRIPTION
			"The number of IP datagram fragments that have
			been generated as a result of fragmentation at
			this entity."
		::= { ip 19 }

-- the IP address table

-- The IP address table contains this entity's IP addressing
-- information.

	ipAddrTable OBJECT-TYPE
		SYNTAX	SEQUENCE OF IpAddrEntry
		ACCESS	not-accessible
		STATUS	mandatory
		DESCRIPTION
			"The table of addressing information relevant to
			this entity's IP addresses."
		::= { ip 20 }

		ipAddrEntry OBJECT-TYPE
		SYNTAX	IpAddrEntry
		ACCESS	not-accessible
		STATUS	mandatory
		DESCRIPTION
			"The addressing information for one of this
			entity's IP addresses."
		INDEX	{ ipAdEntAddr }
		::= { ipAddrTable 1 }

	IpAddrEntry ::= SEQUENCE {
			ipAdEntAddr			IpAddress,
			ipAdEntIfIndex		INTEGER,
			ipAdEntNetMask		IpAddress,
			ipAdEntBcastAddr	INTEGER,
			ipAdEntReasmMaxSize	INTEGER (0..65535)
		}

	ipAdEntAddr OBJECT-TYPE
		SYNTAX	IpAddress
		ACCESS	read-only
		STATUS	mandatory
		DESCRIPTION
			"The IP address to which this entry's addressing
			information pertains."
		::= { ipAddrEntry 1 }

	ipAdEntIfIndex OBJECT-TYPE
		SYNTAX	INTEGER
		ACCESS	read-only
		STATUS	mandatory
		DESCRIPTION
			"The index value which uniquely identifies the
			interface to which this entry is applicable.  The
			interface identified by a particular value of this
			index is the same interface as identified by the
			same value of ifIndex."
		::= { ipAddrEntry 2 }

	ipAdEntNetMask OBJECT-TYPE
		SYNTAX	IpAddress
		ACCESS	read-only
		STATUS	mandatory
		DESCRIPTION
			"The subnet mask associated with the IP address of
			this entry.  The value of the mask is an IP
			address with all the network bits set to 1 and all
			the hosts bits set to 0."
		::= { ipAddrEntry 3 }

	ipAdEntBcastAddr OBJECT-TYPE
		SYNTAX	INTEGER
		ACCESS	read-only
		STATUS	mandatory
		DESCRIPTION
			"The value of the least-significant bit in the IP
			broadcast address used for sending datagrams on
			the (logical) interface associated with the IP
			address of this entry.  For example, when the
			Internet standard all-ones broadcast address is
			used, the value will be 1.  This value applies to
			both the subnet and network broadcasts addresses
			used by the entity on this (logical) interface."
		::= { ipAddrEntry 4 }

	ipAdEntReasmMaxSize OBJECT-TYPE
		SYNTAX	INTEGER (0..65535)
		ACCESS	read-only
		STATUS	mandatory
		DESCRIPTION
			"The size of the largest IP datagram which this
			entity can re-assemble from incoming IP fragmented
			datagrams received on this interface."
		::= { ipAddrEntry 5 }

-- the IP routing table

-- The IP routing table contains an entry for each route
-- presently known to this entity.

	ipRouteTable OBJECT-TYPE
		SYNTAX	SEQUENCE OF IpRouteEntry
		ACCESS	not-accessible
		STATUS	mandatory
		DESCRIPTION
			"This entity's IP Routing table."
		::= { ip 21 }

	ipRouteEntry OBJECT-TYPE
		SYNTAX	IpRouteEntry
		ACCESS	not-accessible
		STATUS	mandatory
		DESCRIPTION
			"A route to a particular destination."
		INDEX   { ipRouteDest }
		::= { ipRouteTable 1 }

	IpRouteEntry ::= SEQUENCE {
			ipRouteDest		IpAddress,
			ipRouteIfIndex	INTEGER,
			ipRouteMetric1	INTEGER,
			ipRouteMetric2	INTEGER,
			ipRouteMetric3	INTEGER,
			ipRouteMetric4	INTEGER,
			ipRouteNextHop	IpAddress,
			ipRouteType		INTEGER,
			ipRouteProto	INTEGER,
			ipRouteAge		INTEGER,
			ipRouteMask		IpAddress,
			ipRouteMetric5	INTEGER,
			ipRouteInfo		OBJECT IDENTIFIER
		}

	ipRouteDest OBJECT-TYPE
		SYNTAX	IpAddress
		ACCESS	read-write
		STATUS	mandatory
		DESCRIPTION
			"The destination IP address of this route.  An
			entry with a value of 0.0.0.0 is considered a
			default route.  Multiple routes to a single
			destination can appear in the table, but access to
			such multiple entries is dependent on the table-
			access mechanisms defined by the network
			management protocol in use."
		::= { ipRouteEntry 1 }

	ipRouteIfIndex OBJECT-TYPE
		SYNTAX	INTEGER
		ACCESS	read-write
		STATUS	mandatory
		DESCRIPTION
			"The index value which uniquely identifies the
			local interface through which the next hop of this
			route should be reached.  The interface identified
			by a particular value of this index is the same
			interface as identified by the same value of
			ifIndex."
		::= { ipRouteEntry 2 }

	ipRouteMetric1 OBJECT-TYPE
		SYNTAX	INTEGER
		ACCESS	read-write
		STATUS	mandatory
		DESCRIPTION
			"The primary routing metric for this route.  The
			semantics of this metric are determined by the
			routing-protocol specified in the route's
			ipRouteProto value.  If this metric is not used,
			its value should be set to -1."
		::= { ipRouteEntry 3 }

	ipRouteMetric2 OBJECT-TYPE
		SYNTAX	INTEGER
		ACCESS	read-write
		STATUS	mandatory
		DESCRIPTION
			"An alternate routing metric for this route.  The
			semantics of this metric are determined by the
			routing-protocol specified in the route's
			ipRouteProto value.  If this metric is not used,
			its value should be set to -1."
		::= { ipRouteEntry 4 }

	ipRouteMetric3 OBJECT-TYPE
		SYNTAX	INTEGER
		ACCESS	read-write
		STATUS	mandatory
		DESCRIPTION
			"An alternate routing metric for this route.  The
			semantics of this metric are determined by the
			routing-protocol specified in the route's
			ipRouteProto value.  If this metric is not used,
			its value should be set to -1."
		::= { ipRouteEntry 5 }

		ipRouteMetric4 OBJECT-TYPE
		SYNTAX	INTEGER
		ACCESS	read-write
		STATUS	mandatory
		DESCRIPTION
			"An alternate routing metric for this route.  The
			semantics of this metric are determined by the
			routing-protocol specified in the route's
			ipRouteProto value.  If this metric is not used,
			its value should be set to -1."
		::= { ipRouteEntry 6 }

	ipRouteNextHop OBJECT-TYPE
		SYNTAX	IpAddress
		ACCESS	read-write
		STATUS	mandatory
		DESCRIPTION
			"The IP address of the next hop of this route.
			(In the case of a route bound to an interface
			which is realized via a broadcast media, the value
			of this field is the agent's IP address on that
			interface.)"
		::= { ipRouteEntry 7 }

	ipRouteType OBJECT-TYPE
		SYNTAX	INTEGER {
				other(1),	-- none of the following
				invalid(2),	-- an invalidated route

							-- route to directly
				direct(3),	-- connected (sub-)network

							-- route to a non-local
				indirect(4)	-- host/network/sub-network
			}
		ACCESS	read-write
		STATUS	mandatory
		DESCRIPTION
			"The type of route.  Note that the values
			direct(3) and indirect(4) refer to the notion of
			direct and indirect routing in the IP
			architecture.

			Setting this object to the value invalid(2) has
			the effect of invalidating the corresponding entry
			in the ipRouteTable object.  That is, it
			effectively dissasociates the destination
			identified with said entry from the route
			identified with said entry.  It is an
			implementation-specific matter as to whether the
			agent removes an invalidated entry from the table.
			Accordingly, management stations must be prepared
			to receive tabular information from agents that
			corresponds to entries not currently in use.
			Proper interpretation of such entries requires
			examination of the relevant ipRouteType object."
		::= { ipRouteEntry 8 }

	ipRouteProto OBJECT-TYPE
		SYNTAX	INTEGER {
				other(1),		-- none of the following

				-- non-protocol information, E.g.,
				-- manually configured entries
				local(2),

				-- set via a network management protocol
				netmgmt(3),

				-- obtained via ICMP, e.g., redirect
				icmp(4),

				-- the remaining values are
				-- all gateway routing
				-- protocols
				egp(5),
				ggp(6),
				hello(7),
				rip(8),
				is-is(9),
				es-is(10),
				ciscoIgrp(11),
				bbnSpfIgp(12),
				ospf(13),
				bgp(14)
			}
		ACCESS	read-only
		STATUS	mandatory
		DESCRIPTION
			"The routing mechanism via which this route was
			learned.  Inclusion of values for gateway routing
			protocols is not intended to imply that hosts
			should support those protocols."
		::= { ipRouteEntry 9 }

	ipRouteAge OBJECT-TYPE
		SYNTAX	INTEGER
		ACCESS	read-write
		STATUS	mandatory
		DESCRIPTION
			"The number of seconds since this route was last
			updated or otherwise determined to be correct.
			Note that no semantics of `too old' can be implied
			except through knowledge of the routing protocol
			by which the route was learned."
		::= { ipRouteEntry 10 }

	ipRouteMask OBJECT-TYPE
		SYNTAX	IpAddress
		ACCESS	read-write
		STATUS	mandatory
		DESCRIPTION
			"Indicate the mask to be logical-ANDed with the
			destination address before being compared to the
			value in the ipRouteDest field.  For those systems
			that do not support arbitrary subnet masks, an
			agent constructs the value of the ipRouteMask by
			determining whether the value of the correspondent
			ipRouteDest field belong to a class-A, B, or C
			network, and then using one of:

			mask           network
			255.0.0.0      class-A
			255.255.0.0    class-B
			255.255.255.0  class-C

			If the value of the ipRouteDest is 0.0.0.0 (a
			default route), then the mask value is also
			0.0.0.0.  It should be noted that all IP routing
			subsystems implicitly use this mechanism."
		::= { ipRouteEntry 11 }

		ipRouteMetric5 OBJECT-TYPE
		SYNTAX	INTEGER
		ACCESS	read-write
		STATUS	mandatory
		DESCRIPTION
			"An alternate routing metric for this route.  The
			semantics of this metric are determined by the
			routing-protocol specified in the route's
			ipRouteProto value.  If this metric is not used,
			its value should be set to -1."
		::= { ipRouteEntry 12 }

	ipRouteInfo OBJECT-TYPE
		SYNTAX	OBJECT IDENTIFIER
		ACCESS	read-write
		STATUS	mandatory
		DESCRIPTION
			"A reference to MIB definitions specific to the
			particular routing protocol which is responsible
			for this route, as determined by the value
			specified in the route's ipRouteProto value.  If
			this information is not present, its value should
			be set to the OBJECT IDENTIFIER { 0 0 }, which is
			a syntatically valid object identifier, and any
			conformant implementation of ASN.1 and BER must be
			able to generate and recognize this value."
		::= { ipRouteEntry 13 }


-- the IP Address Translation table

-- The IP address translation table contain the IpAddress to
-- `physical' address equivalences.  Some interfaces do not
-- use translation tables for determining address
-- equivalences (e.g., DDN-X.25 has an algorithmic method);
-- if all interfaces are of this type, then the Address
-- Translation table is empty, i.e., has zero entries.

--        ipNetToMediaTable OBJECT-TYPE
--            SYNTAX	SEQUENCE OF IpNetToMediaEntry
--            ACCESS	not-accessible
--            STATUS	mandatory
--            DESCRIPTION
--                    "The IP Address Translation table used for mapping
--                    from IP addresses to physical addresses."
--            ::= { ip 22 }

--        ipNetToMediaEntry OBJECT-TYPE
--            SYNTAX	IpNetToMediaEntry
--            ACCESS	not-accessible
--            STATUS	mandatory
--            DESCRIPTION
--                    "Each entry contains one IpAddress to `physical'
--                    address equivalence."
--            INDEX   { ipNetToMediaIfIndex,
--                      ipNetToMediaNetAddress }
--            ::= { ipNetToMediaTable 1 }

--        IpNetToMediaEntry ::=
--            SEQUENCE {
--                ipNetToMediaIfIndex
--                    INTEGER,
--                ipNetToMediaPhysAddress
--                    PhysAddress,
--                ipNetToMediaNetAddress
--                    IpAddress,
--                ipNetToMediaType
--                    INTEGER
--            }

--        ipNetToMediaIfIndex OBJECT-TYPE
--            SYNTAX	INTEGER
--            ACCESS	read-write
--            STATUS	mandatory
--            DESCRIPTION
--                    "The interface on which this entry's equivalence
--                    is effective.  The interface identified by a
--                    particular value of this index is the same
--                    interface as identified by the same value of
--                    ifIndex."
--            ::= { ipNetToMediaEntry 1 }

--        ipNetToMediaPhysAddress OBJECT-TYPE
--            SYNTAX	PhysAddress
--            ACCESS	read-write
--            STATUS	mandatory
--            DESCRIPTION
--                    "The media-dependent `physical' address."
--            ::= { ipNetToMediaEntry 2 }

--        ipNetToMediaNetAddress OBJECT-TYPE
--            SYNTAX	IpAddress
--            ACCESS	read-write
--            STATUS	mandatory
--            DESCRIPTION
--                    "The IpAddress corresponding to the media-
--                    dependent `physical' address."
--            ::= { ipNetToMediaEntry 3 }

--        ipNetToMediaType OBJECT-TYPE
--            SYNTAX	INTEGER {
--                        other(1),         none of the following
--                        invalid(2),       an invalidated mapping
--                        dynamic(3),
--                        static(4)
--                    }
--            ACCESS	read-write
--            STATUS	mandatory
--            DESCRIPTION
--                    "The type of mapping.

--                    Setting this object to the value invalid(2) has
--                    the effect of invalidating the corresponding entry
--                    in the ipNetToMediaTable.  That is, it effectively
--                    dissasociates the interface identified with said
--                    entry from the mapping identified with said entry.
--                    It is an implementation-specific matter as to
--                    whether the agent removes an invalidated entry
--                    from the table.  Accordingly, management stations
--                    must be prepared to receive tabular information
--                    from agents that corresponds to entries not
--                    currently in use.  Proper interpretation of such
--                    entries requires examination of the relevant
--                    ipNetToMediaType object."
--            ::= { ipNetToMediaEntry 4 }

-- the ICMP group

-- Implementation of the ICMP group is mandatory for all
-- systems.

	icmpInMsgs OBJECT-TYPE
		SYNTAX	Counter
		ACCESS	read-only
		STATUS	mandatory
		DESCRIPTION
			"The total number of ICMP messages which the
			entity received.  Note that this counter includes
			all those counted by icmpInErrors."
		::= { icmp 1 }

	icmpInErrors OBJECT-TYPE
		SYNTAX	Counter
		ACCESS	read-only
		STATUS	mandatory
		DESCRIPTION
			"The number of ICMP messages which the entity
			received but determined as having ICMP-specific
			errors (bad ICMP checksums, bad length, etc.)."
		::= { icmp 2 }

	icmpInDestUnreachs OBJECT-TYPE
		SYNTAX	Counter
		ACCESS	read-only
		STATUS	mandatory
		DESCRIPTION
			"The number of ICMP Destination Unreachable
			messages received."
		::= { icmp 3 }

	icmpInTimeExcds OBJECT-TYPE
		SYNTAX	Counter
		ACCESS	read-only
		STATUS	mandatory
		DESCRIPTION
			"The number of ICMP Time Exceeded messages
			received."
		::= { icmp 4 }

	icmpInParmProbs OBJECT-TYPE
		SYNTAX	Counter
		ACCESS	read-only
		STATUS	mandatory
		DESCRIPTION
			"The number of ICMP Parameter Problem messages
			received."
		::= { icmp 5 }

	icmpInSrcQuenchs OBJECT-TYPE
		SYNTAX	Counter
		ACCESS	read-only
		STATUS	mandatory
		DESCRIPTION
			"The number of ICMP Source Quench messages
			received."
		::= { icmp 6 }

	icmpInRedirects OBJECT-TYPE
		SYNTAX	Counter
		ACCESS	read-only
		STATUS	mandatory
		DESCRIPTION
			"The number of ICMP Redirect messages received."
		::= { icmp 7 }

	icmpInEchos OBJECT-TYPE
		SYNTAX	Counter
		ACCESS	read-only
		STATUS	mandatory
		DESCRIPTION
			"The number of ICMP Echo (request) messages
			received."
		::= { icmp 8 }

	icmpInEchoReps OBJECT-TYPE
		SYNTAX	Counter
		ACCESS	read-only
		STATUS	mandatory
		DESCRIPTION
			"The number of ICMP Echo Reply messages received."
		::= { icmp 9 }

	icmpInTimestamps OBJECT-TYPE
		SYNTAX	Counter
		ACCESS	read-only
		STATUS	mandatory
		DESCRIPTION
			"The number of ICMP Timestamp (request) messages
			received."
		::= { icmp 10 }

	icmpInTimestampReps OBJECT-TYPE
		SYNTAX	Counter
		ACCESS	read-only
		STATUS	mandatory
		DESCRIPTION
			"The number of ICMP Timestamp Reply messages
			received."
		::= { icmp 11 }

	icmpInAddrMasks OBJECT-TYPE
		SYNTAX	Counter
		ACCESS	read-only
		STATUS	mandatory
		DESCRIPTION
			"The number of ICMP Address Mask Request messages
			received."
		::= { icmp 12 }

	icmpInAddrMaskReps OBJECT-TYPE
		SYNTAX	Counter
		ACCESS	read-only
		STATUS	mandatory
		DESCRIPTION
			"The number of ICMP Address Mask Reply messages
			received."
		::= { icmp 13 }

	icmpOutMsgs OBJECT-TYPE
		SYNTAX	Counter
		ACCESS	read-only
		STATUS	mandatory
		DESCRIPTION
			"The total number of ICMP messages which this
			entity attempted to send.  Note that this counter
			includes all those counted by icmpOutErrors."
		::= { icmp 14 }

	icmpOutErrors OBJECT-TYPE
		SYNTAX	Counter
		ACCESS	read-only
		STATUS	mandatory
		DESCRIPTION
			"The number of ICMP messages which this entity did
			not send due to problems discovered within ICMP
			such as a lack of buffers.  This value should not
			include errors discovered outside the ICMP layer
			such as the inability of IP to route the resultant
			datagram.  In some implementations there may be no
			types of error which contribute to this counter's
			value."
		::= { icmp 15 }

	icmpOutDestUnreachs OBJECT-TYPE
		SYNTAX	Counter
		ACCESS	read-only
		STATUS	mandatory
		DESCRIPTION
			"The number of ICMP Destination Unreachable
			messages sent."
		::= { icmp 16 }

	icmpOutTimeExcds OBJECT-TYPE
		SYNTAX	Counter
		ACCESS	read-only
		STATUS	mandatory
		DESCRIPTION
			"The number of ICMP Time Exceeded messages sent."
		::= { icmp 17 }

	icmpOutParmProbs OBJECT-TYPE
		SYNTAX	Counter
		ACCESS	read-only
		STATUS	mandatory
		DESCRIPTION
			"The number of ICMP Parameter Problem messages
			sent."
		::= { icmp 18 }

	icmpOutSrcQuenchs OBJECT-TYPE
		SYNTAX	Counter
		ACCESS	read-only
		STATUS	mandatory
		DESCRIPTION
			"The number of ICMP Source Quench messages sent."
		::= { icmp 19 }

	icmpOutRedirects OBJECT-TYPE
		SYNTAX	Counter
		ACCESS	read-only
		STATUS	mandatory
		DESCRIPTION
			"The number of ICMP Redirect messages sent.  For a
			host, this object will always be zero, since hosts
			do not send redirects."
		::= { icmp 20 }

	icmpOutEchos OBJECT-TYPE
		SYNTAX	Counter
		ACCESS	read-only
		STATUS	mandatory
		DESCRIPTION
			"The number of ICMP Echo (request) messages sent."
		::= { icmp 21 }

	icmpOutEchoReps OBJECT-TYPE
		SYNTAX	Counter
		ACCESS	read-only
		STATUS	mandatory
		DESCRIPTION
			"The number of ICMP Echo Reply messages sent."
		::= { icmp 22 }

	icmpOutTimestamps OBJECT-TYPE
		SYNTAX	Counter
		ACCESS	read-only
		STATUS	mandatory
		DESCRIPTION
			"The number of ICMP Timestamp (request) messages
			sent."
		::= { icmp 23 }

	icmpOutTimestampReps OBJECT-TYPE
		SYNTAX	Counter
		ACCESS	read-only
		STATUS	mandatory
		DESCRIPTION
			"The number of ICMP Timestamp Reply messages
			sent."
		::= { icmp 24 }

	icmpOutAddrMasks OBJECT-TYPE
		SYNTAX	Counter
		ACCESS	read-only
		STATUS	mandatory
		DESCRIPTION
			"The number of ICMP Address Mask Request messages
			sent."
		::= { icmp 25 }

	icmpOutAddrMaskReps OBJECT-TYPE
		SYNTAX	Counter
		ACCESS	read-only
		STATUS	mandatory
		DESCRIPTION
			"The number of ICMP Address Mask Reply messages
			sent."
		::= { icmp 26 }

	cIcmp			OBJECT IDENTIFIER ::= { cStdExtensions 5 }

	-- datability Extensions to the icmp group. Primarily, these are
	-- more detailed error indications and detailed breakdowns
	-- for the individual message codes for destination unreachable,
	-- time exceeded, and redirect messages.

	-- Breakdowns of the individual codes for the Redirect Message.
	-- The total of these objects should match the value of
	-- icmpInRedirects. Any discrepancy indicates that some redirects
	-- came in with unknown codes.
	cIcmpInRedirectNet		OBJECT-TYPE
		SYNTAX	Counter
		ACCESS	read-only
		STATUS	mandatory
		DESCRIPTION
			"Number of ICMP Destination Unreachable, Network
			Unreachable messages received."
		::= { cIcmp 1 }

	cIcmpInRedirectHost		OBJECT-TYPE
		SYNTAX	Counter
		ACCESS	read-only
		STATUS	mandatory
		DESCRIPTION
			"Number of ICMP Destination Unreachable, Host
			Unreachable messages received."
		::= { cIcmp 2 }

	cIcmpInRedirectNetTos	OBJECT-TYPE
		SYNTAX	Counter
		ACCESS	read-only
		STATUS	mandatory
		DESCRIPTION
			"Number of ICMP Destination Unreachable, Network/TOS
			Unreachable messages received."
		::= { cIcmp 3 }

	cIcmpInRedirectHostTos	OBJECT-TYPE
		SYNTAX	Counter
		ACCESS	read-only
		STATUS	mandatory
		DESCRIPTION
			"Number of ICMP Destination Unreachable, Host/TOS
			Unreachable messages received."
		::= { cIcmp 4 }

	-- Breakdowns of the individual codes for the Time Exceeded Message.
	-- The total of these objects should match the value of
	-- icmpInTimeExcds. Any discrepancy indicates that some redirects
	-- came in with unknown codes.
	cIcmpInTimeExcTTL		OBJECT-TYPE
		SYNTAX	Counter
		ACCESS	read-only
		STATUS	mandatory
		DESCRIPTION
			"Number of ICMP Time Exceeded, TTL Exceeded in 
			Transit messages received."
		::= { cIcmp 5 }

	cIcmpInTimeExcReAsm		OBJECT-TYPE
		SYNTAX	Counter
		ACCESS	read-only
		STATUS	mandatory
		DESCRIPTION
			"Number of ICMP Time Exceeded, Reassembly Time
			Exceeded messages received."
		::= { cIcmp 6 }

	-- Breakdowns of the individual codes for the Destination UnReachable Message.
	-- The total of these objects should match the value of
	-- icmpInDestUnreachs. Any discrepancy indicates that some redirects
	-- came in with unknown codes.
	cIcmpInDestUnNet		OBJECT-TYPE
		SYNTAX	Counter
		ACCESS	read-only
		STATUS	mandatory
		DESCRIPTION
			"Number of ICMP Network Destination Unreachable
			messages received."
		::= { cIcmp 7 }

	cIcmpInDestUnHost		OBJECT-TYPE
		SYNTAX	Counter
		ACCESS	read-only
		STATUS	mandatory
		DESCRIPTION
			"Number of ICMP Host Destination Unreachable
			messages received."
		::= { cIcmp 8 }

	cIcmpInDestUnProtocol	OBJECT-TYPE
		SYNTAX	Counter
		ACCESS	read-only
		STATUS	mandatory
		DESCRIPTION
			"Number of ICMP Protocol Destination Unreachable
			messages received."
		::= { cIcmp 9 }

	cIcmpInDestUnPort		OBJECT-TYPE
		SYNTAX	Counter
		ACCESS	read-only
		STATUS	mandatory
		DESCRIPTION
			"Number of ICMP Port Destination Unreachable
			messages received."
		::= { cIcmp 10 }

	cIcmpInDestUnFragNeeded	OBJECT-TYPE
		SYNTAX	Counter
		ACCESS	read-only
		STATUS	mandatory
		DESCRIPTION
			"Number of ICMP Fragmentation Needed and DF Set
			Destination Unreachable messages received."
		::= { cIcmp 11 }

	cIcmpInDestUnSourceRoute	OBJECT-TYPE
		SYNTAX	Counter
		ACCESS	read-only
		STATUS	mandatory
		DESCRIPTION
			"Number of ICMP Source Route Failed
			Destination Unreachable messages received."
		::= { cIcmp 12 }

	-- Breakdowns of the individual codes for the Redirect Message.
	-- The total of these objects should match the value of
	-- icmpOutRedirects. Any discrepancy indicates that some redirects
	-- were sent with unknown codes (which really should not happen sinc
	-- our code is perfect :-).

	cIcmpOutRedirectNet		OBJECT-TYPE
		SYNTAX	Counter
		ACCESS	read-only
		STATUS	mandatory
		DESCRIPTION
			"Number of ICMP Destination Unreachable, Network
			Unreachable messages sent."
		::= { cIcmp 13 }

	cIcmpOutRedirectHost		OBJECT-TYPE
		SYNTAX	Counter
		ACCESS	read-only
		STATUS	mandatory
		DESCRIPTION
			"Number of ICMP Destination Unreachable, Host
			Unreachable messages sent."
		::= { cIcmp 14 }

	cIcmpOutRedirectNetTos	OBJECT-TYPE
		SYNTAX	Counter
		ACCESS	read-only
		STATUS	mandatory
		DESCRIPTION
			"Number of ICMP Destination Unreachable, Network/TOS
			Unreachable messages sent."
		::= { cIcmp 15 }

	cIcmpOutRedirectHostTos	OBJECT-TYPE
		SYNTAX	Counter
		ACCESS	read-only
		STATUS	mandatory
		DESCRIPTION
			"Number of ICMP Destination Unreachable, Host/TOS
			Unreachable messages sent."
		::= { cIcmp 16 }

	-- Breakdowns of the individual codes for the Time Exceeded Message.
	-- The total of these objects should match the value of
	-- icmpOutTimeExcds. Any discrepancy indicates that some redirects
	-- were sent with unknown codes (which really should not happen sinc
	-- our code is perfect :-).

	cIcmpOutTimeExcTTL		OBJECT-TYPE
		SYNTAX	Counter
		ACCESS	read-only
		STATUS	mandatory
		DESCRIPTION
			"Number of ICMP Time Exceeded, TTL Exceeded in 
			Transit messages sent."
		::= { cIcmp 17 }

	cIcmpOutTimeExcReAsm		OBJECT-TYPE
		SYNTAX	Counter
		ACCESS	read-only
		STATUS	mandatory
		DESCRIPTION
			"Number of ICMP Time Exceeded, Reassembly Time
			Exceeded messages sent."
		::= { cIcmp 18 }

	-- Breakdowns of the individual codes for the Destination UnReachable Message.
	-- The total of these objects should match the value of
	-- icmpOutDestUnreachs. Any discrepancy indicates that some redirects
	-- were sent with unknown codes (which really should not happen sinc
	-- our code is perfect :-).
	cIcmpOutDestUnNet		OBJECT-TYPE
		SYNTAX	Counter
		ACCESS	read-only
		STATUS	mandatory
		DESCRIPTION
			"Number of ICMP Network Destination Unreachable
			messages sent."
		::= { cIcmp 19 }

	cIcmpOutDestUnHost		OBJECT-TYPE
		SYNTAX	Counter
		ACCESS	read-only
		STATUS	mandatory
		DESCRIPTION
			"Number of ICMP Host Destination Unreachable
			messages sent."
		::= { cIcmp 20 }

	cIcmpOutDestUnProtocol	OBJECT-TYPE
		SYNTAX	Counter
		ACCESS	read-only
		STATUS	mandatory
		DESCRIPTION
			"Number of ICMP Protocol Destination Unreachable
			messages sent."
		::= { cIcmp 21 }

	cIcmpOutDestUnPort		OBJECT-TYPE
		SYNTAX	Counter
		ACCESS	read-only
		STATUS	mandatory
		DESCRIPTION
			"Number of ICMP Port Destination Unreachable
			messages sent."
		::= { cIcmp 22 }

	cIcmpOutDestUnFragNeeded	OBJECT-TYPE
		SYNTAX	Counter
		ACCESS	read-only
		STATUS	mandatory
		DESCRIPTION
			"Number of ICMP Fragmentation Needed and DF Set
			Destination Unreachable messages sent."
		::= { cIcmp 23 }

	cIcmpOutDestUnSourceRoute	OBJECT-TYPE
		SYNTAX	Counter
		ACCESS	read-only
		STATUS	mandatory
		DESCRIPTION
			"Number of ICMP Source Route Failed
			Destination Unreachable messages sent."
		::= { cIcmp 24 }

	--
	-- Extended breakdown of the ICMP errors that
	-- can be detected. These counts are all components
	-- of icmpInErrors. If the sum of these counts does
	-- not equal icmpInErrors, then there were other, 
	-- unspecified, receive errors.
	--
	cIcmpInLengthErrors	OBJECT-TYPE
		SYNTAX	Counter
		ACCESS	read-only
		STATUS	mandatory
		DESCRIPTION
			"Number of alleged ICMP packets that were not
			long enough."
		::= { cIcmp 25 }

	cIcmpInChecksumErrors	OBJECT-TYPE
		SYNTAX	Counter
		ACCESS	read-only
		STATUS	mandatory
		DESCRIPTION
			"Number of alleged ICMP packets that had
			a bad checksum."
		::= { cIcmp 26 }

	cIcmpInUnkTypes	OBJECT-TYPE
		SYNTAX	Counter
		ACCESS	read-only
		STATUS	mandatory
		DESCRIPTION
			"Number of Received ICMP packets with an
			unknown type field value."
		::= { cIcmp 27 }

	--
	-- Additional destination unreachable types defined in host requirements.
	--
	cIcmpInDestUnNetUnknown	OBJECT-TYPE
		SYNTAX	Counter
		ACCESS	read-only
		STATUS	mandatory
		DESCRIPTION
			"Number of ICMP Destination Network Unknown
			Destination Unreachable messages received."
		::= { cIcmp  28 }

	cIcmpInDestUnHostUnknown	OBJECT-TYPE
		SYNTAX	Counter
		ACCESS	read-only
		STATUS	mandatory
		DESCRIPTION
			"Number of ICMP Destination Host Unknown
			Destination Unreachable messages received."
		::= { cIcmp  29 }

	cIcmpInDestUnSrcIsolated	OBJECT-TYPE
		SYNTAX	Counter
		ACCESS	read-only
		STATUS	mandatory
		DESCRIPTION
			"Number of ICMP Source Isolated
			Destination Unreachable messages received."
		::= { cIcmp  30 }

	cIcmpInDestUnHostProhib	OBJECT-TYPE
		SYNTAX	Counter
		ACCESS	read-only
		STATUS	mandatory
		DESCRIPTION
			"Number of ICMP Communication with Host
			Administratively Prohibited Destination
			Unreachable messages received."
		::= { cIcmp  31 }

	cIcmpInDestUnNetProhib	OBJECT-TYPE
		SYNTAX	Counter
		ACCESS	read-only
		STATUS	mandatory
		DESCRIPTION
			"Number of ICMP Communication with Net
			Administratively Prohibited Destination
			Unreachable messages received."
		::= { cIcmp  32 }

	cIcmpInDestUnNetTos	OBJECT-TYPE
		SYNTAX	Counter
		ACCESS	read-only
		STATUS	mandatory
		DESCRIPTION
			"Number of ICMP Network Unreachable with
			TOS messages received."
		::= { cIcmp  33 } 

	cIcmpInDestUnHostTos	OBJECT-TYPE
		SYNTAX	Counter
		ACCESS	read-only
		STATUS	mandatory
		DESCRIPTION
			"Number of ICMP Host Unreachable with
			TOS messages received."
		::= { cIcmp  34 }

	cIcmpOutDestUnNetUnknown	OBJECT-TYPE
		SYNTAX	Counter
		ACCESS	read-only
		STATUS	mandatory
		DESCRIPTION
			"Number of ICMP Destination Network Unknown
			Destination Unreachable messages sent."
		::= { cIcmp 35 }

	cIcmpOutDestUnHostUnknown	OBJECT-TYPE
		SYNTAX	Counter
		ACCESS	read-only
		STATUS	mandatory
		DESCRIPTION
			"Number of ICMP Destination Host Unknown
			Destination Unreachable messages sent."
		::= { cIcmp 36 }

	cIcmpOutDestUnSrcIsolated	OBJECT-TYPE
		SYNTAX	Counter
		ACCESS	read-only
		STATUS	mandatory
		DESCRIPTION
			"Number of ICMP Source Isolated
			Destination Unreachable messages sent."
		::= { cIcmp 37 }

	cIcmpOutDestUnHostProhib	OBJECT-TYPE
		SYNTAX	Counter
		ACCESS	read-only
		STATUS	mandatory
		DESCRIPTION
			"Number of ICMP Communication with Host
			Administratively Prohibited Destination
			Unreachable messages sent."
		::= { cIcmp 38 }

	cIcmpOutDestUnNetProhib	OBJECT-TYPE
		SYNTAX	Counter
		ACCESS	read-only
		STATUS	mandatory
		DESCRIPTION
			"Number of ICMP Communication with Net
			Administratively Prohibited Destination
			Unreachable messages sent."
		::= { cIcmp 39 }

	cIcmpOutDestUnNetTos	OBJECT-TYPE
		SYNTAX	Counter
		ACCESS	read-only
		STATUS	mandatory
		DESCRIPTION
			"Number of ICMP Network Unreachable with
			TOS messages sent."
		::= { cIcmp 40 }

	cIcmpOutDestUnHostTos	OBJECT-TYPE
		SYNTAX	Counter
		ACCESS	read-only
		STATUS	mandatory
		DESCRIPTION
			"Number of ICMP Host Unreachable with
			TOS messages sent."
		::= { cIcmp 41 }

	cIcmpInParmProbMissingOpt	OBJECT-TYPE
		SYNTAX	Counter
		ACCESS	read-only
		STATUS	mandatory
		DESCRIPTION
			"Number of received Parameter Problem messages
			with the Missing Option code."
		::= { cIcmp 42 }

	cIcmpOutParmProbMissingOpt	OBJECT-TYPE
		SYNTAX	Counter
		ACCESS	read-only
		STATUS	mandatory
		DESCRIPTION
			"Number of sent Parameter Problem messages
			with the Missing Option code."
		::= { cIcmp 43 }



-- the TCP group

-- Implementation of the TCP group is mandatory for all
-- systems that implement the TCP.

-- Note that instances of object types that represent
-- information about a particular TCP connection are
-- transient; they persist only as long as the connection
-- in question.

--        tcpRtoAlgorithm OBJECT-TYPE
--            SYNTAX	INTEGER {
--                        other(1),     none of the following

--                        constant(2),  a constant rto
--                        rsre(3),      MIL-STD-1778, Appendix B
--                        vanj(4)       Van Jacobson's algorithm [10]
--                    }
--            ACCESS	read-only
--            STATUS	mandatory
--            DESCRIPTION
--                    "The algorithm used to determine the timeout value
--                    used for retransmitting unacknowledged octets."
--            ::= { tcp 1 }

--        tcpRtoMin OBJECT-TYPE
--            SYNTAX	INTEGER
--            ACCESS	read-only
--            STATUS	mandatory
--            DESCRIPTION
--                    "The minimum value permitted by a TCP
--                    implementation for the retransmission timeout,
--                    measured in milliseconds.  More refined semantics
--                    for objects of this type depend upon the algorithm
--                    used to determine the retransmission timeout.  In
--                    particular, when the timeout algorithm is rsre(3),
--                    an object of this type has the semantics of the
--                    LBOUND quantity described in RFC 793."
--            ::= { tcp 2 }


--        tcpRtoMax OBJECT-TYPE
--            SYNTAX	INTEGER
--            ACCESS	read-only
--            STATUS	mandatory
--            DESCRIPTION
--                    "The maximum value permitted by a TCP
--                    implementation for the retransmission timeout,
--                    measured in milliseconds.  More refined semantics
--                    for objects of this type depend upon the algorithm
--                    used to determine the retransmission timeout.  In
--                    particular, when the timeout algorithm is rsre(3),
--                    an object of this type has the semantics of the
--                    UBOUND quantity described in RFC 793."
--            ::= { tcp 3 }

--        tcpMaxConn OBJECT-TYPE
--            SYNTAX	INTEGER
--            ACCESS	read-only
--            STATUS	mandatory
--            DESCRIPTION
--                    "The limit on the total number of TCP connections
--                    the entity can support.  In entities where the
--                    maximum number of connections is dynamic, this
--                    object should contain the value -1."
--            ::= { tcp 4 }

--        tcpActiveOpens OBJECT-TYPE
--            SYNTAX	Counter
--            ACCESS	read-only
--            STATUS	mandatory
--            DESCRIPTION
--                    "The number of times TCP connections have made a
--                    direct transition to the SYN-SENT state from the
--                    CLOSED state."
--            ::= { tcp 5 }

--        tcpPassiveOpens OBJECT-TYPE
--            SYNTAX	Counter
--            ACCESS	read-only
--            STATUS	mandatory
--            DESCRIPTION
--                    "The number of times TCP connections have made a
--                    direct transition to the SYN-RCVD state from the
--                    LISTEN state."
--            ::= { tcp 6 }

--        tcpAttemptFails OBJECT-TYPE
--            SYNTAX	Counter
--            ACCESS	read-only
--            STATUS	mandatory
--            DESCRIPTION
--                    "The number of times TCP connections have made a
--                    direct transition to the CLOSED state from either
--                    the SYN-SENT state or the SYN-RCVD state, plus the
--                    number of times TCP connections have made a direct
--                    transition to the LISTEN state from the SYN-RCVD
--                    state."
--            ::= { tcp 7 }

--        tcpEstabResets OBJECT-TYPE
--            SYNTAX	Counter
--            ACCESS	read-only
--            STATUS	mandatory
--            DESCRIPTION
--                    "The number of times TCP connections have made a
--                    direct transition to the CLOSED state from either
--                    the ESTABLISHED state or the CLOSE-WAIT state."
--            ::= { tcp 8 }

--        tcpCurrEstab OBJECT-TYPE
--            SYNTAX	Gauge
--            ACCESS	read-only
--            STATUS	mandatory
--            DESCRIPTION
--                    "The number of TCP connections for which the
--                    current state is either ESTABLISHED or CLOSE-
--                    WAIT."
--            ::= { tcp 9 }

--        tcpInSegs OBJECT-TYPE
--            SYNTAX	Counter
--            ACCESS	read-only
--            STATUS	mandatory
--            DESCRIPTION
--                    "The total number of segments received, including
--                    those received in error.  This count includes
--                    segments received on currently established
--                    connections."
--            ::= { tcp 10 }

--        tcpOutSegs OBJECT-TYPE
--            SYNTAX	Counter
--            ACCESS	read-only
--            STATUS	mandatory
--            DESCRIPTION
--                    "The total number of segments sent, including
--                    those on current connections but excluding those
--                    containing only retransmitted octets."
--            ::= { tcp 11 }

--        tcpRetransSegs OBJECT-TYPE
--            SYNTAX	Counter
--            ACCESS	read-only
--            STATUS	mandatory
--            DESCRIPTION
--                    "The total number of segments retransmitted - that
--                    is, the number of TCP segments transmitted
--                    containing one or more previously transmitted
--                    octets."
--            ::= { tcp 12 }

-- the TCP Connection table

-- The TCP connection table contains information about this
-- entity's existing TCP connections.

--        tcpConnTable OBJECT-TYPE
--            SYNTAX	SEQUENCE OF TcpConnEntry
--            ACCESS	not-accessible
--            STATUS	mandatory
--            DESCRIPTION
--                    "A table containing TCP connection-specific
--                    information."
--            ::= { tcp 13 }

--        tcpConnEntry OBJECT-TYPE
--            SYNTAX	TcpConnEntry
--            ACCESS	not-accessible
--            STATUS	mandatory
--            DESCRIPTION
--                    "Information about a particular current TCP
--                    connection.  An object of this type is transient,
--                    in that it ceases to exist when (or soon after)
--                    the connection makes the transition to the CLOSED
--                    state."
--            INDEX   { tcpConnLocalAddress,
--                      tcpConnLocalPort,
--                      tcpConnRemAddress,
--                      tcpConnRemPort }
--            ::= { tcpConnTable 1 }

--        TcpConnEntry ::=
--            SEQUENCE {
--                tcpConnState
--                    INTEGER,
--                tcpConnLocalAddress
--                    IpAddress,
--                tcpConnLocalPort
--                    INTEGER (0..65535),
--                tcpConnRemAddress
--                    IpAddress,
--                tcpConnRemPort
--                    INTEGER (0..65535)
--            }

--        tcpConnState OBJECT-TYPE
--            SYNTAX	INTEGER {
--                        closed(1),
--                        listen(2),
--                        synSent(3),
--                        synReceived(4),
--                        established(5),
--                        finWait1(6),
--                        finWait2(7),
--                        closeWait(8),
--                        lastAck(9),
--                        closing(10),
--                        timeWait(11),
--                        deleteTCB(12)
--                    }
--            ACCESS	read-write
--            STATUS	mandatory
--            DESCRIPTION
--                    "The state of this TCP connection.

--                    The only value which may be set by a management
--                    station is deleteTCB(12).  Accordingly, it is
--                    appropriate for an agent to return a `badValue'
--                    response if a management station attempts to set
--                    this object to any other value.

--                    If a management station sets this object to the
--                    value deleteTCB(12), then this has the effect of
--                    deleting the TCB (as defined in RFC 793) of the
--                    corresponding connection on the managed node,
--                    resulting in immediate termination of the
--                    connection.

--                    As an implementation-specific option, a RST
--                    segment may be sent from the managed node to the
--                    other TCP endpoint (note however that RST segments
--                    are not sent reliably)."
--            ::= { tcpConnEntry 1 }

--        tcpConnLocalAddress OBJECT-TYPE
--            SYNTAX	IpAddress
--            ACCESS	read-only
--            STATUS	mandatory
--            DESCRIPTION
--                    "The local IP address for this TCP connection.  In
--                    the case of a connection in the listen state which
--                    is willing to accept connections for any IP
--                    interface associated with the node, the value
--                    0.0.0.0 is used."
--            ::= { tcpConnEntry 2 }

--        tcpConnLocalPort OBJECT-TYPE
--            SYNTAX	INTEGER (0..65535)
--            ACCESS	read-only
--            STATUS	mandatory
--            DESCRIPTION
--                    "The local port number for this TCP connection."
--            ::= { tcpConnEntry 3 }

--        tcpConnRemAddress OBJECT-TYPE
--            SYNTAX	IpAddress
--            ACCESS	read-only
--            STATUS	mandatory
--            DESCRIPTION
--                    "The remote IP address for this TCP connection."
--            ::= { tcpConnEntry 4 }

--        tcpConnRemPort OBJECT-TYPE
--            SYNTAX	INTEGER (0..65535)
--            ACCESS	read-only
--            STATUS	mandatory
--            DESCRIPTION
--                    "The remote port number for this TCP connection."
--            ::= { tcpConnEntry 5 }

-- additional TCP objects

--        tcpInErrs OBJECT-TYPE
--            SYNTAX	Counter
--            ACCESS	read-only
--            STATUS	mandatory
--            DESCRIPTION
--                    "The total number of segments received in error
--                    (e.g., bad TCP checksums)."
--            ::= { tcp 14 }

--        tcpOutRsts OBJECT-TYPE
--            SYNTAX	Counter
--            ACCESS	read-only
--            STATUS	mandatory
--            DESCRIPTION
--                    "The number of TCP segments sent containing the
--                    RST flag."
--            ::= { tcp 15 }

-- the UDP group

-- Implementation of the UDP group is mandatory for all
-- systems which implement the UDP.

	udpInDatagrams OBJECT-TYPE
		SYNTAX	Counter
		ACCESS	read-only
		STATUS	mandatory
		DESCRIPTION
			"The total number of UDP datagrams delivered to
			UDP users."
		::= { udp 1 }

	udpNoPorts OBJECT-TYPE
		SYNTAX	Counter
		ACCESS	read-only
		STATUS	mandatory
		DESCRIPTION
			"The total number of received UDP datagrams for
			which there was no application at the destination
			port."
		::= { udp 2 }

	udpInErrors OBJECT-TYPE
		SYNTAX	Counter
		ACCESS	read-only
		STATUS	mandatory
		DESCRIPTION
			"The number of received UDP datagrams that could
			not be delivered for reasons other than the lack
			of an application at the destination port."
		::= { udp 3 }

	udpOutDatagrams OBJECT-TYPE
		SYNTAX	Counter
		ACCESS	read-only
		STATUS	mandatory
		DESCRIPTION
			"The total number of UDP datagrams sent from this
			entity."
		::= { udp 4 }


-- the UDP Listener table

-- The UDP listener table contains information about this
-- entity's UDP end-points on which a local application is
-- currently accepting datagrams.

	udpTable OBJECT-TYPE
		SYNTAX	SEQUENCE OF UdpEntry
		ACCESS	not-accessible
		STATUS	mandatory
		DESCRIPTION
			"A table containing UDP listener information."
		::= { udp 5 }

	udpEntry OBJECT-TYPE
		SYNTAX	UdpEntry
		ACCESS	not-accessible
		STATUS	mandatory
		DESCRIPTION
			"Information about a particular current UDP
			listener."
		INDEX	{ udpLocalAddress, udpLocalPort }
		::= { udpTable 1 }

	UdpEntry ::= SEQUENCE {
		udpLocalAddress
			IpAddress,
		udpLocalPort
			INTEGER (0..65535)
	}

	udpLocalAddress OBJECT-TYPE
		SYNTAX	IpAddress
		ACCESS	read-only
		STATUS	mandatory
		DESCRIPTION
			"The local IP address for this UDP listener.  In
			the case of a UDP listener which is willing to
			accept datagrams for any IP interface associated
			with the node, the value 0.0.0.0 is used."
		::= { udpEntry 1 }

	udpLocalPort OBJECT-TYPE
		SYNTAX	INTEGER (0..65535)
		ACCESS	read-only
		STATUS	mandatory
		DESCRIPTION
			"The local port number for this UDP listener."
		::= { udpEntry 2 }

	--
	-- Here are a few exteneded UDP statistics for the UDP
	-- These are in datability proprietary space.
	--

	cUdpHdrDrops	OBJECT-TYPE
		SYNTAX	Counter
		ACCESS	read-only
		STATUS	mandatory
		DESCRIPTION
			"Nr of packets dropped because of internal 
			consistancy problems. This counter is a component
			of the udpInErrors Count."
		::= { cUdp 1 }

	cUdpBadCheckSum	OBJECT-TYPE
		SYNTAX	Counter
		ACCESS	read-only
		STATUS	mandatory
		DESCRIPTION
			"Nr of packets dropped because of an incorrect
			checksum. This counter is a component
			of the udpInErrors Count."
		::= { cUdp 2 }

	cUdpBadLength	OBJECT-TYPE
		SYNTAX	Counter
		ACCESS	read-only
		STATUS	mandatory
		DESCRIPTION
			"Nr of packets dropped because of an incorrect
			length. This counter is a component
			of the udpInErrors Count."
		::= { cUdp 3 }

	cUdpOtherErrors	OBJECT-TYPE
		SYNTAX	Counter
		ACCESS	read-only
		STATUS	mandatory
		DESCRIPTION
			"Nr of packets dropped because of some error other
			than one of the above. This counter is a component
			of the udpInErrors Count.
			
			The most likely cause of these errors is a problem
			in the internal IPC mechanism. Probably because some
			process that was supposed to be receiving packets
			is not."
		::= { cUdp 4 }

	cUdpNoChecksum	OBJECT-TYPE
		SYNTAX	Counter
		ACCESS	read-only
		STATUS	mandatory
		DESCRIPTION
			"Nr of packets received with a checksum of 0. This
			is not an error condition but indicates that there
			are mentally retarded hosts on the network."
		::= { cUdp 5 }

-- the Transmission group

-- Based on the transmission media underlying each interface
-- on a system, the corresponding portion of the Transmission
-- group is mandatory for that system.

-- When Internet-standard definitions for managing
-- transmission media are defined, the transmission group is
-- used to provide a prefix for the names of those objects.

-- Typically, such definitions reside in the experimental
-- portion of the MIB until they are "proven", then as a
-- part of the Internet standardization process, the
-- definitions are accordingly elevated and a new object
-- identifier, under the transmission group is defined. By
-- convention, the name assigned is:
--
--     type OBJECT IDENTIFIER    ::= { transmission number }
--
-- where "type" is the symbolic value used for the media in
-- the ifType column of the ifTable object, and "number" is
-- the actual integer value corresponding to the symbol.

-- ---------------------------------
-- --------------------------------

	snmpInPkts OBJECT-TYPE
		SYNTAX	Counter
		ACCESS	read-only
		STATUS	mandatory
		DESCRIPTION
			"The total number of Messages delivered to the
			SNMP entity from the transport service."
		::= { snmp 1 }

	snmpOutPkts OBJECT-TYPE
		SYNTAX	Counter
		ACCESS	read-only
		STATUS	mandatory
		DESCRIPTION
			"The total number of SNMP Messages which were
			passed from the SNMP protocol entity to the
			transport service."
		::= { snmp 2 }

	snmpInBadVersions OBJECT-TYPE
		SYNTAX	Counter
		ACCESS	read-only
		STATUS	mandatory
		DESCRIPTION
			"The total number of SNMP Messages which were
			delivered to the SNMP protocol entity and were for
			an unsupported SNMP version."
		::= { snmp 3 }

	snmpInBadCommunityNames OBJECT-TYPE
		SYNTAX	Counter
		ACCESS	read-only
		STATUS	mandatory
		DESCRIPTION
			"The total number of SNMP Messages delivered to
			the SNMP protocol entity which used a SNMP
			community name not known to said entity."
		::= { snmp 4 }

	snmpInBadCommunityUses OBJECT-TYPE
		SYNTAX	Counter
		ACCESS	read-only
		STATUS	mandatory
		DESCRIPTION
			"The total number of SNMP Messages delivered to
			the SNMP protocol entity which represented an SNMP
			operation which was not allowed by the SNMP
			community named in the Message."
		::= { snmp 5 }

	snmpInASNParseErrs OBJECT-TYPE
		SYNTAX	Counter
		ACCESS	read-only
		STATUS	mandatory
		DESCRIPTION
			"The total number of ASN.1 or BER errors
			encountered by the SNMP protocol entity when
			decoding received SNMP Messages."
		::= { snmp 6 }

	-- { snmp 7 } is not used

	snmpInTooBigs OBJECT-TYPE
		SYNTAX	Counter
		ACCESS	read-only
		STATUS	mandatory
		DESCRIPTION
			"The total number of SNMP PDUs which were
			delivered to the SNMP protocol entity and for
			which the value of the error-status field is
			`tooBig'."
		::= { snmp 8 }

	snmpInNoSuchNames OBJECT-TYPE
		SYNTAX	Counter
		ACCESS	read-only
		STATUS	mandatory
		DESCRIPTION
			"The total number of SNMP PDUs which were
			delivered to the SNMP protocol entity and for
			which the value of the error-status field is
			`noSuchName'."
		::= { snmp 9 }

	snmpInBadValues OBJECT-TYPE
		SYNTAX	Counter
		ACCESS	read-only
		STATUS	mandatory
		DESCRIPTION
			"The total number of SNMP PDUs which were
			delivered to the SNMP protocol entity and for
			which the value of the error-status field is
			`badValue'."
		::= { snmp 10 }

	snmpInReadOnlys OBJECT-TYPE
		SYNTAX	Counter
		ACCESS	read-only
		STATUS	mandatory
		DESCRIPTION
			"The total number valid SNMP PDUs which were
			delivered to the SNMP protocol entity and for
			which the value of the error-status field is
			`readOnly'.  It should be noted that it is a
			protocol error to generate an SNMP PDU which
			contains the value `readOnly' in the error-status
			field, as such this object is provided as a means
			of detecting incorrect implementations of the
			SNMP."
		::= { snmp 11 }

	snmpInGenErrs OBJECT-TYPE
		SYNTAX	Counter
		ACCESS	read-only
		STATUS	mandatory
		DESCRIPTION
			"The total number of SNMP PDUs which were
			delivered to the SNMP protocol entity and for
			which the value of the error-status field is
			`genErr'."
		::= { snmp 12 }

	snmpInTotalReqVars OBJECT-TYPE
		SYNTAX	Counter
		ACCESS	read-only
		STATUS	mandatory
		DESCRIPTION
			"The total number of MIB objects which have been
			retrieved successfully by the SNMP protocol entity
			as the result of receiving valid SNMP Get-Request
			and Get-Next PDUs."
		::= { snmp 13 }

	snmpInTotalSetVars OBJECT-TYPE
		SYNTAX	Counter
		ACCESS	read-only
		STATUS	mandatory
		DESCRIPTION
			"The total number of MIB objects which have been
			altered successfully by the SNMP protocol entity
			as the result of receiving valid SNMP Set-Request
			PDUs."
		::= { snmp 14 }

	snmpInGetRequests OBJECT-TYPE
		SYNTAX	Counter
		ACCESS	read-only
		STATUS	mandatory
		DESCRIPTION
			"The total number of SNMP Get-Request PDUs which
			have been accepted and processed by the SNMP
			protocol entity."
		::= { snmp 15 }

	snmpInGetNexts OBJECT-TYPE
		SYNTAX	Counter
		ACCESS	read-only
		STATUS	mandatory
		DESCRIPTION
			"The total number of SNMP Get-Next PDUs which have
			been accepted and processed by the SNMP protocol
			entity."
		::= { snmp 16 }

	snmpInSetRequests OBJECT-TYPE
		SYNTAX	Counter
		ACCESS	read-only
		STATUS	mandatory
		DESCRIPTION
			"The total number of SNMP Set-Request PDUs which
			have been accepted and processed by the SNMP
			protocol entity."
		::= { snmp 17 }

	snmpInGetResponses OBJECT-TYPE
		SYNTAX	Counter
		ACCESS	read-only
		STATUS	mandatory
		DESCRIPTION
			"The total number of SNMP Get-Response PDUs which
			have been accepted and processed by the SNMP
			protocol entity."
		::= { snmp 18 }

	snmpInTraps OBJECT-TYPE
		SYNTAX	Counter
		ACCESS	read-only
		STATUS	mandatory
		DESCRIPTION
			"The total number of SNMP Trap PDUs which have
			been accepted and processed by the SNMP protocol
			entity."
		::= { snmp 19 }

	snmpOutTooBigs OBJECT-TYPE
		SYNTAX	Counter
		ACCESS	read-only
		STATUS	mandatory
		DESCRIPTION
			"The total number of SNMP PDUs which were
			generated by the SNMP protocol entity and for
			which the value of the error-status field is
			`tooBig.'"
		::= { snmp 20 }

	snmpOutNoSuchNames OBJECT-TYPE
		SYNTAX	Counter
		ACCESS	read-only
		STATUS	mandatory
		DESCRIPTION
			"The total number of SNMP PDUs which were
			generated by the SNMP protocol entity and for
			which the value of the error-status is
			`noSuchName'."
		::= { snmp 21 }

	snmpOutBadValues OBJECT-TYPE
		SYNTAX	Counter
		ACCESS	read-only
		STATUS	mandatory
		DESCRIPTION
			"The total number of SNMP PDUs which were
			generated by the SNMP protocol entity and for
			which the value of the error-status field is
			`badValue'."
		::= { snmp 22 }

		-- { snmp 23 } is not used

	snmpOutGenErrs OBJECT-TYPE
		SYNTAX	Counter
		ACCESS	read-only
		STATUS	mandatory
		DESCRIPTION
			"The total number of SNMP PDUs which were
			generated by the SNMP protocol entity and for
			which the value of the error-status field is
			`genErr'."
		::= { snmp 24 }

	snmpOutGetRequests OBJECT-TYPE
		SYNTAX	Counter
		ACCESS	read-only
		STATUS	mandatory
		DESCRIPTION
			"The total number of SNMP Get-Request PDUs which
			have been generated by the SNMP protocol entity."
		::= { snmp 25 }
	
	snmpOutGetNexts OBJECT-TYPE
		SYNTAX	Counter
		ACCESS	read-only
		STATUS	mandatory
		DESCRIPTION
			"The total number of SNMP Get-Next PDUs which have
			been generated by the SNMP protocol entity."
		::= { snmp 26 }

	snmpOutSetRequests OBJECT-TYPE
		SYNTAX	Counter
		ACCESS	read-only
		STATUS	mandatory
		DESCRIPTION
			"The total number of SNMP Set-Request PDUs which
			have been generated by the SNMP protocol entity."
		::= { snmp 27 }

	snmpOutGetResponses OBJECT-TYPE
		SYNTAX	Counter
		ACCESS	read-only
		STATUS	mandatory
		DESCRIPTION
			"The total number of SNMP Get-Response PDUs which
			have been generated by the SNMP protocol entity."
		::= { snmp 28 }

	snmpOutTraps OBJECT-TYPE
		SYNTAX	Counter
		ACCESS	read-only
		STATUS	mandatory
		DESCRIPTION
			"The total number of SNMP Trap PDUs which have
			been generated by the SNMP protocol entity."
		::= { snmp 29 }

	snmpEnableAuthenTraps OBJECT-TYPE
		SYNTAX	INTEGER { enabled(1), disabled(2) }
		ACCESS	read-write
		STATUS	mandatory
		DESCRIPTION
			"Indicates whether the SNMP agent process is
			permitted to generate authentication-failure
			traps.  The value of this object overrides any
			configuration information; as such, it provides a
			means whereby all authentication-failure traps may
			be disabled.
	
			Note that it is strongly recommended that this
			object be stored in non-volatile memory so that it
			remains constant between re-initializations of the
			network management system."
		::= { snmp 30 }


-- *************************************************************
--
-- Here are the datability extensions to the MIB.
--
-- First, the Generic Interface Extensions MIB
--
-- *************************************************************


--   Generic Interface Extension Table
--
--  This group of objects is mandatory for all types of
--  subnetwork interface.

	ifExtnsTable  OBJECT-TYPE
		SYNTAX SEQUENCE OF IfExtnsEntry
		ACCESS not-accessible
		STATUS mandatory
		DESCRIPTION
			"A list of interfaces extension entries.
			The number of entries is given by the value
			of ifNumber, defined in [4,6]."
		::= { ifExtensions 1 }

	ifExtnsEntry  OBJECT-TYPE
		SYNTAX IfExtnsEntry
		ACCESS not-accessible
		STATUS mandatory
		DESCRIPTION
			"An extension to the interfaces entry,
			defined in [4,6], containing additional
			objects at the subnetwork layer and below
			for a particular interface."
		INDEX  { ifExtnsIfIndex }
		::= { ifExtnsTable 1 }

	IfExtnsEntry ::= SEQUENCE {
			ifExtnsIfIndex
				INTEGER,
			ifExtnsChipSet
				OBJECT IDENTIFIER,
			ifExtnsRevWare
				DisplayString,
			ifExtnsMulticastsTransmittedOks
				Counter,
			ifExtnsBroadcastsTransmittedOks
				Counter,
			ifExtnsMulticastsReceivedOks
				Counter,
			ifExtnsBroadcastsReceivedOks
				Counter,
			ifExtnsPromiscuous
				INTEGER
		}

	ifExtnsIfIndex  OBJECT-TYPE
		SYNTAX INTEGER
		ACCESS read-only
		STATUS mandatory
		DESCRIPTION
			"The value of this object identifies the
			interface for which this entry contains
			extended management information.  The value
			of this object for a particular interface
			has the same value as the ifIndex object,
			defined in [4,6], for the same interface."
		::= { ifExtnsEntry 1 }

	ifExtnsChipSet	OBJECT-TYPE
		SYNTAX	OBJECT IDENTIFIER
		ACCESS	read-only
		STATUS	mandatory
		DESCRIPTION
			"This object identifies the hardware chip
			set being used in the interface.  The
			assignment of OBJECT IDENTIFIERs to various
			types of hardware chip sets is defined
			elsewhere.  This document assigns only the
			value: unknownChipSet for use if the chip
			set in use is unknown.
				Note that unknownChipSet is a
			syntactically valid object identifier, and
			any conformant implementation of ASN.1 and
			the BER must be able to generate and
			recognize this value."
		::= { ifExtnsEntry 2 }

-- for unknown hardware chip set
--		unknownChipSet  OBJECT IDENTIFIER ::= { 0 0 }

	ifExtnsRevWare  OBJECT-TYPE
		SYNTAX DisplayString (SIZE (0..255))
		ACCESS read-only
		STATUS mandatory
		DESCRIPTION
			"An arbitrary octet string that describes
			the firmware version of this interface.
			It is intended that this should be human
			readable.  It must only contain ASCII
			printable characters.  Typically this
			will be the firmware version of the main
			interface software."
		::= { ifExtnsEntry 3 }

	ifExtnsMulticastsTransmittedOks OBJECT-TYPE
		SYNTAX Counter
		ACCESS read-only
		STATUS mandatory
		DESCRIPTION
			"The count of frames successfully
			transmitted to a subnetwork or link-layer
			multicast destination address other than a
			broadcast address.  For a MAC layer protocol,
			this includes both Group and Functional
			addresses."
		::= { ifExtnsEntry 4 }

	ifExtnsBroadcastsTransmittedOks OBJECT-TYPE
		SYNTAX Counter
		ACCESS read-only
		STATUS mandatory
		DESCRIPTION
			"The count of frames successfully
			transmitted to a subnetwork or link-layer
			broadcast addresses.  It does not include
			frames sent to a multicast address."
		::= { ifExtnsEntry 5 }

	ifExtnsMulticastsReceivedOks OBJECT-TYPE
		SYNTAX	Counter
		ACCESS	read-only
		STATUS	mandatory
		DESCRIPTION
			"The count of frames successfully received
			that are directed to an active subnetwork
			or link-layer multicast address (for a MAC
			layer protocol, this includes both Group and
			Functional addresses). This does not include
			frames directed to a broadcast address, nor
			frames received with errors."
		::= { ifExtnsEntry 6 }

	ifExtnsBroadcastsReceivedOks OBJECT-TYPE
		SYNTAX Counter
		ACCESS read-only
		STATUS mandatory
		DESCRIPTION
			"The count of frames successfully received
			that are directed to a subnetwork or
			link-layer broadcast address."
		::= { ifExtnsEntry 7 }

	ifExtnsPromiscuous  OBJECT-TYPE
		SYNTAX INTEGER {
						true(1),
						false(2)
					}
		ACCESS read-only	-- Note: agent implementors are
							-- encouraged to extend this
							-- access to read-write if that
							-- makes sense in their agent.
		STATUS mandatory
		DESCRIPTION
			"This object has a value of false(2) if
			this interface only accepts packets/frames
			that are addressed to this station. This
			object has a value of true(1) when the
			station accepts all packets/frames
			transmitted on the media.  The value
			true(1) is only legal on certain types of
			media.  If legal, setting this object to a
			value of true(1) may require the interface
			to be reset before becoming effective."
		::= { ifExtnsEntry 8 }

-- --------------------------------------------------------------
--
--    Generic Interface Test Table
--
-- This group of objects is optional, but if the table is
-- implemented, all objects in the table must be implemented.
-- Not implemented in the **** dxa 550 ****
-- 
-- --------------------------------------------------------------
--
--   Generic Receive Address Table
--
-- This group of objects is mandatory for all types of
-- interfaces which can receive packets/frames addressed to
-- more than one address.
--
-- --------------------------------------------------------------

	ifExtnsRcvAddrTable  OBJECT-TYPE
		SYNTAX SEQUENCE OF IfExtnsRcvAddrEntry
		ACCESS not-accessible
		STATUS mandatory
		DESCRIPTION
			"This table contains an entry for each
			address (broadcast, multicast, or uni-cast)
			for which the system will receive packets/
			frames on a particular interface.  When an
			interface is operating in promiscuous mode,
			entries are only required for those
			addresses for which the system would receive
			frames were it not operating in promiscuous
			mode."
		::= { ifExtensions 3 }

	ifExtnsRcvAddrEntry  OBJECT-TYPE
		SYNTAX IfExtnsRcvAddrEntry
		ACCESS not-accessible
		STATUS mandatory
		DESCRIPTION
			"A list of objects identifying an address
			for which the system will accept packets/
			frames on a particular interface."
		INDEX  { ifExtnsRcvAddrIfIndex, ifExtnsRcvAddress }
		::= { ifExtnsRcvAddrTable 1 }

	IfExtnsRcvAddrEntry ::= SEQUENCE {
		ifExtnsRcvAddrIfIndex
			INTEGER,
		ifExtnsRcvAddress
			PhysAddress,
		ifExtnsRcvAddrStatus
			INTEGER
		}

	ifExtnsRcvAddrIfIndex  OBJECT-TYPE
		SYNTAX INTEGER
		ACCESS read-only
		STATUS mandatory
		DESCRIPTION
			"The value of ifIndex, defined in [4,6],
			of an interface which recognizes this
			entry's address."
		::= { ifExtnsRcvAddrEntry 1 }

	ifExtnsRcvAddress OBJECT-TYPE
		SYNTAX	OCTET STRING (SIZE(6))
--		SYNTAX PhysAddress
		ACCESS read-only
		STATUS mandatory
		DESCRIPTION
			"An address for which the system will
			accept packets/frames on this entry's
			interface."
		::= { ifExtnsRcvAddrEntry 2 }

	ifExtnsRcvAddrStatus OBJECT-TYPE
		SYNTAX INTEGER {
					other(1),
					invalid(2),
					volatile(3),
					nonVolatile(4)
				}
		ACCESS read-write
		STATUS mandatory
		DESCRIPTION
			"This object has the value nonVolatile(4)
			for those entries in the table which are
			valid and will not be deleted by the next
			restart of the managed system.  Entries
			having the value volatile(3) are valid
			and exist, but have not been saved, so
			that will not exist after the next
			restart of the managed system.  Entries
			having the value other(1) are valid and
			exist but are not classified as to whether
			they will continue to exist after the next
			restart.  Entries having the value invalid(2)
			are invalid and do not represent an address
			for which an interface accepts frames.
				Setting an object instance to one of
			the values other(1), volatile(3), or
			nonVolatile(4) causes the corresponding
			entry to exist or continue to exist, and
			to take on the respective status as regards
			the next restart of the managed system.
				Setting an object instance to the value
			invalid(2) causes the corresponding entry
			to become invalid or cease to exist.
				It is an implementation-specific matter
			as to whether the agent removes an
			invalidated entry from the table.
			Accordingly, management stations must be
			prepared to receive tabular information
			from agents that corresponds to entries not
			currently in use.  Proper interpretation of
			such entries requires examination of the
			relevant ifExtnsRcvAddrStatus object
			instance."
--		DEFVAL  { volatile }
		::= { ifExtnsRcvAddrEntry 3 }


-- *************************************************************
--
-- Now, the ethernet like interface stuff.
--
-- *************************************************************

-- the Generic Ethernet-like group

-- Implementation of this group is mandatory for all systems
-- that attach to an ethernet-like medium.

	dot3Table OBJECT-TYPE
		SYNTAX	SEQUENCE OF Dot3Entry
		ACCESS	not-accessible
		STATUS	mandatory
		DESCRIPTION
			"Status information and control variables for a
			collection of ethernet-like interfaces attached to
			a particular system."
		::= { dot3 1 }

	dot3Entry OBJECT-TYPE
		SYNTAX	Dot3Entry
		ACCESS	not-accessible
		STATUS	mandatory
		DESCRIPTION
			"Status information and control variables for a
			particular interface to an ethernet-like medium."
		INDEX   { dot3Index }
		::= { dot3Table 1 }

	Dot3Entry ::= SEQUENCE {
		dot3Index
			INTEGER,
		dot3InitializeMac
			INTEGER,
		dot3MacSubLayerStatus
			INTEGER,
		dot3MulticastReceiveStatus
			INTEGER,
		dot3TxEnabled
			INTEGER,
		dot3TestTdrValue
			Gauge
	}

	dot3Index OBJECT-TYPE
		SYNTAX	INTEGER
		ACCESS	read-only
		STATUS	mandatory
		DESCRIPTION
			"An index value that uniquely identifies an
			interface to an ethernet-like medium.  The
			interface identified by a particular value of this
			index is the same interface as identified by the
			same value of ifIndex."
		::= { dot3Entry 1 }

	dot3InitializeMac OBJECT-TYPE
		SYNTAX	INTEGER { initialized(1), uninitialized(2) }
		ACCESS	read-write
		STATUS	mandatory
		DESCRIPTION
			"The initialization status of the MAC and PLS
			(Physical Layer Signalling) subsystems for a
			particular interface. The value initialized(1)
			signifies that the subsystems for a particular
			interface have been previously initialized; the
			value uninitialized(2) signifies that they have
			not been previously initialized.

			Each alteration of an instance of this object to
			either of the values initialized(1) or
			uninitialized(2) is analogous to an invocation of
			the initializeMAC action defined in [9] and has
			the effect of (re-)initializing the MAC and PLS
			subsystems for the associated interface. In
			particular,

				all management counters pertaining to the MAC
				and PLS subsystems for said interface are
				reset to zero;

				the receive and transmit layer management
				state variables (receiveEnabled and
				transmitEnabled in [9]) are set to enable
				reception and transmission of frames;

				the promiscuous receive function is disabled;
				and

				multicast reception is disabled."
		::= { dot3Entry 2 }

	dot3MacSubLayerStatus OBJECT-TYPE
		SYNTAX	INTEGER { enabled(1), disabled(2) }
		ACCESS	read-write
		STATUS	mandatory
		DESCRIPTION
			"The operational status of the MAC sublayer for a
			particular interface.  The value enabled(1)
			signifies that the MAC sublayer for said interface
			is operational for both transmitting and receiving
			frames -- that is, that the value of both the
			receive and transmit layer management state
			variables (receiveEnabled and transmitEnabled in
			[9]) for said interface are true.  The value
			disabled(2) signifies that the MAC sublayer for
			said interface is not operational for either
			transmitting or receiving frames. In particular,
			the value of an instance of this object is
			disabled(2) whenever the value of the
			corresponding instance of the dot3Enabled object
			is false(2).

			Each alteration of an instance of this object to
			the value enabled(1) is analogous to an invocation
			of the enableMACSublayer action defined in [9] and
			has the effect of starting normal transmit and
			receive operations (from the ``idle'' state) on
			the associated interface. In particular, such an
			alteration has the effect of resetting the PLS for
			said interface and of setting the receive and
			transmit layer management state variables
			(receiveEnabled and transmitEnabled in [9]) to be
			true.

			Each alteration of an instance of this object to
			the value disabled(2) is analogous to an
			invocation of the disableMACSublayer action
			defined in [9] and has the effect of terminating
			transmit and receive operations on the associated
			interface. In particular, such an alteration has
			the effect of setting the receive and transmit
			layer management state variables (receiveEnabled
			and transmitEnabled in [9]) to be false. Any
			transmissions/receptions in progress are completed
			before operation is terminated."
		::= { dot3Entry 3 }

	dot3MulticastReceiveStatus OBJECT-TYPE
		SYNTAX	INTEGER { enabled(1), disabled(2) }
		ACCESS	read-write
		STATUS	mandatory
		DESCRIPTION
			"The multicast receive status for a particular
			interface.  The value enabled(1) signifies that
			reception of multicast frames by the MAC sublayer
			is enabled on said interface. The value
			disabled(2) signifies that reception of multicast
			frames by the MAC sublayer is not enabled on said
			interface.

			Each alteration of an instance of this object to
			the value enabled(1) is analogous to an invocation
			of the enableMulticastReceive action defined in
			[9] and has the effect of enabling multicast frame
			reception on the associated interface. Actual
			reception of multicast frames is only possible on
			an interface when the values for the associated
			instances of the dot3MulticastReceiveStatus and
			dot3MacSubLayerStatus objects are enabled(1) and
			enabled(1), respectively.

			Each alteration of an instance of this object to
			the value disabled(2) is analogous to an
			invocation of the disableMulticastReceive action
			defined in [9] and has the effect of inhibiting
			multicast frame reception on the associated
			interface."
		::= { dot3Entry 4 }

	dot3TxEnabled OBJECT-TYPE
		SYNTAX	INTEGER { true(1), false(2)  }
		ACCESS	read-write
		STATUS	mandatory
		DESCRIPTION
			"The transmit layer management state variable
			(transmitEnabled as defined in [9]) for a
			particular interface.  The value true(1) signifies
			that the MAC frame transmission is enabled on said
			interface. The value false(2) signifies that the
			MAC frame transmission is inhibited on said
			interface. In particular, the value of an instance
			of this object is false(2) whenever the value of
			the corresponding instance of the
			dot3MacSubLayerStatus object is disabled(2).

			Each alteration of an instance of this object to
			the value true(1) is analogous to an invocation of
			the enableTransmit action defined in [9] and has
			the effect of enabling MAC sublayer frame
			transmission on the associated interface. In
			particular, such an alteration has the effect of
			setting the transmit layer management state
			variable (transmitEnabled in [9]) for said
			interface to be true.

			Each alteration of an instance of this object to
			the value false(2) is analogous to an invocation
			of the disableTransmit action defined in [9] and
			has the effect of inhibiting MAC sublayer frame
			transmission on the associated interface. In
			particular, such an alteration has the effect of
			setting the transmit layer management state
			variable (transmitEnabled in [9]) for said
			interface to be false. Any transmissions in
			progress are completed before transmission is
			inhibited."
		::= { dot3Entry 5 }

	dot3TestTdrValue OBJECT-TYPE
		SYNTAX	Gauge
		ACCESS	read-only
		STATUS	mandatory
		DESCRIPTION
			"The number of 10 MHz ticks which elapsed between
			the beginning of a TDR measurement and the
			collision which ended it, for the most recently
			executed TDR test.  If no TDR test has been
			executed, or the last TDR value is not available,
			this object has the value 0."
		::= { dot3Entry 6 }

-- the Ethernet-like Statistics group

-- Implementation of this group is mandatory

-- Due to implementation restrictions (e.g. in the instrumentation
-- provided by a chipset, or a device driver), some of the counters
-- in this group may be difficult or impossible to implement.
-- In such cases, an implementator should apply reasonable best
-- effort to detect as many occurrences as possible.  In any case,
-- the value of a counter will be the number actually detected,
-- which will always be less or equal to the number of actual
-- occurrences.  In the extreme case of a total inability to
-- detect occurrences, the counter will always be zero.

-- Vendors are strongly encouraged to document in user guides and
-- other appropriate documentation the conditions under which the
-- values of the counters in this group may represent an
-- underestimate of the true count.

	dot3StatsTable OBJECT-TYPE
		SYNTAX	SEQUENCE OF Dot3StatsEntry
		ACCESS	not-accessible
		STATUS	mandatory
		DESCRIPTION
			"Statistics for a collection of ethernet-like
			interfaces attached to a particular system."
		::= { dot3 2 }

	dot3StatsEntry OBJECT-TYPE
		SYNTAX	Dot3StatsEntry
		ACCESS	not-accessible
		STATUS	mandatory
		DESCRIPTION
			"Statistics for a particular interface to an
			ethernet-like medium."
		INDEX   { dot3StatsIndex }
		::= { dot3StatsTable 1 }

	Dot3StatsEntry ::= SEQUENCE {
		dot3StatsIndex
			INTEGER,
		dot3StatsAlignmentErrors
			Counter,
		dot3StatsFCSErrors
			Counter,
		dot3StatsSingleCollisionFrames
			Counter,
		dot3StatsMultipleCollisionFrames
			Counter,
		dot3StatsSQETestErrors
			Counter,
		dot3StatsDeferredTransmissions
			Counter,
		dot3StatsLateCollisions
			Counter,
		dot3StatsExcessiveCollisions
			Counter,
		dot3StatsInternalMacTransmitErrors
			Counter,
		dot3StatsCarrierSenseErrors
			Counter,
		dot3StatsExcessiveDeferrals
			Counter,
		dot3StatsFrameTooLongs
			Counter,
		dot3StatsInRangeLengthErrors
			Counter,
		dot3StatsOutOfRangeLengthFields
			Counter,
		dot3StatsInternalMacReceiveErrors
			Counter
	}

	dot3StatsIndex OBJECT-TYPE
		SYNTAX	INTEGER
		ACCESS	read-only
		STATUS	mandatory
		DESCRIPTION
			"An index value that uniquely identifies an
			interface to an ethernet-like medium.  The
			interface identified by a particular value of this
			index is the same interface as identified by the
			same value of ifIndex."
		::= { dot3StatsEntry 1 }

	dot3StatsAlignmentErrors OBJECT-TYPE
		SYNTAX	Counter
		ACCESS	read-only
		STATUS	mandatory
		DESCRIPTION
			"A count of frames received on a particular
			interface that are not an integral number of
			octets in length and do not pass the FCS check.

			The count represented by an instance of this
			object is incremented when the alignmentError
			status is returned by the MAC service to the LLC
			(or other MAC user). Received frames for which
			multiple error conditions obtain are, according to
			the conventions of [9], counted exclusively
			according to the error status presented to the
			LLC."
		::= { dot3StatsEntry 2 }

	dot3StatsFCSErrors OBJECT-TYPE
		SYNTAX	Counter
		ACCESS	read-only
		STATUS	mandatory
		DESCRIPTION
			"A count of frames received on a particular
			interface that are an integral number of octets in
			length but do not pass the FCS check.

			The count represented by an instance of this
			object is incremented when the frameCheckError
			status is returned by the MAC service to the LLC
			(or other MAC user). Received frames for which
			multiple error conditions obtain are, according to
			the conventions of [9], counted exclusively
			according to the error status presented to the
			LLC."
		::= { dot3StatsEntry 3 }

	dot3StatsSingleCollisionFrames OBJECT-TYPE
		SYNTAX	Counter
		ACCESS	read-only
		STATUS	mandatory
		DESCRIPTION
			"A count of successfully transmitted frames on a
			particular interface for which transmission is
			inhibited by exactly one collision.

			A frame that is counted by an instance of this
			object is also counted by the corresponding
			instance of either the ifOutUcastPkts or
			ifOutNUcastPkts object and is not counted by the
			corresponding instance of the
			dot3StatsMultipleCollisionFrames object."
		::= { dot3StatsEntry 4 }

	dot3StatsMultipleCollisionFrames OBJECT-TYPE
		SYNTAX	Counter
		ACCESS	read-only
		STATUS	mandatory
		DESCRIPTION
			"A count of successfully transmitted frames on a
			particular interface for which transmission is
			inhibited by more than one collision.

			A frame that is counted by an instance of this
			object is also counted by the corresponding
			instance of either the ifOutUcastPkts or
			ifOutNUcastPkts object and is not counted by the
			corresponding instance of the
			dot3StatsSingleCollisionFrames object."
	::= { dot3StatsEntry 5 }

	dot3StatsSQETestErrors OBJECT-TYPE
		SYNTAX	Counter
		ACCESS	read-only
		STATUS	mandatory
		DESCRIPTION
			"A count of times that the SQE TEST ERROR message
			is generated by the PLS sublayer for a particular
			interface. The SQE TEST ERROR message is defined
			in section 7.2.2.2.4 of [12] and its generation is
			described in section 7.2.4.6 of the same
			document."
		::= { dot3StatsEntry 6 }

	dot3StatsDeferredTransmissions OBJECT-TYPE
		SYNTAX	Counter
		ACCESS	read-only
		STATUS	mandatory
		DESCRIPTION
			"A count of frames for which the first
			transmission attempt on a particular interface is
			delayed because the medium is busy.
			The count represented by an instance of this
			object does not include frames involved in
			collisions."
		::= { dot3StatsEntry 7 }

	dot3StatsLateCollisions OBJECT-TYPE
		SYNTAX	Counter
		ACCESS	read-only
		STATUS	mandatory
		DESCRIPTION
			"The number of times that a collision is detected
			on a particular interface later than 512 bit-times
			into the transmission of a packet.

			Five hundred and twelve bit-times corresponds to
			51.2 microseconds on a 10 Mbit/s system. A (late)
			collision included in a count represented by an
			instance of this object is also considered as a
			(generic) collision for purposes of other
			collision-related statistics."
		::= { dot3StatsEntry 8 }

	dot3StatsExcessiveCollisions OBJECT-TYPE
		SYNTAX	Counter
		ACCESS	read-only
		STATUS	mandatory
		DESCRIPTION
			"A count of frames for which transmission on a
			particular interface fails due to excessive
			collisions."
		::= { dot3StatsEntry 9 }

	dot3StatsInternalMacTransmitErrors OBJECT-TYPE
		SYNTAX	Counter
		ACCESS	read-only
		STATUS	mandatory
		DESCRIPTION
			"A count of frames for which transmission on a
			particular interface fails due to an internal MAC
			sublayer transmit error. A frame is only counted
			by an instance of this object if it is not counted
			by the corresponding instance of either the
			dot3StatsLateCollisions object, the
			dot3StatsExcessiveCollisions object, the
			dot3StatsCarrierSenseErrors object, or the
			dot3StatsExcessiveDeferrals object.

			The precise meaning of the count represented by an
			instance of this object is implementation-
			specific.  In particular, an instance of this
			object may represent a count of transmission
			errors on a particular interface that are not
			otherwise counted."
		::= { dot3StatsEntry 10 }

	dot3StatsCarrierSenseErrors OBJECT-TYPE
		SYNTAX	Counter
		ACCESS	read-only
		STATUS	mandatory
		DESCRIPTION
			"The number of times that the carrier sense
			condition was lost or never asserted when
			attempting to transmit a frame on a particular
			interface.

			The count represented by an instance of this
			object is incremented at most once per
			transmission attempt, even if the carrier sense
			condition fluctuates during a transmission
			attempt."
		::= { dot3StatsEntry 11 }

	dot3StatsExcessiveDeferrals OBJECT-TYPE
		SYNTAX	Counter
		ACCESS	read-only
		STATUS	mandatory
		DESCRIPTION
			"A count of frames for which transmission on a
			particular interface is deferred for an excessive
			period of time."
		::= { dot3StatsEntry 12 }

	dot3StatsFrameTooLongs OBJECT-TYPE
		SYNTAX	Counter
		ACCESS	read-only
		STATUS	mandatory
		DESCRIPTION
			"A count of frames received on a particular
			interface that exceed the maximum permitted frame
			size.

			The count represented by an instance of this
			object is incremented when the frameTooLong status
			is returned by the MAC service to the LLC (or
			other MAC user). Received frames for which
			multiple error conditions obtain are, according to
			the conventions of [9], counted exclusively
			according to the error status presented to the
			LLC."
		::= { dot3StatsEntry 13 }

	dot3StatsInRangeLengthErrors OBJECT-TYPE
		SYNTAX	Counter
		ACCESS	read-only
		STATUS	mandatory
		DESCRIPTION
			"A count of frames received on a particular
			interface with a length field value that falls
			between the minimum unpadded LLC data size and the
			maximum allowed LLC data size inclusive and that
			does not match the number of LLC data octets
			received.

			The count represented by an instance of this
			object also includes frames for which the length
			field value is less than the minimum unpadded LLC
			data size."
		::= { dot3StatsEntry 14 }

	dot3StatsOutOfRangeLengthFields OBJECT-TYPE
		SYNTAX	Counter
		ACCESS	read-only
		STATUS	mandatory
		DESCRIPTION
			"A count of frames received on a particular
			interface for which the length field value exceeds
			the maximum allowed LLC data size.

			The count represented by an instance of this
			object is not incremented in implementations that
			observe Ethernet encapsulation conventions (by
			which the IEEE 802.3 length field is interpreted
			as the Ethernet Type field)."
		::= { dot3StatsEntry 15 }

	dot3StatsInternalMacReceiveErrors OBJECT-TYPE
		SYNTAX	Counter
		ACCESS	read-only
		STATUS	mandatory
		DESCRIPTION
			"A count of frames for which reception on a
			particular interface fails due to an internal MAC
			sublayer receive error. A frame is only counted by
			an instance of this object if it is not counted by
			the corresponding instance of either the
			dot3StatsFrameTooLongs object, the
			dot3StatsAlignmentErrors object, the
			dot3StatsFCSErrors object, the
			dot3StatsInRangeLengthErrors object, or the
			dot3StatsOutOfRangeLengthFields object.

			The precise meaning of the count represented by an
			instance of this object is implementation-
			specific.  In particular, an instance of this
			object may represent a count of receive errors on
			a particular interface that are not otherwise
			counted."
		::= { dot3StatsEntry 16 }

-- ----------------------------------------------------------------
--
-- The Ethernet-like Collision Statistics group (dot3CollTable)
-- is not implemented in the *** dxa 550 ***  since the necessary
-- instrumentation is not present in the IF chipset.
--
-- ----------------------------------------------------------------

--  802.3 Hardware Chipsets

-- The object ifExtnsChipSet is provided in [11] to identify the
-- MAC hardware used to communcate on an interface.  The following
-- hardware chipsets are provided for 802.3:

dot3ChipSets		OBJECT IDENTIFIER ::= { dot3 8 }
dot3ChipSetAMD		OBJECT IDENTIFIER ::= { dot3ChipSets 1 }
dot3ChipSetAMD7990	OBJECT IDENTIFIER ::= { dot3ChipSetAMD 1 }
dot3ChipSetAMD79900	OBJECT IDENTIFIER ::= { dot3ChipSetAMD 2 }

dot3ChipSetIntel      OBJECT IDENTIFIER ::= { dot3ChipSets 2 }
dot3ChipSetIntel82586 OBJECT IDENTIFIER ::= { dot3ChipSetIntel 1 }
dot3ChipSetIntel82596 OBJECT IDENTIFIER ::= { dot3ChipSetIntel 2 }

dot3ChipSetSeeq       OBJECT IDENTIFIER ::= { dot3ChipSets 3 }
dot3ChipSetSeeq8003   OBJECT IDENTIFIER ::= { dot3ChipSetSeeq 1 }

dot3ChipSetNational      OBJECT IDENTIFIER ::= { dot3ChipSets 4 }
dot3ChipSetNational8390  OBJECT IDENTIFIER ::= { dot3ChipSetNational 1 }
dot3ChipSetNationalSonic OBJECT IDENTIFIER ::= { dot3ChipSetNational 2 }

-- For those chipsets not represented above, OBJECT IDENTIFIER
-- assignment is required in other documentation, e.g., assignment
-- within that part of the registration tree delegated to
-- individual enterprises (see [4]).

-- **************************************************************************
--
-- And the internet experimental bridge MIB (3 Feb 91)
--
-- **************************************************************************

-- All representations of MAC addresses in this MIB Module use,
-- as a textual convention (i.e. this convention does not affect
-- their encoding), the data type:

--        MacAddress ::= OCTET STRING (SIZE (6))     a 6 octet address in
                                                    -- the "canonical" order
-- defined by IEEE 802.1a, i.e., as if it were transmitted least
-- significant bit first, even though 802.5 (in contrast to other
-- 802.x protocols) requires MAC addresses to be transmitted most
-- significant bit first.
--
-- 16-bit addresses, if needed, are represented by setting their
-- upper 4 octets to all 0's, i.e., AAFF would be represented
-- as 00000000AAFF.


-- Similarly, all representations of Bridge-Id in this MIB Module
-- use, as a textual convention (i.e. this convention does not affect
-- their encoding), the data type:

--          BridgeId ::= OCTET STRING (SIZE (8))     the Bridge-Identifier as
                                                  -- used in the Spanning Tree
-- Protocol to uniquely identify a bridge.  Its first two octets
-- contain a priority value and its last 6 octets contain the MAC
-- address used to refer to a bridge in a unique fashion (typically,
-- the numerically smallest MAC address of all ports on the bridge).

-- groups in the Bridge MIB

	dot1dBase	OBJECT IDENTIFIER ::= { dot1dBridge 1 }

	dot1dStp	OBJECT IDENTIFIER ::= { dot1dBridge 2 }

	dot1dTp		OBJECT IDENTIFIER ::= { dot1dBridge 4 }

-- the dot1dBase group

-- Implementation of the dot1dBase group is mandatory for all
-- bridges.

	dot1dBaseBridgeAddress OBJECT-TYPE
		SYNTAX	OCTET STRING (SIZE (6))
--		SYNTAX	MacAddress
		ACCESS	read-only
		STATUS	mandatory
		DESCRIPTION
			"The MAC address used by this bridge when it must
			be referred to in a unique fashion.   It is
			recommended that this be the numerically smallest
			MAC address of all ports that belong to this
			bridge.  However it is only required to be unique.
			When concatenated with dot1dStpPriority a unique
			BridgeIdentifier is formed which is used in the
			Spanning Tree Protocol."
		REFERENCE
			"P802.1d/D9, July 14, 1989: Sections 6.4.1.1.3 and 3.12.5"
		::= { dot1dBase 1 }

	dot1dBaseNumPorts OBJECT-TYPE
		SYNTAX	INTEGER
		ACCESS	read-only
		STATUS	mandatory
		DESCRIPTION
			"The number of ports controlled by this bridging
			entity."
		REFERENCE
			"P802.1d/D9, July 14, 1989: Section 6.4.1.1.3"
		::= { dot1dBase 2 }

	dot1dBaseType OBJECT-TYPE
		SYNTAX	INTEGER {
					unknown(1),
					transparent-only(2),
					sourceroute-only(3),
					srt(4)
				}
		ACCESS	read-only
		STATUS	mandatory
		DESCRIPTION
			"Indicates what type of bridging this bridge can
			perform.  If a bridge is actually performing a
			certain type of bridging this will be indicated by
			entries in the port table for the given type."
		::= { dot1dBase 3 }

-- The Generic Bridge Port Table

	dot1dBasePortTable OBJECT-TYPE
		SYNTAX	SEQUENCE OF Dot1dBasePortEntry
		ACCESS	not-accessible
		STATUS	mandatory
		DESCRIPTION
			"A table that contains generic information about
			every port that is associated with this bridge.
			Transparent, source-route, and srt ports are
			included."
		::= { dot1dBase 4 }

	dot1dBasePortEntry OBJECT-TYPE
		SYNTAX	Dot1dBasePortEntry
		ACCESS	not-accessible
		STATUS	mandatory
		DESCRIPTION
			"A list of information for each port of the
			bridge."
		REFERENCE
			"P802.1d/D9, July 14, 1989: Section 6.4.2, 6.6.1"
		INDEX  { dot1dBasePort }
		::= { dot1dBasePortTable 1 }

	Dot1dBasePortEntry ::= SEQUENCE {
		dot1dBasePort
			INTEGER,
		dot1dBasePortIfIndex
			INTEGER,
		dot1dBasePortCircuit
			OBJECT IDENTIFIER,
		dot1dBasePortDelayExceededDiscards
			Counter,
		dot1dBasePortMtuExceededDiscards
			Counter
		}

	dot1dBasePort OBJECT-TYPE
		SYNTAX	INTEGER
		ACCESS	read-only
		STATUS	mandatory
		DESCRIPTION
			"The port number of the port for which this entry
			contains bridge management information"
		::= { dot1dBasePortEntry 1 }

	dot1dBasePortIfIndex OBJECT-TYPE
		SYNTAX	INTEGER
		ACCESS	read-only
		STATUS	mandatory
		DESCRIPTION
			"The value of the instance of the ifIndex object,
			defined in [4,6], for the interface corresponding
			to this port"
		::= { dot1dBasePortEntry 2 }

	dot1dBasePortCircuit OBJECT-TYPE
		SYNTAX	OBJECT IDENTIFIER
		ACCESS	read-only
		STATUS	mandatory
		DESCRIPTION
			"For a port which (potentially) has the same value
			of dot1dBasePortIfIndex as another port on the
			same bridge, this object contains the name of an
			object instance unique to this port.  For example,
			in the case where multiple ports correspond one-
			to-one with multiple X.25 virtual circuits, this
			value might identify an (e.g., the first) object
			instance associated with the X.25 virtual circuit
			corresponding to this port.
 
			For a port which has a unique value of
			dot1dBasePortIfIndex, this object can have the
			value { 0 0 }."
		::= { dot1dBasePortEntry 3 }

	dot1dBasePortDelayExceededDiscards OBJECT-TYPE
		SYNTAX	Counter
		ACCESS	read-only
		STATUS	mandatory
		DESCRIPTION
			"The number of frames discarded by this port due
			to excessive transit delay through the bridge.  It
			is incremented by both transparent and source
			route bridges."
		REFERENCE
			"P802.1d/D9, July 14, 1989: Section 6.6.1.1.3"
		::= { dot1dBasePortEntry 4 }

	dot1dBasePortMtuExceededDiscards OBJECT-TYPE
		SYNTAX	Counter
		ACCESS	read-only
		STATUS	mandatory
		DESCRIPTION
			"The number of frames discarded by this port due
			to an excessive size.  It is incremented by both
			transparent and source route bridges."
		REFERENCE
			"P802.1d/D9, July 14, 1989: Section 6.6.1.1.3"
		::= { dot1dBasePortEntry 5 }


-- the dot1dStp group

-- Implementation of the dot1dStp group is optional.  It is
-- implemented by those bridges that support the Spanning Tree
-- Protocol.  Transparent, Source Route, and SRT bridges will
-- implement this group only if they support the Spanning Tree
-- Protocol.


	dot1dStpProtocolSpecification OBJECT-TYPE
		SYNTAX	INTEGER {
			unknown(1),
			decLb100(2),
			ieee8021d(3)
		}
		ACCESS	read-only
		STATUS	mandatory
		DESCRIPTION
			"An indication of what version of the Spanning
			Tree Protocol is being run.  The value
			'decLb100(2)' indicates the DEC LANbridge 100
			Spanning Tree protocol.  IEEE 802.1d
			implementations will return 'ieee8021d(3)'.  If
			future versions of the IEEE Spanning Tree Protocol
			are released that are incompatible with the
			current version a new value will be defined."
			::= { dot1dStp 1 }

	dot1dStpPriority OBJECT-TYPE
		SYNTAX	INTEGER (0..65535)
		ACCESS	read-write
		STATUS	mandatory
		DESCRIPTION
			"The value of the priority field which is
			contained in the first two octets of the (8 octet
			long) Bridge ID.  The other (last) 6 octets of the
			Bridge ID are given by the value of
			dot1dBaseBridgeAddress."
		REFERENCE
			"P802.1d/D9, July 14, 1989: Section 4.5.3.7"
		::= { dot1dStp 2 }

	dot1dStpTimeSinceTopologyChange OBJECT-TYPE
		SYNTAX	TimeTicks
		ACCESS	read-only
		STATUS	mandatory
		DESCRIPTION
			"The time (in hundreths of a second) since the
			last time a topology change was detected by the
			bridge entity."
		REFERENCE
			"P802.1d/D9, July 14, 1989: Section 6.8.1.1.3"
		::= { dot1dStp 3 }

	dot1dStpTopChanges OBJECT-TYPE
		SYNTAX	Counter
		ACCESS	read-only
		STATUS	mandatory
		DESCRIPTION
			"The total number of topology changes detected by
			this bridge since the management entity was last
			reset or initialized."
		REFERENCE
			"P802.1d/D9, July 14, 1989: Section 6.8.1.1.3"
		::= { dot1dStp 4 }

	dot1dStpDesignatedRoot OBJECT-TYPE
--            SYNTAX	BridgeId
		SYNTAX	OCTET STRING (SIZE(8))
		ACCESS	read-only
		STATUS	mandatory
		DESCRIPTION
			"The bridge identifier of the root of the spanning
			tree as determined by the Spanning Tree Protocol
			as executed by this node.  This value is used as
			the Root Identifier parameter in all Configuration
			Bridge PDUs originated by this node."
		REFERENCE
			"P802.1d/D9, July 14, 1989: Section 4.5.3.1"
		::= { dot1dStp 5 }

	dot1dStpRootCost OBJECT-TYPE
		SYNTAX	INTEGER
		ACCESS	read-only
		STATUS	mandatory
		DESCRIPTION
			"The cost of the path to the root as seen from
			this bridge."
		REFERENCE
			"P802.1d/D9, July 14, 1989: Section 4.5.3.2"
		::= { dot1dStp 6 }

	dot1dStpRootPort OBJECT-TYPE
		SYNTAX	INTEGER
		ACCESS	read-only
		STATUS	mandatory
		DESCRIPTION
			"The port number of the port which offers the
			lowest cost path from this bridge to the root
			bridge."
		REFERENCE
			"P802.1d/D9, July 14, 1989: Section 4.5.3.2"
		::= { dot1dStp 7 }

	dot1dStpMaxAge OBJECT-TYPE
		SYNTAX	INTEGER
		ACCESS	read-only
		STATUS	mandatory
		DESCRIPTION
			"The maximum age of Spanning Tree Protocol
			information learned from the network on any port
			before it is discarded, in units of hundredths of
			a second.  This is the actual value that this
			bridge is currently using."
		REFERENCE
			"P802.1d/D9, July 14, 1989: Section 4.5.3.4"
		::= { dot1dStp 8 }

	dot1dStpHelloTime OBJECT-TYPE
		SYNTAX	INTEGER
		ACCESS	read-only
		STATUS	mandatory
		DESCRIPTION
			"The amount of time between the transmission of
			Configuration bridge PDUs by this node on any port
			when it is the root of the spanning tree or trying
			to become so, in units of hundredths of a second.
			This is the actual value that this bridge is
			currently using."
		REFERENCE
			"P802.1d/D9, July 14, 1989: Section 4.5.3.5"
		::= { dot1dStp 9 }

	dot1dStpHoldTime OBJECT-TYPE
		SYNTAX	INTEGER
		ACCESS	read-only
		STATUS	mandatory
		DESCRIPTION
			"This time value determines the interval length
			during which no more than two Configuration bridge
			PDUs shall be transmitted by this node, in units
			of hundredths of a second."
		REFERENCE
			"P802.1d/D9, July 14, 1989: Section 4.5.3.14"
		::= { dot1dStp 10 }

	dot1dStpForwardDelay OBJECT-TYPE
		SYNTAX INTEGER
		ACCESS	read-only
		STATUS	mandatory
		DESCRIPTION
			"This time value, measured in units of hundredths
			of a second, controls how fast a port changes its
			spanning state when moving towards the Forwarding
			state.  The value determines how long the port
			stays in a particular state before moving to the
			next state.  For example, how long a port stays in
			the Listening state when moving from Blocking to
			Learning.  This value is also used, when a
			topology change has been detected and is underway,
			to age all dynamic entries in the Forwarding
			Database.  [Note that this value is the one that
			this bridge is currently using, in contrast to
			dot1dStpBridgeForwardDelay which is the value that
			this bridge and all others would start using
			if/when this bridge were to become the root.]"
		REFERENCE
			"P802.1d/D9, July 14, 1989: Section 4.5.3.6"
		::= { dot1dStp 11 }

	dot1dStpBridgeMaxAge OBJECT-TYPE
		SYNTAX	INTEGER (600..4000)
		ACCESS	read-write
		STATUS	mandatory
		DESCRIPTION
			"The value that all bridges use for MaxAge when
			this bridge is acting as the root."
		REFERENCE
			"P802.1d/D9, July 14, 1989: Section 4.5.3.8"
		::= { dot1dStp 12 }

	dot1dStpBridgeHelloTime OBJECT-TYPE
		SYNTAX	INTEGER (100..1000)
		ACCESS	read-write
		STATUS	mandatory
		DESCRIPTION
			"The value that all bridges use for HelloTime when
			this bridge is acting as the root."
		REFERENCE
			"P802.1d/D9, July 14, 1989: Section 4.5.3.9"
		::= { dot1dStp 13 }

	dot1dStpBridgeForwardDelay OBJECT-TYPE
		SYNTAX	INTEGER (400..3000)
		ACCESS	read-write
		STATUS	mandatory
		DESCRIPTION
			"The value that all bridges use for ForwardDelay
			when this bridge is acting as the root."
		REFERENCE
			"P802.1d/D9, July 14, 1989: Section 4.5.3.9"
		::= { dot1dStp 14 }


-- The Spanning Tree Port Table

	dot1dStpPortTable OBJECT-TYPE
		SYNTAX	SEQUENCE OF Dot1dStpPortEntry
		ACCESS	not-accessible
		STATUS	mandatory
		DESCRIPTION
			"A table that contains port-specific information
			for the Spanning Tree Protocol."
		::= { dot1dStp 15 }

	dot1dStpPortEntry OBJECT-TYPE
		SYNTAX	Dot1dStpPortEntry
		ACCESS	not-accessible
		STATUS	mandatory
		DESCRIPTION
			"A list of information maintained by every port
			about the Spanning Tree Protocol state for that
			port."
		INDEX   { dot1dStpPort }
		::= { dot1dStpPortTable 1 }

	Dot1dStpPortEntry ::= SEQUENCE {
			dot1dStpPort
				INTEGER,
			dot1dStpPortPriority
				INTEGER,
			dot1dStpPortState
				INTEGER,
			dot1dStpPortEnable
				INTEGER,
			dot1dStpPortPathCost
				INTEGER,
			dot1dStpPortDesignatedRoot
				OCTET STRING,
			dot1dStpPortDesignatedCost
				INTEGER,
			dot1dStpPortDesignatedBridge
				OCTET STRING,
			dot1dStpPortDesignatedPort
				OCTET STRING,
			dot1dStpPortForwardTransitions
				Counter
		}

	dot1dStpPort OBJECT-TYPE
		SYNTAX	INTEGER
		ACCESS	read-only
		STATUS	mandatory
		DESCRIPTION
			"The port number of the port for which this entry
			contains Spanning Tree Protocol management
			information."
		REFERENCE
			"P802.1d/D9, July 14, 1989: Section 6.8.2.1.2"
		::= { dot1dStpPortEntry 1 }

	dot1dStpPortPriority OBJECT-TYPE
		SYNTAX	INTEGER (0..255)
		ACCESS	read-write
		STATUS	mandatory
		DESCRIPTION
			"The value of the priority field which is
			contained in the first octet of the (2 octet long)
			Port ID.  The other octet of the Port ID is given
			by the value of dot1dStpPort."
		REFERENCE
			"P802.1d/D9, July 14, 1989: Section 4.5.5.1"
		::= { dot1dStpPortEntry 2 }

	dot1dStpPortState OBJECT-TYPE
		SYNTAX	INTEGER {
					disabled(1),
					blocking(2),
					listening(3),
					learning(4),
					forwarding(5),
					broken(6)
				}
		ACCESS	read-only
		STATUS	mandatory
		DESCRIPTION
			"The port's current state as defined by
			application of the Spanning Tree Protocol.  This
			state controls what action a port takes on
			reception of a frame.  If the bridge has detected
			a port that is malfunctioning it will place that
			port into the broken(7) state.  For ports which
			are disabled (see dot1dStpPortEnable), this object
			will have a value of disabled(1)."
		REFERENCE
			"P802.1d/D9, July 14, 1989: Section 4.5.5.2"
		::= { dot1dStpPortEntry 3 }

	dot1dStpPortEnable OBJECT-TYPE
		SYNTAX	INTEGER {
				disabled(1),
				enabled(2)
			}
		ACCESS	read-write
		STATUS	mandatory
		DESCRIPTION
			"The enabled/disabled status of the port."
		REFERENCE
			"P802.1d/D9, July 14, 1989: Section 4.5.5.2"
		::= { dot1dStpPortEntry 4 }

	dot1dStpPortPathCost OBJECT-TYPE
		SYNTAX	INTEGER (1..65535)
		ACCESS	read-write
		STATUS	mandatory
		DESCRIPTION
			"The contribution of this port to the path cost of
			paths towards the spanning tree root which include
			this port."
		REFERENCE
			"P802.1d/D9, July 14, 1989: Section 4.5.5.3"
		::= { dot1dStpPortEntry 5 }

	dot1dStpPortDesignatedRoot OBJECT-TYPE
--            SYNTAX	BridgeId
		SYNTAX	OCTET STRING
		ACCESS	read-only
		STATUS	mandatory
		DESCRIPTION
			"The unique Bridge Identifier of the Bridge
			recorded as the Root in the Configuration BPDUs
			transmitted by the Designated Bridge for the LAN
			to which the Port is attached."
		REFERENCE
			"P802.1d/D9, July 14, 1989: Section 4.5.5.4"
		::= { dot1dStpPortEntry 6 }

	dot1dStpPortDesignatedCost OBJECT-TYPE
		SYNTAX	INTEGER
		ACCESS	read-only
		STATUS	mandatory
		DESCRIPTION
			"The path cost of the Designated Port of the
			segment connected to this port.  This value is
			compared to the Root Path Cost field in received
			bridge PDUs."
		REFERENCE
			"P802.1d/D9, July 14, 1989: Section 4.5.5.5"
		::= { dot1dStpPortEntry 7 }

	dot1dStpPortDesignatedBridge OBJECT-TYPE
--		SYNTAX	BridgeId
		SYNTAX	OCTET STRING
		ACCESS	read-only
		STATUS	mandatory
		DESCRIPTION
			"The Bridge Identifier of the bridge which this
			port considers to be the Designated Bridge for
			this port's segment."
		REFERENCE
			"P802.1d/D9, July 14, 1989: Section 4.5.5.6"
		::= { dot1dStpPortEntry 8 }

	dot1dStpPortDesignatedPort OBJECT-TYPE
		SYNTAX	OCTET STRING
		ACCESS	read-only
		STATUS	mandatory
		DESCRIPTION
			"The Port Identifier of the port on the Designated
			Bridge for this port's segment."
		REFERENCE
			"P802.1d/D9, July 14, 1989: Section 4.5.5.7"
		::= { dot1dStpPortEntry 9 }

	dot1dStpPortForwardTransitions OBJECT-TYPE
		SYNTAX	Counter
		ACCESS	read-only
		STATUS	mandatory
		DESCRIPTION
			"The number of times this port has transitioned
			from the Learning state to the Forwarding state."
		::= { dot1dStpPortEntry 10 }

-- ----------------------------------------------------------
--
-- The dot1dSr group is not implemented in the DXA-550.
--
-- ----------------------------------------------------------

-- the dot1dTp group

-- Implementation of the dot1dTp group is optional.  It is
-- implemented by those bridges that support the transparent
-- bridging mode.  A transparent or SRT bridge will implement
-- this group.


	dot1dTpLearntEntryDiscards OBJECT-TYPE
		SYNTAX	Counter
		ACCESS	read-only
		STATUS	mandatory
		DESCRIPTION
			"The total number of Forwarding Database entries,
			which have been or would have been learnt, but
			have been discarded due to a lack of space to
			store them in the Forwarding Database.  If this
			counter is increasing, it indicates that the
			Forwarding Database is regularly becoming full (a
			condition which has unpleasant performance effects
			on the subject LAN).  If this counter has a
			significant value but is not presently increasing,
			it indicates that the problem has been occurring
			but is not persistent."
		REFERENCE
			"P802.1d/D9, July 14, 1989: Section 6.7.1.1.3"
		::= { dot1dTp 1 }

	dot1dTpAgingTime OBJECT-TYPE
		SYNTAX	 INTEGER
		ACCESS	 read-write
		STATUS	 mandatory
		DESCRIPTION
			"The timeout period in seconds for aging out
			dynamically learned forwarding information."
		REFERENCE
			"P802.1d/D9, July 14, 1989: Section 6.7.1.1.3"
		::= { dot1dTp 2 }

--  The Forwarding Database for Transparent Bridges

	dot1dTpFdbTable OBJECT-TYPE
		SYNTAX	SEQUENCE OF Dot1dTpFdbEntry
		ACCESS	not-accessible
		STATUS	mandatory
		DESCRIPTION
			"A table that contains information about unicast
			entries for which the bridge has forwarding and/or
			filtering information.  This information is used
			by the transparent bridging function in
			determining how to propagate a received frame."
		::= { dot1dTp 3 }

	dot1dTpFdbEntry OBJECT-TYPE
		SYNTAX	Dot1dTpFdbEntry
		ACCESS	not-accessible
		STATUS	mandatory
		DESCRIPTION
			"Information about a specific unicast MAC address
			for which the bridge has some forwarding and/or
			filtering information."
		INDEX   { dot1dTpFdbAddress }
		::= { dot1dTpFdbTable 1 }

	Dot1dTpFdbEntry ::= SEQUENCE {
				dot1dTpFdbAddress
					-- MacAddress,
					OCTET STRING,
				dot1dTpFdbPort
					INTEGER,
				dot1dTpFdbStatus
					INTEGER
			}

	dot1dTpFdbAddress OBJECT-TYPE
		SYNTAX	OCTET STRING (SIZE (6))
--		SYNTAX	MacAddress
		ACCESS	read-only
		STATUS	mandatory
		DESCRIPTION
			"A unicast MAC address for which the bridge has
			forwarding and/or filtering information."
		REFERENCE
			"P802.1d/D9, July 14, 1989: Section 3.9.1, 3.9.2"
		::= { dot1dTpFdbEntry 1 }

	dot1dTpFdbPort OBJECT-TYPE
		SYNTAX	INTEGER
		ACCESS	read-only
		STATUS	mandatory
		DESCRIPTION
			"Either the value '0', or the port on which a
			frame having a source address equal to the value
			of the corresponding instance of dot1dTpFdbAddress
			has been seen.  A non-zero value of this object
			indicates the port for which the ifIndex object,
			defined in [4,6], of the corresponding interface
			has the same value.  A value of '0' indicates that
			the port number has not been learned but that the
			bridge does have some forwarding/filtering
			information about this address (e.g. in the
			dot1dStaticTable).  Implementors are encouraged to
			assign the port value to this object whenever it
			is learned even for addresses for which the
			corresponding value of dot1dTpFdbStatus is not
			learned(3)."
	::= { dot1dTpFdbEntry 2 }

	dot1dTpFdbStatus OBJECT-TYPE
		SYNTAX	INTEGER {
					other(1),
					invalid(2),
					learned(3),
					self(4),
					mgmt(5)
				}
		ACCESS	read-only
		STATUS	mandatory
		DESCRIPTION
			"The status of this entry.  The meanings of the
			values are:

			other(1)   : none of the following.  This would
				include the case where some other
				MIB object (not the corresponding
				instance of dot1dTpFdbPort, nor an
				entry in the dot1dStaticTable) is
				being used to determine if and how
				frames addressed to the value of
				the corresponding instance of
				dot1dTpFdbAddress are being
				forwarded.

			invalid(2) : this entry is not longer valid
				(e.g. it was learned but has since
				aged-out), but has not yet been
				flushed from the table.
		
			learned(3) : the value of the corresponding
				instance of dot1dTpFdbPort was
				learned, and is being used.

			self(4)    : the value of the corresponding
				instance of dot1dTpFdbAddress
				represents one of the bridge's
				addresses.  The corresponding
				instance of dot1dTpFdbPort
				indicates which of the bridge's
				ports has this address.

			mgmt(5)    : the value of the corresponding
				instance of dot1dTpFdbAddress is
				also the value of an existing
				instance of dot1dStaticAddress."
		::= { dot1dTpFdbEntry 3 }


        --  Port Table for Transparent Bridges

	dot1dTpPortTable OBJECT-TYPE
		SYNTAX	SEQUENCE OF Dot1dTpPortEntry
		ACCESS	not-accessible
		STATUS	mandatory
		DESCRIPTION
			"A table that contains information about every
			port that is associated with this transparent
			bridge."
		::= { dot1dTp 4 }

	dot1dTpPortEntry OBJECT-TYPE
		SYNTAX	Dot1dTpPortEntry
		ACCESS	not-accessible
		STATUS	mandatory
		DESCRIPTION
			"A list of information for each port of a
			transparent bridge."
		INDEX   { dot1dTpPort }
		::= { dot1dTpPortTable 1 }

	Dot1dTpPortEntry ::= SEQUENCE {
			dot1dTpPort
				INTEGER,
			dot1dTpPortMaxInfo
				INTEGER,
			dot1dTpPortInFrames
				Counter,
			dot1dTpPortOutFrames
				Counter,
			dot1dTpPortInDiscards
				Counter
		}

	dot1dTpPort OBJECT-TYPE
		SYNTAX	INTEGER
		ACCESS	read-only
		STATUS	mandatory
		DESCRIPTION
			"The port number of the port for which this entry
			contains Transparent bridging management
			information."
		::= { dot1dTpPortEntry 1 }

-- It would be nice if we could use ifMtu as the size of the
-- largest INFO field, but we can't because ifMtu is defined
-- to be the size that the (inter-)network layer can use which
-- can differ from the MAC layer (especially if several layers
-- of encapsulation are used).

	dot1dTpPortMaxInfo OBJECT-TYPE
		SYNTAX	INTEGER
		ACCESS	read-only
		STATUS	mandatory
		DESCRIPTION
			"The maximum size of the INFO (non-MAC) field that
			this port will receive or transmit."
		::= { dot1dTpPortEntry 2 }

	dot1dTpPortInFrames OBJECT-TYPE
		SYNTAX	Counter
		ACCESS	read-only
		STATUS	mandatory
		DESCRIPTION
			"The number of frames that have been received by
			this port from its segment. Note that a frame
			received on the interface corresponding to this
			port is only counted by this object if and only if
			it is for a protocol being bridged by this
			entity."
		REFERENCE
			"P802.1d/D9, July 14, 1989: Section 6.6.1.1.3"
		::= { dot1dTpPortEntry 3 }

	dot1dTpPortOutFrames OBJECT-TYPE
		SYNTAX	Counter
		ACCESS	read-only
		STATUS	mandatory
		DESCRIPTION
			"The number of frames that have been transmitted
			by this port to its segment.  Note that a frame
			transmitted on the interface corresponding to this
			port is only counted by this object if and only if
			it is for a protocol being bridged by this
			entity."
		REFERENCE
			"P802.1d/D9, July 14, 1989: Section 6.6.1.1.3"
		::= { dot1dTpPortEntry 4 }

	dot1dTpPortInDiscards OBJECT-TYPE
		SYNTAX	Counter
		ACCESS	read-only
		STATUS	mandatory
		DESCRIPTION
			"Count of valid frames received which were
			discarded by the Forwarding Process."
		REFERENCE
			"P802.1d/D9, July 14, 1989: Section 6.6.1.1.3"
		::= { dot1dTpPortEntry 5 }

-- Traps for use by Bridges

--        newRoot TRAP-TYPE
--            ENTERPRISE  dot1d
--            DESCRIPTION
--                    "The newRoot trap indicates that the sending agent
--                    has become the new root of the Spanning Tree; the
--                    trap is sent by a bridge on the first occurrence
--                    of one of its ports transitioning to the
--                    Forwarding state after becoming root."
--            ::= 1

--        topologyChange TRAP-TYPE
--            ENTERPRISE  dot1d
--            DESCRIPTION
--                    "A topologyChange trap is sent by a bridge when
--                    any of its configured ports transitions into or
--                    out of the Forwarding state.  The trap is not sent
--                    if a newRoot trap is sent for the same
--                    transition."
--            ::= 2

	--
	-- cdxa550 subtree. This subtree contains DXA-500 Series
	-- specific objects i.e. objects for the DXA-550.
	--

	dDXA550AvailableBuffers OBJECT-TYPE
		SYNTAX	Gauge
		ACCESS	read-only
		STATUS	mandatory
		DESCRIPTION
			"Count of available data buffers"
		::= { dDXA550 1 }

	dDXA550InitialBuffers OBJECT-TYPE
		SYNTAX	INTEGER
		ACCESS	read-only
		STATUS	mandatory
		DESCRIPTION
			"Initial amount of buffers available at system startup."
		::= { dDXA550 2 }

	cConstallationBufferDataLength OBJECT-TYPE
		SYNTAX	INTEGER(64..65535)
		ACCESS	read-only
		STATUS	mandatory
		DESCRIPTION
			"Number of data bytes that can be stored in each buffer."
		::= { dDXA550 3 }

	dDXA550InstructionRam OBJECT-TYPE
		SYNTAX	INTEGER
		ACCESS	read-only
		STATUS	mandatory
		DESCRIPTION
			"Number of bytes of system instruction ram available.
			This is fast, zero-wait-state RAM."
		::= { dDXA550 4 }

	dDXA550GlobalDataRam OBJECT-TYPE
		SYNTAX	INTEGER
		ACCESS	read-only
		STATUS	mandatory
		DESCRIPTION
			"Number of bytes of global data ram available.
			This is RAM contains I/O buffers and other
			data structures for which zero-wait-state access
			is not required by the CPU."
		::= { dDXA550 5 }

	dDXA550FastDataRam OBJECT-TYPE
		SYNTAX	INTEGER
		ACCESS	read-only
		STATUS	mandatory
		DESCRIPTION
			"Number of bytes of fast data ram available.
			This is RAM contains data structures for which
			the CPU requires zero-wait-state access, such as
			the bridge forwarding database."
		::= { dDXA550 6 }

	--
	-- Extensions for the dot3 group for our own 
	-- driver, etc, counters.
	--

	cDot3Table OBJECT-TYPE
		SYNTAX	SEQUENCE OF CDot3Entry
		ACCESS	not-accessible
		STATUS	mandatory
		DESCRIPTION
			"Extended status information for the datability
			specific LANCE and ILACC drivers."
		::= { cDot3 1 }

	cDot3Entry OBJECT-TYPE
		SYNTAX	CDot3Entry
		ACCESS	not-accessible
		STATUS	mandatory
		DESCRIPTION
			"Proprietary status information for a particular 
			interface"
		INDEX   { cDot3Index }
		::= { cDot3Table 1 }

	CDot3Entry ::= SEQUENCE {
		cDot3Index			INTEGER,
		cDot3Disables		Counter,
		cDot3MauDisconnect	Counter,
		cDot3Babbles		Counter,
		cDot3MerrDisconnect	Counter,
		cDot3TxonDisconnect	Counter,
		cDot3RxonDisconnect	Counter,
		cDot3XmitFailure	Counter,
		cDot3XmitBuffErr	Counter,
		cDot3XmitUflo		Counter,
		cDot3RcvBuffErr		Counter,
		cDot3RcvOflo		Counter,
		cDot3Startless		Counter,
		cDot3Endless		Counter
	}

	cDot3Index OBJECT-TYPE
		SYNTAX	INTEGER
		ACCESS	read-only
		STATUS	mandatory
		DESCRIPTION
			"An index value that uniquely identifies an
			interface to an ethernet-like medium.  The
			interface identified by a particular value of this
			index is the same interface as identified by the
			same value of ifIndex."
		::= { cDot3Entry 1 }

	cDot3Disables OBJECT-TYPE
		SYNTAX	Counter
		ACCESS	read-only
		STATUS	mandatory
		DESCRIPTION
			"Number of LANCE/ILLAC disconnects that occured
			because the interface was disabled"
		::= { cDot3Entry 2 }

	cDot3MauDisconnect OBJECT-TYPE
		SYNTAX	Counter
		ACCESS	read-only
		STATUS	mandatory
		DESCRIPTION
			"Number of LANCE/ILLAC disconnects that occured
			because m-lance-cs-mau-connected was 0."
		::= { cDot3Entry 3 }

	cDot3Babbles OBJECT-TYPE
		SYNTAX	Counter
		ACCESS	read-only
		STATUS	mandatory
		DESCRIPTION
			"Number of times the LANCE/ILACC Babble bit
			was set."
		::= { cDot3Entry 4 }

	cDot3MerrDisconnect OBJECT-TYPE
		SYNTAX	Counter
		ACCESS	read-only
		STATUS	mandatory
		DESCRIPTION
			"Number of LANCE/ILLAC disconnects that occured
			because the memory error bit was set."
		::= { cDot3Entry 5 }

	cDot3TxonDisconnect OBJECT-TYPE
		SYNTAX	Counter
		ACCESS	read-only
		STATUS	mandatory
		DESCRIPTION
			"Number of LANCE/ILLAC disconnects that occured
			because the txon bit was off."
		::= { cDot3Entry 6 }

	cDot3RxonDisconnect OBJECT-TYPE
		SYNTAX	Counter
		ACCESS	read-only
		STATUS	mandatory
		DESCRIPTION
			"Number of LANCE/ILLAC disconnects that occured
			because the rxon bit was off."
		::= { cDot3Entry 7 }

	cDot3XmitFailure OBJECT-TYPE
		SYNTAX	Counter
		ACCESS	read-only
		STATUS	mandatory
		DESCRIPTION
			"Number of LANCE/ILLAC disconnects that occured
			because no packets were received and every transmit 
			attempt resulted in a failure."
		::= { cDot3Entry 8 }

	cDot3XmitBuffErr OBJECT-TYPE
		SYNTAX	Counter
		ACCESS	read-only
		STATUS	mandatory
		DESCRIPTION
			"Number of LANCE/ILLAC transmit buffer errors that occured."
		::= { cDot3Entry 9 }

	cDot3XmitUflo OBJECT-TYPE
		SYNTAX	Counter
		ACCESS	read-only
		STATUS	mandatory
		DESCRIPTION
			"Number of LANCE/ILLAC transmit underflo errors that occured."
		::= { cDot3Entry 10 }

	cDot3RcvBuffErr OBJECT-TYPE
		SYNTAX	Counter
		ACCESS	read-only
		STATUS	mandatory
		DESCRIPTION
			"Number of LANCE/ILLAC receive buffer errors that occured."
		::= { cDot3Entry 11 }

	cDot3RcvOflo OBJECT-TYPE
		SYNTAX	Counter
		ACCESS	read-only
		STATUS	mandatory
		DESCRIPTION
			"Number of LANCE/ILLAC receive overflo errors that occured."
		::= { cDot3Entry 12 }

	cDot3Startless OBJECT-TYPE
		SYNTAX	Counter
		ACCESS	read-only
		STATUS	mandatory
		DESCRIPTION
			"Number of times that the driver did not get a
			start-of-message when one was expected. This if 
			for reception."
		::= { cDot3Entry 13 }

	cDot3Endless OBJECT-TYPE
		SYNTAX	Counter
		ACCESS	read-only
		STATUS	mandatory
		DESCRIPTION
			"Number of times that the driver detected the 
			start of one packet without detecting the end of
			the previous packet. This is for reception."
		::= { cDot3Entry 14 }

	END
