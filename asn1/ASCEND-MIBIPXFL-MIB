--			Ascend mibipxfl MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBIPXFL-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibipxsapFilterProfile  OBJECT IDENTIFIER ::= { configuration 88}

	-- The mibipxsapFilterProfile table
	--
	-- This table contains parameters for the mibipxsapFilterProfile profile
	--

    mibipxsapFilterProfileTable	OBJECT-TYPE
	SYNTAX		SEQUENCE OF MibipxsapFilterProfileEntry
	ACCESS		not-accessible
	STATUS		mandatory
	DESCRIPTION	"A list of mibipxsapFilterProfile profile entries."
	::= { mibipxsapFilterProfile 1 }

    mibipxsapFilterProfileEntry	OBJECT-TYPE
	SYNTAX		MibipxsapFilterProfileEntry
	ACCESS		not-accessible
	STATUS		mandatory
	DESCRIPTION	"A mibipxsapFilterProfile entry containing objects that
			 maps to the parameters of mibipxsapFilterProfile profile."
	INDEX		{ ipxsapFilterProfile-IpxSapFilterName }
	::= { mibipxsapFilterProfileTable 1 }

    MibipxsapFilterProfileEntry ::=
	SEQUENCE {
	    ipxsapFilterProfile-IpxSapFilterName
		DisplayString,
	    ipxsapFilterProfile-Action-o
		INTEGER
	}

    ipxsapFilterProfile-IpxSapFilterName	OBJECT-TYPE
	SYNTAX	DisplayString
	ACCESS	read-only
	STATUS	mandatory
	DESCRIPTION	"The name of this IPX SAP Filter."
	::= { mibipxsapFilterProfileEntry 1 }

    ipxsapFilterProfile-Action-o	OBJECT-TYPE
	SYNTAX	INTEGER {
		    noAction (1),
		    createProfile (2),
		    deleteProfile (3)
		}
	ACCESS	read-write
	STATUS	mandatory
	DESCRIPTION	""
	::= { mibipxsapFilterProfileEntry 2 }


	-- The mibipxsapFilterProfile__output_ipx_sap_filters table
	--
	-- This table contains parameters for the mibipxsapFilterProfile__output_ipx_sap_filters profile
	--

    mibipxsapFilterProfile-OutputIpxSapFiltersTable	OBJECT-TYPE
	SYNTAX		SEQUENCE OF MibipxsapFilterProfile-OutputIpxSapFiltersEntry
	ACCESS		not-accessible
	STATUS		mandatory
	DESCRIPTION	"A list of mibipxsapFilterProfile__output_ipx_sap_filters profile entries."
	::= { mibipxsapFilterProfile 2 }

    mibipxsapFilterProfile-OutputIpxSapFiltersEntry	OBJECT-TYPE
	SYNTAX		MibipxsapFilterProfile-OutputIpxSapFiltersEntry
	ACCESS		not-accessible
	STATUS		mandatory
	DESCRIPTION	"A mibipxsapFilterProfile__output_ipx_sap_filters entry containing objects that
			 maps to the parameters of mibipxsapFilterProfile__output_ipx_sap_filters profile."
	INDEX		{ ipxsapFilterProfile-OutputIpxSapFilters-IpxSapFilterName, ipxsapFilterProfile-OutputIpxSapFilters-Index-o }
	::= { mibipxsapFilterProfile-OutputIpxSapFiltersTable 1 }

    MibipxsapFilterProfile-OutputIpxSapFiltersEntry ::=
	SEQUENCE {
	    ipxsapFilterProfile-OutputIpxSapFilters-IpxSapFilterName
		DisplayString,
	    ipxsapFilterProfile-OutputIpxSapFilters-Index-o
		INTEGER,
	    ipxsapFilterProfile-OutputIpxSapFilters-ValidFilter
		INTEGER,
	    ipxsapFilterProfile-OutputIpxSapFilters-TypeFilter
		INTEGER,
	    ipxsapFilterProfile-OutputIpxSapFilters-ServerType
		DisplayString,
	    ipxsapFilterProfile-OutputIpxSapFilters-ServerName
		DisplayString
	}

    ipxsapFilterProfile-OutputIpxSapFilters-IpxSapFilterName	OBJECT-TYPE
	SYNTAX	DisplayString
	ACCESS	read-only
	STATUS	mandatory
	DESCRIPTION	""
	::= { mibipxsapFilterProfile-OutputIpxSapFiltersEntry 1 }

    ipxsapFilterProfile-OutputIpxSapFilters-Index-o	OBJECT-TYPE
	SYNTAX	INTEGER
	ACCESS	read-only
	STATUS	mandatory
	DESCRIPTION	""
	::= { mibipxsapFilterProfile-OutputIpxSapFiltersEntry 2 }

    ipxsapFilterProfile-OutputIpxSapFilters-ValidFilter	OBJECT-TYPE
	SYNTAX	INTEGER {
		    no (1),
		    yes (2)
		}
	ACCESS	read-write
	STATUS	mandatory
	DESCRIPTION	"When TRUE, this filter entry has been defined and properly initialized. When FALSE, this filter should be skipped when Filter Table is being applied to in/out SAP data."
	::= { mibipxsapFilterProfile-OutputIpxSapFiltersEntry 3 }

    ipxsapFilterProfile-OutputIpxSapFilters-TypeFilter	OBJECT-TYPE
	SYNTAX	INTEGER {
		    exclude (1),
		    include (2)
		}
	ACCESS	read-write
	STATUS	mandatory
	DESCRIPTION	"Filter may be used to EXCLUDE or, INCLUDE matching SAP fields."
	::= { mibipxsapFilterProfile-OutputIpxSapFiltersEntry 4 }

    ipxsapFilterProfile-OutputIpxSapFilters-ServerType	OBJECT-TYPE
	SYNTAX	DisplayString
	ACCESS	read-write
	STATUS	mandatory
	DESCRIPTION	"Defines the service number to be filtered in/out from SAP data."
	::= { mibipxsapFilterProfile-OutputIpxSapFiltersEntry 5 }

    ipxsapFilterProfile-OutputIpxSapFilters-ServerName	OBJECT-TYPE
	SYNTAX	DisplayString
	ACCESS	read-write
	STATUS	mandatory
	DESCRIPTION	"Defined the server name to be filtered, Wildcard (* and ?) characters are accepted for partial name matching."
	::= { mibipxsapFilterProfile-OutputIpxSapFiltersEntry 6 }


	-- The mibipxsapFilterProfile__input_ipx_sap_filters table
	--
	-- This table contains parameters for the mibipxsapFilterProfile__input_ipx_sap_filters profile
	--

    mibipxsapFilterProfile-InputIpxSapFiltersTable	OBJECT-TYPE
	SYNTAX		SEQUENCE OF MibipxsapFilterProfile-InputIpxSapFiltersEntry
	ACCESS		not-accessible
	STATUS		mandatory
	DESCRIPTION	"A list of mibipxsapFilterProfile__input_ipx_sap_filters profile entries."
	::= { mibipxsapFilterProfile 3 }

    mibipxsapFilterProfile-InputIpxSapFiltersEntry	OBJECT-TYPE
	SYNTAX		MibipxsapFilterProfile-InputIpxSapFiltersEntry
	ACCESS		not-accessible
	STATUS		mandatory
	DESCRIPTION	"A mibipxsapFilterProfile__input_ipx_sap_filters entry containing objects that
			 maps to the parameters of mibipxsapFilterProfile__input_ipx_sap_filters profile."
	INDEX		{ ipxsapFilterProfile-InputIpxSapFilters-IpxSapFilterName, ipxsapFilterProfile-InputIpxSapFilters-Index-o }
	::= { mibipxsapFilterProfile-InputIpxSapFiltersTable 1 }

    MibipxsapFilterProfile-InputIpxSapFiltersEntry ::=
	SEQUENCE {
	    ipxsapFilterProfile-InputIpxSapFilters-IpxSapFilterName
		DisplayString,
	    ipxsapFilterProfile-InputIpxSapFilters-Index-o
		INTEGER,
	    ipxsapFilterProfile-InputIpxSapFilters-ValidFilter
		INTEGER,
	    ipxsapFilterProfile-InputIpxSapFilters-TypeFilter
		INTEGER,
	    ipxsapFilterProfile-InputIpxSapFilters-ServerType
		DisplayString,
	    ipxsapFilterProfile-InputIpxSapFilters-ServerName
		DisplayString
	}

    ipxsapFilterProfile-InputIpxSapFilters-IpxSapFilterName	OBJECT-TYPE
	SYNTAX	DisplayString
	ACCESS	read-only
	STATUS	mandatory
	DESCRIPTION	""
	::= { mibipxsapFilterProfile-InputIpxSapFiltersEntry 1 }

    ipxsapFilterProfile-InputIpxSapFilters-Index-o	OBJECT-TYPE
	SYNTAX	INTEGER
	ACCESS	read-only
	STATUS	mandatory
	DESCRIPTION	""
	::= { mibipxsapFilterProfile-InputIpxSapFiltersEntry 2 }

    ipxsapFilterProfile-InputIpxSapFilters-ValidFilter	OBJECT-TYPE
	SYNTAX	INTEGER {
		    no (1),
		    yes (2)
		}
	ACCESS	read-write
	STATUS	mandatory
	DESCRIPTION	"When TRUE, this filter entry has been defined and properly initialized. When FALSE, this filter should be skipped when Filter Table is being applied to in/out SAP data."
	::= { mibipxsapFilterProfile-InputIpxSapFiltersEntry 3 }

    ipxsapFilterProfile-InputIpxSapFilters-TypeFilter	OBJECT-TYPE
	SYNTAX	INTEGER {
		    exclude (1),
		    include (2)
		}
	ACCESS	read-write
	STATUS	mandatory
	DESCRIPTION	"Filter may be used to EXCLUDE or, INCLUDE matching SAP fields."
	::= { mibipxsapFilterProfile-InputIpxSapFiltersEntry 4 }

    ipxsapFilterProfile-InputIpxSapFilters-ServerType	OBJECT-TYPE
	SYNTAX	DisplayString
	ACCESS	read-write
	STATUS	mandatory
	DESCRIPTION	"Defines the service number to be filtered in/out from SAP data."
	::= { mibipxsapFilterProfile-InputIpxSapFiltersEntry 5 }

    ipxsapFilterProfile-InputIpxSapFilters-ServerName	OBJECT-TYPE
	SYNTAX	DisplayString
	ACCESS	read-write
	STATUS	mandatory
	DESCRIPTION	"Defined the server name to be filtered, Wildcard (* and ?) characters are accepted for partial name matching."
	::= { mibipxsapFilterProfile-InputIpxSapFiltersEntry 6 }

END
