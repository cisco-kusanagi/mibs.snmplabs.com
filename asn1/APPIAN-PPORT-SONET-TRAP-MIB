--
--  Title:  Appian SONET Traps MIB
--
--  Dated:  03/04/2k
--  Author: D. Theriault
--
--  Description:
--
--  This MIB file contains the SONET trap definitions for the Appian
--  Optical Services Access Platform(s).
--
--
APPIAN-PPORT-SONET-TRAP-MIB DEFINITIONS ::= BEGIN

IMPORTS

    acChassisCurrentTime, acChassisRingId           FROM APPIAN-CHASSIS-MIB

    acSonet, 
    acSonetPort, 
    acSonetSection, 
    acSonetLine, 
    acSonetFarEndLine, 
    acSonetPath, 
    acSonetFarEndPath, 
    acSonetVT, 
    acSonetFarEndVT,
    
    acSonetPortNodeId, 
    acSonetPortSlot, 
    acSonetPortPort, 
    
    acSonetSectionTIMNodeId, 
    acSonetSectionTIMSlot, 
    acSonetSectionTIMPort,
    
    acSonetSection15MinuteIntervalNodeId,
    acSonetSection15MinuteIntervalSlot, 
    acSonetSection15MinuteIntervalPort, 
    acSonetSection15MinuteIntervalNumber, 
    
    acSonetSectionDayIntervalNodeId,
    acSonetSectionDayIntervalSlot, 
    acSonetSectionDayIntervalPort, 
    acSonetSectionDayIntervalNumber, 
    
    acSonetLine15MinuteIntervalNodeId,
    acSonetLine15MinuteIntervalSlot,
    acSonetLine15MinuteIntervalPort,    
    acSonetLine15MinuteIntervalNumber,    
    
    acSonetLineDayIntervalNodeId,
    acSonetLineDayIntervalSlot,
    acSonetLineDayIntervalPort,    
    acSonetLineDayIntervalNumber,    
    
    acSonetFarEndLine15MinuteIntervalNodeId,
    acSonetFarEndLine15MinuteIntervalSlot,
    acSonetFarEndLine15MinuteIntervalPort,
    acSonetFarEndLine15MinuteIntervalNumber,
        
    acSonetFarEndLineDayIntervalNodeId,
    acSonetFarEndLineDayIntervalSlot,
    acSonetFarEndLineDayIntervalPort,
    acSonetFarEndLineDayIntervalNumber,
        
    acSonetLineProtectionNodeId, 
    acSonetLineProtectionSlot,
    acSonetLineProtectionPort,
    
    acSonetPath15MinuteIntervalNodeId,
    acSonetPath15MinuteIntervalSlot,
    acSonetPath15MinuteIntervalPort,
    acSonetPath15MinuteIntervalPath,
    acSonetPath15MinuteIntervalNumber,
    
    acSonetPathDayIntervalNodeId,
    acSonetPathDayIntervalSlot,
    acSonetPathDayIntervalPort,
    acSonetPathDayIntervalPath,
    acSonetPathDayIntervalNumber,

    acSonetPathTIMNodeId,
    acSonetPathTIMSlot,
    acSonetPathTIMPort,
    acSonetPathTIMPath,

    acSonetPathPLMNodeId,
    acSonetPathPLMSlot,
    acSonetPathPLMPort,
    acSonetPathPLMPath,

    acSonetFarEndPath15MinuteIntervalNodeId,
    acSonetFarEndPath15MinuteIntervalSlot,
    acSonetFarEndPath15MinuteIntervalPort,
    acSonetFarEndPath15MinuteIntervalPath,
    acSonetFarEndPath15MinuteIntervalNumber,

    acSonetFarEndPathDayIntervalNodeId,
    acSonetFarEndPathDayIntervalSlot,
    acSonetFarEndPathDayIntervalPort,
    acSonetFarEndPathDayIntervalPath,
    acSonetFarEndPathDayIntervalNumber,

    acSonetVT15MinuteIntervalNodeId,
    acSonetVT15MinuteIntervalSlot,
    acSonetVT15MinuteIntervalPort,        
    acSonetVT15MinuteIntervalVT,
    acSonetVT15MinuteIntervalNumber,
    
    acSonetVTDayIntervalNodeId,
    acSonetVTDayIntervalSlot,
    acSonetVTDayIntervalPort,        
    acSonetVTDayIntervalVT,
    acSonetVTDayIntervalNumber,
    
    acSonetFarEndVT15MinuteIntervalNodeId,
    acSonetFarEndVT15MinuteIntervalSlot,
    acSonetFarEndVT15MinuteIntervalPort,        
    acSonetFarEndVT15MinuteIntervalVT,        
    acSonetFarEndVT15MinuteIntervalNumber,  

    acSonetPathProtectionNodeId,
    acSonetPathProtectionSlot, 
    acSonetPathProtectionPort,
    acSonetPathProtectionPath,

    acSonetVTProtectionNodeId,
    acSonetVTProtectionSlot,  
    acSonetVTProtectionPort,
    acSonetVTProtectionVT,

    acSonetFarEndVTDayIntervalNodeId,
    acSonetFarEndVTDayIntervalSlot,
    acSonetFarEndVTDayIntervalPort,        
    acSonetFarEndVTDayIntervalVT,
    acSonetFarEndVTDayIntervalNumber                    FROM APPIAN-PPORT-SONET-MIB
    MODULE-IDENTITY, NOTIFICATION-TYPE                  FROM SNMPv2-SMI;
    

acSonetTraps MODULE-IDENTITY

    LAST-UPDATED                "0003041600Z"
    ORGANIZATION                "Appian Communications, Inc."
    CONTACT-INFO                "Douglas Stahl"
    DESCRIPTION                 "The MIB module to describe SONET/SDH Traps."

    REVISION                    "0003041600Z"
    DESCRIPTION                 "Engineering draft, not for release."

    ::= { acSonet 4 }

-- =============================================================================    
--
-- SONET Port Traps
--
-- =============================================================================
    
acSonetPortTraps  OBJECT IDENTIFIER ::= { acSonetPort 0 }

acSonetPortFacilityLoopbackActiveTrap  NOTIFICATION-TYPE
    OBJECTS { 
        acChassisCurrentTime, acChassisRingId, 
        acSonetPortNodeId, 
        acSonetPortSlot, 
        acSonetPortPort
        }
    STATUS  current
    DESCRIPTION
    "The SONET physical interface has entered a loopback mode where the 
     received optical data is sent out the optical transmitter."
    
    ::= { acSonetPortTraps 1 }
acSonetPortFacilityLoopbackClearTrap  NOTIFICATION-TYPE
    OBJECTS { 
        acChassisCurrentTime, acChassisRingId, 
        acSonetPortNodeId, 
        acSonetPortSlot, 
        acSonetPortPort
        }
    STATUS  current
    DESCRIPTION
    "The SONET physical interface has disabled a loopback mode and is 
     now transmitting and receiving optical data normally."
    
    ::= { acSonetPortTraps 2 }

acSonetPortSectionDCCFailureAlarmTrap NOTIFICATION-TYPE
    OBJECTS { 
        acChassisCurrentTime, acChassisRingId, 
        acSonetPortNodeId, 
        acSonetPortSlot, 
        acSonetPortPort
        }
    STATUS  current
    DESCRIPTION
    "Section DCC for this SONET port has failed."
    
    ::= { acSonetPortTraps 3 }

acSonetPortSectionDCCFailureClearTrap NOTIFICATION-TYPE
    OBJECTS { 
        acChassisCurrentTime, acChassisRingId, 
        acSonetPortNodeId, 
        acSonetPortSlot, 
        acSonetPortPort
        }
    STATUS  current
    DESCRIPTION
    "Section DCC for this SONET port has recovered."
    
    ::= { acSonetPortTraps 4 }

acSonetPortLineDCCFailureAlarmTrap NOTIFICATION-TYPE
    OBJECTS { 
        acChassisCurrentTime, acChassisRingId, 
        acSonetPortNodeId, 
        acSonetPortSlot, 
        acSonetPortPort
        }
    STATUS  current
    DESCRIPTION
    "Line DCC for this SONET port has failed."
    
    ::= { acSonetPortTraps 5 }

acSonetPortLineDCCFailureClearTrap NOTIFICATION-TYPE
    OBJECTS { 
        acChassisCurrentTime, acChassisRingId, 
        acSonetPortNodeId, 
        acSonetPortSlot, 
        acSonetPortPort
        }
    STATUS  current
    DESCRIPTION
    "Line DCC for this SONET port has recovered."
    
    ::= { acSonetPortTraps 6 }

acSonetPortAppianDCCFailureAlarmTrap NOTIFICATION-TYPE
    OBJECTS { 
        acChassisCurrentTime, acChassisRingId, 
        acSonetPortNodeId, 
        acSonetPortSlot, 
        acSonetPortPort
        }
    STATUS  current
    DESCRIPTION
    "Appian DCC for this SONET port has failed."
    
    ::= { acSonetPortTraps 7 }

acSonetPortAppianDCCFailureClearTrap NOTIFICATION-TYPE
    OBJECTS { 
        acChassisCurrentTime, acChassisRingId, 
        acSonetPortNodeId, 
        acSonetPortSlot, 
        acSonetPortPort
        }
    STATUS  current
    DESCRIPTION
    "Appian DCC for this SONET port has recovered."
    
    ::= { acSonetPortTraps 8 }

-- =============================================================================    
--
-- SONET Section Traps
-- 
-- =============================================================================
    
acSonetSectionTraps  OBJECT IDENTIFIER ::= { acSonetSection 0 }

acSonetSectionLOSAlarmTrap NOTIFICATION-TYPE
    OBJECTS { 
        acChassisCurrentTime, acChassisRingId,
        acSonetSection15MinuteIntervalNodeId,
        acSonetSection15MinuteIntervalSlot,
        acSonetSection15MinuteIntervalPort,
        acSonetSection15MinuteIntervalNumber
        }
    STATUS  current
    DESCRIPTION
    "Loss of signal failure."
    
    ::= { acSonetSectionTraps 1 }

acSonetSectionLOSClearTrap NOTIFICATION-TYPE
    OBJECTS { 
        acChassisCurrentTime, acChassisRingId,
        acSonetSection15MinuteIntervalNodeId,
        acSonetSection15MinuteIntervalSlot,
        acSonetSection15MinuteIntervalPort,
        acSonetSection15MinuteIntervalNumber
        }
    STATUS  current
    DESCRIPTION
    "Loss of signal recovered."
    
    ::= { acSonetSectionTraps 2 }

acSonetSectionLOFAlarmTrap NOTIFICATION-TYPE
    OBJECTS { 
        acChassisCurrentTime, acChassisRingId, 
        acSonetSection15MinuteIntervalNodeId,
        acSonetSection15MinuteIntervalSlot,
        acSonetSection15MinuteIntervalPort,
        acSonetSection15MinuteIntervalNumber
        }
    STATUS  current
    DESCRIPTION
    "Loss of frame failure at section level."
    
    ::= { acSonetSectionTraps 3 }

acSonetSectionLOFClearTrap NOTIFICATION-TYPE
    OBJECTS { 
        acChassisCurrentTime, acChassisRingId, 
        acSonetSection15MinuteIntervalNodeId,
        acSonetSection15MinuteIntervalSlot,
        acSonetSection15MinuteIntervalPort,
        acSonetSection15MinuteIntervalNumber
        }
    STATUS  current
    DESCRIPTION
    "Loss of frame at section level recovered."
    
    ::= { acSonetSectionTraps 4 }

acSonetSectionTraceAlarmTrap NOTIFICATION-TYPE
    OBJECTS { 
        acChassisCurrentTime, acChassisRingId, 
        acSonetSectionTIMNodeId,
        acSonetSectionTIMSlot,
        acSonetSectionTIMPort
        }
    STATUS  current
    DESCRIPTION
    "The section trace identifier received for the SONET interface was
    unexpected."
    
    ::= { acSonetSectionTraps 5 }
    
acSonetSectionTraceClearTrap NOTIFICATION-TYPE
    OBJECTS { 
        acChassisCurrentTime, acChassisRingId, 
        acSonetSectionTIMNodeId,
        acSonetSectionTIMSlot,
        acSonetSectionTIMPort
        }
    STATUS  current
    DESCRIPTION
    "The section trace identifier mismatch condition for the SONET interface has
    recovered."
    
    ::= { acSonetSectionTraps 6 }

acSonetSection15MinuteESAlarmTrap NOTIFICATION-TYPE
    OBJECTS { 
        acChassisCurrentTime, acChassisRingId, 
        acSonetSection15MinuteIntervalNodeId,
        acSonetSection15MinuteIntervalSlot,
        acSonetSection15MinuteIntervalPort,
        acSonetSection15MinuteIntervalNumber
        }
    STATUS  current
    DESCRIPTION
    "Errored seconds for the section have exceeded the threshold for 
     the current 15 minute interval."
    
    ::= { acSonetSectionTraps 7 }

acSonetSection15MinuteESClearTrap NOTIFICATION-TYPE
    OBJECTS { 
        acChassisCurrentTime, acChassisRingId, 
        acSonetSection15MinuteIntervalNodeId,
        acSonetSection15MinuteIntervalSlot,
        acSonetSection15MinuteIntervalPort,
        acSonetSection15MinuteIntervalNumber
        }
    STATUS  current
    DESCRIPTION
    "Errored seconds for the section have recovered for the current 
     15 minute interval."
    
    ::= { acSonetSectionTraps 8 }

acSonetSection15MinuteSESAlarmTrap NOTIFICATION-TYPE
    OBJECTS { 
        acChassisCurrentTime, acChassisRingId, 
        acSonetSection15MinuteIntervalNodeId,
        acSonetSection15MinuteIntervalSlot,
        acSonetSection15MinuteIntervalPort,
        acSonetSection15MinuteIntervalNumber
        }
    STATUS  current
    DESCRIPTION
    "Severly errored seconds for the section have exceeded the 
     threshold for the current 15 minute interval."
    
    ::= { acSonetSectionTraps 9 }

acSonetSection15MinuteSESClearTrap NOTIFICATION-TYPE
    OBJECTS { 
        acChassisCurrentTime, acChassisRingId, 
        acSonetSection15MinuteIntervalNodeId,
        acSonetSection15MinuteIntervalSlot,
        acSonetSection15MinuteIntervalPort,
        acSonetSection15MinuteIntervalNumber
        }
    STATUS  current
    DESCRIPTION
    "Severely errored seconds for the section have recovered for the 
     current 15 minute interval."
    
    ::= { acSonetSectionTraps 10 }

acSonetSection15MinuteSEFAlarmTrap NOTIFICATION-TYPE
    OBJECTS { 
        acChassisCurrentTime, acChassisRingId, 
        acSonetSection15MinuteIntervalNodeId,
        acSonetSection15MinuteIntervalSlot,
        acSonetSection15MinuteIntervalPort,
        acSonetSection15MinuteIntervalNumber
        }
    STATUS  current
    DESCRIPTION
    "Severely errored frames for the section have exceeded the 
     threshold for the current 15 minute interval."
    
    ::= { acSonetSectionTraps 11 }

acSonetSection15MinuteSEFClearTrap NOTIFICATION-TYPE
    OBJECTS { 
        acChassisCurrentTime, acChassisRingId, 
        acSonetSection15MinuteIntervalNodeId,
        acSonetSection15MinuteIntervalSlot,
        acSonetSection15MinuteIntervalPort,
        acSonetSection15MinuteIntervalNumber
        }
    STATUS  current
    DESCRIPTION
    "Severely errored frames for the section have recovered for the 
     current 15 minute interval."
    
    ::= { acSonetSectionTraps 12 }

acSonetSection15MinuteCVAlarmTrap NOTIFICATION-TYPE
    OBJECTS { 
        acChassisCurrentTime, acChassisRingId, 
        acSonetSection15MinuteIntervalNodeId,
        acSonetSection15MinuteIntervalSlot,
        acSonetSection15MinuteIntervalPort,
        acSonetSection15MinuteIntervalNumber
        }
    STATUS  current
    DESCRIPTION
    "Coding violations, or BIP errors, for the section have exceeded 
     the threshold for the current 15 minute interval."
    
    ::= { acSonetSectionTraps 13 }

acSonetSection15MinuteCVClearTrap NOTIFICATION-TYPE
    OBJECTS { 
        acChassisCurrentTime, acChassisRingId, 
        acSonetSection15MinuteIntervalNodeId,
        acSonetSection15MinuteIntervalSlot,
        acSonetSection15MinuteIntervalPort,
        acSonetSection15MinuteIntervalNumber
        }
    STATUS  current
    DESCRIPTION
    "Coding violations, or BIP errors, for the section have recovered 
     for the current 15 minute interval."
    
    ::= { acSonetSectionTraps 14 }

acSonetSectionDayESAlarmTrap NOTIFICATION-TYPE
    OBJECTS { 
        acChassisCurrentTime, acChassisRingId, 
        acSonetSectionDayIntervalNodeId,
        acSonetSectionDayIntervalSlot,
        acSonetSectionDayIntervalPort,
        acSonetSectionDayIntervalNumber
        }
    STATUS  current
    DESCRIPTION
    "Errored seconds for the section have exceeded the threshold for the 
     current day interval."
    
    ::= { acSonetSectionTraps 15 }

acSonetSectionDayESClearTrap NOTIFICATION-TYPE
    OBJECTS { 
        acChassisCurrentTime, acChassisRingId, 
        acSonetSectionDayIntervalNodeId,
        acSonetSectionDayIntervalSlot,
        acSonetSectionDayIntervalPort,
        acSonetSectionDayIntervalNumber
        }
    STATUS  current
    DESCRIPTION
    "Errored seconds for the section have recovered for the current day 
     interval."
    
    ::= { acSonetSectionTraps 16 }

acSonetSectionDaySESAlarmTrap NOTIFICATION-TYPE
    OBJECTS { 
        acChassisCurrentTime, acChassisRingId, 
        acSonetSectionDayIntervalNodeId,
        acSonetSectionDayIntervalSlot,
        acSonetSectionDayIntervalPort,
        acSonetSectionDayIntervalNumber
        }
    STATUS  current
    DESCRIPTION
    "Severely errored seconds for the section have exceeded the 
     threshold for the current day interval."
    
    ::= { acSonetSectionTraps 17 }

acSonetSectionDaySESClearTrap NOTIFICATION-TYPE
    OBJECTS { 
        acChassisCurrentTime, acChassisRingId, 
        acSonetSectionDayIntervalNodeId,
        acSonetSectionDayIntervalSlot,
        acSonetSectionDayIntervalPort,
        acSonetSectionDayIntervalNumber
        }
    STATUS  current
    DESCRIPTION
    "Severely errored seconds for the section have recovered for the 
     current day interval."
    
    ::= { acSonetSectionTraps 18 }

acSonetSectionDaySEFAlarmTrap NOTIFICATION-TYPE
    OBJECTS { 
        acChassisCurrentTime, acChassisRingId, 
        acSonetSectionDayIntervalNodeId,
        acSonetSectionDayIntervalSlot,
        acSonetSectionDayIntervalPort,
        acSonetSectionDayIntervalNumber
        }
    STATUS  current
    DESCRIPTION
    "Severely errored frames for the section have exceeded the threshold 
     for the current day interval."
    
    ::= { acSonetSectionTraps 19 }

acSonetSectionDaySEFClearTrap NOTIFICATION-TYPE
    OBJECTS { 
        acChassisCurrentTime, acChassisRingId, 
        acSonetSectionDayIntervalNodeId,
        acSonetSectionDayIntervalSlot,
        acSonetSectionDayIntervalPort,
        acSonetSectionDayIntervalNumber
        }
    STATUS  current
    DESCRIPTION
    "Severely errored frames for the section have recovered for the 
     current day interval."
    
    ::= { acSonetSectionTraps 20 }

acSonetSectionDayCVAlarmTrap NOTIFICATION-TYPE
    OBJECTS { 
        acChassisCurrentTime, acChassisRingId, 
        acSonetSectionDayIntervalNodeId,
        acSonetSectionDayIntervalSlot,
        acSonetSectionDayIntervalPort,
        acSonetSectionDayIntervalNumber
        }
    STATUS  current
    DESCRIPTION
    "Coding violations, or BIP errors, for the section have exceeded 
     the threshold for the current day interval."
    
    ::= { acSonetSectionTraps 21 }

acSonetSectionDayCVClearTrap NOTIFICATION-TYPE
    OBJECTS { 
        acChassisCurrentTime, acChassisRingId, 
        acSonetSectionDayIntervalNodeId,
        acSonetSectionDayIntervalSlot,
        acSonetSectionDayIntervalPort,
        acSonetSectionDayIntervalNumber
        }
    STATUS  current
    DESCRIPTION
    "Coding violations, or BIP errors, for the section have recovered 
     for the current day interval."
    
    ::= { acSonetSectionTraps 22 }

-- =============================================================================    
--
-- SONET Line Traps
-- 
-- =============================================================================    

acSonetLineTraps  OBJECT IDENTIFIER ::= { acSonetLine 0 }

acSonetLineAISAlarmTrap NOTIFICATION-TYPE
    OBJECTS { 
        acChassisCurrentTime, acChassisRingId, 
        acSonetLine15MinuteIntervalNodeId,
        acSonetLine15MinuteIntervalSlot,
        acSonetLine15MinuteIntervalPort,
        acSonetLine15MinuteIntervalNumber
        }
    STATUS  current
    DESCRIPTION
    "AIS detected at line level."
    
    ::= { acSonetLineTraps 1 }
    
acSonetLineAISClearTrap NOTIFICATION-TYPE
    OBJECTS { 
        acChassisCurrentTime, acChassisRingId, 
        acSonetLine15MinuteIntervalNodeId,
        acSonetLine15MinuteIntervalSlot,
        acSonetLine15MinuteIntervalPort,
        acSonetLine15MinuteIntervalNumber
        }
    STATUS  current
    DESCRIPTION
    "AIS cleared at line level."
    
    ::= { acSonetLineTraps 2 }
    
acSonetLineRDIAlarmTrap NOTIFICATION-TYPE
    OBJECTS { 
        acChassisCurrentTime, acChassisRingId, 
        acSonetLine15MinuteIntervalNodeId,
        acSonetLine15MinuteIntervalSlot,
        acSonetLine15MinuteIntervalPort,
        acSonetLine15MinuteIntervalNumber
        }
    STATUS  current
    DESCRIPTION
    "RDI detected at line level."
    
    ::= { acSonetLineTraps 3 }
    
acSonetLineRDIClearTrap NOTIFICATION-TYPE
    OBJECTS { 
        acChassisCurrentTime, acChassisRingId, 
        acSonetLine15MinuteIntervalNodeId,
        acSonetLine15MinuteIntervalSlot,
        acSonetLine15MinuteIntervalPort,
        acSonetLine15MinuteIntervalNumber
        }
    STATUS  current
    DESCRIPTION
    "RDI cleared at line level."
    
    ::= { acSonetLineTraps 4 }
    
acSonetLine15MinuteESAlarmTrap NOTIFICATION-TYPE
    OBJECTS { 
        acChassisCurrentTime, acChassisRingId, 
        acSonetLine15MinuteIntervalNodeId,
        acSonetLine15MinuteIntervalSlot,
        acSonetLine15MinuteIntervalPort,
        acSonetLine15MinuteIntervalNumber
        }
    STATUS  current
    DESCRIPTION
    "Errored seconds for the line have exceeded the threshold for the
     current 15 minute interval."
    
    ::= { acSonetLineTraps 5 }
    
acSonetLine15MinuteESClearTrap NOTIFICATION-TYPE
    OBJECTS { 
        acChassisCurrentTime, acChassisRingId, 
        acSonetLine15MinuteIntervalNodeId,
        acSonetLine15MinuteIntervalSlot,
        acSonetLine15MinuteIntervalPort,
        acSonetLine15MinuteIntervalNumber
        }
    STATUS  current
    DESCRIPTION
    "Errored seconds for the line have recovered for the current
     15 minute interval."
    
    ::= { acSonetLineTraps 6 }
    
acSonetLine15MinuteSESAlarmTrap NOTIFICATION-TYPE
    OBJECTS { 
        acChassisCurrentTime, acChassisRingId, 
        acSonetLine15MinuteIntervalNodeId,
        acSonetLine15MinuteIntervalSlot,
        acSonetLine15MinuteIntervalPort,
        acSonetLine15MinuteIntervalNumber
        }
    STATUS  current
    DESCRIPTION
    "Severely errored seconds for the line have exceeded the threshold 
     for the current 15 minute interval."
    
    ::= { acSonetLineTraps 7 }
    
acSonetLine15MinuteSESClearTrap NOTIFICATION-TYPE
    OBJECTS { 
        acChassisCurrentTime, acChassisRingId, 
        acSonetLine15MinuteIntervalNodeId,
        acSonetLine15MinuteIntervalSlot,
        acSonetLine15MinuteIntervalPort,
        acSonetLine15MinuteIntervalNumber
        }
    STATUS  current
    DESCRIPTION
    "Severely errored seconds for the line have recovered for the current
     15 minute interval."
    
    ::= { acSonetLineTraps 8 }
    
acSonetLine15MinuteCVAlarmTrap NOTIFICATION-TYPE
    OBJECTS { 
        acChassisCurrentTime, acChassisRingId, 
        acSonetLine15MinuteIntervalNodeId,
        acSonetLine15MinuteIntervalSlot,
        acSonetLine15MinuteIntervalPort,
        acSonetLine15MinuteIntervalNumber
        }
    STATUS  current
    DESCRIPTION
    "BIP errors for the line have exceeded the threshold for the 
     current 15 minute interval."
    
    ::= { acSonetLineTraps 9 }
    
acSonetLine15MinuteCVClearTrap NOTIFICATION-TYPE
    OBJECTS { 
        acChassisCurrentTime, acChassisRingId, 
        acSonetLine15MinuteIntervalNodeId,
        acSonetLine15MinuteIntervalSlot,
        acSonetLine15MinuteIntervalPort,
        acSonetLine15MinuteIntervalNumber
        }
    STATUS  current
    DESCRIPTION
    "BIP errors for the line have recovered for the current 15 minute 
     interval."
    
    ::= { acSonetLineTraps 10 }
    
acSonetLine15MinuteUASAlarmTrap NOTIFICATION-TYPE
    OBJECTS { 
        acChassisCurrentTime, acChassisRingId, 
        acSonetLine15MinuteIntervalNodeId,
        acSonetLine15MinuteIntervalSlot,
        acSonetLine15MinuteIntervalPort,
        acSonetLine15MinuteIntervalNumber
        }
    STATUS  current
    DESCRIPTION
    "Unavailable seconds for the line have exceeded the threshold for 
     the current 15 minute interval."
    
    ::= { acSonetLineTraps 11 }
    
acSonetLine15MinuteUASClearTrap NOTIFICATION-TYPE
    OBJECTS { 
        acChassisCurrentTime, acChassisRingId, 
        acSonetLine15MinuteIntervalNodeId,
        acSonetLine15MinuteIntervalSlot,
        acSonetLine15MinuteIntervalPort,
        acSonetLine15MinuteIntervalNumber
        }
    STATUS  current
    DESCRIPTION
    "Unavailable seconds for the line have recovered for the current 15 
     minute interval."
    
    ::= { acSonetLineTraps 12 }
    
acSonetLineDayESAlarmTrap NOTIFICATION-TYPE
    OBJECTS { 
        acChassisCurrentTime, acChassisRingId, 
        acSonetLineDayIntervalNodeId,
        acSonetLineDayIntervalSlot,
        acSonetLineDayIntervalPort,
        acSonetLineDayIntervalNumber
        }
    STATUS  current
    DESCRIPTION
    "Errored seconds for the line have exceeded the threshold for the
     current 15 minute interval."
    
    ::= { acSonetLineTraps 13 }
    
acSonetLineDayESClearTrap NOTIFICATION-TYPE
    OBJECTS { 
        acChassisCurrentTime, acChassisRingId, 
        acSonetLineDayIntervalNodeId,
        acSonetLineDayIntervalSlot,
        acSonetLineDayIntervalPort,
        acSonetLineDayIntervalNumber
        }
    STATUS  current
    DESCRIPTION
    "Errored seconds for the line have recovered for the current
     day interval."
    
    ::= { acSonetLineTraps 14 }
    
acSonetLineDaySESAlarmTrap NOTIFICATION-TYPE
    OBJECTS { 
        acChassisCurrentTime, acChassisRingId, 
        acSonetLineDayIntervalNodeId,
        acSonetLineDayIntervalSlot,
        acSonetLineDayIntervalPort,
        acSonetLineDayIntervalNumber
        }
    STATUS  current
    DESCRIPTION
    "Severely errored seconds for the line have exceeded the threshold 
     for the current day interval."
    
    ::= { acSonetLineTraps 15 }
    
acSonetLineDaySESClearTrap NOTIFICATION-TYPE
    OBJECTS { 
        acChassisCurrentTime, acChassisRingId, 
        acSonetLineDayIntervalNodeId,
        acSonetLineDayIntervalSlot,
        acSonetLineDayIntervalPort,
        acSonetLineDayIntervalNumber
        }
    STATUS  current
    DESCRIPTION
    "Severely errored seconds for the line have recovered for the current
     day interval."
    
    ::= { acSonetLineTraps 16 }
    
acSonetLineDayCVAlarmTrap NOTIFICATION-TYPE
    OBJECTS { 
        acChassisCurrentTime, acChassisRingId, 
        acSonetLineDayIntervalNodeId,
        acSonetLineDayIntervalSlot,
        acSonetLineDayIntervalPort,
        acSonetLineDayIntervalNumber
        }
    STATUS  current
    DESCRIPTION
    "BIP errors for the line have exceeded the threshold for the 
     current day interval."
    
    ::= { acSonetLineTraps 17 }
    
acSonetLineDayCVClearTrap NOTIFICATION-TYPE
    OBJECTS { 
        acChassisCurrentTime, acChassisRingId, 
        acSonetLineDayIntervalNodeId,
        acSonetLineDayIntervalSlot,
        acSonetLineDayIntervalPort,
        acSonetLineDayIntervalNumber
        }
    STATUS  current
    DESCRIPTION
    "BIP errors for the line have recovered for the current day 
     interval."
    
    ::= { acSonetLineTraps 18 }
    
acSonetLineDayUASAlarmTrap NOTIFICATION-TYPE
    OBJECTS { 
        acChassisCurrentTime, acChassisRingId, 
        acSonetLineDayIntervalNodeId,
        acSonetLineDayIntervalSlot,
        acSonetLineDayIntervalPort,
        acSonetLineDayIntervalNumber
        }
    STATUS  current
    DESCRIPTION
    "Unavailable seconds for the line have exceeded the threshold for 
     the current day interval."
    
    ::= { acSonetLineTraps 19 }
    
acSonetLineDayUASClearTrap NOTIFICATION-TYPE
    OBJECTS { 
        acChassisCurrentTime, acChassisRingId, 
        acSonetLineDayIntervalNodeId,
        acSonetLineDayIntervalSlot,
        acSonetLineDayIntervalPort,
        acSonetLineDayIntervalNumber
        }
    STATUS  current
    DESCRIPTION
    "Unavailable seconds for the line have recovered for the current 15 
     minute interval."
    
    ::= { acSonetLineTraps 20 }
    
-- =============================================================================    
--
-- SONET FarEndLineTraps
-- 
-- =============================================================================

acSonetFarEndLineTraps  OBJECT IDENTIFIER ::= { acSonetFarEndLine 0 }

acSonetFarEndLine15MinuteESAlarmTrap NOTIFICATION-TYPE
    OBJECTS { 
        acChassisCurrentTime, acChassisRingId, 
        acSonetFarEndLine15MinuteIntervalNodeId,
        acSonetFarEndLine15MinuteIntervalSlot,
        acSonetFarEndLine15MinuteIntervalPort,
        acSonetFarEndLine15MinuteIntervalNumber
        }
    STATUS  current
    DESCRIPTION
    "Errored seconds for the far end line have exceeded the threshold for the
     current 15 minute interval."
    
    ::= { acSonetFarEndLineTraps 1 }
    
acSonetFarEndLine15MinuteESClearTrap NOTIFICATION-TYPE
    OBJECTS { 
        acChassisCurrentTime, acChassisRingId, 
        acSonetFarEndLine15MinuteIntervalNodeId,
        acSonetFarEndLine15MinuteIntervalSlot,
        acSonetFarEndLine15MinuteIntervalPort,
        acSonetFarEndLine15MinuteIntervalNumber
        }
    STATUS  current
    DESCRIPTION
    "Errored seconds for the far end line have recovered for the current
     15 minute interval."
    
    ::= { acSonetFarEndLineTraps 2 }
    
acSonetFarEndLine15MinuteSESAlarmTrap NOTIFICATION-TYPE
    OBJECTS { 
        acChassisCurrentTime, acChassisRingId, 
        acSonetFarEndLine15MinuteIntervalNodeId,
        acSonetFarEndLine15MinuteIntervalSlot,
        acSonetFarEndLine15MinuteIntervalPort,
        acSonetFarEndLine15MinuteIntervalNumber
        }
    STATUS  current
    DESCRIPTION
    "Severely errored seconds for the far end line have exceeded the 
     threshold for the current 15 minute interval."
    
    ::= { acSonetFarEndLineTraps 3 }
    
acSonetFarEndLine15MinuteSESClearTrap NOTIFICATION-TYPE
    OBJECTS { 
        acChassisCurrentTime, acChassisRingId, 
        acSonetFarEndLine15MinuteIntervalNodeId,
        acSonetFarEndLine15MinuteIntervalSlot,
        acSonetFarEndLine15MinuteIntervalPort,
        acSonetFarEndLine15MinuteIntervalNumber
        }
    STATUS  current
    DESCRIPTION
    "Severely errored seconds for the far end line have recovered for 
     the current 15 minute interval."
    
    ::= { acSonetFarEndLineTraps 4 }
    
acSonetFarEndLine15MinuteCVAlarmTrap NOTIFICATION-TYPE
    OBJECTS { 
        acChassisCurrentTime, acChassisRingId, 
        acSonetFarEndLine15MinuteIntervalNodeId,
        acSonetFarEndLine15MinuteIntervalSlot,
        acSonetFarEndLine15MinuteIntervalPort,
        acSonetFarEndLine15MinuteIntervalNumber
        }
    STATUS  current
    DESCRIPTION
    "Coding violations for the far end line have exceeded the threshold 
     for the current 15 minute interval."
    
    ::= { acSonetFarEndLineTraps 5 }
    
acSonetFarEndLine15MinuteCVClearTrap NOTIFICATION-TYPE
    OBJECTS { 
        acChassisCurrentTime, acChassisRingId, 
        acSonetFarEndLine15MinuteIntervalNodeId,
        acSonetFarEndLine15MinuteIntervalSlot,
        acSonetFarEndLine15MinuteIntervalPort,
        acSonetFarEndLine15MinuteIntervalNumber
        }
    STATUS  current
    DESCRIPTION
    "Coding violations for the far end line have recovered for the 
     current 15 minute interval."
    
    ::= { acSonetFarEndLineTraps 6 }
    
acSonetFarEndLine15MinuteUASAlarmTrap NOTIFICATION-TYPE
    OBJECTS { 
        acChassisCurrentTime, acChassisRingId, 
        acSonetFarEndLine15MinuteIntervalNodeId,
        acSonetFarEndLine15MinuteIntervalSlot,
        acSonetFarEndLine15MinuteIntervalPort,
        acSonetFarEndLine15MinuteIntervalNumber
        }
    STATUS  current
    DESCRIPTION
    "Unavailable seconds for the far end line have exceeded the threshold 
     for the current 15 minute interval."
    
    ::= { acSonetFarEndLineTraps 7 }
    
acSonetFarEndLine15MinuteUASClearTrap NOTIFICATION-TYPE
    OBJECTS { 
        acChassisCurrentTime, acChassisRingId, 
        acSonetFarEndLine15MinuteIntervalNodeId,
        acSonetFarEndLine15MinuteIntervalSlot,
        acSonetFarEndLine15MinuteIntervalPort,
        acSonetFarEndLine15MinuteIntervalNumber
        }
    STATUS  current
    DESCRIPTION
    "Unavailable seconds for the far end line have recovered for the 
     current 15 minute interval."
    
    ::= { acSonetFarEndLineTraps 8 }
    
acSonetFarEndLineDayESAlarmTrap NOTIFICATION-TYPE
    OBJECTS { 
        acChassisCurrentTime, acChassisRingId, 
        acSonetFarEndLine15MinuteIntervalNodeId,
        acSonetFarEndLine15MinuteIntervalSlot,
        acSonetFarEndLine15MinuteIntervalPort,
        acSonetFarEndLine15MinuteIntervalNumber
        }
    STATUS  current
    DESCRIPTION
    "Errored seconds for the far end line have exceeded the threshold for the
     current day interval."
    
    ::= { acSonetFarEndLineTraps 9 }
    
acSonetFarEndLineDayESClearTrap NOTIFICATION-TYPE
    OBJECTS { 
        acChassisCurrentTime, acChassisRingId, 
        acSonetFarEndLineDayIntervalNodeId,
        acSonetFarEndLineDayIntervalSlot,
        acSonetFarEndLineDayIntervalPort,
        acSonetFarEndLineDayIntervalNumber
        }
    STATUS  current
    DESCRIPTION
    "Errored seconds for the far end line have recovered for the current
     day interval."
    
    ::= { acSonetFarEndLineTraps 10 }
    
acSonetFarEndLineDaySESAlarmTrap NOTIFICATION-TYPE
    OBJECTS { 
        acChassisCurrentTime, acChassisRingId, 
        acSonetFarEndLineDayIntervalNodeId,
        acSonetFarEndLineDayIntervalSlot,
        acSonetFarEndLineDayIntervalPort,
        acSonetFarEndLineDayIntervalNumber
        }
    STATUS  current
    DESCRIPTION
    "Severely errored seconds for the far end line have exceeded the 
     threshold for the current day interval."
    
    ::= { acSonetFarEndLineTraps 11 }
    
acSonetFarEndLineDaySESClearTrap NOTIFICATION-TYPE
    OBJECTS { 
        acChassisCurrentTime, acChassisRingId, 
        acSonetFarEndLineDayIntervalNodeId,
        acSonetFarEndLineDayIntervalSlot,
        acSonetFarEndLineDayIntervalPort,
        acSonetFarEndLineDayIntervalNumber
        }
    STATUS  current
    DESCRIPTION
    "Severely errored seconds for the far end line have recovered for 
     the current day interval."
    
    ::= { acSonetFarEndLineTraps 12 }
    
acSonetFarEndLineDayCVAlarmTrap NOTIFICATION-TYPE
    OBJECTS { 
        acChassisCurrentTime, acChassisRingId, 
        acSonetFarEndLineDayIntervalNodeId,
        acSonetFarEndLineDayIntervalSlot,
        acSonetFarEndLineDayIntervalPort,
        acSonetFarEndLineDayIntervalNumber
        }
    STATUS  current
    DESCRIPTION
    "Coding violations for the far end line have exceeded the threshold 
     for the current day interval."
    
    ::= { acSonetFarEndLineTraps 13 }
    
acSonetFarEndLineDayCVClearTrap NOTIFICATION-TYPE
    OBJECTS { 
        acChassisCurrentTime, acChassisRingId, 
        acSonetFarEndLineDayIntervalNodeId,
        acSonetFarEndLineDayIntervalSlot,
        acSonetFarEndLineDayIntervalPort,
        acSonetFarEndLineDayIntervalNumber
        }
    STATUS  current
    DESCRIPTION
    "Coding violations for the far end line have recovered for the 
     current day interval."
    
    ::= { acSonetFarEndLineTraps 14 }
    
acSonetFarEndLineDayUASAlarmTrap NOTIFICATION-TYPE
    OBJECTS { 
        acChassisCurrentTime, acChassisRingId, 
        acSonetFarEndLineDayIntervalNodeId,
        acSonetFarEndLineDayIntervalSlot,
        acSonetFarEndLineDayIntervalPort,
        acSonetFarEndLineDayIntervalNumber
        }
    STATUS  current
    DESCRIPTION
    "Unavailable seconds for the far end line have exceeded the threshold 
     for the current day interval."
    
    ::= { acSonetFarEndLineTraps 15 }
    
acSonetFarEndLineDayUASClearTrap NOTIFICATION-TYPE
    OBJECTS { 
        acChassisCurrentTime, acChassisRingId, 
        acSonetFarEndLineDayIntervalNodeId,
        acSonetFarEndLineDayIntervalSlot,
        acSonetFarEndLineDayIntervalPort,
        acSonetFarEndLineDayIntervalNumber
        }
    STATUS  current
    DESCRIPTION
    "Unavailable seconds for the far end line have recovered for the 
     current day interval."
    
    ::= { acSonetFarEndLineTraps 16 }
    
-- =============================================================================    
--
-- SONET Path Traps
-- 
-- =============================================================================    

acSonetPathTraps  OBJECT IDENTIFIER ::= { acSonetPath 0 }

acSonetPathLOPAlarmTrap NOTIFICATION-TYPE
    OBJECTS { 
        acChassisCurrentTime, acChassisRingId, 
        acSonetPath15MinuteIntervalNodeId,
        acSonetPath15MinuteIntervalSlot,
        acSonetPath15MinuteIntervalPort,
        acSonetPath15MinuteIntervalPath,
        acSonetPath15MinuteIntervalNumber
        }
    STATUS  current
    DESCRIPTION
    "The SONET Path reports a Loss of Pointer (LOP) failure."
    
    ::= { acSonetPathTraps 1 }

acSonetPathLOPClearTrap NOTIFICATION-TYPE
    OBJECTS { 
        acChassisCurrentTime, acChassisRingId, 
        acSonetPath15MinuteIntervalNodeId,
        acSonetPath15MinuteIntervalSlot,
        acSonetPath15MinuteIntervalPort,
        acSonetPath15MinuteIntervalPath,
        acSonetPath15MinuteIntervalNumber
        }
    STATUS  current
    DESCRIPTION
    "The SONET Path recovers from a Loss of Pointer (LOP) failure."
    
    ::= { acSonetPathTraps 2 }

acSonetPathAISAlarmTrap NOTIFICATION-TYPE
    OBJECTS { 
        acChassisCurrentTime, acChassisRingId, 
        acSonetPath15MinuteIntervalNodeId,
        acSonetPath15MinuteIntervalSlot,
        acSonetPath15MinuteIntervalPort,
        acSonetPath15MinuteIntervalPath,
        acSonetPath15MinuteIntervalNumber
        }
    STATUS  current
    DESCRIPTION
    "The SONET Path reports an Alarm Indication Signal (AIS)."
    
    ::= { acSonetPathTraps 3 }

acSonetPathAISClearTrap NOTIFICATION-TYPE
    OBJECTS { 
        acChassisCurrentTime, acChassisRingId, 
        acSonetPath15MinuteIntervalNodeId,
        acSonetPath15MinuteIntervalSlot,
        acSonetPath15MinuteIntervalPort,
        acSonetPath15MinuteIntervalPath,
        acSonetPath15MinuteIntervalNumber
        }
    STATUS  current
    DESCRIPTION
    "The SONET Path recovers from an Alarm Indication Signal (AIS)."
    
    ::= { acSonetPathTraps 4 }

acSonetPathRDIAlarmTrap NOTIFICATION-TYPE
    OBJECTS { 
        acChassisCurrentTime, acChassisRingId, 
        acSonetPath15MinuteIntervalNodeId,
        acSonetPath15MinuteIntervalSlot,
        acSonetPath15MinuteIntervalPort,
        acSonetPath15MinuteIntervalPath,
        acSonetPath15MinuteIntervalNumber
        }
    STATUS  current
    DESCRIPTION
    "The SONET Path reports an RDI signal."
    
    ::= { acSonetPathTraps 5 }

acSonetPathRDIClearTrap NOTIFICATION-TYPE
    OBJECTS { 
        acChassisCurrentTime, acChassisRingId, 
        acSonetPath15MinuteIntervalNodeId,
        acSonetPath15MinuteIntervalSlot,
        acSonetPath15MinuteIntervalPort,
        acSonetPath15MinuteIntervalPath,
        acSonetPath15MinuteIntervalNumber
        }
    STATUS  current
    DESCRIPTION
    "The SONET Path recovers from an RDI signal."
    
    ::= { acSonetPathTraps 6 }

acSonetPathUnequipedAlarmTrap NOTIFICATION-TYPE
    OBJECTS { 
        acChassisCurrentTime, acChassisRingId, 
        acSonetPath15MinuteIntervalNodeId,
        acSonetPath15MinuteIntervalSlot,
        acSonetPath15MinuteIntervalPort,
        acSonetPath15MinuteIntervalPath,
        acSonetPath15MinuteIntervalNumber
        }
    STATUS  current
    DESCRIPTION
    "The SONET Path reports an unequipped condition exists."
    
    ::= { acSonetPathTraps 7 }

acSonetPathUnequipedClearTrap NOTIFICATION-TYPE
    OBJECTS { 
        acChassisCurrentTime, acChassisRingId, 
        acSonetPath15MinuteIntervalNodeId,
        acSonetPath15MinuteIntervalSlot,
        acSonetPath15MinuteIntervalPort,
        acSonetPath15MinuteIntervalPath,
        acSonetPath15MinuteIntervalNumber
        }
    STATUS  current
    DESCRIPTION
    "The SONET Path reports an unequipped condition has been cleared."
    
    ::= { acSonetPathTraps 8 }

acSonetPathTraceAlarmTrap NOTIFICATION-TYPE
    OBJECTS { 
        acChassisCurrentTime, acChassisRingId, 
        acSonetPathTIMNodeId,
        acSonetPathTIMSlot,
        acSonetPathTIMPort,
        acSonetPathTIMPath
        }
    STATUS  current
    DESCRIPTION
    "The path trace identifier received for the SONET interface was
    unexpected."
    
    ::= { acSonetPathTraps 9 }
    
acSonetPathTraceClearTrap NOTIFICATION-TYPE
    OBJECTS { 
        acChassisCurrentTime, acChassisRingId, 
        acSonetPathTIMNodeId,
        acSonetPathTIMSlot,
        acSonetPathTIMPort,
        acSonetPathTIMPath
        }
    STATUS  current
    DESCRIPTION
    "The path trace identifier mismatch condition for the SONET interface has
    recovered."
    
    ::= { acSonetPathTraps 10 }
    
acSonetPathPLMAlarmTrap NOTIFICATION-TYPE
    OBJECTS { 
        acChassisCurrentTime, acChassisRingId, 
        acSonetPathPLMNodeId,
        acSonetPathPLMSlot,
        acSonetPathPLMPort,
        acSonetPathPLMPath
        }
    STATUS  current
    DESCRIPTION
    "A payload label mismatch has been detected on this SONET interface."
    
    ::= { acSonetPathTraps 11 }
    
acSonetPathPLMClearTrap NOTIFICATION-TYPE
    OBJECTS { 
        acChassisCurrentTime, acChassisRingId, 
        acSonetPathPLMNodeId,
        acSonetPathPLMSlot,
        acSonetPathPLMPort,
        acSonetPathPLMPath
        }
    STATUS  current
    DESCRIPTION
    "A payload label mismatch has been cleared on this SONET interface."
    
    ::= { acSonetPathTraps 12 }
    
acSonetPathSDAlarmTrap NOTIFICATION-TYPE
    OBJECTS { 
        acChassisCurrentTime, acChassisRingId, 
        acSonetPath15MinuteIntervalNodeId,
        acSonetPath15MinuteIntervalSlot,
        acSonetPath15MinuteIntervalPort,
        acSonetPath15MinuteIntervalPath,
        acSonetPath15MinuteIntervalNumber
        }
    STATUS  current
    DESCRIPTION
    "The Signal Defects bit error rate for SONET Path have exceeded the 
     configured threshold."
    
    ::= { acSonetPathTraps 13 }

acSonetPathSDClearTrap NOTIFICATION-TYPE
    OBJECTS { 
        acChassisCurrentTime, acChassisRingId, 
        acSonetPath15MinuteIntervalNodeId,
        acSonetPath15MinuteIntervalSlot,
        acSonetPath15MinuteIntervalPort,
        acSonetPath15MinuteIntervalPath,
        acSonetPath15MinuteIntervalNumber
        }
    STATUS  current
    DESCRIPTION
    "The Signal Defects bit error rate for SONET Path have cleared."
    
    ::= { acSonetPathTraps 14 }

acSonetPathSFAlarmTrap NOTIFICATION-TYPE
    OBJECTS { 
        acChassisCurrentTime, acChassisRingId, 
        acSonetPath15MinuteIntervalNodeId,
        acSonetPath15MinuteIntervalSlot,
        acSonetPath15MinuteIntervalPort,
        acSonetPath15MinuteIntervalPath,
        acSonetPath15MinuteIntervalNumber
        }
    STATUS  current
    DESCRIPTION
    "The Signal Failure bit error rate for SONET Path has exceeded the 
     configured threshold."
    
    ::= { acSonetPathTraps 15 }

acSonetPathSFClearTrap NOTIFICATION-TYPE
    OBJECTS { 
        acChassisCurrentTime, acChassisRingId, 
        acSonetPath15MinuteIntervalNodeId,
        acSonetPath15MinuteIntervalSlot,
        acSonetPath15MinuteIntervalPort,
        acSonetPath15MinuteIntervalPath,
        acSonetPath15MinuteIntervalNumber
        }
    STATUS  current
    DESCRIPTION
    "The Signal Failure bit error rate for SONET Path has cleared."
    
    ::= { acSonetPathTraps 16 }

acSonetPath15MinuteESAlarmTrap NOTIFICATION-TYPE
    OBJECTS { 
        acChassisCurrentTime, acChassisRingId, 
        acSonetPath15MinuteIntervalNodeId,
        acSonetPath15MinuteIntervalSlot,
        acSonetPath15MinuteIntervalPort,
        acSonetPath15MinuteIntervalPath,
        acSonetPath15MinuteIntervalNumber
        }
    STATUS  current
    DESCRIPTION
    "The errored seconds (ES) for SONET Path exceeded the configured
    threshold during the current 15 minute interval."
    
    ::= { acSonetPathTraps 17 }

acSonetPath15MinuteESClearTrap NOTIFICATION-TYPE
    OBJECTS { 
        acChassisCurrentTime, acChassisRingId, 
        acSonetPath15MinuteIntervalNodeId,
        acSonetPath15MinuteIntervalSlot,
        acSonetPath15MinuteIntervalPort,
        acSonetPath15MinuteIntervalPath,
        acSonetPath15MinuteIntervalNumber
        }
    STATUS  current
    DESCRIPTION
    "The errored seconds (ES) for SONET Path have cleared for
     the current 15 minute interval."
    
    ::= { acSonetPathTraps 18 }

acSonetPath15MinuteSESAlarmTrap NOTIFICATION-TYPE
    OBJECTS { 
        acChassisCurrentTime, acChassisRingId, 
        acSonetPath15MinuteIntervalNodeId,
        acSonetPath15MinuteIntervalSlot,
        acSonetPath15MinuteIntervalPort,
        acSonetPath15MinuteIntervalPath,
        acSonetPath15MinuteIntervalNumber
        }
    STATUS  current
    DESCRIPTION
    "The severely errored seconds (SES) for SONET Path exceeded the 
    configured threshold during the current 15 minute interval."
    
    ::= { acSonetPathTraps 19 }

acSonetPath15MinuteSESClearTrap NOTIFICATION-TYPE
    OBJECTS { 
        acChassisCurrentTime, acChassisRingId, 
        acSonetPath15MinuteIntervalNodeId,
        acSonetPath15MinuteIntervalSlot,
        acSonetPath15MinuteIntervalPort,
        acSonetPath15MinuteIntervalPath,
        acSonetPath15MinuteIntervalNumber
        }
    STATUS  current
    DESCRIPTION
    "The severely errored seconds (SES) for SONET Path have recovered 
    for the current 15 minute interval."
    
    ::= { acSonetPathTraps 20 }

acSonetPath15MinuteCVAlarmTrap NOTIFICATION-TYPE
    OBJECTS { 
        acChassisCurrentTime, acChassisRingId, 
        acSonetPath15MinuteIntervalNodeId,
        acSonetPath15MinuteIntervalSlot,
        acSonetPath15MinuteIntervalPort,
        acSonetPath15MinuteIntervalPath,
        acSonetPath15MinuteIntervalNumber
        }
    STATUS  current
    DESCRIPTION
    "The BIP errors for SONET Path exceeded the configured
    threshold during the current 15 minute interval."
    
    ::= { acSonetPathTraps 21 }

acSonetPath15MinuteCVClearTrap NOTIFICATION-TYPE
    OBJECTS { 
        acChassisCurrentTime, acChassisRingId, 
        acSonetPath15MinuteIntervalNodeId,
        acSonetPath15MinuteIntervalSlot,
        acSonetPath15MinuteIntervalPort,
        acSonetPath15MinuteIntervalPath,
        acSonetPath15MinuteIntervalNumber
        }
    STATUS  current
    DESCRIPTION
    "The BIP errors for SONET Path have recovered for the 
    current 15 minute interval."
    
    ::= { acSonetPathTraps 22 }

acSonetPath15MinuteUASAlarmTrap NOTIFICATION-TYPE
    OBJECTS { 
        acChassisCurrentTime, acChassisRingId, 
        acSonetPath15MinuteIntervalNodeId,
        acSonetPath15MinuteIntervalSlot,
        acSonetPath15MinuteIntervalPort,
        acSonetPath15MinuteIntervalPath,
        acSonetPath15MinuteIntervalNumber
        }
    STATUS  current
    DESCRIPTION
    "The Unavailable Seconds for SONET Path exceeded the configured
    threshold during the current 15 minute interval."
    
    ::= { acSonetPathTraps 23 }
    
acSonetPath15MinuteUASClearTrap NOTIFICATION-TYPE
    OBJECTS { 
        acChassisCurrentTime, acChassisRingId, 
        acSonetPath15MinuteIntervalNodeId,
        acSonetPath15MinuteIntervalSlot,
        acSonetPath15MinuteIntervalPort,
        acSonetPath15MinuteIntervalPath,
        acSonetPath15MinuteIntervalNumber
        }
    STATUS  current
    DESCRIPTION
    "The Unavailable Seconds for SONET Path have recovered for the 
    current 15 minute interval."
    
    ::= { acSonetPathTraps 24 }
    
acSonetPathDayESAlarmTrap NOTIFICATION-TYPE
    OBJECTS { 
        acChassisCurrentTime, acChassisRingId, 
        acSonetPathDayIntervalNodeId,
        acSonetPathDayIntervalSlot,
        acSonetPathDayIntervalPort,
        acSonetPathDayIntervalPath,
        acSonetPathDayIntervalNumber
        }
    STATUS  current
    DESCRIPTION
    "The errored seconds (ES) for SONET Path exceeded the configured
    threshold during the current day interval."
    
    ::= { acSonetPathTraps 25 }

acSonetPathDayESClearTrap NOTIFICATION-TYPE
    OBJECTS { 
        acChassisCurrentTime, acChassisRingId, 
        acSonetPathDayIntervalNodeId,
        acSonetPathDayIntervalSlot,
        acSonetPathDayIntervalPort,
        acSonetPathDayIntervalPath,
        acSonetPathDayIntervalNumber
        }
    STATUS  current
    DESCRIPTION
    "The errored seconds (ES) for SONET Path have cleared
    for the current day interval."
    
    ::= { acSonetPathTraps 26 }

acSonetPathDaySESAlarmTrap NOTIFICATION-TYPE
    OBJECTS { 
        acChassisCurrentTime, acChassisRingId, 
        acSonetPathDayIntervalNodeId,
        acSonetPathDayIntervalSlot,
        acSonetPathDayIntervalPort,
        acSonetPathDayIntervalPath,
        acSonetPathDayIntervalNumber
        }
    STATUS  current
    DESCRIPTION
    "The severely errored seconds (SES) for SONET Path exceeded the 
    configured threshold during the current day interval."
    
    ::= { acSonetPathTraps 27 }

acSonetPathDaySESClearTrap NOTIFICATION-TYPE
    OBJECTS { 
        acChassisCurrentTime, acChassisRingId, 
        acSonetPathDayIntervalNodeId,
        acSonetPathDayIntervalSlot,
        acSonetPathDayIntervalPort,
        acSonetPathDayIntervalPath,
        acSonetPathDayIntervalNumber
        }
    STATUS  current
    DESCRIPTION
    "The severely errored seconds (SES) for SONET Path have recovered 
    for the current day interval."
    
    ::= { acSonetPathTraps 28 }

acSonetPathDayCVAlarmTrap NOTIFICATION-TYPE
    OBJECTS { 
        acChassisCurrentTime, acChassisRingId, 
        acSonetPathDayIntervalNodeId,
        acSonetPathDayIntervalSlot,
        acSonetPathDayIntervalPort,
        acSonetPathDayIntervalPath,
        acSonetPathDayIntervalNumber
        }
    STATUS  current
    DESCRIPTION
    "The BIP errors for SONET Path exceeded the configured
    threshold during the current day interval."
    
    ::= { acSonetPathTraps 29 }

acSonetPathDayCVClearTrap NOTIFICATION-TYPE
    OBJECTS { 
        acChassisCurrentTime, acChassisRingId, 
        acSonetPathDayIntervalNodeId,
        acSonetPathDayIntervalSlot,
        acSonetPathDayIntervalPort,
        acSonetPathDayIntervalPath,
        acSonetPathDayIntervalNumber
        }
    STATUS  current
    DESCRIPTION
    "The BIP errors for SONET Path have recovered for the 
    current day interval."
    
    ::= { acSonetPathTraps 30 }

acSonetPathDayUASAlarmTrap NOTIFICATION-TYPE
    OBJECTS { 
        acChassisCurrentTime, acChassisRingId, 
        acSonetPathDayIntervalNodeId,
        acSonetPathDayIntervalSlot,
        acSonetPathDayIntervalPort,
        acSonetPathDayIntervalPath,
        acSonetPathDayIntervalNumber
        }
    STATUS  current
    DESCRIPTION
    "The Unavailable Seconds for SONET Path exceeded the configured
    threshold during the current day interval."
    
    ::= { acSonetPathTraps 31 }
    
acSonetPathDayUASClearTrap NOTIFICATION-TYPE
    OBJECTS { 
        acChassisCurrentTime, acChassisRingId, 
        acSonetPathDayIntervalNodeId,
        acSonetPathDayIntervalSlot,
        acSonetPathDayIntervalPort,
        acSonetPathDayIntervalPath,
        acSonetPathDayIntervalNumber
        }
    STATUS  current
    DESCRIPTION
    "The Unavailable Seconds for SONET Path have recovered for the 
    current day interval."
    
    ::= { acSonetPathTraps 32 }
 
acSonetPathRingProtAlarmTrap NOTIFICATION-TYPE
    OBJECTS { 
        acChassisCurrentTime, acChassisRingId, 
        acSonetPathProtectionNodeId,
        acSonetPathProtectionSlot, 
        acSonetPathProtectionPort,
        acSonetPathProtectionPath 
       }
    STATUS  current
    DESCRIPTION
    "The SONET Path reports a ring protection switch."
    
    ::= { acSonetPathTraps 33 }

acSonetPathRingProtClearTrap NOTIFICATION-TYPE
    OBJECTS { 
        acChassisCurrentTime, acChassisRingId, 
        acSonetPathProtectionNodeId,
        acSonetPathProtectionSlot, 
        acSonetPathProtectionPort,
        acSonetPathProtectionPath 
        }
    STATUS  current
    DESCRIPTION
    "The SONET Path recovers from a ring protection switch."
    
    ::= { acSonetPathTraps 34 }

-- =============================================================================    
--
-- SONET Far End Path Traps
-- 
-- =============================================================================    

acSonetFarEndPathTraps  OBJECT IDENTIFIER ::= { acSonetFarEndPath 0 }

acSonetFarEndPath15MinuteESAlarmTrap NOTIFICATION-TYPE
    OBJECTS { 
        acChassisCurrentTime, acChassisRingId, 
        acSonetFarEndPath15MinuteIntervalNodeId,
        acSonetFarEndPath15MinuteIntervalSlot,
        acSonetFarEndPath15MinuteIntervalPort,
        acSonetFarEndPath15MinuteIntervalPath,
        acSonetFarEndPath15MinuteIntervalNumber
        }
    STATUS  current
    DESCRIPTION
    "The errored seconds (ES) for the SONET Far End Path exceeded the 
    configured threshold during the current 15 minute interval."
    
    ::= { acSonetFarEndPathTraps 1 }

acSonetFarEndPath15MinuteESClearTrap NOTIFICATION-TYPE
    OBJECTS { 
        acChassisCurrentTime, acChassisRingId, 
        acSonetFarEndPath15MinuteIntervalNodeId,
        acSonetFarEndPath15MinuteIntervalSlot,
        acSonetFarEndPath15MinuteIntervalPort,
        acSonetFarEndPath15MinuteIntervalPath,
        acSonetFarEndPath15MinuteIntervalNumber
        }
    STATUS  current
    DESCRIPTION
    "The Errored Seconds for SONET Path have recovered for the 
    current 15 minute interval."
    
    ::= { acSonetFarEndPathTraps 2 }

acSonetFarEndPath15MinuteSESAlarmTrap NOTIFICATION-TYPE
    OBJECTS { 
        acChassisCurrentTime, acChassisRingId, 
        acSonetFarEndPath15MinuteIntervalNodeId,
        acSonetFarEndPath15MinuteIntervalSlot,
        acSonetFarEndPath15MinuteIntervalPort,
        acSonetFarEndPath15MinuteIntervalPath,
        acSonetFarEndPath15MinuteIntervalNumber
        }
    STATUS  current
    DESCRIPTION
    "The Severely errored seconds (SES) for the SONET Far End Path 
     exceeded the configured threshold during the current 15 minute 
     interval."
    
    ::= { acSonetFarEndPathTraps 3 }

acSonetFarEndPath15MinuteSESClearTrap NOTIFICATION-TYPE
    OBJECTS { 
        acChassisCurrentTime, acChassisRingId, 
        acSonetFarEndPath15MinuteIntervalNodeId,
        acSonetFarEndPath15MinuteIntervalSlot,
        acSonetFarEndPath15MinuteIntervalPort,
        acSonetFarEndPath15MinuteIntervalPath,
        acSonetFarEndPath15MinuteIntervalNumber
        }
    STATUS  current
    DESCRIPTION
    "The Severely Errored Seconds for SONET Path have recovered for the 
    current 15 minute interval."
    
    ::= { acSonetFarEndPathTraps 4 }

acSonetFarEndPath15MinuteCVAlarmTrap NOTIFICATION-TYPE
    OBJECTS { 
        acChassisCurrentTime, acChassisRingId, 
        acSonetFarEndPath15MinuteIntervalNodeId,
        acSonetFarEndPath15MinuteIntervalSlot,
        acSonetFarEndPath15MinuteIntervalPort,
        acSonetFarEndPath15MinuteIntervalPath,
        acSonetFarEndPath15MinuteIntervalNumber
        }
    STATUS  current
    DESCRIPTION
    "BIP errors for SONET Far End Path exceeded the 
    configured threshold during the current 15 minute interval."
    
    ::= { acSonetFarEndPathTraps 5 }

acSonetFarEndPath15MinuteCVClearTrap NOTIFICATION-TYPE
    OBJECTS { 
        acChassisCurrentTime, acChassisRingId, 
        acSonetFarEndPath15MinuteIntervalNodeId,
        acSonetFarEndPath15MinuteIntervalSlot,
        acSonetFarEndPath15MinuteIntervalPort,
        acSonetFarEndPath15MinuteIntervalPath,
        acSonetFarEndPath15MinuteIntervalNumber
        }
    STATUS  current
    DESCRIPTION
    "The BIP errors for SONET Path have recovered for the 
    current 15 minute interval."
    
    ::= { acSonetFarEndPathTraps 6 }

acSonetFarEndPath15MinuteUASAlarmTrap NOTIFICATION-TYPE
    OBJECTS { 
        acChassisCurrentTime, acChassisRingId, 
        acSonetFarEndPath15MinuteIntervalNodeId,
        acSonetFarEndPath15MinuteIntervalSlot,
        acSonetFarEndPath15MinuteIntervalPort,
        acSonetFarEndPath15MinuteIntervalPath,
        acSonetFarEndPath15MinuteIntervalNumber
        }
    STATUS  current
    DESCRIPTION
    "Unavailable seconds (UAS) for SONET Far ENd Path exceeded the 
    configured threshold during the current 15 minute interval."
    
    ::= { acSonetFarEndPathTraps 7 }
    
acSonetFarEndPath15MinuteUASClearTrap NOTIFICATION-TYPE
    OBJECTS { 
        acChassisCurrentTime, acChassisRingId, 
        acSonetFarEndPath15MinuteIntervalNodeId,
        acSonetFarEndPath15MinuteIntervalSlot,
        acSonetFarEndPath15MinuteIntervalPort,
        acSonetFarEndPath15MinuteIntervalPath,
        acSonetFarEndPath15MinuteIntervalNumber
        }
    STATUS  current
    DESCRIPTION
    "The Unavailable Seconds for SONET Path have recovered for the 
    current 15 minute interval."
    
    ::= { acSonetFarEndPathTraps 8 }
    
acSonetFarEndPathDayESAlarmTrap NOTIFICATION-TYPE
    OBJECTS { 
        acChassisCurrentTime, acChassisRingId, 
        acSonetFarEndPathDayIntervalNodeId,
        acSonetFarEndPathDayIntervalSlot,
        acSonetFarEndPathDayIntervalPort,
        acSonetFarEndPathDayIntervalPath,
        acSonetFarEndPathDayIntervalNumber
        }
    STATUS  current
    DESCRIPTION
    "The errored seconds (ES) for the SONET Far End Path exceeded the 
    configured threshold during the current day interval."
    
    ::= { acSonetFarEndPathTraps 9 }

acSonetFarEndPathDayESClearTrap NOTIFICATION-TYPE
    OBJECTS { 
        acChassisCurrentTime, acChassisRingId, 
        acSonetFarEndPathDayIntervalNodeId,
        acSonetFarEndPathDayIntervalSlot,
        acSonetFarEndPathDayIntervalPort,
        acSonetFarEndPathDayIntervalPath,
        acSonetFarEndPathDayIntervalNumber
        }
    STATUS  current
    DESCRIPTION
    "The Errored Seconds for SONET Path have recovered for the 
    current day interval."
    
    ::= { acSonetFarEndPathTraps 10 }

acSonetFarEndPathDaySESAlarmTrap NOTIFICATION-TYPE
    OBJECTS { 
        acChassisCurrentTime, acChassisRingId, 
        acSonetFarEndPathDayIntervalNodeId,
        acSonetFarEndPathDayIntervalSlot,
        acSonetFarEndPathDayIntervalPort,
        acSonetFarEndPathDayIntervalPath,
        acSonetFarEndPathDayIntervalNumber
        }
    STATUS  current
    DESCRIPTION
    "The Severely errored seconds (SES) for the SONET Far End Path 
     exceeded the configured threshold during the current day 
     interval."
    
    ::= { acSonetFarEndPathTraps 11 }

acSonetFarEndPathDaySESClearTrap NOTIFICATION-TYPE
    OBJECTS { 
        acChassisCurrentTime, acChassisRingId, 
        acSonetFarEndPathDayIntervalNodeId,
        acSonetFarEndPathDayIntervalSlot,
        acSonetFarEndPathDayIntervalPort,
        acSonetFarEndPathDayIntervalPath,
        acSonetFarEndPathDayIntervalNumber
        }
    STATUS  current
    DESCRIPTION
    "The Severely Errored Seconds for SONET Path have recovered for the 
    current day interval."
    
    ::= { acSonetFarEndPathTraps 12 }

acSonetFarEndPathDayCVAlarmTrap NOTIFICATION-TYPE
    OBJECTS { 
        acChassisCurrentTime, acChassisRingId, 
        acSonetFarEndPathDayIntervalNodeId,
        acSonetFarEndPathDayIntervalSlot,
        acSonetFarEndPathDayIntervalPort,
        acSonetFarEndPathDayIntervalPath,
        acSonetFarEndPathDayIntervalNumber
        }
    STATUS  current
    DESCRIPTION
    "BIP errors for SONET Far End Path exceeded the 
    configured threshold during the current day interval."
    
    ::= { acSonetFarEndPathTraps 13 }

acSonetFarEndPathDayCVClearTrap NOTIFICATION-TYPE
    OBJECTS { 
        acChassisCurrentTime, acChassisRingId, 
        acSonetFarEndPathDayIntervalNodeId,
        acSonetFarEndPathDayIntervalSlot,
        acSonetFarEndPathDayIntervalPort,
        acSonetFarEndPathDayIntervalPath,
        acSonetFarEndPathDayIntervalNumber
        }
    STATUS  current
    DESCRIPTION
    "The BIP errors for SONET Path have recovered for the 
    current day interval."
    
    ::= { acSonetFarEndPathTraps 14 }

acSonetFarEndPathDayUASAlarmTrap NOTIFICATION-TYPE
    OBJECTS { 
        acChassisCurrentTime, acChassisRingId, 
        acSonetFarEndPathDayIntervalNodeId,
        acSonetFarEndPathDayIntervalSlot,
        acSonetFarEndPathDayIntervalPort,
        acSonetFarEndPathDayIntervalPath,
        acSonetFarEndPathDayIntervalNumber
        }
    STATUS  current
    DESCRIPTION
    "Unavailable seconds (UAS) for SONET Far ENd Path exceeded the 
    configured threshold during the current day interval."
    
    ::= { acSonetFarEndPathTraps 15 }
    
acSonetFarEndPathDayUASClearTrap NOTIFICATION-TYPE
    OBJECTS { 
        acChassisCurrentTime, acChassisRingId, 
        acSonetFarEndPathDayIntervalNodeId,
        acSonetFarEndPathDayIntervalSlot,
        acSonetFarEndPathDayIntervalPort,
        acSonetFarEndPathDayIntervalPath,
        acSonetFarEndPathDayIntervalNumber
        }
    STATUS  current
    DESCRIPTION
    "The Unavailable Seconds for SONET Path have recovered for the 
    current day interval."
    
    ::= { acSonetFarEndPathTraps 16 }
    
-- =============================================================================    
--
-- SONET VT Traps
-- 
-- =============================================================================    

acSonetVTTrap  OBJECT IDENTIFIER ::= { acSonetVT 0 }

acSonetVTLOPAlarmTrap NOTIFICATION-TYPE
    OBJECTS { 
        acChassisCurrentTime, acChassisRingId,
        acSonetVT15MinuteIntervalNodeId,
        acSonetVT15MinuteIntervalSlot,
        acSonetVT15MinuteIntervalPort,        
        acSonetVT15MinuteIntervalVT,        
        acSonetVT15MinuteIntervalNumber
        }
    STATUS  current
    DESCRIPTION
    "A Loss of Pointer (LOP) for a SONET VT has been detected."
    
    ::= { acSonetVTTrap 1 }

acSonetVTLOPClearTrap NOTIFICATION-TYPE
    OBJECTS { 
        acChassisCurrentTime, acChassisRingId,
        acSonetVT15MinuteIntervalNodeId,
        acSonetVT15MinuteIntervalSlot,
        acSonetVT15MinuteIntervalPort,        
        acSonetVT15MinuteIntervalVT,        
        acSonetVT15MinuteIntervalNumber
        }
    STATUS  current
    DESCRIPTION
    "The SONET VT has recovered from a Loss of Pointer (LOP)."
    
    ::= { acSonetVTTrap 2 }

acSonetVTPathAISAlarmTrap NOTIFICATION-TYPE
    OBJECTS { 
        acChassisCurrentTime, acChassisRingId,
        acSonetVT15MinuteIntervalNodeId,
        acSonetVT15MinuteIntervalSlot,
        acSonetVT15MinuteIntervalPort,        
        acSonetVT15MinuteIntervalVT,        
        acSonetVT15MinuteIntervalNumber
        }
    STATUS  current
    DESCRIPTION
    "A path alarm indication signal (AIS) for a SONET VT has been detected."

    ::= { acSonetVTTrap 3 }
    
acSonetVTPathAISClearTrap NOTIFICATION-TYPE
    OBJECTS { 
        acChassisCurrentTime, acChassisRingId,
        acSonetVT15MinuteIntervalNodeId,
        acSonetVT15MinuteIntervalSlot,
        acSonetVT15MinuteIntervalPort,        
        acSonetVT15MinuteIntervalVT,        
        acSonetVT15MinuteIntervalNumber
        }
    STATUS  current
    DESCRIPTION
    "A VT path has recovered from an alarm indication signal (AIS)."

    ::= { acSonetVTTrap 4 }
    
acSonetVTPathRFIAlarmTrap NOTIFICATION-TYPE
    OBJECTS { 
        acChassisCurrentTime, acChassisRingId,
        acSonetVT15MinuteIntervalNodeId,
        acSonetVT15MinuteIntervalSlot,
        acSonetVT15MinuteIntervalPort,        
        acSonetVT15MinuteIntervalVT,        
        acSonetVT15MinuteIntervalNumber
        }
    STATUS  current
    DESCRIPTION
    "A path remote fault indication (RFI) for a SONET VT has been detected."
    
    ::= { acSonetVTTrap 5 }
    
acSonetVTPathRFIClearTrap NOTIFICATION-TYPE
    OBJECTS { 
        acChassisCurrentTime, acChassisRingId,
        acSonetVT15MinuteIntervalNodeId,
        acSonetVT15MinuteIntervalSlot,
        acSonetVT15MinuteIntervalPort,        
        acSonetVT15MinuteIntervalVT,        
        acSonetVT15MinuteIntervalNumber
        }
    STATUS  current
    DESCRIPTION
    "A path remote fault indication (RFI) for a SONET VT has been cleared."
    
    ::= { acSonetVTTrap 6 }
    
acSonetVTUnequippedAlarmTrap NOTIFICATION-TYPE
    OBJECTS { 
        acChassisCurrentTime, acChassisRingId,
        acSonetVT15MinuteIntervalNodeId,
        acSonetVT15MinuteIntervalSlot,
        acSonetVT15MinuteIntervalPort,        
        acSonetVT15MinuteIntervalVT,        
        acSonetVT15MinuteIntervalNumber
        }
    STATUS  current
    DESCRIPTION
    "The SONET VT has detected an unequipped condition."
    
    ::= { acSonetVTTrap 7 }
    
acSonetVTUnequippedClearTrap NOTIFICATION-TYPE
    OBJECTS { 
        acChassisCurrentTime, acChassisRingId,
        acSonetVT15MinuteIntervalNodeId,
        acSonetVT15MinuteIntervalSlot,
        acSonetVT15MinuteIntervalPort,        
        acSonetVT15MinuteIntervalVT,        
        acSonetVT15MinuteIntervalNumber
        }
    STATUS  current
    DESCRIPTION
    "The SONET VT has cleared an unequipped condition."
    
    ::= { acSonetVTTrap 8 }
    
acSonetVTPLMAlarmTrap NOTIFICATION-TYPE
    OBJECTS { 
        acChassisCurrentTime, acChassisRingId,
        acSonetVT15MinuteIntervalNodeId,
        acSonetVT15MinuteIntervalSlot,
        acSonetVT15MinuteIntervalPort,        
        acSonetVT15MinuteIntervalVT,        
        acSonetVT15MinuteIntervalNumber
        }
    STATUS  current
    DESCRIPTION
    "A payload label mismatch (PLM) error has been detected for a SONET VT."
    
    ::= { acSonetVTTrap 9 }

acSonetVTPLMClearTrap NOTIFICATION-TYPE
    OBJECTS { 
        acChassisCurrentTime, acChassisRingId,
        acSonetVT15MinuteIntervalNodeId,
        acSonetVT15MinuteIntervalSlot,
        acSonetVT15MinuteIntervalPort,        
        acSonetVT15MinuteIntervalVT,        
        acSonetVT15MinuteIntervalNumber
        }
    STATUS  current
    DESCRIPTION
    "A payload label mismatch (PLM) error has been cleared for a SONET VT."
    
    ::= { acSonetVTTrap 10 }

acSonetVTSDAlarmTrap  NOTIFICATION-TYPE
    OBJECTS { 
        acChassisCurrentTime, acChassisRingId, 
        acSonetVT15MinuteIntervalNodeId,
        acSonetVT15MinuteIntervalSlot,
        acSonetVT15MinuteIntervalPort,        
        acSonetVT15MinuteIntervalVT,        
        acSonetVT15MinuteIntervalNumber
        }
    STATUS current
    DESCRIPTION
    "The signal degradation threshold for a VT running over this SONET 
     interface exceeded the configured threshold value."
    
    ::= { acSonetVTTrap 11 }
    
acSonetVTSDClearTrap  NOTIFICATION-TYPE
    OBJECTS { 
        acChassisCurrentTime, acChassisRingId, 
        acSonetVT15MinuteIntervalNodeId,
        acSonetVT15MinuteIntervalSlot,
        acSonetVT15MinuteIntervalPort,        
        acSonetVT15MinuteIntervalVT,        
        acSonetVT15MinuteIntervalNumber
        }
    STATUS current
    DESCRIPTION
    "The signal degradation bit error rate for this VT path has cleared."
    
    ::= { acSonetVTTrap 12 }
    
acSonetVTSFAlarmTrap  NOTIFICATION-TYPE
    OBJECTS { 
        acChassisCurrentTime, acChassisRingId, 
        acSonetVT15MinuteIntervalNodeId,
        acSonetVT15MinuteIntervalSlot,
        acSonetVT15MinuteIntervalPort,        
        acSonetVT15MinuteIntervalVT,        
        acSonetVT15MinuteIntervalNumber
        }
    STATUS current
    DESCRIPTION
    "The signal fail threshold for a VT running over this SONET interface 
     exceeded the configured threshold value."
    
    ::= { acSonetVTTrap 13 }

acSonetVTSFClearTrap  NOTIFICATION-TYPE
    OBJECTS { 
        acChassisCurrentTime, acChassisRingId, 
        acSonetVT15MinuteIntervalNodeId,
        acSonetVT15MinuteIntervalSlot,
        acSonetVT15MinuteIntervalPort,        
        acSonetVT15MinuteIntervalVT,        
        acSonetVT15MinuteIntervalNumber
        }
    STATUS current
    DESCRIPTION
    "The signal fail bit error rate for this VT path has cleared."
    
    ::= { acSonetVTTrap 14 }

acSonetVT15MinuteESAlarmTrap NOTIFICATION-TYPE
    OBJECTS { acChassisCurrentTime, acChassisRingId,
        acSonetVT15MinuteIntervalNodeId,
        acSonetVT15MinuteIntervalSlot,
        acSonetVT15MinuteIntervalPort,        
        acSonetVT15MinuteIntervalVT,        
        acSonetVT15MinuteIntervalNumber
        }
    STATUS  current
    DESCRIPTION
    "The errored seconds (ES) threshold for a SONET VT been exceeded 
     during the current 15 minute interval."
        
    ::= { acSonetVTTrap 15 }    

acSonetVT15MinuteESClearTrap NOTIFICATION-TYPE
    OBJECTS { acChassisCurrentTime, acChassisRingId,
        acSonetVT15MinuteIntervalNodeId,
        acSonetVT15MinuteIntervalSlot,
        acSonetVT15MinuteIntervalPort,        
        acSonetVT15MinuteIntervalVT,        
        acSonetVT15MinuteIntervalNumber
        }
    STATUS  current
    DESCRIPTION
    "The errored seconds (ES) threshold for a SONET VT has been cleared 
     for the current 15 minute interval."
        
    ::= { acSonetVTTrap 16 }    

acSonetVT15MinuteSESAlarmTrap NOTIFICATION-TYPE
    OBJECTS { 
        acChassisCurrentTime, acChassisRingId,
        acSonetVT15MinuteIntervalNodeId,
        acSonetVT15MinuteIntervalSlot,
        acSonetVT15MinuteIntervalPort,        
        acSonetVT15MinuteIntervalVT,        
        acSonetVT15MinuteIntervalNumber
        }
    STATUS  current
    DESCRIPTION
    "The severly errored seconds (SES) for a SONET VT exceeded the 
     configured threshold during the current 15 minute interval."
        
    ::= { acSonetVTTrap 17 }    

acSonetVT15MinuteSESClearTrap NOTIFICATION-TYPE
    OBJECTS { 
        acChassisCurrentTime, acChassisRingId,
        acSonetVT15MinuteIntervalNodeId,
        acSonetVT15MinuteIntervalSlot,
        acSonetVT15MinuteIntervalPort,        
        acSonetVT15MinuteIntervalVT,        
        acSonetVT15MinuteIntervalNumber
        }
    STATUS  current
    DESCRIPTION
    "The severly errored seconds (SES) for a SONET VT has been cleared 
     for the current 15 minute interval."
        
    ::= { acSonetVTTrap 18 }    

acSonetVT15MinuteCVAlarmTrap NOTIFICATION-TYPE
    OBJECTS { 
        acChassisCurrentTime, acChassisRingId,
        acSonetVT15MinuteIntervalNodeId,
        acSonetVT15MinuteIntervalSlot,
        acSonetVT15MinuteIntervalPort,        
        acSonetVT15MinuteIntervalVT,        
        acSonetVT15MinuteIntervalNumber
        }
    STATUS  current
    DESCRIPTION
    "The coding violations (CV) for a SONET VT exceeded the configured 
     threshold during the current 15 minute interval."

    ::= { acSonetVTTrap 19 }    

acSonetVT15MinuteCVClearTrap NOTIFICATION-TYPE
    OBJECTS { 
        acChassisCurrentTime, acChassisRingId,
        acSonetVT15MinuteIntervalNodeId,
        acSonetVT15MinuteIntervalSlot,
        acSonetVT15MinuteIntervalPort,        
        acSonetVT15MinuteIntervalVT,        
        acSonetVT15MinuteIntervalNumber
        }
    STATUS  current
    DESCRIPTION
    "The coding violations (CV) for a SONET VT have cleared 
     for the current 15 minute interval."

    ::= { acSonetVTTrap 20 }    

acSonetVT15MinuteUASAlarmTrap NOTIFICATION-TYPE
    OBJECTS { 
        acChassisCurrentTime, acChassisRingId,
        acSonetVT15MinuteIntervalNodeId,
        acSonetVT15MinuteIntervalSlot,
        acSonetVT15MinuteIntervalPort,        
        acSonetVT15MinuteIntervalVT,        
        acSonetVT15MinuteIntervalNumber
        }
    STATUS  current
    DESCRIPTION
    "The unavailable seconds (UAS) for a SONET VT exceeded the configured 
     threshold during the current 15 minute interval."
    
    ::= { acSonetVTTrap 21 }    

acSonetVT15MinuteUASClearTrap NOTIFICATION-TYPE
    OBJECTS { 
        acChassisCurrentTime, acChassisRingId,
        acSonetVT15MinuteIntervalNodeId,
        acSonetVT15MinuteIntervalSlot,
        acSonetVT15MinuteIntervalPort,        
        acSonetVT15MinuteIntervalVT,        
        acSonetVT15MinuteIntervalNumber
        }
    STATUS  current
    DESCRIPTION
    "The unavailable seconds (UAS) for a SONET VT have cleared 
     for the current 15 minute interval."
    
    ::= { acSonetVTTrap 22 }    

acSonetVTDayESAlarmTrap NOTIFICATION-TYPE
    OBJECTS { acChassisCurrentTime, acChassisRingId,
        acSonetVTDayIntervalNodeId,
        acSonetVTDayIntervalSlot,
        acSonetVTDayIntervalPort,        
        acSonetVTDayIntervalVT,        
        acSonetVTDayIntervalNumber        
        }
    STATUS  current
    DESCRIPTION
    "The errored seconds (ES) threshold for a SONET VT been exceeded 
     during the current day interval."
        
    ::= { acSonetVTTrap 23 }    

acSonetVTDayESClearTrap NOTIFICATION-TYPE
    OBJECTS { acChassisCurrentTime, acChassisRingId,
        acSonetVTDayIntervalNodeId,
        acSonetVTDayIntervalSlot,
        acSonetVTDayIntervalPort,        
        acSonetVTDayIntervalVT,        
        acSonetVTDayIntervalNumber
        }
    STATUS  current
    DESCRIPTION
    "The errored seconds (ES) threshold for a SONET VT has been cleared 
     for the current day interval."
        
    ::= { acSonetVTTrap 24 }    

acSonetVTDaySESAlarmTrap NOTIFICATION-TYPE
    OBJECTS { 
        acChassisCurrentTime, acChassisRingId,
        acSonetVTDayIntervalNodeId,
        acSonetVTDayIntervalSlot,
        acSonetVTDayIntervalPort,        
        acSonetVTDayIntervalVT,        
        acSonetVTDayIntervalNumber
        }
    STATUS  current
    DESCRIPTION
    "The severly errored seconds (SES) for a SONET VT exceeded the 
     configured threshold during the current day interval."
        
    ::= { acSonetVTTrap 25 }    

acSonetVTDaySESClearTrap NOTIFICATION-TYPE
    OBJECTS { 
        acChassisCurrentTime, acChassisRingId,
        acSonetVTDayIntervalNodeId,
        acSonetVTDayIntervalSlot,
        acSonetVTDayIntervalPort,        
        acSonetVTDayIntervalVT,        
        acSonetVTDayIntervalNumber
        }
    STATUS  current
    DESCRIPTION
    "The severly errored seconds (SES) for a SONET VT has been cleared 
     for the current day interval."
        
    ::= { acSonetVTTrap 26 }    

acSonetVTDayCVAlarmTrap NOTIFICATION-TYPE
    OBJECTS { 
        acChassisCurrentTime, acChassisRingId,
        acSonetVTDayIntervalNodeId,
        acSonetVTDayIntervalSlot,
        acSonetVTDayIntervalPort,        
        acSonetVTDayIntervalVT,        
        acSonetVTDayIntervalNumber
        }
    STATUS  current
    DESCRIPTION
    "The coding violations (CV) for a SONET VT exceeded the configured 
     threshold during the current day interval."

    ::= { acSonetVTTrap 27 }    

acSonetVTDayCVClearTrap NOTIFICATION-TYPE
    OBJECTS { 
        acChassisCurrentTime, acChassisRingId,
        acSonetVTDayIntervalNodeId,
        acSonetVTDayIntervalSlot,
        acSonetVTDayIntervalPort,        
        acSonetVTDayIntervalVT,        
        acSonetVTDayIntervalNumber
        }
    STATUS  current
    DESCRIPTION
    "The coding violations (CV) for a SONET VT have cleared 
     for the current day interval."

    ::= { acSonetVTTrap 28 }    

acSonetVTDayUASAlarmTrap NOTIFICATION-TYPE
    OBJECTS { 
        acChassisCurrentTime, acChassisRingId,
        acSonetVTDayIntervalNodeId,
        acSonetVTDayIntervalSlot,
        acSonetVTDayIntervalPort,        
        acSonetVTDayIntervalVT,        
        acSonetVTDayIntervalNumber
        }
    STATUS  current
    DESCRIPTION
    "The unavailable seconds (UAS) for a SONET VT exceeded the configured 
     threshold during the current day interval."
    
    ::= { acSonetVTTrap 29 }    

acSonetVTDayUASClearTrap NOTIFICATION-TYPE
    OBJECTS { 
        acChassisCurrentTime, acChassisRingId,
        acSonetVTDayIntervalNodeId,
        acSonetVTDayIntervalSlot,
        acSonetVTDayIntervalPort,        
        acSonetVTDayIntervalVT,        
        acSonetVTDayIntervalNumber
        }
    STATUS  current
    DESCRIPTION
    "The unavailable seconds (UAS) for a SONET VT have cleared 
     for the current day interval."
    
    ::= { acSonetVTTrap 30 }    

acSonetVTRingProtSwitchAlarmTrap NOTIFICATION-TYPE
    OBJECTS { 
        acChassisCurrentTime, acChassisRingId,
        acSonetVTProtectionNodeId,
        acSonetVTProtectionSlot,  
        acSonetVTProtectionPort,
        acSonetVTProtectionVT
        }
    STATUS  current
    DESCRIPTION
    "A Sonet VT ring protection switch has been detected."
    
    ::= { acSonetVTTrap 31 }

acSonetVTRingProtSwitchClearTrap NOTIFICATION-TYPE
    OBJECTS { 
        acChassisCurrentTime, acChassisRingId,
        acSonetVTProtectionNodeId,
        acSonetVTProtectionSlot,  
        acSonetVTProtectionPort,
        acSonetVTProtectionVT
        }
    STATUS  current
    DESCRIPTION
    "The SONET VT has recovered from Sonet ring protection switch."
     
    ::= { acSonetVTTrap 32 } 

-- =============================================================================    
--
-- SONET Far End VT Traps
-- 
-- =============================================================================    

acSonetFarEndVTTraps  OBJECT IDENTIFIER ::= { acSonetFarEndVT 0 }

acSonetFarEndVT15MinuteESAlarmTrap NOTIFICATION-TYPE
    OBJECTS { 
        acChassisCurrentTime, acChassisRingId,
        acSonetFarEndVT15MinuteIntervalNodeId,
        acSonetFarEndVT15MinuteIntervalSlot,
        acSonetFarEndVT15MinuteIntervalPort,        
        acSonetFarEndVT15MinuteIntervalVT,        
        acSonetFarEndVT15MinuteIntervalNumber
        }
    STATUS  current
    DESCRIPTION
    "Errored seconds (ES) for the Far End SONET VT exceeded
    the configured threshold during the current 15 minute interval."
        
    ::= { acSonetFarEndVTTraps 1 }

acSonetFarEndVT15MinuteESClearTrap NOTIFICATION-TYPE
    OBJECTS { 
        acChassisCurrentTime, acChassisRingId,
        acSonetFarEndVT15MinuteIntervalNodeId,
        acSonetFarEndVT15MinuteIntervalSlot,
        acSonetFarEndVT15MinuteIntervalPort,        
        acSonetFarEndVT15MinuteIntervalVT,        
        acSonetFarEndVT15MinuteIntervalNumber
        }
    STATUS  current
    DESCRIPTION
    "Errored seconds (ES) for the Far End SONET VT have cleared for
    the current 15 minute interval."
        
    ::= { acSonetFarEndVTTraps 2 }

acSonetFarEndVT15MinuteSESAlarmTrap NOTIFICATION-TYPE
    OBJECTS { 
        acChassisCurrentTime, acChassisRingId,
        acSonetFarEndVT15MinuteIntervalNodeId,
        acSonetFarEndVT15MinuteIntervalSlot,
        acSonetFarEndVT15MinuteIntervalPort,        
        acSonetFarEndVT15MinuteIntervalVT,        
        acSonetFarEndVT15MinuteIntervalNumber
        }
    STATUS  current
    DESCRIPTION
    "Severly errored seconds (SES) for the Far End SONET VT exceeded 
    the configured threshold during the current 15 minute interval."
        
    ::= { acSonetFarEndVTTraps 3 }

acSonetFarEndVT15MinuteSESClearTrap NOTIFICATION-TYPE
    OBJECTS { 
        acChassisCurrentTime, acChassisRingId,
        acSonetFarEndVT15MinuteIntervalNodeId,
        acSonetFarEndVT15MinuteIntervalSlot,
        acSonetFarEndVT15MinuteIntervalPort,        
        acSonetFarEndVT15MinuteIntervalVT,        
        acSonetFarEndVT15MinuteIntervalNumber
        }
    STATUS  current
    DESCRIPTION
    "Severly errored seconds (SES) for the Far End SONET VT have 
    cleared for the current 15 minute interval."
        
    ::= { acSonetFarEndVTTraps 4 }

acSonetFarEndVT15MinuteCVAlarmTrap NOTIFICATION-TYPE
    OBJECTS { 
        acChassisCurrentTime, acChassisRingId,
        acSonetFarEndVT15MinuteIntervalNodeId,
        acSonetFarEndVT15MinuteIntervalSlot,
        acSonetFarEndVT15MinuteIntervalPort,        
        acSonetFarEndVT15MinuteIntervalVT,        
        acSonetFarEndVT15MinuteIntervalNumber
        }
    STATUS  current
    DESCRIPTION
    "Coding violations (CV) for a SONET VT exceeded the configured 
    threshold during the current 15 minute interval."

    ::= { acSonetFarEndVTTraps 5 }

acSonetFarEndVT15MinuteCVClearTrap NOTIFICATION-TYPE
    OBJECTS { 
        acChassisCurrentTime, acChassisRingId,
        acSonetFarEndVT15MinuteIntervalNodeId,
        acSonetFarEndVT15MinuteIntervalSlot,
        acSonetFarEndVT15MinuteIntervalPort,        
        acSonetFarEndVT15MinuteIntervalVT,        
        acSonetFarEndVT15MinuteIntervalNumber
        }
    STATUS  current
    DESCRIPTION
    "Coding violations (CV) for a SONET VT have cleared for 
    the current 15 minute interval."

    ::= { acSonetFarEndVTTraps 6 }

acSonetFarEndVT15MinuteUASAlarmTrap NOTIFICATION-TYPE
    OBJECTS { 
        acChassisCurrentTime, acChassisRingId,
        acSonetFarEndVT15MinuteIntervalNodeId,
        acSonetFarEndVT15MinuteIntervalSlot,
        acSonetFarEndVT15MinuteIntervalPort,        
        acSonetFarEndVT15MinuteIntervalVT,        
        acSonetFarEndVT15MinuteIntervalNumber
        }
    STATUS  current
    DESCRIPTION
    "Unavailable seconds (UAS) for a SONET VT exceeded the configured 
    threshold during the current 15 minute interval."
    
    ::= { acSonetFarEndVTTraps 7 }

acSonetFarEndVT15MinuteUASClearTrap NOTIFICATION-TYPE
    OBJECTS { 
        acChassisCurrentTime, acChassisRingId,
        acSonetFarEndVT15MinuteIntervalNodeId,
        acSonetFarEndVT15MinuteIntervalSlot,
        acSonetFarEndVT15MinuteIntervalPort,        
        acSonetFarEndVT15MinuteIntervalVT,        
        acSonetFarEndVT15MinuteIntervalNumber
        }
    STATUS  current
    DESCRIPTION
    "Unavailable seconds (UAS) for a SONET VT have cleared for 
    the current 15 minute interval."
    
    ::= { acSonetFarEndVTTraps 8 }

acSonetFarEndVTDayESAlarmTrap NOTIFICATION-TYPE
    OBJECTS { 
        acChassisCurrentTime, acChassisRingId,
        acSonetFarEndVTDayIntervalNodeId,
        acSonetFarEndVTDayIntervalSlot,
        acSonetFarEndVTDayIntervalPort,        
        acSonetFarEndVTDayIntervalVT,        
        acSonetFarEndVTDayIntervalNumber
        }
    STATUS  current
    DESCRIPTION
    "Errored seconds (ES) for the Far End SONET VT exceeded
    the configured threshold during the current day interval."
        
    ::= { acSonetFarEndVTTraps 9 }

acSonetFarEndVTDayESClearTrap NOTIFICATION-TYPE
    OBJECTS { 
        acChassisCurrentTime, acChassisRingId,
        acSonetFarEndVTDayIntervalNodeId,
        acSonetFarEndVTDayIntervalSlot,
        acSonetFarEndVTDayIntervalPort,        
        acSonetFarEndVTDayIntervalVT,        
        acSonetFarEndVTDayIntervalNumber
        }
    STATUS  current
    DESCRIPTION
    "Errored seconds (ES) for the Far End SONET VT have cleared for
    the current day interval."
        
    ::= { acSonetFarEndVTTraps 10 }

acSonetFarEndVTDaySESAlarmTrap NOTIFICATION-TYPE
    OBJECTS { 
        acChassisCurrentTime, acChassisRingId,
        acSonetFarEndVTDayIntervalNodeId,
        acSonetFarEndVTDayIntervalSlot,
        acSonetFarEndVTDayIntervalPort,        
        acSonetFarEndVTDayIntervalVT,        
        acSonetFarEndVTDayIntervalNumber
        }
    STATUS  current
    DESCRIPTION
    "Severly errored seconds (SES) for the Far End SONET VT exceeded 
    the configured threshold during the current day interval."
        
    ::= { acSonetFarEndVTTraps 11 }

acSonetFarEndVTDaySESClearTrap NOTIFICATION-TYPE
    OBJECTS { 
        acChassisCurrentTime, acChassisRingId,
        acSonetFarEndVTDayIntervalNodeId,
        acSonetFarEndVTDayIntervalSlot,
        acSonetFarEndVTDayIntervalPort,        
        acSonetFarEndVTDayIntervalVT,        
        acSonetFarEndVTDayIntervalNumber
        }
    STATUS  current
    DESCRIPTION
    "Severly errored seconds (SES) for the Far End SONET VT have 
    cleared for the current day interval."
        
    ::= { acSonetFarEndVTTraps 12 }

acSonetFarEndVTDayCVAlarmTrap NOTIFICATION-TYPE
    OBJECTS { 
        acChassisCurrentTime, acChassisRingId,
        acSonetFarEndVTDayIntervalNodeId,
        acSonetFarEndVTDayIntervalSlot,
        acSonetFarEndVTDayIntervalPort,        
        acSonetFarEndVTDayIntervalVT,        
        acSonetFarEndVTDayIntervalNumber
        }
    STATUS  current
    DESCRIPTION
    "Coding violations (CV) for a SONET VT exceeded the configured 
    threshold during the current day interval."

    ::= { acSonetFarEndVTTraps 13 }

acSonetFarEndVTDayCVClearTrap NOTIFICATION-TYPE
    OBJECTS { 
        acChassisCurrentTime, acChassisRingId,
        acSonetFarEndVTDayIntervalNodeId,
        acSonetFarEndVTDayIntervalSlot,
        acSonetFarEndVTDayIntervalPort,        
        acSonetFarEndVTDayIntervalVT,        
        acSonetFarEndVTDayIntervalNumber
        }
    STATUS  current
    DESCRIPTION
    "Coding violations (CV) for a SONET VT have cleared for 
    the current day interval."

    ::= { acSonetFarEndVTTraps 14 }

acSonetFarEndVTDayUASAlarmTrap NOTIFICATION-TYPE
    OBJECTS { 
        acChassisCurrentTime, acChassisRingId,
        acSonetFarEndVTDayIntervalNodeId,
        acSonetFarEndVTDayIntervalSlot,
        acSonetFarEndVTDayIntervalPort,        
        acSonetFarEndVTDayIntervalVT,        
        acSonetFarEndVTDayIntervalNumber
        }
    STATUS  current
    DESCRIPTION
    "Unavailable seconds (UAS) for a SONET VT exceeded the configured 
    threshold during the current day interval."
    
    ::= { acSonetFarEndVTTraps 15 }

acSonetFarEndVTDayUASClearTrap NOTIFICATION-TYPE
    OBJECTS { 
        acChassisCurrentTime, acChassisRingId,
        acSonetFarEndVTDayIntervalNodeId,
        acSonetFarEndVTDayIntervalSlot,
        acSonetFarEndVTDayIntervalPort,        
        acSonetFarEndVTDayIntervalVT,        
        acSonetFarEndVTDayIntervalNumber
        }
    STATUS  current
    DESCRIPTION
    "Unavailable seconds (UAS) for a SONET VT have cleared for 
    the current day interval."
    
    ::= { acSonetFarEndVTTraps 16 }

--------------------------------------------------------------------------------
--
-- SONET Protection Switching Traps
-- 
--------------------------------------------------------------------------------
-- acSonetLineProtectionTraps  OBJECT IDENTIFIER ::= { acSonetLineProtection 0 }

acSonetLineProtectionSwitchAlarmTrap  NOTIFICATION-TYPE
    OBJECTS { 
        acChassisCurrentTime, acChassisRingId, 
        acSonetLineProtectionNodeId,
        acSonetLineProtectionSlot,
        acSonetLineProtectionPort
        }
    STATUS current
    DESCRIPTION
    "Protection switch is currently active on this SONET interface."
    
    ::= { acSonetLineTraps 21 }
    
acSonetLineProtectionSwitchClearTrap  NOTIFICATION-TYPE
    OBJECTS { 
        acChassisCurrentTime, acChassisRingId, 
        acSonetLineProtectionNodeId,
        acSonetLineProtectionSlot,
        acSonetLineProtectionPort
        }
    STATUS current
    DESCRIPTION
    "Protection switch has been released on this SONET interface."
    
    ::= { acSonetLineTraps 22 }
    
acSonetLineProtectionFailureAlarmTrap  NOTIFICATION-TYPE
    OBJECTS { 
        acChassisCurrentTime, acChassisRingId, 
        acSonetLineProtectionNodeId,
        acSonetLineProtectionSlot,
        acSonetLineProtectionPort
        }
    STATUS current
    DESCRIPTION
    "Protection switch failure has occured for this SONET interface."
    
    ::= { acSonetLineTraps 23 }
    
acSonetLineProtectionFailureClearTrap  NOTIFICATION-TYPE
    OBJECTS { 
        acChassisCurrentTime, acChassisRingId, 
        acSonetLineProtectionNodeId,
        acSonetLineProtectionSlot,
        acSonetLineProtectionPort
        }
    STATUS current
    DESCRIPTION
    "Protection switch failure has cleared for this SONET interface."
    
    ::= { acSonetLineTraps 24 }
    
acSonetLineProtectionChannelMismatchAlarmTrap  NOTIFICATION-TYPE
    OBJECTS { 
        acChassisCurrentTime, acChassisRingId, 
        acSonetLineProtectionNodeId,
        acSonetLineProtectionSlot,
        acSonetLineProtectionPort
        }
    STATUS current
    DESCRIPTION
    "A protection switching channel mismatch failure has occured on the
    SONET interface."
    
    ::= { acSonetLineTraps 25 }
    
acSonetLineProtectionChannelMismatchClearTrap  NOTIFICATION-TYPE
    OBJECTS { 
        acChassisCurrentTime, acChassisRingId, 
        acSonetLineProtectionNodeId,
        acSonetLineProtectionSlot,
        acSonetLineProtectionPort
        }
    STATUS current
    DESCRIPTION
    "A protection switching channel mismatch failure has cleared on the
    SONET interface."
    
    ::= { acSonetLineTraps 26 }
    
acSonetLineProtectionModeMismatchAlarmTrap  NOTIFICATION-TYPE
    OBJECTS { 
        acChassisCurrentTime, acChassisRingId, 
        acSonetLineProtectionNodeId,
        acSonetLineProtectionSlot,
        acSonetLineProtectionPort
        }
    STATUS current
    DESCRIPTION
    "A protection switching mode mismatch failure has occured on the
    SONET interface."
        
    ::= { acSonetLineTraps 27 }
    
acSonetLineProtectionModeMismatchClearTrap  NOTIFICATION-TYPE
    OBJECTS { 
        acChassisCurrentTime, acChassisRingId, 
        acSonetLineProtectionNodeId,
        acSonetLineProtectionSlot,
        acSonetLineProtectionPort
        }
    STATUS current
    DESCRIPTION
    "A protection switching mode mismatch failure has cleared on the
    SONET interface."
        
    ::= { acSonetLineTraps 28 }
    
acSonetLineProtectionSwitchingByteFailureAlarmTrap  NOTIFICATION-TYPE
    OBJECTS { 
        acChassisCurrentTime, acChassisRingId, 
        acSonetLineProtectionNodeId,
        acSonetLineProtectionSlot,
        acSonetLineProtectionPort
        }
    STATUS current
    DESCRIPTION
    "A protection switching byte failure has been detected on the
    SONET interface."
    
    ::= { acSonetLineTraps 29 }

acSonetLineProtectionSwitchingByteFailureClearTrap  NOTIFICATION-TYPE
    OBJECTS { 
        acChassisCurrentTime, acChassisRingId, 
        acSonetLineProtectionNodeId,
        acSonetLineProtectionSlot,
        acSonetLineProtectionPort
        }
    STATUS current
    DESCRIPTION
    "A protection switching byte failure has been cleared on the
    SONET interface."
    
    ::= { acSonetLineTraps 30 }

END
