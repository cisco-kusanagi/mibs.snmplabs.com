--
-- Copyright 2003-2006 Innominate Security Technologies AG
-- All Rights Reserved
--
-- innominate mGuard 4.0.0.default
--
-- DO NOT MODIFY THIS FILE. Generated from master. Fri May 26 17:25:27 CEST 2006
--

MGUARDB-MIB DEFINITIONS ::= BEGIN

IMPORTS
  enterprises
    FROM RFC1155-SMI
  OBJECT-TYPE
    FROM RFC-1212
  RowStatus, TruthValue, MacAddress
    FROM SNMPv2-TC
  DisplayString
    FROM RFC1213-MIB
  TRAP-TYPE
    FROM RFC-1215;

  innominate       	OBJECT IDENTIFIER ::= { enterprises 15450 }
  mGuardb          	OBJECT IDENTIFIER ::= { innominate  2 }




  mGuardVPN        OBJECT IDENTIFIER ::= { mGuardb 1 }
  mGuardFirewall   OBJECT IDENTIFIER ::= { mGuardb 2 }
  mGuardNetwork    OBJECT IDENTIFIER ::= { mGuardb 3 }
  mGuardSystem     OBJECT IDENTIFIER ::= { mGuardb 4 }
  mGuardSNMP       OBJECT IDENTIFIER ::= { mGuardb 5 }
  mGuardNTP        OBJECT IDENTIFIER ::= { mGuardb 6 }
  mGuardUpdate     OBJECT IDENTIFIER ::= { mGuardb 7 }
  mGuardRedundancy OBJECT IDENTIFIER ::= { mGuardb 9 }
  mGuardInfo       OBJECT IDENTIFIER ::= { mGuardb 10 }
  mGuardLogging    OBJECT IDENTIFIER ::= { mGuardb 11 }
  mGuardContFilt   OBJECT IDENTIFIER ::= { mGuardb 12 }
  mGuardBlade      OBJECT IDENTIFIER ::= { mGuardb 13 }
  mGuardProfile    OBJECT IDENTIFIER ::= { mGuardb 14 }
  mGuardUsers      OBJECT IDENTIFIER ::= { mGuardb 15 }

--
-- IPsec: Local Certificate
--

 mGuardVPNMachine OBJECT IDENTIFIER ::= { mGuardVPN 1 }

 mGuardVPNMachineCert OBJECT-TYPE
   SYNTAX DisplayString
   ACCESS read-write
   STATUS mandatory
   DESCRIPTION
     "Machine certificate and private key of this device."
 ::= { mGuardVPNMachine 1 }

 mGuardVPNMachinePrivate OBJECT-TYPE
   SYNTAX DisplayString
   ACCESS read-write
   STATUS mandatory
   DESCRIPTION
     "Private key"
 ::= { mGuardVPNMachine 2 }


--
-- IPsec: Connection
--

 mGuardVPNConnectionTable OBJECT-TYPE
    SYNTAX SEQUENCE OF MGuardVPNConnectionEntry
    ACCESS not-accessible
    STATUS mandatory
    DESCRIPTION
    "A table containing the configuration of
    the local device's VPN connections."
 ::= { mGuardVPN 2 }

 mGuardVPNConnectionEntry OBJECT-TYPE
    SYNTAX MGuardVPNConnectionEntry
    ACCESS not-accessible
    STATUS mandatory
    DESCRIPTION
       "Configuration of a single VPN connection."
    INDEX { mGuardVPNconIndex }
 ::= { mGuardVPNConnectionTable 1 }

 MGuardVPNConnectionEntry ::= SEQUENCE {
    mGuardVPNconIndex    INTEGER,
    mGuardVPNconName	 DisplayString,
    mGuardVPNconEnabled  INTEGER,
    mGuardVPNremGW	 DisplayString,
    mGuardVPNconType	 INTEGER,
    mGuardVPNlocalNet    IpAddress,
    mGuardVPNlocalMask   IpAddress,
    mGuardVPNremoteNet   IpAddress,
    mGuardVPNremoteMask  IpAddress,
    mGuardVPNauthType    INTEGER,
    mGuardVPNpsk         DisplayString,
    mGuardVPNx509        DisplayString,
    mGuardVPNikeDH       INTEGER,
    mGuardVPNikeHash     INTEGER,
    mGuardVPNipsecHash   INTEGER,
    mGuardVPNikeAlg      INTEGER,
    mGuardVPNipsecAlg    INTEGER,
    mGuardVPNpfs         INTEGER,
    mGuardVPNconStartUp  INTEGER,
    mGuardVPNvirtIPMethod INTEGER,
    mGuardVPNvirtIP      IpAddress,
    mGuardVPNFWLogDefIn  INTEGER,
    mGuardVPNFWLogDefOut  INTEGER,
    mGuardVPNProtoAH     INTEGER,
    mGuardVPNProtoESP    INTEGER,
    mGuardVPNComp        INTEGER,
    mGuardVPNLocalIDMode INTEGER,
    mGuardVPNLocalID       DisplayString,
    mGuardVPNRemoteIDMode  INTEGER,
    mGuardVPNRemoteID      DisplayString,
    mGuardVPNIkeLifetime   INTEGER,
    mGuardVPNIpsecLifetime INTEGER,
    mGuardVPNRekeyMargin   INTEGER,
    mGuardVPNRekeyFuzz     INTEGER,
    mGuardVPNKeyingTries   INTEGER,
    mGuardVPNRekey         INTEGER,
    mGuardVPNDPDAction     INTEGER,
    mGuardVPNDPDDelay      INTEGER,
    mGuardVPNDPDTimeout    INTEGER,
    mGuardVPNRowStatus   RowStatus,
    mGuardVPNAggressive    INTEGER,
    mGuardVPNlocal          DisplayString,
    mGuardVPNremote         DisplayString
 }

   mGuardVPNconIndex OBJECT-TYPE
      SYNTAX INTEGER (1..250)
      ACCESS not-accessible
      STATUS mandatory
      DESCRIPTION
         "Index to identify the connection."
   ::= { mGuardVPNConnectionEntry 1 }

   mGuardVPNconName OBJECT-TYPE
      SYNTAX DisplayString
      ACCESS read-write
      STATUS mandatory
      DESCRIPTION
         "Descriptive name of the connection."
   ::= { mGuardVPNConnectionEntry 2 }

   mGuardVPNconEnabled OBJECT-TYPE
      SYNTAX INTEGER {
                        enabled(1),
                        disabled(2)
                     }
      ACCESS read-write
      STATUS mandatory
      DESCRIPTION
         "Is the connection enabled: yes / no ."
   ::= { mGuardVPNConnectionEntry 3 }

   mGuardVPNremGW OBJECT-TYPE
      SYNTAX DisplayString
      ACCESS read-write
      STATUS mandatory
      DESCRIPTION
         "Remote VPN gateway."
   ::= { mGuardVPNConnectionEntry 4 }

   mGuardVPNconType OBJECT-TYPE
      SYNTAX INTEGER {
			transport(1),
			tunnel(2),
			l2tp-w2k(3),
			l2tp-ssh(4)
		     }
      ACCESS read-write
      STATUS mandatory
      DESCRIPTION
         "Type of VPN connection: transport / tunnel / l2tp-w2k / l2tp-ssh"
   ::= { mGuardVPNConnectionEntry 5 }

   mGuardVPNlocalNet OBJECT-TYPE
      SYNTAX IpAddress
      ACCESS read-write
      STATUS deprecated
      DESCRIPTION
         "Local net address for VPN connection in tunnel mode."
   ::= { mGuardVPNConnectionEntry 6 }


   mGuardVPNlocalMask OBJECT-TYPE
      SYNTAX IpAddress
      ACCESS read-write
      STATUS deprecated
      DESCRIPTION
        "Local netmask for VPN connection in tunnel mode."
   ::= { mGuardVPNConnectionEntry 7 }

   mGuardVPNremoteNet OBJECT-TYPE
      SYNTAX IpAddress
      ACCESS read-write
      STATUS deprecated
      DESCRIPTION
        "Remote net address for VPN connection in tunnel mode."
   ::= { mGuardVPNConnectionEntry 8 }

   mGuardVPNremoteMask OBJECT-TYPE
      SYNTAX IpAddress
      ACCESS read-write
      STATUS deprecated
      DESCRIPTION
        "Remote netmask for VPN connection in tunnel mode."
   ::= { mGuardVPNConnectionEntry 9 }

   mGuardVPNauthType OBJECT-TYPE
     SYNTAX INTEGER {
			psk(1),
			x509(2)
		    }
     ACCESS read-write
     STATUS mandatory
     DESCRIPTION
       "Authentification mode of the VPN connection: psk / x509"
   ::= { mGuardVPNConnectionEntry 10 }

    mGuardVPNpsk OBJECT-TYPE
      SYNTAX DisplayString
      ACCESS read-write
      STATUS mandatory
      DESCRIPTION
       "Pre Shared Secret"
    ::= { mGuardVPNConnectionEntry 11 }

     mGuardVPNx509 OBJECT-TYPE
      SYNTAX DisplayString
      ACCESS read-write
      STATUS mandatory
      DESCRIPTION
       "X.509 certificate"
    ::= { mGuardVPNConnectionEntry 12 }

    mGuardVPNikeDH OBJECT-TYPE
     SYNTAX INTEGER{
                      all(1),
                      modp1024(2),
                      modp1536(3),
                      modp2048(4),
                      modp3072(5),
                      modp4096(6)
                   }
     ACCESS read-write
     STATUS mandatory
     DESCRIPTION
        "IKE DH algorithm."
     ::= { mGuardVPNConnectionEntry 13 }

    mGuardVPNikeHash OBJECT-TYPE
      SYNTAX INTEGER {
			all(1),
			md5(2),
			sha1(3)
		     }
      ACCESS read-write
      STATUS mandatory
      DESCRIPTION
         "IKE hash algorithm: all / md5 / sha1"
    ::= { mGuardVPNConnectionEntry 14 }

    mGuardVPNipsecHash OBJECT-TYPE
       SYNTAX INTEGER {
			all(1),
			md5(2),
			sha1(3)
		     }
       ACCESS read-write
       STATUS mandatory
       DESCRIPTION
         "ipsec hash algorithm: all / md5 / sha1"
    ::= { mGuardVPNConnectionEntry 15 }

     mGuardVPNikeAlg OBJECT-TYPE
        SYNTAX INTEGER {
			des(1),
			tripledes168(2),
			aes128(3),
			aes192(4),
			aes256(5)
		     }
        ACCESS read-write
        STATUS mandatory
        DESCRIPTION
          "IKE encryption algorithm: des / 3des168 / aes128 / aes192 / aes256"
    ::= { mGuardVPNConnectionEntry 16 }

     mGuardVPNipsecAlg OBJECT-TYPE
         SYNTAX INTEGER {
			des(1),
			tripledes168(2),
			aes128(3),
			aes192(4),
			aes256(5),
			null(6)
		     }
         ACCESS read-write
         STATUS mandatory
         DESCRIPTION
           "ipsec encryption algorithm: des/ 3des168 / aes128 / aes192 / aes256 / null"
    ::= { mGuardVPNConnectionEntry 17 }

    mGuardVPNpfs OBJECT-TYPE
         SYNTAX INTEGER {
			no(1),
			all(2),
			modp1024(3),
			modp1536(4),
			modp2048(5),
			modp3072(6),
                        modp4096(7)
		     }
         ACCESS read-write
         STATUS mandatory
         DESCRIPTION
           "ipsec perfect forward secrecy: no / all / modp1024 / modp1536 / modp2048 / modp3072 / modp4096"
    ::= { mGuardVPNConnectionEntry 18 }

    mGuardVPNconStartUp OBJECT-TYPE
      SYNTAX INTEGER {
			initiate(1),
			waitForRemote(2)
		     }
      ACCESS read-write
      STATUS mandatory
      DESCRIPTION
        "Recognize the startup of the VPN connection or wait
         for connection startup of the  remote gateway: yes / no ."
    ::= {  mGuardVPNConnectionEntry 19 }

   mGuardVPNvirtIPMethod OBJECT-TYPE
       SYNTAX INTEGER{
              static(1),
              dhcp-over-ipsec(2)
              }
       ACCESS read-write
       STATUS mandatory
       DESCRIPTION
         "This option isn't implemented yet."
     ::= {  mGuardVPNConnectionEntry 20 }

    mGuardVPNvirtIP OBJECT-TYPE
       SYNTAX IpAddress
       ACCESS read-write
       STATUS mandatory
       DESCRIPTION
         "Virtual IP to use"
     ::= {  mGuardVPNConnectionEntry 21 }

     mGuardVPNFWLogDefIn OBJECT-TYPE
       SYNTAX INTEGER{
                      yes(1),
    		      no(2)
 	             }
	ACCESS read-write
	STATUS mandatory
        DESCRIPTION
	   "Log entries for undefined incoming connection attemps ?"
     ::= { mGuardVPNConnectionEntry 22 }

     mGuardVPNFWLogDefOut OBJECT-TYPE
       SYNTAX INTEGER{
                      yes(1),
    		      no(2)
 	             }
	ACCESS read-write
	STATUS mandatory
        DESCRIPTION
	   "Log entries for undefined outgoing connection attemps ?"
     ::= { mGuardVPNConnectionEntry 23 }


     mGuardVPNProtoAH OBJECT-TYPE
       SYNTAX INTEGER{
                      yes(1),
                      no(2)
                     }
       ACCESS read-write
       STATUS mandatory
       DESCRIPTION
        "Use the AH protocoll. Only 'no' is supported."
     ::= { mGuardVPNConnectionEntry 26 }

     mGuardVPNProtoESP OBJECT-TYPE
       SYNTAX INTEGER{
                      yes(1),
                      no(2)
                     }
       ACCESS read-write
       STATUS mandatory
       DESCRIPTION
        "Use the ESP protocoll. Only 'yes' is supported."
     ::= { mGuardVPNConnectionEntry 27 }

     mGuardVPNComp OBJECT-TYPE
       SYNTAX INTEGER{
                      yes(1),
                      no(2)
                     }
       ACCESS read-write
       STATUS mandatory
       DESCRIPTION
        "Use IPsec compression. Only 'no' is supported."
     ::= { mGuardVPNConnectionEntry 28 }

     mGuardVPNLocalIDMode OBJECT-TYPE
      SYNTAX INTEGER{
                      auto(1),
                      freeswan(2)
                     }
      ACCESS read-write
      STATUS mandatory
      DESCRIPTION
       "Mode for local ID. This option isn't implemented yet."
     ::= { mGuardVPNConnectionEntry 29 }

     mGuardVPNLocalID OBJECT-TYPE
      SYNTAX DisplayString
      ACCESS read-write
      STATUS mandatory
      DESCRIPTION
         "Local ID."
     ::= { mGuardVPNConnectionEntry 30 }

     mGuardVPNRemoteIDMode OBJECT-TYPE
      SYNTAX INTEGER{
                      auto(1),
                      freeswan(2)
                     }
      ACCESS read-write
      STATUS mandatory
      DESCRIPTION
       "Mode for remote ID. This option isn't implemented yet."
     ::= { mGuardVPNConnectionEntry 31 }

     mGuardVPNRemoteID OBJECT-TYPE
      SYNTAX DisplayString
      ACCESS read-write
      STATUS mandatory
      DESCRIPTION
         "Local ID."
     ::= { mGuardVPNConnectionEntry 32 }

    mGuardVPNIkeLifetime OBJECT-TYPE
     SYNTAX INTEGER
     ACCESS read-write
     STATUS mandatory
     DESCRIPTION
       "ISAKMP SA  lifetime (seconds)."
    ::= { mGuardVPNConnectionEntry 33 }

    mGuardVPNIpsecLifetime OBJECT-TYPE
     SYNTAX INTEGER
     ACCESS read-write
     STATUS mandatory
     DESCRIPTION
       "IPSec SA lifetime (seconds)."
    ::= { mGuardVPNConnectionEntry 34 }

    mGuardVPNRekeyMargin OBJECT-TYPE
     SYNTAX INTEGER
     ACCESS read-write
     STATUS mandatory
     DESCRIPTION
       "Rekey Margin (seconds)."
    ::= { mGuardVPNConnectionEntry 35 }

    mGuardVPNRekeyFuzz OBJECT-TYPE
     SYNTAX INTEGER
     ACCESS read-write
     STATUS mandatory
     DESCRIPTION
       "Rekey fuzz (in percent)."
    ::= { mGuardVPNConnectionEntry 36 }

    mGuardVPNKeyingTries OBJECT-TYPE
     SYNTAX INTEGER
     ACCESS read-write
     STATUS mandatory
     DESCRIPTION
       "Rekey fuzz (in percent)."
    ::= { mGuardVPNConnectionEntry 37 }

    mGuardVPNRekey OBJECT-TYPE
     SYNTAX INTEGER{
                     yes(1),
                     no(2)
                    }
     ACCESS read-write
     STATUS mandatory
     DESCRIPTION
      "Renegotiate connection after the keys have expired? Must be set to
      'no' on both end to be effective."
    ::= { mGuardVPNConnectionEntry 38 }

    mGuardVPNDPDAction OBJECT-TYPE
      SYNTAX INTEGER{
                      hold(1),
                      clear(2)
                    }
      ACCESS read-write
      STATUS mandatory
      DESCRIPTION
        "What to do in case DPD found out that the connection is dead:
        'hold': renegotiate connection.
        'clear': clear connection and don't renegotiate."
    ::= { mGuardVPNConnectionEntry 39 }

    mGuardVPNDPDDelay OBJECT-TYPE
      SYNTAX INTEGER
      ACCESS read-write
      STATUS mandatory
      DESCRIPTION
        "Interval in seconds to wait before sending DPD requests when
        the remote end didn't send data. The default value is 30."
    ::= { mGuardVPNConnectionEntry 40 }

    mGuardVPNDPDTimeout OBJECT-TYPE
      SYNTAX INTEGER
      ACCESS read-write
      STATUS mandatory
      DESCRIPTION
        "Interval in seconds before declaring the remote end as dead after
        sending the first DPD request. The default value is 120."
    ::= { mGuardVPNConnectionEntry 41 }

    mGuardVPNRowStatus OBJECT-TYPE
      SYNTAX RowStatus
      ACCESS read-write
      STATUS mandatory
      DESCRIPTION
        "RowStatus"
    ::= { mGuardVPNConnectionEntry 42 }

    mGuardVPNAggressive OBJECT-TYPE
      SYNTAX INTEGER{
                      no(1),
                      yes(2)
                    }
      ACCESS read-write
      STATUS mandatory
      DESCRIPTION
        "Wether to use/accept aggressive mode VPn connections for this one."
    ::= { mGuardVPNConnectionEntry 43 }

   mGuardVPNlocal OBJECT-TYPE
      SYNTAX DisplayString
      ACCESS read-write
      STATUS mandatory
      DESCRIPTION
         "Local network for VPN connection in tunnel mode in CIDR notation."
   ::= { mGuardVPNConnectionEntry 44 }

   mGuardVPNremote OBJECT-TYPE
      SYNTAX DisplayString
      ACCESS read-write
      STATUS mandatory
      DESCRIPTION
         "Remote network for VPN connection in tunnel mode in CIDR notation."
   ::= { mGuardVPNConnectionEntry 45 }


---
--- IPsec: Incoming Firewall
---

  mGuardVPNFW OBJECT IDENTIFIER ::= { mGuardVPN 3 }

  mGuardVPNFWINTable OBJECT-TYPE
    SYNTAX SEQUENCE OF MGuardVPNFWINEntry
    ACCESS not-accessible
    STATUS mandatory
    DESCRIPTION
      "Table of firewall rules for incoming packets."
    ::= { mGuardVPNFW 1 }

    mGuardVPNFWINEntry OBJECT-TYPE
        SYNTAX MGuardVPNFWINEntry
        ACCESS not-accessible
        STATUS mandatory
        DESCRIPTION
            "An entry containing data of a single rule."
        INDEX { mGuardVPNFWINconIndex, mGuardVPNFWINruleIndex }
    ::= { mGuardVPNFWINTable 1 }

    MGuardVPNFWINEntry ::= SEQUENCE{
      mGuardVPNFWINconIndex        INTEGER,
      mGuardVPNFWINruleIndex       INTEGER,
      mGuardVPNFWINsourceIP        DisplayString,
      mGuardVPNFWINdestinationIP   DisplayString,
      mGuardVPNFWINsport           DisplayString,
      mGuardVPNFWINdport           DisplayString,
      mGuardVPNFWINtarget          INTEGER,
      mGuardVPNFWINproto           INTEGER,
      mGuardVPNFWINlog             INTEGER,
      mGuardVPNFWINRowStatus       RowStatus,
      mGuardVPNFWINcomment         DisplayString
    }

    mGuardVPNFWINconIndex OBJECT-TYPE
      SYNTAX   INTEGER (1..250)
      ACCESS   not-accessible
      STATUS   mandatory
      DESCRIPTION
        "Index to identify the rule."
    ::= { mGuardVPNFWINEntry 1 }

    mGuardVPNFWINruleIndex OBJECT-TYPE
      SYNTAX   INTEGER (1..250)
      ACCESS   not-accessible
      STATUS   mandatory
      DESCRIPTION
        "Index to identify the rule."
    ::= { mGuardVPNFWINEntry 2 }

    mGuardVPNFWINsourceIP OBJECT-TYPE
      SYNTAX DisplayString
      ACCESS read-write
      STATUS mandatory
      DESCRIPTION
         "The rule's source IP address"
     ::= { mGuardVPNFWINEntry 3 }

     mGuardVPNFWINdestinationIP OBJECT-TYPE
      SYNTAX DisplayString
      ACCESS read-write
      STATUS mandatory
      DESCRIPTION
         "The rule's source IP address"
     ::= { mGuardVPNFWINEntry 4 }

     mGuardVPNFWINsport OBJECT-TYPE
      SYNTAX DisplayString
      ACCESS read-write
      STATUS mandatory
      DESCRIPTION
         "The rule's source port"
     ::= { mGuardVPNFWINEntry 5 }

      mGuardVPNFWINdport OBJECT-TYPE
      SYNTAX DisplayString
      ACCESS read-write
      STATUS mandatory
      DESCRIPTION
         "The rule's destination port"
     ::= { mGuardVPNFWINEntry 6 }

     mGuardVPNFWINtarget OBJECT-TYPE
       SYNTAX INTEGER {
                        accept(1),
                        reject(2),
                        drop(3)
                      }
       ACCESS read-write
       STATUS mandatory
       DESCRIPTION
          "The rule's target"
     ::= { mGuardVPNFWINEntry 7 }


     mGuardVPNFWINproto OBJECT-TYPE
      SYNTAX INTEGER {
                        tcp(1),
                        udp(2),
                        icmp(3),
                        all(4)
                      }
      ACCESS read-write
      STATUS mandatory
       DESCRIPTION
        "The rule's transport protocol"
     ::= { mGuardVPNFWINEntry 8 }

      mGuardVPNFWINlog OBJECT-TYPE
        SYNTAX INTEGER {
                         yes(1),
                         no(2)
                       }
        ACCESS read-write
        STATUS mandatory
        DESCRIPTION
          "Log packets matching this rule."
        ::= { mGuardVPNFWINEntry 9 }

      mGuardVPNFWINRowStatus OBJECT-TYPE
        SYNTAX RowStatus
        ACCESS read-write
        STATUS mandatory
        DESCRIPTION
           "RowStatus"
      ::= { mGuardVPNFWINEntry 10 }

      mGuardVPNFWINcomment OBJECT-TYPE
        SYNTAX DisplayString
        ACCESS read-write
        STATUS mandatory
        DESCRIPTION
          "Commentary or name for this rule."
        ::= { mGuardVPNFWINEntry 11 }


--
-- IPsec: Outgoing Firewall
--

  mGuardVPNFWOUTTable OBJECT-TYPE
    SYNTAX SEQUENCE OF MGuardVPNFWOUTEntry
    ACCESS not-accessible
    STATUS mandatory
    DESCRIPTION
      "Table of firewall rules for outgoing packets."
    ::= { mGuardVPNFW 2 }

    mGuardVPNFWOUTEntry OBJECT-TYPE
        SYNTAX MGuardVPNFWOUTEntry
        ACCESS not-accessible
        STATUS mandatory
        DESCRIPTION
            "An entry containing data of a single rule."
        INDEX { mGuardVPNFWOUTconIndex, mGuardVPNFWOUTruleIndex }
    ::= { mGuardVPNFWOUTTable 1 }

    MGuardVPNFWOUTEntry ::= SEQUENCE{
      mGuardVPNFWOUTconIndex        INTEGER,
      mGuardVPNFWOUTruleIndex       INTEGER,
      mGuardVPNFWOUTsourceIP        DisplayString,
      mGuardVPNFWOUTdestinationIP   DisplayString,
      mGuardVPNFWOUTsport           DisplayString,
      mGuardVPNFWOUTdport           DisplayString,
      mGuardVPNFWOUTtarget          INTEGER,
      mGuardVPNFWOUTproto           INTEGER,
      mGuardVPNFWOUTlog             INTEGER,
      mGuardVPNFWOUTRowStatus       RowStatus,
      mGuardVPNFWOUTcomment         DisplayString
    }

    mGuardVPNFWOUTconIndex OBJECT-TYPE
      SYNTAX   INTEGER (1..250)
      ACCESS   not-accessible
      STATUS   mandatory
      DESCRIPTION
        "Index to identify the rule."
    ::= { mGuardVPNFWOUTEntry 1 }

    mGuardVPNFWOUTruleIndex OBJECT-TYPE
      SYNTAX   INTEGER (1..250)
      ACCESS   not-accessible
      STATUS   mandatory
      DESCRIPTION
        "Index to identify the rule."
    ::= { mGuardVPNFWOUTEntry 2 }

    mGuardVPNFWOUTsourceIP OBJECT-TYPE
      SYNTAX DisplayString
      ACCESS read-write
      STATUS mandatory
      DESCRIPTION
         "The rule's source IP address"
     ::= { mGuardVPNFWOUTEntry 3 }

     mGuardVPNFWOUTdestinationIP OBJECT-TYPE
      SYNTAX DisplayString
      ACCESS read-write
      STATUS mandatory
      DESCRIPTION
         "The rule's source IP address"
     ::= { mGuardVPNFWOUTEntry 4 }

     mGuardVPNFWOUTsport OBJECT-TYPE
      SYNTAX DisplayString
      ACCESS read-write
      STATUS mandatory
      DESCRIPTION
         "The rule's source port"
     ::= { mGuardVPNFWOUTEntry 5 }

      mGuardVPNFWOUTdport OBJECT-TYPE
      SYNTAX DisplayString
      ACCESS read-write
      STATUS mandatory
      DESCRIPTION
         "The rule's destination port"
     ::= { mGuardVPNFWOUTEntry 6 }

     mGuardVPNFWOUTtarget OBJECT-TYPE
       SYNTAX INTEGER {
                        accept(1),
                        reject(2),
                        drop(3)
                      }
       ACCESS read-write
       STATUS mandatory
       DESCRIPTION
          "The rule's target"
     ::= { mGuardVPNFWOUTEntry 7 }


     mGuardVPNFWOUTproto OBJECT-TYPE
      SYNTAX INTEGER {
                        tcp(1),
                        udp(2),
                        icmp(3),
                        all(4)
                      }
      ACCESS read-write
      STATUS mandatory
       DESCRIPTION
        "The rule's transport protocol"
     ::= { mGuardVPNFWOUTEntry 8 }

      mGuardVPNFWOUTlog OBJECT-TYPE
        SYNTAX INTEGER {
                         yes(1),
                         no(2)
                       }
        ACCESS read-write
        STATUS mandatory
        DESCRIPTION
          "Log packets matching this rule."
        ::= { mGuardVPNFWOUTEntry 9 }

      mGuardVPNFWOUTRowStatus OBJECT-TYPE
        SYNTAX RowStatus
        ACCESS read-write
        STATUS mandatory
        DESCRIPTION
           "RowStatus"
      ::= { mGuardVPNFWOUTEntry 10 }

      mGuardVPNFWOUTcomment OBJECT-TYPE
        SYNTAX DisplayString
        ACCESS read-write
        STATUS mandatory
        DESCRIPTION
          "Commentary or name for this rule."
        ::= { mGuardVPNFWOUTEntry 11 }

--
-- DynDNS Register
--

    mGuardVPNDynDNS OBJECT IDENTIFIER ::= { mGuardVPN 4 }

    mGuardVPNDynDNSRegister OBJECT IDENTIFIER ::= { mGuardVPNDynDNS 1 }

    mGuardVPNDynDNSReg OBJECT-TYPE
     SYNTAX TruthValue
     ACCESS read-write
     STATUS mandatory
     DESCRIPTION
       " Register at a DynDNS service:
         no, yes"
    ::= { mGuardVPNDynDNSRegister 1 }

    mGuardVPNDynDNSRegInterval OBJECT-TYPE
     SYNTAX INTEGER
     ACCESS read-write
     STATUS mandatory
     DESCRIPTION
       " Refresh interval for registration."
    ::= { mGuardVPNDynDNSRegister 2 }

    mGuardVPNDynDNSRegServer OBJECT-TYPE
     SYNTAX DisplayString
     ACCESS read-write
     STATUS mandatory
     DESCRIPTION
       "DynDNS server."
    ::= { mGuardVPNDynDNSRegister 3 }

    mGuardVPNDynDNSRegLogin OBJECT-TYPE
     SYNTAX DisplayString
     ACCESS read-write
     STATUS mandatory
     DESCRIPTION
       "Login for DynDNS server."
    ::= { mGuardVPNDynDNSRegister 4 }

    mGuardVPNDynDNSRegPasswd OBJECT-TYPE
     SYNTAX DisplayString
     ACCESS read-write
     STATUS mandatory
     DESCRIPTION
       "Password for DynDNS server."
    ::= { mGuardVPNDynDNSRegister 5 }

    mGuardVPNDynDNSRegProvider OBJECT-TYPE
      SYNTAX INTEGER {
                       inominate(1),
		       dyndns(2),
		       dns4biz(3)
                     }
      ACCESS read-write
      STATUS mandatory
      DESCRIPTION
        "DynDNS provider"
    ::= { mGuardVPNDynDNSRegister 6 }	

    mGuardVPNDynDNSRegHostname OBJECT-TYPE
          SYNTAX DisplayString
          ACCESS read-write
          STATUS mandatory
          DESCRIPTION
           "Hostname to register"
    ::= { mGuardVPNDynDNSRegister 7 }

--
-- DynDNS Watch
--

    mGuardVPNDynDNSCheck OBJECT IDENTIFIER ::= { mGuardVPNDynDNS 2 }

    mGuardVPNDynDNSCheckDo OBJECT-TYPE
     SYNTAX TruthValue
     ACCESS read-write
     STATUS mandatory
     DESCRIPTION
       "Should hostnames of remote vpn gateways be checked after certain
       time intervals in case they are at a DynDNS provider? : no,yes"
    ::= {  mGuardVPNDynDNSCheck 1 }

    mGuardVPNDynDNSCheckRefresh OBJECT-TYPE
     SYNTAX INTEGER
     ACCESS read-write
     STATUS mandatory
     DESCRIPTION
       "Refresh interval for checking DNS names of remote VPN peers."
    ::= {  mGuardVPNDynDNSCheck 2 }

--
-- IPSec L2TP
--

    mGuardVPNL2TP  OBJECT IDENTIFIER ::= { mGuardVPN 5 }

    mGuardVPNL2TPStart OBJECT-TYPE
     SYNTAX INTEGER {
			enabled(1),
			disabled(2)
		    }
     ACCESS read-write
     STATUS mandatory
     DESCRIPTION
       "Start the L2TP Server ? yes,no"
    ::= { mGuardVPNL2TP 1 }

    mGuardVPNL2TPLocalIP OBJECT-TYPE
     SYNTAX IpAddress
     ACCESS read-write
     STATUS mandatory
     DESCRIPTION
       "Local IP for L2TP connections"
    ::= { mGuardVPNL2TP 2 }

    mGuardVPNL2TPRemoteIPRangeStart OBJECT-TYPE
     SYNTAX IpAddress
     ACCESS read-write
     STATUS mandatory
     DESCRIPTION
       "Start of range of remote IPs."
    ::= { mGuardVPNL2TP 3 }

    mGuardVPNL2TPRemoteIPRangeEnd OBJECT-TYPE
     SYNTAX IpAddress
     ACCESS read-write
     STATUS mandatory
     DESCRIPTION
       "End of range of remote IPs."
    ::= { mGuardVPNL2TP 4 }

    mGuardVPNL2TPpppdOptTable OBJECT-TYPE
      SYNTAX SEQUENCE OF MGuardVPNL2TPpppdOptEntry
      ACCESS not-accessible
      STATUS mandatory
      DESCRIPTION
        "A table of options set for the pppd process implementing IPsec/L2TP."
     ::= { mGuardVPNL2TP 5 }

    mGuardVPNL2TPpppdOptEntry OBJECT-TYPE
        SYNTAX MGuardVPNL2TPpppdOptEntry
        ACCESS not-accessible
        STATUS mandatory
        DESCRIPTION
         "A single option set for pppd. "
        INDEX { mGuardVPNL2TPpppdOptIndex }
    ::= { mGuardVPNL2TPpppdOptTable 1 }

    MGuardVPNL2TPpppdOptEntry  ::= SEQUENCE {
       mGuardVPNL2TPpppdOptIndex     INTEGER,
       mGuardVPNL2TPpppdOptValue     DisplayString,
       mGuardVPNL2TPpppdOptRowStatus RowStatus
    }

    mGuardVPNL2TPpppdOptIndex OBJECT-TYPE
      SYNTAX INTEGER (1..100)
      ACCESS not-accessible
      STATUS mandatory
      DESCRIPTION
        "Table index."
     ::= { mGuardVPNL2TPpppdOptEntry 1 }

     mGuardVPNL2TPpppdOptValue OBJECT-TYPE
      SYNTAX DisplayString
      ACCESS read-write
      STATUS mandatory
      DESCRIPTION
        "The pppd option."
     ::= { mGuardVPNL2TPpppdOptEntry 2 }

     mGuardVPNL2TPpppdOptRowStatus OBJECT-TYPE
      SYNTAX RowStatus
      ACCESS read-write
      STATUS mandatory
      DESCRIPTION
        "Row Status"
     ::= { mGuardVPNL2TPpppdOptEntry 3 }

--
-- IPsec Options
--

   mGuardVPNSettings  OBJECT IDENTIFIER ::= { mGuardVPN 6 }

   mGuardVPNRequireUniqueIDs OBJECT-TYPE
    SYNTAX INTEGER{
                    yes(1),
		    no(2)
                  }	
    ACCESS read-write
    STATUS mandatory
    DESCRIPTION
     "Allow only one open connection per identity (ie. X.509 certificate)."
   ::= { mGuardVPNSettings 1 }

   mGuardVPNNatTraversal OBJECT-TYPE
    SYNTAX INTEGER{
                    on(1),
                    off(2)
                  }
    ACCESS read-write
    STATUS mandatory
    DESCRIPTION
     "Encapsulate ESP traffic into IKE (UDP) packets to pass IPsec unaware NAT routers."
   ::= { mGuardVPNSettings 2 }

   mGuardVPNNatTPortfloating OBJECT-TYPE
    SYNTAX INTEGER{
                    on(1),
                    off(2)
                  }
    ACCESS read-write
    STATUS mandatory
    DESCRIPTION
     "Some NAT routers fail to perform NAT originating low UDP ports. This option moves IKE from UDP 500 to UDP 4500 if possible"
   ::= { mGuardVPNSettings 3 }

   mGuardVPNNatTKeepAliveInterval OBJECT-TYPE
    SYNTAX INTEGER
    ACCESS read-write
    STATUS mandatory
    DESCRIPTION
     "NAT-T Keepalive Interval (in seconds).
      Keepalives will tell the NAT router not to close the connection. "
   ::= { mGuardVPNSettings 4 }

   mGuardVPNNatTKeepAliveForce OBJECT-TYPE
    SYNTAX INTEGER{
                    yes(1),
                    no(2)
                  }
    ACCESS read-write
    STATUS mandatory
    DESCRIPTION
     "Force NAT-T Keepalive ?"
   ::= { mGuardVPNSettings 5 }

   mGuardVPNIkeLog OBJECT-TYPE
    SYNTAX INTEGER{
                    yes(1),
                    no(2)
                  }
    ACCESS read-write
    STATUS mandatory
    DESCRIPTION
     "Log verbose information on IKE ?"
   ::= { mGuardVPNSettings 6 }

   mGuardVPNHideTos OBJECT-TYPE
    SYNTAX INTEGER{
                    yes(1),
                    no(2)
                  }
    ACCESS read-write
    STATUS mandatory
    DESCRIPTION
     "When set to yes the TOS bit will be cleared on IPsec output. "
  ::= { mGuardVPNSettings 7 }

   mGuardVPNmtu OBJECT-TYPE
    SYNTAX INTEGER
    ACCESS read-write
    STATUS mandatory
    DESCRIPTION
     "ipsec0 mtu"
   ::= { mGuardVPNSettings 8 }

   mGuardVPNStrictCRLPolicy OBJECT-TYPE
    SYNTAX INTEGER{
                    yes(1),
                    no(2)
                  }
    ACCESS read-write
    STATUS mandatory
    DESCRIPTION
     "Use a strict CRL policy?"
   ::= { mGuardVPNSettings 9 }

   mGuardVPNNoCertReqSend OBJECT-TYPE
    SYNTAX INTEGER{
                    yes(1),
                    no(2)
                  }
    ACCESS read-write
    STATUS mandatory
    DESCRIPTION
     "Don't send certificate requests?"
   ::= { mGuardVPNSettings 10 }

--
-- Firewall Incoming
--

   mGuardFirewallIncoming  OBJECT IDENTIFIER ::= { mGuardFirewall 1 }

   mGuardFirewallIncomingTable OBJECT-TYPE
     SYNTAX SEQUENCE OF MGuardFirewallIncomingEntry
     ACCESS not-accessible
     STATUS mandatory
     DESCRIPTION
        "A table containing firewall rules for incoming  packets."
   ::= { mGuardFirewallIncoming 1 }

    mGuardFirewallIncomingEntry OBJECT-TYPE
      SYNTAX MGuardFirewallIncomingEntry
      ACCESS not-accessible
      STATUS mandatory
      DESCRIPTION
       "An entry containing data of a single rule."
      INDEX { mGuardFWINruleIndex }
    ::= { mGuardFirewallIncomingTable 1 }

    MGuardFirewallIncomingEntry ::= SEQUENCE{
      mGuardFWINruleIndex       INTEGER,
      mGuardFWINsourceIP        DisplayString,
      mGuardFWINdestinationIP   DisplayString,
      mGuardFWINsport           DisplayString,
      mGuardFWINdport           DisplayString,
      mGuardFWINtarget          INTEGER,
      mGuardFWINproto           INTEGER,
      mGuardFWINlog             INTEGER,
      mGuardFWINRowStatus       RowStatus,
      mGuardFWINcomment         DisplayString
    }

    mGuardFWINruleIndex OBJECT-TYPE
      SYNTAX   INTEGER (1..250)
      ACCESS   not-accessible
      STATUS   mandatory
      DESCRIPTION
        "Index to identify the rule."
    ::= { mGuardFirewallIncomingEntry 1 }

    mGuardFWINsourceIP OBJECT-TYPE
      SYNTAX DisplayString
      ACCESS read-write
      STATUS mandatory
      DESCRIPTION
         "The rule's source IP address"
     ::= { mGuardFirewallIncomingEntry 2 }

    mGuardFWINdestinationIP OBJECT-TYPE
      SYNTAX DisplayString
      ACCESS read-write
      STATUS mandatory
      DESCRIPTION
         "The rule's source IP address"
     ::= { mGuardFirewallIncomingEntry 3 }

     mGuardFWINsport OBJECT-TYPE
      SYNTAX DisplayString
      ACCESS read-write
      STATUS mandatory
      DESCRIPTION
         "The rule's source port"
     ::= { mGuardFirewallIncomingEntry 4 }

     mGuardFWINdport OBJECT-TYPE
      SYNTAX DisplayString
      ACCESS read-write
      STATUS mandatory
      DESCRIPTION
         "The rule's destination port"
     ::= { mGuardFirewallIncomingEntry 5 }

     mGuardFWINtarget OBJECT-TYPE
       SYNTAX INTEGER {
			accept(1),
			reject(2),
			drop(3)
		      }
       ACCESS read-write
       STATUS mandatory
       DESCRIPTION
          "The rule's target"
     ::= { mGuardFirewallIncomingEntry 6 }

     mGuardFWINproto OBJECT-TYPE
      SYNTAX INTEGER {
			tcp(1),
			udp(2),
			icmp(3),
			all(4)
		      }
      ACCESS read-write
      STATUS mandatory
       DESCRIPTION
        "The rule's transport protocol"
     ::= { mGuardFirewallIncomingEntry 7 }

      mGuardFWINlog OBJECT-TYPE
        SYNTAX INTEGER {
	                 yes(1),
			 no(2)
		       }
        ACCESS read-write
        STATUS mandatory
        DESCRIPTION
	  " Log packets matching this rule ?"
       	::= { mGuardFirewallIncomingEntry 8 }

      mGuardFWINRowStatus OBJECT-TYPE
        SYNTAX RowStatus
        ACCESS read-write
        STATUS mandatory
        DESCRIPTION
           "RowStatus"
      ::= { mGuardFirewallIncomingEntry 9 }

       mGuardFWINcomment OBJECT-TYPE
        SYNTAX DisplayString
        ACCESS read-write
        STATUS mandatory
        DESCRIPTION
          "Commentary or name for this rule."
        ::= { mGuardFirewallIncomingEntry 10 }

     mGuardFirewallINLogDefault OBJECT-TYPE
     SYNTAX INTEGER  {
                       yes(1),
		       no(2)
		     }
     ACCESS read-write
     STATUS mandatory
     DESCRIPTION
        "Log entries for unknown connection attemps ?"
   ::= { mGuardFirewallIncoming 2 }

--
-- Firewall Outgoing
--

   mGuardFirewallOutgoing  OBJECT IDENTIFIER ::= { mGuardFirewall 2 }

   mGuardFirewallOutgoingTable OBJECT-TYPE
     SYNTAX SEQUENCE OF MGuardFirewallOutgoingEntry
     ACCESS not-accessible
     STATUS mandatory
     DESCRIPTION
        "A table containing firewall rules for outgoing  packets."
   ::= { mGuardFirewallOutgoing 1 }

    mGuardFirewallOutgoingEntry OBJECT-TYPE
      SYNTAX MGuardFirewallOutgoingEntry
      ACCESS not-accessible
      STATUS mandatory
      DESCRIPTION
       "An entry containing data of a single rule."
      INDEX { mGuardFWOUTruleIndex }
    ::= { mGuardFirewallOutgoingTable 1 }


    MGuardFirewallOutgoingEntry ::= SEQUENCE {
      mGuardFWOUTruleIndex       INTEGER,
      mGuardFWOUTsourceIP        DisplayString,
      mGuardFWOUTdestinationIP   DisplayString,
      mGuardFWOUTsport           DisplayString,
      mGuardFWOUTdport           DisplayString,
      mGuardFWOUTtarget          INTEGER,
      mGuardFWOUTproto           INTEGER,
      mGuardFWOUTlog             INTEGER,
      mGuardFWOUTRowStatus	 RowStatus,
      mGuardFWOUTcomment         DisplayString
    }

    mGuardFWOUTruleIndex OBJECT-TYPE
      SYNTAX   INTEGER (1..250)
      ACCESS   not-accessible
      STATUS   mandatory
      DESCRIPTION
        "Index to identify the rule."
    ::= { mGuardFirewallOutgoingEntry 1 }

     mGuardFWOUTsourceIP OBJECT-TYPE
      SYNTAX DisplayString
      ACCESS read-write
      STATUS mandatory
      DESCRIPTION
         "The rule's source IP address"
     ::= { mGuardFirewallOutgoingEntry 2 }

     mGuardFWOUTdestinationIP OBJECT-TYPE
      SYNTAX DisplayString
      ACCESS read-write
      STATUS mandatory
      DESCRIPTION
         "The rule's source IP address"
     ::= { mGuardFirewallOutgoingEntry 3 }

     mGuardFWOUTsport OBJECT-TYPE
      SYNTAX DisplayString
      ACCESS read-write
      STATUS mandatory
      DESCRIPTION
         "The rule's source port"
     ::= { mGuardFirewallOutgoingEntry 4 }

     mGuardFWOUTdport OBJECT-TYPE
      SYNTAX DisplayString
      ACCESS read-write
      STATUS mandatory
      DESCRIPTION
         "The rule's destination port"
     ::= { mGuardFirewallOutgoingEntry 5 }

     mGuardFWOUTtarget OBJECT-TYPE
       SYNTAX INTEGER {
			accept(1),
			reject(2),
			drop(3)
		      }
       ACCESS read-write
       STATUS mandatory
       DESCRIPTION
          "The rule's target"
     ::= { mGuardFirewallOutgoingEntry 6 }

    mGuardFWOUTproto OBJECT-TYPE
      SYNTAX INTEGER {
			tcp(1),
			udp(2),
			icmp(3),
			all(4)
		      }
      ACCESS read-write
      STATUS mandatory
       DESCRIPTION
        "The rule's transport protocol"
     ::= { mGuardFirewallOutgoingEntry 7 }

    mGuardFWOUTlog OBJECT-TYPE
      SYNTAX INTEGER {
                       yes(1),
                       no(2)
                     }
      ACCESS read-write
      STATUS mandatory
      DESCRIPTION
        " Log packets matching this rule ?"
      ::= { mGuardFirewallOutgoingEntry 8 }

    mGuardFWOUTRowStatus OBJECT-TYPE
        SYNTAX RowStatus
        ACCESS read-write
        STATUS mandatory
        DESCRIPTION
           "RowStatus"
      ::= { mGuardFirewallOutgoingEntry 9 }

      mGuardFWOUTcomment OBJECT-TYPE
       SYNTAX DisplayString
       ACCESS read-write
       STATUS mandatory
       DESCRIPTION
         "Commentary or name for this rule."
       ::= { mGuardFirewallOutgoingEntry 10 }
	
   mGuardFirewallOUTLogDefault OBJECT-TYPE
     SYNTAX INTEGER  {
                       yes(1),
		       no(2)
		     }
     ACCESS read-write
     STATUS mandatory
     DESCRIPTION
        "Log entries for unknown connection attemps ?"
   ::= { mGuardFirewallOutgoing 2 }

--
-- Firwall Portforwarding
--

  mGuardFirewallPortforwarding OBJECT IDENTIFIER ::= { mGuardFirewall 3 }

  mGuardFirewallPortforwardTable OBJECT-TYPE
     SYNTAX SEQUENCE OF MGuardFirewallPortforwardEntry
     ACCESS not-accessible
     STATUS mandatory
     DESCRIPTION
        "A table containing firewall rules for portforwarding."
   ::= { mGuardFirewallPortforwarding 1 }

    mGuardFirewallPortforwardEntry OBJECT-TYPE
      SYNTAX MGuardFirewallPortforwardEntry
      ACCESS not-accessible
      STATUS mandatory
      DESCRIPTION
       "An entry containing data of a single rule."
      INDEX { mGuardFWPORTFORWruleIndex }
    ::= { mGuardFirewallPortforwardTable 1 }

    MGuardFirewallPortforwardEntry ::= SEQUENCE{
      mGuardFWPORTFORWruleIndex       INTEGER,
      mGuardFWPORTFORWinIP        DisplayString,
      mGuardFWPORTFORWoutIP       DisplayString,
      mGuardFWPORTFORWinport      DisplayString,
      mGuardFWPORTFORWoutport     DisplayString,
      mGuardFWPORTFORWproto       INTEGER,
      mGuardFWPORTFORWlog         INTEGER,
      mGuardFWPORTFORWRowStatus   RowStatus,
      mGuardFWPORTFORWsrcIP       DisplayString,
      mGuardFWPORTFORWsrcport     DisplayString,
      mGuardFWPORTFORWcomment     DisplayString
    }

    mGuardFWPORTFORWruleIndex OBJECT-TYPE
      SYNTAX   INTEGER (1..250)
      ACCESS   not-accessible
      STATUS   mandatory
      DESCRIPTION
        "Index to identify the rule."
    ::= { mGuardFirewallPortforwardEntry 1 }

    mGuardFWPORTFORWinIP OBJECT-TYPE
      SYNTAX DisplayString
      ACCESS read-write
      STATUS mandatory
      DESCRIPTION
         "The rule's incoming IP address"
     ::= { mGuardFirewallPortforwardEntry 2 }

    mGuardFWPORTFORWoutIP OBJECT-TYPE
      SYNTAX DisplayString
      ACCESS read-write
      STATUS mandatory
      DESCRIPTION
         "The rule's redirect IP address"
     ::= { mGuardFirewallPortforwardEntry 3 }

    mGuardFWPORTFORWinport OBJECT-TYPE
      SYNTAX DisplayString
      ACCESS read-write
      STATUS mandatory
      DESCRIPTION
         "The rule's incoming port"
     ::= { mGuardFirewallPortforwardEntry 4 }

    mGuardFWPORTFORWoutport OBJECT-TYPE
      SYNTAX DisplayString
      ACCESS read-write
      STATUS mandatory
      DESCRIPTION
         "The rule's destination port"
     ::= { mGuardFirewallPortforwardEntry 5 }

    mGuardFWPORTFORWproto OBJECT-TYPE
      SYNTAX INTEGER {
			tcp(1),
			udp(2)
		      }
      ACCESS read-write
      STATUS mandatory
       DESCRIPTION
        "The rule's transport protocol"
     ::= { mGuardFirewallPortforwardEntry 6 }

    mGuardFWPORTFORWlog OBJECT-TYPE
      SYNTAX INTEGER {
                       yes(1),
                       no(2)
                     }
      ACCESS read-write
      STATUS mandatory
      DESCRIPTION
        " Log packets matching this rule ?"
      ::= { mGuardFirewallPortforwardEntry 7 }

    mGuardFWPORTFORWRowStatus OBJECT-TYPE
        SYNTAX RowStatus
        ACCESS read-write
        STATUS mandatory
        DESCRIPTION
           "RowStatus"
      ::= { mGuardFirewallPortforwardEntry 8 }

    mGuardFWPORTFORWsrcIP OBJECT-TYPE
      SYNTAX DisplayString
      ACCESS read-write
      STATUS mandatory
      DESCRIPTION
         "The rule's source IP address"
     ::= { mGuardFirewallPortforwardEntry 9 }

    mGuardFWPORTFORWsrcport OBJECT-TYPE
      SYNTAX DisplayString
      ACCESS read-write
      STATUS mandatory
      DESCRIPTION
         "The rule's source port"
     ::= { mGuardFirewallPortforwardEntry 10 }

     mGuardFWPORTFORWcomment OBJECT-TYPE
      SYNTAX DisplayString
      ACCESS read-write
      STATUS mandatory
      DESCRIPTION
        "Commentary or name for this rule."
      ::= { mGuardFirewallPortforwardEntry 11 }

--
-- Firewall NAT
--

   mGuardFirewallNAT OBJECT IDENTIFIER ::= { mGuardFirewall 4 }

   mGuardFirewallNATRuleTable OBJECT-TYPE
     SYNTAX SEQUENCE OF MGuardFirewallNATRuleEntry
     ACCESS not-accessible
     STATUS mandatory
     DESCRIPTION
        "A table containing firewall rules for network address translation."
   ::= { mGuardFirewallNAT 1 }

    mGuardFirewallNATRuleEntry OBJECT-TYPE
      SYNTAX MGuardFirewallNATRuleEntry
      ACCESS not-accessible
      STATUS mandatory
      DESCRIPTION
       "An entry containing data of a single rule."
      INDEX { mGuardFWNATruleIndex }
    ::= { mGuardFirewallNATRuleTable 1 }


    MGuardFirewallNATRuleEntry ::= SEQUENCE{
      mGuardFWNATruleIndex       INTEGER,
      mGuardFWNATIP              DisplayString,
      mGuardFWNATRowStatus       RowStatus,
      mGuardFWNATOutIP           DisplayString
    }

    mGuardFWNATruleIndex OBJECT-TYPE
      SYNTAX   INTEGER (1..250)
      ACCESS   not-accessible
      STATUS   mandatory
      DESCRIPTION
        "Index to identify the rule."
    ::= { mGuardFirewallNATRuleEntry 1 }

    mGuardFWNATIP OBJECT-TYPE
      SYNTAX DisplayString
      ACCESS read-write
      STATUS mandatory
      DESCRIPTION
         "The rule's source IP address"
     ::= { mGuardFirewallNATRuleEntry 2 }

    mGuardFWNATRowStatus OBJECT-TYPE
        SYNTAX RowStatus
        ACCESS read-write
        STATUS mandatory
        DESCRIPTION
           "RowStatus"
      ::= { mGuardFirewallNATRuleEntry 3 }

    mGuardFWNATOutIP OBJECT-TYPE
      SYNTAX DisplayString
      ACCESS read-write
      STATUS mandatory
      DESCRIPTION
         "Reserved for future use"
     ::= { mGuardFirewallNATRuleEntry 4 }

--
-- Firewall Extended Settings
--

    mGuardFirewallExtended  OBJECT IDENTIFIER ::= { mGuardFirewall 5 }

    mGuardFirewallIPConntrackMax OBJECT-TYPE
     SYNTAX INTEGER
     ACCESS read-write
     STATUS mandatory
     DESCRIPTION
      "Maximum size of connection tracking table"
    ::= { mGuardFirewallExtended 1 }

    mGuardFirewallIPSynfloodLimitInt OBJECT-TYPE
     SYNTAX INTEGER
     ACCESS read-write
     STATUS mandatory
     DESCRIPTION
      "Maximum number of new outgoing TCP connections (SYN) per second"
    ::= { mGuardFirewallExtended 2 }

    mGuardFirewallIPSynfloodLimitExt OBJECT-TYPE
     SYNTAX INTEGER
     ACCESS read-write
     STATUS mandatory
     DESCRIPTION
      "Maximum number of new incoming TCP connections (SYN) per second"
    ::= { mGuardFirewallExtended  3 }

    mGuardFirewallICMPLimitInt OBJECT-TYPE
     SYNTAX INTEGER
     ACCESS read-write
     STATUS mandatory
     DESCRIPTION
      "Maximum number of outgoing ping frames (ICMP Echo Request) per second"
    ::= { mGuardFirewallExtended  4 }

    mGuardFirewallICMPLimitExt OBJECT-TYPE
     SYNTAX INTEGER
     ACCESS read-write
     STATUS mandatory
     DESCRIPTION
      "Maximum number of incoming ping frames (ICMP Echo Request) per second"
    ::= { mGuardFirewallExtended  5 }

    mGuardFirewallEnableConntrackFTP OBJECT-TYPE
     SYNTAX INTEGER {
                       yes(1),
                       no(2)
                    }
     ACCESS read-write
     STATUS mandatory
     DESCRIPTION
      "Enable active FTP NAT/Connection Tracking support"
    ::= { mGuardFirewallExtended 6 }

    mGuardFirewallConntrackIRC OBJECT-TYPE
     SYNTAX INTEGER {
                       yes(1),
                       no(2)
                    }
     ACCESS read-write
     STATUS mandatory
     DESCRIPTION
      "Enable IRC NAT/Connection Tracking support"
    ::= { mGuardFirewallExtended 7 }

    mGuardFirewallConntrackPPTP OBJECT-TYPE
     SYNTAX INTEGER {
                       yes(1),
                       no(2)
                    }
     ACCESS read-write
     STATUS mandatory
     DESCRIPTION
      "Enable PPTP NAT/Connection Tracking support"
    ::= { mGuardFirewallExtended 8 }

   mGuardFirewallARPLimitInt OBJECT-TYPE
     SYNTAX INTEGER
     ACCESS read-write
     STATUS mandatory
     DESCRIPTION
      "Maximum number of outgoing arp request frames per second (stealth mode only)"
    ::= { mGuardFirewallExtended  9 }

   mGuardFirewallARPLimitExt OBJECT-TYPE
     SYNTAX INTEGER
     ACCESS read-write
     STATUS mandatory
     DESCRIPTION
      "Maximum number of incoming arp request frames per second (stealth mode only)"
    ::= { mGuardFirewallExtended  10 }

   mGuardFirewallICMPPolicy OBJECT-TYPE
     SYNTAX INTEGER {
                       drop(1),
                       ping(2),
		       all(3)
                    }
     ACCESS read-write
     STATUS mandatory
     DESCRIPTION
      "Allow incoming ICMP frames to the mGuard itself (router modes only):
       drop: default, ping: allow incoming ICMP echo request (required to
       answer ping), all: allow all incoming ICMP request to reach the TCP
       stack.
       Note: ICMP packets related to established connections are handled
       by the connection tracking. This setting is used for unrelated ICMP
       traffic."
    ::= { mGuardFirewallExtended 11 }

    mGuardFirewallConntrackH323 OBJECT-TYPE
     SYNTAX INTEGER {
                       yes(1),
                       no(2)
                    }
     ACCESS read-write
     STATUS mandatory
     DESCRIPTION
      "Enable H323 NAT/Connection Tracking support"
    ::= { mGuardFirewallExtended 12 }

    mGuardFirewallIpUncleanMatch OBJECT-TYPE
     SYNTAX INTEGER {
                       yes(1),
                       no(2)
                    }
     ACCESS read-write
     STATUS mandatory
     DESCRIPTION
      "Enable IP Unclean Match"
    ::= { mGuardFirewallExtended 13 }


--
-- Firewall 1:1 NAT
--

   mGuardFirewall11NAT OBJECT IDENTIFIER ::= { mGuardFirewall 6 }

   mGuardFirewall11NATRuleTable OBJECT-TYPE
     SYNTAX SEQUENCE OF MGuardFirewall11NATRuleEntry
     ACCESS not-accessible
     STATUS mandatory
     DESCRIPTION
        "A table containing firewall rules for network address translation."
   ::= { mGuardFirewall11NAT 1 }

    mGuardFirewall11NATRuleEntry OBJECT-TYPE
      SYNTAX MGuardFirewall11NATRuleEntry
      ACCESS not-accessible
      STATUS mandatory
      DESCRIPTION
       "An entry containing data of a single rule."
      INDEX { mGuardFW11NATruleIndex }
    ::= { mGuardFirewall11NATRuleTable 1 }


    MGuardFirewall11NATRuleEntry ::= SEQUENCE{
      mGuardFW11NATruleIndex     INTEGER,
      mGuardFW11NATLocal         IpAddress,
      mGuardFW11NATRemote        IpAddress,
      mGuardFW11NATMask          INTEGER,
      mGuardFW11NATLog		 INTEGER,
      mGuardFW11NATRowStatus     RowStatus
    }

    mGuardFW11NATruleIndex OBJECT-TYPE
      SYNTAX   INTEGER (1..250)
      ACCESS   not-accessible
      STATUS   mandatory
      DESCRIPTION
        "Index to identify the rule."
    ::= { mGuardFirewall11NATRuleEntry 1 }

    mGuardFW11NATLocal OBJECT-TYPE
      SYNTAX IpAddress
      ACCESS read-write
      STATUS mandatory
      DESCRIPTION
         "Network for 1:1 NAT on local interface."
     ::= { mGuardFirewall11NATRuleEntry 2 }

    mGuardFW11NATRemote OBJECT-TYPE
      SYNTAX IpAddress
      ACCESS read-write
      STATUS mandatory
      DESCRIPTION
         "Network for 1:1 NAT on remote interface."
     ::= { mGuardFirewall11NATRuleEntry 3 }

    mGuardFW11NATMask OBJECT-TYPE
      SYNTAX INTEGER
      ACCESS read-write
      STATUS mandatory
      DESCRIPTION
         "Netmask for 1:1 NAT between 0 and 32."
     ::= { mGuardFirewall11NATRuleEntry 4 }

    mGuardFW11NATLog OBJECT-TYPE
      SYNTAX INTEGER {
        yes(1),
        no(2)
      }
      ACCESS read-write
      STATUS mandatory
      DESCRIPTION
         "Log entries for this rule?"
     ::= { mGuardFirewall11NATRuleEntry 5 }

    mGuardFW11NATRowStatus OBJECT-TYPE
        SYNTAX RowStatus
        ACCESS read-write
        STATUS mandatory
        DESCRIPTION
           "RowStatus"
      ::= { mGuardFirewall11NATRuleEntry 10 }

--
-- User Firewall
--

  mGuardFirewallUserFW OBJECT IDENTIFIER ::= { mGuardFirewall 7 }

  mGuardFirewallUserFWEnabled OBJECT-TYPE
    SYNTAX INTEGER {
			enabled(1),
			disabled(2)
                   }
    ACCESS read-write
    STATUS mandatory
    DESCRIPTION
      "Enable the user firewall."
  ::= { mGuardFirewallUserFW 1 }

  mGuardFirewallUserFWTemplateTable OBJECT-TYPE
    SYNTAX SEQUENCE OF MGuardFirewallUserFWTemplateEntry
    ACCESS not-accessible
    STATUS mandatory
    DESCRIPTION
      "A table containing user firewall templates."
  ::= { mGuardFirewallUserFW 2 }

  mGuardFirewallUserFWTemplateEntry OBJECT-TYPE
    SYNTAX MGuardFirewallUserFWTemplateEntry
    ACCESS not-accessible
    STATUS mandatory
    DESCRIPTION
      "An entry containing a single user firewall template."
    INDEX { mGuardFirewallUserFWTemplateIndex }
  ::= { mGuardFirewallUserFWTemplateTable 1 }

  MGuardFirewallUserFWTemplateEntry ::= SEQUENCE {
    mGuardFirewallUserFWTemplateIndex     INTEGER,
    mGuardFirewallUserFWTemplateEnabled   INTEGER,
    mGuardFirewallUserFWTemplateName      DisplayString,
    mGuardFirewallUserFWTemplateComment   DisplayString,
    mGuardFirewallUserFWTemplateTimeout   INTEGER,
    mGuardFirewallUserFWTemplateSrcIP     DisplayString,
    mGuardFirewallUserFWTemplateRowStatus RowStatus
  }

  mGuardFirewallUserFWTemplateIndex OBJECT-TYPE
    SYNTAX INTEGER (1..100)
    ACCESS not-accessible
    STATUS mandatory
    DESCRIPTION
      "Index to identify the user firewall template entry."
  ::= { mGuardFirewallUserFWTemplateEntry 1 }

  mGuardFirewallUserFWTemplateEnabled OBJECT-TYPE
    SYNTAX INTEGER {
			enabled(1),
			disabled(2)
                   }
    ACCESS read-write
    STATUS mandatory
    DESCRIPTION
      "Enable this user firewall template."
  ::= { mGuardFirewallUserFWTemplateEntry 2 }

  mGuardFirewallUserFWTemplateName OBJECT-TYPE
    SYNTAX DisplayString
    ACCESS read-write
    STATUS mandatory
    DESCRIPTION
      "A descriptive name of the user firewall template."
  ::= { mGuardFirewallUserFWTemplateEntry 3 }

  mGuardFirewallUserFWTemplateComment OBJECT-TYPE
    SYNTAX DisplayString
    ACCESS read-write
    STATUS mandatory
    DESCRIPTION
      "A comment associated with the user firewall template."
  ::= { mGuardFirewallUserFWTemplateEntry 4 }

  mGuardFirewallUserFWTemplateTimeout OBJECT-TYPE
    SYNTAX INTEGER (1..86400)
    ACCESS read-write
    STATUS mandatory
    DESCRIPTION
      "The timeout in seconds of the user firewall template."
  ::= { mGuardFirewallUserFWTemplateEntry 5 }

  mGuardFirewallUserFWTemplateSrcIP OBJECT-TYPE
    SYNTAX DisplayString
    ACCESS read-write
    STATUS mandatory
    DESCRIPTION
      "The source IP address of the user firewall template."
  ::= { mGuardFirewallUserFWTemplateEntry 6 }

  mGuardFirewallUserFWTemplateRowStatus OBJECT-TYPE
    SYNTAX RowStatus
    ACCESS read-write
    STATUS mandatory
    DESCRIPTION
      "Row Status"
  ::= { mGuardFirewallUserFWTemplateEntry 7 }

  mGuardFirewallUserFWTemplateUserTable OBJECT-TYPE
    SYNTAX SEQUENCE OF MGuardFirewallUserFWTemplateUserEntry
    ACCESS not-accessible
    STATUS mandatory
    DESCRIPTION
      "A table containing the users associated with a user firewall template."
  ::= { mGuardFirewallUserFW 3 }

  mGuardFirewallUserFWTemplateUserEntry OBJECT-TYPE
    SYNTAX MGuardFirewallUserFWTemplateUserEntry
    ACCESS not-accessible
    STATUS mandatory
    DESCRIPTION
      "An entry containing a single user associated with a user firewall template."
    INDEX { mGuardFirewallUserFWTemplateUserTemplateIndex, mGuardFirewallUserFWTemplateUserIndex }
  ::= { mGuardFirewallUserFWTemplateUserTable 1 }

  MGuardFirewallUserFWTemplateUserEntry ::= SEQUENCE {
    mGuardFirewallUserFWTemplateUserTemplateIndex INTEGER,
    mGuardFirewallUserFWTemplateUserIndex         INTEGER,
    mGuardFirewallUserFWTemplateUserName          DisplayString,
    mGuardFirewallUserFWTemplateUserRowStatus     RowStatus
  }

  mGuardFirewallUserFWTemplateUserTemplateIndex OBJECT-TYPE
    SYNTAX INTEGER (1..100)
    ACCESS not-accessible
    STATUS mandatory
    DESCRIPTION
      "Index to identify the user firewall template entry."
  ::= { mGuardFirewallUserFWTemplateUserEntry 1 }

  mGuardFirewallUserFWTemplateUserIndex OBJECT-TYPE
    SYNTAX INTEGER (1..100)
    ACCESS not-accessible
    STATUS mandatory
    DESCRIPTION
      "Index to identify the user within the user firewall template entry."
  ::= { mGuardFirewallUserFWTemplateUserEntry 2 }

  mGuardFirewallUserFWTemplateUserName OBJECT-TYPE
    SYNTAX DisplayString
    ACCESS read-write
    STATUS mandatory
    DESCRIPTION
      "The username of the user within the user firewall template entry."
  ::= { mGuardFirewallUserFWTemplateUserEntry 3 }

  mGuardFirewallUserFWTemplateUserRowStatus OBJECT-TYPE
    SYNTAX RowStatus
    ACCESS read-write
    STATUS mandatory
    DESCRIPTION
      "Row Status"
  ::= { mGuardFirewallUserFWTemplateUserEntry 4 }

  mGuardFirewallUserFWTemplateRuleTable OBJECT-TYPE
    SYNTAX SEQUENCE OF MGuardFirewallUserFWTemplateRuleEntry
    ACCESS not-accessible
    STATUS mandatory
    DESCRIPTION
      "A table containing the rules associated with a user firewall template."
  ::= { mGuardFirewallUserFW 4 }

  mGuardFirewallUserFWTemplateRuleEntry OBJECT-TYPE
    SYNTAX MGuardFirewallUserFWTemplateRuleEntry
    ACCESS not-accessible
    STATUS mandatory
    DESCRIPTION
      "An entry containing a single rule associated with a user firewall template."
    INDEX { mGuardFirewallUserFWTemplateRuleTemplateIndex, mGuardFirewallUserFWTemplateRuleIndex }
  ::= { mGuardFirewallUserFWTemplateRuleTable 1 }

  MGuardFirewallUserFWTemplateRuleEntry ::= SEQUENCE {
    mGuardFirewallUserFWTemplateRuleTemplateIndex INTEGER,
    mGuardFirewallUserFWTemplateRuleIndex         INTEGER,
    mGuardFirewallUserFWTemplateRuleProto         INTEGER,
    mGuardFirewallUserFWTemplateRuleSrcPort       DisplayString,
    mGuardFirewallUserFWTemplateRuleDstPort       DisplayString,
    mGuardFirewallUserFWTemplateRuleDstIP         DisplayString,
    mGuardFirewallUserFWTemplateRuleLog           INTEGER,
    mGuardFirewallUserFWTemplateRuleComment       DisplayString,
    mGuardFirewallUserFWTemplateRuleRowStatus     RowStatus
  }

  mGuardFirewallUserFWTemplateRuleTemplateIndex OBJECT-TYPE
    SYNTAX INTEGER (1..100)
    ACCESS not-accessible
    STATUS mandatory
    DESCRIPTION
      "Index to identify the user firewall template entry."
  ::= { mGuardFirewallUserFWTemplateRuleEntry 1 }

  mGuardFirewallUserFWTemplateRuleIndex OBJECT-TYPE
    SYNTAX INTEGER (1..100)
    ACCESS not-accessible
    STATUS mandatory
    DESCRIPTION
      "Index to identify the rule within the user firewall template entry."
  ::= { mGuardFirewallUserFWTemplateRuleEntry 2 }

  mGuardFirewallUserFWTemplateRuleProto OBJECT-TYPE
    SYNTAX INTEGER {
			tcp(1),
			udp(2),
			icmp(3),
			all(4)
                   }
    ACCESS read-write
    STATUS mandatory
    DESCRIPTION
      "The protocol of the  rule within the user firewall template entry."
  ::= { mGuardFirewallUserFWTemplateRuleEntry 3 }

  mGuardFirewallUserFWTemplateRuleSrcPort OBJECT-TYPE
    SYNTAX DisplayString
    ACCESS read-write
    STATUS mandatory
    DESCRIPTION
      "The source port or port range of the rule within the user firewall template entry."
  ::= { mGuardFirewallUserFWTemplateRuleEntry 4 }

  mGuardFirewallUserFWTemplateRuleDstPort OBJECT-TYPE
    SYNTAX DisplayString
    ACCESS read-write
    STATUS mandatory
    DESCRIPTION
      "The destination port or port range of the rule within the user firewall template entry."
  ::= { mGuardFirewallUserFWTemplateRuleEntry 5 }

  mGuardFirewallUserFWTemplateRuleDstIP OBJECT-TYPE
    SYNTAX DisplayString
    ACCESS read-write
    STATUS mandatory
    DESCRIPTION
      "The destination IP address of the rule within the user firewall template entry."
  ::= { mGuardFirewallUserFWTemplateRuleEntry 6 }

  mGuardFirewallUserFWTemplateRuleLog OBJECT-TYPE
    SYNTAX INTEGER {
			yes(1),
			no(2)
                   }
    ACCESS read-write
    STATUS mandatory
    DESCRIPTION
      "Log packets matching the rule within the user firewall template entry."
  ::= { mGuardFirewallUserFWTemplateRuleEntry 7 }

  mGuardFirewallUserFWTemplateRuleComment OBJECT-TYPE
    SYNTAX DisplayString
    ACCESS read-write
    STATUS mandatory
    DESCRIPTION
      "A comment associated with the rule within the user firewall template entry."
  ::= { mGuardFirewallUserFWTemplateRuleEntry 8 }

  mGuardFirewallUserFWTemplateRuleRowStatus OBJECT-TYPE
    SYNTAX RowStatus
    ACCESS read-write
    STATUS mandatory
    DESCRIPTION
      "Row Status"
  ::= { mGuardFirewallUserFWTemplateRuleEntry 9 }


--
-- Network
--

    mGuardNetworkMode OBJECT-TYPE
     SYNTAX INTEGER {
			stealth(1),
			router(2),
			pppoe(3),
			pptp(4)
		    }
     ACCESS read-only
     STATUS mandatory
     DESCRIPTION
        "Network mode:
          router,stealth"
    ::= { mGuardNetwork 1 }


--
-- Stealth
--

    mGuardStealth OBJECT IDENTIFIER ::= { mGuardNetwork 2 }

    mGuardStealthIPConfMode OBJECT-TYPE
     SYNTAX INTEGER {
			autoDetect(1),
			static(2),
			multi(3)
		    }
     ACCESS read-write
     STATUS mandatory
     DESCRIPTION
      "Type of IP Stack configuration in stealth mode.
       autodetect, static, multiple-clients"
    ::= { mGuardStealth 1 }

    mGuardStealthIPConfStatic OBJECT IDENTIFIER ::= { mGuardStealth 2 }

    mGuardStealthStaticIP OBJECT-TYPE
     SYNTAX IpAddress
     ACCESS read-write
     STATUS mandatory
     DESCRIPTION
        "IP address of the protected client in stealth mode (using static ip
        configuration)."
    ::= { mGuardStealthIPConfStatic 1 }

    mGuardStealthStaticMAC OBJECT-TYPE
     SYNTAX MacAddress
     ACCESS read-write
     STATUS mandatory
     DESCRIPTION
        "MAC address of protected client in stealth mode (using static ip
        configuration)."
    ::= { mGuardStealthIPConfStatic 2 }

    mGuardStealthStaticActivate OBJECT-TYPE
      SYNTAX INTEGER {
			activate(1),
			valuescached(2)
		     }
      ACCESS read-write
      STATUS mandatory
      DESCRIPTION
         "Button to activate Stealth Static IP configuration."
   ::= { mGuardStealthIPConfStatic 3 }

    mGuardStealthManageIP OBJECT-TYPE
     SYNTAX IpAddress
     ACCESS read-write
     STATUS mandatory
     DESCRIPTION
        "The management IP address of this system in stealth mode
	 When set, this value is internally cached inside the agent until it
	 is explicitly activated by writing the mGuardStealthManageActivate
	 object. When read the currently active setting is returned, not
	 regarding any cached values."
    ::= { mGuardStealthIPConfStatic 4 }

    mGuardStealthManageNetmask OBJECT-TYPE
     SYNTAX IpAddress
     ACCESS read-write
     STATUS mandatory
     DESCRIPTION
        "The management IP netmask of this system in stealth mode
	 When set, this value is internally cached inside the agent until it
	 is explicitly activated by writing the mGuardStealthManageActivate
	 object. When read the currently active setting is returned, not
	 regarding any cached values."
    ::= { mGuardStealthIPConfStatic 5 }

    mGuardStealthManageGateway OBJECT-TYPE
     SYNTAX IpAddress
     ACCESS read-write
     STATUS mandatory
     DESCRIPTION
        "The default gateway for the management IP of the mGuard in
	 stealth mode When set, this value is internally cached inside the
	 agent until it is explicitly activated by writing the
	 mGuardStealthManageActivate object. When read the currently active
	 setting is returned, not regarding any cached values."
    ::= { mGuardStealthIPConfStatic 6 }

    mGuardStealthManageActivate OBJECT-TYPE
      SYNTAX INTEGER {
			activate(1),
			valuescached(2)
		     }
      ACCESS read-write
      STATUS mandatory
      DESCRIPTION
         "Button to activate the stealth management IP configuration. When
	  activate(1) is written, any cached values for the
	  mGuardStealthManageIP, mGuardStealthManageNetmask, and
	  mGuardStealthManageGateway objects are activated. When read and one
	  or more of the above mentioned objects have been cached,
	  valuescached(2) is returned, not regarding whether the cached valued
	  and the current value are different."
   ::= { mGuardStealthIPConfStatic 7 }


--
-- HiDiscovery in StealthMode
--

    mGuardStealthHiDiscoveryRelay OBJECT-TYPE
      SYNTAX INTEGER {
			enabled(1),
			disabled(2)
		     }
      ACCESS read-write
      STATUS mandatory
      DESCRIPTION
         "Relay/bridge HiDiscovery queries when in Stealth Mode."
   ::= { mGuardStealth 3 }

    mGuardStealthHiDiscoveryState OBJECT-TYPE
      SYNTAX INTEGER {
			readwrite(1),
			disabled(2),
			readonly(3)
		     }
      ACCESS read-write
      STATUS mandatory
      DESCRIPTION
         "Enable HiDiscovery in StealthMode. This is mutually exclusive with
	  the two HiDiscovery router mode settings of course."
   ::= { mGuardStealth 4 }



    mGuardStealthL2Filter OBJECT IDENTIFIER ::= { mGuardStealth 5 }

--
--  mGuardStealthL2FilterIntern
--

    mGuardL2FilterInternTable OBJECT-TYPE
      SYNTAX SEQUENCE OF MGuardL2FilterInternEntry
      ACCESS not-accessible
      STATUS mandatory
      DESCRIPTION
        "Table of firewall rules for Layer 2 filtering on internal interface."
      ::= { mGuardStealthL2Filter 1 }

    mGuardL2FilterInternEntry OBJECT-TYPE
        SYNTAX MGuardL2FilterInternEntry
        ACCESS not-accessible
        STATUS mandatory
        DESCRIPTION
         "A single rule for Layer-2 filter in internal interface. "
        INDEX { mGuardL2FilterInternRuleIndex }
    ::= { mGuardL2FilterInternTable 1 }

    MGuardL2FilterInternEntry ::= SEQUENCE{
      mGuardL2FilterInternRuleIndex	INTEGER,
      mGuardL2FilterInternRowStatus	RowStatus,
      mGuardL2FilterInternSrcMac	MacAddress,
      mGuardL2FilterInternDstMac	MacAddress,
      mGuardL2FilterInternEthType	INTEGER,
      mGuardL2FilterInternTarget	INTEGER,
      mGuardL2FilterInternComment	DisplayString
    }

    mGuardL2FilterInternRuleIndex OBJECT-TYPE
      SYNTAX INTEGER (1..100)
      ACCESS not-accessible
      STATUS mandatory
      DESCRIPTION
        "Table index."
     ::= { mGuardL2FilterInternEntry 1 }

    mGuardL2FilterInternRowStatus OBJECT-TYPE
      SYNTAX RowStatus
      ACCESS read-write
      STATUS mandatory
      DESCRIPTION
        "Row Status."
     ::= { mGuardL2FilterInternEntry 2 }

    mGuardL2FilterInternSrcMac OBJECT-TYPE
      SYNTAX MacAddress
      ACCESS read-write
      STATUS mandatory
      DESCRIPTION
        "Source MAC Address to apply this filter rule for."
     ::= { mGuardL2FilterInternEntry 3 }

    mGuardL2FilterInternDstMac OBJECT-TYPE
      SYNTAX MacAddress
      ACCESS read-write
      STATUS mandatory
      DESCRIPTION
        "Desitination MAC Address to apply this filter rule for."
     ::= { mGuardL2FilterInternEntry 4 }

    mGuardL2FilterInternEthType OBJECT-TYPE
      SYNTAX INTEGER
      ACCESS read-write
      STATUS mandatory
      DESCRIPTION
        "Ethernet type to apply this filter rule for."
     ::= { mGuardL2FilterInternEntry 5 }

    mGuardL2FilterInternTarget OBJECT-TYPE
       SYNTAX INTEGER {
                        accept(1),
                        reject(2),
                        drop(3)
                      }
       ACCESS read-write
       STATUS mandatory
       DESCRIPTION
          "The rule's target"
     ::= { mGuardL2FilterInternEntry 6 }

    mGuardL2FilterInternComment OBJECT-TYPE
      SYNTAX DisplayString
      ACCESS read-write
      STATUS mandatory
      DESCRIPTION
        "Comment or name for this rule."
     ::= { mGuardL2FilterInternEntry 7 }




--
--  mGuardStealthL2FilterExtern
--

    mGuardL2FilterExternTable OBJECT-TYPE
      SYNTAX SEQUENCE OF MGuardL2FilterExternEntry
      ACCESS not-accessible
      STATUS mandatory
      DESCRIPTION
        "Table of firewall rules for Layer 2 filterin on external interface."
      ::= { mGuardStealthL2Filter 2 }

    mGuardL2FilterExternEntry OBJECT-TYPE
        SYNTAX MGuardL2FilterExternEntry
        ACCESS not-accessible
        STATUS mandatory
        DESCRIPTION
         "A single rule for Layer-2 filter in external interface. "
        INDEX { mGuardL2FilterExternRuleIndex }
    ::= { mGuardL2FilterExternTable 1 }

    MGuardL2FilterExternEntry ::= SEQUENCE{
      mGuardL2FilterExternRuleIndex	INTEGER,
      mGuardL2FilterExternRowStatus	RowStatus,
      mGuardL2FilterExternSrcMac	MacAddress,
      mGuardL2FilterExternDstMac	MacAddress,
      mGuardL2FilterExternEthType	INTEGER,
      mGuardL2FilterExternTarget	INTEGER,
      mGuardL2FilterExternComment	DisplayString
    }

    mGuardL2FilterExternRuleIndex OBJECT-TYPE
      SYNTAX INTEGER (1..100)
      ACCESS not-accessible
      STATUS mandatory
      DESCRIPTION
        "Table index."
     ::= { mGuardL2FilterExternEntry 1 }

    mGuardL2FilterExternRowStatus OBJECT-TYPE
      SYNTAX RowStatus
      ACCESS read-write
      STATUS mandatory
      DESCRIPTION
        "Row Status."
     ::= { mGuardL2FilterExternEntry 2 }

    mGuardL2FilterExternSrcMac OBJECT-TYPE
      SYNTAX MacAddress
      ACCESS read-write
      STATUS mandatory
      DESCRIPTION
        "Source MAC Address to apply this filter rule for."
     ::= { mGuardL2FilterExternEntry 3 }

    mGuardL2FilterExternDstMac OBJECT-TYPE
      SYNTAX MacAddress
      ACCESS read-write
      STATUS mandatory
      DESCRIPTION
        "Desitination MAC Address to apply this filter rule for."
     ::= { mGuardL2FilterExternEntry 4 }

    mGuardL2FilterExternEthType OBJECT-TYPE
      SYNTAX INTEGER
      ACCESS read-write
      STATUS mandatory
      DESCRIPTION
        "Ethernet type to apply this filter rule for."
     ::= { mGuardL2FilterExternEntry 5 }

    mGuardL2FilterExternTarget OBJECT-TYPE
       SYNTAX INTEGER {
                        accept(1),
                        reject(2),
                        drop(3)
                      }
       ACCESS read-write
       STATUS mandatory
       DESCRIPTION
          "The rule's target"
     ::= { mGuardL2FilterExternEntry 6 }

    mGuardL2FilterExternComment OBJECT-TYPE
      SYNTAX DisplayString
      ACCESS read-write
      STATUS mandatory
      DESCRIPTION
        "Comment or name for this rule."
     ::= { mGuardL2FilterExternEntry 7 }


--
--  mGuardStealthL2Filter fuer spezielle Protokolle
--

    mGuardStealthL2ForwardGVRP OBJECT-TYPE
       SYNTAX INTEGER {
                        yes(1),
                        no(2)
                      }
      ACCESS read-write
      STATUS mandatory
      DESCRIPTION
        "Enable GVRP forwarding in StealthMode."
      ::= { mGuardStealthL2Filter 3 }

    mGuardStealthL2ForwardSTP OBJECT-TYPE
       SYNTAX INTEGER {
                        yes(1),
                        no(2)
                      }
      ACCESS read-write
      STATUS mandatory
      DESCRIPTION
        "Enable STP forwarding in StealthMode."
      ::= { mGuardStealthL2Filter 4 }

    mGuardStealthL2ForwardDHCP OBJECT-TYPE
       SYNTAX INTEGER {
                        yes(1),
                        no(2)
                      }
      ACCESS read-write
      STATUS mandatory
      DESCRIPTION
        "Enable DHCP forwarding in StealthMode. This will allow computers on
	 the internal/protected side to receive their configuration via
	 DHCP even if no special DHCP rule is configured in the firewall"
      ::= { mGuardStealthL2Filter 5 }



--
-- Stealth Interface
--

    mGuardStealthInterface OBJECT IDENTIFIER ::= { mGuardStealth 6 }

    mGuardStealthMTU OBJECT-TYPE
     SYNTAX INTEGER
     ACCESS read-write
     STATUS mandatory
     DESCRIPTION
      "MTU to use in Stealth Mode."
    ::= { mGuardStealthInterface 1 }

    mGuardStealthVlanMTU OBJECT-TYPE
     SYNTAX INTEGER
     ACCESS read-write
     STATUS mandatory
     DESCRIPTION
      "MTU to use in Stealth Mode for VLAN packets."
    ::= { mGuardStealthInterface 2 }

    mGuardStealthManageUseVLAN OBJECT-TYPE
      SYNTAX INTEGER {
                        yes(1),
                        no(2)
                      }
     ACCESS read-write
     STATUS mandatory
     DESCRIPTION
      "Use VLAn tagging for the management IP address in Stealth Mode."
    ::= { mGuardStealthInterface 3 }

    mGuardStealthManageVLanID OBJECT-TYPE
     SYNTAX INTEGER
     ACCESS read-write
     STATUS mandatory
     DESCRIPTION
      "VLAN ID for the management IP address in Stealth Mode."
    ::= { mGuardStealthInterface 4 }


--
-- Network Internal IP
--

   mGuardRouter OBJECT IDENTIFIER ::= { mGuardNetwork 3 }

   mGuardRouterLocal OBJECT IDENTIFIER ::= { mGuardRouter 1 }

   mGuardRouterLocalIP OBJECT-TYPE
     SYNTAX IpAddress
     ACCESS read-write
     STATUS mandatory
     DESCRIPTION
        "The internal IP address of this device in router mode. When set,
	 this value is internally cached inside the agent until it is
	 explicitly activated by writing the mGuardRouterLocalActivate
	 object. When read the currently active setting is returned,
	 not regarding any cached values."
    ::= { mGuardRouterLocal 1 }

   mGuardRouterLocalNetmask OBJECT-TYPE
     SYNTAX IpAddress
     ACCESS read-write
     STATUS mandatory
     DESCRIPTION
        "The internal subnet mask of this device in router mode. When set,
	 this value is internally cached inside the agent until it is
	 explicitly activated by writing the mGuardRouterLocalActivate
	 object. When read the currently active setting is returned,
	 not regarding any cached values."
    ::= { mGuardRouterLocal 2 }

  mGuardRouterLocalActivate OBJECT-TYPE
    SYNTAX INTEGER {
			activate(1),
			valuescached(2)
		   }
      ACCESS read-write
      STATUS mandatory
      DESCRIPTION
         "Button to activate the router local IP configuration. When
	  activate(1) is written, any cached values for the mGuardRouterLocalIP,
	  mGuardRouterLocalNetmask, and mGuardRouterExternStaticGateway
	  objects are activated. When read and one or more of the above
	  mentioned objects have been cached, valuescached(2) is returned,
	  not regarding whether the cached valued and the current value
	  are different."
   ::= { mGuardRouterLocal 3 }

--
-- Network Internal Aliases
--

   mGuardRouterLocalAliasesTable OBJECT-TYPE
    SYNTAX SEQUENCE OF MGuardRouterLocalAliasesEntry
    ACCESS not-accessible
    STATUS mandatory
    DESCRIPTION
     "A table containing aliases for the local interface."
   ::= { mGuardRouterLocal 4 }

   mGuardRouterLocalAliasesEntry OBJECT-TYPE
    SYNTAX MGuardRouterLocalAliasesEntry
    ACCESS not-accessible
    STATUS mandatory
    DESCRIPTION
     "An entry  containing a single alias for the local interface."
    INDEX { mGuardLocalAliasIndex }
   ::= { mGuardRouterLocalAliasesTable 1 }

   MGuardRouterLocalAliasesEntry ::= SEQUENCE {
     mGuardLocalAliasIndex      INTEGER,
     mGuardLocalAliasIpAddress  IpAddress,
     mGuardLocalAliasNetmask    IpAddress,
     mGuardLocalAliasRowStatus  RowStatus,
     mGuardLocalAliasUseVLAN    INTEGER,
     mGuardLocalAliasVLANid     INTEGER
   }

   mGuardLocalAliasIndex OBJECT-TYPE
     SYNTAX INTEGER(1..100)
     ACCESS not-accessible
     STATUS mandatory
     DESCRIPTION
       "Identifier."
     ::= { mGuardRouterLocalAliasesEntry 1 }

   mGuardLocalAliasIpAddress OBJECT-TYPE
     SYNTAX IpAddress
     ACCESS read-write
     STATUS mandatory
     DESCRIPTION
       "IP address."
     ::= { mGuardRouterLocalAliasesEntry 2 }

   mGuardLocalAliasNetmask OBJECT-TYPE
    SYNTAX IpAddress
     ACCESS read-write
     STATUS mandatory
     DESCRIPTION
       "Netmask."
     ::= { mGuardRouterLocalAliasesEntry 3 }

    mGuardLocalAliasRowStatus OBJECT-TYPE
     SYNTAX RowStatus
     ACCESS read-write
     STATUS mandatory
     DESCRIPTION
       "RowStatus"
    ::= { mGuardRouterLocalAliasesEntry 4 }

    mGuardLocalAliasUseVLAN OBJECT-TYPE
     SYNTAX INTEGER{
                      yes(1),
    		      no(2)
 	             }
     ACCESS read-write
     STATUS mandatory
     DESCRIPTION
       "Use VLAn tagging with this Alias interface."
    ::= { mGuardRouterLocalAliasesEntry 5 }

    mGuardLocalAliasVLANid OBJECT-TYPE
     SYNTAX INTEGER
     ACCESS read-write
     STATUS mandatory
     DESCRIPTION
       "VLAN ID to be used with this Alias."
    ::= { mGuardRouterLocalAliasesEntry 6 }


--
-- Network Internal Routes
--

    mGuardLocalRoutesTable OBJECT-TYPE
     SYNTAX SEQUENCE OF MGuardLocalRoutesEntry
     ACCESS not-accessible
     STATUS mandatory
     DESCRIPTION
      "A table containing additional internal routes interface."
    ::= { mGuardRouterLocal 5 }

    mGuardLocalRoutesEntry OBJECT-TYPE
     SYNTAX MGuardLocalRoutesEntry
     ACCESS not-accessible
     STATUS mandatory
     DESCRIPTION
      "An entry  containing a single internal route."
     INDEX { mGuardLocalRouteIndex }
    ::= { mGuardLocalRoutesTable 1 }

    MGuardLocalRoutesEntry ::= SEQUENCE {
      mGuardLocalRouteIndex      INTEGER,
      mGuardLocalRouteNetwork    DisplayString,
      mGuardLocalRouteGateway    IpAddress,
      mGuardLocalRouteRowStatus  RowStatus
   }

   mGuardLocalRouteIndex OBJECT-TYPE
     SYNTAX INTEGER(1..100)
     ACCESS not-accessible
     STATUS mandatory
     DESCRIPTION
       "Identifier."
     ::= { mGuardLocalRoutesEntry 1 }

   mGuardLocalRouteNetwork OBJECT-TYPE
     SYNTAX DisplayString
     ACCESS read-write
     STATUS mandatory
     DESCRIPTION
       "Routed network."
     ::= { mGuardLocalRoutesEntry 2 }

    mGuardLocalRouteGateway OBJECT-TYPE
     SYNTAX IpAddress
     ACCESS read-write
     STATUS mandatory
     DESCRIPTION
       "Routing gateway."
     ::= { mGuardLocalRoutesEntry 3 }

     mGuardLocalRouteRowStatus OBJECT-TYPE
     SYNTAX RowStatus
     ACCESS read-write
     STATUS mandatory
     DESCRIPTION
       "RowStatus"
     ::= { mGuardLocalRoutesEntry 4 }


   mGuardRouterLocalDevMTU OBJECT-TYPE
     SYNTAX INTEGER
     ACCESS read-write
     STATUS mandatory
     DESCRIPTION
        "Set the MTU for the local interface. Router-Mode only."
    ::= { mGuardRouterLocal 6 }

   mGuardRouterLocalUseVLAN OBJECT-TYPE
     SYNTAX INTEGER{
                      yes(1),
    		      no(2)
 	             }
     ACCESS read-write
     STATUS mandatory
     DESCRIPTION
        "Use VLAN for the local interface. Router-Mode only."
    ::= { mGuardRouterLocal 7 }

   mGuardRouterLocalVlanId OBJECT-TYPE
     SYNTAX INTEGER
     ACCESS read-write
     STATUS mandatory
     DESCRIPTION
        "VLAN-ID for the local interface, used only if set to use VLAN. Router-Mode only."
    ::= { mGuardRouterLocal 8 }

   mGuardRouterLocalDevVlanMTU OBJECT-TYPE
     SYNTAX INTEGER
     ACCESS read-write
     STATUS mandatory
     DESCRIPTION
        "Set the MTU for the VLAN if enabled on local interface. Router-Mode only."
    ::= { mGuardRouterLocal 9 }



--
-- Network External IP
--

    mGuardRouterExtern OBJECT IDENTIFIER ::= { mGuardRouter 2 }

    mGuardRouterExternDHCP OBJECT-TYPE
     SYNTAX INTEGER {
			enabled(1),
			disabled(2)
		    }
     ACCESS read-write
     STATUS mandatory
     DESCRIPTION
        "When enabled, retrieve the external IP via DHCP, otherwise use
        the value stored in mGuardRouterExternStaticIP."
    ::= { mGuardRouterExtern 1 }

    mGuardRouterExternStatic  OBJECT IDENTIFIER ::= { mGuardRouterExtern 2 }

    mGuardRouterExternStaticIP OBJECT-TYPE
     SYNTAX IpAddress
     ACCESS read-write
     STATUS mandatory
     DESCRIPTION
        "The external IP address of this device in router mode
	 (when statically configured). When set, this value is internally
	 cached inside the agent until it is explicitly activated by writing
	 the mGuardRouterExternStaticActivate object. When read the currently
	 active setting is returned, not regarding any cached values."
    ::= { mGuardRouterExternStatic 1 }

    mGuardRouterExternStaticNetmask OBJECT-TYPE
     SYNTAX IpAddress
     ACCESS read-write
     STATUS mandatory
     DESCRIPTION
        "The external netmask of this device in router mode (when
	 statically configured). When set, this value is internally cached
	 inside the agent until it is explicitly activated by writing the
	 mGuardRouterExternStaticActivate object. When read the currently
	 active setting is returned, not regarding any cached values."
    ::= { mGuardRouterExternStatic 2 }

    mGuardRouterExternStaticGateway OBJECT-TYPE
     SYNTAX IpAddress
     ACCESS read-write
     STATUS mandatory
     DESCRIPTION
        "The (extern) default gateway of this device in router mode (when
	 statically configured). When set, this value is internally cached
	 inside the agent until it is explicitly activated by writing the
	 mGuardRouterExternStaticActivate  or mGuardRouterLocalActivate object.
	 When read the currently active setting is returned, not regarding
	 any cached values."
    ::= { mGuardRouterExternStatic 3 }

   mGuardRouterExternActivate OBJECT-TYPE
    SYNTAX INTEGER {
			activate(1),
			valuescached(2)
		   }
      ACCESS read-write
      STATUS mandatory
      DESCRIPTION
         "Button to activate the router extern IP configuration. When
	  activate(1) is written, any cached values for the
	  mGuardRouterExternStaticIP, mGuardRouterExternStaticNetmask, and
	  mGuardRouterExternStaticGateway objects are activated. When read
	  and one or more of the above mentioned objects have been cached,
	  valuescached(2) is returned, not regarding whether the cached valued
	  and the current value are different."
   ::= { mGuardRouterExternStatic 4 }


   mGuardRouterExternDevMTU OBJECT-TYPE
     SYNTAX INTEGER
     ACCESS read-write
     STATUS mandatory
     DESCRIPTION
        "Set the MTU for the external interface. Router-Mode only."
    ::= { mGuardRouterExtern 6 }

   mGuardRouterExternUseVLAN OBJECT-TYPE
     SYNTAX INTEGER{
                      yes(1),
    		      no(2)
 	             }
     ACCESS read-write
     STATUS mandatory
     DESCRIPTION
        "Use VLAN for the external interface. Router-Mode only."
    ::= { mGuardRouterExtern 7 }

   mGuardRouterExternVlanId OBJECT-TYPE
     SYNTAX INTEGER
     ACCESS read-write
     STATUS mandatory
     DESCRIPTION
        "VLAN-ID for the external interface, used only if set to use VLAN. Router-Mode only."
    ::= { mGuardRouterExtern 8 }

   mGuardRouterExternDevVlanMTU OBJECT-TYPE
     SYNTAX INTEGER
     ACCESS read-write
     STATUS mandatory
     DESCRIPTION
        "Set the MTU for the VLAN if enabled on external interface. Router-Mode only."
    ::= { mGuardRouterExtern 9 }



--
-- Network External Aliases
--

  mGuardRouterExternAliasesTable OBJECT-TYPE
    SYNTAX SEQUENCE OF MGuardRouterExternAliasesEntry
    ACCESS not-accessible
    STATUS mandatory
    DESCRIPTION
     "A table containing aliases for the external interface."
   ::= { mGuardRouterExternStatic 5 }

   mGuardRouterExternAliasesEntry OBJECT-TYPE
    SYNTAX MGuardRouterExternAliasesEntry
    ACCESS not-accessible
    STATUS mandatory
    DESCRIPTION
     "An entry  containing a single alias for the extern interface."
    INDEX { mGuardExternAliasIndex }
   ::= { mGuardRouterExternAliasesTable 1 }

   MGuardRouterExternAliasesEntry ::= SEQUENCE {
     mGuardExternAliasIndex      INTEGER,
     mGuardExternAliasIpAddress  IpAddress,
     mGuardExternAliasNetmask    IpAddress,
     mGuardExternAliasRowStatus  RowStatus,
     mGuardExternAliasUseVLAN    INTEGER,
     mGuardExternAliasVLANid     INTEGER
   }

   mGuardExternAliasIndex OBJECT-TYPE
     SYNTAX INTEGER(1..100)
     ACCESS not-accessible
     STATUS mandatory
     DESCRIPTION
       "Identifier."
     ::= { mGuardRouterExternAliasesEntry 1 }

   mGuardExternAliasIpAddress OBJECT-TYPE
     SYNTAX IpAddress
     ACCESS read-write
     STATUS mandatory
     DESCRIPTION
       "IP address."
     ::= { mGuardRouterExternAliasesEntry 2 }

   mGuardExternAliasNetmask OBJECT-TYPE
    SYNTAX IpAddress
     ACCESS read-write
     STATUS mandatory
     DESCRIPTION
       "Netmask."
     ::= { mGuardRouterExternAliasesEntry 3 }

    mGuardExternAliasRowStatus OBJECT-TYPE
     SYNTAX RowStatus
     ACCESS read-write
     STATUS mandatory
     DESCRIPTION
       "RowStatus"
    ::= { mGuardRouterExternAliasesEntry 4 }

    mGuardExternAliasUseVLAN OBJECT-TYPE
     SYNTAX INTEGER{
                      yes(1),
    		      no(2)
 	             }
     ACCESS read-write
     STATUS mandatory
     DESCRIPTION
       "Use VLAn tagging with this Alias interface."
    ::= { mGuardRouterExternAliasesEntry 5 }

    mGuardExternAliasVLANid OBJECT-TYPE
     SYNTAX INTEGER
     ACCESS read-write
     STATUS mandatory
     DESCRIPTION
       "VLAN ID to be used with this Alias."
    ::= { mGuardRouterExternAliasesEntry 6 }


--
-- Network External Routes
--

    mGuardExternRoutesTable OBJECT-TYPE
     SYNTAX SEQUENCE OF MGuardExternRoutesEntry
     ACCESS not-accessible
     STATUS mandatory
     DESCRIPTION
      "A table containing additional external routes."
    ::= { mGuardRouterExternStatic 6 }

    mGuardExternRoutesEntry OBJECT-TYPE
     SYNTAX MGuardExternRoutesEntry
     ACCESS not-accessible
     STATUS mandatory
     DESCRIPTION
      "An entry  containing a single external route."
     INDEX { mGuardExternRouteIndex }
    ::= { mGuardExternRoutesTable 1 }

    MGuardExternRoutesEntry ::= SEQUENCE {
      mGuardExternRouteIndex      INTEGER,
      mGuardExternRouteNetwork    DisplayString,
      mGuardExternRouteGateway    IpAddress,
      mGuardExternRouteRowStatus  RowStatus
   }

   mGuardExternRouteIndex OBJECT-TYPE
     SYNTAX INTEGER(1..100)
     ACCESS not-accessible
     STATUS mandatory
     DESCRIPTION
       "Identifier."
     ::= { mGuardExternRoutesEntry 1 }

   mGuardExternRouteNetwork OBJECT-TYPE
     SYNTAX DisplayString
     ACCESS read-write
     STATUS mandatory
     DESCRIPTION
       "Routed network."
     ::= { mGuardExternRoutesEntry 2 }

    mGuardExternRouteGateway OBJECT-TYPE
     SYNTAX IpAddress
     ACCESS read-write
     STATUS mandatory
     DESCRIPTION
       "Routing gateway."
     ::= { mGuardExternRoutesEntry 3 }

     mGuardExternRouteRowStatus OBJECT-TYPE
     SYNTAX RowStatus
     ACCESS read-write
     STATUS mandatory
     DESCRIPTION
       "RowStatus"
     ::= { mGuardExternRoutesEntry 4 }


--
-- HiDiscovery in RouterMode
--
   mGuardRouterHiDiscovery OBJECT IDENTIFIER ::= { mGuardRouter 3 }

    mGuardRouterHiDiscoveryIntern OBJECT-TYPE
      SYNTAX INTEGER {
			readwrite(1),
			disabled(2),
			readonly(3)
		     }
      ACCESS read-write
      STATUS mandatory
      DESCRIPTION
         "Enable HiDiscovery on internal interface in RouterMode."
   ::= { mGuardRouterHiDiscovery 1 }

    mGuardRouterHiDiscoveryExtern OBJECT-TYPE
      SYNTAX INTEGER {
			readwrite(1),
			disabled(2),
			readonly(3)
		     }
      ACCESS read-write
      STATUS mandatory
      DESCRIPTION
         "Enable HiDiscovery on external interface in RouterMode."
   ::= { mGuardRouterHiDiscovery 2 }



--
-- Network PPPoE
--

   mGuardPPPOE OBJECT IDENTIFIER ::= { mGuardNetwork 4 }

   mGuardPPPOELogin OBJECT-TYPE
    SYNTAX DisplayString
    ACCESS read-write
    STATUS mandatory
    DESCRIPTION
      "PPPoE login user name."
   ::= { mGuardPPPOE 1 }

   mGuardPPPOEPasswd OBJECT-TYPE
    SYNTAX DisplayString
    ACCESS read-write
    STATUS mandatory
    DESCRIPTION
       "PPPoE login password."
   ::={ mGuardPPPOE 2 }

   mGuardPPPOEMSS OBJECT-TYPE
    SYNTAX DisplayString
    ACCESS read-write
    STATUS mandatory
    DESCRIPTION
       "The maximum segment size used for PPPoE"
   ::={ mGuardPPPOE 3 }

   mGuardPPPOEServiceName OBJECT-TYPE
    SYNTAX DisplayString
    ACCESS read-write
    STATUS obsolete
    DESCRIPTION
       "The service name used for PPPoE, normally not used!"
   ::={ mGuardPPPOE 4 }

   mGuardPPPOEAccessConcentName OBJECT-TYPE
    SYNTAX DisplayString
    ACCESS read-write
    STATUS obsolete
    DESCRIPTION
       "The access concentrator name used for PPPoE, normally not used!"
   ::={ mGuardPPPOE 5 }

   mGuardPPPOEHostUnique OBJECT-TYPE
    SYNTAX INTEGER {
			enabled(1),
			disabled(2)
		   }
    ACCESS read-write
    STATUS obsolete
    DESCRIPTION
      "Set 'Host-Unique' tag for discovery, required for operation with
       several daemons"
   ::={ mGuardPPPOE 6 }

  mGuardPPPOEpppdOptionsTable OBJECT-TYPE
    SYNTAX SEQUENCE OF MGuardPPPOEpppdOptionsEntry
    ACCESS not-accessible
    STATUS mandatory
    DESCRIPTION
      "A table of options set for the pppd process implementing PPPOE."
   ::= { mGuardPPPOE 7 }

  mGuardPPPOEpppdOptionsEntry OBJECT-TYPE
      SYNTAX MGuardPPPOEpppdOptionsEntry
      ACCESS not-accessible
      STATUS mandatory
      DESCRIPTION
       "A single option set for pppd. "
      INDEX { mGuardPPPOEpppdOptionsIndex }
  ::= { mGuardPPPOEpppdOptionsTable 1 }

  MGuardPPPOEpppdOptionsEntry  ::= SEQUENCE {
     mGuardPPPOEpppdOptionsIndex     INTEGER,
     mGuardPPPOEpppdOptionsValue     DisplayString,
     mGuardPPPOEpppdOptionsRowStatus RowStatus
  }

  mGuardPPPOEpppdOptionsIndex OBJECT-TYPE
    SYNTAX INTEGER (1..100)
    ACCESS not-accessible
    STATUS mandatory
    DESCRIPTION
      "Table index."
   ::= { mGuardPPPOEpppdOptionsEntry 1 }

   mGuardPPPOEpppdOptionsValue OBJECT-TYPE
    SYNTAX DisplayString
    ACCESS read-write
    STATUS mandatory
    DESCRIPTION
      "The pppd option."
   ::= { mGuardPPPOEpppdOptionsEntry 2 }

   mGuardPPPOEpppdOptionsRowStatus OBJECT-TYPE
    SYNTAX RowStatus
    ACCESS read-write
    STATUS mandatory
    DESCRIPTION
      "Row Status"
   ::= { mGuardPPPOEpppdOptionsEntry 3 }


--
-- DHCP Server & DHCP Relay
--

   mGuardDHCP OBJECT IDENTIFIER ::= { mGuardNetwork 5 }

   mGuardDHCPInt OBJECT IDENTIFIER ::= { mGuardDHCP 1 }
   mGuardDHCPExt OBJECT IDENTIFIER ::= { mGuardDHCP 2 }

   --
   -- Internal DHCP Server & Relay
   --

   mGuardDHCPIntStart OBJECT-TYPE
    SYNTAX INTEGER {
			enabled(1),
			disabled(2),
                        enabled-relay(3)
		   }
    ACCESS read-write
    STATUS mandatory
    DESCRIPTION
      "Enable the internal DHCP/DHCP Relay Server ?"
   ::={ mGuardDHCPInt 1 }

   --
   -- Internal DHCP Server
   --

   mGuardDHCPIntPoolEnable OBJECT-TYPE
    SYNTAX INTEGER {
			enabled(1),
			disabled(2)
		   }
    ACCESS read-write
    STATUS mandatory
    DESCRIPTION
      "Enable the dynamic DHCP Pool ?"
   ::={ mGuardDHCPInt 2 }

   mGuardDHCPIntRangeStart OBJECT-TYPE
    SYNTAX IpAddress
    ACCESS read-write
    STATUS mandatory
    DESCRIPTION
      "Start of ip range provided by the builtin DHCP Server for the internal network."
   ::={ mGuardDHCPInt 3 }

   mGuardDHCPIntRangeEnd OBJECT-TYPE
     SYNTAX IpAddress
     ACCESS read-write
     STATUS mandatory
     DESCRIPTION
        "End of ip range provided by the builtin DHCP Server for the internal network."
   ::={ mGuardDHCPInt 4 }

   mGuardDHCPIntNetmask OBJECT-TYPE
     SYNTAX IpAddress
     ACCESS read-write
     STATUS mandatory
     DESCRIPTION
        "Netmask provided by the builtin DHCP Server for the internal network."
    ::={ mGuardDHCPInt 5 }

   mGuardDHCPIntGateway OBJECT-TYPE
     SYNTAX IpAddress
     ACCESS read-write
     STATUS mandatory
     DESCRIPTION
        "Default gateway provided by the builtin DHCP Server for the internal network."
    ::={ mGuardDHCPInt 6 }

   mGuardDHCPIntDnsServer OBJECT-TYPE
     SYNTAX IpAddress
     ACCESS read-write
     STATUS mandatory
     DESCRIPTION
        "DNS Server provided by the builtin DHCP server."
    ::={ mGuardDHCPInt 7 }

   mGuardDHCPIntStaticTable OBJECT-TYPE
    SYNTAX SEQUENCE OF MGuardDHCPIntStaticEntry
    ACCESS not-accessible
    STATUS mandatory
    DESCRIPTION
      "A table containing static MAC-IP address allocations."
   ::= { mGuardDHCPInt 8 }

   mGuardDHCPIntStaticEntry OBJECT-TYPE
     SYNTAX MGuardDHCPIntStaticEntry
     ACCESS not-accessible
     STATUS mandatory
     DESCRIPTION
     "An entry containing a single MAC-IP address allocation."
     INDEX { mGuardDHCPIntStaticIndex }
    ::= { mGuardDHCPIntStaticTable 1 }

    MGuardDHCPIntStaticEntry ::= SEQUENCE {
         mGuardDHCPIntStaticIndex INTEGER,
         mGuardDHCPIntStaticMAC   MacAddress,
         mGuardDHCPIntStaticIP    IpAddress,
         mGuardDHCPIntStaticRowStatus   RowStatus
    }

    mGuardDHCPIntStaticIndex OBJECT-TYPE
     SYNTAX INTEGER (1..250)
     ACCESS not-accessible
     STATUS mandatory
     DESCRIPTION
       "Index to identify allocation entry."
    ::= { mGuardDHCPIntStaticEntry 1 }

    mGuardDHCPIntStaticMAC OBJECT-TYPE
     SYNTAX MacAddress
     ACCESS read-write
     STATUS mandatory
     DESCRIPTION
       "The client's MAC address"
    ::= { mGuardDHCPIntStaticEntry 2 }

    mGuardDHCPIntStaticIP OBJECT-TYPE
     SYNTAX IpAddress
     ACCESS read-write
     STATUS mandatory
     DESCRIPTION
       "The allocated IP address"
    ::= { mGuardDHCPIntStaticEntry 3 }

    mGuardDHCPIntStaticRowStatus OBJECT-TYPE
      SYNTAX RowStatus
      ACCESS read-write
      STATUS mandatory
      DESCRIPTION
        "RowStatus"
    ::= { mGuardDHCPIntStaticEntry 4 }

   mGuardDHCPIntBroadcast OBJECT-TYPE
     SYNTAX IpAddress
     ACCESS read-write
     STATUS mandatory
     DESCRIPTION
        "Broadcast address provided by the builtin DHCP server."
    ::={ mGuardDHCPInt 9 }

   mGuardDHCPIntWINS OBJECT-TYPE
     SYNTAX IpAddress
     ACCESS read-write
     STATUS mandatory
     DESCRIPTION
        "WINS provided by the builtin DHCP Server for the internal network."
    ::={ mGuardDHCPInt 10 }

   mGuardDHCPIntLeaseTime OBJECT-TYPE
    SYNTAX INTEGER
    ACCESS read-write
    STATUS mandatory
    DESCRIPTION
      "Lifetime for DHCP Leases"
   ::={ mGuardDHCPInt 11 }

   --
   -- Internal DHCP Relay Server
   --

   mGuardDHCPIntRelayServerTable OBJECT-TYPE
    SYNTAX SEQUENCE OF MGuardDHCPIntRelayServerEntry
    ACCESS not-accessible
    STATUS mandatory
    DESCRIPTION
      "List of DHCP Servers to relay to."
   ::= { mGuardDHCPInt 50 }

   mGuardDHCPIntRelayServerEntry OBJECT-TYPE
     SYNTAX MGuardDHCPIntRelayServerEntry
     ACCESS not-accessible
     STATUS mandatory
     DESCRIPTION
     "An entry containing a DHCP Relay Server IP."
     INDEX { mGuardDHCPIntRelayServerIndex }
    ::= { mGuardDHCPIntRelayServerTable 1 }

    MGuardDHCPIntRelayServerEntry ::= SEQUENCE {
         mGuardDHCPIntRelayServerIndex INTEGER,
         mGuardDHCPIntRelayServerIP    IpAddress,
         mGuardDHCPIntRelayRowStatus   RowStatus
    }

    mGuardDHCPIntRelayServerIndex OBJECT-TYPE
     SYNTAX INTEGER (1..100)
     ACCESS not-accessible
     STATUS mandatory
     DESCRIPTION
       "Index to identify relay server entry."
    ::= { mGuardDHCPIntRelayServerEntry 1 }

    mGuardDHCPIntRelayServerIP OBJECT-TYPE
     SYNTAX IpAddress
     ACCESS read-write
     STATUS mandatory
     DESCRIPTION
       "The allocated IP address"
    ::= { mGuardDHCPIntRelayServerEntry 2 }

    mGuardDHCPIntRelayRowStatus OBJECT-TYPE
      SYNTAX RowStatus
      ACCESS read-write
      STATUS mandatory
      DESCRIPTION
        "RowStatus"
    ::= { mGuardDHCPIntRelayServerEntry 10 }

   mGuardDHCPIntRelayMaxHop OBJECT-TYPE
    SYNTAX INTEGER
    ACCESS read-write
    STATUS mandatory
    DESCRIPTION
      "Maximal number of Hops when relaying."
   ::={ mGuardDHCPInt 51 }

   mGuardDHCPIntRelayAppend OBJECT-TYPE
    SYNTAX TruthValue
    ACCESS read-write
    STATUS mandatory
    DESCRIPTION
      "Whether to append DHCP Relay Agent Information."
   ::={ mGuardDHCPInt 52 }

   mGuardDHCPIntRelayAppendLimit OBJECT-TYPE
    SYNTAX INTEGER
    ACCESS read-write
    STATUS mandatory
    DESCRIPTION
      "When appending DHCP Relay Agent Information would exceed
      this limit, it is not appended."
   ::={ mGuardDHCPInt 53 }

   mGuardDHCPIntRelayCircuitInfo OBJECT-TYPE
     SYNTAX INTEGER {
			none(1),
			if-idx(2),
			if-name(3),
			if-mac(4),
			if-ip(5),
			sysname(6),
			text(7),
			if-prefixed-ip(8),
                        rs2(9)
		    }
     ACCESS read-write
     STATUS mandatory
     DESCRIPTION
       "What to append as Circuit ID:
        none: no Cicuit ID
        if-idx: the system interface index (1 octet)
        if-name: the systems interface name (ascii)
        if-mac: the MAC address (6 octets)
        if-ip: the IP address (4 octets)
        sysname: the systems hostname
        text: a text defined in mGuardDHCPIntRelayCircuitText.0
        if-prefixed-ip: prefix IP with 0xA1 Sub Remote ID (2+4 octets)
        rs2: Hirschmann RS2 Sub Circuit Information"
    ::={ mGuardDHCPInt 54 }

   mGuardDHCPIntRelayCircuitText OBJECT-TYPE
     SYNTAX DisplayString
     ACCESS read-write
     STATUS mandatory
     DESCRIPTION
        "Text in case mGuardDHCPIntRelayCircuitInfo.0 is set to text(7)."
    ::= { mGuardDHCPInt 55 }

   mGuardDHCPIntRelayRemoteInfo OBJECT-TYPE
     SYNTAX INTEGER {
			none(1),
			if-idx(2),
			if-name(3),
			if-mac(4),
			if-ip(5),
			sysname(6),
			text(7),
			if-prefixed-ip(8),
                        rs2(9)
		    }
     ACCESS read-write
     STATUS mandatory
     DESCRIPTION
       "What to append as Remote ID:
        none: no Cicuit ID
        if-idx: the system interface index (1 octet)
        if-name: the systems interface name (ascii)
        if-mac: the MAC address (6 octets)
        if-ip: the IP address (4 octets)
        sysname: the systems hostname
        text: a text defined in mGuardDHCPIntRelayRemoteText.0
        if-prefixed-ip: prefix IP with 0xA1 Sub Remote ID (2+4 octets)
        rs2: Hirschmann RS2 Sub Circuit Information"
    ::={ mGuardDHCPInt 56 }

   mGuardDHCPIntRelayRemoteText OBJECT-TYPE
     SYNTAX DisplayString
     ACCESS read-write
     STATUS mandatory
     DESCRIPTION
        "Text in case mGuardDHCPIntRelayRemoteInfo.0 is set to text(7)."
    ::= { mGuardDHCPInt 57 }

   --
   -- External DHCP Server & Relay
   --

   mGuardDHCPExtStart OBJECT-TYPE
    SYNTAX INTEGER {
			enabled(1),
			disabled(2),
                        enabled-relay(3)
		   }
    ACCESS read-write
    STATUS mandatory
    DESCRIPTION
      "Enable the external DHCP/DHCP Relay Server ?"
   ::={ mGuardDHCPExt 1 }

   --
   -- External DHCP Server
   --

   mGuardDHCPExtPoolEnable OBJECT-TYPE
    SYNTAX INTEGER {
			enabled(1),
			disabled(2)
		   }
    ACCESS read-write
    STATUS mandatory
    DESCRIPTION
      "Enable the dynamic DHCP Pool ?"
   ::={ mGuardDHCPExt 2 }

   mGuardDHCPExtRangeStart OBJECT-TYPE
    SYNTAX IpAddress
    ACCESS read-write
    STATUS mandatory
    DESCRIPTION
      "Start of ip range provided by the builtin DHCP Server for the external network."
   ::={ mGuardDHCPExt 3 }

   mGuardDHCPExtRangeEnd OBJECT-TYPE
     SYNTAX IpAddress
     ACCESS read-write
     STATUS mandatory
     DESCRIPTION
        "End of ip range provided by the builtin DHCP Server for the external network."
   ::={ mGuardDHCPExt 4 }

   mGuardDHCPExtNetmask OBJECT-TYPE
     SYNTAX IpAddress
     ACCESS read-write
     STATUS mandatory
     DESCRIPTION
        "Netmask provided by the builtin DHCP Server for the external network."
    ::={ mGuardDHCPExt 5 }

   mGuardDHCPExtGateway OBJECT-TYPE
     SYNTAX IpAddress
     ACCESS read-write
     STATUS mandatory
     DESCRIPTION
        "Default gateway provided by the builtin DHCP Server for the external network."
    ::={ mGuardDHCPExt 6 }

   mGuardDHCPExtDnsServer OBJECT-TYPE
     SYNTAX IpAddress
     ACCESS read-write
     STATUS mandatory
     DESCRIPTION
        "DNS Server provided by the builtin DHCP server."
    ::={ mGuardDHCPExt 7 }

   mGuardDHCPExtStaticTable OBJECT-TYPE
    SYNTAX SEQUENCE OF MGuardDHCPExtStaticEntry
    ACCESS not-accessible
    STATUS mandatory
    DESCRIPTION
      "A table containing static MAC-IP address allocations."
   ::= { mGuardDHCPExt 8 }

   mGuardDHCPExtStaticEntry OBJECT-TYPE
     SYNTAX MGuardDHCPExtStaticEntry
     ACCESS not-accessible
     STATUS mandatory
     DESCRIPTION
     "An entry containing a single MAC-IP address allocation."
     INDEX { mGuardDHCPExtStaticIndex }
    ::= { mGuardDHCPExtStaticTable 1 }

    MGuardDHCPExtStaticEntry ::= SEQUENCE {
         mGuardDHCPExtStaticIndex INTEGER,
         mGuardDHCPExtStaticMAC   MacAddress,
         mGuardDHCPExtStaticIP    IpAddress,
         mGuardDHCPExtStaticRowStatus   RowStatus
    }

    mGuardDHCPExtStaticIndex OBJECT-TYPE
     SYNTAX INTEGER (1..250)
     ACCESS not-accessible
     STATUS mandatory
     DESCRIPTION
       "Index to identify allocation entry."
    ::= { mGuardDHCPExtStaticEntry 1 }

    mGuardDHCPExtStaticMAC OBJECT-TYPE
     SYNTAX MacAddress
     ACCESS read-write
     STATUS mandatory
     DESCRIPTION
       "The client's MAC address"
    ::= { mGuardDHCPExtStaticEntry 2 }

    mGuardDHCPExtStaticIP OBJECT-TYPE
     SYNTAX IpAddress
     ACCESS read-write
     STATUS mandatory
     DESCRIPTION
       "The allocated IP address"
    ::= { mGuardDHCPExtStaticEntry 3 }

    mGuardDHCPExtStaticRowStatus OBJECT-TYPE
      SYNTAX RowStatus
      ACCESS read-write
      STATUS mandatory
      DESCRIPTION
        "RowStatus"
    ::= { mGuardDHCPExtStaticEntry 4 }

   mGuardDHCPExtBroadcast OBJECT-TYPE
     SYNTAX IpAddress
     ACCESS read-write
     STATUS mandatory
     DESCRIPTION
        "Broadcast address provided by the builtin DHCP server."
    ::={ mGuardDHCPExt 9 }

   mGuardDHCPExtWINS OBJECT-TYPE
     SYNTAX IpAddress
     ACCESS read-write
     STATUS mandatory
     DESCRIPTION
        "WINS provided by the builtin DHCP Server for the external network."
    ::={ mGuardDHCPExt 10 }

   mGuardDHCPExtLeaseTime OBJECT-TYPE
    SYNTAX INTEGER
    ACCESS read-write
    STATUS mandatory
    DESCRIPTION
      "Lifetime for DHCP Leases"
   ::={ mGuardDHCPExt 11 }

   --
   -- External DHCP Relay Server
   --

   mGuardDHCPExtRelayServerTable OBJECT-TYPE
    SYNTAX SEQUENCE OF MGuardDHCPExtRelayServerEntry
    ACCESS not-accessible
    STATUS mandatory
    DESCRIPTION
      "List of DHCP Servers to relay to."
   ::= { mGuardDHCPExt 50 }

   mGuardDHCPExtRelayServerEntry OBJECT-TYPE
     SYNTAX MGuardDHCPExtRelayServerEntry
     ACCESS not-accessible
     STATUS mandatory
     DESCRIPTION
     "An entry containing a DHCP Relay Server IP."
     INDEX { mGuardDHCPExtRelayServerIndex }
    ::= { mGuardDHCPExtRelayServerTable 1 }

    MGuardDHCPExtRelayServerEntry ::= SEQUENCE {
         mGuardDHCPExtRelayServerIndex INTEGER,
         mGuardDHCPExtRelayServerIP    IpAddress,
         mGuardDHCPExtRelayRowStatus   RowStatus
    }

    mGuardDHCPExtRelayServerIndex OBJECT-TYPE
     SYNTAX INTEGER (1..100)
     ACCESS not-accessible
     STATUS mandatory
     DESCRIPTION
       "Index to identify relay server entry."
    ::= { mGuardDHCPExtRelayServerEntry 1 }

    mGuardDHCPExtRelayServerIP OBJECT-TYPE
     SYNTAX IpAddress
     ACCESS read-write
     STATUS mandatory
     DESCRIPTION
       "The allocated IP address"
    ::= { mGuardDHCPExtRelayServerEntry 2 }

    mGuardDHCPExtRelayRowStatus OBJECT-TYPE
      SYNTAX RowStatus
      ACCESS read-write
      STATUS mandatory
      DESCRIPTION
        "RowStatus"
    ::= { mGuardDHCPExtRelayServerEntry 10 }

   mGuardDHCPExtRelayMaxHop OBJECT-TYPE
    SYNTAX INTEGER
    ACCESS read-write
    STATUS mandatory
    DESCRIPTION
      "Maximal number of Hops when relaying."
   ::={ mGuardDHCPExt 51 }

   mGuardDHCPExtRelayAppend OBJECT-TYPE
    SYNTAX TruthValue
    ACCESS read-write
    STATUS mandatory
    DESCRIPTION
      "Whether to append DHCP Relay Agent Information."
   ::={ mGuardDHCPExt 52 }

   mGuardDHCPExtRelayAppendLimit OBJECT-TYPE
    SYNTAX INTEGER
    ACCESS read-write
    STATUS mandatory
    DESCRIPTION
      "When appending DHCP Relay Agent Information would exceed
      this limit, it is not appended."
   ::={ mGuardDHCPExt 53 }

   mGuardDHCPExtRelayCircuitInfo OBJECT-TYPE
     SYNTAX INTEGER {
			none(1),
			if-idx(2),
			if-name(3),
			if-mac(4),
			if-ip(5),
			sysname(6),
			text(7),
			if-prefixed-ip(8),
                        rs2(9)
		    }
     ACCESS read-write
     STATUS mandatory
     DESCRIPTION
       "What to append as Circuit ID:
        none: no Cicuit ID
        if-idx: the system interface index (1 octet)
        if-name: the systems interface name (ascii)
        if-mac: the MAC address (6 octets)
        if-ip: the IP address (4 octets)
        sysname: the systems hostname
        text: a text defined in mGuardDHCPExtRelayCircuitText.0
        if-prefixed-ip: prefix IP with 0xA1 Sub Remote ID (2+4 octets)
        rs2: Hirschmann RS2 Sub Circuit Information"
    ::={ mGuardDHCPExt 54 }

   mGuardDHCPExtRelayCircuitText OBJECT-TYPE
     SYNTAX DisplayString
     ACCESS read-write
     STATUS mandatory
     DESCRIPTION
        "Text in case mGuardDHCPExtRelayCircuitInfo.0 is set to text(7)."
    ::= { mGuardDHCPExt 55 }

   mGuardDHCPExtRelayRemoteInfo OBJECT-TYPE
     SYNTAX INTEGER {
			none(1),
			if-idx(2),
			if-name(3),
			if-mac(4),
			if-ip(5),
			sysname(6),
			text(7),
			if-prefixed-ip(8),
                        rs2(9)
		    }
     ACCESS read-write
     STATUS mandatory
     DESCRIPTION
       "What to append as Remote ID:
        none: no Cicuit ID
        if-idx: the system interface index (1 octet)
        if-name: the systems interface name (ascii)
        if-mac: the MAC address (6 octets)
        if-ip: the IP address (4 octets)
        sysname: the systems hostname
        text: a text defined in mGuardDHCPExtRelayRemoteText.0
        if-prefixed-ip: prefix IP with 0xA1 Sub Remote ID (2+4 octets)
        rs2: Hirschmann RS2 Sub Circuit Information"
    ::={ mGuardDHCPExt 56 }

   mGuardDHCPExtRelayRemoteText OBJECT-TYPE
     SYNTAX DisplayString
     ACCESS read-write
     STATUS mandatory
     DESCRIPTION
        "Text in case mGuardDHCPExtRelayRemoteInfo.0 is set to text(7)."
    ::= { mGuardDHCPExt 57 }


--
-- Network DNS
--

    mGuardDNS OBJECT IDENTIFIER ::= { mGuardNetwork 6 }

    mGuardDNSSearchPath OBJECT-TYPE
     SYNTAX DisplayString
     ACCESS read-write
     STATUS mandatory
     DESCRIPTION
        "Domain search path."
    ::= { mGuardDNS 1 }

    mGuardDNSServerType OBJECT-TYPE
     SYNTAX INTEGER {
			root(1),
			provider(2),
			user(3)
		    }
     ACCESS read-write
     STATUS mandatory
     DESCRIPTION
        "Type of DNS Servers to query:
         root: DNS root servers
         provider: Provider defined DNS Servers (via DHCP,PPPOE)
         user: User defined DNS Servers"
    ::={ mGuardDNS 2 }

    mGuardDNSUserDefinedServerTable OBJECT-TYPE
     SYNTAX SEQUENCE OF MGuardDNSUserDefinedServerEntry
     ACCESS not-accessible
     STATUS mandatory
     DESCRIPTION
       " A table containing user defined DNS Servers"
    ::={ mGuardDNS 3 }

    mGuardDNSUserDefinedServerEntry OBJECT-TYPE
     SYNTAX MGuardDNSUserDefinedServerEntry
     ACCESS not-accessible
     STATUS mandatory
     DESCRIPTION
       "A mGuardDNSServer entry."
     INDEX { mGuarddnsServerIndex }
    ::={ mGuardDNSUserDefinedServerTable 1 }

    MGuardDNSUserDefinedServerEntry ::= SEQUENCE {
      mGuarddnsServerIndex INTEGER,
      mGuarddnsServerIP    IpAddress,
      mGuarddnsServerRowStatus RowStatus
    }

    mGuarddnsServerIndex OBJECT-TYPE
     SYNTAX INTEGER (1..100)
     ACCESS not-accessible
     STATUS mandatory
     DESCRIPTION
       "Index to identify DNS Server entry."
    ::= { mGuardDNSUserDefinedServerEntry 1 }

    mGuarddnsServerIP OBJECT-TYPE
     SYNTAX IpAddress
     ACCESS read-write
     STATUS mandatory
     DESCRIPTION
      "DNS Server IP address."
    ::= { mGuardDNSUserDefinedServerEntry 2 }

    mGuarddnsServerRowStatus OBJECT-TYPE
      SYNTAX RowStatus
      ACCESS read-write
      STATUS mandatory
      DESCRIPTION
       "RowStatus"
    ::= { mGuardDNSUserDefinedServerEntry 3 }

    mGuardDNSCacheEnabled OBJECT-TYPE
     SYNTAX INTEGER {
			enabled(1),
			disabled(2)
		    }
     ACCESS read-write
     STATUS mandatory
     DESCRIPTION
        "Enable or disable built-in DNS cache feature"
    ::= { mGuardDNS 4 }


--
-- NetworkStatus
--

   mGuardNetworkStatus OBJECT IDENTIFIER ::= { mGuardNetwork 7 }

   mGuardNetworkStatMode OBJECT-TYPE
     SYNTAX DisplayString
     ACCESS read-only
     STATUS mandatory
     DESCRIPTION
      "Current network mode of this device."
    ::= { mGuardNetworkStatus 1 }

    mGuardNetworkStatExtIP OBJECT-TYPE
     SYNTAX DisplayString
     ACCESS read-only
     STATUS mandatory
     DESCRIPTION
      "external IP address of this device."
    ::= { mGuardNetworkStatus 2 }

   mGuardNetworkStatGateway OBJECT-TYPE
     SYNTAX DisplayString
     ACCESS read-only
     STATUS mandatory
     DESCRIPTION
      "Default gateway via the external IP address."
    ::= { mGuardNetworkStatus 3 }

   mGuardNetworkStatVPN OBJECT-TYPE
     SYNTAX DisplayString
     ACCESS read-only
     STATUS mandatory
     DESCRIPTION
      "Statistics about the VPN connections (total/used/up)."
    ::= { mGuardNetworkStatus 4 }

   mGuardNetworkStatDynIPReg OBJECT-TYPE
     SYNTAX DisplayString
     ACCESS read-only
     STATUS mandatory
     DESCRIPTION
      "Statistics about VPN DynIP registration."
    ::= { mGuardNetworkStatus 5 }

   mGuardNetworkStatHTTPSRemAccess OBJECT-TYPE
     SYNTAX DisplayString
     ACCESS read-only
     STATUS mandatory
     DESCRIPTION
      "Status of HTTPS remote access (yes/no)."
    ::= { mGuardNetworkStatus 6 }

   mGuardNetworkStatSSHRemoteAccess OBJECT-TYPE
     SYNTAX DisplayString
     ACCESS read-only
     STATUS mandatory
     DESCRIPTION
      "Status of SSH remote access (yes/no)."
    ::= { mGuardNetworkStatus 7 }

   mGuardNetworkSoftwareVersion OBJECT-TYPE
     SYNTAX DisplayString
     ACCESS read-only
     STATUS mandatory
     DESCRIPTION
      "Current software version."
    ::= { mGuardNetworkStatus 8 }

   mGuardNetworkStatUptime OBJECT-TYPE
     SYNTAX DisplayString
     ACCESS read-only
     STATUS mandatory
     DESCRIPTION
      "Uptime."
    ::= { mGuardNetworkStatus 9 }

   mGuardNetworkStatLanguage OBJECT-TYPE
     SYNTAX DisplayString
     ACCESS read-only
     STATUS mandatory
     DESCRIPTION
      "GAI Language."
    ::= { mGuardNetworkStatus 10 }

--
-- Network Hostname
--

   mGuardHostname OBJECT-TYPE
    SYNTAX DisplayString
    ACCESS read-write
    STATUS mandatory
    DESCRIPTION
       "The hostname of this system"
   ::= { mGuardNetwork 8 }


   mGuardHostnameMode OBJECT-TYPE
    SYNTAX INTEGER {
                       userDefined(1),
                       providerDefined(2)
                   }
    ACCESS read-write
    STATUS mandatory
    DESCRIPTION
       "Hostname mode:
                      1: defined by mGuardHostname,
                      2: provider defined (e.g. DHCP)
       "
   ::= { mGuardNetwork 9 }

--
-- Network PPTP
--

  mGuardPPTP OBJECT IDENTIFIER ::= { mGuardNetwork 10 }

  mGuardPPTPLogin OBJECT-TYPE
    SYNTAX DisplayString
    ACCESS read-write
    STATUS mandatory
    DESCRIPTION
      "PPTP login"
  ::= { mGuardPPTP 1 }

  mGuardPPTPassword OBJECT-TYPE
    SYNTAX DisplayString
    ACCESS read-write
    STATUS mandatory
    DESCRIPTION
      "PPTP password"
  ::= { mGuardPPTP 2 }

  mGuardPPTPLocalIPMode OBJECT-TYPE
   SYNTAX INTEGER {
                     static(1),
		     dhcp(2)
                  }
   ACCESS read-write
   STATUS mandatory
   DESCRIPTION
     "When set to static will use the value from mGuardPPTPLocalIP on it
     external interface connecting to the PPTP server/modem. Otherwise it
     it use DHCP."
  ::= { mGuardPPTP 3 }

  mGuardPPTPLocalIP OBJECT-TYPE
   SYNTAX IpAddress
   ACCESS read-write
   STATUS mandatory
   DESCRIPTION
      "The external IP of this system when connecting to the PPTP server/modem
      when mGuardPPTPLocalIPMode is set to static."
  ::= { mGuardPPTP 4 }

  mGuardPPTPModemIP OBJECT-TYPE
   SYNTAX IpAddress
   ACCESS read-write
   STATUS mandatory
   DESCRIPTION
      "The IP of the PPTP server/modem."
  ::= { mGuardPPTP 5 }

  mGuardPPTPpppdOptionsTable OBJECT-TYPE
    SYNTAX SEQUENCE OF MGuardPPTPpppdOptionsEntry
    ACCESS not-accessible
    STATUS mandatory
    DESCRIPTION
      "A table of options set for the pppd process implementing PPTP."
   ::= { mGuardPPTP 6 }

  mGuardPPTPpppdOptionsEntry OBJECT-TYPE
      SYNTAX MGuardPPTPpppdOptionsEntry
      ACCESS not-accessible
      STATUS mandatory
      DESCRIPTION
       "A single option set for pppd. "
      INDEX { mGuardPPTPpppdOptionsIndex }
  ::= { mGuardPPTPpppdOptionsTable 1 }

  MGuardPPTPpppdOptionsEntry  ::= SEQUENCE {
     mGuardPPTPpppdOptionsIndex     INTEGER,
     mGuardPPTPpppdOptionsValue     DisplayString,
     mGuardPPTPpppdOptionsRowStatus RowStatus
  }

  mGuardPPTPpppdOptionsIndex OBJECT-TYPE
    SYNTAX INTEGER (1..100)
    ACCESS not-accessible
    STATUS mandatory
    DESCRIPTION
      "Table index."
   ::= { mGuardPPTPpppdOptionsEntry 1 }

   mGuardPPTPpppdOptionsValue OBJECT-TYPE
    SYNTAX DisplayString
    ACCESS read-write
    STATUS mandatory
    DESCRIPTION
      "The pppd option."
   ::= { mGuardPPTPpppdOptionsEntry 2 }

   mGuardPPTPpppdOptionsRowStatus OBJECT-TYPE
    SYNTAX RowStatus
    ACCESS read-write
    STATUS mandatory
    DESCRIPTION
      "Row Status"
   ::= { mGuardPPTPpppdOptionsEntry 3 }

--
-- mGuardSerial
--

  mGuardSerial OBJECT IDENTIFIER ::= { mGuardNetwork 11 }

    mGuardSerialBaud OBJECT-TYPE
      SYNTAX INTEGER
      ACCESS read-write
      STATUS mandatory
      DESCRIPTION
         "Baudrate for the serial line. Possible values are 9600, 19200,
         38400, 57600"
      ::= { mGuardSerial 1 }

    mGuardSerialHWHandshakeEnable OBJECT-TYPE
      SYNTAX INTEGER {
      	enabled(1),
      	disabled(2)
      }
      ACCESS read-write
      STATUS mandatory
      DESCRIPTION
         "Enable hardware handshake"
      ::= { mGuardSerial 2 }

    -- Serial PPP Options

    mGuardSerialPPP OBJECT IDENTIFIER ::= { mGuardSerial 3 }

    mGuardSerialPPPEnable OBJECT-TYPE
      SYNTAX INTEGER {
      	enabled(1),
      	disabled(2)
      }
      ACCESS read-write
      STATUS mandatory
      DESCRIPTION
         "Enable PPP"
      ::= { mGuardSerialPPP 1 }

    mGuardSerialPPPLogin OBJECT-TYPE
      SYNTAX DisplayString
      ACCESS read-write
      STATUS mandatory
      DESCRIPTION
        "Login for Serial PPP."
      ::= { mGuardSerialPPP 2 }

    mGuardSerialPPPPasswd OBJECT-TYPE
      SYNTAX DisplayString
      ACCESS read-write
      STATUS mandatory
      DESCRIPTION
        "Password for Serial PPP."
      ::= { mGuardSerialPPP 3 }

    mGuardSerialPPPLocalIP OBJECT-TYPE
      SYNTAX IpAddress
      ACCESS read-write
      STATUS mandatory
      DESCRIPTION
        "Local IP address for PPP."
      ::= { mGuardSerialPPP 4 }

    mGuardSerialPPPRemoteIP OBJECT-TYPE
      SYNTAX IpAddress
      ACCESS read-write
      STATUS mandatory
      DESCRIPTION
        "Remote IP address for PPP."
      ::= { mGuardSerialPPP 5 }


-- Serial PPP Incoming Firewall

    mGuardSerialPPPFWIN  OBJECT IDENTIFIER ::= { mGuardSerialPPP 6 }
	
      mGuardSerialPPPFWINTable OBJECT-TYPE
        SYNTAX SEQUENCE OF MGuardSerialPPPFWINEntry
        ACCESS not-accessible
        STATUS mandatory
        DESCRIPTION
          "A table containing firewall rules for incoming  packets."
        ::= { mGuardSerialPPPFWIN 1 }

      mGuardSerialPPPFWINEntry OBJECT-TYPE
        SYNTAX MGuardSerialPPPFWINEntry
        ACCESS not-accessible
        STATUS mandatory
        DESCRIPTION
          "An entry containing data of a single rule."
        INDEX { mGuardFWINruleIndex }
      ::= { mGuardSerialPPPFWINTable 1 }

      MGuardSerialPPPFWINEntry ::= SEQUENCE{
        mGuardSerialPPPFWINruleIndex       INTEGER,
        mGuardSerialPPPFWINsourceIP        DisplayString,
        mGuardSerialPPPFWINdestinationIP   DisplayString,
        mGuardSerialPPPFWINsport           DisplayString,
        mGuardSerialPPPFWINdport           DisplayString,
        mGuardSerialPPPFWINtarget          INTEGER,
        mGuardSerialPPPFWINproto           INTEGER,
        mGuardSerialPPPFWINlog             INTEGER,
        mGuardSerialPPPFWINRowStatus       RowStatus,
        mGuardSerialPPPFWINcomment         DisplayString
      }

      mGuardSerialPPPFWINruleIndex OBJECT-TYPE
        SYNTAX   INTEGER (1..250)
        ACCESS   not-accessible
        STATUS   mandatory
        DESCRIPTION
          "Index to identify the rule."
      ::= { mGuardSerialPPPFWINEntry 1 }

      mGuardSerialPPPFWINsourceIP OBJECT-TYPE
        SYNTAX DisplayString
        ACCESS read-write
        STATUS mandatory
        DESCRIPTION
          "The rule's source IP address"
        ::= { mGuardSerialPPPFWINEntry 2 }

      mGuardSerialPPPFWINdestinationIP OBJECT-TYPE
        SYNTAX DisplayString
        ACCESS read-write
        STATUS mandatory
        DESCRIPTION
          "The rule's source IP address"
        ::= { mGuardSerialPPPFWINEntry 3 }

      mGuardSerialPPPFWINsport OBJECT-TYPE
        SYNTAX DisplayString
        ACCESS read-write
        STATUS mandatory
        DESCRIPTION
          "The rule's source port"
        ::= { mGuardSerialPPPFWINEntry 4 }

      mGuardSerialPPPFWINdport OBJECT-TYPE
        SYNTAX DisplayString
        ACCESS read-write
        STATUS mandatory
        DESCRIPTION
          "The rule's destination port"
        ::= { mGuardSerialPPPFWINEntry 5 }

      mGuardSerialPPPFWINtarget OBJECT-TYPE
        SYNTAX INTEGER {
          	  accept(1),
    		  reject(2),
    		  drop(3)
    		}
        ACCESS read-write
        STATUS mandatory
        DESCRIPTION
          "The rule's target"
        ::= { mGuardSerialPPPFWINEntry 6 }

      mGuardSerialPPPFWINproto OBJECT-TYPE
        SYNTAX INTEGER {
          tcp(1),
    		  udp(2),
    		  icmp(3),
    		  all(4)
        }
        ACCESS read-write
        STATUS mandatory
        DESCRIPTION
          "The rule's protocol"
        ::= { mGuardSerialPPPFWINEntry 7 }

      mGuardSerialPPPFWINlog OBJECT-TYPE
        SYNTAX INTEGER {
          yes(1),
          no(2)
        }
        ACCESS read-write
        STATUS mandatory
        DESCRIPTION
          "Log packets matching this rule ?"
        ::= { mGuardSerialPPPFWINEntry 8 }

      mGuardSerialPPPFWINRowStatus OBJECT-TYPE
        SYNTAX RowStatus
        ACCESS read-write
        STATUS mandatory
        DESCRIPTION
          "RowStatus"
        ::= { mGuardSerialPPPFWINEntry 9 }

       mGuardSerialPPPFWINcomment OBJECT-TYPE
        SYNTAX DisplayString
        ACCESS read-write
        STATUS mandatory
        DESCRIPTION
          "Commentary or name for this rule."
        ::= { mGuardSerialPPPFWINEntry 10 }
	
    mGuardSerialPPPFWINLogDefault OBJECT-TYPE
      SYNTAX INTEGER {
        yes(1),
        no(2)
      }
      ACCESS read-write
      STATUS mandatory
      DESCRIPTION
        "Log entries for undefined incoming connection attemps."
      ::= { mGuardSerialPPPFWIN 2 }

-- Serial PPP Outgoing Firewall

  mGuardSerialPPPFWOUT  OBJECT IDENTIFIER ::= { mGuardSerialPPP 7 }

  mGuardSerialPPPFWOUTTable OBJECT-TYPE
    SYNTAX SEQUENCE OF MGuardSerialPPPFWOUTEntry
    ACCESS not-accessible
    STATUS mandatory
    DESCRIPTION
      "A table containing firewall rules for incoming  packets."
    ::= { mGuardSerialPPPFWOUT 1 }

  mGuardSerialPPPFWOUTEntry OBJECT-TYPE
    SYNTAX MGuardSerialPPPFWOUTEntry
    ACCESS not-accessible
    STATUS mandatory
    DESCRIPTION
      "An entry containing data of a single rule."
    INDEX { mGuardSerialPPPFWOUTruleIndex }
    ::= { mGuardSerialPPPFWOUTTable 1 }

  MGuardSerialPPPFWOUTEntry ::= SEQUENCE{
    mGuardSerialPPPFWOUTruleIndex       INTEGER,
    mGuardSerialPPPFWOUTsourceIP        DisplayString,
    mGuardSerialPPPFWOUTtargetIP   	DisplayString,
    mGuardSerialPPPFWOUTsport           DisplayString,
    mGuardSerialPPPFWOUTdport           DisplayString,
    mGuardSerialPPPFWOUTtarget          INTEGER,
    mGuardSerialPPPFWOUTproto           INTEGER,
    mGuardSerialPPPFWOUTlog             INTEGER,
    mGuardSerialPPPFWOUTRowStatus       RowStatus,
    mGuardSerialPPPFWOUTcomment         DisplayString
  }

  mGuardSerialPPPFWOUTruleIndex OBJECT-TYPE
    SYNTAX   INTEGER (1..250)
    ACCESS   not-accessible
    STATUS   mandatory
    DESCRIPTION
      "Index to identify the rule."
  ::= { mGuardSerialPPPFWOUTEntry 1 }

  mGuardSerialPPPFWOUTsourceIP OBJECT-TYPE
    SYNTAX DisplayString
    ACCESS read-write
    STATUS mandatory
    DESCRIPTION
      "The rule's source IP address"
  ::= { mGuardSerialPPPFWOUTEntry 2 }

  mGuardSerialPPPFWOUTtargetIP OBJECT-TYPE
    SYNTAX DisplayString
    ACCESS read-write
    STATUS mandatory
    DESCRIPTION
      "The rule's source IP address"
    ::= { mGuardSerialPPPFWOUTEntry 3 }

  mGuardSerialPPPFWOUTsport OBJECT-TYPE
    SYNTAX DisplayString
    ACCESS read-write
    STATUS mandatory
    DESCRIPTION
      "The rule's source port"
    ::= { mGuardSerialPPPFWOUTEntry 4 }

  mGuardSerialPPPFWOUTdport OBJECT-TYPE
    SYNTAX DisplayString
    ACCESS read-write
    STATUS mandatory
    DESCRIPTION
      "The rule's destination port"
    ::= { mGuardSerialPPPFWOUTEntry 5 }

  mGuardSerialPPPFWOUTtarget OBJECT-TYPE
    SYNTAX INTEGER {
      accept(1),
		  reject(2),
		  drop(3)
		}
    ACCESS read-write
    STATUS mandatory
    DESCRIPTION
      "The rule's target"
    ::= { mGuardSerialPPPFWOUTEntry 6 }

  mGuardSerialPPPFWOUTproto OBJECT-TYPE
    SYNTAX INTEGER {
      tcp(1),
		  udp(2),
		  icmp(3),
		  all(4)
    }
    ACCESS read-write
    STATUS mandatory
    DESCRIPTION
      "The rule's protocol"
    ::= { mGuardSerialPPPFWOUTEntry 7 }

  mGuardSerialPPPFWOUTlog OBJECT-TYPE
    SYNTAX INTEGER {
      yes(1),
      no(2)
    }
    ACCESS read-write
    STATUS mandatory
    DESCRIPTION
      "Log packets matching this rule ?"
    ::= { mGuardSerialPPPFWOUTEntry 8 }

  mGuardSerialPPPFWOUTRowStatus OBJECT-TYPE
    SYNTAX RowStatus
    ACCESS read-write
    STATUS mandatory
    DESCRIPTION
      "RowStatus"
    ::= { mGuardSerialPPPFWOUTEntry 9 }

    mGuardSerialPPPFWOUTcomment OBJECT-TYPE
     SYNTAX DisplayString
     ACCESS read-write
     STATUS mandatory
     DESCRIPTION
       "Commentary or name for this rule."
     ::= { mGuardSerialPPPFWOUTEntry 10 }

  mGuardSerialPPPFWOUTLogDefault OBJECT-TYPE
    SYNTAX INTEGER{
      yes(1),
      no(2)
    }
    ACCESS read-write
    STATUS mandatory
    DESCRIPTION
      "Log entries for unknown outgoing connection attemps ?"
    ::= { mGuardSerialPPPFWOUT 2 }



--
-- ARP Timeout
--

   mGuardArpTimeout OBJECT-TYPE
    SYNTAX INTEGER
    ACCESS read-write
    STATUS mandatory
    DESCRIPTION
       "Global ARP timeout in seconds."
   ::= { mGuardNetwork 12 }



--
-- Passwords
--

    mGuardPasswords OBJECT IDENTIFIER ::= { mGuardSystem 1 }


    mGuardRootPassword OBJECT-TYPE
     SYNTAX DisplayString
     ACCESS read-write
     STATUS mandatory
     DESCRIPTION
       "Object to change the root password.
       Change by setting:  <old root password> <new root password>"
    ::= { mGuardPasswords 1 }

    mGuardAdminPassword OBJECT-TYPE
     SYNTAX DisplayString
     ACCESS read-write
     STATUS mandatory
     DESCRIPTION
       "Object to change the admin password."
    ::= { mGuardPasswords 2 }

    mGuardUserPassword OBJECT-TYPE
     SYNTAX DisplayString
     ACCESS read-write
     STATUS mandatory
     DESCRIPTION
       "Object to change the user password."
    ::= { mGuardPasswords 3 }

    mGuardUserPwdEnable OBJECT-TYPE
     SYNTAX TruthValue
     ACCESS read-write
     STATUS mandatory
     DESCRIPTION
       "Enable user password ?
           yes,no"
    ::= { mGuardPasswords 4 }

--
-- HTTPS Remote Access
--

    mGuardHTTPSRemoteAccess OBJECT IDENTIFIER ::= { mGuardSystem 2 }

    mGuardHTTPSRemoteEnable OBJECT-TYPE
     SYNTAX TruthValue
     ACCESS read-write
     STATUS mandatory
     DESCRIPTION
       " Value to control HTTPS remote access:
            yes: enabled
            no: disabled"
    ::= { mGuardHTTPSRemoteAccess 1 }

    mGuardHTTPSRemotePort OBJECT-TYPE
     SYNTAX DisplayString
     ACCESS read-write
     STATUS mandatory
     DESCRIPTION
       "Port for HTTPS remote Access (regularly 443), service names allowed."
    ::= { mGuardHTTPSRemoteAccess 2 }

    mGuardHTTPSRemoteFWRuleTable OBJECT-TYPE
     SYNTAX SEQUENCE OF MGuardHTTPSRemoteFWRuleEntry
     ACCESS not-accessible
     STATUS mandatory
     DESCRIPTION
        "A table containing firewall rules to allow HTTPS remote access."
     ::= { mGuardHTTPSRemoteAccess 3 }

    mGuardHTTPSRemoteFWRuleEntry OBJECT-TYPE
     SYNTAX MGuardHTTPSRemoteFWRuleEntry
     ACCESS not-accessible
     STATUS mandatory
     DESCRIPTION
     "An entry containing a single firewall rule to allow HTTPS remote access."
      INDEX { mGuardHTTPSFWruleIndex }
      ::= { mGuardHTTPSRemoteFWRuleTable 1 }

    MGuardHTTPSRemoteFWRuleEntry ::= SEQUENCE {
         mGuardHTTPSFWruleIndex INTEGER,
         mGuardHTTPSFWsourceIP  DisplayString,
         mGuardHTTPSFWinterface INTEGER,
         mGuardHTTPSFWtarget    INTEGER,
         mGuardHTTPSFWlog       INTEGER,
         mGuardHTTPSFWRowStatus  RowStatus,
         mGuardHTTPSFWcomment    DisplayString
    }

    mGuardHTTPSFWruleIndex OBJECT-TYPE
     SYNTAX INTEGER (1..100)
     ACCESS not-accessible
     STATUS mandatory
     DESCRIPTION
       "Index to identify rule."
    ::= { mGuardHTTPSRemoteFWRuleEntry 1 }

    mGuardHTTPSFWsourceIP OBJECT-TYPE
     SYNTAX DisplayString
     ACCESS read-write
     STATUS mandatory
     DESCRIPTION
       "The rule's source IP address  "
    ::= { mGuardHTTPSRemoteFWRuleEntry 2 }

    mGuardHTTPSFWinterface OBJECT-TYPE
     SYNTAX INTEGER {
			extern(1),
			intern(2)
		    }
     ACCESS read-write
     STATUS mandatory
     DESCRIPTION
       "The network interface the rule belongs to (extern/intern)."
    ::= { mGuardHTTPSRemoteFWRuleEntry 3 }

    mGuardHTTPSFWtarget OBJECT-TYPE
     SYNTAX INTEGER {
			accept(1),
			reject(2),
			drop(3)
		    }
     ACCESS read-write
     STATUS mandatory
     DESCRIPTION
       "The target of the rule (accept,reject,drop)."
    ::= { mGuardHTTPSRemoteFWRuleEntry 4 }

    mGuardHTTPSFWlog OBJECT-TYPE
     SYNTAX INTEGER {
                      yes(1),
                      no(2)
                    }
     ACCESS read-write
     STATUS mandatory
     DESCRIPTION
       " Log packets matching this rule ?"
     ::= { mGuardHTTPSRemoteFWRuleEntry 5 }


    mGuardHTTPSFWRowStatus OBJECT-TYPE
     SYNTAX RowStatus
     ACCESS read-write
     STATUS mandatory
     DESCRIPTION
      "RowStatus"
    ::= { mGuardHTTPSRemoteFWRuleEntry 6 }

    mGuardHTTPSFWcomment OBJECT-TYPE
     SYNTAX DisplayString
     ACCESS read-write
     STATUS mandatory
     DESCRIPTION
       "Commentary or name for this rule."
     ::= { mGuardHTTPSRemoteFWRuleEntry 7 }

--
-- SSH Remote Access
--

    mGuardSSHRemoteAccess OBJECT IDENTIFIER ::= { mGuardSystem 3 }

    mGuardSSHRemoteEnable OBJECT-TYPE
     SYNTAX TruthValue
     ACCESS read-write
     STATUS mandatory
     DESCRIPTION
       " Value to control SSH remote access:
            yes: enabled
            no: disabled"
    ::= { mGuardSSHRemoteAccess 1 }


    mGuardSSHRemotePort OBJECT-TYPE
     SYNTAX DisplayString
     ACCESS read-write
     STATUS mandatory
     DESCRIPTION
       "Port for SSH remote Access (regularly 22), service names allowed."
    ::= { mGuardSSHRemoteAccess 2 }


     mGuardSSHRemoteFWRuleTable OBJECT-TYPE
      SYNTAX SEQUENCE OF MGuardSSHRemoteFWRuleEntry
      ACCESS not-accessible
      STATUS mandatory
      DESCRIPTION
        "A table containing firewall rules to allow SSH remote access."
     ::= { mGuardSSHRemoteAccess 3 }

     mGuardSSHRemoteFWRuleEntry OBJECT-TYPE
      SYNTAX MGuardSSHRemoteFWRuleEntry
      ACCESS not-accessible
      STATUS mandatory
      DESCRIPTION
      "An entry containing a single firewall rule to allow SSH remote access."
      INDEX { mGuardSSHFWruleIndex }
     ::= { mGuardSSHRemoteFWRuleTable 1 }

    MGuardSSHRemoteFWRuleEntry ::= SEQUENCE {
         mGuardSSHFWruleIndex INTEGER,
         mGuardSSHFWsourceIP  DisplayString,
         mGuardSSHFWinterface INTEGER,
         mGuardSSHFWtarget    INTEGER,
         mGuardSSHFWlog       INTEGER,
         mGuardSSHFWRowStatus RowStatus,
         mGuardSSHFWcomment   DisplayString
    }

    mGuardSSHFWruleIndex OBJECT-TYPE
     SYNTAX INTEGER (1..100)
     ACCESS not-accessible
     STATUS mandatory
     DESCRIPTION
       "Index to identify rule."
    ::= { mGuardSSHRemoteFWRuleEntry 1 }

    mGuardSSHFWsourceIP OBJECT-TYPE
     SYNTAX DisplayString
     ACCESS read-write
     STATUS mandatory
     DESCRIPTION
       "The rule's source IP address  "
    ::= { mGuardSSHRemoteFWRuleEntry 2 }

    mGuardSSHFWinterface OBJECT-TYPE
     SYNTAX INTEGER {
			extern(1),
			intern(2)
		    }
     ACCESS read-write
     STATUS mandatory
     DESCRIPTION
       "The network interface the rule belongs to (extern/intern)."
    ::= { mGuardSSHRemoteFWRuleEntry 3 }

    mGuardSSHFWtarget OBJECT-TYPE
     SYNTAX INTEGER {
			accept(1),
			reject(2),
			drop(3)
		    }
     ACCESS read-write
     STATUS mandatory
     DESCRIPTION
       "The target of the rule (accept/reject/drop)."
    ::= { mGuardSSHRemoteFWRuleEntry 4 }


     mGuardSSHFWlog OBJECT-TYPE
      SYNTAX INTEGER {
                       yes(1),
                       no(2)
                    }
      ACCESS read-write
      STATUS mandatory
      DESCRIPTION
        " Log packets matching this rule ?"
      ::= { mGuardSSHRemoteFWRuleEntry 5 }


    mGuardSSHFWRowStatus OBJECT-TYPE
     SYNTAX RowStatus
     ACCESS read-write
     STATUS mandatory
     DESCRIPTION
      "RowStatus"
    ::= { mGuardSSHRemoteFWRuleEntry 6 }

    mGuardSSHFWcomment OBJECT-TYPE
     SYNTAX DisplayString
     ACCESS read-write
     STATUS mandatory
     DESCRIPTION
       "Commentary or name for this rule."
     ::= { mGuardSSHRemoteFWRuleEntry 7 }


--
-- Web Interface Setting
--

    mGuardWebInterface OBJECT IDENTIFIER ::= { mGuardSystem 4 }

    mGuardWebInterfaceLanguage OBJECT-TYPE
     SYNTAX INTEGER {
			automatic(1),
			english(2),
			german(3),
			japanese(4)
                    }
     ACCESS read-write
     STATUS mandatory
     DESCRIPTION
      "The language used in the web interface."
    ::= { mGuardWebInterface 1 }

    mGuardWebInterfaceSessionTimeout OBJECT-TYPE
     SYNTAX INTEGER
     ACCESS read-write
     STATUS mandatory
     DESCRIPTION
      "The session timeout of the web interface in seconds.  If no changes are submitted
       for the specified time, the session is terminated and it will be necessary to log
       in again before further use of the web interface."
    ::= { mGuardWebInterface 2 }

    mGuardWebInterfaceApplyButtonScope OBJECT-TYPE
     SYNTAX INTEGER {
			page(1),
			session(2)
                   }
     ACCESS read-write
     STATUS mandatory
     DESCRIPTION
      "The scope of the Apply button in the web interface."
    ::= { mGuardWebInterface 3 }


--
-- Product numbers
--

    mGuardSysProduct OBJECT-TYPE
      SYNTAX INTEGER {
                        unknown(1),
                        mGuard-smart-pr(51001),
                        mGuard-core-266(51002),
                        mGuard-smart-gw-266(51003),
                        mGuard-smart-enxl(51011),
                        mGuard-core-533(51012),
                        mGuard-smart-gw-533(51013),
                        mGuard-smart(51020),
                        mGuard-smart-en(51021),
                        mGuard-pci(51030),
                        mGuard-pci-pr(51031),
                        mGuard-pci-en(51032),
                        mGuard-pci-enxl(51033),
                        mGuard-industrial-enfw(51040),
                        mGuard-industrial-enxl(51044),
                        mGuard-blade-en(51052),
                        mGuard-blade-enxl(51053),
                        mGuard-delta(51060),
                        mGuard-delta-en(51062),
                        mGuard-delta-enxl(51063)
                     }
      ACCESS read-only
      STATUS mandatory
      DESCRIPTION
       "Manufacturer-defined product identifier."
    ::= { mGuardSystem 9 }

--
-- Hardware Information
--

    mGuardHardwareInformation OBJECT IDENTIFIER ::= { mGuardSystem 5 }

    mGuardHardware OBJECT-TYPE
     SYNTAX DisplayString
     ACCESS read-only
     STATUS mandatory
     DESCRIPTION
       "The hardware of the mGuard."
    ::= { mGuardHardwareInformation 1 }


    mGuardCPU OBJECT-TYPE
     SYNTAX DisplayString
     ACCESS read-only
     STATUS mandatory
     DESCRIPTION
       "The CPU name."
    ::= { mGuardHardwareInformation 2 }


    mGuardCPUFamily OBJECT-TYPE
     SYNTAX DisplayString
     ACCESS read-only
     STATUS mandatory
     DESCRIPTION
       "The CPU family."
    ::= { mGuardHardwareInformation 3 }

    mGuardCPUStepping OBJECT-TYPE
     SYNTAX DisplayString
     ACCESS read-only
     STATUS mandatory
     DESCRIPTION
       "The CPU stepping."
    ::= { mGuardHardwareInformation 4 }

   mGuardCPUSpeed OBJECT-TYPE
     SYNTAX DisplayString
     ACCESS read-only
     STATUS mandatory
     DESCRIPTION
       "The CPU speed in MHz."
    ::= { mGuardHardwareInformation 5 }

   mGuardSystemTemperature OBJECT-TYPE
     SYNTAX DisplayString
     ACCESS read-only
     STATUS mandatory
     DESCRIPTION
       "The current system temperature (in degrees Celsius)."
    ::= { mGuardHardwareInformation 6 }

    mGuardUptime OBJECT-TYPE
     SYNTAX DisplayString
     ACCESS read-only
     STATUS mandatory
     DESCRIPTION
       "The system uptime."
    ::= { mGuardHardwareInformation 7 }

    mGuardUSMem OBJECT-TYPE
     SYNTAX DisplayString
     ACCESS read-only
     STATUS mandatory
     DESCRIPTION
       "The userspace memory."
    ::= { mGuardHardwareInformation 8 }

    mGuardMAC1 OBJECT-TYPE
     SYNTAX DisplayString
     ACCESS read-only
     STATUS mandatory
     DESCRIPTION
       "The MAC address of the first network interface."
    ::= { mGuardHardwareInformation 9 }

    mGuardMAC2 OBJECT-TYPE
     SYNTAX DisplayString
     ACCESS read-only
     STATUS mandatory
     DESCRIPTION
       "The MAC address of the second network interface."
    ::= { mGuardHardwareInformation 10 }

    mGuardMAC3 OBJECT-TYPE
     SYNTAX DisplayString
     ACCESS read-only
     STATUS mandatory
     DESCRIPTION
       "The MAC address of the third network interface."
    ::= { mGuardHardwareInformation 11 }

    mGuardSerialNumber OBJECT-TYPE
     SYNTAX DisplayString
     ACCESS read-only
     STATUS mandatory
     DESCRIPTION
       "The system's serial number ."
    ::= { mGuardHardwareInformation 12 }

   mGuardVerParSet OBJECT-TYPE
     SYNTAX DisplayString
     ACCESS read-only
     STATUS mandatory
     DESCRIPTION
       "The parameterset version."
    ::= { mGuardHardwareInformation 13 }

    mGuardProductName OBJECT-TYPE
     SYNTAX DisplayString
     ACCESS read-only
     STATUS mandatory
     DESCRIPTION
       "The product name."
    ::= { mGuardHardwareInformation 14 }

    mGuardOEMName OBJECT-TYPE
     SYNTAX DisplayString
     ACCESS read-only
     STATUS mandatory
     DESCRIPTION
       "The name of the OEM."
    ::= { mGuardHardwareInformation 15 }

    mGuardOEMSerial OBJECT-TYPE
     SYNTAX DisplayString
     ACCESS read-only
     STATUS mandatory
     DESCRIPTION
       "The OEM serial number ."
    ::= { mGuardHardwareInformation 16 }

    mGuardManufacturer OBJECT-TYPE
     SYNTAX DisplayString
     ACCESS read-only
     STATUS mandatory
     DESCRIPTION
       "The system manufacturer."
    ::= { mGuardHardwareInformation 17 }

    mGuardManuDate OBJECT-TYPE
     SYNTAX DisplayString
     ACCESS read-only
     STATUS mandatory
     DESCRIPTION
       "Date of manufacturing."
    ::= { mGuardHardwareInformation 18 }

    mGuardBootLoader OBJECT-TYPE
     SYNTAX DisplayString
     ACCESS read-only
     STATUS mandatory
     DESCRIPTION
       "The bootloader used at production ."
    ::= { mGuardHardwareInformation 19 }

    mGuardHardwareVersion OBJECT-TYPE
     SYNTAX DisplayString
     ACCESS read-only
     STATUS mandatory
     DESCRIPTION
       "The hardware version."
    ::= { mGuardHardwareInformation 20 }

   mGuardRescueSystem OBJECT-TYPE
     SYNTAX DisplayString
     ACCESS read-only
     STATUS mandatory
     DESCRIPTION
       "The rescue system used at production ."
    ::= { mGuardHardwareInformation 21 }

   mGuardProdSoft OBJECT-TYPE
     SYNTAX DisplayString
     ACCESS read-only
     STATUS mandatory
     DESCRIPTION
       "The software used at production ."
    ::= { mGuardHardwareInformation 22 }

--
-- Package Information
--

    mGuardVersions OBJECT IDENTIFIER ::= { mGuardSystem 7 }

    mGuardVersion OBJECT-TYPE
     SYNTAX DisplayString
     ACCESS read-only
     STATUS mandatory
     DESCRIPTION
       "The current version."
    ::= { mGuardVersions 1 }

    mGuardBaseVersion OBJECT-TYPE
     SYNTAX DisplayString
     ACCESS read-only
     STATUS mandatory
     DESCRIPTION
       "The base version."
    ::=  { mGuardVersions 2 }

    mGuardUpdates OBJECT-TYPE
     SYNTAX DisplayString
     ACCESS read-only
     STATUS mandatory
     DESCRIPTION
       "Performed updates."
     ::= { mGuardVersions 3 }


    mGuardPackageVersionTable OBJECT-TYPE
      SYNTAX SEQUENCE OF MGuardPackageVersionEntry
      ACCESS not-accessible
      STATUS mandatory
      DESCRIPTION
       "Package descriptions."
    ::= { mGuardVersions 4 }

     mGuardPackageVersionEntry OBJECT-TYPE
      SYNTAX MGuardPackageVersionEntry
      ACCESS not-accessible
      STATUS mandatory
      DESCRIPTION
       "Description of a single package."
      INDEX { mGuardPkgIndex }
    ::= { mGuardPackageVersionTable 1 }

    MGuardPackageVersionEntry ::= SEQUENCE
    {
      mGuardPkgIndex  INTEGER,
      mGuardPkgName   DisplayString,
      mGuardPkgVerNum DisplayString,
      mGuardPkgVerVersion DisplayString,
      mGuardPkgVerFlavour DisplayString
    }

    mGuardPkgIndex OBJECT-TYPE
     SYNTAX INTEGER (1..250)
     ACCESS not-accessible
     STATUS mandatory
     DESCRIPTION
       "Index to identify package."
    ::= {mGuardPackageVersionEntry 1 }

    mGuardPkgName OBJECT-TYPE
     SYNTAX DisplayString
     ACCESS read-only
     STATUS mandatory
     DESCRIPTION
       "Package name."
    ::= {mGuardPackageVersionEntry 2 }

    mGuardPkgVerNum OBJECT-TYPE
     SYNTAX DisplayString
     ACCESS read-only
     STATUS mandatory
     DESCRIPTION
       "Package version number."
    ::= {mGuardPackageVersionEntry 3 }

    mGuardPkgVerVersion OBJECT-TYPE
     SYNTAX DisplayString
     ACCESS read-only
     STATUS mandatory
     DESCRIPTION
       "Package version."
    ::= {mGuardPackageVersionEntry 4 }

    mGuardPkgVerFlavour OBJECT-TYPE
     SYNTAX DisplayString
     ACCESS read-only
     STATUS mandatory
     DESCRIPTION
       "Package flavour."
    ::= {mGuardPackageVersionEntry 5 }

--
-- Reboot
--

    mGuardAction OBJECT-TYPE
     SYNTAX INTEGER {
			reboot(1)
		    }
     ACCESS read-write
     STATUS mandatory
     DESCRIPTION
       "If set to 1, the system reboots."
    ::= { mGuardSystem 8 }

--
-- SNMP Remote Access
--

   mGuardSNMPenableV3 OBJECT-TYPE
    SYNTAX INTEGER {
                      yes(1),
		      no(2)
		   }
    ACCESS read-write
    STATUS mandatory
    DESCRIPTION
      "Should SNMPv3 be enabled ?"
   ::= { mGuardSNMP 1 }

    mGuardSNMPenableV1 OBJECT-TYPE
    SYNTAX INTEGER {
                      yes(1),
		      no(2)
		   }
    ACCESS read-write
    STATUS mandatory
    DESCRIPTION
      "Should SNMPv1 be enabled ?"
   ::= { mGuardSNMP 2 }

   mGuardSNMPport OBJECT-TYPE
    SYNTAX DisplayString
    ACCESS read-write
    STATUS mandatory
    DESCRIPTION
      "The port the snmp agent listens to."
    ::= { mGuardSNMP 3 }

   mGuardSNMPv1ROCommunity OBJECT-TYPE
    SYNTAX DisplayString
    ACCESS read-write
    STATUS mandatory
    DESCRIPTION
      "Read-only community string for SNMPv1."
   ::= { mGuardSNMP 4 }

   mGuardSNMPv1RWCommunity OBJECT-TYPE
    SYNTAX DisplayString
    ACCESS read-write
    STATUS mandatory
    DESCRIPTION
      "Read-write community string for SNMPv1."
   ::= { mGuardSNMP 5 }


   mGuardSNMPFWRuleTable OBJECT-TYPE
    SYNTAX SEQUENCE OF MGuardSNMPFWRuleEntry
    ACCESS not-accessible
    STATUS mandatory
    DESCRIPTION
      "A table containing firewall rules to allow SNMP access."
   ::= { mGuardSNMP 6 }


-- SNMP access rule table

   mGuardSNMPFWRuleEntry OBJECT-TYPE
     SYNTAX MGuardSNMPFWRuleEntry
     ACCESS not-accessible
     STATUS mandatory
     DESCRIPTION
     "An entry containing a single firewall rule to allow SNMP access."
     INDEX { mGuardSNMPFWruleIndex }
    ::= { mGuardSNMPFWRuleTable 1 }

    MGuardSNMPFWRuleEntry ::= SEQUENCE {
         mGuardSNMPFWruleIndex INTEGER,
         mGuardSNMPFWsourceIP  DisplayString,
         mGuardSNMPFWinterface INTEGER,
         mGuardSNMPFWtarget    INTEGER,
         mGuardSNMPFWlog       INTEGER,
         mGuardSNMPFWRowStatus RowStatus,
         mGuardSNMPFWcomment   DisplayString
    }

    mGuardSNMPFWruleIndex OBJECT-TYPE
     SYNTAX INTEGER (1..100)
     ACCESS not-accessible
     STATUS mandatory
     DESCRIPTION
       "Index to identify rule."
    ::= { mGuardSNMPFWRuleEntry 1 }

    mGuardSNMPFWsourceIP OBJECT-TYPE
     SYNTAX DisplayString
     ACCESS read-write
     STATUS mandatory
     DESCRIPTION
       "The rule's source IP address  "
    ::= { mGuardSNMPFWRuleEntry 2 }

    mGuardSNMPFWinterface OBJECT-TYPE
     SYNTAX INTEGER {
			extern(1),
			intern(2)
		    }
     ACCESS read-write
     STATUS mandatory
     DESCRIPTION
       "The network interface the rule belongs to (extern/intern)."
    ::= { mGuardSNMPFWRuleEntry 3 }

    mGuardSNMPFWtarget OBJECT-TYPE
     SYNTAX INTEGER {
			accept(1),
			reject(2),
			drop(3)
		    }
     ACCESS read-write
     STATUS mandatory
     DESCRIPTION
       "The target of the rule (accept/reject/drop)."
    ::= { mGuardSNMPFWRuleEntry 4 }


     mGuardSNMPFWlog OBJECT-TYPE
      SYNTAX INTEGER {
                       yes(1),
                       no(2)
                     }
      ACCESS read-write
      STATUS mandatory
      DESCRIPTION
        " Log packets matching this rule ?"
      ::= { mGuardSNMPFWRuleEntry 5 }


    mGuardSNMPFWRowStatus OBJECT-TYPE
     SYNTAX RowStatus
     ACCESS read-write
     STATUS mandatory
     DESCRIPTION
      "RowStatus"
    ::= { mGuardSNMPFWRuleEntry 6 }

    mGuardSNMPFWcomment OBJECT-TYPE
     SYNTAX DisplayString
     ACCESS read-write
     STATUS mandatory
     DESCRIPTION
       "Commentary or name for this rule."
     ::= { mGuardSNMPFWRuleEntry 7 }



-- SNMP trap configuration


    mGuardSNMPTrapReceiverTable OBJECT-TYPE
         SYNTAX      SEQUENCE OF MGuardSNMPTrapReceiverEntry
         ACCESS      not-accessible
         STATUS      mandatory
         DESCRIPTION
                     "Trap messages are sent across a network to an SNMP Network Manager.
                     These messages alert the manager to events occurring within the security
                     gateway or on the network. Up to six simultaneous trap receivers are supported."
         ::= { mGuardSNMP 7 }

    mGuardSNMPTrapReceiverEntry OBJECT-TYPE
         SYNTAX      MGuardSNMPTrapReceiverEntry
         ACCESS      not-accessible
         STATUS      mandatory
         DESCRIPTION
                     "Security gateway's Snmp Trap Receiver Config entry"
         INDEX       { mGuardSNMPTrapReceiverIndex }
         ::= { mGuardSNMPTrapReceiverTable 1 }

    MGuardSNMPTrapReceiverEntry ::= SEQUENCE {
           mGuardSNMPTrapReceiverIndex
               INTEGER,
           mGuardSNMPTrapReceiverCommunity
               DisplayString (SIZE(1..16)),
           mGuardSNMPTrapReceiverIPAddress
               IpAddress,
           mGuardSNMPTrapReceiverName
	         DisplayString,
           mGuardSNMPTrapReceiverRowStatus
               INTEGER
       }

    mGuardSNMPTrapReceiverIndex OBJECT-TYPE
         SYNTAX      INTEGER (1..255)
         ACCESS      not-accessible
         STATUS      mandatory
         DESCRIPTION
                     "The security gateway's Snmp Trap Receiver Index"
         ::= { mGuardSNMPTrapReceiverEntry 1 }

    mGuardSNMPTrapReceiverCommunity OBJECT-TYPE
         SYNTAX      DisplayString
         ACCESS      read-write
         STATUS      mandatory
         DESCRIPTION
                     "The security gateway's Snmp Trap Receiver Community Name.
                     This is the SNMP community name of the remote network manager;
                     the name can be up to 16 characters (????), and is case-sensitive."
         ::= { mGuardSNMPTrapReceiverEntry 2 }

    mGuardSNMPTrapReceiverIPAddress OBJECT-TYPE
         SYNTAX      IpAddress
         ACCESS      read-write
         STATUS      mandatory
         DESCRIPTION
                     "IP Address - Each IP address parameter is four integer numbers.
                     The numbers range from 0 to 255."
         ::= { mGuardSNMPTrapReceiverEntry 3 }

    mGuardSNMPTrapReceiverName OBJECT-TYPE
         SYNTAX      DisplayString
         ACCESS      read-write
         STATUS      mandatory
         DESCRIPTION
                     "The name of this Trap Receiver entry "
         ::= { mGuardSNMPTrapReceiverEntry 4 }

    mGuardSNMPTrapReceiverRowStatus OBJECT-TYPE
         SYNTAX      RowStatus
         ACCESS      read-write
         STATUS      mandatory
         DESCRIPTION
                     "The security gateway's Snmp Trap Reciever Row Status."

         ::= { mGuardSNMPTrapReceiverEntry 5 }


    -- mGuardSNMPTrapConfigGroup

    mGuardSNMPTrapConfigGroup       OBJECT IDENTIFIER ::= { mGuardSNMP 8  }

    mGuardSNMPAuthenticationTrapFlag OBJECT-TYPE
         SYNTAX      INTEGER {
                     enable(1),
                     disable(2)
                  }
         ACCESS      read-write
         STATUS      mandatory
         DESCRIPTION
                     "Authentication Flag - Enable/Disable SNMP authentication trap."
         ::= { mGuardSNMPTrapConfigGroup 1 }

    mGuardSNMPLinkUpDownTrapFlag OBJECT-TYPE
         SYNTAX      INTEGER {
                     enable(1),
                     disable(2)
                  }
         ACCESS      read-write
         STATUS      mandatory
         DESCRIPTION
                     "Link Up/Down Flag - Enable/Disable Link Up/Link Down traps for the
                     entire security gateway."
         ::= { mGuardSNMPTrapConfigGroup 2 }

    mGuardSNMPColdStartTrapFlag OBJECT-TYPE
         SYNTAX      INTEGER {
                     enable(1),
                     disable(2)
                  }
         ACCESS      read-write
         STATUS      mandatory
         DESCRIPTION
                     "ColdStart Flag - Enable/Disable SNMP coldstart trap."
         ::= { mGuardSNMPTrapConfigGroup 3 }

    mGuardSNMPTrapFlag OBJECT-TYPE
         SYNTAX      INTEGER {
                     enable(1),
                     disable(2)
                  }
         ACCESS      read-write
         STATUS      mandatory
         DESCRIPTION
                     "Enables/Disables the traps with enterprise = mGuardb."
         ::= { mGuardSNMPTrapConfigGroup 4 }

    mGuardSNMPChassisTrapFlag OBJECT-TYPE
         SYNTAX      INTEGER {
                     enable(1),
                     disable(2)
                  }
         ACCESS      read-write
         STATUS      mandatory
         DESCRIPTION
                     "Enables/Disables the traps with enterprise = hmChassis."
         ::= { mGuardSNMPTrapConfigGroup 5 }

    mGuardSNMPAgentTrapFlag OBJECT-TYPE
         SYNTAX      INTEGER {
                     enable(1),
                     disable(2)
                  }
         ACCESS      read-write
         STATUS      mandatory
         DESCRIPTION
                     "Enables/Disables the traps with enterprise = hmAgent."
         ::= { mGuardSNMPTrapConfigGroup 6 }

    mGuardSNMPAvFailTrapFlag OBJECT-TYPE
         SYNTAX      INTEGER {
                     enable(1),
                     disable(2)
                  }
         ACCESS      read-write
         STATUS      mandatory
         DESCRIPTION
                     "Enables/Disables the traps with AntiVirus failures (update or engine failures)."
         ::= { mGuardSNMPTrapConfigGroup 7 }

    mGuardSNMPAvInfoTrapFlag OBJECT-TYPE
         SYNTAX      INTEGER {
                     enable(1),
                     disable(2)
                  }
         ACCESS      read-write
         STATUS      mandatory
         DESCRIPTION
                     "Enables/Disables the traps with informational AntiVirus messages."
         ::= { mGuardSNMPTrapConfigGroup 8 }

    mGuardSNMPBladeStateTrapFlag OBJECT-TYPE
         SYNTAX      INTEGER {
                     enable(1),
                     disable(2)
                  }
         ACCESS      read-write
         STATUS      mandatory
         DESCRIPTION
                     "Enables/Disables traps sent at blade status change."
         ::= { mGuardSNMPTrapConfigGroup 9 }

    mGuardSNMPBladeConfigTrapFlag OBJECT-TYPE
         SYNTAX      INTEGER {
                     enable(1),
                     disable(2)
                  }
         ACCESS      read-write
         STATUS      mandatory
         DESCRIPTION
                     "Enables/Disables traps sent at automatic blade configuration or backup."
         ::= { mGuardSNMPTrapConfigGroup 10 }

    mGuardSNMPRouterRedundancyStatusFlag OBJECT-TYPE
         SYNTAX      INTEGER {
                     enable(1),
                     disable(2)
                  }
         ACCESS      read-write
         STATUS      mandatory
         DESCRIPTION
                     "Enables/Disables traps sent at change of HA state."
         ::= { mGuardSNMPTrapConfigGroup 11 }

--
-- NTP Service
--

  mGuardNTPactivate OBJECT-TYPE
  SYNTAX INTEGER { yes(1),
                   no(2)
		 }
  ACCESS read-write
  STATUS mandatory
  DESCRIPTION
    "Activate NTP ?"
  ::={ mGuardNTP 1 }

  mGuardNTPtimestamp OBJECT-TYPE
   SYNTAX INTEGER  {
                      yes(1),
		      no(2)
		   }
  ACCESS read-write
  STATUS mandatory
  DESCRIPTION
    "Time stamp in filesystem ?"
  ::={ mGuardNTP 2 }
		
  mGuardNTPServerTable OBJECT-TYPE
    SYNTAX SEQUENCE OF MGuardNTPServerEntry
    ACCESS not-accessible
    STATUS mandatory
    DESCRIPTION
      "A table of NTP Servers."
 ::= { mGuardNTP 3 }

  mGuardNTPTimezone OBJECT-TYPE
   SYNTAX DisplayString
   ACCESS read-write
   STATUS mandatory
   DESCRIPTION
     "Timezone in POSIX.1 notation"
  ::={ mGuardNTP 4 }

   mGuardNTPStatus OBJECT-TYPE
     SYNTAX DisplayString
     ACCESS read-only
     STATUS mandatory
     DESCRIPTION
        "NTP state"
  ::={ mGuardNTP 5 }


  mGuardNTPServerEntry OBJECT-TYPE
      SYNTAX MGuardNTPServerEntry
      ACCESS not-accessible
      STATUS mandatory
      DESCRIPTION
       "A single NTP Server."
      INDEX { mGuardNTPServerIndex }
  ::= { mGuardNTPServerTable 1 }

  MGuardNTPServerEntry  ::= SEQUENCE {
     mGuardNTPServerIndex INTEGER,
     mGuardNTPServerHost DisplayString,
     mGuardNTPServerRowStatus RowStatus
  }

  mGuardNTPServerIndex OBJECT-TYPE
    SYNTAX INTEGER (1..20)
    ACCESS not-accessible
    STATUS mandatory
    DESCRIPTION
      "Table index"
   ::= { mGuardNTPServerEntry 1 }

   mGuardNTPServerHost OBJECT-TYPE
    SYNTAX DisplayString
    ACCESS read-write
    STATUS mandatory
    DESCRIPTION
      "Hostname or IP address of the NTP Server."
   ::= { mGuardNTPServerEntry 2 }

   mGuardNTPServerRowStatus OBJECT-TYPE
    SYNTAX RowStatus
    ACCESS read-write
    STATUS mandatory
    DESCRIPTION
      "Row status"
   ::= { mGuardNTPServerEntry 3 }

--
-- Update Server Table
--

  mGuardUpdateServerTable OBJECT-TYPE
    SYNTAX SEQUENCE OF MGuardUpdateServerEntry
    ACCESS not-accessible
    STATUS mandatory
    DESCRIPTION
      "A table of update server repositories."
   ::= { mGuardUpdate 1 }

  mGuardUpdateServerEntry OBJECT-TYPE
      SYNTAX MGuardUpdateServerEntry
      ACCESS not-accessible
      STATUS mandatory
      DESCRIPTION
       "A single update server repository. "
      INDEX { mGuardUpdateServerIndex }
  ::= { mGuardUpdateServerTable 1 }

  MGuardUpdateServerEntry  ::= SEQUENCE {
     mGuardUpdateServerIndex INTEGER,
     mGuardUpdateServer  DisplayString,
     mGuardUpdateServerRowStatus RowStatus,
     mGuardUpdateServerProto DisplayString,
     mGuardUpdateServerHost DisplayString,
     mGuardUpdateServerLogin DisplayString,
     mGuardUpdateServerPassword DisplayString
  }

  mGuardUpdateServerIndex OBJECT-TYPE
    SYNTAX INTEGER (1..20)
    ACCESS not-accessible
    STATUS mandatory
    DESCRIPTION
      "Table index."
   ::= { mGuardUpdateServerEntry 1 }

   mGuardUpdateServer OBJECT-TYPE
    SYNTAX DisplayString
    ACCESS read-write
    STATUS deprecated
    DESCRIPTION
      "URL of the update server."
   ::= { mGuardUpdateServerEntry 2 }

   mGuardUpdateServerRowStatus OBJECT-TYPE
    SYNTAX RowStatus
    ACCESS read-write
    STATUS mandatory
    DESCRIPTION
      "Row Status"
   ::= { mGuardUpdateServerEntry 3 }

   mGuardUpdateServerProto OBJECT-TYPE
    SYNTAX DisplayString
    ACCESS read-write
    STATUS mandatory
    DESCRIPTION
      "Protocol, either https or http"
   ::= { mGuardUpdateServerEntry 4 }

   mGuardUpdateServerHost OBJECT-TYPE
    SYNTAX DisplayString
    ACCESS read-write
    STATUS mandatory
    DESCRIPTION
      "Hostname of the update server."
   ::= { mGuardUpdateServerEntry 5 }

   mGuardUpdateServerLogin OBJECT-TYPE
    SYNTAX DisplayString
    ACCESS read-write
    STATUS mandatory
    DESCRIPTION
      "Login on the update server."
   ::= { mGuardUpdateServerEntry 6 }

   mGuardUpdateServerPassword OBJECT-TYPE
    SYNTAX DisplayString
    ACCESS read-write
    STATUS mandatory
    DESCRIPTION
      "Password on the update server."
   ::= { mGuardUpdateServerEntry 7 }

--
-- Error
--

   mGuardSNMPError OBJECT-TYPE
    SYNTAX DisplayString
    ACCESS read-only
    STATUS mandatory
    DESCRIPTION
       "Field, providing textual description of errors caused by SNMP
       operations."
   ::= { mGuardb 8 }

--
-- mGuard Router Redundancy
--
   mGuardRouterRedundancy OBJECT IDENTIFIER ::= { mGuardRedundancy 2 }

   mGuardRouterRedundancyEnable OBJECT-TYPE
      SYNTAX INTEGER {
                        enabled(1),
                        disabled(2)
                     }
      ACCESS read-write
      STATUS mandatory
      DESCRIPTION
         "Enable Router Redundancy."
   ::= { mGuardRouterRedundancy 1 }

   mGuardRouterRedundancyTrack OBJECT-TYPE
      SYNTAX INTEGER {
                        enabled(1),
                        disabled(2)
                     }
      ACCESS read-write
      STATUS mandatory
      DESCRIPTION
         "Run ICMP checks against redundancy peer."
   ::= { mGuardRouterRedundancy 2 }

   mGuardRouterRedundancyInternalID OBJECT-TYPE
      SYNTAX INTEGER
      ACCESS read-write
      STATUS mandatory
      DESCRIPTION
         "Internal ID of the virtual router."
   ::= { mGuardRouterRedundancy 3 }

   mGuardRouterRedundancyExternalID OBJECT-TYPE
      SYNTAX INTEGER
      ACCESS read-write
      STATUS mandatory
      DESCRIPTION
         "External ID of the virtual router."
   ::= { mGuardRouterRedundancy 4 }

   mGuardRouterRedundancyPassword OBJECT-TYPE
      SYNTAX DisplayString
      ACCESS read-write
      STATUS mandatory
      DESCRIPTION
         "Passwort for synchronization between the virtual router peers."
   ::= { mGuardRouterRedundancy 5 }

   mGuardRouterRedundancyPeerIntern OBJECT-TYPE
      SYNTAX IpAddress
      ACCESS read-write
      STATUS mandatory
      DESCRIPTION
         "Internal IP of the VR peer."
   ::= { mGuardRouterRedundancy 6 }

   mGuardRouterRedundancyPeerExtern OBJECT-TYPE
      SYNTAX IpAddress
      ACCESS read-write
      STATUS mandatory
      DESCRIPTION
         "External IP of the VR peer."
   ::= { mGuardRouterRedundancy 7 }

   mGuardRouterRedundancyPriority OBJECT-TYPE
      SYNTAX INTEGER
      ACCESS read-write
      STATUS mandatory
      DESCRIPTION
         "Priority for the virtual router."
   ::= { mGuardRouterRedundancy 8 }

   mGuardRouterRedundancyVirtIpInt OBJECT-TYPE
      SYNTAX IpAddress
      ACCESS read-write
      STATUS mandatory
      DESCRIPTION
         "Virtual IP address of the HA cluster for the internal network."
   ::= { mGuardRouterRedundancy 9 }

   mGuardRouterRedundancyVirtIpExt OBJECT-TYPE
      SYNTAX IpAddress
      ACCESS read-write
      STATUS mandatory
      DESCRIPTION
         "Virtual IP address of the HA cluster for the external network."
   ::= { mGuardRouterRedundancy 10 }

   mGuardRouterRedundancyWantState OBJECT-TYPE
      SYNTAX INTEGER {
                        master(1),
                        backup(2)
                     }
      ACCESS read-write
      STATUS mandatory
      DESCRIPTION
         "HA cluster state to start this mGuard with at boot time."
   ::= { mGuardRouterRedundancy 11 }


   mGuardRouterRedExtHostCheckTable OBJECT-TYPE
      SYNTAX SEQUENCE OF MGuardRouterRedExtHostCheckEntry
      ACCESS not-accessible
      STATUS mandatory
      DESCRIPTION
        "A table of hosts to check with ICMP for detecting the VR state."
   ::= { mGuardRouterRedundancy 12 }

    mGuardRouterRedExtHostCheckEntry OBJECT-TYPE
        SYNTAX MGuardRouterRedExtHostCheckEntry
        ACCESS not-accessible
        STATUS mandatory
        DESCRIPTION
         "External hosts to check with ICMP for detecting the VR state."
        INDEX { mGuardRouterRedExtHostCheckIndex }
    ::= { mGuardRouterRedExtHostCheckTable 1 }

    MGuardRouterRedExtHostCheckEntry  ::= SEQUENCE {
       mGuardRouterRedExtHostCheckIndex	INTEGER,
       mGuardRouterRedExtHostCheckIP	IpAddress,
       mGuardRouterRedExtHostCheckRowSt	RowStatus
    }

    mGuardRouterRedExtHostCheckIndex OBJECT-TYPE
      SYNTAX INTEGER (1..100)
      ACCESS not-accessible
      STATUS mandatory
      DESCRIPTION
        "Table index."
    ::= { mGuardRouterRedExtHostCheckEntry 1 }

     mGuardRouterRedExtHostCheckIP OBJECT-TYPE
      SYNTAX IpAddress
      ACCESS read-write
      STATUS mandatory
      DESCRIPTION
        "The IP address."
    ::= { mGuardRouterRedExtHostCheckEntry 2 }

     mGuardRouterRedExtHostCheckRowSt OBJECT-TYPE
      SYNTAX RowStatus
      ACCESS read-write
      STATUS mandatory
      DESCRIPTION
        "Row Status"
    ::= { mGuardRouterRedExtHostCheckEntry 3 }



   mGuardRouterRedIntHostCheckTable OBJECT-TYPE
      SYNTAX SEQUENCE OF MGuardRouterRedIntHostCheckEntry
      ACCESS not-accessible
      STATUS mandatory
      DESCRIPTION
        "A table of hosts to check with ICMP for detecting the VR state."
   ::= { mGuardRouterRedundancy 13 }

    mGuardRouterRedIntHostCheckEntry OBJECT-TYPE
        SYNTAX MGuardRouterRedIntHostCheckEntry
        ACCESS not-accessible
        STATUS mandatory
        DESCRIPTION
         "External hosts to check with ICMP for detecting the VR state."
        INDEX { mGuardRouterRedIntHostCheckIndex }
    ::= { mGuardRouterRedIntHostCheckTable 1 }

    MGuardRouterRedIntHostCheckEntry  ::= SEQUENCE {
       mGuardRouterRedIntHostCheckIndex	INTEGER,
       mGuardRouterRedIntHostCheckIP	IpAddress,
       mGuardRouterRedIntHostCheckRowSt	RowStatus
    }

    mGuardRouterRedIntHostCheckIndex OBJECT-TYPE
      SYNTAX INTEGER (1..100)
      ACCESS not-accessible
      STATUS mandatory
      DESCRIPTION
        "Table index."
    ::= { mGuardRouterRedIntHostCheckEntry 1 }

     mGuardRouterRedIntHostCheckIP OBJECT-TYPE
      SYNTAX IpAddress
      ACCESS read-write
      STATUS mandatory
      DESCRIPTION
        "The IP address."
    ::= { mGuardRouterRedIntHostCheckEntry 2 }

     mGuardRouterRedIntHostCheckRowSt OBJECT-TYPE
      SYNTAX RowStatus
      ACCESS read-write
      STATUS mandatory
      DESCRIPTION
        "Row Status"
    ::= { mGuardRouterRedIntHostCheckEntry 3 }

   mGuardRouterRedundancyState OBJECT-TYPE
      SYNTAX INTEGER {
                        backup(1),
			master(2),
                        fault(3),
			disabled(4)
                     }
      ACCESS read-only
      STATUS mandatory
      DESCRIPTION
         "Current HA cluster state."
   ::= { mGuardRouterRedundancy 14 }

-- mGuardInfo

   mGuardHTTPSLastAccessIP OBJECT-TYPE
    SYNTAX IpAddress
    ACCESS read-only
    STATUS mandatory
    DESCRIPTION
       "Address of the last IP from which a wrong authentication information
        was sent for HTTPS access was sent."
   ::= { mGuardInfo 1 }

   mGuardShellLastAccessIP OBJECT-TYPE
    SYNTAX IpAddress
    ACCESS read-only
    STATUS mandatory
    DESCRIPTION
       "Address of the last IP from which a login event occured."
   ::= { mGuardInfo 2 }

   mGuardDHCPLastAccessMAC OBJECT-TYPE
    SYNTAX MacAddress
    ACCESS read-only
    STATUS mandatory
    DESCRIPTION
       "MAC Address of the last unknown client trying to obtain a lease."
   ::= { mGuardInfo 3 }


--
-- mGuardTrapResources
--

  mGuardTrapResources  OBJECT IDENTIFIER ::= { mGuardInfo 4 }

   mGuardTResDiscFull OBJECT-TYPE
    SYNTAX INTEGER
                 {
		   free(1),
                   tight(2),
                   full(3)
		 }
    ACCESS read-only
    STATUS mandatory
    DESCRIPTION
       "Status of file system free space. If multiple file systems, the worst state is used."
   ::= { mGuardTrapResources 1 }

   mGuardTResCpuLoadHigh OBJECT-TYPE
    SYNTAX INTEGER
    ACCESS read-only
    STATUS mandatory
    DESCRIPTION
       "CPU load (uptime*10)."
   ::= { mGuardTrapResources 2 }

   mGuardTResMemoryFull OBJECT-TYPE
    SYNTAX INTEGER
    ACCESS read-only
    STATUS mandatory
    DESCRIPTION
       "Free memory (RAM) in KiByte."
   ::= { mGuardTrapResources 3 }

   mGuardTResColdstart OBJECT-TYPE
   SYNTAX INTEGER
    ACCESS read-only
    STATUS mandatory
    DESCRIPTION
       "Trap sent when system rebooted (snmp daemon started)."
   ::= { mGuardTrapResources 4 }



--
-- mGuardTrapAV
--

  mGuardTResAV  OBJECT IDENTIFIER ::= { mGuardTrapResources 6 }

   mGuardTResAvUpdateDone OBJECT-TYPE
    SYNTAX DisplayString
    ACCESS read-only
    STATUS mandatory
    DESCRIPTION
       "AV Update was performed successfully."
   ::= { mGuardTResAV 1 }

   mGuardTResAvUpdateError OBJECT-TYPE
    SYNTAX DisplayString
    ACCESS read-only
    STATUS mandatory
    DESCRIPTION
       "Error when performing AV Update."
   ::= { mGuardTResAV 2 }

   mGuardTResAvVirusDetected OBJECT-TYPE
    SYNTAX DisplayString
    ACCESS read-only
    STATUS mandatory
    DESCRIPTION
       "AV found a virus."
   ::= { mGuardTResAV 3 }

   mGuardTResAvFileNotScanned OBJECT-TYPE
    SYNTAX DisplayString
    ACCESS read-only
    STATUS mandatory
    DESCRIPTION
       "The file was not scanned for viruses."
   ::= { mGuardTResAV 4 }

   mGuardTResAvFailed OBJECT-TYPE
    SYNTAX DisplayString
    ACCESS read-only
    STATUS mandatory
    DESCRIPTION
       "General AV failure."
   ::= { mGuardTResAV 5 }


--
-- mGuardTResPlatformSpecific
--

  mGuardTResPlatformSpecific  OBJECT IDENTIFIER ::= { mGuardTrapResources 7 }


  mGuardTResIndustrial  OBJECT IDENTIFIER ::= { mGuardTResPlatformSpecific 1 }

  mGuardTResIndustrialPower  OBJECT IDENTIFIER ::= { mGuardTResIndustrial 1 }

  mGuardTResIndustrialTemperature  OBJECT IDENTIFIER
    ::= { mGuardTResIndustrial 2 }


  mGuardPSTable OBJECT-TYPE
     SYNTAX SEQUENCE OF MguardPSEntry
     ACCESS not-accessible
     STATUS mandatory
     DESCRIPTION
	"This table contains all variables related to the power supply
         units of the chassis/switch. For each power supply slot exists
	 one instance."
   ::= { mGuardTResIndustrialPower 2 }

  mGuardPSEntry OBJECT-TYPE
     SYNTAX MguardPSEntry
     ACCESS not-accessible
     STATUS mandatory
     DESCRIPTION "Power supply entry"
     INDEX  { mGuardPSSysID, mGuardPSID }
   ::= { mGuardPSTable 1 }

  MguardPSEntry ::= SEQUENCE {
     mGuardPSSysID INTEGER,
     mGuardPSID INTEGER,
     mGuardPSState INTEGER
  }

  mGuardPSSysID OBJECT-TYPE
     SYNTAX INTEGER (1..100)
     ACCESS read-only
     STATUS mandatory
     DESCRIPTION
        "The value of SysID is assigned so as to uniquely identify a
         chassis/switch among the subordinate managed objects of the
         system."
   ::= { mGuardPSEntry 1 }

  mGuardPSID OBJECT-TYPE
     SYNTAX INTEGER(1..100)
     ACCESS read-only
     STATUS mandatory
     DESCRIPTION
        "This Index is used to identify the associated power supply unit."
   ::= { mGuardPSEntry 2 }

  mGuardPSState OBJECT-TYPE
     SYNTAX INTEGER {
                 ok (1),
		 failed (2),
		 notInstalled (3),
		 unknown (4)
     }
     ACCESS read-only
     STATUS mandatory
     DESCRIPTION
        "Indicates the operational state of the associated power supply. If
	 the value of this variable changes, a mGuardPowerSupply trap is sent."
   ::= { mGuardPSEntry 3 }


  mGuardTResIndustrialTempHiLimit OBJECT-TYPE
    SYNTAX INTEGER
    ACCESS read-write
    STATUS mandatory
    DESCRIPTION
       "Upper limit of allowed system temperature."
   ::= { mGuardTResIndustrialTemperature 2 }

  mGuardTResIndustrialTempLowLimit OBJECT-TYPE
    SYNTAX INTEGER
    ACCESS read-write
    STATUS mandatory
    DESCRIPTION
       "Lower limit of allowed system temperature."
   ::= { mGuardTResIndustrialTemperature 3 }

  mGuardTResAutoConfigAdapterState OBJECT-TYPE
    SYNTAX INTEGER {
		notPresent(1),
		removed(2),
		ok(3),
		notInSync(4),
		outOfMemory(5),
		wrongMachine(6),
		checksumErr(7),
		genericErr(8)
	}
    ACCESS read-only
    STATUS mandatory
    DESCRIPTION
       "Trap sent when ACA was accessed."
   ::= { mGuardTResIndustrial 4 }


  mGuardTResSignalRelais  OBJECT IDENTIFIER ::= { mGuardTResIndustrial 3 }

   mGuardTResSignalRelaisState OBJECT-TYPE
      SYNTAX INTEGER
      ACCESS read-only
      STATUS mandatory
      DESCRIPTION
         "Current state of the signal relais (1=on, 2=off)."
   ::= { mGuardTResSignalRelais 1 }

   mGuardTResSignalRelaisReason OBJECT-TYPE
      SYNTAX OBJECT IDENTIFIER
      ACCESS read-only
      STATUS mandatory
      DESCRIPTION
         "Reason why the signal relais was triggered."
   ::= { mGuardTResSignalRelais 2 }

   mGuardTResSignalRelaisReasonIdx OBJECT-TYPE
      SYNTAX INTEGER
      ACCESS read-only
      STATUS mandatory
      DESCRIPTION
         "Reason number (ue0=1, ue1=2, number of TX bytes for eth)."
   ::= { mGuardTResSignalRelais 3 }

   mGuardTResSignalRelaisPowerAlarm OBJECT-TYPE
      SYNTAX	INTEGER {
		enable(1),
		disable(2)
      }
      ACCESS	read-write
      STATUS	mandatory
      DESCRIPTION
	"Enables/disables an alarm for the signalling relay of the powersupply state."
      ::= { mGuardTResSignalRelais 4 }

   mGuardTResSignalRelaisMode OBJECT-TYPE
      SYNTAX INTEGER {
		standard(1),
		manual(2)
      }
      ACCESS read-write
      STATUS mandatory
      DESCRIPTION
      "When set to standard, this is the default, the signalling relay shows the state of
      hmRS2SigRelayState.
      When set to manual, the relay is controlled by the configured Manual State."
      ::= {  mGuardTResSignalRelais 5 }


   mGuardTResSignalRelaisManualStat OBJECT-TYPE
      SYNTAX  INTEGER {
		on(1),
		off(2)
      }
      ACCESS read-write
      STATUS mandatory
      DESCRIPTION
      "When set to on, this is the default, the signalling relay is opened.
      When set to off the relay is closed."
      ::= {  mGuardTResSignalRelais 6 }


  mGuardTResSignalLinkTable  OBJECT IDENTIFIER ::= { mGuardTResIndustrial 5 }

  mGuardTResSigLinkID   OBJECT-TYPE
    SYNTAX    INTEGER  (1..7)
    ACCESS    read-only
    STATUS    mandatory
    DESCRIPTION
     "This index is used to identify the associated link and
     corresponds with ifMauIfIndex."
    ::= { mGuardTResSignalLinkTable 1 }

  mGuardTResSigLinkAlarm   OBJECT-TYPE
    SYNTAX    INTEGER {
        on (1),
        off (2)
        }
    ACCESS    read-write
    STATUS    mandatory
    DESCRIPTION
                 "DURABLE:  { off:all }
                 Indicates whether an alarm for the signalling relay of the
                 associated link will be produced or not, so you can mask the
                 value of ifMauMediaAvailable."
    ::= { mGuardTResSignalLinkTable 2 }




  mGuardTResBladeCTRL  OBJECT IDENTIFIER ::= { mGuardTResPlatformSpecific 2 }

  mGuardTResBladeInfo  OBJECT IDENTIFIER ::= { mGuardTResBladeCTRL 1 }
  mGuardTResBladeCtrlCfg  OBJECT IDENTIFIER ::= { mGuardTResBladeCTRL 5 }

  mGuardTResBladeRackID OBJECT-TYPE
      SYNTAX DisplayString
      ACCESS read-only
      STATUS mandatory
      DESCRIPTION
         "Rack ID in question when sending a Blade-related SNMP trap."
   ::= { mGuardTResBladeInfo 1 }

  mGuardTResBladeSlotNr OBJECT-TYPE
      SYNTAX INTEGER
      ACCESS read-only
      STATUS mandatory
      DESCRIPTION
         "Slot ID in question when sending a Blade-related SNMP trap."
   ::= { mGuardTResBladeInfo 2 }

  mGuardTResBladeCtrlPowerStatus OBJECT-TYPE
    SYNTAX INTEGER
                 {
		   absent(1),
                   present(2),
                   online(3)
		 }
      ACCESS read-only
      STATUS mandatory
      DESCRIPTION
         "Status of the BladePack's power supplies when sending an SNMP trap."
   ::= { mGuardTResBladeCTRL 2 }

  mGuardTResBladeCtrlRunStatus OBJECT-TYPE
    SYNTAX INTEGER
                 {
		   absent(1),
                   present(2),
                   online(3)
		 }
      ACCESS read-only
      STATUS mandatory
      DESCRIPTION
         "Status of the Blade's run status when sending an SNMP trap."
   ::= { mGuardTResBladeCTRL 3 }


  mGuardTResBladeCtrlCfgBackup OBJECT-TYPE
      SYNTAX INTEGER {
			downloaded(3)
                     }
      ACCESS read-only
      STATUS mandatory
      DESCRIPTION
         "Reason/details for configuration backup to Blade CTRL when sending an SNMP trap."
   ::= { mGuardTResBladeCtrlCfg 1 }

  mGuardTResBladeCtrlCfgRestored OBJECT-TYPE
      SYNTAX INTEGER {
			automatic(1),
			manual(2)
                     }
      ACCESS read-only
      STATUS mandatory
      DESCRIPTION
         "Reason for configuration restore from Blade CTRL when sending an SNMP trap."
   ::= { mGuardTResBladeCtrlCfg 2 }

   mGuardTResRedundancy  OBJECT IDENTIFIER ::= { mGuardTrapResources 8 }

   mGuardTResRedundacyReason OBJECT-TYPE
    SYNTAX DisplayString
    ACCESS read-only
    STATUS mandatory
    DESCRIPTION
       "Reason for redundancy status change."
   ::= { mGuardTResRedundancy 1 }

   mGuardTResRedundacyBackupDown OBJECT-TYPE
    SYNTAX DisplayString
    ACCESS read-only
    STATUS mandatory
    DESCRIPTION
       "Information sent by Master device when Backup device is not reachable."
   ::= { mGuardTResRedundancy 2 }


--
-- Logging
--

   mGuardLoggingRemoteActivate OBJECT-TYPE
       SYNTAX INTEGER
                 {
		   yes(1),
                   no(2)
		 }
       ACCESS read-write
       STATUS mandatory
       DESCRIPTION
          "Activate remote logging?"
   ::={ mGuardLogging 1 }

   mGuardLoggingRemoteIP OBJECT-TYPE
      SYNTAX IpAddress
      ACCESS read-write
      STATUS mandatory
      DESCRIPTION
         "IP address of the remote log server"
   ::= { mGuardLogging 2 }

    mGuardLoggingRemotePort OBJECT-TYPE
      SYNTAX DisplayString
      ACCESS read-write
      STATUS mandatory
      DESCRIPTION
         "UDP port of the remote logging service"
     ::= { mGuardLogging 3 }

--
-- mGuardContFilt
--

  mGuardContFiltAVP    OBJECT IDENTIFIER ::= { mGuardContFilt 1 }
  mGuardContFiltHTTP   OBJECT IDENTIFIER ::= { mGuardContFilt 2 }
  mGuardContFiltPOP3   OBJECT IDENTIFIER ::= { mGuardContFilt 3 }
  mGuardContFiltSMTP   OBJECT IDENTIFIER ::= { mGuardContFilt 4 }
  mGuardContFiltFTP    OBJECT IDENTIFIER ::= { mGuardContFilt 5 }


--
-- mGuardContFiltAVP
--

   mGuardContFiltAVPSchedule OBJECT-TYPE
    SYNTAX INTEGER
              {
	        never(1),
		onboot(2),
		quarterhourly(15),
		halfhourly(30),
		hourly(60),
		bihourly(120),
		triplehourly(360),
		sixhourly(720),
		twicedayly(1440)
	      }
    ACCESS read-write
    STATUS mandatory
    DESCRIPTION
       "The period used when updating the antivirus database"
  ::= { mGuardContFiltAVP 1 }

  mGuardContFiltAVPServerTable OBJECT-TYPE
    SYNTAX SEQUENCE OF MGuardContFiltAVPServerEntry
    ACCESS not-accessible
    STATUS mandatory
    DESCRIPTION
      "A table of update server repositories."
   ::= { mGuardContFiltAVP 2 }

  mGuardContFiltAVPServerEntry OBJECT-TYPE
      SYNTAX MGuardContFiltAVPServerEntry
      ACCESS not-accessible
      STATUS mandatory
      DESCRIPTION
       "A single update server repository. "
      INDEX { mGuardContFiltAVPServerIndex }
  ::= { mGuardContFiltAVPServerTable 1 }

  MGuardContFiltAVPServerEntry  ::= SEQUENCE {
     mGuardContFiltAVPServerIndex INTEGER,
     mGuardContFiltAVPServerURL  DisplayString,
     mGuardContFiltAVPServerRowStatus RowStatus
  }

  mGuardContFiltAVPServerIndex OBJECT-TYPE
    SYNTAX INTEGER (1..100)
    ACCESS not-accessible
    STATUS mandatory
    DESCRIPTION
      "Table index."
   ::= { mGuardContFiltAVPServerEntry 1 }

   mGuardContFiltAVPServerURL OBJECT-TYPE
    SYNTAX DisplayString
    ACCESS read-write
    STATUS mandatory
    DESCRIPTION
      "URL of the update server."
   ::= { mGuardContFiltAVPServerEntry 2 }

   mGuardContFiltAVPServerRowStatus OBJECT-TYPE
    SYNTAX RowStatus
    ACCESS read-write
    STATUS mandatory
    DESCRIPTION
      "Row Status"
   ::= { mGuardContFiltAVPServerEntry 3 }


  mGuardContFiltAVPHTTPProxy OBJECT IDENTIFIER ::= { mGuardContFiltAVP 3 }

  mGuardContFiltAVPHTTPProxyLogin OBJECT-TYPE
    SYNTAX DisplayString
    ACCESS read-write
    STATUS mandatory
    DESCRIPTION
       "Login for a HTTP proxy for retrival of anti-virus patterns."
   ::= { mGuardContFiltAVPHTTPProxy 1 }

  mGuardContFiltAVPHTTPProxyPasswd OBJECT-TYPE
    SYNTAX DisplayString
    ACCESS read-write
    STATUS mandatory
    DESCRIPTION
       "Password for mGuardContFiltAVPHTTPProxyLogin."
   ::= { mGuardContFiltAVPHTTPProxy 2 }

  mGuardContFiltAVPHTTPProxyServer OBJECT-TYPE
    SYNTAX DisplayString
    ACCESS read-write
    STATUS mandatory
    DESCRIPTION
       "Hostname or IP of an HTTP proxy for retrival of anti-virus patterns."
   ::= { mGuardContFiltAVPHTTPProxy 3 }

  mGuardContFiltAVPHTTPProxyPort OBJECT-TYPE
    SYNTAX DisplayString
    ACCESS read-write
    STATUS mandatory
    DESCRIPTION
       "Port of an HTTP proxy for retrival of anti-virus patterns, eg. 3128."
   ::= { mGuardContFiltAVPHTTPProxy 4 }


-- global AVP settings

   mGuardContFiltAVPLogLevel OBJECT-TYPE
    SYNTAX INTEGER (1..5)
    ACCESS read-write
    STATUS mandatory
    DESCRIPTION
       "AVP log detail level with 0 lowest 5 highest, defaults to 2."
  ::= { mGuardContFiltAVP 5 }

   mGuardContFiltAVPMaxConnections OBJECT-TYPE
    SYNTAX INTEGER
    ACCESS read-write
    STATUS mandatory
    DESCRIPTION
       "Maximum number of connections the AVP will handle."
  ::= { mGuardContFiltAVP 6 }

   mGuardContFiltAVPScanTimeout OBJECT-TYPE
    SYNTAX INTEGER
    ACCESS read-write
    STATUS mandatory
    DESCRIPTION
       "Maximum time the protocol wrapper will wait for the scan engine in seconds."
  ::= { mGuardContFiltAVP 7 }


  mGuardContFiltAVPpass    OBJECT IDENTIFIER ::= { mGuardContFiltAVP 8 }

   mGuardContFiltAVPpassCorrupt OBJECT-TYPE
    SYNTAX INTEGER
              {
	        yes(1),
		no(2)
	      }
    ACCESS read-write
    STATUS mandatory
    DESCRIPTION
       "Let corrupt (archive) files pass, treat them as not virus infected."
  ::= { mGuardContFiltAVPpass 1 }


   mGuardContFiltAVPpassEncrypted OBJECT-TYPE
    SYNTAX INTEGER
              {
	        yes(1),
		no(2)
	      }
    ACCESS read-write
    STATUS mandatory
    DESCRIPTION
       "Let encrypted files pass, treat them as not virus infected."
  ::= { mGuardContFiltAVPpass 2 }


   mGuardContFiltAVPpassSuspicious OBJECT-TYPE
    SYNTAX INTEGER
              {
	        yes(1),
		no(2)
	      }
    ACCESS read-write
    STATUS mandatory
    DESCRIPTION
       "Let suspicious files (e.g. known spyware) pass, treat them as not virus infected."
  ::= { mGuardContFiltAVPpass 3 }


   mGuardContFiltAVPpassWarnings OBJECT-TYPE
    SYNTAX INTEGER
              {
	        yes(1),
		no(2)
	      }
    ACCESS read-write
    STATUS mandatory
    DESCRIPTION
       "Let files pass that triggered a warning, treat them as not virus infected."
  ::= { mGuardContFiltAVPpass 4 }


-- mGuardContFiltQuarantine

  mGuardContFiltQuarantine    OBJECT IDENTIFIER ::= { mGuardContFiltAVP 9 }

  mGuardContFiltQuarantineClean OBJECT-TYPE
    SYNTAX INTEGER
              {
	        yes(1),
		no(2)
	      }
    ACCESS read-write
    STATUS mandatory
    DESCRIPTION
       "Send clean files to quarantine server for debugging
        (warning: do not violate privacy law with this option!)."
   ::= { mGuardContFiltQuarantine 1 }

  mGuardContFiltQuarantineError OBJECT-TYPE
    SYNTAX INTEGER
              {
	        yes(1),
		no(2)
	      }
    ACCESS read-write
    STATUS mandatory
    DESCRIPTION
       "Send files producing an error to quarantine server for debugging
        (warning: do not violate privacy law with this option!)."
   ::= { mGuardContFiltQuarantine 2 }

  mGuardContFiltQuarantineVirus OBJECT-TYPE
    SYNTAX INTEGER
              {
	        yes(1),
		no(2)
	      }
    ACCESS read-write
    STATUS mandatory
    DESCRIPTION
       "Send files found to be infected to quarantine server for debugging
        (warning: do not violate privacy law with this option!)."
   ::= { mGuardContFiltQuarantine 3 }

  mGuardContFiltQuarantineSrvIP OBJECT-TYPE
    SYNTAX DisplayString
    ACCESS read-write
    STATUS mandatory
    DESCRIPTION
       "IP Address of the quarantine server."
   ::= { mGuardContFiltQuarantine 4 }

  mGuardContFiltQuarantineSrvPort OBJECT-TYPE
    SYNTAX DisplayString
    ACCESS read-write
    STATUS mandatory
    DESCRIPTION
       "Port used for/on the quarantine server (Innominate Quarantine Server Protocol)."
   ::= { mGuardContFiltQuarantine 5 }


-- mGuardContFiltInfo

  mGuardContFiltInfo    OBJECT IDENTIFIER ::= { mGuardContFiltAVP 10 }

  mGuardContFiltInfoFlashID OBJECT-TYPE
    SYNTAX DisplayString
    ACCESS read-only
    STATUS mandatory
    DESCRIPTION
       "Flash ID of the device to be used for license handling."
   ::= { mGuardContFiltInfo 1 }

--
-- mGuardContFiltHTTP
--

   mGuardContFiltHTTPEnable OBJECT-TYPE
    SYNTAX INTEGER
              {
	        enable(1),
		disable(2)
	      }
    ACCESS read-write
    STATUS mandatory
    DESCRIPTION
       "Enable HTTP procotol proxy"
  ::= { mGuardContFiltHTTP 1 }

   mGuardContFiltHTTPVirusAction OBJECT-TYPE
    SYNTAX INTEGER
              {
	        error(1)
	      }
    ACCESS read-write
    STATUS mandatory
    DESCRIPTION
       "Action to take on virus detection"
  ::= { mGuardContFiltHTTP 2 }

   mGuardContFiltHTTPMaxSize OBJECT-TYPE
    SYNTAX INTEGER
              {
	        dottwomeg(200000),
	        dotfivemeg(500000),
	        onemeg(1000000),
	        twomeg(2000000),
	        fourmeg(4000000),
	        fivemeg(5000000),
	        eightmeg(8000000),
		tenmeg(10000000)
	      }
    ACCESS read-write
    STATUS mandatory
    DESCRIPTION
       "Maximum object size to be handled (actually sizes may depend on
	software version and underlying hardware."
  ::= { mGuardContFiltHTTP 3 }

   mGuardContFiltHTTPExceedAction OBJECT-TYPE
    SYNTAX INTEGER
              {
	        block(1),
		pass(2)
	      }
    ACCESS read-write
    STATUS mandatory
    DESCRIPTION
       "Action to take if an object exceeds the maximum handled size"
  ::= { mGuardContFiltHTTP 4 }

  mGuardContFiltHTTPSrvrTable OBJECT-TYPE
    SYNTAX SEQUENCE OF MGuardContFiltHTTPSrvrEntry
    ACCESS not-accessible
    STATUS mandatory
    DESCRIPTION
      "A table of update server repositories."
   ::= { mGuardContFiltHTTP 5 }

  mGuardContFiltHTTPSrvrEntry OBJECT-TYPE
      SYNTAX MGuardContFiltHTTPSrvrEntry
      ACCESS not-accessible
      STATUS mandatory
      DESCRIPTION
       "A single update server repository. "
      INDEX { mGuardContFiltHTTPSrvrIndex }
  ::= { mGuardContFiltHTTPSrvrTable 1 }

  MGuardContFiltHTTPSrvrEntry  ::= SEQUENCE {
     mGuardContFiltHTTPSrvrIndex INTEGER,
     mGuardContFiltHTTPSrvrIP DisplayString,
     mGuardContFiltHTTPSrvrPort  DisplayString,
     mGuardContFiltHTTPSrvrScanAction  INTEGER,
     mGuardContFiltHTTPSrvrRowStatus RowStatus,
     mGuardContFiltHTTPSrvrComment  DisplayString
  }

  mGuardContFiltHTTPSrvrIndex OBJECT-TYPE
    SYNTAX INTEGER (1..100)
    ACCESS not-accessible
    STATUS mandatory
    DESCRIPTION
      "Table index."
   ::= { mGuardContFiltHTTPSrvrEntry 1 }

   mGuardContFiltHTTPSrvrIP OBJECT-TYPE
    SYNTAX DisplayString
    ACCESS read-write
    STATUS mandatory
    DESCRIPTION
      "IP address expression for http server(s)."
   ::= { mGuardContFiltHTTPSrvrEntry 2 }

  mGuardContFiltHTTPSrvrPort OBJECT-TYPE
    SYNTAX DisplayString
    ACCESS read-write
    STATUS mandatory
    DESCRIPTION
      "Port the HTTP server listens to.."
   ::= { mGuardContFiltHTTPSrvrEntry 3 }

  mGuardContFiltHTTPSrvrScanAction OBJECT-TYPE
    SYNTAX INTEGER
              {
	        scan(1),
		noscan(2)
              }
    ACCESS read-write
    STATUS mandatory
    DESCRIPTION
      "Action to be taken when contacting respective servers."
   ::= { mGuardContFiltHTTPSrvrEntry 4 }

   mGuardContFiltHTTPSrvrRowStatus OBJECT-TYPE
    SYNTAX RowStatus
    ACCESS read-write
    STATUS mandatory
    DESCRIPTION
      "Row Status"
   ::= { mGuardContFiltHTTPSrvrEntry 5 }

   mGuardContFiltHTTPSrvrComment OBJECT-TYPE
    SYNTAX DisplayString
    ACCESS read-write
    STATUS mandatory
    DESCRIPTION
      "Comment for this rule."
   ::= { mGuardContFiltHTTPSrvrEntry 6 }

--
-- mGuardContFiltPOP3
--

   mGuardContFiltPOP3Enable OBJECT-TYPE
    SYNTAX INTEGER
              {
	        enable(1),
		disable(2)
	      }
    ACCESS read-write
    STATUS mandatory
    DESCRIPTION
       "Enable POP3 procotol proxy"
  ::= { mGuardContFiltPOP3 1 }

   mGuardContFiltPOP3VirusAction OBJECT-TYPE
    SYNTAX INTEGER
              {
	        error(1),
		mail(2)
	      }
    ACCESS read-write
    STATUS mandatory
    DESCRIPTION
       "Action to take on virus detection"
  ::= { mGuardContFiltPOP3 2 }

   mGuardContFiltPOP3MaxSize OBJECT-TYPE
    SYNTAX INTEGER
              {
	        dottwomeg(200000),
	        dotfivemeg(500000),
	        onemeg(1000000),
	        twomeg(2000000),
	        fourmeg(4000000),
	        fivemeg(5000000),
	        eightmeg(8000000),
		tenmeg(10000000)
	      }
    ACCESS read-write
    STATUS mandatory
    DESCRIPTION
       "Maximum object size to be handled (actually sizes may depend on
	software version and underlying hardware."
  ::= { mGuardContFiltPOP3 3 }

   mGuardContFiltPOP3ExceedAction OBJECT-TYPE
    SYNTAX INTEGER
              {
	        block(1),
		pass(2)
	      }
    ACCESS read-write
    STATUS mandatory
    DESCRIPTION
       "Action to take if an object exceeds the maximum handled size"
  ::= { mGuardContFiltPOP3 4 }

  mGuardContFiltPOP3SrvrTable OBJECT-TYPE
    SYNTAX SEQUENCE OF MGuardContFiltPOP3SrvrEntry
    ACCESS not-accessible
    STATUS mandatory
    DESCRIPTION
      "A table of update server repositories."
   ::= { mGuardContFiltPOP3 5 }

  mGuardContFiltPOP3SrvrEntry OBJECT-TYPE
      SYNTAX MGuardContFiltPOP3SrvrEntry
      ACCESS not-accessible
      STATUS mandatory
      DESCRIPTION
       "A single update server repository. "
      INDEX { mGuardContFiltPOP3SrvrIndex }
  ::= { mGuardContFiltPOP3SrvrTable 1 }

  MGuardContFiltPOP3SrvrEntry  ::= SEQUENCE {
     mGuardContFiltPOP3SrvrIndex INTEGER,
     mGuardContFiltPOP3SrvrIP DisplayString,
     mGuardContFiltPOP3SrvrPort  DisplayString,
     mGuardContFiltPOP3SrvrScanAction  INTEGER,
     mGuardContFiltPOP3SrvrRowStatus RowStatus,
     mGuardContFiltPOP3SrvrComment  DisplayString
  }

  mGuardContFiltPOP3SrvrIndex OBJECT-TYPE
    SYNTAX INTEGER (1..100)
    ACCESS not-accessible
    STATUS mandatory
    DESCRIPTION
      "Table index."
   ::= { mGuardContFiltPOP3SrvrEntry 1 }

   mGuardContFiltPOP3SrvrIP OBJECT-TYPE
    SYNTAX DisplayString
    ACCESS read-write
    STATUS mandatory
    DESCRIPTION
      "IP address expression for pop3 server(s)."
   ::= { mGuardContFiltPOP3SrvrEntry 2 }

   mGuardContFiltPOP3SrvrPort OBJECT-TYPE
    SYNTAX DisplayString
    ACCESS read-write
    STATUS mandatory
    DESCRIPTION
      "Port expression for pop3 server(s)."
   ::= { mGuardContFiltPOP3SrvrEntry 3 }

  mGuardContFiltPOP3SrvrScanAction OBJECT-TYPE
    SYNTAX INTEGER
              {
	        scan(1),
		noscan(2)
              }
    ACCESS not-accessible
    STATUS mandatory
    DESCRIPTION
      "Action to be taken when contacting respective servers."
   ::= { mGuardContFiltPOP3SrvrEntry 4 }

   mGuardContFiltPOP3SrvrRowStatus OBJECT-TYPE
    SYNTAX RowStatus
    ACCESS read-write
    STATUS mandatory
    DESCRIPTION
      "Row Status"
   ::= { mGuardContFiltPOP3SrvrEntry 5 }

   mGuardContFiltPOP3SrvrComment OBJECT-TYPE
    SYNTAX DisplayString
    ACCESS read-write
    STATUS mandatory
    DESCRIPTION
      "Comment for this rule."
   ::= { mGuardContFiltPOP3SrvrEntry 6 }

--
-- mGuardContFiltSMTP
--

   mGuardContFiltSMTPEnable OBJECT-TYPE
    SYNTAX INTEGER
              {
	        enable(1),
		disable(2)
	      }
    ACCESS read-write
    STATUS mandatory
    DESCRIPTION
       "Enable SMTP procotol proxy"
  ::= { mGuardContFiltSMTP 1 }

   mGuardContFiltSMTPVirusAction OBJECT-TYPE
    SYNTAX INTEGER
              {
	        error(1)
	      }
    ACCESS read-write
    STATUS mandatory
    DESCRIPTION
       "Action to take on virus detection"
  ::= { mGuardContFiltSMTP 2 }

   mGuardContFiltSMTPMaxSize OBJECT-TYPE
    SYNTAX INTEGER
              {
	        dottwomeg(200000),
	        dotfivemeg(500000),
	        onemeg(1000000),
	        twomeg(2000000),
	        fourmeg(4000000),
	        fivemeg(5000000),
	        eightmeg(8000000),
		tenmeg(10000000)
	      }
    ACCESS read-write
    STATUS mandatory
    DESCRIPTION
       "Maximum object size to be handled (actually sizes may depend on
	software version and underlying hardware."
  ::= { mGuardContFiltSMTP 3 }

   mGuardContFiltSMTPExceedAction OBJECT-TYPE
    SYNTAX INTEGER
              {
	        block(1),
		pass(2)
	      }
    ACCESS read-write
    STATUS mandatory
    DESCRIPTION
       "Action to take if an object exceeds the maximum handled size"
  ::= { mGuardContFiltSMTP 4 }

  mGuardContFiltSMTPSrvrTable OBJECT-TYPE
    SYNTAX SEQUENCE OF MGuardContFiltSMTPSrvrEntry
    ACCESS not-accessible
    STATUS mandatory
    DESCRIPTION
      "A table of update server repositories."
   ::= { mGuardContFiltSMTP 5 }

  mGuardContFiltSMTPSrvrEntry OBJECT-TYPE
      SYNTAX MGuardContFiltSMTPSrvrEntry
      ACCESS not-accessible
      STATUS mandatory
      DESCRIPTION
       "A single update server repository. "
      INDEX { mGuardContFiltSMTPSrvrIndex }
  ::= { mGuardContFiltSMTPSrvrTable 1 }

  MGuardContFiltSMTPSrvrEntry  ::= SEQUENCE {
     mGuardContFiltSMTPSrvrIndex INTEGER,
     mGuardContFiltSMTPSrvrIP DisplayString,
     mGuardContFiltSMTPSrvrPort  DisplayString,
     mGuardContFiltSMTPSrvrScanAction  INTEGER,
     mGuardContFiltSMTPSrvrRowStatus RowStatus,
     mGuardContFiltSMTPSrvrComment  DisplayString
  }

  mGuardContFiltSMTPSrvrIndex OBJECT-TYPE
    SYNTAX INTEGER (1..100)
    ACCESS not-accessible
    STATUS mandatory
    DESCRIPTION
      "Table index."
   ::= { mGuardContFiltSMTPSrvrEntry 1 }

   mGuardContFiltSMTPSrvrIP OBJECT-TYPE
    SYNTAX DisplayString
    ACCESS read-write
    STATUS mandatory
    DESCRIPTION
      "IP address expression for smtp server(s)."
   ::= { mGuardContFiltSMTPSrvrEntry 2 }

   mGuardContFiltSMTPSrvrPort OBJECT-TYPE
    SYNTAX DisplayString
    ACCESS read-write
    STATUS mandatory
    DESCRIPTION
      "Port expression for smtp server(s)."
   ::= { mGuardContFiltSMTPSrvrEntry 3 }

  mGuardContFiltSMTPSrvrScanAction OBJECT-TYPE
    SYNTAX INTEGER
              {
	        scan(1),
		noscan(2)
              }
    ACCESS not-accessible
    STATUS mandatory
    DESCRIPTION
      "Action to be taken when contacting respective servers."
   ::= { mGuardContFiltSMTPSrvrEntry 4 }

   mGuardContFiltSMTPSrvrRowStatus OBJECT-TYPE
    SYNTAX RowStatus
    ACCESS read-write
    STATUS mandatory
    DESCRIPTION
      "Row Status"
   ::= { mGuardContFiltSMTPSrvrEntry 5 }

   mGuardContFiltSMTPSrvrComment OBJECT-TYPE
    SYNTAX DisplayString
    ACCESS read-write
    STATUS mandatory
    DESCRIPTION
      "Comment for this rule."
   ::= { mGuardContFiltSMTPSrvrEntry 6 }

--
-- mGuardContFiltFTP
--

   mGuardContFiltFTPEnable OBJECT-TYPE
    SYNTAX INTEGER
              {
	        enable(1),
		disable(2)
	      }
    ACCESS read-write
    STATUS mandatory
    DESCRIPTION
       "Enable FTP procotol proxy"
  ::= { mGuardContFiltFTP 1 }

   mGuardContFiltFTPVirusAction OBJECT-TYPE
    SYNTAX INTEGER
              {
	        error(1)
	      }
    ACCESS read-write
    STATUS mandatory
    DESCRIPTION
       "Action to take on virus detection"
  ::= { mGuardContFiltFTP 2 }

   mGuardContFiltFTPMaxSize OBJECT-TYPE
    SYNTAX INTEGER
              {
	        dottwomeg(200000),
	        dotfivemeg(500000),
	        onemeg(1000000),
	        twomeg(2000000),
	        fourmeg(4000000),
	        fivemeg(5000000),
	        eightmeg(8000000),
		tenmeg(10000000)
	      }
    ACCESS read-write
    STATUS mandatory
    DESCRIPTION
       "Maximum object size to be handled (actually sizes may depend on
	software version and underlying hardware."
  ::= { mGuardContFiltFTP 3 }

   mGuardContFiltFTPExceedAction OBJECT-TYPE
    SYNTAX INTEGER
              {
	        block(1),
		pass(2)
	      }
    ACCESS read-write
    STATUS mandatory
    DESCRIPTION
       "Action to take if an object exceeds the maximum handled size"
  ::= { mGuardContFiltFTP 4 }

  mGuardContFiltFTPSrvrTable OBJECT-TYPE
    SYNTAX SEQUENCE OF MGuardContFiltFTPSrvrEntry
    ACCESS not-accessible
    STATUS mandatory
    DESCRIPTION
      "A table of update server repositories."
   ::= { mGuardContFiltFTP 5 }

  mGuardContFiltFTPSrvrEntry OBJECT-TYPE
      SYNTAX MGuardContFiltFTPSrvrEntry
      ACCESS not-accessible
      STATUS mandatory
      DESCRIPTION
       "A single update server repository. "
      INDEX { mGuardContFiltFTPSrvrIndex }
  ::= { mGuardContFiltFTPSrvrTable 1 }

  MGuardContFiltFTPSrvrEntry  ::= SEQUENCE {
     mGuardContFiltFTPSrvrIndex INTEGER,
     mGuardContFiltFTPSrvrIP DisplayString,
     mGuardContFiltFTPSrvrPort  DisplayString,
     mGuardContFiltFTPSrvrScanAction  INTEGER,
     mGuardContFiltFTPSrvrRowStatus RowStatus,
     mGuardContFiltFTPSrvrComment  DisplayString
  }

  mGuardContFiltFTPSrvrIndex OBJECT-TYPE
    SYNTAX INTEGER (1..100)
    ACCESS not-accessible
    STATUS mandatory
    DESCRIPTION
      "Table index."
   ::= { mGuardContFiltFTPSrvrEntry 1 }

   mGuardContFiltFTPSrvrIP OBJECT-TYPE
    SYNTAX DisplayString
    ACCESS read-write
    STATUS mandatory
    DESCRIPTION
      "IP address expression for smtp server(s)."
   ::= { mGuardContFiltFTPSrvrEntry 2 }

   mGuardContFiltFTPSrvrPort OBJECT-TYPE
    SYNTAX DisplayString
    ACCESS read-write
    STATUS mandatory
    DESCRIPTION
      "Port expression for smtp server(s)."
   ::= { mGuardContFiltFTPSrvrEntry 3 }

  mGuardContFiltFTPSrvrScanAction OBJECT-TYPE
    SYNTAX INTEGER
              {
	        scan(1),
		noscan(2)
              }
    ACCESS not-accessible
    STATUS mandatory
    DESCRIPTION
      "Action to be taken when contacting respective servers."
   ::= { mGuardContFiltFTPSrvrEntry 4 }

   mGuardContFiltFTPSrvrRowStatus OBJECT-TYPE
    SYNTAX RowStatus
    ACCESS read-write
    STATUS mandatory
    DESCRIPTION
      "Row Status"
   ::= { mGuardContFiltFTPSrvrEntry 5 }

   mGuardContFiltFTPSrvrComment OBJECT-TYPE
    SYNTAX DisplayString
    ACCESS read-write
    STATUS mandatory
    DESCRIPTION
      "Comment for this rule."
   ::= { mGuardContFiltFTPSrvrEntry 6 }

--
-- Blade
--

  mGuardBladeRackID OBJECT-TYPE
    SYNTAX INTEGER
    ACCESS read-write
    STATUS mandatory
    DESCRIPTION
      "Blade rack ID, read-only on a blade, read-write on a controller"
  ::= { mGuardBlade 1 }

  mGuardBladeSlotID OBJECT-TYPE
    SYNTAX INTEGER
    ACCESS not-accessible
    STATUS mandatory
    DESCRIPTION
      "Blade slot ID, slot ID in a mGuard Rack"
  ::= { mGuardBlade 2 }


  mGuardBladeCtrlTable OBJECT-TYPE
    SYNTAX SEQUENCE OF  MGuardBladeCtrlEntry
    ACCESS not-accessible
    STATUS mandatory
    DESCRIPTION
      "Overview of controlled blades."
   ::= { mGuardBlade 3 }

  mGuardBladeCtrlEntry OBJECT-TYPE
      SYNTAX MGuardBladeCtrlEntry
      ACCESS not-accessible
      STATUS mandatory
      DESCRIPTION
       "A single update server repository. "
      INDEX { mGuardBladeCtrlIndex }
  ::= { mGuardBladeCtrlTable 1 }

  MGuardBladeCtrlEntry  ::= SEQUENCE {
     mGuardBladeCtrlIndex INTEGER,
     mGuardBladeCtrlDevice DisplayString,
     mGuardBladeCtrlStatus INTEGER,
     mGuardBladeCtrlAVRRevision DisplayString,
     mGuardBladeCtrlSlotID DisplayString,
     mGuardBladeCtrlProductID DisplayString,
     mGuardBladeCtrlAssemblyID DisplayString,
     mGuardBladeCtrlSerial DisplayString,
     mGuardBladeCtrlFlashID DisplayString,
     mGuardBladeCtrlVersion DisplayString,
     mGuardBladeCtrlBackup INTEGER,
     mGuardBladeCtrlRestore INTEGER
  }

  mGuardBladeCtrlIndex OBJECT-TYPE
    SYNTAX INTEGER (1..100)
    ACCESS not-accessible
    STATUS mandatory
    DESCRIPTION
      "Table index."
   ::= { mGuardBladeCtrlEntry 1 }

   mGuardBladeCtrlDevice OBJECT-TYPE
    SYNTAX DisplayString
    ACCESS read-only
    STATUS mandatory
    DESCRIPTION
      "The name of the device inside the slot."
   ::= { mGuardBladeCtrlEntry 2 }

   mGuardBladeCtrlStatus OBJECT-TYPE
    SYNTAX INTEGER {
      absent(1),
      present(2),
      online(3)
    }
    ACCESS read-only
    STATUS mandatory
    DESCRIPTION
      "The status of the blade/slot."
   ::= { mGuardBladeCtrlEntry 3 }

   mGuardBladeCtrlAVRRevision OBJECT-TYPE
    SYNTAX DisplayString
    ACCESS read-only
    STATUS mandatory
    DESCRIPTION
      "The AVR revision of the blades bus controller."
   ::= { mGuardBladeCtrlEntry 4 }

   mGuardBladeCtrlSlotID OBJECT-TYPE
    SYNTAX DisplayString
    ACCESS read-only
    STATUS mandatory
    DESCRIPTION
      "The blades slot ID, as seen by the blade."
   ::= { mGuardBladeCtrlEntry 5 }

   mGuardBladeCtrlProductID OBJECT-TYPE
    SYNTAX DisplayString
    ACCESS read-only
    STATUS mandatory
    DESCRIPTION
      "The blades product ID."
   ::= { mGuardBladeCtrlEntry 6 }

   mGuardBladeCtrlAssemblyID OBJECT-TYPE
    SYNTAX DisplayString
    ACCESS read-only
    STATUS mandatory
    DESCRIPTION
      "The blades assembly ID."
   ::= { mGuardBladeCtrlEntry 7 }

   mGuardBladeCtrlSerial OBJECT-TYPE
    SYNTAX DisplayString
    ACCESS read-only
    STATUS mandatory
    DESCRIPTION
      "The blades serial number."
   ::= { mGuardBladeCtrlEntry 8 }

   mGuardBladeCtrlFlashID OBJECT-TYPE
    SYNTAX DisplayString
    ACCESS read-only
    STATUS mandatory
    DESCRIPTION
      "The blades Flash ID."
   ::= { mGuardBladeCtrlEntry 9 }

   mGuardBladeCtrlVersion OBJECT-TYPE
    SYNTAX DisplayString
    ACCESS read-only
    STATUS mandatory
    DESCRIPTION
      "The blades software version."
   ::= { mGuardBladeCtrlEntry 10 }

   mGuardBladeCtrlBackup OBJECT-TYPE
    SYNTAX INTEGER {
      yes(1),
      no(2)
    }
    ACCESS read-write
    STATUS mandatory
    DESCRIPTION
      "Wether to automatically pull the configuration off the blade/slot."
   ::= { mGuardBladeCtrlEntry 11 }

   mGuardBladeCtrlRestore OBJECT-TYPE
    SYNTAX INTEGER {
      yes(1),
      no(2)
    }
    ACCESS read-write
    STATUS mandatory
    DESCRIPTION
      "Wether to automatically push the configuration to the blade freshly inserted into the slot."
   ::= { mGuardBladeCtrlEntry 12 }


  mGuardBladePwrTable OBJECT-TYPE
    SYNTAX SEQUENCE OF  MGuardBladePwrEntry
    ACCESS not-accessible
    STATUS mandatory
    DESCRIPTION
      "Overview of controlled power supplies."
   ::= { mGuardBlade 4 }

  mGuardBladePwrEntry OBJECT-TYPE
      SYNTAX MGuardBladePwrEntry
      ACCESS not-accessible
      STATUS mandatory
      DESCRIPTION
       "Table entry."
      INDEX { mGuardBladePwrIndex }
  ::= { mGuardBladePwrTable 1 }

  MGuardBladePwrEntry  ::= SEQUENCE {
     mGuardBladePwrIndex INTEGER,
     mGuardBladePwrStatus INTEGER
  }

  mGuardBladePwrIndex OBJECT-TYPE
    SYNTAX INTEGER (1..100)
    ACCESS not-accessible
    STATUS mandatory
    DESCRIPTION
      "Table index."
   ::= { mGuardBladePwrEntry 1 }

   mGuardBladePwrStatus OBJECT-TYPE
    SYNTAX INTEGER {
      absent(1),
      fatal(2),
      defect(3),
      ok(4)
    }
    ACCESS read-only
    STATUS mandatory
    DESCRIPTION
      "Status of the power supply."
   ::= { mGuardBladePwrEntry 2 }


--
-- Configuration Profiles
--

  mGuardProfilePush OBJECT IDENTIFIER ::= { mGuardProfile 1 }

  mGuardProfilePull OBJECT IDENTIFIER ::= { mGuardProfile 2 }

  mGuardProfilePullSchedule OBJECT-TYPE
    SYNTAX INTEGER
              {
	        never(1),
		onboot(2),
		quarterhourly(15),
		halfhourly(30),
		hourly(60),
		bihourly(120),
		triplehourly(360),
		sixhourly(720),
		twicedayly(1440)
	      }
    ACCESS read-write
    STATUS mandatory
    DESCRIPTION
       "The period used when polling remote configuration profiles."
  ::= { mGuardProfilePull 1 }

  mGuardProfilePullHTTPS OBJECT IDENTIFIER ::= { mGuardProfilePull 2 }

  mGuardProfilePullHTTPSCert OBJECT-TYPE
    SYNTAX DisplayString
    ACCESS read-write
    STATUS mandatory
    DESCRIPTION
      "X.509 Certificate of the HTTPS server to pull configuration profiles
       from. This used to authenticate the HTTPS server."
  ::= { mGuardProfilePullHTTPS 1 }

  mGuardProfilePullHTTPSServer OBJECT-TYPE
    SYNTAX DisplayString
    ACCESS read-write
    STATUS mandatory
    DESCRIPTION
      "Hostname or IP of the HTTPS server to pull configuration profiles
       from."
  ::= { mGuardProfilePullHTTPS 2 }

  mGuardProfilePullHTTPSPort OBJECT-TYPE
    SYNTAX DisplayString
    ACCESS read-write
    STATUS mandatory
    DESCRIPTION
      "Port of the HTTPS server to pull configuration profiles from.
       Usually 443."
  ::= { mGuardProfilePullHTTPS 3 }

  mGuardProfilePullHTTPSFile OBJECT-TYPE
    SYNTAX DisplayString
    ACCESS read-write
    STATUS mandatory
    DESCRIPTION
      "Filename of the configuration to pull. Default is an empty name, in
       which case the serialnumber with the extension '.atv' is used."
  ::= { mGuardProfilePullHTTPS 4 }

  mGuardProfilePullHTTPSLogin OBJECT-TYPE
    SYNTAX DisplayString
    ACCESS read-write
    STATUS mandatory
    DESCRIPTION
      "Login on the HTTPS server to pull configuration profiles from."
  ::= { mGuardProfilePullHTTPS 5 }

  mGuardProfilePullHTTPSPasswd OBJECT-TYPE
    SYNTAX DisplayString
    ACCESS read-write
    STATUS mandatory
    DESCRIPTION
      "Password on the HTTPS server to pull configuration profiles from."
  ::= { mGuardProfilePullHTTPS 6 }

  mGuardProfilePullHTTPSDirectory OBJECT-TYPE
    SYNTAX DisplayString
    ACCESS read-write
    STATUS mandatory
    DESCRIPTION
      "Directory on the HTTPS server to pull configuration profiles from."
  ::= { mGuardProfilePullHTTPS 7 }


--
-- Users
--

  mGuardRemoteUsers OBJECT IDENTIFIER ::= { mGuardUsers 1 }

  mGuardRADIUS OBJECT IDENTIFIER ::= { mGuardRemoteUsers 1 }

  mGuardRADIUSTimeout OBJECT-TYPE
    SYNTAX INTEGER (1..100)
    ACCESS read-write
    STATUS mandatory
    DESCRIPTION
      "Time to wait before deciding that a RADIUS server has not responded to a request."
  ::= { mGuardRADIUS 1 }

  mGuardRADIUSRetries OBJECT-TYPE
    SYNTAX INTEGER (1..100)
    ACCESS read-write
    STATUS mandatory
    DESCRIPTION
      "The number of packets of sent to a RADIUS server before giving up."
  ::= { mGuardRADIUS 2 }

  mGuardRADIUSServerTable OBJECT-TYPE
    SYNTAX SEQUENCE OF MGuardRADIUSServerEntry
    ACCESS not-accessible
    STATUS mandatory
    DESCRIPTION
      "A table containing RADIUS servers."
  ::= { mGuardRADIUS 3 }

  mGuardRADIUSServerEntry OBJECT-TYPE
    SYNTAX MGuardRADIUSServerEntry
    ACCESS not-accessible
    STATUS mandatory
    DESCRIPTION
      "An entry containing a single RADIUS server."
    INDEX { mGuardRADIUSServerIndex }
  ::= { mGuardRADIUSServerTable 1 }

  MGuardRADIUSServerEntry ::= SEQUENCE {
    mGuardRADIUSServerIndex     INTEGER,
    mGuardRADIUSServerHostname  DisplayString,
    mGuardRADIUSServerPort      INTEGER,
    mGuardRADIUSServerSecret    DisplayString,
    mGuardRADIUSServerRowStatus RowStatus
  }

  mGuardRADIUSServerIndex OBJECT-TYPE
    SYNTAX INTEGER (1..100)
    ACCESS not-accessible
    STATUS mandatory
    DESCRIPTION
      "Index to identify RADIUS server entry."
  ::= { mGuardRADIUSServerEntry 1 }

  mGuardRADIUSServerHostname OBJECT-TYPE
    SYNTAX DisplayString
    ACCESS read-write
    STATUS mandatory
    DESCRIPTION
      "The hostname or IP address of the RADIUS server."
  ::= { mGuardRADIUSServerEntry 2 }

  mGuardRADIUSServerPort OBJECT-TYPE
    SYNTAX INTEGER (1..65535)
    ACCESS read-write
    STATUS mandatory
    DESCRIPTION
      "The port number of the RADIUS server."
  ::= { mGuardRADIUSServerEntry 3 }

  mGuardRADIUSServerSecret OBJECT-TYPE
    SYNTAX DisplayString
    ACCESS read-write
    STATUS mandatory
    DESCRIPTION
      "The secret shared with the RADIUS server."
  ::= { mGuardRADIUSServerEntry 4 }

  mGuardRADIUSServerRowStatus OBJECT-TYPE
    SYNTAX RowStatus
    ACCESS read-write
    STATUS mandatory
    DESCRIPTION
      "Row Status"
  ::= { mGuardRADIUSServerEntry 5 }

  mGuardUserFWUsers OBJECT IDENTIFIER ::= { mGuardRemoteUsers 2 }

  mGuardUserFWUserTable OBJECT-TYPE
    SYNTAX SEQUENCE OF MGuardUserFWUserEntry
    ACCESS not-accessible
    STATUS mandatory
    DESCRIPTION
      "A table containing user firewall users."
  ::= { mGuardUserFWUsers 1 }

  mGuardUserFWUserEntry OBJECT-TYPE
    SYNTAX MGuardUserFWUserEntry
    ACCESS not-accessible
    STATUS mandatory
    DESCRIPTION
      "An entry containing a single user firewall user."
    INDEX { mGuardUserFWUserIndex }
  ::= { mGuardUserFWUserTable 1 }

  MGuardUserFWUserEntry ::= SEQUENCE {
    mGuardUserFWUserIndex      INTEGER,
    mGuardUserFWUserName       DisplayString,
    mGuardUserFWUserAuthMethod INTEGER,
    mGuardUserFWUserPassword   DisplayString,
    mGuardUserFWUserRowStatus  RowStatus
  }

  mGuardUserFWUserIndex OBJECT-TYPE
    SYNTAX INTEGER (1..100)
    ACCESS not-accessible
    STATUS mandatory
    DESCRIPTION
      "Index to identify the user firewall user entry."
  ::= { mGuardUserFWUserEntry 1 }

  mGuardUserFWUserName OBJECT-TYPE
    SYNTAX DisplayString
    ACCESS read-write
    STATUS mandatory
    DESCRIPTION
      "The username of the user firewall user entry."
  ::= { mGuardUserFWUserEntry 2 }

  mGuardUserFWUserAuthMethod OBJECT-TYPE
    SYNTAX INTEGER {
			radius(1),
			local(2)
                   }
    ACCESS read-write
    STATUS mandatory
    DESCRIPTION
      "The authentication method of the user firewall user entry."
  ::= { mGuardUserFWUserEntry 3 }

  mGuardUserFWUserPassword OBJECT-TYPE
    SYNTAX DisplayString
    ACCESS read-write
    STATUS mandatory
    DESCRIPTION
      "The password of the user firewall user entry.  The password can be set, but not obtained.
       If the variable is read, a * character is returned."
  ::= { mGuardUserFWUserEntry 4 }

  mGuardUserFWUserRowStatus OBJECT-TYPE
    SYNTAX RowStatus
    ACCESS read-write
    STATUS mandatory
    DESCRIPTION
      "Row Status"
  ::= { mGuardUserFWUserEntry 5 }


-- ****************************************************************
-- * Traps according to RfC 1215                                  *
-- ****************************************************************

  mGuardTraps  OBJECT IDENTIFIER ::= { mGuardInfo 5 }

   mGuardTrapDiscFull TRAP-TYPE
    ENTERPRISE  mGuardTraps
    VARIABLES  { mGuardTResDiscFull }
    DESCRIPTION
       "Status of file system free space. If multiple file systems, the worst state is used."
   ::= 1

   mGuardTrapCpuLoadHigh TRAP-TYPE
    ENTERPRISE  mGuardTraps
    VARIABLES  { mGuardTResCpuLoadHigh }
    DESCRIPTION
       "CPU load above 1."
   ::= 2

   mGuardTrapMemoryFull TRAP-TYPE
    ENTERPRISE  mGuardTraps
    VARIABLES  { mGuardTResMemoryFull }
    DESCRIPTION
       "Free memory (RAM) low."
   ::= 3

   mGuardTrapColdstart TRAP-TYPE
    ENTERPRISE  mGuardTraps
    VARIABLES  { mGuardTResColdstart }
    DESCRIPTION
       "Trap sent when system rebooted (snmp daemon started)."
   ::= 4


--
-- Traps with enterprise = mGuardb
--
mGuardHTTPSLoginTrap TRAP-TYPE
	ENTERPRISE	mGuardb
	VARIABLES	{ mGuardHTTPSLastAccessIP }
	DESCRIPTION
	  "This trap is sent when someone is trying to open a HTTPS session
           using the wrong password. mGuardHTTPSLastAccessIP contains the IP
	   address of the last unsuccessfull login request."
	::= 1

mGuardShellLoginTrap TRAP-TYPE
	ENTERPRISE	mGuardb
	VARIABLES	{ mGuardShellLastAccessIP }
	DESCRIPTION
	    "This trap is sent when someone opens the shell through SSH or
	     serial console. mGuardShellAccessLastIP contains the IP address of
	     the login request. The value of mGuardShellAccessLastIP is 0.0.0.0,
	     if the request was sent via serial console. "
	::= 2

mGuardDHCPNewClientTrap TRAP-TYPE
	ENTERPRISE	mGuardb
	VARIABLES	{ mGuardDHCPLastAccessMAC }
	DESCRIPTION
	    "This trap is sent when a DHCP request was received from an unknown
	     client"
	::= 3


--
-- mGuardTrapAV
--

  mGuardTrapAV  OBJECT IDENTIFIER ::= { mGuardInfo 6 }

   mGuardTrapAvUpdateDone TRAP-TYPE
    ENTERPRISE  mGuardTrapAV
    VARIABLES  { mGuardTResAvUpdateDone }
    DESCRIPTION
       "AV Update was performed successfully."
   ::= 1

   mGuardTrapAvUpdateError TRAP-TYPE
    ENTERPRISE  mGuardTrapAV
    VARIABLES  { mGuardTResAvUpdateError }
    DESCRIPTION
       "Error when performing AV Update."
   ::= 2

   mGuardTrapAvVirusDetected TRAP-TYPE
    ENTERPRISE  mGuardTrapAV
    VARIABLES  { mGuardTResAvVirusDetected }
    DESCRIPTION
       "AV found a virus."
   ::= 3

   mGuardTrapAvFileNotScanned TRAP-TYPE
    ENTERPRISE  mGuardTrapAV
    VARIABLES  { mGuardTResAvFileNotScanned }
    DESCRIPTION
       "The file was not scanned for viruses."
   ::= 4

   mGuardTrapAvFailed TRAP-TYPE
    ENTERPRISE  mGuardTrapAV
    VARIABLES  { mGuardTResAvFailed }
    DESCRIPTION
       "General AV failure."
   ::= 5


--
-- mGuardTrapPlatformSpecific
--

  mGuardTrapPlatformSpecific  OBJECT IDENTIFIER ::= { mGuardInfo 7 }

  mGuardTrapIndustrial  OBJECT IDENTIFIER ::= { mGuardTrapPlatformSpecific 1 }

  mGuardTrapIndustrialPowerStatus TRAP-TYPE
   ENTERPRISE  mGuardTrapIndustrial
   VARIABLES  { mGuardPSState }
   DESCRIPTION
       "Trap sent when power supply failure was detected."
   ::= 2

  mGuardTrapIndustrialTemperature  TRAP-TYPE
   ENTERPRISE  mGuardTrapIndustrial
   VARIABLES  { mGuardSystemTemperature, mGuardTResIndustrialTempHiLimit, mGuardTResIndustrialTempLowLimit }
   DESCRIPTION
       "Trap reporting temperature exceeding the given limits."
   ::= 1

  mGuardTrapSignalRelais TRAP-TYPE
    ENTERPRISE  mGuardTrapIndustrial
    VARIABLES  { mGuardTResSignalRelaisState, mGuardTResSignalRelaisReason, mGuardTResSignalRelaisReasonIdx }
    DESCRIPTION
         "Current state of the signal relais changed (0=off, 1=on)."
   ::= 3

  mGuardTrapAutoConfigAdapterState TRAP-TYPE
   ENTERPRISE  mGuardTrapIndustrial
   VARIABLES  { mGuardTResAutoConfigAdapterState }
   DESCRIPTION
       "Trap sent when ACA was accessed."
   ::= 4

  mGuardTrapBladeCTRL  OBJECT IDENTIFIER ::= { mGuardTrapPlatformSpecific 2 }

  mGuardTrapBladeCtrlCfg  OBJECT IDENTIFIER ::= { mGuardTrapBladeCTRL 5 }

  mGuardTrapBladeCtrlPowerStatus TRAP-TYPE
   ENTERPRISE  mGuardTrapBladeCTRL
   VARIABLES  { mGuardTResBladeRackID, mGuardTResBladeSlotNr, mGuardTResBladeCtrlPowerStatus }
   DESCRIPTION
         "BladePack's power supplies status changed."
   ::= 2

  mGuardTrapBladeCtrlRunStatus TRAP-TYPE
   ENTERPRISE  mGuardTrapBladeCTRL
   VARIABLES  { mGuardTResBladeRackID, mGuardTResBladeSlotNr, mGuardTResBladeCtrlRunStatus }
   DESCRIPTION
         "Blade's run status changed."
   ::= 3

  mGuardTrapBladeCtrlCfgBackup TRAP-TYPE
   ENTERPRISE  mGuardTrapBladeCtrlCfg
   VARIABLES  { mGuardTResBladeRackID, mGuardTResBladeSlotNr, mGuardTResBladeCtrlCfgBackup }
   DESCRIPTION
         "Configuration backup to Blade CTRL is triggered."
   ::= 1

  mGuardTrapBladeCtrlCfgRestored TRAP-TYPE
   ENTERPRISE  mGuardTrapBladeCtrlCfg
   VARIABLES  { mGuardTResBladeRackID, mGuardTResBladeSlotNr, mGuardTResBladeCtrlCfgRestored }
   DESCRIPTION
         "Configuration restore from Blade CTRL is triggered."
   ::= 2

--
-- mGuardTrapRouterRedundancy
--

   mGuardTrapRouterRedundancy  OBJECT IDENTIFIER ::= { mGuardInfo 8 }

   mGuardTrapRouterRedundancyStatusChange TRAP-TYPE
    ENTERPRISE mGuardTrapRouterRedundancy
    VARIABLES  { mGuardRouterRedundancyState, mGuardTResRedundacyReason }
    DESCRIPTION
       "Current HA cluster state changed."
   ::= 1

   mGuardTrapRouterRedundancyBackupDown TRAP-TYPE
    ENTERPRISE mGuardTrapRouterRedundancy
    VARIABLES  { mGuardTResRedundacyBackupDown }
    DESCRIPTION
       "Backup device  is not reachable by Master device (This trap is only sent, when ICMP checks are activated)."
   ::= 2


END
