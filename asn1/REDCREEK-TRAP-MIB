REDCREEK-TRAP-MIB DEFINITIONS ::= BEGIN

-- TRAP MIB
-- Date 10/02/96

-- Copyright(C) RedCreek Communications.
-- All rights reserved.
-- This RedCreek Communications SNMP Management Information Base
-- Specification is RedCreek Communications' confidential and
-- proprietary intellectual property. RedCreek Communications retains
-- all title and ownership in the Specification, including any
-- revisions.

-- This Specification is supplied "AS IS," and RedCreek Communications
-- makes no warranty, either express or implied, as to the use,
-- operation, condition, or performance of the Specification.

-- Imports

IMPORTS
		TRAP-TYPE		FROM RFC-1215
		rcTrap FROM RCV3;

-- TRAP Definitions.

rcBadSignature  TRAP-TYPE
    ENTERPRISE rcTrap
	--VARIABLES { rcIpAddress }
	DESCRIPTION
	    "Signature verified to be bad by ISAKMP. This Trap will provide
		the IP Address of the remote unit, whose signature is verified 
		as bad."
	::= 1

rcHashFailed TRAP-TYPE
    ENTERPRISE rcTrap
    --VARIABLES  { rcIpAddress }
    DESCRIPTION
    "TRAP generated when the unit receives a Set Request with an incorrect
    Hash object. The rcIpAddress will indicate the Client IP Address that 
    generated the Set Request."
    ::= 2

rcFirmwareDownloadSucceded  TRAP-TYPE
    ENTERPRISE rcTrap
    --VARIABLES  { rcIpAddress }
    DESCRIPTION
        "This trap indicates that new firmware download to the box was 
        successful. The variable is the IP Address of the configurator
        tool that initiated the download process."
    ::= 3

rcFirmwareDownloadFailed  TRAP-TYPE
    ENTERPRISE rcTrap
    --VARIABLES { rcIpAddress, rcLastErrorCode }
    DESCRIPTION
        "This trap indicates that firmware download to the box failed. The
        variable is the IP Address of the configurator tool that 
        initiated the download process. rcLastErrorCode, indicates the
        reason for download failure."
    ::= 4

rcTunnelStatusThreshold  TRAP-TYPE
    ENTERPRISE rcTrap
    --VARIABLES { rcTunnelStatus }
    DESCRIPTION
        "This TRAP is generated by a Ravlin unit, if the polling statistics
        is below the warning threshold. rcTunnelStatus variable is a string
        formated to describe the information."
    ::= 5


END
