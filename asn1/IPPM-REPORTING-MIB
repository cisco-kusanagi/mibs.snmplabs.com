-- extracted from draft-ietf-ippm-reporting-mib-06.txt
-- at Wed Jul 21 06:22:32 2004

      IPPM-REPORTING-MIB DEFINITIONS ::= BEGIN


      IMPORTS
      mib-2,
      MODULE-IDENTITY,
      NOTIFICATION-TYPE,
      OBJECT-TYPE,
      Integer32, zeroDotZero, Counter64, Unsigned32
          FROM SNMPv2-SMI
      InetAddressType,
      InetAddress
          FROM INET-ADDRESS-MIB
      SnmpAdminString
          FROM SNMP-FRAMEWORK-MIB
      RowStatus,
      StorageType,
      TEXTUAL-CONVENTION
          FROM SNMPv2-TC
      MODULE-COMPLIANCE,
      OBJECT-GROUP,
      NOTIFICATION-GROUP
          FROM SNMPv2-CONF;







   ippm MODULE-IDENTITY
      LAST-UPDATED "200407151200Z" --  15 July 2004
      ORGANIZATION "IP Performance Metrics (ippm) Working Group"
      CONTACT-INFO
        "Emile Stephan
        France Telecom - R&D
        E-mail: emile.stephan@francetelecom.com


        Jessie Jewitt
        France Telecom - R&D
        E-mail : jessie.jewitt@rd.francetelecom.com


        Comments about this document should be send to the IPPM
        working group mailing list at ippm@ietf.org.
        "
      DESCRIPTION
          "This memo defines a portion of the Management Information
          Base (MIB) for use with network management protocols in
          TCP/IP-based internets. In particular, it specifies the
          objects used for managing the results of the IPPM metrics
          measurements, alarms and reporting of measurement results."


      REVISION "200210181200Z" -- 18 October 2002
      DESCRIPTION
          "General cleanup
          Change 5 tables to read write"


      REVISION "200302141200Z" --  14 February 2003
      DESCRIPTION
          "Modifications based upon feedback from IETF-55"


      REVISION "200306291200Z" --  29 June 2003
      DESCRIPTION
          "Adaptation to VACM, preparation of the final version"


      REVISION "200310241200Z" --  24 October 2003
      DESCRIPTION
          "Modifications based upon feedback from experimental
          implementation."


      REVISION "200402121200Z" --  12 February 2004
      DESCRIPTION
          "Modifications based upon feedback 58th IETF: The report
          group and the corresponding notification are removed."


      REVISION "200407151200Z" --  15 July 2004
      DESCRIPTION
          "Rewritten in XML and Clean up."


      ::= { mib-2 XXX }
      -- RFC Ed.: replace XXX with IANA-assigned number
      --          & remove this note

   --
   -- TEXTUAL-CONVENTION


   --


   IppmOwnerString ::= TEXTUAL-CONVENTION
      STATUS       current
      DESCRIPTION
          "The owner namespace is defined in the INDEX of a table as a
          couple of 2 objects where the type of the first one is
          IppmOwnerString and the type of the second is IppmOwnerIndex.
          IppmOwnerString is an OwnerString which length is limited to
          32 bytes."
      SYNTAX OCTET STRING (SIZE (0..32))








   IppmOwnerIndex ::= TEXTUAL-CONVENTION
      STATUS       current
      DESCRIPTION
          "The owner namespace is defined in the INDEX of a table as a
          couple of 2 objects where the type of first one is
          IppmOwnerString and the type of the second is IppmOwnerIndex.
          An object of type IppmOwnerIndex uniquely identifies a row of
          a table inside an owner namespace.
          Inside one namespace several objects of type IppmOwnerIndex
          coexist and share the IppmOwnerIndex range of values to
          provide an unique instance identifier.
          "
          SYNTAX Unsigned32 (1.. 65535)


   TimeUnit ::= TEXTUAL-CONVENTION
      STATUS       current
      DESCRIPTION
          "A enumerated list of time units."
      SYNTAX       INTEGER {
          week(1),
          day(2),
          hour(3),
          minute(4),
          second(5),
          millisecond(6),
          microsecond(7),
          nanosecond(8)

      }







   --
   --


   IppmStandardMetrics ::= TEXTUAL-CONVENTION
      STATUS      current
      DESCRIPTION
       " Each standard metric is identified in the IPPM-METRICS-
       REGISTRY under the node rfc in chronological order. In order to
       allow for several metrics to be calculated in a single measure,
       there is a need to describe in a bit string the metrics to be
       measured.


       This textual convention defines an octet string that gathers in a
       bit string a sequence of bits. The bit order corresponds to the
       order of the metric identifiers in the registry.
       The first bit of the string has the index 0. The index 1
       corresponds to the first metric of the registry
       (instantaneousUnidirectionalConnectivity ).


       Example:
       One-way-Delay(6) is identified as the leaf number 6 of the node
       rfc of the registry. One-way-Packet-Loss(12) is identified as the
       leaf number 12 of the node
       rfc of the registry. A network measure performing both One-way-
       Delay(6) and One-way-Packet-Loss(12) will be described as
       '0001000001000000'b, '1040'B.
       "
      SYNTAX OCTET STRING (SIZE (1..64))

   IppmMetricsRegistryIndex ::= TEXTUAL-CONVENTION
      STATUS      current
      DESCRIPTION
       "IppmMetricsRegistryIndex defines an unambiguous index for each
       standardized metric. It identifies a metric, and as such its
       value is the value of the node of the metric in the IPPM
       registry. This value is the same in any implementation of the
       IPPM REPORTING MIB.


       Example:
       In the IPPM-METRICS-REGISTRY, onewayPacketLossAverage is
       registered as the node 14 of ippmMetricsRegistry.metrics.rfc.
       Consequently the index of the metric onewayPacketLossAverage in
       the IppmMetricsTable will always be '14'. At large an instance,
       which type is IppmMetricsRegistryIndex and which value is '14',
       points to the metric onewayPacketLossAverage."
      SYNTAX Unsigned32 (1.. 65535)








   GMTTimeStamp ::= TEXTUAL-CONVENTION
      STATUS       current
      DESCRIPTION
          "The time value at which a measure or an event took place.


          field  octets  contents                  range
          -----  ------  --------                  -----
          1       1-4    second since 1 Jan 1900 0H00*    0..2^31 - 1
          2       5-8    fractional part of the second*   0..2^32 - 1
          * the value is in network-byte order


          The timestamp format is the NTP timestamp format [RFC 1305].
          The reference of time is GMT.


          "
      SYNTAX       OCTET STRING (SIZE (8))

   PacketType  ::= TEXTUAL-CONVENTION
     STATUS       current
     DESCRIPTION
       "This textual convention is a display string used to describe the
       protocol encapsulation list of a packet, and is used as the value
       of the SYNTAX clause for the type of the Src and Dst of an IPPM
       measure. The RFC2895 specifies a macro named PROTOCOL-IDENTIFIER
       for the definition of protocol identifiers, while its companion
       document, the RFC2896 defines a set of protocol identifiers.


       PacketType is defined as a display string. It consists of a list
       of dot separated protocol names. Each protocol name has been
       previously defined using the macro PROTOCOL-IDENTIFIER of the RFC
       2895.


       Examples:
       The RFC2896 defines the protocol identifiers 'ether2', 'ip',
       'ipip4', 'udp', 'tcp', 'telnet'...


       The PacketType of the source address corresponding to telnet is
       the string 'ip.tcp.telnet'.


       The PacketType of the source address corresponding to UDP packets
       sent in an IP tunnel is the string 'ip.ipip4.udp'.


       Note:
       An IPPM measure is active, so generally a PacketType value does
       not describe the link layer (i.e. ether2...). Valid Internet
       packets are sent from Src to Dst. Then the choice of the link
       layer relies on the Internet stack."
     SYNTAX       OCTET STRING (SIZE (0..512))

   PacketTypeAddress ::= TEXTUAL-CONVENTION
     DISPLAY-HINT "255a"
     STATUS       current
     DESCRIPTION
       "This textual convention is a Display string used to describe the
       parameters of the protocol encapsulation list of a packet,
       basically the address.


       PacketTypeAddress is defined as a display string. It consists in
       a list of blank separated addresses that reflect the
       encapsulation of the PacketType. Each parameter in the list
       corresponds to a parameter of a PROTOCOL-IDENTIFIER of the
       PacketType.
       Example:
       The PacketType 'ip.ipip4' has 2 parameters. A valid
       PacketTypeAddress value is '192.168.1.1 128.2.6.7'."
     SYNTAX       OCTET STRING (SIZE (0..512))









     IppmMetricResultFilter ::= TEXTUAL-CONVENTION
     STATUS        current
     DESCRIPTION
     "Given that not all results from a metric measurement are
        pertinent, and that the size of the history must be limited whenever
        possible, the TC IppmMetricResultFilter defines basic filters to
        limit the among of data collected:


        Filter's parameters are the 2 fields ippmAggrMeasureLowThreshold and
        ippmAggrMeasureLowThreshold of the aggregated measure setup.


        A filter determines if the result of the current aggregation has to
        be stored:


        LogInBandValue:
        The value is stored if it is lower than the high threshold of
        the aggregated measure setup and greater than the low
        threshold of of the aggregated measure setup.


        LogOutBandValue:
        The value is stored if it is greater than the high threshold
        of the aggregated measure setup or lower than the low
        threshold of the aggregated measure setup.
        LogAboveValue:
        The value is stored if it is greater than the high threshold
        of the aggregated measure setup.


        LogBelowValue:
        The value is stored if it is lower than the low metric
        threshold field of the aggregated measure setup.


        logUpAndDownValue:
        This filter stores contiguous results that are on opposite
        sides of the up and down metric thresholds:
             A result is stored if it is the first result aggregated:
        If it is greater than the high threshold and lower than the
        low threshold then its value is set to the value of the low
        threshold;


             A result greater than the high threshold is stored if the
        previous result is lower than the low threshold;


             A result lower than the low threshold is stored if the
        previous result is greater than the high threshold;


        "

      SYNTAX       INTEGER {
          logInBandValue(1),
          logOutBandValue(2),
          logAboveValue(3),
          logBelowValue(4),
          logUpAndDownValue(5)
      }





   --
   -- IPPM  Notifications
   --
   ippmNotifications OBJECT IDENTIFIER ::= { ippm 0 }


   --
   -- IPPM MIB Object definitions
   --
   ippmMibObjects      OBJECT IDENTIFIER   ::= { ippm 1 }



   ippmSystem           OBJECT IDENTIFIER   ::= { ippmMibObjects 1 }
   ippmOwners           OBJECT IDENTIFIER   ::= { ippmMibObjects 2 }
   ippmHistory          OBJECT IDENTIFIER   ::= { ippmMibObjects 3 }
   ippmNetMeasure       OBJECT IDENTIFIER   ::= { ippmMibObjects 4 }
   ippmAggrMeasure      OBJECT IDENTIFIER   ::= { ippmMibObjects 5 }



   --
   -- IPPM  Conformance
   --
   ippmConformance      OBJECT IDENTIFIER   ::= { ippm 2 }







   --
   -- ippmSystem  Group
   --
   --




   ippmSystemTime OBJECT-TYPE
      SYNTAX GMTTimeStamp
      MAX-ACCESS read-only
      STATUS     current
      DESCRIPTION
          "The current time of the system running the IPPM REPORTING MIB
          SNMP agent. When the agent is running in proxy mode, it is the
          current time of the proxy agent.
          When the agent is located in the probe, it is the current time
           of the probe agent. "
      ::= { ippmSystem  1 }


   ippmSystemSynchronizationType OBJECT-TYPE
      SYNTAX INTEGER  {
           other(0),


           ntp(1),
           gps(2),
           cdma(3)
      }
      MAX-ACCESS read-only
      STATUS     current
      DESCRIPTION
          "ippmSystemSynchronizationType describes the mechanism
          used to synchronize the system running the IPPM REPORTING MIB
          SNMP agent.


          Other(0)
          The synchronization process must be defined
          in the ippmSystemSynchonizationDescription.


          Ntp(1)
          The system is synchronized using the network
          time protocol. The NTP synchronization must be described
          in the ippmSystemSynchonizationDescription.


          Gps(2)
          The system is synchronized using the GPS clocks.


          Cdma(3)
          The system is synchronized using the CDMA clocks."
      ::= { ippmSystem 2 }



   ippmSystemSynchronizationDesc OBJECT-TYPE
      SYNTAX SnmpAdminString
      MAX-ACCESS read-only
      STATUS     current
      DESCRIPTION
          "The description of the synchronization process of the system
          running the IPPM REPORTING MIB SNMP agent."
      ::= { ippmSystem 3 }


   ippmSystemClockResolution OBJECT-TYPE
      SYNTAX     Unsigned32
      UNITS "Nanoseconds"
      MAX-ACCESS read-only
      STATUS     current
      DESCRIPTION
        "ippmSystemClockResolution provides the precision of the clock
        used for the measures . The unit is the nanosecond. For example,
        the clock on an old Unix host might advance only once every 10
        msec, and thus have a resolution of 10 msec. So its resolution
        is 10000000 nanoseconds and the value of
        ippmSystemClockResolution is 10000000."
      ::= { ippmSystem 4 }



   ippmSystemOperationalStatus OBJECT-TYPE


      SYNTAX INTEGER  {
           unknown(0),
           up(1),
           down(2)
      }
      MAX-ACCESS read-only
      STATUS     current
      DESCRIPTION
        "This object describes the status of the system running the IPPM
        REPORTING MIB SNMP agent. It does not describe end point
        measurement status:


          unknown(0) means the service is unknown.
          up(1) means the service is operational and available for
          general use.
          down(2) means the agent is not available for use.
          "
      ::= { ippmSystem 5 }


   ippmSystemAggregatedMetrics OBJECT-TYPE
      SYNTAX     IppmStandardMetrics
      MAX-ACCESS read-only
      STATUS     current
      DESCRIPTION
          "ippmSystemAggregatedMetrics lists the aggregated metrics that
          are performed in the SNMP agent instead of in the point of
          measure."
      ::= { ippmSystem 6 }

   ippmSynchronizationTable OBJECT-TYPE
      SYNTAX     SEQUENCE OF IppmSynchronizationEntry
      MAX-ACCESS not-accessible
      STATUS     current
      DESCRIPTION
          "This table registers the event related to the synchronization
           of the points of measure. Each event is described in an
          ippmSynchronizationEntry.
          ippmSynchronizationTable is mandatory.
          ippmSynchronizationTable content is read only."
      ::= { ippmSystem 7 }


      ippmSynchronizationEntry OBJECT-TYPE
      SYNTAX     IppmSynchronizationEntry
      MAX-ACCESS not-accessible
      STATUS     current
      DESCRIPTION
          "An entry describes a modification of the synchronization
          status."
      INDEX { ippmPointOfMeasureIndex, ippmSynchronizationIndex }
      ::= { ippmSynchronizationTable 1 }



   IppmSynchronizationEntry ::=
      SEQUENCE {
          ippmSynchronizationIndex               Unsigned32,
          ippmSynchronizationTime                GMTTimeStamp,
          ippmSynchronizationStratum             Unsigned32,
          ippmSynchronizationResolution          Unsigned32
      }



   ippmSynchronizationIndex     OBJECT-TYPE
      SYNTAX     Unsigned32 (1 .. 65535)
      MAX-ACCESS not-accessible
      STATUS     current
      DESCRIPTION
          "An index that identifies the synchronization events in
          chronological order.
          65535 is an arbitrary size. It is not recommended to keep
          permanently a history of 65535 events."
      ::= { ippmSynchronizationEntry 1 }



   ippmSynchronizationTime OBJECT-TYPE
   SYNTAX GMTTimeStamp
      MAX-ACCESS read-only
      STATUS     current
      DESCRIPTION
          "The time when the synchronization event occurs."
      ::= { ippmSynchronizationEntry 2 }


   ippmSynchronizationStratum OBJECT-TYPE
      SYNTAX     Unsigned32
      MAX-ACCESS read-only
      STATUS     current
      DESCRIPTION
          "The stratum level of the clock computed when the
          synchronization event occurs."
      ::= { ippmSynchronizationEntry 3 }


   ippmSynchronizationResolution OBJECT-TYPE
      SYNTAX     Unsigned32
      UNITS      "Nanoseconds"
      MAX-ACCESS read-only
      STATUS     current
      DESCRIPTION
          "The new time resolution computed after the synchronization
          event occurred."
      ::= { ippmSynchronizationEntry 4 }








   ippmPointOfMeasureTable OBJECT-TYPE
      SYNTAX     SEQUENCE OF IppmPointOfMeasureEntry
      MAX-ACCESS not-accessible
      STATUS     current


      DESCRIPTION
          " This table is the list of measurement end points available
          in the measurement system.


          Proxy mode:
          It is the list of the measurement end points of the set of
          probes for which the IPPM agent provides an SNMP interface.


          IPPM MIB implemented in a probe:
          It is the list of the measurement end points of the probe.


          The ippmPointOfMeasureTable content is read only. This
          implies that the measurement software handles the table
          internally ippmPointOfMeasureTable is mandatory."
      ::= { ippmSystem 8 }


   ippmPointOfMeasureEntry OBJECT-TYPE
      SYNTAX     IppmPointOfMeasureEntry
      MAX-ACCESS not-accessible
      STATUS     current
      DESCRIPTION
          " An entry may be the management address of some middleware in
          charge of the management of a set of probes. It may the
          management address of a probe that contains several line
          cards.


          An entry describes the capability of a point of measure.


          ippmPointOfMeasureMetrics lists the metrics handles by the
          point of measure."
      INDEX { ippmPointOfMeasureIndex }
      ::= { ippmPointOfMeasureTable 1 }


   IppmPointOfMeasureEntry ::= SEQUENCE {
      ippmPointOfMeasureIndex                Unsigned32,
      ippmPointOfMeasureMgmtAddrType         InetAddressType,
      ippmPointOfMeasureMgmtAddress          InetAddress,
      ippmPointOfMeasureTestAddrType      InetAddressType,
      ippmPointOfMeasureTestAddress          InetAddress,
      ippmPointOfMeasureMetrics              IppmStandardMetrics
   }




   ippmPointOfMeasureIndex OBJECT-TYPE
      SYNTAX Unsigned32 (1 .. 65535)
      MAX-ACCESS not-accessible
      STATUS     current
      DESCRIPTION
          "A local index that identifies an entry in the point of
          measure table."


      ::= { ippmPointOfMeasureEntry 1 }


   ippmPointOfMeasureMgmtAddrType OBJECT-TYPE
      SYNTAX InetAddressType
      MAX-ACCESS read-only
      STATUS     current
      DESCRIPTION
          "The address type associated with the management address."
      ::= { ippmPointOfMeasureEntry 2 }

   ippmPointOfMeasureMgmtAddress OBJECT-TYPE
      SYNTAX InetAddress  (SIZE  (1..128))
      MAX-ACCESS read-only
      STATUS     current
      DESCRIPTION
          "The management address on the point of measure"
      ::= { ippmPointOfMeasureEntry 3 }



   ippmPointOfMeasureTestAddrType OBJECT-TYPE
      SYNTAX InetAddressType
      MAX-ACCESS read-only
      STATUS     current
      DESCRIPTION
          "Defines the address type of the measurement interface of the
          point of measure."
      ::= { ippmPointOfMeasureEntry 4 }


   ippmPointOfMeasureTestAddress OBJECT-TYPE
      SYNTAX InetAddress
      MAX-ACCESS read-only
      STATUS     current
      DESCRIPTION
          "Specifies the address of the measurement interface for the
          point of measure."
      ::= { ippmPointOfMeasureEntry 5}


   ippmPointOfMeasureMetrics OBJECT-TYPE
      SYNTAX     IppmStandardMetrics
      MAX-ACCESS read-only
      STATUS     current
      DESCRIPTION
          " ippmPointOfMeasureMetrics lists the metrics this point of
          measure implements."
      ::= { ippmPointOfMeasureEntry 6 }







   ippmMetricsTable OBJECT-TYPE
      SYNTAX     SEQUENCE OF IppmMetricsEntry
      MAX-ACCESS not-accessible


      STATUS     current
      DESCRIPTION
          "This table is mandatory. It describes the current
          implementation. Each IPPM standardized metric must be
          described in the table.
          ippmMetricsTable content is read only."
      ::= { ippmSystem 9 }


   ippmMetricsEntry OBJECT-TYPE
      SYNTAX     IppmMetricsEntry
      MAX-ACCESS not-accessible
      STATUS     current
      DESCRIPTION
          "An entry describes the static capabilities of a metric
          implementation."
      INDEX { ippmMetricsIndex }
      ::= { ippmMetricsTable 1 }


   IppmMetricsEntry ::=
   SEQUENCE {
      ippmMetricsIndex           IppmMetricsRegistryIndex,
      ippmMetricsType            INTEGER,
      ippmMetricsUnit            INTEGER,
      ippmMetricsDescription     SnmpAdminString
   }


   ippmMetricsIndex OBJECT-TYPE
      SYNTAX IppmMetricsRegistryIndex
      MAX-ACCESS not-accessible
      STATUS     current
      DESCRIPTION
          "ippmMetricsIndex defines an unambiguous index for each
          standardized metric. It identifies a metric, and as such its
          value is the value of the node of the metric in the IPPM
          registry. This value is the same in any implementation of the
          IPPM REPORTING MIB.


          Example:
          In the IPPM-METRICS-REGISTRY, onewayPacketLossAverage is
          registered as the node 14 of ippmMetricsRegistry.metrics.rfc.
          Consequently the index of the metric onewayPacketLossAverage
          in the IppmMetricsTable will always be '14'"
      ::= { ippmMetricsEntry 1 }



   ippmMetricsType OBJECT-TYPE
      SYNTAX INTEGER {
      network(0),
      aggregated(1)
      }
      MAX-ACCESS read-only
      STATUS     current
      DESCRIPTION
          "Indicates the metric type, whether it is network or
          aggregated."
      ::= { ippmMetricsEntry 2 }



   ippmMetricsUnit OBJECT-TYPE
      SYNTAX INTEGER {
           noUnit(0),
           second(1),
           millisecond(2),
           microsecond(3),
           nanosecond(4),
           percentage(5),
           packet(6),
           byte(7),
           kilobyte(8),
           megabyte(9)
           }
      MAX-ACCESS read-only
      STATUS     current
      DESCRIPTION
          "The unit used in the current entity for the results of the
          measurement of this metric."
      ::= { ippmMetricsEntry 3 }


   ippmMetricsDescription OBJECT-TYPE
      SYNTAX SnmpAdminString
      MAX-ACCESS read-only
      STATUS     current
      DESCRIPTION
          "A textual description of the metric implementation following
          the exact name of this metric in the registry. For example:
          oneWayDelay: OWD Metric ."
      ::= { ippmMetricsEntry 4 }








   --
   -- ippmOwners Group
   --
   -- The ippmOwners objects are responsible for managing
   -- the owners access to the measurements.
   --
   --


   ippmOwnersTable OBJECT-TYPE
      SYNTAX     SEQUENCE OF IppmOwnersEntry
      MAX-ACCESS not-accessible
      STATUS     current
      DESCRIPTION
   "A management entity wishing to access or aggregate remote Ippm
   measurements in an agent must previously be registered in the
   ippmOwnersTable. This table is read-create and contains at least  the
   owner 'monitor'."


      ::= { ippmOwners 1 }


   ippmOwnersEntry OBJECT-TYPE
      SYNTAX     IppmOwnersEntry
      MAX-ACCESS not-accessible
      STATUS     current
      DESCRIPTION
          "The description of the resources granted to an SNMP
          application.


          For example, an instance of ippmOwnersOwner with an
          IppmOwnerString 'acme', which represents the 14th owner
          created in ippmOwnersTable would be named
          ippmOwnersEntryOwner.14.
          "
      INDEX { ippmOwnersOwner }
      ::= { ippmOwnersTable 1 }


   IppmOwnersEntry ::= SEQUENCE {
      ippmOwnersOwner              IppmOwnerString,
      ippmOwnersGrantedMetrics     IppmStandardMetrics,
      ippmOwnersQuota              Unsigned32,
      ippmOwnersIpAddressType      InetAddressType,
      ippmOwnersIpAddress          InetAddress,
      ippmOwnersEmail              SnmpAdminString,
      ippmOwnersStatus             RowStatus
   }


   ippmOwnersOwner OBJECT-TYPE
      SYNTAX     IppmOwnerString
      MAX-ACCESS not-accessible
      STATUS     current
      DESCRIPTION
          "The owner described by this entry."
      ::= { ippmOwnersEntry 1 }

   ippmOwnersGrantedMetrics OBJECT-TYPE
      SYNTAX     IppmStandardMetrics
      MAX-ACCESS read-create
      STATUS     current
      DESCRIPTION
          " Defines the metrics granted to an owner for which
          measurements can be performed."
      ::= { ippmOwnersEntry 2 }


   ippmOwnersQuota OBJECT-TYPE
      SYNTAX     Unsigned32
      MAX-ACCESS read-create
      STATUS     current
      DESCRIPTION
          "The maximum number of records that this owner may have in the
          history table and in the report table."
      ::= { ippmOwnersEntry 3 }



   ippmOwnersIpAddressType OBJECT-TYPE
      SYNTAX     InetAddressType
      MAX-ACCESS read-create
      STATUS     current
      DESCRIPTION
          "The IP address type of the management entity corresponding to
          this owner.
           InetAddressType is restricted to ipv4(1),ipv6(2)and dns(16)."
      ::= { ippmOwnersEntry 4 }


   ippmOwnersIpAddress OBJECT-TYPE
      SYNTAX     InetAddress  (SIZE  (1..128))
      MAX-ACCESS read-create
      STATUS     current
      DESCRIPTION
          "The IP address of the management entity corresponding to this
          owner. For example, the IP address of the management console
          used to send SNMP requests."
      ::= { ippmOwnersEntry 5 }


   ippmOwnersEmail OBJECT-TYPE
      SYNTAX     SnmpAdminString
      MAX-ACCESS read-create
      STATUS     current
      DESCRIPTION
          "The email address of the management entity corresponding to
          this owner."
      ::= { ippmOwnersEntry 6 }

   ippmOwnersStatus OBJECT-TYPE
      SYNTAX     RowStatus
      MAX-ACCESS read-create
      STATUS     current
      DESCRIPTION
          "The status of this table entry. Once this status is set to
          active, the corresponding entry in the table may not be
          modified."
      ::= { ippmOwnersEntry 7 }






   --
   -- ippmHistory Group
   --
   --
   -- ippmHistoryTable
   --


   ippmHistoryTable OBJECT-TYPE
      SYNTAX     SEQUENCE OF IppmHistoryEntry
      MAX-ACCESS not-accessible


      STATUS     current
      DESCRIPTION
          "The table containing the measurement results."
      ::= { ippmHistory 1 }



   ippmHistoryEntry OBJECT-TYPE
      SYNTAX     IppmHistoryEntry
      MAX-ACCESS not-accessible
      STATUS     current
      DESCRIPTION
         "An ippmHistoryEntry entry is one of the results of a measure
         identified by ippmHistoryMeasureOwner, ippmHistoryMeasureIndex,
         ippmHistoryMetricIndex and ippmHistorySequence.


         In the index :


         + ippmHistoryMeasureOwner identifies the owner of the measure;


         + ippmHistoryMeasureIndex identifies the measure in the owner
         namespace;


         + ippmHistoryMetricIndex identifies the metric measured by the
         measure. The metric is described in the corresponding entry of
         the  ippmMetricsTable;


         + ippmHistorySequence is the sequence number of the measurement
         result for an entry in the history table."
      INDEX { ippmHistoryMeasureOwner, ippmHistoryMeasureIndex,
      ippmHistoryMetricIndex, ippmHistorySequence }
      ::= { ippmHistoryTable 1 }


   IppmHistoryEntry ::=
      SEQUENCE {
          ippmHistoryMeasureOwner      IppmOwnerString,
          ippmHistoryMeasureIndex      IppmOwnerIndex,
          ippmHistoryMetricIndex       IppmMetricsRegistryIndex,
          ippmHistorySequence          Unsigned32,
          ippmHistoryTimestamp         GMTTimeStamp,
          ippmHistoryValue             Integer32
      }


   ippmHistoryMeasureOwner OBJECT-TYPE
      SYNTAX     IppmOwnerString
      MAX-ACCESS not-accessible
      STATUS     current
      DESCRIPTION
          "The owner of the measure that produced this result. The
          measure is either an ippmNetMeasure or an ippmAggrMeasure."
      ::= { ippmHistoryEntry 1 }



   ippmHistoryMeasureIndex OBJECT-TYPE
      SYNTAX IppmOwnerIndex
      MAX-ACCESS not-accessible
      STATUS     current
      DESCRIPTION
          "The owner index of the measure that produced this result. The
          measure is either an entry of the ippmNetMeasureTable or of
          the ippmAggrMeasureTable."
      ::= { ippmHistoryEntry 2 }


   ippmHistoryMetricIndex OBJECT-TYPE
      SYNTAX IppmMetricsRegistryIndex
      MAX-ACCESS not-accessible
      STATUS     current
      DESCRIPTION
          " ippmHistoryMetricIndex identifies the metric measured by the
          measure. The metric is described in the corresponding entry of
          the ippmMetricsTable."
      ::= { ippmHistoryEntry 3 }

   ippmHistorySequence OBJECT-TYPE
      SYNTAX Unsigned32 (0..4294967295)
      MAX-ACCESS not-accessible
          STATUS     current
          DESCRIPTION
          "ippmHistorySequence is the sequence number of the measurement
          results for a metric.


          Network metrics:
          It's the sequence number of a measurement packet. Typically,
          it identifies the order of the packet in the stream of packets
          sent by the source.


          Aggregated metrics:
          It is the sequence order of the aggregation computed."
      ::= { ippmHistoryEntry 4 }




   ippmHistoryTimestamp OBJECT-TYPE
      SYNTAX GMTTimeStamp
      MAX-ACCESS read-only
      STATUS     current
      DESCRIPTION
          "The timestamp when the measurement occurred."
      ::= { ippmHistoryEntry 5 }


   ippmHistoryValue OBJECT-TYPE
      SYNTAX Integer32


      MAX-ACCESS read-only
      STATUS     current
      DESCRIPTION
          "The observed value of the measurement."
      ::= { ippmHistoryEntry 6 }


   ippmHistoryPathToResults   OBJECT-TYPE
      SYNTAX SnmpAdminString
      MAX-ACCESS read-only
      STATUS     current
      DESCRIPTION
          "It is typically an URL describing the file location where
          bulk results are logged."
      ::= { ippmHistory 2 }

   --
   -- ippmNetMeasure Group
   --



   --
   -- ippmNetMeasureTable
   --
   --


   ippmNetMeasureTable OBJECT-TYPE
      SYNTAX     SEQUENCE OF IppmNetMeasureEntry
      MAX-ACCESS not-accessible
      STATUS     current
      DESCRIPTION
          "An entry is a measurement that performs network measures and
          provides results.
          It performs several metric measurements per packet exchange.
          Each step of a measure produces a singleton result per metric.
          The time of the measurement and the value of the metric are
          saved in the ippmHistoryTable."
      ::= { ippmNetMeasure 1 }


   ippmNetMeasureEntry OBJECT-TYPE
      SYNTAX     IppmNetMeasureEntry
      MAX-ACCESS not-accessible
      STATUS     current
      DESCRIPTION
         " The IppmNetMeasureTable is mandatory, and its content is read
         only. It means that the measurement software handles the table
         internally. The setup of the network measure is not permitted
         through the IPPM REPORTING MIB. As an example, OWAP provides a
         setup protocol to setup and tear down networks measures.


         The ippmNetMeasureMetrics is set to a list of metrics to be
         computed from the same raw packet exchange. Each step of
         measurement delivers a singleton per metric. Results are
         timestamped and saved in the ippmHistoryTable.


         One may create aggregated measures by using the results of
         network measures."


      INDEX { ippmNetMeasureOwner, ippmNetMeasureIndex }
      ::= { ippmNetMeasureTable 1 }


   IppmNetMeasureEntry ::= SEQUENCE {
      ippmNetMeasureOwner               IppmOwnerString,
      ippmNetMeasureIndex               IppmOwnerIndex,
      ippmNetMeasureName                SnmpAdminString,
      ippmNetMeasureMetrics             IppmStandardMetrics,
      ippmNetMeasureBeginTime           GMTTimeStamp,
      ippmNetMeasureCollectionRateUnit  TimeUnit,
      ippmNetMeasureCollectionRate      Unsigned32,
      ippmNetMeasureDurationUnit        TimeUnit,
      ippmNetMeasureDuration            Unsigned32,
      ippmNetMeasureHistorySize         Unsigned32,
      ippmNetMeasureFailureMgmtMode     INTEGER,
      ippmNetMeasureResultsMgmt         INTEGER,
      ippmNetMeasureSrcPacketType       PacketType,
      ippmNetMeasureSrc                 PacketTypeAddress,
      ippmNetMeasureDstPacketType       PacketType,
      ippmNetMeasureDst                 PacketTypeAddress,
      ippmNetMeasureTxMode              INTEGER,
      ippmNetMeasureTxPacketRateUnit    TimeUnit,
      ippmNetMeasureTxPacketRate        Unsigned32,
      ippmNetMeasureMedOrBurstSize      Unsigned32,
      ippmNetMeasureDevOrIntBurstSize   Unsigned32,
      ippmNetMeasureLossTimeout         Unsigned32,
      ippmNetMeasureL3PacketSize        Unsigned32,
      ippmNetMeasureDataPattern         OCTET STRING,
      ippmNetMeasureTotalPktsRecv       Counter64,
      ippmNetMeasureLastUpdate          GMTTimeStamp,
      ippmNetMeasureOperState           INTEGER
   }








   ippmNetMeasureOwner OBJECT-TYPE
      SYNTAX     IppmOwnerString
      MAX-ACCESS not-accessible
      STATUS     current
      DESCRIPTION
          "The owner of the network measure."
      ::= { ippmNetMeasureEntry 1 }


   ippmNetMeasureIndex OBJECT-TYPE
      SYNTAX IppmOwnerIndex
      MAX-ACCESS not-accessible
      STATUS     current
      DESCRIPTION
          "The owner index of the network measure."
      ::= { ippmNetMeasureEntry 2 }

   ippmNetMeasureName OBJECT-TYPE
      SYNTAX SnmpAdminString
      MAX-ACCESS read-create
      STATUS     current
      DESCRIPTION
          "The name of the metric instance(s) as defined in
          ippmNetMeasureMetrics. It illustrates the specificity of the
          metric(s) and includes the metric(s) and the PacketType.


          Example:
          IP-TCP-HTTP-One-way-Delay: free text "
      ::= { ippmNetMeasureEntry 3 }




   ippmNetMeasureMetrics OBJECT-TYPE
      SYNTAX IppmStandardMetrics
      MAX-ACCESS read-create
      STATUS     current
      DESCRIPTION
          "ippmNetMeasureMetrics defines the metrics to compute within
          this measure. Only network metrics of the same type are
          allowed in this field (e.g. poisson-based metrics and
          periodic-based metrics are incompatibles, while one-way delay
          and packet loss are generally processed simultaneously: a very
           bad delay is potentially a very good packet loss).


          Results are saved in the ippmHistoryTable.


          Results of a metric are identified using an index of type
          IppmMetricsRegistryIndex.


          Example:
          Given a multi-metrics measure of One-way-Delay(6) and One-way-
          Packet-Loss(12). The value of the field ippmNetMeasureMetrics
          is '0001000001000000'b, '1040'B. Results are logged in the
          ippmHistoryTable where One-way-Delay singletons have a value
          of ippmMetricsIndex of 6 while One-way-Packet-Loss singletons
          have a value of ippmMetricsIndex of 12.


          "
      ::= { ippmNetMeasureEntry 4 }


   ippmNetMeasureBeginTime OBJECT-TYPE
      SYNTAX GMTTimeStamp
      MAX-ACCESS read-create
      STATUS     current
      DESCRIPTION
          "Specifies the time at which the measurement begins."
      ::= { ippmNetMeasureEntry 5 }



   ippmNetMeasureCollectionRateUnit OBJECT-TYPE
      SYNTAX TimeUnit
      MAX-ACCESS read-create
      STATUS     current
      DESCRIPTION
          "Specifies the unit of the measurement period."
      ::= { ippmNetMeasureEntry 6 }


   ippmNetMeasureCollectionRate OBJECT-TYPE
      SYNTAX     Unsigned32
      MAX-ACCESS read-create
      STATUS     current
      DESCRIPTION
           "Gives the period used to collect singletons from the point
           of measures. This value is used as the cycle period in the
           report."
      ::= { ippmNetMeasureEntry 7 }



   ippmNetMeasureDurationUnit OBJECT-TYPE
      SYNTAX TimeUnit
      MAX-ACCESS read-create
      STATUS     current
      DESCRIPTION
          "Specifies the measurement duration unit."
      ::= { ippmNetMeasureEntry 8 }


   ippmNetMeasureDuration OBJECT-TYPE
      SYNTAX     Unsigned32
      MAX-ACCESS read-create
      STATUS     current
      DESCRIPTION
          "Specifies the measurement duration."
      ::= { ippmNetMeasureEntry 9 }


   ippmNetMeasureHistorySize OBJECT-TYPE
      SYNTAX     Unsigned32
      MAX-ACCESS read-create
      STATUS     current
      DESCRIPTION
          "Specifies the maximum number of results saved for each metric
          of this measure.
          Overflow condition will be managed by the object
          ippmNetMeasureResultsMgmt. "


      ::= { ippmNetMeasureEntry 10 }



   ippmNetMeasureFailureMgmtMode OBJECT-TYPE
      SYNTAX     INTEGER {
          auto(1),
          manual(2),
          discarded(3)
      }
      MAX-ACCESS  read-create
      STATUS      current
      DESCRIPTION
          "This object defines whether this row (and the measure
          controlled by this row) is restarted automatically, manually,
          or discarded upon failure, or reboot of the measurement
           system:
            'auto'
               The measure is restarted automatically.
            'manual'
               The measure has to be restarted manually.
            'discarded'
               The measure and it results are discarded.
          "
      ::= { ippmNetMeasureEntry 11 }


   ippmNetMeasureResultsMgmt OBJECT-TYPE
      SYNTAX INTEGER {
          wrap(1),
          suspend(2)
      }
      MAX-ACCESS read-create
      STATUS     current
      DESCRIPTION
          "
          Action to take when the log is full. The measurement system
          owner may choose to either wrap, in which case the agent
          writes over existing records. The user may choose to suspend
          writing to the log in the event that he wishes to archive the
          data. The resume action causes the agent to begin to write in
          the log, and assumes the data has been cleared.
          This object indicates the way the measurement results are
          managed when the owner quota has been exceeded:
            'wrap'
               continue the measurement and erase the older entries in
               the history.
            'suspend'
               stop the measure and keep the results in the history.
          "
      ::= { ippmNetMeasureEntry 12 }


   ippmNetMeasureSrcPacketType OBJECT-TYPE
      SYNTAX PacketType
      MAX-ACCESS read-create
      STATUS     current
      DESCRIPTION
          "Defines the type P of the source address of the packets sent
          by the measure."
      ::= { ippmNetMeasureEntry 13 }


   ippmNetMeasureSrc OBJECT-TYPE
      SYNTAX PacketTypeAddress
      MAX-ACCESS read-create
      STATUS     current
      DESCRIPTION
          "Specifies the address of the source of the measure.
          It is represented as a list of parameters corresponding to
          those of the PROTOCOL IDENTIFIER set in
          ippmNetMeasureSrcPacketType."
      ::= { ippmNetMeasureEntry 14}


   ippmNetMeasureDstPacketType OBJECT-TYPE
      SYNTAX PacketType
      MAX-ACCESS read-create
      STATUS     current
      DESCRIPTION
          "Defines the type P of the destination address of the packets
          sent by the measure."
      ::= { ippmNetMeasureEntry 15 }



   ippmNetMeasureDst OBJECT-TYPE
      SYNTAX PacketTypeAddress
      MAX-ACCESS read-create
      STATUS     current
      DESCRIPTION
          "Specifies the address of the destination of the measure.
          It is represented as a list of parameters corresponding to
          those of the PROTOCOL IDENTIFIER set in
          ippmNetMeasureDstPacketType."
      ::= { ippmNetMeasureEntry 16 }


   ippmNetMeasureTxMode OBJECT-TYPE
      SYNTAX INTEGER {
          other(0),
          periodic(1),
          poisson(2),
          multiburst(3)
             }
      MAX-ACCESS read-create
      STATUS     current
      DESCRIPTION
          "The transmit mode used to send the packets:


          'other'
             The rule used to send the packets is unknown.
          'periodic'
             Packets are sent periodically at ippmNetMeasureTxPacketRate
               rate.
          'poisson'
             Packets are sent using a Poisson law, the median is the
             value of ippmNetMeasureDevOrIntBurstSize, the deviation is
             ippmNetMeasureMedOrBurstSize.
          'multiburst'
             Packets are sent bursty at ippmNetMeasureTxPacketRate. The
             size of the burst is made of ippmNetMeasureMedOrBurstSize
             packets.
             Between 2 consecutive bursts, transmission stops during the
             time needed to send ippmNetMeasureDevOrIntBurstSize.


          "
      ::= { ippmNetMeasureEntry 17 }


   ippmNetMeasureTxPacketRateUnit      OBJECT-TYPE
      SYNTAX TimeUnit
      MAX-ACCESS read-create
      STATUS     current
      DESCRIPTION
          "The packet rate unit used to send the packets."
      ::= { ippmNetMeasureEntry 18 }


   ippmNetMeasureTxPacketRate OBJECT-TYPE
      SYNTAX Unsigned32
      UNITS "Packets"
      MAX-ACCESS read-create
      STATUS     current
      DESCRIPTION
          "The rate the packets are sent."
      ::= { ippmNetMeasureEntry 19 }


   ippmNetMeasureMedOrBurstSize   OBJECT-TYPE
      SYNTAX     Unsigned32
      UNITS "Packets"
      MAX-ACCESS read-create
      STATUS     current
      DESCRIPTION
          "
          Multi-burst mode: This field represents the burst size in
          number of packets.
          Poisson mode: This field indicates the number of packets sent,
          on average, during each period corresponding to the median.
          The median is therefore
          MedOrBurstSize*TxPacketRateUnit/TxPacketRate.


          Example:
          If  TxPacketRateUnit/TxPacketRate is 100 packets/second, and
          if MedOrBurstSize, the number of packets sent during the
          period corresponding to the median is 50 packets, then the
          median equals 50*1/100 = 1/2 seconds.
          "
      ::= { ippmNetMeasureEntry 20 }



   ippmNetMeasureDevOrIntBurstSize   OBJECT-TYPE
      SYNTAX     Unsigned32
      UNITS "Packets"
      MAX-ACCESS read-create
      STATUS     current
      DESCRIPTION
          "
          Multi-burst mode: This field indicates the gap between 2
          bursts, in number of packets.
          Example:
          If TxPacketRateUnit/TxPacketRate is 100 packets/second,
          and DevOrIntBurstSize equals 50 packets, then the gap between
          2 bursts is equal to 50*1/100, or 1/2 second.


          Poisson mode:
          This field indicates the typical difference between the
          packets of the period corresponding to the median.


          "
      ::= { ippmNetMeasureEntry 21 }



   ippmNetMeasureLossTimeout OBJECT-TYPE
      SYNTAX     Unsigned32
      UNITS      "Milliseconds"
      MAX-ACCESS read-create
      STATUS     current
      DESCRIPTION
          "Specifies the delay after which the packet is considered
          lost by the sink."
      ::= { ippmNetMeasureEntry 22 }



   ippmNetMeasureL3PacketSize OBJECT-TYPE
      SYNTAX     Unsigned32
      UNITS      "Bytes"
      MAX-ACCESS read-create
      STATUS     current
      DESCRIPTION
          "Specifies the size of the packets counted at the IP network
          layer in regards to the PacketType definition.
          Example: For a PacketType 'ip ipip4' the L3 size will be the
          size of the packet at ipip4 level.
          "
      ::= { ippmNetMeasureEntry 23 }


   ippmNetMeasureDataPattern OBJECT-TYPE


      SYNTAX     OCTET STRING
      MAX-ACCESS read-create
      STATUS     current
      DESCRIPTION
          "The pattern used to fill the payload of the packet."


      ::= { ippmNetMeasureEntry 24 }



   ippmNetMeasureTotalPktsRecv  OBJECT-TYPE
      SYNTAX Counter64
      UNITS "Packets"
      MAX-ACCESS read-only
      STATUS     current
      DESCRIPTION
          "Reports the current number of packets received since the
          beginning of the measure.
          This parameters is useful to monitor the measure and it is
          needed to compute statistics."
      ::= { ippmNetMeasureEntry 25 }



   ippmNetMeasureLastUpdate OBJECT-TYPE
   SYNTAX GMTTimeStamp
      MAX-ACCESS read-only
      STATUS     current
      DESCRIPTION
          "The time when the last aggregation was computed."
      ::= { ippmNetMeasureEntry 26 }



   ippmNetMeasureOperState OBJECT-TYPE
      SYNTAX INTEGER {
          unknown(0),
          running(1),
          stopped(2)
      }
      MAX-ACCESS read-only
      STATUS     current
      DESCRIPTION
          "Reports the operational status of the network measure."
      ::= { ippmNetMeasureEntry 27 }







   --
   --
   -- ippmAggrMeasure Group
   --
   --


   --




   --
   -- ippmAggrMeasureTable
   --
   --


   ippmAggrMeasureTable OBJECT-TYPE
      SYNTAX     SEQUENCE OF IppmAggrMeasureEntry
      MAX-ACCESS not-accessible
      STATUS     current
      DESCRIPTION
          "An aggregated measure summarizes the results of previous
          network or aggregated measures. The results are saved in the
          ippmHistoryTable.
          Each step of the calculation for the measure produces a
          singleton result per metric."
      ::= { ippmAggrMeasure 1 }


   ippmAggrMeasureEntry OBJECT-TYPE
      SYNTAX     IppmAggrMeasureEntry
      MAX-ACCESS not-accessible
      STATUS     current
      DESCRIPTION
          "Typically, the configuration operation creates and sets the
          value of the fields of a new ippmAggrMeasureEntry.
          ippmAggrMeasureOwner and ippmAggrMeasureIndex identify the
          instance created.
          The field ippmAggrMeasureMetrics identifies the metric to
          compute. As such its ippmMetricsType should be 'aggregated'.


          The measure aggregates the results of a measure identified by
          ippmAggrMeasureHistoryOwner, ippmAggrMeasureHistoryIndex and
          ippmAggrMeasureHistoryMetric. The measure to aggregate belongs
          to ippmNetMeasureTable or ippmAggrMeasureTable.


          The aggregation starts at ippmAggrMeasureBeginTime and ends
          after ippmAggrMeasureDuration.


          An aggregated result is computed for each
          ippmMeasureCollectionRate tick and saved in the
          ippmHistoryTable."
      INDEX { ippmAggrMeasureOwner, ippmAggrMeasureIndex }
      ::= { ippmAggrMeasureTable 1 }



   IppmAggrMeasureEntry ::= SEQUENCE {
      ippmAggrMeasureOwner                  IppmOwnerString,
      ippmAggrMeasureIndex                  IppmOwnerIndex,
      ippmAggrMeasureName                   SnmpAdminString,
      ippmAggrMeasureMetrics                IppmStandardMetrics,
      ippmAggrMeasureHistoryOwner           IppmOwnerString,
      ippmAggrMeasureHistoryIndex           IppmOwnerIndex,
      ippmAggrMeasureHistoryMetric          IppmMetricsRegistryIndex,
      ippmAggrMeasureFilter                 IppmMetricResultFilter,
      ippmAggrMeasureLowThreshold           Unsigned32,
      ippmAggrMeasureHighThreshold          Unsigned32,
      ippmAggrMeasureBeginTime              GMTTimeStamp,
      ippmAggrMeasureAggrPeriodUnit         TimeUnit,
      ippmAggrMeasureAggrPeriod             Unsigned32,
      ippmAggrMeasureDurationUnit           TimeUnit,
      ippmAggrMeasureDuration               Unsigned32,
      ippmAggrMeasureHistorySize            Unsigned32,
      ippmAggrMeasureStorageType            StorageType,
      ippmAggrMeasureAdminState             INTEGER,
      ippmAggrMeasureFastReport             OBJECT IDENTIFIER,
      ippmAggrMeasureResultsMgmt            INTEGER,
      ippmAggrMeasureLastUpdate             GMTTimeStamp,
      ippmAggrMeasureOperState              INTEGER,
      ippmAggrMeasureNbPktsTreated          Counter64,
      ippmAggrMeasureStatus                 RowStatus
   }


   ippmAggrMeasureOwner OBJECT-TYPE
      SYNTAX     IppmOwnerString
      MAX-ACCESS not-accessible
      STATUS     current
      DESCRIPTION
          "The owner who has configured this entry."
      ::= { ippmAggrMeasureEntry 1 }


   ippmAggrMeasureIndex OBJECT-TYPE
      SYNTAX IppmOwnerIndex
      MAX-ACCESS not-accessible
      STATUS     current
      DESCRIPTION
          "The index of the aggregated measure. The value is managed by
          the owner."
      ::= { ippmAggrMeasureEntry 2 }


   ippmAggrMeasureName OBJECT-TYPE
      SYNTAX SnmpAdminString
      MAX-ACCESS read-create
      STATUS     current
      DESCRIPTION
          "The name of the instance of the metric. It illustrates the
          specificity of the metric and includes the metric and the
          typeP.


          example: IP-port-HTTP-connectivity: free text."
      ::= { ippmAggrMeasureEntry 3 }



   ippmAggrMeasureMetrics OBJECT-TYPE
      SYNTAX IppmStandardMetrics


      MAX-ACCESS read-create
      STATUS     current
      DESCRIPTION
          "ippmAggrMeasureMetrics defines the metrics to compute within
          this aggregated measure.


          Only aggregated metrics of the same type are allowed in this
          field (e.g. Measurement of minimum, average and maximum
          metrics are generally processed simultaneously on the same
          network measure).
          Results are saved in the ippmHistoryTable.


          Results of a metric are identified using an index of type
          IppmMetricsRegistryIndex.


          Example:
          Given a multi-aggregation of One-way-Delay-Median(9) and
          One-way-Delay-Minimum(10). The value of the field
          ippmAggrMeasureMetrics is '0000011000000000'b, '0600'B.


          Results are logged in the ippmHistoryTable where
          One-way-Delay-Median singletons have a value of
          ippmMetricsIndex of 9 while One-way-Delay-Minimum singletons
          have a value of ippmMetricsIndex of 10.


          NOTE WELL: It is not recommended to use the multi aggregation
          capability in conjunction with the filter feature.
      "
      ::= { ippmAggrMeasureEntry 4 }



   ippmAggrMeasureHistoryOwner OBJECT-TYPE
      SYNTAX IppmOwnerString
      MAX-ACCESS read-create
      STATUS     current
      DESCRIPTION
          "The owner of the measure to summarize. "
      ::= { ippmAggrMeasureEntry 5 }


   ippmAggrMeasureHistoryIndex OBJECT-TYPE
      SYNTAX IppmOwnerIndex
      MAX-ACCESS read-create
      STATUS     current
      DESCRIPTION
          "The owner index of the measure to summarize. "
      ::= { ippmAggrMeasureEntry 6 }


   ippmAggrMeasureHistoryMetric OBJECT-TYPE
      SYNTAX IppmMetricsRegistryIndex
      MAX-ACCESS read-create
      STATUS     current
      DESCRIPTION
          "The metric of the measure to summarize. "
      ::= { ippmAggrMeasureEntry 7 }




   ippmAggrMeasureFilter OBJECT-TYPE
      SYNTAX IppmMetricResultFilter
      MAX-ACCESS read-create
      STATUS     current
      DESCRIPTION
          "
          ippmAggrMeasureFilter defines the kind of filter to apply on a
          result to determine if the result is stored or not. The
          parameters of the filter are ippmAggrMeasureLowThreshold and
          ippmAggrMeasureHighThreshold.


          Thresholds have the same unit as the metric value.


          In the following examples we consider an aggregated measure.
          Its low threshold is set to 80.its high threshold is set to
          100. The aggregation produced a flow of 12 aggregated results
          {40 30 60 85 140 130 190 95 50 90 30 20}.


          If the filter is set to 'logInBandValue' then the results 85,
          95, 90 will be stored.


          If the filter is set to 'logOutBandValue' then the results 40
          30 60 140 130 190 50 30 20 will be stored.


          If the filter is set to 'logAboveValue' then the results 140
          130 190 will be stored.


          If the filter is set to 'logBelowValue' then the results 40 30
           60 50 30 20 will be stored.


          If the filter is set to 'logUpAndDownValue' then the results
          40, 140, 50 will be stored."
      ::= { ippmAggrMeasureEntry 8 }



   ippmAggrMeasureLowThreshold OBJECT-TYPE
      SYNTAX Unsigned32
      MAX-ACCESS read-create
      STATUS     current
      DESCRIPTION
          "An event is generated when the result of the measure of the
          metric is lower that the value of ippmAggrMeasureLowThreshold.
          The threshold has the same unit as the metric. The metric unit
          is recorded in the object ippmMetricsUnit of this metric entry
          in the ippmMetricsTable.
          "
      ::= { ippmAggrMeasureEntry 9 }


   ippmAggrMeasureHighThreshold OBJECT-TYPE
      SYNTAX Unsigned32
      MAX-ACCESS read-create
      STATUS     current
      DESCRIPTION
          "An event is generated when the result of the measure of the
          metric exceeds the value of ippmAggrMeasureHighThreshold.
          The threshold has the same unit as the metric. The metric unit
          is recorded in the object ippmMetricsUnit of this metric entry
          in the ippmMetricsTable.
          "
      ::= { ippmAggrMeasureEntry 10 }


   ippmAggrMeasureBeginTime OBJECT-TYPE
      SYNTAX GMTTimeStamp
      MAX-ACCESS read-create
      STATUS     current
      DESCRIPTION
          "Specifies the time at which the aggregated measure starts."
      ::= { ippmAggrMeasureEntry 11 }



   ippmAggrMeasureAggrPeriodUnit OBJECT-TYPE
      SYNTAX TimeUnit
      MAX-ACCESS read-create
      STATUS     current
      DESCRIPTION
          "Specifies the unit of the aggregated measure period."
      DEFVAL { second }
      ::= { ippmAggrMeasureEntry 12 }


   ippmAggrMeasureAggrPeriod OBJECT-TYPE
      SYNTAX     Unsigned32
      MAX-ACCESS read-create
      STATUS     current
      DESCRIPTION
          "Specifies the amount of time between 2 measurement action
          intervals. The action is specific to the semantic of the
          measure.


          Network metrics:


          The ippmNetMeasureClockPattern transforms the flow of
          periodical instants as a flow of unpredictable instants of
          measurement packet emission.


          As the source and the sink share the definition of the clock
          of the measure, and as the sending timestamp is part of the
          measurement packet, the sink has the information to verify
          that the stream of packets generated by the source respects
          the clock law.


          Aggregated metrics:



          They are performed periodically on a sequence of results of
          other measures. The period corresponds to the interval between
          two successive computations of the metric. The value of
          ippmHistoryTimestamp result of a aggregated metric computed
          corresponds to the value of the ippmHistoryTimestamp of the
          last metric result of the sequence used to compute the
          aggregated metric."
      DEFVAL { 60 }


      ::= { ippmAggrMeasureEntry 13 }



   ippmAggrMeasureDurationUnit OBJECT-TYPE
      SYNTAX TimeUnit
      MAX-ACCESS read-create
      STATUS     current
      DESCRIPTION
          "Specifies the unit of the measure duration."
      DEFVAL { second }
      ::= { ippmAggrMeasureEntry 14 }


   ippmAggrMeasureDuration OBJECT-TYPE
      SYNTAX     Unsigned32
      MAX-ACCESS read-create
      STATUS     current
      DESCRIPTION
          "Specifies the duration of the measure."
      DEFVAL { 120 }
      ::= { ippmAggrMeasureEntry 15 }


   ippmAggrMeasureHistorySize OBJECT-TYPE
      SYNTAX     Unsigned32
      MAX-ACCESS read-create
      STATUS     current
      DESCRIPTION
          "Specifies the maximum number of results saved for each metric
          of this measure. Overflow condition will be managed by the
          object ippmAggrMeasureResultsMgmt. "
      DEFVAL { 2 }
      ::= { ippmAggrMeasureEntry 16 }


   ippmAggrMeasureStorageType OBJECT-TYPE
      SYNTAX     StorageType
      MAX-ACCESS  read-create
      STATUS      current
      DESCRIPTION
          "This object defines whether this row and the measure
          controlled by this row are kept in volatile storage and lost
           upon reboot or if this row is backed up
          by non-volatile or permanent storage.


          Possible values are: other(1), volatile(2), nonVolatile(3),
          permanent(4), readOnly(5)."
      DEFVAL { nonVolatile }
      ::= { ippmAggrMeasureEntry 17 }


   ippmAggrMeasureResultsMgmt OBJECT-TYPE
      SYNTAX INTEGER {
          wrap(1),
          suspend(2)
      }
      MAX-ACCESS read-only
      STATUS     current
      DESCRIPTION
          "This object displays the way the history of the aggregated
          measure is managed.
          'wrap'
             continue the measure and erase the older entries in the
          history.
          'suspend'
             stop the measure and keep the results in the history.
          "
      DEFVAL { wrap }
      ::= { ippmAggrMeasureEntry 18 }



   ippmAggrMeasureAdminState OBJECT-TYPE
      SYNTAX INTEGER {
          start(0),
          stop(1)
      }
      MAX-ACCESS read-create
      STATUS     current
      DESCRIPTION
          "This object controls the activity of the aggregated measure.
          'start'
             The aggregated measure is started.
          'stop'
             The aggregated measure is stopped."
      DEFVAL { start }
      ::= { ippmAggrMeasureEntry 19 }



   ippmAggrMeasureFastReport OBJECT-TYPE
      SYNTAX     OBJECT IDENTIFIER
      MAX-ACCESS read-create
      STATUS     current
      DESCRIPTION
          "A fast report is required in order to verify quickly that a
          measure is running well.
          'fast report' feature is active if ippmAggrMeasureFastReport
          is not null and points to a notification.
          A fast report consists of sending by email to the owner of the
          measure, a table of the results of all the metrics computed by
          this aggregated measure. The owner email address is read from
          the ippmOwnersTable.


          ippmAggrMeasureFastReport identifies the notification which
          defines the header of the report.


          The results part of the report is made of a column of results
          per metrics. Results are separated using commas.


          To avoid disaster, an aggregated measure using a fast report
          must have a cycle of aggregation greater than or equal to 1
          second and should not sent more than an email every 5 minutes
          and should not sent more than 12 emails."
      DEFVAL { zeroDotZero }
      ::= { ippmAggrMeasureEntry 20 }



   ippmAggrMeasureLastUpdate OBJECT-TYPE
   SYNTAX GMTTimeStamp
      MAX-ACCESS read-only
      STATUS     current
      DESCRIPTION
          "The time when the last aggregated measure was computed."
      ::= { ippmAggrMeasureEntry 21 }



   ippmAggrMeasureOperState OBJECT-TYPE
      SYNTAX INTEGER {
          unknown(0),
          running(1),
          stopped(2)
      }
      MAX-ACCESS read-only
      STATUS     current
      DESCRIPTION
          "Reports the operational status of the aggregated measure."
      ::= { ippmAggrMeasureEntry 22 }



   ippmAggrMeasureNbPktsTreated  OBJECT-TYPE
      SYNTAX Counter64
      UNITS  "Packets"
      MAX-ACCESS read-only
      STATUS     current
      DESCRIPTION
          "Reports the current number of packets used to calculate the
          aggregation since the start of the measure.


          This parameters is useful to monitor the measure and it is
          needed to compute statistics."
      ::= { ippmAggrMeasureEntry 23 }


   ippmAggrMeasureStatus OBJECT-TYPE
      SYNTAX     RowStatus
      MAX-ACCESS read-create
      STATUS     current
      DESCRIPTION
          "The status of this entry. Once the entry status is set to
          active, the associate entry cannot be modified.
          "
      ::= { ippmAggrMeasureEntry 24 }








   --
   -- IPPM  Notifications
   --



   ippmAggrMeasureReport    NOTIFICATION-TYPE
      OBJECTS      {
          ippmAggrMeasureFilter,
          ippmAggrMeasureLowThreshold,
          ippmAggrMeasureHighThreshold,
          ippmMetricsType,
          ippmMetricsUnit,
          ippmMetricsDescription,
          ippmHistoryTimestamp,
          ippmHistoryValue,
          ippmHistoryPathToResults
      }
      STATUS       current
      DESCRIPTION
          "A notification sent because the value of the measure is under
          the high threshold value and greater than the low threshold
          value.
          The notification contains the instances of the
          ippmHistoryValue object that exceeded the threshold.
          The notification contains the instances of the
          ippmHistoryTimestamp identifying the time the event occurred.
          ippmHistoryPathToResults is a link to the file name, which
          contains detailed results corresponding to this event."
      ::= { ippmNotifications 1 }




   ippmAggrMeasureHistoryFull    NOTIFICATION-TYPE
      OBJECTS      {
          ippmAggrMeasureName,


          ippmAggrMeasureHistorySize,
          ippmMetricsType,
          ippmMetricsUnit,
          ippmMetricsDescription,
          ippmHistoryTimestamp,
          ippmHistoryValue


      }
      STATUS       current
      DESCRIPTION
          "A notification sent when the size of the history of a metric
          of a aggregated measure exceeds ippmAggrMeasureHistorySize.
          The agent will then manage the reports according to the policy
          described in ippmAggrMeasureResultsMgmt."
      ::= { ippmNotifications 2 }


   ippmNetMeasureHistoryFull    NOTIFICATION-TYPE
      OBJECTS {
          ippmNetMeasureName,
          ippmNetMeasureHistorySize,
          ippmMetricsType,
          ippmMetricsUnit,
          ippmMetricsDescription,
          ippmHistoryTimestamp,
          ippmHistoryValue
      }
      STATUS       current
      DESCRIPTION
          "A notification sent when the size of the history of a metric
          of a network measure exceeded ippmNetMeasureHistorySize. Then
          the agent manages the records according to the policy
          described in ippmNetMeasureResultsMgmt."
      ::= { ippmNotifications 3 }







   --
   -- IPPM MIB Conformance statements
   --


   ippmCompliances OBJECT IDENTIFIER ::={ ippmConformance 1 }


   ippmGroups OBJECT IDENTIFIER ::={ ippmConformance 2 }







   ippmProxyInterDomainCompliances         MODULE-COMPLIANCE
      STATUS             current
      DESCRIPTION
          "The compliance statement for SNMP entities which implement
          the IPPM MIB as a proxy in interdomain. The implementation of
          the VACM control is mandatory."
      MODULE -- this module
      MANDATORY-GROUPS {


          ippmSystemGroup, ippmHistoryGroup, ippmNetMeasureGroup,
          ippmAggrMeasureGroup, ippmNotificationGroup
      }



      OBJECT   ippmNetMeasureName
      MIN-ACCESS read-only
      DESCRIPTION
         "In Proxy mode network measures may be managed using another
         interface than SNMP."


      OBJECT   ippmNetMeasureMetrics
      MIN-ACCESS read-only
      DESCRIPTION
         "In Proxy mode network measures may be managed using another
         interface than SNMP."


      OBJECT   ippmNetMeasureBeginTime
      MIN-ACCESS read-only
      DESCRIPTION
         "In Proxy mode network measures may be managed using another
         interface than SNMP."


      OBJECT   ippmNetMeasureCollectionRateUnit
      MIN-ACCESS read-only
      DESCRIPTION
         "In Proxy mode network measures may be managed using another
         interface than SNMP."


      OBJECT   ippmNetMeasureCollectionRate
      MIN-ACCESS read-only
      DESCRIPTION
         "In Proxy mode network measures may be managed using another
         interface than SNMP."


      OBJECT   ippmNetMeasureDurationUnit
      MIN-ACCESS read-only
      DESCRIPTION
         "In Proxy mode network measures may be managed using another
         interface than SNMP."


      OBJECT   ippmNetMeasureDuration
      MIN-ACCESS read-only
      DESCRIPTION
         "In Proxy mode network measures may be managed using another
         interface than SNMP."


      OBJECT   ippmNetMeasureHistorySize
      MIN-ACCESS read-only
      DESCRIPTION
         "In Proxy mode network measures may be managed using another
         interface than SNMP."


      OBJECT   ippmNetMeasureFailureMgmtMode
      MIN-ACCESS read-only
      DESCRIPTION
         "In Proxy mode network measures may be managed using another
         interface than SNMP."


      OBJECT   ippmNetMeasureResultsMgmt
      MIN-ACCESS read-only
      DESCRIPTION
         "In Proxy mode network measures may be managed using another
         interface than SNMP."


      OBJECT   ippmNetMeasureSrcPacketType
      MIN-ACCESS read-only
      DESCRIPTION
         "In Proxy mode network measures may be managed using another
         interface than SNMP."


      OBJECT   ippmNetMeasureSrc
      MIN-ACCESS read-only
      DESCRIPTION
         "In Proxy mode network measures may be managed using another
         interface than SNMP."


      OBJECT   ippmNetMeasureDstPacketType
      MIN-ACCESS read-only
      DESCRIPTION
         "In Proxy mode network measures may be managed using another
         interface than SNMP."


      OBJECT   ippmNetMeasureDst
      MIN-ACCESS read-only
      DESCRIPTION
         "In Proxy mode network measures may be managed using another
         interface than SNMP."


      OBJECT   ippmNetMeasureTxMode
      MIN-ACCESS read-only
      DESCRIPTION
         "In Proxy mode network measures may be managed using another
         interface than SNMP."


      OBJECT   ippmNetMeasureTxPacketRateUnit
      MIN-ACCESS read-only
      DESCRIPTION
         "In Proxy mode network measures may be managed using another
         interface than SNMP."


      OBJECT   ippmNetMeasureTxPacketRate
      MIN-ACCESS read-only
      DESCRIPTION
         "In Proxy mode network measures may be managed using another
         interface than SNMP."


      OBJECT   ippmNetMeasureMedOrBurstSize
      MIN-ACCESS read-only
      DESCRIPTION
         "In Proxy mode network measures may be managed using another
         interface than SNMP."


      OBJECT   ippmNetMeasureDevOrIntBurstSize
      MIN-ACCESS read-only
      DESCRIPTION
         "In Proxy mode network measures may be managed using another
         interface than SNMP."


      OBJECT   ippmNetMeasureLossTimeout
      MIN-ACCESS read-only
      DESCRIPTION
         "In Proxy mode network measures may be managed using another
         interface than SNMP."


      OBJECT   ippmNetMeasureL3PacketSize
      MIN-ACCESS read-only
      DESCRIPTION
         "In Proxy mode network measures may be managed using another
         interface than SNMP."


      OBJECT   ippmNetMeasureDataPattern
      MIN-ACCESS read-only
      DESCRIPTION
         "In Proxy mode network measures may be managed using another
         interface than SNMP."


      ::= { ippmCompliances 1 }






   ippmProxyCompliance         MODULE-COMPLIANCE
      STATUS             current
      DESCRIPTION
          "The compliance statement for SNMP entities which implement
          the IPPM MIB as a proxy."
      MODULE -- this module
      MANDATORY-GROUPS {
          ippmSystemGroup, ippmOwnersGroup, ippmHistoryGroup,
          ippmNetMeasureGroup, ippmAggrMeasureGroup,
          ippmNotificationGroup
      }
      GROUP ippmOwnersGroup
      DESCRIPTION
          "The ippmOwnersGroup is manadatory if VACM is not
          implemented."


      OBJECT   ippmNetMeasureName
      MIN-ACCESS read-only
      DESCRIPTION
         "In Proxy mode network measures may be managed using another
         interface than SNMP."


      OBJECT   ippmNetMeasureMetrics
      MIN-ACCESS read-only
      DESCRIPTION
         "In Proxy mode network measures may be managed using another
         interface than SNMP."


      OBJECT   ippmNetMeasureBeginTime
      MIN-ACCESS read-only
      DESCRIPTION
         "In Proxy mode network measures may be managed using another
         interface than SNMP."


      OBJECT   ippmNetMeasureCollectionRateUnit
      MIN-ACCESS read-only
      DESCRIPTION
         "In Proxy mode network measures may be managed using another
         interface than SNMP."


      OBJECT   ippmNetMeasureCollectionRate
      MIN-ACCESS read-only
      DESCRIPTION
         "In Proxy mode network measures may be managed using another
         interface than SNMP."


      OBJECT   ippmNetMeasureDurationUnit
      MIN-ACCESS read-only
      DESCRIPTION
         "In Proxy mode network measures may be managed using another
         interface than SNMP."


      OBJECT   ippmNetMeasureDuration
      MIN-ACCESS read-only
      DESCRIPTION
         "In Proxy mode network measures may be managed using another
         interface than SNMP."


      OBJECT   ippmNetMeasureHistorySize
      MIN-ACCESS read-only
      DESCRIPTION
         "In Proxy mode network measures may be managed using another
         interface than SNMP."


      OBJECT   ippmNetMeasureFailureMgmtMode
      MIN-ACCESS read-only
      DESCRIPTION
         "In Proxy mode network measures may be managed using another
         interface than SNMP."


      OBJECT   ippmNetMeasureResultsMgmt
      MIN-ACCESS read-only
      DESCRIPTION
         "In Proxy mode network measures may be managed using another
         interface than SNMP."


      OBJECT   ippmNetMeasureSrcPacketType
      MIN-ACCESS read-only
      DESCRIPTION
         "In Proxy mode network measures may be managed using another
         interface than SNMP."


      OBJECT   ippmNetMeasureSrc
      MIN-ACCESS read-only
      DESCRIPTION
         "In Proxy mode network measures may be managed using another
         interface than SNMP."


      OBJECT   ippmNetMeasureDstPacketType
      MIN-ACCESS read-only
      DESCRIPTION
         "In Proxy mode network measures may be managed using another
         interface than SNMP."


      OBJECT   ippmNetMeasureDst
      MIN-ACCESS read-only
      DESCRIPTION
         "In Proxy mode network measures may be managed using another
         interface than SNMP."


      OBJECT   ippmNetMeasureTxMode
      MIN-ACCESS read-only
      DESCRIPTION
         "In Proxy mode network measures may be managed using another
         interface than SNMP."


      OBJECT   ippmNetMeasureTxPacketRateUnit
      MIN-ACCESS read-only
      DESCRIPTION
         "In Proxy mode network measures may be managed using another
         interface than SNMP."


      OBJECT   ippmNetMeasureTxPacketRate
      MIN-ACCESS read-only
      DESCRIPTION
         "In Proxy mode network measures may be managed using another
         interface than SNMP."


      OBJECT   ippmNetMeasureMedOrBurstSize
      MIN-ACCESS read-only
      DESCRIPTION
         "In Proxy mode network measures may be managed using another
         interface than SNMP."


      OBJECT   ippmNetMeasureDevOrIntBurstSize
      MIN-ACCESS read-only
      DESCRIPTION
         "In Proxy mode network measures may be managed using another
         interface than SNMP."


      OBJECT   ippmNetMeasureLossTimeout
      MIN-ACCESS read-only
      DESCRIPTION
         "In Proxy mode network measures may be managed using another
         interface than SNMP."


      OBJECT   ippmNetMeasureL3PacketSize
      MIN-ACCESS read-only
      DESCRIPTION
         "In Proxy mode network measures may be managed using another
         interface than SNMP."


      OBJECT   ippmNetMeasureDataPattern
      MIN-ACCESS read-only
      DESCRIPTION
         "In Proxy mode network measures may be managed using another
         interface than SNMP."
      ::= { ippmCompliances 2 }

   ippmEmbeddedCompliance  MODULE-COMPLIANCE
      STATUS             current
      DESCRIPTION
          "The compliance statement for SNMP entities which implement
          the IPPM MIB in a probe."
      MODULE -- this module
      MANDATORY-GROUPS {
          ippmSystemGroup, ippmHistoryGroup, ippmNetMeasureGroup
      }
      ::= { ippmCompliances 3 }







   ippmSystemGroup    OBJECT-GROUP
      OBJECTS {
          ippmSystemSynchronizationDesc,
          ippmSystemTime,
          ippmSystemSynchronizationType,
          ippmSystemClockResolution,
          ippmSynchronizationTime,
          ippmSynchronizationStratum,
          ippmSynchronizationResolution,
          ippmPointOfMeasureMgmtAddrType,
          ippmPointOfMeasureMgmtAddress,
          ippmPointOfMeasureTestAddrType,
          ippmPointOfMeasureTestAddress,
          ippmSystemOperationalStatus,
          ippmSystemAggregatedMetrics,
          ippmPointOfMeasureMetrics,
          ippmMetricsType,
          ippmMetricsUnit,


          ippmMetricsDescription
      }
      STATUS  current
      DESCRIPTION
          "The IPPM System Group"
      ::=  { ippmGroups  1}



   ippmNetMeasureGroup   OBJECT-GROUP
      OBJECTS  {
          ippmNetMeasureName,
          ippmNetMeasureMetrics,
          ippmNetMeasureBeginTime,
          ippmNetMeasureCollectionRateUnit,
          ippmNetMeasureCollectionRate,
          ippmNetMeasureDurationUnit,
          ippmNetMeasureDuration,
          ippmNetMeasureHistorySize,
          ippmNetMeasureFailureMgmtMode,
          ippmNetMeasureResultsMgmt,
          ippmNetMeasureSrcPacketType,
          ippmNetMeasureSrc,
          ippmNetMeasureDstPacketType,
          ippmNetMeasureDst,
          ippmNetMeasureTxMode,
          ippmNetMeasureTxPacketRateUnit,
          ippmNetMeasureTxPacketRate,
          ippmNetMeasureMedOrBurstSize,
          ippmNetMeasureDevOrIntBurstSize,
          ippmNetMeasureLossTimeout,
          ippmNetMeasureL3PacketSize,
          ippmNetMeasureDataPattern,
          ippmNetMeasureTotalPktsRecv,
          ippmNetMeasureLastUpdate,
          ippmNetMeasureOperState
      }
      STATUS  current
      DESCRIPTION
          "The IPPM Network Measure Group"
      ::=  { ippmGroups  2}



   ippmHistoryGroup   OBJECT-GROUP
      OBJECTS  {
          ippmHistoryTimestamp,
          ippmHistoryValue,
          ippmHistoryPathToResults
      }
      STATUS  current
      DESCRIPTION
          "The IPPM History Group"


      ::=  { ippmGroups  3}


   ippmAggrMeasureGroup       OBJECT-GROUP
      OBJECTS  {
          ippmAggrMeasureName,
          ippmAggrMeasureMetrics,
          ippmAggrMeasureBeginTime,
          ippmAggrMeasureAggrPeriodUnit,
          ippmAggrMeasureAggrPeriod,
          ippmAggrMeasureDurationUnit,
          ippmAggrMeasureDuration,
          ippmAggrMeasureFilter,
          ippmAggrMeasureLowThreshold,
          ippmAggrMeasureHighThreshold,
          ippmAggrMeasureHistorySize,
          ippmAggrMeasureStorageType,
          ippmAggrMeasureHistoryOwner,
          ippmAggrMeasureHistoryIndex,
          ippmAggrMeasureHistoryMetric,
          ippmAggrMeasureAdminState,
          ippmAggrMeasureFastReport,
          ippmAggrMeasureResultsMgmt,
          ippmAggrMeasureLastUpdate,
          ippmAggrMeasureOperState,
          ippmAggrMeasureNbPktsTreated,
          ippmAggrMeasureStatus
      }
      STATUS  current
      DESCRIPTION
          "The IPPM AggregatedMeasure Group"
      ::=  { ippmGroups 4}



   ippmOwnersGroup    OBJECT-GROUP
      OBJECTS  {
          ippmOwnersGrantedMetrics,
          ippmOwnersQuota,
          ippmOwnersIpAddressType,
          ippmOwnersIpAddress,
          ippmOwnersEmail,
          ippmOwnersStatus
      }
      STATUS  current
      DESCRIPTION
          "The IPPM Owners Group"
      ::=  { ippmGroups 5}



   ippmNotificationGroup       NOTIFICATION-GROUP
      NOTIFICATIONS  {
          ippmAggrMeasureReport,


          ippmNetMeasureHistoryFull,
          ippmAggrMeasureHistoryFull
      }
      STATUS  current
      DESCRIPTION
          "The IPPM Notification Group"
      ::=  { ippmGroups 6}


   END

-- 
-- 
--    Copyright (C) The Internet Society (2004).  All Rights Reserved.
-- 
-- 
--    This document and translations of it may be copied and furnished to
--    others, and derivative works that comment on or otherwise explain it
--    or assist in its implementation may be prepared, copied, published
--    and distributed, in whole or in part, without restriction of any
--    kind, provided that the above copyright notice and this paragraph are
--    included on all such copies and derivative works.  However, this
--    document itself may not be modified in any way, such as by removing
--    the copyright notice or references to the Internet Society or other
--    Internet organizations, except as needed for the purpose of
--    developing Internet standards in which case the procedures for
--    copyrights defined in the Internet Standards process must be
--    followed, or as required to translate it into languages other than
--    English.
-- 
-- 
--    The limited permissions granted above are perpetual and will not be
--    revoked by the Internet Society or its successors or assignees.
-- 
-- 
--    This document and the information contained herein is provided on an
--    "AS IS" basis and THE INTERNET SOCIETY AND THE INTERNET ENGINEERING
--    TASK FORCE DISCLAIMS ALL WARRANTIES, EXPRESS OR IMPLIED, INCLUDING
--    BUT NOT LIMITED TO ANY WARRANTY THAT THE USE OF THE INFORMATION
--    HEREIN WILL NOT INFRINGE ANY RIGHTS OR ANY IMPLIED WARRANTIES OF
--    MERCHANTABILITY OR FITNESS FOR A PARTICULAR PURPOSE.
-- 
-- 
-- 
-- Acknowledgment
-- 
-- 
--    Funding for the RFC Editor function is currently provided by the
--    Internet Society.
