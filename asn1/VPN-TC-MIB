-- extracted from draft-ietf-l3vpn-tc-mib-02.txt
-- at Fri Jun  4 06:20:33 2004

VPN-TC-MIB DEFINITIONS ::= BEGIN

IMPORTS
    MODULE-IDENTITY, mib-2
        FROM SNMPv2-SMI

    TEXTUAL-CONVENTION  
        FROM SNMPv2-TC;

vpnTcMIB MODULE-IDENTITY
    LAST-UPDATED "200405261200Z"  -- 26 May 2004 12:00:00 GMT
    ORGANIZATION 
        "Layer 3 Virtual Private Networks (L3VPN) Working Group."
    CONTACT-INFO
        "Benson Schliesser
         bensons@savvis.net

         Thomas D. Nadeau
         tnadeau@cisco.com

         This TC MIB is a product of the PPVPN 
         http://www.ietf.org/html.charters/ppvpn-charter.html
         and subsequently the L3VPN
         http://www.ietf.org/html.charters/l3vpn-charter.html
         working groups.

         Comments and discussion should be directed to l3vpn@ietf.org"
    DESCRIPTION
        "This MIB contains TCs for VPNs.

         Copyright (C) The Internet Society (2004).  This version
         of this MIB module is part of RFC yyyy;  see the RFC
         itself for full legal notices."
-- RFC Ed.: replace yyyy with actual RFC number & remove this note
    -- Revision history.
    REVISION "200405261200Z"  -- 26 May 2004 12:00:00 GMT
    DESCRIPTION "Initial version, published as RFC yyyy."
-- RFC Ed.: replace yyyy with actual RFC number & remove this note
    ::= { mib-2 XXX }
-- RFC Ed.: replace XXX with IANA-assigned number & remove this note

-- definition of textual conventions

VPNId ::= TEXTUAL-CONVENTION
    STATUS current
    DESCRIPTION
        "The purpose of a VPN-ID is to uniquely identify a VPN.
         The Global VPN Identifier format is:
         3 octet VPN Authority, Organizationally Unique Identifier
         followed by
         4 octet VPN index identifying VPN according to OUI"
    REFERENCE
        "Fox, B. and Gleeson, B., 'Virtual Private Networks
         Identifier', RFC 2685, September 1999."
    SYNTAX    OCTET STRING (SIZE (7))

END

-- 
--     Copyright (C) The Internet Society (2004). All Rights
--     Reserved.
-- 
--     This document and translations of it may be copied and
--     furnished to others, and derivative works that comment on
--     or otherwise explain it or assist in its implementation
--     may be prepared, copied, published and distributed, in
--     whole or in part, without restriction of any kind,
--     provided that the above copyright notice and this
--     paragraph are included on all such copies and derivative
--     works.  However, this document itself may not be modified
--     in any way, such as by removing the copyright notice or
--     references to the Internet Society or other Internet
--     organizations, except as needed for the purpose of
--     developing Internet standards in which case the
--     procedures for copyrights defined in the Internet
--     Standards process must be followed, or as required to
--     translate it into languages other than English.
-- 
--     The limited permissions granted above are perpetual and
--     will not be revoked by the Internet Society or its
--     successors or assigns. This document and the information
--     contained herein is provided on an "AS IS" basis and THE
--     INTERNET SOCIETY AND THE INTERNET ENGINEERING TASK FORCE
--     DISCLAIMS ALL WARRANTIES, EXPRESS OR IMPLIED, INCLUDING
--     BUT NOT LIMITED TO ANY WARRANTY THAT THE USE OF THE
--     INFORMATION HEREIN WILL NOT INFRINGE ANY RIGHTS OR ANY
--     IMPLIED WARRANTIES OF MERCHANTABILITY OR FITNESS FOR A
--     PARTICULAR PURPOSE.
