Wellfleet-RFWALL-MIB DEFINITIONS ::= BEGIN

-- Created by mdl2asn version 3.1
-- Creation date: Wed May  8 17:23:42 EDT 1996
-- Modified for 13.20 Firewall Phase 3 by rmehta on 11/22/98

    IMPORTS

      IpAddress
        FROM RFC1155-SMI
      OBJECT-TYPE
        FROM RFC-1212
      wfFwallGroup
        FROM Wellfleet-COMMON-MIB;


    wfRFwallGroup	OBJECT IDENTIFIER ::= { wfFwallGroup 2 }

    wfRFwallDelete OBJECT-TYPE
        SYNTAX  INTEGER {
    		        created(1),
    		        deleted(2)
                }
        ACCESS  read-write
        STATUS  mandatory
        DESCRIPTION
                "Create/Delete parameter"
        DEFVAL  { created }
        ::= { wfRFwallGroup 1 }

    wfRFwallDisable OBJECT-TYPE
        SYNTAX  INTEGER {
    		        enabled(1),
    		        disabled(2)
    	        }
        ACCESS  read-write
        STATUS  mandatory
        DESCRIPTION
                "Enable/Disable parameter"
        DEFVAL  { enabled }
        ::= { wfRFwallGroup 2 }

    wfRFwallState OBJECT-TYPE
        SYNTAX  INTEGER {
    		        up(1),
    		        down(2),
    		        init(3),
    		        notpresent(4)
    	        }
        ACCESS  read-only
        STATUS  mandatory
        DESCRIPTION
                "State parameter"
        DEFVAL  { init }
        ::= { wfRFwallGroup 3 }

    wfRFwallLogHostIp OBJECT-TYPE
        SYNTAX	IpAddress
        ACCESS	read-write
        STATUS	mandatory
        DESCRIPTION
                "Primary Log Machine IP address ip notation"
        ::= { wfRFwallGroup 4 }

    wfRFwallLogHostIpInt OBJECT-TYPE
        SYNTAX  INTEGER
        ACCESS  read-write
        STATUS  obsolete
        DESCRIPTION
                "Primary Log Machine IP address decimal value: NOT IN USE"
        ::= { wfRFwallGroup 5 }

    wfRFwallLocalHostIp OBJECT-TYPE
        SYNTAX  IpAddress
        ACCESS  read-write
        STATUS  mandatory
        DESCRIPTION
                "Local host IP address ip notation"
        ::= { wfRFwallGroup 6 }

    wfRFwallLocalHostIpInt OBJECT-TYPE
        SYNTAX  INTEGER
        ACCESS  read-write
        STATUS  obsolete
        DESCRIPTION
                "Local host IP address decimal value: NOT IN USE"
        ::= { wfRFwallGroup 7 }

    wfRFwallVersion OBJECT-TYPE
        SYNTAX  INTEGER
        ACCESS  read-write
        STATUS  mandatory
        DESCRIPTION
                "Version parameter - FireWall Protocol Version Number"
        DEFVAL  { 1 }
        ::= { wfRFwallGroup 8 }

    wfRFwallHmemMin OBJECT-TYPE
        SYNTAX  INTEGER
        ACCESS  read-write
        STATUS  mandatory
        DESCRIPTION
                "Memory allocator initialization parameter: Min Value"
        DEFVAL	{ 50000 }
        ::= { wfRFwallGroup 9 }

    wfRFwallHmemMax OBJECT-TYPE
        SYNTAX  INTEGER
        ACCESS  read-write
        STATUS  mandatory
        DESCRIPTION
                "Memory allocator initialization parameter: Max Value"
        DEFVAL	{ 100000 }
        ::= { wfRFwallGroup 10 }

    wfRFwallLogHostIpBkp1 OBJECT-TYPE
        SYNTAX  IpAddress
        ACCESS  read-write
        STATUS  mandatory
        DESCRIPTION
                "Secondary Log Machine IP address ip notation"
        ::= { wfRFwallGroup 11 }

    wfRFwallLogHostIpIntBkp1 OBJECT-TYPE
        SYNTAX  INTEGER
        ACCESS  read-write
        STATUS  obsolete
        DESCRIPTION
                "Secondary Log Machine IP address decimal value: NOT IN USE"
        ::= { wfRFwallGroup 12 }

    wfRFwallLogHostIpBkp2 OBJECT-TYPE
        SYNTAX  IpAddress
        ACCESS  read-write
        STATUS  mandatory
        DESCRIPTION
                "Tertiary Log Machine IP address ip notation"
        ::= { wfRFwallGroup 13 }

    wfRFwallLogHostIpIntBkp2 OBJECT-TYPE
        SYNTAX  INTEGER
        ACCESS  read-write
        STATUS  obsolete
        DESCRIPTION
                "Tertiary Log Machine IP address decimal value: NOT IN USE"
        ::= { wfRFwallGroup 14 }

    wfRFwallFastPathDisable OBJECT-TYPE
        SYNTAX  INTEGER {
    		        enabled(1),
    		        disabled(2)
    		    }
        ACCESS  read-write
        STATUS  mandatory
        DESCRIPTION
                "Fast Path optimization Enable/Disable parameter"
        DEFVAL  { enabled }
        ::= { wfRFwallGroup 15 }

    wfRFwallFilterTimer OBJECT-TYPE
        SYNTAX  INTEGER (20..180)
        ACCESS  read-write
        STATUS  mandatory
        DESCRIPTION
                "This timer value specified in seconds, is the time
                 interval between the attempts to download the filter
                 from the backup management station if the download is
                 not successful from the current management station."
        DEFVAL  { 40 }
        ::= { wfRFwallGroup 16 }

    wfRFwallLogTimer OBJECT-TYPE
        SYNTAX  INTEGER (20..180)
        ACCESS  read-write
        STATUS  mandatory
        DESCRIPTION
                "This timer value specified in seconds, is the time
                 interval between the attempts to log to the backup
                 management hosts if the logging is not successful to
                 the current management station."
        DEFVAL	{ 40 }
        ::= { wfRFwallGroup 17 }

    wfRFwallKeepaliveTimerIdle OBJECT-TYPE
        SYNTAX  INTEGER(0..3600)
        ACCESS  read-write
        STATUS  mandatory
        DESCRIPTION
                "Idle session timeout period, in seconds.  If an established
                TCP connection remains inactive for this interval, KEEPALIVE
                messages will be sent to the peer (if the Keepalive Timer is
                non-zero).  Setting the Idle Timer to zero disables the
                keepalive feature."
        DEFVAL  { 180 }
        ::= { wfRFwallGroup 18 }

    wfRFwallKeepaliveTimerRetryTmo OBJECT-TYPE
        SYNTAX  INTEGER(0..600)
        ACCESS  read-write
        STATUS  mandatory
        DESCRIPTION
                "KEEPALIVE retransmit timeout period, in seconds.  This is
                the interval at which unacknowledged KEEPALIVE messages will
                be retransmitted.  If the Idle Timer is set to zero, this
                timer ignored.  If the Idle Timer is non-zero and this timer
                IS zero, no KEEPALIVEs are sent and the session is terminated
                upon expiration of the Idle Timer."
        DEFVAL  { 5 }
        ::= { wfRFwallGroup 19 }

    wfRFwallKeepaliveTimerRetries OBJECT-TYPE
        SYNTAX  INTEGER(0..100)
        ACCESS  read-write
        STATUS  mandatory
        DESCRIPTION
                "Number of unacknowledged KEEPALIVE messages retransmitted
                before the TCP session is terminated.  If this count is set
                to zero, only one KEEPALIVE message will be sent."
        DEFVAL  { 10 }
        ::= { wfRFwallGroup 20 }

END  -- Wellfleet-RFWALL-MIB
