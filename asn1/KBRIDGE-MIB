KBRIDGE-MIB DEFINITIONS ::= BEGIN

		IMPORTS
			MODULE-IDENTITY, OBJECT-TYPE, 
			Integer32, Counter32, IpAddress, Gauge32, Unsigned32,
			enterprises 
				FROM SNMPv2-SMI;
-- **********************************************************************
-- * MODULE IDENTITY
-- **********************************************************************

	karlnet MODULE-IDENTITY
		LAST-UPDATED "200201281200Z"
		ORGANIZATION "KarlNet Incorporated"
		CONTACT-INFO
			"Postal: KarlNet Incorporated
			         525 Metro Place North
			         Suite 100
			         Dublin, OH 43017 USA
			    Tel: +1 614 822 5275
			    Fax: +1 614 822 0024
			 E-mail: info@karlnet.com"
		DESCRIPTION
			"The MIB module for KarlNet entities.
			iso(1).org(3).dod(6).internet(1).mgmt(4).enterprises(1).karlnet(762)"
        REVISION 	"200201281200Z"
		DESCRIPTION	"Several minor updates; also added ClientInfo and SEC MIB sections."
        REVISION 	"200107171200Z"
		DESCRIPTION	"Converted to public form."
        REVISION 	"200105091200Z"
		DESCRIPTION	"Updated CONTACT-INFO.
					Added the kbSEC and kbClientInfo sections."
        REVISION 	"200009181200Z"
		DESCRIPTION	"Changed kbWirelessStationSNR type from Gauge32 to INTEGER"
        REVISION 	"200007251200Z"
    	DESCRIPTION	"Added description text on kbControlTemperature to clarify that the
    				temperature given is in half-degree increments centigrade. That is,
    				kbControlTemperature = 66 implies 33 degrees Celsius."
	    REVISION 	"200007111200Z"
    	DESCRIPTION	"Initial Release."

		::= { enterprises 762 }

	kbridge-mib OBJECT IDENTIFIER ::= { karlnet 2 }

	karlNetKBControl OBJECT IDENTIFIER ::= { kbridge-mib 1 }
		  
		  --            (Borrowed from the Bridge MIB)                    
          -- All representations of MAC addresses in this MIB Module
          -- use, as a textual convention (i.e. this convention does
          -- not affect their encoding), the data type:
          MacAddress ::= OCTET STRING (SIZE (6))    -- a 6 octet address
                                                    -- in the
                                                    -- "canonical"
                                                    -- order
          -- 16-bit addresses, if needed, are represented by setting
          -- their upper 4 octets to all 0's, i.e., AAFF would be
          -- represented as 00000000AAFF.


-- ******************************************
-- ** kbControl block
-- ******************************************		                      
-- KBRIDGE control MIB.
-- 6 = kbControlReboot 
-- 9 = kbDummy - used for testing write community
-- 11 = shutdown (1 = shutdown)
-- 12 = Temperature from Dallas chip in 1/2 degree centagrade increments)	

	kbControlReboot OBJECT-TYPE
		SYNTAX INTEGER (1)
		MAX-ACCESS write-only
		STATUS current
		DESCRIPTION 
			"Set this OID value to 1 to reboot the KarlBridge."
		::= { karlNetKBControl 6 }
		
	kbControlTestSNMPWrite OBJECT-TYPE
		SYNTAX INTEGER (1)
		MAX-ACCESS write-only
		STATUS current
		DESCRIPTION 
			"This OID is provided to test whether your SNMP software can 
			successfully set an OID on the KarlBridge by setting its value to 1."
		::= { karlNetKBControl 9 }
		
	kbControlShutdown OBJECT-TYPE
		SYNTAX INTEGER (1)
		MAX-ACCESS write-only
		STATUS current
		DESCRIPTION 
			"Set this OID to 1 to shutdown the KarlBridge."
		::= { karlNetKBControl 11 }
		
	kbControlTemperature OBJECT-TYPE
		SYNTAX INTEGER
		MAX-ACCESS read-only
		STATUS current
		DESCRIPTION 
			"For KarlBridges equipped with a Dallas temperature chip, returns the temperature 
			of the Dallas chip in 1/2 degree centigrade increments (+/- 0.5 degrees C).
			To determine the correct temperature in Centigrade, divide by 2.
			To determine the correct temperature in Fahrenheit, divide by 2, then multiply by 9/5 and add 32.
			KarlBridges that are not equipped with the Dallas chip return a 'noSuchName' error."
		::= { karlNetKBControl 12 }
		
	-------------------------------------------------------------------
	--- KarlBridge kbWireless MIB module
	---    Holds various client station statistics, mostly for the 
	---     TurboCell outdoor protocols. 
	---    The 'kbWirelessTest*' values are also used for general-purpose
	---     wireless link test statistics
	---
	kbWireless OBJECT IDENTIFIER ::= { kbridge-mib 5 }

	kbWirelessStationNumber OBJECT-TYPE
		SYNTAX INTEGER
		MAX-ACCESS read-only
		STATUS current
		DESCRIPTION
			"The number of registered stations (i.e. valid entries) in the 
			kbWirelessStationTable."
		::= { kbWireless 1 }		

	kbWirelessStationTable OBJECT-TYPE
		SYNTAX SEQUENCE OF KBWirelessStationEntry
		MAX-ACCESS not-accessible
		STATUS current
		DESCRIPTION
			"List of wireless connections and their attributes. 
			Each entry in the table corresponds to a particular 
			wireless station (usually a satellite) that is 
			attached to a particular wireless interface."
		::= { kbWireless 2 }

	kbWirelessStationEntry OBJECT-TYPE
		SYNTAX KBWirelessStationEntry
		MAX-ACCESS not-accessible
		STATUS current
		DESCRIPTION
			"An entry in the kbWirelessStationTable. Each entry
			corresponds to a particular wireless station connected
			to one of the KarlBridge's interfaces. The entries are 
			indexed by kbWirelessStationIndex and also can be generally
			considered unique based upon the kbWirelessStationMACAddress
			field."
		INDEX { kbWirelessStationIndex }
		::= { kbWirelessStationTable 1 }

	KBWirelessStationEntry ::=
		SEQUENCE {
                kbWirelessStationIndex
                        Unsigned32,
                kbWirelessStationInterfaceNumber
                        Unsigned32,
                kbWirelessStationName
                        OCTET STRING,
                kbWirelessStationExclHellos
                        Counter32,
                kbWirelessStationGoodHellos
                        Counter32,
                kbWirelessStationLowHellos
                        Counter32,
                kbWirelessStationSignalLevel
                        Gauge32,
                kbWirelessStationNoiseLevel
                        Gauge32,
                kbWirelessStationSignalQuality
                        Gauge32,
                kbWirelessStationPktTransmits
                        Counter32,
                kbWirelessStationMACAddress
                        OCTET STRING,
                kbWirelessStationTransmits
                        Counter32,
                kbWirelessStationBadTransmits
                        Counter32,
                kbWirelessStationReTransmits
                        Counter32,
                kbWirelessStationIPAddress
                        IpAddress,
                kbWirelessStationType
                        INTEGER, 
                kbWirelessStationSNR
                        INTEGER, 
                kbWirelessStationState
                        INTEGER,
                kbWirelessPoll
                        Counter32,
                kbWirelessPollData
                        Counter32,
                kbWirelessPollNoData
                        Counter32,
                kbWirelessPollMoreData
                        Counter32,
                kbWirelessPollTimeouts 
                        Counter32,
                kbWirelessPollOfflines
                        Counter32,
                kbWirelessTestTime
                        Counter32,
                kbWirelessTestInterval
                        Unsigned32,
                kbWirelessTestPacketSize
                        Integer32,
                kbWirelessTestOurTx
                        Counter32,
                kbWirelessTestOurRx 
                        Counter32,
                kbWirelessTestHisTx
                        Counter32,
                kbWirelessTestHisRx
                        Counter32,
                kbWirelessTestOurCurSignalLevel
                        Gauge32,
                kbWirelessTestOurCurNoiseLevel
                        Gauge32,
                kbWirelessTestOurCurSignalQuality
                        Gauge32,
                kbWirelessTestOurCurSNR
                        Gauge32,
                kbWirelessTestOurMinSignalLevel
                        Gauge32,
                kbWirelessTestOurMinNoiseLevel
                        Gauge32,
                kbWirelessTestOurMinSignalQuality
                        Gauge32,
                kbWirelessTestOurMinSNR
                        Gauge32,
                kbWirelessTestOurMaxSignalLevel
                        Gauge32,
                kbWirelessTestOurMaxNoiseLevel
                        Gauge32,
                kbWirelessTestOurMaxSignalQuality
                        Gauge32,
                kbWirelessTestOurMaxSNR
                        Gauge32,
                kbWirelessTestHisCurSignalLevel
                        Gauge32,
                kbWirelessTestHisCurNoiseLevel
                        Gauge32,
                kbWirelessTestHisCurSignalQuality
                        Gauge32,               				
                kbWirelessTestHisCurSNR
                        Gauge32,
                kbWirelessTestHisMinSignalLevel
                        Gauge32,
                kbWirelessTestHisMinNoiseLevel
                        Gauge32,
                kbWirelessTestHisMinSignalQuality
                        Gauge32,
                kbWirelessTestHisMinSNR
                        Gauge32,
                kbWirelessTestHisMaxSignalLevel
                        Gauge32,
                kbWirelessTestHisMaxNoiseLevel
                        Gauge32,
                kbWirelessTestHisMaxSignalQuality
                        Gauge32,
                kbWirelessTestHisMaxSNR
                        Gauge32,
                kbWirelessTestLinkUp
                        INTEGER,         
                kbWirelessTestLostLink
                        INTEGER,
                kbWirelessTestLostTestPkts
                        INTEGER,
                kbWirelessStationRadioType
                        INTEGER,
                kbWirelessRecordType
                        INTEGER,
                kbWirelessStationPktReceives
                        Counter32,
                kbWirelessStationReceives
                        Counter32,
                kbWirelessStationBytesReceives
                        Counter32,
                kbWirelessStationBytesTransmits
                        Counter32,
                kbWirelessRegistrationRecord
                        OCTET STRING,
                kbWirelessStationFragmentDiscards
                        Counter32,
                kbWirelessStationFragmentMissings 
                        Counter32,
                kbWirelessStationFragmentLostFrames 
                        Counter32,
                kbWirelessStationFragmentErrors
                        Counter32
	}

	kbWirelessStationIndex OBJECT-TYPE
		SYNTAX Unsigned32 (0..4294967295)
		MAX-ACCESS read-only
		STATUS current
		DESCRIPTION
			"The index of this entry in the kbWirelessStationTable.
			Each entry in the table has a unique kbWirelessStationIndex."
		::= { kbWirelessStationEntry 1 }

	kbWirelessStationInterfaceNumber OBJECT-TYPE
		SYNTAX Unsigned32 (0..4294967295)
		MAX-ACCESS read-only
		STATUS current
		DESCRIPTION
			"The interface number of the wireless network interface
			that this entry is attached to. When a KarlBridge contains 
			multiple wireless network interfaces, different entries
			may contain different values for this field. Interface 
			numbering includes non-wireless interfaces, with the 
			first network interface being number 1."
		::= { kbWirelessStationEntry 2 }

	kbWirelessStationName OBJECT-TYPE
		SYNTAX OCTET STRING
		MAX-ACCESS read-only
		STATUS current
		DESCRIPTION
			"The name of the remote wireless station as reported 
			to the KarlBridge."
		::= { kbWirelessStationEntry 3 }

	kbWirelessStationExclHellos OBJECT-TYPE
		SYNTAX Counter32
		MAX-ACCESS read-only
		STATUS current
		DESCRIPTION
			"The number of Hello packets from the KarlBridge that were
			received by the remote station with Excellent signal quality."
		::= { kbWirelessStationEntry 4 }

	kbWirelessStationGoodHellos OBJECT-TYPE
		SYNTAX Counter32
		MAX-ACCESS read-only
		STATUS current
		DESCRIPTION
			"The number of Hello packets from the KarlBridge that were
			received by the remote station with Good signal quality."
		::= { kbWirelessStationEntry 5 }

	kbWirelessStationLowHellos OBJECT-TYPE
		SYNTAX Counter32
		MAX-ACCESS read-only
		STATUS current
		DESCRIPTION
			"The number of Hello packets from the KarlBridge that were
			received by the remote station with Low signal quality."
		::= { kbWirelessStationEntry 6 }

	kbWirelessStationSignalLevel OBJECT-TYPE
		SYNTAX Gauge32
		MAX-ACCESS read-only
		STATUS current
		DESCRIPTION
			"The radio signal level in percentage."
		::= { kbWirelessStationEntry 7 }

	kbWirelessStationNoiseLevel OBJECT-TYPE
		SYNTAX Gauge32
		MAX-ACCESS read-only
		STATUS current
		DESCRIPTION
			"The radio noise level in percentage."
		::= { kbWirelessStationEntry 8 }

	kbWirelessStationSignalQuality OBJECT-TYPE
		SYNTAX Gauge32 
		MAX-ACCESS read-only
		STATUS current
		DESCRIPTION
			"The relative signal quality of the radio transmissions."
		::= { kbWirelessStationEntry 9 }

	kbWirelessStationPktTransmits OBJECT-TYPE
		SYNTAX Counter32
		MAX-ACCESS read-only
		STATUS current
		DESCRIPTION
			"The number of Ethernet packets the remote station has 
			transmitted through the wireless interface connected 
			to the KarlBridge."
		::= { kbWirelessStationEntry 10 }

	kbWirelessStationMACAddress OBJECT-TYPE
		SYNTAX OCTET STRING
		MAX-ACCESS read-only
		STATUS current
		DESCRIPTION
			"The Ethernet (MAC) address of the remote station's 
			wireless interface that is connected to the KarlBridge."
		::= { kbWirelessStationEntry 11 }

	kbWirelessStationTransmits OBJECT-TYPE
		SYNTAX Counter32
		MAX-ACCESS read-only
		STATUS current
		DESCRIPTION
			"The total number of wireless transmissions the KarlBridge 
			has made to the remote station through this interface.
			This number does not necessarily correspond to the number 
			of Ethernet packets transmitted through this interface 
			(see kbWirelessStationPktTransmits)."
		::= { kbWirelessStationEntry 12 }

	kbWirelessStationBadTransmits OBJECT-TYPE
		SYNTAX Counter32
		MAX-ACCESS read-only
		STATUS current
		DESCRIPTION
			"The total number of failed wireless transmissions the KarlBridge 
			has made to the remote station through this interface. If a 
			wireless transmission is not received after 10 attempts, this
			counter is incremented."
		::= { kbWirelessStationEntry 13 }

	kbWirelessStationReTransmits OBJECT-TYPE
		SYNTAX Counter32
		MAX-ACCESS read-only
		STATUS current
		DESCRIPTION
			"The total number of wireless re-transmissions the KarlBridge 
			has attempted to the remote station through this interface."
		::= { kbWirelessStationEntry 14 }

	kbWirelessStationIPAddress OBJECT-TYPE
		SYNTAX IpAddress
		MAX-ACCESS read-only
		STATUS current
		DESCRIPTION
			"The IP address of the remote station, if any."
		::= { kbWirelessStationEntry 15 }

	kbWirelessStationType OBJECT-TYPE
		SYNTAX INTEGER 
			{
				compatibility-Mode(1),
				tc-Peer-to-Peer(2),
				tc-Base-Station(3),
				tc-Satellite-Station(4),
				tc-Polling-Base-Station(5),
				tc-PtP-Controller(6)
			}
		MAX-ACCESS read-only
		STATUS current
		DESCRIPTION
			"The remote station's mode of operation on this radio interface. Possible values are:
				compatibility-Mode(1)     	-- IEEE 802.11 mode or legacy Wireless(-I) mode
				tc-Peer-to-Peer(2)        	-- TurboCell Peer-to-Peer Station (no base stations, no polling)
				tc-Base-Station(3)        	-- TurboCell Base Station
				tc-Satellite-Station(4)	  	-- TurboCell Satellite Station
				tc-Polling-Base-Station(5)	-- TurboCell Polling Base Station
				tc-PtP-Controller(6)      	-- TurboCell Point-to-Point Controller (Single-User Base Station)"
		::= { kbWirelessStationEntry 16 }

	kbWirelessStationSNR OBJECT-TYPE
		SYNTAX INTEGER 
			{
			unknown-SNR(1),
			low-SNR(2),
			good-SNR(3),
			excellent-SNR(4)
			}
		MAX-ACCESS read-only
		STATUS current
		DESCRIPTION
			"The relative Signal-to-Noise Ratio of the wireless connection
			between the remote station and the KarlBridge."
		::= { kbWirelessStationEntry 17 }
	
	kbWirelessStationState OBJECT-TYPE
		SYNTAX INTEGER 
			{
			online(1),
		 	offline(2)
			}
		MAX-ACCESS read-only
		STATUS current
		DESCRIPTION
			"The remote station's wireless connection status.
			The remote station is said to be offline when it appears
			to cease wireless communication, either because it no longer
			acknowledges poll packets or no longer sends poll packets"
		::= { kbWirelessStationEntry 18 }

	kbWirelessPoll OBJECT-TYPE
		SYNTAX Counter32
		MAX-ACCESS read-only
		STATUS current
		DESCRIPTION
			"The number of times the KarlBridge has polled the remote station."
		::= { kbWirelessStationEntry 19 }

	kbWirelessPollData OBJECT-TYPE
		SYNTAX Counter32
		MAX-ACCESS read-only
		STATUS current
		DESCRIPTION
			"The number of times the KarlBridge has polled the remote station 
			that the remote station has responded with data, after which the
			remote station's transmit queue is empty."
		::= { kbWirelessStationEntry 20 }

	kbWirelessPollNoData OBJECT-TYPE
		SYNTAX Counter32
		MAX-ACCESS read-only
		STATUS current
		DESCRIPTION
			"The number of times the KarlBridge has polled the remote station
			that the remote station has not responded with data."
		::= { kbWirelessStationEntry 21 }

	kbWirelessPollMoreData OBJECT-TYPE
		SYNTAX Counter32
		MAX-ACCESS read-only
		STATUS deprecated
		DESCRIPTION
			"The number of times the KarlBridge has polled the remote station
			that the remote station has had more data in its transmit queue 
			than it could transmit in a single poll response."
		::= { kbWirelessStationEntry 22 }

	kbWirelessPollTimeouts OBJECT-TYPE
		SYNTAX Counter32
		MAX-ACCESS read-write
		STATUS current
		DESCRIPTION
			"The number of times the KarlBridge has polled the remote station
			and the remote station has not responded before the timeout 
			period expired."
		::= { kbWirelessStationEntry 23 }

	kbWirelessPollOfflines OBJECT-TYPE
		SYNTAX Counter32
		MAX-ACCESS read-write
		STATUS current
		DESCRIPTION
			"The number of times the remote station has gone offline.
			The value is relevant only when the KarlBridge is in one of 
			the Base Station modes (polling or non-polling)."
		::= { kbWirelessStationEntry 24 }

	kbWirelessTestTime OBJECT-TYPE
		SYNTAX Counter32
		MAX-ACCESS read-write
		STATUS current
		DESCRIPTION
			"The number of seconds remaining in the wireless link test.
			This value is read-writable, and is decremented by the device 
                        every second until it reaches 0, at which point the test is 
			finished. To stop the test, set this value to 0."
		::= { kbWirelessStationEntry 25 }

	kbWirelessTestInterval OBJECT-TYPE
		SYNTAX Unsigned32 (0..4294967295)
		MAX-ACCESS read-write
		STATUS current
		DESCRIPTION
			"The duration (in hundredths of seconds) of the radio link test
			performed between the KarlBridge and the remote station."
		::= { kbWirelessStationEntry 26 }

	kbWirelessTestPacketSize OBJECT-TYPE
		SYNTAX Integer32 (0..2147483647)
		MAX-ACCESS read-write
		STATUS current
		DESCRIPTION
			"The size of the radio link test packets
			sent between the KarlBridge and the remote station." 
		::= { kbWirelessStationEntry 27 }

	kbWirelessTestOurTx OBJECT-TYPE
		SYNTAX Counter32
		MAX-ACCESS read-only
		STATUS current
		DESCRIPTION
			"The radio transmit rate of the KarlBridge's radio when 
			performing the radio link test."
		::= { kbWirelessStationEntry 28 }

	kbWirelessTestOurRx OBJECT-TYPE
		SYNTAX Counter32
		MAX-ACCESS read-only
		STATUS current
		DESCRIPTION
			"The radio receive rate used by the KarlBridge 
			when performing the radio link test."
		::= { kbWirelessStationEntry 29 }

	kbWirelessTestHisTx OBJECT-TYPE
		SYNTAX Counter32
		MAX-ACCESS read-only
		STATUS current
		DESCRIPTION
			"The radio transmit rate of the remote station's radio when 
			performing the radio link test."
		::= { kbWirelessStationEntry 30 }

	kbWirelessTestHisRx OBJECT-TYPE
		SYNTAX Counter32
		MAX-ACCESS read-only
		STATUS current
		DESCRIPTION
			"The radio receive rate used by the remote station 
			when performing the radio link test."
		::= { kbWirelessStationEntry 31 }

	kbWirelessTestOurCurSignalLevel OBJECT-TYPE
		SYNTAX Gauge32
		MAX-ACCESS read-only
		STATUS current
		DESCRIPTION
			"The current local signal level 
			for the radio link test as recorded by the KarlBridge."
		::= { kbWirelessStationEntry 32 }

	kbWirelessTestOurCurNoiseLevel OBJECT-TYPE
		SYNTAX Gauge32
		MAX-ACCESS read-only
		STATUS current
		DESCRIPTION
			"The current local noise level 
			for the radio link test as recorded by the KarlBridge."
		::= { kbWirelessStationEntry 33 }

	kbWirelessTestOurCurSignalQuality OBJECT-TYPE
		SYNTAX Gauge32
		MAX-ACCESS read-only
		STATUS current
		DESCRIPTION
			"The current relative signal quality 
			for the radio link test as recorded by the KarlBridge."
		::= { kbWirelessStationEntry 34 }

	kbWirelessTestOurCurSNR OBJECT-TYPE
		SYNTAX Gauge32
		MAX-ACCESS read-only
		STATUS current
		DESCRIPTION
			"The current local Signal-to-Noise Ratio (SNR)
			for the radio link test as recorded by the KarlBridge."
		::= { kbWirelessStationEntry 35 }

	kbWirelessTestOurMinSignalLevel OBJECT-TYPE
		SYNTAX Gauge32
		MAX-ACCESS read-only
		STATUS current
		DESCRIPTION
			"The minimum local signal level 
			recorded by the KarlBridge during the radio link test."
		::= { kbWirelessStationEntry 36 }

	kbWirelessTestOurMinNoiseLevel OBJECT-TYPE
		SYNTAX Gauge32
		MAX-ACCESS read-only
		STATUS current
		DESCRIPTION
			"The minimum local noise level 
			recorded by the KarlBridge during the radio link test."
		::= { kbWirelessStationEntry 37 }

	kbWirelessTestOurMinSignalQuality OBJECT-TYPE
		SYNTAX Gauge32
		MAX-ACCESS read-only
		STATUS current
		DESCRIPTION
			"The minimum local signal quality 
			recorded by the KarlBridge during the radio link test."
		::= { kbWirelessStationEntry 38 }

	kbWirelessTestOurMinSNR OBJECT-TYPE
		SYNTAX Gauge32
		MAX-ACCESS read-only
		STATUS current
		DESCRIPTION
			"The minimum local Signal-to-Noise Ratio (SNR) 
			recorded by the KarlBridge during the radio link test."
		::= { kbWirelessStationEntry 39 }

	kbWirelessTestOurMaxSignalLevel OBJECT-TYPE
		SYNTAX Gauge32
		MAX-ACCESS read-only
		STATUS current
		DESCRIPTION
			"The maximum local signal level 
			recorded by the KarlBridge during the radio link test."
		::= { kbWirelessStationEntry 40 }

	kbWirelessTestOurMaxNoiseLevel OBJECT-TYPE
		SYNTAX Gauge32
		MAX-ACCESS read-only
		STATUS current
		DESCRIPTION
			"The maximum local noise level 
			recorded by the KarlBridge during the radio link test."
		::= { kbWirelessStationEntry 41 }

	kbWirelessTestOurMaxSignalQuality OBJECT-TYPE
		SYNTAX Gauge32
		MAX-ACCESS read-only
		STATUS current
		DESCRIPTION
			"The maximum local signal quality 
			recorded by the KarlBridge during the radio link test."
		::= { kbWirelessStationEntry 42 }

	kbWirelessTestOurMaxSNR OBJECT-TYPE
		SYNTAX Gauge32
		MAX-ACCESS read-only
		STATUS current
		DESCRIPTION
			"The maximum local Signal-to-Noise Ratio (SNR) 
			recorded by the KarlBridge during the radio link test."
		::= { kbWirelessStationEntry 43 }

	kbWirelessTestHisCurSignalLevel OBJECT-TYPE
		SYNTAX Gauge32
		MAX-ACCESS read-only
		STATUS current
		DESCRIPTION
			"The current signal level
			at the remote station for the radio link test."
		::= { kbWirelessStationEntry 44 }

	kbWirelessTestHisCurNoiseLevel OBJECT-TYPE
		SYNTAX Gauge32
		MAX-ACCESS read-only
		STATUS current
		DESCRIPTION
			"The current noise level 
			at the remote station for the radio link test."
		::= { kbWirelessStationEntry 45 }

	kbWirelessTestHisCurSignalQuality OBJECT-TYPE
		SYNTAX Gauge32
		MAX-ACCESS read-only
		STATUS current
		DESCRIPTION
			"The current signal quality 
			at the remote station for the radio link test."
		::= { kbWirelessStationEntry 46 }

	kbWirelessTestHisCurSNR OBJECT-TYPE
		SYNTAX Gauge32 
		MAX-ACCESS read-only
		STATUS current
		DESCRIPTION
			"The current Signal-to-Noise Ratio (SNR) 
			at the remote station for the radio link test."
		::= { kbWirelessStationEntry 47 }

	kbWirelessTestHisMinSignalLevel OBJECT-TYPE
		SYNTAX Gauge32 
		MAX-ACCESS read-only
		STATUS current
		DESCRIPTION
			"The minimum signal level recorded
			at the remote station during the radio link test."
		::= { kbWirelessStationEntry 48 }

	kbWirelessTestHisMinNoiseLevel OBJECT-TYPE
		SYNTAX Gauge32 
		MAX-ACCESS read-only
		STATUS current
		DESCRIPTION
			"The minimum noise level recorded
			at the remote station during the radio link test."
		::= { kbWirelessStationEntry 49 }

	kbWirelessTestHisMinSignalQuality OBJECT-TYPE
		SYNTAX Gauge32
		MAX-ACCESS read-only
		STATUS current
		DESCRIPTION
			"The minimum signal quality recorded
			at the remote station during the radio link test."
		::= { kbWirelessStationEntry 50 }

	kbWirelessTestHisMinSNR OBJECT-TYPE
		SYNTAX Gauge32 
		MAX-ACCESS read-only
		STATUS current
		DESCRIPTION
			"The minimum signal level recorded
			at the remote station during the radio link test."
		::= { kbWirelessStationEntry 51 }

	kbWirelessTestHisMaxSignalLevel OBJECT-TYPE
		SYNTAX Gauge32 
		MAX-ACCESS read-only
		STATUS current
		DESCRIPTION
			"The maximum signal level recorded
			at the remote station during the radio link test."
		::= { kbWirelessStationEntry 52 }

	kbWirelessTestHisMaxNoiseLevel OBJECT-TYPE
		SYNTAX Gauge32 
		MAX-ACCESS read-only
		STATUS current
		DESCRIPTION
			"The maximum remote noise level recorded
			at the remote station during the radio link test."
		::= { kbWirelessStationEntry 53 }

	kbWirelessTestHisMaxSignalQuality OBJECT-TYPE
		SYNTAX Gauge32 
		MAX-ACCESS read-only
		STATUS current
		DESCRIPTION
			"The maximum signal quality recorded
			at the remote station during the radio link test."
		::= { kbWirelessStationEntry 54 }

	kbWirelessTestHisMaxSNR OBJECT-TYPE
		SYNTAX Gauge32 
		MAX-ACCESS read-only
		STATUS current
		DESCRIPTION
			"The maximum Signal-to-Noise Ratio (SNR) recorded
			at the remote station during the radio link test."
		::= { kbWirelessStationEntry 55 }

	kbWirelessTestLinkUp OBJECT-TYPE
		SYNTAX INTEGER
			{        
				down(0),
				up(1)
			} 
		MAX-ACCESS read-only
		STATUS current
		DESCRIPTION
			"The status of the radio link test. Possible values are:
				down(0)	-- the radio link test IS NOT currently running
				up(1)	-- the radio link test IS currently running"
		::= { kbWirelessStationEntry 56 }

	kbWirelessTestLostLink OBJECT-TYPE
		SYNTAX INTEGER
		MAX-ACCESS read-only
		STATUS current
		DESCRIPTION
			"The number of time this link was lost while performing the radio link test."
		::= { kbWirelessStationEntry 57 }

	kbWirelessTestLostTestPkts OBJECT-TYPE
		SYNTAX INTEGER
		MAX-ACCESS read-only
		STATUS current
		DESCRIPTION
			"The total number of radio link test packets 
			that were lost during the test interval."
		::= { kbWirelessStationEntry 58 }

	kbWirelessStationRadioType OBJECT-TYPE
		SYNTAX INTEGER
			{
			waveLAN-I(0),
			clarion-M10(1),
			waveLAN-IEEE(2),
			microwave(3),
			radioLAN(4)
			}
		MAX-ACCESS read-only
		STATUS current
		DESCRIPTION
			"The type of radio the remote station is using on this interface. 
			Possible values include:
				waveLAN-I(0)	-- legacy Lucent Wireless-I radio (900 MHz)
				clarion-M10(1)	-- Clarion M10 radio
				waveLAN-IEEE(2)	-- Lucent ORiNOCO (WaveLAN) IEEE 802.11 radio (2.4 GHz)
				microwave(3)	-- some type of microwave radio
				radioLAN(4) 	-- some type of RadioLAN radio"
		::= { kbWirelessStationEntry 59 }

	kbWirelessRecordType OBJECT-TYPE
		SYNTAX INTEGER
			{
				linktest(1),
				turboCell(2),
				combination(3)
			}
		MAX-ACCESS read-only
		STATUS current
		DESCRIPTION
			"The type of this record entry. Possible values include:
				linktest(1)   	-- This record contains ONLY LinkTest results
				turboCell(2)  	-- This record contains ONLY a TurboCell station entry
				combination(3)	-- This record contains BOTH LinkTest results AND a TurboCell station entry"
		::= { kbWirelessStationEntry 60 }

	kbWirelessStationPktReceives OBJECT-TYPE
		SYNTAX Counter32
		MAX-ACCESS read-only
		STATUS current
		DESCRIPTION 
			"The number of packets the KarlBridge has received on this link."
		::= { kbWirelessStationEntry 61 }

	kbWirelessStationReceives OBJECT-TYPE
		SYNTAX Counter32
		MAX-ACCESS read-only
		STATUS current
		DESCRIPTION 
			"The number of wireless transmissions the KarlBridge has received on this link."
		::= { kbWirelessStationEntry 62 }

	kbWirelessStationBytesReceives OBJECT-TYPE
		SYNTAX Counter32
		MAX-ACCESS read-only
		STATUS current
		DESCRIPTION 
			"The number of bytes received by the KarlBridge on this link, 
			including wireless packet headers."
		::= { kbWirelessStationEntry 63 }

	kbWirelessStationBytesTransmits OBJECT-TYPE
		SYNTAX Counter32
		MAX-ACCESS read-only
		STATUS current
		DESCRIPTION 
			"The number of bytes transmitted by the KarlBridge on this link, 
			including wireless packet headers."
		::= { kbWirelessStationEntry 64 }

	kbWirelessRegistrationRecord OBJECT-TYPE
		SYNTAX OCTET STRING
		MAX-ACCESS read-only
		STATUS obsolete
		DESCRIPTION 
			"For testing purposes only."
		::= { kbWirelessStationEntry 65 }

	kbWirelessStationFragmentDiscards OBJECT-TYPE
		SYNTAX Counter32
		MAX-ACCESS read-only
		STATUS current
		DESCRIPTION 
			"The number of times on this connection that the KarlBridge 
			has discarded a fragment. A fragment is discarded because not all 
			fragments needed to reconstruct a packet are present or 
			we need room for a more recent fragment."
		::= { kbWirelessStationEntry 66 }

	kbWirelessStationFragmentMissings OBJECT-TYPE
		SYNTAX Counter32
		MAX-ACCESS read-only
		STATUS current
		DESCRIPTION 
			"The number of times on this connection that the KarlBridge 
			has detected that a fragment needed to recontruct a packet is missing."
		::= { kbWirelessStationEntry 67 }

	kbWirelessStationFragmentLostFrames OBJECT-TYPE
		SYNTAX Counter32
		MAX-ACCESS read-only
		STATUS current
		DESCRIPTION 
			"The number of times on this connection that the KarlBridge 
			detected that a frame containing fragments needed to 
			reconstruct a packet is lost."
		::= { kbWirelessStationEntry 68 }

	kbWirelessStationFragmentErrors OBJECT-TYPE
		SYNTAX Counter32
		MAX-ACCESS read-only
		STATUS current
		DESCRIPTION 
			"The number of times on this connection the KarlBridge 
			has encountered an error while reconstructing a packet from fragments."
		::= { kbWirelessStationEntry 69 }

-- ***********************************************************************
-- ** THE OID'S BELOW MAY CHANGE AND ARE NOT GUARANTEED TO BE SUPPORTED **
-- **************************************************************************
-- Each of these OID's is a list corresponding to each interface.
-- **************************************************************************
	
--	kbWirelessLocalInterfaceType OBJECT IDENTIFIER
--	OBJECT-TYPE
--		SYNTAX SEQUENCE OF INTEGER 
--			{   
--				compatibility-Mode(1),
--				tc-Peer-to-Peer(2),
--				tc-Base-Station(3),
--				tc-Satellite-Station(4),
--				tc-Polling-Base-Station(5)
--			}
--		MAX-ACCESS read-write
--		STATUS current
--		DESCRIPTION
--				"How the KarlBridge's network interfaces are configured. Possible values are:
--				compatibility-Mode(1)		 IEEE 802.11 mode or legacy Wireless(-I) mode
--				tc-Peer-to-Peer(2)			 TurboCell Peer-to-Peer Station (no base stations, no polling)
--				tc-Base-Station(3)			 TurboCell Base Station
--				tc-Satellite-Station(4)		 TurboCell Satellite Station
--				tc-Polling-Base-Station(5)	 TurboCell Polling Base Station"
--		::= { kbWireless 3 }
--			
--	kbWirelessTestExploreTime OBJECT IDENTIFIER
--	OBJECT-TYPE
--		SYNTAX INTEGER
--		MAX-ACCESS read-write
--		STATUS current
--		DESCRIPTION
--			"Time in seconds for the explore phase of the radio link test.
--			(The explore phase finds suitable partners with which to perform 
--			a radio link test.) It is set to non-zero value to start the test. 
--			The KarlBridge resets the number after starting the explore phase."
--		::= { kbWireless 4 }
--
--	kbWirelessTestExploreRate OBJECT IDENTIFIER
--	OBJECT-TYPE
--		SYNTAX INTEGER
--		MAX-ACCESS read-write
--		STATUS current
--		DESCRIPTION
--			"The interval in hundredths of seconds between radio link test 
--			explore packets."
--		::= { kbWireless 5 }
--                                  


--- **************************************************************************
--  ** END UNSUPPORTED OID'S
--- **************************************************************************
	-------------------------------------------------------------------
	--- KarlBridge SEC MIB module
	---    The Super Ethernet Converter (SEC) tunnels Ethernet traffic 
	---    from multiple client stations to another station by wrapping
	---    each Ethernet packet with a source of the SEC Station and
	---    destination address of the tunnel partner.
	---
	kbSEC OBJECT IDENTIFIER ::= { kbridge-mib 8 }

        kbSECClientTable OBJECT-TYPE
            SYNTAX  SEQUENCE OF KBSECClientEntry
            ACCESS  not-accessible
            STATUS  current
            DESCRIPTION
                    "A table that contains information about Super 
                    Ethernet Converter (SEC) clients and the SEC station 
                    through which they are connected."
            ::= { kbSEC 1 }

          kbSECClientEntry OBJECT-TYPE
              SYNTAX  KBSECClientEntry
              ACCESS  not-accessible
              STATUS  current
              DESCRIPTION
                      "An entry in the kbSECClientTable. Each entry contains
                      the client's MAC address (which is the table index) and
                      the MAC address of the SEC through which the client is
                      connected."
              INDEX   { kbSECClientAddress }
              ::= { kbSECClientTable 1 }

          KBSECClientEntry ::=
              SEQUENCE {
                  kbSECClientAddress
                      MacAddress,
                  kbSECStationAddress
                      MacAddress
              }

          kbSECClientAddress OBJECT-TYPE
              SYNTAX  MacAddress
              ACCESS  read-only
              STATUS  current
              DESCRIPTION
                      "The unicast MAC address of the client station that is
                      connecting through the SEC unit denoted by 
                      kbSECStationAddress."
              ::= { kbSECClientEntry 1 }

          kbSECStationAddress OBJECT-TYPE
              SYNTAX  MacAddress
              ACCESS  read-only
              STATUS  current
              DESCRIPTION
                      "The unicast MAC address of the SEC station through which 
                      the client is connected."
              ::= { kbSECClientEntry 2 }

	-------------------------------------------------------------------
	--- KarlBridge Client Info MIB module              
	---
	---
	kbClientInfo OBJECT IDENTIFIER ::= { kbridge-mib 9 }
                                    
        --------------------
		--- The kbClientInfoByNumberTable, which is the same information as the 
		---   kbClientInfoByMacTable below, but is indexed by virtual port number. 
		---		              
	  	---   	.kbCIbyNumberVirtualPortNumber(1) [ 4 bytes]    
	  	---   	.kbCIbyNumberMACAddress(2)        [ 6 bytes]    
	  	---   	.kbCIByNumberInterfaceNum(3)      [ 4 bytes]
	  	---   	.kbCIbyNumberStationName(4)       [32 bytes]
	  	---   	.kbCIbyNumberTotalBytes(5)        [ 4 bytes]
	  	---   	.kbCIbyNumberTotalPackets(6)      [ 4 bytes]
	  	---   	.kbCIbyNumberSNRAverage(7)        [ 4 bytes]
	  	---   	.kbCIbyNumberTimeLastRecv(8)      [ 4 bytes]
        kbClientInfoByNumberTable OBJECT-TYPE
            SYNTAX  SEQUENCE OF KBClientInfoByNumberEntry
            ACCESS  not-accessible
            STATUS  current
            DESCRIPTION
                    "A table that contains information about (wireless) clients 
                    that pass traffic through this KarlBridge, indexed by a 
                    virtual port number that is unique only within this table."
            ::= { kbClientInfo 1 }

          kbClientInfoByNumberEntry OBJECT-TYPE
              SYNTAX  KBClientInfoByNumberEntry
              ACCESS  not-accessible
              STATUS  current
              DESCRIPTION
                      "An entry in the kbClientInfoByNumberTable. Each entry contains 
                      information for a particular client station indexed by the 
                      client's virtual port number."
              INDEX   { kbCIbyNumberVirtualPort }
              ::= { kbClientInfoByNumberTable 1 }

          KBClientInfoByNumberEntry ::=
              SEQUENCE {
                  kbCIbyNumberVirtualPort
                  	  Unsigned32,
                  kbCIbyNumberMACAddress
                      MacAddress,
                  kbCIByNumberInterfaceNum
                      Unsigned32,
                  kbCIbyNumberStationName
                  	  OCTET STRING,
                  kbCIbyNumberTotalBytes
                      Counter32,
                  kbCIbyNumberTotalPackets
                      Counter32,
                  kbCIbyNumberSNRAverage
                      Gauge32,
                  kbCIbyNumberTimeLastRecv
                      Counter32    
              }

          kbCIbyNumberVirtualPort OBJECT-TYPE
              SYNTAX  Unsigned32 (0..4294967295)
              ACCESS  read-only
              STATUS  current
              DESCRIPTION
                      "The virtual port number to which the client is connected.
                       Used as the index for this table."
              ::= { kbClientInfoByNumberEntry 1 }

          kbCIbyNumberMACAddress OBJECT-TYPE
              SYNTAX  MacAddress
              ACCESS  read-only
              STATUS  current
              DESCRIPTION
                      "The client's unique unicast MAC Address. 
                       This value can be used as the index in the kbClientInfoByMacTable."
              ::= { kbClientInfoByNumberEntry 2 }

          kbCIByNumberInterfaceNum OBJECT-TYPE
              SYNTAX  Unsigned32 (0..4294967295)
              ACCESS  read-only
              STATUS  current
              DESCRIPTION
                      "The KarlBridge interface to which the client is connected."
              ::= { kbClientInfoByNumberEntry 3 }

          kbCIbyNumberStationName OBJECT-TYPE
              SYNTAX  OCTET STRING
              ACCESS  read-only
              STATUS  current
              DESCRIPTION
                      "The client's ASCII Station Name."
              ::= { kbClientInfoByNumberEntry 4 } 
              
          kbCIbyNumberTotalBytes OBJECT-TYPE
              SYNTAX  Counter32
              ACCESS  read-only
              STATUS  current
              DESCRIPTION
                      "The total number of bytes that have been passed through the
                      KarlBridge for this client 
                      (clientTotalBytes = clientSentBytes + clientRecvBytes)"
              ::= { kbClientInfoByNumberEntry 5 }
          
          kbCIbyNumberTotalPackets OBJECT-TYPE
              SYNTAX  Counter32
              ACCESS  read-only
              STATUS  current
              DESCRIPTION
                      "The total number of packets that have been passed through the
                      KarlBridge for this client 
                      (clientTotalPackets = clientSentPackets + clientRecvPackets)"
              ::= { kbClientInfoByNumberEntry 6 }
              
          kbCIbyNumberSNRAverage OBJECT-TYPE
              SYNTAX  Gauge32
              ACCESS  read-only
              STATUS  current
              DESCRIPTION
                      "The running average of the Signal-to-Noise Ratio (SNR)
                      for this client, if the client is connected directly to
                      the KarlBridge on a wireless interface. 0 otherwise."
              ::= { kbClientInfoByNumberEntry 7 }
              
          kbCIbyNumberTimeLastRecv OBJECT-TYPE
              SYNTAX  Counter32
              ACCESS  read-only
              STATUS  current
              DESCRIPTION
                      "The number of time ticks (in 1/100ths of a second) since a
                      packet was last received from this client."
              ::= { kbClientInfoByNumberEntry 8 }
        
	  	--------------------
	  	--- The kbClientInfoByMacTable, which is the same information as the 
	  	---   kbClientInfoByNumberTable above, but is indexed by MAC Address. 
	  	---		              
	  	---   	.kbCIbyMacMACAddress(1)        [ 6 bytes]    
	  	---   	.kbCIbyMacVirtualPort(2)       [ 4 bytes]    
	  	---   	.kbCIByMacInterfaceNum(3)      [ 4 bytes]
	  	---   	.kbCIbyMacStationName(4)       [32 bytes]
	  	---   	.kbCIbyMacTotalBytes(5)        [ 4 bytes]
	  	---   	.kbCIbyMacTotalPackets(6)      [ 4 bytes]
	  	---   	.kbCIbyMacSNRAverage(7)        [ 4 bytes]
	  	---   	.kbCIbyMacTimeLastRecv(8)      [ 4 bytes]
        kbClientInfoByMacTable OBJECT-TYPE
            SYNTAX  SEQUENCE OF KBClientInfoByMacEntry
            ACCESS  not-accessible
            STATUS  current
            DESCRIPTION
                    "A table that contains information about (wireless) clients 
                    that pass traffic through this KarlBridge, indexed by client MAC Address."
            ::= { kbClientInfo 2 }

          kbClientInfoByMacEntry OBJECT-TYPE
              SYNTAX  KBClientInfoByMacEntry
              ACCESS  not-accessible
              STATUS  current
              DESCRIPTION
                      "An entry in the kbClientInfoByMacTable. Each entry contains 
                      information for a particular client station indexed by the 
                      client's unique MAC Address."
              INDEX   { kbCIbyMacMACAddress }
              ::= { kbClientInfoByMacTable 1 }

          KBClientInfoByMacEntry ::=
              SEQUENCE {
                  kbCIbyMacMACAddress
                      MacAddress,
                  kbCIbyMacVirtualPort
                  	  Unsigned32,
                  kbCIbyMacInterfaceNum
                      Unsigned32,
                  kbCIbyMacStationName
                  	  OCTET STRING,
                  kbCIbyMacTotalBytes
                      Counter32,
                  kbCIbyMacTotalPackets
                      Counter32,
                  kbCIbyMacSNRAverage
                      Gauge32,
                  kbCIbyMacTimeLastRecv
                      Counter32    
              }

          kbCIbyMacMACAddress OBJECT-TYPE
              SYNTAX  MacAddress
              ACCESS  read-only
              STATUS  current
              DESCRIPTION
                      "The client's unique unicast MAC Address. 
                       Used as the index for this table."
              ::= { kbClientInfoByMacEntry 1 }

          kbCIbyMacVirtualPort OBJECT-TYPE
              SYNTAX  Unsigned32 (0..4294967295)
              ACCESS  read-only
              STATUS  current
              DESCRIPTION
                      "The virtual port number to which the client is connected.
                       This value can be used as the index in the kbClientInfoByNumberTable."
              ::= { kbClientInfoByMacEntry 2 }

          kbCIbyMacInterfaceNum OBJECT-TYPE
              SYNTAX  Unsigned32 (0..4294967295)
              ACCESS  read-only
              STATUS  current
              DESCRIPTION
                      "The KarlBridge interface to which the client is connected."
              ::= { kbClientInfoByMacEntry 3 }

          kbCIbyMacStationName OBJECT-TYPE
              SYNTAX  OCTET STRING
              ACCESS  read-only
              STATUS  current
              DESCRIPTION
                      "The client's ASCII Station Name."
              ::= { kbClientInfoByMacEntry 4 } 
              
          kbCIbyMacTotalBytes OBJECT-TYPE
              SYNTAX  Counter32
              ACCESS  read-only
              STATUS  current
              DESCRIPTION
                      "The total number of bytes that have been passed through the
                      KarlBridge for this client 
                      (clientTotalBytes = clientSentBytes + clientRecvBytes)"
              ::= { kbClientInfoByMacEntry 5 }
          
          kbCIbyMacTotalPackets OBJECT-TYPE
              SYNTAX  Counter32
              ACCESS  read-only
              STATUS  current
              DESCRIPTION
                      "The total number of packets that have been passed through the
                      KarlBridge for this client 
                      (clientTotalPackets = clientSentPackets + clientRecvPackets)"
              ::= { kbClientInfoByMacEntry 6 }
              
          kbCIbyMacSNRAverage OBJECT-TYPE
              SYNTAX  Gauge32
              ACCESS  read-only
              STATUS  current
              DESCRIPTION
                      "The running average of the Signal-to-Noise Ratio (SNR)
                      for this client, if the client is connected directly to
                      the KarlBridge on a wireless interface. 0 otherwise."
              ::= { kbClientInfoByMacEntry 7 }
              
          kbCIbyMacTimeLastRecv OBJECT-TYPE
              SYNTAX  Counter32
              ACCESS  read-only
              STATUS  current
              DESCRIPTION
                      "The number of time ticks (in 1/100ths of a second) since a
                      packet was last received from this client."
              ::= { kbClientInfoByMacEntry 8 }              
  ---
	--- END of KarlBridge Client Info MIB module
	-------------------------------------------------------------------

END
