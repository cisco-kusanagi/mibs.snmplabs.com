--
-- 	Copyright 1996 Shiva Corporation
--

SHIVA-FLASH-MIB DEFINITIONS ::= BEGIN

IMPORTS
    	OBJECT-TYPE
    		FROM RFC-1212		-- Concise MIB Definitions
	DisplayString
		FROM RFC1213-MIB
	flash
    		FROM SHIVA-MIB;

-- MIB for the contents of a flash memory in a device having a flash
-- memory.  Presently only documents the raw memory statistics, but
-- will later include statistics on each component in the flash.

    flashSize OBJECT-TYPE
	SYNTAX	INTEGER
	ACCESS  read-only
	STATUS  mandatory
	DESCRIPTION
	    	"The size of the flash in bytes."
	::= { flash 1 }

    flashAvailable OBJECT-TYPE
	SYNTAX	INTEGER
	ACCESS  read-only
	STATUS  mandatory
	DESCRIPTION
	    	"The number of bytes available in flash.  Note that
		the flash uses a block structure, so it cannot be
		used at 100% efficiency."
	::= { flash 2 }

-- flash component table

    flashComponentTable	OBJECT-TYPE
	SYNTAX	SEQUENCE OF FlashComponentEntry
	ACCESS	not-accessible
	STATUS	mandatory
	DESCRIPTION
		"A table of flash components."
	::= { flash 3 }

    flashComponentEntry OBJECT-TYPE
	SYNTAX	FlashComponentEntry
	ACCESS	not-accessible
	STATUS	mandatory
	DESCRIPTION
		"Flash component information."
	INDEX { flashComponentIndex }
	::= { flashComponentTable 1 }

    FlashComponentEntry ::= SEQUENCE {
	flashComponentIndex	INTEGER,
	flashComponentName	DisplayString,
	flashComponentRev	DisplayString,
	flashComponentFileName	DisplayString
    }

    flashComponentIndex OBJECT-TYPE
	SYNTAX	INTEGER
	ACCESS	read-only
	STATUS	mandatory
	DESCRIPTION
		"Flash component index."
	::= { flashComponentEntry 1 }

    flashComponentName OBJECT-TYPE
	SYNTAX	DisplayString
	ACCESS	read-only
	STATUS	mandatory
	DESCRIPTION
		"Flash component name."
	::= { flashComponentEntry 2 }

    flashComponentRev OBJECT-TYPE
	SYNTAX	DisplayString
	ACCESS	read-only
	STATUS	mandatory
	DESCRIPTION
		"Flash component revision."
	::= { flashComponentEntry 3 }

    flashComponentFileName OBJECT-TYPE
	SYNTAX	DisplayString
	ACCESS	read-only
	STATUS	mandatory
	DESCRIPTION
		"Flash component filename from rev.c."
	::= { flashComponentEntry 4 }

END
