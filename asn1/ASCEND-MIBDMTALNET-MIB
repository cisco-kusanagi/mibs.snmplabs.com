--			Ascend mibdmtalnet MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBDMTALNET-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibdmtAlDslNetworkProfile  OBJECT IDENTIFIER ::= { configuration 10}

	-- The mibdmtAlDslNetworkProfile table
	--
	-- This table contains parameters for the mibdmtAlDslNetworkProfile profile
	--

    mibdmtAlDslNetworkProfileTable	OBJECT-TYPE
	SYNTAX		SEQUENCE OF MibdmtAlDslNetworkProfileEntry
	ACCESS		not-accessible
	STATUS		mandatory
	DESCRIPTION	"A list of mibdmtAlDslNetworkProfile profile entries."
	::= { mibdmtAlDslNetworkProfile 1 }

    mibdmtAlDslNetworkProfileEntry	OBJECT-TYPE
	SYNTAX		MibdmtAlDslNetworkProfileEntry
	ACCESS		not-accessible
	STATUS		mandatory
	DESCRIPTION	"A mibdmtAlDslNetworkProfile entry containing objects that
			 maps to the parameters of mibdmtAlDslNetworkProfile profile."
	INDEX		{ dmtAlDslNetworkProfile-Shelf-o, dmtAlDslNetworkProfile-Slot-o, dmtAlDslNetworkProfile-Item-o }
	::= { mibdmtAlDslNetworkProfileTable 1 }

    MibdmtAlDslNetworkProfileEntry ::=
	SEQUENCE {
	    dmtAlDslNetworkProfile-Shelf-o
		INTEGER,
	    dmtAlDslNetworkProfile-Slot-o
		INTEGER,
	    dmtAlDslNetworkProfile-Item-o
		INTEGER,
	    dmtAlDslNetworkProfile-Name
		DisplayString,
	    dmtAlDslNetworkProfile-PhysicalAddress-Shelf
		INTEGER,
	    dmtAlDslNetworkProfile-PhysicalAddress-Slot
		INTEGER,
	    dmtAlDslNetworkProfile-PhysicalAddress-ItemNumber
		INTEGER,
	    dmtAlDslNetworkProfile-Enabled
		INTEGER,
	    dmtAlDslNetworkProfile-SparingMode
		INTEGER,
	    dmtAlDslNetworkProfile-ProfileNumber
		INTEGER,
	    dmtAlDslNetworkProfile-IgnoreLineup
		INTEGER,
	    dmtAlDslNetworkProfile-LineConfig-NailedGroup
		INTEGER,
	    dmtAlDslNetworkProfile-LineConfig-VpSwitchingVpi
		INTEGER,
	    dmtAlDslNetworkProfile-LineConfig-RateAdaptModeUp
		INTEGER,
	    dmtAlDslNetworkProfile-LineConfig-RateAdaptModeDown
		INTEGER,
	    dmtAlDslNetworkProfile-LineConfig-RateAdaptRatioUp
		INTEGER,
	    dmtAlDslNetworkProfile-LineConfig-RateAdaptRatioDown
		INTEGER,
	    dmtAlDslNetworkProfile-LineConfig-MaxAggrPowerLevelUp
		INTEGER,
	    dmtAlDslNetworkProfile-LineConfig-MaxAggrPowerLevelDown
		INTEGER,
	    dmtAlDslNetworkProfile-LineConfig-MaxPowerSpectralDensity
		INTEGER,
	    dmtAlDslNetworkProfile-LineConfig-LineCode
		INTEGER,
	    dmtAlDslNetworkProfile-LineConfig-LineLatencyDown
		INTEGER,
	    dmtAlDslNetworkProfile-LineConfig-LineLatencyUp
		INTEGER,
	    dmtAlDslNetworkProfile-LineConfig-TrellisEncoding
		INTEGER,
	    dmtAlDslNetworkProfile-LineConfig-GainDefault
		INTEGER,
	    dmtAlDslNetworkProfile-LineConfig-UpstreamStartBin
		INTEGER,
	    dmtAlDslNetworkProfile-LineConfig-UpstreamEndBin
		INTEGER,
	    dmtAlDslNetworkProfile-LineConfig-DownstreamStartBin
		INTEGER,
	    dmtAlDslNetworkProfile-LineConfig-DownstreamEndBin
		INTEGER,
	    dmtAlDslNetworkProfile-LineConfig-LoopBack
		INTEGER,
	    dmtAlDslNetworkProfile-LineConfig-BitSwapping
		INTEGER,
	    dmtAlDslNetworkProfile-LineConfig-FbmDbmMode
		INTEGER,
	    dmtAlDslNetworkProfile-LineConfig-AlcatelUs413Boost
		INTEGER,
	    dmtAlDslNetworkProfile-FastPathConfig-MinBitrateUp
		INTEGER,
	    dmtAlDslNetworkProfile-FastPathConfig-MinBitrateDown
		INTEGER,
	    dmtAlDslNetworkProfile-FastPathConfig-MaxBitrateUp
		INTEGER,
	    dmtAlDslNetworkProfile-FastPathConfig-MaxBitrateDown
		INTEGER,
	    dmtAlDslNetworkProfile-FastPathConfig-PlannedBitrateUp
		INTEGER,
	    dmtAlDslNetworkProfile-FastPathConfig-PlannedBitrateDown
		INTEGER,
	    dmtAlDslNetworkProfile-InterleavePathConfig-MinBitrateUp
		INTEGER,
	    dmtAlDslNetworkProfile-InterleavePathConfig-MinBitrateDown
		INTEGER,
	    dmtAlDslNetworkProfile-InterleavePathConfig-MaxBitrateUp
		INTEGER,
	    dmtAlDslNetworkProfile-InterleavePathConfig-MaxBitrateDown
		INTEGER,
	    dmtAlDslNetworkProfile-InterleavePathConfig-PlannedBitrateUp
		INTEGER,
	    dmtAlDslNetworkProfile-InterleavePathConfig-PlannedBitrateDown
		INTEGER,
	    dmtAlDslNetworkProfile-InterleavePathConfig-MaxDelayUp
		INTEGER,
	    dmtAlDslNetworkProfile-InterleavePathConfig-MaxDelayDown
		INTEGER,
	    dmtAlDslNetworkProfile-MarginConfig-TargetNoiseMarginUp
		INTEGER,
	    dmtAlDslNetworkProfile-MarginConfig-TargetNoiseMarginDown
		INTEGER,
	    dmtAlDslNetworkProfile-MarginConfig-MinNoiseMarginUp
		INTEGER,
	    dmtAlDslNetworkProfile-MarginConfig-MinNoiseMarginDown
		INTEGER,
	    dmtAlDslNetworkProfile-MarginConfig-MaxAddNoiseMarginUp
		INTEGER,
	    dmtAlDslNetworkProfile-MarginConfig-MaxAddNoiseMarginDown
		INTEGER,
	    dmtAlDslNetworkProfile-MarginConfig-RaDownshiftMarginUp
		INTEGER,
	    dmtAlDslNetworkProfile-MarginConfig-RaDownshiftIntUp
		INTEGER,
	    dmtAlDslNetworkProfile-MarginConfig-RaDownshiftMarginDown
		INTEGER,
	    dmtAlDslNetworkProfile-MarginConfig-RaDownshiftIntDown
		INTEGER,
	    dmtAlDslNetworkProfile-MarginConfig-RaUpshiftMarginUp
		INTEGER,
	    dmtAlDslNetworkProfile-MarginConfig-RaUpshiftIntUp
		INTEGER,
	    dmtAlDslNetworkProfile-MarginConfig-RaUpshiftMarginDown
		INTEGER,
	    dmtAlDslNetworkProfile-MarginConfig-RaUpshiftIntDown
		INTEGER,
	    dmtAlDslNetworkProfile-ThreshProfile
		DisplayString,
	    dmtAlDslNetworkProfile-Action-o
		INTEGER
	}

    dmtAlDslNetworkProfile-Shelf-o	OBJECT-TYPE
	SYNTAX	INTEGER
	ACCESS	read-only
	STATUS	mandatory
	DESCRIPTION	""
	::= { mibdmtAlDslNetworkProfileEntry 1 }

    dmtAlDslNetworkProfile-Slot-o	OBJECT-TYPE
	SYNTAX	INTEGER
	ACCESS	read-only
	STATUS	mandatory
	DESCRIPTION	""
	::= { mibdmtAlDslNetworkProfileEntry 2 }

    dmtAlDslNetworkProfile-Item-o	OBJECT-TYPE
	SYNTAX	INTEGER
	ACCESS	read-only
	STATUS	mandatory
	DESCRIPTION	""
	::= { mibdmtAlDslNetworkProfileEntry 3 }

    dmtAlDslNetworkProfile-Name	OBJECT-TYPE
	SYNTAX	DisplayString
	ACCESS	read-write
	STATUS	mandatory
	DESCRIPTION	"For future use. The current design does not use the name field but instead references Cell Based Dmt Adsl lines by the physical address; we may in the future support referencing Cell Based Dmt Adsl lines by name as well as by address. The name consists of a null terminated ascii string supplied by the user; it defaults to the ascii form of the Cell Based Dmt Adsl line physical address."
	::= { mibdmtAlDslNetworkProfileEntry 4 }

    dmtAlDslNetworkProfile-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibdmtAlDslNetworkProfileEntry 5 }

    dmtAlDslNetworkProfile-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibdmtAlDslNetworkProfileEntry 6 }

    dmtAlDslNetworkProfile-PhysicalAddress-ItemNumber	OBJECT-TYPE
	SYNTAX	INTEGER
	ACCESS	read-write
	STATUS	mandatory
	DESCRIPTION	"A number that specifies an addressable entity within the context of shelf and slot."
	::= { mibdmtAlDslNetworkProfileEntry 7 }

    dmtAlDslNetworkProfile-Enabled	OBJECT-TYPE
	SYNTAX	INTEGER {
		    no (1),
		    yes (2)
		}
	ACCESS	read-write
	STATUS	mandatory
	DESCRIPTION	"TRUE if the line is enabled, otherwise FALSE."
	::= { mibdmtAlDslNetworkProfileEntry 8 }

    dmtAlDslNetworkProfile-SparingMode	OBJECT-TYPE
	SYNTAX	INTEGER {
		    inactive (1),
		    manual (2),
		    automatic (3)
		}
	ACCESS	read-write
	STATUS	mandatory
	DESCRIPTION	"Port sparing operational mode for this port."
	::= { mibdmtAlDslNetworkProfileEntry 63 }

    dmtAlDslNetworkProfile-ProfileNumber	OBJECT-TYPE
	SYNTAX	INTEGER
	ACCESS	read-write
	STATUS	mandatory
	DESCRIPTION	"For potential backwards compatibility. The current design consists of one line profile numbered 0."
	::= { mibdmtAlDslNetworkProfileEntry 9 }

    dmtAlDslNetworkProfile-IgnoreLineup	OBJECT-TYPE
	SYNTAX	INTEGER {
		    systemDefined (1),
		    no (2),
		    yes (3)
		}
	ACCESS	read-write
	STATUS	mandatory
	DESCRIPTION	"Ignore line up value for this port."
	::= { mibdmtAlDslNetworkProfileEntry 73 }

    dmtAlDslNetworkProfile-LineConfig-NailedGroup	OBJECT-TYPE
	SYNTAX	INTEGER
	ACCESS	read-write
	STATUS	mandatory
	DESCRIPTION	"A number that identifies the set of lines that makes up a nailed group. 0 means this line is not part of a nailed group."
	::= { mibdmtAlDslNetworkProfileEntry 11 }

    dmtAlDslNetworkProfile-LineConfig-VpSwitchingVpi	OBJECT-TYPE
	SYNTAX	INTEGER
	ACCESS	read-write
	STATUS	mandatory
	DESCRIPTION	"The Vpi to be used for the VP switching. Rest of the VPIs within valid vpi-vci-range will be used for the VC switching. Changes in this range will take effect immediately. THE USER SHOULD BE VERY CAREFUL WHILE CHANGING THIS VALUE BECAUSE ALL CONNECTIONS ON THE LIM WHERE THIS PORT BELONGS WILL BE DROPPED IN ORDER TO MAKE THIS NEW VALUE EFFECTIVE IMMEDIATELY."
	::= { mibdmtAlDslNetworkProfileEntry 55 }

    dmtAlDslNetworkProfile-LineConfig-RateAdaptModeUp	OBJECT-TYPE
	SYNTAX	INTEGER {
		    operator (1),
		    automaticAtStartup (2),
		    dynamic (3)
		}
	ACCESS	read-write
	STATUS	mandatory
	DESCRIPTION	"The up stream rate adaptive mode of operation. ONLY OPERATOR_CONTROLLED and AUTOMATIC_AT_STARTUP are currently supported. "
	::= { mibdmtAlDslNetworkProfileEntry 19 }

    dmtAlDslNetworkProfile-LineConfig-RateAdaptModeDown	OBJECT-TYPE
	SYNTAX	INTEGER {
		    operator (1),
		    automaticAtStartup (2),
		    dynamic (3)
		}
	ACCESS	read-write
	STATUS	mandatory
	DESCRIPTION	"The down stream rate adaptive mode of operation. ONLY OPERATOR_CONTROLLED and AUTOMATIC_AT_STARTUP are currently supported. "
	::= { mibdmtAlDslNetworkProfileEntry 20 }

    dmtAlDslNetworkProfile-LineConfig-RateAdaptRatioUp	OBJECT-TYPE
	SYNTAX	INTEGER
	ACCESS	read-write
	STATUS	mandatory
	DESCRIPTION	"The ratio in percent of excess bitrate distribution over the up stream fast and interleaved latencies. 100% - fast path , 0% - interleaved path. Valid ONLY in rate-adapt-mode = AUTOMATIC_AT_STARTUP or DYNAMIC . "
	::= { mibdmtAlDslNetworkProfileEntry 21 }

    dmtAlDslNetworkProfile-LineConfig-RateAdaptRatioDown	OBJECT-TYPE
	SYNTAX	INTEGER
	ACCESS	read-write
	STATUS	mandatory
	DESCRIPTION	"The ratio in percent of excess bitrate distribution over the down stream fast and interleaved latencies. 100% - fast path , 0% - interleaved path. Valid ONLY in rate-adapt-mode = AUTOMATIC_AT_STARTUP or DYNAMIC . "
	::= { mibdmtAlDslNetworkProfileEntry 22 }

    dmtAlDslNetworkProfile-LineConfig-MaxAggrPowerLevelUp	OBJECT-TYPE
	SYNTAX	INTEGER
	ACCESS	read-write
	STATUS	mandatory
	DESCRIPTION	"The maximum aggregate output power in dBm allowed on the line in the up stream direction. Increasing value may result in capacity boosting. "
	::= { mibdmtAlDslNetworkProfileEntry 56 }

    dmtAlDslNetworkProfile-LineConfig-MaxAggrPowerLevelDown	OBJECT-TYPE
	SYNTAX	INTEGER
	ACCESS	read-write
	STATUS	mandatory
	DESCRIPTION	"The maximum aggregate output power in dBm allowed on the line in the down stream direction. Increasing value may result in capacity boosting. "
	::= { mibdmtAlDslNetworkProfileEntry 57 }

    dmtAlDslNetworkProfile-LineConfig-MaxPowerSpectralDensity	OBJECT-TYPE
	SYNTAX	INTEGER
	ACCESS	read-write
	STATUS	mandatory
	DESCRIPTION	"The power spectral density in dBm/Hz allowed on the line. Decreasing the value may reduce capacity. Defined for downstream only. Actual value is negative."
	::= { mibdmtAlDslNetworkProfileEntry 25 }

    dmtAlDslNetworkProfile-LineConfig-LineCode	OBJECT-TYPE
	SYNTAX	INTEGER {
		    autoSelect (3),
		    gLite (2),
		    ansiDmt (4),
		    gDmt (5),
		    legacyMode (6),
		    etsiAnnexB (7)
		}
	ACCESS	read-write
	STATUS	mandatory
	DESCRIPTION	"The DMT line code is used for the training. NOTE: for the ADSL 12-ports LIM card only (which uses the ALCATEL chipset), setting the line code to ansi-dmt will provide better line rate than auto-select for an ansi-dmt link. Therefore, set the line code to ansi-dmt for an ansi-dmt link to obtain optimal rate."
	::= { mibdmtAlDslNetworkProfileEntry 58 }

    dmtAlDslNetworkProfile-LineConfig-LineLatencyDown	OBJECT-TYPE
	SYNTAX	INTEGER {
		    none (1),
		    fast (2),
		    interleave (3),
		    both (4)
		}
	ACCESS	read-write
	STATUS	mandatory
	DESCRIPTION	"The DMT line latency to be used for the downstream data transport."
	::= { mibdmtAlDslNetworkProfileEntry 59 }

    dmtAlDslNetworkProfile-LineConfig-LineLatencyUp	OBJECT-TYPE
	SYNTAX	INTEGER {
		    none (1),
		    fast (2),
		    interleave (3),
		    both (4)
		}
	ACCESS	read-write
	STATUS	mandatory
	DESCRIPTION	"The DMT line latency to be used for the upstream data transport."
	::= { mibdmtAlDslNetworkProfileEntry 60 }

    dmtAlDslNetworkProfile-LineConfig-TrellisEncoding	OBJECT-TYPE
	SYNTAX	INTEGER {
		    no (1),
		    yes (2)
		}
	ACCESS	read-write
	STATUS	mandatory
	DESCRIPTION	"TRUE if trellis encoding is to be enabled, FALSE otherwise."
	::= { mibdmtAlDslNetworkProfileEntry 61 }

    dmtAlDslNetworkProfile-LineConfig-GainDefault	OBJECT-TYPE
	SYNTAX	INTEGER {
		    n-20Db (2),
		    n-16Db (1)
		}
	ACCESS	read-write
	STATUS	mandatory
	DESCRIPTION	"The default gain value in db to be used for the AGC."
	::= { mibdmtAlDslNetworkProfileEntry 62 }

    dmtAlDslNetworkProfile-LineConfig-UpstreamStartBin	OBJECT-TYPE
	SYNTAX	INTEGER
	ACCESS	read-write
	STATUS	mandatory
	DESCRIPTION	"The starting upstream frequency bin."
	::= { mibdmtAlDslNetworkProfileEntry 64 }

    dmtAlDslNetworkProfile-LineConfig-UpstreamEndBin	OBJECT-TYPE
	SYNTAX	INTEGER
	ACCESS	read-write
	STATUS	mandatory
	DESCRIPTION	"The ending upstream frequency bin."
	::= { mibdmtAlDslNetworkProfileEntry 65 }

    dmtAlDslNetworkProfile-LineConfig-DownstreamStartBin	OBJECT-TYPE
	SYNTAX	INTEGER
	ACCESS	read-write
	STATUS	mandatory
	DESCRIPTION	"The starting downstream frequency bin."
	::= { mibdmtAlDslNetworkProfileEntry 66 }

    dmtAlDslNetworkProfile-LineConfig-DownstreamEndBin	OBJECT-TYPE
	SYNTAX	INTEGER
	ACCESS	read-write
	STATUS	mandatory
	DESCRIPTION	"The ending downstream frequency bin."
	::= { mibdmtAlDslNetworkProfileEntry 67 }

    dmtAlDslNetworkProfile-LineConfig-LoopBack	OBJECT-TYPE
	SYNTAX	INTEGER {
		    none (1),
		    analog (2),
		    digital (3)
		}
	ACCESS	read-write
	STATUS	mandatory
	DESCRIPTION	"Configuration of different modem loopbacks."
	::= { mibdmtAlDslNetworkProfileEntry 69 }

    dmtAlDslNetworkProfile-LineConfig-BitSwapping	OBJECT-TYPE
	SYNTAX	INTEGER {
		    no (1),
		    yes (2)
		}
	ACCESS	read-write
	STATUS	mandatory
	DESCRIPTION	"Controls wether Bit-Swapping is enabled or no. On 12 port DMT card and 48 port G.lite card has not effect."
	::= { mibdmtAlDslNetworkProfileEntry 70 }

    dmtAlDslNetworkProfile-LineConfig-FbmDbmMode	OBJECT-TYPE
	SYNTAX	INTEGER {
		    fbm (1),
		    dbm (2)
		}
	ACCESS	read-write
	STATUS	mandatory
	DESCRIPTION	"Controls wether the line is in Fixed-Bit-Map or Dual-Bit-Map mode. Only relevant for Annex-C cards."
	::= { mibdmtAlDslNetworkProfileEntry 71 }

    dmtAlDslNetworkProfile-LineConfig-AlcatelUs413Boost	OBJECT-TYPE
	SYNTAX	INTEGER {
		    new (1),
		    old (2),
		    unknown (3)
		}
	ACCESS	read-write
	STATUS	mandatory
	DESCRIPTION	"Provides an increase in upstream rate in T1.413 mode for 24/48 Port Annex A boards based on the Globespan chip set when connected to an Alcatel CPE. Irrelevant for any other situtation. Use with extreme caution."
	::= { mibdmtAlDslNetworkProfileEntry 74 }

    dmtAlDslNetworkProfile-FastPathConfig-MinBitrateUp	OBJECT-TYPE
	SYNTAX	INTEGER
	ACCESS	read-write
	STATUS	mandatory
	DESCRIPTION	"The up stream minimum requested bitrate, in Kbps. NOT valid in rate-adapt-mode = OPERATOR_CONTROLLED. "
	::= { mibdmtAlDslNetworkProfileEntry 26 }

    dmtAlDslNetworkProfile-FastPathConfig-MinBitrateDown	OBJECT-TYPE
	SYNTAX	INTEGER
	ACCESS	read-write
	STATUS	mandatory
	DESCRIPTION	"The down stream minimum requested bitrate, in Kbps. NOT valid in rate-adapt-mode = OPERATOR_CONTROLLED. "
	::= { mibdmtAlDslNetworkProfileEntry 27 }

    dmtAlDslNetworkProfile-FastPathConfig-MaxBitrateUp	OBJECT-TYPE
	SYNTAX	INTEGER
	ACCESS	read-write
	STATUS	mandatory
	DESCRIPTION	"The up stream maximum requested bitrate, in Kbps. NOT valid in rate-adapt-mode = OPERATOR_CONTROLLED. "
	::= { mibdmtAlDslNetworkProfileEntry 28 }

    dmtAlDslNetworkProfile-FastPathConfig-MaxBitrateDown	OBJECT-TYPE
	SYNTAX	INTEGER
	ACCESS	read-write
	STATUS	mandatory
	DESCRIPTION	"The down stream maximum requested bitrate, in Kbps. NOT valid in rate-adapt-mode = OPERATOR_CONTROLLED. "
	::= { mibdmtAlDslNetworkProfileEntry 29 }

    dmtAlDslNetworkProfile-FastPathConfig-PlannedBitrateUp	OBJECT-TYPE
	SYNTAX	INTEGER
	ACCESS	read-write
	STATUS	mandatory
	DESCRIPTION	"The up stream rate that will be used, in Kbps. ONLY valid in rate-adapt-mode = OPERATOR_CONTROLLED. "
	::= { mibdmtAlDslNetworkProfileEntry 30 }

    dmtAlDslNetworkProfile-FastPathConfig-PlannedBitrateDown	OBJECT-TYPE
	SYNTAX	INTEGER
	ACCESS	read-write
	STATUS	mandatory
	DESCRIPTION	"The down stream rate that will be used, in Kbps. ONLY valid in rate-adapt-mode = OPERATOR_CONTROLLED. "
	::= { mibdmtAlDslNetworkProfileEntry 31 }

    dmtAlDslNetworkProfile-InterleavePathConfig-MinBitrateUp	OBJECT-TYPE
	SYNTAX	INTEGER
	ACCESS	read-write
	STATUS	mandatory
	DESCRIPTION	"The up stream minimum requested bitrate, in Kbps. NOT valid in rate-adapt-mode = OPERATOR_CONTROLLED. "
	::= { mibdmtAlDslNetworkProfileEntry 32 }

    dmtAlDslNetworkProfile-InterleavePathConfig-MinBitrateDown	OBJECT-TYPE
	SYNTAX	INTEGER
	ACCESS	read-write
	STATUS	mandatory
	DESCRIPTION	"The down stream minimum requested bitrate, in Kbps. NOT valid in rate-adapt-mode = OPERATOR_CONTROLLED. "
	::= { mibdmtAlDslNetworkProfileEntry 33 }

    dmtAlDslNetworkProfile-InterleavePathConfig-MaxBitrateUp	OBJECT-TYPE
	SYNTAX	INTEGER
	ACCESS	read-write
	STATUS	mandatory
	DESCRIPTION	"The up stream maximum requested bitrate, in Kbps. NOT valid in rate-adapt-mode = OPERATOR_CONTROLLED. "
	::= { mibdmtAlDslNetworkProfileEntry 34 }

    dmtAlDslNetworkProfile-InterleavePathConfig-MaxBitrateDown	OBJECT-TYPE
	SYNTAX	INTEGER
	ACCESS	read-write
	STATUS	mandatory
	DESCRIPTION	"The down stream maximum requested bitrate, in Kbps. NOT valid in rate-adapt-mode = OPERATOR_CONTROLLED. "
	::= { mibdmtAlDslNetworkProfileEntry 35 }

    dmtAlDslNetworkProfile-InterleavePathConfig-PlannedBitrateUp	OBJECT-TYPE
	SYNTAX	INTEGER
	ACCESS	read-write
	STATUS	mandatory
	DESCRIPTION	"The up stream rate that will be used, in Kbps. ONLY valid in rate-adapt-mode = OPERATOR_CONTROLLED. "
	::= { mibdmtAlDslNetworkProfileEntry 36 }

    dmtAlDslNetworkProfile-InterleavePathConfig-PlannedBitrateDown	OBJECT-TYPE
	SYNTAX	INTEGER
	ACCESS	read-write
	STATUS	mandatory
	DESCRIPTION	"The down stream rate that will be used, in Kbps. ONLY valid in rate-adapt-mode = OPERATOR_CONTROLLED. "
	::= { mibdmtAlDslNetworkProfileEntry 37 }

    dmtAlDslNetworkProfile-InterleavePathConfig-MaxDelayUp	OBJECT-TYPE
	SYNTAX	INTEGER
	ACCESS	read-write
	STATUS	mandatory
	DESCRIPTION	"The maximum allowed up stream interleaver induced delay, in msec. "
	::= { mibdmtAlDslNetworkProfileEntry 38 }

    dmtAlDslNetworkProfile-InterleavePathConfig-MaxDelayDown	OBJECT-TYPE
	SYNTAX	INTEGER
	ACCESS	read-write
	STATUS	mandatory
	DESCRIPTION	"The maximum allowed down stream interleaver induced delay, in msec. "
	::= { mibdmtAlDslNetworkProfileEntry 39 }

    dmtAlDslNetworkProfile-MarginConfig-TargetNoiseMarginUp	OBJECT-TYPE
	SYNTAX	INTEGER
	ACCESS	read-write
	STATUS	mandatory
	DESCRIPTION	"The up stream noise margin in dB that the modem shall achieve relative to BER 10^-7. "
	::= { mibdmtAlDslNetworkProfileEntry 40 }

    dmtAlDslNetworkProfile-MarginConfig-TargetNoiseMarginDown	OBJECT-TYPE
	SYNTAX	INTEGER
	ACCESS	read-write
	STATUS	mandatory
	DESCRIPTION	"The down stream noise margin in dB that the modem shall achieve relative to BER 10^-7. "
	::= { mibdmtAlDslNetworkProfileEntry 41 }

    dmtAlDslNetworkProfile-MarginConfig-MinNoiseMarginUp	OBJECT-TYPE
	SYNTAX	INTEGER
	ACCESS	read-write
	STATUS	mandatory
	DESCRIPTION	"The up stream minimum noise margin in dB that the modem shall tolerate relative to BER 10^-7. If current noise margin falls below this level the ATU shall attempt to increase far-end output power to get margin above this limit, by means of bit swapping. "
	::= { mibdmtAlDslNetworkProfileEntry 42 }

    dmtAlDslNetworkProfile-MarginConfig-MinNoiseMarginDown	OBJECT-TYPE
	SYNTAX	INTEGER
	ACCESS	read-write
	STATUS	mandatory
	DESCRIPTION	"The down stream minimum noise margin in dB that the modem shall tolerate relative to BER 10^-7. If current noise margin falls below this level the ATU shall attempt to increase far-end output power to get margin above this limit, by means of bit swapping. "
	::= { mibdmtAlDslNetworkProfileEntry 43 }

    dmtAlDslNetworkProfile-MarginConfig-MaxAddNoiseMarginUp	OBJECT-TYPE
	SYNTAX	INTEGER
	ACCESS	read-write
	STATUS	mandatory
	DESCRIPTION	"The up stream maximum noise margin in dB on top of the target-noise-margin that the modem shall tolerate relative to BER 10^-7. If current noise margin is above this level the ATU shall attempt to reduce far-end output power to get margin below this limit, by means of bit swapping. "
	::= { mibdmtAlDslNetworkProfileEntry 44 }

    dmtAlDslNetworkProfile-MarginConfig-MaxAddNoiseMarginDown	OBJECT-TYPE
	SYNTAX	INTEGER
	ACCESS	read-write
	STATUS	mandatory
	DESCRIPTION	"The down stream maximum noise margin in dB on top of the target-noise-margin that the modem shall tolerate relative to BER 10^-7. If current noise margin is above this level the ATU shall attempt to reduce far-end output power to get margin below this limit, by means of bit swapping. "
	::= { mibdmtAlDslNetworkProfileEntry 45 }

    dmtAlDslNetworkProfile-MarginConfig-RaDownshiftMarginUp	OBJECT-TYPE
	SYNTAX	INTEGER
	ACCESS	read-write
	STATUS	mandatory
	DESCRIPTION	"Valid ONLY in rate-adapt-mode = DYNAMIC. In dB. If current up stream noise margin is below this parameter for more than ra-downshift-int-up sec, modem shall attemp to rate adapt (bitrate down). "
	::= { mibdmtAlDslNetworkProfileEntry 46 }

    dmtAlDslNetworkProfile-MarginConfig-RaDownshiftIntUp	OBJECT-TYPE
	SYNTAX	INTEGER
	ACCESS	read-write
	STATUS	mandatory
	DESCRIPTION	"Valid ONLY in rate-adapt-mode = DYNAMIC. In seconds. If current up stream noise margin is below ra-downshift-margin-up for more than this, modem shall attemp to rate adapt (bitrate down). "
	::= { mibdmtAlDslNetworkProfileEntry 47 }

    dmtAlDslNetworkProfile-MarginConfig-RaDownshiftMarginDown	OBJECT-TYPE
	SYNTAX	INTEGER
	ACCESS	read-write
	STATUS	mandatory
	DESCRIPTION	"Valid ONLY in rate-adapt-mode = DYNAMIC. In dB. If current down stream noise margin is below this parameter for more than ra-downshift-int-down sec, modem shall attemp to rate adapt (bitrate down). "
	::= { mibdmtAlDslNetworkProfileEntry 48 }

    dmtAlDslNetworkProfile-MarginConfig-RaDownshiftIntDown	OBJECT-TYPE
	SYNTAX	INTEGER
	ACCESS	read-write
	STATUS	mandatory
	DESCRIPTION	"Valid ONLY in rate-adapt-mode = DYNAMIC. In seconds. If current down stream noise margin is below ra-downshift-margin-down for more than this, modem shall attemp to rate adapt (bitrate down). "
	::= { mibdmtAlDslNetworkProfileEntry 49 }

    dmtAlDslNetworkProfile-MarginConfig-RaUpshiftMarginUp	OBJECT-TYPE
	SYNTAX	INTEGER
	ACCESS	read-write
	STATUS	mandatory
	DESCRIPTION	"Valid ONLY in rate-adapt-mode = DYNAMIC. In dB. If current up stream noise margin is above this parameter for more than ra-downshift-int-up sec, modem shall attemp to rate adapt (bitrate up). "
	::= { mibdmtAlDslNetworkProfileEntry 50 }

    dmtAlDslNetworkProfile-MarginConfig-RaUpshiftIntUp	OBJECT-TYPE
	SYNTAX	INTEGER
	ACCESS	read-write
	STATUS	mandatory
	DESCRIPTION	"Valid ONLY in rate-adapt-mode = DYNAMIC. In seconds. If current up stream noise margin is above ra-downshift-margin-up for more than this, modem shall attemp to rate adapt (bitrate up). "
	::= { mibdmtAlDslNetworkProfileEntry 51 }

    dmtAlDslNetworkProfile-MarginConfig-RaUpshiftMarginDown	OBJECT-TYPE
	SYNTAX	INTEGER
	ACCESS	read-write
	STATUS	mandatory
	DESCRIPTION	"Valid ONLY in rate-adapt-mode = DYNAMIC. In dB. If current down stream noise margin is above this parameter for more than ra-downshift-int-down sec, modem shall attemp to rate adapt (bitrate up). "
	::= { mibdmtAlDslNetworkProfileEntry 52 }

    dmtAlDslNetworkProfile-MarginConfig-RaUpshiftIntDown	OBJECT-TYPE
	SYNTAX	INTEGER
	ACCESS	read-write
	STATUS	mandatory
	DESCRIPTION	"Valid ONLY in rate-adapt-mode = DYNAMIC. In seconds. If current down stream noise margin is above ra-downshift-margin-down for more than this, modem shall attemp to rate adapt (bitrate up). "
	::= { mibdmtAlDslNetworkProfileEntry 53 }

    dmtAlDslNetworkProfile-ThreshProfile	OBJECT-TYPE
	SYNTAX	DisplayString
	ACCESS	read-write
	STATUS	mandatory
	DESCRIPTION	"The name of the DSL-THRESHOLD profile which applies to this ADSL line. "
	::= { mibdmtAlDslNetworkProfileEntry 72 }

    dmtAlDslNetworkProfile-Action-o	OBJECT-TYPE
	SYNTAX	INTEGER {
		    noAction (1),
		    createProfile (2),
		    deleteProfile (3)
		}
	ACCESS	read-write
	STATUS	mandatory
	DESCRIPTION	""
	::= { mibdmtAlDslNetworkProfileEntry 54 }

END
