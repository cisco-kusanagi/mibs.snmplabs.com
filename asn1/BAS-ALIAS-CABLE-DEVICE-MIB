BAS-ALIAS-CABLE-DEVICE-MIB DEFINITIONS ::= BEGIN

IMPORTS
	MODULE-IDENTITY, OBJECT-TYPE, 
	-- BITS, 
	IpAddress, Unsigned32,
	Integer32, Counter32			FROM SNMPv2-SMI

	DisplayString, RowStatus,
	DateAndTime, TruthValue,
	TEXTUAL-CONVENTION				FROM SNMPv2-TC

	--      InterfaceIndexOrZero
	--              FROM IF-MIB;

	basAliasDocsCd, BasChassisId,
	BasSlotId, BasInterfaceId,
	BasLogicalPortId				FROM BAS-MIB;


basAliasDocsCdMib MODULE-IDENTITY
	LAST-UPDATED "9810081200Z"
	ORGANIZATION "Broadband Access Systems"
	CONTACT-INFO
		" Tech Support
		  Broadband Access Systems
		  201 Forest Street
		  Marlboro, MA  01752
		  U.S.A.
		  
		  508-485-8200
		  support@basystems.com"
	DESCRIPTION
		"This MIB module defines the Alias DocsCd MIB objects
		 for a Broadband Access System Cluster."
	::= { basAliasDocsCd 1 }

-- The following textual convention is from the
-- Interfaces MIB draft. It should go away once this
-- draft has been published as RFC.

InterfaceIndexOrZero ::= TEXTUAL-CONVENTION
    DISPLAY-HINT "d"
    STATUS       current
    DESCRIPTION
            "This textual convention is an extension of the


            InterfaceIndex convention.  The latter defines a
            greater than zero value used to identify an interface
            or interface sub-layer in the managed system.  This
            extension permits the additional value of zero.  the
            value zero is object-specific and must therefore be
            defined as part of the description of any object which
            uses this syntax.  Examples of the usage of zero might
            include situations where interface was unknown, or
            when none or all interfaces need to be referenced."
    SYNTAX       Integer32 (0..2147483647)

basDocsDevMIBObjects  OBJECT IDENTIFIER ::= { basAliasDocsCdMib 1 }

basDocsDevBase OBJECT IDENTIFIER ::= { basDocsDevMIBObjects 1 }

basDocsDevBaseTable OBJECT-TYPE
        SYNTAX      SEQUENCE OF BasDocsDevBaseEntry
        MAX-ACCESS  not-accessible
        STATUS      current
        DESCRIPTION
            ""
        ::= { basDocsDevBase 1 }

basDocsDevBaseEntry OBJECT-TYPE
        SYNTAX      BasDocsDevBaseEntry
        MAX-ACCESS  not-accessible
        STATUS      current
        DESCRIPTION
			""
        INDEX { 
				basDocsDevChassis,
				basDocsDevSlot,
				basDocsDevIf,
				basDocsDevLPort
				}
        ::= { basDocsDevBaseTable 1 }

BasDocsDevBaseEntry ::= SEQUENCE {
			basDocsDevRole						INTEGER,
			basDocsDevDateTime					DateAndTime,
			basDocsDevResetNow					TruthValue,
			basDocsDevSerialNumber				DisplayString,
			basDocsDevSTPControl				INTEGER,
			basDocsDevChassis					BasChassisId,
			basDocsDevSlot						BasSlotId,
			basDocsDevIf						BasInterfaceId,
			basDocsDevLPort						BasLogicalPortId
        }

--
-- For the following object, there is no concept in the
-- RFI specification corresponding to a backup CMTS. The
-- enumeration is provided here in case someone is able
-- to define such a role or device.
--

basDocsDevRole OBJECT-TYPE
        SYNTAX INTEGER {
            cm(1),
            cmtsActive(2),
            cmtsBackup(3)
        }
        MAX-ACCESS  read-only
        STATUS      current
        DESCRIPTION
            "Defines the current role of this device."
        ::= { basDocsDevBaseEntry 1 }

basDocsDevDateTime OBJECT-TYPE
        SYNTAX      DateAndTime
        MAX-ACCESS  read-write
        STATUS      current
        DESCRIPTION
            "The date and time, with optional timezone information."
        ::= { basDocsDevBaseEntry 2 }

basDocsDevResetNow OBJECT-TYPE
        SYNTAX      TruthValue
        MAX-ACCESS  read-write
        STATUS      current
        DESCRIPTION
            "Setting this object to true(1) causes the device to reset.
             Reading this object always returns false(2)."
        ::= { basDocsDevBaseEntry 3 }

basDocsDevSerialNumber OBJECT-TYPE
        SYNTAX      DisplayString


        MAX-ACCESS  read-only
        STATUS      current
        DESCRIPTION
            "The manufacturer's serial number for this device."
        ::= { basDocsDevBaseEntry 4 }

basDocsDevSTPControl OBJECT-TYPE
        SYNTAX INTEGER {
            stEnabled(1),
            noStFilterBpdu(2),
            noStPassBpdu(3)
        }
        MAX-ACCESS  read-write
        STATUS      current
        DESCRIPTION
            "This object controls operation of the spanning tree
             protocol (as distinguished from transparent bridging).
             If set to stEnabled(1) then the spanning tree protocol
             is enabled, subject to bridging constraints. If
             noStFilterBpdu(2), then spanning tree is not active,
             and Bridge PDUs received are discarded.
             If noStPassBpdu(3) then spanning tree is not active
             and Bridge PDUs are transparently forwarded. Note that
             a device need not implement all of these options,
             but that noStFilterBpdu(2) is required."
        ::= { basDocsDevBaseEntry 5 }

basDocsDevChassis OBJECT-TYPE
	SYNTAX		BasChassisId
	MAX-ACCESS	not-accessible
	STATUS		current
	DESCRIPTION
		"The BAS Chassis ID of this card."
	::= { basDocsDevBaseEntry 6 }

basDocsDevSlot OBJECT-TYPE
	SYNTAX		BasSlotId
	MAX-ACCESS	not-accessible
	STATUS		current
	DESCRIPTION
		"The BAS Slot ID of this card."
	::= { basDocsDevBaseEntry 7 }

basDocsDevIf OBJECT-TYPE
	SYNTAX		BasInterfaceId
	MAX-ACCESS	not-accessible
	STATUS		current
	DESCRIPTION
		"The BAS interface ID of this card."
	::= { basDocsDevBaseEntry 8 }

basDocsDevLPort OBJECT-TYPE
	SYNTAX		BasLogicalPortId
	MAX-ACCESS	not-accessible
	STATUS		current
	DESCRIPTION
		"The BAS logical port ID of this card."
	::= { basDocsDevBaseEntry 9 }


--
-- The following table provides one level of security for access
-- to the device by network management stations.
-- Note that access is also constrained by the
-- community strings and any vendor-specific security.
--

basDocsDevNmAccessTable OBJECT-TYPE
        SYNTAX      SEQUENCE OF BasDocsDevNmAccessEntry
        MAX-ACCESS  not-accessible
        STATUS      current
        DESCRIPTION
            "This table controls access to SNMP objects by network
             management stations. If the table is empty, access
             to SNMP objects is unrestricted."
        ::= { basDocsDevMIBObjects 2 }

basDocsDevNmAccessEntry OBJECT-TYPE
        SYNTAX      BasDocsDevNmAccessEntry
        MAX-ACCESS  not-accessible
        STATUS      current
        DESCRIPTION
            "Controls access to SNMP objects by a particular network
             management station. For each entry in this table, the
             contents are not readable unless the management station
             has read-write permission."
        INDEX { 
				basDocsDevNmAccessChassis,
				basDocsDevNmAccessSlot,
				basDocsDevNmAccessIf,
				basDocsDevNmAccessLPort,
				basDocsDevNmAccessIndex  }
        ::= {  basDocsDevNmAccessTable 1 }

BasDocsDevNmAccessEntry ::= SEQUENCE {
            basDocsDevNmAccessIndex         INTEGER,
            basDocsDevNmAccessIp            IpAddress,
            basDocsDevNmAccessIpMask        IpAddress,
            basDocsDevNmAccessCommunity     DisplayString,
            basDocsDevNmAccessControl       INTEGER,
            basDocsDevNmAccessInterfaces    OCTET STRING,
            basDocsDevNmAccessStatus        RowStatus,
			basDocsDevNmAccessChassis		BasChassisId,
			basDocsDevNmAccessSlot			BasSlotId,
			basDocsDevNmAccessIf			BasInterfaceId,
			basDocsDevNmAccessLPort			BasLogicalPortId
        }

basDocsDevNmAccessIndex OBJECT-TYPE
        SYNTAX      INTEGER (1..2147483647)
        MAX-ACCESS  not-accessible
        STATUS      current
        DESCRIPTION
            "Index used to order the application of access entries."
        ::= { basDocsDevNmAccessEntry 1 }

basDocsDevNmAccessIp OBJECT-TYPE
        SYNTAX      IpAddress
        MAX-ACCESS  read-create
        STATUS      current
        DESCRIPTION
            "The IP address (or subnet) of the network management
             station. The address 255.255.255.255 is defined to mean
             any NMS. If traps are enabled for this entry, then the
             value must be the address of a specific device."
        DEFVAL { 'ffffffff'h }
        ::= { basDocsDevNmAccessEntry 2 }

basDocsDevNmAccessIpMask OBJECT-TYPE
        SYNTAX      IpAddress
        MAX-ACCESS  read-create
        STATUS      current
        DESCRIPTION
            "The IP subnet mask of the network management stations.
             If traps are enabled for this entry, then the value must
             be 255.255.255.255."
        DEFVAL { 'ffffffff'h }
        ::= { basDocsDevNmAccessEntry 3 }

basDocsDevNmAccessCommunity OBJECT-TYPE
        SYNTAX      DisplayString
        MAX-ACCESS  read-create
        STATUS      current
        DESCRIPTION
            "The community string to be matched for access by this
             entry. If set to the null string then any community string
             will match."
        DEFVAL { "public" }
        ::= { basDocsDevNmAccessEntry 4 }

basDocsDevNmAccessControl OBJECT-TYPE
        SYNTAX         INTEGER {
            none(1),
            read(2),
            readWrite(3),
            roWithTraps(4),
            rwWithTraps(5),
            trapsOnly(6)
        }
        MAX-ACCESS  read-create
        STATUS      current
        DESCRIPTION
            "Specifies the type of access allowed to this NMS. Setting
             this object to none(1) causes the table entry to be
             destroyed. Read(2) allows access by 'get' and 'get-next'
             PDUs. ReadWrite(3) allows access by 'set' as well.
             RoWithtraps(4), rwWithTraps(5), and trapsOnly(6)
             control distribution of Trap PDUs transmitted by this
             device."
        DEFVAL { read }
        ::= { basDocsDevNmAccessEntry 5 }

-- The syntax of the following object was copied from RFC1493,
-- dot1dStaticAllowedToGoTo.

basDocsDevNmAccessInterfaces OBJECT-TYPE
        SYNTAX      OCTET STRING
        MAX-ACCESS  read-create
        STATUS      current
        DESCRIPTION
            "Specifies the set of interfaces from which requests from
             this NMS will be accepted.
             Each octet within the value of this object specifies a set
             of eight interfaces, with the first octet specifying ports
             1 through 8, the second octet specifying interfaces 9
             through 16, etc.  Within each octet, the most significant
             bit represents the lowest numbered interface, and the least
             significant bit represents the highest numbered interface.
             Thus, each interface is represented by a single bit within
             the value of this object. If that bit has a value of '1'
             then that interface is included in the set.

             Note that entries in this table apply only to link-layer
             interfaces (e.g., Ethernet and CATV MAC). Upstream and
             downstream channel interfaces must not be specified."
--         DEFVAL is the bitmask corresponding to all interfaces
        ::= { basDocsDevNmAccessEntry 6 }


basDocsDevNmAccessStatus OBJECT-TYPE
        SYNTAX      RowStatus
        MAX-ACCESS  read-create
        STATUS      current
        DESCRIPTION
            "Controls and reflects the status of rows in this table."
        ::= { basDocsDevNmAccessEntry 7 }

basDocsDevNmAccessChassis OBJECT-TYPE
	SYNTAX		BasChassisId
	MAX-ACCESS	not-accessible
	STATUS		current
	DESCRIPTION
		"The BAS Chassis ID of this card."
	::= { basDocsDevNmAccessEntry 8 }

basDocsDevNmAccessSlot OBJECT-TYPE
	SYNTAX		BasSlotId
	MAX-ACCESS	not-accessible
	STATUS		current
	DESCRIPTION
		"The BAS Slot ID of this card."
	::= { basDocsDevNmAccessEntry 9 }

basDocsDevNmAccessIf OBJECT-TYPE
	SYNTAX		BasInterfaceId
	MAX-ACCESS	not-accessible
	STATUS		current
	DESCRIPTION
		"The BAS interface ID of this card."
	::= { basDocsDevNmAccessEntry 10 }

basDocsDevNmAccessLPort OBJECT-TYPE
	SYNTAX		BasLogicalPortId
	MAX-ACCESS	not-accessible
	STATUS		current
	DESCRIPTION
		"The BAS logical port ID of this card."
	::= { basDocsDevNmAccessEntry 11 }


--
--  Procedures for using the following group are described in section
--  3.2.1
--

basDocsDevSoftware OBJECT IDENTIFIER ::= { basDocsDevMIBObjects 3 }


basDocsDevSwTable OBJECT-TYPE
        SYNTAX      SEQUENCE OF BasDocsDevSwEntry
        MAX-ACCESS  not-accessible
        STATUS      current
        DESCRIPTION
            ""
        ::= { basDocsDevSoftware 1 }

basDocsDevSwEntry OBJECT-TYPE
        SYNTAX      BasDocsDevSwEntry
        MAX-ACCESS  not-accessible
        STATUS      current
        DESCRIPTION
            ""
        INDEX { 
				basDocsDevSwChassis,
				basDocsDevSwSlot,
				basDocsDevSwIf,
				basDocsDevSwLPort
				}
        ::= {  basDocsDevSwTable 1 }

BasDocsDevSwEntry ::= SEQUENCE {
			basDocsDevSwServer			IpAddress,
			basDocsDevSwFilename		DisplayString,
			basDocsDevSwAdminStatus		INTEGER,
			basDocsDevSwOperStatus		INTEGER,
			basDocsDevSwChassis			BasChassisId,
			basDocsDevSwSlot			BasSlotId,
			basDocsDevSwIf				BasInterfaceId,
			basDocsDevSwLPort			BasLogicalPortId
        }

basDocsDevSwServer OBJECT-TYPE
        SYNTAX      IpAddress
        MAX-ACCESS  read-write
        STATUS      current
        DESCRIPTION
            "The address of the TFTP server used for software upgrades."
        ::= { basDocsDevSwEntry 1 }

basDocsDevSwFilename OBJECT-TYPE
        SYNTAX      DisplayString (SIZE (0..64))
        MAX-ACCESS  read-write
        STATUS      current
        DESCRIPTION
            "The file name of the software image to be loaded into this
             device. Unless set via SNMP, this is the file name
             specified by the provisioning server that corresponds to
             the software version that is desired for this device.
             If unknown, the string '(unknown)' is returned."
        ::= { basDocsDevSwEntry 2 }

basDocsDevSwAdminStatus OBJECT-TYPE
        SYNTAX INTEGER {
            upgradeFromMgt(1),
            allowProvisioningUpgrade(2),
            ignoreProvisioningUpgrade(3)
        }
        MAX-ACCESS  read-write
        STATUS      current
        DESCRIPTION
            "If set to upgradeFromMgt(1), the device will initiate a
             TFTP software image download using docsDevSwFilename.
             After successfully receiving an image, the device will
             set its state to ignoreProvisioningUpgrade(3) and reboot.
             If the download process is interrupted by a reset or
             power failure, the device will load the previous image
             and, after re-initialization, continue to attempt loading
             the image specified in docsDevSwFilename.


             If set to allowProvisioningUpgrade(2), the device will
             use the software version information supplied by the
             provisioning server when next rebooting (this does not
             cause a reboot).

             When set to ignoreProvisioningUpgrade(3), the device
             will disregard software image upgrade information from the
             provisioning server.

             Note that reading this object can return upgradeFromMgt(1).
             This indicates that a software download is currently in
             progress, and that the device will reboot after
             successfully receiving an image."
        ::= { basDocsDevSwEntry 3 }

basDocsDevSwOperStatus OBJECT-TYPE
        SYNTAX INTEGER {
            inProgress(1),
            completeFromProvisioning(2),
            completeFromMgt(3),
            failed(4),
            other(5)
        }
        MAX-ACCESS  read-only
        STATUS      current
        DESCRIPTION
            "InProgress(1) indicates that a TFTP download is underway,
             either as a result of a version mismatch at provisioning
             or as a result of a upgradeFromMgt request.
             CompleteFromProvisioning(2) indicates that the last
             software upgrade was a result of version mismatch at
             provisioning. CompleteFromMgt(3) indicates that the last
             software upgrade was a result of setting
             docsDevSwAdminStatus to upgradeFromMgt.
             Failed(4) indicates that the last attempted download
             failed, ordinarily due to TFTP timeout."
        ::= { basDocsDevSwEntry 4 }

basDocsDevSwChassis OBJECT-TYPE
	SYNTAX		BasChassisId
	MAX-ACCESS	not-accessible
	STATUS		current
	DESCRIPTION
		"The BAS Chassis ID of this card."
	::= { basDocsDevSwEntry 5 }

basDocsDevSwSlot OBJECT-TYPE
	SYNTAX		BasSlotId
	MAX-ACCESS	not-accessible
	STATUS		current
	DESCRIPTION
		"The BAS Slot ID of this card."
	::= { basDocsDevSwEntry 6 }

basDocsDevSwIf OBJECT-TYPE
	SYNTAX		BasInterfaceId
	MAX-ACCESS	not-accessible
	STATUS		current
	DESCRIPTION
		"The BAS interface ID of this card."
	::= { basDocsDevSwEntry 7 }

basDocsDevSwLPort OBJECT-TYPE
	SYNTAX		BasLogicalPortId
	MAX-ACCESS	not-accessible
	STATUS		current
	DESCRIPTION
		"The BAS logical port ID of this card."
	::= { basDocsDevSwEntry 8 }


--
-- The following group describes server access and parameters used for
-- initial provisioning and bootstrapping.
--

basDocsDevServer OBJECT IDENTIFIER ::= { basDocsDevMIBObjects 4 }

basDocsDevServerTable OBJECT-TYPE
        SYNTAX      SEQUENCE OF BasDocsDevServerEntry
        MAX-ACCESS  not-accessible
        STATUS      current
        DESCRIPTION
            ""
        ::= { basDocsDevServer 1 }

basDocsDevServerEntry OBJECT-TYPE
        SYNTAX      BasDocsDevServerEntry
        MAX-ACCESS  not-accessible
        STATUS      current
        DESCRIPTION
            ""
        INDEX { 
				basDocsDevServerChassis,
				basDocsDevServerSlot,
				basDocsDevServerIf,
				basDocsDevServerLPort
				}
        ::= {  basDocsDevServerTable 1 }

BasDocsDevServerEntry ::= SEQUENCE {
			basDocsDevServerBootState		INTEGER,
			basDocsDevServerDhcp			IpAddress,
			basDocsDevServerTime			IpAddress,
			basDocsDevServerTftp			IpAddress,
			basDocsDevServerConfigFile		DisplayString,
			basDocsDevServerChassis			BasChassisId,
			basDocsDevServerSlot			BasSlotId,
			basDocsDevServerIf				BasInterfaceId,
			basDocsDevServerLPort			BasLogicalPortId
        }

basDocsDevServerBootState OBJECT-TYPE
        SYNTAX INTEGER {
            operational(1),
            disabled(2),
            waitingForDhcpOffer(3),
            waitingForDhcpResponse(4),
            waitingForTimeServer(5),
            waitingForTftp(6),
            refusedByCmts(7),
            forwardingDenied(8),
            other(9),
            unknown(10)
        }
        MAX-ACCESS  read-only
        STATUS      current
        DESCRIPTION
            "If operational(1), the device has completed loading and
             processing of configuration parameters and the CMTS has
             completed the Registration exchange.
             If disabled(2) then the device was administratively
             disabled, possibly by being refused network access in the
             configuration file.
             If waitingForDhcpOffer(3) then a DHCP Discover has been
             transmitted and no offer has yet been received.
             If waitingForDhcpResponse(4) then a DHCP Request has been
             transmitted and no response has yet been received.
             If waitingForTimeServer(5) then a Time Request has been
             transmitted and no response has yet been received.
             If waitingForTftp(6) then a request to the TFTP parameter
             server has been made and no response received.
             If refusedByCmts(7) then the Registration Request/Response
             exchange with the CMTS failed.
             If forwardingDenied(8) then the registration process
             completed, but the network access option in the received
             configuration file prohibits forwarding. "
        ::= { basDocsDevServerEntry 1 }

basDocsDevServerDhcp OBJECT-TYPE
        SYNTAX      IpAddress
        MAX-ACCESS  read-only
        STATUS      current
        DESCRIPTION
            "The IP address of the DHCP server that assigned an IP
             address to this device. Returns 0.0.0.0 if DHCP was not
             used for IP address assignment."
        ::= { basDocsDevServerEntry 2 }

basDocsDevServerTime OBJECT-TYPE
        SYNTAX      IpAddress
        MAX-ACCESS  read-only
        STATUS      current
        DESCRIPTION
            "The IP address of the Time server (RFC-868)."
        ::= { basDocsDevServerEntry 3 }

basDocsDevServerTftp OBJECT-TYPE
        SYNTAX      IpAddress
        MAX-ACCESS  read-only


        STATUS      current
        DESCRIPTION
            "The IP address of the TFTP server responsible for
             downloading provisioning and configuration parameters
             to this device."
        ::= { basDocsDevServerEntry 4 }

basDocsDevServerConfigFile OBJECT-TYPE
        SYNTAX      DisplayString
        MAX-ACCESS  read-only
        STATUS      current
        DESCRIPTION
            "The name of the device configuration file read from the
             TFTP server."
        ::= { basDocsDevServerEntry 5 }

basDocsDevServerChassis OBJECT-TYPE
	SYNTAX		BasChassisId
	MAX-ACCESS	not-accessible
	STATUS		current
	DESCRIPTION
		"The BAS Chassis ID of this card."
	::= { basDocsDevServerEntry 6 }

basDocsDevServerSlot OBJECT-TYPE
	SYNTAX		BasSlotId
	MAX-ACCESS	not-accessible
	STATUS		current
	DESCRIPTION
		"The BAS Slot ID of this card."
	::= { basDocsDevServerEntry 7 }

basDocsDevServerIf OBJECT-TYPE
	SYNTAX		BasInterfaceId
	MAX-ACCESS	not-accessible
	STATUS		current
	DESCRIPTION
		"The BAS interface ID of this card."
	::= { basDocsDevServerEntry 8 }

basDocsDevServerLPort OBJECT-TYPE
	SYNTAX		BasLogicalPortId
	MAX-ACCESS	not-accessible
	STATUS		current
	DESCRIPTION
		"The BAS logical port ID of this card."
	::= { basDocsDevServerEntry 9 }

--
--  Event Reporting
--

basDocsDevEvent OBJECT IDENTIFIER ::= { basDocsDevMIBObjects 5 }

basDocsDevEvTable OBJECT-TYPE
        SYNTAX      SEQUENCE OF BasDocsDevEvEntry
        MAX-ACCESS  not-accessible
        STATUS      current
        DESCRIPTION
            ""
        ::= { basDocsDevEvent 1 }

basDocsDevEvEntry OBJECT-TYPE
        SYNTAX      BasDocsDevEvEntry
        MAX-ACCESS  not-accessible
        STATUS      current
        DESCRIPTION
            ""
        INDEX { 
				basDocsDevEvChassis,
				basDocsDevEvSlot,
				basDocsDevEvIf,
				basDocsDevEvLPort
				}
        ::= {  basDocsDevEvTable 1 }

BasDocsDevEvEntry ::= SEQUENCE {
			basDocsDevEvControl					INTEGER,
			basDocsDevEvSyslog					IpAddress,
			basDocsDevEvThrottleAdminStatus		INTEGER,
			basDocsDevEvThrottleInhibited		TruthValue,
			basDocsDevEvThrottleThreshold		Unsigned32,
			basDocsDevEvThrottleInterval		INTEGER,
			basDocsDevEvChassis			BasChassisId,
			basDocsDevEvSlot			BasSlotId,
			basDocsDevEvIf				BasInterfaceId,
			basDocsDevEvLPort			BasLogicalPortId
        }

basDocsDevEvControl OBJECT-TYPE
        SYNTAX INTEGER {
            resetLog(1),
            useDefaultReporting(2)
        }
        MAX-ACCESS  read-write
        STATUS      current
        DESCRIPTION
            "Setting this object to resetLog(1) empties the event log.
             All data is deleted. Setting it to useDefaultReporting(2)
             returns all event priorities to their factory-default
             reporting. Reading this object always returns
             useDefaultReporting(2)."
        ::= { basDocsDevEvEntry 1 }

basDocsDevEvSyslog OBJECT-TYPE
        SYNTAX      IpAddress
        MAX-ACCESS  read-write
        STATUS      current
        DESCRIPTION
            "The IP address of the Syslog server. If 0.0.0.0, syslog
             transmission is inhibited."
        ::= { basDocsDevEvEntry 2 }

basDocsDevEvThrottleAdminStatus OBJECT-TYPE
        SYNTAX INTEGER {
            unconstrained(1),
            maintainBelowThreshold(2),
            stopAtThreshold(3),
            inhibited(4)


        }
        MAX-ACCESS  read-write
        STATUS      current
        DESCRIPTION
            "Controls the transmission of traps and syslog messages
             with respect to the trap pacing threshold.
             unconstrained(1) causes traps and syslog messages to be
             transmitted without regard to the threshold settings.
             maintainBelowThreshold(2) causes trap transmission and
             syslog messages to be suppressed if the number of traps
             would otherwise exceed the threshold.
             stopAtThreshold(3) causes trap transmission to cease
             at the threshold, and not resume until directed to do so.
             inhibited(4) causes all trap transmission and syslog
             messages to be suppressed.

             A single event is always treated as a single event for
             threshold counting. That is, an event causing both a trap
             and a syslog message is still treated as a single event.

             Writing to this object resets the thresholding state."
        ::= { basDocsDevEvEntry 3 }

basDocsDevEvThrottleInhibited OBJECT-TYPE
        SYNTAX      TruthValue
        MAX-ACCESS  read-only
        STATUS      current
        DESCRIPTION
            "If true(1), trap and syslog transmission is currently
             inhibited due to thresholds and/or the current setting of
             docsDevEvThrottleAdminStatus."
        ::= { basDocsDevEvEntry 4 }

basDocsDevEvThrottleThreshold OBJECT-TYPE
        SYNTAX      Unsigned32
        MAX-ACCESS  read-write
        STATUS      current
        DESCRIPTION
            "Number of trap/syslog events per docsDevEvThrottleInterval
             to be transmitted before throttling.

             A single event is always treated as a single event for
             threshold counting. That is, an event causing both a trap
             and a syslog message is still treated as a single event."
        ::= { basDocsDevEvEntry 5 }

basDocsDevEvThrottleInterval OBJECT-TYPE
        SYNTAX      INTEGER(1..2147483647)
        UNITS       "seconds"
        MAX-ACCESS  read-write
        STATUS      current
        DESCRIPTION
            "The interval over which the trap threshold applies."
        ::= { basDocsDevEvEntry 6 }

basDocsDevEvChassis OBJECT-TYPE
	SYNTAX		BasChassisId
	MAX-ACCESS	not-accessible
	STATUS		current
	DESCRIPTION
		"The BAS Chassis ID of this card."
	::= { basDocsDevEvEntry 7 }

basDocsDevEvSlot OBJECT-TYPE
	SYNTAX		BasSlotId
	MAX-ACCESS	not-accessible
	STATUS		current
	DESCRIPTION
		"The BAS Slot ID of this card."
	::= { basDocsDevEvEntry 8 }

basDocsDevEvIf OBJECT-TYPE
	SYNTAX		BasInterfaceId
	MAX-ACCESS	not-accessible
	STATUS		current
	DESCRIPTION
		"The BAS interface ID of this card."
	::= { basDocsDevEvEntry 9 }

basDocsDevEvLPort OBJECT-TYPE
	SYNTAX		BasLogicalPortId
	MAX-ACCESS	not-accessible
	STATUS		current
	DESCRIPTION
		"The BAS logical port ID of this card."
	::= { basDocsDevEvEntry 10 }


--
-- The following table controls the reporting of the various classes of
-- events. For each event priority,
-- a combination of logging and reporting mechanisms may be chosen. The
-- mapping of event types
-- to priorities is vendor-dependent. Vendors may also choose to allow
-- the user to control that mapping
-- through proprietary means.

basDocsDevEvControlTable OBJECT-TYPE
        SYNTAX      SEQUENCE OF BasDocsDevEvControlEntry
        MAX-ACCESS  not-accessible
        STATUS      current
        DESCRIPTION
            "Allows control of the reporting of event classes."
        ::= {  basDocsDevEvent 7 }

basDocsDevEvControlEntry OBJECT-TYPE
        SYNTAX      BasDocsDevEvControlEntry
        MAX-ACCESS  not-accessible
        STATUS      current
        DESCRIPTION
            "Allows configuration of the reporting mechanisms for a
             particular event priority."
        INDEX { 
				basDocsDevEvControlChassis,
				basDocsDevEvControlSlot,
				basDocsDevEvControlIf,
				basDocsDevEvControlLPort,
				basDocsDevEvPriority }
        ::= { basDocsDevEvControlTable 1 }

BasDocsDevEvControlEntry ::= SEQUENCE {
            basDocsDevEvPriority        INTEGER,
            basDocsDevEvReporting       BITS,
			basDocsDevEvControlChassis	BasChassisId,
			basDocsDevEvControlSlot		BasSlotId,
			basDocsDevEvControlIf		BasInterfaceId,
			basDocsDevEvControlLPort	BasLogicalPortId
        }

basDocsDevEvPriority OBJECT-TYPE
        SYNTAX INTEGER {
            emergency(1),
            alert(2),
            critical(3),
            error(4),
            warning(5),
            notice(6),
            information(7),
            debug(8)
        }
        MAX-ACCESS  not-accessible
        STATUS      current
        DESCRIPTION
            "The priority level that is controlled by this entry."
        ::= { basDocsDevEvControlEntry 1 }


basDocsDevEvReporting OBJECT-TYPE
        SYNTAX BITS {
            local(0),
            traps(1),
            syslog(2)
        }
        MAX-ACCESS  read-write
        STATUS      current
        DESCRIPTION
            "Defines the action to be taken on occurrence of this
             event class. Implementations may not necessarily support
             all options for all event classes, but at minimum must
             allow traps and syslogging to be disabled."
        ::= { basDocsDevEvControlEntry 2 }

basDocsDevEvControlChassis OBJECT-TYPE
	SYNTAX		BasChassisId
	MAX-ACCESS	not-accessible
	STATUS		current
	DESCRIPTION
		"The BAS Chassis ID of this card."
	::= { basDocsDevEvControlEntry 3 }

basDocsDevEvControlSlot OBJECT-TYPE
	SYNTAX		BasSlotId
	MAX-ACCESS	not-accessible
	STATUS		current
	DESCRIPTION
		"The BAS Slot ID of this card."
	::= { basDocsDevEvControlEntry 4 }

basDocsDevEvControlIf OBJECT-TYPE
	SYNTAX		BasInterfaceId
	MAX-ACCESS	not-accessible
	STATUS		current
	DESCRIPTION
		"The BAS interface ID of this card."
	::= { basDocsDevEvControlEntry 5 }

basDocsDevEvControlLPort OBJECT-TYPE
	SYNTAX		BasLogicalPortId
	MAX-ACCESS	not-accessible
	STATUS		current
	DESCRIPTION
		"The BAS logical port ID of this card."
	::= { basDocsDevEvControlEntry 6 }




basDocsDevEventTable OBJECT-TYPE
        SYNTAX      SEQUENCE OF BasDocsDevEventEntry
        MAX-ACCESS  not-accessible
        STATUS      current
        DESCRIPTION
            "Contains a log of network and device events that may be
             of interest in fault isolation and troubleshooting."
        ::= {  basDocsDevEvent 8 }

basDocsDevEventEntry OBJECT-TYPE
        SYNTAX      BasDocsDevEventEntry
        MAX-ACCESS  not-accessible
        STATUS      current
        DESCRIPTION
            "Describes a network or device event that may be of
             interest in fault isolation and troubleshooting."
        INDEX { 
				basDocsDevEvEventChassis,
				basDocsDevEvEventSlot,
				basDocsDevEvEventIf,
				basDocsDevEvEventLPort,
				basDocsDevEvIndex }
        ::= { basDocsDevEventTable 1 }

BasDocsDevEventEntry ::= SEQUENCE {
            basDocsDevEvIndex           INTEGER,
            basDocsDevEvFirstTime       DateAndTime,
            basDocsDevEvLastTime        DateAndTime,
            basDocsDevEvCount           Counter32,
            basDocsDevEvLevel           INTEGER,
            basDocsDevEvId              Unsigned32,
            basDocsDevEvText            DisplayString,
			basDocsDevEvEventChassis	BasChassisId,
			basDocsDevEvEventSlot		BasSlotId,
			basDocsDevEvEventIf		BasInterfaceId,
			basDocsDevEvEventLPort	BasLogicalPortId
        }

basDocsDevEvIndex OBJECT-TYPE
        SYNTAX      INTEGER (1..2147483647)
        MAX-ACCESS  not-accessible
        STATUS      current
        DESCRIPTION
            "Provides relative ordering of the objects in the event
             log. This object will always increase except when
             (a) the log is reset via docsDevEvControl,


             (b) the device reboots and does not implement nonvolatile
             storage for this log, or (c) it reaches the value 2^31.
             The next entry for all the above cases is 1."
        ::= { basDocsDevEventEntry 1 }

basDocsDevEvFirstTime OBJECT-TYPE
        SYNTAX      DateAndTime
        MAX-ACCESS  read-only
        STATUS      current
        DESCRIPTION
            "The time that this entry was created."
        ::= { basDocsDevEventEntry 2 }

basDocsDevEvLastTime OBJECT-TYPE
        SYNTAX      DateAndTime
        MAX-ACCESS  read-only
        STATUS      current
        DESCRIPTION
            "If multiple events are reported via the same entry, the
             time that the last event for this entry occurred."
        ::= { basDocsDevEventEntry 3 }

basDocsDevEvCount OBJECT-TYPE
        SYNTAX      Counter32
        MAX-ACCESS  read-only
        STATUS      current
        DESCRIPTION
            "The number of consecutive event instances reported by
             this entry."
        ::= { basDocsDevEventEntry 4 }

basDocsDevEvLevel OBJECT-TYPE
        SYNTAX INTEGER {
            emergency(1),
            alert(2),
            critical(3),
            error(4),
            warning(5),
            notice(6),
            information(7),
            debug(8)
        }
        MAX-ACCESS  read-only
        STATUS      current
        DESCRIPTION
            "The priority level of this event."
        ::= { basDocsDevEventEntry 5 }

--
-- Vendors will provide their own enumerations for the following.
-- The interpretation of the enumeration is unambiguous for a
-- particular value of the vendor's enterprise number in sysObjectID.


--

basDocsDevEvId OBJECT-TYPE
        SYNTAX      Unsigned32
        MAX-ACCESS  read-only
        STATUS      current
        DESCRIPTION
            "For this product, uniquely identifies the type of event
             that is reported by this entry."
        ::= { basDocsDevEventEntry 6 }

basDocsDevEvText OBJECT-TYPE
        SYNTAX      DisplayString
        MAX-ACCESS  read-only
        STATUS      current
        DESCRIPTION
            "Provides a human-readable description of the event,
             including all relevant context (interface numbers,
             etc.)."
        ::= { basDocsDevEventEntry 7 }

basDocsDevEvEventChassis OBJECT-TYPE
	SYNTAX		BasChassisId
	MAX-ACCESS	not-accessible
	STATUS		current
	DESCRIPTION
		"The BAS Chassis ID of this card."
	::= { basDocsDevEventEntry 8 }

basDocsDevEvEventSlot OBJECT-TYPE
	SYNTAX		BasSlotId
	MAX-ACCESS	not-accessible
	STATUS		current
	DESCRIPTION
		"The BAS Slot ID of this card."
	::= { basDocsDevEventEntry 9 }

basDocsDevEvEventIf OBJECT-TYPE
	SYNTAX		BasInterfaceId
	MAX-ACCESS	not-accessible
	STATUS		current
	DESCRIPTION
		"The BAS interface ID of this card."
	::= { basDocsDevEventEntry 10 }

basDocsDevEvEventLPort OBJECT-TYPE
	SYNTAX		BasLogicalPortId
	MAX-ACCESS	not-accessible
	STATUS		current
	DESCRIPTION
		"The BAS logical port ID of this card."
	::= { basDocsDevEventEntry 11 }





basDocsDevFilter OBJECT IDENTIFIER ::= { basDocsDevMIBObjects 6 }

basDocsDevFilterTable OBJECT-TYPE
        SYNTAX      SEQUENCE OF BasDocsDevFilterEntry
        MAX-ACCESS  not-accessible
        STATUS      current
        DESCRIPTION
            "Contains a log of network and device events that may be
             of interest in fault isolation and troubleshooting."
        ::= {  basDocsDevFilter 1 }

basDocsDevFilterEntry OBJECT-TYPE
        SYNTAX      BasDocsDevFilterEntry
        MAX-ACCESS  not-accessible
        STATUS      current
        DESCRIPTION
            "Describes a network or device event that may be of
             interest in fault isolation and troubleshooting."
        INDEX { 
				basDocsDevFilterChassis,
				basDocsDevFilterSlot,
				basDocsDevFilterIf,
				basDocsDevFilterLPort
			  }
        ::= { basDocsDevFilterTable 1 }

BasDocsDevFilterEntry ::= SEQUENCE {
			basDocsDevFilterLLCDefault	INTEGER,
			basDocsDevFilterChassis		BasChassisId,
			basDocsDevFilterSlot		BasSlotId,
			basDocsDevFilterIf			BasInterfaceId,
			basDocsDevFilterLPort		BasLogicalPortId
        }

-- LLC filters can be defined on an inclusive or exclusive basis: CMs
-- can be configured to forward only packets matching a set of layer
-- three protocols,  or to drop packets matching a set of layer three
-- protocols.

basDocsDevFilterLLCDefault OBJECT-TYPE
        SYNTAX INTEGER {
            discard(1),
            accept(2)
        }
        MAX-ACCESS  read-write
        STATUS      current
        DESCRIPTION
            "If set to discard(1), all packets not matching an LLC
             filter will be discarded. If set to accept(2), all
             packets not matching an LLC filter will be accepted for
             further processing (e.g., bridging)."
        ::= { basDocsDevFilterEntry 1 }

basDocsDevFilterChassis OBJECT-TYPE
	SYNTAX		BasChassisId
	MAX-ACCESS	not-accessible
	STATUS		current
	DESCRIPTION
		"The BAS Chassis ID of this card."
	::= { basDocsDevFilterEntry 2 }

basDocsDevFilterSlot OBJECT-TYPE
	SYNTAX		BasSlotId
	MAX-ACCESS	not-accessible
	STATUS		current
	DESCRIPTION
		"The BAS Slot ID of this card."
	::= { basDocsDevFilterEntry 3 }

basDocsDevFilterIf OBJECT-TYPE
	SYNTAX		BasInterfaceId
	MAX-ACCESS	not-accessible
	STATUS		current
	DESCRIPTION
		"The BAS interface ID of this card."
	::= { basDocsDevFilterEntry 4 }

basDocsDevFilterLPort OBJECT-TYPE
	SYNTAX		BasLogicalPortId
	MAX-ACCESS	not-accessible
	STATUS		current
	DESCRIPTION
		"The BAS logical port ID of this card."
	::= { basDocsDevFilterEntry 5 }



basDocsDevFilterLLCTable OBJECT-TYPE
        SYNTAX      SEQUENCE OF BasDocsDevFilterLLCEntry
        MAX-ACCESS  not-accessible
        STATUS      current
        DESCRIPTION
            "A list of filters to apply to (bridged) LLC traffic, which
             forwards or drops packets on the basis of the layer three
             protocol type."
        ::= { basDocsDevFilter 2 }


basDocsDevFilterLLCEntry OBJECT-TYPE
        SYNTAX      BasDocsDevFilterLLCEntry
        MAX-ACCESS  not-accessible
        STATUS      current
        DESCRIPTION
            "Describes a single filter to apply to (bridged) LLC traffic
             received on a specified interface. "
        INDEX { 
				basDocsDevFilterLLCChassis,
				basDocsDevFilterLLCSlot,
				basDocsDevFilterLLCIf,
				basDocsDevFilterLLCLPort,
				basDocsDevFilterLLCIndex }
        ::= { basDocsDevFilterLLCTable 1 }

BasDocsDevFilterLLCEntry ::= SEQUENCE {
            basDocsDevFilterLLCIndex               INTEGER,
            basDocsDevFilterLLCStatus              RowStatus,
            basDocsDevFilterLLCIfIndex             InterfaceIndexOrZero,
            basDocsDevFilterLLCProtocolType        INTEGER,
            basDocsDevFilterLLCProtocol            INTEGER,
            basDocsDevFilterLLCMatches             Counter32,
			basDocsDevFilterLLCChassis				BasChassisId,
			basDocsDevFilterLLCSlot					BasSlotId,
			basDocsDevFilterLLCIf					BasInterfaceId,
			basDocsDevFilterLLCLPort				BasLogicalPortId
        }

basDocsDevFilterLLCIndex OBJECT-TYPE
        SYNTAX      INTEGER (1..2147483647)
        MAX-ACCESS  not-accessible
        STATUS      current
        DESCRIPTION
            "Index used for the identification of filters (note that LLC
             filter order is irrelevant)."
        ::= { basDocsDevFilterLLCEntry 1 }

basDocsDevFilterLLCStatus OBJECT-TYPE
        SYNTAX      RowStatus
        MAX-ACCESS  read-create
        STATUS      current
        DESCRIPTION
            "Controls and reflects the status of rows in this table."
        ::= { basDocsDevFilterLLCEntry 2}

basDocsDevFilterLLCIfIndex OBJECT-TYPE
        SYNTAX      InterfaceIndexOrZero
        MAX-ACCESS  read-create
        STATUS      current
        DESCRIPTION
            "The entry interface to which this filter applies.
             The value corresponds to ifIndex for either a CATV MAC
             or another network interface. If the value is zero, the
             filter applies to all interfaces. In Cable Modems, the
             default value is the customer side interface. In Cable
             Modem Termination Systems, this object has to be
             specified to create a row in this table."
        ::= { basDocsDevFilterLLCEntry 3 }

basDocsDevFilterLLCProtocolType OBJECT-TYPE
        SYNTAX INTEGER {


            ethertype(1),
            dsap(2)
        }
        MAX-ACCESS  read-create
        STATUS      current
        DESCRIPTION
            "The format of the value in docsDevFilterLLCProtocol:
             either a two-byte Ethernet Ethertype, or a one-byte
             802.2 SAP value. EtherType(1) also applies to SNAP-
             encapsulated frames."
        DEFVAL { ethertype }
        ::= { basDocsDevFilterLLCEntry 4 }

basDocsDevFilterLLCProtocol OBJECT-TYPE
        SYNTAX      INTEGER (0..65535)
        MAX-ACCESS  read-create
        STATUS      current
        DESCRIPTION
            "The layer three protocol for which this filter applies.
             The protocol value format depends on
             docsDevFilterLLCProtocolType. Note that for SNAP frames,
             etherType filtering is performed rather than DSAP=0xAA."
        DEFVAL { 0 }
        ::= { basDocsDevFilterLLCEntry 5 }

basDocsDevFilterLLCMatches OBJECT-TYPE
        SYNTAX      Counter32
        MAX-ACCESS  read-only
        STATUS      current
        DESCRIPTION
            "Counts the number of times this filter was matched."
        ::= { basDocsDevFilterLLCEntry 6 }

basDocsDevFilterLLCChassis OBJECT-TYPE
	SYNTAX		BasChassisId
	MAX-ACCESS	not-accessible
	STATUS		current
	DESCRIPTION
		"The BAS Chassis ID of this card."
	::= { basDocsDevFilterLLCEntry 7 }

basDocsDevFilterLLCSlot OBJECT-TYPE
	SYNTAX		BasSlotId
	MAX-ACCESS	not-accessible
	STATUS		current
	DESCRIPTION
		"The BAS Slot ID of this card."
	::= { basDocsDevFilterLLCEntry 8 }

basDocsDevFilterLLCIf OBJECT-TYPE
	SYNTAX		BasInterfaceId
	MAX-ACCESS	not-accessible
	STATUS		current
	DESCRIPTION
		"The BAS interface ID of this card."
	::= { basDocsDevFilterLLCEntry 9 }

basDocsDevFilterLLCLPort OBJECT-TYPE
	SYNTAX		BasLogicalPortId
	MAX-ACCESS	not-accessible
	STATUS		current
	DESCRIPTION
		"The BAS logical port ID of this card."
	::= { basDocsDevFilterLLCEntry 10 }



basDocsDevFilterIpDefTable OBJECT-TYPE
        SYNTAX      SEQUENCE OF BasDocsDevFilterIpDefEntry
        MAX-ACCESS  not-accessible
        STATUS      current
        DESCRIPTION
            "Contains a log of network and device events that may be
             of interest in fault isolation and troubleshooting."
        ::= {  basDocsDevFilter 3 }

basDocsDevFilterIpDefEntry OBJECT-TYPE
        SYNTAX      BasDocsDevFilterIpDefEntry
        MAX-ACCESS  not-accessible
        STATUS      current
        DESCRIPTION
            "Describes a network or device event that may be of
             interest in fault isolation and troubleshooting."
        INDEX { 
				basDocsDevFilterIpDefChassis,
				basDocsDevFilterIpDefSlot,
				basDocsDevFilterIpDefIf,
				basDocsDevFilterIpDefLPort
			  }
        ::= { basDocsDevFilterIpDefTable 1 }

BasDocsDevFilterIpDefEntry ::= SEQUENCE {
			basDocsDevFilterIpDefault			INTEGER,
			basDocsDevFilterIpDefChassis		BasChassisId,
			basDocsDevFilterIpDefSlot		BasSlotId,
			basDocsDevFilterIpDefIf			BasInterfaceId,
			basDocsDevFilterIpDefLPort		BasLogicalPortId
        }

-- The default behavior for (bridged) packets that do not match IP
-- filters is defined by
-- docsDevFilterIpDefault.

basDocsDevFilterIpDefault OBJECT-TYPE
        SYNTAX INTEGER {
            discard(1),
            accept(2)
        }
        MAX-ACCESS  read-write
        STATUS      current
        DESCRIPTION
            "If set to discard(1), all packets not matching an IP filter
             will be discarded. If set to accept(2), all packets not
             matching an IP filter will be accepted for further
             processing (e.g., bridging)."
        ::= { basDocsDevFilterIpDefEntry 1 }

basDocsDevFilterIpDefChassis OBJECT-TYPE
	SYNTAX		BasChassisId
	MAX-ACCESS	not-accessible
	STATUS		current
	DESCRIPTION
		"The BAS Chassis ID of this card."
	::= { basDocsDevFilterIpDefEntry 2 }

basDocsDevFilterIpDefSlot OBJECT-TYPE
	SYNTAX		BasSlotId
	MAX-ACCESS	not-accessible
	STATUS		current
	DESCRIPTION
		"The BAS Slot ID of this card."
	::= { basDocsDevFilterIpDefEntry 3 }

basDocsDevFilterIpDefIf OBJECT-TYPE
	SYNTAX		BasInterfaceId
	MAX-ACCESS	not-accessible
	STATUS		current
	DESCRIPTION
		"The BAS interface ID of this card."
	::= { basDocsDevFilterIpDefEntry 4 }

basDocsDevFilterIpDefLPort OBJECT-TYPE
	SYNTAX		BasLogicalPortId
	MAX-ACCESS	not-accessible
	STATUS		current
	DESCRIPTION
		"The BAS logical port ID of this card."
	::= { basDocsDevFilterIpDefEntry 5 }




basDocsDevFilterIpTable OBJECT-TYPE
        SYNTAX      SEQUENCE OF BasDocsDevFilterIpEntry
        MAX-ACCESS  not-accessible
        STATUS      current
        DESCRIPTION
            "An ordered list of filters to apply to IP traffic. Filter
             application is ordered by the filter index, rather than
             by a best match algorithm. Packets which match no filters
             are discarded or forwarded according to the setting of
             docsDevFilterIpDefault."
        ::= { basDocsDevFilter 4 }

basDocsDevFilterIpEntry OBJECT-TYPE
        SYNTAX      BasDocsDevFilterIpEntry
        MAX-ACCESS  not-accessible
        STATUS      current
        DESCRIPTION
            "Describes a filter to apply to IP traffic received on a
             specified interface. Both source and destination addresses
             must match for the filter to apply."
        INDEX { 
				basDocsDevFilterIpChassis,
				basDocsDevFilterIpSlot,
				basDocsDevFilterIpIf,
				basDocsDevFilterIpLPort,
				basDocsDevFilterIpIndex }
        ::= { basDocsDevFilterIpTable 1 }

BasDocsDevFilterIpEntry ::= SEQUENCE {
            basDocsDevFilterIpIndex             INTEGER,
            basDocsDevFilterIpStatus            RowStatus,
            basDocsDevFilterIpControl           INTEGER,
            basDocsDevFilterIpIfIndex           InterfaceIndexOrZero,
            basDocsDevFilterIpDirection         INTEGER,
            basDocsDevFilterIpBroadcast         TruthValue,
            basDocsDevFilterIpSaddr             IpAddress,
            basDocsDevFilterIpSmask             IpAddress,
            basDocsDevFilterIpDaddr             IpAddress,
            basDocsDevFilterIpDmask             IpAddress,
            basDocsDevFilterIpProtocol          INTEGER,
            basDocsDevFilterIpSourcePortLow     INTEGER,
            basDocsDevFilterIpSourcePortHigh    INTEGER,
            basDocsDevFilterIpDestPortLow       INTEGER,
            basDocsDevFilterIpDestPortHigh      INTEGER,
            basDocsDevFilterIpMatches           Counter32,
			basDocsDevFilterIpChassis				BasChassisId,
			basDocsDevFilterIpSlot					BasSlotId,
			basDocsDevFilterIpIf					BasInterfaceId,
			basDocsDevFilterIpLPort				BasLogicalPortId
        }

basDocsDevFilterIpIndex OBJECT-TYPE
        SYNTAX      INTEGER (1..2147483647)
        MAX-ACCESS  not-accessible
        STATUS      current
        DESCRIPTION
            "Index used to order the application of filters.
             The filter with the lowest index is always applied
             first."
        ::= { basDocsDevFilterIpEntry 1 }

basDocsDevFilterIpStatus OBJECT-TYPE


        SYNTAX      RowStatus
        MAX-ACCESS  read-create
        STATUS      current
        DESCRIPTION
            "Controls and reflects the status of rows in this table."
        ::= { basDocsDevFilterIpEntry 2 }

basDocsDevFilterIpControl OBJECT-TYPE
        SYNTAX INTEGER {
            discard(1),
            accept(2)
        }
        MAX-ACCESS  read-create
        STATUS      current
        DESCRIPTION
            "If set to discard(1), all packets matching this filter
             will be discarded and scanning of the remainder of the
             filter list will be aborted. If set to accept(2), all
             packets matching this filter will be accepted for further
             processing (e.g., bridging) and scanning of the remainder
             of the filter list will be aborted. "
        DEFVAL { discard }
        ::= { basDocsDevFilterIpEntry 3 }

basDocsDevFilterIpIfIndex OBJECT-TYPE
        SYNTAX      InterfaceIndexOrZero
        MAX-ACCESS  read-create
        STATUS      current
        DESCRIPTION
            "The entry interface to which this filter applies. The
             value corresponds to ifIndex for either a CATV MAC or
             another network interface. If the value is zero, the
             filter applies to all interfaces. Default value in Cable
             Modems is the customer-side interface. In Cable Modem
             Termination Systems, this object has to be specified to
             create a row in this table."
        ::= { basDocsDevFilterIpEntry 4 }

basDocsDevFilterIpDirection OBJECT-TYPE
        SYNTAX INTEGER {
            inbound(1),
            outbound(2),
            both(3)
        }
        MAX-ACCESS  read-create
        STATUS      current
        DESCRIPTION
            "Determines whether the filter is applied to inbound(1)
             traffic, outbound(2) traffic, or traffic in both(3)
             directions."
        DEFVAL { inbound }
        ::= { basDocsDevFilterIpEntry 5 }


basDocsDevFilterIpBroadcast OBJECT-TYPE
        SYNTAX      TruthValue
        MAX-ACCESS  read-create
        STATUS      current
        DESCRIPTION
            "If set to true(1), the filter only applies to multicast
             and broadcast traffic. If set to false(2), the filter
             applies to all traffic."
        DEFVAL { false }
        ::= { basDocsDevFilterIpEntry 6 }

basDocsDevFilterIpSaddr OBJECT-TYPE
        SYNTAX      IpAddress
        MAX-ACCESS  read-create
        STATUS      current
        DESCRIPTION
            "The source IP address, or portion thereof, that is to be
             matched for this filter."
        DEFVAL { '00000000'h }
        ::= { basDocsDevFilterIpEntry 7 }

basDocsDevFilterIpSmask OBJECT-TYPE
        SYNTAX      IpAddress
        MAX-ACCESS  read-create
        STATUS      current
        DESCRIPTION
            "A bit mask that is to be applied to the source address
             prior to matching. This mask is not necessarily the same
             as a subnet mask, but 1's bits must be leftmost and
             contiguous."
        DEFVAL { '00000000'h }
        ::= { basDocsDevFilterIpEntry 8 }

basDocsDevFilterIpDaddr OBJECT-TYPE
        SYNTAX      IpAddress
        MAX-ACCESS  read-create
        STATUS      current
        DESCRIPTION
            "The destination IP address, or portion thereof, that is
             to be matched for this filter "
        DEFVAL { '00000000'h }
        ::= { basDocsDevFilterIpEntry 9 }

basDocsDevFilterIpDmask OBJECT-TYPE
        SYNTAX      IpAddress
        MAX-ACCESS  read-create
        STATUS      current
        DESCRIPTION
            "A bit mask that is to be applied to the destination
             address prior to matching. This mask is not necessarily
             the same as a subnet mask, but 1's bits must be leftmost
             and contiguous "


        DEFVAL { '00000000'h }
        ::= { basDocsDevFilterIpEntry 10 }

basDocsDevFilterIpProtocol OBJECT-TYPE
        SYNTAX INTEGER {
            icmp(1),
            tcp(6),
            udp(17),
            any(256)
        }
        MAX-ACCESS  read-create
        STATUS      current
        DESCRIPTION
            "The IP protocol value that is to be matched."
        DEFVAL { any }
        ::= { basDocsDevFilterIpEntry 11 }

basDocsDevFilterIpSourcePortLow OBJECT-TYPE
        SYNTAX      INTEGER (0..65535)
        MAX-ACCESS  read-create
        STATUS      current
        DESCRIPTION
            "If docsDevFilterIpProtocol is udp or tcp, this is the
             inclusive lower bound of the transport-layer source port
             range that is to be matched."
        DEFVAL { 0 }
        ::= { basDocsDevFilterIpEntry 12 }

basDocsDevFilterIpSourcePortHigh OBJECT-TYPE
        SYNTAX      INTEGER (0..65535)
        MAX-ACCESS  read-create
        STATUS      current
        DESCRIPTION
            "If docsDevFilterIpProtocol is udp or tcp, this is the
             inclusive upper bound of the transport-layer source port
             range that is to be matched."
        DEFVAL { 65535 }
        ::= { basDocsDevFilterIpEntry 13 }

basDocsDevFilterIpDestPortLow OBJECT-TYPE
        SYNTAX      INTEGER (0..65535)
        MAX-ACCESS  read-create
        STATUS      current
        DESCRIPTION
            "If docsDevFilterIpProtocol is udp or tcp, this is the
             inclusive lower bound of the transport-layer destination
             port range that is to be matched."
        DEFVAL { 0 }
        ::= { basDocsDevFilterIpEntry 14 }

basDocsDevFilterIpDestPortHigh OBJECT-TYPE
        SYNTAX      INTEGER (0..65535)


        MAX-ACCESS  read-create
        STATUS      current
        DESCRIPTION
            "If docsDevFilterIpProtocol is udp or tcp, this is the
             inclusive upper bound of the transport-layer destination
             port range that is to be matched."
        DEFVAL { 65535 }
        ::= { basDocsDevFilterIpEntry 15 }

basDocsDevFilterIpMatches OBJECT-TYPE
        SYNTAX      Counter32
        MAX-ACCESS  read-only
        STATUS      current
        DESCRIPTION
            "Counts the number of times this filter was matched."
        ::= { basDocsDevFilterIpEntry 16 }

basDocsDevFilterIpChassis OBJECT-TYPE
	SYNTAX		BasChassisId
	MAX-ACCESS	not-accessible
	STATUS		current
	DESCRIPTION
		"The BAS Chassis ID of this card."
	::= { basDocsDevFilterIpEntry 17 }

basDocsDevFilterIpSlot OBJECT-TYPE
	SYNTAX		BasSlotId
	MAX-ACCESS	not-accessible
	STATUS		current
	DESCRIPTION
		"The BAS Slot ID of this card."
	::= { basDocsDevFilterIpEntry 18 }

basDocsDevFilterIpIf OBJECT-TYPE
	SYNTAX		BasInterfaceId
	MAX-ACCESS	not-accessible
	STATUS		current
	DESCRIPTION
		"The BAS interface ID of this card."
	::= { basDocsDevFilterIpEntry 19 }

basDocsDevFilterIpLPort OBJECT-TYPE
	SYNTAX		BasLogicalPortId
	MAX-ACCESS	not-accessible
	STATUS		current
	DESCRIPTION
		"The BAS logical port ID of this card."
	::= { basDocsDevFilterIpEntry 20 }

END
