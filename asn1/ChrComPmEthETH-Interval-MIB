ChrComPmEthETH-Interval-MIB

--FORCE-INCLUDE	<mib.h>
--FORCE-INCLUDE	<snmpdefs.h>
--FORCE-INCLUDE	"mibhand.h"

	DEFINITIONS  ::=  BEGIN

IMPORTS
	OBJECT-TYPE, Counter32			FROM  SNMPv2-SMI
	Integer32, Unsigned32			FROM  SNMPv2-SMI
	chrComPmEth				FROM  Chromatis-MIB
	chrComIfifIndex					FROM  ChrComIfifTable-MIB
	TruthValue				FROM  ChrTyp-MIB
	Gauge32				FROM  SNMPv2-SMI;

-- chrComPmEthETH-Interval Table

chrComPmEthETH-IntervalTable		OBJECT-TYPE
	SYNTAX		SEQUENCE OF ChrComPmEthETH-IntervalEntry
	MAX-ACCESS	not-accessible
	STATUS		current
	DESCRIPTION
	""
	::= { chrComPmEth 12}

chrComPmEthETH-IntervalEntry		OBJECT-TYPE
	SYNTAX		ChrComPmEthETH-IntervalEntry
	MAX-ACCESS	not-accessible
	STATUS		current
	DESCRIPTION
	""
	INDEX  {  chrComIfifIndex, chrComPmEthIntervalNumber }

--DEFAULT  get-function-async  MNIL_GetRoutine
--DEFAULT  set-function-async  MNIL_SetRoutine
--DEFAULT  next-function-async MNIL_NextRoutine
--DEFAULT  test-function-async MNIL_TestRoutine
--DEFAULT  cookie "ETH-Interval"
	::= { chrComPmEthETH-IntervalTable  1 }

ChrComPmEthETH-IntervalEntry  ::=
	SEQUENCE  {
	chrComPmEthIntervalNumber		Unsigned32	(1..32),
	chrComPmEthSuspectedInterval	TruthValue,
	chrComPmEthElapsedTime		Unsigned32	(0..4294967295),
	chrComPmEthSuppressedIntrvls	Gauge32			(0..4294967295),
	chrComPmEthdot3StatsFCSErrors	Gauge32			(0..4294967295),
	chrComPmEthdot3StatsLateCollisions	Gauge32			(0..4294967295),
	chrComPmEthdot3StatsFrameTooLongs	Gauge32			(0..4294967295),
	chrComPmEthdot3StatsInternalMacReceiveErrors Gauge32			(0..4294967295),
	chrComPmEthifInOctets		Gauge32			(0..4294967295),
	chrComPmEthifInUcastPkts		Gauge32			(0..4294967295),
	chrComPmEthifInDiscards		Gauge32			(0..4294967295),
	chrComPmEthifInErrors		Gauge32			(0..4294967295),
	chrComPmEthifOutOctets		Gauge32			(0..4294967295),
	chrComPmEthifOutUcastPkts		Gauge32			(0..4294967295),
	chrComPmEthifInMulticastPkts	Gauge32			(0..4294967295),
	chrComPmEthifInBroadcastPkts	Gauge32			(0..4294967295),
	chrComPmEthifOutMulticastPkts	Gauge32			(0..4294967295),
	chrComPmEthifOutBroadcastPkts	Gauge32			(0..4294967295),
	chrComPmEthchrFrames64Bytes	Gauge32			(0..4294967295),
	chrComPmEthchrFrames65to127Bytes	Gauge32			(0..4294967295),
	chrComPmEthchrFrames128to256Bytes	Gauge32			(0..4294967295),
	chrComPmEthchrFrames257to512Bytes	Gauge32			(0..4294967295),
	chrComPmEthchrFrames513to1024Bytes	Gauge32			(0..4294967295),
	chrComPmEthchrFrames1024toMaxBytes	Gauge32			(0..4294967295)
}

chrComPmEthIntervalNumber 	OBJECT-TYPE
	SYNTAX		Unsigned32	(1..32)
	MAX-ACCESS 	read-only
	STATUS 		current
	DESCRIPTION
	""
	::= { chrComPmEthETH-IntervalEntry  1 }

chrComPmEthSuspectedInterval 	OBJECT-TYPE
	SYNTAX		TruthValue
	MAX-ACCESS 	read-only
	STATUS 		current
	DESCRIPTION
	""
	::= { chrComPmEthETH-IntervalEntry  2 }

chrComPmEthElapsedTime 	OBJECT-TYPE
	SYNTAX		Unsigned32	(0..4294967295)
	MAX-ACCESS 	read-only
	STATUS 		current
	DESCRIPTION
	""
	::= { chrComPmEthETH-IntervalEntry  3 }

chrComPmEthSuppressedIntrvls 	OBJECT-TYPE
	SYNTAX		Gauge32			(0..4294967295)
	MAX-ACCESS 	read-only
	STATUS 		current
	DESCRIPTION
	""
	::= { chrComPmEthETH-IntervalEntry  4 }

chrComPmEthdot3StatsFCSErrors 	OBJECT-TYPE
	SYNTAX		Gauge32			(0..4294967295)
	MAX-ACCESS 	read-only
	STATUS 		current
	DESCRIPTION
	""
	::= { chrComPmEthETH-IntervalEntry  5 }

chrComPmEthdot3StatsLateCollisions 	OBJECT-TYPE
	SYNTAX		Gauge32			(0..4294967295)
	MAX-ACCESS 	read-only
	STATUS 		current
	DESCRIPTION
	""
	::= { chrComPmEthETH-IntervalEntry  6 }

chrComPmEthdot3StatsFrameTooLongs 	OBJECT-TYPE
	SYNTAX		Gauge32			(0..4294967295)
	MAX-ACCESS 	read-only
	STATUS 		current
	DESCRIPTION
	""
	::= { chrComPmEthETH-IntervalEntry  7 }

chrComPmEthdot3StatsInternalMacReceiveErrors 	OBJECT-TYPE
	SYNTAX		Gauge32			(0..4294967295)
	MAX-ACCESS 	read-only
	STATUS 		current
	DESCRIPTION
	""
	::= { chrComPmEthETH-IntervalEntry  8 }

chrComPmEthifInOctets 	OBJECT-TYPE
	SYNTAX		Gauge32			(0..4294967295)
	MAX-ACCESS 	read-only
	STATUS 		current
	DESCRIPTION
	""
	::= { chrComPmEthETH-IntervalEntry  9 }

chrComPmEthifInUcastPkts 	OBJECT-TYPE
	SYNTAX		Gauge32			(0..4294967295)
	MAX-ACCESS 	read-only
	STATUS 		current
	DESCRIPTION
	""
	::= { chrComPmEthETH-IntervalEntry  10 }

chrComPmEthifInDiscards 	OBJECT-TYPE
	SYNTAX		Gauge32			(0..4294967295)
	MAX-ACCESS 	read-only
	STATUS 		current
	DESCRIPTION
	""
	::= { chrComPmEthETH-IntervalEntry  11 }

chrComPmEthifInErrors 	OBJECT-TYPE
	SYNTAX		Gauge32			(0..4294967295)
	MAX-ACCESS 	read-only
	STATUS 		current
	DESCRIPTION
	""
	::= { chrComPmEthETH-IntervalEntry  12 }

chrComPmEthifOutOctets 	OBJECT-TYPE
	SYNTAX		Gauge32			(0..4294967295)
	MAX-ACCESS 	read-only
	STATUS 		current
	DESCRIPTION
	""
	::= { chrComPmEthETH-IntervalEntry  13 }

chrComPmEthifOutUcastPkts 	OBJECT-TYPE
	SYNTAX		Gauge32			(0..4294967295)
	MAX-ACCESS 	read-only
	STATUS 		current
	DESCRIPTION
	""
	::= { chrComPmEthETH-IntervalEntry  14 }

chrComPmEthifInMulticastPkts 	OBJECT-TYPE
	SYNTAX		Gauge32			(0..4294967295)
	MAX-ACCESS 	read-only
	STATUS 		current
	DESCRIPTION
	""
	::= { chrComPmEthETH-IntervalEntry  15 }

chrComPmEthifInBroadcastPkts 	OBJECT-TYPE
	SYNTAX		Gauge32			(0..4294967295)
	MAX-ACCESS 	read-only
	STATUS 		current
	DESCRIPTION
	""
	::= { chrComPmEthETH-IntervalEntry  16 }

chrComPmEthifOutMulticastPkts 	OBJECT-TYPE
	SYNTAX		Gauge32			(0..4294967295)
	MAX-ACCESS 	read-only
	STATUS 		current
	DESCRIPTION
	""
	::= { chrComPmEthETH-IntervalEntry  17 }

chrComPmEthifOutBroadcastPkts 	OBJECT-TYPE
	SYNTAX		Gauge32			(0..4294967295)
	MAX-ACCESS 	read-only
	STATUS 		current
	DESCRIPTION
	""
	::= { chrComPmEthETH-IntervalEntry  18 }

chrComPmEthchrFrames64Bytes 	OBJECT-TYPE
	SYNTAX		Gauge32			(0..4294967295)
	MAX-ACCESS 	read-only
	STATUS 		current
	DESCRIPTION
	""
	::= { chrComPmEthETH-IntervalEntry  19 }

chrComPmEthchrFrames65to127Bytes 	OBJECT-TYPE
	SYNTAX		Gauge32			(0..4294967295)
	MAX-ACCESS 	read-only
	STATUS 		current
	DESCRIPTION
	""
	::= { chrComPmEthETH-IntervalEntry  20 }

chrComPmEthchrFrames128to256Bytes 	OBJECT-TYPE
	SYNTAX		Gauge32			(0..4294967295)
	MAX-ACCESS 	read-only
	STATUS 		current
	DESCRIPTION
	""
	::= { chrComPmEthETH-IntervalEntry  21 }

chrComPmEthchrFrames257to512Bytes 	OBJECT-TYPE
	SYNTAX		Gauge32			(0..4294967295)
	MAX-ACCESS 	read-only
	STATUS 		current
	DESCRIPTION
	""
	::= { chrComPmEthETH-IntervalEntry  22 }

chrComPmEthchrFrames513to1024Bytes 	OBJECT-TYPE
	SYNTAX		Gauge32			(0..4294967295)
	MAX-ACCESS 	read-only
	STATUS 		current
	DESCRIPTION
	""
	::= { chrComPmEthETH-IntervalEntry  23 }

chrComPmEthchrFrames1024toMaxBytes 	OBJECT-TYPE
	SYNTAX		Gauge32			(0..4294967295)
	MAX-ACCESS 	read-only
	STATUS 		current
	DESCRIPTION
	""
	::= { chrComPmEthETH-IntervalEntry  24 }


END
