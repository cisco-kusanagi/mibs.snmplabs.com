INTEL-DHCPS-MIB DEFINITIONS ::= BEGIN

-- Copyright (C) 1998 Intel Corporation. All rights reserved.
--
-- DHCP Server MIB, 1998-11-18
--
-- Proprietary MIB containing information about DHCP Server.
--
-- Build 2
--

IMPORTS
       IpAddress               FROM RFC1155-SMI
       mib2ext                 FROM INTEL-GEN-MIB
       OBJECT-TYPE             FROM RFC-1212
       DisplayString           FROM RFC1213-MIB;

dhcps            OBJECT IDENTIFIER ::= { mib2ext 7 }
dhcpsInfo        OBJECT IDENTIFIER ::= { dhcps 1 }
dhcpsConf        OBJECT IDENTIFIER ::= { dhcps 2 }

dhcpsInfoTable OBJECT-TYPE
    SYNTAX SEQUENCE OF DhcpsInfoEntry
    ACCESS not-accessible
    STATUS mandatory
    DESCRIPTION "Monitoring information for DHCP server."
    ::= { dhcpsInfo 1 }

dhcpsInfoEntry OBJECT-TYPE
    SYNTAX DhcpsInfoEntry
    ACCESS not-accessible
    STATUS mandatory
    DESCRIPTION ""
    INDEX { dhcpsInfoHostAddress }
    ::= { dhcpsInfoTable 1 }

DhcpsInfoEntry ::= SEQUENCE {
                        dhcpsInfoHostAddress
                           IpAddress,
                        dhcpsInfoMacAddress
                           OCTET STRING,
                        dhcpsInfoHostName
                           DisplayString (SIZE(20)),
                        dhcpsInfoAge
                           INTEGER,
                        dhcpsInfoState
                           INTEGER
                        }

dhcpsInfoHostAddress OBJECT-TYPE
    SYNTAX IpAddress
    ACCESS read-only
    STATUS mandatory
    DESCRIPTION "The IP address assigned to the client."
    ::= { dhcpsInfoEntry 1 }

dhcpsInfoMacAddress OBJECT-TYPE
    SYNTAX OCTET STRING (SIZE(6))
    ACCESS read-only
    STATUS mandatory
    DESCRIPTION "The client's MAC Address."
    ::= { dhcpsInfoEntry 2 }

dhcpsInfoHostName OBJECT-TYPE
    SYNTAX DisplayString (SIZE(20))
    ACCESS read-only
    STATUS mandatory
    DESCRIPTION "The client's hostname."
    ::= { dhcpsInfoEntry 3 }

dhcpsInfoAge OBJECT-TYPE
    SYNTAX INTEGER
    ACCESS read-only
    STATUS mandatory
    DESCRIPTION "The no. of seconds since last change of state."
    ::= { dhcpsInfoEntry 4 }

dhcpsInfoState OBJECT-TYPE
    SYNTAX INTEGER {
	deleted(1),
	declined(2),
	offered(3),
	assigned(4),
	modified(5),
	pinged(6),
	reserved(7),
	released(8),
	obsolete(9)
    }
    ACCESS read-write
    STATUS mandatory
    DESCRIPTION "The state of the DHCP entry."
    ::= { dhcpsInfoEntry 5 }

dhcpsConfInfoTable OBJECT-TYPE
    SYNTAX SEQUENCE OF DhcpsConfInfoEntry
    ACCESS not-accessible
    STATUS mandatory
    DESCRIPTION "Configuration information for DHCP server."
    ::= { dhcpsConf 1 }

dhcpsConfInfoEntry OBJECT-TYPE
    SYNTAX DhcpsConfInfoEntry
    ACCESS not-accessible
    STATUS mandatory
    DESCRIPTION ""
    INDEX { dhcpsConfInfoId }
    ::= { dhcpsConfInfoTable 1 }

DhcpsConfInfoEntry ::= SEQUENCE {
                        dhcpsConfInfoId
                           OCTET STRING,
                        dhcpsConfInfoHandle
                           INTEGER,
                        dhcpsConfInfoType
                           INTEGER,
                        dhcpsConfInfoTableOffset
                           INTEGER,
                        dhcpsConfInfoIndexOffset
                           INTEGER,
                        dhcpsConfInfoRecordCount
                           INTEGER,
                        dhcpsConfInfoRecordLength
                           INTEGER
                        }

dhcpsConfInfoId OBJECT-TYPE
    SYNTAX OCTET STRING (SIZE(4))
    ACCESS read-only
    STATUS mandatory
    DESCRIPTION "Parameter block ID. The DHCP server uses two
                 parameter blocks: KBE.1 (75.66.69.1) and
                 KBE.2 (75.66.69.2)."
    ::= { dhcpsConfInfoEntry 1 }

dhcpsConfInfoHandle OBJECT-TYPE
    SYNTAX INTEGER
    ACCESS read-only
    STATUS mandatory
    DESCRIPTION "The current handle for all set requests in
                 dhcpsConfInfoTable."
    ::= { dhcpsConfInfoEntry 2 }

dhcpsConfInfoType OBJECT-TYPE
    SYNTAX INTEGER {
	noTable(1),
	tableIndexSize0(2),
	tableIndexSize1(3),
	tableIndexSize2(4),
	tableIndexSize4(5)
    }
    ACCESS read-only
    STATUS mandatory
    DESCRIPTION "There are 5 types of parameter blocks:
                 noTable:         A plain block of data
                 tableIndexSize0: A table where the indexes are implicit
                 tableIndexSize1: A table where the indexes takes up 1 byte
                 tableIndexSize2: A table where the indexes takes up 2 bytes
                 tableIndexSize4: A table where the indexes takes up 4 bytes."
    ::= { dhcpsConfInfoEntry 3 }

dhcpsConfInfoTableOffset OBJECT-TYPE
    SYNTAX INTEGER
    ACCESS read-only
    STATUS mandatory
    DESCRIPTION "The offset in dhcpsConfData where the table starts. Always 0
                 when dhcpsConfInfoType is noTable."
    ::= { dhcpsConfInfoEntry 4 }

dhcpsConfInfoIndexOffset OBJECT-TYPE
    SYNTAX INTEGER
    ACCESS read-only
    STATUS mandatory
    DESCRIPTION "The offset in dhcpsConfData where the index can be found.
                 Always 0 when dhcpsConfInfoType is noTable or
                 tableIndexSize0."
    ::= { dhcpsConfInfoEntry 5 }

dhcpsConfInfoRecordCount OBJECT-TYPE
    SYNTAX INTEGER
    ACCESS read-only
    STATUS mandatory
    DESCRIPTION "The number of records in the table. Always 0 when
                 dhcpsConfInfoType is noTable."
    ::= { dhcpsConfInfoEntry 6 }

dhcpsConfInfoRecordLength OBJECT-TYPE
    SYNTAX INTEGER
    ACCESS read-only
    STATUS mandatory
    DESCRIPTION "The length of a record in the table. Always 0 when
                 dhcpsConfInfoType is noTable."
    ::= { dhcpsConfInfoEntry 7 }

dhcpsConfTable OBJECT-TYPE
    SYNTAX SEQUENCE OF DhcpsConfEntry
    ACCESS not-accessible
    STATUS mandatory
    DESCRIPTION "Configuration for DHCP server."
    ::= { dhcpsConf 2 }

dhcpsConfEntry OBJECT-TYPE
    SYNTAX DhcpsConfEntry
    ACCESS not-accessible
    STATUS mandatory
    DESCRIPTION ""
    INDEX { dhcpsConfId, dhcpsConfIndex, dhcpsConfHandle }
    ::= { dhcpsConfTable 1 }

DhcpsConfEntry ::= SEQUENCE {
                        dhcpsConfId
                           OCTET STRING,
                        dhcpsConfIndex
                           OCTET STRING,
                        dhcpsConfHandle
                           INTEGER,
                        dhcpsConfData
                           OCTET STRING,
                        dhcpsConfOptions
                           INTEGER,
                        dhcpsConfStatus
                           INTEGER
                        }

dhcpsConfId OBJECT-TYPE
    SYNTAX OCTET STRING (SIZE(4))
    ACCESS read-only
    STATUS mandatory
    DESCRIPTION "Parameter block ID. The DHCP server uses two
                 parameter blocks: KBE.1 (75.66.69.1) and
                 KBE.2 (75.66.69.2)."
    ::= { dhcpsConfEntry 1 }

dhcpsConfIndex OBJECT-TYPE
    SYNTAX OCTET STRING (SIZE(4))
    ACCESS read-only
    STATUS mandatory
    DESCRIPTION "The index of the current record in a table.
                 If the index is 0, dhcpsConfData has some non-table
                 data. If dhcpsConfInfoTableOffset is 0,
                 dhcpsConfIndex is always 0."
    ::= { dhcpsConfEntry 2 }

dhcpsConfHandle OBJECT-TYPE
    SYNTAX INTEGER
    ACCESS read-only
    STATUS mandatory
    DESCRIPTION "The current handle. To get the current handle refer
                 to dhcpsConfInfoHandle."
    ::= { dhcpsConfEntry 3 }

dhcpsConfData OBJECT-TYPE
    SYNTAX OCTET STRING (SIZE(255))
    ACCESS read-write
    STATUS mandatory
    DESCRIPTION "The data. All numbers are big-endian.
                 KBE.1 is of type noTable and has the following layout:
                   UINT32        lease_time;
                   BYTE          domain_name[27];
                   BYTE          limit_lease;
                   UINT32        primary_dns;
                   UINT32        secondary_dns;
                   UINT32        primary_wins;
                   UINT32        secondary_wins;
                   BYTE          node_type;
                   BYTE          server_enabled;
                   UINT16        max_entries;
                 KBE.2 is of type tableIndexSize0 and has the following layout:
                   UINT32        start_addr;
                   UINT32        stop_addr;
                   UINT32        mask;"
    ::= { dhcpsConfEntry 4 }

dhcpsConfOptions OBJECT-TYPE
    SYNTAX INTEGER
    ACCESS read-only
    STATUS mandatory
    DESCRIPTION "Currently not used, always 0."
    ::= { dhcpsConfEntry 5 }

dhcpsConfStatus OBJECT-TYPE
    SYNTAX INTEGER {
	normal(1),
	delete(2),
	copy(3)
    }
    ACCESS read-write
    STATUS mandatory
    DESCRIPTION "The status of the record. copy(3) is for future use."
    ::= { dhcpsConfEntry 6 }

END
