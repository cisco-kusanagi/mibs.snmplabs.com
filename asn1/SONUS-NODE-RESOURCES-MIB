--
-- This SMIv2 module has been generated by smidump 0.2-cvs. Do not edit.
--

SONUS-NODE-RESOURCES-MIB DEFINITIONS ::= BEGIN

IMPORTS
    Integer32, IpAddress, MODULE-IDENTITY, NOTIFICATION-TYPE, 
    OBJECT-TYPE
        FROM SNMPv2-SMI
    DisplayString, RowStatus
        FROM SNMPv2-TC
    sonusEventClass, sonusEventDescription, sonusEventLevel
        FROM SONUS-COMMON-MIB
    sonusResourcesMIBs
        FROM SONUS-SMI
    SonusAdminState, SonusName, SonusNameReference
        FROM SONUS-TC;

sonusNodeResourcesMIB MODULE-IDENTITY
    LAST-UPDATED    "200107310000Z"
    ORGANIZATION    
            "Sonus Networks, Inc."
    CONTACT-INFO    
            "   Customer Support    
             Sonus Networks, Inc,
             5 carlisle Road
             Westford, MA 01886
             USA
             
             Tel: 978-692-8999
             Fax: 978-392-9118
             E-mail: cs.snmp@sonusnet.com"
    DESCRIPTION     
            "The MIB Module for Node Resources Management."
    ::= { sonusResourcesMIBs 2 }


sonusNodeResourcesMIBObjects OBJECT IDENTIFIER
    ::= { sonusNodeResourcesMIB 1 }

sonusServProfile OBJECT IDENTIFIER
    ::= { sonusNodeResourcesMIBObjects 1 }

sonusServProfileNextIndex OBJECT-TYPE
    SYNTAX          Integer32
    MAX-ACCESS      read-only
    STATUS          deprecated
    DESCRIPTION     
            "This field is deprecated. The next valid index to use when creating an entry in
             the sonusServProfileTable."
    ::= { sonusServProfile 1 }

sonusServProfileTable OBJECT-TYPE
    SYNTAX          SEQUENCE OF SonusServProfileEntry
    MAX-ACCESS      not-accessible
    STATUS          deprecated
    DESCRIPTION     
            "This field is deprecated. This table specifies the service profile list for the node."
    ::= { sonusServProfile 2 }

sonusServProfileEntry OBJECT-TYPE
    SYNTAX          SonusServProfileEntry
    MAX-ACCESS      not-accessible
    STATUS          deprecated
    DESCRIPTION     
            "This field is deprecated. "
    INDEX           { sonusServProfileIndex }
    ::= { sonusServProfileTable 1 }

SonusServProfileEntry ::=
    SEQUENCE {
        sonusServProfileIndex           Integer32,
        sonusServProfileState           INTEGER,
        sonusServProfileName            SonusName,
        sonusServProfileType            INTEGER,
        sonusServProfileVCktEncoding    INTEGER,
        sonusServProfileVCktBandwidth   Integer32,
        sonusServProfileVCktNecEnable   INTEGER,
        sonusServProfileVPktEncoding    INTEGER,
        sonusServProfileVPktFrameSize   Integer32,
        sonusServProfileVPktFramesPerPacket   Integer32,
        sonusServProfileVPktMaxNetworkJitter    Integer32,
        sonusServProfileVPktTosValue    Integer32,
        sonusServProfileCttTestType     INTEGER,
        sonusServProfileCttTimeout      Integer32,
        sonusServProfileCttMinDetectTime Integer32,
        sonusServProfileCttMinReleaseTime Integer32,
        sonusServProfileCapability      INTEGER,
        sonusServProfileDPktRestrictedCfg INTEGER,
        sonusServProfileDPktRtpPayloadType  Integer32,
        sonusServProfileDPktMaxNetworkJitter    Integer32,
        sonusServProfileRowStatus       RowStatus
    }

sonusServProfileIndex OBJECT-TYPE
    SYNTAX          Integer32
    MAX-ACCESS      read-only
    STATUS          deprecated
    DESCRIPTION     
            "This field is deprecated. Identifies the target service profile entry."
    ::= { sonusServProfileEntry 1 }

sonusServProfileState OBJECT-TYPE
    SYNTAX          INTEGER { disabled(1), enabled(2) }
    MAX-ACCESS      read-write
    STATUS          deprecated
    DESCRIPTION     
            "This field is deprecated. The administrative state of this service profile entry."
    DEFVAL          { disabled }
    ::= { sonusServProfileEntry 2 }

sonusServProfileName OBJECT-TYPE
    SYNTAX          SonusName
    MAX-ACCESS      read-write
    STATUS          deprecated
    DESCRIPTION     
            "This field is deprecated. The user name of this service profile."
    ::= { sonusServProfileEntry 3 }

sonusServProfileType OBJECT-TYPE
    SYNTAX          INTEGER { circuit(1), packet(2) }
    MAX-ACCESS      read-write
    STATUS          deprecated
    DESCRIPTION     
            "This field is deprecated. The type of endpoint (circuit or packet) supported by this service profile.
             Circuit endpoints support all the VCkt and VPkt profile parameters for echo
             cancellation and packetization. Packet endpoints support only the VPkt
             parameters for packetization."
    DEFVAL          { circuit }
    ::= { sonusServProfileEntry 4 }

sonusServProfileVCktEncoding OBJECT-TYPE
    SYNTAX          INTEGER { g711ulaw(1), g711alaw(2), none(5) }
    MAX-ACCESS      read-write
    STATUS          deprecated
    DESCRIPTION     
            "This field is deprecated. The audio encoding method to be performed on the voice data
             received from, and destined to the PSTN. The default encoding
             method is G.711 Ulaw."
    DEFVAL          { g711ulaw }
    ::= { sonusServProfileEntry 5 }

sonusServProfileVCktBandwidth OBJECT-TYPE
    SYNTAX          Integer32 (1..24)
    MAX-ACCESS      read-write
    STATUS          deprecated
    DESCRIPTION     
            "This field is deprecated. The number of DS0 channels to group for Nx64 connections. 
             Valid entries are 1 to 24 channels, allowing up to a 
             complete set of T1 channels to be grouped at a single
             connection. The default bandwidth is 1 channel."
    DEFVAL          { 1 }
    ::= { sonusServProfileEntry 6 }

sonusServProfileVCktNecEnable OBJECT-TYPE
    SYNTAX          INTEGER { disabled(1), enabled(2) }
    MAX-ACCESS      read-write
    STATUS          deprecated
    DESCRIPTION     
            "This field is deprecated. Specifies whether Network Echo Cancellation (NEC) is 
             enabled for the channel. When enabled, NEC is enabled
             acording to the appropriate NEC configuration parameters.
             When disabled, the Voice Packet Assembler/Disassember (VPAD)
             operates in a circuit emulation mode."
    DEFVAL          { enabled }
    ::= { sonusServProfileEntry 7 }

sonusServProfileVPktEncoding OBJECT-TYPE
    SYNTAX          INTEGER { g711ulaw(1), g711alaw(2), g7231(3), 
                        g729a(4), none(5) }
    MAX-ACCESS      read-write
    STATUS          deprecated
    DESCRIPTION     
            "This field is deprecated. The audio encoding method to be performed on the packet data
             received from, and destined to the IP network. The default 
             encoding method is G.711 Ulaw."
    DEFVAL          { g711ulaw }
    ::= { sonusServProfileEntry 8 }

sonusServProfileVPktFrameSize OBJECT-TYPE
    SYNTAX          Integer32
    MAX-ACCESS      read-write
    STATUS          deprecated
    DESCRIPTION     
            "This field is deprecated. Specifies the number of samples per frame. For G.711
             encoding mode, value must be a multiple of 8 samples.
             For G.723 encoding mode, value must be a multiple of
             240 samples. For G.729A, value must be a multiple of
             80 samples. Note that 8 samples represent one millisecond
             of voice data. 
             
             A value of 0 specifies a frame size equal to the minimum 
             for the encoding method (e.g 8 samples for G.711)"
    DEFVAL          { 8 }
    ::= { sonusServProfileEntry 9 }

sonusServProfileVPktFramesPerPacket OBJECT-TYPE
    SYNTAX          Integer32
    MAX-ACCESS      read-write
    STATUS          deprecated
    DESCRIPTION     
            "This field is deprecated. Specifies the number of frames to transmit per packet.
             For G.711 encoding mode, valid values range from 5 to
             40 frames, in increments of 5 frames. The default value
             for G.711 is 10 frames per packet. For G.723 encoding
             mode, valid values are 1 or 2, with a default value of
             1 frame per packet.
             
             A value of 0 specifies the number of frames per packet
             equal to the default value for the encoding mode
             (e.g. 10 frames per packet for G.711)."
    DEFVAL          { 10 }
    ::= { sonusServProfileEntry 10 }

sonusServProfileVPktMaxNetworkJitter OBJECT-TYPE
    SYNTAX          Integer32 (40..400)
    MAX-ACCESS      read-write
    STATUS          deprecated
    DESCRIPTION     
            "This field is deprecated. Specifies the maximum expected network jitter across the
             IP network in increments of 125usec. This value defines
             the size of the initial playout buffer required to 
             absorb the maximum expected packet delay across the 
             network. The minimum value is 40 (5msec) and the maximum
             value is 400 (50msec), with a default value of 80 (10msec)."
    DEFVAL          { 80 }
    ::= { sonusServProfileEntry 11 }

sonusServProfileVPktTosValue OBJECT-TYPE
    SYNTAX          Integer32 (0..255)
    MAX-ACCESS      read-write
    STATUS          deprecated
    DESCRIPTION     
            "This field is deprecated. Specifies the Type Of Service (TOS) parameters to be provided in the 
             IP header for voice packets. The TOS value is specified as an 8-bit hex 
             value 0x00-0xFF allowing complete flexibility with respect to the contents
             of the TOS byte."
    DEFVAL          { 0 }
    ::= { sonusServProfileEntry 12 }

sonusServProfileCttTestType OBJECT-TYPE
    SYNTAX          INTEGER { remoteLoopback(1), remote2Wire(2), 
                        remote4Wire(3) }
    MAX-ACCESS      read-write
    STATUS          deprecated
    DESCRIPTION     
            "This field is deprecated. For ISUP service profiles, specifies the type of continuity
             test to perform, based on the configuration of the remote
             switch or trunk connection. The remoteLoopback test is used
             when the remote switch will loop back channel being tested.
             The remote2Wire test is used when the remote switch supports
             the 2 wire continuity test procedure. And the remote4Wire 
             test mode is used when the remote switch supports the 4 wire
             continuity test procedure. The default value is remoteLoopback."
    DEFVAL          { remoteLoopback }
    ::= { sonusServProfileEntry 13 }

sonusServProfileCttTimeout OBJECT-TYPE
    SYNTAX          Integer32 (1..10)
    MAX-ACCESS      read-write
    STATUS          deprecated
    DESCRIPTION     
            "This field is deprecated. For ISUP service profiles, specifies the overall test timeout
             value. The continuity test will be declared failed if the
             continuity tone is not detected within this timeout period. 
             The timeout is specified in seconds, with a default value of
             2 seconds."
    DEFVAL          { 2 }
    ::= { sonusServProfileEntry 14 }

sonusServProfileCttMinDetectTime OBJECT-TYPE
    SYNTAX          Integer32 (10..60)
    MAX-ACCESS      read-write
    STATUS          deprecated
    DESCRIPTION     
            "This field is deprecated. For ISUP service profiles, specifies the minimum time
             to detect the presence of the continuity test tone. The 
             minimum detect time is specified in milliseconds, with
             a default time of 45 ms."
    DEFVAL          { 45 }
    ::= { sonusServProfileEntry 15 }

sonusServProfileCttMinReleaseTime OBJECT-TYPE
    SYNTAX          Integer32 (10..40)
    MAX-ACCESS      read-write
    STATUS          deprecated
    DESCRIPTION     
            "This field is deprecated. For ISUP service profiles, specifies the minimum time
             to detect that the continuity test tone has been removed
             and is no longer present. The minimum release time
             is specified in milliseconds, with a default time of 25 ms."
    DEFVAL          { 25 }
    ::= { sonusServProfileEntry 16 }

sonusServProfileCapability OBJECT-TYPE
    SYNTAX          INTEGER { voiceOnly(1), circuitModeData(2), 
                        voiceOrCircuitModeData(3) }
    MAX-ACCESS      read-write
    STATUS          deprecated
    DESCRIPTION     
            "This field is deprecated. Specifies the data capabilities for the circuit. This parameter
             specifies whether voice only, circuit mode data only, or both voice
             and circuit mode data can be supported by the circuit."
    DEFVAL          { voiceOrCircuitModeData }
    ::= { sonusServProfileEntry 17 }

sonusServProfileDPktRestrictedCfg OBJECT-TYPE
    SYNTAX          INTEGER { unrestricted(1), restricted(2) }
    MAX-ACCESS      read-write
    STATUS          deprecated
    DESCRIPTION     
            "This field is deprecated. Specifies whether the circuit may support 64 Kbit/s unrestricted data, or
             if the circuit supports 56 Kbit/s restricted data."
    DEFVAL          { unrestricted }
    ::= { sonusServProfileEntry 18 }

sonusServProfileDPktRtpPayloadType OBJECT-TYPE
    SYNTAX          Integer32 (0..127)
    MAX-ACCESS      read-write
    STATUS          deprecated
    DESCRIPTION     
            "This field is deprecated. Specifies the RTP payload type to be included in the RTP header of the voice data
             packet"
    DEFVAL          { 56 }
    ::= { sonusServProfileEntry 19 }

sonusServProfileDPktMaxNetworkJitter OBJECT-TYPE
    SYNTAX          Integer32 (40..400)
    MAX-ACCESS      read-write
    STATUS          deprecated
    DESCRIPTION     
            "This field is deprecated. Specifies the maximum expected network jitter across the
             network for data calls in increments of 125usec. This value 
             defines the size of the initial playout buffer required to 
             absorb the maximum expected packet delay across the 
             network. A separate value for data calls is provided to 
             allow a single service profile to specify the jitter buffer
             size for both voice calls and data calls.
             The minimum value is 40 (5msec) and the maximum value is 400 (50msec), 
             with a default value of 400 (50msec)."
    DEFVAL          { 400 }
    ::= { sonusServProfileEntry 20 }

sonusServProfileRowStatus OBJECT-TYPE
    SYNTAX          RowStatus
    MAX-ACCESS      read-write
    STATUS          deprecated
    DESCRIPTION     
            "This field is deprecated. "
    ::= { sonusServProfileEntry 21 }

sonusSonicBusStatTable OBJECT-TYPE
    SYNTAX          SEQUENCE OF SonusSonicBusStatEntry
    MAX-ACCESS      not-accessible
    STATUS          current
    DESCRIPTION     
            "This table presents Sonic Bus statistics for the node."
    ::= { sonusNodeResourcesMIBObjects 2 }

sonusSonicBusStatEntry OBJECT-TYPE
    SYNTAX          SonusSonicBusStatEntry
    MAX-ACCESS      not-accessible
    STATUS          current
    DESCRIPTION     
            ""
    INDEX           { sonusSonicBusStatShelfIndex }
    ::= { sonusSonicBusStatTable 1 }

SonusSonicBusStatEntry ::=
    SEQUENCE {
        sonusSonicBusStatShelfIndex     Integer32,
        sonusSonicBusStatNumCalls       Integer32,
        sonusSonicBusStatBwAllocated    Integer32,
        sonusSonicBusStatSduCount       Integer32
    }

sonusSonicBusStatShelfIndex OBJECT-TYPE
    SYNTAX          Integer32 (1..6)
    MAX-ACCESS      read-only
    STATUS          current
    DESCRIPTION     
            "Identifies the target shelf."
    ::= { sonusSonicBusStatEntry 1 }

sonusSonicBusStatNumCalls OBJECT-TYPE
    SYNTAX          Integer32
    MAX-ACCESS      read-only
    STATUS          current
    DESCRIPTION     
            "Indicates the number of active calls on the shelf."
    ::= { sonusSonicBusStatEntry 2 }

sonusSonicBusStatBwAllocated OBJECT-TYPE
    SYNTAX          Integer32
    MAX-ACCESS      read-only
    STATUS          current
    DESCRIPTION     
            "Indicates the percentage of Sonic Bus bandwidth allocated to
             the active calls on the shelf."
    ::= { sonusSonicBusStatEntry 3 }

sonusSonicBusStatSduCount OBJECT-TYPE
    SYNTAX          Integer32
    MAX-ACCESS      read-only
    STATUS          current
    DESCRIPTION     
            "Indicates the number of Sonic Bus data units allocated to
             the active calls on the shelf."
    ::= { sonusSonicBusStatEntry 4 }

sonusActiveCallTable OBJECT-TYPE
    SYNTAX          SEQUENCE OF SonusActiveCallEntry
    MAX-ACCESS      not-accessible
    STATUS          current
    DESCRIPTION     
            "This table presents the active call data for the node."
    ::= { sonusNodeResourcesMIBObjects 3 }

sonusActiveCallEntry OBJECT-TYPE
    SYNTAX          SonusActiveCallEntry
    MAX-ACCESS      not-accessible
    STATUS          current
    DESCRIPTION     
            ""
    INDEX           { sonusActiveCallShelfIndex, 
                      sonusActiveCallSlotIndex, sonusActiveCallIndex }
    ::= { sonusActiveCallTable 1 }

SonusActiveCallEntry ::=
    SEQUENCE {
        sonusActiveCallShelfIndex       Integer32,
        sonusActiveCallSlotIndex        Integer32,
        sonusActiveCallIndex            Integer32,
        sonusActiveCallId               Integer32,
        sonusActiveCallSonicBusUnitsAllocated     Integer32,
        sonusActiveCallNumResources     Integer32,
        sonusActiveCallState            DisplayString,
        sonusActiveCallIngressServProfile DisplayString,
        sonusActiveCallEgressServProfile DisplayString,
        sonusActiveCallCallingNum       DisplayString,
        sonusActiveCallCalledNum        DisplayString,
        sonusActiveCallAddressTransPerformed    INTEGER,
        sonusActiveCallOrigCalledNum    DisplayString,
        sonusActiveCallScenarioType     DisplayString,
        sonusActiveCallIngressPstnSlotNum Integer32,
        sonusActiveCallIngressPstnPortNum Integer32,
        sonusActiveCallIngressPstnChannelNum    Integer32,
        sonusActiveCallIngressPstnChannelCount      Integer32,
        sonusActiveCallIngressPstnChannelBitMap       Integer32,
        sonusActiveCallEgressPstnSlotNum Integer32,
        sonusActiveCallEgressPstnPortNum Integer32,
        sonusActiveCallEgressPstnChannelNum   Integer32,
        sonusActiveCallEgressPstnChannelCount     Integer32,
        sonusActiveCallEgressPstnChannelBitMap      Integer32,
        sonusActiveCallIngressLocalIpSockAddr     IpAddress,
        sonusActiveCallIngressRemoteIpSockAddr      IpAddress,
        sonusActiveCallEgressLocalIpSockAddr    IpAddress,
        sonusActiveCallEgressRemoteIpSockAddr     IpAddress,
        sonusActiveCallIngressPstnTrunk DisplayString,
        sonusActiveCallEgressPstnTrunk  DisplayString,
        sonusActiveCallIngressIpDestGwName  DisplayString,
        sonusActiveCallEgressIpDestGwName DisplayString,
        sonusActiveCallDuration         Integer32,
        sonusActiveCallIngressEpType    INTEGER,
        sonusActiveCallEgressEpType     INTEGER,
        sonusActiveCallIngressSgType    INTEGER,
        sonusActiveCallEgressSgType     INTEGER,
        sonusActiveCallPacketsSent      Integer32,
        sonusActiveCallPacketsReceived  Integer32,
        sonusActiveCallOctetsSent       Integer32,
        sonusActiveCallOctetsReceived   Integer32,
        sonusActiveCallPacketsLost      Integer32,
        sonusActiveCallPacketsDiscarded Integer32,
        sonusActiveCallInterarrivalJitter Integer32,
        sonusActiveCallPacketLatency    Integer32
    }

sonusActiveCallShelfIndex OBJECT-TYPE
    SYNTAX          Integer32 (1..6)
    MAX-ACCESS      read-only
    STATUS          current
    DESCRIPTION     
            "Identifies the target shelf."
    ::= { sonusActiveCallEntry 1 }

sonusActiveCallSlotIndex OBJECT-TYPE
    SYNTAX          Integer32 (1..16)
    MAX-ACCESS      read-only
    STATUS          current
    DESCRIPTION     
            "Identifies the target slot."
    ::= { sonusActiveCallEntry 2 }

sonusActiveCallIndex OBJECT-TYPE
    SYNTAX          Integer32
    MAX-ACCESS      read-only
    STATUS          current
    DESCRIPTION     
            "Identifies the target call index."
    ::= { sonusActiveCallEntry 3 }

sonusActiveCallId OBJECT-TYPE
    SYNTAX          Integer32
    MAX-ACCESS      read-only
    STATUS          current
    DESCRIPTION     
            "Represents the global call identifier (GCID) for the call. GCID is unique
             across the entire node."
    ::= { sonusActiveCallEntry 4 }

sonusActiveCallSonicBusUnitsAllocated OBJECT-TYPE
    SYNTAX          Integer32
    MAX-ACCESS      read-only
    STATUS          current
    DESCRIPTION     
            "Represents the SonicBus bandwidth allocated for the call expressed as
             SonicData Units per second."
    ::= { sonusActiveCallEntry 5 }

sonusActiveCallNumResources OBJECT-TYPE
    SYNTAX          Integer32
    MAX-ACCESS      read-only
    STATUS          current
    DESCRIPTION     
            "Represents the number of resources currently allocated to the call."
    ::= { sonusActiveCallEntry 6 }

sonusActiveCallState OBJECT-TYPE
    SYNTAX          DisplayString (SIZE(0..23))
    MAX-ACCESS      read-only
    STATUS          current
    DESCRIPTION     
            "Represents the current call state."
    ::= { sonusActiveCallEntry 7 }

sonusActiveCallIngressServProfile OBJECT-TYPE
    SYNTAX          DisplayString (SIZE(0..23))
    MAX-ACCESS      read-only
    STATUS          current
    DESCRIPTION     
            "The name of the ingress service profile associated with this call."
    ::= { sonusActiveCallEntry 8 }

sonusActiveCallEgressServProfile OBJECT-TYPE
    SYNTAX          DisplayString (SIZE(0..23))
    MAX-ACCESS      read-only
    STATUS          current
    DESCRIPTION     
            "The name of the egress service profile associated with this call."
    ::= { sonusActiveCallEntry 9 }

sonusActiveCallCallingNum OBJECT-TYPE
    SYNTAX          DisplayString (SIZE(0..30))
    MAX-ACCESS      read-only
    STATUS          current
    DESCRIPTION     
            "The E.164 number representing the Calling Party's telephone number."
    ::= { sonusActiveCallEntry 10 }

sonusActiveCallCalledNum OBJECT-TYPE
    SYNTAX          DisplayString (SIZE(0..30))
    MAX-ACCESS      read-only
    STATUS          current
    DESCRIPTION     
            "The E.164 number representing the Called Party's telephone number."
    ::= { sonusActiveCallEntry 11 }

sonusActiveCallAddressTransPerformed OBJECT-TYPE
    SYNTAX          INTEGER { none(1), lnp(2), tollfree(3) }
    MAX-ACCESS      read-only
    STATUS          current
    DESCRIPTION     
            "Indicates whether any address translation has been performed on the 
             called party number. Valid translations are Local Number Portability (LPN), 
             and 800 number translation (Tollfree)."
    ::= { sonusActiveCallEntry 12 }

sonusActiveCallOrigCalledNum OBJECT-TYPE
    SYNTAX          DisplayString (SIZE(0..30))
    MAX-ACCESS      read-only
    STATUS          current
    DESCRIPTION     
            "If an address translation has been performed on the called party number, 
             this entry contains the original, untranslated number."
    ::= { sonusActiveCallEntry 13 }

sonusActiveCallScenarioType OBJECT-TYPE
    SYNTAX          DisplayString (SIZE(0..23))
    MAX-ACCESS      read-only
    STATUS          current
    DESCRIPTION     
            "Specifies the call scenario type for this call."
    ::= { sonusActiveCallEntry 14 }

sonusActiveCallIngressPstnSlotNum OBJECT-TYPE
    SYNTAX          Integer32 (1..16)
    MAX-ACCESS      read-only
    STATUS          current
    DESCRIPTION     
            "For calls originating from the PSTN (circuit) side, indicates the slot
             of the circuit card on which the call was delivered."
    ::= { sonusActiveCallEntry 15 }

sonusActiveCallIngressPstnPortNum OBJECT-TYPE
    SYNTAX          Integer32 (1..28)
    MAX-ACCESS      read-only
    STATUS          current
    DESCRIPTION     
            "For calls originating from the PSTN (circuit) side, indicates the T1 port
             on the circuit card on which the call was delivered. For CNS10 cards, the
             port number will be in the range 1-12; for CNS30 cards, the port number will
             be in the range 1-28."
    ::= { sonusActiveCallEntry 16 }

sonusActiveCallIngressPstnChannelNum OBJECT-TYPE
    SYNTAX          Integer32 (1..24)
    MAX-ACCESS      read-only
    STATUS          current
    DESCRIPTION     
            "For calls originating from the PSTN (circuit) side, indicates the DS0 channel
             on which the call is being carried."
    ::= { sonusActiveCallEntry 17 }

sonusActiveCallIngressPstnChannelCount OBJECT-TYPE
    SYNTAX          Integer32 (1..24)
    MAX-ACCESS      read-only
    STATUS          current
    DESCRIPTION     
            "For calls originating from the PSTN (circuit) side, indicates the number of
             DS0 channels on which the call is being carried. This value is meaningful for
             Nx64 service calls."
    ::= { sonusActiveCallEntry 18 }

sonusActiveCallIngressPstnChannelBitMap OBJECT-TYPE
    SYNTAX          Integer32
    MAX-ACCESS      read-only
    STATUS          current
    DESCRIPTION     
            "For calls originating from the PSTN (circuit) side, provides a bit map of DS0
             channels on which the call is being carried. For Nx64 service calls where N is
             greater than 1, multiple bits will be marked in the bit map."
    ::= { sonusActiveCallEntry 19 }

sonusActiveCallEgressPstnSlotNum OBJECT-TYPE
    SYNTAX          Integer32 (1..16)
    MAX-ACCESS      read-only
    STATUS          current
    DESCRIPTION     
            "For calls delivered to the PSTN (circuit) side, indicates the slot
             of the circuit card on which the call was delivered."
    ::= { sonusActiveCallEntry 20 }

sonusActiveCallEgressPstnPortNum OBJECT-TYPE
    SYNTAX          Integer32 (1..28)
    MAX-ACCESS      read-only
    STATUS          current
    DESCRIPTION     
            "For calls delivered to the PSTN (circuit) side, indicates the T1 port
             on the circuit card on which the call was delivered. For CNS10 cards, the
             port number will be in the range 1-12; for CNS30 cards, the port number will
             be in the range 1-28."
    ::= { sonusActiveCallEntry 21 }

sonusActiveCallEgressPstnChannelNum OBJECT-TYPE
    SYNTAX          Integer32 (1..24)
    MAX-ACCESS      read-only
    STATUS          current
    DESCRIPTION     
            "For calls delivered to the PSTN (circuit) side, indicates the DS0 channel
             on which the call is being carried."
    ::= { sonusActiveCallEntry 22 }

sonusActiveCallEgressPstnChannelCount OBJECT-TYPE
    SYNTAX          Integer32 (1..24)
    MAX-ACCESS      read-only
    STATUS          current
    DESCRIPTION     
            "For calls delivered to the PSTN (circuit) side, indicates the number of
             DS0 channels on which the call is being carried. This value is meaningful for
             Nx64 service calls."
    ::= { sonusActiveCallEntry 23 }

sonusActiveCallEgressPstnChannelBitMap OBJECT-TYPE
    SYNTAX          Integer32
    MAX-ACCESS      read-only
    STATUS          current
    DESCRIPTION     
            "For calls delivered to the PSTN (circuit) side, provides a bit map of DS0
             channels on which the call is being carried. For Nx64 service calls where N is
             greater than 1, multiple bits will be marked in the bit map."
    ::= { sonusActiveCallEntry 24 }

sonusActiveCallIngressLocalIpSockAddr OBJECT-TYPE
    SYNTAX          IpAddress
    MAX-ACCESS      read-only
    STATUS          current
    DESCRIPTION     
            "For calls originated on the IP (packet) side, indicates the IP address
             of the incoming (ingress) local socket connection."
    ::= { sonusActiveCallEntry 25 }

sonusActiveCallIngressRemoteIpSockAddr OBJECT-TYPE
    SYNTAX          IpAddress
    MAX-ACCESS      read-only
    STATUS          current
    DESCRIPTION     
            "For calls originated on the IP (packet) side, indicates the IP address
             of the incoming (ingress) remote socket connection."
    ::= { sonusActiveCallEntry 26 }

sonusActiveCallEgressLocalIpSockAddr OBJECT-TYPE
    SYNTAX          IpAddress
    MAX-ACCESS      read-only
    STATUS          current
    DESCRIPTION     
            "For calls delivered to the IP (packet) side, indicates the IP address
             of the outgoing (egress) local socket connection."
    ::= { sonusActiveCallEntry 27 }

sonusActiveCallEgressRemoteIpSockAddr OBJECT-TYPE
    SYNTAX          IpAddress
    MAX-ACCESS      read-only
    STATUS          current
    DESCRIPTION     
            "For calls delivered to the IP (packet) side, indicates the IP address
             of the outgoing (egress) remote socket connection."
    ::= { sonusActiveCallEntry 28 }

sonusActiveCallIngressPstnTrunk OBJECT-TYPE
    SYNTAX          DisplayString (SIZE(0..23))
    MAX-ACCESS      read-only
    STATUS          current
    DESCRIPTION     
            "For calls originating from the PSTN (circuit) side, specifies the trunk
             group name to which the Ingress Pstn Channel belongs."
    ::= { sonusActiveCallEntry 29 }

sonusActiveCallEgressPstnTrunk OBJECT-TYPE
    SYNTAX          DisplayString (SIZE(0..23))
    MAX-ACCESS      read-only
    STATUS          current
    DESCRIPTION     
            "For calls delivered to the PSTN (circuit) side, specifies the trunk
             group name to which the Egress Pstn Channel belongs."
    ::= { sonusActiveCallEntry 30 }

sonusActiveCallIngressIpDestGwName OBJECT-TYPE
    SYNTAX          DisplayString (SIZE(0..23))
    MAX-ACCESS      read-only
    STATUS          current
    DESCRIPTION     
            "For calls originating from the IP (packet) side, specifies the name of the
             remote gateway on which the call originated."
    ::= { sonusActiveCallEntry 31 }

sonusActiveCallEgressIpDestGwName OBJECT-TYPE
    SYNTAX          DisplayString (SIZE(0..23))
    MAX-ACCESS      read-only
    STATUS          current
    DESCRIPTION     
            "For calls delivered to the IP (packet) side, specifies the name of the 
             remote gateway to which the call was delivered."
    ::= { sonusActiveCallEntry 32 }

sonusActiveCallDuration OBJECT-TYPE
    SYNTAX          Integer32
    MAX-ACCESS      read-only
    STATUS          current
    DESCRIPTION     
            "Indicates the duration in seconds for this call following answer."
    ::= { sonusActiveCallEntry 33 }

sonusActiveCallIngressEpType OBJECT-TYPE
    SYNTAX          INTEGER { unknown(0), circuit(1), packet(2) }
    MAX-ACCESS      read-only
    STATUS          current
    DESCRIPTION     
            "Indicates the end point type for the ingress end point."
    ::= { sonusActiveCallEntry 34 }

sonusActiveCallEgressEpType OBJECT-TYPE
    SYNTAX          INTEGER { unknown(0), circuit(1), packet(2) }
    MAX-ACCESS      read-only
    STATUS          current
    DESCRIPTION     
            "Indicates the end point type for the egress end point."
    ::= { sonusActiveCallEntry 35 }

sonusActiveCallIngressSgType OBJECT-TYPE
    SYNTAX          INTEGER { unknown(0), isup(1), cas(2), isdn(3), 
                        h323(4), gwip(5), internal1(6), internal2(7), 
                        mg(8), asg(9), static(10) }
    MAX-ACCESS      read-only
    STATUS          current
    DESCRIPTION     
            "Indicates the signaling type for the ingress end point."
    ::= { sonusActiveCallEntry 36 }

sonusActiveCallEgressSgType OBJECT-TYPE
    SYNTAX          INTEGER { unknown(0), isup(1), cas(2), isdn(3), 
                        h323(4), gwip(5), internal1(6), internal2(7), 
                        mg(8), asg(9), static(10) }
    MAX-ACCESS      read-only
    STATUS          current
    DESCRIPTION     
            "Indicates the signaling type for the egress end point."
    ::= { sonusActiveCallEntry 37 }

sonusActiveCallPacketsSent OBJECT-TYPE
    SYNTAX          Integer32
    MAX-ACCESS      read-only
    STATUS          current
    DESCRIPTION     
            "Indicates the number of RTP packets sent on this call."
    ::= { sonusActiveCallEntry 38 }

sonusActiveCallPacketsReceived OBJECT-TYPE
    SYNTAX          Integer32
    MAX-ACCESS      read-only
    STATUS          current
    DESCRIPTION     
            "Indicates the number of RTP packets received on this call."
    ::= { sonusActiveCallEntry 39 }

sonusActiveCallOctetsSent OBJECT-TYPE
    SYNTAX          Integer32
    MAX-ACCESS      read-only
    STATUS          current
    DESCRIPTION     
            "Indicates the number of RTP octets sent on this call."
    ::= { sonusActiveCallEntry 40 }

sonusActiveCallOctetsReceived OBJECT-TYPE
    SYNTAX          Integer32
    MAX-ACCESS      read-only
    STATUS          current
    DESCRIPTION     
            "Indicates the number of RTP octets received on this call."
    ::= { sonusActiveCallEntry 41 }

sonusActiveCallPacketsLost OBJECT-TYPE
    SYNTAX          Integer32
    MAX-ACCESS      read-only
    STATUS          current
    DESCRIPTION     
            "Indicates the number of RTP packets lost on this call."
    ::= { sonusActiveCallEntry 42 }

sonusActiveCallPacketsDiscarded OBJECT-TYPE
    SYNTAX          Integer32
    MAX-ACCESS      read-only
    STATUS          current
    DESCRIPTION     
            "Indicates the number of RTP packets discarded by the jitter buffer."
    ::= { sonusActiveCallEntry 43 }

sonusActiveCallInterarrivalJitter OBJECT-TYPE
    SYNTAX          Integer32
    MAX-ACCESS      read-only
    STATUS          current
    DESCRIPTION     
            "Indicates the interarrival packet jitter on this call."
    ::= { sonusActiveCallEntry 44 }

sonusActiveCallPacketLatency OBJECT-TYPE
    SYNTAX          Integer32
    MAX-ACCESS      read-only
    STATUS          current
    DESCRIPTION     
            "Indicates the latency experienced on this call."
    ::= { sonusActiveCallEntry 45 }

sonusCallResTable OBJECT-TYPE
    SYNTAX          SEQUENCE OF SonusCallResEntry
    MAX-ACCESS      not-accessible
    STATUS          current
    DESCRIPTION     
            "This table presents the call resource data for the node. Each active
             call contains a set of allocated resources. This table provides a brief
             description and the information required to access detailed information
             about each allocated resource."
    ::= { sonusNodeResourcesMIBObjects 4 }

sonusCallResEntry OBJECT-TYPE
    SYNTAX          SonusCallResEntry
    MAX-ACCESS      not-accessible
    STATUS          current
    DESCRIPTION     
            ""
    INDEX           { sonusCallResShelfIndex, sonusCallResSlotIndex, 
                      sonusCallResCallIndex, sonusCallResIndex }
    ::= { sonusCallResTable 1 }

SonusCallResEntry ::=
    SEQUENCE {
        sonusCallResShelfIndex          Integer32,
        sonusCallResSlotIndex           Integer32,
        sonusCallResCallIndex           Integer32,
        sonusCallResIndex               Integer32,
        sonusCallResId                  Integer32,
        sonusCallResCallId              Integer32,
        sonusCallResType                INTEGER,
        sonusCallResMgrHandle           Integer32,
        sonusCallResMgrShelfIndex       Integer32,
        sonusCallResMgrSlotIndex        Integer32
    }

sonusCallResShelfIndex OBJECT-TYPE
    SYNTAX          Integer32 (1..6)
    MAX-ACCESS      read-only
    STATUS          current
    DESCRIPTION     
            "Identifies the target shelf containing the call to be accessed."
    ::= { sonusCallResEntry 1 }

sonusCallResSlotIndex OBJECT-TYPE
    SYNTAX          Integer32 (1..16)
    MAX-ACCESS      read-only
    STATUS          current
    DESCRIPTION     
            "Identifies the target slot containing the call to be accessed."
    ::= { sonusCallResEntry 2 }

sonusCallResCallIndex OBJECT-TYPE
    SYNTAX          Integer32
    MAX-ACCESS      read-only
    STATUS          current
    DESCRIPTION     
            "Identifies the target call to be accessed."
    ::= { sonusCallResEntry 3 }

sonusCallResIndex OBJECT-TYPE
    SYNTAX          Integer32
    MAX-ACCESS      read-only
    STATUS          current
    DESCRIPTION     
            "Identifies the target resource index to access within the call."
    ::= { sonusCallResEntry 4 }

sonusCallResId OBJECT-TYPE
    SYNTAX          Integer32
    MAX-ACCESS      read-only
    STATUS          current
    DESCRIPTION     
            "Represents the internal resource identifier that uniquely represents
             the resource to the resource manager entity responsible for the
             resource."
    ::= { sonusCallResEntry 5 }

sonusCallResCallId OBJECT-TYPE
    SYNTAX          Integer32
    MAX-ACCESS      read-only
    STATUS          current
    DESCRIPTION     
            "Represents the global call identifier (GCID) for the call to which this
             resource is allocated. This information is provided to ensure that the 
             resource is truly allocated to the call."
    ::= { sonusCallResEntry 6 }

sonusCallResType OBJECT-TYPE
    SYNTAX          INTEGER { bresIcm(0), bresSw2Nif(1), 
                        bresSw2DspCtrl(2), bresSw2DspLocal(3), 
                        bresSw2DspSonic(4), bresDsp2Dsp(5), 
                        bresDsp2Sonic(6), bresLe2Sonic(7), bresAtm2Sw(8), 
                        bresSw2Atm(9), dresPstn(10), dresService(11), 
                        pres(12), xresCntrl(13), xresUser(14), 
                        aresAmq2Dsp(15), atmres(16), bresSw2DspApps(17) }
    MAX-ACCESS      read-only
    STATUS          current
    DESCRIPTION     
            "Specifies the resource type for this resource."
    ::= { sonusCallResEntry 7 }

sonusCallResMgrHandle OBJECT-TYPE
    SYNTAX          Integer32
    MAX-ACCESS      read-only
    STATUS          current
    DESCRIPTION     
            "Specifies the internal handle for the resource manager entity responsible
             for this resource. This element is provided for information only."
    ::= { sonusCallResEntry 8 }

sonusCallResMgrShelfIndex OBJECT-TYPE
    SYNTAX          Integer32
    MAX-ACCESS      read-only
    STATUS          current
    DESCRIPTION     
            "Specifies the shelf on which this resource resides."
    ::= { sonusCallResEntry 9 }

sonusCallResMgrSlotIndex OBJECT-TYPE
    SYNTAX          Integer32
    MAX-ACCESS      read-only
    STATUS          current
    DESCRIPTION     
            "Specifies the card slot on which this resource resides."
    ::= { sonusCallResEntry 10 }

sonusCallPegCountsTable OBJECT-TYPE
    SYNTAX          SEQUENCE OF SonusCallPegCountsEntry
    MAX-ACCESS      not-accessible
    STATUS          current
    DESCRIPTION     
            "This table presents call peg count statistics for the node."
    ::= { sonusNodeResourcesMIBObjects 5 }

sonusCallPegCountsEntry OBJECT-TYPE
    SYNTAX          SonusCallPegCountsEntry
    MAX-ACCESS      not-accessible
    STATUS          current
    DESCRIPTION     
            ""
    INDEX           { sonusCallPegCountsShelfIndex, 
                      sonusCallPegCountsSlotIndex }
    ::= { sonusCallPegCountsTable 1 }

SonusCallPegCountsEntry ::=
    SEQUENCE {
        sonusCallPegCountsShelfIndex    Integer32,
        sonusCallPegCountsSlotIndex     Integer32,
        sonusCallPegCountsReset         INTEGER,
        sonusCallPegCountsAttempts      Integer32,
        sonusCallPegCountsCompletions   Integer32,
        sonusCallPegCountsActiveCalls   Integer32,
        sonusCallPegCountsStableCalls   Integer32,
        sonusCallPegCountsUpdates       Integer32,
        sonusCallPegCountsActiveCallsNonUser    Integer32,
        sonusCallPegCountsStableCallsNonUser    Integer32
    }

sonusCallPegCountsShelfIndex OBJECT-TYPE
    SYNTAX          Integer32 (1..6)
    MAX-ACCESS      read-only
    STATUS          current
    DESCRIPTION     
            "Identifies the target shelf to obtain the call counters."
    ::= { sonusCallPegCountsEntry 1 }

sonusCallPegCountsSlotIndex OBJECT-TYPE
    SYNTAX          Integer32 (1..16)
    MAX-ACCESS      read-only
    STATUS          current
    DESCRIPTION     
            "Identifies the target slot."
    ::= { sonusCallPegCountsEntry 2 }

sonusCallPegCountsReset OBJECT-TYPE
    SYNTAX          INTEGER { unknown(1), reset(2) }
    MAX-ACCESS      read-create
    STATUS          current
    DESCRIPTION     
            "Provides a means to reset the active call attempt and
             completion counters. Any set operation on this object will
             result in the attempt and completion counters being cleared."
    ::= { sonusCallPegCountsEntry 3 }

sonusCallPegCountsAttempts OBJECT-TYPE
    SYNTAX          Integer32
    MAX-ACCESS      read-only
    STATUS          current
    DESCRIPTION     
            "Indicates the number of call attempts on this shelf."
    ::= { sonusCallPegCountsEntry 4 }

sonusCallPegCountsCompletions OBJECT-TYPE
    SYNTAX          Integer32
    MAX-ACCESS      read-only
    STATUS          current
    DESCRIPTION     
            "Indicates the total number of completed call attempts on this shelf."
    ::= { sonusCallPegCountsEntry 5 }

sonusCallPegCountsActiveCalls OBJECT-TYPE
    SYNTAX          Integer32
    MAX-ACCESS      read-only
    STATUS          current
    DESCRIPTION     
            "Indicates the current number of active calls in the shelf."
    ::= { sonusCallPegCountsEntry 6 }

sonusCallPegCountsStableCalls OBJECT-TYPE
    SYNTAX          Integer32
    MAX-ACCESS      read-only
    STATUS          current
    DESCRIPTION     
            "Indicates the current number of stable calls in the shelf."
    ::= { sonusCallPegCountsEntry 7 }

sonusCallPegCountsUpdates OBJECT-TYPE
    SYNTAX          Integer32
    MAX-ACCESS      read-only
    STATUS          current
    DESCRIPTION     
            "Indicates the number of call updates (modifications) on this shelf."
    ::= { sonusCallPegCountsEntry 8 }

sonusCallPegCountsActiveCallsNonUser OBJECT-TYPE
    SYNTAX          Integer32
    MAX-ACCESS      read-only
    STATUS          current
    DESCRIPTION     
            "Indicates the current number of active non-call associated signalling channels in the shelf. (ie ISDN D channel)"
    ::= { sonusCallPegCountsEntry 9 }

sonusCallPegCountsStableCallsNonUser OBJECT-TYPE
    SYNTAX          Integer32
    MAX-ACCESS      read-only
    STATUS          current
    DESCRIPTION     
            "Indicates the current number of stable non-call associated signalling channels in the shelf. (ie ISDN D channel)"
    ::= { sonusCallPegCountsEntry 10 }

sonusToneObjects OBJECT IDENTIFIER
    ::= { sonusNodeResourcesMIBObjects 6 }

sonusToneProfile OBJECT IDENTIFIER
    ::= { sonusToneObjects 1 }

sonusToneProfileNextIndex OBJECT-TYPE
    SYNTAX          Integer32
    MAX-ACCESS      read-only
    STATUS          current
    DESCRIPTION     
            "The next valid index to use when creating an entry in
             the sonusToneProfileTable."
    ::= { sonusToneProfile 1 }

sonusToneProfileTable OBJECT-TYPE
    SYNTAX          SEQUENCE OF SonusToneProfileEntry
    MAX-ACCESS      not-accessible
    STATUS          current
    DESCRIPTION     
            "This table contains tone profiles for the node."
    ::= { sonusToneProfile 2 }

sonusToneProfileEntry OBJECT-TYPE
    SYNTAX          SonusToneProfileEntry
    MAX-ACCESS      not-accessible
    STATUS          current
    DESCRIPTION     
            ""
    INDEX           { sonusToneProfileIndex }
    ::= { sonusToneProfileTable 1 }

SonusToneProfileEntry ::=
    SEQUENCE {
        sonusToneProfileIndex           Integer32,
        sonusToneProfileName            SonusName,
        sonusToneProfileGenerationMethod INTEGER,
        sonusToneProfileTone1Freq       Integer32,
        sonusToneProfileTone1Power      Integer32,
        sonusToneProfileTone2Freq       Integer32,
        sonusToneProfileTone2Power      Integer32,
        sonusToneProfileCarrierFreq     Integer32,
        sonusToneProfileSignalFreq      Integer32,
        sonusToneProfileModPower        Integer32,
        sonusToneProfileModIndex        Integer32,
        sonusToneProfileMake1           Integer32,
        sonusToneProfileBreak1          Integer32,
        sonusToneProfileMake2           Integer32,
        sonusToneProfileBreak2          Integer32,
        sonusToneProfileMake3           Integer32,
        sonusToneProfileBreak3          Integer32,
        sonusToneProfileRepeat          Integer32,
        sonusToneProfileRowStatus       RowStatus
    }

sonusToneProfileIndex OBJECT-TYPE
    SYNTAX          Integer32
    MAX-ACCESS      read-only
    STATUS          current
    DESCRIPTION     
            "Identifies the tone profile entry."
    ::= { sonusToneProfileEntry 1 }

sonusToneProfileName OBJECT-TYPE
    SYNTAX          SonusName
    MAX-ACCESS      read-write
    STATUS          current
    DESCRIPTION     
            "The user name of this tone profile."
    ::= { sonusToneProfileEntry 2 }

sonusToneProfileGenerationMethod OBJECT-TYPE
    SYNTAX          INTEGER { singleTone(1), dualTone(2), 
                        modulatedTone(3) }
    MAX-ACCESS      read-write
    STATUS          current
    DESCRIPTION     
            "Determines the generation method for the tone.  This value
             is specified at object creation time and cannot be modified."
    ::= { sonusToneProfileEntry 3 }

sonusToneProfileTone1Freq OBJECT-TYPE
    SYNTAX          Integer32 (0..3999)
    MAX-ACCESS      read-write
    STATUS          current
    DESCRIPTION     
            "Specifies Tone 1 Frequency in Hertz.
             If 0, then silence is generated.
             Only valid if generation method is singleTone or dualTone."
    DEFVAL          { 0 }
    ::= { sonusToneProfileEntry 4 }

sonusToneProfileTone1Power OBJECT-TYPE
    SYNTAX          Integer32 (-50..3)
    MAX-ACCESS      read-write
    STATUS          current
    DESCRIPTION     
            "Specifies Tone 1 Power in dBm.  Power levels range from
             -50 dBm (minimum power) to +3 dBm (maximum power).
             Only valid if generation method is singleTone or dualTone."
    DEFVAL          { 0 }
    ::= { sonusToneProfileEntry 5 }

sonusToneProfileTone2Freq OBJECT-TYPE
    SYNTAX          Integer32 (0..3999)
    MAX-ACCESS      read-write
    STATUS          current
    DESCRIPTION     
            "Specifies Tone 2 Frequency in Hertz.
             If 0, then a single frequency tone is generated.
             Only valid if generation method is dualTone."
    DEFVAL          { 0 }
    ::= { sonusToneProfileEntry 6 }

sonusToneProfileTone2Power OBJECT-TYPE
    SYNTAX          Integer32 (-50..3)
    MAX-ACCESS      read-write
    STATUS          current
    DESCRIPTION     
            "Specifies Tone 2 Power in dBm.  Power levels range from
             -50 dBm (minimum power) to +3 dBm (maximum power).
             Only valid if generation method is dualTone."
    DEFVAL          { 0 }
    ::= { sonusToneProfileEntry 7 }

sonusToneProfileCarrierFreq OBJECT-TYPE
    SYNTAX          Integer32 (0..3999)
    MAX-ACCESS      read-write
    STATUS          current
    DESCRIPTION     
            "Specifies the frequency in Hertz of the carrier for the
             modulated signal.  Value must be less than 4000.
             If set to 0, then silence is generated.
             Only valid if generation method is modulatedTone."
    DEFVAL          { 0 }
    ::= { sonusToneProfileEntry 8 }

sonusToneProfileSignalFreq OBJECT-TYPE
    SYNTAX          Integer32 (0..3999)
    MAX-ACCESS      read-write
    STATUS          current
    DESCRIPTION     
            "Specifies the frequency in Hertz of the sinusoid modulating
             the carrier sinusoid.  Value must be less than 4000.
             Only valid if generation method is modulatedTone."
    DEFVAL          { 0 }
    ::= { sonusToneProfileEntry 9 }

sonusToneProfileModPower OBJECT-TYPE
    SYNTAX          Integer32 (-50..3)
    MAX-ACCESS      read-write
    STATUS          current
    DESCRIPTION     
            "Specifies Carrier Power in dBm.  Power levels range from
             -50 dBm (minimum power) to +3 dBm (maximum power).
             Only valid if generation method is modulatedTone."
    DEFVAL          { 0 }
    ::= { sonusToneProfileEntry 10 }

sonusToneProfileModIndex OBJECT-TYPE
    SYNTAX          Integer32 (0..300)
    MAX-ACCESS      read-write
    STATUS          current
    DESCRIPTION     
            "Specifies the modulation index of the signal.
             Value must be in the range of 0 to 300 in 1% units.
             Only valid if generation method is modulatedTone."
    DEFVAL          { 0 }
    ::= { sonusToneProfileEntry 11 }

sonusToneProfileMake1 OBJECT-TYPE
    SYNTAX          Integer32 (-1..8000)
    MAX-ACCESS      read-write
    STATUS          current
    DESCRIPTION     
            "Duration of the first on cadence in milliseconds.
             If 0, then the duration of the first on cadence is 0 msec.
             If -1, then the tone is played continuously."
    DEFVAL          { 0 }
    ::= { sonusToneProfileEntry 12 }

sonusToneProfileBreak1 OBJECT-TYPE
    SYNTAX          Integer32 (-1..8000)
    MAX-ACCESS      read-write
    STATUS          current
    DESCRIPTION     
            "Duration of the first off cadence in milliseconds.
             If 0, then silence is not generated between the on cadences.
             If -1, then silence is generated continuously."
    DEFVAL          { 0 }
    ::= { sonusToneProfileEntry 13 }

sonusToneProfileMake2 OBJECT-TYPE
    SYNTAX          Integer32 (-1..8000)
    MAX-ACCESS      read-write
    STATUS          current
    DESCRIPTION     
            "Duration of the second on cadence in milliseconds.
             If 0, then the duration of the second on cadence is 0 msec.
             If -1, then the tone is played continuously."
    DEFVAL          { 0 }
    ::= { sonusToneProfileEntry 14 }

sonusToneProfileBreak2 OBJECT-TYPE
    SYNTAX          Integer32 (-1..8000)
    MAX-ACCESS      read-write
    STATUS          current
    DESCRIPTION     
            "Duration of the second off cadence in milliseconds.
             If 0, then silence is not generated between the on cadences.
             If -1, then silence is generated continuously."
    DEFVAL          { 0 }
    ::= { sonusToneProfileEntry 15 }

sonusToneProfileMake3 OBJECT-TYPE
    SYNTAX          Integer32 (-1..8000)
    MAX-ACCESS      read-write
    STATUS          current
    DESCRIPTION     
            "Duration of the thrid on cadence in milliseconds.
             If 0, then the duration of the third on cadence is 0 msec.
             If -1, then the tone is played continuously."
    DEFVAL          { 0 }
    ::= { sonusToneProfileEntry 16 }

sonusToneProfileBreak3 OBJECT-TYPE
    SYNTAX          Integer32 (-1..8000)
    MAX-ACCESS      read-write
    STATUS          current
    DESCRIPTION     
            "Duration of the third off cadence in milliseconds.
             If 0, then silence is not generated after the third on cadence.
             If -1, then silence is generated continuously."
    DEFVAL          { 0 }
    ::= { sonusToneProfileEntry 17 }

sonusToneProfileRepeat OBJECT-TYPE
    SYNTAX          Integer32
    MAX-ACCESS      read-write
    STATUS          current
    DESCRIPTION     
            "Number of cadence cycles to generate.
             If 0, then the tone pattern is repeated indefinitely."
    DEFVAL          { 1 }
    ::= { sonusToneProfileEntry 18 }

sonusToneProfileRowStatus OBJECT-TYPE
    SYNTAX          RowStatus
    MAX-ACCESS      read-write
    STATUS          current
    DESCRIPTION     
            ""
    ::= { sonusToneProfileEntry 19 }

sonusToneType OBJECT IDENTIFIER
    ::= { sonusToneObjects 2 }

sonusToneTypeNextIndex OBJECT-TYPE
    SYNTAX          Integer32
    MAX-ACCESS      read-only
    STATUS          current
    DESCRIPTION     
            "The next valid index to use when creating an entry in
             the sonusToneTypeTable."
    ::= { sonusToneType 1 }

sonusToneTypeTable OBJECT-TYPE
    SYNTAX          SEQUENCE OF SonusToneTypeEntry
    MAX-ACCESS      not-accessible
    STATUS          current
    DESCRIPTION     
            "This table contains tone types for the node."
    ::= { sonusToneType 2 }

sonusToneTypeEntry OBJECT-TYPE
    SYNTAX          SonusToneTypeEntry
    MAX-ACCESS      not-accessible
    STATUS          current
    DESCRIPTION     
            ""
    INDEX           { sonusToneTypeIndex }
    ::= { sonusToneTypeTable 1 }

SonusToneTypeEntry ::=
    SEQUENCE {
        sonusToneTypeIndex              Integer32,
        sonusToneTypeName               SonusName,
        sonusToneTypeRowStatus          RowStatus
    }

sonusToneTypeIndex OBJECT-TYPE
    SYNTAX          Integer32
    MAX-ACCESS      read-only
    STATUS          current
    DESCRIPTION     
            "Identifies the tone type entry."
    ::= { sonusToneTypeEntry 1 }

sonusToneTypeName OBJECT-TYPE
    SYNTAX          SonusName
    MAX-ACCESS      read-write
    STATUS          current
    DESCRIPTION     
            "The user name of this tone type.  Possible types include
             'dial', 'busy', 'reorder', etc."
    ::= { sonusToneTypeEntry 2 }

sonusToneTypeRowStatus OBJECT-TYPE
    SYNTAX          RowStatus
    MAX-ACCESS      read-write
    STATUS          current
    DESCRIPTION     
            ""
    ::= { sonusToneTypeEntry 3 }

sonusTonePackage OBJECT IDENTIFIER
    ::= { sonusToneObjects 3 }

sonusTonePackageNextIndex OBJECT-TYPE
    SYNTAX          Integer32
    MAX-ACCESS      read-only
    STATUS          current
    DESCRIPTION     
            "The next valid index to use when creating an entry in
             the sonusTonePackageTable."
    ::= { sonusTonePackage 1 }

sonusTonePackageTable OBJECT-TYPE
    SYNTAX          SEQUENCE OF SonusTonePackageEntry
    MAX-ACCESS      not-accessible
    STATUS          current
    DESCRIPTION     
            "This table contains tone packages for the node."
    ::= { sonusTonePackage 2 }

sonusTonePackageEntry OBJECT-TYPE
    SYNTAX          SonusTonePackageEntry
    MAX-ACCESS      not-accessible
    STATUS          current
    DESCRIPTION     
            ""
    INDEX           { sonusTonePackageIndex }
    ::= { sonusTonePackageTable 1 }

SonusTonePackageEntry ::=
    SEQUENCE {
        sonusTonePackageIndex           Integer32,
        sonusTonePackageName            SonusName,
        sonusTonePackageRowStatus       RowStatus
    }

sonusTonePackageIndex OBJECT-TYPE
    SYNTAX          Integer32
    MAX-ACCESS      read-only
    STATUS          current
    DESCRIPTION     
            "Identifies the tone package."
    ::= { sonusTonePackageEntry 1 }

sonusTonePackageName OBJECT-TYPE
    SYNTAX          SonusName
    MAX-ACCESS      read-write
    STATUS          current
    DESCRIPTION     
            "The name of this tone package.  This name should reflect
             the country or carrier which will be using this package."
    ::= { sonusTonePackageEntry 2 }

sonusTonePackageRowStatus OBJECT-TYPE
    SYNTAX          RowStatus
    MAX-ACCESS      read-write
    STATUS          current
    DESCRIPTION     
            ""
    ::= { sonusTonePackageEntry 3 }

sonusTonePkgElem OBJECT IDENTIFIER
    ::= { sonusToneObjects 4 }

sonusTonePkgElemTable OBJECT-TYPE
    SYNTAX          SEQUENCE OF SonusTonePkgElemEntry
    MAX-ACCESS      not-accessible
    STATUS          current
    DESCRIPTION     
            "This table contains elements which bind tone types to
             tone profiles for a given tone package."
    ::= { sonusTonePkgElem 1 }

sonusTonePkgElemEntry OBJECT-TYPE
    SYNTAX          SonusTonePkgElemEntry
    MAX-ACCESS      not-accessible
    STATUS          current
    DESCRIPTION     
            ""
    INDEX           { sonusTonePkgElemIndex }
    ::= { sonusTonePkgElemTable 1 }

SonusTonePkgElemEntry ::=
    SEQUENCE {
        sonusTonePkgElemIndex           Integer32,
        sonusTonePkgElemTonePackageRef  SonusNameReference,
        sonusTonePkgElemToneTypeRef     SonusNameReference,
        sonusTonePkgElemToneProfileRef  SonusNameReference,
        sonusTonePkgElemRowStatus       RowStatus
    }

sonusTonePkgElemIndex OBJECT-TYPE
    SYNTAX          Integer32
    MAX-ACCESS      read-only
    STATUS          current
    DESCRIPTION     
            "Identifies the target tone package element."
    ::= { sonusTonePkgElemEntry 1 }

sonusTonePkgElemTonePackageRef OBJECT-TYPE
    SYNTAX          SonusNameReference
    MAX-ACCESS      read-write
    STATUS          current
    DESCRIPTION     
            "Identifies the tone packge for this element."
    ::= { sonusTonePkgElemEntry 2 }

sonusTonePkgElemToneTypeRef OBJECT-TYPE
    SYNTAX          SonusNameReference
    MAX-ACCESS      read-write
    STATUS          current
    DESCRIPTION     
            "Identifies the tone type for this element."
    ::= { sonusTonePkgElemEntry 3 }

sonusTonePkgElemToneProfileRef OBJECT-TYPE
    SYNTAX          SonusNameReference
    MAX-ACCESS      read-write
    STATUS          current
    DESCRIPTION     
            "The name of the tone profile that this tone type maps
             to for this tone package."
    DEFVAL          { "default" }
    ::= { sonusTonePkgElemEntry 4 }

sonusTonePkgElemRowStatus OBJECT-TYPE
    SYNTAX          RowStatus
    MAX-ACCESS      read-write
    STATUS          current
    DESCRIPTION     
            ""
    ::= { sonusTonePkgElemEntry 5 }

sonusDigitProfile OBJECT IDENTIFIER
    ::= { sonusNodeResourcesMIBObjects 7 }

sonusDigitProfileNextIndex OBJECT-TYPE
    SYNTAX          Integer32
    MAX-ACCESS      read-only
    STATUS          current
    DESCRIPTION     
            "The next valid index to use when creating an entry in
             the sonusDigitProfileTable."
    ::= { sonusDigitProfile 1 }

sonusDigitProfileTable OBJECT-TYPE
    SYNTAX          SEQUENCE OF SonusDigitProfileEntry
    MAX-ACCESS      not-accessible
    STATUS          current
    DESCRIPTION     
            "This table contains digit profiles for the node.  Digit Profiles
             contain both digit generation (sonusDigitProfileGen...) and
             digit detection (sonusDigitProfileDet...) parameters."
    ::= { sonusDigitProfile 2 }

sonusDigitProfileEntry OBJECT-TYPE
    SYNTAX          SonusDigitProfileEntry
    MAX-ACCESS      not-accessible
    STATUS          current
    DESCRIPTION     
            ""
    INDEX           { sonusDigitProfileIndex }
    ::= { sonusDigitProfileTable 1 }

SonusDigitProfileEntry ::=
    SEQUENCE {
        sonusDigitProfileIndex          Integer32,
        sonusDigitProfileName           SonusName,
        sonusDigitProfileType           INTEGER,
        sonusDigitProfileGenPower       Integer32,
        sonusDigitProfileGenMake        Integer32,
        sonusDigitProfileGenBreak       Integer32,
        sonusDigitProfileDetMinPower    Integer32,
        sonusDigitProfileDetMinOnDuration Integer32,
        sonusDigitProfileDetMinOffDuration  Integer32,
        sonusDigitProfileDetFreqAcceptRange   INTEGER,
        sonusDigitProfileDtmfDetTwistCutoff   Integer32,
        sonusDigitProfileMfr1GenMakeKp  Integer32,
        sonusDigitProfileRowStatus      RowStatus
    }

sonusDigitProfileIndex OBJECT-TYPE
    SYNTAX          Integer32
    MAX-ACCESS      read-only
    STATUS          current
    DESCRIPTION     
            "Identifies the digit profile entry."
    ::= { sonusDigitProfileEntry 1 }

sonusDigitProfileName OBJECT-TYPE
    SYNTAX          SonusName
    MAX-ACCESS      read-write
    STATUS          current
    DESCRIPTION     
            "The user name of this digit profile."
    ::= { sonusDigitProfileEntry 2 }

sonusDigitProfileType OBJECT-TYPE
    SYNTAX          INTEGER { dtmf(1), mfr1(2), mfr2f(3), mfr2b(4) }
    MAX-ACCESS      read-write
    STATUS          current
    DESCRIPTION     
            "Specifies the digit's format.  This value is set at object
             creation time and cannot be modified."
    ::= { sonusDigitProfileEntry 3 }

sonusDigitProfileGenPower OBJECT-TYPE
    SYNTAX          Integer32 (-50..3)
    MAX-ACCESS      read-write
    STATUS          current
    DESCRIPTION     
            "Specifies digit generation power level in dBm.  Power level
             ranges from -50 dBm (minimum power) to +3 dBm (maximum power)."
    DEFVAL          { -10 }
    ::= { sonusDigitProfileEntry 4 }

sonusDigitProfileGenMake OBJECT-TYPE
    SYNTAX          Integer32 (0..8000)
    MAX-ACCESS      read-write
    STATUS          current
    DESCRIPTION     
            "Specifies duration of generated digits in milliseconds."
    DEFVAL          { 100 }
    ::= { sonusDigitProfileEntry 5 }

sonusDigitProfileGenBreak OBJECT-TYPE
    SYNTAX          Integer32 (0..8000)
    MAX-ACCESS      read-write
    STATUS          current
    DESCRIPTION     
            "Specifies silence between generated digits in milliseconds."
    DEFVAL          { 100 }
    ::= { sonusDigitProfileEntry 6 }

sonusDigitProfileDetMinPower OBJECT-TYPE
    SYNTAX          Integer32 (-45..-25)
    MAX-ACCESS      read-write
    STATUS          current
    DESCRIPTION     
            "Specifies minimum power level in dBm required for digit
             detection.  Valid levels range from -45dBm to -25dBm."
    DEFVAL          { -45 }
    ::= { sonusDigitProfileEntry 7 }

sonusDigitProfileDetMinOnDuration OBJECT-TYPE
    SYNTAX          Integer32 (25..100)
    MAX-ACCESS      read-write
    STATUS          current
    DESCRIPTION     
            "Specifies minimum tone duration in milliseconds required
             for digit detection.  The value must in increments of 5ms.
             For DTMF digits, the value must be between 25ms and 80ms.
             For MF digits, the value must be between 25ms and 100ms."
    DEFVAL          { 40 }
    ::= { sonusDigitProfileEntry 8 }

sonusDigitProfileDetMinOffDuration OBJECT-TYPE
    SYNTAX          Integer32 (10..100)
    MAX-ACCESS      read-write
    STATUS          current
    DESCRIPTION     
            "Specifies minimum interdigit duration in milliseconds for
             digit detection.  The value must be in increments of 5ms.
             For DTMF digits, the value must be between 25ms and 80ms.
             For MF digits, the value must be between 10ms and 100ms.
             "
    DEFVAL          { 40 }
    ::= { sonusDigitProfileEntry 9 }

sonusDigitProfileDetFreqAcceptRange OBJECT-TYPE
    SYNTAX          INTEGER { narrow(1), medium(2), wide(3), wider(4) }
    MAX-ACCESS      read-write
    STATUS          current
    DESCRIPTION     
            "Specifies frequency tolerances for digit detection.  For DTMF
             digits the value represents accept and reject ranges.  For MF
             digits the value represents only the accept range.	 Frequencies
             detected within the accept range will result in digit detection.
             Frequencies detected outside the reject range will not result
             in digit detection.
             .                   DTMF     DTMF       MFR1
             VALUE  ENUMERATION  ACCEPT   REJECT     ACCEPT
             -----  -----------  ----------------    ------------------
             1      narrow       +/-2.0%  +/-3.0%    +/-(1.5% + 5Hz)
             2      medium       +/-2.5%  +/-3.5%    +/-(1.5% + 10Hz)
             3      wide         +/-3.0%  +/-4.0%    +/-(1.5% + 15Hz)
             4      wider        +/-3.5%  +/-4.5%    N/A"
    DEFVAL          { 2 }
    ::= { sonusDigitProfileEntry 10 }

sonusDigitProfileDtmfDetTwistCutoff OBJECT-TYPE
    SYNTAX          Integer32 (4..12)
    MAX-ACCESS      read-write
    STATUS          current
    DESCRIPTION     
            "For DTMF digit detection only.  Twist is the ratio of high
             group power to low.  Twist ratios below the twist cutoff will
             result in digit detection.  Twist ratios above the twist
             cutoff will result in digit rejection.
             Value must be between 4dB and 12dB in increments of 2dB."
    DEFVAL          { 8 }
    ::= { sonusDigitProfileEntry 11 }

sonusDigitProfileMfr1GenMakeKp OBJECT-TYPE
    SYNTAX          Integer32 (0..8000)
    MAX-ACCESS      read-write
    STATUS          current
    DESCRIPTION     
            "Specifies duration of generated KP digit in milliseconds.
             Only applicable if digit type is MFR1."
    DEFVAL          { 105 }
    ::= { sonusDigitProfileEntry 12 }

sonusDigitProfileRowStatus OBJECT-TYPE
    SYNTAX          RowStatus
    MAX-ACCESS      read-write
    STATUS          current
    DESCRIPTION     
            ""
    ::= { sonusDigitProfileEntry 13 }

sonusStaticCall OBJECT IDENTIFIER
    ::= { sonusNodeResourcesMIBObjects 8 }

sonusStaticCallNextIndex OBJECT-TYPE
    SYNTAX          Integer32
    MAX-ACCESS      read-only
    STATUS          current
    DESCRIPTION     
            "The next valid index to use when creating an entry in
             the sonusStaticCallAdmnTable"
    ::= { sonusStaticCall 1 }

sonusStaticCallAdmnTable OBJECT-TYPE
    SYNTAX          SEQUENCE OF SonusStaticCallAdmnEntry
    MAX-ACCESS      not-accessible
    STATUS          current
    DESCRIPTION     
            "This table specifies the static call list for the node."
    ::= { sonusStaticCall 2 }

sonusStaticCallAdmnEntry OBJECT-TYPE
    SYNTAX          SonusStaticCallAdmnEntry
    MAX-ACCESS      not-accessible
    STATUS          current
    DESCRIPTION     
            ""
    INDEX           { sonusStaticCallAdmnIndex }
    ::= { sonusStaticCallAdmnTable 1 }

SonusStaticCallAdmnEntry ::=
    SEQUENCE {
        sonusStaticCallAdmnIndex        Integer32,
        sonusStaticCallAdmnState        INTEGER,
        sonusStaticCallAdmnName         SonusName,
        sonusStaticCallAdmnEndPointAShelf Integer32,
        sonusStaticCallAdmnEndPointASlot Integer32,
        sonusStaticCallAdmnEndPointAPort Integer32,
        sonusStaticCallAdmnEndPointAChannel   Integer32,
        sonusStaticCallAdmnEndPointAServProfile       SonusName,
        sonusStaticCallAdmnEndPointBType INTEGER,
        sonusStaticCallAdmnEndPointBShelf Integer32,
        sonusStaticCallAdmnEndPointBSlot Integer32,
        sonusStaticCallAdmnEndPointBPort Integer32,
        sonusStaticCallAdmnEndPointBChannel   Integer32,
        sonusStaticCallAdmnEndPointBLocalRTPPort        Integer32,
        sonusStaticCallAdmnEndPointBLocalIpAddress          IpAddress,
        sonusStaticCallAdmnEndPointBRemoteRTPPort         Integer32,
        sonusStaticCallAdmnEndPointBRemoteIpAddress           IpAddress,
        sonusStaticCallAdmnEndPointBServProfile       SonusName,
        sonusStaticCallAdmnCircuitMode  INTEGER,
        sonusStaticCallAdmnRowStatus    RowStatus
    }

sonusStaticCallAdmnIndex OBJECT-TYPE
    SYNTAX          Integer32
    MAX-ACCESS      read-only
    STATUS          current
    DESCRIPTION     
            "Identifies the target static call entry."
    ::= { sonusStaticCallAdmnEntry 1 }

sonusStaticCallAdmnState OBJECT-TYPE
    SYNTAX          INTEGER { disabled(1), enabled(2) }
    MAX-ACCESS      read-write
    STATUS          current
    DESCRIPTION     
            "The administrative state of this static call entry."
    DEFVAL          { disabled }
    ::= { sonusStaticCallAdmnEntry 2 }

sonusStaticCallAdmnName OBJECT-TYPE
    SYNTAX          SonusName
    MAX-ACCESS      read-write
    STATUS          current
    DESCRIPTION     
            "The user name of this static call."
    ::= { sonusStaticCallAdmnEntry 3 }

sonusStaticCallAdmnEndPointAShelf OBJECT-TYPE
    SYNTAX          Integer32 (1..6)
    MAX-ACCESS      read-write
    STATUS          current
    DESCRIPTION     
            "A 32-bit integer identifying the shelf of the end point A"
    ::= { sonusStaticCallAdmnEntry 4 }

sonusStaticCallAdmnEndPointASlot OBJECT-TYPE
    SYNTAX          Integer32 (1..16)
    MAX-ACCESS      read-write
    STATUS          current
    DESCRIPTION     
            "A 32-bit integer identifying the slot of the end point A"
    ::= { sonusStaticCallAdmnEntry 5 }

sonusStaticCallAdmnEndPointAPort OBJECT-TYPE
    SYNTAX          Integer32 (1..65535)
    MAX-ACCESS      read-write
    STATUS          current
    DESCRIPTION     
            "Port index of end point A."
    ::= { sonusStaticCallAdmnEntry 6 }

sonusStaticCallAdmnEndPointAChannel OBJECT-TYPE
    SYNTAX          Integer32 (1..32)
    MAX-ACCESS      read-write
    STATUS          current
    DESCRIPTION     
            "Indicates the DS0 channel of the end point A"
    ::= { sonusStaticCallAdmnEntry 7 }

sonusStaticCallAdmnEndPointAServProfile OBJECT-TYPE
    SYNTAX          SonusName
    MAX-ACCESS      read-write
    STATUS          current
    DESCRIPTION     
            "The service profile used for end point A"
    ::= { sonusStaticCallAdmnEntry 8 }

sonusStaticCallAdmnEndPointBType OBJECT-TYPE
    SYNTAX          INTEGER { circuit(1), packet(2) }
    MAX-ACCESS      read-write
    STATUS          current
    DESCRIPTION     
            "The type of end point B (circuit or packet)."
    DEFVAL          { circuit }
    ::= { sonusStaticCallAdmnEntry 9 }

sonusStaticCallAdmnEndPointBShelf OBJECT-TYPE
    SYNTAX          Integer32 (1..6)
    MAX-ACCESS      read-write
    STATUS          current
    DESCRIPTION     
            "A 32-bit integer identifying the shelf of the end point B"
    ::= { sonusStaticCallAdmnEntry 10 }

sonusStaticCallAdmnEndPointBSlot OBJECT-TYPE
    SYNTAX          Integer32 (1..16)
    MAX-ACCESS      read-write
    STATUS          current
    DESCRIPTION     
            "A 32-bit integer identifying the slot of the end point B"
    ::= { sonusStaticCallAdmnEntry 11 }

sonusStaticCallAdmnEndPointBPort OBJECT-TYPE
    SYNTAX          Integer32 (1..65535)
    MAX-ACCESS      read-write
    STATUS          current
    DESCRIPTION     
            "Port index of end point B."
    ::= { sonusStaticCallAdmnEntry 12 }

sonusStaticCallAdmnEndPointBChannel OBJECT-TYPE
    SYNTAX          Integer32 (1..32)
    MAX-ACCESS      read-write
    STATUS          current
    DESCRIPTION     
            "Indicates the DS0 channel of the end point B"
    ::= { sonusStaticCallAdmnEntry 13 }

sonusStaticCallAdmnEndPointBLocalRTPPort OBJECT-TYPE
    SYNTAX          Integer32
    MAX-ACCESS      read-write
    STATUS          current
    DESCRIPTION     
            "Indicates the local RTP port."
    ::= { sonusStaticCallAdmnEntry 14 }

sonusStaticCallAdmnEndPointBLocalIpAddress OBJECT-TYPE
    SYNTAX          IpAddress
    MAX-ACCESS      read-write
    STATUS          current
    DESCRIPTION     
            "The IP Address of the end point B if it is packet"
    ::= { sonusStaticCallAdmnEntry 15 }

sonusStaticCallAdmnEndPointBRemoteRTPPort OBJECT-TYPE
    SYNTAX          Integer32
    MAX-ACCESS      read-write
    STATUS          current
    DESCRIPTION     
            "Indicates the remote RTP port."
    ::= { sonusStaticCallAdmnEntry 16 }

sonusStaticCallAdmnEndPointBRemoteIpAddress OBJECT-TYPE
    SYNTAX          IpAddress
    MAX-ACCESS      read-write
    STATUS          current
    DESCRIPTION     
            "The IP Address of the end point B if it is packet"
    ::= { sonusStaticCallAdmnEntry 17 }

sonusStaticCallAdmnEndPointBServProfile OBJECT-TYPE
    SYNTAX          SonusName
    MAX-ACCESS      read-write
    STATUS          current
    DESCRIPTION     
            "The service profile used for end point B"
    ::= { sonusStaticCallAdmnEntry 18 }

sonusStaticCallAdmnCircuitMode OBJECT-TYPE
    SYNTAX          INTEGER { voice(1), data(2) }
    MAX-ACCESS      read-write
    STATUS          current
    DESCRIPTION     
            "The circuit mode for this static call"
    DEFVAL          { voice }
    ::= { sonusStaticCallAdmnEntry 19 }

sonusStaticCallAdmnRowStatus OBJECT-TYPE
    SYNTAX          RowStatus
    MAX-ACCESS      read-write
    STATUS          current
    DESCRIPTION     
            ""
    ::= { sonusStaticCallAdmnEntry 20 }

sonusStaticCallStatTable OBJECT-TYPE
    SYNTAX          SEQUENCE OF SonusStaticCallStatEntry
    MAX-ACCESS      not-accessible
    STATUS          current
    DESCRIPTION     
            "The Manual Call Stat Table"
    ::= { sonusNodeResourcesMIBObjects 9 }

sonusStaticCallStatEntry OBJECT-TYPE
    SYNTAX          SonusStaticCallStatEntry
    MAX-ACCESS      not-accessible
    STATUS          current
    DESCRIPTION     
            "An entry in the Manual Call Stat Table"
    INDEX           { sonusStaticCallStatIndex }
    ::= { sonusStaticCallStatTable 1 }

SonusStaticCallStatEntry ::=
    SEQUENCE {
        sonusStaticCallStatIndex        Integer32,
        sonusStaticCallStatCallId       Integer32,
        sonusStaticCallStatState        DisplayString,
        sonusStaticCallStatTime         DisplayString
    }

sonusStaticCallStatIndex OBJECT-TYPE
    SYNTAX          Integer32
    MAX-ACCESS      read-only
    STATUS          current
    DESCRIPTION     
            "The index for target static call."
    ::= { sonusStaticCallStatEntry 1 }

sonusStaticCallStatCallId OBJECT-TYPE
    SYNTAX          Integer32
    MAX-ACCESS      read-only
    STATUS          current
    DESCRIPTION     
            "The call identifier(GCID) assigned to this static call"
    ::= { sonusStaticCallStatEntry 2 }

sonusStaticCallStatState OBJECT-TYPE
    SYNTAX          DisplayString (SIZE(0..23))
    MAX-ACCESS      read-only
    STATUS          current
    DESCRIPTION     
            "The status of the static call"
    ::= { sonusStaticCallStatEntry 3 }

sonusStaticCallStatTime OBJECT-TYPE
    SYNTAX          DisplayString (SIZE(0..23))
    MAX-ACCESS      read-only
    STATUS          current
    DESCRIPTION     
            "Displays the Date/time the connection was created"
    ::= { sonusStaticCallStatEntry 4 }

sonusStaticCallActionObjects OBJECT IDENTIFIER
    ::= { sonusNodeResourcesMIBObjects 10 }

sonusStaticCallGcid OBJECT-TYPE
    SYNTAX          Integer32
    MAX-ACCESS      read-write
    STATUS          current
    DESCRIPTION     
            "The call identifier for a call to be deleted"
    ::= { sonusStaticCallActionObjects 1 }

sonusStaticCallAction OBJECT-TYPE
    SYNTAX          INTEGER { none(1), delete(2) }
    MAX-ACCESS      read-write
    STATUS          current
    DESCRIPTION     
            "The action that should be taken on the call"
    DEFVAL          { none }
    ::= { sonusStaticCallActionObjects 2 }

sonusCallTrace OBJECT IDENTIFIER
    ::= { sonusNodeResourcesMIBObjects 11 }

sonusCallTraceNextIndex OBJECT-TYPE
    SYNTAX          Integer32
    MAX-ACCESS      read-only
    STATUS          current
    DESCRIPTION     
            "The next valid index to use when creating an entry in
             the sonusCallTraceTable."
    ::= { sonusCallTrace 1 }

sonusCallTraceTable OBJECT-TYPE
    SYNTAX          SEQUENCE OF SonusCallTraceEntry
    MAX-ACCESS      not-accessible
    STATUS          current
    DESCRIPTION     
            "This table specifies the Call Trace Table"
    ::= { sonusCallTrace 2 }

sonusCallTraceEntry OBJECT-TYPE
    SYNTAX          SonusCallTraceEntry
    MAX-ACCESS      not-accessible
    STATUS          current
    DESCRIPTION     
            ""
    INDEX           { sonusCallTraceIndex }
    ::= { sonusCallTraceTable 1 }

SonusCallTraceEntry ::=
    SEQUENCE {
        sonusCallTraceIndex             Integer32,
        sonusCallTraceState             INTEGER,
        sonusCallTraceName              SonusName,
        sonusCallTraceType              INTEGER,
        sonusCallTraceCalledNumber      DisplayString,
        sonusCallTraceCallingNumber     DisplayString,
        sonusCallTraceLevel             INTEGER,
        sonusCallTraceRowStatus         RowStatus
    }

sonusCallTraceIndex OBJECT-TYPE
    SYNTAX          Integer32
    MAX-ACCESS      read-only
    STATUS          current
    DESCRIPTION     
            "The index of this Call Trace entry."
    ::= { sonusCallTraceEntry 1 }

sonusCallTraceState OBJECT-TYPE
    SYNTAX          INTEGER { disabled(1), enabled(2) }
    MAX-ACCESS      read-write
    STATUS          current
    DESCRIPTION     
            "The administrative state of this Call Trace entry."
    DEFVAL          { disabled }
    ::= { sonusCallTraceEntry 2 }

sonusCallTraceName OBJECT-TYPE
    SYNTAX          SonusName
    MAX-ACCESS      read-write
    STATUS          current
    DESCRIPTION     
            "The name of this Call Trace entry."
    ::= { sonusCallTraceEntry 3 }

sonusCallTraceType OBJECT-TYPE
    SYNTAX          INTEGER { calledcalling(1), calledonly(2), 
                        callingonly(3) }
    MAX-ACCESS      read-write
    STATUS          current
    DESCRIPTION     
            "The trace type of this Call Trace entry."
    DEFVAL          { calledcalling }
    ::= { sonusCallTraceEntry 4 }

sonusCallTraceCalledNumber OBJECT-TYPE
    SYNTAX          DisplayString (SIZE(0..30))
    MAX-ACCESS      read-write
    STATUS          current
    DESCRIPTION     
            "The called number being traced."
    ::= { sonusCallTraceEntry 5 }

sonusCallTraceCallingNumber OBJECT-TYPE
    SYNTAX          DisplayString (SIZE(0..30))
    MAX-ACCESS      read-write
    STATUS          current
    DESCRIPTION     
            "The calling number being traced."
    ::= { sonusCallTraceEntry 6 }

sonusCallTraceLevel OBJECT-TYPE
    SYNTAX          INTEGER { level1(1), level2(2), level3(3) }
    MAX-ACCESS      read-write
    STATUS          current
    DESCRIPTION     
            "The trace level of this call trace entry, currently only one level is supported."
    DEFVAL          { level2 }
    ::= { sonusCallTraceEntry 7 }

sonusCallTraceRowStatus OBJECT-TYPE
    SYNTAX          RowStatus
    MAX-ACCESS      read-write
    STATUS          current
    DESCRIPTION     
            ""
    ::= { sonusCallTraceEntry 8 }

sonusCktServProfile OBJECT IDENTIFIER
    ::= { sonusNodeResourcesMIBObjects 12 }

sonusCktServProfileNextIndex OBJECT-TYPE
    SYNTAX          Integer32
    MAX-ACCESS      read-only
    STATUS          current
    DESCRIPTION     
            "The next valid index to use when creating an entry in
             the sonusCktServProfileTable."
    ::= { sonusCktServProfile 1 }

sonusCktServProfileTable OBJECT-TYPE
    SYNTAX          SEQUENCE OF SonusCktServProfileEntry
    MAX-ACCESS      not-accessible
    STATUS          current
    DESCRIPTION     
            "This table specifies the Circuit service profile list for the node."
    ::= { sonusCktServProfile 2 }

sonusCktServProfileEntry OBJECT-TYPE
    SYNTAX          SonusCktServProfileEntry
    MAX-ACCESS      not-accessible
    STATUS          current
    DESCRIPTION     
            ""
    INDEX           { sonusCktServProfileIndex }
    ::= { sonusCktServProfileTable 1 }

SonusCktServProfileEntry ::=
    SEQUENCE {
        sonusCktServProfileIndex        Integer32,
        sonusCktServProfileState        INTEGER,
        sonusCktServProfileName         SonusName,
        sonusCktServProfileAudioEncoding INTEGER,
        sonusCktServProfileBandwidth    Integer32,
        sonusCktServProfileNecEnable    INTEGER,
        sonusCktServProfileCttTestType  INTEGER,
        sonusCktServProfileCttTimeout   Integer32,
        sonusCktServProfileCttMinDetectTime   Integer32,
        sonusCktServProfileCttMinReleaseTime    Integer32,
        sonusCktServProfileCapability   INTEGER,
        sonusCktServProfileDataRestrictedCfg    INTEGER,
        sonusCktServProfileDtmfProfileName  SonusNameReference,
        sonusCktServProfileRowStatus    RowStatus,
        sonusCktServProfileInterworkingXfrCap     INTEGER
    }

sonusCktServProfileIndex OBJECT-TYPE
    SYNTAX          Integer32
    MAX-ACCESS      read-only
    STATUS          current
    DESCRIPTION     
            "Identifies the target circuit service profile entry."
    ::= { sonusCktServProfileEntry 1 }

sonusCktServProfileState OBJECT-TYPE
    SYNTAX          INTEGER { disabled(1), enabled(2) }
    MAX-ACCESS      read-write
    STATUS          current
    DESCRIPTION     
            "The administrative state of this circuit service profile entry."
    DEFVAL          { disabled }
    ::= { sonusCktServProfileEntry 2 }

sonusCktServProfileName OBJECT-TYPE
    SYNTAX          SonusName
    MAX-ACCESS      read-write
    STATUS          current
    DESCRIPTION     
            "The name of this circuit service profile."
    ::= { sonusCktServProfileEntry 3 }

sonusCktServProfileAudioEncoding OBJECT-TYPE
    SYNTAX          INTEGER { g711ulaw(1), g711alaw(2) }
    MAX-ACCESS      read-write
    STATUS          current
    DESCRIPTION     
            "The audio encoding method to be performed on the voice data
             received from, and destined to the PSTN. The default encoding
             method is G.711 Ulaw."
    DEFVAL          { g711ulaw }
    ::= { sonusCktServProfileEntry 4 }

sonusCktServProfileBandwidth OBJECT-TYPE
    SYNTAX          Integer32 (1..24)
    MAX-ACCESS      read-write
    STATUS          current
    DESCRIPTION     
            "The number of DS0 channels to group for Nx64 connections. 
             Valid entries are 1 to 24 channels, allowing up to a 
             complete set of T1 channels to be grouped at a single
             connection. The default bandwidth is 1 channel."
    DEFVAL          { 1 }
    ::= { sonusCktServProfileEntry 5 }

sonusCktServProfileNecEnable OBJECT-TYPE
    SYNTAX          INTEGER { disabled(1), enabled(2) }
    MAX-ACCESS      read-write
    STATUS          current
    DESCRIPTION     
            "Specifies whether Network Echo Cancellation (NEC) is 
             enabled for the channel. When enabled, NEC is enabled
             acording to the appropriate NEC configuration parameters.
             When disabled, the echo chaceller is bypassed."
    DEFVAL          { enabled }
    ::= { sonusCktServProfileEntry 6 }

sonusCktServProfileCttTestType OBJECT-TYPE
    SYNTAX          INTEGER { remoteLoopback(1), remote2Wire(2), 
                        remote4Wire(3) }
    MAX-ACCESS      read-write
    STATUS          current
    DESCRIPTION     
            "For ISUP service profiles, specifies the type of continuity
             test to perform, based on the configuration of the remote
             switch or trunk connection. The remoteLoopback test is used
             when the remote switch will loop back channel being tested.
             The remote2Wire test is used when the remote switch supports
             the 2 wire continuity test procedure. And the remote4Wire 
             test mode is used when the remote switch supports the 4 wire
             continuity test procedure. The default value is remoteLoopback."
    DEFVAL          { remoteLoopback }
    ::= { sonusCktServProfileEntry 7 }

sonusCktServProfileCttTimeout OBJECT-TYPE
    SYNTAX          Integer32 (1..8)
    MAX-ACCESS      read-write
    STATUS          current
    DESCRIPTION     
            "For ISUP service profiles, specifies the overall test timeout
             value. The continuity test will be declared failed if the
             continuity tone is not detected within this timeout period. 
             The timeout is specified in seconds, with a default value of
             2 seconds."
    DEFVAL          { 2 }
    ::= { sonusCktServProfileEntry 8 }

sonusCktServProfileCttMinDetectTime OBJECT-TYPE
    SYNTAX          Integer32 (10..60)
    MAX-ACCESS      read-write
    STATUS          current
    DESCRIPTION     
            "For ISUP service profiles, specifies the minimum time
             to detect the presence of the continuity test tone. The 
             minimum detect time is specified in milliseconds, with
             a default time of 45 ms."
    DEFVAL          { 45 }
    ::= { sonusCktServProfileEntry 9 }

sonusCktServProfileCttMinReleaseTime OBJECT-TYPE
    SYNTAX          Integer32 (10..40)
    MAX-ACCESS      read-write
    STATUS          current
    DESCRIPTION     
            "For ISUP service profiles, specifies the minimum time
             to detect that the continuity test tone has been removed
             and is no longer present. The minimum release time
             is specified in milliseconds, with a default time of 25 ms."
    DEFVAL          { 25 }
    ::= { sonusCktServProfileEntry 10 }

sonusCktServProfileCapability OBJECT-TYPE
    SYNTAX          INTEGER { voiceOnly(1), circuitModeData(2), 
                        voiceOrCircuitModeData(3) }
    MAX-ACCESS      read-write
    STATUS          current
    DESCRIPTION     
            "Specifies the data capabilities for the circuit. This parameter
             specifies whether voice only, circuit mode data only, or both voice
             and circuit mode data can be supported by the circuit."
    DEFVAL          { voiceOrCircuitModeData }
    ::= { sonusCktServProfileEntry 11 }

sonusCktServProfileDataRestrictedCfg OBJECT-TYPE
    SYNTAX          INTEGER { unrestricted(1), restricted(2) }
    MAX-ACCESS      read-write
    STATUS          current
    DESCRIPTION     
            "Specifies whether the circuit may support 64 Kbit/s unrestricted data, 
             or if the circuit supports 56 Kbit/s restricted data."
    DEFVAL          { unrestricted }
    ::= { sonusCktServProfileEntry 12 }

sonusCktServProfileDtmfProfileName OBJECT-TYPE
    SYNTAX          SonusNameReference
    MAX-ACCESS      read-write
    STATUS          current
    DESCRIPTION     
            "The name of DTMF profile associated with this circuit service profile."
    ::= { sonusCktServProfileEntry 13 }

sonusCktServProfileRowStatus OBJECT-TYPE
    SYNTAX          RowStatus
    MAX-ACCESS      read-write
    STATUS          current
    DESCRIPTION     
            ""
    ::= { sonusCktServProfileEntry 14 }

sonusCktServProfileInterworkingXfrCap OBJECT-TYPE
    SYNTAX          INTEGER { speech(1), audio31Khz(2) }
    MAX-ACCESS      read-write
    STATUS          current
    DESCRIPTION     
            "The transfer capability for audio calls when interworking
             with CAS. The default transfer capability is speech."
    DEFVAL          { speech }
    ::= { sonusCktServProfileEntry 15 }

sonusPktServProfile OBJECT IDENTIFIER
    ::= { sonusNodeResourcesMIBObjects 13 }

sonusPktServProfileNextIndex OBJECT-TYPE
    SYNTAX          Integer32
    MAX-ACCESS      read-only
    STATUS          current
    DESCRIPTION     
            "The next valid index to use when creating an entry in
             the sonusPktServProfileTable."
    ::= { sonusPktServProfile 1 }

sonusPktServProfileTable OBJECT-TYPE
    SYNTAX          SEQUENCE OF SonusPktServProfileEntry
    MAX-ACCESS      not-accessible
    STATUS          current
    DESCRIPTION     
            "This table specifies the packet service profile list for the node."
    ::= { sonusPktServProfile 2 }

sonusPktServProfileEntry OBJECT-TYPE
    SYNTAX          SonusPktServProfileEntry
    MAX-ACCESS      not-accessible
    STATUS          current
    DESCRIPTION     
            ""
    INDEX           { sonusPktServProfileIndex }
    ::= { sonusPktServProfileTable 1 }

SonusPktServProfileEntry ::=
    SEQUENCE {
        sonusPktServProfileIndex        Integer32,
        sonusPktServProfileState        INTEGER,
        sonusPktServProfileName         SonusName,
        sonusPktServProfileDestProtocol INTEGER,
        sonusPktServProfilePrfdAudioEncoding    INTEGER,
        sonusPktServProfilePrfdFramesPerPacket      Integer32,
        sonusPktServProfileDefFramesPerPacket     Integer32,
        sonusPktServProfileDefAudioEnable INTEGER,
        sonusPktServProfileSilenceFactor Integer32,
        sonusPktServProfileVInitPlayoutBufDelay       Integer32,
        sonusPktServProfileFaxRelay     INTEGER,
        sonusPktServProfileDtmfRelay    INTEGER,
        sonusPktServProfileFallbackHandling   INTEGER,
        sonusPktServProfileTosValue     Integer32,
        sonusPktServProfileDInitPlayoutBufDelay       Integer32,
        sonusPktServProfileDataRtpPayloadType     Integer32,
        sonusPktServProfileRowStatus    RowStatus,
        sonusPktServProfileG711SendSidPackets     INTEGER,
        sonusPktServProfileG711SidRtpPayloadType        Integer32,
        sonusPktServProfileSidHeartbeat INTEGER,
        sonusPktServProfileRtcp         INTEGER,
        sonusPktServProfilePacketLossThreshold      Integer32,
        sonusPktServProfilePacketLossAction   INTEGER,
        sonusPktServProfileRtpPeerAbsenceAction       INTEGER,
        sonusPktServProfileDtmfRelayOutOfBand     INTEGER,
        sonusPktServProfileDtmfRelayRemoveDigits        INTEGER
    }

sonusPktServProfileIndex OBJECT-TYPE
    SYNTAX          Integer32
    MAX-ACCESS      read-only
    STATUS          current
    DESCRIPTION     
            "Identifies the target packet service profile entry."
    ::= { sonusPktServProfileEntry 1 }

sonusPktServProfileState OBJECT-TYPE
    SYNTAX          INTEGER { disabled(1), enabled(2) }
    MAX-ACCESS      read-write
    STATUS          current
    DESCRIPTION     
            "The administrative state of this packet service profile entry."
    DEFVAL          { disabled }
    ::= { sonusPktServProfileEntry 2 }

sonusPktServProfileName OBJECT-TYPE
    SYNTAX          SonusName
    MAX-ACCESS      read-write
    STATUS          current
    DESCRIPTION     
            "The user name of this packet service profile."
    ::= { sonusPktServProfileEntry 3 }

sonusPktServProfileDestProtocol OBJECT-TYPE
    SYNTAX          INTEGER { gsx(1), h323(2) }
    MAX-ACCESS      read-write
    STATUS          current
    DESCRIPTION     
            "Specifies the Packet Destination Protocal used. 
             GSX - uses Sonus GSX-GSX MCS protocol.
             h323 - uses H.323 protocol."
    DEFVAL          { gsx }
    ::= { sonusPktServProfileEntry 4 }

sonusPktServProfilePrfdAudioEncoding OBJECT-TYPE
    SYNTAX          INTEGER { g711(1), g711ss(2), g729a(4), g729ab(5) }
    MAX-ACCESS      read-write
    STATUS          current
    DESCRIPTION     
            "The preferred audio encoding method to be performed on the packet data received from, 
             and destined to the IP network. 
             The possible options are: G.711, G.711 with Silence Suppression, G.729A and G.729A+B. 
             The default encoding method is G.711. For G.711, the law is determined by Circuit Service Profile."
    DEFVAL          { g711 }
    ::= { sonusPktServProfileEntry 5 }

sonusPktServProfilePrfdFramesPerPacket OBJECT-TYPE
    SYNTAX          Integer32
    MAX-ACCESS      read-write
    STATUS          current
    DESCRIPTION     
            "Specifies the Preferred Audio Encoding Packet Size in milliseconds.
             For G.711 encoding mode, valid values range from 10 ms to
             40 ms, in increments of 5 ms. The default value for G.711 is 10 ms. 
             For G.729 encoding mode, valid values from 10 ms to 40 ms, in increments of 10 ms. The default value for G.729 is 20 ms."
    DEFVAL          { 10 }
    ::= { sonusPktServProfileEntry 6 }

sonusPktServProfileDefFramesPerPacket OBJECT-TYPE
    SYNTAX          Integer32
    MAX-ACCESS      read-write
    STATUS          current
    DESCRIPTION     
            "Specifies the default Audio Encoding Packet Size in milliseconds.
             For G.711 encoding mode, valid values range from 10 ms to
             40 ms, in increments of 5 ms. The default value for G.711 is 10 ms. 
             For G.729 encoding mode, valid values from 10 ms to 40 ms, in increments of 10 ms. The default value for G.729 is 20 ms."
    DEFVAL          { 10 }
    ::= { sonusPktServProfileEntry 7 }

sonusPktServProfileDefAudioEnable OBJECT-TYPE
    SYNTAX          INTEGER { disabled(1), enabled(2) }
    MAX-ACCESS      read-write
    STATUS          current
    DESCRIPTION     
            "Specifies whether or not to allow default Audio (G.711).
             If enabled, allow use of G.711 if preferred audio resource is not available. 
             If disabled, Do not use of G.711 if preferred audio resource is not available and the call is disconnected."
    DEFVAL          { enabled }
    ::= { sonusPktServProfileEntry 8 }

sonusPktServProfileSilenceFactor OBJECT-TYPE
    SYNTAX          Integer32 (0..50)
    MAX-ACCESS      read-write
    STATUS          current
    DESCRIPTION     
            "Specifies percentage of call time that silence is expected."
    DEFVAL          { 0 }
    ::= { sonusPktServProfileEntry 9 }

sonusPktServProfileVInitPlayoutBufDelay OBJECT-TYPE
    SYNTAX          Integer32
    MAX-ACCESS      read-write
    STATUS          current
    DESCRIPTION     
            "This value defines the size of the initial playout bufferrequired to absorb 
             the maximum expected voice packet delay across the network.
             Range from 1 ms to 50 ms, in increments of 1 ms."
    DEFVAL          { 10 }
    ::= { sonusPktServProfileEntry 10 }

sonusPktServProfileFaxRelay OBJECT-TYPE
    SYNTAX          INTEGER { never(0), useIfCompressedAudio(1), 
                        always(2) }
    MAX-ACCESS      read-write
    STATUS          current
    DESCRIPTION     
            "If never is specified, Fax Relay is not used regardless of the audio encoding method.
             If useIfCompressedAudio is specified, Fax Relay is used if the compressed resource is available.
             If always is specified, Fax Relay is used regardless of the audio encoding method."
    DEFVAL          { never }
    ::= { sonusPktServProfileEntry 11 }

sonusPktServProfileDtmfRelay OBJECT-TYPE
    SYNTAX          INTEGER { never(0), useIfCompressedAudio(1), 
                        always(2) }
    MAX-ACCESS      read-write
    STATUS          current
    DESCRIPTION     
            "If never is specified, DTMF Relay is not used regardless of the audio encoding method.
             If useIfCompressedAudio is specified, DTMF Relay is used if the compressed resource is available.
             If always is specified, DTMF Relay is used regardless of the audio encoding method."
    DEFVAL          { never }
    ::= { sonusPktServProfileEntry 12 }

sonusPktServProfileFallbackHandling OBJECT-TYPE
    SYNTAX          INTEGER { disconnet(1), continue(2) }
    MAX-ACCESS      read-write
    STATUS          current
    DESCRIPTION     
            "This specifies the behavior when a compressed codec call needs to revert to G.711 (e.g., to pass modem data) 
             and there is no bandwidth available."
    DEFVAL          { continue }
    ::= { sonusPktServProfileEntry 13 }

sonusPktServProfileTosValue OBJECT-TYPE
    SYNTAX          Integer32 (0..255)
    MAX-ACCESS      read-write
    STATUS          current
    DESCRIPTION     
            "Specifies the Type Of Service (TOS) parameters to be provided in the IP header for voice packets.
             The TOS value is specified as an 8-bit hex value 0x00-0xFF allowing complete flexibility with 
             respect to the contents of the TOS byte."
    DEFVAL          { 0 }
    ::= { sonusPktServProfileEntry 14 }

sonusPktServProfileDInitPlayoutBufDelay OBJECT-TYPE
    SYNTAX          Integer32
    MAX-ACCESS      read-write
    STATUS          current
    DESCRIPTION     
            "This value defines the size of the initial playout buffer required to absorb the 
             maximum expected data packet delay across the network.
             Range from 5 ms to 50 ms, in increments of 1 ms. The default value is 50 ms."
    DEFVAL          { 50 }
    ::= { sonusPktServProfileEntry 15 }

sonusPktServProfileDataRtpPayloadType OBJECT-TYPE
    SYNTAX          Integer32 (0..127)
    MAX-ACCESS      read-write
    STATUS          current
    DESCRIPTION     
            "Specifies the RTP payload type to be included in the RTP header of the data packet"
    DEFVAL          { 56 }
    ::= { sonusPktServProfileEntry 16 }

sonusPktServProfileRowStatus OBJECT-TYPE
    SYNTAX          RowStatus
    MAX-ACCESS      read-write
    STATUS          current
    DESCRIPTION     
            ""
    ::= { sonusPktServProfileEntry 17 }

sonusPktServProfileG711SendSidPackets OBJECT-TYPE
    SYNTAX          INTEGER { disabled(1), enabled(2) }
    MAX-ACCESS      read-write
    STATUS          current
    DESCRIPTION     
            " Specifies whether sending SID packets is enabled.
             This applies only if preferred audio encoding is G.711 with silence suppression."
    DEFVAL          { enabled }
    ::= { sonusPktServProfileEntry 18 }

sonusPktServProfileG711SidRtpPayloadType OBJECT-TYPE
    SYNTAX          Integer32 (0..127)
    MAX-ACCESS      read-write
    STATUS          current
    DESCRIPTION     
            " Specifies G.711 SID RTP payload type.
             This applies only if preferred audio encoding is G.711 with silence suppression. Range 0 to 127."
    DEFVAL          { 19 }
    ::= { sonusPktServProfileEntry 19 }

sonusPktServProfileSidHeartbeat OBJECT-TYPE
    SYNTAX          INTEGER { disabled(1), enabled(2) }
    MAX-ACCESS      read-write
    STATUS          current
    DESCRIPTION     
            " Specifies whether sending SID heartbeat packets is enabled.
             This applies if preferred audio encoding is either G.711 with silence suppression or G.729A+B."
    DEFVAL          { enabled }
    ::= { sonusPktServProfileEntry 20 }

sonusPktServProfileRtcp OBJECT-TYPE
    SYNTAX          INTEGER { disabled(1), enabled(2) }
    MAX-ACCESS      read-write
    STATUS          current
    DESCRIPTION     
            "Specifies whether RTCP is enabled for the call."
    DEFVAL          { disabled }
    ::= { sonusPktServProfileEntry 21 }

sonusPktServProfilePacketLossThreshold OBJECT-TYPE
    SYNTAX          Integer32
    MAX-ACCESS      read-write
    STATUS          current
    DESCRIPTION     
            " Specifies the RTCP packet loss threshold in packets/100,000.
             0 means no detection.
             Requires RTCP to be enabled."
    DEFVAL          { 0 }
    ::= { sonusPktServProfileEntry 22 }

sonusPktServProfilePacketLossAction OBJECT-TYPE
    SYNTAX          INTEGER { none(0), trap(1), trapAndDisconnect(3) }
    MAX-ACCESS      read-write
    STATUS          current
    DESCRIPTION     
            " Specifies the action taken when the packet loss threshold is
             exceeded. Requires RTCP to be enabled."
    DEFVAL          { none }
    ::= { sonusPktServProfileEntry 23 }

sonusPktServProfileRtpPeerAbsenceAction OBJECT-TYPE
    SYNTAX          INTEGER { none(0), trap(1), trapAndDisconnect(3) }
    MAX-ACCESS      read-write
    STATUS          current
    DESCRIPTION     
            " Specifies the action taken when the RTP peer is detected to be absent (due to lack of RTP and RTCP packets).
             Requires RTCP to be enabled."
    DEFVAL          { none }
    ::= { sonusPktServProfileEntry 24 }

sonusPktServProfileDtmfRelayOutOfBand OBJECT-TYPE
    SYNTAX          INTEGER { disabled(1), enabled(2) }
    MAX-ACCESS      read-write
    STATUS          current
    DESCRIPTION     
            " Specifies whether out of band DTMF relay is enabled.
             This applies if DTMF relay is configured as useIfCompressedAudio or always ."
    DEFVAL          { disabled }
    ::= { sonusPktServProfileEntry 25 }

sonusPktServProfileDtmfRelayRemoveDigits OBJECT-TYPE
    SYNTAX          INTEGER { disabled(1), enabled(2) }
    MAX-ACCESS      read-write
    STATUS          current
    DESCRIPTION     
            " Specifies whether removing DTMF digits from the media stream is enabled.
             This applies if DTMF relay is configured as useIfCompressedAudio or always ."
    DEFVAL          { enabled }
    ::= { sonusPktServProfileEntry 26 }

sonusDisconnectTreatmentObjects OBJECT IDENTIFIER
    ::= { sonusNodeResourcesMIBObjects 14 }

sonusDiscTreatProfile OBJECT IDENTIFIER
    ::= { sonusDisconnectTreatmentObjects 1 }

sonusDiscTreatProfileNextIndex OBJECT-TYPE
    SYNTAX          Integer32
    MAX-ACCESS      read-only
    STATUS          current
    DESCRIPTION     
            "The next valid index to use when creating an entry in
             the sonusDiscTreatProfileTable."
    ::= { sonusDiscTreatProfile 1 }

sonusDiscTreatProfileTable OBJECT-TYPE
    SYNTAX          SEQUENCE OF SonusDiscTreatProfileEntry
    MAX-ACCESS      not-accessible
    STATUS          current
    DESCRIPTION     
            "This table contains Disconnect Treatment Profiles for the node."
    ::= { sonusDiscTreatProfile 2 }

sonusDiscTreatProfileEntry OBJECT-TYPE
    SYNTAX          SonusDiscTreatProfileEntry
    MAX-ACCESS      not-accessible
    STATUS          current
    DESCRIPTION     
            ""
    INDEX           { sonusDiscTreatProfileIndex }
    ::= { sonusDiscTreatProfileTable 1 }

SonusDiscTreatProfileEntry ::=
    SEQUENCE {
        sonusDiscTreatProfileIndex      Integer32,
        sonusDiscTreatProfileName       SonusName,
        sonusDiscTreatProfileRowStatus  RowStatus
    }

sonusDiscTreatProfileIndex OBJECT-TYPE
    SYNTAX          Integer32
    MAX-ACCESS      not-accessible
    STATUS          current
    DESCRIPTION     
            "Identifies the Disconnect Treatment Profile."
    ::= { sonusDiscTreatProfileEntry 1 }

sonusDiscTreatProfileName OBJECT-TYPE
    SYNTAX          SonusName
    MAX-ACCESS      read-write
    STATUS          current
    DESCRIPTION     
            "The user name of this Disconnect Treatment Profile."
    ::= { sonusDiscTreatProfileEntry 2 }

sonusDiscTreatProfileRowStatus OBJECT-TYPE
    SYNTAX          RowStatus
    MAX-ACCESS      read-write
    STATUS          current
    DESCRIPTION     
            ""
    ::= { sonusDiscTreatProfileEntry 3 }

sonusDiscTreatmentAdmnTable OBJECT-TYPE
    SYNTAX          SEQUENCE OF SonusDiscTreatmentAdmnEntry
    MAX-ACCESS      not-accessible
    STATUS          current
    DESCRIPTION     
            ""
    ::= { sonusDisconnectTreatmentObjects 2 }

sonusDiscTreatmentAdmnEntry OBJECT-TYPE
    SYNTAX          SonusDiscTreatmentAdmnEntry
    MAX-ACCESS      not-accessible
    STATUS          current
    DESCRIPTION     
            ""
    INDEX           { sonusDiscTreatmentProfileIndex, 
                      sonusDiscTreatmentIndex }
    ::= { sonusDiscTreatmentAdmnTable 1 }

SonusDiscTreatmentAdmnEntry ::=
    SEQUENCE {
        sonusDiscTreatmentProfileIndex  Integer32,
        sonusDiscTreatmentIndex         Integer32,
        sonusDiscTreatmentReason        Integer32,
        sonusDiscTreatmentSigSeqProfileName   SonusNameReference,
        sonusDiscTreatmentRowStatus     RowStatus
    }

sonusDiscTreatmentProfileIndex OBJECT-TYPE
    SYNTAX          Integer32
    MAX-ACCESS      not-accessible
    STATUS          current
    DESCRIPTION     
            "Identifies the Disconnect Treatment Profile to which this entry belongs."
    ::= { sonusDiscTreatmentAdmnEntry 1 }

sonusDiscTreatmentIndex OBJECT-TYPE
    SYNTAX          Integer32
    MAX-ACCESS      not-accessible
    STATUS          current
    DESCRIPTION     
            "Identifies the target Disconnect Treatment entry."
    ::= { sonusDiscTreatmentAdmnEntry 2 }

sonusDiscTreatmentReason OBJECT-TYPE
    SYNTAX          Integer32 (0..255)
    MAX-ACCESS      read-only
    STATUS          current
    DESCRIPTION     
            "Disconnect Reason Code."
    ::= { sonusDiscTreatmentAdmnEntry 3 }

sonusDiscTreatmentSigSeqProfileName OBJECT-TYPE
    SYNTAX          SonusNameReference
    MAX-ACCESS      read-write
    STATUS          current
    DESCRIPTION     
            "For given Disconnect Treatment Profile and Disconnect
             Reason Code, execute this Disconnect SSP."
    ::= { sonusDiscTreatmentAdmnEntry 4 }

sonusDiscTreatmentRowStatus OBJECT-TYPE
    SYNTAX          RowStatus
    MAX-ACCESS      read-write
    STATUS          current
    DESCRIPTION     
            ""
    ::= { sonusDiscTreatmentAdmnEntry 5 }

sonusDiscSspGroupAdmn OBJECT IDENTIFIER
    ::= { sonusDisconnectTreatmentObjects 3 }

sonusDiscSspNextIndex OBJECT-TYPE
    SYNTAX          Integer32
    MAX-ACCESS      read-only
    STATUS          current
    DESCRIPTION     
            "The next valid index to use when creating a new sonusDiscSspGroupAdmnEntry"
    ::= { sonusDiscSspGroupAdmn 1 }

sonusDiscSspAdmnTable OBJECT-TYPE
    SYNTAX          SEQUENCE OF SonusDiscSspAdmnEntry
    MAX-ACCESS      not-accessible
    STATUS          current
    DESCRIPTION     
            ""
    ::= { sonusDiscSspGroupAdmn 2 }

sonusDiscSspAdmnEntry OBJECT-TYPE
    SYNTAX          SonusDiscSspAdmnEntry
    MAX-ACCESS      not-accessible
    STATUS          current
    DESCRIPTION     
            ""
    INDEX           { sonusDiscSigSeqProfileIndex }
    ::= { sonusDiscSspAdmnTable 1 }

SonusDiscSspAdmnEntry ::=
    SEQUENCE {
        sonusDiscSigSeqProfileIndex     Integer32,
        sonusDiscSigSeqProfileName      SonusName,
        sonusDiscSigSeqProfileRowStatus RowStatus
    }

sonusDiscSigSeqProfileIndex OBJECT-TYPE
    SYNTAX          Integer32
    MAX-ACCESS      not-accessible
    STATUS          current
    DESCRIPTION     
            "Identifies the target Disconnect Signal Sequence Profile."
    ::= { sonusDiscSspAdmnEntry 1 }

sonusDiscSigSeqProfileName OBJECT-TYPE
    SYNTAX          SonusName
    MAX-ACCESS      read-write
    STATUS          current
    DESCRIPTION     
            "The user name of this Disconnect Signal Sequence Profile."
    ::= { sonusDiscSspAdmnEntry 2 }

sonusDiscSigSeqProfileRowStatus OBJECT-TYPE
    SYNTAX          RowStatus
    MAX-ACCESS      read-write
    STATUS          current
    DESCRIPTION     
            ""
    ::= { sonusDiscSspAdmnEntry 3 }

sonusDiscSigSeqAdmnTable OBJECT-TYPE
    SYNTAX          SEQUENCE OF SonusDiscSigSeqAdmnEntry
    MAX-ACCESS      not-accessible
    STATUS          current
    DESCRIPTION     
            ""
    ::= { sonusDisconnectTreatmentObjects 4 }

sonusDiscSigSeqAdmnEntry OBJECT-TYPE
    SYNTAX          SonusDiscSigSeqAdmnEntry
    MAX-ACCESS      not-accessible
    STATUS          current
    DESCRIPTION     
            ""
    INDEX           { sonusDiscSigSequenceProfileIndex, 
                      sonusDiscSigSequenceIndex }
    ::= { sonusDiscSigSeqAdmnTable 1 }

SonusDiscSigSeqAdmnEntry ::=
    SEQUENCE {
        sonusDiscSigSequenceProfileIndex Integer32,
        sonusDiscSigSequenceIndex       Integer32,
        sonusDiscSigSequencePosition    Integer32,
        sonusDiscSigSequenceToken       INTEGER,
        sonusDiscSigSequenceParam1      DisplayString,
        sonusDiscSigSequenceParam2      DisplayString,
        sonusDiscSigSequenceAdminState  SonusAdminState,
        sonusDiscSigSequenceRowStatus   RowStatus
    }

sonusDiscSigSequenceProfileIndex OBJECT-TYPE
    SYNTAX          Integer32
    MAX-ACCESS      not-accessible
    STATUS          current
    DESCRIPTION     
            ""
    ::= { sonusDiscSigSeqAdmnEntry 1 }

sonusDiscSigSequenceIndex OBJECT-TYPE
    SYNTAX          Integer32
    MAX-ACCESS      not-accessible
    STATUS          current
    DESCRIPTION     
            ""
    ::= { sonusDiscSigSeqAdmnEntry 2 }

sonusDiscSigSequencePosition OBJECT-TYPE
    SYNTAX          Integer32 (0..31)
    MAX-ACCESS      read-write
    STATUS          current
    DESCRIPTION     
            ""
    DEFVAL          { 0 }
    ::= { sonusDiscSigSeqAdmnEntry 3 }

sonusDiscSigSequenceToken OBJECT-TYPE
    SYNTAX          INTEGER { playTone(7), playAnn(8), delay(9), 
                        clear(16), exec(17) }
    MAX-ACCESS      read-write
    STATUS          current
    DESCRIPTION     
            ""
    DEFVAL          { clear }
    ::= { sonusDiscSigSeqAdmnEntry 4 }

sonusDiscSigSequenceParam1 OBJECT-TYPE
    SYNTAX          DisplayString (SIZE(0..31))
    MAX-ACCESS      read-write
    STATUS          current
    DESCRIPTION     
            ""
    ::= { sonusDiscSigSeqAdmnEntry 5 }

sonusDiscSigSequenceParam2 OBJECT-TYPE
    SYNTAX          DisplayString (SIZE(0..31))
    MAX-ACCESS      read-write
    STATUS          current
    DESCRIPTION     
            ""
    ::= { sonusDiscSigSeqAdmnEntry 6 }

sonusDiscSigSequenceAdminState OBJECT-TYPE
    SYNTAX          SonusAdminState
    MAX-ACCESS      read-write
    STATUS          current
    DESCRIPTION     
            ""
    DEFVAL          { disabled }
    ::= { sonusDiscSigSeqAdmnEntry 7 }

sonusDiscSigSequenceRowStatus OBJECT-TYPE
    SYNTAX          RowStatus
    MAX-ACCESS      read-write
    STATUS          current
    DESCRIPTION     
            ""
    ::= { sonusDiscSigSeqAdmnEntry 8 }

sonusTestCall OBJECT IDENTIFIER
    ::= { sonusNodeResourcesMIBObjects 15 }

sonusTestCallNextIndex OBJECT-TYPE
    SYNTAX          Integer32
    MAX-ACCESS      read-only
    STATUS          current
    DESCRIPTION     
            "The next valid index to use when creating an entry in
             the sonusTestCallAdmnTable"
    ::= { sonusTestCall 1 }

sonusTestCallAdmnTable OBJECT-TYPE
    SYNTAX          SEQUENCE OF SonusTestCallAdmnEntry
    MAX-ACCESS      not-accessible
    STATUS          current
    DESCRIPTION     
            "This table specifies the test call list for the node."
    ::= { sonusTestCall 2 }

sonusTestCallAdmnEntry OBJECT-TYPE
    SYNTAX          SonusTestCallAdmnEntry
    MAX-ACCESS      not-accessible
    STATUS          current
    DESCRIPTION     
            ""
    INDEX           { sonusTestCallAdmnIndex }
    ::= { sonusTestCallAdmnTable 1 }

SonusTestCallAdmnEntry ::=
    SEQUENCE {
        sonusTestCallAdmnIndex          Integer32,
        sonusTestCallAdmnState          INTEGER,
        sonusTestCallAdmnName           SonusName,
        sonusTestCallAdmnEndPointShelf  Integer32,
        sonusTestCallAdmnEndPointSlot   Integer32,
        sonusTestCallAdmnEndPointPort   Integer32,
        sonusTestCallAdmnEndPointChannel Integer32,
        sonusTestCallAdmnRowStatus      RowStatus,
        sonusTestCallAdmnType           INTEGER,
        sonusTestCallAdmnPower          Integer32,
        sonusTestCallAdmnFrequency      Integer32,
        sonusTestCallAdmnStatPower      Integer32,
        sonusTestCallAdmnStatPowerTenths Integer32
    }

sonusTestCallAdmnIndex OBJECT-TYPE
    SYNTAX          Integer32
    MAX-ACCESS      read-only
    STATUS          current
    DESCRIPTION     
            "Identifies the target test call entry."
    ::= { sonusTestCallAdmnEntry 1 }

sonusTestCallAdmnState OBJECT-TYPE
    SYNTAX          INTEGER { disabled(0), enabled(1) }
    MAX-ACCESS      read-write
    STATUS          current
    DESCRIPTION     
            "The administrative state of this test call entry."
    DEFVAL          { disabled }
    ::= { sonusTestCallAdmnEntry 2 }

sonusTestCallAdmnName OBJECT-TYPE
    SYNTAX          SonusName
    MAX-ACCESS      read-write
    STATUS          current
    DESCRIPTION     
            "The user name of this test call."
    ::= { sonusTestCallAdmnEntry 3 }

sonusTestCallAdmnEndPointShelf OBJECT-TYPE
    SYNTAX          Integer32 (1..6)
    MAX-ACCESS      read-write
    STATUS          current
    DESCRIPTION     
            "A 32-bit integer identifying the shelf of the end point"
    ::= { sonusTestCallAdmnEntry 4 }

sonusTestCallAdmnEndPointSlot OBJECT-TYPE
    SYNTAX          Integer32 (1..16)
    MAX-ACCESS      read-write
    STATUS          current
    DESCRIPTION     
            "A 32-bit integer identifying the slot of the end point"
    ::= { sonusTestCallAdmnEntry 5 }

sonusTestCallAdmnEndPointPort OBJECT-TYPE
    SYNTAX          Integer32 (1..65535)
    MAX-ACCESS      read-write
    STATUS          current
    DESCRIPTION     
            "Port index of end point."
    ::= { sonusTestCallAdmnEntry 6 }

sonusTestCallAdmnEndPointChannel OBJECT-TYPE
    SYNTAX          Integer32 (1..32)
    MAX-ACCESS      read-write
    STATUS          current
    DESCRIPTION     
            "Indicates the DS0 channel of the end point."
    ::= { sonusTestCallAdmnEntry 7 }

sonusTestCallAdmnRowStatus OBJECT-TYPE
    SYNTAX          RowStatus
    MAX-ACCESS      read-write
    STATUS          current
    DESCRIPTION     
            ""
    ::= { sonusTestCallAdmnEntry 8 }

sonusTestCallAdmnType OBJECT-TYPE
    SYNTAX          INTEGER { listen(0), play(1) }
    MAX-ACCESS      read-write
    STATUS          current
    DESCRIPTION     
            "The circuit type for this test call."
    DEFVAL          { listen }
    ::= { sonusTestCallAdmnEntry 9 }

sonusTestCallAdmnPower OBJECT-TYPE
    SYNTAX          Integer32 (-50..3)
    MAX-ACCESS      read-write
    STATUS          current
    DESCRIPTION     
            "The power in dBm of the tone to play."
    DEFVAL          { -6 }
    ::= { sonusTestCallAdmnEntry 10 }

sonusTestCallAdmnFrequency OBJECT-TYPE
    SYNTAX          Integer32 (0..3999)
    MAX-ACCESS      read-write
    STATUS          current
    DESCRIPTION     
            "The frequency in Hz of the tone to play or listen for."
    DEFVAL          { 1004 }
    ::= { sonusTestCallAdmnEntry 11 }

sonusTestCallAdmnStatPower OBJECT-TYPE
    SYNTAX          Integer32 (-1000..3)
    MAX-ACCESS      read-write
    STATUS          current
    DESCRIPTION     
            "The dBm of the tone received in LISTEN mode."
    DEFVAL          { -1000 }
    ::= { sonusTestCallAdmnEntry 12 }

sonusTestCallAdmnStatPowerTenths OBJECT-TYPE
    SYNTAX          Integer32 (0..9)
    MAX-ACCESS      read-write
    STATUS          current
    DESCRIPTION     
            "The tenths of dBm of the tone received in LISTEN mode."
    DEFVAL          { 0 }
    ::= { sonusTestCallAdmnEntry 13 }

sonusTestCallStatTable OBJECT-TYPE
    SYNTAX          SEQUENCE OF SonusTestCallStatEntry
    MAX-ACCESS      not-accessible
    STATUS          current
    DESCRIPTION     
            "The Manual Call Stat Table"
    ::= { sonusNodeResourcesMIBObjects 16 }

sonusTestCallStatEntry OBJECT-TYPE
    SYNTAX          SonusTestCallStatEntry
    MAX-ACCESS      not-accessible
    STATUS          current
    DESCRIPTION     
            "An entry in the Manual Call Stat Table"
    INDEX           { sonusTestCallStatIndex }
    ::= { sonusTestCallStatTable 1 }

SonusTestCallStatEntry ::=
    SEQUENCE {
        sonusTestCallStatIndex          Integer32,
        sonusTestCallStatCallId         Integer32,
        sonusTestCallStatState          DisplayString,
        sonusTestCallStatTime           DisplayString
    }

sonusTestCallStatIndex OBJECT-TYPE
    SYNTAX          Integer32
    MAX-ACCESS      read-only
    STATUS          current
    DESCRIPTION     
            "The index for target test call."
    ::= { sonusTestCallStatEntry 1 }

sonusTestCallStatCallId OBJECT-TYPE
    SYNTAX          Integer32
    MAX-ACCESS      read-only
    STATUS          current
    DESCRIPTION     
            "The call identifier(GCID) assigned to this test call"
    ::= { sonusTestCallStatEntry 2 }

sonusTestCallStatState OBJECT-TYPE
    SYNTAX          DisplayString (SIZE(0..23))
    MAX-ACCESS      read-only
    STATUS          current
    DESCRIPTION     
            "The status of the test call"
    ::= { sonusTestCallStatEntry 3 }

sonusTestCallStatTime OBJECT-TYPE
    SYNTAX          DisplayString (SIZE(0..23))
    MAX-ACCESS      read-only
    STATUS          current
    DESCRIPTION     
            "Displays the Date/time the connection was created"
    ::= { sonusTestCallStatEntry 4 }

sonusTestCallActionObjects OBJECT IDENTIFIER
    ::= { sonusNodeResourcesMIBObjects 17 }

sonusTestCallGcid OBJECT-TYPE
    SYNTAX          Integer32
    MAX-ACCESS      read-write
    STATUS          current
    DESCRIPTION     
            "The call identifier for a call to be deleted"
    ::= { sonusTestCallActionObjects 1 }

sonusTestCallAction OBJECT-TYPE
    SYNTAX          INTEGER { none(1), delete(2) }
    MAX-ACCESS      read-write
    STATUS          current
    DESCRIPTION     
            "The action that should be taken on the call"
    DEFVAL          { none }
    ::= { sonusTestCallActionObjects 2 }

sonusNodeResourcesMIBNotifications OBJECT IDENTIFIER
    ::= { sonusNodeResourcesMIB 2 }

sonusNodeResourcesMIBNotificationsPrefix OBJECT IDENTIFIER
    ::= { sonusNodeResourcesMIBNotifications 0 }

sonusNodeResourcesMIBNotificationsObjects OBJECT IDENTIFIER
    ::= { sonusNodeResourcesMIBNotifications 1 }

sonusCallAdmissionChangeReason OBJECT-TYPE
    SYNTAX          DisplayString (SIZE(1..101))
    MAX-ACCESS      read-only
    STATUS          current
    DESCRIPTION     
            "The reason why the call admission control state has changes."
    ::= { sonusNodeResourcesMIBNotificationsObjects 1 }

sonusNodeResourcesCallAdmissionSuspendedNotification NOTIFICATION-TYPE
    OBJECTS         { sonusCallAdmissionChangeReason, 
                      sonusEventDescription, sonusEventClass, 
                      sonusEventLevel }
    STATUS          current
    DESCRIPTION     
            "This trap indicates that call admission into the GSX has been
             suspended. Information provided by this trap includes the reason
             why call admission has been suspended."
    ::= { sonusNodeResourcesMIBNotificationsPrefix 1 }

sonusNodeResourcesCallAdmissionEnabledNotification NOTIFICATION-TYPE
    OBJECTS         { sonusCallAdmissionChangeReason, 
                      sonusEventDescription, sonusEventClass, 
                      sonusEventLevel }
    STATUS          current
    DESCRIPTION     
            "This trap indicates that call admission into the GSX has been
             enabled. Information provided by this trap includes the reason
             why call admission has been enabled."
    ::= { sonusNodeResourcesMIBNotificationsPrefix 2 }

sonusNodeResourcesCallTraceHitNotification NOTIFICATION-TYPE
    OBJECTS         { sonusCallTraceCalledNumber, 
                      sonusCallTraceCallingNumber, sonusEventDescription, 
                      sonusEventClass, sonusEventLevel }
    STATUS          current
    DESCRIPTION     
            "This trap indicates that call trace filter had a hit.
             Information provided by this trap includes the called number
             and the calling number."
    ::= { sonusNodeResourcesMIBNotificationsPrefix 3 }

END -- end of module SONUS-NODE-RESOURCES-MIB.
