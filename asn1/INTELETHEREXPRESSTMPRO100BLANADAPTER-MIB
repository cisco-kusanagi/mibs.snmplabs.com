-- MIB generated by miftomib version 1.0a

INTELETHEREXPRESSTMPRO100BLANADAPTER-MIB DEFINITIONS ::= BEGIN

-- This component implements a set of twelve groups relating to the LAN 
-- Adapter.

IMPORTS
    OBJECT-TYPE
    FROM RFC-1212
    Counter, enterprises
    FROM RFC1155-SMI
    DisplayString
    FROM RFC1213-MIB;

DmiCounter			::= Counter
DmiCounter64X		::= INTEGER (0..18446744073709551615)
DmiInteger			::= INTEGER
DmiDisplaystring	::= DisplayString
DmiDateX			::= OCTET STRING (SIZE (28))
DmiComponentIndex	::= INTEGER

intel                  	OBJECT IDENTIFIER ::= {enterprises 343}
products                OBJECT IDENTIFIER ::= {intel 2}
server-products         OBJECT IDENTIFIER ::= {products 6}
nic                     OBJECT IDENTIFIER ::= {server-products 4}
e100b                   OBJECT IDENTIFIER ::= {nic 1}
dmtfGroups          	OBJECT IDENTIFIER ::= {e100b 1}

SComponentid ::= SEQUENCE {
	a1Manufacturer                          	DmiDisplaystring,
	a1Product                               	DmiDisplaystring,
	a1Version                               	DmiDisplaystring,
	a1SerialNumber                          	DmiDisplaystring,
	a1Installation                          	DmiDateX,
	a1Verify                                	DmiInteger
}

tComponentid OBJECT-TYPE
	SYNTAX		SEQUENCE OF SComponentid
	ACCESS		not-accessible
	STATUS		mandatory
	DESCRIPTION	"This group defines attributes common to all components. This
group is required."
	::= {dmtfGroups 1}

eComponentid OBJECT-TYPE
	SYNTAX		SComponentid
	ACCESS		not-accessible
	STATUS		mandatory
	DESCRIPTION	""
	INDEX		{DmiComponentIndex}
	::= {tComponentid 1}

a1Manufacturer OBJECT-TYPE
	SYNTAX		DmiDisplaystring
	ACCESS		read-only
	STATUS		mandatory
	DESCRIPTION	"Manufacturer of this component."
	::= {eComponentid 1}

a1Product OBJECT-TYPE
	SYNTAX		DmiDisplaystring
	ACCESS		read-only
	STATUS		mandatory
	DESCRIPTION	"Product name for this component."
	::= {eComponentid 2}

a1Version OBJECT-TYPE
	SYNTAX		DmiDisplaystring
	ACCESS		not-accessible
	STATUS		mandatory
	DESCRIPTION	"Version number of this component."
	::= {eComponentid 3}

a1SerialNumber OBJECT-TYPE
	SYNTAX		DmiDisplaystring
	ACCESS		not-accessible
	STATUS		mandatory
	DESCRIPTION	"Serial number for this component."
	::= {eComponentid 4}

a1Installation OBJECT-TYPE
	SYNTAX		DmiDateX
	ACCESS		read-only
	STATUS		mandatory
	DESCRIPTION	"The date of the install of this component."
	::= {eComponentid 5}

a1Verify OBJECT-TYPE
	SYNTAX		INTEGER {
		vAnErrorOccurredCheckStatusCode         	(0),
		vThisComponentDoesNotExist              	(1),
		vVerificationIsNotSupported             	(2),
		vReserved                               	(3),
		vThisComponentExistsButTheFunctionalityI	(4),
		vThisComponentExistsButTheFunctionality1	(5),
		vThisComponentExistsAndIsNotFunctioningC	(6),
		vThisComponentExistsAndIsFunctioningCorr	(7)
	}
	ACCESS		read-only
	STATUS		mandatory
	DESCRIPTION	"A code that provides a level of verification that the component
is still installed and working."
	::= {eComponentid 6}

SSystemResourcesDescription ::= SEQUENCE {
	a2DeviceCount                           	DmiInteger,
	a2SystemResourceCount                   	DmiInteger
}

tSystemResourcesDescription OBJECT-TYPE
	SYNTAX		SEQUENCE OF SSystemResourcesDescription
	ACCESS		not-accessible
	STATUS		mandatory
	DESCRIPTION	"The System Resources Description group describes the number
of entries in the System Resources Group. "
	::= {dmtfGroups 2}

eSystemResourcesDescription OBJECT-TYPE
	SYNTAX		SSystemResourcesDescription
	ACCESS		not-accessible
	STATUS		mandatory
	DESCRIPTION	""
	INDEX		{DmiComponentIndex}
	::= {tSystemResourcesDescription 1}

a2DeviceCount OBJECT-TYPE
	SYNTAX		DmiInteger
	ACCESS		read-only
	STATUS		mandatory
	DESCRIPTION	"A count of the number of different hardware devices represented
in this table."
	::= {eSystemResourcesDescription 1}

a2SystemResourceCount OBJECT-TYPE
	SYNTAX		DmiInteger
	ACCESS		read-only
	STATUS		mandatory
	DESCRIPTION	"A count of the total number of system resources on this system."
	::= {eSystemResourcesDescription 2}

SSystemResources ::= SEQUENCE {
	a3DeviceId                              	DmiInteger,
	a3ResourceNumber                        	DmiInteger,
	a3ResourceType                          	DmiInteger,
	a3ResourceBase                          	DmiInteger,
	a3ResourceSize                          	DmiInteger,
	a3ResourceFlags                         	DmiInteger,
	a3GroupId                               	DmiInteger
}

tSystemResources OBJECT-TYPE
	SYNTAX		SEQUENCE OF SSystemResources
	ACCESS		not-accessible
	STATUS		mandatory
	DESCRIPTION	"The System Resources group contains hardware descriptions
which are commonly used on PC style computers such as IRQs, IO ports, and
memory address ranges."
	::= {dmtfGroups 3}

eSystemResources OBJECT-TYPE
	SYNTAX		SSystemResources
	ACCESS		not-accessible
	STATUS		mandatory
	DESCRIPTION	""
	INDEX		{DmiComponentIndex, a3DeviceId, a3ResourceNumber}
	::= {tSystemResources 1}

a3DeviceId OBJECT-TYPE
	SYNTAX		DmiInteger
	ACCESS		read-only
	STATUS		mandatory
	DESCRIPTION	"On systems that implement a PnP-like subsystem, the device
ID should be the ID used by that subsystem. On systems that do not have inherent
device numbering, then the instrumentation supporting the system resources
group should devise a device number scheme. In either case, the table will
naturally group all of the resources associated with a device."
	::= {eSystemResources 1}

a3ResourceNumber OBJECT-TYPE
	SYNTAX		DmiInteger
	ACCESS		read-only
	STATUS		mandatory
	DESCRIPTION	"This attribute is the ordinal of the resource within a device.
Within the table, any device may have one or more resources."
	::= {eSystemResources 2}

a3ResourceType OBJECT-TYPE
	SYNTAX		INTEGER {
		vOther                                  	(1),
		vUnknown                                	(2),
		vMemoryRange                            	(3),
		vIoPort                                 	(4),
		vIrq                                    	(5),
		vDma                                    	(6)
	}
	ACCESS		read-only
	STATUS		mandatory
	DESCRIPTION	"The type of system resource represented by this entry."
	::= {eSystemResources 3}

a3ResourceBase OBJECT-TYPE
	SYNTAX		DmiInteger
	ACCESS		read-only
	STATUS		mandatory
	DESCRIPTION	"The starting address of the system resource in the appropriate
address space."
	::= {eSystemResources 4}

a3ResourceSize OBJECT-TYPE
	SYNTAX		DmiInteger
	ACCESS		read-only
	STATUS		mandatory
	DESCRIPTION	"The size of the system resource."
	::= {eSystemResources 5}

a3ResourceFlags OBJECT-TYPE
	SYNTAX		DmiInteger
	ACCESS		not-accessible
	STATUS		mandatory
	DESCRIPTION	"This attribute contains fields representing the status of
this resource entry.  The meaning of this field varies according to the Resource
Type field in this group."
	::= {eSystemResources 6}

a3GroupId OBJECT-TYPE
	SYNTAX		DmiInteger
	ACCESS		read-only
	STATUS		mandatory
	DESCRIPTION	"This attribute is a 'back pointer' to a group within this
MIF, if applicable.  If the back pointer is not known, either because the
device is not represented by a group, or the actual device type is not known,
then the value of this attribute will be 0."
	::= {eSystemResources 7}

SNetworkAdapter802PortGroup ::= SEQUENCE {
	a4PortIndex                             	DmiInteger,
	a4PermanentNetworkAddress               	DmiDisplaystring,
	a4CurrentNetworkAddress                 	DmiDisplaystring,
	a4ConnectorType                         	DmiInteger,
	a4DataRate                              	DmiInteger,
	a4TotalPacketsTransmitted               	DmiCounter64X,
	a4TotalBytesTransmitted                 	DmiCounter64X,
	a4TotalPacketsReceived                  	DmiCounter64X,
	a4TotalBytesReceived                    	DmiCounter64X,
	a4TotalTransmitErrors                   	DmiCounter64X,
	a4TotalReceiveErrors                    	DmiCounter64X,
	a4TotalHostErrors                       	DmiCounter64X,
	a4TotalWireErrors                       	DmiCounter64X
}

tNetworkAdapter802PortGroup OBJECT-TYPE
	SYNTAX		SEQUENCE OF SNetworkAdapter802PortGroup
	ACCESS		not-accessible
	STATUS		mandatory
	DESCRIPTION	"Contains objects related to each of the network ports on
the network adapter."
	::= {dmtfGroups 4}

eNetworkAdapter802PortGroup OBJECT-TYPE
	SYNTAX		SNetworkAdapter802PortGroup
	ACCESS		not-accessible
	STATUS		mandatory
	DESCRIPTION	""
	INDEX		{DmiComponentIndex, a4PortIndex}
	::= {tNetworkAdapter802PortGroup 1}

a4PortIndex OBJECT-TYPE
	SYNTAX		DmiInteger
	ACCESS		read-only
	STATUS		mandatory
	DESCRIPTION	"This attribute is the ordinal of the network port within
the network adapter, i.e. the 'port number'."
	::= {eNetworkAdapter802PortGroup 1}

a4PermanentNetworkAddress OBJECT-TYPE
	SYNTAX		DmiDisplaystring
	ACCESS		read-only
	STATUS		mandatory
	DESCRIPTION	"This is the node address stored permanently in the adapter."
	::= {eNetworkAdapter802PortGroup 2}

a4CurrentNetworkAddress OBJECT-TYPE
	SYNTAX		DmiDisplaystring
	ACCESS		read-only
	STATUS		mandatory
	DESCRIPTION	"This is the node address that can be modified by software,
sometimes referred to as the Locally Administered Address (LAA)."
	::= {eNetworkAdapter802PortGroup 3}

a4ConnectorType OBJECT-TYPE
	SYNTAX		INTEGER {
		vUnknown                                	(1),
		vAui                                    	(2),
		vUtpCategory3                           	(3),
		vUtpCategory4                           	(4),
		vUtpCategory5                           	(5),
		vBnc                                    	(6),
		vStpRj45                                	(7),
		vStpDb9                                 	(8),
		vFiberMic                               	(9),
		vAppleAui                               	(10)
	}
	ACCESS		read-only
	STATUS		mandatory
	DESCRIPTION	"This is the type of connector currently being used to physically
attach this port to the LAN."
	::= {eNetworkAdapter802PortGroup 4}

a4DataRate OBJECT-TYPE
	SYNTAX		DmiInteger
	ACCESS		read-only
	STATUS		mandatory
	DESCRIPTION	"This is the rate at which data is transferred over the LAN
in Mbps."
	::= {eNetworkAdapter802PortGroup 5}

a4TotalPacketsTransmitted OBJECT-TYPE
	SYNTAX		DmiCounter64X
	ACCESS		read-only
	STATUS		mandatory
	DESCRIPTION	"This is the total number of packets transmitted."
	::= {eNetworkAdapter802PortGroup 6}

a4TotalBytesTransmitted OBJECT-TYPE
	SYNTAX		DmiCounter64X
	ACCESS		read-only
	STATUS		mandatory
	DESCRIPTION	"This is the total number of bytes transmitted."
	::= {eNetworkAdapter802PortGroup 7}

a4TotalPacketsReceived OBJECT-TYPE
	SYNTAX		DmiCounter64X
	ACCESS		read-only
	STATUS		mandatory
	DESCRIPTION	"This is the total number packets received."
	::= {eNetworkAdapter802PortGroup 8}

a4TotalBytesReceived OBJECT-TYPE
	SYNTAX		DmiCounter64X
	ACCESS		read-only
	STATUS		mandatory
	DESCRIPTION	"This is the total number of bytes received."
	::= {eNetworkAdapter802PortGroup 9}

a4TotalTransmitErrors OBJECT-TYPE
	SYNTAX		DmiCounter64X
	ACCESS		read-only
	STATUS		mandatory
	DESCRIPTION	"This is the total number of transmit errors of any type."
	::= {eNetworkAdapter802PortGroup 10}

a4TotalReceiveErrors OBJECT-TYPE
	SYNTAX		DmiCounter64X
	ACCESS		read-only
	STATUS		mandatory
	DESCRIPTION	"This is the total number of receive errors of any type."
	::= {eNetworkAdapter802PortGroup 11}

a4TotalHostErrors OBJECT-TYPE
	SYNTAX		DmiCounter64X
	ACCESS		read-only
	STATUS		mandatory
	DESCRIPTION	"This is the total number of errors due to problems with the
network adapter host interface (e.g. overrun / underrun errors)."
	::= {eNetworkAdapter802PortGroup 12}

a4TotalWireErrors OBJECT-TYPE
	SYNTAX		DmiCounter64X
	ACCESS		read-only
	STATUS		mandatory
	DESCRIPTION	"This is the total number of either receive or transmit errors
 due to problems with the network (e.g. receive CRC Errors). "
	::= {eNetworkAdapter802PortGroup 13}

S802AlternateAddressGroup ::= SEQUENCE {
	a5AlternateAddressIndex                 	DmiInteger,
	a5PortIndex                             	DmiInteger,
	a5AddressType                           	DmiInteger,
	a5AlternateAddress                      	DmiDisplaystring
}

t802AlternateAddressGroup OBJECT-TYPE
	SYNTAX		SEQUENCE OF S802AlternateAddressGroup
	ACCESS		not-accessible
	STATUS		mandatory
	DESCRIPTION	"Contains objects related to alternate addresses for each
network adapter port."
	::= {dmtfGroups 5}

e802AlternateAddressGroup OBJECT-TYPE
	SYNTAX		S802AlternateAddressGroup
	ACCESS		not-accessible
	STATUS		mandatory
	DESCRIPTION	""
	INDEX		{DmiComponentIndex, a5AlternateAddressIndex}
	::= {t802AlternateAddressGroup 1}

a5AlternateAddressIndex OBJECT-TYPE
	SYNTAX		DmiInteger
	ACCESS		not-accessible
	STATUS		mandatory
	DESCRIPTION	"This is an arbitrary number assigned to each alternate address.
 The Alternate Address Index usually starts with 1 and increments for each
alternate address."
	::= {e802AlternateAddressGroup 1}

a5PortIndex OBJECT-TYPE
	SYNTAX		DmiInteger
	ACCESS		not-accessible
	STATUS		mandatory
	DESCRIPTION	"The value of the Port Index attribute for the network port
that uses this alternate address, i.e. the 'port number'."
	::= {e802AlternateAddressGroup 2}

a5AddressType OBJECT-TYPE
	SYNTAX		INTEGER {
		vMulticast                              	(1),
		vFunctional                             	(2),
		vGroup                                  	(3)
	}
	ACCESS		not-accessible
	STATUS		mandatory
	DESCRIPTION	"This is the type of alternate address, e.g. multicast, functiona
, etc."
	::= {e802AlternateAddressGroup 3}

a5AlternateAddress OBJECT-TYPE
	SYNTAX		DmiDisplaystring
	ACCESS		not-accessible
	STATUS		mandatory
	DESCRIPTION	"This is the actual alternate address value."
	::= {e802AlternateAddressGroup 4}

SNetworkAdapterDriverGroup ::= SEQUENCE {
	a6DriverIndex                           	DmiInteger,
	a6DriverSoftwareName                    	DmiDisplaystring,
	a6DriverSoftwareVersion                 	DmiDisplaystring,
	a6DriverSoftwareDescription             	DmiDisplaystring,
	a6DriverSize                            	DmiInteger,
	a6DriverInterfaceType                   	DmiInteger,
	a6DriverInterfaceVersion                	DmiDisplaystring,
	a6DriverInterfaceDescription            	DmiDisplaystring
}

tNetworkAdapterDriverGroup OBJECT-TYPE
	SYNTAX		SEQUENCE OF SNetworkAdapterDriverGroup
	ACCESS		not-accessible
	STATUS		mandatory
	DESCRIPTION	"Contains objects related to the network adapter device drivers
currently in use."
	::= {dmtfGroups 6}

eNetworkAdapterDriverGroup OBJECT-TYPE
	SYNTAX		SNetworkAdapterDriverGroup
	ACCESS		not-accessible
	STATUS		mandatory
	DESCRIPTION	""
	INDEX		{DmiComponentIndex, a6DriverIndex}
	::= {tNetworkAdapterDriverGroup 1}

a6DriverIndex OBJECT-TYPE
	SYNTAX		DmiInteger
	ACCESS		read-only
	STATUS		mandatory
	DESCRIPTION	"This is an arbitrary number assigned to each device driver.
 Driver Index usually starts with 1 and increments for each additional device
driver."
	::= {eNetworkAdapterDriverGroup 1}

a6DriverSoftwareName OBJECT-TYPE
	SYNTAX		DmiDisplaystring
	ACCESS		read-only
	STATUS		mandatory
	DESCRIPTION	"This is the sign-on name of the driver."
	::= {eNetworkAdapterDriverGroup 2}

a6DriverSoftwareVersion OBJECT-TYPE
	SYNTAX		DmiDisplaystring
	ACCESS		read-only
	STATUS		mandatory
	DESCRIPTION	"This is the revision level of the driver software."
	::= {eNetworkAdapterDriverGroup 3}

a6DriverSoftwareDescription OBJECT-TYPE
	SYNTAX		DmiDisplaystring
	ACCESS		read-only
	STATUS		mandatory
	DESCRIPTION	"This is an expanded description of the device driver software."
	::= {eNetworkAdapterDriverGroup 4}

a6DriverSize OBJECT-TYPE
	SYNTAX		DmiInteger
	ACCESS		read-only
	STATUS		mandatory
	DESCRIPTION	"This is the resident memory size of the driver in bytes."
	::= {eNetworkAdapterDriverGroup 5}

a6DriverInterfaceType OBJECT-TYPE
	SYNTAX		INTEGER {
		vOther                                  	(1),
		vIpx                                    	(2),
		vOdi                                    	(3),
		vNdis                                   	(4),
		vPacketDriver                           	(5),
		vLantastic                              	(6),
		vUnix                                   	(7),
		vAppletalk                              	(8),
		vIbmLanSupportProgram                   	(9),
		vLlc                                    	(10),
		vNetbios                                	(11),
		vPathworksDll                           	(12)
	}
	ACCESS		read-only
	STATUS		mandatory
	DESCRIPTION	"This is the specification or network operating system to
which this LAN driver conforms, e.g. IPX, NDIS, etc."
	::= {eNetworkAdapterDriverGroup 6}

a6DriverInterfaceVersion OBJECT-TYPE
	SYNTAX		DmiDisplaystring
	ACCESS		read-only
	STATUS		mandatory
	DESCRIPTION	"This is the version of the driver interface specification,
e.g. for NDIS, this attribute could be 2.01, 3.0, etc."
	::= {eNetworkAdapterDriverGroup 7}

a6DriverInterfaceDescription OBJECT-TYPE
	SYNTAX		DmiDisplaystring
	ACCESS		read-only
	STATUS		mandatory
	DESCRIPTION	"An expanded description of the driver interface specification
in use."
	::= {eNetworkAdapterDriverGroup 8}

SNetworkAdapterHardwareGroup ::= SEQUENCE {
	a7NetworkTopology                       	DmiInteger,
	a7TransmissionCapability                	DmiInteger,
	a7NetworkAdapterRamSize                 	DmiInteger,
	a7BusType                               	DmiInteger,
	a7BusWidth                              	DmiInteger
}

tNetworkAdapterHardwareGroup OBJECT-TYPE
	SYNTAX		SEQUENCE OF SNetworkAdapterHardwareGroup
	ACCESS		not-accessible
	STATUS		mandatory
	DESCRIPTION	"Contains objects related to the network adapter hardware."
	::= {dmtfGroups 7}

eNetworkAdapterHardwareGroup OBJECT-TYPE
	SYNTAX		SNetworkAdapterHardwareGroup
	ACCESS		not-accessible
	STATUS		mandatory
	DESCRIPTION	""
	INDEX		{DmiComponentIndex}
	::= {tNetworkAdapterHardwareGroup 1}

a7NetworkTopology OBJECT-TYPE
	SYNTAX		INTEGER {
		vOther                                  	(1),
		v10MbpsEthernet                         	(2),
		v100MbpsEthernet                        	(3),
		v10010MbpsEthernet                      	(4),
		v100MbpsVgAnylan                        	(5),
		v4MbpsToken-ring                        	(6),
		v16MbpsToken-ring                       	(7),
		v164MbpsToken-ring                      	(8),
		v2MbpsArcnet                            	(9),
		v20MbpsArcnet                           	(10),
		vFddi                                   	(11),
		vAtm                                    	(12),
		vAppletalk1                             	(13)
	}
	ACCESS		read-only
	STATUS		mandatory
	DESCRIPTION	"This is the network media access method/topology supported
by this adapter."
	::= {eNetworkAdapterHardwareGroup 1}

a7TransmissionCapability OBJECT-TYPE
	SYNTAX		INTEGER {
		vNormal                                 	(1),
		vFullDuplex                             	(2)
	}
	ACCESS		read-only
	STATUS		mandatory
	DESCRIPTION	"The transmission capabilities of the adapter."
	::= {eNetworkAdapterHardwareGroup 2}

a7NetworkAdapterRamSize OBJECT-TYPE
	SYNTAX		DmiInteger
	ACCESS		read-only
	STATUS		mandatory
	DESCRIPTION	"This is the total size of adapter RAM in Kb."
	::= {eNetworkAdapterHardwareGroup 3}

a7BusType OBJECT-TYPE
	SYNTAX		INTEGER {
		vOther                                  	(1),
		vIsa                                    	(2),
		vEisa                                   	(3),
		vMca                                    	(4),
		vPci                                    	(5),
		vVl                                     	(6),
		vPcmcia                                 	(7),
		vParallel                               	(8),
		vNec98                                  	(9),
		vMotherboard                            	(256)
	}
	ACCESS		read-only
	STATUS		mandatory
	DESCRIPTION	"This is the type of bus used to interface the adapter to
the host."
	::= {eNetworkAdapterHardwareGroup 4}

a7BusWidth OBJECT-TYPE
	SYNTAX		INTEGER {
		vOther                                  	(1),
		vUnknown                                	(2),
		v8BitCard                               	(3),
		v16BitCard                              	(4),
		v32BitCard                              	(5),
		v64BitCard                              	(6),
		v128BitCard                             	(7)
	}
	ACCESS		read-only
	STATUS		mandatory
	DESCRIPTION	"This is the width (in bits) of the data path used to interface
the adapter to the host."
	::= {eNetworkAdapterHardwareGroup 5}

SOperationalState ::= SEQUENCE {
	a8OperationalStateInstanceIndex         	DmiInteger,
	a8DeviceGroupIndex                      	DmiInteger,
	a8OperationalStatus                     	DmiInteger,
	a8UsageState                            	DmiInteger,
	a8AvailabilityStatus                    	DmiInteger,
	a8AdministrativeState                   	DmiInteger,
	a8FatalErrorCount                       	DmiCounter,
	a8MajorErrorCount                       	DmiCounter,
	a8WarningErrorCount                     	DmiCounter
}

tOperationalState OBJECT-TYPE
	SYNTAX		SEQUENCE OF SOperationalState
	ACCESS		not-accessible
	STATUS		mandatory
	DESCRIPTION	"This group provides the operational state, usage,  availability
status, and administrative state indicators for specific Device Group instances."
	::= {dmtfGroups 8}

eOperationalState OBJECT-TYPE
	SYNTAX		SOperationalState
	ACCESS		not-accessible
	STATUS		mandatory
	DESCRIPTION	""
	INDEX		{DmiComponentIndex, a8OperationalStateInstanceIndex}
	::= {tOperationalState 1}

a8OperationalStateInstanceIndex OBJECT-TYPE
	SYNTAX		DmiInteger
	ACCESS		read-only
	STATUS		mandatory
	DESCRIPTION	"The Index into the Operational State table."
	::= {eOperationalState 1}

a8DeviceGroupIndex OBJECT-TYPE
	SYNTAX		DmiInteger
	ACCESS		read-only
	STATUS		mandatory
	DESCRIPTION	"The group ID of the group referencing this instance."
	::= {eOperationalState 2}

a8OperationalStatus OBJECT-TYPE
	SYNTAX		INTEGER {
		vOther                                  	(1),
		vUnknown                                	(2),
		vEnabled                                	(3),
		vDisabled                               	(4),
		vNotApplicable                          	(5)
	}
	ACCESS		read-only
	STATUS		mandatory
	DESCRIPTION	"The operational status of the Device group instance."
	::= {eOperationalState 3}

a8UsageState OBJECT-TYPE
	SYNTAX		INTEGER {
		vOther                                  	(1),
		vUnknown                                	(2),
		vIdle                                   	(3),
		vActive                                 	(4),
		vBusy                                   	(5),
		vNotApplicable                          	(6)
	}
	ACCESS		read-only
	STATUS		mandatory
	DESCRIPTION	"The usage state of the Device Group instance."
	::= {eOperationalState 4}

a8AvailabilityStatus OBJECT-TYPE
	SYNTAX		INTEGER {
		vOther                                  	(1),
		vUnknown                                	(2),
		vRunning                                	(3),
		vWarning                                	(4),
		vInTest                                 	(5),
		vNotApplicable                          	(6),
		vPowerOff                               	(7),
		vOffLine                                	(8),
		vOffDuty                                	(9),
		vDegraded                               	(10),
		vNotInstalled                           	(11),
		vInstallError                           	(12),
		vPowerSave                              	(13)
	}
	ACCESS		read-only
	STATUS		mandatory
	DESCRIPTION	"The availability status of the Device Group instance."
	::= {eOperationalState 5}

a8AdministrativeState OBJECT-TYPE
	SYNTAX		INTEGER {
		vOther                                  	(1),
		vUnknown                                	(2),
		vLocked                                 	(3),
		vUnlocked                               	(4),
		vNotApplicable                          	(5),
		vShuttingDown                           	(6)
	}
	ACCESS		read-only
	STATUS		mandatory
	DESCRIPTION	"The administrative state of the Device Group instance."
	::= {eOperationalState 6}

a8FatalErrorCount OBJECT-TYPE
	SYNTAX		DmiCounter
	ACCESS		read-only
	STATUS		mandatory
	DESCRIPTION	"The accumulated fatal error count for this Device Group Instance
"
	::= {eOperationalState 7}

a8MajorErrorCount OBJECT-TYPE
	SYNTAX		DmiCounter
	ACCESS		read-only
	STATUS		mandatory
	DESCRIPTION	"The accumulated major error count for this Device Group Instance
"
	::= {eOperationalState 8}

a8WarningErrorCount OBJECT-TYPE
	SYNTAX		DmiCounter
	ACCESS		read-only
	STATUS		mandatory
	DESCRIPTION	"The accumulated warning error count for this Device Group
Instance."
	::= {eOperationalState 9}

SFruTable ::= SEQUENCE {
	a9FruIndex                              	DmiInteger,
	a9DeviceGroupIndex                      	DmiInteger,
	a9Description                           	DmiDisplaystring,
	a9Manufacturer                          	DmiDisplaystring,
	a9Model                                 	DmiDisplaystring,
	a9PartNumber                            	DmiDisplaystring,
	a9FruSerialNumber                       	DmiDisplaystring,
	a9RevisionLevel                         	DmiDisplaystring,
	a9WarrantyStartDate                     	DmiDateX,
	a9WarrantyDuration                      	DmiInteger,
	a9SupportPhoneNumber                    	DmiDisplaystring
}

tFruTable OBJECT-TYPE
	SYNTAX		SEQUENCE OF SFruTable
	ACCESS		not-accessible
	STATUS		mandatory
	DESCRIPTION	"A Field Replaceable Unit (FRU), is defined as a hardware
component which is designed to be separately removable"
	::= {dmtfGroups 9}

eFruTable OBJECT-TYPE
	SYNTAX		SFruTable
	ACCESS		not-accessible
	STATUS		mandatory
	DESCRIPTION	""
	INDEX		{DmiComponentIndex, a9FruIndex}
	::= {tFruTable 1}

a9FruIndex OBJECT-TYPE
	SYNTAX		DmiInteger
	ACCESS		read-only
	STATUS		mandatory
	DESCRIPTION	"The index into the Field Replaceable Unit table."
	::= {eFruTable 1}

a9DeviceGroupIndex OBJECT-TYPE
	SYNTAX		DmiInteger
	ACCESS		read-only
	STATUS		mandatory
	DESCRIPTION	"The group ID of the group referencing this Field Replaceable
Unit instance."
	::= {eFruTable 2}

a9Description OBJECT-TYPE
	SYNTAX		DmiDisplaystring
	ACCESS		read-only
	STATUS		mandatory
	DESCRIPTION	"A clear description of this Field Replaceable Unit."
	::= {eFruTable 3}

a9Manufacturer OBJECT-TYPE
	SYNTAX		DmiDisplaystring
	ACCESS		read-only
	STATUS		mandatory
	DESCRIPTION	"The name of the company manufacturing or providing this Field
Replaceable Unit."
	::= {eFruTable 4}

a9Model OBJECT-TYPE
	SYNTAX		DmiDisplaystring
	ACCESS		read-only
	STATUS		mandatory
	DESCRIPTION	"The manufacturer's model number for this Field Replaceable
Unit."
	::= {eFruTable 5}

a9PartNumber OBJECT-TYPE
	SYNTAX		DmiDisplaystring
	ACCESS		not-accessible
	STATUS		mandatory
	DESCRIPTION	"A part number by which a replacement part can be ordered
for this Field Replaceable Unit."
	::= {eFruTable 6}

a9FruSerialNumber OBJECT-TYPE
	SYNTAX		DmiDisplaystring
	ACCESS		not-accessible
	STATUS		mandatory
	DESCRIPTION	"The manufacturer's serial number for this Field Replaceable
Unit."
	::= {eFruTable 7}

a9RevisionLevel OBJECT-TYPE
	SYNTAX		DmiDisplaystring
	ACCESS		not-accessible
	STATUS		mandatory
	DESCRIPTION	"The revision level of this Field Replaceable Unit."
	::= {eFruTable 8}

a9WarrantyStartDate OBJECT-TYPE
	SYNTAX		DmiDateX
	ACCESS		read-only
	STATUS		mandatory
	DESCRIPTION	"The start date of the service Warranty for this Field Replaceabl
 Unit."
	::= {eFruTable 9}

a9WarrantyDuration OBJECT-TYPE
	SYNTAX		DmiInteger
	ACCESS		read-only
	STATUS		mandatory
	DESCRIPTION	"The total duration of this Field Replaceable Unit Warranty
in months. (9999 = Lifetime)."
	::= {eFruTable 10}

a9SupportPhoneNumber OBJECT-TYPE
	SYNTAX		DmiDisplaystring
	ACCESS		read-only
	STATUS		mandatory
	DESCRIPTION	"The phone number(s) for support for this Field Replaceable
Unit."
	::= {eFruTable 11}

SBootRomConfiguration ::= SEQUENCE {
	a10BootRomDescription                   	DmiDisplaystring,
	a10BootRomVersion                       	DmiDisplaystring,
	a10RemoteBootProtocolType               	DmiInteger,
	a10RemoteBootProtocolVersion            	DmiDisplaystring
}

tBootRomConfiguration OBJECT-TYPE
	SYNTAX		SEQUENCE OF SBootRomConfiguration
	ACCESS		not-accessible
	STATUS		mandatory
	DESCRIPTION	"This group describes the characteristics of the boot ROM."
	::= {dmtfGroups 10}

eBootRomConfiguration OBJECT-TYPE
	SYNTAX		SBootRomConfiguration
	ACCESS		not-accessible
	STATUS		mandatory
	DESCRIPTION	""
	INDEX		{DmiComponentIndex}
	::= {tBootRomConfiguration 1}

a10BootRomDescription OBJECT-TYPE
	SYNTAX		DmiDisplaystring
	ACCESS		read-only
	STATUS		mandatory
	DESCRIPTION	"This is the description of the software contained in the
boot ROM."
	::= {eBootRomConfiguration 1}

a10BootRomVersion OBJECT-TYPE
	SYNTAX		DmiDisplaystring
	ACCESS		read-only
	STATUS		mandatory
	DESCRIPTION	"This is the version number of the boot ROM software."
	::= {eBootRomConfiguration 2}

a10RemoteBootProtocolType OBJECT-TYPE
	SYNTAX		INTEGER {
		vOther                                  	(1),
		vNone                                   	(2),
		vRpl                                    	(3),
		vBootp                                  	(4),
		vDecMop                                 	(5),
		vNativeNetware                          	(6)
	}
	ACCESS		read-only
	STATUS		mandatory
	DESCRIPTION	"This is the type of remote boot protocol supported by this
ROM."
	::= {eBootRomConfiguration 3}

a10RemoteBootProtocolVersion OBJECT-TYPE
	SYNTAX		DmiDisplaystring
	ACCESS		read-only
	STATUS		mandatory
	DESCRIPTION	"The version of the remote boot protocol supported by this
ROM."
	::= {eBootRomConfiguration 4}

SBootRomCapabilities ::= SEQUENCE {
	a11CapabilityIndex                      	DmiInteger,
	a11CapabilityDescription                	DmiDisplaystring,
	a11CapabilityStatus                     	DmiDisplaystring
}

tBootRomCapabilities OBJECT-TYPE
	SYNTAX		SEQUENCE OF SBootRomCapabilities
	ACCESS		not-accessible
	STATUS		mandatory
	DESCRIPTION	"This group describes the capabilities or special features
supported by this ROM."
	::= {dmtfGroups 11}

eBootRomCapabilities OBJECT-TYPE
	SYNTAX		SBootRomCapabilities
	ACCESS		not-accessible
	STATUS		mandatory
	DESCRIPTION	""
	INDEX		{DmiComponentIndex, a11CapabilityIndex}
	::= {tBootRomCapabilities 1}

a11CapabilityIndex OBJECT-TYPE
	SYNTAX		DmiInteger
	ACCESS		read-only
	STATUS		mandatory
	DESCRIPTION	"This is an arbitrary number assigned to each capability.Capabili
y Index usually starts with 1 and increments for each additional capability."
	::= {eBootRomCapabilities 1}

a11CapabilityDescription OBJECT-TYPE
	SYNTAX		DmiDisplaystring
	ACCESS		read-only
	STATUS		mandatory
	DESCRIPTION	"This is a clear description of a property or special feature
of the ROM, e.g. 'virus protection'."
	::= {eBootRomCapabilities 2}

a11CapabilityStatus OBJECT-TYPE
	SYNTAX		DmiDisplaystring
	ACCESS		read-only
	STATUS		mandatory
	DESCRIPTION	"The current state or value associated with the capability
or special feature, e.g. 'enabled', 'active', etc."
	::= {eBootRomCapabilities 3}

SIntellanadapterextensionsgroup ::= SEQUENCE {
	a12DriverFilename                       	DmiDisplaystring,
	a12DriverDate                           	DmiDateX,
	a12MifAndInstrumentationFilename        	DmiDisplaystring,
	a12InstrumentationVersion               	DmiDisplaystring,
	a12MifVersion                           	DmiDisplaystring
}

tIntellanadapterextensionsgroup OBJECT-TYPE
	SYNTAX		SEQUENCE OF SIntellanadapterextensionsgroup
	ACCESS		not-accessible
	STATUS		mandatory
	DESCRIPTION	"These attributes provide extended information for use with
Intel software."
	::= {dmtfGroups 12}

eIntellanadapterextensionsgroup OBJECT-TYPE
	SYNTAX		SIntellanadapterextensionsgroup
	ACCESS		not-accessible
	STATUS		mandatory
	DESCRIPTION	""
	INDEX		{DmiComponentIndex}
	::= {tIntellanadapterextensionsgroup 1}

a12DriverFilename OBJECT-TYPE
	SYNTAX		DmiDisplaystring
	ACCESS		read-only
	STATUS		mandatory
	DESCRIPTION	"The filename of the LAN adapter driver."
	::= {eIntellanadapterextensionsgroup 1}

a12DriverDate OBJECT-TYPE
	SYNTAX		DmiDateX
	ACCESS		read-only
	STATUS		mandatory
	DESCRIPTION	"The timestamp of the LAN adapter driver."
	::= {eIntellanadapterextensionsgroup 2}

a12MifAndInstrumentationFilename OBJECT-TYPE
	SYNTAX		DmiDisplaystring
	ACCESS		read-only
	STATUS		mandatory
	DESCRIPTION	""
	::= {eIntellanadapterextensionsgroup 3}

a12InstrumentationVersion OBJECT-TYPE
	SYNTAX		DmiDisplaystring
	ACCESS		read-only
	STATUS		mandatory
	DESCRIPTION	"The version number of component instrumentation."
	::= {eIntellanadapterextensionsgroup 4}

a12MifVersion OBJECT-TYPE
	SYNTAX		DmiDisplaystring
	ACCESS		read-only
	STATUS		mandatory
	DESCRIPTION	"This is the version of the MIF file"
	::= {eIntellanadapterextensionsgroup 5}

SIndication_control_group ::= SEQUENCE {
	a151PortIndex                           	DmiInteger,
	a151IndicationEnable                    	DmiInteger,
	a151TotalTransmitIndicationEnable       	DmiInteger,
	a151TotalTransmitErrorsThreshold        	DmiCounter64X,
	a151TotalReceiveIndicationEnable        	DmiInteger,
	a151TotalReceiveErrorsThreshold         	DmiCounter64X,
	a151TotalHostIndicationEnable           	DmiInteger,
	a151TotalHostErrorsThreshold            	DmiCounter64X,
	a151TotalWireIndicationEnable           	DmiInteger,
	a151TotalWireErrorsThreshold            	DmiCounter64X
}

tIndication_control_group OBJECT-TYPE
	SYNTAX		SEQUENCE OF SIndication_control_group
	ACCESS		not-accessible
	STATUS		mandatory
	DESCRIPTION	"This group defines the indication control settings
for the
LAN instrumentation"
	::= {dmtfGroups 151}

eIndication_control_group OBJECT-TYPE
	SYNTAX		SIndication_control_group
	ACCESS		not-accessible
	STATUS		mandatory
	DESCRIPTION	""
	INDEX		{DmiComponentIndex, a151PortIndex}
	::= {tIndication_control_group 1}

a151PortIndex OBJECT-TYPE
	SYNTAX		DmiInteger
	ACCESS		read-only
	STATUS		mandatory
	DESCRIPTION	"This attribute is the ordinal of the network port within
the network adapter, i.e. the 'port number'."
	::= {eIndication_control_group 1}

a151IndicationEnable OBJECT-TYPE
	SYNTAX		INTEGER {
		vOff                                    	(0),
		vOn                                     	(1)
	}
	ACCESS		read-write
	STATUS		mandatory
	DESCRIPTION	"Used to control indications"
	::= {eIndication_control_group 2}

a151TotalTransmitIndicationEnable OBJECT-TYPE
	SYNTAX		INTEGER {
		vOff                                    	(0),
		vOn                                     	(1)
	}
	ACCESS		read-write
	STATUS		mandatory
	DESCRIPTION	"Used to control indications"
	::= {eIndication_control_group 3}

a151TotalTransmitErrorsThreshold OBJECT-TYPE
	SYNTAX		DmiCounter64X
	ACCESS		read-write
	STATUS		mandatory
	DESCRIPTION	"This is a threshold value used to trigger indications
when
the total number of transfer errors exceed this value"
	::= {eIndication_control_group 4}

a151TotalReceiveIndicationEnable OBJECT-TYPE
	SYNTAX		INTEGER {
		vOff                                    	(0),
		vOn                                     	(1)
	}
	ACCESS		read-write
	STATUS		mandatory
	DESCRIPTION	"Used to control indications"
	::= {eIndication_control_group 5}

a151TotalReceiveErrorsThreshold OBJECT-TYPE
	SYNTAX		DmiCounter64X
	ACCESS		read-write
	STATUS		mandatory
	DESCRIPTION	"This is a threshold value used to trigger indications
when
the total number of receive errors exceed this value"
	::= {eIndication_control_group 6}

a151TotalHostIndicationEnable OBJECT-TYPE
	SYNTAX		INTEGER {
		vOff                                    	(0),
		vOn                                     	(1)
	}
	ACCESS		read-write
	STATUS		mandatory
	DESCRIPTION	"Used to control indications"
	::= {eIndication_control_group 7}

a151TotalHostErrorsThreshold OBJECT-TYPE
	SYNTAX		DmiCounter64X
	ACCESS		read-write
	STATUS		mandatory
	DESCRIPTION	"This is a threshold value used to trigger indications
when
the total number of host errors exceed this value"
	::= {eIndication_control_group 8}

a151TotalWireIndicationEnable OBJECT-TYPE
	SYNTAX		INTEGER {
		vOff                                    	(0),
		vOn                                     	(1)
	}
	ACCESS		read-write
	STATUS		mandatory
	DESCRIPTION	"Used to control indications"
	::= {eIndication_control_group 9}

a151TotalWireErrorsThreshold OBJECT-TYPE
	SYNTAX		DmiCounter64X
	ACCESS		read-write
	STATUS		mandatory
	DESCRIPTION	"This is a threshold value used to trigger indications
when
the total number of wire errors exceed this value"
	::= {eIndication_control_group 10}

SErrorcontrol ::= SEQUENCE {
	a152Selfid                              	DmiInteger,
	a152Fatalcount                          	DmiCounter,
	a152Majorcount                          	DmiCounter,
	a152Warningcount                        	DmiCounter,
	a152Errstatus                           	DmiInteger,
	a152Errstatustype                       	DmiInteger
}

tErrorcontrol OBJECT-TYPE
	SYNTAX		SEQUENCE OF SErrorcontrol
	ACCESS		not-accessible
	STATUS		mandatory
	DESCRIPTION	"Indication control and status for the parent group"
	::= {dmtfGroups 152}

eErrorcontrol OBJECT-TYPE
	SYNTAX		SErrorcontrol
	ACCESS		not-accessible
	STATUS		mandatory
	DESCRIPTION	""
	INDEX		{DmiComponentIndex, a152Selfid}
	::= {tErrorcontrol 1}

a152Selfid OBJECT-TYPE
	SYNTAX		DmiInteger
	ACCESS		read-only
	STATUS		mandatory
	DESCRIPTION	"Instance identifer. A unique number that identifies this
row."
	::= {eErrorcontrol 1}

a152Fatalcount OBJECT-TYPE
	SYNTAX		DmiCounter
	ACCESS		read-only
	STATUS		mandatory
	DESCRIPTION	"Count of all fatal errors since system startup."
	::= {eErrorcontrol 2}

a152Majorcount OBJECT-TYPE
	SYNTAX		DmiCounter
	ACCESS		read-only
	STATUS		mandatory
	DESCRIPTION	"Count of all major errors since system startup."
	::= {eErrorcontrol 3}

a152Warningcount OBJECT-TYPE
	SYNTAX		DmiCounter
	ACCESS		read-only
	STATUS		mandatory
	DESCRIPTION	"Count of all warning errors since system startup."
	::= {eErrorcontrol 4}

a152Errstatus OBJECT-TYPE
	SYNTAX		INTEGER {
		vOk                                     	(0),
		vWarning1                               	(1),
		vMajor                                  	(2),
		vFatal                                  	(3),
		vUnknown                                	(4)
	}
	ACCESS		read-only
	STATUS		mandatory
	DESCRIPTION	"current error status"
	::= {eErrorcontrol 5}

a152Errstatustype OBJECT-TYPE
	SYNTAX		INTEGER {
		vPost                                   	(0),
		vRuntime                                	(1),
		vDiagnosticTest                         	(2)
	}
	ACCESS		read-only
	STATUS		mandatory
	DESCRIPTION	"Indicates the type of detection that set the current error
status."
	::= {eErrorcontrol 6}

SMiftomib ::= SEQUENCE {
	a153MibName                             	DmiDisplaystring,
	a153MibOid                              	DmiDisplaystring,
	a153DisableTrap                         	DmiInteger
}

tMiftomib OBJECT-TYPE
	SYNTAX		SEQUENCE OF SMiftomib
	ACCESS		not-accessible
	STATUS		mandatory
	DESCRIPTION	"This group defines attributes required for DMI
to SNMP translati
n"
	::= {dmtfGroups 153}

eMiftomib OBJECT-TYPE
	SYNTAX		SMiftomib
	ACCESS		not-accessible
	STATUS		mandatory
	DESCRIPTION	""
	INDEX		{DmiComponentIndex}
	::= {tMiftomib 1}

a153MibName OBJECT-TYPE
	SYNTAX		DmiDisplaystring
	ACCESS		read-only
	STATUS		mandatory
	DESCRIPTION	"The MIB name that defines this MIF"
	::= {eMiftomib 1}

a153MibOid OBJECT-TYPE
	SYNTAX		DmiDisplaystring
	ACCESS		read-only
	STATUS		mandatory
	DESCRIPTION	"The MIB OID that corresponds to this MIF"
	::= {eMiftomib 2}

a153DisableTrap OBJECT-TYPE
	SYNTAX		DmiInteger
	ACCESS		read-write
	STATUS		mandatory
	DESCRIPTION	"Used to dissable the SNMP trap"
	::= {eMiftomib 3}


-- Here is the TRAP definition for the MIB
-- Append this to the MIB produced by MIFTOMIB
-- DO NOT CHANGE ANYTHING in this definition, SNMP-DMI translator only
--         handles this specific format of the TRAP
-- changing this format WILL cause trnaslator to fail

tTrapGroup OBJECT-TYPE
    SYNTAX        SEQUENCE OF STrapGroup
    ACCESS        not-accessible
    STATUS        mandatory
    DESCRIPTION    "This group defines attributes needed for Trap
            definition. This group does not exist in MIF file"
    ::= {dmtfGroups 9999}

STrapGroup ::= SEQUENCE {
    a9999ErrorTime              DisplayString,
    a9999ErrorStatus            DmiInteger,
    a9999ErrorGroupId           DmiInteger,
    a9999ErrorInstanceId        DmiInteger,
    a9999ComponentId            DmiInteger,
    a9999GroupId                DmiInteger,
    a9999InstanceId             DmiInteger,
    a9999VendorCode1            DmiInteger,
    a9999VendorCode2            DmiInteger,
    a9999VendorText             OCTET STRING,
    a9999ParentGroupId          DmiInteger,
    a9999ParentInstanceId       DmiInteger
}

eTrapGroup OBJECT-TYPE
    SYNTAX        STrapGroup
    ACCESS        not-accessible
    STATUS        mandatory
    DESCRIPTION    ""
    INDEX        {DmiComponentIndex}
    ::= {tTrapGroup 1}

a9999ErrorTime OBJECT-TYPE
    SYNTAX        DisplayString
    ACCESS        read-only
    STATUS        mandatory
    DESCRIPTION    "The Date & Time when the error occured"
    ::= {eTrapGroup 1}

a9999ErrorStatus OBJECT-TYPE
    SYNTAX        DmiInteger
    ACCESS        read-only
    STATUS        mandatory
    DESCRIPTION    "Error Status Code"
    ::= {eTrapGroup 2}

a9999ErrorGroupId OBJECT-TYPE
    SYNTAX        DmiInteger
    ACCESS        read-only
    STATUS        mandatory
    DESCRIPTION    "Group ID of the errorControl Group"
    ::= {eTrapGroup 3}

a9999ErrorInstanceId OBJECT-TYPE
    SYNTAX        DmiInteger
    ACCESS        read-only
    STATUS        mandatory
    DESCRIPTION    "Instance ID of the errorControl Group"
    ::= {eTrapGroup 4}

a9999ComponentId OBJECT-TYPE
    SYNTAX        DmiInteger
    ACCESS        read-only
    STATUS        mandatory
    DESCRIPTION    "Component ID of the component that caused this error"
    ::= {eTrapGroup 5}

a9999GroupId OBJECT-TYPE
    SYNTAX        DmiInteger
    ACCESS        read-only
    STATUS        mandatory
    DESCRIPTION    "Group ID of the Group that caused this error"
    ::= {eTrapGroup 6}

a9999InstanceId OBJECT-TYPE
    SYNTAX        DmiInteger
    ACCESS        read-only
    STATUS        mandatory
    DESCRIPTION    "Instance ID of the Group that caused this error"
    ::= {eTrapGroup 7}

a9999VendorCode1 OBJECT-TYPE
    SYNTAX        DmiInteger
    ACCESS        read-only
    STATUS        mandatory
    DESCRIPTION    "Vendor specific code 1"
    ::= {eTrapGroup 8}

a9999VendorCode2 OBJECT-TYPE
    SYNTAX        DmiInteger
    ACCESS        read-only
    STATUS        mandatory
    DESCRIPTION    "Vendor specific code 2"
    ::= {eTrapGroup 9}

a9999VendorText OBJECT-TYPE
    SYNTAX        OCTET STRING
    ACCESS        read-only
    STATUS        mandatory
    DESCRIPTION    "Vendor specific octet string info"
    ::= {eTrapGroup 10}

a9999ParentGroupId OBJECT-TYPE
    SYNTAX        DmiInteger
    ACCESS        read-only
    STATUS        mandatory
    DESCRIPTION    "Group ID of parent of Group that caused this error"
    ::= {eTrapGroup 11}

a9999ParentInstanceId OBJECT-TYPE
    SYNTAX        DmiInteger
    ACCESS        read-only
    STATUS        mandatory
    DESCRIPTION    "Instance ID of parent of Group that caused this error"
    ::= {eTrapGroup 12}

e100bEventError TRAP-TYPE
    ENTERPRISE eTrapGroup
    VARIABLES  { a9999ErrorTime,
                 a9999ErrorStatus,
                 a9999ErrorGroupId,
                 a9999ErrorInstanceId,
                 a9999ComponentId,
                 a9999GroupId,
                 a9999InstanceId,
                 a9999VendorCode1,
                 a9999VendorCode2,
                 a9999VendorText,
                 a9999ParentGroupId,
                 a9999ParentInstanceId}

    DESCRIPTION "DMI Service Layer generated event for E100B Adapter"

    --NMS trap annotation

    --#TYPE       "DMI NIC E100B Error Event"
    --#SUMMARY    "Event Data: (%s,%d,%d,%d) (%d,%d,%d,%d,%d) (%d,%d)"
    --#ARGUMENTS  {0, 1, 2, 3, 4, 5, 6, 7, 8, 10, 11}
    --#SEVERITY   CRITICAL
    --#TIMEINDEX  12
    --#STATE      DEGRADED
    ::= 1
END
