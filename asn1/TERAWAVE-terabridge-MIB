TERAWAVE-terabridge-MIB DEFINITIONS ::= BEGIN
        -- Created by sml2mib compiler 
        IMPORTS

	Counter32 FROM SNMPv2-SMI
	MacAddress FROM SNMPv2-TC
 enterprises,  OBJECT-TYPE,  Counter,  Gauge,  TimeTicks
        FROM RFC1155-SMI;

terawave OBJECT IDENTIFIER ::=  { enterprises 4513 }

tera1dBridge OBJECT IDENTIFIER ::=  { terawave 3 }

     -- teraDot1dStpTable

teraDot1dStpTable OBJECT-TYPE
     SYNTAX SEQUENCE OF TeraDot1dStpTableEntryType
     ACCESS not-accessible
     STATUS mandatory
     DESCRIPTION
          " table teraDot1dStpTable"
     ::= { tera1dBridge 1 }

teraDot1dStpTableEntry OBJECT-TYPE
          SYNTAX TeraDot1dStpTableEntryType
          ACCESS not-accessible
          STATUS mandatory
          DESCRIPTION
               " table entry teraDot1dStpTableEntry "
          INDEX {                   teraStpId }
     ::= { teraDot1dStpTable 1 }

TeraDot1dStpTableEntryType ::= SEQUENCE {
          teraStpId   
             INTEGER (1..10),
          teraDot1dStpProtocolSpecification   
             INTEGER,
          teraDot1dStpPriority   
             INTEGER (0..65535),
          teraDot1dStpTimeSinceTopologyChange   
             TimeTicks,
          teraDot1dStpTopChanges   
             Counter32,
          teraDot1dStpDesignatedRoot   
             OCTET STRING,
          teraDot1dStpRootCost   
             INTEGER,
          teraDot1dStpRootPort   
             INTEGER,
          teraDot1dStpMaxAge   
             TimeTicks,
          teraDot1dStpHelloTime   
             TimeTicks,
          teraDot1dStpHoldTime   
             TimeTicks,
          teraDot1dStpForwardDelay   
             TimeTicks,
          teraDot1dStpBridgeMaxAge   
             TimeTicks (600..4000),
          teraDot1dStpBridgeHelloTime   
             TimeTicks (100..1000),
          teraDot1dStpBridgeForwardDelay   
             TimeTicks (400..3000),
          teraDot1dStpBridgeGroupList   
             OCTET STRING,
          teraDot1dStpState   
             INTEGER
}

teraStpId OBJECT-TYPE
          SYNTAX INTEGER (1..10)
          ACCESS read-only
          STATUS mandatory
          DESCRIPTION
               ""
          ::= { teraDot1dStpTableEntry 1 }

teraDot1dStpProtocolSpecification OBJECT-TYPE
          SYNTAX INTEGER
                  {
                  unknown(1),
                  decLb100(2),
                  ieee8021d(3)
                  }
          ACCESS read-only
          STATUS mandatory
          DESCRIPTION
               ""
          ::= { teraDot1dStpTableEntry 2 }

teraDot1dStpPriority OBJECT-TYPE
          SYNTAX INTEGER (0..65535)
          ACCESS read-write
          STATUS mandatory
          DESCRIPTION
               ""
          ::= { teraDot1dStpTableEntry 3 }

teraDot1dStpTimeSinceTopologyChange OBJECT-TYPE
          SYNTAX TimeTicks
          ACCESS read-only
          STATUS mandatory
          DESCRIPTION
               ""
          ::= { teraDot1dStpTableEntry 4 }

teraDot1dStpTopChanges OBJECT-TYPE
          SYNTAX Counter32
          ACCESS read-only
          STATUS mandatory
          DESCRIPTION
               ""
          ::= { teraDot1dStpTableEntry 5 }

teraDot1dStpDesignatedRoot OBJECT-TYPE
          SYNTAX OCTET STRING
          ACCESS read-only
          STATUS mandatory
          DESCRIPTION
               ""
          ::= { teraDot1dStpTableEntry 6 }

teraDot1dStpRootCost OBJECT-TYPE
          SYNTAX INTEGER
          ACCESS read-only
          STATUS mandatory
          DESCRIPTION
               ""
          ::= { teraDot1dStpTableEntry 7 }

teraDot1dStpRootPort OBJECT-TYPE
          SYNTAX INTEGER
          ACCESS read-only
          STATUS mandatory
          DESCRIPTION
               ""
          ::= { teraDot1dStpTableEntry 8 }

teraDot1dStpMaxAge OBJECT-TYPE
          SYNTAX TimeTicks
          ACCESS read-only
          STATUS mandatory
          DESCRIPTION
               ""
          ::= { teraDot1dStpTableEntry 9 }

teraDot1dStpHelloTime OBJECT-TYPE
          SYNTAX TimeTicks
          ACCESS read-only
          STATUS mandatory
          DESCRIPTION
               ""
          ::= { teraDot1dStpTableEntry 10 }

teraDot1dStpHoldTime OBJECT-TYPE
          SYNTAX TimeTicks
          ACCESS read-only
          STATUS mandatory
          DESCRIPTION
               ""
          ::= { teraDot1dStpTableEntry 11 }

teraDot1dStpForwardDelay OBJECT-TYPE
          SYNTAX TimeTicks
          ACCESS read-only
          STATUS mandatory
          DESCRIPTION
               ""
          ::= { teraDot1dStpTableEntry 12 }

teraDot1dStpBridgeMaxAge OBJECT-TYPE
          SYNTAX TimeTicks (600..4000)
          ACCESS read-write
          STATUS mandatory
          DESCRIPTION
               ""
          ::= { teraDot1dStpTableEntry 13 }

teraDot1dStpBridgeHelloTime OBJECT-TYPE
          SYNTAX TimeTicks (100..1000)
          ACCESS read-write
          STATUS mandatory
          DESCRIPTION
               ""
          ::= { teraDot1dStpTableEntry 14 }

teraDot1dStpBridgeForwardDelay OBJECT-TYPE
          SYNTAX TimeTicks (400..3000)
          ACCESS read-write
          STATUS mandatory
          DESCRIPTION
               ""
          ::= { teraDot1dStpTableEntry 15 }

teraDot1dStpBridgeGroupList OBJECT-TYPE
          SYNTAX OCTET STRING
          ACCESS read-write
          STATUS mandatory
          DESCRIPTION
               ""
          ::= { teraDot1dStpTableEntry 16 }

teraDot1dStpState OBJECT-TYPE
          SYNTAX INTEGER
                  {
                  ok(1),
                  delete(2),
                  unknown(3)
                  }
          ACCESS read-write
          STATUS mandatory
          DESCRIPTION
               ""
          ::= { teraDot1dStpTableEntry 17 }

     -- teraBridgePVCPortTable

teraBridgePVCPortTable OBJECT-TYPE
     SYNTAX SEQUENCE OF TeraBridgePVCPortTableEntryType
     ACCESS not-accessible
     STATUS mandatory
     DESCRIPTION
          " table teraBridgePVCPortTable"
     ::= { tera1dBridge 3 }

teraBridgePVCPortTableEntry OBJECT-TYPE
          SYNTAX TeraBridgePVCPortTableEntryType
          ACCESS not-accessible
          STATUS mandatory
          DESCRIPTION
               " table entry teraBridgePVCPortTableEntry "
          INDEX {                   dot1dBasePort }
     ::= { teraBridgePVCPortTable 1 }

TeraBridgePVCPortTableEntryType ::= SEQUENCE {
          teraBridgeEncapsulation   
             INTEGER,
          teraBridgePriority   
             INTEGER (0..7),
          teraPVCPortLocalHostFilter   
             INTEGER,
          teraPVCPortTrunkFrameType   
             INTEGER,
          teraPVCPortTrunkTagSwap   
             INTEGER
}

teraBridgeEncapsulation OBJECT-TYPE
          SYNTAX INTEGER
                  {
                  raw(1),
                  llcBrNoFCS(2),
                  vcMuxBrNoFCS(3),
                  other(4)
                  }
          ACCESS read-write
          STATUS mandatory
          DESCRIPTION
               ""
          ::= { teraBridgePVCPortTableEntry 1 }

teraBridgePriority OBJECT-TYPE
          SYNTAX INTEGER (0..7)
          ACCESS read-write
          STATUS mandatory
          DESCRIPTION
               ""
          ::= { teraBridgePVCPortTableEntry 2 }

teraPVCPortLocalHostFilter OBJECT-TYPE
          SYNTAX INTEGER
                  {
                  true(1),
                  false(2)
                  }
          ACCESS read-write
          STATUS mandatory
          DESCRIPTION
               ""
          ::= { teraBridgePVCPortTableEntry 3 }

teraPVCPortTrunkFrameType OBJECT-TYPE
          SYNTAX INTEGER
                  {
                  sendOnlyUntagged(1),
                  sendOnlyVlanTagged(2),
                  sendAll(3)
                  }
          ACCESS read-write
          STATUS mandatory
          DESCRIPTION
               ""
          ::= { teraBridgePVCPortTableEntry 4 }

teraPVCPortTrunkTagSwap OBJECT-TYPE
          SYNTAX INTEGER
                  {
                  true(1),
                  false(2)
                  }
          ACCESS read-write
          STATUS mandatory
          DESCRIPTION
               ""
          ::= { teraBridgePVCPortTableEntry 5 }

     -- teraDot1dTpPortTable

teraDot1dTpPortTable OBJECT-TYPE
     SYNTAX SEQUENCE OF TeraDot1dTpPortTableEntryType
     ACCESS not-accessible
     STATUS mandatory
     DESCRIPTION
          " table teraDot1dTpPortTable"
     ::= { tera1dBridge 4 }

teraDot1dTpPortTableEntry OBJECT-TYPE
          SYNTAX TeraDot1dTpPortTableEntryType
          ACCESS not-accessible
          STATUS mandatory
          DESCRIPTION
               " table entry teraDot1dTpPortTableEntry "
          INDEX {                   teraDot1dTpPort }
     ::= { teraDot1dTpPortTable 1 }

TeraDot1dTpPortTableEntryType ::= SEQUENCE {
          teraDot1dTpPort   
             INTEGER (1..65535),
          teraDot1dFFType   
             INTEGER,
          teraDot1dLoopback   
             INTEGER,
          teraDot1dTpUseDefaultFwd   
             INTEGER,
          teraDot1dTpDefaultFwdPort   
             INTEGER (0..89)
}

teraDot1dTpPort OBJECT-TYPE
          SYNTAX INTEGER (1..65535)
          ACCESS read-only
          STATUS mandatory
          DESCRIPTION
               ""
          ::= { teraDot1dTpPortTableEntry 1 }

teraDot1dFFType OBJECT-TYPE
          SYNTAX INTEGER
                  {
                  static(1),
                  combined(2),
                  dynamic(3),
                  vlanTag(4)
                  }
          ACCESS read-write
          STATUS mandatory
          DESCRIPTION
               ""
          ::= { teraDot1dTpPortTableEntry 2 }

teraDot1dLoopback OBJECT-TYPE
          SYNTAX INTEGER
                  {
                  none(0),
                  terminal(1),
                  facility(2)
                  }
          ACCESS read-write
          STATUS mandatory
          DESCRIPTION
               ""
          ::= { teraDot1dTpPortTableEntry 3 }

teraDot1dTpUseDefaultFwd OBJECT-TYPE
          SYNTAX INTEGER
                  {
                  false(1),
                  true(2)
                  }
          ACCESS read-write
          STATUS mandatory
          DESCRIPTION
               ""
          ::= { teraDot1dTpPortTableEntry 4 }

teraDot1dTpDefaultFwdPort OBJECT-TYPE
          SYNTAX INTEGER (0..89)
          ACCESS read-write
          STATUS mandatory
          DESCRIPTION
               ""
          ::= { teraDot1dTpPortTableEntry 5 }

     -- teraDot1dStaticTable

teraDot1dStaticTable OBJECT-TYPE
     SYNTAX SEQUENCE OF TeraDot1dStaticTableEntryType
     ACCESS not-accessible
     STATUS mandatory
     DESCRIPTION
          " table teraDot1dStaticTable"
     ::= { tera1dBridge 5 }

teraDot1dStaticTableEntry OBJECT-TYPE
          SYNTAX TeraDot1dStaticTableEntryType
          ACCESS not-accessible
          STATUS mandatory
          DESCRIPTION
               " table entry teraDot1dStaticTableEntry "
          INDEX {                   teraDot1dStaticReceivePort,                  teraDot1dStaticAddress }
     ::= { teraDot1dStaticTable 1 }

TeraDot1dStaticTableEntryType ::= SEQUENCE {
          teraDot1dStaticReceivePort   
             INTEGER,
          teraDot1dStaticAddress   
             MacAddress,
          teraDot1dStaticAllowedToGoTo   
             OCTET STRING,
          teraDot1dStaticStatus   
             INTEGER
}

teraDot1dStaticReceivePort OBJECT-TYPE
          SYNTAX INTEGER
          ACCESS read-only
          STATUS mandatory
          DESCRIPTION
               ""
          ::= { teraDot1dStaticTableEntry 1 }

teraDot1dStaticAddress OBJECT-TYPE
          SYNTAX MacAddress
          ACCESS read-only
          STATUS mandatory
          DESCRIPTION
               ""
          ::= { teraDot1dStaticTableEntry 2 }

teraDot1dStaticAllowedToGoTo OBJECT-TYPE
          SYNTAX OCTET STRING
          ACCESS read-write
          STATUS mandatory
          DESCRIPTION
               ""
          ::= { teraDot1dStaticTableEntry 3 }

teraDot1dStaticStatus OBJECT-TYPE
          SYNTAX INTEGER
                  {
                  allowed(1),
                  disallowed(2),
                  delete(3)
                  }
          ACCESS read-write
          STATUS mandatory
          DESCRIPTION
               ""
          ::= { teraDot1dStaticTableEntry 4 }

     -- teraDot1dBasePortTable

teraDot1dBasePortTable OBJECT-TYPE
     SYNTAX SEQUENCE OF TeraDot1dBasePortTableEntryType
     ACCESS not-accessible
     STATUS mandatory
     DESCRIPTION
          " table teraDot1dBasePortTable"
     ::= { tera1dBridge 6 }

teraDot1dBasePortTableEntry OBJECT-TYPE
          SYNTAX TeraDot1dBasePortTableEntryType
          ACCESS not-accessible
          STATUS mandatory
          DESCRIPTION
               " table entry teraDot1dBasePortTableEntry "
          INDEX {                   teraDot1dBaseInternalVPI,                  teraDot1dBaseInternalVCI,                  teraDot1dBaseParentPortIfIndex }
     ::= { teraDot1dBasePortTable 1 }

TeraDot1dBasePortTableEntryType ::= SEQUENCE {
          teraDot1dBasePort   
             INTEGER (1..65535),
          teraDot1dBaseParentPortIfIndex   
             INTEGER,
          teraDot1dBaseInternalVPI   
             INTEGER (0..4095),
          teraDot1dBaseInternalVCI   
             INTEGER (1..65535),
          teraDot1dBaseParentVPI   
             INTEGER (0..4095),
          teraDot1dBaseParentVCI   
             INTEGER (1..65535)
}

teraDot1dBasePort OBJECT-TYPE
          SYNTAX INTEGER (1..65535)
          ACCESS read-only
          STATUS mandatory
          DESCRIPTION
               ""
          ::= { teraDot1dBasePortTableEntry 1 }

teraDot1dBaseParentPortIfIndex OBJECT-TYPE
          SYNTAX INTEGER
          ACCESS read-only
          STATUS mandatory
          DESCRIPTION
               ""
          ::= { teraDot1dBasePortTableEntry 2 }

teraDot1dBaseInternalVPI OBJECT-TYPE
          SYNTAX INTEGER (0..4095)
          ACCESS read-only
          STATUS mandatory
          DESCRIPTION
               ""
          ::= { teraDot1dBasePortTableEntry 3 }

teraDot1dBaseInternalVCI OBJECT-TYPE
          SYNTAX INTEGER (1..65535)
          ACCESS read-only
          STATUS mandatory
          DESCRIPTION
               ""
          ::= { teraDot1dBasePortTableEntry 4 }

teraDot1dBaseParentVPI OBJECT-TYPE
          SYNTAX INTEGER (0..4095)
          ACCESS read-only
          STATUS mandatory
          DESCRIPTION
               ""
          ::= { teraDot1dBasePortTableEntry 5 }

teraDot1dBaseParentVCI OBJECT-TYPE
          SYNTAX INTEGER (1..65535)
          ACCESS read-only
          STATUS mandatory
          DESCRIPTION
               ""
          ::= { teraDot1dBasePortTableEntry 6 }

     -- teraVlanPortGroupTable

teraVlanPortGroupTable OBJECT-TYPE
     SYNTAX SEQUENCE OF TeraVlanPortGroupTableEntryType
     ACCESS not-accessible
     STATUS mandatory
     DESCRIPTION
          " table teraVlanPortGroupTable"
     ::= { tera1dBridge 7 }

teraVlanPortGroupTableEntry OBJECT-TYPE
          SYNTAX TeraVlanPortGroupTableEntryType
          ACCESS not-accessible
          STATUS mandatory
          DESCRIPTION
               " table entry teraVlanPortGroupTableEntry "
          INDEX {                   dot1qVlanIndex }
     ::= { teraVlanPortGroupTable 1 }

TeraVlanPortGroupTableEntryType ::= SEQUENCE {
          dot1qVlanIndex   
             INTEGER (1..4094),
          teraVlanPorts   
             OCTET STRING,
          teraVlanPortGroupTableAction   
             INTEGER
}

dot1qVlanIndex OBJECT-TYPE
          SYNTAX INTEGER (1..4094)
          ACCESS read-only
          STATUS mandatory
          DESCRIPTION
               ""
          ::= { teraVlanPortGroupTableEntry 1 }

teraVlanPorts OBJECT-TYPE
          SYNTAX OCTET STRING
          ACCESS read-write
          STATUS mandatory
          DESCRIPTION
               ""
          ::= { teraVlanPortGroupTableEntry 2 }

teraVlanPortGroupTableAction OBJECT-TYPE
          SYNTAX INTEGER
                  {
                  ok(1),
                  delete(2)
                  }
          ACCESS read-write
          STATUS mandatory
          DESCRIPTION
               ""
          ::= { teraVlanPortGroupTableEntry 3 }

     -- teraDot1qVlanPortTable

teraDot1qVlanPortTable OBJECT-TYPE
     SYNTAX SEQUENCE OF TeraDot1qVlanPortTableEntryType
     ACCESS not-accessible
     STATUS mandatory
     DESCRIPTION
          " table teraDot1qVlanPortTable"
     ::= { tera1dBridge 8 }

teraDot1qVlanPortTableEntry OBJECT-TYPE
          SYNTAX TeraDot1qVlanPortTableEntryType
          ACCESS not-accessible
          STATUS mandatory
          DESCRIPTION
               " table entry teraDot1qVlanPortTableEntry "
          INDEX {                   teraDot1qVlanPort }
     ::= { teraDot1qVlanPortTable 1 }

TeraDot1qVlanPortTableEntryType ::= SEQUENCE {
          teraDot1qVlanPort   
             INTEGER (1..81),
          teraDot1qVlanPortIngressFrameTypes   
             INTEGER,
          teraDot1qVlanPortIngressFiltering   
             INTEGER,
          teraDot1qVlanPortEgressFrameType   
             INTEGER,
          teraDot1qVlanPortEgressTagSwap   
             INTEGER,
          teraDot1qVlanPortDisUntaggedBcast   
             INTEGER
}

teraDot1qVlanPort OBJECT-TYPE
          SYNTAX INTEGER (1..81)
          ACCESS read-only
          STATUS mandatory
          DESCRIPTION
               ""
          ::= { teraDot1qVlanPortTableEntry 1 }

teraDot1qVlanPortIngressFrameTypes OBJECT-TYPE
          SYNTAX INTEGER
                  {
                  admitAll(1),
                  admitOnlyVlanTagged(2),
                  admitOnlyUntagged(3)
                  }
          ACCESS read-write
          STATUS mandatory
          DESCRIPTION
               ""
          ::= { teraDot1qVlanPortTableEntry 2 }

teraDot1qVlanPortIngressFiltering OBJECT-TYPE
          SYNTAX INTEGER
                  {
                  true(1),
                  false(2)
                  }
          ACCESS read-write
          STATUS mandatory
          DESCRIPTION
               ""
          ::= { teraDot1qVlanPortTableEntry 3 }

teraDot1qVlanPortEgressFrameType OBJECT-TYPE
          SYNTAX INTEGER
                  {
                  sendOnlyUntagged(1),
                  sendOnlyVlanTagged(2),
                  sendAll(3)
                  }
          ACCESS read-write
          STATUS mandatory
          DESCRIPTION
               ""
          ::= { teraDot1qVlanPortTableEntry 4 }

teraDot1qVlanPortEgressTagSwap OBJECT-TYPE
          SYNTAX INTEGER
                  {
                  true(1),
                  false(2)
                  }
          ACCESS read-write
          STATUS mandatory
          DESCRIPTION
               ""
          ::= { teraDot1qVlanPortTableEntry 5 }

teraDot1qVlanPortDisUntaggedBcast OBJECT-TYPE
          SYNTAX INTEGER
                  {
                  true(1),
                  false(2)
                  }
          ACCESS read-write
          STATUS mandatory
          DESCRIPTION
               ""
          ::= { teraDot1qVlanPortTableEntry 6 }

     -- teraDot1dTp

teraDot1dTp OBJECT-TYPE
     SYNTAX SEQUENCE OF TeraDot1dTpEntryType
     ACCESS not-accessible
     STATUS mandatory
     DESCRIPTION
          " table teraDot1dTp"
     ::= { tera1dBridge 9 }

teraDot1dTpEntry OBJECT-TYPE
          SYNTAX TeraDot1dTpEntryType
          ACCESS not-accessible
          STATUS mandatory
          DESCRIPTION
               " table entry teraDot1dTpEntry "
          INDEX {                   teraDot1dTpSlot,                  teraDot1dTpProcessor }
     ::= { teraDot1dTp 1 }

TeraDot1dTpEntryType ::= SEQUENCE {
          teraDot1dTpSlot   
             INTEGER (1..3),
          teraDot1dTpProcessor   
             INTEGER (1..2),
          teraDot1dTpLearnedEntryDiscards   
             Counter32,
          teraDot1dTpAgingTime   
             INTEGER (10..1000000)
}

teraDot1dTpSlot OBJECT-TYPE
          SYNTAX INTEGER (1..3)
          ACCESS read-only
          STATUS mandatory
          DESCRIPTION
               ""
          ::= { teraDot1dTpEntry 1 }

teraDot1dTpProcessor OBJECT-TYPE
          SYNTAX INTEGER (1..2)
          ACCESS read-only
          STATUS mandatory
          DESCRIPTION
               ""
          ::= { teraDot1dTpEntry 2 }

teraDot1dTpLearnedEntryDiscards OBJECT-TYPE
          SYNTAX Counter32
          ACCESS read-only
          STATUS mandatory
          DESCRIPTION
               ""
          ::= { teraDot1dTpEntry 3 }

teraDot1dTpAgingTime OBJECT-TYPE
          SYNTAX INTEGER (10..1000000)
          ACCESS read-write
          STATUS mandatory
          DESCRIPTION
               ""
          ::= { teraDot1dTpEntry 4 }

     -- teraDot1qFdbTable

teraDot1qFdbTable OBJECT-TYPE
     SYNTAX SEQUENCE OF TeraDot1qFdbTableEntryType
     ACCESS not-accessible
     STATUS mandatory
     DESCRIPTION
          " table teraDot1qFdbTable"
     ::= { tera1dBridge 10 }

teraDot1qFdbTableEntry OBJECT-TYPE
          SYNTAX TeraDot1qFdbTableEntryType
          ACCESS not-accessible
          STATUS mandatory
          DESCRIPTION
               " table entry teraDot1qFdbTableEntry "
          INDEX {                   teraDot1dTpSlot,                  teraDot1dTpProcessor,                  dot1qVlanIndex }
     ::= { teraDot1qFdbTable 1 }

TeraDot1qFdbTableEntryType ::= SEQUENCE {
          teraDot1qFdbDynamicCount   
             Counter32
}

teraDot1qFdbDynamicCount OBJECT-TYPE
          SYNTAX Counter32
          ACCESS read-only
          STATUS mandatory
          DESCRIPTION
               ""
          ::= { teraDot1qFdbTableEntry 1 }

     -- teraDot1qTpFdbTable

teraDot1qTpFdbTable OBJECT-TYPE
     SYNTAX SEQUENCE OF TeraDot1qTpFdbTableEntryType
     ACCESS not-accessible
     STATUS mandatory
     DESCRIPTION
          " table teraDot1qTpFdbTable"
     ::= { tera1dBridge 11 }

teraDot1qTpFdbTableEntry OBJECT-TYPE
          SYNTAX TeraDot1qTpFdbTableEntryType
          ACCESS not-accessible
          STATUS mandatory
          DESCRIPTION
               " table entry teraDot1qTpFdbTableEntry "
          INDEX {                   teraDot1dTpSlot,                  teraDot1dTpProcessor,                  dot1qFdbId,                  teraDot1qTpFdbAddress }
     ::= { teraDot1qTpFdbTable 1 }

TeraDot1qTpFdbTableEntryType ::= SEQUENCE {
          teraDot1qTpFdbAddress   
             MacAddress,
          teraDot1qTpFdbPort   
             INTEGER (0..65535),
          teraDot1qTpFdbStatus   
             INTEGER
}

teraDot1qTpFdbAddress OBJECT-TYPE
          SYNTAX MacAddress
          ACCESS read-only
          STATUS mandatory
          DESCRIPTION
               ""
          ::= { teraDot1qTpFdbTableEntry 1 }

teraDot1qTpFdbPort OBJECT-TYPE
          SYNTAX INTEGER (0..65535)
          ACCESS read-only
          STATUS mandatory
          DESCRIPTION
               ""
          ::= { teraDot1qTpFdbTableEntry 2 }

teraDot1qTpFdbStatus OBJECT-TYPE
          SYNTAX INTEGER
                  {
                  other(1),
                  invalid(2),
                  learned(3),
                  self(4),
                  mgmt(5)
                  }
          ACCESS read-only
          STATUS mandatory
          DESCRIPTION
               ""
          ::= { teraDot1qTpFdbTableEntry 3 }

     -- teraDot1dPvcStatTable

teraDot1dPvcStatTable OBJECT-TYPE
     SYNTAX SEQUENCE OF TeraDot1dPvcStatTableEntryType
     ACCESS not-accessible
     STATUS mandatory
     DESCRIPTION
          " table teraDot1dPvcStatTable"
     ::= { tera1dBridge 12 }

teraDot1dPvcStatTableEntry OBJECT-TYPE
          SYNTAX TeraDot1dPvcStatTableEntryType
          ACCESS not-accessible
          STATUS mandatory
          DESCRIPTION
               " table entry teraDot1dPvcStatTableEntry "
          INDEX {                   teraDot1dTpPort }
     ::= { teraDot1dPvcStatTable 1 }

TeraDot1dPvcStatTableEntryType ::= SEQUENCE {
          teraDot1dPvcStatTxPktCount   
             Counter32,
          teraDot1dPvcStatTxOverrun   
             Counter32,
          teraDot1dPvcStatTxUnderrun   
             Counter32,
          teraDot1dPvcStatRxPktCount   
             Counter32,
          teraDot1dPvcStatRxOverrun   
             Counter32,
          teraDot1dPvcStatRxUnderrun   
             Counter32,
          teraDot1dPvcStatRxCrcError   
             Counter32,
          teraDot1dPvcStatRxLengthError   
             Counter32,
          teraDot1dPvcStatRxAbort   
             Counter32,
          teraDot1dPvcStatRxSlip   
             Counter32,
          teraDot1dPvcStatRxNoBuffer   
             Counter32,
          teraDot1dPvcStatState   
             INTEGER
}

teraDot1dPvcStatTxPktCount OBJECT-TYPE
          SYNTAX Counter32
          ACCESS read-only
          STATUS mandatory
          DESCRIPTION
               ""
          ::= { teraDot1dPvcStatTableEntry 1 }

teraDot1dPvcStatTxOverrun OBJECT-TYPE
          SYNTAX Counter32
          ACCESS read-only
          STATUS mandatory
          DESCRIPTION
               ""
          ::= { teraDot1dPvcStatTableEntry 2 }

teraDot1dPvcStatTxUnderrun OBJECT-TYPE
          SYNTAX Counter32
          ACCESS read-only
          STATUS mandatory
          DESCRIPTION
               ""
          ::= { teraDot1dPvcStatTableEntry 3 }

teraDot1dPvcStatRxPktCount OBJECT-TYPE
          SYNTAX Counter32
          ACCESS read-only
          STATUS mandatory
          DESCRIPTION
               ""
          ::= { teraDot1dPvcStatTableEntry 4 }

teraDot1dPvcStatRxOverrun OBJECT-TYPE
          SYNTAX Counter32
          ACCESS read-only
          STATUS mandatory
          DESCRIPTION
               ""
          ::= { teraDot1dPvcStatTableEntry 5 }

teraDot1dPvcStatRxUnderrun OBJECT-TYPE
          SYNTAX Counter32
          ACCESS read-only
          STATUS mandatory
          DESCRIPTION
               ""
          ::= { teraDot1dPvcStatTableEntry 6 }

teraDot1dPvcStatRxCrcError OBJECT-TYPE
          SYNTAX Counter32
          ACCESS read-only
          STATUS mandatory
          DESCRIPTION
               ""
          ::= { teraDot1dPvcStatTableEntry 7 }

teraDot1dPvcStatRxLengthError OBJECT-TYPE
          SYNTAX Counter32
          ACCESS read-only
          STATUS mandatory
          DESCRIPTION
               ""
          ::= { teraDot1dPvcStatTableEntry 8 }

teraDot1dPvcStatRxAbort OBJECT-TYPE
          SYNTAX Counter32
          ACCESS read-only
          STATUS mandatory
          DESCRIPTION
               ""
          ::= { teraDot1dPvcStatTableEntry 9 }

teraDot1dPvcStatRxSlip OBJECT-TYPE
          SYNTAX Counter32
          ACCESS read-only
          STATUS mandatory
          DESCRIPTION
               ""
          ::= { teraDot1dPvcStatTableEntry 10 }

teraDot1dPvcStatRxNoBuffer OBJECT-TYPE
          SYNTAX Counter32
          ACCESS read-only
          STATUS mandatory
          DESCRIPTION
               ""
          ::= { teraDot1dPvcStatTableEntry 11 }

teraDot1dPvcStatState OBJECT-TYPE
          SYNTAX INTEGER
                  {
                  ok(1),
                  clear(2)
                  }
          ACCESS read-write
          STATUS mandatory
          DESCRIPTION
               ""
          ::= { teraDot1dPvcStatTableEntry 12 }

     -- teraBridgeConnIdTable

teraBridgeConnIdTable OBJECT-TYPE
     SYNTAX SEQUENCE OF TeraBridgeConnIdTableEntryType
     ACCESS not-accessible
     STATUS mandatory
     DESCRIPTION
          " table teraBridgeConnIdTable"
     ::= { tera1dBridge 13 }

teraBridgeConnIdTableEntry OBJECT-TYPE
          SYNTAX TeraBridgeConnIdTableEntryType
          ACCESS not-accessible
          STATUS mandatory
          DESCRIPTION
               " table entry teraBridgeConnIdTableEntry "
          INDEX {                   teraPvcLogPortId }
     ::= { teraBridgeConnIdTable 1 }

TeraBridgeConnIdTableEntryType ::= SEQUENCE {
          teraPvcLogPortId   
             INTEGER,
          teraConnId   
             Counter32
}

teraPvcLogPortId OBJECT-TYPE
          SYNTAX INTEGER
          ACCESS read-only
          STATUS mandatory
          DESCRIPTION
               ""
          ::= { teraBridgeConnIdTableEntry 1 }

teraConnId OBJECT-TYPE
          SYNTAX Counter32
          ACCESS read-write
          STATUS mandatory
          DESCRIPTION
               ""
          ::= { teraBridgeConnIdTableEntry 2 }

     -- teraVlanStatTable

teraVlanStatTable OBJECT-TYPE
     SYNTAX SEQUENCE OF TeraVlanStatTableEntryType
     ACCESS not-accessible
     STATUS mandatory
     DESCRIPTION
          " table teraVlanStatTable"
     ::= { tera1dBridge 14 }

teraVlanStatTableEntry OBJECT-TYPE
          SYNTAX TeraVlanStatTableEntryType
          ACCESS not-accessible
          STATUS mandatory
          DESCRIPTION
               " table entry teraVlanStatTableEntry "
          INDEX {                   dot1dBasePort,                  dot1qVlanIndex }
     ::= { teraVlanStatTable 1 }

TeraVlanStatTableEntryType ::= SEQUENCE {
          teraVlanStatState   
             INTEGER,
          teraVlanStatRxMcastSrcAddr   
             Counter32,
          teraVlanStatRxInvalidVlanId   
             Counter32,
          teraVlanStatRxMacAddrNotInStaticTbl   
             Counter32,
          teraVlanStatRxMacAddrInStaticTbl   
             Counter32,
          teraVlanStatRxInvalidOutPort   
             Counter32,
          teraVlanStatRxInvalidInPort   
             Counter32,
          teraVlanStatRxDestMacAddrDisallowed   
             Counter32,
          teraVlanStatRxPortBlocked   
             Counter32,
          teraVlanStatRxDiscardTaggedFrame   
             Counter32,
          teraVlanStatRxDiscardUntaggedFrame   
             Counter32,
          teraVlanStatRxDiscardBcastBlocked   
             Counter32,
          teraVlanStatRxDiscardLocalDest   
             Counter32,
          teraVlanStatRxFFTypeMismatch   
             Counter32,
          teraVlanStatRxNoBuffer   
             Counter32,
          teraVlanStatRxTxFail   
             Counter32,
          teraVlanStatRxInvalidEncap   
             Counter32
}

teraVlanStatState OBJECT-TYPE
          SYNTAX INTEGER
                  {
                  ok(1),
                  clear(2)
                  }
          ACCESS read-write
          STATUS mandatory
          DESCRIPTION
               ""
          ::= { teraVlanStatTableEntry 1 }

teraVlanStatRxMcastSrcAddr OBJECT-TYPE
          SYNTAX Counter32
          ACCESS read-only
          STATUS mandatory
          DESCRIPTION
               ""
          ::= { teraVlanStatTableEntry 2 }

teraVlanStatRxInvalidVlanId OBJECT-TYPE
          SYNTAX Counter32
          ACCESS read-only
          STATUS mandatory
          DESCRIPTION
               ""
          ::= { teraVlanStatTableEntry 3 }

teraVlanStatRxMacAddrNotInStaticTbl OBJECT-TYPE
          SYNTAX Counter32
          ACCESS read-only
          STATUS mandatory
          DESCRIPTION
               ""
          ::= { teraVlanStatTableEntry 4 }

teraVlanStatRxMacAddrInStaticTbl OBJECT-TYPE
          SYNTAX Counter32
          ACCESS read-only
          STATUS mandatory
          DESCRIPTION
               ""
          ::= { teraVlanStatTableEntry 5 }

teraVlanStatRxInvalidOutPort OBJECT-TYPE
          SYNTAX Counter32
          ACCESS read-only
          STATUS mandatory
          DESCRIPTION
               ""
          ::= { teraVlanStatTableEntry 6 }

teraVlanStatRxInvalidInPort OBJECT-TYPE
          SYNTAX Counter32
          ACCESS read-only
          STATUS mandatory
          DESCRIPTION
               ""
          ::= { teraVlanStatTableEntry 7 }

teraVlanStatRxDestMacAddrDisallowed OBJECT-TYPE
          SYNTAX Counter32
          ACCESS read-only
          STATUS mandatory
          DESCRIPTION
               ""
          ::= { teraVlanStatTableEntry 8 }

teraVlanStatRxPortBlocked OBJECT-TYPE
          SYNTAX Counter32
          ACCESS read-only
          STATUS mandatory
          DESCRIPTION
               ""
          ::= { teraVlanStatTableEntry 9 }

teraVlanStatRxDiscardTaggedFrame OBJECT-TYPE
          SYNTAX Counter32
          ACCESS read-only
          STATUS mandatory
          DESCRIPTION
               ""
          ::= { teraVlanStatTableEntry 10 }

teraVlanStatRxDiscardUntaggedFrame OBJECT-TYPE
          SYNTAX Counter32
          ACCESS read-only
          STATUS mandatory
          DESCRIPTION
               ""
          ::= { teraVlanStatTableEntry 11 }

teraVlanStatRxDiscardBcastBlocked OBJECT-TYPE
          SYNTAX Counter32
          ACCESS read-only
          STATUS mandatory
          DESCRIPTION
               ""
          ::= { teraVlanStatTableEntry 12 }

teraVlanStatRxDiscardLocalDest OBJECT-TYPE
          SYNTAX Counter32
          ACCESS read-only
          STATUS mandatory
          DESCRIPTION
               ""
          ::= { teraVlanStatTableEntry 13 }

teraVlanStatRxFFTypeMismatch OBJECT-TYPE
          SYNTAX Counter32
          ACCESS read-only
          STATUS mandatory
          DESCRIPTION
               ""
          ::= { teraVlanStatTableEntry 14 }

teraVlanStatRxNoBuffer OBJECT-TYPE
          SYNTAX Counter32
          ACCESS read-only
          STATUS mandatory
          DESCRIPTION
               ""
          ::= { teraVlanStatTableEntry 15 }

teraVlanStatRxTxFail OBJECT-TYPE
          SYNTAX Counter32
          ACCESS read-only
          STATUS mandatory
          DESCRIPTION
               ""
          ::= { teraVlanStatTableEntry 16 }

teraVlanStatRxInvalidEncap OBJECT-TYPE
          SYNTAX Counter32
          ACCESS read-only
          STATUS mandatory
          DESCRIPTION
               ""
          ::= { teraVlanStatTableEntry 17 }

     -- teraEtherStatTable

teraEtherStatTable OBJECT-TYPE
     SYNTAX SEQUENCE OF TeraEtherStatTableEntryType
     ACCESS not-accessible
     STATUS mandatory
     DESCRIPTION
          " table teraEtherStatTable"
     ::= { tera1dBridge 15 }

teraEtherStatTableEntry OBJECT-TYPE
          SYNTAX TeraEtherStatTableEntryType
          ACCESS not-accessible
          STATUS mandatory
          DESCRIPTION
               " table entry teraEtherStatTableEntry "
          INDEX {                   etherStatsIndex }
     ::= { teraEtherStatTable 1 }

TeraEtherStatTableEntryType ::= SEQUENCE {
          teraEtherStatRxTotalFrames   
             Counter32,
          teraEtherStatRxGoodFrames   
             Counter32,
          teraEtherStatRxForwardFrames   
             Counter32,
          teraEtherStatRxForwardOctets   
             Counter32,
          teraEtherStatRxPause   
             Counter32,
          teraEtherStatRxTotalDiscard   
             Counter32,
          teraEtherStatRxNoBuffer   
             Counter32,
          teraEtherStatRxTotalBadFrames   
             Counter32,
          teraEtherStatRxBadFrameLenViolation   
             Counter32,
          teraEtherStatRxBadFrameNotAlign   
             Counter32,
          teraEtherStatRxBadFrameTooShort   
             Counter32,
          teraEtherStatRxBadFrameCRC   
             Counter32,
          teraEtherStatRxBadFrameOverrun   
             Counter32,
          teraEtherStatRxBadFrameCollision   
             Counter32,
          teraEtherStatTxTotalFrames   
             Counter32,
          teraEtherStatTxGoodFrames   
             Counter32,
          teraEtherStatTxFramesSentOut   
             Counter32,
          teraEtherStatTxOctets   
             Counter32,
          teraEtherStatTxPause   
             Counter32,
          teraEtherStatTxQueueOverflow   
             Counter32,
          teraEtherStatTxTotalBadFrames   
             Counter32,
          teraEtherStatTxBadFrameCarrierLost   
             Counter32,
          teraEtherStatTxBadFrameUnderrun   
             Counter32,
          teraEtherStatTxBadFrameRexmitLimit   
             Counter32,
          teraEtherStatTxBadFrameLateCollision   
             Counter32,
          teraEtherStatTxBadFrameTxErr   
             Counter32,
          teraEtherStatTxBadFrameReset1   
             Counter32,
          teraEtherStatTxBadFrameReset2   
             Counter32,
          teraEtherStatTxBadFramePortDisable   
             Counter32,
          teraEtherStatState   
             INTEGER
}

teraEtherStatRxTotalFrames OBJECT-TYPE
          SYNTAX Counter32
          ACCESS read-only
          STATUS mandatory
          DESCRIPTION
               ""
          ::= { teraEtherStatTableEntry 1 }

teraEtherStatRxGoodFrames OBJECT-TYPE
          SYNTAX Counter32
          ACCESS read-only
          STATUS mandatory
          DESCRIPTION
               ""
          ::= { teraEtherStatTableEntry 2 }

teraEtherStatRxForwardFrames OBJECT-TYPE
          SYNTAX Counter32
          ACCESS read-only
          STATUS mandatory
          DESCRIPTION
               ""
          ::= { teraEtherStatTableEntry 3 }

teraEtherStatRxForwardOctets OBJECT-TYPE
          SYNTAX Counter32
          ACCESS read-only
          STATUS mandatory
          DESCRIPTION
               ""
          ::= { teraEtherStatTableEntry 4 }

teraEtherStatRxPause OBJECT-TYPE
          SYNTAX Counter32
          ACCESS read-only
          STATUS mandatory
          DESCRIPTION
               ""
          ::= { teraEtherStatTableEntry 5 }

teraEtherStatRxTotalDiscard OBJECT-TYPE
          SYNTAX Counter32
          ACCESS read-only
          STATUS mandatory
          DESCRIPTION
               ""
          ::= { teraEtherStatTableEntry 6 }

teraEtherStatRxNoBuffer OBJECT-TYPE
          SYNTAX Counter32
          ACCESS read-only
          STATUS mandatory
          DESCRIPTION
               ""
          ::= { teraEtherStatTableEntry 7 }

teraEtherStatRxTotalBadFrames OBJECT-TYPE
          SYNTAX Counter32
          ACCESS read-only
          STATUS mandatory
          DESCRIPTION
               ""
          ::= { teraEtherStatTableEntry 8 }

teraEtherStatRxBadFrameLenViolation OBJECT-TYPE
          SYNTAX Counter32
          ACCESS read-only
          STATUS mandatory
          DESCRIPTION
               ""
          ::= { teraEtherStatTableEntry 9 }

teraEtherStatRxBadFrameNotAlign OBJECT-TYPE
          SYNTAX Counter32
          ACCESS read-only
          STATUS mandatory
          DESCRIPTION
               ""
          ::= { teraEtherStatTableEntry 10 }

teraEtherStatRxBadFrameTooShort OBJECT-TYPE
          SYNTAX Counter32
          ACCESS read-only
          STATUS mandatory
          DESCRIPTION
               ""
          ::= { teraEtherStatTableEntry 11 }

teraEtherStatRxBadFrameCRC OBJECT-TYPE
          SYNTAX Counter32
          ACCESS read-only
          STATUS mandatory
          DESCRIPTION
               ""
          ::= { teraEtherStatTableEntry 12 }

teraEtherStatRxBadFrameOverrun OBJECT-TYPE
          SYNTAX Counter32
          ACCESS read-only
          STATUS mandatory
          DESCRIPTION
               ""
          ::= { teraEtherStatTableEntry 13 }

teraEtherStatRxBadFrameCollision OBJECT-TYPE
          SYNTAX Counter32
          ACCESS read-only
          STATUS mandatory
          DESCRIPTION
               ""
          ::= { teraEtherStatTableEntry 14 }

teraEtherStatTxTotalFrames OBJECT-TYPE
          SYNTAX Counter32
          ACCESS read-only
          STATUS mandatory
          DESCRIPTION
               ""
          ::= { teraEtherStatTableEntry 15 }

teraEtherStatTxGoodFrames OBJECT-TYPE
          SYNTAX Counter32
          ACCESS read-only
          STATUS mandatory
          DESCRIPTION
               ""
          ::= { teraEtherStatTableEntry 16 }

teraEtherStatTxFramesSentOut OBJECT-TYPE
          SYNTAX Counter32
          ACCESS read-only
          STATUS mandatory
          DESCRIPTION
               ""
          ::= { teraEtherStatTableEntry 17 }

teraEtherStatTxOctets OBJECT-TYPE
          SYNTAX Counter32
          ACCESS read-only
          STATUS mandatory
          DESCRIPTION
               ""
          ::= { teraEtherStatTableEntry 18 }

teraEtherStatTxPause OBJECT-TYPE
          SYNTAX Counter32
          ACCESS read-only
          STATUS mandatory
          DESCRIPTION
               ""
          ::= { teraEtherStatTableEntry 19 }

teraEtherStatTxQueueOverflow OBJECT-TYPE
          SYNTAX Counter32
          ACCESS read-only
          STATUS mandatory
          DESCRIPTION
               ""
          ::= { teraEtherStatTableEntry 20 }

teraEtherStatTxTotalBadFrames OBJECT-TYPE
          SYNTAX Counter32
          ACCESS read-only
          STATUS mandatory
          DESCRIPTION
               ""
          ::= { teraEtherStatTableEntry 21 }

teraEtherStatTxBadFrameCarrierLost OBJECT-TYPE
          SYNTAX Counter32
          ACCESS read-only
          STATUS mandatory
          DESCRIPTION
               ""
          ::= { teraEtherStatTableEntry 22 }

teraEtherStatTxBadFrameUnderrun OBJECT-TYPE
          SYNTAX Counter32
          ACCESS read-only
          STATUS mandatory
          DESCRIPTION
               ""
          ::= { teraEtherStatTableEntry 23 }

teraEtherStatTxBadFrameRexmitLimit OBJECT-TYPE
          SYNTAX Counter32
          ACCESS read-only
          STATUS mandatory
          DESCRIPTION
               ""
          ::= { teraEtherStatTableEntry 24 }

teraEtherStatTxBadFrameLateCollision OBJECT-TYPE
          SYNTAX Counter32
          ACCESS read-only
          STATUS mandatory
          DESCRIPTION
               ""
          ::= { teraEtherStatTableEntry 25 }

teraEtherStatTxBadFrameTxErr OBJECT-TYPE
          SYNTAX Counter32
          ACCESS read-only
          STATUS mandatory
          DESCRIPTION
               ""
          ::= { teraEtherStatTableEntry 26 }

teraEtherStatTxBadFrameReset1 OBJECT-TYPE
          SYNTAX Counter32
          ACCESS read-only
          STATUS mandatory
          DESCRIPTION
               ""
          ::= { teraEtherStatTableEntry 27 }

teraEtherStatTxBadFrameReset2 OBJECT-TYPE
          SYNTAX Counter32
          ACCESS read-only
          STATUS mandatory
          DESCRIPTION
               ""
          ::= { teraEtherStatTableEntry 28 }

teraEtherStatTxBadFramePortDisable OBJECT-TYPE
          SYNTAX Counter32
          ACCESS read-only
          STATUS mandatory
          DESCRIPTION
               ""
          ::= { teraEtherStatTableEntry 29 }

teraEtherStatState OBJECT-TYPE
          SYNTAX INTEGER
                  {
                  ok(1),
                  clear(2)
                  }
          ACCESS read-write
          STATUS mandatory
          DESCRIPTION
               ""
          ::= { teraEtherStatTableEntry 30 }

     -- teraLanPolicingTable

teraLanPolicingTable OBJECT-TYPE
     SYNTAX SEQUENCE OF TeraLanPolicingTableEntryType
     ACCESS not-accessible
     STATUS mandatory
     DESCRIPTION
          " table teraLanPolicingTable"
     ::= { tera1dBridge 16 }

teraLanPolicingTableEntry OBJECT-TYPE
          SYNTAX TeraLanPolicingTableEntryType
          ACCESS not-accessible
          STATUS mandatory
          DESCRIPTION
               " table entry teraLanPolicingTableEntry "
          INDEX {                   etherStatsIndex }
     ::= { teraLanPolicingTable 1 }

TeraLanPolicingTableEntryType ::= SEQUENCE {
          teraLanIngPolicing   
             INTEGER,
          teraLanIngPolicingInterval   
             Counter32 (200..10000),
          teraLanIngPolicingRate   
             Counter32 (1..100000),
          teraLanIngPolicingMaxAccr   
             Counter32 (200..10000),
          teraLanEgrShaping   
             INTEGER,
          teraLanEgrShapingInterval   
             Counter32 (200..10000),
          teraLanEgrShapingRate   
             Counter32 (1..100000)
}

teraLanIngPolicing OBJECT-TYPE
          SYNTAX INTEGER
                  {
                  disable(1),
                  enable(2)
                  }
          ACCESS read-write
          STATUS mandatory
          DESCRIPTION
               ""
          ::= { teraLanPolicingTableEntry 1 }

teraLanIngPolicingInterval OBJECT-TYPE
          SYNTAX Counter32 (200..10000)
          ACCESS read-write
          STATUS mandatory
          DESCRIPTION
               ""
          ::= { teraLanPolicingTableEntry 2 }

teraLanIngPolicingRate OBJECT-TYPE
          SYNTAX Counter32 (1..100000)
          ACCESS read-write
          STATUS mandatory
          DESCRIPTION
               ""
          ::= { teraLanPolicingTableEntry 3 }

teraLanIngPolicingMaxAccr OBJECT-TYPE
          SYNTAX Counter32 (200..10000)
          ACCESS read-write
          STATUS mandatory
          DESCRIPTION
               ""
          ::= { teraLanPolicingTableEntry 4 }

teraLanEgrShaping OBJECT-TYPE
          SYNTAX INTEGER
                  {
                  disable(1),
                  enable(2)
                  }
          ACCESS read-write
          STATUS mandatory
          DESCRIPTION
               ""
          ::= { teraLanPolicingTableEntry 5 }

teraLanEgrShapingInterval OBJECT-TYPE
          SYNTAX Counter32 (200..10000)
          ACCESS read-write
          STATUS mandatory
          DESCRIPTION
               ""
          ::= { teraLanPolicingTableEntry 6 }

teraLanEgrShapingRate OBJECT-TYPE
          SYNTAX Counter32 (1..100000)
          ACCESS read-write
          STATUS mandatory
          DESCRIPTION
               ""
          ::= { teraLanPolicingTableEntry 7 }

     -- teraLanUsageHistoryControlTable

teraLanUsageHistoryControlTable OBJECT-TYPE
     SYNTAX SEQUENCE OF TeraLanUsageHistoryControlTableEntryType
     ACCESS not-accessible
     STATUS mandatory
     DESCRIPTION
          " table teraLanUsageHistoryControlTable"
     ::= { tera1dBridge 17 }

teraLanUsageHistoryControlTableEntry OBJECT-TYPE
          SYNTAX TeraLanUsageHistoryControlTableEntryType
          ACCESS not-accessible
          STATUS mandatory
          DESCRIPTION
               " table entry teraLanUsageHistoryControlTableEntry "
          INDEX {                   dot1dBasePort }
     ::= { teraLanUsageHistoryControlTable 1 }

TeraLanUsageHistoryControlTableEntryType ::= SEQUENCE {
          teraLanUsageHistoryControlBucketsRequested   
             INTEGER (1..65535),
          teraLanUsageHistoryControlBucketsGranted   
             INTEGER (1..65535),
          teraLanUsageHistoryControlInterval   
             INTEGER (1..3600),
          teraLanUsageHistoryControlStatus   
             INTEGER
}

teraLanUsageHistoryControlBucketsRequested OBJECT-TYPE
          SYNTAX INTEGER (1..65535)
          ACCESS read-write
          STATUS mandatory
          DESCRIPTION
               ""
          ::= { teraLanUsageHistoryControlTableEntry 1 }

teraLanUsageHistoryControlBucketsGranted OBJECT-TYPE
          SYNTAX INTEGER (1..65535)
          ACCESS read-only
          STATUS mandatory
          DESCRIPTION
               ""
          ::= { teraLanUsageHistoryControlTableEntry 2 }

teraLanUsageHistoryControlInterval OBJECT-TYPE
          SYNTAX INTEGER (1..3600)
          ACCESS read-write
          STATUS mandatory
          DESCRIPTION
               ""
          ::= { teraLanUsageHistoryControlTableEntry 3 }

teraLanUsageHistoryControlStatus OBJECT-TYPE
          SYNTAX INTEGER
                  {
                  valid(1),
                  createRequest(2),
                  underCreation(3),
                  invalid(4)
                  }
          ACCESS read-write
          STATUS mandatory
          DESCRIPTION
               ""
          ::= { teraLanUsageHistoryControlTableEntry 4 }

     -- teraLanUsageTable

teraLanUsageTable OBJECT-TYPE
     SYNTAX SEQUENCE OF TeraLanUsageTableEntryType
     ACCESS not-accessible
     STATUS mandatory
     DESCRIPTION
          " table teraLanUsageTable"
     ::= { tera1dBridge 18 }

teraLanUsageTableEntry OBJECT-TYPE
          SYNTAX TeraLanUsageTableEntryType
          ACCESS not-accessible
          STATUS mandatory
          DESCRIPTION
               " table entry teraLanUsageTableEntry "
          INDEX {                   dot1dBasePort }
     ::= { teraLanUsageTable 1 }

TeraLanUsageTableEntryType ::= SEQUENCE {
          teraLanUsageIngRcvBytes   
             Counter32,
          teraLanUsageIngPolicingDropBytes   
             Counter32,
          teraLanUsageEgrRcvBytes   
             Counter32,
          teraLanUsageEgrSentBytes   
             Counter32,
          teraLanUsageStatus   
             INTEGER
}

teraLanUsageIngRcvBytes OBJECT-TYPE
          SYNTAX Counter32
          ACCESS read-only
          STATUS mandatory
          DESCRIPTION
               ""
          ::= { teraLanUsageTableEntry 1 }

teraLanUsageIngPolicingDropBytes OBJECT-TYPE
          SYNTAX Counter32
          ACCESS read-only
          STATUS mandatory
          DESCRIPTION
               ""
          ::= { teraLanUsageTableEntry 2 }

teraLanUsageEgrRcvBytes OBJECT-TYPE
          SYNTAX Counter32
          ACCESS read-only
          STATUS mandatory
          DESCRIPTION
               ""
          ::= { teraLanUsageTableEntry 3 }

teraLanUsageEgrSentBytes OBJECT-TYPE
          SYNTAX Counter32
          ACCESS read-only
          STATUS mandatory
          DESCRIPTION
               ""
          ::= { teraLanUsageTableEntry 4 }

teraLanUsageStatus OBJECT-TYPE
          SYNTAX INTEGER
                  {
                  ok(1),
                  clear(2)
                  }
          ACCESS read-write
          STATUS mandatory
          DESCRIPTION
               ""
          ::= { teraLanUsageTableEntry 5 }

     -- teraLanUsageHistoryTable

teraLanUsageHistoryTable OBJECT-TYPE
     SYNTAX SEQUENCE OF TeraLanUsageHistoryTableEntryType
     ACCESS not-accessible
     STATUS mandatory
     DESCRIPTION
          " table teraLanUsageHistoryTable"
     ::= { tera1dBridge 19 }

teraLanUsageHistoryTableEntry OBJECT-TYPE
          SYNTAX TeraLanUsageHistoryTableEntryType
          ACCESS not-accessible
          STATUS mandatory
          DESCRIPTION
               " table entry teraLanUsageHistoryTableEntry "
          INDEX {                   dot1dBasePort,                  teraLanUsageHistorySampleIndex }
     ::= { teraLanUsageHistoryTable 1 }

TeraLanUsageHistoryTableEntryType ::= SEQUENCE {
          teraLanUsageHistorySampleIndex   
             INTEGER (1..2147483647),
          teraLanUsageHistoryIntervalStart   
             INTEGER,
          teraLanUsageHistoryIngRcvBytes   
             Counter32,
          teraLanUsageHistoryIngPolicingDropBytes   
             Counter32,
          teraLanUsageHistoryEgrRcvBytes   
             Counter32,
          teraLanUsageHistoryEgrSentBytes   
             Counter32
}

teraLanUsageHistorySampleIndex OBJECT-TYPE
          SYNTAX INTEGER (1..2147483647)
          ACCESS read-only
          STATUS mandatory
          DESCRIPTION
               ""
          ::= { teraLanUsageHistoryTableEntry 1 }

teraLanUsageHistoryIntervalStart OBJECT-TYPE
          SYNTAX INTEGER
          ACCESS read-only
          STATUS mandatory
          DESCRIPTION
               ""
          ::= { teraLanUsageHistoryTableEntry 2 }

teraLanUsageHistoryIngRcvBytes OBJECT-TYPE
          SYNTAX Counter32
          ACCESS read-only
          STATUS mandatory
          DESCRIPTION
               ""
          ::= { teraLanUsageHistoryTableEntry 3 }

teraLanUsageHistoryIngPolicingDropBytes OBJECT-TYPE
          SYNTAX Counter32
          ACCESS read-only
          STATUS mandatory
          DESCRIPTION
               ""
          ::= { teraLanUsageHistoryTableEntry 4 }

teraLanUsageHistoryEgrRcvBytes OBJECT-TYPE
          SYNTAX Counter32
          ACCESS read-only
          STATUS mandatory
          DESCRIPTION
               ""
          ::= { teraLanUsageHistoryTableEntry 5 }

teraLanUsageHistoryEgrSentBytes OBJECT-TYPE
          SYNTAX Counter32
          ACCESS read-only
          STATUS mandatory
          DESCRIPTION
               ""
          ::= { teraLanUsageHistoryTableEntry 6 }

     -- teraLanCardModeTable

teraLanCardModeTable OBJECT-TYPE
     SYNTAX SEQUENCE OF TeraLanCardModeTableEntryType
     ACCESS not-accessible
     STATUS mandatory
     DESCRIPTION
          " table teraLanCardModeTable"
     ::= { tera1dBridge 20 }

teraLanCardModeTableEntry OBJECT-TYPE
          SYNTAX TeraLanCardModeTableEntryType
          ACCESS not-accessible
          STATUS mandatory
          DESCRIPTION
               " table entry teraLanCardModeTableEntry "
          INDEX {                   teraDot1dTpSlot }
     ::= { teraLanCardModeTable 1 }

TeraLanCardModeTableEntryType ::= SEQUENCE {
          teraLanCardMode   
             INTEGER
}

teraLanCardMode OBJECT-TYPE
          SYNTAX INTEGER
                  {
                  port-2(1),
                  port-4(2)
                  }
          ACCESS read-write
          STATUS mandatory
          DESCRIPTION
               ""
          ::= { teraLanCardModeTableEntry 1 }

END
