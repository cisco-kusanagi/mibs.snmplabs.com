INTEL-TUNNEL-MIB DEFINITIONS ::= BEGIN

-- Copyright (C) 1997 Intel Corporation. All rights reserved.
--
-- Tunneling MIB, 10-06-1997
--
-- Proprietary MIB containing information about TCP Tunneling.
--
-- Change History:
-- 97-06-10 Initial version
--

IMPORTS
       IpAddress               FROM RFC1155-SMI
       mib2ext                 FROM INTEL-GEN-MIB
       OBJECT-TYPE             FROM RFC-1212;

tunnel        OBJECT IDENTIFIER ::= { mib2ext 26 }
tunnelInfo    OBJECT IDENTIFIER ::= { tunnel 1 }

tunnelInfoTable OBJECT-TYPE
    SYNTAX SEQUENCE OF TunnelInfoEntry
    ACCESS not-accessible
    STATUS mandatory
    DESCRIPTION "Configuration and monitoring information for tunneling."
    ::= { tunnelInfo 1 }

tunnelInfoEntry OBJECT-TYPE
    SYNTAX TunnelInfoEntry
    ACCESS not-accessible
    STATUS mandatory
    DESCRIPTION ""
    INDEX { tunnelInfoIfIndex }
    ::= { tunnelInfoTable 1 }

TunnelInfoEntry ::= SEQUENCE {
                        tunnelInfoIfIndex
                           INTEGER,
                        tunnelInfoState
                           INTEGER,
                        tunnelInfoDirection
                           INTEGER,
                        tunnelInfoLocalAddress
                           IpAddress,
                        tunnelInfoRemoteAddress
                           IpAddress,
                        tunnelInfoLocalPort
                           INTEGER,
                        tunnelInfoRemotePort
                           INTEGER,
                        tunnelInfoReceiveQueueSize
                           INTEGER,
                        tunnelInfoTransmitQueueSize
                           INTEGER
                        }

tunnelInfoIfIndex OBJECT-TYPE
    SYNTAX INTEGER
    ACCESS read-only
    STATUS mandatory
    DESCRIPTION "Interface index"
    ::= { tunnelInfoEntry 1 }

tunnelInfoState OBJECT-TYPE
    SYNTAX INTEGER {
        void(1),
        create(2),
        closed(3),
        open(4),
	closing(5),
        call(6),
        destroy(7)
    }
    ACCESS read-only
    STATUS mandatory
    DESCRIPTION "Interface state"
    ::= { tunnelInfoEntry 2 }

tunnelInfoDirection OBJECT-TYPE
    SYNTAX INTEGER { client(1), server(2) }
    ACCESS read-only
    STATUS mandatory
    DESCRIPTION "Call direction"
    ::= { tunnelInfoEntry 3 }

tunnelInfoLocalAddress OBJECT-TYPE
    SYNTAX IpAddress
    ACCESS read-only
    STATUS mandatory
    DESCRIPTION "Local IP address"
    ::= { tunnelInfoEntry 4 }

tunnelInfoRemoteAddress OBJECT-TYPE
    SYNTAX IpAddress
    ACCESS read-only
    STATUS mandatory
    DESCRIPTION "Remote IP address"
    ::= { tunnelInfoEntry 5 }

tunnelInfoLocalPort OBJECT-TYPE
    SYNTAX INTEGER
    ACCESS read-only
    STATUS mandatory
    DESCRIPTION "Local TCP port"
    ::= { tunnelInfoEntry 6 }

tunnelInfoRemotePort OBJECT-TYPE
    SYNTAX INTEGER
    ACCESS read-only
    STATUS mandatory
    DESCRIPTION "Remote TCP port"
    ::= { tunnelInfoEntry 7 }

tunnelInfoReceiveQueueSize OBJECT-TYPE
    SYNTAX INTEGER
    ACCESS read-only
    STATUS mandatory
    DESCRIPTION "Number of buffers in receive queue
                 waiting to be processed"
    ::= { tunnelInfoEntry 8 }

tunnelInfoTransmitQueueSize OBJECT-TYPE
    SYNTAX INTEGER
    ACCESS read-only
    STATUS mandatory
    DESCRIPTION "Number of buffers in transmit queue
                 waiting to be sent"
    ::= { tunnelInfoEntry 9 }

END
