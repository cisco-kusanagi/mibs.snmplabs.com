-- $Id: ir-chassis-mib.mib,v 1.1 2002/06/27 15:42:02 sse Exp $
  MRV-IN-REACH-CHASSIS-MIB DEFINITIONS ::= BEGIN

               IMPORTS
                        Counter, Gauge, IpAddress
                                FROM RFC1155-SMI
                        DisplayString
                                FROM RFC1213-MIB
                        MacAddress
                                FROM BRIDGE-MIB
                        OBJECT-TYPE
                                FROM RFC-1212
                        mrvInReachProductDivision, AddressType, HardwareType, IOType
                                FROM MRV-IN-REACH-PRODUCT-DIVISION-MIB;

       xChassis         OBJECT IDENTIFIER ::= { mrvInReachProductDivision 16 }

       -- MRV In-Reach Character subgroups

       xChassisBasic    OBJECT IDENTIFIER ::= { xChassis 1 }
       xSegment         OBJECT IDENTIFIER ::= { xChassis 2 }
       xPort            OBJECT IDENTIFIER ::= { xChassis 3 }
       xController      OBJECT IDENTIFIER ::= { xChassis 4 }
       xInterface       OBJECT IDENTIFIER ::= { xChassis 5 }
       xSlotBootControl OBJECT IDENTIFIER ::= { xChassis 6 }
       xSlot            OBJECT IDENTIFIER ::= { xChassis 7 }
       xPowerSupply     OBJECT IDENTIFIER ::= { xChassis 8 }
       xFirmwareUpdate  OBJECT IDENTIFIER ::= { xChassis 9 }


            -- This is a MIB module for all MRV Communications systems that
            -- are on the management bus of a Network 9000 chassis.

            -- Copyright 2002 MRV Communications, Inc. All Rights Reserved.
            -- Reproduction of this document is authorized on
            -- condition that this copyright notice is included.
            -- This MIB document embodies MRV Communications, Inc.'s 
            -- proprietary intellectual property.  MRV Communications, Inc.
            -- retains all title and ownership in this MIB, including any
            -- revisions.
            --
            -- It is MRV Communications, Inc.'s intent to encourage the
            -- widespread use of this MIB in connection with the management of
            -- MRV Communications, Inc. products. MRV Communications,
            -- Inc. grants vendors,end-users, and other interested parties a
            -- non-exclusive license to use this MIB in connection with the
            -- management of MRV Communications, Inc. products.
            --
            -- This MIB document is supplied "AS IS," and MRV 
            -- Communications, Inc. makes no warranty, either express or
            -- implied, as to the use operation, condition, or performance of
            -- the MIB.


       -- Textual Conventions

       NetworkType ::=
           INTEGER { unknown(1), other(2), ethernet(3),
                            tokenRing(4), fddi(5), wan(6),
                            ethernetRepeater(7),
                            tokenRingConcentrator(8),
                            fddiConcentrator(9),
							atm(10), isdn(11),
							switchplane(12), switchedEthernet(13) }
       -- This data type is used in the MRV In-Reach Chassis MIB
       -- to indicate the type of segment or port.

       SerialNumber ::=
           OCTET STRING (SIZE (0..6))
       -- This data type is used in the MRV In-Reach Chassis MIB
       -- to indicate a 6-byte serial number, stored high-
       -- order byte first.  A zero-length value indicates
       -- unknown.

       Letter ::=
           INTEGER { a(1), b(2), c(3), d(4), e(5), f(6), g(7),
                     h(8), i(9), j(10), k(11), l(12), m(13),
                     n(14), o(15), p(16), q(17), r(18), s(19),
                     t(20), u(21), v(22), w(23), x(24), y(25),
                     z(26) }
       -- This data type is used in the MRV In-Reach Chassis MIB
       -- to identify an object with a letter.


       -- the Chassis Basic group

       -- Implementation of this group is mandatory for all MRV In-Reach
       -- Network 9000 management bus systems

       -- Chassis type, revision, and status are found in the
       -- MRV In-Reach System MIB objects sysChassisType,
       -- sysChassisVersion, and sysChassisState

       basicBase802Address OBJECT-TYPE
           SYNTAX MacAddress
           ACCESS read-only
           STATUS mandatory
           DESCRIPTION
               "Base IEEE 802 global address for the chassis."
           ::= { xChassisBasic 1 }

       basicSlot OBJECT-TYPE
           SYNTAX INTEGER
           ACCESS read-only
           STATUS mandatory
           DESCRIPTION
               "Chassis slot number (slotIndex) of the system whose 
               agent is supplying this MIB."
           ::= { xChassisBasic 2 }

       basicSlotNumber OBJECT-TYPE
           SYNTAX INTEGER
           ACCESS read-only
           STATUS mandatory
           DESCRIPTION
               "Number of slots in the chassis."
           ::= { xChassisBasic 3 }

       basicNewBase802Address OBJECT-TYPE
           SYNTAX MacAddress
           ACCESS read-write
           STATUS mandatory
           DESCRIPTION
               "New base IEEE 802 global address for the chassis.  
               Must be set in conjunction with featType 
               'changeEthernetAddress' and featKey from the MRV In-Reach 
               System MIB."
           ::= { xChassisBasic 4 }


       -- the Chassis Segment group

       -- Implementation of this group is mandatory for all MRV In-Reach
       -- Network 9000 management bus systems

       -- the Segment table

       segmentTable OBJECT-TYPE
           SYNTAX SEQUENCE OF SegmentEntry
           ACCESS not-accessible
           STATUS mandatory
           DESCRIPTION
               "A list of segment entries, one for each segment of 
               each type on the chassis."
           ::= { xSegment 1 }

       segmentEntry OBJECT-TYPE
           SYNTAX SegmentEntry
           ACCESS not-accessible
           STATUS mandatory
           DESCRIPTION
               "Values for a chassis segment."
           INDEX { segmentType, segmentIndex }
           ::= { segmentTable 1 }

       SegmentEntry ::=
           SEQUENCE {
               segmentType
                   NetworkType,
               segmentIndex
                   Letter
           }

       segmentType OBJECT-TYPE
           SYNTAX NetworkType
           ACCESS read-only
           STATUS mandatory
           DESCRIPTION
               "The segment type."
           ::= { segmentEntry 1 }

       segmentIndex OBJECT-TYPE
           SYNTAX Letter
           ACCESS read-only
           STATUS mandatory
           DESCRIPTION
               "An index value that uniquely identifies a 
               segment."
           ::= { segmentEntry 2 }


       -- the Chassis Port group

       -- Implementation of this group is mandatory for all MRV In-Reach
       -- Network 9000 management bus systems.  It describes only
       -- the local system's own ports and is intended for network
       -- ports as opposed to terminal or printer ports.

       portIOCardType OBJECT-TYPE
           SYNTAX IOType
           ACCESS read-only
           STATUS mandatory
           DESCRIPTION
               "The hardware type of the I/O card in this slot."
           ::= { xPort 1 }

       portIOCardSerialNumber OBJECT-TYPE
           SYNTAX SerialNumber
           ACCESS read-only
           STATUS mandatory
           DESCRIPTION
               "The MRV In-Reach serial number of the I/O card in this 
               slot."
           ::= { xPort 2 }

       portIOCardOperStatus OBJECT-TYPE
           SYNTAX INTEGER { unknown(1), mismatch(2), good(3) }
           ACCESS read-only
           STATUS mandatory
           DESCRIPTION
               "Status of the I/O card relative to the function 
               card in this slot."
           ::= { xPort 3 }

       -- the Port table

       portTable OBJECT-TYPE
           SYNTAX SEQUENCE OF PortEntry
           ACCESS not-accessible
           STATUS mandatory
           DESCRIPTION
               "A list of port entries, one for each port of each 
               type on the slots I/O card."
           ::= { xPort 4 }

       portEntry OBJECT-TYPE
           SYNTAX PortEntry
           ACCESS not-accessible
           STATUS mandatory
           DESCRIPTION
               "Values for an I/O card port."
           INDEX { portType, portIndex }
           ::= { portTable 1 }

       PortEntry ::=
           SEQUENCE {
               portType
                   NetworkType,
               portIndex
                   INTEGER
           }

       portType OBJECT-TYPE
           SYNTAX NetworkType
           ACCESS read-only
           STATUS mandatory
           DESCRIPTION
               "The port type."
           ::= { portEntry 1 }

       portIndex OBJECT-TYPE
           SYNTAX INTEGER
           ACCESS read-only
           STATUS mandatory
           DESCRIPTION
               "An index value that uniquely identifies a port."
           ::= { portEntry 2 }


       -- the Chassis Controller group

       -- Implementation of this group is mandatory for all MRV In-Reach
       -- Network 9000 management bus systems.  It describes only
       -- the local system's own controllers.

       -- the Controller table

       controllerTable OBJECT-TYPE
           SYNTAX SEQUENCE OF ControllerEntry
           ACCESS not-accessible
           STATUS mandatory
           DESCRIPTION
               "A list of controller entries, one for each 
               controller of each type on the local system."
           ::= { xController 1 }

       controllerEntry OBJECT-TYPE
           SYNTAX ControllerEntry
           ACCESS not-accessible
           STATUS mandatory
           DESCRIPTION
               "Values for a controller."
           INDEX { controllerType, controllerIndex }
           ::= { controllerTable 1 }

       ControllerEntry ::=
           SEQUENCE {
               controllerType
                   NetworkType,
               controllerIndex
                   INTEGER,
               controllerNetwork
                   OBJECT IDENTIFIER
           }

       controllerType OBJECT-TYPE
           SYNTAX NetworkType
           ACCESS read-only
           STATUS mandatory
           DESCRIPTION
               "The controller type."
           ::= { controllerEntry 1 }

       controllerIndex OBJECT-TYPE
           SYNTAX INTEGER
           ACCESS read-only
           STATUS mandatory
           DESCRIPTION
               "An index value that uniquely identifies a 
               controller."
           ::= { controllerEntry 2 }

       controllerNetwork OBJECT-TYPE
           SYNTAX OBJECT IDENTIFIER
           ACCESS read-write
           STATUS mandatory
           DESCRIPTION
               "The instance identifier of the first object in the 
               conceptual row entry for the segment, port, or 
               controller this controller is to use, that is, 
               segmentType, portType or controllerType."
           ::= { controllerEntry 3 }


       -- the Chassis Interface group

       -- Implementation of this group is mandatory for all MRV In-Reach
       -- Network 9000 management bus systems.  It describes only
       -- the local system's own interfaces.

       -- the Interface table

       interfaceTable OBJECT-TYPE
           SYNTAX SEQUENCE OF InterfaceEntry
           ACCESS not-accessible
           STATUS mandatory
           DESCRIPTION
               "A list of interface entries, corresponding to the 
               MIB II Interface group.  These are directly 
               equivalent to hardware network controllers, and must 
               be the lowest numbered interfaces on the system."
           ::= { xInterface 1 }

       interfaceEntry OBJECT-TYPE
           SYNTAX InterfaceEntry
           ACCESS not-accessible
           STATUS mandatory
           DESCRIPTION
               "Values for an interface."
           INDEX { interfaceIndex }
           ::= { interfaceTable 1 }

       InterfaceEntry ::=
           SEQUENCE {
               interfaceIndex
                   INTEGER,
               interfaceNetwork
                   OBJECT IDENTIFIER
           }

       interfaceIndex OBJECT-TYPE
           SYNTAX INTEGER
           ACCESS read-only
           STATUS mandatory
           DESCRIPTION
               "An index value that uniquely identifies an 
               interface.  The interface identified by a particular 
               value of this index is the same interface as 
               identified by the same value of ifIndex."
           ::= { interfaceEntry 1 }

       interfaceNetwork OBJECT-TYPE
           SYNTAX OBJECT IDENTIFIER
           ACCESS read-write
           STATUS mandatory
           DESCRIPTION
               "The instance identifier of the first object in the 
               conceptual row entry for the segment, port, or 
               controller this interface is to use, that is, 
               segmentType, portType, or controllerType."
           ::= { interfaceEntry 2 }


       -- the Chassis Boot Control group

       -- Full implementation of this group is optional for MRV In-Reach
       -- Network 9000 management bus systems.  It is fully
       -- implemented on such systems that supply cross chassis
       -- management.  All systems must implement the instance
       -- corresponding to their own slot number.

       -- the Slot Boot Control table

       slotBootControlTable OBJECT-TYPE
           SYNTAX SEQUENCE OF SlotBootControlEntry
           ACCESS not-accessible
           STATUS mandatory
           DESCRIPTION
               "A list of slot boot control entries."
           ::= { xSlotBootControl 1 }

       slotBootControlEntry OBJECT-TYPE
           SYNTAX SlotBootControlEntry
           ACCESS not-accessible
           STATUS mandatory
           DESCRIPTION
               "Values for a chassis slot."
           INDEX { slotBootControlSlot, slotBootControlIndex }
           ::= { slotBootControlTable 1 }

       SlotBootControlEntry ::=
           SEQUENCE {
               slotBootControlSlot
                   INTEGER,
               slotBootControlIndex
                   INTEGER,
               slotBootControlStatus
                   INTEGER,
               slotBootControlController
                   OBJECT IDENTIFIER,
               slotBootControlNetwork
                   OBJECT IDENTIFIER,
               slotBootControlMopFile
                   DisplayString,
               slotBootControlInternetFile
                   DisplayString,
               slotBootControlInternetAddress
                   IpAddress,
               slotBootControlInternetServer
                   IpAddress,
               slotBootControlInternetGateway
                   IpAddress,
               slotBootControlInternetDelimiter
                   DisplayString
      }

       slotBootControlSlot OBJECT-TYPE
           SYNTAX INTEGER
           ACCESS read-only
           STATUS mandatory
           DESCRIPTION
               "An index value that uniquely identifies a slot, 
               defined the same as slotIndex."
           ::= { slotBootControlEntry 1 }

       slotBootControlIndex OBJECT-TYPE
           SYNTAX INTEGER
           ACCESS read-only
           STATUS mandatory
           DESCRIPTION
               "An index value that uniquely identifies a boot 
               control entry, from 1 to the number of entries for 
               the slot."
           ::= { slotBootControlEntry 2 }

       slotBootControlStatus OBJECT-TYPE
           SYNTAX INTEGER { disabled(1), enabled(2) }
           ACCESS read-write
           STATUS mandatory
           DESCRIPTION
               "The status of the entry.  Set to 'disabled' to 
               disable the entry."
           DEFVAL { enabled }
           ::= { slotBootControlEntry 3 }

       slotBootControlController OBJECT-TYPE
           SYNTAX OBJECT IDENTIFIER
           ACCESS read-write
           STATUS mandatory
           DESCRIPTION
               "The instance identifier of the first object in the 
               conceptual row entry for the controller this entry 
               selects for bootstrap operation, that is, 
               controllerType.  This entry must be compatible with 
               slotBootControlNetwork, including being of the same 
               network type.  The value 0.0 indicates default 
               action."
           DEFVAL { { 0 0 } }  -- 0.0
           ::= { slotBootControlEntry 4 }

       slotBootControlNetwork OBJECT-TYPE
           SYNTAX OBJECT IDENTIFIER
           ACCESS read-write
           STATUS mandatory
           DESCRIPTION
               "The instance identifier of the first object in the 
               conceptual row entry for the segment or port this                entry selects for bootstrap operation, that is, 
               segmentType or portType.  This entry must be 
               compatible with slotBootControlController, including 
               being of the same network type.  The value 0.0 
               indicates default action."
           DEFVAL { { 0 0 } }  -- 0.0
           ::= { slotBootControlEntry 5 }

       slotBootControlMopFile OBJECT-TYPE
           SYNTAX DisplayString (SIZE (0..15))
           ACCESS read-write
           STATUS mandatory
           DESCRIPTION
               "The software file name to request for down-line 
               load of the server via MOP or XMOP."
           DEFVAL { '00'h }  -- the null string
           ::= { slotBootControlEntry 6 }

       slotBootControlInternetFile OBJECT-TYPE
           SYNTAX DisplayString (SIZE (0..64))
           ACCESS read-write
           STATUS mandatory
           DESCRIPTION
               "The filename to request when loading an image via 
               TFTP."
           DEFVAL { '00'h }  -- the null string
           ::= { slotBootControlEntry 7 }

       slotBootControlInternetAddress OBJECT-TYPE
           SYNTAX IpAddress
           ACCESS read-write
           STATUS mandatory
           DESCRIPTION
               "The internet address of the system is to use for 
               itself when loading via TFTP.  The value 0.0.0.0 
               indicates default action."
           DEFVAL { 0 }
           ::= { slotBootControlEntry 8 }

       slotBootControlInternetServer OBJECT-TYPE
           SYNTAX IpAddress
           ACCESS read-write
           STATUS mandatory
           DESCRIPTION
               "The internet address of the server to use when 
               loading an image via TFTP.  The value 0.0.0.0 
               indicates default action."
           DEFVAL { 0 }
           ::= { slotBootControlEntry 9 }

       slotBootControlInternetGateway OBJECT-TYPE
           SYNTAX IpAddress
           ACCESS read-write
           STATUS mandatory
           DESCRIPTION
               "The internet address of the gateway to use when 
               loading an image via TFTP.  The value 0.0.0.0 
               indicates default action."
           DEFVAL { 0 }
           ::= { slotBootControlEntry 10 }

       slotBootControlInternetDelimiter OBJECT-TYPE
           SYNTAX DisplayString (SIZE (0..1))
           ACCESS read-write
           STATUS mandatory
           DESCRIPTION
               "The character separating the load file directory name  
               from the file name."
           DEFVAL { '00'h }  -- the null string
           ::= { slotBootControlEntry 11 }

       -- the Slot Boot Control Flag table

       -- Entries in this table are directly connected to a 
       -- particular slotBootControlIndex, and are created and 
       -- deleted together with that entry.

       -- By convention, this table contains flags in recurring
       -- groups of three operations for each protocol.  Adding
       -- a new protocol will add three new objects in the same
       -- order of operations.

       slotBootControlFlagTable OBJECT-TYPE
           SYNTAX SEQUENCE OF SlotBootControlFlagEntry
           ACCESS not-accessible
           STATUS mandatory
           DESCRIPTION
               "A list of slot boot control source flag entries."
           ::= { xSlotBootControl 2 }

       slotBootControlFlagEntry OBJECT-TYPE
           SYNTAX SlotBootControlFlagEntry
           ACCESS not-accessible
           STATUS mandatory
           DESCRIPTION
               "Values for a boot control flag."
           INDEX { slotBootControlSlot, slotBootControlIndex }
           ::= { slotBootControlFlagTable 1 }

       SlotBootControlFlagEntry ::=
           SEQUENCE {
               slotBootControlFlagLoadBootpTftp
                   INTEGER,
               slotBootControlFlagParamBootpTftp
                   INTEGER,
               slotBootControlFlagDumpBootpTftp
                   INTEGER,
               slotBootControlFlagLoadTftpDirect
                   INTEGER,
               slotBootControlFlagParamTftpDirect
                   INTEGER,
               slotBootControlFlagDumpTftpDirect
                   INTEGER,
               slotBootControlFlagLoadLocal
                   INTEGER,
               slotBootControlFlagParamLocal
                   INTEGER,
               slotBootControlFlagDumpLocal
                   INTEGER,
               slotBootControlFlagLoadMop
                   INTEGER,
               slotBootControlFlagParamMop
                   INTEGER,
               slotBootControlFlagDumpMop
                   INTEGER,
               slotBootControlFlagLoadXmop
                   INTEGER,
               slotBootControlFlagParamXmop
                   INTEGER,
               slotBootControlFlagDumpXmop
                   INTEGER,
               slotBootControlFlagLoadRarpTftp
                   INTEGER,
               slotBootControlFlagParamRarpTftp
                   INTEGER,
               slotBootControlFlagDumpRarpTftp
                   INTEGER
           }

       slotBootControlFlagLoadBootpTftp OBJECT-TYPE
           SYNTAX INTEGER { disabled(1), enabled(2) }
           ACCESS read-write
           STATUS mandatory
           DESCRIPTION
               "Control for performing load over BOOTP/TFTP."
           ::= { slotBootControlFlagEntry 1 }

       slotBootControlFlagParamBootpTftp OBJECT-TYPE
           SYNTAX INTEGER { disabled(1), enabled(2) }
           ACCESS read-write
           STATUS mandatory
           DESCRIPTION
               "Control for performing parameter load over 
               BOOTP/TFTP."
           ::= { slotBootControlFlagEntry 2 }

       slotBootControlFlagDumpBootpTftp OBJECT-TYPE
           SYNTAX INTEGER { disabled(1), enabled(2) }
           ACCESS read-write
           STATUS mandatory
           DESCRIPTION
               "Control for performing dump over BOOTP/TFTP."
           ::= { slotBootControlFlagEntry 3 }

       slotBootControlFlagLoadTftpDirect OBJECT-TYPE
           SYNTAX INTEGER { disabled(1), enabled(2) }
           ACCESS read-write
           STATUS mandatory
           DESCRIPTION
               "Control for performing load over direct TFTP."
           ::= { slotBootControlFlagEntry 4 }

       slotBootControlFlagParamTftpDirect OBJECT-TYPE
           SYNTAX INTEGER { disabled(1), enabled(2) }
           ACCESS read-write
           STATUS mandatory
           DESCRIPTION
               "Control for performing parameter load over direct 
               TFTP."
           ::= { slotBootControlFlagEntry 5 }

       slotBootControlFlagDumpTftpDirect OBJECT-TYPE
           SYNTAX INTEGER { disabled(1), enabled(2) }
           ACCESS read-write
           STATUS mandatory
           DESCRIPTION
               "Control for performing dump over direct TFTP."
           ::= { slotBootControlFlagEntry 6 }

       slotBootControlFlagLoadLocal OBJECT-TYPE
           SYNTAX INTEGER { disabled(1), enabled(2) }
           ACCESS read-write
           STATUS mandatory
           DESCRIPTION
               "Control for performing load from a local device."
           ::= { slotBootControlFlagEntry 7 }

       slotBootControlFlagParamLocal OBJECT-TYPE
           SYNTAX INTEGER { disabled(1), enabled(2) }
           ACCESS read-write
           STATUS mandatory
           DESCRIPTION
               "Control for performing parameter load from a local 
               device."
           ::= { slotBootControlFlagEntry 8 }

       slotBootControlFlagDumpLocal OBJECT-TYPE
           SYNTAX INTEGER { disabled(1), enabled(2) }
           ACCESS read-write
           STATUS mandatory
           DESCRIPTION
               "Control for performing dump from a local device."
           ::= { slotBootControlFlagEntry 9 }

       slotBootControlFlagLoadMop OBJECT-TYPE
           SYNTAX INTEGER { disabled(1), enabled(2) }
           ACCESS read-write
           STATUS mandatory
           DESCRIPTION
               "Control for performing load over Digital's MOP."
           ::= { slotBootControlFlagEntry 10 }

       slotBootControlFlagParamMop OBJECT-TYPE
           SYNTAX INTEGER { disabled(1), enabled(2) }
           ACCESS read-write
           STATUS mandatory
           DESCRIPTION
               "Control for performing parameter load over 
               Digital's MOP."
           ::= { slotBootControlFlagEntry 11 }

       slotBootControlFlagDumpMop OBJECT-TYPE
           SYNTAX INTEGER { disabled(1), enabled(2) }
           ACCESS read-write
           STATUS mandatory
           DESCRIPTION
               "Control for performing dump over Digital's MOP."
           ::= { slotBootControlFlagEntry 12 }

       slotBootControlFlagLoadXmop OBJECT-TYPE
           SYNTAX INTEGER { disabled(1), enabled(2) }
           ACCESS read-write
           STATUS mandatory
           DESCRIPTION
               "Control for performing load over MRV In-Reach extended 
               MOP."
           ::= { slotBootControlFlagEntry 13 }

       slotBootControlFlagParamXmop OBJECT-TYPE
           SYNTAX INTEGER { disabled(1), enabled(2) }
           ACCESS read-write
           STATUS mandatory
           DESCRIPTION
               "Control for performing parameter load over MRV In-Reach 
               extended MOP."
           ::= { slotBootControlFlagEntry 14 }

       slotBootControlFlagDumpXmop OBJECT-TYPE
           SYNTAX INTEGER { disabled(1), enabled(2) }
           ACCESS read-write
           STATUS mandatory
           DESCRIPTION
               "Control for performing dump over MRV In-Reach extended 
               MOP."
           ::= { slotBootControlFlagEntry 15 }

       slotBootControlFlagLoadRarpTftp OBJECT-TYPE
           SYNTAX INTEGER { disabled(1), enabled(2) }
           ACCESS read-write
           STATUS mandatory
           DESCRIPTION
               "Control for performing load over RARP/TFTP."
           ::= { slotBootControlFlagEntry 16 }

       slotBootControlFlagParamRarpTftp OBJECT-TYPE
           SYNTAX INTEGER { disabled(1), enabled(2) }
           ACCESS read-write
           STATUS mandatory
           DESCRIPTION
               "Control for performing parameter load over 
               RARP/TFTP."
           ::= { slotBootControlFlagEntry 17 }

       slotBootControlFlagDumpRarpTftp OBJECT-TYPE
           SYNTAX INTEGER { disabled(1), enabled(2) }
           ACCESS read-write
           STATUS mandatory
           DESCRIPTION
               "Control for performing dump over RARP/TFTP."
           ::= { slotBootControlFlagEntry 18 }


       slotBootControlStorageTable OBJECT-TYPE
           SYNTAX SEQUENCE OF SlotBootControlStorageEntry
           ACCESS not-accessible 
           STATUS mandatory 
           DESCRIPTION
               "A list of slot boot control Storage entries."
           ::= { xSlotBootControl 3 }
                
       slotBootControlStorageEntry OBJECT-TYPE
           SYNTAX SlotBootControlStorageEntry 
           ACCESS not-accessible
           STATUS mandatory 
           DESCRIPTION 
               "Values for a chassis slot."
           INDEX { slotBootControlStorageClientSlot,  slotBootControlStorageServerSlot}
           ::= { slotBootControlStorageTable 1 }
                
       SlotBootControlStorageEntry ::= 
           SEQUENCE {
               slotBootControlStorageClientSlot 
                   INTEGER, 
               slotBootControlStorageServerSlot
                   INTEGER, 
               slotBootControlStorageStatus
                   INTEGER,
               slotBootControlStorageFailures
                   Counter
              }

       slotBootControlStorageClientSlot OBJECT-TYPE
           SYNTAX INTEGER 
           ACCESS read-only 
           STATUS mandatory 
           DESCRIPTION 
               "An index value that uniquely identifies a slot,
               defined the same as slotIndex."
           ::= { slotBootControlStorageEntry 1 }
             
       slotBootControlStorageServerSlot OBJECT-TYPE
           SYNTAX INTEGER
           ACCESS read-only
           STATUS mandatory 
           DESCRIPTION    
               "An index value that uniquely identifies the slot in
               which the Storage record resides, with the same values
               as slotIndex."
           ::= { slotBootControlStorageEntry 2 } 
            
       slotBootControlStorageStatus OBJECT-TYPE
           SYNTAX INTEGER { present(1), failed(2), ok(3), notpresent(4) }
           ACCESS read-only
           STATUS mandatory
           DESCRIPTION 
               "The status of the entry."
           ::= { slotBootControlStorageEntry 3 } 

       slotBootControlStorageFailures OBJECT-TYPE
           SYNTAX Counter
           ACCESS read-only
           STATUS mandatory
           DESCRIPTION 
               "The number of times a read from or write to a given 
               Storage location failed"
           ::= { slotBootControlStorageEntry 4 } 


       -- the Chassis Slot group

       -- Implementation of this group is optional for MRV In-Reach
       -- Network 9000 management bus systems.  It is implemented
       -- on such systems that supply cross chassis management.

       -- the Slot table

       slotTable OBJECT-TYPE
           SYNTAX SEQUENCE OF SlotEntry
           ACCESS not-accessible
           STATUS mandatory
           DESCRIPTION
               "A list of slot entries."
           ::= { xSlot 1 }

       slotEntry OBJECT-TYPE
           SYNTAX SlotEntry
           ACCESS not-accessible
           STATUS mandatory
           DESCRIPTION
               "Values for a chassis slot."
           INDEX { slotIndex }
           ::= { slotTable 1 }

       SlotEntry ::=
           SEQUENCE {
               slotIndex
                   INTEGER,
               slotAdminAction
                   INTEGER,
               slotOperStatus
                   INTEGER,
               slotSecondsSinceReset
                   Gauge,
               slotHardwareType
                   HardwareType,
               slotHardwareSerialNumber
                   SerialNumber,
               slotHardwareRevision
                   INTEGER,
               slotIOCardType
                   IOType,
               slotIOCardSerialNumber
                   SerialNumber,
               slotIOCardOperStatus
                   INTEGER,
               slotBootstrapFirmwareRevision
                   INTEGER,
               slotElementalFirmwareRevision
                   INTEGER,
               slotMemorySize
                   INTEGER,
               slotLedNumber
                   Gauge,
               slotLedStatus
                   OCTET STRING,
               slotBase802Address
                   MacAddress,
               slotIpAddress
                   IpAddress,
               slotPlus5Status
                   INTEGER,
               slotPlus12Status
                   INTEGER,
               slotMinus12Status
                   INTEGER,
               slotPlus5Watts
                   Gauge,
               slotPlus12Watts
                   Gauge,
               slotMinus12Watts
                   Gauge,
               slotIOCardHardwareVersion
                   INTEGER,
               slotRestoreNVS
                   INTEGER,
               slotDefaultNVS
                   INTEGER
                   }

       slotIndex OBJECT-TYPE
           SYNTAX INTEGER
           ACCESS read-only
           STATUS mandatory
           DESCRIPTION
               "An index value that uniquely identifies a slot, in 
               the range 0 to basicSlotNumber, where the value 0 
               indicates the same slot as basicSlot.  As the 
               objects found at instance zero are duplicates, that 
               instance does not appear in responses a get-next, 
               that is, the lowest numbered slotIndex returned by 
               get-next is 1."
           ::= { slotEntry 1 }

       slotAdminAction OBJECT-TYPE
           SYNTAX INTEGER { ready(1), reset(2), resetHold(3) }
           ACCESS read-write
           STATUS mandatory
           DESCRIPTION
               "Control to cause reset of the system in a slot.  
               When read, the value is always 'ready'.  Setting to 
               'reset' or 'resetHold' causes a single attempt to 
               take that action, but does not ensure transition to 
               any particular value of slotOperStatus."
           ::= { slotEntry 2 }

       slotOperStatus OBJECT-TYPE
           SYNTAX INTEGER { loadRequested(1),
                            loading(2),
                            dumpRequested(3),
                            dumping(4),
                            paramRequested(5),
                            paramLoading(6),
                            running(7),
                            initializing(8),     -- ROM wait
                            attended(9),         -- in config menu
                            internal10(10),      -- read chas info
                            internal11(11),      -- read config
                            inhibited(12),       -- run inhibited
                            maxserverCard(13),
                            invalidConfigStorage(14), -- suspended
                            securityLockdown(15),

                            resetHold(64),       -- SCM, reset
                            selfTest(65),        -- SCM, diag.
                            notResponding(66),   -- SCM running
                            broken(67),          -- SCM, failed
                            unknown(68),         -- SCM
                            notApplicable(69)    -- SCM
                           }
           ACCESS read-only
           STATUS mandatory
           DESCRIPTION
               "Relative to the chassis, the current operating 
               status of the system in the slot."
           ::= { slotEntry 3 }

       slotSecondsSinceReset OBJECT-TYPE
           SYNTAX Gauge
           ACCESS read-only
           STATUS mandatory
           DESCRIPTION
               "The number of seconds since the system in the slot 
               was last reset by hardware or software."
           ::= { slotEntry 4 }

       slotHardwareType OBJECT-TYPE
           SYNTAX HardwareType
           ACCESS read-only
           STATUS mandatory
           DESCRIPTION
               "The type of hardware in the slot."
           ::= { slotEntry 5 }

       slotHardwareSerialNumber OBJECT-TYPE
           SYNTAX SerialNumber
           ACCESS read-only
           STATUS mandatory
           DESCRIPTION
               "The MRV In-Reach serial number of the function card 
               hardware in this slot."
           ::= { slotEntry 6 }

       slotHardwareRevision OBJECT-TYPE
           SYNTAX INTEGER
           ACCESS read-only
           STATUS mandatory
           DESCRIPTION
               "This revision level of the function card hardware 
               in the slot."
           ::= { slotEntry 7 }

       slotIOCardType OBJECT-TYPE
           SYNTAX IOType
           ACCESS read-only
           STATUS mandatory
           DESCRIPTION
               "The hardware type of the I/O card in this slot."
           ::= { slotEntry 8 }

       slotIOCardSerialNumber OBJECT-TYPE
           SYNTAX SerialNumber
           ACCESS read-only
           STATUS mandatory
           DESCRIPTION
               "The MRV In-Reach serial number of the I/O card in this 
               slot."
           ::= { slotEntry 9 }

       slotIOCardOperStatus OBJECT-TYPE
           SYNTAX INTEGER { unknown(1), mismatch(2), good(3),
                            notApplicable(4) }
           ACCESS read-only
           STATUS mandatory
           DESCRIPTION
               "Status of the I/O card relative to the function 
               card in this slot."
           ::= { slotEntry 10 }

       slotBootstrapFirmwareRevision OBJECT-TYPE
           SYNTAX INTEGER
           ACCESS read-only
           STATUS mandatory
           DESCRIPTION
               "The firmware revision level of the bootstrap ROM 
               installed in the system in the slot."
           ::= { slotEntry 11 }

       slotElementalFirmwareRevision OBJECT-TYPE
           SYNTAX INTEGER
           ACCESS read-only
           STATUS mandatory
           DESCRIPTION
               "The firmware revision level of the minimal function 
               ROM (management bus microprocessor) installed in the 
               system in the slot."
           ::= { slotEntry 12 }

       slotMemorySize OBJECT-TYPE
           SYNTAX INTEGER
           ACCESS read-only
           STATUS mandatory
           DESCRIPTION
               "The number of bytes of memory installed in the 
               system in the slot."
           ::= { slotEntry 13 }

       slotLedNumber OBJECT-TYPE
           SYNTAX Gauge
           ACCESS read-only
           STATUS mandatory
           DESCRIPTION
               "The number of LEDs on the system in the slot.  A 
               value of 0 indicates none, unknown, or status not 
               readable."
           ::= { slotEntry 14 }

       slotLedStatus OBJECT-TYPE
           SYNTAX OCTET STRING (SIZE (0..9))
           ACCESS read-only
           STATUS mandatory
           DESCRIPTION
               "The status of the LEDs displayed on the front and 
               back of the system in the slot.  The first bit is 
               the high-order bit of the first byte of the value, 
               proceeding to the low-order bit, then to then next 
               byte.  On the system hardware, the first LED is at 
               the top, left, front, proceeding left to right, top 
               to bottom, and front to back."
           ::= { slotEntry 15 }

       slotBase802Address OBJECT-TYPE
           SYNTAX MacAddress
           ACCESS read-only
           STATUS mandatory
           DESCRIPTION
               "Base IEEE 802 global address for the slot."
           ::= { slotEntry 16 }

       slotIpAddress OBJECT-TYPE
           SYNTAX IpAddress
           ACCESS read-only
           STATUS mandatory
           DESCRIPTION
               "An internet address to which the system in this 
               slot might respond.  May be one of many."
           ::= { slotEntry 17 }

       slotPlus5Status OBJECT-TYPE
           SYNTAX INTEGER { unknown(1), broken(2), good(3) }
           ACCESS read-only
           STATUS mandatory
           DESCRIPTION
               "Status of the +5 volt power to the slot."
           ::= { slotEntry 18 }

       slotPlus12Status OBJECT-TYPE
           SYNTAX INTEGER { unknown(1), broken(2), good(3) }
           ACCESS read-only
           STATUS mandatory
           DESCRIPTION
               "Status of the +12 volt power to the slot."
           ::= { slotEntry 19 }

       slotMinus12Status OBJECT-TYPE
           SYNTAX INTEGER { unknown(1), broken(2), good(3) }
           ACCESS read-only
           STATUS mandatory
           DESCRIPTION
               "Status of the -12 volt power to the slot."
           ::= { slotEntry 20 }

       slotPlus5Watts OBJECT-TYPE
           SYNTAX Gauge
           ACCESS read-only
           STATUS mandatory
           DESCRIPTION
               "Tenths of watts of +5 volt power currently drawn by 
               the slot."
           ::= { slotEntry 21 }

       slotPlus12Watts OBJECT-TYPE
           SYNTAX Gauge
           ACCESS read-only
           STATUS mandatory
           DESCRIPTION
               "Tenths of watts of +12 volt power currently drawn 
               by the slot."
           ::= { slotEntry 22 }

       slotMinus12Watts OBJECT-TYPE
           SYNTAX Gauge
           ACCESS read-only
           STATUS mandatory
           DESCRIPTION
               "Tenths of watts of -12 volt power currently drawn 
               by the slot."
           ::= { slotEntry 23 }

       slotIOCardHardwareVersion OBJECT-TYPE
           SYNTAX INTEGER
           ACCESS read-only
           STATUS mandatory
           DESCRIPTION
               "Version number of I/O card in the slot."
           ::= { slotEntry 24 }

       slotRestoreNVS OBJECT-TYPE
           SYNTAX INTEGER { ready(1), execute(2) }
           ACCESS read-write
           STATUS mandatory
           DESCRIPTION
               "Setting to 'execute' causes the non-volatile 
               parameter storage to be restored from an installed 
               memory card.  Setting to 'ready' has no effect."
           ::= { slotEntry 25 }

       slotDefaultNVS OBJECT-TYPE
           SYNTAX INTEGER { ready(1), execute(2) }
           ACCESS read-write
           STATUS mandatory
           DESCRIPTION
               "Setting to 'execute' causes non-volatile stored 
               parameters to be reset to factory defaults.  Setting 
               to 'ready' has no effect."
           ::= { slotEntry 26 }


       -- the Slot Bootstrap Status table

       slotBootTable OBJECT-TYPE
           SYNTAX SEQUENCE OF SlotBootEntry
           ACCESS not-accessible
           STATUS mandatory
           DESCRIPTION
               "A list of slot bootstrap status entries.  A given 
               slot has an entry in this table only when 
               slotOperStatus is one of:  loadRequested, loading, 
               dumpRequested, dumping, paramRequested, 
               paramLoading"
           ::= { xSlot 2 }

       slotBootEntry OBJECT-TYPE
           SYNTAX SlotBootEntry
           ACCESS not-accessible
           STATUS mandatory
           DESCRIPTION
               "Bootstrap status values for a chassis slot."
           INDEX { slotBootIndex }
           ::= { slotBootTable 1 }

       SlotBootEntry ::=
           SEQUENCE {
               slotBootIndex
                   INTEGER,
               slotBootIfIndex
                   INTEGER,
               slotBootNetwork
                   OBJECT IDENTIFIER,
               slotBootProtocol
                   INTEGER,
               slotBoot802Address
                   MacAddress,
               slotBootAddressType
                   AddressType,
               slotBootAddress
                   OCTET STRING,
               slotBootServerAddressType
                   AddressType,
               slotBootServerAddress
                   OCTET STRING,
               slotBootGatewayAddress
                   IpAddress,
               slotBootFileName
                   DisplayString,
               slotBootBlockNumber
                   Gauge,
               slotBootCrashCode
                   OCTET STRING
           }

       slotBootIndex OBJECT-TYPE
           SYNTAX INTEGER
           ACCESS read-only
           STATUS mandatory
           DESCRIPTION
               "An index value that uniquely identifies a slot, 
               defined the same as slotIndex."
           ::= { slotBootEntry 1 }

       slotBootIfIndex OBJECT-TYPE
           SYNTAX INTEGER
           ACCESS read-only
           STATUS mandatory
           DESCRIPTION
               "An index value that uniquely identifies the 
               interface in use for bootstrap functions.  The 
               interface identified by a particular value of this 
               index is the same interface as identified by the 
               same value of ifIndex."
           ::= { slotBootEntry 2 }

       slotBootNetwork OBJECT-TYPE
           SYNTAX OBJECT IDENTIFIER
           ACCESS read-only
           STATUS mandatory
           DESCRIPTION
               "The instance identifier of the first object in the 
               conceptual row entry for the segment or port this 
               interface is using, that is, segmentType or 
               portType."
           ::= { slotBootEntry 3 }

       slotBootProtocol OBJECT-TYPE
           SYNTAX INTEGER { other(1), unknown(2), mop(3), xmop(4),
                            rarpTftp(5), bootpTftp(6), tftp(7),
                            local(8), managementBus(9) }
           ACCESS read-only
           STATUS mandatory
           DESCRIPTION
               "The protocol in use for bootstrap operation."
           ::= { slotBootEntry 4 }

       slotBoot802Address OBJECT-TYPE
           SYNTAX MacAddress
           ACCESS read-only
           STATUS mandatory
           DESCRIPTION
               "IEEE 802 global address in use for bootstrap 
               operation."
           ::= { slotBootEntry 5 }

       slotBootAddressType OBJECT-TYPE
           SYNTAX AddressType
           ACCESS read-only
           STATUS mandatory
           DESCRIPTION
               "The type of network address contained in 
               slotBootAddress."
           ::= { slotBootEntry 6 }

       slotBootAddress OBJECT-TYPE
           SYNTAX OCTET STRING (SIZE (0..6))
           ACCESS read-only
           STATUS mandatory
           DESCRIPTION
               "The network address the system in the slot is using 
               to identify itself for bootstrap operation."
           ::= { slotBootEntry 7 }

       slotBootServerAddressType OBJECT-TYPE
           SYNTAX AddressType
           ACCESS read-only
           STATUS mandatory
           DESCRIPTION
               "The type of network address contained in 
               slotBootServerAddress."
           ::= { slotBootEntry 8 }

       slotBootServerAddress OBJECT-TYPE
           SYNTAX OCTET STRING (SIZE (0..6))
           ACCESS read-only
           STATUS mandatory
           DESCRIPTION
               "The network address of the system supplying 
               bootstrap services to the system in the slot."
           ::= { slotBootEntry 9 }

       slotBootGatewayAddress OBJECT-TYPE
           SYNTAX IpAddress
           ACCESS read-only
           STATUS mandatory
           DESCRIPTION
               "The internet address of the router in use for 
               bootstrap operation."
           ::= { slotBootEntry 10 }

       slotBootFileName OBJECT-TYPE
           SYNTAX DisplayString (SIZE (0..64))
           ACCESS read-only
           STATUS mandatory
           DESCRIPTION
               "The full name of the file in use for bootstrap 
               operation."
           ::= { slotBootEntry 11 }

       slotBootBlockNumber OBJECT-TYPE
           SYNTAX Gauge
           ACCESS read-only
           STATUS mandatory
           DESCRIPTION
               "The current block number being transferred for 
               bootstrap operation, zero if unknown or not 
               applicable."
           ::= { slotBootEntry 12 }

       slotBootCrashCode OBJECT-TYPE
           SYNTAX OCTET STRING (SIZE (0..4))
           ACCESS read-only
           STATUS mandatory
           DESCRIPTION
               "If slotOperStatus is dumpRequested or dumping, a 
               code number to identify the crash reason; otherwise 
               zero length."
           ::= { slotBootEntry 13 }


       -- the Slot Controller table

       slotControllerTable OBJECT-TYPE
           SYNTAX SEQUENCE OF SlotControllerEntry
           ACCESS not-accessible
           STATUS mandatory
           DESCRIPTION
               "A list of controller entries, one for each 
               controller of each type in each slot."
           ::= { xSlot 3 }

       slotControllerEntry OBJECT-TYPE
           SYNTAX SlotControllerEntry
           ACCESS not-accessible
           STATUS mandatory
           DESCRIPTION
               "Values for a controller."
           INDEX { slotControllerType,
                   slotControllerIndex }
           ::= { slotControllerTable 1 }

       SlotControllerEntry ::=
           SEQUENCE {
               slotControllerType
                   NetworkType,
               slotControllerIndex
                   INTEGER,
               slotControllerNetwork
                   OBJECT IDENTIFIER
           }

       slotControllerType OBJECT-TYPE
           SYNTAX NetworkType
           ACCESS read-only
           STATUS mandatory
           DESCRIPTION
               "The controller type."
           ::= { slotControllerEntry 1 }

       slotControllerIndex OBJECT-TYPE
           SYNTAX INTEGER
           ACCESS read-only
           STATUS mandatory
           DESCRIPTION
               "An index value that uniquely identifies a 
               controller."
           ::= { slotControllerEntry 2 }

       slotControllerNetwork OBJECT-TYPE
           SYNTAX OBJECT IDENTIFIER
           ACCESS read-only
           STATUS mandatory
           DESCRIPTION
               "The instance identifier of the first object in the 
               conceptual row entry for the segment or port this 
               controller is to use, that is, segmentType or 
               portType."
           ::= { slotControllerEntry 3 }


       -- the Chassis Power Supply group

       -- Implementation of this group is optional for MRV In-Reach
       -- Network 9000 management bus systems.  It is implemented
       -- on such systems that supply full chassis management.

       -- the Power Supply table

       powerSupplyTable OBJECT-TYPE
           SYNTAX SEQUENCE OF PowerSupplyEntry
           ACCESS not-accessible
           STATUS mandatory
           DESCRIPTION
               "A list of power supply entries."
           ::= { xPowerSupply 1 }

       powerSupplyEntry OBJECT-TYPE
           SYNTAX PowerSupplyEntry
           ACCESS not-accessible
           STATUS mandatory
           DESCRIPTION
               "Values for a chassis power supply."
           INDEX { powerSupplyIndex }
           ::= { powerSupplyTable 1 }

       PowerSupplyEntry ::=
           SEQUENCE {
               powerSupplyIndex
                   INTEGER,
               powerSupplyAdminAction
                   INTEGER,
               powerSupplyFirmwareVersion
                   INTEGER,
               powerSupplyRedundancyStatus
                   INTEGER,
               powerSupplyPlus5Status
                   INTEGER,
               powerSupplyPlus12Status
                   INTEGER,
               powerSupplyMinus12Status
                   INTEGER,
               powerSupplyThermalWarningStatus
                   INTEGER,
               powerSupplyThermalShutdownStatus
                   INTEGER,
               powerSupplyFanStatus
                   INTEGER,
               powerSupplyHardwareInhibitStatus
                   INTEGER,
               powerSupplyPlus5History
                   INTEGER,
               powerSupplyPlus12History
                   INTEGER,
               powerSupplyMinus12History
                   INTEGER,
               powerSupplyThermalWarningHistory
                   INTEGER,
               powerSupplyThermalShutdownHistory
                   INTEGER,
               powerSupplyFanHistory
                   INTEGER,
               powerSupplyHardwareInhibitHistory
                   INTEGER,
               powerSupplyPlus5Volts
                   Gauge,
               powerSupplyPlus12Volts
                   Gauge,
               powerSupplyMinus12Volts
                   Gauge,
               powerSupplyWatts
                   Gauge,
               powerSupplyWattsMax
                   Gauge,
               powerSupplyChassisWatts
                   Gauge,
               powerSupplyChassisWattsMax
                   Gauge,
               powerSupplyHardwareType
                   INTEGER
           }

       powerSupplyIndex OBJECT-TYPE
           SYNTAX INTEGER
           ACCESS read-only
           STATUS mandatory
           DESCRIPTION
               "An index value that uniquely identifies a power 
               supply, in the range 1 to the number of power supply 
               slots in the chassis."
           ::= { powerSupplyEntry 1 }

       powerSupplyAdminAction OBJECT-TYPE
           SYNTAX INTEGER { ready(1), reset(2), resetHold(3) }
           ACCESS read-write
           STATUS mandatory
           DESCRIPTION
               "Control to cause reset of the power supply.  When 
               read, the value is always 'ready'.  Setting to 
               'reset' or 'resetHold' causes a single attempt to 
               take that action, but does not ensure transition to 
               any particular value of 
               powerSupplyRedundancyStatus."
           ::= { powerSupplyEntry 2 }

       powerSupplyFirmwareVersion OBJECT-TYPE
           SYNTAX INTEGER
           ACCESS read-only
           STATUS mandatory
           DESCRIPTION
               "Version number of power supply firmware."
           ::= { powerSupplyEntry 3 }

       powerSupplyRedundancyStatus OBJECT-TYPE
           SYNTAX INTEGER { unknown(1), disabled(2),
                            redundant(3), engaged(4) }
           ACCESS read-only
           STATUS mandatory
           DESCRIPTION
               "The current redundancy status of the power 
               supply."
           ::= { powerSupplyEntry 4 }

       powerSupplyPlus5Status OBJECT-TYPE
           SYNTAX INTEGER { unknown(1), good(2), broken(3) }
           ACCESS read-only
           STATUS mandatory
           DESCRIPTION
               "Status of the +5 volt power from the power 
               supply."
           ::= { powerSupplyEntry 5 }

       powerSupplyPlus12Status OBJECT-TYPE
           SYNTAX INTEGER { unknown(1), good(2), broken(3) }
           ACCESS read-only
           STATUS mandatory
           DESCRIPTION
               "Status of the +12 volt power from the power 
               supply."
           ::= { powerSupplyEntry 6 }

       powerSupplyMinus12Status OBJECT-TYPE
           SYNTAX INTEGER { unknown(1), good(2), broken(3) }
           ACCESS read-only
           STATUS mandatory
           DESCRIPTION
               "Status of the -12 volt power from the power 
               supply."
           ::= { powerSupplyEntry 7 }

       powerSupplyThermalWarningStatus OBJECT-TYPE
           SYNTAX INTEGER { unknown(1), good(2), broken(3) }
           ACCESS read-only
           STATUS mandatory
           DESCRIPTION
               "The current thermal warning status of the power 
               supply."
           ::= { powerSupplyEntry 8 }

       powerSupplyThermalShutdownStatus OBJECT-TYPE
           SYNTAX INTEGER { unknown(1), good(2), broken(3) }
           ACCESS read-only
           STATUS mandatory
           DESCRIPTION
               "The current thermal shutdown status of the power 
               supply."
           ::= { powerSupplyEntry 9 }

       powerSupplyFanStatus OBJECT-TYPE
           SYNTAX INTEGER { unknown(1), good(2), broken(3) }
           ACCESS read-only
           STATUS mandatory
           DESCRIPTION
               "The current status of the power supply's fan."
           ::= { powerSupplyEntry 10 }

       powerSupplyHardwareInhibitStatus OBJECT-TYPE
           SYNTAX INTEGER { unknown(1), good(2), broken(3) }
           ACCESS read-only
           STATUS mandatory
           DESCRIPTION
               "The current status of the power supply's hardware 
               inhibit."
           ::= { powerSupplyEntry 11 }

       powerSupplyPlus5History OBJECT-TYPE
           SYNTAX INTEGER { unknown(1), good(2), broken(3) }
           ACCESS read-only
           STATUS mandatory
           DESCRIPTION
               "History of the +5 volt power from the power 
               supply."
           ::= { powerSupplyEntry 12 }

       powerSupplyPlus12History OBJECT-TYPE
           SYNTAX INTEGER { unknown(1), good(2), broken(3) }
           ACCESS read-only
           STATUS mandatory
           DESCRIPTION
               "History of the +12 volt power from the power 
               supply."
           ::= { powerSupplyEntry 13 }

       powerSupplyMinus12History OBJECT-TYPE
           SYNTAX INTEGER { unknown(1), good(2), broken(3) }
           ACCESS read-only
           STATUS mandatory
           DESCRIPTION
               "History of the -12 volt power from the power 
               supply."
           ::= { powerSupplyEntry 14 }

       powerSupplyThermalWarningHistory OBJECT-TYPE
           SYNTAX INTEGER { unknown(1), good(2), broken(3) }
           ACCESS read-only
           STATUS mandatory
           DESCRIPTION
               "The thermal warning history of the power supply."
           ::= { powerSupplyEntry 15 }

       powerSupplyThermalShutdownHistory OBJECT-TYPE
           SYNTAX INTEGER { unknown(1), good(2), broken(3) }
           ACCESS read-only
           STATUS mandatory
           DESCRIPTION
               "The thermal shutdown history of the power supply."
           ::= { powerSupplyEntry 16 }

       powerSupplyFanHistory OBJECT-TYPE
           SYNTAX INTEGER { unknown(1), good(2), broken(3) }
           ACCESS read-only
           STATUS mandatory
           DESCRIPTION
               "The status history of the power supply's fan."
           ::= { powerSupplyEntry 17 }

       powerSupplyHardwareInhibitHistory OBJECT-TYPE
           SYNTAX INTEGER { unknown(1), good(2), broken(3) }
           ACCESS read-only
           STATUS mandatory
           DESCRIPTION
               "The status history of the power supply's hardware 
               inhibit."
           ::= { powerSupplyEntry 18 }

       powerSupplyPlus5Volts OBJECT-TYPE
           SYNTAX Gauge
           ACCESS read-only
           STATUS mandatory
           DESCRIPTION
               "In hundredths, volts of +5 volt power currently 
               provided by the power supply.  A value of 0 
               indicates unknown."
           ::= { powerSupplyEntry 19 }

       powerSupplyPlus12Volts OBJECT-TYPE
           SYNTAX Gauge
           ACCESS read-only
           STATUS mandatory
           DESCRIPTION
               "In hundredths, volts of +12 volt power currently 
               provided by the power supply.  A value of 0 
               indicates unknown."
           ::= { powerSupplyEntry 20 }

       powerSupplyMinus12Volts OBJECT-TYPE
           SYNTAX Gauge
           ACCESS read-only
           STATUS mandatory
           DESCRIPTION
               "In hundredths, volts of -12 volt power currently 
               provided by the power supply.  A value of 0 
               indicates unknown."
           ::= { powerSupplyEntry 21 }

       powerSupplyWatts OBJECT-TYPE
           SYNTAX Gauge
           ACCESS read-only
           STATUS mandatory
           DESCRIPTION
               "Watts of power currently drawn from this power 
               supply.  A value of 0 indicates unknown."
           ::= { powerSupplyEntry 22 }

       powerSupplyWattsMax OBJECT-TYPE
           SYNTAX Gauge
           ACCESS read-only
           STATUS mandatory
           DESCRIPTION
               "Maximum watts of power available from this power 
               supply.  A value of 0 indicates unknown."
           ::= { powerSupplyEntry 23 }

       powerSupplyChassisWatts OBJECT-TYPE
           SYNTAX Gauge
           ACCESS read-only
           STATUS mandatory
           DESCRIPTION
               "Total watts of power currently drawn by the entire 
               chassis.  A value of 0 indicates unknown."
           ::= { powerSupplyEntry 24 }

       powerSupplyChassisWattsMax OBJECT-TYPE
           SYNTAX Gauge
           ACCESS read-only
           STATUS mandatory
           DESCRIPTION
               "Total maximum watts of power available from all the 
               power supplies in the chassis.  A value of 0 
               indicates unknown."
           ::= { powerSupplyEntry 25 }

       powerSupplyHardwareType OBJECT-TYPE
           SYNTAX INTEGER { other(1), ps130(2), bb190(3) }
           ACCESS read-only
           STATUS mandatory
           DESCRIPTION
               "The type of power supply."
           ::= { powerSupplyEntry 26 }

       -- The firmware update group

       -- A table which contains information and status
       -- concerning the writing of firmware to a target
       -- I/O card.

       -- The firmware update table

       firmwareUpdateTable OBJECT-TYPE
           SYNTAX SEQUENCE OF FirmwareUpdateEntry
           ACCESS not-accessible
           STATUS mandatory
           DESCRIPTION
               "Table of descriptive and status information concerning
               the writing of firmware to a target I/O card."
           ::= { xFirmwareUpdate 1 }

       firmwareUpdateEntry OBJECT-TYPE
           SYNTAX FirmwareUpdateEntry
           ACCESS not-accessible
           STATUS mandatory
           DESCRIPTION
               "An entry in the table concerning the writing of
               firmware to a target I/O card."
           INDEX { firmwareUpdateSlotIndex }
           ::= { firmwareUpdateTable 1 }

       FirmwareUpdateEntry  ::=
           SEQUENCE {
               firmwareUpdateSlotIndex
                   INTEGER,
               firmwareUpdateDefaultFileName
                   DisplayString,
               firmwareUpdateFileName
                   DisplayString,
               firmwareUpdateStatus
                   INTEGER,
               firmwareUpdateState
                   INTEGER,
               firmwareUpdateCompletionStatus
                   INTEGER,
			   firmwareUpdateMethod
                   INTEGER
           }

       firmwareUpdateSlotIndex  OBJECT-TYPE
           SYNTAX INTEGER
           ACCESS read-only
           STATUS mandatory
           DESCRIPTION
               "This variable identifies the slot to which is to
               be the target of the firmware update."
           ::= { firmwareUpdateEntry 1 }

       firmwareUpdateDefaultFileName  OBJECT-TYPE
           SYNTAX DisplayString
           ACCESS read-only
           STATUS mandatory
           DESCRIPTION
               "This variable when read will obtain the default
               file name from the target."
           ::= { firmwareUpdateEntry 2 }

       firmwareUpdateFileName  OBJECT-TYPE
           SYNTAX DisplayString
           ACCESS read-write
           STATUS mandatory
           DESCRIPTION
               "This variable contains the name of the file to be
               read from the flash memory card and written to the
               target."
           ::= { firmwareUpdateEntry 3 }

       firmwareUpdateStatus  OBJECT-TYPE
           SYNTAX INTEGER { ready(1), execute(2) }
           ACCESS read-write
           STATUS mandatory
           DESCRIPTION
               "This variable is used to start the update process.
               The agent always 'ready' for this value.  Setting this
               value to 'execute' causes the agent to write the file
               specified by firmwareUpdateFileName to be written to
               the taget.  Setting this value to 'execute' when
               firmwareUpdateFileName has not been written or when
               firmwareUpdateState is 'writing' causes bad value to be
               returned."
           ::= { firmwareUpdateEntry 4 }

       firmwareUpdateState  OBJECT-TYPE
           SYNTAX INTEGER { idle(1), writing(2) }
           ACCESS read-only
           STATUS mandatory
           DESCRIPTION
               "This variable indicates the current state of firmware
               update, 'idle' indicates that firmware update may be
               initiated, and 'writing' indicates that an update is in
               process."
           ::= { firmwareUpdateEntry 5 }

       firmwareUpdateCompletionStatus  OBJECT-TYPE
           SYNTAX INTEGER { none(1),
                            success(2),
                            noTarget(3),
                            busError(4),
                            badFileName(5),
                            targetError(6),
                            timeout(7)
                          }
           ACCESS read-only
           STATUS mandatory
           DESCRIPTION
               "This variable indicates the completion status of the
               the last firmware update attempt.  'none' indicates
               that no firmware update has yet been attempted."
           ::= { firmwareUpdateEntry 6 }

       firmwareUpdateMethod  OBJECT-TYPE
           SYNTAX INTEGER { card(1), local(2) }
           ACCESS read-write
           STATUS mandatory
           DESCRIPTION
               "This variable indicates the method of update of the
               firmware update attempt. "
           ::= { firmwareUpdateEntry 7 }

END
