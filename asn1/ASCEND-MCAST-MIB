--			Ascend Multicast MIB
--
--			Ascend Communications, Inc
--			1275 Harbor Bay Pkwy
--			Alameda, CA 94502
--			+1 510 769 6001
--			info@ascend.com
--
--		Copyright (c) 1993-1997 Ascend Communications, Inc.
--		All rights reserved.
--
-- $Id: mcast.mib,v 29.1 1997/03/13 20:51:00 ravim Exp $
--
-- 11 Mar 97:	Initial release

ASCEND-MCAST-MIB DEFINITIONS ::= BEGIN

    IMPORTS
	mCastGroup
	    FROM ASCEND-MIB
        IpAddress
            FROM RFC1155-SMI
	Counter
	    FROM RFC1155-SMI
	OBJECT-TYPE
	    FROM RFC-1212;

    heartBeatMulticastGroupAddress OBJECT-TYPE
	SYNTAX	                   IpAddress
	ACCESS	                   read-only
	STATUS	                   mandatory
	DESCRIPTION                "Multicast Group address used to receive
                                   HeartBeat packets."
        ::= { mCastGroup 1 }

    heartBeatSourceAddress OBJECT-TYPE
	SYNTAX	           IpAddress
	ACCESS	           read-only
	STATUS	           mandatory
	DESCRIPTION        "Source address of last valid heartbeat
			    packet received."
        ::= { mCastGroup 2 }

    heartBeatSlotTimeInterval OBJECT-TYPE
	SYNTAX	              INTEGER
	ACCESS	              read-only
	STATUS	              mandatory
	DESCRIPTION           "Number of seconds MAX waits to
			       receive a valid heartBeat packet."
        ::= { mCastGroup 3 }

    heartBeatSlotCount   OBJECT-TYPE
	SYNTAX	         INTEGER
	ACCESS	         read-only
	STATUS	         mandatory
	DESCRIPTION      "Number of slot intervals MAX waits before
		          checking if expected number of
			  heartbeat packets received or not."
        ::= { mCastGroup 4 }

    heartBeatPacketCount OBJECT-TYPE
	SYNTAX	         Counter
	ACCESS	         read-only
	STATUS	         mandatory
	DESCRIPTION      "Number of heartbeat packets received
		          in Slot Count intervals when
			  entering Alarm Mode."
        ::= { mCastGroup 5 }

END
