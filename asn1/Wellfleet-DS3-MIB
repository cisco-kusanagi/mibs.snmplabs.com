Wellfleet-DS3-MIB DEFINITIONS ::= BEGIN

-- Created by mdl2asn version 3.1
-- Creation date: Wed Aug 30 16:40:18 EDT 1995


    IMPORTS

      IpAddress, Counter, Gauge, TimeTicks, Opaque, enterprises, mgmt
        FROM RFC1155-SMI
      OBJECT-TYPE
        FROM RFC-1212
      TRAP-TYPE
        FROM RFC-1215
      DisplayString, mib-2
        FROM RFC1213-MIB
      wfDs3Group
        FROM Wellfleet-COMMON-MIB;


    wfDs3Config OBJECT-TYPE
        SYNTAX	SEQUENCE OF WfDs3ConfigEntry
        ACCESS	not-accessible
        STATUS	mandatory
        DESCRIPTION
                "The DS3 Configuration table"
        ::= { wfDs3Group 1 }

    wfDs3ConfigEntry OBJECT-TYPE
        SYNTAX	WfDs3ConfigEntry
        ACCESS	not-accessible
        STATUS	mandatory
        DESCRIPTION
                "per circuit DS3 configuration objects; wfDs3LineIndex
                corresponds to Wellfleet circuit number"
        INDEX	{ wfDs3LineIndex }
        ::= { wfDs3Config 1 }

    WfDs3ConfigEntry ::= SEQUENCE {
    	    wfDs3LineIndex
    		INTEGER,
    	    wfDs3TimeElapsed
    		INTEGER,
    	    wfDs3ValidIntervals
    		INTEGER,
    	    wfDs3LineType
    		INTEGER,
    	    wfDs3ZeroCoding
    		INTEGER,
    	    wfDs3SendCode
    		INTEGER,
    	    wfDs3CircuitIdentifier
    		DisplayString,
    	    wfDs3LoopbackConfig
    		INTEGER,
    	    wfDs3LineStatus
    		INTEGER
        }

    wfDs3LineIndex OBJECT-TYPE
        SYNTAX	INTEGER(1..1024)
        ACCESS	read-only
        STATUS	mandatory
        DESCRIPTION
                "this corresponds to the Wellfleet circuit number"
        ::= { wfDs3ConfigEntry 1 }

    wfDs3TimeElapsed OBJECT-TYPE
        SYNTAX	INTEGER
        ACCESS	read-only
        STATUS	mandatory
        DESCRIPTION
                "1..900 seconds within the current 15-minute interval"
        ::= { wfDs3ConfigEntry 2 }

    wfDs3ValidIntervals OBJECT-TYPE
        SYNTAX	INTEGER
        ACCESS	read-only
        STATUS	mandatory
        DESCRIPTION
                "0..96 previous intervals that valid data
                were collected. This is 96 unless the CSU
                device was brought on line within the last 24
                hours."
        ::= { wfDs3ConfigEntry 3 }

    wfDs3LineType OBJECT-TYPE
        SYNTAX	INTEGER {
    		    other(1),
    		    ds3cbitparity(4),
    		    ds3clearchannel(5)
    		}
        ACCESS	read-only
        STATUS	mandatory
        DESCRIPTION
                "the variety of DS3 implementing this circuit"
        ::= { wfDs3ConfigEntry 4 }

    wfDs3ZeroCoding OBJECT-TYPE
        SYNTAX	INTEGER {
    		    ds3b3zs(2)
    		}
        ACCESS	read-only
        STATUS	mandatory
        DESCRIPTION
                "the variety of Zero Code Suppression used on the link"
        ::= { wfDs3ConfigEntry 5 }

    wfDs3SendCode OBJECT-TYPE
        SYNTAX	INTEGER {
    		    ds3sendnocode(2)
    		}
        ACCESS	read-only
        STATUS	mandatory
        DESCRIPTION
                "the type of code being sent across the DS3 circuit by
                the CSU"
        ::= { wfDs3ConfigEntry 6 }

    wfDs3CircuitIdentifier OBJECT-TYPE
        SYNTAX	DisplayString
        ACCESS	read-only
        STATUS	mandatory
        DESCRIPTION
                "the transmission vendor's circuit identifier"
        ::= { wfDs3ConfigEntry 7 }

    wfDs3LoopbackConfig OBJECT-TYPE
        SYNTAX	INTEGER {
    		    ds3noloop(1),
    		    ds3mgrpayloadloop(2),
    		    ds3mgrlineloop(3),
    		    ds3netreqpayloadloop(4),
    		    ds3netreqlineloop(5),
    		    ds3otherloop(6)
    		}
        ACCESS	read-only
        STATUS	mandatory
        DESCRIPTION
                "the loopback state of the CSU"
        ::= { wfDs3ConfigEntry 8 }

    wfDs3LineStatus OBJECT-TYPE
        SYNTAX	INTEGER {
    		    ds3noalarm(1),
    		    ds3farendalarm(2),
    		    ds3alarmindicationsignal(4),
    		    ds3lossofframe(8),
    		    ds3lossofsignal(16),
    		    ds3loopbackstate(32)
    		}
        ACCESS	read-only
        STATUS	mandatory
        DESCRIPTION
                "the state of the DS3 line"
        ::= { wfDs3ConfigEntry 9 }

    wfDs3Current OBJECT-TYPE
        SYNTAX	SEQUENCE OF WfDs3CurrentEntry
        ACCESS	not-accessible
        STATUS	mandatory
        DESCRIPTION
                "The DS3 Current table"
        ::= { wfDs3Group 2 }

    wfDs3CurrentEntry OBJECT-TYPE
        SYNTAX	WfDs3CurrentEntry
        ACCESS	not-accessible
        STATUS	mandatory
        DESCRIPTION
                "per circuit DS3 current objects - wfDs3CurrentIndex
                corresponds to Wellfleet circuit number"
        INDEX	{ wfDs3CurrentIndex }
        ::= { wfDs3Current 1 }

    WfDs3CurrentEntry ::= SEQUENCE {
    	    wfDs3CurrentIndex
    		INTEGER,
    	    wfDs3CurrentESs
    		Counter,
    	    wfDs3CurrentSESs
    		Counter,
    	    wfDs3CurrentSEFs
    		Counter,
    	    wfDs3CurrentUASs
    		Counter,
    	    wfDs3CurrentBPVs
    		Counter,
    	    wfDs3CurrentCVs
    		Counter
        }

    wfDs3CurrentIndex OBJECT-TYPE
        SYNTAX	INTEGER(1..1024)
        ACCESS	read-only
        STATUS	mandatory
        DESCRIPTION
                "this corresponds to the Wellfleet circuit number"
        ::= { wfDs3CurrentEntry 1 }

    wfDs3CurrentESs OBJECT-TYPE
        SYNTAX	Counter
        ACCESS	read-only
        STATUS	mandatory
        DESCRIPTION
                "the count of errored seconds in the current interval"
        ::= { wfDs3CurrentEntry 2 }

    wfDs3CurrentSESs OBJECT-TYPE
        SYNTAX	Counter
        ACCESS	read-only
        STATUS	mandatory
        DESCRIPTION
                "the count of severely errored seconds in the
                current interval"
        ::= { wfDs3CurrentEntry 3 }

    wfDs3CurrentSEFs OBJECT-TYPE
        SYNTAX	Counter
        ACCESS	read-only
        STATUS	mandatory
        DESCRIPTION
                "the count of severely errored framing seconds in the current
                interval"
        ::= { wfDs3CurrentEntry 4 }

    wfDs3CurrentUASs OBJECT-TYPE
        SYNTAX	Counter
        ACCESS	read-only
        STATUS	mandatory
        DESCRIPTION
                "the number of unavailable seconds in the current interval"
        ::= { wfDs3CurrentEntry 5 }

    wfDs3CurrentBPVs OBJECT-TYPE
        SYNTAX	Counter
        ACCESS	read-only
        STATUS	mandatory
        DESCRIPTION
                "the count of bipolar violations in the current interval"
        ::= { wfDs3CurrentEntry 6 }

    wfDs3CurrentCVs OBJECT-TYPE
        SYNTAX	Counter
        ACCESS	read-only
        STATUS	mandatory
        DESCRIPTION
                "the count of code violation error events in the
                current interval"
        ::= { wfDs3CurrentEntry 7 }

    wfDs3Interval OBJECT-TYPE
        SYNTAX	SEQUENCE OF WfDs3IntervalEntry
        ACCESS	not-accessible
        STATUS	mandatory
        DESCRIPTION
                "The DS3 Interval table"
        ::= { wfDs3Group 3 }

    wfDs3IntervalEntry OBJECT-TYPE
        SYNTAX	WfDs3IntervalEntry
        ACCESS	not-accessible
        STATUS	mandatory
        DESCRIPTION
                "per circuit DS3 interval objects - wfDs3IntervalIndex
                corresponds to Wellfleet circuit number,
                wfDs3IntervalNumber is the numbered previous
                15-minute interval"
        INDEX	{ wfDs3IntervalIndex,
    		  wfDs3IntervalNumber }
        ::= { wfDs3Interval 1 }

    WfDs3IntervalEntry ::= SEQUENCE {
    	    wfDs3IntervalIndex
    		INTEGER,
    	    wfDs3IntervalNumber
    		INTEGER,
    	    wfDs3IntervalESs
    		Gauge,
    	    wfDs3IntervalSESs
    		Gauge,
    	    wfDs3IntervalSEFs
    		Gauge,
    	    wfDs3IntervalUASs
    		Gauge,
    	    wfDs3IntervalBPVs
    		Gauge,
    	    wfDs3IntervalCVs
    		Gauge
        }

    wfDs3IntervalIndex OBJECT-TYPE
        SYNTAX	INTEGER(1..1024)
        ACCESS	read-only
        STATUS	mandatory
        DESCRIPTION
                "this corresponds to the Wellfleet circuit number"
        ::= { wfDs3IntervalEntry 1 }

    wfDs3IntervalNumber OBJECT-TYPE
        SYNTAX	INTEGER(1..96)
        ACCESS	read-only
        STATUS	mandatory
        DESCRIPTION
                "1..96 where 1 is the most recent 15-minute interval and 96 is
                the least"
        ::= { wfDs3IntervalEntry 2 }

    wfDs3IntervalESs OBJECT-TYPE
        SYNTAX	Gauge
        ACCESS	read-only
        STATUS	mandatory
        DESCRIPTION
                "the count of errored seconds in the specified interval"
        ::= { wfDs3IntervalEntry 3 }

    wfDs3IntervalSESs OBJECT-TYPE
        SYNTAX	Gauge
        ACCESS	read-only
        STATUS	mandatory
        DESCRIPTION
                "the count of severely errored seconds in the specified
                interval"
        ::= { wfDs3IntervalEntry 4 }

    wfDs3IntervalSEFs OBJECT-TYPE
        SYNTAX	Gauge
        ACCESS	read-only
        STATUS	mandatory
        DESCRIPTION
                "the count of severely errored framing seconds in the specified
                interval"
        ::= { wfDs3IntervalEntry 5 }

    wfDs3IntervalUASs OBJECT-TYPE
        SYNTAX	Gauge
        ACCESS	read-only
        STATUS	mandatory
        DESCRIPTION
                "the number of unavailable seconds in the specified interval"
        ::= { wfDs3IntervalEntry 6 }

    wfDs3IntervalBPVs OBJECT-TYPE
        SYNTAX	Gauge
        ACCESS	read-only
        STATUS	mandatory
        DESCRIPTION
                "the count of bipolar violations in the specified interval"
        ::= { wfDs3IntervalEntry 7 }

    wfDs3IntervalCVs OBJECT-TYPE
        SYNTAX	Gauge
        ACCESS	read-only
        STATUS	mandatory
        DESCRIPTION
                "the count of code violation error events in the
                specified interval"
        ::= { wfDs3IntervalEntry 8 }

    wfDs3Total OBJECT-TYPE
        SYNTAX	SEQUENCE OF WfDs3TotalEntry
        ACCESS	not-accessible
        STATUS	mandatory
        DESCRIPTION
                "The DS3 Total table"
        ::= { wfDs3Group 4 }

    wfDs3TotalEntry OBJECT-TYPE
        SYNTAX	WfDs3TotalEntry
        ACCESS	not-accessible
        STATUS	mandatory
        DESCRIPTION
                "per circuit DS3 total objects - wfDs3TotalIndex
                corresponds to Wellfleet circuit number"
        INDEX	{ wfDs3TotalIndex }
        ::= { wfDs3Total 1 }

    WfDs3TotalEntry ::= SEQUENCE {
    	    wfDs3TotalIndex
    		INTEGER,
    	    wfDs3TotalESs
    		Gauge,
    	    wfDs3TotalSESs
    		Gauge,
    	    wfDs3TotalSEFs
    		Gauge,
    	    wfDs3TotalUASs
    		Gauge,
    	    wfDs3TotalBPVs
    		Gauge,
    	    wfDs3TotalCVs
    		Gauge
        }

    wfDs3TotalIndex OBJECT-TYPE
        SYNTAX	INTEGER(1..1024)
        ACCESS	read-only
        STATUS	mandatory
        DESCRIPTION
                "this corresponds to the Wellfleet circuit number"
        ::= { wfDs3TotalEntry 1 }

    wfDs3TotalESs OBJECT-TYPE
        SYNTAX	Gauge
        ACCESS	read-only
        STATUS	mandatory
        DESCRIPTION
                "total count of errored seconds"
        ::= { wfDs3TotalEntry 2 }

    wfDs3TotalSESs OBJECT-TYPE
        SYNTAX	Gauge
        ACCESS	read-only
        STATUS	mandatory
        DESCRIPTION
                "total count of severely errored seconds"
        ::= { wfDs3TotalEntry 3 }

    wfDs3TotalSEFs OBJECT-TYPE
        SYNTAX	Gauge
        ACCESS	read-only
        STATUS	mandatory
        DESCRIPTION
                "total count of severely errored framing seconds"
        ::= { wfDs3TotalEntry 4 }

    wfDs3TotalUASs OBJECT-TYPE
        SYNTAX	Gauge
        ACCESS	read-only
        STATUS	mandatory
        DESCRIPTION
                "total number of unavailable seconds"
        ::= { wfDs3TotalEntry 5 }

    wfDs3TotalBPVs OBJECT-TYPE
        SYNTAX	Gauge
        ACCESS	read-only
        STATUS	mandatory
        DESCRIPTION
                "total count of bipolar violations"
        ::= { wfDs3TotalEntry 6 }

    wfDs3TotalCVs OBJECT-TYPE
        SYNTAX	Gauge
        ACCESS	read-only
        STATUS	mandatory
        DESCRIPTION
                "total count of code violation error events"
        ::= { wfDs3TotalEntry 7 }

    wfDs3FeConfig OBJECT-TYPE
        SYNTAX	SEQUENCE OF WfDs3FeConfigEntry
        ACCESS	not-accessible
        STATUS	mandatory
        DESCRIPTION
                "The DS3 Far End Configuration table"
        ::= { wfDs3Group 5 }

    wfDs3FeConfigEntry OBJECT-TYPE
        SYNTAX	WfDs3FeConfigEntry
        ACCESS	not-accessible
        STATUS	mandatory
        DESCRIPTION
                "per circuit DS3 far end config objects -
                wfDs3FeIntervalIndex corresponds to Wellfleet circuit
                number"
        INDEX	{ wfDs3FeConfigIndex }
        ::= { wfDs3FeConfig 1 }

    WfDs3FeConfigEntry ::= SEQUENCE {
    	    wfDs3FeConfigIndex
    		INTEGER,
    	    wfDs3FarEndEquipCode
    		DisplayString,
    	    wfDs3FarEndLocationIDCode
    		DisplayString,
    	    wfDs3FarEndFrameIDCode
    		DisplayString,
    	    wfDs3FarEndUnitCode
    		DisplayString,
    	    wfDs3FarEndFacilityIDCode
    		DisplayString
        }

    wfDs3FeConfigIndex OBJECT-TYPE
        SYNTAX	INTEGER(1..1024)
        ACCESS	read-only
        STATUS	mandatory
        DESCRIPTION
                "this corresponds to the Wellfleet circuit number"
        ::= { wfDs3FeConfigEntry 1 }

    wfDs3FarEndEquipCode OBJECT-TYPE
        SYNTAX	DisplayString
        ACCESS	read-write
        STATUS	mandatory
        DESCRIPTION
                "equipment description code - C-bit parity only"
        ::= { wfDs3FeConfigEntry 2 }

    wfDs3FarEndLocationIDCode OBJECT-TYPE
        SYNTAX	DisplayString
        ACCESS	read-write
        STATUS	mandatory
        DESCRIPTION
                "equipment location code - C-bit parity only"
        ::= { wfDs3FeConfigEntry 3 }

    wfDs3FarEndFrameIDCode OBJECT-TYPE
        SYNTAX	DisplayString
        ACCESS	read-write
        STATUS	mandatory
        DESCRIPTION
                "code for the equipment location within a building"
        ::= { wfDs3FeConfigEntry 4 }

    wfDs3FarEndUnitCode OBJECT-TYPE
        SYNTAX	DisplayString
        ACCESS	read-write
        STATUS	mandatory
        DESCRIPTION
                "code for the equipment location within a bay"
        ::= { wfDs3FeConfigEntry 5 }

    wfDs3FarEndFacilityIDCode OBJECT-TYPE
        SYNTAX	DisplayString
        ACCESS	read-write
        STATUS	mandatory
        DESCRIPTION
                "path identification code"
        ::= { wfDs3FeConfigEntry 6 }

    wfDs3FeCurrent OBJECT-TYPE
        SYNTAX	SEQUENCE OF WfDs3FeCurrentEntry
        ACCESS	not-accessible
        STATUS	mandatory
        DESCRIPTION
                "The DS3 Far End Current table"
        ::= { wfDs3Group 6 }

    wfDs3FeCurrentEntry OBJECT-TYPE
        SYNTAX	WfDs3FeCurrentEntry
        ACCESS	not-accessible
        STATUS	mandatory
        DESCRIPTION
                "per circuit DS3 far end current objects
                wfDs3FeCurrentIndex corresponds to Wellfleet circuit
                number"
        INDEX	{ wfDs3FeCurrentIndex }
        ::= { wfDs3FeCurrent 1 }

    WfDs3FeCurrentEntry ::= SEQUENCE {
    	    wfDs3FeCurrentIndex
    		INTEGER,
    	    wfDs3FeCurrentESs
    		Counter,
    	    wfDs3FeCurrentSESs
    		Counter,
    	    wfDs3FeCurrentCVs
    		Counter
        }

    wfDs3FeCurrentIndex OBJECT-TYPE
        SYNTAX	INTEGER(1..1024)
        ACCESS	read-only
        STATUS	mandatory
        DESCRIPTION
                "this corresponds to the Wellfleet circuit number"
        ::= { wfDs3FeCurrentEntry 1 }

    wfDs3FeCurrentESs OBJECT-TYPE
        SYNTAX	Counter
        ACCESS	read-only
        STATUS	mandatory
        DESCRIPTION
                "the count of errored seconds in the current interval"
        ::= { wfDs3FeCurrentEntry 2 }

    wfDs3FeCurrentSESs OBJECT-TYPE
        SYNTAX	Counter
        ACCESS	read-only
        STATUS	mandatory
        DESCRIPTION
                "the count of severely errored seconds in the
                current interval"
        ::= { wfDs3FeCurrentEntry 3 }

    wfDs3FeCurrentCVs OBJECT-TYPE
        SYNTAX	Counter
        ACCESS	read-only
        STATUS	mandatory
        DESCRIPTION
                "the count of code violation error events in the
                current interval"
        ::= { wfDs3FeCurrentEntry 4 }

    wfDs3FeInterval OBJECT-TYPE
        SYNTAX	SEQUENCE OF WfDs3FeIntervalEntry
        ACCESS	not-accessible
        STATUS	mandatory
        DESCRIPTION
                "The DS3 Far End Interval table"
        ::= { wfDs3Group 7 }

    wfDs3FeIntervalEntry OBJECT-TYPE
        SYNTAX	WfDs3FeIntervalEntry
        ACCESS	not-accessible
        STATUS	mandatory
        DESCRIPTION
                "per circuit DS3 far end interval objects -
                wfDs3FeIntervalIndex corresponds to Wellfleet circuit
                number, wfDs3FeIntervalNumber is the numbered previous
                15-minute interval"
        INDEX	{ wfDs3FeIntervalIndex,
    		  wfDs3FeIntervalNumber }
        ::= { wfDs3FeInterval 1 }

    WfDs3FeIntervalEntry ::= SEQUENCE {
    	    wfDs3FeIntervalIndex
    		INTEGER,
    	    wfDs3FeIntervalNumber
    		INTEGER,
    	    wfDs3FeIntervalESs
    		Gauge,
    	    wfDs3FeIntervalSESs
    		Gauge,
    	    wfDs3FeIntervalCVs
    		Gauge
        }

    wfDs3FeIntervalIndex OBJECT-TYPE
        SYNTAX	INTEGER(1..1024)
        ACCESS	read-only
        STATUS	mandatory
        DESCRIPTION
                "this corresponds to the Wellfleet circuit number"
        ::= { wfDs3FeIntervalEntry 1 }

    wfDs3FeIntervalNumber OBJECT-TYPE
        SYNTAX	INTEGER(1..96)
        ACCESS	read-only
        STATUS	mandatory
        DESCRIPTION
                "1..96 where 1 is the most recent 15-minute interval and 96 is
                the least"
        ::= { wfDs3FeIntervalEntry 2 }

    wfDs3FeIntervalESs OBJECT-TYPE
        SYNTAX	Gauge
        ACCESS	read-only
        STATUS	mandatory
        DESCRIPTION
                "the count of errored seconds in the specified interval"
        ::= { wfDs3FeIntervalEntry 3 }

    wfDs3FeIntervalSESs OBJECT-TYPE
        SYNTAX	Gauge
        ACCESS	read-only
        STATUS	mandatory
        DESCRIPTION
                "the count of severely errored seconds in the
                specified interval"
        ::= { wfDs3FeIntervalEntry 4 }

    wfDs3FeIntervalCVs OBJECT-TYPE
        SYNTAX	Gauge
        ACCESS	read-only
        STATUS	mandatory
        DESCRIPTION
                "the count of code violation error events in the
                specified interval"
        ::= { wfDs3FeIntervalEntry 5 }

    wfDs3FeTotal OBJECT-TYPE
        SYNTAX	SEQUENCE OF WfDs3FeTotalEntry
        ACCESS	not-accessible
        STATUS	mandatory
        DESCRIPTION
                "The DS3 Far End Total table"
        ::= { wfDs3Group 8 }

    wfDs3FeTotalEntry OBJECT-TYPE
        SYNTAX	WfDs3FeTotalEntry
        ACCESS	not-accessible
        STATUS	mandatory
        DESCRIPTION
                "per circuit far end DS3 total objects - wfDs3FeTotalIndex
                corresponds to Wellfleet circuit number"
        INDEX	{ wfDs3FeTotalIndex }
        ::= { wfDs3FeTotal 1 }

    WfDs3FeTotalEntry ::= SEQUENCE {
    	    wfDs3FeTotalIndex
    		INTEGER,
    	    wfDs3FeTotalESs
    		Gauge,
    	    wfDs3FeTotalSESs
    		Gauge,
    	    wfDs3FeTotalCVs
    		Gauge
        }

    wfDs3FeTotalIndex OBJECT-TYPE
        SYNTAX	INTEGER(1..1024)
        ACCESS	read-only
        STATUS	mandatory
        DESCRIPTION
                "this corresponds to the Wellfleet circuit number"
        ::= { wfDs3FeTotalEntry 1 }

    wfDs3FeTotalESs OBJECT-TYPE
        SYNTAX	Gauge
        ACCESS	read-only
        STATUS	mandatory
        DESCRIPTION
                "total count of errored seconds"
        ::= { wfDs3FeTotalEntry 2 }

    wfDs3FeTotalSESs OBJECT-TYPE
        SYNTAX	Gauge
        ACCESS	read-only
        STATUS	mandatory
        DESCRIPTION
                "total count of severely errored seconds"
        ::= { wfDs3FeTotalEntry 3 }

    wfDs3FeTotalCVs OBJECT-TYPE
        SYNTAX	Gauge
        ACCESS	read-only
        STATUS	mandatory
        DESCRIPTION
                "total count of code violation error events"
        ::= { wfDs3FeTotalEntry 4 }

    END  -- Wellfleet-DS3-MIB
