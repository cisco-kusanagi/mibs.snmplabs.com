TERAWAVE-teratca-MIB DEFINITIONS ::= BEGIN
        -- Created by sml2mib compiler 
        IMPORTS

 enterprises,  OBJECT-TYPE,  Counter,  Gauge,  TimeTicks
        FROM RFC1155-SMI;

terawave OBJECT IDENTIFIER ::=  { enterprises 4513 }

teratraps OBJECT IDENTIFIER ::=  { terawave 1 }

teraTCA OBJECT IDENTIFIER ::=  { teratraps 4 }

     -- teraTcaTable

teraTcaTable OBJECT-TYPE
     SYNTAX SEQUENCE OF TeraTcaTableEntryType
     ACCESS not-accessible
     STATUS mandatory
     DESCRIPTION
          " table teraTcaTable"
     ::= { teraTCA 1 }

teraTcaTableEntry OBJECT-TYPE
          SYNTAX TeraTcaTableEntryType
          ACCESS not-accessible
          STATUS mandatory
          DESCRIPTION
               " table entry teraTcaTableEntry "
          INDEX {                   teraTcaIndex }
     ::= { teraTcaTable 1 }

TeraTcaTableEntryType ::= SEQUENCE {
          teraTcaIndex   
             INTEGER,
          teraTcaInterval   
             INTEGER,
          teraTcaVariable   
             OBJECT IDENTIFIER,
          teraTcaIntervalSec   
             INTEGER,
          teraTcaValue   
             INTEGER,
          teraTcaType   
             INTEGER,
          teraTcaRisingThreshold   
             INTEGER,
          teraTcaFallingThreshold   
             INTEGER,
          teraTcaRisingEvent   
             INTEGER,
          teraTcaFallingEvent   
             INTEGER,
          teraTcaOwner   
             OCTET STRING,
          teraTcaStatus   
             INTEGER
}

teraTcaIndex OBJECT-TYPE
          SYNTAX INTEGER
          ACCESS read-only
          STATUS mandatory
          DESCRIPTION
               ""
          ::= { teraTcaTableEntry 1 }

teraTcaInterval OBJECT-TYPE
          SYNTAX INTEGER
                  {
                  duration-15m(1),
                  duration-1day(2),
                  duration-Var(3)
                  }
          ACCESS read-write
          STATUS mandatory
          DESCRIPTION
               ""
          ::= { teraTcaTableEntry 2 }

teraTcaVariable OBJECT-TYPE
          SYNTAX OBJECT IDENTIFIER
          ACCESS read-write
          STATUS mandatory
          DESCRIPTION
               ""
          ::= { teraTcaTableEntry 3 }

teraTcaIntervalSec OBJECT-TYPE
          SYNTAX INTEGER
          ACCESS read-write
          STATUS mandatory
          DESCRIPTION
               ""
          ::= { teraTcaTableEntry 4 }

teraTcaValue OBJECT-TYPE
          SYNTAX INTEGER
          ACCESS read-only
          STATUS mandatory
          DESCRIPTION
               ""
          ::= { teraTcaTableEntry 5 }

teraTcaType OBJECT-TYPE
          SYNTAX INTEGER
                  {
                  risingTca(1),
                  fallingTca(2),
                  risingOrFalingTca(3)
                  }
          ACCESS read-write
          STATUS mandatory
          DESCRIPTION
               ""
          ::= { teraTcaTableEntry 6 }

teraTcaRisingThreshold OBJECT-TYPE
          SYNTAX INTEGER
          ACCESS read-write
          STATUS mandatory
          DESCRIPTION
               ""
          ::= { teraTcaTableEntry 7 }

teraTcaFallingThreshold OBJECT-TYPE
          SYNTAX INTEGER
          ACCESS read-write
          STATUS mandatory
          DESCRIPTION
               ""
          ::= { teraTcaTableEntry 8 }

teraTcaRisingEvent OBJECT-TYPE
          SYNTAX INTEGER
                  {
                  tcaTrap(1),
                  tcaLog(2),
                  tcaIgnore(3)
                  }
          ACCESS read-write
          STATUS mandatory
          DESCRIPTION
               ""
          ::= { teraTcaTableEntry 9 }

teraTcaFallingEvent OBJECT-TYPE
          SYNTAX INTEGER
                  {
                  tcaTrap(1),
                  tcaLog(2),
                  tcaIgnore(3)
                  }
          ACCESS read-write
          STATUS mandatory
          DESCRIPTION
               ""
          ::= { teraTcaTableEntry 10 }

teraTcaOwner OBJECT-TYPE
          SYNTAX OCTET STRING
          ACCESS read-write
          STATUS mandatory
          DESCRIPTION
               ""
          ::= { teraTcaTableEntry 11 }

teraTcaStatus OBJECT-TYPE
          SYNTAX INTEGER
                  {
                  valid(1),
                  createdRequest(2),
                  underCreation(3),
                  invalid(4)
                  }
          ACCESS read-write
          STATUS mandatory
          DESCRIPTION
               ""
          ::= { teraTcaTableEntry 12 }

END
