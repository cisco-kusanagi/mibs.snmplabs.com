--			Ascend mibthreshhdsl2shdsl MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBTHRESHHDSL2SHDSL-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibthreshHdsl2ShdslProfile  OBJECT IDENTIFIER ::= { configuration 160}

	-- The mibthreshHdsl2ShdslProfile table
	--
	-- This table contains parameters for the mibthreshHdsl2ShdslProfile profile
	--

    mibthreshHdsl2ShdslProfileTable	OBJECT-TYPE
	SYNTAX		SEQUENCE OF MibthreshHdsl2ShdslProfileEntry
	ACCESS		not-accessible
	STATUS		mandatory
	DESCRIPTION	"A list of mibthreshHdsl2ShdslProfile profile entries."
	::= { mibthreshHdsl2ShdslProfile 1 }

    mibthreshHdsl2ShdslProfileEntry	OBJECT-TYPE
	SYNTAX		MibthreshHdsl2ShdslProfileEntry
	ACCESS		not-accessible
	STATUS		mandatory
	DESCRIPTION	"A mibthreshHdsl2ShdslProfile entry containing objects that
			 maps to the parameters of mibthreshHdsl2ShdslProfile profile."
	INDEX		{ threshHdsl2ShdslProfile-Name }
	::= { mibthreshHdsl2ShdslProfileTable 1 }

    MibthreshHdsl2ShdslProfileEntry ::=
	SEQUENCE {
	    threshHdsl2ShdslProfile-Name
		DisplayString,
	    threshHdsl2ShdslProfile-LoopAttenuationThresh
		INTEGER,
	    threshHdsl2ShdslProfile-SnrMgnThresh
		INTEGER,
	    threshHdsl2ShdslProfile-ErroredSecondsThresh
		INTEGER,
	    threshHdsl2ShdslProfile-SeverelyErroredSecondsThresh
		INTEGER,
	    threshHdsl2ShdslProfile-CrcThresh
		INTEGER,
	    threshHdsl2ShdslProfile-LoswsThresh
		INTEGER,
	    threshHdsl2ShdslProfile-UasThresh
		INTEGER,
	    threshHdsl2ShdslProfile-Action-o
		INTEGER
	}

    threshHdsl2ShdslProfile-Name	OBJECT-TYPE
	SYNTAX	DisplayString
	ACCESS	read-only
	STATUS	mandatory
	DESCRIPTION	"The name consists of a null terminated ascii string supplied by the user."
	::= { mibthreshHdsl2ShdslProfileEntry 1 }

    threshHdsl2ShdslProfile-LoopAttenuationThresh	OBJECT-TYPE
	SYNTAX	INTEGER
	ACCESS	read-write
	STATUS	mandatory
	DESCRIPTION	"This object configures the loop attentuation alarm threshold. When the current value reaches or drops below this threshold, a hdsl2ShdslLoopAttenCrossing trap will be generated."
	::= { mibthreshHdsl2ShdslProfileEntry 2 }

    threshHdsl2ShdslProfile-SnrMgnThresh	OBJECT-TYPE
	SYNTAX	INTEGER
	ACCESS	read-write
	STATUS	mandatory
	DESCRIPTION	"This object configures the SNR margin alarm threshold. When the current value reaches or drops below this threshold, a hdsl2ShdslSNRMarginCrossing trap will be generated."
	::= { mibthreshHdsl2ShdslProfileEntry 3 }

    threshHdsl2ShdslProfile-ErroredSecondsThresh	OBJECT-TYPE
	SYNTAX	INTEGER
	ACCESS	read-write
	STATUS	mandatory
	DESCRIPTION	"This object configures the threshold for the number of errored seconds (ES) within any given 15-minute performance data collection interval. If the value of errored seconds in a particular 15-minute collection interval reaches/ exceeds this value, a hdsl2ShdslPerfESThresh trap will be generated. One notification will be sent per interval per endpoint."
	::= { mibthreshHdsl2ShdslProfileEntry 4 }

    threshHdsl2ShdslProfile-SeverelyErroredSecondsThresh	OBJECT-TYPE
	SYNTAX	INTEGER
	ACCESS	read-write
	STATUS	mandatory
	DESCRIPTION	"This object configures the threshold for the number of severely errored seconds (SES) within any given 15-minute performance data collection interval. If the value of severely errored seconds in a particular 15-minute collection interval reaches/exceeds this value, a hdsl2ShdslPerfSESThresh trap will be generated. One notification will be sent per interval per endpoint."
	::= { mibthreshHdsl2ShdslProfileEntry 5 }

    threshHdsl2ShdslProfile-CrcThresh	OBJECT-TYPE
	SYNTAX	INTEGER
	ACCESS	read-write
	STATUS	mandatory
	DESCRIPTION	"This object configures the threshold for the number of CRC anomalies within any given 15-minute performance data collection interval. If the value of CRC anomalies in a particular 15-minute collection interval reaches/exceeds this value, a hdsl2ShdslPerfCRCanomaliesThresh trap will be generated. One notification will be sent per interval per endpoint."
	::= { mibthreshHdsl2ShdslProfileEntry 6 }

    threshHdsl2ShdslProfile-LoswsThresh	OBJECT-TYPE
	SYNTAX	INTEGER
	ACCESS	read-write
	STATUS	mandatory
	DESCRIPTION	"This object configures the threshold for the number of Loss of Sync Word (LOSW) Seconds within any given 15-minute performance data collection interval. If the value of LOSW in a particular 15-minute collection interval reaches/exceeds this value, a hdsl2ShdslPerfLOSWSThresh trap will be generated. One notification will be sent per interval per endpoint."
	::= { mibthreshHdsl2ShdslProfileEntry 7 }

    threshHdsl2ShdslProfile-UasThresh	OBJECT-TYPE
	SYNTAX	INTEGER
	ACCESS	read-write
	STATUS	mandatory
	DESCRIPTION	"This object configures the threshold for the number of unavailable seconds (UAS) within any given 15-minute performance data collection interval. If the value of UAS in a particular 15-minute collection interval reaches/exceeds this value, a hdsl2ShdslPerfUASThresh trap will be generated. One notification will be sent per interval per endpoint."
	::= { mibthreshHdsl2ShdslProfileEntry 8 }

    threshHdsl2ShdslProfile-Action-o	OBJECT-TYPE
	SYNTAX	INTEGER {
		    noAction (1),
		    createProfile (2),
		    deleteProfile (3)
		}
	ACCESS	read-write
	STATUS	mandatory
	DESCRIPTION	""
	::= { mibthreshHdsl2ShdslProfileEntry 9 }

END
