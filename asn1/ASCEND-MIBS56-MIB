--			Ascend mibs56 MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBS56-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibs56NetworkProfile  OBJECT IDENTIFIER ::= { configuration 106}

	-- The mibs56NetworkProfile table
	--
	-- This table contains parameters for the mibs56NetworkProfile profile
	--

    mibs56NetworkProfileTable	OBJECT-TYPE
	SYNTAX		SEQUENCE OF Mibs56NetworkProfileEntry
	ACCESS		not-accessible
	STATUS		mandatory
	DESCRIPTION	"A list of mibs56NetworkProfile profile entries."
	::= { mibs56NetworkProfile 1 }

    mibs56NetworkProfileEntry	OBJECT-TYPE
	SYNTAX		Mibs56NetworkProfileEntry
	ACCESS		not-accessible
	STATUS		mandatory
	DESCRIPTION	"A mibs56NetworkProfile entry containing objects that
			 maps to the parameters of mibs56NetworkProfile profile."
	INDEX		{ s56NetworkProfile-Shelf-o, s56NetworkProfile-Slot-o, s56NetworkProfile-Item-o }
	::= { mibs56NetworkProfileTable 1 }

    Mibs56NetworkProfileEntry ::=
	SEQUENCE {
	    s56NetworkProfile-Shelf-o
		INTEGER,
	    s56NetworkProfile-Slot-o
		INTEGER,
	    s56NetworkProfile-Item-o
		INTEGER,
	    s56NetworkProfile-ProfileNumber
		INTEGER,
	    s56NetworkProfile-Name
		DisplayString,
	    s56NetworkProfile-PhysicalAddress-Shelf
		INTEGER,
	    s56NetworkProfile-PhysicalAddress-Slot
		INTEGER,
	    s56NetworkProfile-PhysicalAddress-ItemNumber
		INTEGER,
	    s56NetworkProfile-Action-o
		INTEGER
	}

    s56NetworkProfile-Shelf-o	OBJECT-TYPE
	SYNTAX	INTEGER
	ACCESS	read-only
	STATUS	mandatory
	DESCRIPTION	""
	::= { mibs56NetworkProfileEntry 1 }

    s56NetworkProfile-Slot-o	OBJECT-TYPE
	SYNTAX	INTEGER
	ACCESS	read-only
	STATUS	mandatory
	DESCRIPTION	""
	::= { mibs56NetworkProfileEntry 2 }

    s56NetworkProfile-Item-o	OBJECT-TYPE
	SYNTAX	INTEGER
	ACCESS	read-only
	STATUS	mandatory
	DESCRIPTION	""
	::= { mibs56NetworkProfileEntry 3 }

    s56NetworkProfile-ProfileNumber	OBJECT-TYPE
	SYNTAX	INTEGER
	ACCESS	read-write
	STATUS	mandatory
	DESCRIPTION	"For potential backwards compatibility. The current design consists of one line profile numbered 0."
	::= { mibs56NetworkProfileEntry 4 }

    s56NetworkProfile-Name	OBJECT-TYPE
	SYNTAX	DisplayString
	ACCESS	read-write
	STATUS	mandatory
	DESCRIPTION	"For potential backwards compatibility. The current design does not use the name field since there is only one line profile. If used in the future it will consits of a null terminated ascii string that the user gave to this particular profile."
	::= { mibs56NetworkProfileEntry 5 }

    s56NetworkProfile-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibs56NetworkProfileEntry 6 }

    s56NetworkProfile-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibs56NetworkProfileEntry 7 }

    s56NetworkProfile-PhysicalAddress-ItemNumber	OBJECT-TYPE
	SYNTAX	INTEGER
	ACCESS	read-write
	STATUS	mandatory
	DESCRIPTION	"A number that specifies an addressable entity within the context of shelf and slot."
	::= { mibs56NetworkProfileEntry 8 }

    s56NetworkProfile-Action-o	OBJECT-TYPE
	SYNTAX	INTEGER {
		    noAction (1),
		    createProfile (2),
		    deleteProfile (3)
		}
	ACCESS	read-write
	STATUS	mandatory
	DESCRIPTION	""
	::= { mibs56NetworkProfileEntry 9 }


	-- The mibs56NetworkProfile__line_interface table
	--
	-- This table contains parameters for the mibs56NetworkProfile__line_interface profile
	--

    mibs56NetworkProfile-LineInterfaceTable	OBJECT-TYPE
	SYNTAX		SEQUENCE OF Mibs56NetworkProfile-LineInterfaceEntry
	ACCESS		not-accessible
	STATUS		mandatory
	DESCRIPTION	"A list of mibs56NetworkProfile__line_interface profile entries."
	::= { mibs56NetworkProfile 2 }

    mibs56NetworkProfile-LineInterfaceEntry	OBJECT-TYPE
	SYNTAX		Mibs56NetworkProfile-LineInterfaceEntry
	ACCESS		not-accessible
	STATUS		mandatory
	DESCRIPTION	"A mibs56NetworkProfile__line_interface entry containing objects that
			 maps to the parameters of mibs56NetworkProfile__line_interface profile."
	INDEX		{ s56NetworkProfile-LineInterface-Shelf-o, s56NetworkProfile-LineInterface-Slot-o, s56NetworkProfile-LineInterface-Item-o, s56NetworkProfile-LineInterface-Index-o }
	::= { mibs56NetworkProfile-LineInterfaceTable 1 }

    Mibs56NetworkProfile-LineInterfaceEntry ::=
	SEQUENCE {
	    s56NetworkProfile-LineInterface-Shelf-o
		INTEGER,
	    s56NetworkProfile-LineInterface-Slot-o
		INTEGER,
	    s56NetworkProfile-LineInterface-Item-o
		INTEGER,
	    s56NetworkProfile-LineInterface-Index-o
		INTEGER,
	    s56NetworkProfile-LineInterface-LineEnabled
		INTEGER
	}

    s56NetworkProfile-LineInterface-Shelf-o	OBJECT-TYPE
	SYNTAX	INTEGER
	ACCESS	read-only
	STATUS	mandatory
	DESCRIPTION	""
	::= { mibs56NetworkProfile-LineInterfaceEntry 1 }

    s56NetworkProfile-LineInterface-Slot-o	OBJECT-TYPE
	SYNTAX	INTEGER
	ACCESS	read-only
	STATUS	mandatory
	DESCRIPTION	""
	::= { mibs56NetworkProfile-LineInterfaceEntry 2 }

    s56NetworkProfile-LineInterface-Item-o	OBJECT-TYPE
	SYNTAX	INTEGER
	ACCESS	read-only
	STATUS	mandatory
	DESCRIPTION	""
	::= { mibs56NetworkProfile-LineInterfaceEntry 3 }

    s56NetworkProfile-LineInterface-Index-o	OBJECT-TYPE
	SYNTAX	INTEGER
	ACCESS	read-only
	STATUS	mandatory
	DESCRIPTION	""
	::= { mibs56NetworkProfile-LineInterfaceEntry 4 }

    s56NetworkProfile-LineInterface-LineEnabled	OBJECT-TYPE
	SYNTAX	INTEGER {
		    no (1),
		    yes (2)
		}
	ACCESS	read-write
	STATUS	mandatory
	DESCRIPTION	"TRUE if the line is enabled, otherwise FALSE."
	::= { mibs56NetworkProfile-LineInterfaceEntry 5 }


	-- The mibs56NetworkProfile__line_interface__channel_config table
	--
	-- This table contains parameters for the mibs56NetworkProfile__line_interface__channel_config profile
	--

    mibs56NetworkProfile-LineInterface-ChannelConfigTable	OBJECT-TYPE
	SYNTAX		SEQUENCE OF Mibs56NetworkProfile-LineInterface-ChannelConfigEntry
	ACCESS		not-accessible
	STATUS		mandatory
	DESCRIPTION	"A list of mibs56NetworkProfile__line_interface__channel_config profile entries."
	::= { mibs56NetworkProfile 3 }

    mibs56NetworkProfile-LineInterface-ChannelConfigEntry	OBJECT-TYPE
	SYNTAX		Mibs56NetworkProfile-LineInterface-ChannelConfigEntry
	ACCESS		not-accessible
	STATUS		mandatory
	DESCRIPTION	"A mibs56NetworkProfile__line_interface__channel_config entry containing objects that
			 maps to the parameters of mibs56NetworkProfile__line_interface__channel_config profile."
	INDEX		{ s56NetworkProfile-LineInterface-ChannelConfig-Shelf-o, s56NetworkProfile-LineInterface-ChannelConfig-Slot-o, s56NetworkProfile-LineInterface-ChannelConfig-Item-o, s56NetworkProfile-LineInterface-ChannelConfig-Index-o, s56NetworkProfile-LineInterface-ChannelConfig-Index1-o }
	::= { mibs56NetworkProfile-LineInterface-ChannelConfigTable 1 }

    Mibs56NetworkProfile-LineInterface-ChannelConfigEntry ::=
	SEQUENCE {
	    s56NetworkProfile-LineInterface-ChannelConfig-Shelf-o
		INTEGER,
	    s56NetworkProfile-LineInterface-ChannelConfig-Slot-o
		INTEGER,
	    s56NetworkProfile-LineInterface-ChannelConfig-Item-o
		INTEGER,
	    s56NetworkProfile-LineInterface-ChannelConfig-Index-o
		INTEGER,
	    s56NetworkProfile-LineInterface-ChannelConfig-Index1-o
		INTEGER,
	    s56NetworkProfile-LineInterface-ChannelConfig-ChannelUsage
		INTEGER,
	    s56NetworkProfile-LineInterface-ChannelConfig-LoopbackEnable
		INTEGER,
	    s56NetworkProfile-LineInterface-ChannelConfig-PhoneNumber
		DisplayString,
	    s56NetworkProfile-LineInterface-ChannelConfig-RoutePort-SlotNumber-SlotNumber
		INTEGER,
	    s56NetworkProfile-LineInterface-ChannelConfig-RoutePort-SlotNumber-ShelfNumber
		INTEGER,
	    s56NetworkProfile-LineInterface-ChannelConfig-RoutePort-RelativePortNumber-RelativePortNumber
		INTEGER,
	    s56NetworkProfile-LineInterface-ChannelConfig-TrunkGroup
		INTEGER,
	    s56NetworkProfile-LineInterface-ChannelConfig-AdslCapRateMode
		INTEGER,
	    s56NetworkProfile-LineInterface-ChannelConfig-AdslCapUpStreamRate
		INTEGER,
	    s56NetworkProfile-LineInterface-ChannelConfig-AdslCapDownStreamRate
		INTEGER,
	    s56NetworkProfile-LineInterface-ChannelConfig-MaxUpStreamRate
		INTEGER,
	    s56NetworkProfile-LineInterface-ChannelConfig-MaxDownStreamRate
		INTEGER,
	    s56NetworkProfile-LineInterface-ChannelConfig-AdslDmtRateMode
		INTEGER,
	    s56NetworkProfile-LineInterface-ChannelConfig-UpStreamMargin
		INTEGER,
	    s56NetworkProfile-LineInterface-ChannelConfig-DownStreamMargin
		INTEGER,
	    s56NetworkProfile-LineInterface-ChannelConfig-UpStreamInterleave
		INTEGER,
	    s56NetworkProfile-LineInterface-ChannelConfig-DownStreamInterleave
		INTEGER,
	    s56NetworkProfile-LineInterface-ChannelConfig-TxPowerLevel
		INTEGER,
	    s56NetworkProfile-LineInterface-ChannelConfig-TxPowerAutoState
		INTEGER,
	    s56NetworkProfile-LineInterface-ChannelConfig-MaintainLanUp
		INTEGER,
	    s56NetworkProfile-LineInterface-ChannelConfig-HdlcDataSense
		INTEGER,
	    s56NetworkProfile-LineInterface-ChannelConfig-SdslDataFormat
		INTEGER,
	    s56NetworkProfile-LineInterface-ChannelConfig-SdslRateMode
		INTEGER,
	    s56NetworkProfile-LineInterface-ChannelConfig-SdslLineRate
		INTEGER,
	    s56NetworkProfile-LineInterface-ChannelConfig-SdslUnitType
		INTEGER,
	    s56NetworkProfile-LineInterface-ChannelConfig-SdslAutoBaseRate
		INTEGER,
	    s56NetworkProfile-LineInterface-ChannelConfig-Hdsl2UnitType
		INTEGER,
	    s56NetworkProfile-LineInterface-ChannelConfig-FrontEndBalance
		INTEGER,
	    s56NetworkProfile-LineInterface-ChannelConfig-Trellis
		INTEGER,
	    s56NetworkProfile-LineInterface-ChannelConfig-AdslLineCode
		INTEGER,
	    s56NetworkProfile-LineInterface-ChannelConfig-HdslInterfaceType
		INTEGER,
	    s56NetworkProfile-LineInterface-ChannelConfig-RateMode
		INTEGER,
	    s56NetworkProfile-LineInterface-ChannelConfig-MaxRate
		INTEGER,
	    s56NetworkProfile-LineInterface-ChannelConfig-MinRate
		INTEGER,
	    s56NetworkProfile-LineInterface-ChannelConfig-GshdslStandardNetworkType
		INTEGER,
	    s56NetworkProfile-LineInterface-ChannelConfig-GshdslPsdType
		INTEGER,
	    s56NetworkProfile-LineInterface-ChannelConfig-FastRetrain
		INTEGER,
	    s56NetworkProfile-LineInterface-ChannelConfig-BitSwapping
		INTEGER,
	    s56NetworkProfile-LineInterface-ChannelConfig-FramingMode
		INTEGER,
	    s56NetworkProfile-LineInterface-ChannelConfig-TxPower
		INTEGER,
	    s56NetworkProfile-LineInterface-ChannelConfig-MaxDownRate
		INTEGER,
	    s56NetworkProfile-LineInterface-ChannelConfig-DnstreamStartBin
		INTEGER,
	    s56NetworkProfile-LineInterface-ChannelConfig-DnstreamEndBin
		INTEGER,
	    s56NetworkProfile-LineInterface-ChannelConfig-UpstreamStartBin
		INTEGER,
	    s56NetworkProfile-LineInterface-ChannelConfig-UpstreamEndBin
		INTEGER,
	    s56NetworkProfile-LineInterface-ChannelConfig-AnnexbAnfpEnabled
		INTEGER
	}

    s56NetworkProfile-LineInterface-ChannelConfig-Shelf-o	OBJECT-TYPE
	SYNTAX	INTEGER
	ACCESS	read-only
	STATUS	mandatory
	DESCRIPTION	""
	::= { mibs56NetworkProfile-LineInterface-ChannelConfigEntry 1 }

    s56NetworkProfile-LineInterface-ChannelConfig-Slot-o	OBJECT-TYPE
	SYNTAX	INTEGER
	ACCESS	read-only
	STATUS	mandatory
	DESCRIPTION	""
	::= { mibs56NetworkProfile-LineInterface-ChannelConfigEntry 2 }

    s56NetworkProfile-LineInterface-ChannelConfig-Item-o	OBJECT-TYPE
	SYNTAX	INTEGER
	ACCESS	read-only
	STATUS	mandatory
	DESCRIPTION	""
	::= { mibs56NetworkProfile-LineInterface-ChannelConfigEntry 3 }

    s56NetworkProfile-LineInterface-ChannelConfig-Index-o	OBJECT-TYPE
	SYNTAX	INTEGER
	ACCESS	read-only
	STATUS	mandatory
	DESCRIPTION	""
	::= { mibs56NetworkProfile-LineInterface-ChannelConfigEntry 4 }

    s56NetworkProfile-LineInterface-ChannelConfig-Index1-o	OBJECT-TYPE
	SYNTAX	INTEGER
	ACCESS	read-only
	STATUS	mandatory
	DESCRIPTION	""
	::= { mibs56NetworkProfile-LineInterface-ChannelConfigEntry 5 }

    s56NetworkProfile-LineInterface-ChannelConfig-ChannelUsage	OBJECT-TYPE
	SYNTAX	INTEGER {
		    unusedChannel (1),
		    switchedChannel (2),
		    nailed64Channel (3),
		    dChannel (4),
		    nfasPrimaryDChannel (5),
		    nfasSecondaryDChannel (6),
		    semiPermChannel (7),
		    ss7SignalingChannel (8)
		}
	ACCESS	read-write
	STATUS	mandatory
	DESCRIPTION	""
	::= { mibs56NetworkProfile-LineInterface-ChannelConfigEntry 6 }

    s56NetworkProfile-LineInterface-ChannelConfig-LoopbackEnable	OBJECT-TYPE
	SYNTAX	INTEGER {
		    no (1),
		    yes (2)
		}
	ACCESS	read-write
	STATUS	mandatory
	DESCRIPTION	""
	::= { mibs56NetworkProfile-LineInterface-ChannelConfigEntry 7 }

    s56NetworkProfile-LineInterface-ChannelConfig-PhoneNumber	OBJECT-TYPE
	SYNTAX	DisplayString
	ACCESS	read-write
	STATUS	mandatory
	DESCRIPTION	""
	::= { mibs56NetworkProfile-LineInterface-ChannelConfigEntry 8 }

    s56NetworkProfile-LineInterface-ChannelConfig-RoutePort-SlotNumber-SlotNumber	OBJECT-TYPE
	SYNTAX	INTEGER
	ACCESS	read-write
	STATUS	mandatory
	DESCRIPTION	""
	::= { mibs56NetworkProfile-LineInterface-ChannelConfigEntry 9 }

    s56NetworkProfile-LineInterface-ChannelConfig-RoutePort-SlotNumber-ShelfNumber	OBJECT-TYPE
	SYNTAX	INTEGER
	ACCESS	read-write
	STATUS	mandatory
	DESCRIPTION	"TNT is a multi shelf system. To minimise the changes required to existing code the shelf number is added to this structure as it will almost always be needed when a slot number is needed."
	::= { mibs56NetworkProfile-LineInterface-ChannelConfigEntry 10 }

    s56NetworkProfile-LineInterface-ChannelConfig-RoutePort-RelativePortNumber-RelativePortNumber	OBJECT-TYPE
	SYNTAX	INTEGER
	ACCESS	read-write
	STATUS	mandatory
	DESCRIPTION	""
	::= { mibs56NetworkProfile-LineInterface-ChannelConfigEntry 11 }

    s56NetworkProfile-LineInterface-ChannelConfig-TrunkGroup	OBJECT-TYPE
	SYNTAX	INTEGER
	ACCESS	read-write
	STATUS	mandatory
	DESCRIPTION	""
	::= { mibs56NetworkProfile-LineInterface-ChannelConfigEntry 12 }

    s56NetworkProfile-LineInterface-ChannelConfig-AdslCapRateMode	OBJECT-TYPE
	SYNTAX	INTEGER {
		    autobaud (2),
		    singlebaud (3)
		}
	ACCESS	read-write
	STATUS	mandatory
	DESCRIPTION	""
	::= { mibs56NetworkProfile-LineInterface-ChannelConfigEntry 13 }

    s56NetworkProfile-LineInterface-ChannelConfig-AdslCapUpStreamRate	OBJECT-TYPE
	SYNTAX	INTEGER {
		    n-1088000 (51),
		    n-952000 (52),
		    n-816000 (53),
		    n-680000 (54),
		    n-544000 (55),
		    n-408000 (56),
		    n-272000 (57)
		}
	ACCESS	read-write
	STATUS	mandatory
	DESCRIPTION	""
	::= { mibs56NetworkProfile-LineInterface-ChannelConfigEntry 14 }

    s56NetworkProfile-LineInterface-ChannelConfig-AdslCapDownStreamRate	OBJECT-TYPE
	SYNTAX	INTEGER {
		    n-7168000 (1),
		    n-6272000 (2),
		    n-5120000 (3),
		    n-4480000 (4),
		    n-3200000 (5),
		    n-2688000 (6),
		    n-2560000 (7),
		    n-2240000 (8),
		    n-1920000 (9),
		    n-1600000 (10),
		    n-1280000 (11),
		    n-960000 (12),
		    n-640000 (13)
		}
	ACCESS	read-write
	STATUS	mandatory
	DESCRIPTION	""
	::= { mibs56NetworkProfile-LineInterface-ChannelConfigEntry 15 }

    s56NetworkProfile-LineInterface-ChannelConfig-MaxUpStreamRate	OBJECT-TYPE
	SYNTAX	INTEGER {
		    upstrmMegMax (151),
		    n-1088000 (152),
		    n-928000 (153),
		    n-896000 (154),
		    n-800000 (155),
		    n-768000 (156),
		    n-640000 (157),
		    n-512000 (158),
		    n-384000 (159),
		    n-256000 (160),
		    n-128000 (161)
		}
	ACCESS	read-write
	STATUS	mandatory
	DESCRIPTION	""
	::= { mibs56NetworkProfile-LineInterface-ChannelConfigEntry 16 }

    s56NetworkProfile-LineInterface-ChannelConfig-MaxDownStreamRate	OBJECT-TYPE
	SYNTAX	INTEGER {
		    dwnstrmMegMax (101),
		    n-9504000 (102),
		    n-8960000 (103),
		    n-8000000 (104),
		    n-7168000 (105),
		    n-6272000 (106),
		    n-5120000 (107),
		    n-4480000 (108),
		    n-3200000 (109),
		    n-2688000 (110),
		    n-2560000 (111),
		    n-2240000 (112),
		    n-1920000 (113),
		    n-1600000 (114),
		    n-1280000 (115),
		    n-960000 (116),
		    n-768000 (117),
		    n-640000 (118),
		    n-512000 (119),
		    n-384000 (120),
		    n-256000 (121),
		    n-128000 (122)
		}
	ACCESS	read-write
	STATUS	mandatory
	DESCRIPTION	""
	::= { mibs56NetworkProfile-LineInterface-ChannelConfigEntry 17 }

    s56NetworkProfile-LineInterface-ChannelConfig-AdslDmtRateMode	OBJECT-TYPE
	SYNTAX	INTEGER {
		    autobaud (2),
		    singlebaud (3)
		}
	ACCESS	read-write
	STATUS	mandatory
	DESCRIPTION	""
	::= { mibs56NetworkProfile-LineInterface-ChannelConfigEntry 18 }

    s56NetworkProfile-LineInterface-ChannelConfig-UpStreamMargin	OBJECT-TYPE
	SYNTAX	INTEGER
	ACCESS	read-write
	STATUS	mandatory
	DESCRIPTION	""
	::= { mibs56NetworkProfile-LineInterface-ChannelConfigEntry 19 }

    s56NetworkProfile-LineInterface-ChannelConfig-DownStreamMargin	OBJECT-TYPE
	SYNTAX	INTEGER
	ACCESS	read-write
	STATUS	mandatory
	DESCRIPTION	""
	::= { mibs56NetworkProfile-LineInterface-ChannelConfigEntry 20 }

    s56NetworkProfile-LineInterface-ChannelConfig-UpStreamInterleave	OBJECT-TYPE
	SYNTAX	INTEGER {
		    dmt0 (1),
		    dmt2 (3),
		    dmt4 (5),
		    dmt8 (9),
		    dmt16 (17),
		    dmt32 (33),
		    dmt64 (65)
		}
	ACCESS	read-write
	STATUS	mandatory
	DESCRIPTION	""
	::= { mibs56NetworkProfile-LineInterface-ChannelConfigEntry 21 }

    s56NetworkProfile-LineInterface-ChannelConfig-DownStreamInterleave	OBJECT-TYPE
	SYNTAX	INTEGER {
		    dmt0 (1),
		    dmt2 (3),
		    dmt4 (5),
		    dmt8 (9),
		    dmt16 (17),
		    dmt32 (33),
		    dmt64 (65)
		}
	ACCESS	read-write
	STATUS	mandatory
	DESCRIPTION	""
	::= { mibs56NetworkProfile-LineInterface-ChannelConfigEntry 22 }

    s56NetworkProfile-LineInterface-ChannelConfig-TxPowerLevel	OBJECT-TYPE
	SYNTAX	INTEGER
	ACCESS	read-write
	STATUS	mandatory
	DESCRIPTION	""
	::= { mibs56NetworkProfile-LineInterface-ChannelConfigEntry 23 }

    s56NetworkProfile-LineInterface-ChannelConfig-TxPowerAutoState	OBJECT-TYPE
	SYNTAX	INTEGER {
		    disabled (1),
		    adjusting (2),
		    tracking (3),
		    locked (4)
		}
	ACCESS	read-write
	STATUS	mandatory
	DESCRIPTION	""
	::= { mibs56NetworkProfile-LineInterface-ChannelConfigEntry 24 }

    s56NetworkProfile-LineInterface-ChannelConfig-MaintainLanUp	OBJECT-TYPE
	SYNTAX	INTEGER {
		    no (1),
		    yes (2)
		}
	ACCESS	read-write
	STATUS	mandatory
	DESCRIPTION	""
	::= { mibs56NetworkProfile-LineInterface-ChannelConfigEntry 25 }

    s56NetworkProfile-LineInterface-ChannelConfig-HdlcDataSense	OBJECT-TYPE
	SYNTAX	INTEGER {
		    normal (1),
		    inv (2)
		}
	ACCESS	read-write
	STATUS	mandatory
	DESCRIPTION	""
	::= { mibs56NetworkProfile-LineInterface-ChannelConfigEntry 26 }

    s56NetworkProfile-LineInterface-ChannelConfig-SdslDataFormat	OBJECT-TYPE
	SYNTAX	INTEGER {
		    serial (1)
		}
	ACCESS	read-write
	STATUS	mandatory
	DESCRIPTION	""
	::= { mibs56NetworkProfile-LineInterface-ChannelConfigEntry 27 }

    s56NetworkProfile-LineInterface-ChannelConfig-SdslRateMode	OBJECT-TYPE
	SYNTAX	INTEGER {
		    autobaud (2),
		    singlebaud (3)
		}
	ACCESS	read-write
	STATUS	mandatory
	DESCRIPTION	""
	::= { mibs56NetworkProfile-LineInterface-ChannelConfigEntry 28 }

    s56NetworkProfile-LineInterface-ChannelConfig-SdslLineRate	OBJECT-TYPE
	SYNTAX	INTEGER {
		    n-144000 (1),
		    n-272000 (2),
		    n-400000 (3),
		    n-528000 (4),
		    n-784000 (5),
		    n-1168000 (6),
		    n-1552000 (7),
		    n-2320000 (8),
		    n-160000 (9),
		    n-192000 (10),
		    n-208000 (11),
		    n-384000 (12),
		    n-416000 (13),
		    n-768000 (14),
		    n-1040000 (15),
		    n-1152000 (16),
		    n-1536000 (17),
		    n-1568000 (18),
		    n-1680000 (19),
		    n-1920000 (20),
		    n-2160000 (21)
		}
	ACCESS	read-write
	STATUS	mandatory
	DESCRIPTION	""
	::= { mibs56NetworkProfile-LineInterface-ChannelConfigEntry 29 }

    s56NetworkProfile-LineInterface-ChannelConfig-SdslUnitType	OBJECT-TYPE
	SYNTAX	INTEGER {
		    coe (1),
		    cpe (2)
		}
	ACCESS	read-write
	STATUS	mandatory
	DESCRIPTION	""
	::= { mibs56NetworkProfile-LineInterface-ChannelConfigEntry 30 }

    s56NetworkProfile-LineInterface-ChannelConfig-SdslAutoBaseRate	OBJECT-TYPE
	SYNTAX	INTEGER {
		    n-144000 (1),
		    n-272000 (2),
		    n-400000 (3),
		    n-528000 (4),
		    n-784000 (5),
		    n-1168000 (6),
		    n-1552000 (7),
		    n-2320000 (8),
		    n-160000 (9),
		    n-192000 (10),
		    n-208000 (11),
		    n-384000 (12),
		    n-416000 (13),
		    n-768000 (14),
		    n-1040000 (15),
		    n-1152000 (16),
		    n-1536000 (17),
		    n-1568000 (18),
		    n-1680000 (19),
		    n-1920000 (20),
		    n-2160000 (21)
		}
	ACCESS	read-write
	STATUS	mandatory
	DESCRIPTION	""
	::= { mibs56NetworkProfile-LineInterface-ChannelConfigEntry 31 }

    s56NetworkProfile-LineInterface-ChannelConfig-Hdsl2UnitType	OBJECT-TYPE
	SYNTAX	INTEGER {
		    coe (1),
		    cpe (2)
		}
	ACCESS	read-write
	STATUS	mandatory
	DESCRIPTION	""
	::= { mibs56NetworkProfile-LineInterface-ChannelConfigEntry 32 }

    s56NetworkProfile-LineInterface-ChannelConfig-FrontEndBalance	OBJECT-TYPE
	SYNTAX	INTEGER {
		    upstrmBoost (1)
		}
	ACCESS	read-write
	STATUS	mandatory
	DESCRIPTION	""
	::= { mibs56NetworkProfile-LineInterface-ChannelConfigEntry 33 }

    s56NetworkProfile-LineInterface-ChannelConfig-Trellis	OBJECT-TYPE
	SYNTAX	INTEGER {
		    no (1),
		    yes (2)
		}
	ACCESS	read-write
	STATUS	mandatory
	DESCRIPTION	""
	::= { mibs56NetworkProfile-LineInterface-ChannelConfigEntry 34 }

    s56NetworkProfile-LineInterface-ChannelConfig-AdslLineCode	OBJECT-TYPE
	SYNTAX	INTEGER {
		    no (1),
		    yes (2)
		}
	ACCESS	read-write
	STATUS	mandatory
	DESCRIPTION	""
	::= { mibs56NetworkProfile-LineInterface-ChannelConfigEntry 35 }

    s56NetworkProfile-LineInterface-ChannelConfig-HdslInterfaceType	OBJECT-TYPE
	SYNTAX	INTEGER {
		    default (1),
		    gShdsl (2),
		    hdsl2 (3)
		}
	ACCESS	read-write
	STATUS	mandatory
	DESCRIPTION	""
	::= { mibs56NetworkProfile-LineInterface-ChannelConfigEntry 45 }

    s56NetworkProfile-LineInterface-ChannelConfig-RateMode	OBJECT-TYPE
	SYNTAX	INTEGER {
		    fixed (1),
		    auto (2)
		}
	ACCESS	read-write
	STATUS	mandatory
	DESCRIPTION	""
	::= { mibs56NetworkProfile-LineInterface-ChannelConfigEntry 46 }

    s56NetworkProfile-LineInterface-ChannelConfig-MaxRate	OBJECT-TYPE
	SYNTAX	INTEGER {
		    n-72000 (72001),
		    n-136000 (136001),
		    n-200000 (200001),
		    n-264000 (264001),
		    n-328000 (328001),
		    n-392000 (392001),
		    n-520000 (520001),
		    n-776000 (776001),
		    n-1032000 (1032001),
		    n-1160000 (1160001),
		    n-1288000 (1288001),
		    n-1544000 (1544001),
		    n-2056000 (2056001),
		    n-2312000 (2312001)
		}
	ACCESS	read-write
	STATUS	mandatory
	DESCRIPTION	""
	::= { mibs56NetworkProfile-LineInterface-ChannelConfigEntry 47 }

    s56NetworkProfile-LineInterface-ChannelConfig-MinRate	OBJECT-TYPE
	SYNTAX	INTEGER {
		    n-72000 (72001),
		    n-136000 (136001),
		    n-200000 (200001),
		    n-264000 (264001),
		    n-328000 (328001),
		    n-392000 (392001),
		    n-520000 (520001),
		    n-776000 (776001),
		    n-1032000 (1032001),
		    n-1160000 (1160001),
		    n-1288000 (1288001),
		    n-1544000 (1544001),
		    n-2056000 (2056001),
		    n-2312000 (2312001)
		}
	ACCESS	read-write
	STATUS	mandatory
	DESCRIPTION	""
	::= { mibs56NetworkProfile-LineInterface-ChannelConfigEntry 48 }

    s56NetworkProfile-LineInterface-ChannelConfig-GshdslStandardNetworkType	OBJECT-TYPE
	SYNTAX	INTEGER {
		    northAmericanAnnexA (1),
		    europeanAnnexB (2),
		    autoDetect (3)
		}
	ACCESS	read-write
	STATUS	mandatory
	DESCRIPTION	"Per the G.SHDSL Standard G.991.2. This parameter allows selection for the modem to operate either the North American Annex 'A' or European Annex 'B' standard network types."
	::= { mibs56NetworkProfile-LineInterface-ChannelConfigEntry 49 }

    s56NetworkProfile-LineInterface-ChannelConfig-GshdslPsdType	OBJECT-TYPE
	SYNTAX	INTEGER {
		    symmetric (1),
		    asymmetric776kPsdAnnexA (4),
		    asymmetric1544kPsdAnnexA (5),
		    asymmetric2056kPsdAnnexB (6),
		    asymmetric2312kPsdAnnexB (7),
		    autoDetect (8)
		}
	ACCESS	read-write
	STATUS	mandatory
	DESCRIPTION	"Per the G.SHDSL Standard G.911.2. This parameter allows selection for the modem to output a symmetric PSD at all rates or asymmetric PSD's at fixed rates of 776kbps or 1544kbps."
	::= { mibs56NetworkProfile-LineInterface-ChannelConfigEntry 50 }

    s56NetworkProfile-LineInterface-ChannelConfig-FastRetrain	OBJECT-TYPE
	SYNTAX	INTEGER {
		    no (1),
		    yes (2)
		}
	ACCESS	read-write
	STATUS	mandatory
	DESCRIPTION	""
	::= { mibs56NetworkProfile-LineInterface-ChannelConfigEntry 36 }

    s56NetworkProfile-LineInterface-ChannelConfig-BitSwapping	OBJECT-TYPE
	SYNTAX	INTEGER {
		    no (1),
		    yes (2)
		}
	ACCESS	read-write
	STATUS	mandatory
	DESCRIPTION	""
	::= { mibs56NetworkProfile-LineInterface-ChannelConfigEntry 37 }

    s56NetworkProfile-LineInterface-ChannelConfig-FramingMode	OBJECT-TYPE
	SYNTAX	INTEGER
	ACCESS	read-write
	STATUS	mandatory
	DESCRIPTION	""
	::= { mibs56NetworkProfile-LineInterface-ChannelConfigEntry 38 }

    s56NetworkProfile-LineInterface-ChannelConfig-TxPower	OBJECT-TYPE
	SYNTAX	INTEGER
	ACCESS	read-write
	STATUS	mandatory
	DESCRIPTION	""
	::= { mibs56NetworkProfile-LineInterface-ChannelConfigEntry 39 }

    s56NetworkProfile-LineInterface-ChannelConfig-MaxDownRate	OBJECT-TYPE
	SYNTAX	INTEGER
	ACCESS	read-write
	STATUS	mandatory
	DESCRIPTION	""
	::= { mibs56NetworkProfile-LineInterface-ChannelConfigEntry 40 }

    s56NetworkProfile-LineInterface-ChannelConfig-DnstreamStartBin	OBJECT-TYPE
	SYNTAX	INTEGER
	ACCESS	read-write
	STATUS	mandatory
	DESCRIPTION	""
	::= { mibs56NetworkProfile-LineInterface-ChannelConfigEntry 41 }

    s56NetworkProfile-LineInterface-ChannelConfig-DnstreamEndBin	OBJECT-TYPE
	SYNTAX	INTEGER
	ACCESS	read-write
	STATUS	mandatory
	DESCRIPTION	""
	::= { mibs56NetworkProfile-LineInterface-ChannelConfigEntry 42 }

    s56NetworkProfile-LineInterface-ChannelConfig-UpstreamStartBin	OBJECT-TYPE
	SYNTAX	INTEGER
	ACCESS	read-write
	STATUS	mandatory
	DESCRIPTION	""
	::= { mibs56NetworkProfile-LineInterface-ChannelConfigEntry 43 }

    s56NetworkProfile-LineInterface-ChannelConfig-UpstreamEndBin	OBJECT-TYPE
	SYNTAX	INTEGER
	ACCESS	read-write
	STATUS	mandatory
	DESCRIPTION	""
	::= { mibs56NetworkProfile-LineInterface-ChannelConfigEntry 44 }

    s56NetworkProfile-LineInterface-ChannelConfig-AnnexbAnfpEnabled	OBJECT-TYPE
	SYNTAX	INTEGER {
		    no (1),
		    yes (2)
		}
	ACCESS	read-write
	STATUS	mandatory
	DESCRIPTION	"TRUE if Annex B ANFP functionality is enabled, otherwise FALSE. The gshdsl-standard-network-type must be set to European Annex B, and the port cannot be CPE. This field makes the modem perform in Annex B mode, but slightly differently. This is to comply with the UK ANFP requirements and pass the BTexact Technologies PSD measurement technique to meet BT approval. Only enable this field for that test specifically."
	::= { mibs56NetworkProfile-LineInterface-ChannelConfigEntry 52 }

END
