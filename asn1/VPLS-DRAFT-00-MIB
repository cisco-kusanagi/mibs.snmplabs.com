-- extracted from draft-nadeau-l2vpn-vpls-mib-00.txt
-- at Tue Jun 20 06:06:28 2006

      VPLS-DRAFT-00-MIB DEFINITIONS ::= BEGIN 
       
      IMPORTS 
      NOTIFICATION-TYPE, MODULE-IDENTITY, OBJECT-TYPE,  
       Integer32, Unsigned32, Counter32, Counter64, TimeTicks, 
      transmission  
         FROM SNMPv2-SMI                    -- RFC2578
    
      MODULE-COMPLIANCE, OBJECT-GROUP, NOTIFICATION-GROUP  
         FROM SNMPv2-CONF                   -- RFC2580 
    
      TruthValue, RowStatus, StorageType,  
      TimeStamp  
         FROM SNMPv2-TC                     -- RFC2579 
    
      SnmpAdminString  
         FROM SNMP-FRAMEWORK-MIB            -- RFC3411
    
      InterfaceIndexOrZero  
         FROM IF-MIB                        -- RFC2863 
    
      InetAddressType, InetAddress  
         FROM INET-ADDRESS-MIB              -- RFC4001 
       
       PwIndexType
               FROM PW-TC-STD-MIB

        VPNIdOrZero 
               FROM VPN-TC-STD-MIB           -- RFC4265
;
       
   vplsDraft00MIB MODULE-IDENTITY  
       draft-nadeau-l2vpn-vpls-mib-00   L2-VPN-MIB      June 16, 2006



      LAST-UPDATED "200606041200Z"  -- 4 June 2006 12:00:00 GMT  
      ORGANIZATION "Layer 2 Virtual Private Networks (L2VPN) 
                                 Working  Group"  
      CONTACT-INFO  
          "  
           Thomas D. Nadeau  
           Email:  tnadeau@cisco.com  
    
           The L2VPN Working Group (email distribution l2vpn@ietf.org,  
           http://www.ietf.org/html.charters/l2vpn-charter.html)  
           "  
    
      DESCRIPTION  
          "Copyright (C) The Internet Society (2006). The initial  
           version of this MIB module was published in RFC XXXX.  
   -- RFC Editor: Please replace XXXX with RFC number & remove 
   --                    this note.  
    
           For full legal notices see the RFC itself or see: 
           http://www.ietf.org/copyrights/ianamib.html 
                  
           This MIB module contains managed object definitions for   
           Virtual Private LAN Services as in [VPLS-LDP]
    
           This MIB module enables the use of any underlying Pseudo Wire 
           network. 
        
           Copyright (C) The Internet Society (2006).  This version  
           of this MIB module is part of RFC XXX;  see the RFC  
           itself for full legal notices.  
      -- RFC Ed.: replace XXX with actual RFC number & remove this  
      -- note  
           "  
    
      -- Revision history.  
    
      REVISION  
          "200606041200Z"  -- 4 June 2006 12:00:00 GMT  
      DESCRIPTION "Initial version published as part of RFC YYYY." 
   -- RFC Editor: please replace YYYY with IANA assigned value, and  
   -- delete this note.  
    
         ::= { transmission XXXX } 
   -- RFC Editor: please replace XXXX with IANA assigne value, and  
   -- delete this note.  
    
   -- Top-level components of this MIB.  
       draft-nadeau-l2vpn-vpls-mib-00   L2-VPN-MIB      June 16, 2006



   -- Notifications  
   vplsNotifications OBJECT IDENTIFIER   
                                 ::= { vplsDraft00MIB 0 }  
   -- Tables, Scalars  
   vplsObjects       OBJECT IDENTIFIER  
                                 ::= { vplsDraft00MIB 1 }  
   -- Conformance  
   vplsConformance   OBJECT IDENTIFIER   
                                 ::= { vplsDraft00MIB 2 }  
    
   -- PW Virtual Connection Table  
    
   vplsIndexNext OBJECT-TYPE  
      SYNTAX            Unsigned32  
      MAX-ACCESS        read-only  
      STATUS            current  
      DESCRIPTION  
          "This object contains an appropriate value to be used  
           for vplsIndex when creating entries in the  
           vplsConfigTable. The value 0 indicates that no  
           unassigned entries are available.  To obtain the  
           value of vplsIndex for a new entry in the  
           vplsTable, the manager issues a management  
           protocol retrieval operation to obtain the current  
           value of vplsIndex.  After each retrieval  
           operation, the agent should modify the value to  
           reflect the next unassigned index.  After a manager  
           retrieves a value the agent will determine through  
           its local policy when this index value will be made  
           available for reuse."  
      ::= { vplsObjects 1 }  

       
      vplsConfigTable OBJECT-TYPE 
          SYNTAX          SEQUENCE OF VplsConfigEntry 
          MAX-ACCESS      not-accessible 
          STATUS          current 
          DESCRIPTION     
               "This table specifies information for configuring
                and monitoring Virtual Private Lan Services(VPLS).
                " 
          ::= { vplsObjects 2 } 
       
      vplsConfigEntry OBJECT-TYPE 
          SYNTAX          VplsConfigEntry 
          MAX-ACCESS      not-accessible 
          STATUS          current 
          DESCRIPTION     

       draft-nadeau-l2vpn-vpls-mib-00   L2-VPN-MIB      June 16, 2006



           "A row in this table represents a Virtual Private Lan 
            Service(VPLS) in a packet network. It is indexed by  
            vplsIndex, which uniquely identifies a single VPLS.   

            A row is created by the operator or by the agent if a 
            VPLS service is created by non-SNMP application or 
            due to autodiscovery process.  

            None of the read-create objects values can be 
            changed when vplsRowStatus is in the active(1) 
            state. Changes are allowed when the vplsRowStatus 
            is in notInService(2) or notReady(3) states only.   
            If the operator need to change one of the values 
            for an active row the vplsRowStatus should be 
            first changed to notInService(2), the objects may 
            be changed now, and later to active(1) in order to 
            re-initiate the signaling process with the new 
            values in effect.  
            "  
          INDEX           { vplsIndex } 
          ::= { vplsConfigTable 1 } 
               
     VplsConfigEntry ::= 
        SEQUENCE { 
          vplsIndex                                 Unsigned32, 
         vplsName                                 SnmpAdminString,
         vplsDescr                                SnmpAdminString,
         vplsAdminStatus                     INTEGER, 
         vplsOperStatus                        INTEGER, 
         vplsMacLearning                     TruthValue, 
         vplsDiscardUnknownDest       TruthValue, 
         vplsMacAging                         TruthValue, 
         vplsVpnId                                VPNIdOrZero, 
         vplsConfigFwdFullHighWatermark   Unsigned32, 
         vplsConfigFwdFullLowWatermark     Unsigned32, 
         vplsRowStatus                                  RowStatus 
          } 
       
      vplsIndex  OBJECT-TYPE 
          SYNTAX          Unsigned32 (1.. 2147483647)
          MAX-ACCESS      not-accessible 
          STATUS          current 
          DESCRIPTION     
               "Unique index for the conceptual row identifying 
                a VPLS service." 
          ::= { vplsConfigEntry 1 } 

      vplsName  OBJECT-TYPE 
       draft-nadeau-l2vpn-vpls-mib-00   L2-VPN-MIB      June 16, 2006



          SYNTAX          SnmpAdminString 
          MAX-ACCESS      read-create
          STATUS          current 
          DESCRIPTION     
               "A textual name of the VPLS.
                If there is no local name, or this object is 
                otherwise not applicable, then this object MUST 
                contain a zero-length octet string." 
          DEFVAL           { "" }
          ::= { vplsConfigEntry 2 } 

      vplsDescr  OBJECT-TYPE 
          SYNTAX          SnmpAdminString 
          MAX-ACCESS      read-create
          STATUS          current 
          DESCRIPTION     
               "A textual string containing information about the
               VPLS service. If there is no information for this VPLS
               service, then this object MUST contain a zero-length 
               octet string."
          DEFVAL           { "" }
          ::= { vplsConfigEntry 3 } 
              
      vplsAdminStatus OBJECT-TYPE 
          SYNTAX          INTEGER { 
                              up(1), 
                              down(2),
                              testing(3)   -- in some test mode
 
                          } 
          MAX-ACCESS      read-create 
          STATUS          current 
          DESCRIPTION     
               "The desired administrative state of the VPLS  
                service. If the administrative status of the 
                Vpls service is changed to enable then this 
                service is able to utilize the pseudo wire to 
                perform the tasks of a VPLS service. 
                The testing(3) state indicates that no operational 
                packets can be passed. " 
          DEFVAL           { down } 
          ::= { vplsConfigEntry 4 } 
       
      vplsOperStatus OBJECT-TYPE 
          SYNTAX          INTEGER { 
                              unknown(0),
                              up(1), 
                              down(2)

       draft-nadeau-l2vpn-vpls-mib-00   L2-VPN-MIB      June 16, 2006



                          } 
          MAX-ACCESS      read-only 
          STATUS          current 
          DESCRIPTION     
               "The current operational state of this VPLS Service." 
          ::= { vplsConfigEntry 5 } 
       
      vplsMacLearning OBJECT-TYPE 
          SYNTAX          TruthValue
          MAX-ACCESS      read-create 
          STATUS          current 
          DESCRIPTION     
               "This object specifies if MAC Learning is enabled
                in this service. If this object is true then Mac
                Learning is enabled. If false, then Mac Learning is
                disabled."
          DEFVAL          { true } 
          ::= { vplsConfigEntry 6 } 
       
      vplsDiscardUnknownDest OBJECT-TYPE 
          SYNTAX          TruthValue
          MAX-ACCESS      read-create 
          STATUS          current 
          DESCRIPTION     
               "If the value of this object is 'true', then frames 
                received with an unknown destination MAC are 
                discarded in this VPLS. If 'false', then the 
                packets are processed."
          DEFVAL          { false } 
          ::= { vplsConfigEntry 7 } 
       

      vplsMacAging OBJECT-TYPE 
          SYNTAX          TruthValue
          MAX-ACCESS      read-create 
          STATUS          current 
          DESCRIPTION     
               "If the value of this object is 'true'
                then the MAC ageing process is enabled in 
                this VPLS. If 'false', then the MAC ageing process
                is disabled" 
          DEFVAL          { true } 
          ::= { vplsConfigEntry 8 } 
       
       
      vplsVpnId OBJECT-TYPE 
          SYNTAX          VPNIdOrZero
          MAX-ACCESS      read-only 

       draft-nadeau-l2vpn-vpls-mib-00   L2-VPN-MIB      June 16, 2006



          STATUS          current 
          DESCRIPTION     
               "This objects indicates the IEEE 802-1990 
                 VPN ID of the associated VPLS service." 
-- Ed note: Should we import the VPNIdOrZero TC or 
 --              define a new TC?
          ::= { vplsConfigEntry 9 } 

      vplsConfigFwdFullHighWatermark OBJECT-TYPE 
          SYNTAX          Unsigned32 (0..100) 
          UNITS           "percentage"
          MAX-ACCESS      read-create 
          STATUS          current 
          DESCRIPTION     
               "This object specifies the utilization of the
                forwarding database for this VPLS instance at 
                which the vplsFwdFullAlarmRaised notification 
                will be sent." 
          DEFVAL          { 95 } 
          ::= { vplsConfigEntry 10 } 
       
      vplsConfigFwdFullLowWatermark OBJECT-TYPE 
          SYNTAX          Unsigned32 (0..100) 
          UNITS           "percentage" 
          MAX-ACCESS      read-create 
          STATUS          current 
          DESCRIPTION     
               "This object specifies the utilization of the
                forwarding database for this VPLS instance 
                at which the vplsFwdFullAlarmCleared 
                notification will be sent." 
          DEFVAL          { 90 } 
          ::= { vplsConfigEntry 11 } 

      vplsRowStatus OBJECT-TYPE 
          SYNTAX          RowStatus 
          MAX-ACCESS      read-create 
          STATUS          current 
          DESCRIPTION     
               "For creating, modifying, and deleting this row. 
                None of the read-create objects in the 
                conceptual rows may be changed when this 
                object is in the active(1) state." 
          ::= { vplsConfigEntry 12 } 

    
      -- VPLS PW Binding Table 
       draft-nadeau-l2vpn-vpls-mib-00   L2-VPN-MIB      June 16, 2006



      vplsPwBindTable OBJECT-TYPE 
          SYNTAX          SEQUENCE OF VplsPwBindEntry 
          MAX-ACCESS      not-accessible 
          STATUS          current 
          DESCRIPTION    
               "This table provides an association between a 
                VPLS service and the corresponding Pseudo 
                Wires. A service can have more than one Pseudo 
                Wire association. Pseudo Wires are defined in 
                the pwTable [PWE3-PW-MIB]" 
          ::= { vplsObjects 3 } 
       
      vplsPwBindEntry OBJECT-TYPE 
          SYNTAX          VplsPwBindEntry 
          MAX-ACCESS      not-accessible 
          STATUS          current 
          DESCRIPTION     
               "Each row represents an association between a 
                VPLS instance and one or more Pseudo Wires 
                defined in the pwTable. Each index is unique 
                in describing an entry in this table. However
                both indexes are required to define the one 
                to many association of service to 
                pseudowire." 
          INDEX  { vplsIndex, vplsPwIndex } 
          ::= { vplsPwBindTable 1 } 
       
      VplsPwBindEntry ::= 
          SEQUENCE { 
              vplsPwIndex                     PwIndexType,
              vplsPwBindBindType              INTEGER,
              vplsPwBindMacAddressLimit       Unsigned32, 
              vplsPwBindRowStatus             RowStatus
          } 

      vplsPwIndex        OBJECT-TYPE               
           SYNTAX        PwIndexType
           MAX-ACCESS    not-accessible 
           STATUS        current 
           DESCRIPTION 
              "Secondary Index for the conceptual row identifying
               a pseudowire within the PwEntry which MUST 
               match an entry from the PW-STD-MIB's PwTable 
               which represents an already-provisioned 
               pseuwowire that is then associated with this 
               VPLS instance." 
          ::= { vplsPwBindEntry 1 } 

       draft-nadeau-l2vpn-vpls-mib-00   L2-VPN-MIB      June 16, 2006



      vplsPwBindBindType   OBJECT-TYPE 
           SYNTAX          INTEGER { 
                                   manual        (1), 
                                   autodiscovery (2) 
                           } 
           MAX-ACCESS      read-create 
           STATUS          current 
           DESCRIPTION     
                "The value of this object indicates  
                 whether the Pseudo Wire binding was created
                 manually or via autodiscovery.

                 The value of this object must be 
                 specifed when the row is created and cannot 
                 be changed while the row status is active(1)" 
          ::= { vplsPwBindEntry 2 } 
       
      vplsPwBindMacAddressLimit OBJECT-TYPE 
          SYNTAX          Unsigned32 (0.. 4294967295)
          MAX-ACCESS      read-create 
          STATUS          current 
          DESCRIPTION    
               "The value of this object specifies the maximum number 
                of learned and static entries allowed in the 
                Forwarding database for this PW Binding. The value 0 
                means there is no limit for this PW Binding."
          DEFVAL          { 0 } 
          ::= { vplsPwBindEntry 3 } 

      vplsPwBindRowStatus  OBJECT-TYPE 
           SYNTAX          RowStatus 
           MAX-ACCESS      read-create 
           STATUS          current 
           DESCRIPTION     
                "For creating, modifying, and deleting this row. 
                 None of the read-create objects in the 
                 conceptual rows may be changed when this 
                 object is in the active(1) state"
          ::= { vplsPwBindEntry 4 } 
             
   vplsStatusNotifEnable  OBJECT-TYPE  
      SYNTAX      TruthValue  
      MAX-ACCESS  read-write  
      STATUS      current  
      DESCRIPTION  
           "If this object is set to true(1), then it enables  
            the emission of vplsStatusChanged
            notification; otherwise this notification is not  

       draft-nadeau-l2vpn-vpls-mib-00   L2-VPN-MIB      June 16, 2006



            emitted."  
      REFERENCE  
           "See also [RFC3413] for explanation that  
            notifications are under the ultimate control of the  
            MIB module in this document."  
      DEFVAL { false }  
      ::= { vplsObjects 4 }  

   vplsNotificationMaxRate OBJECT-TYPE
      SYNTAX       Unsigned32
      MAX-ACCESS   read-write
      STATUS       current
      DESCRIPTION
           "This object indicates the maximum number of
            notifications issued per second. If events occur
            more rapidly, the implementation may simply fail to
            emit these notifications during that period, or may
            queue them until an appropriate time. A value of 0
            means no throttling is applied and events may be
            notified at the rate at which they occur."
      DEFVAL       { 0 }
      ::= { vplsObjects 5 }
 

      -- VPLS Service Notifications 

      vplsStatusChanged NOTIFICATION-TYPE 
          OBJECTS { 
              vplsVpnId, 
              vplsAdminStatus, 
              vplsOperStatus 
          } 
          STATUS          current 
          DESCRIPTION     
               "The vplsStatusChanged notification is generated  
                when there is a change in the administrative or 
                operating status of a VPLS service." 
          ::= { vplsNotifications 1 } 

      vplsFwdFullAlarmRaised NOTIFICATION-TYPE 
          OBJECTS { 
              vplsVpnId, 
              vplsConfigFwdFullHighWatermark,
              vplsConfigFwdFullLowWatermark
          } 
          STATUS          current 
          DESCRIPTION     
               "The vplsFwdFullAlarmRaised notification is 

       draft-nadeau-l2vpn-vpls-mib-00   L2-VPN-MIB      June 16, 2006



                generated when the utilization of the Forwarding
                database is above the value specified by                     
                vplsConfigFwdFullHighWatermark." 
          ::= { vplsNotifications 2 } 

      vplsFwdFullAlarmCleared NOTIFICATION-TYPE 
          OBJECTS { 
              vplsVpnId, 
              vplsConfigFwdFullHighWatermark,
              vplsConfigFwdFullLowWatermark
          } 
          STATUS          current 
          DESCRIPTION     
               "The vplsFwdFullAlarmCleared notification is 
                generated when the utilization of the Forwarding
                database is below the value specified by                     
                vplsConfigFwdFullLowWatermark." 
          ::= { vplsNotifications 3 } 

   -- Compliance requirement for read-only implementations.

   vplsCompliances       
     OBJECT IDENTIFIER ::= { vplsConformance 1 }

   vplsModuleReadOnlyCompliance MODULE-COMPLIANCE
      STATUS current
      DESCRIPTION
           "Compliance requirement for implementations that only
            provide read-only support for VPLS-DRAFT-00-MIB.
            Such devices can then be monitored but cannot be
            configured using this MIB modules."

      MODULE -- this module

         GROUP vplsGroup
         DESCRIPTION
             "This group is mandatory for devices which support
              VPLS. Write access is not mandatory for objects in 
              this group."

         GROUP vplsPwBindGroup
         DESCRIPTION
             "This group is mandatory for devices which support
              VPLS. Write access is not mandatory for objects in 
              this group."

         GROUP vplsNotificationGroup
         DESCRIPTION

       draft-nadeau-l2vpn-vpls-mib-00   L2-VPN-MIB      June 16, 2006



             "This group is mandatory for devices which support
              VPLS."

      ::= { vplsCompliances 1 }
       
-- Units of conformance.

      vplsGroups       
        OBJECT IDENTIFIER ::= { vplsConformance 2 } 

      vplsGroup OBJECT-GROUP 
          OBJECTS { 
              vplsName,
              vplsDescr,
              vplsAdminStatus,
              vplsOperStatus,
              vplsMacLearning,
              vplsDiscardUnknownDest,
              vplsMacAging,
              vplsVpnId,
              vplsConfigFwdFullHighWatermark,
              vplsConfigFwdFullLowWatermark,
              vplsRowStatus,
              vplsIndexNext
          } 
          STATUS          current 
          DESCRIPTION     
               "The group of objects supporting  
                management of L2VPN VPLS services" 
          ::= { vplsGroups 1 } 
       
      vplsPwBindGroup OBJECT-GROUP 
          OBJECTS { 
              vplsPwBindBindType, 
              vplsPwBindRowStatus, 
              vplsPwBindMacAddressLimit,
              vplsStatusNotifEnable,
              vplsNotificationMaxRate
          } 
          STATUS          current 
          DESCRIPTION     
               "The group of objects supporting 
                management of  
                Pseudo Wire (PW) Binding to VPLS."  
          ::= { vplsGroups 2 } 
       
      vplsNotificationGroup NOTIFICATION-GROUP 
          NOTIFICATIONS   { 

       draft-nadeau-l2vpn-vpls-mib-00   L2-VPN-MIB      June 16, 2006



              vplsStatusChanged, 
              vplsFwdFullAlarmRaised,
              vplsFwdFullAlarmCleared
          } 
          STATUS          current 
          DESCRIPTION     
               "The group of notifications supporting 
                the  Notifications generated for 
                VPLS Services" 
          ::= { vplsGroups 3 }        

       END       

-- 
--    Copyright (C) The Internet Society (2006). This document is subject
--    to the rights, licenses and restrictions contained in BCP 78, and
--    except as set forth therein, the authors retain all their rights.
-- 
--    This document and the information contained herein are provided on an
--    "AS IS" basis and THE CONTRIBUTOR, THE ORGANIZATION HE/SHE REPRESENTS
--    OR IS SPONSORED BY (IF ANY), THE INTERNET SOCIETY AND THE INTERNET
--    ENGINEERING TASK FORCE DISCLAIM ALL WARRANTIES, EXPRESS OR IMPLIED,
--    INCLUDING BUT NOT LIMITED TO ANY WARRANTY THAT THE USE OF THE
--    INFORMATION HEREIN WILL NOT INFRINGE ANY RIGHTS OR ANY IMPLIED
--    WARRANTIES OF MERCHANTABILITY OR FITNESS FOR A PARTICULAR PURPOSE.
