PANDATEL-FME-MODEM-MIB DEFINITIONS ::= BEGIN

 -- This is the private mib group section for the FM-E modems.
 -- Because these modems must be installed in the PANDATEL modem rack
 -- the PANDATEL-MODEM-MIB also applies.

 -- Ver.1.06    Sep.13.1999

        IMPORTS
                enterprises
                        FROM RFC1155-SMI
                DisplayString
                        FROM RFC1213-MIB
                OBJECT-TYPE
                        FROM RFC-1212
                mdmSpecifics, device-id
                        FROM PANDATEL-MODEM-MIB;

-- ********************** THE MDM-FME SUBTREE ******************************

-- the specific identifier is identical to the modem type integer
-- of the FM-E modem entries in the PANDATEL-MODEM-MIB mdmModemTable.

fme-modem      OBJECT IDENTIFIER ::= { device-id 601 }     -- chassis-mib

fme            OBJECT IDENTIFIER ::= { mdmSpecifics 601 }  -- this subtree

fmeModemTable OBJECT-TYPE
        SYNTAX  SEQUENCE OF FmeTableEntry
        ACCESS  not-accessible
        STATUS  mandatory
        DESCRIPTION
                "This table contains information about all FME units within all stacks."
        ::= { fme 1 }

fmeTableEntry OBJECT-TYPE
        SYNTAX  FmeTableEntry
        ACCESS  not-accessible
        STATUS  mandatory
        DESCRIPTION
                "The index of the table."
        INDEX   { mdmRack, mdmModem, mdmPosition }
        ::= { fmeModemTable 1 }

FmeTableEntry ::= SEQUENCE {
        mdmRack
                INTEGER,
        mdmModem
                INTEGER,
        mdmPosition
                INTEGER,
        mdmModemName
                DisplayString,
        mdmActiveLink
                INTEGER,
        mdmAlarmConditionPort7
                INTEGER,
        mdmAlarmConditionPort8
                INTEGER
        }

mdmRack OBJECT-TYPE
        SYNTAX  INTEGER
        ACCESS  read-only
        STATUS  mandatory
        DESCRIPTION
                "The index of the stack the unit belongs to. The stack
                 corresponds to a rack, the FME units correspond to rack
                 mount cards installed in a rack."
        ::= { fmeTableEntry 1 }

mdmModem OBJECT-TYPE
        SYNTAX  INTEGER
        ACCESS  read-only
        STATUS  mandatory
        DESCRIPTION
                "This entry displays the index of the FME unit. It
                 corresponds with its position in the stack."
        ::= { fmeTableEntry 2 }

mdmPosition OBJECT-TYPE
        SYNTAX  INTEGER {
                local       (1),
                remote      (2)
                }
        ACCESS  read-only
        STATUS  mandatory
        DESCRIPTION
                "This entry displays the location of the corresponding unit:
                 'local' or 'remote'. The unit which belongs to a managed
                 stack is 'local', the counterpart is 'remote'."
        ::= { fmeTableEntry 3 }

mdmModemName OBJECT-TYPE
        SYNTAX  DisplayString
        ACCESS  read-only
        STATUS  mandatory
        DESCRIPTION
                "The verbal name of this unit."
        ::= { fmeTableEntry 5 }

mdmActiveLink OBJECT-TYPE
        SYNTAX  INTEGER {
                line-port-7     (7),
                line-port-8     (8),
                disable         (90)
        }
        ACCESS  read-only
        STATUS  mandatory
        DESCRIPTION
                "This entry displays the line port that is receiving data."
        ::= { fmeTableEntry 12 }

mdmAlarmConditionPort7 OBJECT-TYPE
        SYNTAX  INTEGER {
                other                        (1),
                disable                      (2),
                no-link-signal               (3),
                laser-fail                   (4),
                no-link-signal-or-laser-fail (5),
                not-available                (100)
        }
        ACCESS  read-write
        STATUS  mandatory
        DESCRIPTION
                "The alarm trigger mode at port 7: 'disable', i.e. no alarm
                 is triggered, 'no-link-signal', i.e. an alarm is triggered if
                 the link is down, 'laser-fail', i.e. an alarm is triggered
                 if the laser diode is defective, or 'no-link-signal-or-laser-fail',
                 i.e. the link is down or the laser diode is defective."
        ::= { fmeTableEntry 116 }

mdmAlarmConditionPort8 OBJECT-TYPE
        SYNTAX  INTEGER {
                other                        (1),
                disable                      (2),
                no-link-signal               (3),
                laser-fail                   (4),
                no-link-signal-or-laser-fail (5),
                not-available                (100)
        }
        ACCESS  read-write
        STATUS  mandatory
        DESCRIPTION
                "The alarm trigger mode at port 8: 'disable', i.e. no alarm
                 is triggered, 'no-link-signal', i.e. an alarm is triggered if
                 the link is down, 'laser-fail', i.e. an alarm is triggered
                 if the laser diode is defective, or 'no-link-signal-or-laser-fail',
                 i.e. the link is down or the laser diode is defective."
        ::= { fmeTableEntry 117 }

-- *********************** Port Table ***********************************

fmePortTable OBJECT-TYPE
        SYNTAX  SEQUENCE OF FmeTableEntry
        ACCESS  not-accessible
        STATUS  mandatory
        DESCRIPTION
                "This table contains information about all I/F ports of the
                 FME units within all stacks."
        ::= { fme 2 }

fmePortEntry OBJECT-TYPE
        SYNTAX  FmeTableEntry
        ACCESS  not-accessible
        STATUS  mandatory
        DESCRIPTION
                "The index of the table."
        INDEX   { portRack, portModem, portPosition, portPort }
        ::= { fmePortTable 1 }

FmePortEntry ::= SEQUENCE {
        portRack
                INTEGER,
        portModem
                INTEGER,
        portPosition
                INTEGER,
        portPort
                INTEGER,
        portInterfaceEmulationMode
                INTEGER,
        mdmModemProperty
                INTEGER,
        portClockSystem
                INTEGER,
        portClockSource
                INTEGER,
        portDataRate
                INTEGER,
        portLocalCarrierDetect
                INTEGER,
        portTDPhaseLocking
                INTEGER,
        portLineBuiltOut
                INTEGER
        }


portRack OBJECT-TYPE
        SYNTAX  INTEGER
        ACCESS  read-only
        STATUS  mandatory
        DESCRIPTION
                "The index of the stack the port belongs to."
        ::= { fmePortEntry 1 }

portModem OBJECT-TYPE
        SYNTAX  INTEGER
        ACCESS  read-only
        STATUS  mandatory
        DESCRIPTION
                "The index of the FME unit the port belongs to."
        ::= { fmePortEntry 2 }

portPosition OBJECT-TYPE
        SYNTAX  INTEGER {
                local       (1),
                remote      (2)
                }
        ACCESS  read-only
        STATUS  mandatory
        DESCRIPTION
                "This entry displays the location of the corresponding port:
                 'local' or 'remote'. The port which belongs to a managed stack
                 is 'local', the counterpart is 'remote'."
        ::= { fmePortEntry 3 }

portPort OBJECT-TYPE
        SYNTAX  INTEGER
        ACCESS  read-only
        STATUS  mandatory
        DESCRIPTION
                "The index of the port."
        ::= { fmePortEntry 4 }

portInterfaceEmulationMode OBJECT-TYPE
        SYNTAX  INTEGER {
                other       (1),
                dte         (2),
                dce         (3),
                te          (4),
                nt          (5),
                unknown     (99)
        }
        ACCESS  read-only
        STATUS  mandatory
        DESCRIPTION
                "Interface mode of the port: 'dte', 'dce', 'te', or 'nt'."
        ::= { fmePortEntry 6 }

mdmModemProperty OBJECT-TYPE
        SYNTAX  INTEGER {
                other           (1),
                e1              (2),
                t1              (3),
                unknown         (99)
        }
        ACCESS  read-only
        STATUS  mandatory
        DESCRIPTION
                "The speed class of the port: 'e1' or 't1'."
        ::= { fmePortEntry 7 }

portClockSystem OBJECT-TYPE
        SYNTAX  INTEGER {
                other       (1),
                dual        (2),
                single      (3)
        }
        ACCESS  read-write
        STATUS  mandatory
        DESCRIPTION
                "The clock system at the interface port: 'single' or 'dual'. The 
                available values depend on the interface type."
        ::= { fmePortEntry 23 }

portClockSource OBJECT-TYPE
        SYNTAX  INTEGER {
                other       (1),
                internal    (2),
                remote      (3),
                external    (4)
        }
        ACCESS  read-write
        STATUS  mandatory
        DESCRIPTION
                "The clock source at the interface port: 'internal',
                 'remote', or 'external'."
        ::= { fmePortEntry 24 }

portDataRate OBJECT-TYPE
        SYNTAX  INTEGER {
                other       (1)
        }
        ACCESS  read-write
        STATUS  mandatory
        DESCRIPTION
                "The data rate at the interface port in bits per seconds. The
                 data rate at the remote counterpart changes simultaneously."
        ::= { fmePortEntry 25 }

portLocalCarrierDetect OBJECT-TYPE
        SYNTAX  INTEGER {
                other                           (1),
                fo-link-and-remote-handshake    (2),
                fo-link                         (3),
                not-available                   (100)
        }
        ACCESS  read-write
        STATUS  mandatory
        DESCRIPTION
                "The data carrier detect mode at the interface: if set to
                 'fo-link-and-remote-handshake' the DCD signal (resp. I for
                 X.21, etc.) follows link status and remote RTS (resp. C for
                 X.21, etc.), if set to 'fo-link' the DCD signal follows link
                 status only. Not available for units with G.703 onboard."
        ::= { fmePortEntry 60 }

portTDPhaseLocking OBJECT-TYPE
        SYNTAX  INTEGER {
                other                   (1),
                positive-clock-slope    (2),
                negative-clock-slope    (3),
                unknown                 (99)
        }
        ACCESS  read-write
        STATUS  mandatory
        DESCRIPTION
                "This entry defines the data phase locking for I/F data:
                 'positive-clock-slope' or 'negative-clock-slope'. For units
                 with G.703 onboard the value 'positive-clock-slope' is
                 valid only."
        ::= { fmePortEntry 67 }

portLineBuiltOut OBJECT-TYPE
        SYNTAX  INTEGER {
                other               (1),
                itu-rec-g703        (2),
                dsx-1-0to133-ft     (3),
                dsx-1-133to266-ft   (4),
                dsx-1-266to399-ft   (5),
                dsx-1-399to533-ft   (6),
                dsx-1-533to655-ft   (7),
                not-available       (100)
        }
        ACCESS  read-write
        STATUS  mandatory
        DESCRIPTION
                "The G.703 transmission mode of the unit. Valid for
                 units with G.703 onboard only."
        ::= { fmePortEntry 68 }

END
