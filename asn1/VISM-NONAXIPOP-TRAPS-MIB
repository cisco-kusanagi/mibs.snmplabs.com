-- *****************************************************************
-- VISM Non Axis POP Traps MIB
--
-- August 1999
--
-- Copyright (c) 1999-2001 by cisco Systems, Inc.
-- All rights reserved.
--
-- *****************************************************************
--       
--    LAST-UPDATED "200112261500Z"
--    DESCRIPTION
--        "TRAPS specific to VISM card which have been defined
--         as extensions to SMI v2 MIBs MGMIB, SRCP-MIB. The traps in
--         this file do not go into AXIPOP MIB and hence are kept in a 
--         separate file."
--
--    REVISION    "200112261500Z"
--    DESCRIPTION
--        "Added traps for Announcement Files:
--         cwAnnFileAddStarted   = 50674,
--         cwAnnFileLoadComplete = 50675,
--         cwAnnFileLoadFailed   = 50676,           
--         cwAnnFileDeleted      = 50677."
--       
--    REVISION    "200109281500Z"
--    DESCRIPTION "
--                Add vismRtpLcn to trap:50650"
--
--    REVISION    "200109101500Z"
--    DESCRIPTION "
--                Each state change trap has been split into multiple traps each 
--                representing a specific state.
--                For example: mgAdministrativeStateChange in MGMIB has been 
--                changed to  mgAdministrativeStateLocked, 
--                mgAdministrativeStateUnlocked, mgAdministrativeStateShuttingDown.
--                "
-- 
--    REVISION    "200108281500Z"
--    DESCRIPTION "
--                Deleted traps for mgcRedundancyGrpAssociated,
--                mgcRedundancyGrpUnassociated, mgcRedundancyGrpAssociatedCommLoss,
--                and added traps for mgcRedundancyGrpCommOk and 
--                mgcRedundancyGrpCommLoss."
--
--    REVISION    "200108281400Z"
--    DESCRIPTION "
--                Changed trap number of mgDomainNameAdded as the trap used the
--                same number as trapNetworkCacConfigState. "
--
--    REVISION    "200107011400Z"
--    DESCRIPTION "
--                Added VoIP Trunking traps - vismRtpConnAdded, vismRtpConnDeleted
--                vismRtpConnStateChg, vismLapdTrStateIs, vismLapdTrStateOos,
--                vismLapdTrunkAdded, vismLapdTrunkDeleted "
--
--    REVISION    "200105251400Z"
--    DESCRIPTION "
--                Obsoleted the following traps - mgcAssociated, mgcUnassociated,
--                mgcAssociatedCommLoss, mgcProtocolAdded, mgcProtocolDeleted and
--                added new traps - mgcRedundancyGrpAdded mgcRedundancyGrpDeleted,
--                mgcRedundancyGrpAssociated, mgcRedundancyGrpUnassociated,
--                mgcRedundancyGrpAssociatedCommLoss,
--                mgcRedundancyGrpProtocolAdded and
--                mgcRedundancyGrpProtocolDeleted."
--
--    REVISION    "200005111400Z"
--    DESCRIPTION "
--                Move vismRudpSession and vismLapd related traps from 
--                vismTraps.my to this file."
--
--    REVISION    "199908101400Z"
--    DESCRIPTION "
--                Replaced all "not-accessible" varbinds with
--                vismTrapIntIndex1 & vismTrapIntIndex2"
--
--    REVISION    "200107191500Z"
--    DESCRIPTION "
--                Added traps when an entry is implicitly added or removed
--                in mgcRedundancyGrpParamTable or srcpPeerGrpParamTable"
--
--    REVISION    "200202111500Z"
--    DESCRIPTION "RSVP Compilation problem fix."
--                

VISM-NONAXIPOP-TRAPS-MIB DEFINITIONS ::= BEGIN

IMPORTS
        TRAP-TYPE                       FROM RFC-1215
        lastSequenceNumber              FROM RTM-MIB
        shelfNodeName,
        shelfNum                       FROM BASIS-SHELF-MIB

        moduleSlotNumber,
        moduleTrapAlarmSeverity,
        functionModuleType             FROM BASIS-GENERIC-MIB

        genericTimeStamp               FROM GENERICOBJECT-MIB
        mgAdministrativeState,
        mgcName,
        mgcAssociationState,
        mgcResolutionCommState,
        mgEndpointLineNumber,
        mgEndpointChannelMap,
        mgEndpointState,
        mgDomainName,
        mgDnsResolutionType,
        mgcResolutionName,
        mgcResolutionIpAddress         FROM CISCO-WAN-MG-MIB
        mgcRedundancyGrpActState       FROM CISCO-WAN-MGC-REDUN-MIB    
        srcpPeerGrpTimeSinceHeartbeat,
        srcpPeerTimeSinceHeartbeat         FROM CISCO-WAN-SRCP-MIB
        vismLapdIndex,
        vismLapdDlcIndex,
        vismLapdDlcSapi,
        vismLapdDlcTei,
        vismLapdDlcLinkState            FROM VISM-LAPD-MIB
        vismSessionSetNum,
        vismSessionSetState,
        vismSessionGrpNum,
        vismRudpSessionNum,
        vismRudpSessionState,
        vismSessionGrpState            FROM VISM-SESSION-MIB
        vismTrapIntIndex1,
        vismTrapIntIndex2              FROM CISCO-WAN-AXIPOP-MIB
        persistentXgcpEventName        FROM CISCO-WAN-PERSISTENT-XGCP-EVENTS-MIB
        tonePlanRegionName,
        tonePlanVersionNumber,
        tonePlanFileName               FROM CISCO-WAN-VISM-TONE-PLAN-MIB
        vismLapdTrunkState             FROM CISCO-WAN-LAPD-TRUNK-MIB
        vismRtpConnAlarmState,        
        vismRtpLcn,
        vismRtpFailReason              FROM CISCO-WAN-RTP-CONN-MIB
        cwAnnFileName,
        cwAnnFileCodec,
        cwAnnFileStatus                FROM CISCO-WAN-ANNOUNCEMENT-MIB
        basis                          FROM BASIS-MIB
        intSrvFlowStatus               FROM INT-SERV-MIB
        rsvpSessionDestAddr,
        rsvpResvFwdStatus,
        rsvpResvStatus,
        rsvpSenderStatus              FROM RSVP-MIB;





mgAdministrativeStateLocked     TRAP-TYPE
        ENTERPRISE      basis
        VARIABLES       { 
                        lastSequenceNumber,
                        shelfNodeName,
                        shelfNum,
                        moduleSlotNumber,
                        moduleTrapAlarmSeverity,
			functionModuleType,
			genericTimeStamp,
                        mgAdministrativeState
                        }
 
        DESCRIPTION
            "Triggered when mgAdministrativeState transitions to locked.
             The transition may be from unlocked to locked or from 
             shuttingdown to locked.
	    "
        ::= 50719

mgAdministrativeStateUnlocked     TRAP-TYPE
        ENTERPRISE      basis
        VARIABLES       { 
                        lastSequenceNumber,
                        shelfNodeName,
                        shelfNum,
                        moduleSlotNumber,
                        moduleTrapAlarmSeverity,
			functionModuleType,
			genericTimeStamp,
                        mgAdministrativeState
                        }
 
        DESCRIPTION
            "Triggered when mgAdministrativeState transitions from locked
             to unlocked.
	    "
        ::= 50720


mgAdministrativeStateShuttingDown     TRAP-TYPE
        ENTERPRISE      basis
        VARIABLES       { 
                        lastSequenceNumber,
                        shelfNodeName,
                        shelfNum,
                        moduleSlotNumber,
                        moduleTrapAlarmSeverity,
			functionModuleType,
			genericTimeStamp,
                        mgAdministrativeState
                        }
 
        DESCRIPTION
            "Triggered when mgAdministrativeState transitions from unlocked
             to shuttingdown.
	    "
        ::= 50721

--
-- STATUS of following trap: Obsoleted
--
-- This object has been deprecated in the MIB table.
--
mgcAssociated     TRAP-TYPE
        ENTERPRISE      basis
        VARIABLES       { 
                        lastSequenceNumber,
                        shelfNodeName,
                        shelfNum,
                        moduleSlotNumber,
                        moduleTrapAlarmSeverity,
			functionModuleType,
			genericTimeStamp,
                        vismTrapIntIndex1,
                        mgcName,
                        mgcAssociationState
                        }
 
        DESCRIPTION
            "Triggered when mgAssociationState transitions to associated.
             The transition may be from unassociated to associated or from
             associatedCommLoss to associated.
             The value of vismTrapIntIndex1 gives the value of mgcNumber.
	    "
        ::= 50722

--
-- STATUS of following trap: Obsoleted
--
-- This object has been deprecated in the MIB table.
--
mgcUnassociated     TRAP-TYPE
        ENTERPRISE      basis
        VARIABLES       { 
                        lastSequenceNumber,
                        shelfNodeName,
                        shelfNum,
                        moduleSlotNumber,
                        moduleTrapAlarmSeverity,
			functionModuleType,
			genericTimeStamp,
                        vismTrapIntIndex1,
                        mgcName,
                        mgcAssociationState
                        }
 
        DESCRIPTION
            "Triggered when mgAssociationState transitions to Unassociated.
             The transition may be from associated to Unassociated or from
             associatedCommLoss to Unassociated.
             The value of vismTrapIntIndex1 gives the value of mgcNumber.
	    "
        ::= 50723

--
-- STATUS of following trap: Obsoleted
--
-- This object has been deprecated in the MIB table.
--
mgcAssociatedCommLoss     TRAP-TYPE
        ENTERPRISE      basis
        VARIABLES       { 
                        lastSequenceNumber,
                        shelfNodeName,
                        shelfNum,
                        moduleSlotNumber,
                        moduleTrapAlarmSeverity,
			functionModuleType,
			genericTimeStamp,
                        vismTrapIntIndex1,
                        mgcName,
                        mgcAssociationState
                        }
 
        DESCRIPTION
            "Triggered when mgAssociationState transitions from 
             associated to associatedCommLoss.
             The value of vismTrapIntIndex1 gives the value of mgcNumber.
	    "
        ::= 50724


mgcCommStateActive     TRAP-TYPE
        ENTERPRISE      basis
        VARIABLES       { 
                        lastSequenceNumber,
                        shelfNodeName,
                        shelfNum,
                        moduleSlotNumber,
                        moduleTrapAlarmSeverity,
			functionModuleType,
			genericTimeStamp,
                        vismTrapIntIndex1,
                        mgcResolutionIpAddress,
                        mgcResolutionCommState
                        }
 
        DESCRIPTION
            "Triggered when mgcResolutionCommState transitions from inactive
             to active.  Indicates that an IP address of an MGC has become 
             active.
             The value of vismTrapIntIndex1 gives the value of 
             mgcResolutionIndex.
	    "
        ::= 50725

mgcCommStateInactive     TRAP-TYPE
        ENTERPRISE      basis
        VARIABLES       { 
                        lastSequenceNumber,
                        shelfNodeName,
                        shelfNum,
                        moduleSlotNumber,
                        moduleTrapAlarmSeverity,
			functionModuleType,
			genericTimeStamp,
                        vismTrapIntIndex1,
                        mgcResolutionIpAddress,
                        mgcResolutionCommState
                        }
 
        DESCRIPTION
            "Triggered when mgcResolutionCommState transitions from active
             to inactive.  Indicates that an IP address of an MGC has become 
             inactive.
             The value of vismTrapIntIndex1 gives the value of 
             mgcResolutionIndex.
            "
        ::= 50726

mgEndpointCreated     TRAP-TYPE
        ENTERPRISE      basis
        VARIABLES       { 
                        lastSequenceNumber,
                        shelfNodeName,
                        shelfNum,
                        moduleSlotNumber,
                        moduleTrapAlarmSeverity,
			functionModuleType,
			genericTimeStamp,
                        vismTrapIntIndex1,
                        mgEndpointLineNumber,
                        mgEndpointChannelMap
                        }
 
        DESCRIPTION
            "Triggered by creation of an endpoint.  
             The value of vismTrapIntIndex1 gives the value of 
             mgEndpointNumber.
	    "
        ::= 50727


mgEndpointDeleted     TRAP-TYPE
        ENTERPRISE      basis
        VARIABLES       { 
                        lastSequenceNumber,
                        shelfNodeName,
                        shelfNum,
                        moduleSlotNumber,
                        moduleTrapAlarmSeverity,
			functionModuleType,
			genericTimeStamp,
                        vismTrapIntIndex1,
                        mgEndpointLineNumber,
                        mgEndpointChannelMap
                        }
 
        DESCRIPTION
            "Triggered by deletion of an endpoint.  
             The value of vismTrapIntIndex1 gives the value of 
             mgEndpointNumber.
	    "
        ::= 50728


mgEndpointActive     TRAP-TYPE
        ENTERPRISE      basis
        VARIABLES       { 
                        lastSequenceNumber,
                        shelfNodeName,
                        shelfNum,
                        moduleSlotNumber,
                        moduleTrapAlarmSeverity,
			functionModuleType,
			genericTimeStamp,
                        vismTrapIntIndex1,
                        mgEndpointLineNumber,
                        mgEndpointChannelMap,
                        mgEndpointState
                        }
 
        DESCRIPTION
            "Triggered when mgEndpointState transitions from failed/degraded
             to active. 
             The value of vismTrapIntIndex1 gives the value of 
             mgEndpointNumber.
	    "
        ::= 50729

mgEndpointFailed     TRAP-TYPE
        ENTERPRISE      basis
        VARIABLES       { 
                        lastSequenceNumber,
                        shelfNodeName,
                        shelfNum,
                        moduleSlotNumber,
                        moduleTrapAlarmSeverity,
			functionModuleType,
			genericTimeStamp,
                        vismTrapIntIndex1,
                        mgEndpointLineNumber,
                        mgEndpointChannelMap,
                        mgEndpointState
                        }
 
        DESCRIPTION
            "Triggered when mgEndpointState transitions from active to
             failed/degraded.
             The value of vismTrapIntIndex1 gives the value of 
             mgEndpointNumber.
	    "
        ::= 50730

mgcAdded     TRAP-TYPE
        ENTERPRISE      basis
        VARIABLES       { 
                        lastSequenceNumber,
                        shelfNodeName,
                        shelfNum,
                        moduleSlotNumber,
                        moduleTrapAlarmSeverity,
			functionModuleType,
			genericTimeStamp,
                        vismTrapIntIndex1,
                        mgcName
                        }
 
        DESCRIPTION
            "Indicates that an entry is added to mgcTable.
             The value of vismTrapIntIndex1 gives the value of mgcNumber.
	    "
        ::= 50731

mgcDeleted     TRAP-TYPE
        ENTERPRISE      basis
        VARIABLES       { 
                        lastSequenceNumber,
                        shelfNodeName,
                        shelfNum,
                        moduleSlotNumber,
                        moduleTrapAlarmSeverity,
			functionModuleType,
			genericTimeStamp,
                        vismTrapIntIndex1,
                        mgcName
                        }
 
        DESCRIPTION
            "Indicates that an entry is deleted from mgcTable.
             The value of vismTrapIntIndex1 gives the value of mgcNumber.
	    "
        ::= 50732

--
-- STATUS of following trap: Obsoleted
--
-- This object has been deprecated in the MIB table.
--
mgcProtocolAdded     TRAP-TYPE
        ENTERPRISE      basis
        VARIABLES       { 
                        lastSequenceNumber,
                        shelfNodeName,
                        shelfNum,
                        moduleSlotNumber,
                        moduleTrapAlarmSeverity,
			functionModuleType,
			genericTimeStamp,
                        vismTrapIntIndex1,
                        vismTrapIntIndex2
                        }
 
        DESCRIPTION
            "Indicates that an entry is added to mgcProtocolTable.
             The value of vismTrapIntIndex1 gives the value of mgcNumber.
             The value of vismTrapIntIndex2 gives the value of 
             mgProtocolNumber.
	    "
        ::= 50733

--
-- STATUS of following trap: Obsoleted
--
-- This object has been deprecated in the MIB table.
--
mgcProtocolDeleted     TRAP-TYPE
        ENTERPRISE      basis
        VARIABLES       { 
                        lastSequenceNumber,
                        shelfNodeName,
                        shelfNum,
                        moduleSlotNumber,
                        moduleTrapAlarmSeverity,
			functionModuleType,
			genericTimeStamp,
                        vismTrapIntIndex1,
                        vismTrapIntIndex2
                        }
 
        DESCRIPTION
            "Indicates that an entry is deleted from mgcProtocolTable.
             The value of vismTrapIntIndex1 gives the value of mgcNumber.
             The value of vismTrapIntIndex2 gives the value of 
             mgProtocolNumber.
	    "
        ::= 50734

mgcResolutionAdded     TRAP-TYPE
        ENTERPRISE      basis
        VARIABLES       { 
                        lastSequenceNumber,
                        shelfNodeName,
                        shelfNum,
                        moduleSlotNumber,
                        moduleTrapAlarmSeverity,
			functionModuleType,
			genericTimeStamp,
                        vismTrapIntIndex1,
                        mgcResolutionName,
                        mgcResolutionIpAddress
                        }
 
        DESCRIPTION
            "Indicates that an entry is added to mgcResolutionTable.
             The value of vismTrapIntIndex1 gives the value of 
             mgcResolutionIndex.
	    "
        ::= 50735

mgcResolutionDeleted     TRAP-TYPE
        ENTERPRISE      basis
        VARIABLES       { 
                        lastSequenceNumber,
                        shelfNodeName,
                        shelfNum,
                        moduleSlotNumber,
                        moduleTrapAlarmSeverity,
			functionModuleType,
			genericTimeStamp,
                        vismTrapIntIndex1,
                        mgcResolutionName,
                        mgcResolutionIpAddress
                        }
 
        DESCRIPTION
            "Indicates that an entry is deleted from mgcResolutionTable.
             The value of vismTrapIntIndex1 gives the value of 
             mgcResolutionIndex.
	    "
        ::= 50736



-- The following traps have been taken from SRCP MIB. The additional varbinds
-- to address RTM compliance have been added. 
--
-- Each state change trap has been split into multiple traps each 
-- representing a specific state.
-- For example: peerHeartbeatStateChange in SRCP MIB has been changed to
-- peerHeartbeatLost, peerHeartbeatDetected.
-- 
-- The trap numbers are yet to be registered.
--
-- STATUS - Obsoleted
--
-- This trap has been obsoleted since that object has been deprecated from
-- the MIB.

peerHeartbeatLost     TRAP-TYPE
        ENTERPRISE      basis
        VARIABLES       { 
                        lastSequenceNumber,
                        shelfNodeName,
                        shelfNum,
                        moduleSlotNumber,
                        moduleTrapAlarmSeverity,
			functionModuleType,
			genericTimeStamp,
                        vismTrapIntIndex1,
                        srcpPeerTimeSinceHeartbeat
                        }
 
        DESCRIPTION
            "This notification indicates that the system failed to receive 
             a heartbeat from a specific peer. The notification is sent 
             when srcpPeerTimeSinceHeartbeat crosses the 
             srcpPeerHeartbeatInterval threshold.
             The value of vismTrapIntIndex1 gives the value of srcpPeerId.
	    "
        ::= 50737

--
-- STATUS - Obsoleted.
--
-- This trap has been obsoleted since the object has been deprecated from the
-- MIB.
--
peerHeartbeatDetected     TRAP-TYPE
        ENTERPRISE      basis
        VARIABLES       { 
                        lastSequenceNumber,
                        shelfNodeName,
                        shelfNum,
                        moduleSlotNumber,
                        moduleTrapAlarmSeverity,
			functionModuleType,
			genericTimeStamp,
                        vismTrapIntIndex1,
                        srcpPeerTimeSinceHeartbeat
                        }
 
        DESCRIPTION
            "This notification indicates that the system detected a heartbeat
             from a specific peer after it had been lost. The notification 
             is sent when srcpPeerTimeSinceHeartbeat which had exceeded
             the threshold, resets to 0 due to receipt of a heartbeat.
             The value of vismTrapIntIndex1 gives the value of srcpPeerId.
	    "
        ::= 50738


-- The following traps are defined for PRI Backhaul on VISM card.
-- There is a trap for each table entry creation or deletion.
-- There is also traps for the state change in each table.

-- ----------------------------------------------------------------------
-- LAPD related traps
-- ----------------------------------------------------------------------
trapLapdAdded    TRAP-TYPE
    ENTERPRISE    basis
    VARIABLES     {
        lastSequenceNumber,
        shelfNodeName,
        shelfNum,
        moduleSlotNumber,
        moduleTrapAlarmSeverity,
        functionModuleType,
        genericTimeStamp,
        vismLapdIndex
    }
    DESCRIPTION
        "Indicates that an entry has been added to vismLapdEntry table."
    ::= 50761

trapLapdDeleted    TRAP-TYPE
    ENTERPRISE    basis
    VARIABLES     {
        lastSequenceNumber,
        shelfNodeName,
        shelfNum,
        moduleSlotNumber,
        moduleTrapAlarmSeverity,
        functionModuleType,
        genericTimeStamp,
        vismLapdIndex
    }
    DESCRIPTION
        "Indicates that an entry has been deleted from vismLapdEntry table."
    ::= 50762

-- Any change to the following object in vismLapdEntry table, 
-- trapVismTableChange (50746) will be sent out with a bit map 
-- 0x8000(TRAP_LAPD_TBL_CHG) indicates vismLapdEntry table 
-- has changed.
-- vismLapdWinSize
-- vismLapdRetransCount
-- vismLapdCongestionTimer
-- vismLapdT200Timer
-- vismLapdT203Timer
-- vismLapdType

-- -------------------------------------------------------------------------
-- RUDP session related traps
-- -------------------------------------------------------------------------

  trapSessionSetAdded    TRAP-TYPE
      ENTERPRISE    basis
      VARIABLES     {
          lastSequenceNumber,
          shelfNodeName,
          shelfNum,
          moduleSlotNumber,
          moduleTrapAlarmSeverity,
          functionModuleType,
          genericTimeStamp,
          vismSessionSetNum
      }
      DESCRIPTION
          "Indicates that an entry has been added to vismSessionSetEntry 
           table."
      ::= 50763

  trapSessionSetDeleted    TRAP-TYPE
      ENTERPRISE    basis
      VARIABLES     {
          lastSequenceNumber,
          shelfNodeName,
          shelfNum,
          moduleSlotNumber,
          moduleTrapAlarmSeverity,
          functionModuleType,
          genericTimeStamp,
          vismSessionSetNum
      }
      DESCRIPTION
          "Indicates that an entry has been deleted from vismSessionSetEntry 
           table."
      ::= 50764

trapSessionGrpAdded    TRAP-TYPE
    ENTERPRISE    basis
    VARIABLES     {
        lastSequenceNumber,
        shelfNodeName,
        shelfNum,
        moduleSlotNumber,
        moduleTrapAlarmSeverity,
        functionModuleType,
        genericTimeStamp,
        vismSessionGrpNum
    }
    DESCRIPTION
        "Indicates that an entry has been added to vismSessionGrpEntry 
         table."
    ::= 50765

trapSessionGrpDeleted    TRAP-TYPE
    ENTERPRISE    basis
    VARIABLES     {
        lastSequenceNumber,
        shelfNodeName,
        shelfNum,
        moduleSlotNumber,
        moduleTrapAlarmSeverity,
        functionModuleType,
        genericTimeStamp,
        vismSessionGrpNum
    }
    DESCRIPTION
        "Indicates that an entry has been deleted from vismSessionGrpEntry 
         table."
    ::= 50766

trapRudpSessionAdded    TRAP-TYPE
    ENTERPRISE    basis
    VARIABLES     {
        lastSequenceNumber,
        shelfNodeName,
        shelfNum,
        moduleSlotNumber,
        moduleTrapAlarmSeverity,
        functionModuleType,
        genericTimeStamp,
        vismRudpSessionNum
    }
    DESCRIPTION
        "Indicates that an entry has been added to vismRudpSessionEntry 
         table."
    ::= 50767

trapRudpSessionDeleted    TRAP-TYPE
    ENTERPRISE    basis
    VARIABLES     {
        lastSequenceNumber,
        shelfNodeName,
        shelfNum,
        moduleSlotNumber,
        moduleTrapAlarmSeverity,
        functionModuleType,
        genericTimeStamp,
        vismRudpSessionNum
    }
    DESCRIPTION
        "Indicates that an entry has been deleted from vismRudpSessionEntry 
         table."
    ::= 50768

-- Any change to the following object in vismRudpSessionCnfEntry table, 
-- trapVismTableChange (50746) will be sent out with a bit map 
-- 0x10000(TRAP_RUDPSESSION_TBL_CHG) indicates vismRudpSessionCnfEntry table 
-- has changed.
-- vismRudpSessionLocalPort
-- vismRudpSessionRmtPort
-- vismRudpSessionMaxWindow
-- vismRudpSessionSyncAttempts
-- vismRudpSessionMaxSegSize
-- vismRudpSessionMaxSegSize
-- vismRudpSessionMaxAutoReset
-- vismRudpSessionRetransTmout
-- vismRudpSessionMaxRetrans
-- vismRudpSessionMaxCumAck
-- vismRudpSessionCumAckTmout
-- vismRudpSessionMaxOutOfSeq
-- vismRudpSessionNullSegTmout
-- vismRudpSessionTransStateTmout
--

trapRudpSessionOos    TRAP-TYPE
    ENTERPRISE    basis
    VARIABLES     {
        lastSequenceNumber,
        shelfNodeName,
        shelfNum,
        moduleSlotNumber,
        moduleTrapAlarmSeverity,
        functionModuleType,
        genericTimeStamp,
        vismRudpSessionNum,
        vismRudpSessionState
    }
    DESCRIPTION
        "When a session loses communication with the MGC the state 
         changes to 'oos' and sends out this trap. The severity of
         this trap should be minor severity."
    ::= 50769

trapRudpSessionIs    TRAP-TYPE
    ENTERPRISE    basis
    VARIABLES     {
        lastSequenceNumber,
        shelfNodeName,
        shelfNum,
        moduleSlotNumber,
        moduleTrapAlarmSeverity,
        functionModuleType,
        genericTimeStamp,
        vismRudpSessionNum,
        vismRudpSessionState
    }
    DESCRIPTION
        "When a session state changes to 'is'. This trap is sent out.
         the severity should be 'don't care', no alarm. 
         "
    ::= 50770

trapRudpSessionPrimaryIs    TRAP-TYPE
    ENTERPRISE    basis
    VARIABLES     {
        lastSequenceNumber,
        shelfNodeName,
        shelfNum,
        moduleSlotNumber,
        moduleTrapAlarmSeverity,
        functionModuleType,
        genericTimeStamp,
        vismRudpSessionNum,
        vismRudpSessionState
    }
    DESCRIPTION
        "This trap is sent out when a session state is changed to 
         'primary-is'. 
         The severity should be 'don't care', no alarm. 
        "
    ::= 50771

trapRudpSessionActive    TRAP-TYPE
    ENTERPRISE    basis
    VARIABLES     {
        lastSequenceNumber,
        shelfNodeName,
        shelfNum,
        moduleSlotNumber,
        moduleTrapAlarmSeverity,
        functionModuleType,
        genericTimeStamp,
        vismRudpSessionNum,
        vismRudpSessionState
    }
    DESCRIPTION
        "When a 'primary-is' session in a group receives ACTIVE message 
         from the MGC this trap will be sent out.
         The severity should be 'don't care', no alarm.
        "
    ::= 50772

trapSessionGrpOos    TRAP-TYPE
    ENTERPRISE    basis
    VARIABLES     {
        lastSequenceNumber,
        shelfNodeName,
        shelfNum,
        moduleSlotNumber,
        moduleTrapAlarmSeverity,
        functionModuleType,
        genericTimeStamp,
        vismSessionGrpNum,
        vismSessionGrpState
    }
    DESCRIPTION
        "When all the sessions in the group have changed to 'oos' state,
         the state of this group is changed to 'oos' and this trap 
         will be sent out.
         The severity should be 'minor', no alarm.
        "
    ::= 50773

trapSessionGrpIs    TRAP-TYPE
    ENTERPRISE    basis
    VARIABLES     {
        lastSequenceNumber,
        shelfNodeName,
        shelfNum,
        moduleSlotNumber,
        moduleTrapAlarmSeverity,
        functionModuleType,
        genericTimeStamp,
        vismSessionGrpNum,
        vismSessionGrpState
    }
    DESCRIPTION
        "When the state of this group is changed to 'is'  
         this trap will be sent out.
         The severity should be 'don't care', no alarm.
        "
    ::= 50774

trapSessionSetOos    TRAP-TYPE
    ENTERPRISE    basis
    VARIABLES     {
        lastSequenceNumber,
        shelfNodeName,
        shelfNum,
        moduleSlotNumber,
        moduleTrapAlarmSeverity,
        functionModuleType,
        genericTimeStamp,
        vismSessionSetNum,
        vismSessionSetState
    }
    DESCRIPTION
        "When the session set state is changed to 'oos'
         this trap will be sent out.
         The severity should be 'minor', no alarm.
        "
    ::= 50775

trapSessionSetActiveIs    TRAP-TYPE
    ENTERPRISE    basis
    VARIABLES     {
        lastSequenceNumber,
        shelfNodeName,
        shelfNum,
        moduleSlotNumber,
        moduleTrapAlarmSeverity,
        functionModuleType,
        genericTimeStamp,
        vismSessionSetNum,
        vismSessionSetState
    }
    DESCRIPTION
        "When the session set state is changed to 'active-is' state 
         this trap will be sent out.
         The severity should be 'don't care', no alarm.
        "
    ::= 50776

trapSessionSetStandbyIs    TRAP-TYPE
    ENTERPRISE    basis
    VARIABLES     {
        lastSequenceNumber,
        shelfNodeName,
        shelfNum,
        moduleSlotNumber,
        moduleTrapAlarmSeverity,
        functionModuleType,
        genericTimeStamp,
        vismSessionSetNum,
        vismSessionSetState
    }
    DESCRIPTION
        "When the session set state is changed to 'standby-is' state 
         this trap will be sent out.
         The severity should be 'don't care', no alarm.
        "
    ::= 50777

trapSessionSetFullIs    TRAP-TYPE
    ENTERPRISE    basis
    VARIABLES     {
        lastSequenceNumber,
        shelfNodeName,
        shelfNum,
        moduleSlotNumber,
        moduleTrapAlarmSeverity,
        functionModuleType,
        genericTimeStamp,
        vismSessionSetNum,
        vismSessionSetState
    }
    DESCRIPTION
        "When the session set state is changed from other state to 
         'full-is' state this trap will be sent out.
         The severity should be 'don't care', no alarm.
        "
    ::= 50778


-- ----------------------------------------------------------------------
-- LAPD Dlc related traps
-- ----------------------------------------------------------------------
trapLapdDlcAdded    TRAP-TYPE
    ENTERPRISE    basis
    VARIABLES     {
        lastSequenceNumber,
        shelfNodeName,
        shelfNum,
        moduleSlotNumber,
        moduleTrapAlarmSeverity,
        functionModuleType,
        genericTimeStamp,
        vismLapdDlcIndex,
        vismLapdDlcSapi,
        vismLapdDlcTei
    }
    DESCRIPTION
        "Indicates that an entry has been added to vismLapdDlcEntry table.
        "
    ::= 50779

trapLapdDlcDeleted    TRAP-TYPE
    ENTERPRISE    basis
    VARIABLES     {
        lastSequenceNumber,
        shelfNodeName,
        shelfNum,
        moduleSlotNumber,
        moduleTrapAlarmSeverity,
        functionModuleType,
        genericTimeStamp,
        vismLapdDlcIndex,
        vismLapdDlcSapi,
        vismLapdDlcTei
    }
    DESCRIPTION
        "Indicates that an entry has been deleted from vismLapdDlcEntry 
         table.
        "
    ::= 50780

trapLapdDlcUp    TRAP-TYPE
    ENTERPRISE    basis
    VARIABLES     {
        lastSequenceNumber,
        shelfNodeName,
        shelfNum,
        moduleSlotNumber,
        moduleTrapAlarmSeverity,
        functionModuleType,
        genericTimeStamp,
        vismLapdDlcIndex,
        vismLapdDlcSapi,
        vismLapdDlcTei,
        vismLapdDlcLinkState
    }
    DESCRIPTION
        "Indicates that the linking state between TDM and DLC on a 
         specific D-channel changes to up. 
        "
    ::= 50781

trapLapdDlcDown    TRAP-TYPE
    ENTERPRISE    basis
    VARIABLES     {
        lastSequenceNumber,
        shelfNodeName,
        shelfNum,
        moduleSlotNumber,
        moduleTrapAlarmSeverity,
        functionModuleType,
        genericTimeStamp,
        vismLapdDlcIndex,
        vismLapdDlcSapi,
        vismLapdDlcTei,
        vismLapdDlcLinkState
    }
    DESCRIPTION
        "Indicates that the linking state between TDM and DLC on a 
         specific D-channel changes to down.
        "
    ::= 50782

persistentXgcpEventCreated   TRAP-TYPE
        ENTERPRISE      basis
        VARIABLES       {
                        lastSequenceNumber,
                        shelfNodeName,
                        shelfNum,
                        moduleSlotNumber,
                        moduleTrapAlarmSeverity,
                        functionModuleType,
                        genericTimeStamp,
                        vismTrapIntIndex1,
                        persistentXgcpEventName
                        }

        DESCRIPTION
            "Indicates that an entry is added to persistantXgcpEvents table.
             The value of vismTrapIntIndex1 gives the value of persistantXgcpEventNum. 
             persistantXgcpEventName gives the name associated with that event
             num.
            "
        ::= 50786

persistentXgcpEventDeleted     TRAP-TYPE
        ENTERPRISE      basis
        VARIABLES       {
                        lastSequenceNumber,
                        shelfNodeName,
                        shelfNum,
                        moduleSlotNumber,
                        moduleTrapAlarmSeverity,
                        functionModuleType,
                        genericTimeStamp,
                        vismTrapIntIndex1,
                        persistentXgcpEventName
                        }

        DESCRIPTION
            "Indicates that an entry is deleted from persistantXgcpEvents table.
             The value of vismTrapIntIndex1 gives the value of persistantXgcpEventNum. 
             persistantXgcpEventName gives the name associated with that event
             num.
            "
        ::= 50787

------------------------------
-- Traps for mgDomainNameTable
------------------------------

mgDomainNameAdded     TRAP-TYPE
        ENTERPRISE      basis
        VARIABLES       { 
                        lastSequenceNumber,
                        shelfNodeName,
                        shelfNum,
                        moduleSlotNumber,
                        moduleTrapAlarmSeverity,
                        functionModuleType,
                        genericTimeStamp,
                        vismTrapIntIndex1,
                        mgDomainName,
                        mgDnsResolutionType
                        }
 
        DESCRIPTION
            "Indicates that an entry is added to mgDomainNameTable.
            "
        ::= 50791

mgDomainNameDeleted     TRAP-TYPE
        ENTERPRISE      basis
        VARIABLES       { 
                        lastSequenceNumber,
                        shelfNodeName,
                        shelfNum,
                        moduleSlotNumber,
                        moduleTrapAlarmSeverity,
                        functionModuleType,
                        genericTimeStamp,
                        vismTrapIntIndex1
                        }
 
        DESCRIPTION
            "Indicates that an entry is deleted from mgDomainNameTable.
            "
        ::= 50789







------------------------------
-- Traps for vismTonePlanTable
------------------------------

vismTonePlanAdded       TRAP-TYPE
        ENTERPRISE      basis
        VARIABLES       { 
                        lastSequenceNumber,
                        shelfNodeName,
                        shelfNum,
                        moduleSlotNumber,
                        moduleTrapAlarmSeverity,
                        functionModuleType,
                        genericTimeStamp,
                        vismTrapIntIndex1,
                        tonePlanRegionName,
                        tonePlanVersionNumber,
                        tonePlanFileName
                        }
 
        DESCRIPTION
            "Indicates that an entry is added to vismTonePlanTable.
             The value of vismTrapIntIndex1 gives the value of tonePlanIndex. 
            "
        ::= 50798

vismTonePlanDeleted     TRAP-TYPE
        ENTERPRISE      basis
        VARIABLES       { 
                        lastSequenceNumber,
                        shelfNodeName,
                        shelfNum,
                        moduleSlotNumber,
                        moduleTrapAlarmSeverity,
                        functionModuleType,
                        genericTimeStamp,
                        vismTrapIntIndex1,
                        tonePlanRegionName,
                        tonePlanVersionNumber,
                        tonePlanFileName
                        }
 
        DESCRIPTION
            "Indicates that an entry is deleted from vismTonePlanTable.
             The value of vismTrapIntIndex1 gives the value of tonePlanIndex. 
            "
        ::= 50799






-- -------------------------------------------------------------------------
-- VOIP trunking related traps
-- -------------------------------------------------------------------------

vismRtpConnAdded    TRAP-TYPE
    ENTERPRISE      basis
    VARIABLES       {
        lastSequenceNumber,
        shelfNodeName,
        shelfNum,
        moduleSlotNumber,
        moduleTrapAlarmSeverity,
        functionModuleType,
        genericTimeStamp,
	vismTrapIntIndex1,
        vismRtpLcn
        }
 
    DESCRIPTION
        " Indicates that an entry has been added to vismRtpConnGrpTable.
          The value of vismTrapIntIndex1 gives the vismRtpConnNum.
        "
    ::= 50650

vismRtpConnDeleted   TRAP-TYPE
    ENTERPRISE      basis
    VARIABLES       {
        lastSequenceNumber,
        shelfNodeName,
        shelfNum,
        moduleSlotNumber,
        moduleTrapAlarmSeverity,
        functionModuleType,
        genericTimeStamp,
	vismTrapIntIndex1,
        vismRtpLcn
        }
 
    DESCRIPTION
        " Indicates that an entry has been deleted from vismRtpConnGrpTable.
          The value of vismTrapIntIndex1 gives the vismRtpConnNum.
        "
    ::= 50651

vismRtpConnStateChg    TRAP-TYPE
    ENTERPRISE      basis
    VARIABLES       {
        lastSequenceNumber,
        shelfNodeName,
        shelfNum,
        moduleSlotNumber,
        moduleTrapAlarmSeverity,
        functionModuleType,
        genericTimeStamp,
	vismTrapIntIndex1,
        vismRtpConnAlarmState,
        vismRtpLcn,
        vismRtpFailReason
        }
 
    DESCRIPTION
        " Indicates that the alarm state of an entry in vismRtpConnGrpTable
          is changed. The value of vismTrapIntIndex1 gives the vismRtpConnNum. 
        "
    ::= 50652

vismLapdTrStateIs    TRAP-TYPE
    ENTERPRISE      basis
    VARIABLES       {
        lastSequenceNumber,
        shelfNodeName,
        shelfNum,
        moduleSlotNumber,
        moduleTrapAlarmSeverity,
        functionModuleType,
        genericTimeStamp,
	vismTrapIntIndex1,
        vismLapdTrunkState
        }
 
    DESCRIPTION
        " Indicates that the Lapd Trunk State has changed to In Service. 
          The value of vismTrapIntIndex1 gives the value of vismLapdTrunkNum.    
        "
    ::= 50653

vismLapdTrStateOos    TRAP-TYPE
    ENTERPRISE      basis
    VARIABLES       {
        lastSequenceNumber,
        shelfNodeName,
        shelfNum,
        moduleSlotNumber,
        moduleTrapAlarmSeverity,
        functionModuleType,
        genericTimeStamp,
	vismTrapIntIndex1,
        vismLapdTrunkState
        }
 
    DESCRIPTION
        " Indicates that the Lapd Trunk State has changed to Out of Service.     
          The value of vismTrapIntIndex1 gives the value of vismLapdTrunkNum.    
        "
    ::= 50654
 
vismLapdTrunkAdded    TRAP-TYPE
    ENTERPRISE      basis
    VARIABLES       {
        lastSequenceNumber,
        shelfNodeName,
        shelfNum,
        moduleSlotNumber,
        moduleTrapAlarmSeverity,
        functionModuleType,
        genericTimeStamp,
	vismTrapIntIndex1
        }
 
    DESCRIPTION
        " Indicates that a new entry has been added in the vismLapdTrunkGrpTable.
          The value of vismTrapIntIndex1 gives the value of vismLapdTrunkNum.       
        "
    ::= 50655

vismLapdTrunkDeleted    TRAP-TYPE
    ENTERPRISE      basis
    VARIABLES       {
        lastSequenceNumber,
        shelfNodeName,
        shelfNum,
        moduleSlotNumber,
        moduleTrapAlarmSeverity,
        functionModuleType,
        genericTimeStamp,
	vismTrapIntIndex1
        }
 
    DESCRIPTION
        " Indicates that an existing entry has been deleted from the 
          vismLapdTrunkGrpTable. The value of vismTrapIntIndex1 gives the 
          value of vismLapdTrunkNum.        
        "
    ::= 50656

-- -------------------------------------------------------------------------
-- PRI BH binding related traps
-- -------------------------------------------------------------------------

-- Since vismPriBhBindEntry table are defered for now, the trap for 
-- add and delete in this table are deffered.
--

--trapPriBhBindAdded    TRAP-TYPE
--    ENTERPRISE    basis
--    VARIABLES     {
--        lastSequenceNumber,
--        shelfNodeName,
--        shelfNum,
--        moduleSlotNumber,
--        moduleTrapAlarmSeverity,
--        functionModuleType,
--        genericTimeStamp,
--        vismPriBhIfIndex,
--        vismPriBhSetNum
--    }
--    DESCRIPTION
--        "Indicates that an entry has been added to vismPriBhBindEntry 
--         table."
--    ::= 50783

--trapPriBhBindDeleted    TRAP-TYPE
--    ENTERPRISE    basis
--    VARIABLES     {
--        lastSequenceNumber,
--        shelfNodeName,
--        shelfNum,
--        moduleSlotNumber,
--        moduleTrapAlarmSeverity,
--        functionModuleType,
--        genericTimeStamp,
--        vismPriBhIfIndex,
--        vismPriBhSetNum
--    }
--    DESCRIPTION
--        "Indicates that an entry has been deleted from vismPriBhBindEntry 
--         table."
--    ::= 50784


-- -------------------------------------------------------------------------
-- Traps for the MGC redundancy group objects
-- -------------------------------------------------------------------------
-- Traps for mgcRedundancyGrpEntry_t


mgcRedundancyGrpAdded           TRAP-TYPE
        ENTERPRISE              basis
        VARIABLES               {
                                lastSequenceNumber,
                                shelfNodeName,
                                shelfNum,
                                moduleSlotNumber,
                                moduleTrapAlarmSeverity,
                                functionModuleType,
                                genericTimeStamp,
                                vismTrapIntIndex1,
                                vismTrapIntIndex2
                                }
        DESCRIPTION
            "Indicates that an entry has been added in the 
             mgcRedundancyGrptable. 
             The value of vismTrapIntIndex1 gives the value of
             mgcRedundancyGrpNum and vismTrapIntIndex2 gives the
             value of mgcNumber.
        "
        ::= 50657


mgcRedundancyGrpDeleted         TRAP-TYPE
        ENTERPRISE              basis
        VARIABLES               {
                                lastSequenceNumber,
                                shelfNodeName,
                                shelfNum,
                                moduleSlotNumber,
                                moduleTrapAlarmSeverity,
                                functionModuleType,
                                genericTimeStamp,
                                vismTrapIntIndex1,
                                vismTrapIntIndex2
                                }
        DESCRIPTION
            "Indicates that an entry has been deleted from the
             mgcRedudancyGrpTable.
             The value of vismTrapIntIndex1 gives the value of
             mgcRedundancyGrpNum and vismTrapIntIndex2 gives the
             value of mgcNumber.
        "
        ::= 50658


-- Traps related to mgcRedundancyGrpParamTable

mgcRedundancyGrpCommOk      TRAP-TYPE
        ENTERPRISE              basis
        VARIABLES               {
                                lastSequenceNumber,
                                shelfNodeName,
                                shelfNum,
                                moduleSlotNumber,
                                moduleTrapAlarmSeverity,
                                functionModuleType,
                                genericTimeStamp,
                                vismTrapIntIndex1
                                }
        DESCRIPTION
            "Triggered when the comm state of the MGC redundancy group
             transitions to commOk state. The transition will be from
             commLoss to CommOk when communication between the GW and
             the callagent is established.
             The value of vismTrapIntIndex1 gives the value of
             mgcRedundancyGrpNum.
        "
        ::= 50659


mgcRedundancyGrpCommLoss      TRAP-TYPE
        ENTERPRISE              basis
        VARIABLES               {
                                lastSequenceNumber,
                                shelfNodeName,
                                shelfNum,
                                moduleSlotNumber,
                                moduleTrapAlarmSeverity,
                                functionModuleType,
                                genericTimeStamp,
                                vismTrapIntIndex1
                                }
        DESCRIPTION
            "Triggered when the comm state of the MGC redundancy group
             transitions to commLoss. The transition will be from
             commOk to commLoss when the callagent does not respond to
             GW initiated messages.
             The value of vismTrapIntIndex1 gives the value of
             mgcRedundancyGrpNum.
        "
        ::= 50660

-- Traps related to MgcRedundancyGrpTable

mgcActiveInGrp          TRAP-TYPE
        ENTERPRISE      basis
        VARIABLES       {
                        lastSequenceNumber,
                        shelfNodeName,
                        shelfNum,
                        moduleSlotNumber,
                        moduleTrapAlarmSeverity,
                        functionModuleType,
                        genericTimeStamp,
                        vismTrapIntIndex1,
                        vismTrapIntIndex2,
                        mgcRedundancyGrpActState          
                        }

        DESCRIPTION
            "Triggered when the MGC in an MGC Redundancy Group transitions
             from inactive to active state. Indicates the active MGC in an
             MGC Redundancy group.
             The value of vismTrapIntIndex1 gives the value of
             mgcRedundancyGrpNum. The value of vismTrapIntIndex2 gives the
             value of mgcNumber.
        "
        ::= 50665

mgcInactiveInGrp        TRAP-TYPE
        ENTERPRISE      basis
        VARIABLES       {
                        lastSequenceNumber,
                        shelfNodeName,
                        shelfNum,
                        moduleSlotNumber,
                        moduleTrapAlarmSeverity,
                        functionModuleType,
                        genericTimeStamp,
                        vismTrapIntIndex1,
                        vismTrapIntIndex2,
                        mgcRedundancyGrpActState
                        }

        DESCRIPTION
            "Triggered when the MGC in an MGC Redundancy Group transitions
             from active to inactive state.
             The value of vismTrapIntIndex1 gives the value of
             mgcRedundancyGrpNum. The value of vismTrapIntIndex2 gives the 
             value of mgcNumber.
        "
        ::= 50666



-- Traps related to mgcRedundancyGrpProtocolTable
mgcRedundancyGrpProtocolAdded           TRAP-TYPE
        ENTERPRISE              basis
        VARIABLES               {
                                lastSequenceNumber,
                                shelfNodeName,
                                shelfNum,
                                moduleSlotNumber,
                                moduleTrapAlarmSeverity,
                                functionModuleType,
                                genericTimeStamp,
                                vismTrapIntIndex1,
                                vismTrapIntIndex2
                                }

        DESCRIPTION
            "Indicates that an entry is added to the 
             mgcRedundancyGrpProtocolTable.
             The value of vismTrapIntIndex1 gives the
             value of mgcRedundancyGrpNum.
             The value of vismTrapIntIndex2 gives the
             value of mgProtocolNumber.
        "
        ::= 50661

mgcRedundancyGrpProtocolDeleted         TRAP-TYPE
        ENTERPRISE              basis
        VARIABLES               {
                                lastSequenceNumber,
                                shelfNodeName,
                                shelfNum,
                                moduleSlotNumber,
                                moduleTrapAlarmSeverity,
                                functionModuleType,
                                genericTimeStamp,
                                vismTrapIntIndex1,
                                vismTrapIntIndex2
                                }

        DESCRIPTION
            "Indicates that an entry is deleted from the
             mgcRedundancyGrpProtocolTable.
             The value of vismTrapIntIndex1 gives the
             value of mgcRedundancyGrpNum.
             The value of vismTrapIntIndex2 gives the
             value of mgProtocolNumber.
        "
        ::= 50662

peerGrpHeartbeatLost    TRAP-TYPE
        ENTERPRISE      basis
        VARIABLES       {
                        lastSequenceNumber,
                        shelfNodeName,
                        shelfNum,
                        moduleSlotNumber,
                        moduleTrapAlarmSeverity,
                        functionModuleType,
                        genericTimeStamp,
                        vismTrapIntIndex1,
                        srcpPeerGrpTimeSinceHeartbeat
                        }

        DESCRIPTION
            "This notification indicates that the system failed to receive
             a heartbeat from a specific peer group. The notification is sent
             when srcpPeerGrpTimeSinceHeartbeat crosses the
             srcpPeerGrpHeartbeatInterval threshold.
             The value of vismTrapIntIndex1 gives the value of
             mgcRedundancyGrpNum.
        "
        ::= 50663


peerGrpHeartbeatDetected     TRAP-TYPE
        ENTERPRISE      basis
        VARIABLES       {
                        lastSequenceNumber,
                        shelfNodeName,
                        shelfNum,
                        moduleSlotNumber,
                        moduleTrapAlarmSeverity,
                        functionModuleType,
                        genericTimeStamp,
                        vismTrapIntIndex1,
                        srcpPeerGrpTimeSinceHeartbeat
                        }

        DESCRIPTION
            "This notification indicates that the system detected a heartbeat
             from a specific peer group after it had been lost. The notification
             is sent when srcpPeerGrpTimeSinceHeartbeat which had exceeded
             the threshold, resets to 0 due to receipt of a heartbeat.
             The value of vismTrapIntIndex1 gives the value of
             mgcRedundancyGrpNum.
        "
        ::= 50664


-- 
-- Traps definition for mgcRedundancyGrpParamTable
--
mgcRedundancyGrpParamEntryAdded TRAP-TYPE
        ENTERPRISE      basis
        VARIABLES       {
                        lastSequenceNumber,
                        shelfNodeName,
                        shelfNum,
                        moduleSlotNumber,
                        moduleTrapAlarmSeverity,
                        functionModuleType,
                        genericTimeStamp,
                        vismTrapIntIndex1
                        }
        DESCRIPTION
            "Indicates that an entry has been added in the
             mgcRedundancyGrpParamTable.
             The value of vismTrapIntIndex1 gives the value of
             mgcRedundancyGrpNum. 
             The entries in the mgcRedundancyGrpParamTable are
             implicitly added when the first entry for that 
             mgcRedundancyGrpNum is added into the
             mgcRedundancyGrpTable by the user.
        "
        ::= 50668

mgcRedundancyGrpParamEntryDeleted  TRAP-TYPE
        ENTERPRISE      basis
        VARIABLES       {
                        lastSequenceNumber,
                        shelfNodeName,
                        shelfNum,
                        moduleSlotNumber,
                        moduleTrapAlarmSeverity,
                        functionModuleType,
                        genericTimeStamp,
                        vismTrapIntIndex1
                        }
        DESCRIPTION
            "Indicates that an entry has been deleted from the
             mgcRedundancyGrpParamTable.
             The value of vismTrapIntIndex1 gives the value of
             mgcRedundancyGrpNum.
             The entries in the mgcRedundancyGrpParamTable are
             implicitly deleted when the last entry for that
             mgcRedundancyGrpNum is removed from the
             mgcRedundancyGrpTable by the user.
        "
        ::= 50669

--
-- Traps for srcpPeerGrpParamTable (entry added or removed)
--
srcpPeerGrpParamEntryAdded      TRAP-TYPE
        ENTERPRISE      basis
        VARIABLES       {
                        lastSequenceNumber,
                        shelfNodeName,
                        shelfNum,
                        moduleSlotNumber,
                        moduleTrapAlarmSeverity,
                        functionModuleType,
                        genericTimeStamp,
                        vismTrapIntIndex1
                        }
        DESCRIPTION
            "Indicates that an entry has been added to the
             srcpPeerGrpParamTable.
             The value of vismTrapIntIndex1 gives the value of
             mgcRedundancyGrpNum.
             The entries in the srcpPeerGrpParamTable are
             implicitly created when SRCP protocol is added for
             the Mgc Redundancy Group.
        "
        ::= 50670

srcpPeerGrpParamEntryDeleted    TRAP-TYPE
        ENTERPRISE      basis
        VARIABLES       {
                        lastSequenceNumber,
                        shelfNodeName,
                        shelfNum,
                        moduleSlotNumber,
                        moduleTrapAlarmSeverity,
                        functionModuleType,
                        genericTimeStamp,
                        vismTrapIntIndex1
                        }
        DESCRIPTION
            "Indicates that an entry has been deleted from the
             srcpPeerGrpParamTable.
             The value of vismTrapIntIndex1 gives the value of
             mgcRedundancyGrpNum.
             The entries in the srcpPeerGrpParamTable are 
             implicitly deleted when the SRCP protocol configured
             for the Mgc Redundancy Group is deleted.
        "
        ::= 50671








------------------------------
-- Traps for Announcement File Table
------------------------------

cwAnnFileAddStarted     TRAP-TYPE
        ENTERPRISE      basis
        VARIABLES       { 
                        lastSequenceNumber,
                        shelfNodeName,
                        shelfNum,
                        moduleSlotNumber,
                        moduleTrapAlarmSeverity,
                        functionModuleType,
                        genericTimeStamp,
                        vismTrapIntIndex1,
                        cwAnnFileName,
                        cwAnnFileCodec,
                        cwAnnFileStatus
                        }
        DESCRIPTION
            "Indicates that an attempt was made to add an entry to the
             announceTable.

             This trap will not be generated at Card reset time when all of
             previously configured permanent files are downloaded to bring
             the Card up to date.

             The value of vismTrapIntIndex1 gives the value of announceIndex. 
            "
        ::= 50674





cwAnnFileLoadComplete   TRAP-TYPE
        ENTERPRISE      basis
        VARIABLES       { 
                        lastSequenceNumber,
                        shelfNodeName,
                        shelfNum,
                        moduleSlotNumber,
                        moduleTrapAlarmSeverity,
                        functionModuleType,
                        genericTimeStamp,
                        vismTrapIntIndex1,
                        cwAnnFileName,
                        cwAnnFileCodec,
                        cwAnnFileStatus
                        }
        DESCRIPTION
            "Indicates that an attempt to add an entry to the announceTable 
             has been successfully completed.

             The value of vismTrapIntIndex1 gives the value of announceIndex. 
            "
        ::= 50675




cwAnnFileLoadFailed     TRAP-TYPE
        ENTERPRISE      basis
        VARIABLES       { 
                        lastSequenceNumber,
                        shelfNodeName,
                        shelfNum,
                        moduleSlotNumber,
                        moduleTrapAlarmSeverity,
                        functionModuleType,
                        genericTimeStamp,
                        vismTrapIntIndex1,
                        cwAnnFileName,
                        cwAnnFileCodec,
                        cwAnnFileStatus
                        }
        DESCRIPTION
            "Indicates that an attempt to add an entry to the announceTable 
             has failed.

             The value of vismTrapIntIndex1 gives the value of announceIndex. 
            "
        ::= 50676




cwAnnFileDeleted        TRAP-TYPE
        ENTERPRISE      basis
        VARIABLES       { 
                        lastSequenceNumber,
                        shelfNodeName,
                        shelfNum,
                        moduleSlotNumber,
                        moduleTrapAlarmSeverity,
                        functionModuleType,
                        genericTimeStamp,
                        vismTrapIntIndex1
                        }
        DESCRIPTION
            "Indicates that an entry is deleted from announceTable.
             The value of vismTrapIntIndex1 gives the value of announceIndex. 
            "
        ::= 50677






newFlow                   TRAP-TYPE
        ENTERPRISE      basis
        VARIABLES       {
                        lastSequenceNumber,
                        shelfNodeName,
                        shelfNum,
                        moduleSlotNumber,
                        moduleTrapAlarmSeverity,
                        functionModuleType,
                        genericTimeStamp,
                        intSrvFlowStatus, 
                        rsvpSessionDestAddr,
                        rsvpResvFwdStatus, 
                        rsvpResvStatus, 
                        rsvpSenderStatus
                        }
        DESCRIPTION
           "The   newFlow   trap   indicates   that    the
           originating  system has installed a new flow in
           its   classifier,    or    (when    reservation
           authorization   is  in  view)  is  prepared  to
           install such a flow in the  classifier  and  is
           requesting authorization.  The objects included
           with the  Notification  may  be  used  to  read
           further   information   using   the  Integrated
           Services and RSVP MIBs.  Authorization or  non-
           authorization  may be enacted by a write to the
           variable intSrvFlowStatus."

       ::= 50672


    lostFlow TRAP-TYPE
        ENTERPRISE      basis
        VARIABLES       {
                        lastSequenceNumber,
                        shelfNodeName,
                        shelfNum,
                        moduleSlotNumber,
                        moduleTrapAlarmSeverity,
                        functionModuleType,
                        genericTimeStamp,
                        intSrvFlowStatus, 
                        rsvpSessionDestAddr,
                        rsvpResvFwdStatus, 
                        rsvpResvStatus, 
                        rsvpSenderStatus
                        }
        DESCRIPTION
           "The   lostFlow   trap   indicates   that   the
           originating  system has removed a flow from its
           classifier."

       ::= 50673

END

-- -----------------------------------------------------------------
--
-- END: TRAPS specific to VISM card.
--
-- -----------------------------------------------------------------
