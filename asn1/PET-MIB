--***********************************************************************\
--*                                                                       *
--*               INTEL CORPORATION PROPRIETARY INFORMATION               *
--*  This software is supplied under the terms of a license agreement or  *
--*  nondisclosure agreement with Intel Corporation and may not be copied *
--*   or disclosed except in accordance with the terms of that agreement. *
--*        Copyright (c) 1998 Intel Corporation. All Rights Reserved.     *
--*                                                                       *
--\***********************************************************************/

--/**************************************************************************
--*
--* NAME:
--*   aolnprxy.mib
--*
--* DESCRIPTION:
--* 	Alert on LAN MIB
--*	  
--*  
--*  $WorkFile: $  
--*  $Revision: 6 $  
--*  $ModTime:  $  
--*  $Author: Psaranga $  
--*
--***************************************************************************

PET-MIB

DEFINITIONS ::= BEGIN

-- Title : Alert on LAN pET MIB version 1.0.

IMPORTS
  MODULE-IDENTITY,  
  OBJECT-TYPE,
  Integer32, IpAddress  
  FROM SNMPv2-SMI
    enterprises
	  FROM RFC1155-SMI
	DisplayString
	  FROM RFC1213-MIB
	    TRAP-TYPE
		  FROM RFC-1215
	  ;


wired-for-management        OBJECT IDENTIFIER ::= { enterprises 3183 }
pET                         OBJECT IDENTIFIER ::= { wired-for-management 1 }
pET-version-1               OBJECT IDENTIFIER ::= { pET 1 }


-- MODULE IDENTIFICATION
--
-- Alert-on-LAN MODULE-IDENTITY
--  LAST-UPDATED "9807210000Z"
--  ORGANIZATION "Intel Corporation"
--  CONTACT-INFO
--   " Alert On LAN* Software
--     Intel Corporation, JF3-4
--	 Hillsboro, OR. "
--  DESCRIPTION
--  " This is the pET MIB. Version 1.0 "
-- We should be able to plug this branch into any tree from this point forward


-- ****************************************
-- SYSTEM INFORMATION BRANCH STARTS HERE.
-- ****************************************


pETTrap OBJECT-TYPE
 SYNTAX OCTET STRING ( SIZE(110) )
 ACCESS read-only
 STATUS current
 DESCRIPTION
  "Trap information"
::= { pET-version-1 1 }

pET-PresenceHeartbeat TRAP-TYPE
 ENTERPRISE pET-version-1
 DESCRIPTION 
  "Presence Heartbeat Expired"
 ::= 2584320

pET-CoverTamper TRAP-TYPE
 ENTERPRISE pET-version-1
 DESCRIPTION 
  "Cover Tamper"
 ::= 356096

pET-Voltage-Fan-Temperature TRAP-TYPE
 ENTERPRISE pET-version-1
 DESCRIPTION 
  "Voltage/Fan/Temperature Out of Specification"
 ::= 552706

pET-LANLeash TRAP-TYPE
 ENTERPRISE pET-version-1
 DESCRIPTION 
  "LAN Leash Tamper"
 ::= 356100

pET-Temperature TRAP-TYPE
 ENTERPRISE pET-version-1
 DESCRIPTION 
  "Temperature Out of Specification"
 ::= 93952

pET-ProcessorMissing TRAP-TYPE
 ENTERPRISE pET-version-1
 DESCRIPTION 
  "Processor Missing"
 ::= 356099

pET-ProcessorTemperature TRAP-TYPE
 ENTERPRISE pET-version-1
 DESCRIPTION 
  "Processor Over Temperature"
 ::= 487169

pET-Watchdog TRAP-TYPE
 ENTERPRISE pET-version-1
 DESCRIPTION 
  "Watchdog Event"
 ::= 1142534

pET-P-O-S-T TRAP-TYPE
 ENTERPRISE pET-version-1
 DESCRIPTION 
  "P.O.S.T."
 ::= 1011456

pET-Voltage TRAP-TYPE
 ENTERPRISE pET-version-1
 DESCRIPTION 
  "Voltage Out of Specification"
 ::= 159488

pET-Fan TRAP-TYPE
 ENTERPRISE pET-version-1
 DESCRIPTION 
  "Fan Out of Specification"
 ::= 290560

pET-Fan-Temperature TRAP-TYPE
 ENTERPRISE pET-version-1
 DESCRIPTION 
  "Fan/Temperature Out of Specification"
 ::= 683778

pET-Undock TRAP-TYPE
 ENTERPRISE pET-version-1
 DESCRIPTION 
  "Surprised Undock event"
 ::= 356101 

pET-EventClear TRAP-TYPE
 ENTERPRISE pET-version-1
 DESCRIPTION 
  "Event clear"
 ::= 1076994

pET-AlertOnLAN TRAP-TYPE
 ENTERPRISE pET-version-1
 DESCRIPTION 
  "Alert on LAN 2 Event has occured"
 ::= 2277391

END
