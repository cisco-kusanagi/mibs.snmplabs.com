--  Title:    aiSPY.MIB
--  Version:  1.21
--  Date:     01/07/99 1:00 pm	
--
--  Copyright @ 1999 Applied Innovation, Inc.  All rights reserved worldwide.
--
--  This MIB defines objects for the aiSPY SNMP agent.
--

AISPY-MIB DEFINITIONS ::= BEGIN

IMPORTS
	TruthValue
		FROM RFC1253-MIB
	DisplayString
		FROM RFC1213-MIB
	OBJECT-TYPE
		FROM RFC-1212
	TRAP-TYPE FROM RFC-1215
	Counter, enterprises
		FROM RFC1155-SMI
	Gauge32, OBJECT-IDENTITY FROM SNMPv2-SMI;

aii OBJECT IDENTIFIER ::= { enterprises  539 }

aiSPY   OBJECT IDENTIFIER ::= { aii  20 }

aiSPYIdent OBJECT IDENTIFIER ::= { aiSPY 1 }

aiSPYIdentManufacturer OBJECT-TYPE
    SYNTAX  DisplayString
    ACCESS  read-only
    STATUS  mandatory
    DESCRIPTION
           "The Monitor Control Unit manufacturer."
    ::= { aiSPYIdent  1 }

aiSPYIdentModel OBJECT-TYPE
    SYNTAX  DisplayString
    ACCESS  read-only
    STATUS  mandatory
    DESCRIPTION
           "The Monitor Control Unit Model designation."
    ::= { aiSPYIdent  2 }

aiSPYIdentSoftwareVersion OBJECT-TYPE
    SYNTAX  DisplayString
    ACCESS  read-only
    STATUS  mandatory
    DESCRIPTION
           "The aiSPY SNMP Agent software version."
    ::= { aiSPYIdent  3 }

aiSPYIdentSpecific OBJECT-TYPE
    SYNTAX  OBJECT IDENTIFIER
    ACCESS  read-only
    STATUS  mandatory
    DESCRIPTION
           "A reference to MIB definitions specific to the
            particular Monitor Unit being managed. This
            object is used to locate the product-specific MIB
            for this device.

            If this information is not present, its value
            should be the OBJECT IDENTIFIER { 0 0 },
            which is a syntactically valid object identifier,
            and any conformant implementation of ASN.1 and BER
            must be able to generate and recognize this value."
    ::= { aiSPYIdent  4 }

aiSPYSystem OBJECT IDENTIFIER ::= { aiSPY 2 }

aiSPYClock OBJECT-TYPE
    SYNTAX  DisplayString
    ACCESS  read-write
    STATUS  mandatory
    DESCRIPTION
           "The aiSPY internal clock settings.
            Displayed as MM/DD/YY HH:MM:SS"
    ::= { aiSPYSystem  1 }

aiSPYDoorAlarmBypass OBJECT-TYPE
    SYNTAX  INTEGER (-2147483648..2147483647)
    ACCESS  read-write
    STATUS  mandatory
    DESCRIPTION
           "The aiSPY door alarm bypass switch.
            This allows the alarm to be bypassed upon valid keypad access.
            Zero disables this, or use 1 thru 20 for the corresponding
            aiSPY input."
    ::= { aiSPYSystem  2 }

aiSPYKeypad OBJECT IDENTIFIER ::= { aiSPYSystem 3 }

aiSPYKeypadCode1 OBJECT-TYPE
    SYNTAX  DisplayString
    ACCESS  read-write
    STATUS  mandatory
    DESCRIPTION
           "The aiSPY keypad access code for user #1.
            This can be up to six numeric characters."
    ::= { aiSPYKeypad  1 }

aiSPYKeypadName1 OBJECT-TYPE
    SYNTAX  DisplayString
    ACCESS  read-write
    STATUS  mandatory
    DESCRIPTION
           "The aiSPY keypad access name for user #1.
            This can be up to 20 characters."
    ::= { aiSPYKeypad  2 }

aiSPYKeypadCode2 OBJECT-TYPE
    SYNTAX  DisplayString
    ACCESS  read-write
    STATUS  mandatory
    DESCRIPTION
           "The aiSPY keypad access code for user #2.
            This can be up to six numeric characters."
    ::= { aiSPYKeypad  3 }

aiSPYKeypadName2 OBJECT-TYPE
    SYNTAX  DisplayString
    ACCESS  read-write
    STATUS  mandatory
    DESCRIPTION
           "The aiSPY keypad access name for user #2.
            This can be up to 20 characters."
    ::= { aiSPYKeypad  4 }

aiSPYKeypadCode3 OBJECT-TYPE
    SYNTAX  DisplayString
    ACCESS  read-write
    STATUS  mandatory
    DESCRIPTION
           "The aiSPY keypad access code for user #3.
            This can be up to six numeric characters."
    ::= { aiSPYKeypad  5 }

aiSPYKeypadName3 OBJECT-TYPE
    SYNTAX  DisplayString
    ACCESS  read-write
    STATUS  mandatory
    DESCRIPTION
           "The aiSPY keypad access name for user #3.
            This can be up to 20 characters."
    ::= { aiSPYKeypad  6 }

aiSPYKeypadCode4 OBJECT-TYPE
    SYNTAX  DisplayString
    ACCESS  read-write
    STATUS  mandatory
    DESCRIPTION
           "The aiSPY keypad access code for user #4.
            This can be up to six numeric characters."
    ::= { aiSPYKeypad  7 }

aiSPYKeypadName4 OBJECT-TYPE
    SYNTAX  DisplayString
    ACCESS  read-write
    STATUS  mandatory
    DESCRIPTION
           "The aiSPY keypad access name for user #4.
            This can be up to 20 characters."
    ::= { aiSPYKeypad  8 }

aiSPYKeypadCode5 OBJECT-TYPE
    SYNTAX  DisplayString
    ACCESS  read-write
    STATUS  mandatory
    DESCRIPTION
           "The aiSPY keypad access code for user #5.
            This can be up to six numeric characters."
    ::= { aiSPYKeypad  9 }

aiSPYKeypadName5 OBJECT-TYPE
    SYNTAX  DisplayString
    ACCESS  read-write
    STATUS  mandatory
    DESCRIPTION
           "The aiSPY keypad access name for user #5.
            This can be up to 20 characters."
    ::= { aiSPYKeypad  10 }

aiSPYKeypadCode6 OBJECT-TYPE
    SYNTAX  DisplayString
    ACCESS  read-write
    STATUS  mandatory
    DESCRIPTION
           "The aiSPY keypad access code for user #6.
            This can be up to six numeric characters."
    ::= { aiSPYKeypad  11 }

aiSPYKeypadName6 OBJECT-TYPE
    SYNTAX  DisplayString
    ACCESS  read-write
    STATUS  mandatory
    DESCRIPTION
           "The aiSPY keypad access name for user #6.
            This can be up to 20 characters."
    ::= { aiSPYKeypad  12 }

aiSPYKeypadCode7 OBJECT-TYPE
    SYNTAX  DisplayString
    ACCESS  read-write
    STATUS  mandatory
    DESCRIPTION
           "The aiSPY keypad access code for user #7.
            This can be up to six numeric characters."
    ::= { aiSPYKeypad  13 }

aiSPYKeypadName7 OBJECT-TYPE
    SYNTAX  DisplayString
    ACCESS  read-write
    STATUS  mandatory
    DESCRIPTION
           "The aiSPY keypad access name for user #7.
            This can be up to 20 characters."
    ::= { aiSPYKeypad  14 }

aiSPYKeypadCode8 OBJECT-TYPE
    SYNTAX  DisplayString
    ACCESS  read-write
    STATUS  mandatory
    DESCRIPTION
           "The aiSPY keypad access code for user #8.
            This can be up to six numeric characters."
    ::= { aiSPYKeypad  15 }

aiSPYKeypadName8 OBJECT-TYPE
    SYNTAX  DisplayString
    ACCESS  read-write
    STATUS  mandatory
    DESCRIPTION
           "The aiSPY keypad access name for user #8.
            This can be up to 20 characters."
    ::= { aiSPYKeypad  16 }

aiSPYKeypadCode9 OBJECT-TYPE
    SYNTAX  DisplayString
    ACCESS  read-write
    STATUS  mandatory
    DESCRIPTION
           "The aiSPY keypad access code for user #9.
            This can be up to six numeric characters."
    ::= { aiSPYKeypad  17 }

aiSPYKeypadName9 OBJECT-TYPE
    SYNTAX  DisplayString
    ACCESS  read-write
    STATUS  mandatory
    DESCRIPTION
           "The aiSPY keypad access name for user #9.
            This can be up to 20 characters."
    ::= { aiSPYKeypad  18 }

aiSPYKeypadCode10 OBJECT-TYPE
    SYNTAX  DisplayString
    ACCESS  read-write
    STATUS  mandatory
    DESCRIPTION
           "The aiSPY keypad access code for user #10.
            This can be up to six numeric characters."
    ::= { aiSPYKeypad  19 }

aiSPYKeypadName10 OBJECT-TYPE
    SYNTAX  DisplayString
    ACCESS  read-write
    STATUS  mandatory
    DESCRIPTION
           "The aiSPY keypad access name for user #10.
            This can be up to 20 characters."
    ::= { aiSPYKeypad  20 }

aiSPYKeypadCode11 OBJECT-TYPE
    SYNTAX  DisplayString
    ACCESS  read-write
    STATUS  mandatory
    DESCRIPTION
           "The aiSPY keypad access code for user #11.
            This can be up to six numeric characters."
    ::= { aiSPYKeypad  21 }

aiSPYKeypadName11 OBJECT-TYPE
    SYNTAX  DisplayString
    ACCESS  read-write
    STATUS  mandatory
    DESCRIPTION
           "The aiSPY keypad access name for user #11.
            This can be up to 20 characters."
    ::= { aiSPYKeypad  22 }

aiSPYKeypadCode12 OBJECT-TYPE
    SYNTAX  DisplayString
    ACCESS  read-write
    STATUS  mandatory
    DESCRIPTION
           "The aiSPY keypad access code for user #12.
            This can be up to six numeric characters."
    ::= { aiSPYKeypad  23 }

aiSPYKeypadName12 OBJECT-TYPE
    SYNTAX  DisplayString
    ACCESS  read-write
    STATUS  mandatory
    DESCRIPTION
           "The aiSPY keypad access name for user #12.
            This can be up to 20 characters."
    ::= { aiSPYKeypad  24 }

aiSPYKeypadCode13 OBJECT-TYPE
    SYNTAX  DisplayString
    ACCESS  read-write
    STATUS  mandatory
    DESCRIPTION
           "The aiSPY keypad access code for user #13.
            This can be up to six numeric characters."
    ::= { aiSPYKeypad  25 }

aiSPYKeypadName13 OBJECT-TYPE
    SYNTAX  DisplayString
    ACCESS  read-write
    STATUS  mandatory
    DESCRIPTION
           "The aiSPY keypad access name for user #13.
            This can be up to 20 characters."
    ::= { aiSPYKeypad  26 }

aiSPYKeypadCode14 OBJECT-TYPE
    SYNTAX  DisplayString
    ACCESS  read-write
    STATUS  mandatory
    DESCRIPTION
           "The aiSPY keypad access code for user #14.
            This can be up to six numeric characters."
    ::= { aiSPYKeypad  27 }

aiSPYKeypadName14 OBJECT-TYPE
    SYNTAX  DisplayString
    ACCESS  read-write
    STATUS  mandatory
    DESCRIPTION
           "The aiSPY keypad access name for user #14.
            This can be up to 20 characters."
    ::= { aiSPYKeypad  28 }

aiSPYKeypadCode15 OBJECT-TYPE
    SYNTAX  DisplayString
    ACCESS  read-write
    STATUS  mandatory
    DESCRIPTION
           "The aiSPY keypad access code for user #15.
            This can be up to six numeric characters."
    ::= { aiSPYKeypad  29 }

aiSPYKeypadName15 OBJECT-TYPE
    SYNTAX  DisplayString
    ACCESS  read-write
    STATUS  mandatory
    DESCRIPTION
           "The aiSPY keypad access name for user #15.
            This can be up to 20 characters."
    ::= { aiSPYKeypad  30 }

aiSPYKeypadCode16 OBJECT-TYPE
    SYNTAX  DisplayString
    ACCESS  read-write
    STATUS  mandatory
    DESCRIPTION
           "The aiSPY keypad access code for user #16.
            This can be up to six numeric characters."
    ::= { aiSPYKeypad  31 }

aiSPYKeypadName16 OBJECT-TYPE
    SYNTAX  DisplayString
    ACCESS  read-write
    STATUS  mandatory
    DESCRIPTION
           "The aiSPY keypad access name for user #16.
            This can be up to 20 characters."
    ::= { aiSPYKeypad  32 }

aiSPYKeypadCode17 OBJECT-TYPE
    SYNTAX  DisplayString
    ACCESS  read-write
    STATUS  mandatory
    DESCRIPTION
           "The aiSPY keypad access code for user #17.
            This can be up to six numeric characters."
    ::= { aiSPYKeypad  33 }

aiSPYKeypadName17 OBJECT-TYPE
    SYNTAX  DisplayString
    ACCESS  read-write
    STATUS  mandatory
    DESCRIPTION
           "The aiSPY keypad access name for user #17.
            This can be up to 20 characters."
    ::= { aiSPYKeypad  34 }

aiSPYKeypadCode18 OBJECT-TYPE
    SYNTAX  DisplayString
    ACCESS  read-write
    STATUS  mandatory
    DESCRIPTION
           "The aiSPY keypad access code for user #18.
            This can be up to six numeric characters."
    ::= { aiSPYKeypad  35 }

aiSPYKeypadName18 OBJECT-TYPE
    SYNTAX  DisplayString
    ACCESS  read-write
    STATUS  mandatory
    DESCRIPTION
           "The aiSPY keypad access name for user #18.
            This can be up to 20 characters."
    ::= { aiSPYKeypad  36 }

aiSPYKeypadCode19 OBJECT-TYPE
    SYNTAX  DisplayString
    ACCESS  read-write
    STATUS  mandatory
    DESCRIPTION
           "The aiSPY keypad access code for user #19.
            This can be up to six numeric characters."
    ::= { aiSPYKeypad  37 }

aiSPYKeypadName19 OBJECT-TYPE
    SYNTAX  DisplayString
    ACCESS  read-write
    STATUS  mandatory
    DESCRIPTION
           "The aiSPY keypad access name for user #19.
            This can be up to 20 characters."
    ::= { aiSPYKeypad  38 }

aiSPYKeypadCode20 OBJECT-TYPE
    SYNTAX  DisplayString
    ACCESS  read-write
    STATUS  mandatory
    DESCRIPTION
           "The aiSPY keypad access code for user #20.
            This can be up to six numeric characters."
    ::= { aiSPYKeypad  39 }

aiSPYKeypadName20 OBJECT-TYPE
    SYNTAX  DisplayString
    ACCESS  read-write
    STATUS  mandatory
    DESCRIPTION
           "The aiSPY keypad access name for user #20.
            This can be up to 20 characters."
    ::= { aiSPYKeypad  40 }

aiSPYInputVoltage OBJECT-TYPE
    SYNTAX  INTEGER (-2147483648..2147483647)
    ACCESS  read-only
    STATUS  mandatory
    DESCRIPTION
           "The aiSPY input voltage (DC Power)."
    ::= { aiSPYSystem  4 }

aiSPYOnBattery OBJECT-TYPE
    SYNTAX  INTEGER {
    notInstalled(0),
    installed(1)
}
    ACCESS  read-write
    STATUS  mandatory
    DESCRIPTION
           "The state of use of the On Battery Alarm. When
            the State is set to installed(1), the On Battery and
            Low Battery alarms are enabled.
            This variable is stored in non-volatile memory."
    ::= { aiSPYSystem  5 }

aiSPYLowBatteryThreshold OBJECT-TYPE
    SYNTAX  INTEGER (-2147483648..2147483647)
    ACCESS  read-write
    STATUS  mandatory
    DESCRIPTION
           "The low voltage trip point for the low battery alarm.
            When the input voltage goes below this voltage, the
            Low Battery alarm is set.
            This variable is stored in non-volatile memory."
    ::= { aiSPYSystem  6 }

aiSPYAnalogAverage OBJECT-TYPE
    SYNTAX  INTEGER (0..60)
    ACCESS  read-write
    STATUS  mandatory
    DESCRIPTION
           "This is the analog averaging duration in seconds.
            The analog input readings are averaged for this time
            period before updating. This value must be set to
            1,2,3,4,5,6,10,15,20,30 or 60 seconds.
            This variable is stored in non-volatile memory."
    ::= { aiSPYSystem  7 }

aiSPYInputs OBJECT IDENTIFIER ::= { aiSPY  3 }

aiSPYInput1 OBJECT IDENTIFIER ::= { aiSPYInputs 1 }

aiSPYInput1State OBJECT-TYPE
    SYNTAX  INTEGER {
    notinstalled(1),
    analog-4to20-installed(2)
}
    ACCESS  read-write
    STATUS  mandatory
    DESCRIPTION
           "The state of use of Input Number 1. When a sensor is
            connected to Input 1 set State to installed(2) to
            indicate that the value of aiSPYReading1 is valid.
            When no sensor is connected to Input 1 set
            State to notInstalled(1) to indicate that the value of
            aiSPYReading1 may not be valid.
            This variable is stored in non-volatile memory."
    ::= { aiSPYInput1  1 }

aiSPYInput1Reading OBJECT-TYPE
    SYNTAX  INTEGER (-2147483648..2147483647)
    ACCESS  read-only
    STATUS  mandatory
    DESCRIPTION
           "The reading for sensor 1.
            If the input is digital, the reading will be 1 (active) or
            0 (inactive)"
    ::= { aiSPYInput1  2 }

aiSPYInput1Gain OBJECT-TYPE
    SYNTAX  INTEGER (-2147483648..2147483647)
    ACCESS  read-write
    STATUS  mandatory
    DESCRIPTION
           "A correction gain associated with the sensor variable.
            The value of gain is multiplied by the value from
            Input Sensor Number 1 to obtain the value of
            the Input1 variable. The gain variable is stored in
            non-volatile memory."
    ::= { aiSPYInput1  3 }

aiSPYInput1Offset OBJECT-TYPE
    SYNTAX  INTEGER (-2147483648..2147483647)
    ACCESS  read-write
    STATUS  mandatory
    DESCRIPTION
           "A correction Offset associated with the sensor variable.
            The value of Offset is added to the value from
            Input Sensor Number 1 to obtain the value of
            the Input1 variable. The Offset variable is stored in
            non-volatile memory."
    ::= { aiSPYInput1  4 }

aiSPYInput1Label OBJECT-TYPE
    SYNTAX  DisplayString
    ACCESS  read-write
    STATUS  mandatory
    DESCRIPTION
           "A user-defined text string associated with Input Number 1.
            The text string is stored in non-volatile memory."
    ::= { aiSPYInput1  5 }

aiSPYInput1UOM OBJECT-TYPE
    SYNTAX  DisplayString
    ACCESS  read-write
    STATUS  mandatory
    DESCRIPTION
           "A user-defined text string associated with Input Number 1.
            The text string is stored in non-volatile memory."
    ::= { aiSPYInput1  6 }

aiSPYInput1HighLimit OBJECT-TYPE
    SYNTAX  INTEGER (-2147483648..2147483647)
    ACCESS  read-write
    STATUS  mandatory
    DESCRIPTION
           "When input 1 reaches or exceeds this value a trap will
            be generated signifying a high alarm condition at
            sensor 1.
            The HighLimit variable is stored in non-volatile memory."
    ::= { aiSPYInput1  7 }

aiSPYInput1LowLimit OBJECT-TYPE
    SYNTAX  INTEGER (-2147483648..2147483647)
    ACCESS  read-write
    STATUS  mandatory
    DESCRIPTION
           "When input 1 reaches or goes below this value a trap will
            be generated signifying a low alarm condition at sensor 1.
            The LowLimit variable is stored in non-volatile memory."
    ::= { aiSPYInput1  8 }

aiSPYInput1RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { aiSPYInput1  9 }

aiSPYInput1Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { aiSPYInput1  10 }

aiSPYInput1RTNDelay OBJECT-TYPE
    SYNTAX  INTEGER (0..600)
    ACCESS  read-write
    STATUS  mandatory
    DESCRIPTION
           "The number of seconds a cleared alarm for this input must
            be present before annunication. The range of this
            setting is 0..600.
            This variable is stored in non-volatile memory."
    ::= { aiSPYInput1  11 }


aiSPYInput1Hysteresis OBJECT-TYPE
    SYNTAX  INTEGER (0..2147483647)
    ACCESS  read-write
    STATUS  mandatory
    DESCRIPTION
           "The value of alarm hysteresis for this input.
            The input reading must decrease or increase by this
            value before the alarm will clear.
            This variable is stored in non-volatile memory."
    ::= { aiSPYInput1  12 }

aiSPYInput2 OBJECT IDENTIFIER ::= { aiSPYInputs 2 }

aiSPYInput2State OBJECT-TYPE
    SYNTAX  INTEGER {
    notInstalled(1),
    analog-4to20-installed(2)
}
    ACCESS  read-write
    STATUS  mandatory
    DESCRIPTION
           "The state of use of Input Number 2. When a sensor is
            connected to Input 2 set State to installed(2) to
            indicate that the value of aiSPYReading2 is valid.
            When no sensor is connected to Input 2 set
            State to notInstalled(1) to indicate that the value of
            aiSPYReading2 may not be valid.
            This variable is stored in non-volatile memory."
    ::= { aiSPYInput2  1 }

aiSPYInput2Reading OBJECT-TYPE
    SYNTAX  INTEGER (-2147483648..2147483647)
    ACCESS  read-only
    STATUS  mandatory
    DESCRIPTION
           "The reading for sensor 2.
            If the input is digital, the reading will be 1 (active) or
            0 (inactive)"
    ::= { aiSPYInput2  2 }

aiSPYInput2Gain OBJECT-TYPE
    SYNTAX  INTEGER (-2147483648..2147483647)
    ACCESS  read-write
    STATUS  mandatory
    DESCRIPTION
           "A correction gain associated with the sensor variable.
            The value of gain is multiplied by the value from
            Input Sensor Number 2 to obtain the value of
            the Input2 variable. The gain variable is stored in
            non-volatile memory."
    ::= { aiSPYInput2  3 }

aiSPYInput2Offset OBJECT-TYPE
    SYNTAX  INTEGER (-2147483648..2147483647)
    ACCESS  read-write
    STATUS  mandatory
    DESCRIPTION
           "A correction Offset associated with the sensor variable.
            The value of Offset is added to the value from
            Input Sensor Number 2 to obtain the value of
            the Input2 variable. The Offset variable is stored in
            non-volatile memory."
    ::= { aiSPYInput2  4 }

aiSPYInput2Label OBJECT-TYPE
    SYNTAX  DisplayString
    ACCESS  read-write
    STATUS  mandatory
    DESCRIPTION
           "A user-defined text string associated with Input Number 2.
            The text string is stored in non-volatile memory."
    ::= { aiSPYInput2  5 }

aiSPYInput2UOM OBJECT-TYPE
    SYNTAX  DisplayString
    ACCESS  read-write
    STATUS  mandatory
    DESCRIPTION
           "A user-defined text string associated with Input Number 2.
            The text string is stored in non-volatile memory."
    ::= { aiSPYInput2  6 }

aiSPYInput2HighLimit OBJECT-TYPE
    SYNTAX  INTEGER (-2147483648..2147483647)
    ACCESS  read-write
    STATUS  mandatory
    DESCRIPTION
           "When input 2 reaches or exceeds this value a trap will
            be generated signifying a high alarm condition at
            sensor 2.
            The HighLimit variable is stored in non-volatile memory."
    ::= { aiSPYInput2  7 }

aiSPYInput2LowLimit OBJECT-TYPE
    SYNTAX  INTEGER (-2147483648..2147483647)
    ACCESS  read-write
    STATUS  mandatory
    DESCRIPTION
           "When input 2 reaches or goes below this value a trap will
            be generated signifying a low alarm condition at sensor 2.
            The LowLimit variable is stored in non-volatile memory."
    ::= { aiSPYInput2  8 }

aiSPYInput2RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { aiSPYInput2  9 }

aiSPYInput2Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { aiSPYInput2  10 }

aiSPYInput2RTNDelay OBJECT-TYPE
    SYNTAX  INTEGER (0..600)
    ACCESS  read-write
    STATUS  mandatory
    DESCRIPTION
           "The number of seconds a cleared alarm for this input must
            be present before annunication. The range of this
            setting is 0..600.
            This variable is stored in non-volatile memory."
    ::= { aiSPYInput2  11 }


aiSPYInput2Hysteresis OBJECT-TYPE
    SYNTAX  INTEGER (0..2147483647)
    ACCESS  read-write
    STATUS  mandatory
    DESCRIPTION
           "The value of alarm hysteresis for this input.
            The input reading must decrease or increase by this
            value before the alarm will clear.
            This variable is stored in non-volatile memory."
    ::= { aiSPYInput2  12 }

aiSPYInput3 OBJECT IDENTIFIER ::= { aiSPYInputs 3 }

aiSPYInput3State OBJECT-TYPE
    SYNTAX  INTEGER {
    notInstalled(1),
    analog-4to20-installed(2)
}
    ACCESS  read-write
    STATUS  mandatory
    DESCRIPTION
           "The state of use of Input Number 3. When a sensor is
            connected to Input 3 set State to installed(2) to
            indicate that the value of aiSPYReading3 is valid.
            When no sensor is connected to Input 3 set
            State to notInstalled(1) to indicate that the value of
            aiSPYReading3 may not be valid.
            This variable is stored in non-volatile memory."
    ::= { aiSPYInput3  1 }

aiSPYInput3Reading OBJECT-TYPE
    SYNTAX  INTEGER (-2147483648..2147483647)
    ACCESS  read-only
    STATUS  mandatory
    DESCRIPTION
           "The reading for sensor 3.
            If the input is digital, the reading will be 1 (active) or
            0 (inactive)"
    ::= { aiSPYInput3  2 }

aiSPYInput3Gain OBJECT-TYPE
    SYNTAX  INTEGER (-2147483648..2147483647)
    ACCESS  read-write
    STATUS  mandatory
    DESCRIPTION
           "A correction gain associated with the sensor variable.
            The value of gain is multiplied by the value from
            Input Sensor Number 3 to obtain the value of
            the Input3 variable. The gain variable is stored in
            non-volatile memory."
    ::= { aiSPYInput3  3 }

aiSPYInput3Offset OBJECT-TYPE
    SYNTAX  INTEGER (-2147483648..2147483647)
    ACCESS  read-write
    STATUS  mandatory
    DESCRIPTION
           "A correction Offset associated with the sensor variable.
            The value of Offset is added to the value from
            Input Sensor Number 3 to obtain the value of
            the Input3 variable. The Offset variable is stored in
            non-volatile memory."
    ::= { aiSPYInput3  4 }

aiSPYInput3Label OBJECT-TYPE
    SYNTAX  DisplayString
    ACCESS  read-write
    STATUS  mandatory
    DESCRIPTION
           "A user-defined text string associated with Input Number 3.
            The text string is stored in non-volatile memory."
    ::= { aiSPYInput3  5 }

aiSPYInput3UOM OBJECT-TYPE
    SYNTAX  DisplayString
    ACCESS  read-write
    STATUS  mandatory
    DESCRIPTION
           "A user-defined text string associated with Input Number 3.
            The text string is stored in non-volatile memory."
    ::= { aiSPYInput3  6 }

aiSPYInput3HighLimit OBJECT-TYPE
    SYNTAX  INTEGER (-2147483648..2147483647)
    ACCESS  read-write
    STATUS  mandatory
    DESCRIPTION
           "When input 3 reaches or exceeds this value a trap will
            be generated signifying a high alarm condition at
            sensor 3.
            The HighLimit variable is stored in non-volatile memory."
    ::= { aiSPYInput3  7 }

aiSPYInput3LowLimit OBJECT-TYPE
    SYNTAX  INTEGER (-2147483648..2147483647)
    ACCESS  read-write
    STATUS  mandatory
    DESCRIPTION
           "When input 3 reaches or goes below this value a trap will
            be generated signifying a low alarm condition at sensor 3.
            The LowLimit variable is stored in non-volatile memory."
    ::= { aiSPYInput3  8 }

aiSPYInput3RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { aiSPYInput3  9 }

aiSPYInput3Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { aiSPYInput3  10 }

aiSPYInput3RTNDelay OBJECT-TYPE
    SYNTAX  INTEGER (0..600)
    ACCESS  read-write
    STATUS  mandatory
    DESCRIPTION
           "The number of seconds a cleared alarm for this input must
            be present before annunication. The range of this
            setting is 0..600.
            This variable is stored in non-volatile memory."
    ::= { aiSPYInput3  11 }


aiSPYInput3Hysteresis OBJECT-TYPE
    SYNTAX  INTEGER (0..2147483647)
    ACCESS  read-write
    STATUS  mandatory
    DESCRIPTION
           "The value of alarm hysteresis for this input.
            The input reading must decrease or increase by this
            value before the alarm will clear.
            This variable is stored in non-volatile memory."
    ::= { aiSPYInput3  12 }

aiSPYInput4 OBJECT IDENTIFIER ::= { aiSPYInputs 4 }

aiSPYInput4State OBJECT-TYPE
    SYNTAX  INTEGER {
    notInstalled(1),
    analog-4to20-installed(2)
}
    ACCESS  read-write
    STATUS  mandatory
    DESCRIPTION
           "The state of use of Input Number 4. When a sensor is
            connected to Input 4 set State to installed(2) to
            indicate that the value of aiSPYReading4 is valid.
            When no sensor is connected to Input 4 set
            State to notInstalled(1) to indicate that the value of
            aiSPYReading4 may not be valid.
            This variable is stored in non-volatile memory."
    ::= { aiSPYInput4  1 }

aiSPYInput4Reading OBJECT-TYPE
    SYNTAX  INTEGER (-2147483648..2147483647)
    ACCESS  read-only
    STATUS  mandatory
    DESCRIPTION
           "The reading for sensor 4.
            If the input is digital, the reading will be 1 (active) or
            0 (inactive)"
    ::= { aiSPYInput4  2 }

aiSPYInput4Gain OBJECT-TYPE
    SYNTAX  INTEGER (-2147483648..2147483647)
    ACCESS  read-write
    STATUS  mandatory
    DESCRIPTION
           "A correction gain associated with the sensor variable.
            The value of gain is multiplied by the value from
            Input Sensor Number 4 to obtain the value of
            the Input4 variable. The gain variable is stored in
            non-volatile memory."
    ::= { aiSPYInput4  3 }

aiSPYInput4Offset OBJECT-TYPE
    SYNTAX  INTEGER (-2147483648..2147483647)
    ACCESS  read-write
    STATUS  mandatory
    DESCRIPTION
           "A correction Offset associated with the sensor variable.
            The value of Offset is added to the value from
            Input Sensor Number 4 to obtain the value of
            the Input4 variable. The Offset variable is stored in
            non-volatile memory."
    ::= { aiSPYInput4  4 }

aiSPYInput4Label OBJECT-TYPE
    SYNTAX  DisplayString
    ACCESS  read-write
    STATUS  mandatory
    DESCRIPTION
           "A user-defined text string associated with Input Number 4.
            The text string is stored in non-volatile memory."
    ::= { aiSPYInput4  5 }

aiSPYInput4UOM OBJECT-TYPE
    SYNTAX  DisplayString
    ACCESS  read-write
    STATUS  mandatory
    DESCRIPTION
           "A user-defined text string associated with Input Number 4.
            The text string is stored in non-volatile memory."
    ::= { aiSPYInput4  6 }

aiSPYInput4HighLimit OBJECT-TYPE
    SYNTAX  INTEGER (-2147483648..2147483647)
    ACCESS  read-write
    STATUS  mandatory
    DESCRIPTION
           "When input 4 reaches or exceeds this value a trap will
            be generated signifying a high alarm condition at
            sensor 4.
            The HighLimit variable is stored in non-volatile memory."
    ::= { aiSPYInput4  7 }

aiSPYInput4LowLimit OBJECT-TYPE
    SYNTAX  INTEGER (-2147483648..2147483647)
    ACCESS  read-write
    STATUS  mandatory
    DESCRIPTION
           "When input 4 reaches or goes below this value a trap will
            be generated signifying a low alarm condition at sensor 4.
            The LowLimit variable is stored in non-volatile memory."
    ::= { aiSPYInput4  8 }

aiSPYInput4RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { aiSPYInput4  9 }

aiSPYInput4Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { aiSPYInput4  10 }

aiSPYInput4RTNDelay OBJECT-TYPE
    SYNTAX  INTEGER (0..600)
    ACCESS  read-write
    STATUS  mandatory
    DESCRIPTION
           "The number of seconds a cleared alarm for this input must
            be present before annunication. The range of this
            setting is 0..600.
            This variable is stored in non-volatile memory."
    ::= { aiSPYInput4  11 }


aiSPYInput4Hysteresis OBJECT-TYPE
    SYNTAX  INTEGER (0..2147483647)
    ACCESS  read-write
    STATUS  mandatory
    DESCRIPTION
           "The value of alarm hysteresis for this input.
            The input reading must decrease or increase by this
            value before the alarm will clear.
            This variable is stored in non-volatile memory."
    ::= { aiSPYInput4  12 }

aiSPYInput5 OBJECT IDENTIFIER ::= { aiSPYInputs 5 }

aiSPYInput5State OBJECT-TYPE
    SYNTAX  INTEGER {
    notInstalled(1),
    analog-4to20-installed(2)
}
    ACCESS  read-write
    STATUS  mandatory
    DESCRIPTION
           "The state of use of Input Number 5. When a sensor is
            connected to Input 5 set State to installed(2) to
            indicate that the value of aiSPYReading4 is valid.
            When no sensor is connected to Input 5 set
            State to notInstalled(1) to indicate that the value of
            aiSPYReading5 may not be valid.
            This variable is stored in non-volatile memory."
    ::= { aiSPYInput5  1 }

aiSPYInput5Reading OBJECT-TYPE
    SYNTAX  INTEGER (-2147483648..2147483647)
    ACCESS  read-only
    STATUS  mandatory
    DESCRIPTION
           "The reading for sensor 5.
            If the input is digital, the reading will be 1 (active) or
            0 (inactive)"
    ::= { aiSPYInput5  2 }

aiSPYInput5Gain OBJECT-TYPE
    SYNTAX  INTEGER (-2147483648..2147483647)
    ACCESS  read-write
    STATUS  mandatory
    DESCRIPTION
           "A correction gain associated with the sensor variable.
            The value of gain is multiplied by the value from
            Input Sensor Number 5 to obtain the value of
            the Input5 variable. The gain variable is stored in
            non-volatile memory."
    ::= { aiSPYInput5  3 }

aiSPYInput5Offset OBJECT-TYPE
    SYNTAX  INTEGER (-2147483648..2147483647)
    ACCESS  read-write
    STATUS  mandatory
    DESCRIPTION
           "A correction Offset associated with the sensor variable.
            The value of Offset is added to the value from
            Input Sensor Number 5 to obtain the value of
            the Input5 variable. The Offset variable is stored in
            non-volatile memory."
    ::= { aiSPYInput5  4 }

aiSPYInput5Label OBJECT-TYPE
    SYNTAX  DisplayString
    ACCESS  read-write
    STATUS  mandatory
    DESCRIPTION
           "A user-defined text string associated with Input Number 5.
            The text string is stored in non-volatile memory."
    ::= { aiSPYInput5  5 }

aiSPYInput5UOM OBJECT-TYPE
    SYNTAX  DisplayString
    ACCESS  read-write
    STATUS  mandatory
    DESCRIPTION
           "A user-defined text string associated with Input Number 5.
            The text string is stored in non-volatile memory."
    ::= { aiSPYInput5  6 }

aiSPYInput5HighLimit OBJECT-TYPE
    SYNTAX  INTEGER (-2147483648..2147483647)
    ACCESS  read-write
    STATUS  mandatory
    DESCRIPTION
           "When input 5 reaches or exceeds this value a trap will
            be generated signifying a high alarm condition at
            sensor 5.
            The HighLimit variable is stored in non-volatile memory."
    ::= { aiSPYInput5  7 }

aiSPYInput5LowLimit OBJECT-TYPE
    SYNTAX  INTEGER (-2147483648..2147483647)
    ACCESS  read-write
    STATUS  mandatory
    DESCRIPTION
           "When input 5 reaches or goes below this value a trap will
            be generated signifying a low alarm condition at sensor 5.
            The LowLimit variable is stored in non-volatile memory."
    ::= { aiSPYInput5  8 }

aiSPYInput5RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { aiSPYInput5  9 }

aiSPYInput5Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { aiSPYInput5  10 }

aiSPYInput5RTNDelay OBJECT-TYPE
    SYNTAX  INTEGER (0..600)
    ACCESS  read-write
    STATUS  mandatory
    DESCRIPTION
           "The number of seconds a cleared alarm for this input must
            be present before annunication. The range of this
            setting is 0..600.
            This variable is stored in non-volatile memory."
    ::= { aiSPYInput5  11 }


aiSPYInput5Hysteresis OBJECT-TYPE
    SYNTAX  INTEGER (0..2147483647)
    ACCESS  read-write
    STATUS  mandatory
    DESCRIPTION
           "The value of alarm hysteresis for this input.
            The input reading must decrease or increase by this
            value before the alarm will clear.
            This variable is stored in non-volatile memory."
    ::= { aiSPYInput5  12 }

aiSPYInput6 OBJECT IDENTIFIER ::= { aiSPYInputs 6 }

aiSPYInput6State OBJECT-TYPE
    SYNTAX  INTEGER {
    notInstalled(1),
    analog-4to20-installed(2)
}
    ACCESS  read-write
    STATUS  mandatory
    DESCRIPTION
           "The state of use of Input Number 6. When a sensor is
            connected to Input 6 set State to installed(2) to
            indicate that the value of aiSPYReading6 is valid.
            When no sensor is connected to Input 6 set
            State to notInstalled(1) to indicate that the value of
            aiSPYReading6 may not be valid.
            This variable is stored in non-volatile memory."
    ::= { aiSPYInput6  1 }

aiSPYInput6Reading OBJECT-TYPE
    SYNTAX  INTEGER (-2147483648..2147483647)
    ACCESS  read-only
    STATUS  mandatory
    DESCRIPTION
           "The reading for sensor 6.
            If the input is digital, the reading will be 1 (active) or
            0 (inactive)"
    ::= { aiSPYInput6  2 }

aiSPYInput6Gain OBJECT-TYPE
    SYNTAX  INTEGER (-2147483648..2147483647)
    ACCESS  read-write
    STATUS  mandatory
    DESCRIPTION
           "A correction gain associated with the sensor variable.
            The value of gain is multiplied by the value from
            Input Sensor Number 6 to obtain the value of
            the Input6 variable. The gain variable is stored in
            non-volatile memory."
    ::= { aiSPYInput6  3 }

aiSPYInput6Offset OBJECT-TYPE
    SYNTAX  INTEGER (-2147483648..2147483647)
    ACCESS  read-write
    STATUS  mandatory
    DESCRIPTION
           "A correction Offset associated with the sensor variable.
            The value of Offset is added to the value from
            Input Sensor Number 6 to obtain the value of
            the Input6 variable. The Offset variable is stored in
            non-volatile memory."
    ::= { aiSPYInput6  4 }

aiSPYInput6Label OBJECT-TYPE
    SYNTAX  DisplayString
    ACCESS  read-write
    STATUS  mandatory
    DESCRIPTION
           "A user-defined text string associated with Input Number 6.
            The text string is stored in non-volatile memory."
    ::= { aiSPYInput6  5 }

aiSPYInput6UOM OBJECT-TYPE
    SYNTAX  DisplayString
    ACCESS  read-write
    STATUS  mandatory
    DESCRIPTION
           "A user-defined text string associated with Input Number 6.
            The text string is stored in non-volatile memory."
    ::= { aiSPYInput6  6 }

aiSPYInput6HighLimit OBJECT-TYPE
    SYNTAX  INTEGER (-2147483648..2147483647)
    ACCESS  read-write
    STATUS  mandatory
    DESCRIPTION
           "When input 6 reaches or exceeds this value a trap will
            be generated signifying a high alarm condition at
            sensor 6.
            The HighLimit variable is stored in non-volatile memory."
    ::= { aiSPYInput6  7 }

aiSPYInput6LowLimit OBJECT-TYPE
    SYNTAX  INTEGER (-2147483648..2147483647)
    ACCESS  read-write
    STATUS  mandatory
    DESCRIPTION
           "When input 6 reaches or goes below this value a trap will
            be generated signifying a low alarm condition at sensor 6.
            The LowLimit variable is stored in non-volatile memory."
    ::= { aiSPYInput6  8 }

aiSPYInput6RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { aiSPYInput6  9 }

aiSPYInput6Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { aiSPYInput6  10 }

aiSPYInput6RTNDelay OBJECT-TYPE
    SYNTAX  INTEGER (0..600)
    ACCESS  read-write
    STATUS  mandatory
    DESCRIPTION
           "The number of seconds a cleared alarm for this input must
            be present before annunication. The range of this
            setting is 0..600.
            This variable is stored in non-volatile memory."
    ::= { aiSPYInput6  11 }


aiSPYInput6Hysteresis OBJECT-TYPE
    SYNTAX  INTEGER (0..2147483647)
    ACCESS  read-write
    STATUS  mandatory
    DESCRIPTION
           "The value of alarm hysteresis for this input.
            The input reading must decrease or increase by this
            value before the alarm will clear.
            This variable is stored in non-volatile memory."
    ::= { aiSPYInput6  12 }

aiSPYInput7 OBJECT IDENTIFIER ::= { aiSPYInputs 7 }

aiSPYInput7State OBJECT-TYPE
    SYNTAX  INTEGER {
    notInstalled(1),
    analog-4to20-installed(2)
}
    ACCESS  read-write
    STATUS  mandatory
    DESCRIPTION
           "The state of use of Input Number 7. When a sensor is
            connected to Input 7 set State to installed(2) to
            indicate that the value of aiSPYReading4 is valid.
            When no sensor is connected to Input 7 set
            State to notInstalled(1) to indicate that the value of
            aiSPYReading7 may not be valid.
            This variable is stored in non-volatile memory."
    ::= { aiSPYInput7  1 }

aiSPYInput7Reading OBJECT-TYPE
    SYNTAX  INTEGER (-2147483648..2147483647)
    ACCESS  read-only
    STATUS  mandatory
    DESCRIPTION
           "The reading for sensor 7.
            If the input is digital, the reading will be 1 (active) or
            0 (inactive)"
    ::= { aiSPYInput7  2 }

aiSPYInput7Gain OBJECT-TYPE
    SYNTAX  INTEGER (-2147483648..2147483647)
    ACCESS  read-write
    STATUS  mandatory
    DESCRIPTION
           "A correction gain associated with the sensor variable.
            The value of gain is multiplied by the value from
            Input Sensor Number 7 to obtain the value of
            the Input7 variable. The gain variable is stored in
            non-volatile memory."
    ::= { aiSPYInput7  3 }

aiSPYInput7Offset OBJECT-TYPE
    SYNTAX  INTEGER (-2147483648..2147483647)
    ACCESS  read-write
    STATUS  mandatory
    DESCRIPTION
           "A correction Offset associated with the sensor variable.
            The value of Offset is added to the value from
            Input Sensor Number 7 to obtain the value of
            the Input7 variable. The Offset variable is stored in
            non-volatile memory."
    ::= { aiSPYInput7  4 }

aiSPYInput7Label OBJECT-TYPE
    SYNTAX  DisplayString
    ACCESS  read-write
    STATUS  mandatory
    DESCRIPTION
           "A user-defined text string associated with Input Number 7.
            The text string is stored in non-volatile memory."
    ::= { aiSPYInput7  5 }

aiSPYInput7UOM OBJECT-TYPE
    SYNTAX  DisplayString
    ACCESS  read-write
    STATUS  mandatory
    DESCRIPTION
           "A user-defined text string associated with Input Number 7.
            The text string is stored in non-volatile memory."
    ::= { aiSPYInput7  6 }

aiSPYInput7HighLimit OBJECT-TYPE
    SYNTAX  INTEGER (-2147483648..2147483647)
    ACCESS  read-write
    STATUS  mandatory
    DESCRIPTION
           "When input 7 reaches or exceeds this value a trap will
            be generated signifying a high alarm condition at
            sensor 7.
            The HighLimit variable is stored in non-volatile memory."
    ::= { aiSPYInput7  7 }

aiSPYInput7LowLimit OBJECT-TYPE
    SYNTAX  INTEGER (-2147483648..2147483647)
    ACCESS  read-write
    STATUS  mandatory
    DESCRIPTION
           "When input 7 reaches or goes below this value a trap will
            be generated signifying a low alarm condition at sensor 7.
            The LowLimit variable is stored in non-volatile memory."
    ::= { aiSPYInput7  8 }

aiSPYInput7RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { aiSPYInput7  9 }

aiSPYInput7Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { aiSPYInput7  10 }

aiSPYInput7RTNDelay OBJECT-TYPE
    SYNTAX  INTEGER (0..600)
    ACCESS  read-write
    STATUS  mandatory
    DESCRIPTION
           "The number of seconds a cleared alarm for this input must
            be present before annunication. The range of this
            setting is 0..600.
            This variable is stored in non-volatile memory."
    ::= { aiSPYInput7  11 }


aiSPYInput7Hysteresis OBJECT-TYPE
    SYNTAX  INTEGER (0..2147483647)
    ACCESS  read-write
    STATUS  mandatory
    DESCRIPTION
           "The value of alarm hysteresis for this input.
            The input reading must decrease or increase by this
            value before the alarm will clear.
            This variable is stored in non-volatile memory."
    ::= { aiSPYInput7  12 }

aiSPYInput8 OBJECT IDENTIFIER ::= { aiSPYInputs 8 }

aiSPYInput8State OBJECT-TYPE
    SYNTAX  INTEGER {
    notInstalled(1),
    analog-4to20-installed(2)
}
    ACCESS  read-write
    STATUS  mandatory
    DESCRIPTION
           "The state of use of Input Number 8. When a sensor is
            connected to Input 8 set State to installed(2) to
            indicate that the value of aiSPYReading8 is valid.
            When no sensor is connected to Input 8 set
            State to notInstalled(1) to indicate that the value of
            aiSPYReading8 may not be valid.
            This variable is stored in non-volatile memory."
    ::= { aiSPYInput8  1 }

aiSPYInput8Reading OBJECT-TYPE
    SYNTAX  INTEGER (-2147483648..2147483647)
    ACCESS  read-only
    STATUS  mandatory
    DESCRIPTION
           "The reading for sensor 8.
            If the input is digital, the reading will be 1 (active) or
            0 (inactive)"
    ::= { aiSPYInput8  2 }

aiSPYInput8Gain OBJECT-TYPE
    SYNTAX  INTEGER (-2147483648..2147483647)
    ACCESS  read-write
    STATUS  mandatory
    DESCRIPTION
           "A correction gain associated with the sensor variable.
            The value of gain is multiplied by the value from
            Input Sensor Number 8 to obtain the value of
            the Input8 variable. The gain variable is stored in
            non-volatile memory."
    ::= { aiSPYInput8  3 }

aiSPYInput8Offset OBJECT-TYPE
    SYNTAX  INTEGER (-2147483648..2147483647)
    ACCESS  read-write
    STATUS  mandatory
    DESCRIPTION
           "A correction Offset associated with the sensor variable.
            The value of Offset is added to the value from
            Input Sensor Number 8 to obtain the value of
            the Input8 variable. The Offset variable is stored in
            non-volatile memory."
    ::= { aiSPYInput8  4 }

aiSPYInput8Label OBJECT-TYPE
    SYNTAX  DisplayString
    ACCESS  read-write
    STATUS  mandatory
    DESCRIPTION
           "A user-defined text string associated with Input Number 8.
            The text string is stored in non-volatile memory."
    ::= { aiSPYInput8  5 }

aiSPYInput8UOM OBJECT-TYPE
    SYNTAX  DisplayString
    ACCESS  read-write
    STATUS  mandatory
    DESCRIPTION
           "A user-defined text string associated with Input Number 8.
            The text string is stored in non-volatile memory."
    ::= { aiSPYInput8  6 }

aiSPYInput8HighLimit OBJECT-TYPE
    SYNTAX  INTEGER (-2147483648..2147483647)
    ACCESS  read-write
    STATUS  mandatory
    DESCRIPTION
           "When input 8 reaches or exceeds this value a trap will
            be generated signifying a high alarm condition at
            sensor 8.
            The HighLimit variable is stored in non-volatile memory."
    ::= { aiSPYInput8  7 }

aiSPYInput8LowLimit OBJECT-TYPE
    SYNTAX  INTEGER (-2147483648..2147483647)
    ACCESS  read-write
    STATUS  mandatory
    DESCRIPTION
           "When input 8 reaches or goes below this value a trap will
            be generated signifying a low alarm condition at sensor 8.
            The LowLimit variable is stored in non-volatile memory."
    ::= { aiSPYInput8  8 }

aiSPYInput8RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { aiSPYInput8  9 }

aiSPYInput8Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { aiSPYInput8  10 }

aiSPYInput8RTNDelay OBJECT-TYPE
    SYNTAX  INTEGER (0..600)
    ACCESS  read-write
    STATUS  mandatory
    DESCRIPTION
           "The number of seconds a cleared alarm for this input must
            be present before annunication. The range of this
            setting is 0..600.
            This variable is stored in non-volatile memory."
    ::= { aiSPYInput8  11 }


aiSPYInput8Hysteresis OBJECT-TYPE
    SYNTAX  INTEGER (0..2147483647)
    ACCESS  read-write
    STATUS  mandatory
    DESCRIPTION
           "The value of alarm hysteresis for this input.
            The input reading must decrease or increase by this
            value before the alarm will clear.
            This variable is stored in non-volatile memory."
    ::= { aiSPYInput8  12 }

aiSPYInput9 OBJECT IDENTIFIER ::= { aiSPYInputs 25 }

aiSPYInput9State OBJECT-TYPE
    SYNTAX  INTEGER {
    notInstalled(1),
    digital-no-installed(3),
    digital-nc-installed(4)
}
    ACCESS  read-write
    STATUS  mandatory
    DESCRIPTION
           "The state of use of Input Number 9.
            This variable is stored in non-volatile memory."
    ::= { aiSPYInput9  1 }

aiSPYInput9Reading OBJECT-TYPE
    SYNTAX  INTEGER (0..1)
    ACCESS  read-only
    STATUS  mandatory
    DESCRIPTION
           "The reading for input 9.
            The reading will be 1 (active) or 0 (inactive)"
    ::= { aiSPYInput9  2 }

aiSPYInput9Label OBJECT-TYPE
    SYNTAX  DisplayString
    ACCESS  read-write
    STATUS  mandatory
    DESCRIPTION
           "A user-defined text string associated with Input Number 9.
            The text string is stored in non-volatile memory."
    ::= { aiSPYInput9  3 }

aiSPYInput9RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { aiSPYInput9  4 }

aiSPYInput9Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { aiSPYInput9  5 }

aiSPYInput9RTNDelay OBJECT-TYPE
    SYNTAX  INTEGER (0..600)
    ACCESS  read-write
    STATUS  mandatory
    DESCRIPTION
           "The number of seconds a cleared alarm for this input must
            be present before annunication. The range of this
            setting is 0..600.
            This variable is stored in non-volatile memory."
    ::= { aiSPYInput9  6 }


aiSPYInput10 OBJECT IDENTIFIER ::= { aiSPYInputs 26 }

aiSPYInput10State OBJECT-TYPE
    SYNTAX  INTEGER {
    notInstalled(1),
    digital-no-installed(3),
    digital-nc-installed(4)
}
    ACCESS  read-write
    STATUS  mandatory
    DESCRIPTION
           "The state of use of Input Number 10.
            This variable is stored in non-volatile memory."
    ::= { aiSPYInput10  1 }

aiSPYInput10Reading OBJECT-TYPE
    SYNTAX  INTEGER (0..1)
    ACCESS  read-only
    STATUS  mandatory
    DESCRIPTION
           "The reading for input 10.
            The reading will be 1 (active) or 0 (inactive)"
    ::= { aiSPYInput10  2 }

aiSPYInput10Label OBJECT-TYPE
    SYNTAX  DisplayString
    ACCESS  read-write
    STATUS  mandatory
    DESCRIPTION
           "A user-defined text string associated with Input Number 10.
            The text string is stored in non-volatile memory."
    ::= { aiSPYInput10  3 }

aiSPYInput10RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { aiSPYInput10  4 }

aiSPYInput10Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { aiSPYInput10  5 }

aiSPYInput10RTNDelay OBJECT-TYPE
    SYNTAX  INTEGER (0..600)
    ACCESS  read-write
    STATUS  mandatory
    DESCRIPTION
           "The number of seconds a cleared alarm for this input must
            be present before annunication. The range of this
            setting is 0..600.
            This variable is stored in non-volatile memory."
    ::= { aiSPYInput10  6 }


aiSPYInput11 OBJECT IDENTIFIER ::= { aiSPYInputs 27 }

aiSPYInput11State OBJECT-TYPE
    SYNTAX  INTEGER {
    notInstalled(1),
    digital-no-installed(3),
    digital-nc-installed(4)
}
    ACCESS  read-write
    STATUS  mandatory
    DESCRIPTION
           "The state of use of Input Number 11.
            This variable is stored in non-volatile memory."
    ::= { aiSPYInput11  1 }

aiSPYInput11Reading OBJECT-TYPE
    SYNTAX  INTEGER (0..1)
    ACCESS  read-only
    STATUS  mandatory
    DESCRIPTION
           "The reading for input 11.
            The reading will be 1 (active) or 0 (inactive)"
    ::= { aiSPYInput11  2 }

aiSPYInput11Label OBJECT-TYPE
    SYNTAX  DisplayString
    ACCESS  read-write
    STATUS  mandatory
    DESCRIPTION
           "A user-defined text string associated with Input Number 11.
            The text string is stored in non-volatile memory."
    ::= { aiSPYInput11  3 }

aiSPYInput11RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { aiSPYInput11  4 }

aiSPYInput11Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { aiSPYInput11  5 }

aiSPYInput11RTNDelay OBJECT-TYPE
    SYNTAX  INTEGER (0..600)
    ACCESS  read-write
    STATUS  mandatory
    DESCRIPTION
           "The number of seconds a cleared alarm for this input must
            be present before annunication. The range of this
            setting is 0..600.
            This variable is stored in non-volatile memory."
    ::= { aiSPYInput11  6 }


aiSPYInput12 OBJECT IDENTIFIER ::= { aiSPYInputs 28 }

aiSPYInput12State OBJECT-TYPE
    SYNTAX  INTEGER {
    notInstalled(1),
    digital-no-installed(3),
    digital-nc-installed(4)
}
    ACCESS  read-write
    STATUS  mandatory
    DESCRIPTION
           "The state of use of Input Number 12.
            This variable is stored in non-volatile memory."
    ::= { aiSPYInput12  1 }

aiSPYInput12Reading OBJECT-TYPE
    SYNTAX  INTEGER (0..1)
    ACCESS  read-only
    STATUS  mandatory
    DESCRIPTION
           "The reading for input 12.
            The reading will be 1 (active) or 0 (inactive)"
    ::= { aiSPYInput12  2 }

aiSPYInput12Label OBJECT-TYPE
    SYNTAX  DisplayString
    ACCESS  read-write
    STATUS  mandatory
    DESCRIPTION
           "A user-defined text string associated with Input Number 12.
            The text string is stored in non-volatile memory."
    ::= { aiSPYInput12  3 }

aiSPYInput12RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { aiSPYInput12  4 }

aiSPYInput12Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { aiSPYInput12  5 }

aiSPYInput12RTNDelay OBJECT-TYPE
    SYNTAX  INTEGER (0..600)
    ACCESS  read-write
    STATUS  mandatory
    DESCRIPTION
           "The number of seconds a cleared alarm for this input must
            be present before annunication. The range of this
            setting is 0..600.
            This variable is stored in non-volatile memory."
    ::= { aiSPYInput12  6 }


aiSPYInput13 OBJECT IDENTIFIER ::= { aiSPYInputs 29 }

aiSPYInput13State OBJECT-TYPE
    SYNTAX  INTEGER {
    notInstalled(1),
    digital-no-installed(3),
    digital-nc-installed(4)
}
    ACCESS  read-write
    STATUS  mandatory
    DESCRIPTION
           "The state of use of Input Number 13.
            This variable is stored in non-volatile memory."
    ::= { aiSPYInput13  1 }

aiSPYInput13Reading OBJECT-TYPE
    SYNTAX  INTEGER (0..1)
    ACCESS  read-only
    STATUS  mandatory
    DESCRIPTION
           "The reading for input 13.
            The reading will be 1 (active) or 0 (inactive)"
    ::= { aiSPYInput13  2 }

aiSPYInput13Label OBJECT-TYPE
    SYNTAX  DisplayString
    ACCESS  read-write
    STATUS  mandatory
    DESCRIPTION
           "A user-defined text string associated with Input Number 13.
            The text string is stored in non-volatile memory."
    ::= { aiSPYInput13  3 }

aiSPYInput13RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { aiSPYInput13  4 }

aiSPYInput13Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { aiSPYInput13  5 }

aiSPYInput13RTNDelay OBJECT-TYPE
    SYNTAX  INTEGER (0..600)
    ACCESS  read-write
    STATUS  mandatory
    DESCRIPTION
           "The number of seconds a cleared alarm for this input must
            be present before annunication. The range of this
            setting is 0..600.
            This variable is stored in non-volatile memory."
    ::= { aiSPYInput13  6 }


aiSPYInput14 OBJECT IDENTIFIER ::= { aiSPYInputs 30 }

aiSPYInput14State OBJECT-TYPE
    SYNTAX  INTEGER {

    notInstalled(1),
    digital-no-installed(3),
    digital-nc-installed(4)
}
    ACCESS  read-write
    STATUS  mandatory
    DESCRIPTION
           "The state of use of Input Number 14.
            This variable is stored in non-volatile memory."
    ::= { aiSPYInput14  1 }

aiSPYInput14Reading OBJECT-TYPE
    SYNTAX  INTEGER (0..1)
    ACCESS  read-only
    STATUS  mandatory
    DESCRIPTION
           "The reading for input 14.
            The reading will be 1 (active) or 0 (inactive)"
    ::= { aiSPYInput14  2 }

aiSPYInput14Label OBJECT-TYPE
    SYNTAX  DisplayString
    ACCESS  read-write
    STATUS  mandatory
    DESCRIPTION
           "A user-defined text string associated with Input Number 14.
            The text string is stored in non-volatile memory."
    ::= { aiSPYInput14  3 }

aiSPYInput14RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { aiSPYInput14  4 }

aiSPYInput14Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { aiSPYInput14  5 }

aiSPYInput14RTNDelay OBJECT-TYPE
    SYNTAX  INTEGER (0..600)
    ACCESS  read-write
    STATUS  mandatory
    DESCRIPTION
           "The number of seconds a cleared alarm for this input must
            be present before annunication. The range of this
            setting is 0..600.
            This variable is stored in non-volatile memory."
    ::= { aiSPYInput14  6 }


aiSPYInput15 OBJECT IDENTIFIER ::= { aiSPYInputs 31 }

aiSPYInput15State OBJECT-TYPE
    SYNTAX  INTEGER {
    notInstalled(1),
    digital-no-installed(3),
    digital-nc-installed(4)
}
    ACCESS  read-write
    STATUS  mandatory
    DESCRIPTION
           "The state of use of Input Number 15.
            This variable is stored in non-volatile memory."
    ::= { aiSPYInput15  1 }

aiSPYInput15Reading OBJECT-TYPE
    SYNTAX  INTEGER (0..1)
    ACCESS  read-only
    STATUS  mandatory
    DESCRIPTION
           "The reading for input 15.
            The reading will be 1 (active) or 0 (inactive)"
    ::= { aiSPYInput15  2 }

aiSPYInput15Label OBJECT-TYPE
    SYNTAX  DisplayString
    ACCESS  read-write
    STATUS  mandatory
    DESCRIPTION
           "A user-defined text string associated with Input Number 15.
            The text string is stored in non-volatile memory."
    ::= { aiSPYInput15  3 }

aiSPYInput15RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { aiSPYInput15  4 }

aiSPYInput15Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { aiSPYInput15  5 }

aiSPYInput15RTNDelay OBJECT-TYPE
    SYNTAX  INTEGER (0..600)
    ACCESS  read-write
    STATUS  mandatory
    DESCRIPTION
           "The number of seconds a cleared alarm for this input must
            be present before annunication. The range of this
            setting is 0..600.
            This variable is stored in non-volatile memory."
    ::= { aiSPYInput15  6 }


aiSPYInput16 OBJECT IDENTIFIER ::= { aiSPYInputs 32 }

aiSPYInput16State OBJECT-TYPE
    SYNTAX  INTEGER {
    notInstalled(1),
    digital-no-installed(3),
    digital-nc-installed(4)
}
    ACCESS  read-write
    STATUS  mandatory
    DESCRIPTION
           "The state of use of Input Number 16.
            This variable is stored in non-volatile memory."
    ::= { aiSPYInput16  1 }

aiSPYInput16Reading OBJECT-TYPE
    SYNTAX  INTEGER (0..1)
    ACCESS  read-only
    STATUS  mandatory
    DESCRIPTION
           "The reading for input 16.
            The reading will be 1 (active) or 0 (inactive)"
    ::= { aiSPYInput16  2 }

aiSPYInput16Label OBJECT-TYPE
    SYNTAX  DisplayString
    ACCESS  read-write
    STATUS  mandatory
    DESCRIPTION
           "A user-defined text string associated with Input Number 16.
            The text string is stored in non-volatile memory."
    ::= { aiSPYInput16  3 }

aiSPYInput16RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { aiSPYInput16  4 }

aiSPYInput16Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { aiSPYInput16  5 }

aiSPYInput16RTNDelay OBJECT-TYPE
    SYNTAX  INTEGER (0..600)
    ACCESS  read-write
    STATUS  mandatory
    DESCRIPTION
           "The number of seconds a cleared alarm for this input must
            be present before annunication. The range of this
            setting is 0..600.
            This variable is stored in non-volatile memory."
    ::= { aiSPYInput16  6 }


aiSPYInput17 OBJECT IDENTIFIER ::= { aiSPYInputs 33 }

aiSPYInput17State OBJECT-TYPE
    SYNTAX  INTEGER {
    notInstalled(1),
    digital-no-installed(3),
    digital-nc-installed(4)
}
    ACCESS  read-write
    STATUS  mandatory
    DESCRIPTION
           "The state of use of Input Number 17.
            This variable is stored in non-volatile memory."
    ::= { aiSPYInput17  1 }

aiSPYInput17Reading OBJECT-TYPE
    SYNTAX  INTEGER (0..1)
    ACCESS  read-only
    STATUS  mandatory
    DESCRIPTION
           "The reading for input 17.
            The reading will be 1 (active) or 0 (inactive)"
    ::= { aiSPYInput17  2 }

aiSPYInput17Label OBJECT-TYPE
    SYNTAX  DisplayString
    ACCESS  read-write
    STATUS  mandatory
    DESCRIPTION
           "A user-defined text string associated with Input Number 17.
            The text string is stored in non-volatile memory."
    ::= { aiSPYInput17  3 }

aiSPYInput17RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { aiSPYInput17  4 }

aiSPYInput17Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { aiSPYInput17  5 }

aiSPYInput17RTNDelay OBJECT-TYPE
    SYNTAX  INTEGER (0..600)
    ACCESS  read-write
    STATUS  mandatory
    DESCRIPTION
           "The number of seconds a cleared alarm for this input must
            be present before annunication. The range of this
            setting is 0..600.
            This variable is stored in non-volatile memory."
    ::= { aiSPYInput17  6 }

aiSPYInput18 OBJECT IDENTIFIER ::= { aiSPYInputs 34 }

aiSPYInput18State OBJECT-TYPE
    SYNTAX  INTEGER {
    notInstalled(1),
    digital-no-installed(3),
    digital-nc-installed(4)
}
    ACCESS  read-write
    STATUS  mandatory
    DESCRIPTION
           "The state of use of Input Number 18.
            This variable is stored in non-volatile memory."
    ::= { aiSPYInput18  1 }

aiSPYInput18Reading OBJECT-TYPE
    SYNTAX  INTEGER (0..1)
    ACCESS  read-only
    STATUS  mandatory
    DESCRIPTION
           "The reading for input 18.
            The reading will be 1 (active) or 0 (inactive)"
    ::= { aiSPYInput18  2 }

aiSPYInput18Label OBJECT-TYPE
    SYNTAX  DisplayString
    ACCESS  read-write
    STATUS  mandatory
    DESCRIPTION
           "A user-defined text string associated with Input Number 18.
            The text string is stored in non-volatile memory."
    ::= { aiSPYInput18  3 }

aiSPYInput18RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { aiSPYInput18  4 }

aiSPYInput18Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { aiSPYInput18  5 }

aiSPYInput18RTNDelay OBJECT-TYPE
    SYNTAX  INTEGER (0..600)
    ACCESS  read-write
    STATUS  mandatory
    DESCRIPTION
           "The number of seconds a cleared alarm for this input must
            be present before annunication. The range of this
            setting is 0..600.
            This variable is stored in non-volatile memory."
    ::= { aiSPYInput18  6 }

aiSPYInput19 OBJECT IDENTIFIER ::= { aiSPYInputs 35 }

aiSPYInput19State OBJECT-TYPE
    SYNTAX  INTEGER {
    notInstalled(1),
    digital-no-installed(3),
    digital-nc-installed(4)
}
    ACCESS  read-write
    STATUS  mandatory
    DESCRIPTION
           "The state of use of Input Number 19.
            This variable is stored in non-volatile memory."
    ::= { aiSPYInput19  1 }

aiSPYInput19Reading OBJECT-TYPE
    SYNTAX  INTEGER (0..1)
    ACCESS  read-only
    STATUS  mandatory
    DESCRIPTION
           "The reading for input 19.
            The reading will be 1 (active) or 0 (inactive)"
    ::= { aiSPYInput19  2 }

aiSPYInput19Label OBJECT-TYPE
    SYNTAX  DisplayString
    ACCESS  read-write
    STATUS  mandatory
    DESCRIPTION
           "A user-defined text string associated with Input Number 19.
            The text string is stored in non-volatile memory."
    ::= { aiSPYInput19  3 }

aiSPYInput19RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { aiSPYInput19  4 }

aiSPYInput19Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { aiSPYInput19  5 }

aiSPYInput19RTNDelay OBJECT-TYPE
    SYNTAX  INTEGER (0..600)
    ACCESS  read-write
    STATUS  mandatory
    DESCRIPTION
           "The number of seconds a cleared alarm for this input must
            be present before annunication. The range of this
            setting is 0..600.
            This variable is stored in non-volatile memory."
    ::= { aiSPYInput19  6 }

aiSPYInput20 OBJECT IDENTIFIER ::= { aiSPYInputs 36 }

aiSPYInput20State OBJECT-TYPE
    SYNTAX  INTEGER {
    notInstalled(1),
    digital-no-installed(3),
    digital-nc-installed(4)
}
    ACCESS  read-write
    STATUS  mandatory
    DESCRIPTION
           "The state of use of Input Number 20.
            This variable is stored in non-volatile memory."
    ::= { aiSPYInput20  1 }

aiSPYInput20Reading OBJECT-TYPE
    SYNTAX  INTEGER (0..1)
    ACCESS  read-only
    STATUS  mandatory
    DESCRIPTION
           "The reading for input 20.
            The reading will be 1 (active) or 0 (inactive)"
    ::= { aiSPYInput20  2 }

aiSPYInput20Label OBJECT-TYPE
    SYNTAX  DisplayString
    ACCESS  read-write
    STATUS  mandatory
    DESCRIPTION
           "A user-defined text string associated with Input Number 20.
            The text string is stored in non-volatile memory."
    ::= { aiSPYInput20  3 }

aiSPYInput20RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { aiSPYInput20  4 }

aiSPYInput20Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { aiSPYInput20  5 }

aiSPYInput20RTNDelay OBJECT-TYPE
    SYNTAX  INTEGER (0..600)
    ACCESS  read-write
    STATUS  mandatory
    DESCRIPTION
           "The number of seconds a cleared alarm for this input must
            be present before annunication. The range of this
            setting is 0..600.
            This variable is stored in non-volatile memory."
    ::= { aiSPYInput20  6 }


aiSPYInput21 OBJECT IDENTIFIER ::= { aiSPYInputs 37 }

aiSPYInput21State OBJECT-TYPE
    SYNTAX  INTEGER {
    notInstalled(1),
    digital-no-installed(3),
    digital-nc-installed(4)
}
    ACCESS  read-write
    STATUS  mandatory
    DESCRIPTION
           "The state of use of Input Number 21.
            This variable is stored in non-volatile memory."
    ::= { aiSPYInput21  1 }

aiSPYInput21Reading OBJECT-TYPE
    SYNTAX  INTEGER (0..1)
    ACCESS  read-only
    STATUS  mandatory
    DESCRIPTION
           "The reading for input 21.
            The reading will be 1 (active) or 0 (inactive)"
    ::= { aiSPYInput21  2 }

aiSPYInput21Label OBJECT-TYPE
    SYNTAX  DisplayString
    ACCESS  read-write
    STATUS  mandatory
    DESCRIPTION
           "A user-defined text string associated with Input Number 21.
            The text string is stored in non-volatile memory."
    ::= { aiSPYInput21 3 }

aiSPYInput21RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { aiSPYInput21  4 }

aiSPYInput21Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { aiSPYInput21  5 }

aiSPYInput21RTNDelay OBJECT-TYPE
    SYNTAX  INTEGER (0..600)
    ACCESS  read-write
    STATUS  mandatory
    DESCRIPTION
           "The number of seconds a cleared alarm for this input must
            be present before annunication. The range of this
            setting is 0..600.
            This variable is stored in non-volatile memory."
    ::= { aiSPYInput21  6 }


aiSPYInput22 OBJECT IDENTIFIER ::= { aiSPYInputs 38 }

aiSPYInput22State OBJECT-TYPE
    SYNTAX  INTEGER {
    notInstalled(1),
    digital-no-installed(3),
    digital-nc-installed(4)
}
    ACCESS  read-write
    STATUS  mandatory
    DESCRIPTION
           "The state of use of Input Number 22.
            This variable is stored in non-volatile memory."
    ::= { aiSPYInput22  1 }

aiSPYInput22Reading OBJECT-TYPE
    SYNTAX  INTEGER (0..1)
    ACCESS  read-only
    STATUS  mandatory
    DESCRIPTION
           "The reading for input 22.
            The reading will be 1 (active) or 0 (inactive)"
    ::= { aiSPYInput22  2 }

aiSPYInput22Label OBJECT-TYPE
    SYNTAX  DisplayString
    ACCESS  read-write
    STATUS  mandatory
    DESCRIPTION
           "A user-defined text string associated with Input Number 22.
            The text string is stored in non-volatile memory."
    ::= { aiSPYInput22  3 }

aiSPYInput22RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { aiSPYInput22  4 }

aiSPYInput22Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { aiSPYInput22  5 }

aiSPYInput22RTNDelay OBJECT-TYPE
    SYNTAX  INTEGER (0..600)
    ACCESS  read-write
    STATUS  mandatory
    DESCRIPTION
           "The number of seconds a cleared alarm for this input must
            be present before annunication. The range of this
            setting is 0..600.
            This variable is stored in non-volatile memory."
    ::= { aiSPYInput22  6 }


aiSPYInput23 OBJECT IDENTIFIER ::= { aiSPYInputs 39 }

aiSPYInput23State OBJECT-TYPE
    SYNTAX  INTEGER {
    notInstalled(1),
    digital-no-installed(3),
    digital-nc-installed(4)
}
    ACCESS  read-write
    STATUS  mandatory
    DESCRIPTION
           "The state of use of Input Number 23.
            This variable is stored in non-volatile memory."
    ::= { aiSPYInput23  1 }

aiSPYInput23Reading OBJECT-TYPE
    SYNTAX  INTEGER (0..1)
    ACCESS  read-only
    STATUS  mandatory
    DESCRIPTION
           "The reading for input 23.
            The reading will be 1 (active) or 0 (inactive)"
    ::= { aiSPYInput23  2 }

aiSPYInput23Label OBJECT-TYPE
    SYNTAX  DisplayString
    ACCESS  read-write
    STATUS  mandatory
    DESCRIPTION
           "A user-defined text string associated with Input Number 23.
            The text string is stored in non-volatile memory."
    ::= { aiSPYInput23  3 }

aiSPYInput23RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { aiSPYInput23  4 }

aiSPYInput23Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { aiSPYInput23  5 }

aiSPYInput23RTNDelay OBJECT-TYPE
    SYNTAX  INTEGER (0..600)
    ACCESS  read-write
    STATUS  mandatory
    DESCRIPTION
           "The number of seconds a cleared alarm for this input must
            be present before annunication. The range of this
            setting is 0..600.
            This variable is stored in non-volatile memory."
    ::= { aiSPYInput23  6 }


aiSPYInput24 OBJECT IDENTIFIER ::= { aiSPYInputs 40 }

aiSPYInput24State OBJECT-TYPE
    SYNTAX  INTEGER {
    notInstalled(1),
    digital-no-installed(3),
    digital-nc-installed(4)
}
    ACCESS  read-write
    STATUS  mandatory
    DESCRIPTION
           "The state of use of Input Number 24.
            This variable is stored in non-volatile memory."
    ::= { aiSPYInput24  1 }

aiSPYInput24Reading OBJECT-TYPE
    SYNTAX  INTEGER (0..1)
    ACCESS  read-only
    STATUS  mandatory
    DESCRIPTION
           "The reading for input 24.
            The reading will be 1 (active) or 0 (inactive)"
    ::= { aiSPYInput24  2 }

aiSPYInput24Label OBJECT-TYPE
    SYNTAX  DisplayString
    ACCESS  read-write
    STATUS  mandatory
    DESCRIPTION
           "A user-defined text string associated with Input Number 24.
            The text string is stored in non-volatile memory."
    ::= { aiSPYInput24  3 }

aiSPYInput24RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { aiSPYInput24  4 }

aiSPYInput24Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { aiSPYInput24  5 }

aiSPYInput24RTNDelay OBJECT-TYPE
    SYNTAX  INTEGER (0..600)
    ACCESS  read-write
    STATUS  mandatory
    DESCRIPTION
           "The number of seconds a cleared alarm for this input must
            be present before annunication. The range of this
            setting is 0..600.
            This variable is stored in non-volatile memory."
    ::= { aiSPYInput24  6 }


aiSPYInput25 OBJECT IDENTIFIER ::= { aiSPYInputs 41 }

aiSPYInput25State OBJECT-TYPE
    SYNTAX  INTEGER {
    notInstalled(1),
    digital-no-installed(3),
    digital-nc-installed(4)
}
    ACCESS  read-write
    STATUS  mandatory
    DESCRIPTION
           "The state of use of Input Number 25.
            This variable is stored in non-volatile memory."
    ::= { aiSPYInput25  1 }

aiSPYInput25Reading OBJECT-TYPE
    SYNTAX  INTEGER (0..1)
    ACCESS  read-only
    STATUS  mandatory
    DESCRIPTION
           "The reading for input 25.
            The reading will be 1 (active) or 0 (inactive)"
    ::= { aiSPYInput25  2 }

aiSPYInput25Label OBJECT-TYPE
    SYNTAX  DisplayString
    ACCESS  read-write
    STATUS  mandatory
    DESCRIPTION
           "A user-defined text string associated with Input Number 25.
            The text string is stored in non-volatile memory."
    ::= { aiSPYInput25  3 }

aiSPYInput25RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { aiSPYInput25  4 }

aiSPYInput25Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { aiSPYInput25  5 }

aiSPYInput25RTNDelay OBJECT-TYPE
    SYNTAX  INTEGER (0..600)
    ACCESS  read-write
    STATUS  mandatory
    DESCRIPTION
           "The number of seconds a cleared alarm for this input must
            be present before annunication. The range of this
            setting is 0..600.
            This variable is stored in non-volatile memory."
    ::= { aiSPYInput25  6 }


aiSPYInput26 OBJECT IDENTIFIER ::= { aiSPYInputs 42 }

aiSPYInput26State OBJECT-TYPE
    SYNTAX  INTEGER {
    notInstalled(1),
    digital-no-installed(3),
    digital-nc-installed(4)
}
    ACCESS  read-write
    STATUS  mandatory
    DESCRIPTION
           "The state of use of Input Number 26.
            This variable is stored in non-volatile memory."
    ::= { aiSPYInput26  1 }

aiSPYInput26Reading OBJECT-TYPE
    SYNTAX  INTEGER (0..1)
    ACCESS  read-only
    STATUS  mandatory
    DESCRIPTION
           "The reading for input 26.
            The reading will be 1 (active) or 0 (inactive)"
    ::= { aiSPYInput26  2 }

aiSPYInput26Label OBJECT-TYPE
    SYNTAX  DisplayString
    ACCESS  read-write
    STATUS  mandatory
    DESCRIPTION
           "A user-defined text string associated with Input Number 26.
            The text string is stored in non-volatile memory."
    ::= { aiSPYInput26  3 }

aiSPYInput26RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { aiSPYInput26  4 }

aiSPYInput26Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { aiSPYInput26  5 }

aiSPYInput26RTNDelay OBJECT-TYPE
    SYNTAX  INTEGER (0..600)
    ACCESS  read-write
    STATUS  mandatory
    DESCRIPTION
           "The number of seconds a cleared alarm for this input must
            be present before annunication. The range of this
            setting is 0..600.
            This variable is stored in non-volatile memory."
    ::= { aiSPYInput26  6 }


aiSPYInput27 OBJECT IDENTIFIER ::= { aiSPYInputs 43 }

aiSPYInput27State OBJECT-TYPE
    SYNTAX  INTEGER {
    notInstalled(1),
    digital-no-installed(3),
    digital-nc-installed(4)
}
    ACCESS  read-write
    STATUS  mandatory
    DESCRIPTION
           "The state of use of Input Number 27.
            This variable is stored in non-volatile memory."
    ::= { aiSPYInput27  1 }

aiSPYInput27Reading OBJECT-TYPE
    SYNTAX  INTEGER (0..1)
    ACCESS  read-only
    STATUS  mandatory
    DESCRIPTION
           "The reading for input 27.
            The reading will be 1 (active) or 0 (inactive)"
    ::= { aiSPYInput27  2 }

aiSPYInput27Label OBJECT-TYPE
    SYNTAX  DisplayString
    ACCESS  read-write
    STATUS  mandatory
    DESCRIPTION
           "A user-defined text string associated with Input Number 27.
            The text string is stored in non-volatile memory."
    ::= { aiSPYInput27  3 }

aiSPYInput27RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { aiSPYInput27  4 }

aiSPYInput27Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { aiSPYInput27  5 }

aiSPYInput27RTNDelay OBJECT-TYPE
    SYNTAX  INTEGER (0..600)
    ACCESS  read-write
    STATUS  mandatory
    DESCRIPTION
           "The number of seconds a cleared alarm for this input must
            be present before annunication. The range of this
            setting is 0..600.
            This variable is stored in non-volatile memory."
    ::= { aiSPYInput27  6 }


aiSPYInput28 OBJECT IDENTIFIER ::= { aiSPYInputs 44 }

aiSPYInput28State OBJECT-TYPE
    SYNTAX  INTEGER {
    notInstalled(1),
    digital-no-installed(3),
    digital-nc-installed(4)
}
    ACCESS  read-write
    STATUS  mandatory
    DESCRIPTION
           "The state of use of Input Number 28.
            This variable is stored in non-volatile memory."
    ::= { aiSPYInput28  1 }

aiSPYInput28Reading OBJECT-TYPE
    SYNTAX  INTEGER (0..1)
    ACCESS  read-only
    STATUS  mandatory
    DESCRIPTION
           "The reading for input 28.
            The reading will be 1 (active) or 0 (inactive)"
    ::= { aiSPYInput28  2 }

aiSPYInput28Label OBJECT-TYPE
    SYNTAX  DisplayString
    ACCESS  read-write
    STATUS  mandatory
    DESCRIPTION
           "A user-defined text string associated with Input Number 28.
            The text string is stored in non-volatile memory."
    ::= { aiSPYInput28  3 }

aiSPYInput28RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { aiSPYInput28  4 }

aiSPYInput28Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { aiSPYInput28  5 }

aiSPYInput28RTNDelay OBJECT-TYPE
    SYNTAX  INTEGER (0..600)
    ACCESS  read-write
    STATUS  mandatory
    DESCRIPTION
           "The number of seconds a cleared alarm for this input must
            be present before annunication. The range of this
            setting is 0..600.
            This variable is stored in non-volatile memory."
    ::= { aiSPYInput28  6 }


aiSPYOutputs OBJECT IDENTIFIER ::= { aiSPY  4 }

aiSPYRelay1 OBJECT IDENTIFIER ::= { aiSPYOutputs 1 }

aiSPYRelay1State OBJECT-TYPE
    SYNTAX  INTEGER {
    normallyoff(1),
    normallyon(2),
    forceon(3),
    forceoff(4),
    keypadcontrolled(5)
}
    ACCESS  read-write
    STATUS  mandatory
    DESCRIPTION
           "The state of use of Relay Number 1. The relay can be
            set for normally open or closed. The relay can be forced
            to an on or off condition, or controlled by the keypad.
            This variable is stored in non-volatile memory."
    ::= { aiSPYRelay1  1 }

aiSPYRelay1Status OBJECT-TYPE
    SYNTAX  INTEGER {
    normaloff(1),
    normalon(2),
    forcedon(3),
    forcedoff(4),
    keycodeactive(5),
    alarmedactive(6)
}
    ACCESS  read-only
    STATUS  mandatory
    DESCRIPTION
           "The current status for relay 1."
    ::= { aiSPYRelay1  2 }

aiSPYRelay1Label OBJECT-TYPE
    SYNTAX  DisplayString
    ACCESS  read-write
    STATUS  mandatory
    DESCRIPTION
           "A user-defined text string associated with Relay Number 1.
            The text string is stored in non-volatile memory."
    ::= { aiSPYRelay1  3 }

aiSPYRelay1Time OBJECT-TYPE
    SYNTAX  INTEGER (-2147483648..2147483647)
    MAX-ACCESS read-write
    STATUS     mandatory
    DESCRIPTION
        "The number of seconds the relay will be activated.
         Set this to -1 for indefinitely."
    ::= { aiSPYRelay1  4 }

aiSPYRelay2 OBJECT IDENTIFIER ::= { aiSPYOutputs 2 }

aiSPYRelay2State OBJECT-TYPE
    SYNTAX  INTEGER {
    normallyoff(1),
    normallyon(2),
    forceon(3),
    forceoff(4),
    keypadcontrolled(5)
}
    ACCESS  read-write
    STATUS  mandatory
    DESCRIPTION
           "The state of use of Relay Number 2. The relay can be
            set for normally open or closed. The relay can be forced
            to an on or off condition, or controlled by the keypad.
            This variable is stored in non-volatile memory."
    ::= { aiSPYRelay2  1 }

aiSPYRelay2Status OBJECT-TYPE
    SYNTAX  INTEGER {
    normaloff(1),
    normalon(2),
    forcedon(3),
    forcedoff(4),
    keycodeactive(5),
    alarmedactive(6)
}
    ACCESS  read-only
    STATUS  mandatory
    DESCRIPTION
           "The current status for relay 2."
    ::= { aiSPYRelay2  2 }

aiSPYRelay2Label OBJECT-TYPE
    SYNTAX  DisplayString
    ACCESS  read-write
    STATUS  mandatory
    DESCRIPTION
           "A user-defined text string associated with Relay Number 2.
            The text string is stored in non-volatile memory."
    ::= { aiSPYRelay2  3 }

aiSPYRelay2Time OBJECT-TYPE
    SYNTAX  INTEGER (-2147483648..2147483647)
    MAX-ACCESS read-write
    STATUS     mandatory
    DESCRIPTION
        "The number of seconds the relay will be activated.
         Set this to -1 for indefinitely."
    ::= { aiSPYRelay2  4 }

aiSPYRelay3 OBJECT IDENTIFIER ::= { aiSPYOutputs 3 }

aiSPYRelay3State OBJECT-TYPE
    SYNTAX  INTEGER {
    normallyoff(1),
    normallyon(2),
    forceon(3),
    forceoff(4),
    keypadcontrolled(5)
}
    ACCESS  read-write
    STATUS  mandatory
    DESCRIPTION
           "The state of use of Relay Number 3. The relay can be
            set for normally open or closed. The relay can be forced
            to an on or off condition, or controlled by the keypad.
            This variable is stored in non-volatile memory."
    ::= { aiSPYRelay3  1 }

aiSPYRelay3Status OBJECT-TYPE
    SYNTAX  INTEGER {
    normaloff(1),
    normalon(2),
    forcedon(3),
    forcedoff(4),
    keycodeactive(5),
    alarmedactive(6)
}
    ACCESS  read-only
    STATUS  mandatory
    DESCRIPTION
           "The current status for relay 3."
    ::= { aiSPYRelay3  2 }

aiSPYRelay3Label OBJECT-TYPE
    SYNTAX  DisplayString
    ACCESS  read-write
    STATUS  mandatory
    DESCRIPTION
           "A user-defined text string associated with Relay Number 3.
            The text string is stored in non-volatile memory."
    ::= { aiSPYRelay3  3 }

aiSPYRelay3Time OBJECT-TYPE
    SYNTAX  INTEGER (-2147483648..2147483647)
    MAX-ACCESS read-write
    STATUS     mandatory
    DESCRIPTION
        "The number of seconds the relay will be activated.
         Set this to -1 for indefinitely."
    ::= { aiSPYRelay3  4 }

aiSPYRelay4 OBJECT IDENTIFIER ::= { aiSPYOutputs 4 }

aiSPYRelay4State OBJECT-TYPE
    SYNTAX  INTEGER {
    normallyoff(1),
    normallyon(2),
    forceon(3),
    forceoff(4),
    keypadcontrolled(5)
}
    ACCESS  read-write
    STATUS  mandatory
    DESCRIPTION
           "The state of use of Relay Number 4. The relay can be
            set for normally open or closed. The relay can be forced
            to an on or off condition, or controlled by the keypad.
            This variable is stored in non-volatile memory."
    ::= { aiSPYRelay4  1 }

aiSPYRelay4Status OBJECT-TYPE
    SYNTAX  INTEGER {
    normaloff(1),
    normalon(2),
    forcedon(3),
    forcedoff(4),
    keycodeactive(5),
    alarmedactive(6)
}
    ACCESS  read-only
    STATUS  mandatory
    DESCRIPTION
           "The current status for relay 4."
    ::= { aiSPYRelay4  2 }

aiSPYRelay4Label OBJECT-TYPE
    SYNTAX  DisplayString
    ACCESS  read-write
    STATUS  mandatory
    DESCRIPTION
           "A user-defined text string associated with Relay Number 4.
            The text string is stored in non-volatile memory."
    ::= { aiSPYRelay4  3 }

aiSPYRelay4Time OBJECT-TYPE
    SYNTAX  INTEGER (-2147483648..2147483647)
    MAX-ACCESS read-write
    STATUS     mandatory
    DESCRIPTION
        "The number of seconds the relay will be activated.
         Set this to -1 for indefinitely."
    ::= { aiSPYRelay4  4 }

aiSPYRelay5 OBJECT IDENTIFIER ::= { aiSPYOutputs 5 }

aiSPYRelay5State OBJECT-TYPE
    SYNTAX  INTEGER {
    normallyoff(1),
    normallyon(2),
    forceon(3),
    forceoff(4),
    keypadcontrolled(5)
}
    ACCESS  read-write
    STATUS  mandatory
    DESCRIPTION
           "The state of use of Relay Number 5. The relay can be
            set for normally open or closed. The relay can be forced
            to an on or off condition, or controlled by the keypad.
            This variable is stored in non-volatile memory."
    ::= { aiSPYRelay5  1 }

aiSPYRelay5Status OBJECT-TYPE
    SYNTAX  INTEGER {
    normaloff(1),
    normalon(2),
    forcedon(3),
    forcedoff(4),
    keycodeactive(5),
    alarmedactive(6)
}
    ACCESS  read-only
    STATUS  mandatory
    DESCRIPTION
           "The current status for relay 5."
    ::= { aiSPYRelay5  2 }

aiSPYRelay5Label OBJECT-TYPE
    SYNTAX  DisplayString
    ACCESS  read-write
    STATUS  mandatory
    DESCRIPTION
           "A user-defined text string associated with Relay Number 5.
            The text string is stored in non-volatile memory."
    ::= { aiSPYRelay5  3 }

aiSPYRelay5Time OBJECT-TYPE
    SYNTAX  INTEGER (-2147483648..2147483647)
    MAX-ACCESS read-write
    STATUS     mandatory
    DESCRIPTION
        "The number of seconds the relay will be activated.
         Set this to -1 for indefinitely."
    ::= { aiSPYRelay5  4 }

aiSPYRelay6 OBJECT IDENTIFIER ::= { aiSPYOutputs 6 }

aiSPYRelay6State OBJECT-TYPE
    SYNTAX  INTEGER {
    normallyoff(1),
    normallyon(2),
    forceon(3),
    forceoff(4),
    keypadcontrolled(5)
}
    ACCESS  read-write
    STATUS  mandatory
    DESCRIPTION
           "The state of use of Relay Number 6. The relay can be
            set for normally open or closed. The relay can be forced
            to an on or off condition, or controlled by the keypad.
            This variable is stored in non-volatile memory."
    ::= { aiSPYRelay6  1 }

aiSPYRelay6Status OBJECT-TYPE
    SYNTAX  INTEGER {
    normaloff(1),
    normalon(2),
    forcedon(3),
    forcedoff(4),
    keycodeactive(5),
    alarmedactive(6)
}
    ACCESS  read-only
    STATUS  mandatory
    DESCRIPTION
           "The current status for relay 6."
    ::= { aiSPYRelay6  2 }

aiSPYRelay6Label OBJECT-TYPE
    SYNTAX  DisplayString
    ACCESS  read-write
    STATUS  mandatory
    DESCRIPTION
           "A user-defined text string associated with Relay Number 6.
            The text string is stored in non-volatile memory."
    ::= { aiSPYRelay6  3 }

aiSPYRelay6Time OBJECT-TYPE
    SYNTAX  INTEGER (-2147483648..2147483647)
    MAX-ACCESS read-write
    STATUS     mandatory
    DESCRIPTION
        "The number of seconds the relay will be activated.
         Set this to -1 for indefinitely."
    ::= { aiSPYRelay6  4 }

aiSPYAlarms OBJECT IDENTIFIER ::= { aiSPY  5 }

aiSPYAlarmsPresent OBJECT-TYPE
    SYNTAX     Gauge32
    MAX-ACCESS read-only
    STATUS     current
    DESCRIPTION
        "The present number of active alarm conditions."
    ::= { aiSPYAlarms 1 }

aiSPYAlarmTable OBJECT-TYPE
    SYNTAX     SEQUENCE OF AlarmEntry
    MAX-ACCESS not-accessible
    STATUS     current
    DESCRIPTION
       "A list of alarm table entries.  The table contains
        zero, one, or many rows at any moment, depending upon
        the number of alarm conditions in effect.  The table
        is initially empty at agent startup.  The agent
        creates a row in the table each time a condition is
        detected and deletes that row when that condition no
        longer pertains.  The agent creates the first row with
        aiSPYAlarmId equal to 1, and increments the value of
        aiSPYAlarmId each time a new row is created, wrapping to
        the first free value greater than or equal to 1 when
        the maximum value of aiSPYAlarmId would otherwise be
        exceeded.  Consequently, after multiple operations,
        the table may become sparse, e.g., containing entries
        for rows 95, 100, 101, and 203 and the entries should
        not be assumed to be in chronological order because
        aiSPYAlarmId might have wrapped.

        Alarms are named by an AutonomousType (OBJECT
        IDENTIFIER), aiSPYAlarmDescr, to allow a single table to
        reflect well known alarms plus alarms defined by a
        particular implementation, i.e., as documented in the
        private enterprise MIB definition for the device.  No
        two rows will have the same value of aiSPYAlarmDescr,
        since alarms define conditions.  In order to meet this
        requirement, care should be taken in the definition of
        alarm conditions to insure that a system cannot enter
        the same condition multiple times simultaneously.

        The number of rows in the table at any given time is
        reflected by the value of aiSPYAlarmsPresent."
    ::= { aiSPYAlarms 2 }

aiSPYAlarmEntry OBJECT-TYPE
    SYNTAX     AlarmEntry
    MAX-ACCESS not-accessible
    STATUS     current
    DESCRIPTION
         "An entry containing information applicable to a
         particular alarm."
   INDEX { aiSPYAlarmId }
   ::= { aiSPYAlarmTable 1 }

AlarmEntry ::= SEQUENCE {
    aiSPYAlarmId          INTEGER,
    aiSPYAlarmDescr       OBJECT IDENTIFIER
}

aiSPYAlarmId OBJECT-TYPE
    SYNTAX     INTEGER
    MAX-ACCESS not-accessible
    STATUS     current
    DESCRIPTION
         "A unique identifier for an alarm condition.  This
          value must remain constant."
    ::= { aiSPYAlarmEntry 1 }

aiSPYAlarmDescr OBJECT-TYPE
    SYNTAX     OBJECT IDENTIFIER
    MAX-ACCESS read-only
    STATUS     current
    DESCRIPTION
        "A reference to an alarm description object.  The
         object referenced should not be accessible, but rather
         be used to provide a unique description of the alarm
         condition."
    ::= { aiSPYAlarmEntry 2 }

--
-- Well known alarm conditions.
--

aiSPYWellKnownAlarms    OBJECT IDENTIFIER ::= { aiSPYAlarms 3 }

aiSPYInput1HighAlarm OBJECT-IDENTITY
    STATUS     current
    DESCRIPTION
        "The reading for sensor 1 has reached the high limit
        value."
    ::= { aiSPYWellKnownAlarms  1 }

aiSPYInput1LowAlarm OBJECT-IDENTITY
    STATUS     current
    DESCRIPTION
        "The reading for sensor 1 has reached the low limit
        value."
    ::= { aiSPYWellKnownAlarms  2 }

aiSPYInput2HighAlarm OBJECT-IDENTITY
    STATUS     current
    DESCRIPTION
        "The reading for sensor 2 has reached the high limit
        value."
    ::= { aiSPYWellKnownAlarms  3 }

aiSPYInput2LowAlarm OBJECT-IDENTITY
    STATUS     current
    DESCRIPTION
        "The reading for sensor 2 has reached the low limit
        value."
    ::= { aiSPYWellKnownAlarms  4 }

aiSPYInput3HighAlarm OBJECT-IDENTITY
    STATUS     current
    DESCRIPTION
        "The reading for sensor 3 has reached the high limit
        value."
    ::= { aiSPYWellKnownAlarms  5 }

aiSPYInput3LowAlarm OBJECT-IDENTITY
    STATUS     current
    DESCRIPTION
        "The reading for sensor 3 has reached the low limit
        value."
    ::= { aiSPYWellKnownAlarms  6 }

aiSPYInput4HighAlarm OBJECT-IDENTITY
    STATUS     current
    DESCRIPTION
        "The reading for sensor 4 has reached the high limit
        value."
    ::= { aiSPYWellKnownAlarms  7 }

aiSPYInput4LowAlarm OBJECT-IDENTITY
    STATUS     current
    DESCRIPTION
        "The reading for sensor 4 has reached the low limit
        value."
    ::= { aiSPYWellKnownAlarms  8 }

aiSPYInput5HighAlarm OBJECT-IDENTITY
    STATUS     current
    DESCRIPTION
        "The reading for sensor 5 has reached the high limit
        value."
    ::= { aiSPYWellKnownAlarms  9 }

aiSPYInput5LowAlarm OBJECT-IDENTITY
    STATUS     current
    DESCRIPTION
        "The reading for sensor 5 has reached the low limit
        value."
    ::= { aiSPYWellKnownAlarms  10 }

aiSPYInput6HighAlarm OBJECT-IDENTITY
    STATUS     current
    DESCRIPTION
        "The reading for sensor 6 has reached the high limit
        value."
    ::= { aiSPYWellKnownAlarms  11 }

aiSPYInput6LowAlarm OBJECT-IDENTITY
    STATUS     current
    DESCRIPTION
        "The reading for sensor 6 has reached the low limit
        value."
    ::= { aiSPYWellKnownAlarms  12 }

aiSPYInput7HighAlarm OBJECT-IDENTITY
    STATUS     current
    DESCRIPTION
        "The reading for sensor 7 has reached the high limit
        value."
    ::= { aiSPYWellKnownAlarms  13 }

aiSPYInput7LowAlarm OBJECT-IDENTITY
    STATUS     current
    DESCRIPTION
        "The reading for sensor 7 has reached the low limit
        value."
    ::= { aiSPYWellKnownAlarms  14 }

aiSPYInput8HighAlarm OBJECT-IDENTITY
    STATUS     current
    DESCRIPTION
        "The reading for sensor 8 has reached the high limit
        value."
    ::= { aiSPYWellKnownAlarms  15 }

aiSPYInput8LowAlarm OBJECT-IDENTITY
    STATUS     current
    DESCRIPTION
        "The reading for sensor 8 has reached the low limit
        value."
    ::= { aiSPYWellKnownAlarms  16 }

aiSPYInput1DigAlarm OBJECT-IDENTITY
    STATUS     current
    DESCRIPTION
        "The digital input 1 has been activated."
    ::= { aiSPYWellKnownAlarms  17 }

aiSPYInput2DigAlarm OBJECT-IDENTITY
    STATUS     current
    DESCRIPTION
        "The digital input 2 has been activated."
    ::= { aiSPYWellKnownAlarms  18 }

aiSPYInput3DigAlarm OBJECT-IDENTITY
    STATUS     current
    DESCRIPTION
        "The digital input 3 has been activated."
    ::= { aiSPYWellKnownAlarms  19 }

aiSPYInput4DigAlarm OBJECT-IDENTITY
    STATUS     current
    DESCRIPTION
        "The digital input 4 has been activated."
    ::= { aiSPYWellKnownAlarms  20 }

aiSPYInput5DigAlarm OBJECT-IDENTITY
    STATUS     current
    DESCRIPTION
        "The digital input 5 has been activated."
    ::= { aiSPYWellKnownAlarms  21 }

aiSPYInput6DigAlarm OBJECT-IDENTITY
    STATUS     current
    DESCRIPTION
        "The digital input 6 has been activated."
    ::= { aiSPYWellKnownAlarms  22 }

aiSPYInput7DigAlarm OBJECT-IDENTITY
    STATUS     current
    DESCRIPTION
        "The digital input 7 has been activated."
    ::= { aiSPYWellKnownAlarms  23 }

aiSPYInput8DigAlarm OBJECT-IDENTITY
    STATUS     current
    DESCRIPTION
        "The digital input 8 has been activated."
    ::= { aiSPYWellKnownAlarms  24 }

aiSPYInput9DigAlarm OBJECT-IDENTITY
    STATUS     current
    DESCRIPTION
        "The digital input 9 has been activated."
    ::= { aiSPYWellKnownAlarms  25 }

aiSPYInput10DigAlarm OBJECT-IDENTITY
    STATUS     current
    DESCRIPTION
        "The digital input 10 has been activated."
    ::= { aiSPYWellKnownAlarms  26 }

aiSPYInput11DigAlarm OBJECT-IDENTITY
    STATUS     current
    DESCRIPTION
        "The digital input 11 has been activated."
    ::= { aiSPYWellKnownAlarms  27 }

aiSPYInput12DigAlarm OBJECT-IDENTITY
    STATUS     current
    DESCRIPTION
        "The digital input 12 has been activated."
    ::= { aiSPYWellKnownAlarms  28 }

aiSPYInput13DigAlarm OBJECT-IDENTITY
    STATUS     current
    DESCRIPTION
        "The digital input 13 has been activated."
    ::= { aiSPYWellKnownAlarms  29 }

aiSPYInput14DigAlarm OBJECT-IDENTITY
    STATUS     current
    DESCRIPTION
        "The digital input 14 has been activated."
    ::= { aiSPYWellKnownAlarms  30 }

aiSPYInput15DigAlarm OBJECT-IDENTITY
    STATUS     current
    DESCRIPTION
        "The digital input 15 has been activated."
    ::= { aiSPYWellKnownAlarms  31 }

aiSPYInput16DigAlarm OBJECT-IDENTITY
    STATUS     current
    DESCRIPTION
        "The digital input 16 has been activated."
    ::= { aiSPYWellKnownAlarms  32 }

aiSPYInput17DigAlarm OBJECT-IDENTITY
    STATUS     current
    DESCRIPTION
        "The digital input 17 has been activated."
    ::= { aiSPYWellKnownAlarms  33 }

aiSPYInput18DigAlarm OBJECT-IDENTITY
    STATUS     current
    DESCRIPTION
        "The digital input 18 has been activated."
    ::= { aiSPYWellKnownAlarms  34 }

aiSPYInput19DigAlarm OBJECT-IDENTITY
    STATUS     current
    DESCRIPTION
        "The digital input 19 has been activated."
    ::= { aiSPYWellKnownAlarms  35 }

aiSPYInput20DigAlarm OBJECT-IDENTITY
    STATUS     current
    DESCRIPTION
        "The digital input 20 has been activated."
    ::= { aiSPYWellKnownAlarms  36 }

aiSPYInput21DigAlarm OBJECT-IDENTITY
    STATUS     current
    DESCRIPTION
        "The digital input 21 has been activated."
    ::= { aiSPYWellKnownAlarms  37 }

aiSPYInput22DigAlarm OBJECT-IDENTITY
    STATUS     current
    DESCRIPTION
        "The digital input 22 has been activated."
    ::= { aiSPYWellKnownAlarms  38 }

aiSPYInput23DigAlarm OBJECT-IDENTITY
    STATUS     current
    DESCRIPTION
        "The digital input 23 has been activated."
    ::= { aiSPYWellKnownAlarms  39 }

aiSPYInput24DigAlarm OBJECT-IDENTITY
    STATUS     current
    DESCRIPTION
        "The digital input 24 has been activated."
    ::= { aiSPYWellKnownAlarms  40 }

aiSPYInput25DigAlarm OBJECT-IDENTITY
    STATUS     current
    DESCRIPTION
        "The digital input 25 has been activated."
    ::= { aiSPYWellKnownAlarms  41 }

aiSPYInput26DigAlarm OBJECT-IDENTITY
    STATUS     current
    DESCRIPTION
        "The digital input 26 has been activated."
    ::= { aiSPYWellKnownAlarms  42 }

aiSPYInput27DigAlarm OBJECT-IDENTITY
    STATUS     current
    DESCRIPTION
        "The digital input 27 has been activated."
    ::= { aiSPYWellKnownAlarms  43 }

aiSPYInput28DigAlarm OBJECT-IDENTITY
    STATUS     current
    DESCRIPTION
        "The digital input 28 has been activated."
    ::= { aiSPYWellKnownAlarms  44 }

aiSPYOnBatteryAlarm OBJECT-IDENTITY
    STATUS     current
    DESCRIPTION
        "The On Battery input has been activated."
    ::= { aiSPYWellKnownAlarms  96 }

aiSPYLowBatteryAlarm OBJECT-IDENTITY
    STATUS     current
    DESCRIPTION
        "The aiSPY has detected a low battery condition."
    ::= { aiSPYWellKnownAlarms  97 }

aiSPYTraps OBJECT IDENTIFIER ::= { aiSPY  6 }

aiSPYAlarmEntryAdded TRAP-TYPE
    ENTERPRISE  { aiSPYTraps }
    DESCRIPTION
           "An AlarmEntryAdded Trap signifies that the a sensor
            reading has reached a high or low limit value."
    ::= 1

aiSPYAlarmEntryRemoved TRAP-TYPE
    ENTERPRISE  { aiSPYTraps }
    DESCRIPTION
           "An AlarmEntryAdded Trap signifies that the a sensor
            reading has gone below the high limit value or above
            the low limit value."
    ::= 2

aiSPYAccessGranted TRAP-TYPE
    ENTERPRISE  { aiSPYTraps }
    DESCRIPTION
           "An aiSPYAccessGranted Trap signifies that a valid
            key code sequence was processed by the aiSPY."
    ::= 3

aiSPYAccessDenied TRAP-TYPE
    ENTERPRISE  { aiSPYTraps }
    DESCRIPTION
           "An aiSPYAccessedDenied Trap signifies that an invalid
            key code sequence was processed by the aiSPY."
    ::= 4

aiSPYAlarmHistory OBJECT IDENTIFIER ::= { aiSPY  7 }

aiSPYAlarmHistoryEntries OBJECT-TYPE
    SYNTAX     Gauge32
    MAX-ACCESS read-only
    STATUS     current
    DESCRIPTION
        "The present number of entries in the alarm history."
    ::= { aiSPYAlarmHistory 1 }

aiSPYAlarmHistoryClear OBJECT-TYPE
    SYNTAX  INTEGER {
    clearbuffer(1)
}
    ACCESS  read-write
    STATUS  mandatory
    DESCRIPTION
           "Setting this value to ClearBuffer(1) will clear the
            alarm history buffer. "
    ::= { aiSPYAlarmHistory 2 }

aiSPYAlarmHistoryTable OBJECT-TYPE
    SYNTAX     SEQUENCE OF AlarmHistoryEntry
    MAX-ACCESS not-accessible
    STATUS     current
    DESCRIPTION
       "A list of alarm history table entries stored in the
        in the non-volatile memory.  The table contains zero,
        one, or many rows at any moment, depending upon the
        number of alarm conditions in effect. The aiSPY creates
        a row in the table each time a new alarm is detected.
        The aiSPY creates the first row with aiSPYAlarmHistoryId
        equal to 1, and increments the value of aiSPYAlarmHistoryId
        each time a new row is created, up to a maximum of 100.
        After 100 entries are created, the aiSPY will overwrite
        the earliest entry with the latest alarm.
        The number of rows in the table at any given time is
        reflected by the value of aiSPYAlarmHistoryEntries."
    ::= { aiSPYAlarmHistory 3 }

aiSPYAlarmHistoryEntry OBJECT-TYPE
    SYNTAX     AlarmHistoryEntry
    MAX-ACCESS not-accessible
    STATUS     current
    DESCRIPTION
         "An entry containing information applicable to a
         particular alarm history entry."
   INDEX { aiSPYAlarmHistoryId }
   ::= { aiSPYAlarmHistoryTable 1 }

AlarmHistoryEntry ::= SEQUENCE {
    aiSPYAlarmHistoryId     INTEGER,
    aiSPYAlarmHistoryText   OBJECT IDENTIFIER
}

aiSPYAlarmHistoryId OBJECT-TYPE
    SYNTAX     INTEGER
    MAX-ACCESS not-accessible
    STATUS     current
    DESCRIPTION
         "A unique identifier for an alarm event.  This
          value must remain constant."
    ::= { aiSPYAlarmHistoryEntry 1 }

aiSPYAlarmHistoryText OBJECT-TYPE
    SYNTAX     DisplayString
    MAX-ACCESS read-only
    STATUS     current
    DESCRIPTION
        "A text desciption of the alarm history entry.
         Each of the strings will have the following format,
         AHxxx-id-type-timestamp label
         xxx  = number entry in the table
         id   = Alarm ID
         type = HIGH, LOW, ALM or RTN
         timestamp = MM/DD/YY HH:MM:SS
         Label = The label associated with the input channel
         These alarms are stored in non-volatile memory."
    ::= { aiSPYAlarmHistoryEntry 2 }

aiSPYTrapSettings OBJECT IDENTIFIER ::= { aiSPY  8 }

aiSPYPersistantTraps OBJECT-TYPE
    SYNTAX  INTEGER (0..2147483647)
    MAX-ACCESS read-write
    STATUS     mandatory
    DESCRIPTION
        "The number of minutes between persistant traps.
         Set this to 0 to turn off persistant traps.
         This value is stored in non-volatile memory."
    ::= { aiSPYTrapSettings 1 }

aiSPYAlarmAcknowledge OBJECT-TYPE
    SYNTAX  INTEGER {
    acknowledgealarms(1)
}
    ACCESS  read-write
    STATUS  mandatory
    DESCRIPTION
           "Setting this value to AcknowledgeAlarms(1) will
            stop the aiSPY from sending persistant traps
            and dial out sequences."
    ::= { aiSPYTrapSettings 2 }

--
-- The aiSPY Extension
--
        aiSPY8124 OBJECT IDENTIFIER ::= { aiSPY 3 }

END
