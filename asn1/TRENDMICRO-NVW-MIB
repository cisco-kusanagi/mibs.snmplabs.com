--
-- Trend Micro Inc. root SMI
--
-- Copyright (C) 1995, 2003 by Trend Micro Inc.
-- All rights reserved.
--
-- Comments to: <webmaster@trendmicro.com>
-- Web URL: http://www.trendmicro.com/
--

         TRENDMICRO-NVW-MIB DEFINITIONS ::= BEGIN

         IMPORTS
                tmNVW
                        FROM TRENDMICRO-SMI
                NOTIFICATION-TYPE, OBJECT-TYPE, Integer32
                        FROM SNMPv2-SMI
                DisplayString
                        FROM SNMPv2-TC;

          
         nvwScanCurrConn OBJECT-TYPE
             SYNTAX  INTEGER
             ACCESS  read-only
             STATUS  mandatory
             DESCRIPTION
                     "Concurrent scan connections (NVE)"
             ::= { tmNVW 1 }

         nvwScanCurrMem OBJECT-TYPE
             SYNTAX  INTEGER
             ACCESS  read-only
             STATUS  mandatory
             DESCRIPTION
                     "Current scan memory usage (NVE)"
             ::= { tmNVW 2 }

         nvwPolicyCurrConn OBJECT-TYPE
             SYNTAX  INTEGER
             ACCESS  read-only
             STATUS  mandatory
             DESCRIPTION
                     "Concurrent number of user (Policy Enforcer)."
             ::= { tmNVW 3 }

nvwTraps OBJECT IDENTIFIER ::= { tmNVW 251 }

oppOn NOTIFICATION-TYPE
    STATUS      current
    DESCRIPTION
	""
    ::= { nvwTraps 1 }

oppOff NOTIFICATION-TYPE
    STATUS current
    DESCRIPTION
	""
    ::= { nvwTraps 2 }

bootFactory NOTIFICATION-TYPE
    STATUS current
    DESCRIPTION
	"Boot to factory default partition."
    ::= { nvwTraps 3 }

bootPrevious NOTIFICATION-TYPE
    STATUS current
    DESCRIPTION
	"Boot to previous partition."
    ::= { nvwTraps 4 }

haFailover NOTIFICATION-TYPE
    STATUS current
    DESCRIPTION
	"HA role changed."
    ::= { nvwTraps 5 }


         END
