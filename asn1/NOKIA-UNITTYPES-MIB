NOKIA-UNITTYPES-MIB DEFINITIONS ::= BEGIN

IMPORTS
    ntcCommonModules, ntcHWUnitTypeMibs
        FROM NOKIA-COMMON-MIB-OID-REGISTRATION-MIB
    MODULE-IDENTITY
        FROM SNMPv2-SMI;

ntcHWUnitTypeModule MODULE-IDENTITY
    LAST-UPDATED "9808270000Z"
    ORGANIZATION "Nokia"
    CONTACT-INFO
        "Mika Kiikkila
         Nokia Telecommunications Oy
         Hiomotie 5, FIN-0380 Helsinki, Finland
         +358 9 51121
         mika.kiikkila@ntc.nokia.com"
    DESCRIPTION
        "This module contains the OID values for the
         different types of circuit cards that are produced
         for use in Nokia equipment."

    REVISION "9809240000Z"
    DESCRIPTION
        "Rev 0.1   Initial release"

    REVISION       "9810040000Z"
    DESCRIPTION
        "Rev 0.2   Updated anchors to use values registered by
                    Mika Kiikkila."

    REVISION       "9811250000Z"
    DESCRIPTION
        "Rev 0.3   Updated for BBAN units by Andreas Terstegge"

    REVISION       "9812030000Z"
    DESCRIPTION
        "Rev 0.4   Updated with general slot and backplane definitions by
                   Andreas Terstegge"
    REVISION       "9910180000Z"
    DESCRIPTION
        "Rev 0.5   Comment for usage of this module and for OIDs 21 and 22 
                   added by Anna-Kaisa Lindfors."
    REVISION       "0103140000Z"
    DESCRIPTION
        "Rev 0.6   Updated for IPRG units by Petri Jarre
                   (added by Heinz-Guenter Boettger)"
    REVISION       "0202080000Z"
    DESCRIPTION
        "Rev 0.7   Hard Disk and Crypto Accelerator, Jeffrey Lampert
                   (added by Heinz-Guenter Boettger)"

    ::= { ntcCommonModules 3 }

--
-- OIDs defined in this module are mentioned to be entPhysicalVendorTypes
-- needed in ENTITY-MIB ! ! !
--

--
-- Entries should be preceded by a brief comment about the unit
--

-- ***********************
-- ** COMMON UNIT TYPES **
-- ***********************
--
-- Use this when no hardware is expected or is configured for use
-- (for instance in a particular slot).
ntcHWUnitNone   OBJECT IDENTIFIER ::= { ntcHWUnitTypeMibs 1 }

-- Use this when a wild card unit is needed.  For instance, if any
-- hardware unit (within reason) is allowed, or when the equipment
-- operator doesn't care.
ntcHWUnitAny   OBJECT IDENTIFIER ::= { ntcHWUnitTypeMibs 2 }

-- This OID is used for the 'container' entries in the entity MIB.
ntcHWSlot   OBJECT IDENTIFIER ::= { ntcHWUnitTypeMibs 21 }

-- This OID is used for identifying a generic backplane, if there are
-- no special backplane types defined for a product.
ntcHWBackplane   OBJECT IDENTIFIER ::= { ntcHWUnitTypeMibs 22 }


-- ***********************
-- ** IAN R2 UNIT TYPES **
-- ***********************
--
-- IAN NCA board with STM-1 Electrical interface
ntcHWUnitIanNcaStm1Electrical OBJECT IDENTIFIER ::= { ntcHWUnitTypeMibs 3 }

-- IAN NCA board with STM-1 Optical Single-Mode Fiber interface
ntcHWUnitNcaStm1SingleModeOptical OBJECT IDENTIFIER ::= { ntcHWUnitTypeMibs 4 }

-- IAN NCA board with STM-1 Optical Multi-Mode Fiber interface
ntcHWUnitNcaStm1MultiModeOptical OBJECT IDENTIFIER ::= { ntcHWUnitTypeMibs 5 }

-- IAN ATM Switching Unit
ntcHWUnitIanASU   OBJECT IDENTIFIER ::= { ntcHWUnitTypeMibs 6 }

-- IAN 4 port V35 interface
ntcHWUnitIan4PortV35   OBJECT IDENTIFIER ::= { ntcHWUnitTypeMibs 7 }

-- IAN 4 port E1 interface
ntcHWUnitIan4PortE1   OBJECT IDENTIFIER ::= { ntcHWUnitTypeMibs 8 }

-- IAN 4 port MSDSL interface
ntcHWUnitIan4PortMsdsl   OBJECT IDENTIFIER ::= { ntcHWUnitTypeMibs 9 }

-- IAN IP Forwarding Unit
ntcHWUnitIanIpFwrdingUnit   OBJECT IDENTIFIER ::= { ntcHWUnitTypeMibs 10 }


-- *********************
-- ** BBAN UNIT TYPES **
-- *********************

-- BBAN Alba with STM1 electrical mezzanine
ntcHWUnitBbanAlbaStm1E   OBJECT IDENTIFIER ::= { ntcHWUnitTypeMibs 11 } 

-- BBAN Alba with STM1 optical multimode mezzanine
ntcHWUnitBbanAlbaStm1Om   OBJECT IDENTIFIER ::= { ntcHWUnitTypeMibs 12 } 

-- BBAN Alba with STM1 optical singlemode mezzanine
ntcHWUnitBbanAlbaStm1Os   OBJECT IDENTIFIER ::= { ntcHWUnitTypeMibs 13 } 

-- BBAN Alba with E3 mezzanine
ntcHWUnitBbanAlbaE3   OBJECT IDENTIFIER ::= { ntcHWUnitTypeMibs 14 } 


-- BBAN SLIU with 4 channel ADSL DMT Mitec chipset
ntcHWUnitBbanSliuAdslMiDmt   OBJECT IDENTIFIER ::= { ntcHWUnitTypeMibs 15 }

-- BBAN SLIU with 4 channel ADSL DMT Analog Devices chipset
ntcHWUnitBbanSliuAdslAdDmt   OBJECT IDENTIFIER ::= { ntcHWUnitTypeMibs 16 }

-- BBAN SLIU with 4 channel E1 interface (75 Ohm)
ntcHWUnitBbanSliuE1I75   OBJECT IDENTIFIER ::= { ntcHWUnitTypeMibs 17 }

-- BBAN SLIU with 4 channel E1 interface (120 Ohm)
ntcHWUnitBbanSliuE1I120   OBJECT IDENTIFIER ::= { ntcHWUnitTypeMibs 18 }


-- BBAN backplane with 8 slots (BBAN only)
ntcHWUnitBbanBackplane8   OBJECT IDENTIFIER ::= { ntcHWUnitTypeMibs 19 }

-- BBAN backplane with 17 slots (GAN backplane, NAN + BBAN combined)
ntcHWUnitBbanBackplane17   OBJECT IDENTIFIER ::= { ntcHWUnitTypeMibs 20 }

--
-- ntcHWUnitTypeMibs 21 and 22 OIDs are defined (reserved) in Common
-- Unit Types part of this module. See above.
--

-- *********************
-- ** IPRG UNIT TYPES **
-- *********************
-- Sequoia units

-- Sequoia CRP
ntcHWUnitIprgSeqCrp   OBJECT IDENTIFIER ::= { ntcHWUnitTypeMibs 23 }

-- Sequoia GPLC1
ntcHWUnitIprgSeqGplc1   OBJECT IDENTIFIER ::= { ntcHWUnitTypeMibs 24 }

-- Sequoia GPLC2
ntcHWUnitIprgSeqGplc2   OBJECT IDENTIFIER ::= { ntcHWUnitTypeMibs 25 }

-- Sequoia WSLC
ntcHWUnitIprgSeqWslc   OBJECT IDENTIFIER ::= { ntcHWUnitTypeMibs 26 }

-- PCI/CPCI interface modules

-- 1 port Ethernet unit
ntcHWUnitIprgEth1   OBJECT IDENTIFIER ::= { ntcHWUnitTypeMibs 27 }

-- 2 port Ethernet unit
ntcHWUnitIprgEth2   OBJECT IDENTIFIER ::= { ntcHWUnitTypeMibs 28 }

-- 4 port Ethernet unit
ntcHWUnitIprgEth4   OBJECT IDENTIFIER ::= { ntcHWUnitTypeMibs 29 }

-- ATM 
ntcHWUnitIprgAtm   OBJECT IDENTIFIER ::= { ntcHWUnitTypeMibs 30 }

-- 1 port X.21
ntcHWUnitIprgX211   OBJECT IDENTIFIER ::= { ntcHWUnitTypeMibs 31 }

-- 1 port V.35
ntcHWUnitIprgV351   OBJECT IDENTIFIER ::= { ntcHWUnitTypeMibs 32 }

-- 2 port X.21
ntcHWUnitIprgX212   OBJECT IDENTIFIER ::= { ntcHWUnitTypeMibs 33 }

-- 2 port V.35
ntcHWUnitIprgV352   OBJECT IDENTIFIER ::= { ntcHWUnitTypeMibs 34 }

-- HSSI
ntcHWUnitIprgHssi   OBJECT IDENTIFIER ::= { ntcHWUnitTypeMibs 35 }

-- E1
ntcHWUnitIprgE1   OBJECT IDENTIFIER ::= { ntcHWUnitTypeMibs 36 }

-- T1
ntcHWUnitIprgT1   OBJECT IDENTIFIER ::= { ntcHWUnitTypeMibs 37 }

-- FDDI
ntcHWUnitIprgFddi   OBJECT IDENTIFIER ::= { ntcHWUnitTypeMibs 38 }

-- Token Ring
ntcHWUnitIprgTok   OBJECT IDENTIFIER ::= { ntcHWUnitTypeMibs 39 }

-- ISDN
ntcHWUnitIprgIsdn   OBJECT IDENTIFIER ::= { ntcHWUnitTypeMibs 40 }

-- 1 port Gigabit Ethernet unit
ntcHWUnitIpsoGigEth1   OBJECT IDENTIFIER ::= { ntcHWUnitTypeMibs 57 }

-- Ss7 unit
ntcHWUnitIpsoSs7   OBJECT IDENTIFIER ::= { ntcHWUnitTypeMibs 58 }

-- Cryptographic Accelerator (i.e. IPSec)
ntcHWUnitIpsoCryptoAccelerator   OBJECT IDENTIFIER ::= { ntcHWUnitTypeMibs 59 }


-- Backplanes

-- IP110
ntcHWUnitIprgBackplaneIP110 OBJECT IDENTIFIER ::= { ntcHWUnitTypeMibs 41 }

-- IP330
ntcHWUnitIprgBackplaneIP330 OBJECT IDENTIFIER ::= { ntcHWUnitTypeMibs 42 }

-- IP440
ntcHWUnitIprgBackplaneIP440 OBJECT IDENTIFIER ::= { ntcHWUnitTypeMibs 43 }

-- IP530
ntcHWUnitIprgBackplaneIP530 OBJECT IDENTIFIER ::= { ntcHWUnitTypeMibs 44 }

-- IP650
ntcHWUnitIprgBackplaneIP650 OBJECT IDENTIFIER ::= { ntcHWUnitTypeMibs 45 }

-- IP730
ntcHWUnitIprgBackplaneIP730 OBJECT IDENTIFIER ::= { ntcHWUnitTypeMibs 46 }

-- Sequoia 9 slot
ntcHWUnitIprgBackplaneSeq9 OBJECT IDENTIFIER ::= { ntcHWUnitTypeMibs 47 }

-- Sequoia 18 slot
ntcHWUnitIprgBackplaneSeq18 OBJECT IDENTIFIER ::= { ntcHWUnitTypeMibs 48 }


-- Chassis types

-- IP110
ntcHWUnitIprgChassisIP110 OBJECT IDENTIFIER ::= { ntcHWUnitTypeMibs 49 }

-- IP330
ntcHWUnitIprgChassisIP330 OBJECT IDENTIFIER ::= { ntcHWUnitTypeMibs 50 }

-- IP440
ntcHWUnitIprgChassisIP440 OBJECT IDENTIFIER ::= { ntcHWUnitTypeMibs 51 }

-- IP530
ntcHWUnitIprgChassisIP530 OBJECT IDENTIFIER ::= { ntcHWUnitTypeMibs 52 }

-- IP650
ntcHWUnitIprgChassisIP650 OBJECT IDENTIFIER ::= { ntcHWUnitTypeMibs 53 }

-- IP730
ntcHWUnitIprgChassisIP730 OBJECT IDENTIFIER ::= { ntcHWUnitTypeMibs 54 }

-- Sequoia 9 slot
ntcHWUnitIprgChassisSeq9 OBJECT IDENTIFIER ::= { ntcHWUnitTypeMibs 55 }

-- Sequoia 18 slot
ntcHWUnitIprgChassisSeq18 OBJECT IDENTIFIER ::= { ntcHWUnitTypeMibs 56 }


-- Disks
ntcHWUnitIpsoHardDisk   OBJECT IDENTIFIER ::= { ntcHWUnitTypeMibs 60 }

--
-- lines should not exceed this line's length - - - - - - - - - - ->  80 columns
--

END
