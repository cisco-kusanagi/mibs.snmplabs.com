TIARARIP-MIB DEFINITIONS ::= BEGIN

IMPORTS
	MODULE-IDENTITY, OBJECT-TYPE, 
		 IpAddress, Integer32, Counter32	FROM SNMPv2-SMI
	RowStatus, TruthValue				FROM SNMPv2-TC
	DisplayString					FROM RFC1213-MIB
--	tiaraMib					FROM TIARA-MIB;
	tiaraMgmt					FROM TIARA-NETWORKS-SMI;



tiaraRipMib MODULE-IDENTITY
	LAST-UPDATED "9407272253Z" --to be corrected
	ORGANIZATION "Tiara Networks Inc."
	CONTACT-INFO
	     "       Tiara Networks
                        Customer Service

                Postal: 525 Race Street, Suite 100,
                        San Jose, CA 95126
                        USA

                   Tel: +1 408-216-4700
                   Fax: +1 408-216-4701

                E-mail: support@tiaranetworks.com"


	DESCRIPTION
	"This file contains Tiara's enterprise specific MIB module for
	 RIP implementation"
--	::= { tiaraMib 1 } 
	::= { tiaraMgmt 110 } --to be filled in


-- TiararipScalarVariables definition

tiaraRipGlobals OBJECT IDENTIFIER ::= { tiaraRipMib 1 }

tiaraRoutingEnable OBJECT-TYPE
        SYNTAX		TruthValue
        MAX-ACCESS	read-write   
        STATUS		current
        DESCRIPTION
	" This variable is used to globally enable/disable Routing.
	DEFVAL { false}"
       ::= { tiaraRipGlobals 1 }

tiaraRipGlobalEnable OBJECT-TYPE
        SYNTAX		TruthValue
        MAX-ACCESS	read-write   
        STATUS		current
        DESCRIPTION
	" This variable is used to globally enable/disable RIP. The per-
	  interface enable/disable override the setting of this variable"
	DEFVAL { false}
       ::= { tiaraRipGlobals 2 }

tiaraRipGlobalUseTrustedNeighbour OBJECT-TYPE
        SYNTAX		TruthValue
        MAX-ACCESS	read-write   
        STATUS		current
        DESCRIPTION
	" This variable is used to enable/disable the use of Trusted Neighbour"
	DEFVAL { false}
       ::= { tiaraRipGlobals 3 }


tiaraRipGlobalValidateSrcIpAddr OBJECT-TYPE
        SYNTAX		TruthValue
        MAX-ACCESS	read-write   
        STATUS		current
        DESCRIPTION
	" enable/disable validating source IP address"
	DEFVAL { true}
       ::= { tiaraRipGlobals 4 }

tiaraRipGlobalVersion OBJECT-TYPE
	SYNTAX 		INTEGER {
					version1(1),
					version2(2)
				}
	MAX-ACCESS 	read-write   
	STATUS   	current
	DESCRIPTION
	"version of RIP to be used. per-interface send and receive versions
	 override the setting of this variable"
	::= { tiaraRipGlobals 5 }
	   

--ConfigureTripTable
	   
tiaraRipIfConfTable OBJECT-TYPE
        SYNTAX		SEQUENCE OF TiaraRipIfConfEntry
        MAX-ACCESS	not-accessible
        STATUS		current
        DESCRIPTION
	"A list of RIP interfaces and Per-Interface RIP Configuration Table"
	::= { tiaraRipMib 2 }

tiaraRipIfConfEntry OBJECT-TYPE
	SYNTAX  	TiaraRipIfConfEntry 
	MAX-ACCESS 	not-accessible
	STATUS   	current
	DESCRIPTION
	"A single RIP interface and its configuration parameters"
	INDEX { tiaraRipIfConfIpAddr }
	::= { tiaraRipIfConfTable 1 }

TiaraRipIfConfEntry ::=
        SEQUENCE {
            tiaraRipIfConfIpAddr
                IpAddress,
            tiaraRipIfConfAuthString
                DisplayString,
            tiaraRipIfConfAutoSummaryEnable
                TruthValue,
            tiaraRipIfConfDefaultAnnounceEnable
                TruthValue,
            tiaraRipIfConfEnable
                TruthValue,
            tiaraRipIfConfAnnounceHostEnable
                TruthValue,
            tiaraRipIfConfPassiveEnable
                TruthValue,
            tiaraRipIfConfReceiveVersion
                INTEGER,
            tiaraRipIfConfSendVersion
                INTEGER,
            tiaraRipIfConfSplitHorizonEnable
                TruthValue,
            tiaraRipIfConfStaticAnnounceEnable
                TruthValue,
	    	tiaraRipIfConfUpdateTimer
				Integer32,
	    	tiaraRipIfConfHoldDownTimer
				Integer32,
       	    tiaraRipIfConfFlushTimer
				Integer32,
			tiaraRipIfConfInvTimer
				Integer32,
            tiaraRipIfConfRowStatus
                RowStatus
    }

tiaraRipIfConfIpAddr OBJECT-TYPE
	SYNTAX		IpAddress
        MAX-ACCESS	not-accessible
        STATUS		current
        DESCRIPTION
	" The IP Address assigned to the given RIP interface. This variable
	is also used to index into the table"
	::= { tiaraRipIfConfEntry 1 }
	   
tiaraRipIfConfAuthString OBJECT-TYPE
        SYNTAX		DisplayString
        MAX-ACCESS	read-create   
        STATUS		current
        DESCRIPTION
	" The string to be used as the authentication key
	  Setting this string to NULL value has the effect of
	  disabling authentication. Setting this string to a non-value
	  has the effect enabling authentication, with the value of
	  the string used as authentication string. By default, the value
	  of the string is null and hence authentication is disabled"
	DEFVAL		{""}
	::= { tiaraRipIfConfEntry 2 }

tiaraRipIfConfAutoSummaryEnable OBJECT-TYPE
        SYNTAX		TruthValue
        MAX-ACCESS	read-create   
        STATUS		current
        DESCRIPTION
	" Used to enable/disable route summarization"
	DEFVAL		{true}
	::= { tiaraRipIfConfEntry 3 }
	   
tiaraRipIfConfDefaultAnnounceEnable OBJECT-TYPE
        SYNTAX		TruthValue
        MAX-ACCESS	read-create   
        STATUS		current
        DESCRIPTION
	" Used to enable/disable announcing RIP default route"
	DEFVAL		{true}
	::= { tiaraRipIfConfEntry 4 }

tiaraRipIfConfEnable OBJECT-TYPE
        SYNTAX		TruthValue
        MAX-ACCESS	read-create   
        STATUS		current
        DESCRIPTION
	" enable/disable RIP for this interface. The value of this variable
	overrides the value of the Global variable, tiaraRipGlobalEnable"  
	DEFVAL		{false}
	::= { tiaraRipIfConfEntry 5 }

tiaraRipIfConfAnnounceHostEnable OBJECT-TYPE
        SYNTAX		TruthValue
        MAX-ACCESS 	read-create   
        STATUS   	current
        DESCRIPTION
	" enable/disable announcing IP host routes"
	DEFVAL		{true}
	::= { tiaraRipIfConfEntry 6 }

tiaraRipIfConfPassiveEnable OBJECT-TYPE
        SYNTAX   	TruthValue
        MAX-ACCESS 	read-create   
        STATUS		current
        DESCRIPTION
	" suppress/do not suppress sending of routing updates"
	DEFVAL		{false}
	::= { tiaraRipIfConfEntry 7 }

tiaraRipIfConfReceiveVersion OBJECT-TYPE
        SYNTAX		INTEGER {
	       				version1(1),
					version2(2),
					version1and2(3)
				}
        MAX-ACCESS	read-create   
        STATUS		current
        DESCRIPTION
	"configuration variable for RIP receive version for this interface"
	DEFVAL		{version1and2}
	::= { tiaraRipIfConfEntry 8 }
	   
tiaraRipIfConfSendVersion OBJECT-TYPE
        SYNTAX		INTEGER {
					version1(1),
					version2(2),
					version1and2(3),
					version1compatible(4)
				}
        MAX-ACCESS	read-create   
        STATUS		current
        DESCRIPTION	
	"configuration variable for RIP send version for this interface"
	DEFVAL		{version1}
	::= { tiaraRipIfConfEntry 9 }
	
tiaraRipIfConfSplitHorizonEnable OBJECT-TYPE
        SYNTAX		TruthValue
        MAX-ACCESS	read-create   
        STATUS		current
        DESCRIPTION
	"enable/disable split horizon"
	DEFVAL		{true}
	::= { tiaraRipIfConfEntry 10 }
	   
tiaraRipIfConfStaticAnnounceEnable OBJECT-TYPE
        SYNTAX		TruthValue
        MAX-ACCESS	read-create   
        STATUS		current
        DESCRIPTION
	"enable/disable announcing static IP routes"
	DEFVAL		{false}
	::= { tiaraRipIfConfEntry 11 }
	   
tiaraRipIfConfUpdateTimer OBJECT-TYPE
        SYNTAX		Integer32 (1..65535)
	UNITS		"seconds"
        MAX-ACCESS	read-create   
        STATUS		current
        DESCRIPTION
	"The value of the Update Timer"
	DEFVAL		{30}
	::= { tiaraRipIfConfEntry 12 }

tiaraRipIfConfHoldDownTimer OBJECT-TYPE
        SYNTAX		Integer32 -- RANGE??
	UNITS		"seconds"
        MAX-ACCESS	read-create   
        STATUS		current
        DESCRIPTION
	"The value of the hold-down timer"
	DEFVAL		{120}
	::= { tiaraRipIfConfEntry 13 }

tiaraRipIfConfFlushTimer OBJECT-TYPE
	SYNTAX		Integer32 -- RANGE??
	UNITS		"seconds"
	MAX-ACCESS	read-create
	STATUS		current
        DESCRIPTION
	"The value of the Flush Timer"
	DEFVAL		{120}
	::= { tiaraRipIfConfEntry 14 }

tiaraRipIfConfInvTimer OBJECT-TYPE
        SYNTAX		Integer32 -- RANGE??
	UNITS		"seconds"
        MAX-ACCESS	read-create   
        STATUS		current
        DESCRIPTION
	"The value of the invalid timer"
	DEFVAL		{180}
	::= { tiaraRipIfConfEntry 15 }
	   
tiaraRipIfConfRowStatus OBJECT-TYPE
        SYNTAX		RowStatus 
        MAX-ACCESS	read-create   
        STATUS		current
        DESCRIPTION
	"This variable is used to create/delete rows in the configuration table"
	::= { tiaraRipIfConfEntry 16 }
	   
--Statistics table
	   
tiaraRipStatTable OBJECT-TYPE
        SYNTAX		SEQUENCE OF TiaraRipStatEntry
        MAX-ACCESS	not-accessible
        STATUS		current
        DESCRIPTION
	"A list of RIP interfaces for which the statistics are maintained"
       ::= { tiaraRipMib 3 }

tiaraRipStatEntry OBJECT-TYPE
	SYNTAX		TiaraRipStatEntry 
	MAX-ACCESS	not-accessible
	STATUS		current
	DESCRIPTION
	"per-interface statistics"
	INDEX { tiaraRipIfConfIpAddr }
	::= { tiaraRipStatTable 1 }

TiaraRipStatEntry ::=
        SEQUENCE {
            tiaraRipStatRequestPktsSent
                Counter32,
            tiaraRipStatResponsePktsSent
                Counter32,
            tiaraRipStatPktsReceived
                Counter32,
            tiaraRipStatRequestPktsReceived
                Counter32,
            tiaraRipStatResponsePktsReceived
                Counter32,
            tiaraRipStatUnrecognizedPktsReceived
                Counter32,
            tiaraRipStatBadVersions
                Counter32,
            tiaraRipStatBadAddrFamilies
                Counter32,
            tiaraRipStatBadRequestFormats
                Counter32,
            tiaraRipStatBadMetrics
                Counter32,
            tiaraRipStatBadResponseFormats
                Counter32,
            tiaraRipStatResponsesNotFromRipPort
                Counter32,
            tiaraRipStatResponsesRecdFromLoopBackIf
                Counter32,
            tiaraRipStatPktsRejected
                Counter32
    }

tiaraRipStatRequestPktsSent OBJECT-TYPE
	SYNTAX		Counter32
        MAX-ACCESS	read-only   
        STATUS		current
        DESCRIPTION
	"Number of request packets sent on this interface"
	::= { tiaraRipStatEntry 1 }
	   
tiaraRipStatResponsePktsSent OBJECT-TYPE
        SYNTAX		Counter32
        MAX-ACCESS	read-only   
        STATUS		current
        DESCRIPTION
	"Number of response packets received on this interface"
	::= { tiaraRipStatEntry 2 }

tiaraRipStatPktsReceived OBJECT-TYPE
        SYNTAX		Counter32
        MAX-ACCESS	read-only   
        STATUS		current
        DESCRIPTION
	"Total number of packets received on this interface"
	::= { tiaraRipStatEntry 3 }

tiaraRipStatRequestPktsReceived OBJECT-TYPE
        SYNTAX		Counter32
        MAX-ACCESS	read-only   
        STATUS		current
        DESCRIPTION
	"Number of request packets received on this interface"
	::= { tiaraRipStatEntry 4 }

tiaraRipStatResponsePktsReceived OBJECT-TYPE
        SYNTAX		Counter32
        MAX-ACCESS	read-only   
        STATUS		current
        DESCRIPTION
	"Number of response packets received on this interface"
	::= { tiaraRipStatEntry 5 }
	   
tiaraRipStatUnrecognizedPktsReceived OBJECT-TYPE
        SYNTAX		Counter32
        MAX-ACCESS	read-only   
        STATUS		current
        DESCRIPTION
	"Number of unrecognised packets received on this interface"
	::= { tiaraRipStatEntry 6 }

tiaraRipStatBadVersions OBJECT-TYPE
        SYNTAX		Counter32
        MAX-ACCESS	read-only   
        STATUS		current
        DESCRIPTION
	"Number of invalid version packets received on this interface"
	::= { tiaraRipStatEntry 7 }

tiaraRipStatBadAddrFamilies OBJECT-TYPE
        SYNTAX		Counter32
        MAX-ACCESS	read-only   
        STATUS		current
        DESCRIPTION
	"Number of invalid address family packets received on this interface"
	::= { tiaraRipStatEntry 8 }

tiaraRipStatBadRequestFormats OBJECT-TYPE
        SYNTAX		Counter32
        MAX-ACCESS	read-only   
        STATUS		current
        DESCRIPTION
	"Number of invalid address format packets received on this interface"
	::= { tiaraRipStatEntry 9 }
	   
tiaraRipStatBadMetrics OBJECT-TYPE
	SYNTAX		Counter32
        MAX-ACCESS	read-only   
        STATUS		current
        DESCRIPTION
	"Tiara-fill"
	::= { tiaraRipStatEntry 10 }

tiaraRipStatBadResponseFormats OBJECT-TYPE
        SYNTAX		Counter32
        MAX-ACCESS	read-only   
        STATUS		current
        DESCRIPTION
	"Tiara-fill"
	::= { tiaraRipStatEntry 11 }
	   
tiaraRipStatResponsesNotFromRipPort OBJECT-TYPE
        SYNTAX		Counter32
        MAX-ACCESS	read-only   
	STATUS		current
        DESCRIPTION
	"Tiara-fill"
	::= { tiaraRipStatEntry 12 }
	   
tiaraRipStatResponsesRecdFromLoopBackIf OBJECT-TYPE
        SYNTAX		Counter32
        MAX-ACCESS	read-only   
        STATUS		current
        DESCRIPTION
	"Number of responses received from loopback interface"
	::= { tiaraRipStatEntry 13 }

tiaraRipStatPktsRejected OBJECT-TYPE
        SYNTAX		Counter32
        MAX-ACCESS	read-only   
        STATUS		current
        DESCRIPTION
	"Number of packets rejected on this interface"
	::= { tiaraRipStatEntry 14 }
	   

-- Reject IP Address Table

tiaraRipRejectAddrTable OBJECT-TYPE
        SYNTAX		SEQUENCE OF TiaraRipRejectAddrEntry
        MAX-ACCESS	not-accessible
        STATUS		current
        DESCRIPTION
	"List of Reject IP addresses along with the interfaces they
	correspond to"
	::= { tiaraRipMib 4 }

tiaraRipRejectAddrEntry OBJECT-TYPE
	SYNTAX		TiaraRipRejectAddrEntry
	MAX-ACCESS	not-accessible
	STATUS		current
	DESCRIPTION
	"A single Reject IP address along with the interface that it
	corresponds to"
	INDEX 		{ tiaraRipIfConfIpAddr, tiaraRipRejectIpAddr }
	::= { tiaraRipRejectAddrTable 1 }

TiaraRipRejectAddrEntry ::=
        SEQUENCE {
	  tiaraRipRejectIpAddr
		IpAddress,
	  tiaraRipRejectRowStatus
		RowStatus
	 }
 
tiaraRipRejectIpAddr	OBJECT-TYPE
        SYNTAX		IpAddress
        MAX-ACCESS	not-accessible
        STATUS		current
        DESCRIPTION
	"The reject IpAddress for this interface"
	::= { tiaraRipRejectAddrEntry 1 }

tiaraRipRejectRowStatus	OBJECT-TYPE
        SYNTAX		RowStatus
        MAX-ACCESS	read-create
        STATUS		current
        DESCRIPTION	
	"Row Status variable used to create/delete rows in this table"
	::= { tiaraRipRejectAddrEntry 2 }

-- Advertise IP Address Table

tiaraRipAdvertiseAddrTable OBJECT-TYPE
        SYNTAX		SEQUENCE OF TiaraRipAdvertiseAddrEntry
        MAX-ACCESS	not-accessible
        STATUS		current
        DESCRIPTION
	"List of Advertise IP addresses along with the interfaces they
	correspond to"
	::= { tiaraRipMib 5 }

tiaraRipAdvertiseAddrEntry OBJECT-TYPE
	SYNTAX		TiaraRipAdvertiseAddrEntry
	MAX-ACCESS	not-accessible
	STATUS		current
	DESCRIPTION
	"A single advertise IP address along with the interface it corresponds
	to"
	INDEX 		{ tiaraRipIfConfIpAddr, tiaraRipAdvertiseIpAddr}
	::= { tiaraRipAdvertiseAddrTable 1 }

TiaraRipAdvertiseAddrEntry ::=
        SEQUENCE {
	  tiaraRipAdvertiseIpAddr
		IpAddress,
	  tiaraRipAdvertiseRowStatus
		RowStatus
	 }
 
tiaraRipAdvertiseIpAddr	OBJECT-TYPE
        SYNTAX		IpAddress
        MAX-ACCESS	not-accessible
        STATUS		current
        DESCRIPTION
	"One Advertise IpAddress for this interface"
	::= { tiaraRipAdvertiseAddrEntry 1 }

tiaraRipAdvertiseRowStatus	OBJECT-TYPE
        SYNTAX		RowStatus
        MAX-ACCESS	read-create
        STATUS		current
        DESCRIPTION	
	"Row Status variable used to create/delete rows in this table"
	::= { tiaraRipAdvertiseAddrEntry 2 }

-- Neighbour IP Address Table

tiaraRipNeighbourAddrTable OBJECT-TYPE
        SYNTAX		SEQUENCE OF TiaraRipNeighbourAddrEntry
        MAX-ACCESS	not-accessible
        STATUS		current
        DESCRIPTION
	"List of neighbour IP addresses along with the interfaces they
	correspond to"
	::= { tiaraRipMib 6 }

tiaraRipNeighbourAddrEntry OBJECT-TYPE
	SYNTAX		TiaraRipNeighbourAddrEntry
	MAX-ACCESS	not-accessible
	STATUS		current
	DESCRIPTION
	"A single neighbour IP address along with the interface it corresponds
	to"
	INDEX 		{ tiaraRipIfConfIpAddr, tiaraRipNeighbourIpAddr}
	::= { tiaraRipNeighbourAddrTable 1 }

TiaraRipNeighbourAddrEntry ::=
        SEQUENCE {
	  tiaraRipNeighbourIpAddr
		IpAddress,
	  tiaraRipNeighbourRowStatus
		RowStatus
	 }
 
tiaraRipNeighbourIpAddr	OBJECT-TYPE
        SYNTAX		IpAddress
        MAX-ACCESS	not-accessible
        STATUS		current
        DESCRIPTION
	"One neighbour IP address for this interface"
	::= { tiaraRipNeighbourAddrEntry 1 }

tiaraRipNeighbourRowStatus	OBJECT-TYPE
        SYNTAX		RowStatus
        MAX-ACCESS	read-create
        STATUS		current
        DESCRIPTION	
	"Row Status variable used to create/delete rows in this table"
	::= { tiaraRipNeighbourAddrEntry 2 }

-- Trusted Neighbour IP Address Table

tiaraRipTrustedNeighbourAddrTable OBJECT-TYPE
        SYNTAX		SEQUENCE OF TiaraRipTrustedNeighbourAddrEntry
        MAX-ACCESS	not-accessible
        STATUS		current
        DESCRIPTION
	"List of trusted neighbour IP addresses along with the interfaces they
	correspond to"
	::= { tiaraRipMib 7 }

tiaraRipTrustedNeighbourAddrEntry OBJECT-TYPE
	SYNTAX		TiaraRipTrustedNeighbourAddrEntry
	MAX-ACCESS	not-accessible
	STATUS		current
	DESCRIPTION
	"A single trusted neighbour IP address along with the 
	interface it corresponds to"
	INDEX 		{ tiaraRipTrustedNeighbourAddr}
	::= { tiaraRipTrustedNeighbourAddrTable 1 }

TiaraRipTrustedNeighbourAddrEntry ::=
        SEQUENCE {
	  tiaraRipTrustedNeighbourAddr
		IpAddress,
	  tiaraRipTrustedNeighbourRowStatus
		RowStatus
	 }
 
tiaraRipTrustedNeighbourAddr	OBJECT-TYPE
        SYNTAX		IpAddress
        MAX-ACCESS	not-accessible
        STATUS		current
        DESCRIPTION
	"One Trusted Neighbour IP address for this interface"
	::= { tiaraRipTrustedNeighbourAddrEntry 1 }

tiaraRipTrustedNeighbourRowStatus	OBJECT-TYPE
        SYNTAX		RowStatus
        MAX-ACCESS	read-create
        STATUS		current
        DESCRIPTION	
	"Row Status variable used to create/delete rows in this table"
	::= { tiaraRipTrustedNeighbourAddrEntry 2 }

END
