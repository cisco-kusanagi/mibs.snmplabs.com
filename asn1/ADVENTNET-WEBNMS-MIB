ADVENTNET-WEBNMS-MIB { iso org(3) dod(6) internet(1) private(4) enterprises(1) adventnet(2162) }
DEFINITIONS ::= BEGIN

IMPORTS			enterprises, OBJECT-TYPE, IpAddress, Gauge
					FROM RFC1155-SMI ;

adventnet			OBJECT IDENTIFIER ::= { enterprises 2162 }

webNMS			OBJECT IDENTIFIER ::= { adventnet 4 }

webNMSSystem		OBJECT IDENTIFIER ::= { webNMS 1 }

webNMSSeverity		OBJECT IDENTIFIER ::= { webNMS 2 }

webNMSFrontEnd		OBJECT IDENTIFIER ::= { webNMS 3 }

webNMSProcessInfo	OBJECT IDENTIFIER ::= { webNMS 4 }

webNMSTraps			OBJECT IDENTIFIER ::= { webNMS 5 }


-- The information of the WebNMS system.

 webNMSType			OBJECT-TYPE
					SYNTAX	DisplayString(SIZE(0..255))
					ACCESS	read-only
					STATUS	mandatory
					DESCRIPTION
						"The type of the AdventNet WebNMS System."
				::= { webNMSSystem 1 }


webNMSVersion	OBJECT-TYPE
				SYNTAX	DisplayString(SIZE(0..255))
				ACCESS	read-only
				STATUS	mandatory
				DESCRIPTION
					"The version number of the AdventNet WebNMS System."
				::= { webNMSSystem 2 }

webNMSHost		OBJECT-TYPE
				SYNTAX	DisplayString(SIZE(0..255))
				ACCESS	read-only
				STATUS	mandatory
				DESCRIPTION
					"The hostname of the system in which 
					the AdventNet WebNMS system is executed on."
				::= { webNMSSystem 3 }

webNMSIpAddress	OBJECT-TYPE
			SYNTAX	IpAddress
			ACCESS	read-only
			STATUS	mandatory
			DESCRIPTION
				"The ipaddress of the system in which 
				the AdventNet WebNMS system is executed on."
			::= { webNMSSystem 4 }

webNMSHttpPort		OBJECT-TYPE
			SYNTAX	INTEGER
			ACCESS	read-only
			STATUS	optional
			DESCRIPTION
				"The port used by http server of the 
				 AdventNet WebNMS system."
			::= { webNMSSystem 5 }

webNMSNumObjects	OBJECT-TYPE
					SYNTAX	INTEGER
					ACCESS	read-only
					STATUS	mandatory
					DESCRIPTION
						"The number of objects being managed
						by the AdventNet WebNMS system."
					::= { webNMSSystem 6 }

webNMSNumNetworks	OBJECT-TYPE
					SYNTAX	INTEGER
					ACCESS	read-only
					STATUS	mandatory
					DESCRIPTION
						"The number of networks being managed
						by the AdventNet WebNMS system."
					::= { webNMSSystem 7 }

webNMSNumNodes		OBJECT-TYPE
					SYNTAX	INTEGER
					ACCESS	read-only
					STATUS	mandatory
					DESCRIPTION
						"The number of nodes being managed
						by the AdventNet WebNMS system."
					::= { webNMSSystem 8 }

webNMSNumInterfaces		OBJECT-TYPE
						SYNTAX	INTEGER
						ACCESS	read-only
						STATUS	mandatory
						DESCRIPTION
							"The number of interfaces being managed
							by the AdventNet WebNMS system."
						::= { webNMSSystem 9 }

webNMSNumPollObjects	OBJECT-TYPE
			SYNTAX	INTEGER
			ACCESS	read-only
			STATUS	mandatory
			DESCRIPTION
				"The number of PolledData being managed
				by the AdventNet WebNMS system."
			::= { webNMSSystem 10 }

webNMSNumEvents		OBJECT-TYPE
						SYNTAX	INTEGER
						ACCESS	read-only
						STATUS	mandatory
						DESCRIPTION
							"The total Number of Events
							in the AdventNet WebNMS system"
						::= { webNMSSystem 11 }

webNMSNumAlerts		OBJECT-TYPE
						SYNTAX	INTEGER
						ACCESS	read-only
						STATUS	mandatory
						DESCRIPTION
							"The total Number of Alerts
							in the AdventNet WebNMS system"
						::= { webNMSSystem 12 }

webNMSEventsInBuffer	OBJECT-TYPE
						SYNTAX	INTEGER
						ACCESS	read-only
						STATUS	mandatory
						DESCRIPTION
							"The Size of the Event Queue in the 
							AdventNet WebNMS system"
						::= { webNMSSystem 13 }

webNMSAlertsInBuffer	OBJECT-TYPE
						SYNTAX	INTEGER
						ACCESS	read-only
						STATUS	mandatory
						DESCRIPTION
							"The Size of the Alert Queue in the 
							AdventNet WebNMS system"
						::= { webNMSSystem 14 }

webNMSTrapsInBuffer		OBJECT-TYPE
						SYNTAX	INTEGER
						ACCESS	read-only
						STATUS	mandatory
						DESCRIPTION
							"The Size of the Trap Buffer in the
							AdventNet WebNMS system"
						::= { webNMSSystem 15 }

webNMSSchedulerTable	OBJECT-TYPE
						SYNTAX	SEQUENCE OF WebNMSSchedulerEntry
						ACCESS	not-accessible
						STATUS	optional
						DESCRIPTION
							"A table of WebNMS scheduler instances"
						::= { webNMSSystem 16 }

webNMSschedulerEntry	OBJECT-TYPE
						SYNTAX	WebNMSSchedulerEntry
						ACCESS	not-accessible
						STATUS	mandatory
						DESCRIPTION
							"A collection objects specific to
							the WebNMS system Scheduler"
			INDEX   { webNMSSchedulerIndex }
			::= { webNMSSchedulerTable 1 }

	WebNMSSchedulerEntry	::=
		SEQUENCE {
			webNMSSchedulerIndex
				INTEGER,
			webNMSSchedulerDesc
				DisplayString(SIZE(0..255)),
			webNMSSchedulerNumTasks
				INTEGER,
			webNMSSchedulerNumThreads
				INTEGER,
			webNMSSchedulerActiveThreads
				INTEGER,
			webNMSSchedulerIdleThreads
				INTEGER
		}

webNMSSchedulerIndex	OBJECT-TYPE
			SYNTAX	INTEGER
			ACCESS	read-only
			STATUS	mandatory
			DESCRIPTION
				"The index for the WebNMS Scheduler instance"
			::= { webNMSschedulerEntry 1 }

webNMSSchedulerDesc	OBJECT-TYPE
			SYNTAX	DisplayString(SIZE(0..255))
			ACCESS	read-only
			STATUS	mandatory
			DESCRIPTION
				"A description of the WebNMS Scheduler instance"
			::= { webNMSschedulerEntry 2 }

webNMSSchedulerNumTasks		OBJECT-TYPE
			SYNTAX	INTEGER
			ACCESS	read-only
			STATUS	mandatory
			DESCRIPTION
				"The number of tasks scheduled in this WebNMS
				Scheduler instance"
			::= { webNMSschedulerEntry 3 }


webNMSSchedulerNumThreads	OBJECT-TYPE
				SYNTAX	INTEGER
				ACCESS	read-only
				STATUS	mandatory
				DESCRIPTION
					"Total number of Worker threads available"
				::= { webNMSschedulerEntry 4 }

webNMSSchedulerActiveThreads	OBJECT-TYPE
					SYNTAX	INTEGER
					ACCESS	read-only
					STATUS	mandatory
					DESCRIPTION
						"The number of active Worker threads" 
					::= { webNMSschedulerEntry 5 }

webNMSSchedulerIdleThreads	OBJECT-TYPE
				SYNTAX	INTEGER
				ACCESS	read-only
				STATUS	mandatory
				DESCRIPTION
					"The number of idle Worker threads"
				::= { webNMSschedulerEntry 6 }


--managerSeverity group --

-- svStdGroup group
--
-- Standard severity information.
--

webNMSSeverityGroup	OBJECT IDENTIFIER ::= { webNMSSeverity 1 }

webNMSMaxSeverity		OBJECT-TYPE
				SYNTAX	INTEGER {
				inform(0),
				clear(1), 
				warning(2), 
				minor(3), 
				major(4), 
				critical(5),
				None(6)
			}
			ACCESS	read-only
			STATUS	mandatory
			DESCRIPTION
				"The level of the maximum standard severity."
			::= { webNMSSeverityGroup 1 }

webNMSNumInformSeverity	OBJECT-TYPE
						SYNTAX	INTEGER
						ACCESS	read-only
						STATUS	mandatory
						DESCRIPTION
							"The number of standard information level alarms." 
						::= { webNMSSeverityGroup 2 }

webNMSNumWarningSeverity	OBJECT-TYPE
							SYNTAX	INTEGER
							ACCESS	read-only
							STATUS	mandatory
							DESCRIPTION
								"The number of standard warning level alarms." 
							::= { webNMSSeverityGroup 3 }

webNMSNumMinorSeverity		OBJECT-TYPE
							SYNTAX	INTEGER
							ACCESS	read-only
							STATUS	mandatory
							DESCRIPTION
								"The number of standard minor level alarms." 
							::= { webNMSSeverityGroup 4 }

webNMSNumMajorSeverity		OBJECT-TYPE
							SYNTAX	INTEGER
							ACCESS	read-only
							STATUS	mandatory
							DESCRIPTION
								"The number of standard major level alarms." 
							::= { webNMSSeverityGroup 5 }

webNMSNumCriticalSeverity	OBJECT-TYPE
							SYNTAX	INTEGER
							ACCESS	read-only
							STATUS	mandatory
							DESCRIPTION
								"The number of standard critical level alarms." 
							::= { webNMSSeverityGroup 6 }
							
--webNMSFrontEnd starts

webNMSFrontEndTable		OBJECT-TYPE
						SYNTAX	SEQUENCE OF webNMSFrontEndEntry
						ACCESS	not-accessible
						STATUS	optional
						DESCRIPTION
							"A table of WebNMS front end server instances"
						::= { webNMSFrontEnd 1 }

webNMSFrontEndEntry		OBJECT-TYPE
						SYNTAX	WebNMSSchedulerEntry
						ACCESS	not-accessible
						STATUS	mandatory
						DESCRIPTION
							"A collection objects specific to
							the WebNMS front end servers"
						INDEX   { webNMSFrontEndIpAddress }
						::= { webNMSFrontEndTable 1 }

WebNMSFrontEndEntry	::=	SEQUENCE {
						webNMSFrontEndIpAddress
						IpAddress
					}

webNMSFrontEndIpAddress		OBJECT-TYPE
							SYNTAX	IpAddress
							ACCESS	read-only
							STATUS	mandatory
							DESCRIPTION
								"The IpAddress of the system running this
								Front End instance"
							::= { webNMSFrontEndEntry 1 }
							
webNMSFrontEndNumClient		OBJECT-TYPE
							SYNTAX	INTEGER
							ACCESS	read-only
							STATUS	mandatory
							DESCRIPTION
								"The Number of clients connected to this
								Front End Instance" 
							::= { webNMSFrontEndEntry 2 }

							
-- webNMSProcessInfo starts

webNMSCPUUtilization	OBJECT-TYPE
						SYNTAX	Gauge32
						ACCESS	read-only
						STATUS	mandatory
						DESCRIPTION
							"The CPU utilization of the WebNMS Process"
						::= { webNMSProcessInfo 1 }

webNMSTotalMemory		OBJECT-TYPE
						SYNTAX	INTEGER
						ACCESS	read-only
						STATUS	mandatory
						DESCRIPTION
							"The Total memory used by the WebNMS Process"
						::= { webNMSProcessInfo 2 }

webNMSFreeMemory		OBJECT-TYPE
						SYNTAX	INTEGER
						ACCESS	read-only
						STATUS	mandatory
						DESCRIPTION
							"The Free memory available for the WebNMS Process"
						::= { webNMSProcessInfo 3 }

-- webNMSTraps starts

webNMSEventQueueOverFlow	NOTIFICATION-TYPE
						OBJECTS	
						{
							webNMSEventQueueSize
						}
						STATUS  current
						DESCRIPTION
							"This trap signifies that the Event queue has reached its maximum
							limit. When this happens the processing of traps will slow down."
						::= { webNMSTraps 1 }

webNMSAlertQueueOverFlow	NOTIFICATION-TYPE
							OBJECTS	
							{
								webNMSAlertQueueSize
							}
							STATUS  current
							DESCRIPTION
								"This trap signifies that the Alert queue has reached its maximum
								limit. When this happens the processing of traps and events will
								slow down."
							::= { webNMSTraps 2 }

END
