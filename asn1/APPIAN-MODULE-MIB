--
--  Title:  Appian Modules MIB
--
--  Dated:  11/7/99
--  Author: D. Theriault
--
--  Description:
--
--  This MIB file contains the definitions and support for the Appian
--  Optical Services Access Platform(s).
-- 
--  The Appian Modules MIB supports attributes which are specific to 
--  individual modules and cards within the system chassis.
--
--
APPIAN-MODULE-MIB DEFINITIONS ::= BEGIN

    IMPORTS
        acOsap, AcOpStatus, AcSlotNumber, 
        AcAdminStatus, AcNodeId, AcSwVersion     FROM APPIAN-SMI-MIB

        acChassisCurrentTime, acChassisRingId    FROM APPIAN-CHASSIS-MIB

        MODULE-IDENTITY,OBJECT-TYPE, 
        Counter32, NOTIFICATION-TYPE             FROM SNMPv2-SMI

        DisplayString,TruthValue,
        TEXTUAL-CONVENTION                       FROM SNMPv2-TC;


acModule    
    MODULE-IDENTITY
        LAST-UPDATED        "9911040000Z"
        ORGANIZATION        "Appian Communications, Inc."
        CONTACT-INFO        "Douglas Theriault"

        DESCRIPTION 
        "Appian Communications OSAP Modules MIB contain the definitions for 
        module hardware information and status." 

        REVISION            "9911110000Z" 
        
        DESCRIPTION         "Draft MIB for Engineering use only."

    ::= { acOsap 2 }


    AcModuleType  ::= TEXTUAL-CONVENTION
    STATUS  current
    DESCRIPTION
    "List of module types currently supported on the OSAP platform.
     Some details of certain types are shown below:
     Note that the designation in parentheses is connector style
     gbe-sx - built with 8 ports of short-reach multi-mode (MT_RJ)
     gbe-lx - built with 8 ports of intermediate-reach single-mode laser
     gbe-sfp - built with 8 Small Form-factor Pluggable transceivers
        Note: This card will use instances of acPfot to describe each port
     oc3-ir-1 - built with 1 intermediate-reach oc-3 port (SC)
     oc3-ir-2 - built with 2 intermediate-reach oc-3 port2 (SC)
     oc3-sr-1 - built with 1 short-reach oc-3 port (SC)
     oc3-sr-2 - built with 2 short-reach oc-3 ports (SC)
     oc3-lr-1 - built with 1 long-reach oc-3 port (SC)
     oc3-lr-2 - built with 2 long-reach oc-3 ports (SC)
     oc3c-ir-4 - built with 4 intermediate-reach oc-3c ports (LC)
     oc12-ir-1-oc3c-ir-4 - built with 1 intermediate reach oc12 port (LC) 
                           and 4 intermediate-reach oc3c ports (LC)
     oc12-ir-1 - built with 1 intermediate-reach oc-12 port (SC)
     oc12-ir-2 - built with 2 intermediate-reach oc-12 ports (SC)
     oc12-lr-1 - built with 1 long-reach oc-12 port (SC)
     oc12-lr-2 - built with 2 long-reach oc-12 ports (SC)
     oc48-ir-1-oc12-ir-4 - built with 1 intermediate reach oc48 port (LC) 
                           and 4 intermediate-reach oc12 ports (LC)
     oc48-ir-1 - built with 1 intermediate-reach oc-48 port (SC)
     oc48-ir-2 - built with 2 intermediate-reach oc-48 ports (SC)
     oc48-lr-1 - built with 1 long-reach oc-48 port (SC)
     oc48-lr-2 - built with 2 long-reach oc-48 ports (SC)"

    SYNTAX  INTEGER {
                unknown(0),
                not-present(1),
                bits-s3(2),
                svcproc-1(3),
                fe16-mc(4),
                fe8-tx-io(5),
                fe8-fx-io(6),
                gbe-sx(7),
                gbe-lx(8),
                gbe-sfp(9),
                oc48-ir-2(10),
                oc48-ir-1(11),
                ds1-14-mc(12),
                ds1-7-io(13),
                ds3-network(14),
                ds3-access(15),
                ds3-io(16),
                oc3-ir-1(17),
                oc3-ir-2(18),
                oc3-sr-1(19),
                oc3-sr-2(20),
                oc3-lr-1(21),
                oc3-lr-2(22),
                oc3c-ir-4(23),
                oc12-ir-1-oc3c-ir-4(24),
                oc12-ir-1(25),
                oc12-ir-2(26),
		oc12-ir-4(27),
                oc12-lr-1(28),
                oc12-lr-2(29),
		oc48-ir-1-oc12-ir-4(30),
                oc48-lr-2(31),
                oc48-lr-1(32),
                e1(33),
                e1-io(34),
                e3(35),
                e3-io(36),
                enet-agg(37)
            }

    --
    -- Appian Module Number
    --            
    AcModuleNumber    ::= TEXTUAL-CONVENTION
    
    STATUS  current
    DESCRIPTION
                "A module number in an OSAP Chassis which is within the range
                of (1..2)."
    SYNTAX  INTEGER (1..2)

    --
    -- Appian Media Slot Number
    --            
    AcMediaSlotNumber    ::= TEXTUAL-CONVENTION
    
    STATUS  current
    DESCRIPTION
                "A slot number in an OSAP Chassis which is within the range
                of (0..9). This type indicates the slot number for a media
                card in the OSAP chassis and is in the range 5-9 if valid,
                and 0 if not valid."
    SYNTAX  INTEGER (0..9)
--
-- Module MIB starts
--

acModuleTable   OBJECT-TYPE
    SYNTAX  SEQUENCE OF AcModuleEntry
    MAX-ACCESS  not-accessible
    STATUS  current
    DESCRIPTION
    "A table containing the module information for each module within the
    chassis. This table is automatically created during system initialization
    and updated when modules are removed and inserted. When a module is 
    removed, the row is automatically removed."

    ::= { acModule 1 }

acModuleEntry   OBJECT-TYPE
    SYNTAX  AcModuleEntry
    MAX-ACCESS  not-accessible
    STATUS  current
    DESCRIPTION
    "Module information record containing hardware, software, firmware, name
    data for a specific node.slot within a chassis.  Row's in this table are
    automatically instantiated at system initialization."
    
    INDEX   { acModuleNodeId, acModuleSlot, acModuleNumber }

    ::= { acModuleTable 1 }

    AcModuleEntry ::=
        SEQUENCE {
            acModuleNodeId                      AcNodeId,
            acModuleSlot                        AcSlotNumber,
            acModuleNumber                      AcModuleNumber,
            acModuleAdminStatus                 AcAdminStatus,
            acModuleCfgType                     AcModuleType,            
            acModuleType                        AcModuleType,
            acModuleOpStatus                    AcOpStatus,
            acModuleRevision                    INTEGER,
            acModuleSerialNumber                DisplayString,
            acModuleProductionDate              DisplayString,
            acModuleFirmwareName                DisplayString,
            acModuleFirmwareRevision            INTEGER,
            acModuleNumberFailures              Counter32,
            acModuleReset                       TruthValue,
            acModuleNumberPorts                 INTEGER,
            acModuleName                        DisplayString,
            acModuleSwVersion                   AcSwVersion,
            acModuleDiagTestMode                INTEGER,
            acModuleDiagStatus                  INTEGER,
            acModuleDiagResultString            DisplayString,
            acModuleActiveSlot                  AcMediaSlotNumber,
            acModulePrimarySlot                 AcMediaSlotNumber,
            acModuleBackupSlot                  AcMediaSlotNumber
        }


acModuleNodeId    OBJECT-TYPE
    SYNTAX      AcNodeId
    MAX-ACCESS  accessible-for-notify
    STATUS      current
    DESCRIPTION
    "The unique node identification number representing a chassis within a
    ring of OSAP's."

    ::= { acModuleEntry 1 }

acModuleSlot    OBJECT-TYPE
    SYNTAX      AcSlotNumber
    MAX-ACCESS  accessible-for-notify
    STATUS      current
    DESCRIPTION
    "The slot number within the chassis where this module resides."

    ::= { acModuleEntry 2 }

acModuleNumber    OBJECT-TYPE
    SYNTAX      AcModuleNumber
    MAX-ACCESS  accessible-for-notify
    STATUS      current
    DESCRIPTION
    "The module number within the slot where this module resides."

    ::= { acModuleEntry 3 }

acModuleAdminStatus  OBJECT-TYPE
    SYNTAX  AcAdminStatus
    MAX-ACCESS  read-write
    STATUS  current
    DESCRIPTION
    "The administrative status. See AcAdminStatus for the semantics."
    DEFVAL { inactivate }

    ::= { acModuleEntry 4 }

acModuleCfgType OBJECT-TYPE
    SYNTAX  AcModuleType
    MAX-ACCESS  read-write
    STATUS  current
    DESCRIPTION
    "The acModuleCfgType field enumeration is used to uniquely identify the
    module type which is currently in a slot within the chassis, as 
    defined by the AppianVista EMS."
    DEFVAL { unknown }
    
    ::= { acModuleEntry 5 }

acModuleType    OBJECT-TYPE
    SYNTAX  AcModuleType
    MAX-ACCESS  read-only
    STATUS      current
    DESCRIPTION
    "The acModuleType field enumeration is used to uniquely identify the
    module type which is currently in a slot within the chassis."

    ::= { acModuleEntry 6 }

acModuleOpStatus  OBJECT-TYPE
    SYNTAX  AcOpStatus
    MAX-ACCESS  read-only
    STATUS      current
    DESCRIPTION
    "This field indicates the current operational status for the module. Only
    the following values are applicable to the module: operational, offline,
    initializing, selfTesting, upgrading, standby, shuttingDown and failed."

    ::= { acModuleEntry 7 }

acModuleRevision    OBJECT-TYPE
    SYNTAX  INTEGER (0..255)
    MAX-ACCESS  read-only
    STATUS      current
    DESCRIPTION
    "Contains the manufacturing revision number for this module."

    ::= { acModuleEntry 8 }

acModuleSerialNumber    OBJECT-TYPE
    SYNTAX  DisplayString (SIZE (0..32))
    MAX-ACCESS  read-only
    STATUS  current
    DESCRIPTION
    "A display string representing the manufacturing serial number as stored
    in the modules I2C prom."

    ::= { acModuleEntry 9 }

acModuleProductionDate  OBJECT-TYPE
    SYNTAX  DisplayString (SIZE (0..5))
    MAX-ACCESS  read-only
    STATUS  current
    DESCRIPTION
    "The date code when this module was manufactured.  This field 
    is read-only and set by manufacturing in the I2C prom. The format used
    is YYWW; with YY = year and WW = week."

    ::= { acModuleEntry 10 }

acModuleFirmwareName    OBJECT-TYPE
    SYNTAX  DisplayString   (SIZE (0..32))
    MAX-ACCESS  read-only
    STATUS  current
    DESCRIPTION
    "This string contains the name of the firmware file resident on the
    switch controller file system. Note: Not all modules contain firmware."

    ::= { acModuleEntry 11 }

acModuleFirmwareRevision    OBJECT-TYPE
    SYNTAX  INTEGER (0..255)
    MAX-ACCESS  read-only
    STATUS  current
    DESCRIPTION
    "The revision of the firmware."

    ::= { acModuleEntry 12 }

acModuleNumberFailures  OBJECT-TYPE
    SYNTAX  Counter32
    MAX-ACCESS  read-only
    STATUS  current
    DESCRIPTION
    "The total number of failure events reported by the module."

    ::= { acModuleEntry 13 }

acModuleReset   OBJECT-TYPE
    SYNTAX  TruthValue 
    MAX-ACCESS  read-write
    STATUS  current
    DESCRIPTION
    "This field allows the user to reset a specified module within the 
    chassis. Note: If resetting the active SCP on which the management
    session is active, loss of connection will result as the standby SCP
    gains control."
    DEFVAL { false }
    
    ::= { acModuleEntry 14 }

acModuleNumberPorts OBJECT-TYPE
    SYNTAX  INTEGER (0..32)
    MAX-ACCESS  read-only
    STATUS  current
    DESCRIPTION
    "A count of the total number of ports located on this module. Not all 
    modules contain user configurable or usable ports."

    ::= { acModuleEntry 15 }

acModuleName    OBJECT-TYPE
    SYNTAX  DisplayString   (SIZE (0..48))
    MAX-ACCESS  read-only
    STATUS      current
    DESCRIPTION
    "The official human readable name for the type of module indicated by
    acModuleType."

    ::= { acModuleEntry 16 }
    
acModuleSwVersion  OBJECT-TYPE
    SYNTAX  AcSwVersion
    MAX-ACCESS  read-only
    STATUS      current
    DESCRIPTION
    "The current software version if any which is operational on this module.
    This attribute will be NULL if the physical module does not execute a 
    software image (re: it is controlled by the switch controller)."

    ::= { acModuleEntry 17 }

acModuleDiagTestMode  OBJECT-TYPE
    SYNTAX  INTEGER {
                basic(1),
                advanced(2),
                stress(3)
            }
    MAX-ACCESS  read-write
    STATUS      current
    DESCRIPTION
    "The diagnostics test mode allows the user to select a basic(1), 
    advanced(2) or stress(3) series of powerup self tests to be run
    when the acModuleOpStatus field is changed to selfTesting(4).  A
    basic(1) test performs a quick self test and is the mode which is
    by default selected at powerup.  Advanced(2) mode is used to run
    a more thorough series of tests and stress(3) mode is used to 
    execute a system test packet loopback type of powerup test.  In
    all test modes, the acModuleDiagStatus field contains a unique
    results code (Refer to diagnostics utility guide).  The results
    of a test request is also written as a string to the 
    acModuleDiagResultString field."

    DEFVAL { basic }
    
    ::= { acModuleEntry 18 }

acModuleDiagStatus  OBJECT-TYPE
    SYNTAX  INTEGER
    MAX-ACCESS  read-only
    STATUS      current
    DESCRIPTION
    "The unique results code as returned from the test mode issued 
    via acModuleDiagTestMode.  Refer to the diagnostic utility 
    guide for details."

    ::= { acModuleEntry 19 }

acModuleDiagResultString  OBJECT-TYPE
    SYNTAX  DisplayString (SIZE(0..255))
    MAX-ACCESS  read-only
    STATUS      current
    DESCRIPTION
    "The results of the diagnostic test returned as a printable
    ASCII string.  Refer to the diagnostics utility guide for 
    details."

    ::= { acModuleEntry 20 }

acModuleActiveSlot    OBJECT-TYPE
    SYNTAX      AcMediaSlotNumber
    MAX-ACCESS  read-only
    STATUS      current
    DESCRIPTION
    "The slot number within the chassis where the media module that 
     is driving this module resides. This attribute is set to 0 for
     rows in which the module is either not an IO card or is an IO
     card that has no appropriate media card present in the chassis."

    ::= { acModuleEntry 21 }

acModulePrimarySlot    OBJECT-TYPE
    SYNTAX      AcMediaSlotNumber
    MAX-ACCESS  read-only
    STATUS      current
    DESCRIPTION
    "The slot number within the chassis where the primary media module that 
     could drive this module resides. This attribute is set to 0 for
     rows in which the module is either not an IO card or is an IO
     card that has no appropriate media card present in the chassis."

    ::= { acModuleEntry 22 }

acModuleBackupSlot    OBJECT-TYPE
    SYNTAX      AcMediaSlotNumber
    MAX-ACCESS  read-only
    STATUS      current
    DESCRIPTION
    "The slot number within the chassis where the backup media module that 
     could drive this module resides. This attribute is set to 0 for
     rows in which the module is either not an IO card or is an IO
     card that has no appropriate media card present in the chassis."

    ::= { acModuleEntry 23 }

-- 
-- Module MIB Trap Definitions
--
--

acModuleTraps   OBJECT IDENTIFIER ::= { acModule 0 }

acModuleCfgMismatchTrap  NOTIFICATION-TYPE
    OBJECTS { 
        acChassisCurrentTime, acChassisRingId, 
        acModuleNodeId, 
        acModuleSlot,
        acModuleCfgType,
        acModuleType
    } 
    STATUS  current
    DESCRIPTION
    "The configured module type does not match with the actual module present."
    
    ::= { acModuleTraps 1 }

acModuleResetFailedTrap  NOTIFICATION-TYPE
    OBJECTS { 
        acChassisCurrentTime, acChassisRingId,
        acModuleNodeId, 
        acModuleReset, 
        acModuleSlot 
    } 
    STATUS  current
    DESCRIPTION
    "The module couldn't be reset."
    
    ::= { acModuleTraps 2 }
    
acModuleSwVersionTrap  NOTIFICATION-TYPE
    OBJECTS { 
        acChassisCurrentTime, acChassisRingId,
        acModuleNodeId, 
        acModuleSlot, 
        acModuleSwVersion 
    } 
    STATUS  current
    DESCRIPTION
    "Two different version of software are currently running within the same
    chassis.  This is an unsupported operational mode."
    
    ::= { acModuleTraps 3 }

acModuleRemovalTrap  NOTIFICATION-TYPE
    OBJECTS { 
        acChassisCurrentTime, acChassisRingId,
        acModuleNodeId, 
        acModuleSlot
    } 
    STATUS  current
    DESCRIPTION
    "A module has been removed from this chassis."
    
    ::= { acModuleTraps 4 }

acModuleInsertedTrap  NOTIFICATION-TYPE
    OBJECTS { 
        acChassisCurrentTime, acChassisRingId,
        acModuleNodeId, 
        acModuleSlot,
        acModuleType
    } 
    STATUS  current
    DESCRIPTION
    "A module has been inserted into this chassis."
    
    ::= { acModuleTraps 5 }
    
acModuleFailureTrap  NOTIFICATION-TYPE
    OBJECTS { 
        acChassisCurrentTime, acChassisRingId,
        acModuleNodeId, 
        acModuleSlot,
        acModuleType,
        acModuleDiagStatus,
        acModuleDiagResultString
    } 
    STATUS  current
    DESCRIPTION
    "The module in this slot did not pass diagnostics or has been marked as a failed
    board by operational software."
    
    ::= { acModuleTraps 6 }
    
    
END
