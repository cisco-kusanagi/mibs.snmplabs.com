LUMINOUS-TOPOLOGY-MIB DEFINITIONS ::= BEGIN
     IMPORTS
             enterprises,
             MODULE-IDENTITY, OBJECT-TYPE, NOTIFICATION-TYPE,
				 IpAddress, Integer32      
                                              FROM SNMPv2-SMI
             DisplayString FROM RFC1213-MIB
             RowStatus                         FROM SNMPv2-TC;




  -- IANA-registered  Luminous Network Enterprise Number of 4614

     luminous OBJECT IDENTIFIER ::= { enterprises 4614}


  -- leaving tree-space for the future products:

     lumADM   OBJECT IDENTIFIER ::= { luminous 1}


  --  This MIB module defines only Shelf/Node and Card groups so far.

 
     lumTopologyMIB  MODULE-IDENTITY      
                         LAST-UPDATED "0003080000Z"
                         ORGANIZATION "Luminous Networks"
                         CONTACT-INFO 
                                      "  Luminous Technical Support

                                         Postal: Luminous Networks,
                                                 14060 Bubb Road,
                                                 Cupertino, CA 95014

                                            Tel: +1 408 342 6400
                                            Fax: +1 408 863 1100
                                         E-mail: support@lumnet.com
                                         
                                        Authors: Jason Fan,
                                                 Nick Gandin
                                            Tel: +1 408 342 6431
                                                 +1 408 342 6417
                                         E-mail: jason@lumnet.com
                                                  nick@lumnet.com"
                                         
                                         

                 DESCRIPTION  "The Luminous Topology MIB contains        
                               information related to the   
                               Luminous Ring Topology." 
                         ::= { lumADM   3}


     lumRingCommands  OBJECT IDENTIFIER ::= { lumTopologyMIB 1}




--  Topology Discovery Commands

   
     lumTopoDiscoveryGroup OBJECT IDENTIFIER ::= { lumRingCommands 1}



       lumTopoDiscoveryRetries  OBJECT-TYPE
             SYNTAX      Integer32
             MAX-ACCESS  read-write
             STATUS      current
             DESCRIPTION  "Initially set to 3."
             DEFVAL  { 3 }
            ::= { lumTopoDiscoveryGroup 1 }


       lumTopoNeighborInfoTimer  OBJECT-TYPE
             SYNTAX      Integer32
             MAX-ACCESS  read-write
             STATUS      current
             DESCRIPTION  "The Neighbor Information Timer sets the
                           amount of time between periodic sends
                           of the neighbor information message
                           from each node on each egress link."
            ::= { lumTopoDiscoveryGroup 2 }



       lumTopoDiscoveryConvergenceTimer  OBJECT-TYPE
             SYNTAX      Integer32
             MAX-ACCESS  read-write
             STATUS      current
             DESCRIPTION  "The topology convergence timer sets the
                           amount of time during which no messages
                           indicating a change of topology have
                           been received before the topology can
                           be considered to have converged. If the
                           topology convergence timer has not
                           reached the required value for
                           convergence, the topology discovery
                           timer is reset."
            ::= { lumTopoDiscoveryGroup 3 }


       lumTopoDiscoveryTimer  OBJECT-TYPE
             SYNTAX      Integer32
             MAX-ACCESS  read-write
             STATUS      current
             DESCRIPTION  "The topology discovery timer sets the
                           total amount of time until the topology
                           convergence timer is checked. If the
                           topology convergence timer has not
                           reached the required value for
                           convergence, the topology discovery
                           timer is reset."
            ::= { lumTopoDiscoveryGroup 4 }


        lumTopoDiscovery  OBJECT-TYPE
             SYNTAX      INTEGER {
                                  none(1),
                                  doDiscover(2),
                                  stopDiscover(3),
                                  discoveryFailed(4)
                                  }
             MAX-ACCESS read-write
             STATUS     current
             DESCRIPTION  "Setting this field to doDiscover(2) has
                           the effect of starting the Ring Topology
                           Discovery. The Retries and Timers in the
                           fields above in order for them to have
                           effect should be set before attempting
                           to start discovery.

                           Upon Discovery completion this field is
                           set by the SNMP Agent to either none(1)
                           or ,if failed to discoveryFailed(4).
                           
                           stopDiscovery(3) is for the future.
                           
                           Setting to discoveryFailed(4) is not
                           allowed by SNMP Agent.

                           discoveryFailed(4) can be also the
                           outcome of topology discovery performed
                           by the ring management without NMS
                           requesting it."
             DEFVAL  { none }
            ::= { lumTopoDiscoveryGroup 5 }


        lumTopoDiscoveryFailedNode  OBJECT-TYPE
             SYNTAX      IpAddress
             MAX-ACCESS read-only
             STATUS     current
             DESCRIPTION  "The node that causes the the Topology
                           Discovery failure. 
                           
                           Valid only if  lumTopoDiscovery is
                           discoveryFailed(4)."
            ::= { lumTopoDiscoveryGroup 6 }


--   Other Ring Commands



        lumRingCommand  OBJECT-TYPE
             SYNTAX      INTEGER {
                                  none(1),
                                  clearAll(2),
                                  lockoutOfProtection(3),
                                  commandFailed(4)
                                  }
             MAX-ACCESS read-write
             STATUS     current
             DESCRIPTION  "Setting this field to clearAll(2) has
                           the effect of clearing all
                           lumLinkAdminStatus (setting it to 0).
                           This clears all externally initiated
                           commands.

                           
                           Setting this field to
               lockoutOfProtection(3) results in all
                           traffic on the ring returning to
               the shortest-hop available path. This
                           sets all LinkAdminStatus values to
                           16000 (standard operational link).

                           Setting this field to
                           switchToRevertiveMode(4), has the
                           effect of switching from non-revertive
                           mode to revertive mode fot the whole
                           ring. 

                           commandFailed(5) cannot be set. The
                           lumRingCommand is set to this value
                           by SNMP Agent when requested command
                           fails."
             DEFVAL  { none }
            ::= { lumRingCommands 2 }


         lumRingRevertiveMode   OBJECT-TYPE
             SYNTAX      INTEGER {
                                  revertiveMode(1),
                                  nonRevertiveMode(2)
                                  }
             MAX-ACCESS read-write
             STATUS     current
             DESCRIPTION  "Setting this field to revertiveMode(1),
                           has the effect of switching from
                           non-revertive mode to revertive mode
                           for the whole ring.
                           
                           Likewise setting this field to 
                           nonRevertiveMode(2), has the effect of
                           switching from revertive  mode to 
                           non-revertive mode fot the whole ring." 
             DEFVAL  { nonRevertiveMode }
            ::= { lumRingCommands 3 }



        lumProtectionSwitchHysteresis  OBJECT-TYPE
             SYNTAX     Integer32
             MAX-ACCESS read-only
             STATUS     current
             DESCRIPTION  "Hysteresis factor. This factor prevents
                           ping-ponging in protection switching
                           when a link's measured status is
                           varying with time. Valid values are
                           between 5 and 100."
             DEFVAL  { 10 }
            ::= { lumRingCommands 4 }
  


--   Protective Switching

       

         lumProtectionSwitchingTable OBJECT-TYPE
             SYNTAX  SEQUENCE OF LumProtectionSwitchingEntry 
             MAX-ACCESS not-accessible
             STATUS  current
             DESCRIPTION
                "The Luminous Protection Switching Table."
            ::= { lumTopologyMIB 2   }


         lumProtectionSwitchingEntry OBJECT-TYPE
            SYNTAX      LumProtectionSwitchingEntry 
            MAX-ACCESS  not-accessible
            STATUS      current
            DESCRIPTION "Each entry represents connection information
                         of current node to other nodes on the ring."
                  INDEX   { lumProtDestinationIP}
          ::= { lumProtectionSwitchingTable 1 }


         LumProtectionSwitchingEntry ::= SEQUENCE {
                      lumProtDestinationIP           IpAddress,
                      lumProtMeasDestCost            Integer32,
                      lumProtNonRevDestCost          Integer32,
                      lumProtMeasPrefDir             Integer32,
                      lumProtNonRevPrefDir           Integer32
                                           }




      lumProtDestinationIP         OBJECT-TYPE
             SYNTAX     IpAddress
             MAX-ACCESS read-only
             STATUS     current
             DESCRIPTION  "This is the address of the destination
                           node."
            ::= { lumProtectionSwitchingEntry 1 }

      lumProtMeasDestCost         OBJECT-TYPE
             SYNTAX     Integer32
             MAX-ACCESS read-only
             STATUS     current
             DESCRIPTION  "This is the cumulative measured cost per
                           destination for each egress interface of
                           a node."
            ::= { lumProtectionSwitchingEntry 2 }

      lumProtNonRevDestCost         OBJECT-TYPE
             SYNTAX     Integer32
             MAX-ACCESS read-only
             STATUS     current
             DESCRIPTION  "This is the non-revertive cost per
                           destination for each egress interface of
                           a node.  This is used only for
                           non-revertive protection switching."
            ::= { lumProtectionSwitchingEntry 3 }
            
      lumProtMeasPrefDir         OBJECT-TYPE
             SYNTAX     Integer32
             MAX-ACCESS read-only
             STATUS     current
             DESCRIPTION  "This is the interface number corresponding
                           to the preferred direction for data from
                           this node to lumProtDestinationIP based
                           on measured costs."
            ::= { lumProtectionSwitchingEntry 4 }

      lumProtNonRevPrefDir         OBJECT-TYPE
             SYNTAX     Integer32
             MAX-ACCESS read-only
             STATUS     current
             DESCRIPTION  "This is the interface number corresponding
                           to the preferred direction for data from
                           this node to lumProtDestinationIP based
                           on non-revertive costs."
            ::= { lumProtectionSwitchingEntry 5 }


       

     lumRingLinkTable OBJECT-TYPE
             SYNTAX  SEQUENCE OF LumRingLinkEntry 
             MAX-ACCESS not-accessible
             STATUS  current
             DESCRIPTION
                "The Luminous Ring Topology Table."
            ::= { lumTopologyMIB 3   }


         lumRingLinkEntry OBJECT-TYPE
            SYNTAX      LumRingLinkEntry 
            MAX-ACCESS  not-accessible
            STATUS      current
            DESCRIPTION "Each entry represents connection information
                         of every ingress to every ingress node on
                         the ring"
                  INDEX   { lumLinkIngressNodeIP,
                            lumLinkEgressNodeIP,
                            lumLinkIngressInterface,
                            lumLinkEgressInterface  }
          ::= { lumRingLinkTable 1 }


         LumRingLinkEntry ::= SEQUENCE {
                      lumLinkIngressNodeIP    IpAddress,
                      lumLinkEgressNodeIP     IpAddress,
                      lumLinkIngressInterface Integer32,
                      lumLinkEgressInterface  Integer32,
                      lumLinkOperStatus       Integer32,
                      lumLinkNonRevStatus     Integer32,
                      lumLinkAdminStatus      Integer32,
                      lumLinkSyncOperStatus   Integer32,
                      lumLinkSyncNonRevStatus Integer32,
                      lumLinkSyncAdminStatus  Integer32
                                           }




      lumLinkIngressNodeIP         OBJECT-TYPE
             SYNTAX     IpAddress
             MAX-ACCESS read-only
             STATUS     current
             DESCRIPTION  "This is the address of the ingress link
                           node."
            ::= { lumRingLinkEntry 1 }

      lumLinkEgressNodeIP         OBJECT-TYPE
             SYNTAX     IpAddress
             MAX-ACCESS read-only
             STATUS     current
             DESCRIPTION  "This is the address of the egress link
                           node."
            ::= { lumRingLinkEntry 2 }

      lumLinkIngressInterface      OBJECT-TYPE
             SYNTAX     Integer32
             MAX-ACCESS read-only
             STATUS     current
             DESCRIPTION  "This is the interface number (slot number)
                           of the ring transition card connected to
                           the link at the ingress node."
            ::= { lumRingLinkEntry 3 }

      lumLinkEgressInterface      OBJECT-TYPE
             SYNTAX     Integer32
             MAX-ACCESS read-only
             STATUS     current
             DESCRIPTION  "This is the interface number (slot number)
                           of the ring transition card connected to 
                           the link at the egress node."
            ::= { lumRingLinkEntry 4 }

      lumLinkOperStatus      OBJECT-TYPE
             SYNTAX     Integer32
             MAX-ACCESS read-only
             STATUS     current
             DESCRIPTION  "This is the latest measured operational
                           status of the link. It is reported from
                           the ring applications to the shelf manager
                           to the NMS. Currently, traffic congestion
                           is not taken into account in status
                           computations. A bit error rate of
                           a * 10 ^ (-b), where a is greater or
                           equal to 1 and less than 10 and has 3
                           significant digits, is represented to NMS
                           as 1000*b + 100*(10 - a). The minimum
                           value of lumLinkOperStatus is 1000 to
                           show that the link is down, and the
                           maximum value of lumLinkOperStatus is
                           16000 to show a standard operational
                           link."
            ::= { lumRingLinkEntry 5 }

      lumLinkNonRevStatus      OBJECT-TYPE
             SYNTAX     Integer32
             MAX-ACCESS read-only
             STATUS     current
             DESCRIPTION  "This is the minimum value of link
                           operational status reported since the last
                           Revert-To-Measured-Oper-Status command
                           from the NMS.
                           
                           This field is used only for non-revertive
                           protection switching, e.g.
                           lumLinkNonRevStatus will differ from
                           lumLinkOperStatus if a link goes down and
                           then comes back up, since the operator
                           must reactivate a link under such
                           conditions. For revertive protection
                           switching,  this field is equal to
                           lumLinkOperStatus. 
                           This value is set by the ring applications
                           and reported to EMS via the shelf
                           manager."
            ::= { lumRingLinkEntry 6 }

      lumLinkAdminStatus      OBJECT-TYPE
             SYNTAX     Integer32
             MAX-ACCESS read-write
             STATUS     current
             DESCRIPTION  "This is the latest administrative status 
                           of the link set by the operator. It is
                           reported to the ring applications via the
                           shelf manager. 

                           There are several options for this field.
                           If the value of lumLinkAdminStatus is set
                           to 0 by the operator, it is ignored by 
                           the ring applications, e.g. the ring
                           applications use lumLinkOperStatus and
                           lumLinkAdminStatus for all decision-
                           making. If lumLinkAdminStatus is set to
                           a valid lumLinkOperStatus value by
                           the operator, the link is considered to
                           have that bit error rate irrespective of
                           the actual lumLinkOperStatus value. It
                           is expected that the 'a' value of BER
                           need only have one significant digit
                           when entered by the operator."
            ::= { lumRingLinkEntry 7 }

      lumLinkSyncOperStatus      OBJECT-TYPE
             SYNTAX     Integer32
             MAX-ACCESS read-only
             STATUS     current
             DESCRIPTION  "This is a single indicator of whether a 
                           link is an active part of a
                           synchronization path.  
                           This value is set by the ring itself and
                           reported to NMS."
            ::= { lumRingLinkEntry 8 }

      lumLinkSyncNonRevStatus      OBJECT-TYPE
             SYNTAX     Integer32
             MAX-ACCESS read-only
             STATUS     current
             DESCRIPTION  "."
            ::= { lumRingLinkEntry 9 }

      lumLinkSyncAdminStatus      OBJECT-TYPE
             SYNTAX     Integer32
             MAX-ACCESS read-write
             STATUS     current
             DESCRIPTION  "This is the latest administrative status of
                           the link for synchronization set by the
                           operator.  It is to be set by NMS."
            ::= { lumRingLinkEntry 10 }




     lumRingThresholdTable OBJECT-TYPE
             SYNTAX  SEQUENCE OF LumRingThresholdEntry 
             MAX-ACCESS not-accessible
             STATUS  current
             DESCRIPTION
                "The Luminous Ring Threshold Table."
            ::= { lumTopologyMIB 4   }


         lumRingThresholdEntry OBJECT-TYPE
            SYNTAX      LumRingThresholdEntry 
            MAX-ACCESS  not-accessible
            STATUS      current
            DESCRIPTION "Each entry represents threshold values
                         per threshold window on the ring."
                  INDEX   { lumRingThresholdWindow  }
          ::= { lumRingThresholdTable 1 }


         LumRingThresholdEntry ::= SEQUENCE {
                      lumRingThresholdWindow  Integer32,
                      lumRingThresholdValue   Integer32,
                      lumRingThresholdStatus  RowStatus }




      lumRingThresholdWindow         OBJECT-TYPE
             SYNTAX     Integer32
             MAX-ACCESS read-write
             STATUS     current
             DESCRIPTION  "This is the threshold window size."
            ::= { lumRingThresholdEntry 1 }

      lumRingThresholdValue         OBJECT-TYPE
             SYNTAX     Integer32
             MAX-ACCESS read-write
             STATUS     current
             DESCRIPTION  "This is the threshold value for
                           this window."
            ::= { lumRingThresholdEntry 2 }

      lumRingThresholdStatus        OBJECT-TYPE
             SYNTAX     RowStatus
             MAX-ACCESS read-write
             STATUS     current
             DESCRIPTION  "This object is used to create and
                           delete rows in the Threshold Table."
            ::= { lumRingThresholdEntry 3 }



     END
