-- 
-- Copyright 1999 by Fore Systems, Inc. 
-- Converted to SMIv2 rfc 2578,2579,2580 - STD 58
--
-- Copyright 1997-1999 by Fore Systems, Inc.
--
-- This is a FORE-proprietary MIB that facilitates the configuration
-- of FR/ATM and FUNI service and their associated connections. 
-- Users are allowed to define a number of profiles which group
-- a specific sets of configuration parameters that are applicable
-- to either services or connections.
--
-- This MIB contains the following profile tables:
--
-- 1. LMI profile                - service specific
-- 2. FR rate profile            - connection specific
-- 3. FUNI profile               - service specific
-- 4. FRF.8 profile              - connection specific
-- 5. Generic service profile    - service specific 
-- 6. EPD/PPD profile            - connection specific
-- 7. FRF.5 profile              - connection specific
--
-- References:
--
-- Refer to the standard documents, such as FRF.8, FRF.5, FUNI and
-- RFC1604, for background information.
--
-- Row Status:
--
-- Note that a row status is defined in each profile table
-- to facilitate the creation of table entry. Refer to RFC1903
-- for the usage of row status.
--
-- Reference Count:
--
-- Also note that a reference count is defined in each profile
-- table to keep track of how many objects are referring to a
-- specific profile entry. If the reference count of a profile
-- entry is not equal to zero, the profile entry is not allowed
-- to be deleted.
--
-- Directions:
--
-- In the following description, the term "ingress direction" is
-- used to describe the FR-to-ATM direction of an interworking
-- function; the term "egress direction" is used to describe the
-- ATM-to-FR direction of an interworking function.
--
--------------------------------------------------------------------


Fore-Profile-MIB   DEFINITIONS ::= BEGIN

IMPORTS
        Integer32,
        OBJECT-TYPE,
        MODULE-IDENTITY         FROM SNMPv2-SMI
        DisplayString,
        RowStatus               FROM SNMPv2-TC
        frameInternetworking    FROM Fore-Common-MIB;


  foreProfileModule   MODULE-IDENTITY
     LAST-UPDATED    "9704011044-0400"
     ORGANIZATION    "FORE"
     CONTACT-INFO    "
             Postal: FORE Systems Inc.
                     1000 FORE Drive
                     Warrendale, PA 15086-7502
             Tel:    +1 724 742 6900
             Email:  nm_mibs@fore.com
             Web:    http://www.fore.com"
     DESCRIPTION
             "This MIB module defines several profile tables
              that facilitate the creation of FR/ATM and FUNI
              services and connections."
	  ::= { frameInternetworking 4 }


----------------------------------------------------------------------------
 -- The LMI profile table incorporates the information relevant to
 -- the different profiles of FR Link Management Interface protocol,
 -- to be associated to FR/ATM services.
 --

  profileLmiTable     OBJECT-TYPE
      SYNTAX          SEQUENCE OF ProfileLmiEntry
      MAX-ACCESS          not-accessible
      STATUS          current
      DESCRIPTION
        "The LMI profile table."
      ::= { foreProfileModule 1 }

  profileLmiEntry     OBJECT-TYPE
      SYNTAX          ProfileLmiEntry
      MAX-ACCESS          not-accessible
      STATUS          current
      DESCRIPTION
        "An entry in the LMI profile table."
      INDEX   { profileLmiIndex }
      ::= { profileLmiTable 1 }

 ProfileLmiEntry ::= SEQUENCE {
      profileLmiIndex     Integer32,
      profileLmiRowStatus RowStatus,
      profileLmiName      DisplayString,
      profileLmiFlavour   INTEGER,
      profileLmiT391      Integer32,
      profileLmiN391      Integer32,
      profileLmiT392      Integer32,
      profileLmiN392      Integer32,
      profileLmiN393      Integer32,
      profileLminT3       Integer32,
      profileLmiDirection INTEGER,
      profileLmiRole      INTEGER,
      profileLmiRefCnt    Integer32
 }

 profileLmiIndex        OBJECT-TYPE
     SYNTAX             Integer32
     MAX-ACCESS             read-only
     STATUS             current
     DESCRIPTION
       "This objects identifies the index of a profile entry in this
        table."
     ::= { profileLmiEntry 1 }

 profileLmiRowStatus   OBJECT-TYPE
     SYNTAX            RowStatus
     MAX-ACCESS            read-create
     STATUS            current
     DESCRIPTION
       "This object is used to create new rows and delete existing
        rows in this table."
     ::= { profileLmiEntry 2 }

 profileLmiName         OBJECT-TYPE
     SYNTAX             DisplayString
     MAX-ACCESS             read-create
     STATUS             current
     DESCRIPTION
       "This object specifies the symbolic name assigned to
        this profile for user reference."
     ::= { profileLmiEntry 3 }

 profileLmiFlavour      OBJECT-TYPE
     SYNTAX             INTEGER {
                                none      (1),
                                lmi       (2),
                                t1617d    (3),
                                t1617b    (4),
                                q933a     (5)
                        }
     MAX-ACCESS             read-create
     STATUS             current
     DESCRIPTION
       "This object specifies the type of the LMI protocol used 
        over this FR service. This object corresponds to 
        frLportVCSigProtocol in RFC1604 and frDlcmiState in
        RFC1315."
     DEFVAL { q933a }
     ::= { profileLmiEntry 4 }

 profileLmiT391         OBJECT-TYPE
     SYNTAX             Integer32 (5..30)
     MAX-ACCESS             read-create
     STATUS             current
     DESCRIPTION
       "The value of this object identifies the User-side
        T391 link integrity verification polling timer
        value (in seconds) for this UNI/NNI logical port. 
        If the logical port is not performing user-side
        procedures, then this value is equal to noSuchName.
        This object applies to Q.933 Annex A and T1.617 Annex D.
        This object corresponds to frMgtVCSigUserT391 in RFC1604
        and frDlcmiPollingInterval in RFC1315."
     DEFVAL { 10 }
     ::= { profileLmiEntry 5 }

 profileLmiN391         OBJECT-TYPE
     SYNTAX             Integer32 (1..255)
     MAX-ACCESS             read-create
     STATUS             current
     DESCRIPTION
       "The value of this object identifies the User-side
        N391 full status polling cycle value for this
        UNI/NNI logical port.  If the logical port is not
        performing user-side procedures, then this value
        is equal to noSuchName. This object applies to
        Q.933 Annex A and T1.617 Annex D. This object 
        corresponds to frMgtVCSigUserN391 in RFC1604 and
        frDlcmiFullEnquiryInterval."
     DEFVAL { 6 }
     ::= { profileLmiEntry 6 }

 profileLmiT392         OBJECT-TYPE
     SYNTAX             Integer32 (5..30)
     MAX-ACCESS             read-create
     STATUS             current
     DESCRIPTION
       "The value of this object identifies the Network-
        side T392 polling verification timer value in seconds
        (nT2 for LMI)  for this UNI/NNI logical port.  If the
        logical port is not performing network-side
        procedures, then this value is equal to noSuchName.
        This object applies to Q.933 Annex A, LMI and 
        T1.617 Annex D. This object corresponds to 
        frMgtVCSigNetT392 in RFC1604."
     DEFVAL { 15 }
     ::= { profileLmiEntry 7 }

 profileLmiN392         OBJECT-TYPE
     SYNTAX             Integer32 (1..10)
     MAX-ACCESS             read-create
     STATUS             current
     DESCRIPTION
       "The value of this object identifies the Network-
        side N392 error threshold value (nN2 for LMI) for
        this UNI/NNI logical port.  If the logical port is
        not performing network-side procedures, then this
        value is equal to noSuchName. This object applies
        to Q.933 Annex A, T1.617 Annex D and LMI. This 
        object corresponds to frMgtVCSigNetN392 and
        frMgtVCSigUserN392 when the LMI role is network
        and user respectively in RFC1604, and
        frDlcmiErrorThreshold in RFC1315."
     DEFVAL { 3 }
     ::= { profileLmiEntry 8 }

 profileLmiN393         OBJECT-TYPE
     SYNTAX             Integer32 (1..10)
     MAX-ACCESS             read-create
     STATUS             current
     DESCRIPTION
       "The value of this object identifies the Network-
        side N393 monitored events count value (nN3 for
        LMI) for this UNI/NNI logical port.  If the
        logical port is not performing network-side
        procedures, then this value is equal to noSuchName.
        This object applies to Q.933 Annex A, LMI and
        T1.617 Annex D. This object corresponds to 
        frMgtVCSigNetN393 and frMgtVCSigUserN393 when the
        LMI role is network and user respectively in RFC1604,
        and frDlcmiMonitoredEvents in RFC1315."
     DEFVAL { 4 }
     ::= { profileLmiEntry 9 }

 profileLminT3          OBJECT-TYPE
     SYNTAX             Integer32 (5 | 10 | 15 | 20 | 25 | 30)
     MAX-ACCESS             read-create
     STATUS             current
     DESCRIPTION
       "The value of this object identifies the Network-side 
        nT3 timer in seconds (for nN4 status enquires received) 
        value for this FR service. This object applies only to 
        LMI(STRATACOM) flavour. The allowable values include
        5, 10, 15, 20, 25 and 30 seconds. This object corresponds
        to frMgtVCSigNetnT3 in RFC1604."
     DEFVAL { 20 }
     ::= { profileLmiEntry 10 }


 profileLmiDirection    OBJECT-TYPE
     SYNTAX             INTEGER {
                               uni (1),
                               bi  (2)
                        }
     MAX-ACCESS             read-create
     STATUS             current
     DESCRIPTION
       "The value of this object identifies the Local
        In-Channel Signaling Procedure that is used for
        this UNI/NNI logical port.  The UNI/NNI logical
        port can be performing only user-to-network
        network-side procedures or bidirectional
        procedures.This object corresponds to frMgtVCSigProced
        in RFC1604."
     DEFVAL { bi }
     ::= { profileLmiEntry 11 }

 profileLmiRole         OBJECT-TYPE
     SYNTAX             INTEGER {
                                user    (1),
                                network (2)
                        }
     MAX-ACCESS             read-create
     STATUS             current
     DESCRIPTION
       "This object specifies the role of operation of this 
        FR service - user (DTE) or network (DCE)"
     DEFVAL { network }
     ::= { profileLmiEntry 12 }

 profileLmiRefCnt     OBJECT-TYPE
     SYNTAX             Integer32
     MAX-ACCESS             read-only
     STATUS             current
     DESCRIPTION
       "This object identifies the number of services
        that are currently referring to this profile."
     DEFVAL { 0 }
     ::= { profileLmiEntry 13 }


------------------------------------------------------------------------
-- The FR rate profile table incorporates the information
-- relevant to defined sets of FR rate enforcement and rate 
-- adaptation parameters used by FR connections

  profileFrRateTable    OBJECT-TYPE
      SYNTAX            SEQUENCE OF ProfileFrRateEntry
      MAX-ACCESS            not-accessible
      STATUS            current
      DESCRIPTION
    "The FR rate profile table."
  ::= { foreProfileModule 2 }


  profileFrRateEntry    OBJECT-TYPE
      SYNTAX            ProfileFrRateEntry
      MAX-ACCESS            not-accessible
      STATUS            current
      DESCRIPTION
        "An entry in the FR rate profile table."
      INDEX   { profileFrRateIndex }
      ::= { profileFrRateTable 1 }

 ProfileFrRateEntry ::= 
        SEQUENCE {
                profileFrRateIndex     Integer32,
                profileFrRateRowStatus RowStatus,
                profileFrRateName      DisplayString,
                profileFrRateInBc      Integer32,
                profileFrRateInBe      Integer32,
                profileFrRateInCir     Integer32,
                profileFrRateOutBc     Integer32,
                profileFrRateOutBe     Integer32,
                profileFrRateOutCir    Integer32,
                profileFrRateMinBc     Integer32,
                profileFrRateCmPeriod  Integer32,
                profileFrRateRefCnt    Integer32
        }

 profileFrRateIndex     OBJECT-TYPE
     SYNTAX             Integer32
     MAX-ACCESS             read-only
     STATUS             current
     DESCRIPTION
       "This object identifies the index of a profile entry in this
        table."
     ::= { profileFrRateEntry 1 }

 profileFrRateRowStatus  OBJECT-TYPE
     SYNTAX              RowStatus
     MAX-ACCESS              read-create
     STATUS              current
     DESCRIPTION
       "This object is used to create new rows and delete existing
        rows in this table."
     ::= { profileFrRateEntry 2 }

 profileFrRateName      OBJECT-TYPE
     SYNTAX             DisplayString
     MAX-ACCESS             read-create
     STATUS             current
     DESCRIPTION
       "This object identifies the symbolic name assigned to this 
        profile used for user reference."
     ::= { profileFrRateEntry 3 }

 profileFrRateInBc      OBJECT-TYPE
     SYNTAX             Integer32
     MAX-ACCESS             read-create
     STATUS             current
     DESCRIPTION
       "This object represents the committed burst size (bits) in the 
        ingress direction of a connection. This object corresponds to
        frPVCEndptInBc in RFC1604 and frCircuitCommittedBurst in
        RFC1315."
     ::= { profileFrRateEntry 4 }

 profileFrRateInBe      OBJECT-TYPE
     SYNTAX             Integer32
     MAX-ACCESS             read-create
     STATUS             current
     DESCRIPTION
       "This object represents the excess burst size (bits) in the 
        ingress direction of a connection. This object corresponds
        to frPVCEndptInBe in RFC1604 and frCircuitExcessBurst in
        RFC1315."
     ::= { profileFrRateEntry 5 }

 profileFrRateInCir     OBJECT-TYPE
     SYNTAX             Integer32
     MAX-ACCESS             read-create
     STATUS             current
     DESCRIPTION
       "This object represents the committed information rate (kbps) 
        in the ingress direction of a connection. This object
        corresponds to frPVCEndptInCIR in RFC1604 and 
        frCircuitThroughput in RFC1315."
     ::= { profileFrRateEntry 6 }

 profileFrRateOutBc     OBJECT-TYPE
     SYNTAX             Integer32
     MAX-ACCESS             read-create
     STATUS             current
     DESCRIPTION
       "This object represents the committed burst size (bits) in the 
        egress direction of a connection. This object corresponds
        frPVCEndptOutBc in RFC1604."
     ::= { profileFrRateEntry 7 }

 profileFrRateOutBe     OBJECT-TYPE
     SYNTAX             Integer32
     MAX-ACCESS             read-create
     STATUS             current
     DESCRIPTION
       "This object represents the excess burst size (bits) in the 
        egress direction of a connection. This object corresponds
        frPVCEndptOutBe in RFC1604."
     ::= { profileFrRateEntry 8 }

 profileFrRateOutCir    OBJECT-TYPE
     SYNTAX             Integer32
     MAX-ACCESS             read-create
     STATUS             current
     DESCRIPTION
       "This object represents the committed information rate (kbps) 
        in the egress direction of a connection. This object 
        corresponds frPVCEndptOutCIR in RFC1604."
     ::= { profileFrRateEntry 9 }

 profileFrRateMinBc     OBJECT-TYPE
     SYNTAX             Integer32
     MAX-ACCESS             read-create
     STATUS             current
     DESCRIPTION
       "This object represents the minimum committed burst size (bits) 
        which can be set on a connection by rate adaptation."
     DEFVAL { 1000 }
     ::= { profileFrRateEntry 10 }

 profileFrRateCmPeriod  OBJECT-TYPE
     SYNTAX             Integer32
     MAX-ACCESS             read-create
     STATUS             current
     DESCRIPTION
       "This object represents the time period (msec) during which 
        BECNs are monitored before the rate adaptation mechanism decides
        to change the current committed burst size in the egress direction."
     DEFVAL { 1000 }
     ::= { profileFrRateEntry 11 }

 profileFrRateRefCnt    OBJECT-TYPE
     SYNTAX             Integer32
     MAX-ACCESS             read-only
     STATUS             current
     DESCRIPTION
       "This object identifies the number of connections that are
        currently referring to this profile entry."
     DEFVAL { 0 }
     ::= { profileFrRateEntry 12 }



----------------------------------------------------------------------------
 -- The FUNI profile table incorporates the information
 -- relevant to defined sets of FUNI service parameters. 

  profileFuniTable      OBJECT-TYPE
      SYNTAX            SEQUENCE OF ProfileFuniEntry
      MAX-ACCESS            not-accessible
      STATUS            current
      DESCRIPTION
        "The FUNI profile table."
      ::= { foreProfileModule 3 }

  profileFuniEntry      OBJECT-TYPE
      SYNTAX            ProfileFuniEntry
      MAX-ACCESS            not-accessible
      STATUS            current
      DESCRIPTION
        "An entry in the FUNI profile table."
      INDEX   { profileFuniIndex }
      ::= { profileFuniTable 1 }

 ProfileFuniEntry ::= SEQUENCE {
      profileFuniIndex         Integer32,
      profileFuniRowStatus     RowStatus,
      profileFuniName          DisplayString,
      profileFuniIlmiVpi       Integer32,
      profileFuniIlmiVci       Integer32,
      profileFuniSigVpi        Integer32,
      profileFuniSigVci        Integer32,
      profileFuniMinVci        Integer32,
      profileFuniMaxVci        Integer32,
      profileFuniIlmiSupport   INTEGER,
      profileFuniSigSupport    INTEGER,
      profileFuniOamSupport    INTEGER,
      profileFuniActiveVpiBits Integer32,
      profileFuniActiveVciBits Integer32,
      profileFuniConfMode      INTEGER,
      profileFuniFcsBits       INTEGER,
      profileFuniHdrBytes      INTEGER,
      profileFuniAal34Support  INTEGER,
      profileFuniRefCnt        Integer32
 }

 profileFuniIndex       OBJECT-TYPE
     SYNTAX             Integer32
     MAX-ACCESS             read-only
     STATUS             current
     DESCRIPTION
       "This object identifies the index of a profile entry in
        this table."
     ::= { profileFuniEntry 1 }

 profileFuniRowStatus   OBJECT-TYPE
     SYNTAX             RowStatus
     MAX-ACCESS             read-create
     STATUS             current
     DESCRIPTION
       "This object is used to create new rows and delete existing
        rows in this table."
     ::= { profileFuniEntry 2 }

 profileFuniName        OBJECT-TYPE
     SYNTAX             DisplayString
     MAX-ACCESS             read-create
     STATUS             current
     DESCRIPTION
       "This object specifies the symbolic name assigned to this
        profile for user reference."
     ::= { profileFuniEntry 3 }

 profileFuniIlmiVpi     OBJECT-TYPE
     SYNTAX             Integer32 
     MAX-ACCESS             read-create
     STATUS             current
     DESCRIPTION
       "This object represents VPI value used by ILMI
        over this FUNI interface. This object corresponds
        to funiIfConfIlmiVpi in FUNI MIB."
     DEFVAL { 0 }
     ::= { profileFuniEntry 4 }

 profileFuniIlmiVci     OBJECT-TYPE
     SYNTAX             Integer32
     MAX-ACCESS             read-create
     STATUS             current
     DESCRIPTION
       "This object represents VCI value used by ILMI
        over this FUNI service. This object corresponds to
        funiIfConfIlmiVci in FUNI MIB."
     DEFVAL { 16 }
     ::= { profileFuniEntry 5 }

 profileFuniSigVpi      OBJECT-TYPE
     SYNTAX             Integer32 
     MAX-ACCESS             read-create
     STATUS             current
     DESCRIPTION
       "This object represents VPI value used for the signalling
        channel over this FUNI service. This object corresponds to
        funiIfConfSigVpi in FUNI MIB."
     DEFVAL { 0 }
     ::= { profileFuniEntry 6 }

 profileFuniSigVci      OBJECT-TYPE
     SYNTAX             Integer32
     MAX-ACCESS             read-create
     STATUS             current
     DESCRIPTION
       "This object represents VCI value used for the signalling
        channel over this FUNI service. This object corresponds to
        funiIfConfSigVci in FUNI MIB."
     DEFVAL { 5 }
     ::= { profileFuniEntry 7 }

 profileFuniMinVci      OBJECT-TYPE
     SYNTAX             Integer32 (32..63)
     MAX-ACCESS             read-create
     STATUS             current
     DESCRIPTION
       "This object represents minimal numeric value allowed to be
        used as a VCI on any user connection over this FUNI service."
     DEFVAL { 32 }
     ::= { profileFuniEntry 8 }

 profileFuniMaxVci      OBJECT-TYPE
     SYNTAX             Integer32 (32..63)
     MAX-ACCESS             read-create
     STATUS             current
     DESCRIPTION
       "This object represents maximal numeric value allowed to be
        used as a VCI on any user connection over this FUNI service."
     DEFVAL { 63 }
     ::= { profileFuniEntry 9 }

 profileFuniIlmiSupport    OBJECT-TYPE
     SYNTAX                INTEGER {
                                enabled  (1),
                                disabled (2)
                           }
     MAX-ACCESS                read-create
     STATUS                current
     DESCRIPTION
       "This object specifies that an ILMI instance is to be
        supported on this FUNI service if the mode is set to enabled.
        This object corresponds to funiIfConfIlmiSupport in FUNI MIB."
     DEFVAL { disabled }
     ::= { profileFuniEntry 10 }

 profileFuniSigSupport     OBJECT-TYPE
     SYNTAX                INTEGER {
                                enabled  (1),
                                disabled (2)
                           }
     MAX-ACCESS                read-create
     STATUS                current
     DESCRIPTION
       "This object specifies that a signalling instance is to
        be supported on this FUNI service if the mode is set to enabled.
        This object corresponds to funiIfConfSigSupport in FUNI MIB."
     DEFVAL { disabled }
     ::= { profileFuniEntry 11 }

 profileFuniOamSupport     OBJECT-TYPE
     SYNTAX                INTEGER {
                                enabled  (1),
                                disabled (2)
                           }
     MAX-ACCESS                read-create
     STATUS                current
     DESCRIPTION
       "This object specifies that OAM cells and frames are to be
        transferred on this FUNI service if the mode is set to enabled.
        This object corresponds to funiIfConfOamSupport in FUNI MIB."
     DEFVAL { disabled }
     ::= { profileFuniEntry 12 }

 profileFuniActiveVpiBits     OBJECT-TYPE
     SYNTAX                   Integer32 (0..8)
     MAX-ACCESS                   read-create
     STATUS                   current
     DESCRIPTION
       "The value of this object identifies the maximum number of 
        active VPI bits configured for use at this FUNI interface.
        At the ATM FUNI, this value will be smaller than or equal to
        4 and 8 when the FUNI header size is two and four bytes respectively,
        as specified by the profile attribute profileFuniConfMode. This 
        object corresponds to atmInterfaceMaxActiveVpiBits in the ATOM MIB."
     DEFVAL { 4 }
     ::= { profileFuniEntry 13 }

 profileFuniActiveVciBits     OBJECT-TYPE
     SYNTAX                   Integer32 (0..16)
     MAX-ACCESS                   read-create
     STATUS                   current
     DESCRIPTION
       "The value of this object identifies the maximum number of 
        active VCI bits configured for use at this FUNI interface.
        At the ATM FUNI, this value will be smaller than or equal to 
        6 and 16 when the FUNI header size is two and four bytes respectively,
        as specified by the profile attribute profileFuniConfMode. This 
        object corresponds to atmInterfaceMaxActiveVciBits in the ATOM MIB."
     DEFVAL { 6 }
     ::= { profileFuniEntry 14 }

 profileFuniConfMode    OBJECT-TYPE
     SYNTAX             INTEGER {
                                mode1a(1),
                                mode1b(2),
                                mode3(3),
                                mode4(4)
                        }                 
     MAX-ACCESS             read-create
     STATUS             current
     DESCRIPTION
       "The value of this object specifies whether a 2 or 4 byte header
        is present in each FUNI frame header over a FUNI service. For
        mode1a, mode1b and mode 3, a 2-byte header is used. For mode 4,
        a 4-byte header is used. This object corresponds to 
        funiIfConfMode in FUNI MIB."
     DEFVAL { mode1a }
     ::= { profileFuniEntry 15 }


 profileFuniFcsBits     OBJECT-TYPE
     SYNTAX             INTEGER {
                                fcsBits16(1),
                                fcsBits32(2)
                        }
     MAX-ACCESS             read-create
     STATUS             current
     DESCRIPTION      
       "This object specifies whether a 16- or 32-bit FCS is used
        in each FUNI frame header over this FUNI logical interface."
     DEFVAL { fcsBits16 }
     ::= { profileFuniEntry 16 }

 profileFuniHdrBytes    OBJECT-TYPE
     SYNTAX             INTEGER {
                                hdrBytes2(1),
                                hdrBytes4(2)
                        }
     MAX-ACCESS             read-create
     STATUS             current
     DESCRIPTION      
       "This object specifies whether a 2- or 4-bytes header is used
        in each FUNI frame header over this FUNI logical interface."
     DEFVAL { hdrBytes2 }
     ::= { profileFuniEntry 17 }

 profileFuniAal34Support OBJECT-TYPE
     SYNTAX              INTEGER {
                                 enabled(1),
                                 disabled(2)
                         }
     MAX-ACCESS              read-create
     STATUS              current
     DESCRIPTION      
       "This object specifies whether support for AAL3/4 VCCs shall
        be allowed on this FUNI logical interface. A FUNI logical
        interface that cannot support AAL3/4 VCCs must only allow
        the value disabled(2)."
     DEFVAL { disabled }
     ::= { profileFuniEntry 18 }


 profileFuniRefCnt      OBJECT-TYPE
     SYNTAX             Integer32
     MAX-ACCESS             read-only
     STATUS             current
     DESCRIPTION
       "The value of this object identifies the number of services that
        are referring to this profile."
     DEFVAL { 0 }
     ::= { profileFuniEntry 19 }


------------------------------------------------------------------------
 -- The FRF.8 profile table incorporates the information
 -- relevant to defined sets of FRF.8 parameters used by
 -- FR/ATM service interworking connections.

 profileFrf8Table            OBJECT-TYPE
     SYNTAX                  SEQUENCE OF ProfileFrf8Entry
     MAX-ACCESS                  not-accessible
     STATUS                  current
     DESCRIPTION
       "The FRF.8 profile table."
     ::= { foreProfileModule 4 }

  profileFrf8Entry          OBJECT-TYPE
      SYNTAX                ProfileFrf8Entry
      MAX-ACCESS                not-accessible
      STATUS                current
      DESCRIPTION
        "An entry in the FRF.8 profile table."
      INDEX   { profileFrf8Index }
      ::= { profileFrf8Table 1 }

 ProfileFrf8Entry ::= SEQUENCE {
      profileFrf8Index          Integer32,
      profileFrf8RowStatus      RowStatus,
      profileFrf8Name           DisplayString,
      profileFrf8DeMode         INTEGER,
      profileFrf8ClpMode        INTEGER,
      profileFrf8FecnMode       INTEGER,
      profileFrf8DefaultDe      Integer32,
      profileFrf8DefaultClp     Integer32,
      profileFrf8Protocols      Integer32,
      profileFrf8RefCnt         Integer32
 }

 profileFrf8Index       OBJECT-TYPE
     SYNTAX             Integer32
     MAX-ACCESS             read-only
     STATUS             current
     DESCRIPTION
       "This object identifies the index of a profile in this
        table."
     ::= { profileFrf8Entry 1 }

 profileFrf8RowStatus   OBJECT-TYPE
     SYNTAX             RowStatus
     MAX-ACCESS             read-create
     STATUS             current
     DESCRIPTION
       "This object is used to create new rows and delete existing
        rows in this table."
     ::= { profileFrf8Entry 2 }

 profileFrf8Name        OBJECT-TYPE
     SYNTAX             DisplayString
     MAX-ACCESS             read-create
     STATUS             current
     DESCRIPTION
       "This object specifies the symbolic name assigned to this
        profile for user reference."
     ::= { profileFrf8Entry 3 }

 profileFrf8DeMode      OBJECT-TYPE
     SYNTAX             INTEGER {
                                mapped  (1),
                                ignored (2)
                        }
     MAX-ACCESS             read-create
     STATUS             current
     DESCRIPTION
        "If the DE mode is set to mapped, the DE field in the Q922
         core frame is mapped to the ATM CLP filled of every cell
         generated by the segmentation process of the AAL5 PDU
         containing the information of that frame. Otherwise, the
         ATM CLP of every ATM cell generated by the segmentation
         process of the AAL5 PDU containing the information of that
         frame is set to a constant value specified by the configuration
         parameter profileFrf8DefaultClp."
     DEFVAL { mapped }
     ::= { profileFrf8Entry 4 }

 profileFrf8ClpMode     OBJECT-TYPE
     SYNTAX             INTEGER {
                                mapped  (1),
                                ignored (2)
                        }
     MAX-ACCESS             read-create
     STATUS             current
     DESCRIPTION
        "If the CLP mode is set to mapped, then the FR/ATM service
         interworking function will set the DE field of the Q922 core
         frame, provided that one or more cells belonging to this
         frame has its CLP field set. Otherwise, the DE field of the
         Q922 core frame is set to a constant value specified by the
         configuration parameter profileFrf8DefaultDe."
     DEFVAL { mapped }
     ::= { profileFrf8Entry 5 }

 profileFrf8FecnMode    OBJECT-TYPE
     SYNTAX             INTEGER {
                                mapped  (1),
                                ignored (2)
                        }
     MAX-ACCESS             read-create
     STATUS             current
     DESCRIPTION
        "If the Fecn mode is set to mapped, the FECN field in the
         Q922 core frame is mapped to the ATM EFCI field of every
         cell generated by the segmentation process of the AAL5
         PDU containing the information of that frame. This mode
         provides congestion indication to the end-points where
         higher layer protocol entities might be involved in
         traffic control mechanisms. Otherwise, the EFCI field of
         cells generated by the segmentation process of the AAL5
         PDU containing the information of the frame is always
         set to congestion-not-experienced."         
     DEFVAL { mapped }
     ::= { profileFrf8Entry 6 }

 profileFrf8DefaultDe   OBJECT-TYPE
     SYNTAX             Integer32 (0..1)
     MAX-ACCESS             read-create
     STATUS             current
     DESCRIPTION
       "This object represents the DE bit value of all generated FR
        frame headers if the CLP mode is set to ignored."
     DEFVAL { 0 }
     ::= { profileFrf8Entry 7 }

 profileFrf8DefaultClp  OBJECT-TYPE
     SYNTAX             Integer32 (0..1)
     MAX-ACCESS             read-create
     STATUS             current
     DESCRIPTION
       "This object represents the CLP bit value of all generated ATM
        cell headers if the DE mode is set to ignored."
     DEFVAL { 0 }
     ::= { profileFrf8Entry 8 }

 profileFrf8Protocols   OBJECT-TYPE
     SYNTAX             Integer32 (0..8191)
     MAX-ACCESS         read-create
     STATUS             current
     DESCRIPTION
       "This object represents a binary map which lists all possible
       encapsulation translation protocols over this FRF.8 IWF
       instance. Any combination of the specified encapsulation modes
       will be supported. The binary map assignment is defined as
       below:
       ethernet      (0000000000001)
       ethernetFcs   (0000000000010)
       tokenRing     (0000000000100)
       tokenRingFcs  (0000000001000)
       ipRouted      (0000000010000)
       arp           (0000000100000)
       ipx           (0000001000000)
       sna	     (0000010000000) 
       fddi          (0000100000000) 
       fddiFcs       (0001000000000)
       x.25/75       (0010000000000)
       802.6         (0100000000000)
       routedIso     (1000000000000)
       or any combinations of the binary map. The allowable range of
       the input is from 0 to 8191. This object corresponds to 
       frf8ProtProtocol in fore-frf8 MIB."
     DEFVAL { 0 }
     ::= { profileFrf8Entry 9 }

 profileFrf8RefCnt      OBJECT-TYPE
     SYNTAX             Integer32
     MAX-ACCESS             read-only
     STATUS             current
     DESCRIPTION
       "The value of this object identifies the number of connections that
       are currently referring to this profile."
     DEFVAL { 0 }
     ::= { profileFrf8Entry 10 }


----------------------------------------------------------------------------
 -- The generic service profile table incorporates the configuration
 -- parameters that are common between FR/ATM Service Interworking
 -- and FUNI services.


 profileServiceTable        OBJECT-TYPE
     SYNTAX                 SEQUENCE OF ProfileServiceEntry
     MAX-ACCESS                 not-accessible
     STATUS                 current
     DESCRIPTION
       "The generic service profile table."
     ::= { foreProfileModule 5 }

  profileServiceEntry       OBJECT-TYPE
      SYNTAX                ProfileServiceEntry
      MAX-ACCESS                not-accessible
      STATUS                current
      DESCRIPTION
        "An entry in the generic service profile table."
      INDEX   { profileServiceIndex }
      ::= { profileServiceTable 1 }


 ProfileServiceEntry ::= SEQUENCE {
      profileServiceIndex            Integer32,
      profileServiceRowStatus        RowStatus,
      profileServiceName             DisplayString,
      profileServiceAccRate          Integer32,
      profileServiceMaxPayloadSize   Integer32,
      profileServiceMaxVccs          Integer32,
      profileServiceInBwOb           Integer32,
      profileServiceOutBwOb          Integer32,
      profileServiceRefCnt           Integer32
 }

 profileServiceIndex        OBJECT-TYPE
     SYNTAX                 Integer32
     MAX-ACCESS                 read-only
     STATUS                 current
     DESCRIPTION
       "This object identifies the index of a profile in this
        table."
     ::= { profileServiceEntry 1 }

 profileServiceRowStatus     OBJECT-TYPE
     SYNTAX                  RowStatus
     MAX-ACCESS                  read-create
     STATUS                  current
     DESCRIPTION
       "This object is used to create new rows and delete existing
        rows in this table."
     ::= { profileServiceEntry 2 }

 profileServiceName         OBJECT-TYPE
     SYNTAX                 DisplayString
     MAX-ACCESS                 read-create
     STATUS                 current
     DESCRIPTION
       "This object specifies the symbolic name assigned to this
        profile for user reference."
     ::= { profileServiceEntry 3 }

 profileServiceAccRate     OBJECT-TYPE
     SYNTAX                Integer32
     MAX-ACCESS                read-create
     STATUS                current
     DESCRIPTION
       "This object represents the access rate of the service (kbps)."
     ::= { profileServiceEntry 4 }

 profileServiceMaxVccs    OBJECT-TYPE
     SYNTAX               Integer32 
     MAX-ACCESS               read-create
     STATUS               current
     DESCRIPTION 
       "The maximum number of virtual circuits supported in this
        service. This object corresponds to frDlcmiMaxSupportedVCs
        in RFC1315 and funiIfExtConfVccs in fore-funi MIB."
     DEFVAL { 10 }
     ::= { profileServiceEntry 5 }

 profileServiceMaxPayloadSize     OBJECT-TYPE
     SYNTAX                       Integer32
     MAX-ACCESS                       read-create
     STATUS                       current
     DESCRIPTION
       "This object represents the maximum payload size (bytes)
        supported by the service. This object corresponds to
        frPVCEndptInMaxFrameSize and frPVCEndptOutMaxFrameSize
        in RFC1604."
     DEFVAL { 4096 }
     ::= { profileServiceEntry 6 }

 profileServiceInBwOb      OBJECT-TYPE
     SYNTAX                Integer32 (1..500)
     MAX-ACCESS                read-create
     STATUS                current
     DESCRIPTION
       "This object represents the bandwidth overbooking (percentage)
        of the service in the inbound direction. If the percentage is
        bigger than 100%, it is overbooking; otherwise it is 
        underbooking."
     DEFVAL { 100 }
     ::= { profileServiceEntry 7 }

 profileServiceOutBwOb      OBJECT-TYPE
     SYNTAX                 Integer32 (1..500)
     MAX-ACCESS                 read-create
     STATUS                 current
     DESCRIPTION
       "This object represents the bandwidth overbooking (percentage)
        of the service in the outbound direction. If the percentage is
        bigger than 100%, it is overbooking; otherwise it is
        underbooking."
     DEFVAL { 100 }
     ::= { profileServiceEntry 8 }

 profileServiceRefCnt   OBJECT-TYPE
     SYNTAX             Integer32
     MAX-ACCESS             read-only
     STATUS             current
     DESCRIPTION
       "The value of this object identifies the number of services that
       are currently referring to this profile."
     DEFVAL { 0 }
     ::= { profileServiceEntry 9 }


----------------------------------------------------------------------------
 -- The EPD/PPD profile table incorporates the information relevant
 -- to defined set of EPD/PPD controller configuration parameters, which are 
 -- FRAM netmod specific, used to control traffic discard for FR/ATM and 
 -- FUNI connections.


 profileEpdPpdTable         OBJECT-TYPE
     SYNTAX                 SEQUENCE OF ProfileEpdPpdEntry
     MAX-ACCESS                 not-accessible
     STATUS                 current
     DESCRIPTION
       "The EPD/PPD profile table."
     ::= { foreProfileModule 6 }

  profileEpdPpdEntry        OBJECT-TYPE
      SYNTAX                ProfileEpdPpdEntry
      MAX-ACCESS                not-accessible
      STATUS                current
      DESCRIPTION
        "An entry in the EPD/PPD profile table."
      INDEX   { profileEpdPpdIndex }
      ::= { profileEpdPpdTable 1 }

 ProfileEpdPpdEntry ::= SEQUENCE {
      profileEpdPpdIndex            Integer32,
      profileEpdPpdRowStatus        RowStatus,
      profileEpdPpdName             DisplayString,
      profileEpdPpdPriority         INTEGER,
      profileEpdPpdClp0Epd          INTEGER,
      profileEpdPpdClp1Ppd          INTEGER,
      profileEpdPpdClp1Epd          INTEGER,
      profileEpdPpdRefCnt           Integer32
 }

 profileEpdPpdIndex     OBJECT-TYPE
     SYNTAX             Integer32
     MAX-ACCESS             read-only
     STATUS             current
     DESCRIPTION
       "This object identifies the index of a profile in this
        table."
     ::= { profileEpdPpdEntry 1 }

 profileEpdPpdRowStatus  OBJECT-TYPE
     SYNTAX              RowStatus
     MAX-ACCESS              read-create
     STATUS              current
     DESCRIPTION
       "This object is used to create new rows and delete existing
        rows in this table."
     ::= { profileEpdPpdEntry 2 }

 profileEpdPpdName      OBJECT-TYPE
     SYNTAX             DisplayString
     MAX-ACCESS             read-create
     STATUS             current
     DESCRIPTION
       "This object specifies the symbolic name assigned to this
        profile for user reference."
     ::= { profileEpdPpdEntry 3 }

 profileEpdPpdPriority  OBJECT-TYPE
     SYNTAX             INTEGER {
                                low (1),
                                high (2)
                        }
     MAX-ACCESS             read-create
     STATUS             current
     DESCRIPTION
       "This object specifies the EPD/PPD priority queue the
        connection is assigned."
     DEFVAL { low }
     ::= { profileEpdPpdEntry 4 }

 profileEpdPpdClp0Epd  OBJECT-TYPE
     SYNTAX            INTEGER {
                                enabled (1),
                                disabled (2)
                       }
     MAX-ACCESS            read-create
     STATUS            current
     DESCRIPTION
       "This object specifies whether the EPD/PPD controller
        discards CLP=0 traffic after the Clp0Epd threshold has been hit."
     DEFVAL { enabled }
     ::= { profileEpdPpdEntry 5 }

 profileEpdPpdClp1Ppd  OBJECT-TYPE
     SYNTAX            INTEGER {
                                enabled (1),
                                disabled (2)
                       }       
     MAX-ACCESS            read-create
     STATUS            current
     DESCRIPTION
       "This object specifies whether the EPD/PPD controller
        discards CLP=1 traffic after the Clp1Ppd threshold has been hit."
     DEFVAL { enabled }
     ::= { profileEpdPpdEntry 6 }

 profileEpdPpdClp1Epd  OBJECT-TYPE
     SYNTAX            INTEGER {
                                enabled (1),
                                disabled (2)
                       }       
     MAX-ACCESS            read-create
     STATUS            current
     DESCRIPTION
       "This object specifies whether the EPD/PPD controller
        discards CLP=1 traffic after the Clp1Epd threshold has been hit."
     DEFVAL { enabled }
     ::= { profileEpdPpdEntry 7 }

 profileEpdPpdRefCnt    OBJECT-TYPE
     SYNTAX             Integer32
     MAX-ACCESS             read-only
     STATUS             current
     DESCRIPTION
       "The value of this object identifies the number of connections that
        are currently referring to this profile."
     DEFVAL { 0 }
     ::= { profileEpdPpdEntry 8 }

------------------------------------------------------------------------
 -- The FRF.5 profile table incorporates the information
 -- relevant to defined sets of FRF.5 parameters used by
 -- FR/ATM network interworking connections.

 profileFrf5Table            OBJECT-TYPE
     SYNTAX                  SEQUENCE OF ProfileFrf5Entry
     MAX-ACCESS              not-accessible
     STATUS                  current
     DESCRIPTION
       "The FRF.5 profile table."
     ::= { foreProfileModule 7}

  profileFrf5Entry          OBJECT-TYPE
      SYNTAX                ProfileFrf5Entry
      MAX-ACCESS            not-accessible
      STATUS                current
      DESCRIPTION
        "An entry in the FRF.5 profile table."
      INDEX   { profileFrf5Index }
      ::= { profileFrf5Table 1 }

 ProfileFrf5Entry ::= SEQUENCE {
      profileFrf5Index          	INTEGER,
      profileFrf5RowStatus      	RowStatus,
      profileFrf5Name           	DisplayString,
      profileFrf5DeMode         	INTEGER,
      profileFrf5ClpFrsscsDeMode	INTEGER,
      profileFrf5DefaultClp     	INTEGER,
      profileFrf5MaxPayloadSize   	INTEGER,
      profileFrf5MaxDlcis          	INTEGER,
      profileFrf5RefCnt         	INTEGER
 }

 profileFrf5Index       OBJECT-TYPE
     SYNTAX             INTEGER
     MAX-ACCESS         read-only
     STATUS             current
     DESCRIPTION
       "This object identifies the index of a profile in this
        table. Indices 1 though 20 are reserved for system defaults"
     ::= { profileFrf5Entry 1 }

 profileFrf5RowStatus   OBJECT-TYPE
     SYNTAX             RowStatus
     MAX-ACCESS         read-write
     STATUS             current
     DESCRIPTION
       "This object is used to create new rows and delete existing
        rows in this table."
     ::= { profileFrf5Entry 2 }

 profileFrf5Name        OBJECT-TYPE
     SYNTAX             DisplayString
     MAX-ACCESS         read-write
     STATUS             current
     DESCRIPTION
       "This object specifies the symbolic name assigned to this
        profile for user reference."
     ::= { profileFrf5Entry 3 }

 profileFrf5DeMode      OBJECT-TYPE
     SYNTAX             INTEGER {
                                mapped  (1),
                                ignored (2)
                        }
     MAX-ACCESS         read-write
     STATUS             current
     DESCRIPTION
        "If the DE mode is set to mapped, the DE field in the FR_SSCS
         frame is mapped to the ATM CLP filled of every cell
         generated by the segmentation process of the AAL5 PDU
         containing the information of that frame. Otherwise, if the 
	 DE mode is set to ignored, the ATM CLP of every ATM cell generated 
         by the segmentation process of the AAL5 PDU containing the information
         of that frame is set to a constant value specified by the configuration
         parameter profileFrf5DefaultClp."
     DEFVAL { mapped }
     ::= { profileFrf5Entry 4 }

 profileFrf5ClpFrsscsDeMode     OBJECT-TYPE
     SYNTAX             INTEGER {
                                mapped  (1),
                                ignored (2)
                        }
     MAX-ACCESS         read-write
     STATUS             current
     DESCRIPTION
        "If the CLP mode is set to mapped, the FR/ATM network
         interworking function will set the DE field of the Q922 core
         frame, provided that one or more cells belonging to this
         frame has its CLP field set, or the DE bit of FR_SSCS frame is set. 
	 Otherwise, if the CLP mode is set to ignored, the DE bit of FR_SSCS 
	 frame is copied to the Q922 core frame."
     DEFVAL { mapped }
     ::= { profileFrf5Entry 5 }

 profileFrf5DefaultClp  OBJECT-TYPE
     SYNTAX             INTEGER (0..1)
     MAX-ACCESS         read-write
     STATUS             current
     DESCRIPTION
       "This object represents the CLP bit value of all generated ATM
        cell headers if the DE mode is set to ignored."
     DEFVAL { 0 }
     ::= { profileFrf5Entry 6 }

 profileFrf5MaxDlcis    OBJECT-TYPE
     SYNTAX               INTEGER 
     MAX-ACCESS           read-write
     STATUS               current
     DESCRIPTION 
       "The maximum number of virtual circuits supported in this
        VCC."
     DEFVAL { 5 }
     ::= { profileFrf5Entry 7 }

 profileFrf5MaxPayloadSize     OBJECT-TYPE
     SYNTAX                       INTEGER
     MAX-ACCESS                   read-write
     STATUS                       current
     DESCRIPTION
       "This object represents the maximum payload size (bytes)
        supported by the VCC."
     DEFVAL { 4092 }
     ::= { profileFrf5Entry 8 }

 profileFrf5RefCnt      OBJECT-TYPE
     SYNTAX             INTEGER
     MAX-ACCESS         read-only
     STATUS             current
     DESCRIPTION
       "The value of this object identifies the number of connections
        that are currently referring to this profile."
     DEFVAL { 0 }
     ::= { profileFrf5Entry 9 }

--------------------------------------------------------------------



END
