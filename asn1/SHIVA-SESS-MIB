--
-- 	Copyright 1992, 1993, 1995, 1996, 1999 Shiva Corporation
--

--
--	Shiva systems session MIB
--

SHIVA-SESS-MIB DEFINITIONS ::= BEGIN

IMPORTS
	OBJECT-TYPE
		FROM RFC-1212		-- Concise MIB Definitions
	DisplayString, PhysAddress
		FROM RFC1213-MIB
	Counter, IpAddress, TimeTicks
		FROM RFC1155-SMI
	session
		FROM SHIVA-MIB;

-- textual conventions - stolen from shiva-nw.asn

	IpxNetNumber ::=	-- 4 octets of net number
				-- in network byte order
		OCTET STRING (SIZE (4))
		-- used to encode IPX network numbers.

	IpxNodeNumber ::=	-- 6 octets of node number
				-- in network byte order
		OCTET STRING (SIZE (6))
		-- used to encode IPX node numbers.

-- stolen from RFC1243

	DdpAddress ::=		-- 2 octets of net number
				-- in network byte order,
	              		-- 1 octet of node number
		OCTET STRING (SIZE (3))
		-- This data type is used for encoding a DDP protocol
		-- address.  The format of this address is a serial
		-- encoding of the two octets of network number in
		-- network byte order, followed by the 1 octet node
		-- number.

    sessionTable OBJECT-TYPE
	SYNTAX	SEQUENCE OF SessionEntry
	ACCESS	not-accessible
	STATUS	deprecated
	DESCRIPTION
		"A table of current users of the box."
	::= { session 1 }

    sessionEntry OBJECT-TYPE
	SYNTAX	SessionEntry
	ACCESS	not-accessible
	STATUS	deprecated
	DESCRIPTION
		"A user of the box."
	INDEX { sessionLine }
	::= { sessionTable 1 }

    SessionEntry ::= SEQUENCE {
	sessionLine			INTEGER,
	sessionUser			DisplayString,
	sessionConnect			INTEGER,
	sessionIdle			INTEGER,
	sessionLocation			DisplayString,
	sessionActivity			INTEGER,
	sessionDescription		DisplayString,
	sessionMaxConnect		INTEGER,
	sessionMaxIdle			INTEGER,
	sessionDialBackNumber		DisplayString,
	sessionIpaddr			IpAddress,
	sessionIpxNet			IpxNetNumber,
	sessionIpxNode			IpxNodeNumber,
	sessionNetbeuiAddr		PhysAddress,
	sessionConnectStr		DisplayString,
	sessionProtocols		INTEGER,
	sessionPacketSize		INTEGER,
	sessionOverruns			Counter,
	sessionParityErrs		Counter,
	sessionFrameErrs		Counter,
	sessionBreakErrs		Counter,
	sessionFcsErrs			Counter,
	sessionTooBig			Counter,
	sessionPktAbort			Counter,
	sessionDdpAddress		DdpAddress,
	sessionLineMode			INTEGER,
	sessionSynFcsErrs		Counter,
	sessionSynOverruns		Counter,
	sessionSynUnderruns		Counter,
	sessionSynFrAborts		Counter,
	sessionSynIntframes		Counter,
	sessionPPPCompDecomp		INTEGER,
	sessionPPPCompComp		INTEGER,
	sessionPPPCompDecompRatio	INTEGER,
	sessionPPPCompCompRatio		INTEGER,
	sessionPPPCompExpandedPackets	Counter,
	sessionPPPCompExpandedOctets	Counter,
	sessionPPPCompExpandedTooBig	Counter,
	sessionPPPCompStacSendCheck	INTEGER,
	sessionPPPCompStacRecvCheck	INTEGER,
	sessionIPAddrSrc		INTEGER
    }

    sessionLine OBJECT-TYPE
	SYNTAX	INTEGER
	ACCESS	read-only
	STATUS	deprecated
	DESCRIPTION
		"The unique number identifying this session.  Formerly
		a line number, but not anymore."
	::= { sessionEntry 1 }

    sessionUser OBJECT-TYPE
	SYNTAX	DisplayString
	ACCESS	read-only
	STATUS	deprecated
	DESCRIPTION
		"The name of the user associated with the session.
		This may be empty if the user has not yet authenticated."
	::= { sessionEntry 2 }

    sessionConnect OBJECT-TYPE
	SYNTAX	INTEGER
	ACCESS	read-only
	STATUS	deprecated
	DESCRIPTION
		"Session connect time in minutes."
	::= { sessionEntry 3 }

    sessionIdle	OBJECT-TYPE
	SYNTAX	INTEGER
	ACCESS	read-only
	STATUS	deprecated
	DESCRIPTION
		"Session idle time in minutes."
	::= { sessionEntry 4 }

    sessionLocation OBJECT-TYPE
	SYNTAX	DisplayString
	ACCESS	read-only
	STATUS	deprecated
	DESCRIPTION
		"A description of the location of the session source."
	::= { sessionEntry 5 }

    sessionActivity OBJECT-TYPE
	SYNTAX	INTEGER {
		none(1),	-- write this value to abort session
		dialin(2),
		shell(3),
		dialout(4),
		file(5),	-- ie; FTP or SFTP
		lantolan(6),
		busyout(7)
	}
	ACCESS	read-write
	STATUS	deprecated
	DESCRIPTION
		"An indication of the current activity type."
	::= { sessionEntry 6 }

    sessionDescription OBJECT-TYPE
	SYNTAX	DisplayString
	ACCESS	read-only
	STATUS	deprecated
	DESCRIPTION
		"A description of the current activity."
	::= { sessionEntry 7 }

    sessionMaxConnect OBJECT-TYPE
	SYNTAX	INTEGER
	ACCESS	read-only
	STATUS	deprecated
	DESCRIPTION
		"Session connect time limit in minutes.
		If zero, there is no limit."
	::= { sessionEntry 8 }

    sessionMaxIdle OBJECT-TYPE
	SYNTAX	INTEGER
	ACCESS	read-only
	STATUS	deprecated
	DESCRIPTION
		"Session idle time limit in minutes.
		If zero, there is no limit."
	::= { sessionEntry 9 }

    sessionDialBackNumber OBJECT-TYPE
	SYNTAX	DisplayString
	ACCESS	read-only
	STATUS	deprecated
	DESCRIPTION
		"The dialback phone number used by the connection."
	::= { sessionEntry 10 }

    sessionIpaddr OBJECT-TYPE
	SYNTAX	IpAddress
	ACCESS	read-only
	STATUS	deprecated
	DESCRIPTION
		"The IP address used by the client of the connection."
	::= { sessionEntry 11 }

    sessionIpxNet OBJECT-TYPE
	SYNTAX	IpxNetNumber
	ACCESS	read-only
	STATUS	deprecated
	DESCRIPTION
		"The IPX network number used for the connection."
	::= { sessionEntry 12 }

    sessionIpxNode OBJECT-TYPE
	SYNTAX	IpxNodeNumber
	ACCESS	read-only
	STATUS	deprecated
	DESCRIPTION
		"The IPX node number used by the client of the connection."
	::= { sessionEntry 13 }

    sessionNetbeuiAddr OBJECT-TYPE
	SYNTAX	PhysAddress
	ACCESS	read-only
	STATUS	deprecated
	DESCRIPTION
		"The NetBEUI address used for bridging by the client of the
		connection."
	::= { sessionEntry 14 }

    sessionConnectStr OBJECT-TYPE
	SYNTAX	DisplayString
	ACCESS	read-only
	STATUS	deprecated
	DESCRIPTION
		"The modem connect string returned on the connection."
	::= { sessionEntry 15 }

    sessionProtocols OBJECT-TYPE
	SYNTAX	INTEGER
	ACCESS	read-only
	STATUS	deprecated
	DESCRIPTION
		"The protocols used on the connection, represented as a
		bitmask;
			0x00000001 - PPP
			0x00000002 - IP
			0x00000004 - IPX
			0x00000008 - AppleTalk
			0x00000010 - SLIP
			0x00000020 - NetBEUI
			0x00000040 - LLC
			0x00000080 - AALAP
			0x00000100 - ARA 1.0
			0x00000200 - ARA 2.0
			0x00000400 - MacIP
			0x00000800 - L2F client
			0x00001000 - L2F dialin"

	::= { sessionEntry 16 }

    sessionPacketSize OBJECT-TYPE
	SYNTAX	INTEGER
	ACCESS	read-only
	STATUS	deprecated
	DESCRIPTION
		"The maximum packet sized allowed on this connection."
	::= { sessionEntry 17 }

    sessionOverruns OBJECT-TYPE
	SYNTAX	Counter
	ACCESS	read-only
	STATUS	deprecated
	DESCRIPTION
		"The number of overruns seen on this connection.
		Always 0.  See sessLineAsyncOverruns."
	::= { sessionEntry 18 }

    sessionParityErrs OBJECT-TYPE
	SYNTAX	Counter
	ACCESS	read-only
	STATUS	deprecated
	DESCRIPTION
		"The number of parity errors seen on this connection.
		Always 0.  See sessLineAsyncParityErrs."
	::= { sessionEntry 19 }

    sessionFrameErrs OBJECT-TYPE
	SYNTAX	Counter
	ACCESS	read-only
	STATUS	deprecated
	DESCRIPTION
		"The number of framing errors seen on this connection.
		Always 0.  See sessLineAsyncFrameErrs."
	::= { sessionEntry 20 }

    sessionBreakErrs OBJECT-TYPE
	SYNTAX	Counter
	ACCESS	read-only
	STATUS	deprecated
	DESCRIPTION
		"The number of break errors seen on this connection.
		Always 0.  See sessLineAsyncBreakErrs."
	::= { sessionEntry 21 }

    sessionFcsErrs OBJECT-TYPE
	SYNTAX	Counter
	ACCESS	read-only
	STATUS	deprecated
	DESCRIPTION
		"The number of checksum errors seen on this connection.
		Always 0.  See sessLineAsyncFcsErrs."
	::= { sessionEntry 22 }

    sessionTooBig OBJECT-TYPE
	SYNTAX	Counter
	ACCESS	read-only
	STATUS	deprecated
	DESCRIPTION
		"The number of too large packets seen on this connection.
		Always 0.  See sessLineAsyncTooBig."
	::= { sessionEntry 23 }

    sessionPktAbort OBJECT-TYPE
	SYNTAX	Counter
	ACCESS	read-only
	STATUS	deprecated
	DESCRIPTION
		"The number of packet abort indications seen on this
		connection.  Always 0.  See sessLineAsyncPktAbort."
	::= { sessionEntry 24 }

    sessionDdpAddress OBJECT-TYPE
	SYNTAX	DdpAddress
	ACCESS	read-only
	STATUS	deprecated
	DESCRIPTION
		"The DDP address used by the client of the connection."
	::= { sessionEntry 25 }

    sessionLineMode OBJECT-TYPE
	SYNTAX	INTEGER {
		unknown(1),
		async(2),
		sync(3)
	}
	ACCESS	read-only
	STATUS	deprecated
	DESCRIPTION
		"The line type on this connection."
	::= { sessionEntry 26 }

    sessionSynFcsErrs OBJECT-TYPE
	SYNTAX	Counter
	ACCESS	read-only
	STATUS	deprecated
	DESCRIPTION
		"The number of FCS errors in sync mode on this connection.
		Always 0.  See sessLineSyncFcsErrs."
	::= { sessionEntry 27 }

    sessionSynOverruns OBJECT-TYPE
	SYNTAX	Counter
	ACCESS	read-only
	STATUS	deprecated
	DESCRIPTION
		"The number of sync receive overruns on this connection.
		Always 0.  See sessLineSyncOverruns."
	::= { sessionEntry 28 }

    sessionSynUnderruns OBJECT-TYPE
	SYNTAX	Counter
	ACCESS	read-only
	STATUS	deprecated
	DESCRIPTION
		"The number of sync transmit underruns on this connection.
		Always 0.  See sessLineSyncUnderruns."
	::= { sessionEntry 29 }

    sessionSynFrAborts OBJECT-TYPE
	SYNTAX	Counter
	ACCESS	read-only
	STATUS	deprecated
	DESCRIPTION
		"The number of sync frame aborts on this connection.
		Always 0.  See sessLineSyncFrAborts."
	::= { sessionEntry 30 }

    sessionSynIntframes OBJECT-TYPE
	SYNTAX	Counter
	ACCESS	read-only
	STATUS	deprecated
	DESCRIPTION
		"The number of sync interrupted frames on this connection.
		Always 0.  See sessLineSyncIntFrames."
	::= { sessionEntry 31 }

    sessionPPPCompDecomp OBJECT-TYPE
	SYNTAX	INTEGER {
		none(1),		-- none
		stacLZS(2),		-- Stac LZS
		microsoftPPC(3)		-- Microsoft PPC
	}
	ACCESS	read-only
	STATUS	deprecated
	DESCRIPTION
		"The decompression protocol in use on this session."

	::= { sessionEntry 32 }

    sessionPPPCompComp OBJECT-TYPE
	SYNTAX	INTEGER {
		none(1),		-- none
		stacLZS(2),		-- Stac LZS
		microsoftPPC(3)		-- Microsoft PPC
	}
	ACCESS	read-only
	STATUS	deprecated
	DESCRIPTION
		"The compression protocol in use on this session."

	::= { sessionEntry 33 }


    sessionPPPCompDecompRatio OBJECT-TYPE
	SYNTAX	INTEGER
	ACCESS	read-only
	STATUS	deprecated
	DESCRIPTION
		"The average decompression ratio, multiplied by 100.
		A value of 200 indicates a 1:2 decompression ratio."

	::= { sessionEntry 34 }

    sessionPPPCompCompRatio OBJECT-TYPE
	SYNTAX	INTEGER
	ACCESS	read-only
	STATUS	deprecated
	DESCRIPTION
		"The average compression ratio, multiplied by 100.  A
		value of 200 indicates a 2:1 compression ratio."

	::= { sessionEntry 35 }

    sessionPPPCompExpandedPackets OBJECT-TYPE
	SYNTAX	Counter
	ACCESS	read-only
	STATUS	deprecated
	DESCRIPTION
		"The number of packets that were sent in compressed
		form that were larger than they would have been
		had they not been compressed."
	::= { sessionEntry 36 }

    sessionPPPCompExpandedOctets OBJECT-TYPE
	SYNTAX	Counter
	ACCESS	read-only
	STATUS	deprecated
	DESCRIPTION
		"The total number of extra octets that were sent
		when packets were sent in compressed form that were 
		larger than they would have been had they not been
		compressed."
	::= { sessionEntry 37 }

    sessionPPPCompExpandedTooBig OBJECT-TYPE
	SYNTAX	Counter
	ACCESS	read-only
	STATUS	deprecated
	DESCRIPTION
		"The number of packets that were of a compressible
		type, but were not sent in compressed form because
		the compressed version was so large that it
		exceeded local or remote (MTU) constraints."
	::= { sessionEntry 38 }

    sessionPPPCompStacSendCheck OBJECT-TYPE
	SYNTAX	INTEGER {
		none(1),		-- none
		sequenceNumber(4),	-- Stac 8 bit sequence number
		microsoft(5)		-- Microsoft 12 bit sequence number
	}
	ACCESS	read-only
	STATUS	deprecated
	DESCRIPTION
		"The type of coherency check in use for Stac LZS
		compression on transmitted packets.  If compression
		is not Stac LZS, will have value none(1)." 
	::= { sessionEntry 39 }

    sessionPPPCompStacRecvCheck OBJECT-TYPE
	SYNTAX	INTEGER {
		none(1),		-- none
		sequenceNumber(4),	-- Stac 8 bit sequence number
		microsoft(5)		-- Microsoft 12 bit sequence number
	}
	ACCESS	read-only
	STATUS	deprecated
	DESCRIPTION
		"The type of coherency check in use for Stac LZS
		decompression on received packets.  If decompression
		is not Stac LZS, will have value none(1)."
	::= { sessionEntry 40 }

    sessionIPAddrSrc OBJECT-TYPE
	SYNTAX	INTEGER {
		none(1),	-- no IP address
		peer(2),	-- address proposed by remote peer or client
		usercfg(3),	-- configured address for user
		dhcp(5),	-- address obtained from DHCP server
		pool(6)		-- from configured pool for dialin
	}
	ACCESS	read-only
	STATUS	deprecated
	DESCRIPTION
		"The source of the IP address for this session.
		The source is a function of configured IP address
		assignment policy.  Policy is hierarchical.  The
		source for the session is the highest source in
		the hierarchy which is enabled and provides a
		valid address."
	::= { sessionEntry 41 }

-- This is the current session table.  There is one session for each
-- active user/session pair on the box.  With virtual connections and
-- PPP Multilink, sessions are not uniquely bound to lines, and may
-- not have any line at a given point in time.  To find the line
-- to session bindings, and line-oriented data, see sessLineTable.

    sessTable OBJECT-TYPE
	SYNTAX	SEQUENCE OF SessEntry
	ACCESS	not-accessible
	STATUS	mandatory
	DESCRIPTION
		"A table of current users of the box."
	::= { session 2 }

    sessEntry OBJECT-TYPE
	SYNTAX	SessEntry
	ACCESS	not-accessible
	STATUS	mandatory
	DESCRIPTION
		"A user of the box."
	INDEX { sessIdentifier }
	::= { sessTable 1 }

    SessEntry ::= SEQUENCE {
	sessIdentifier			INTEGER,
	sessLines			INTEGER,
	sessStatus			INTEGER,
	sessUser			DisplayString,
	sessConnect			INTEGER,
	sessIdle			INTEGER,
	sessVirtual			INTEGER,
	sessVirtualIdle			INTEGER,
	sessMaxVirtualIdle		INTEGER,
	sessSuspended			INTEGER,
	sessVirtualLastChange		TimeTicks,
	sessLocation			DisplayString,
	sessActivity			INTEGER,
	sessDescription			DisplayString,
	sessMaxConnect			INTEGER,
	sessMaxIdle			INTEGER,
	sessPacketSize			INTEGER,
	sessProtocols			INTEGER,
	sessIpaddr			IpAddress,
	sessIPAddrSrc			INTEGER,
	sessIpxNet			IpxNetNumber,
	sessIpxNode			IpxNodeNumber,
	sessDdpAddress			DdpAddress,
	sessNetbeuiAddr			PhysAddress,
	sessPPPCompDecomp		INTEGER,
	sessPPPCompComp			INTEGER,
	sessPPPCompDecompRatio		INTEGER,
	sessPPPCompCompRatio		INTEGER,
	sessPPPCompExpandedPackets	Counter,
	sessPPPCompExpandedOctets	Counter,
	sessPPPCompExpandedTooBig	Counter,
	sessPPPCompStacSendCheck	INTEGER,
	sessPPPCompStacRecvCheck	INTEGER,
	sessTotalConnect		INTEGER,
	sessPPPCompSentUncompressed	Counter,
	sessPBurstIpxNcpAccelReq	Counter,
	sessPBurstIpxNcpBytesReq	Counter,
	sessPBurstIpxNcpAccel		Counter,
	sessPBurstIpxNcpBytes		Counter
    }

    sessIdentifier OBJECT-TYPE
	SYNTAX	INTEGER (256..65535)
	ACCESS	read-only
	STATUS	mandatory
	DESCRIPTION
		"The unique serial number identifying this session."
	::= { sessEntry 1 }

    sessLines OBJECT-TYPE
	SYNTAX	INTEGER
	ACCESS	read-only
	STATUS	mandatory
	DESCRIPTION
		"The number of physical lines in use by this session.
		This can be as low as 0, as when the session is suspended."
	::= { sessEntry 2 }

    sessStatus	OBJECT-TYPE
	SYNTAX	INTEGER	{
		connect(1),
		disconnect(2),
		suspend(3),
		resume(4)
	}
	ACCESS	read-write
	STATUS	mandatory
	DESCRIPTION
		"Setting this to a value puts the connection in that state."
	::= { sessEntry 3 }

    sessUser OBJECT-TYPE
	SYNTAX	DisplayString
	ACCESS	read-only
	STATUS	mandatory
	DESCRIPTION
		"The name of the user associated with the session.
		This may be empty if the user has not yet authenticated."
	::= { sessEntry 4 }

    sessConnect OBJECT-TYPE
	SYNTAX	INTEGER
	ACCESS	read-only
	STATUS	mandatory
	DESCRIPTION
		"Session connect time in minutes."
	::= { sessEntry 5 }

    sessIdle	OBJECT-TYPE
	SYNTAX	INTEGER
	ACCESS	read-only
	STATUS	mandatory
	DESCRIPTION
		"Session idle time in minutes for purposes of deciding
		whether to terminate session."
	::= { sessEntry 6 }

    sessVirtual	OBJECT-TYPE
	SYNTAX	INTEGER	{
		normal(1),
		virtual(2)
	}
	ACCESS	read-only
	STATUS	mandatory
	DESCRIPTION
		"If virtual, the session is subject to suspension,
		if normal, it will never suspend."
	::= { sessEntry 7 }

    sessVirtualIdle OBJECT-TYPE
	SYNTAX	INTEGER
	ACCESS	read-only
	STATUS	mandatory
	DESCRIPTION
		"Session idle time in seconds for purposes of deciding
		whether to suspend session."
	::= { sessEntry 8 }

    sessMaxVirtualIdle OBJECT-TYPE
	SYNTAX	INTEGER
	ACCESS	read-only
	STATUS	mandatory
	DESCRIPTION
		"Session maximum idle time limit in seconds before session
		 will be suspended.  If zero, session will never be suspended."
	::= { sessEntry 9 }

    sessSuspended OBJECT-TYPE
	SYNTAX	INTEGER	{
		connected(1),
		suspended(2)
	}
	ACCESS	read-only
	STATUS	mandatory
	DESCRIPTION
		"Indicates whether session is connected to line,
		or is suspended.  Can only be suspeneded if
		sessVirtual is virtual."
	::= { sessEntry 10 }

    sessVirtualLastChange OBJECT-TYPE
	SYNTAX  TimeTicks
	ACCESS  read-only
	STATUS  mandatory
	DESCRIPTION
		"The value of sysUpTime at the time the session
		last changed from connected to suspeneded, or
		vice-versa."
	::= { sessEntry 11 }

    sessLocation OBJECT-TYPE
	SYNTAX	DisplayString
	ACCESS	read-only
	STATUS	mandatory
	DESCRIPTION
		"A description of the location of the session source."
	::= { sessEntry 12 }

    sessActivity OBJECT-TYPE
	SYNTAX	INTEGER {
		none(1),	-- write this value to abort session
		dialin(2),
		shell(3),
		dialout(4),
		file(5),	-- ie; FTP or SFTP
		lantolan(6),
		busyout(7)
	}
	ACCESS	read-only
	STATUS	mandatory
	DESCRIPTION
		"An indication of the current activity type."
	::= { sessEntry 13 }

    sessDescription OBJECT-TYPE
	SYNTAX	DisplayString
	ACCESS	read-only
	STATUS	mandatory
	DESCRIPTION
		"A description of the current activity."
	::= { sessEntry 14 }

    sessMaxConnect OBJECT-TYPE
	SYNTAX	INTEGER
	ACCESS	read-only
	STATUS	mandatory
	DESCRIPTION
		"Session connect time limit in minutes.
		If zero, there is no limit."
	::= { sessEntry 15 }

    sessMaxIdle OBJECT-TYPE
	SYNTAX	INTEGER
	ACCESS	read-only
	STATUS	mandatory
	DESCRIPTION
		"Session idle time limit in minutes.
		If zero, there is no limit."
	::= { sessEntry 16 }

    sessPacketSize OBJECT-TYPE
	SYNTAX	INTEGER
	ACCESS	read-only
	STATUS	mandatory
	DESCRIPTION
		"The maximum packet sized allowed on this connection."
	::= { sessEntry 17 }

    sessProtocols OBJECT-TYPE
	SYNTAX	INTEGER
	ACCESS	read-only
	STATUS	mandatory
	DESCRIPTION
		"The protocols used on the connection, represented as a
		bitmask;
			0x00000001 - PPP
			0x00000002 - IP
			0x00000004 - IPX
			0x00000008 - AppleTalk
			0x00000010 - SLIP
			0x00000020 - NetBEUI
			0x00000040 - LLC
			0x00000080 - AALAP
			0x00000100 - ARA 1.0
			0x00000200 - ARA 2.0
			0x00000400 - MacIP
			0x00000800 - L2F client
			0x00001000 - L2F dialin"
	::= { sessEntry 18 }

    sessIpaddr OBJECT-TYPE
	SYNTAX	IpAddress
	ACCESS	read-only
	STATUS	mandatory
	DESCRIPTION
		"The IP address used by the client of the connection."
	::= { sessEntry 19 }

    sessIPAddrSrc OBJECT-TYPE
	SYNTAX	INTEGER {
		none(1),	-- no IP address
		peer(2),	-- address proposed by remote peer or client
		usercfg(3),	-- configured address for user
		dhcp(5),	-- address obtained from DHCP server
		pool(6)		-- from configured pool for dialin
	}
	ACCESS	read-only
	STATUS	mandatory
	DESCRIPTION
		"The source of the IP address for this session.
		The source is a function of configured IP address
		assignment policy.  Policy is hierarchical.  The
		source for the session is the highest source in
		the hierarchy which is enabled and provides a
		valid address.
		
		The former portcfg(4) value has been deprecated,
		addresses are not configured on a port basis as of 4.0."
	::= { sessEntry 20 }

    sessIpxNet OBJECT-TYPE
	SYNTAX	IpxNetNumber
	ACCESS	read-only
	STATUS	mandatory
	DESCRIPTION
		"The IPX network number used for the connection."
	::= { sessEntry 21 }

    sessIpxNode OBJECT-TYPE
	SYNTAX	IpxNodeNumber
	ACCESS	read-only
	STATUS	mandatory
	DESCRIPTION
		"The IPX node number used by the client of the connection."
	::= { sessEntry 22 }

    sessDdpAddress OBJECT-TYPE
	SYNTAX	DdpAddress
	ACCESS	read-only
	STATUS	mandatory
	DESCRIPTION
		"The DDP address used by the client of the connection."
	::= { sessEntry 23 }

    sessNetbeuiAddr OBJECT-TYPE
	SYNTAX	PhysAddress
	ACCESS	read-only
	STATUS	mandatory
	DESCRIPTION
		"The NetBEUI address used for bridging by the client of the
		connection."
	::= { sessEntry 24 }

    sessPPPCompDecomp OBJECT-TYPE
	SYNTAX	INTEGER {
		none(1),		-- none
		stacLZS(2),		-- Stac LZS
		microsoftPPC(3)		-- Microsoft PPC
	}
	ACCESS	read-only
	STATUS	mandatory
	DESCRIPTION
		"The decompression protocol in use on this session."
	::= { sessEntry 25 }

    sessPPPCompComp OBJECT-TYPE
	SYNTAX	INTEGER {
		none(1),		-- none
		stacLZS(2),		-- Stac LZS
		microsoftPPC(3)		-- Microsoft PPC
	}
	ACCESS	read-only
	STATUS	mandatory
	DESCRIPTION
		"The compression protocol in use on this session."
	::= { sessEntry 26 }

    sessPPPCompDecompRatio OBJECT-TYPE
	SYNTAX	INTEGER
	ACCESS	read-only
	STATUS	mandatory
	DESCRIPTION
		"The average decompression ratio, multiplied by 100.
		A value of 200 indicates a 1:2 decompression ratio."
	::= { sessEntry 27 }

    sessPPPCompCompRatio OBJECT-TYPE
	SYNTAX	INTEGER
	ACCESS	read-only
	STATUS	mandatory
	DESCRIPTION
		"The average compression ratio, multiplied by 100.  A
		value of 200 indicates a 2:1 compression ratio."
	::= { sessEntry 28 }

    sessPPPCompExpandedPackets OBJECT-TYPE
	SYNTAX	Counter
	ACCESS	read-only
	STATUS	deprecated
	DESCRIPTION
		"The number of packets that were sent in compressed
		form that were larger than they would have been
		had they not been compressed.  Always 0, since this
		is never done."
	::= { sessEntry 29 }

    sessPPPCompExpandedOctets OBJECT-TYPE
	SYNTAX	Counter
	ACCESS	read-only
	STATUS	mandatory
	DESCRIPTION
		"The total number of extra octets that were sent
		when packets were sent in compressed form that were 
		larger than they would have been had they not been
		compressed.  Always 0, since this is never done."
	::= { sessEntry 30 }

    sessPPPCompExpandedTooBig OBJECT-TYPE
	SYNTAX	Counter
	ACCESS	read-only
	STATUS	mandatory
	DESCRIPTION
		"The number of packets that were of a compressible
		type, but were not sent in compressed form because
		the compressed version was so large that it
		exceeded local or remote (MTU) constraints.
		Happens when the overhead of the compression
		header is too much more."
	::= { sessEntry 31 }

    sessPPPCompStacSendCheck OBJECT-TYPE
	SYNTAX	INTEGER {
		none(1),		-- none
		sequenceNumber(4),	-- Stac 8 bit sequence number
		microsoft(5)		-- Microsoft 12 bit sequence number
	}
	ACCESS	read-only
	STATUS	mandatory
	DESCRIPTION
		"The type of coherency check in use for Stac LZS
		compression on transmitted packets.  If compression
		is not Stac LZS, will have value none(1)." 
	::= { sessEntry 32 }

    sessPPPCompStacRecvCheck OBJECT-TYPE
	SYNTAX	INTEGER {
		none(1),		-- none
		sequenceNumber(4),	-- Stac 8 bit sequence number
		microsoft(5)		-- Microsoft 12 bit sequence number
	}
	ACCESS	read-only
	STATUS	mandatory
	DESCRIPTION
		"The type of coherency check in use for Stac LZS
		decompression on received packets.  If decompression
		is not Stac LZS, will have value none(1)."
	::= { sessEntry 33 }

    sessTotalConnect OBJECT-TYPE
	SYNTAX	INTEGER
	ACCESS	read-only
	STATUS	mandatory
	DESCRIPTION
		"Session total connect time in minutes.  Time is not
		counted when a Virtual Connection is suspended."
	::= { sessEntry 34 }

    sessPPPCompSentUncompressed OBJECT-TYPE
	SYNTAX	Counter
	ACCESS	read-only
	STATUS	deprecated
	DESCRIPTION
		"The number of packets that were sent in uncompressed
		so as not to cause the data to expand on the wire."
	::= { sessEntry 35 }

    sessPBurstIpxNcpAccelReq OBJECT-TYPE
	SYNTAX	Counter
	ACCESS	read-only
	STATUS	mandatory
	DESCRIPTION
		"The number of IPX NCP requests received by the
		Powerburst accelerator Agent"

	::= { sessEntry 36 }

    sessPBurstIpxNcpBytesReq OBJECT-TYPE
	SYNTAX	Counter
	ACCESS	read-only
	STATUS	mandatory
	DESCRIPTION
		"The number of bytes requested in all IPX NCP requests
		 processed by the Powerburst accelerator Agent"

	::= { sessEntry 37 }

    sessPBurstIpxNcpAccel OBJECT-TYPE
	SYNTAX	Counter
	ACCESS	read-only
	STATUS	mandatory
	DESCRIPTION
		"The number of IPX NCP requests that did not require
		 data transfer due to usage of the Powerburst accelerator"

	::= { sessEntry 38 }

    sessPBurstIpxNcpBytes OBJECT-TYPE
	SYNTAX	Counter
	ACCESS	read-only
	STATUS	mandatory
	DESCRIPTION
		"The number of bytes that did not have to be transmitted
		 due to usage of the Powerburst accelerator"

	::= { sessEntry 39 }


-- The sessLineTable has one row per line that is currently in use by
-- a session.  It is used to determine which lines are in use, and to
-- keep session-related data that is particular to a specific line 
-- in use by a session.

    sessLineTable OBJECT-TYPE
	SYNTAX	SEQUENCE OF SessLineEntry
	ACCESS	not-accessible
	STATUS	mandatory
	DESCRIPTION
		"A table of current active lines of the box."
	::= { session 3 }

    sessLineEntry OBJECT-TYPE
	SYNTAX	SessLineEntry
	ACCESS	not-accessible
	STATUS	mandatory
	DESCRIPTION
		"A user of the box."
	INDEX { sessLineLine }
	::= { sessLineTable 1 }

    SessLineEntry ::= SEQUENCE {
	sessLineLine		INTEGER,
	sessLineSession		INTEGER,
	sessLineDialBackNumber	DisplayString,
	sessLinePacketSize	INTEGER,
	sessLineLineMode	INTEGER,
	sessLineAsyncOverruns	Counter,
	sessLineAsyncParityErrs	Counter,
	sessLineAsyncFrameErrs	Counter,
	sessLineAsyncBreakErrs	Counter,
	sessLineAsyncFcsErrs	Counter,
	sessLineAsyncTooBig	Counter,
	sessLineAsyncPktAbort	Counter,
	sessLineSyncFcsErrs	Counter,
	sessLineSyncOverruns	Counter,
	sessLineSyncUnderruns	Counter,
	sessLineSyncFrAborts	Counter,
	sessLineSyncIntframes	Counter,
	sessLinePktsIn		Counter,
	sessLinePktsOut		Counter,
	sessLineSlot		INTEGER,
	sessLineChan		INTEGER,
	sessLineType		INTEGER,
	sessLineIfIndex		INTEGER,
	sessLineSpeed		INTEGER,
	sessLinePhysPort	INTEGER,
	sessLineLogSlot		INTEGER,
	sessLineLogChan		INTEGER

    }

    sessLineLine OBJECT-TYPE
	SYNTAX	INTEGER
	ACCESS	read-only
	STATUS	mandatory
	DESCRIPTION
		"Line number on which a session exists.  May not be
		only line in session."
	::= { sessLineEntry 1 }

    sessLineSession OBJECT-TYPE
	SYNTAX	INTEGER
	ACCESS	read-only
	STATUS	mandatory
	DESCRIPTION
		"The value of sessIdentifier for the session using this
		line."
	::= { sessLineEntry 2 }

    sessLineDialBackNumber OBJECT-TYPE
	SYNTAX	DisplayString
	ACCESS	read-only
	STATUS	deprecated
	DESCRIPTION
		"The dialback phone number used by the connection."
	::= { sessLineEntry 3 }

    sessLinePacketSize OBJECT-TYPE
	SYNTAX	INTEGER
	ACCESS	read-only
	STATUS	mandatory
	DESCRIPTION
		"The maximum packet sized allowed on this line."
	::= { sessLineEntry 4 }

    sessLineLineMode OBJECT-TYPE
	SYNTAX	INTEGER {
		unknown(1),
		async(2),
		sync(3)
	}
	ACCESS	read-only
	STATUS	mandatory
	DESCRIPTION
		"The line type on this connection."
	::= { sessLineEntry 5 }

    sessLineAsyncOverruns OBJECT-TYPE
	SYNTAX	Counter
	ACCESS	read-only
	STATUS	mandatory
	DESCRIPTION
		"The number of overruns seen on this connection."
	::= { sessLineEntry 6 }

    sessLineAsyncParityErrs OBJECT-TYPE
	SYNTAX	Counter
	ACCESS	read-only
	STATUS	mandatory
	DESCRIPTION
		"The number of async parity errors seen on this connection."
	::= { sessLineEntry 7 }

    sessLineAsyncFrameErrs OBJECT-TYPE
	SYNTAX	Counter
	ACCESS	read-only
	STATUS	mandatory
	DESCRIPTION
		"The number of async framing errors seen on this connection."
	::= { sessLineEntry 8 }

    sessLineAsyncBreakErrs OBJECT-TYPE
	SYNTAX	Counter
	ACCESS	read-only
	STATUS	mandatory
	DESCRIPTION
		"The number of async break errors seen on this connection."
	::= { sessLineEntry 9 }

    sessLineAsyncFcsErrs OBJECT-TYPE
	SYNTAX	Counter
	ACCESS	read-only
	STATUS	mandatory
	DESCRIPTION
		"The number of async checksum errors seen on this connection."
	::= { sessLineEntry 10 }

    sessLineAsyncTooBig OBJECT-TYPE
	SYNTAX	Counter
	ACCESS	read-only
	STATUS	mandatory
	DESCRIPTION
		"The number of async too large packets seen on this
		connection."
	::= { sessLineEntry 11 }

    sessLineAsyncPktAbort OBJECT-TYPE
	SYNTAX	Counter
	ACCESS	read-only
	STATUS	mandatory
	DESCRIPTION
		"The number of async packet abort indications seen on this
		connection."
	::= { sessLineEntry 12 }

    sessLineSyncFcsErrs OBJECT-TYPE
	SYNTAX	Counter
	ACCESS	read-only
	STATUS	mandatory
	DESCRIPTION
		"The number of sync FCS errors in sync mode on this 
		connection."
	::= { sessLineEntry 13 }

    sessLineSyncOverruns OBJECT-TYPE
	SYNTAX	Counter
	ACCESS	read-only
	STATUS	mandatory
	DESCRIPTION
		"The number of sync receive overruns on this connection."
	::= { sessLineEntry 14 }

    sessLineSyncUnderruns OBJECT-TYPE
	SYNTAX	Counter
	ACCESS	read-only
	STATUS	mandatory
	DESCRIPTION
		"The number of sync transmit underruns on this connection."
	::= { sessLineEntry 15 }

    sessLineSyncFrAborts OBJECT-TYPE
	SYNTAX	Counter
	ACCESS	read-only
	STATUS	mandatory
	DESCRIPTION
		"The number of sync frame aborts on this connection."
	::= { sessLineEntry 16 }

    sessLineSyncIntframes OBJECT-TYPE
	SYNTAX	Counter
	ACCESS	read-only
	STATUS	mandatory
	DESCRIPTION
		"The number of sync interrupted frames on this connection."
	::= { sessLineEntry 17 }

    sessLinePktsIn OBJECT-TYPE
	SYNTAX	Counter
	ACCESS	read-only
	STATUS	mandatory
	DESCRIPTION
		"The number of link-level packets received on this connection."
	::= { sessLineEntry 18 }

    sessLinePktsOut OBJECT-TYPE
	SYNTAX	Counter
	ACCESS	read-only
	STATUS	mandatory
	DESCRIPTION
		"The number of link-level packets sent on this connection."
	::= { sessLineEntry 19 }

    sessLineSlot OBJECT-TYPE
	SYNTAX	INTEGER (0..11)
	ACCESS	read-only
	STATUS	mandatory
	DESCRIPTION
		"On a LanRover or NetModem, sessLineSlot is the slot number
		 of the interface on which the session is created.
		 Empty slots are skipped.  Range of values:  (1..8).

		 On LanRover Access Switches, sessLineSlot is the
		 slot number of the telephone trunk on which the
		 session is created.  Range of values:  (1..11).

		 On LanRover Access Switches, if the current session was
		 created over a VPDN interface, the sessLineSlot value is 
		 not applicable, therefore, this value should be zero."
	::= { sessLineEntry 20 }

    sessLineChan OBJECT-TYPE
	SYNTAX	INTEGER (0..30)
	ACCESS	read-only
	STATUS	mandatory
	DESCRIPTION
		"On a LanRover or NetModem, sessLineChan is the logical channel
		 number on the interface on which the session is
		 created.  BRI cards have two channels, all others
		 have one.  Range of values:  (1..2).

		 On a LanRover Access Switch, sessLineChan is the 
		 timeslot of the telephone trunk on which the session 
		 is created.  Range of values:  (1..30).

		 On LanRover Access Switches, if the current session was
		 created over a VPDN interface, the sessLineChan value is 
		 not applicable, therefore, this value should be zero."
	::= { sessLineEntry 21 }

    sessLineType OBJECT-TYPE
	SYNTAX	INTEGER {
                empty(1),
                unknown(2),
                uart(3),
                modem(4),
                switched56(5),
                bri-st(6),
                usart(7),
                bri-u(8),
		pri(9),
		dmc(10),
		shiva-16-v34-modem-card(11),	-- in LanRover/E XP16
		ccm(12), 	-- transient, occurs during call startup
		l2f(13),
		l2tp(14),
		qbri-st(15),
		qbri-u(16)
	}
	ACCESS	read-only
	STATUS	mandatory
	DESCRIPTION
		"Type of line for this session.  This duplicates
		serialLineType of the index sessLineLine."
	::= { sessLineEntry 22 }

    sessLineIfIndex OBJECT-TYPE
	SYNTAX	INTEGER
	ACCESS	read-only
	STATUS	mandatory
	DESCRIPTION
		"The value of ifIndex for this interface."
	::= { sessLineEntry 23 }

    sessLineSpeed OBJECT-TYPE
	SYNTAX	INTEGER
	ACCESS	read-only
	STATUS	mandatory
	DESCRIPTION
		"Speed in bits/second that the modem (if any) on this call is
		operating at."
	::= { sessLineEntry 24 }

    sessLinePhysPort OBJECT-TYPE
	SYNTAX	INTEGER (1..4)
	ACCESS	read-only
	STATUS	mandatory
	DESCRIPTION
		"On a LanRover or NetModem, sessLinePhysPort is 1 since there is
		 never more than 1 physical port per physical slot.
		 Range of values:  (1..1).

		 On a LanRover Access Switch, sessLinePhysPort is the 
		 telephone trunk on which the session is created.  
		 For digital sessLineType calls, sessLineTrunk is the same as 
		 sessLineLogChan.  Range of values:  (1..4).

		 On LanRover Access Switches, if the current session was
		 created over a VPDN interface, the sessLinePhysPort value is 
		 equivalent to the VPDN interface number."
	::= { sessLineEntry 25 }

    sessLineLogSlot OBJECT-TYPE
	SYNTAX	INTEGER (0..11)
	ACCESS	read-only
	STATUS	mandatory
	DESCRIPTION
		"On a LanRover or NetModem, sessLineLogSlot is the same as
		 the sessLineSlot.

		 On a LanRover Access Switch, for analog sessLineType
		 calls (dmc sessLineType), sessLineLogSlot is the
		 slot in which the modem resides. For digital sessLineType 
		 calls, sessLineLogSlot is the slot in which the call's 
		 telephone trunk resides.  Range of values:  (1..11).

		 On LanRover Access Switches, if the current session was
		 created over a VPDN interface, the sessLineLogSlot value is 
		 not applicable, therefore, this value should be zero."
	::= { sessLineEntry 26 }

    sessLineLogChan OBJECT-TYPE
	SYNTAX	INTEGER
	ACCESS	read-only
	STATUS	mandatory
	DESCRIPTION
		"On a LanRover or NetModem, this is the same as the 
		 sessLineChan. Range of values:  (1..2).

		 On a LanRover Access Switch, for analog sessLineType
		 calls (dmc sessLineType), sessLineLogChan is the
		 modem on which this session is created.  For digital 
		 sessLineType calls, sessLineLogChan is the telephone trunk,
		 the same value as the sessLinePhysPort.  Range of
		 values: (1..36) for analog calls, (1..4) for digital calls.

		 On LanRover Access Switches, if the current session was
		 created over a VPDN interface, the sessLineLogChan value is 
		 not applicable, therefore, this value should be zero."
	::= { sessLineEntry 27 }

-- Miscellaneous session data

    sessionSessCount OBJECT-TYPE
	SYNTAX	INTEGER
	ACCESS	read-only
	STATUS	mandatory
	DESCRIPTION
		"A count of the number of sessions in progress in the
		 LanRover or LanRover Access Switch."
	::= { session 4 }

END
