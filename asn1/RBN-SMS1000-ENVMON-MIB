-- *****************************************************************
-- RBN-SMS1000-ENVMON-MIB	SMS1000 Environmental Monitor MIB
--
-- Copyright (c) 1998 RedBack Networks, Inc.
-- All rights reserved.
-- 
-- *****************************************************************

RBN-SMS1000-ENVMON-MIB DEFINITIONS ::= BEGIN

IMPORTS
	NOTIFICATION-TYPE, MODULE-IDENTITY,
	OBJECT-TYPE
		FROM SNMPv2-SMI
	TruthValue
		FROM SNMPv2-TC
	MODULE-COMPLIANCE,
	NOTIFICATION-GROUP, OBJECT-GROUP
		FROM SNMPv2-CONF
	rbnMgmt
		FROM RBN-SMI;

rbnSMS1000EnvMonMIB MODULE-IDENTITY
	LAST-UPDATED	"9810062300Z"
	ORGANIZATION	"RedBack Networks, Inc."
	CONTACT-INFO
		"	RedBack Networks, Inc.

		Postal:	1389 Moffett Park Drive
			Sunnyvale, CA  94089-1134
			USA

		 Phone:	+1 408 548 3500
		   Fax: +1 408 548 3599

		E-mail:	mib-info@RedBackNetworks.com"
	DESCRIPTION
		"The MIB used to manage the SMS1000 Environmental
		Monitor functionality."
	::= { rbnMgmt 3 }

rbnSMS1000EnvMonMIBNotifications OBJECT IDENTIFIER
	::= { rbnSMS1000EnvMonMIB 0 }

rbnSMS1000EnvMonMIBObjects OBJECT IDENTIFIER
	::= { rbnSMS1000EnvMonMIB 1 }

rbnSMS1000EnvMonMIBConformance OBJECT IDENTIFIER
	::= { rbnSMS1000EnvMonMIB 2 }

-- MIB Objects

rbnSMS1000FanFail OBJECT-TYPE
	SYNTAX	    TruthValue
	MAX-ACCESS  read-only
	STATUS	    current
	DESCRIPTION
		"The status of the SMS 1000 fan assemblies.  If this
		object has the value true, then one or both of the
		SMS 1000 fan assemblies has failed.  If this object has
		the value false, then all installed fan assemblies are
		operational."
	::= { rbnSMS1000EnvMonMIBObjects 1 }

rbnSMS1000PowerFail OBJECT-TYPE
	SYNTAX	    TruthValue
	MAX-ACCESS  read-only
	STATUS	    current
	DESCRIPTION
		"The status of the SMS 1000 power modules.  If this
		object has the value true, then one or both of the
		SMS 1000 power modules has failed.  If this object has
		the value false, then all installed power modules are
		operational."
	::= { rbnSMS1000EnvMonMIBObjects 2 }

-- Notifications

rbnSMS1000FanFailChange NOTIFICATION-TYPE
	OBJECTS	    { rbnSMS1000FanFail }
	STATUS	    current
	DESCRIPTION
		"A rbnSMS1000FanFailChange notification signifies
		that the value of rbnSMS1000FanFail has changed."
	::= { rbnSMS1000EnvMonMIBNotifications 1 }

rbnSMS1000PowerFailChange NOTIFICATION-TYPE
	OBJECTS	    { rbnSMS1000PowerFail }
	STATUS	    current
	DESCRIPTION
		"A rbnSMS1000PowerFailChange notification signifies
		that the value of rbnSMS1000PowerFail has changed"
	::= { rbnSMS1000EnvMonMIBNotifications 2 }

-- Conformance Statements

rbnSMS1000EnvMonMIBGroups OBJECT IDENTIFIER
	::= { rbnSMS1000EnvMonMIBConformance 1 }

rbnSMS1000EnvMonMIBCompliances OBJECT IDENTIFIER
	::= { rbnSMS1000EnvMonMIBConformance 2 }

rbnSMS1000EnvMonMIBObjectGroup OBJECT-GROUP
	OBJECTS	    {	rbnSMS1000FanFail,
			rbnSMS1000PowerFail
		    }
	STATUS	    current
	DESCRIPTION
		"A collection of objects providing SMS 1000 
		environmental monitor information."
	::= { rbnSMS1000EnvMonMIBGroups 1 }

rbnSMS1000EnvMonMIBNotificationGroup NOTIFICATION-GROUP
	NOTIFICATIONS {	rbnSMS1000FanFailChange,
			rbnSMS1000PowerFailChange
		    }
	STATUS	    current
	DESCRIPTION
		"A collection of notifications providing SMS 1000 
		environmental monitor information."
	::= { rbnSMS1000EnvMonMIBGroups 2 }

rbnSMS1000EnvMonMIBCompliance MODULE-COMPLIANCE
	STATUS	    current
	DESCRIPTION
		"The compliance statement for the SMS 1000 EnvMon MIB"
	MODULE	    -- this module
	GROUP	    rbnSMS1000EnvMonMIBObjectGroup
	DESCRIPTION
		"This group is mandatory for the SMS 1000 Chassis"
	GROUP	    rbnSMS1000EnvMonMIBNotificationGroup
	DESCRIPTION
		"This group is mandatory for the SMS 1000 Chassis"
	::= { rbnSMS1000EnvMonMIBCompliances 1 }
END
