PORT-MIB 

          DEFINITIONS ::= BEGIN

          -- This file contains the definition of the port mib for Coriolis Networks.

          IMPORTS
                  Counter
                      FROM RFC1155-SMI
                  Unsigned32, OBJECT-TYPE, MODULE-IDENTITY, Integer32, 
                  Counter32, Counter64
                     FROM SNMPv2-SMI
                  port, coriolisMibs
                     FROM CORIOLIS-MIB
				      slotNo
				         FROM CARD-MIB
                  ifAdminStatus, ifOperStatus, ifSpeed, InterfaceIndex
                      FROM IF-MIB
                  dot3StatsDuplexStatus
				         FROM EtherLike-MIB
                  ifMauAutoNegConfig
				         FROM MAU-MIB
                  sonetSectionCurrentStatus, sonetLineCurrentStatus, 
                  sonetPathCurrentStatus, sonetVTCurrentStatus
                      FROM SONET-MIB
                  TruthValue
                      FROM SNMPv2-TC
                  TRAP-TYPE
                      FROM RFC-1215;

          portMIB MODULE-IDENTITY
              LAST-UPDATED "0007270000Z"
              ORGANIZATION "Coriolis Networks"
              CONTACT-INFO
                      "        Shubhra Garg

                       Postal: 330 Codman Hill Road,
                               Boxboro MA, 01719.

                          Tel: +1 978 264 1904
                          Fax: +1 978 264 1929

                       E-mail: shubhra@coriolisnet.com"
              DESCRIPTION
                      "The MIB module for cards in coriolis boxes"
              ::= { port 1 }

          portTable OBJECT-TYPE
          SYNTAX SEQUENCE OF PortEntry
          MAX-ACCESS not-accessible
          STATUS current
          DESCRIPTION
          "The port table. This contains the portNo variable, which is used as 
		      an index into specific port tables"
          ::= { port 2 }

          portEntry OBJECT-TYPE
          SYNTAX PortEntry
          MAX-ACCESS not-accessible
          STATUS current
          DESCRIPTION
          "Entry containing the portNo variable"
          INDEX { slotNo, portNo }
          ::= { portTable 1 }

          PortEntry ::= SEQUENCE {
             portNo 	 INTEGER,
	          mib2IfIndex InterfaceIndex
          }

		  portNo OBJECT-TYPE
		  SYNTAX INTEGER(1..16)
		  MAX-ACCESS not-accessible
		  STATUS current
		  DESCRIPTION
		  " The purpose of this variable is to be used as index into tables "
		  ::= { portEntry 1}

	      mib2IfIndex	OBJECT-TYPE
		  SYNTAX	InterfaceIndex
		  MAX-ACCESS	read-only
		  STATUS	current
		  DESCRIPTION	
		      "This variable serves to identify the slot and port number."
		  ::= { portEntry 2}

          -- This table contains attributes specific to ethernet ports

          etherPortTable OBJECT-TYPE
          SYNTAX SEQUENCE OF EtherPortEntry
          MAX-ACCESS not-accessible
          STATUS current
          DESCRIPTION
          "The ethernet port table. This table contains information about
           the ethernet ports in this device."
          ::= { port 3 }

          etherPortEntry OBJECT-TYPE
          SYNTAX EtherPortEntry
          MAX-ACCESS not-accessible
          STATUS current
          DESCRIPTION
          "Entry containing information about ethernet ports"
          INDEX { slotNo, portNo }
          ::= { etherPortTable 1 }

          EtherPortEntry ::= SEQUENCE {
            etherPortSpeedCfg
              INTEGER,
            etherPortSpeedStatus
			  INTEGER,
            etherPortDuplexCfg
              INTEGER,
            etherPortLoopback
              INTEGER,
            etherPortPhyReset
			  INTEGER, 
            etherPortStatsTxPkts64Octets 
              Counter,
            etherPortStatsTxPkts65to127Octets
              Counter,
            etherPortStatsTxPkts128to255Octets
              Counter,
            etherPortStatsTxPkts256to511Octets 
              Counter,
            etherPortStatsTxPkts512to1023Octets
              Counter,
            etherPortStatsTxPkts1024to1518Octets
              Counter,
			etherPortStatsTxPkts1519to1530Octets
			  Counter,        
            etherPortStatsTxFCSErrors
              Counter,
            etherPortStatsTxOversize
              Counter,
            etherPortStatsTxUndersize
              Counter,
		    etherPortStatsTxControlFrames
			  Counter,
		    etherPortStatsTxBadFifoUnderrun
			  Counter,
		    etherPortStatsTxBadFifoOverrun
			  Counter,
		    etherPortStatsTxDropFifoOverrun
			  Counter,
			etherPortStatsTxBadParityError
			  Counter,
			etherPortStatsTxDropParityError
			  Counter,
		    etherPortStatsTxBadSequenceError
			  Counter,
		    etherPortStatsTxDropSequenceError
			  Counter,
		    etherPortStatsTxBadJamError
			  Counter,
		    etherPortStatsTxDropJamError
			  Counter,
			etherPortSpeedTrapEnable
			  INTEGER,
			etherPortDuplexTrapEnable
			  INTEGER,
			etherPortAutonegTrapEnable
			  INTEGER,
		    etherPortRowStatus
			  INTEGER,
	 	    etherPortAutonegAdvSpeed
		      INTEGER,
		    etherPortAutonegAdvDuplex
		      INTEGER,
            etherPortPauseStateReceived
			  INTEGER,
            etherPortVlanMode
			  INTEGER,
            etherPortDefaultVlanId
			  INTEGER,
            etherPortRxOverrun
			  Counter,
            etherPortRxSyncErrors
			  Counter,
            etherPortRxDelSeqErrors
			  Counter,
            etherPortRxFifoOverrunErrors
			  Counter,
            etherPortRxControlFrames
			  Counter,
            etherPortRxThreshOvrszFrames
			  Counter,
			etherPortStatsRxPkts1519to1530Octets
			  Counter           
          }

          etherPortSpeedCfg OBJECT-TYPE
          SYNTAX INTEGER {
            speed10(1),
            speed100(2),
            speed1000(3)
          }
          MAX-ACCESS read-write
          STATUS current
          DESCRIPTION
          " The desired port speed if Autonegotiation is disabled.  Management 
            control of the port speed can also be accomplished through the MAU MIB 
            via ifMauDefaultType.  Note that this object provides redundant information 
            with ifMauType.  Normally, redundant objects are discouraged.  However, in 
            this instance, it allows a management application to configure the duplex 
            mode of an interface without having to know every possible value of ifMauType.
            This was felt to be sufficiently valuable to justify the redundancy."
          ::= { etherPortEntry 1 }

		etherPortSpeedStatus OBJECT-TYPE
          SYNTAX INTEGER {
            speed10(1),
            speed100(2),
            speed1000(3)
          }
          MAX-ACCESS read-write
          STATUS current
          DESCRIPTION
          " The speed of the port.  If autoneg is enabled, this is determined by the 
            results of the autoneg process.  If autoneg is disabled, this is the same 
            as IfAdminSpeed."
          ::= { etherPortEntry 2 }

        etherPortDuplexCfg OBJECT-TYPE
          SYNTAX INTEGER {
            unknown(1),
            half(2),
			full(3)
          }
          MAX-ACCESS read-write
          STATUS current
          DESCRIPTION
          " The desired duplex mode of operation of the MAC entity if Autonegotiation 
            is disabled.  Management control of the duplex mode can also be accomplished 
            through the MAU MIB via ifMauDefaultType.Note that this object provides redundant 
            information with ifMauType.  Normally, redundant objects are discouraged.  However, 
            in this instance, it allows a management application to configure the duplex mode 
            of an interface without having to know every possible value of ifMauType.  This was 
            felt to be sufficiently valuable to justify the redundancy."
          ::= { etherPortEntry 3 }

          etherPortLoopback OBJECT-TYPE
          SYNTAX INTEGER {
            enable(1),
            disable(2)
          }
          MAX-ACCESS read-write
          STATUS current
          DESCRIPTION
          " Enables/disables loopback mode."
          ::= { etherPortEntry 4}         

--
		  etherPortPhyReset OBJECT-TYPE
		  SYNTAX INTEGER {
		    inReset(1),
			outOfReset(2)
          }
          MAX-ACCESS read-write
          STATUS current
          DESCRIPTION
          " Ethernet port phy reset"
          ::= { etherPortEntry 5 }  
   
          etherPortStatsTxPkts64Octets OBJECT-TYPE 
          SYNTAX Counter
          MAX-ACCESS read-only
          STATUS current
          DESCRIPTION
          " Total 64 byte packets transmitted on ethernet port."
          ::= { etherPortEntry 6 } 

  
          etherPortStatsTxPkts65to127Octets OBJECT-TYPE 
          SYNTAX Counter
          MAX-ACCESS read-only
          STATUS current
          DESCRIPTION
          " The total number of packets (including bad packets) transmitted 
            that were between 65 and 127 octets in length inclusive (excluding 
            framing bits but including FCS octets)."
          ::= { etherPortEntry 7 } 

  
          etherPortStatsTxPkts128to255Octets OBJECT-TYPE 
          SYNTAX Counter
          MAX-ACCESS read-only
          STATUS current
          DESCRIPTION
          " The total number of packets (including bad packets) transmitted that 
            were between 128 and 255 octets in length inclusive (excluding framing 
            bits but including FCS octets)."
          ::= { etherPortEntry 8 } 


          etherPortStatsTxPkts256to511Octets OBJECT-TYPE 
          SYNTAX Counter
          MAX-ACCESS read-only
          STATUS current
          DESCRIPTION
          " The total number of packets (including bad packets) transmitted that 
            were between 256 and 511 octets in length inclusive (excluding framing 
            bits but including FCS octets)."
          ::= { etherPortEntry 9 } 

            
          etherPortStatsTxPkts512to1023Octets OBJECT-TYPE 
          SYNTAX Counter
          MAX-ACCESS read-only
          STATUS current
          DESCRIPTION
          " The total number of packets (including bad packets) transmitted that 
            were between 512 and 1023 octets in length inclusive (excluding framing 
            bits but including FCS octets)."
          ::= { etherPortEntry 10 } 


          etherPortStatsTxPkts1024to1518Octets OBJECT-TYPE 
          SYNTAX Counter
          MAX-ACCESS read-only
          STATUS current
          DESCRIPTION
          " The total number of packets (including bad packets) transmitted that 
            were between 1024 and 1518 octets in length inclusive (excluding 
            framing bits but including FCS octets)."
          ::= { etherPortEntry 11 } 
 
          etherPortStatsTxPkts1519to1530Octets OBJECT-TYPE
		  SYNTAX Counter
          MAX-ACCESS read-only
          STATUS current
          DESCRIPTION
          " The total number of packets (including bad packets) transmitted 
            that were between 1519 and 1530 octets in length inclusive (excluding 
            framing bits but including FCS octets)."
          ::= { etherPortEntry 12 } 

          etherPortStatsTxFCSErrors OBJECT-TYPE
          SYNTAX Counter
          MAX-ACCESS read-only
          STATUS current
          DESCRIPTION
          " Total packets transmitted on ethernet port with FCS errors (if MAC 
            generates the FCS, this can never be incremented)."
          ::= { etherPortEntry 13 } 

          etherPortStatsTxOversize OBJECT-TYPE
          SYNTAX Counter
          MAX-ACCESS read-only
          STATUS current
          DESCRIPTION
          " Number of frames transmitted greater than 1518 bytes."
          ::= { etherPortEntry 14 } 

          etherPortStatsTxUndersize OBJECT-TYPE
          SYNTAX Counter
          MAX-ACCESS read-only
          STATUS current
          DESCRIPTION
          " Number of packets less than 64 bytes transmitted."
          ::= { etherPortEntry 15 } 

		  etherPortStatsTxControlFrames OBJECT-TYPE
          SYNTAX Counter
          MAX-ACCESS read-only
          STATUS current
          DESCRIPTION
          " Number of control frames transmitted."
          ::= { etherPortEntry 16 } 

		  etherPortStatsTxBadFifoUnderrun OBJECT-TYPE
          SYNTAX Counter
          MAX-ACCESS read-only
          STATUS current
          DESCRIPTION
          " Number of bad frames (due to Transmit FIFO underrun) transmitted."
          ::= { etherPortEntry 17 } 

		  etherPortStatsTxBadFifoOverrun OBJECT-TYPE
		  SYNTAX Counter
          MAX-ACCESS read-only
          STATUS current
          DESCRIPTION
          " Number of bad frames (due to Transmit FIFO overrun) transmitted."
          ::= { etherPortEntry 18 } 

		  etherPortStatsTxDropFifoOverrun OBJECT-TYPE
          SYNTAX Counter
          MAX-ACCESS read-only
          STATUS current
          DESCRIPTION
          " Number of frames dropped due to Transmit FIFO underrun."
          ::= { etherPortEntry 19 } 

		  etherPortStatsTxBadParityError OBJECT-TYPE
          SYNTAX Counter
          MAX-ACCESS read-only
          STATUS current
          DESCRIPTION
          " Number of bad frames (due to parity error) transmitted."
          ::= { etherPortEntry 20 } 

		  etherPortStatsTxDropParityError OBJECT-TYPE
          SYNTAX Counter
          MAX-ACCESS read-only
          STATUS current
          DESCRIPTION
          " Number of bad frames (due to parity error) dropped."
          ::= { etherPortEntry 21 } 

		  etherPortStatsTxBadSequenceError OBJECT-TYPE
          SYNTAX Counter
          MAX-ACCESS read-only
          STATUS current
          DESCRIPTION
          " Number of bad frames (due to frame Sequence Error) transmitted."
          ::= { etherPortEntry 22 } 

		  etherPortStatsTxDropSequenceError OBJECT-TYPE
          SYNTAX Counter
          MAX-ACCESS read-only
          STATUS current
          DESCRIPTION
          " Number of bad frames (due to frame Sequence Error) dropped."
          ::= { etherPortEntry 23 } 

		  etherPortStatsTxBadJamError OBJECT-TYPE
          SYNTAX Counter
          MAX-ACCESS read-only
          STATUS current
          DESCRIPTION
          " Number of bad frames (due to Jam Bit Error) transmitted."
          ::= { etherPortEntry 24 } 

		  etherPortStatsTxDropJamError OBJECT-TYPE
          SYNTAX Counter
          MAX-ACCESS read-only
          STATUS current
          DESCRIPTION
          " Number of bad frames (due to Jam Bit Error) dropped."
          ::= { etherPortEntry 25 } 

		  etherPortSpeedTrapEnable OBJECT-TYPE
          SYNTAX INTEGER {
            enabled(1),
			disabled(2)
          }
          MAX-ACCESS read-write
          STATUS current
          DESCRIPTION
          " Indicates whether portSpeedTrap traps should be generated for this interface."
          ::= { etherPortEntry 26 }

		  etherPortDuplexTrapEnable OBJECT-TYPE
          SYNTAX INTEGER {
            enabled(1),
			disabled(2)
          }
          MAX-ACCESS read-write
          STATUS current
          DESCRIPTION
          " Ethernet port duplex trap enable "
          ::= { etherPortEntry 27 }

		  etherPortAutonegTrapEnable OBJECT-TYPE
          SYNTAX INTEGER {
            enabled(1),
			disabled(2)
          }
          MAX-ACCESS read-write
          STATUS current
          DESCRIPTION
          " Indicates whether autoNegCompleteTrap traps should be generated 
            for this interface."
          ::= { etherPortEntry 28 }

		  etherPortRowStatus OBJECT-TYPE
          SYNTAX INTEGER {
            active(1),
            notInService(2),
            createAndGo(4),
            createAndWait(5),
            destroy(6)
          }
          MAX-ACCESS read-write
          STATUS current
          DESCRIPTION
          " This variable is used to create or delete instances of ethernet ports
            This variable subsumes the admin state variable, and once the row is
            created, its value returns the admin state of the port"
          ::= {etherPortEntry 29}

          etherPortAutonegAdvSpeed OBJECT-TYPE
	      SYNTAX INTEGER {
	            speed10(1),
				speed100(2),
				speed1000(3)
			     }
          MAX-ACCESS read-write
          STATUS current
          DESCRIPTION
          " This specifies what speed capability is advertised for autonegotiation.  
            If 100 MBPS is set, then 10 MBPS is also advertised.This does not apply 
            to Gig Ethernet Phys, since they do not autonegotiate speed or duplex."
          ::= { etherPortEntry 30 }

          etherPortAutonegAdvDuplex OBJECT-TYPE
	      SYNTAX INTEGER {
	            unknown (1),
				half (2),
				full (3)
			     }
          MAX-ACCESS read-write
          STATUS current
          DESCRIPTION
          " This specifies what duplex capability is advertised for autonegotiation.  
            If Full Duplex is set, then Half Duplex is also adveetised.This does not 
            apply to Gig Ethernet Phys, since they do not autonegotiate speed or duplex."
          ::= { etherPortEntry 31 }

		  etherPortPauseStateReceived OBJECT-TYPE
		  SYNTAX INTEGER {
		      noPause(1),
			  enableTx(2),
			  enableRx(3),
			  enableTxRx(4),
			  undefined(5)  
		      }
          MAX-ACCESS read-only
          STATUS current
          DESCRIPTION
          " The PAUSE mode received from the remote device, as read from the Auto 
		    Negotiation Partner Ability GMII Register of the PHY.If autoNegotiation
		    is not enabled and completed, then this is set to undefined. This is 
			used to determine the dot3PauseOperMode for the interface. "
          ::= { etherPortEntry 32 }

--
          etherPortVlanMode OBJECT-TYPE
		  SYNTAX INTEGER {
            enabled(1),
			stripVID(2),
			transparent(3)		      
		  }
		  MAX-ACCESS read-write
		  STATUS current
		  DESCRIPTION
		  " Specifies the VLAN mode for the port "
		  ::= { etherPortEntry 33 }

          etherPortDefaultVlanId OBJECT-TYPE
		  SYNTAX INTEGER 
		  MAX-ACCESS read-write
		  STATUS current
		  DESCRIPTION
		  " Specifies what the default Vlan Id is for the port.  
		    This is used on ingress only if vlanMode is Enabled and a frame is received 
			either untagged or tagged with a VID not known to the port. "
          ::= { etherPortEntry 34 }

          etherPortRxOverrun OBJECT-TYPE
		  SYNTAX Counter
		  MAX-ACCESS read-only
		  STATUS current
		  DESCRIPTION
		  " The total number of packets dropped by the GMAC due to the occurence of a receive
		    overrun (gig only- supported by GMAC-D2 and later)"
          ::= { etherPortEntry 35 }

--
          etherPortRxSyncErrors OBJECT-TYPE
		  SYNTAX Counter
		  MAX-ACCESS read-only
		  STATUS current
		  DESCRIPTION
		  " The total number of packets dropped due to loss of sync during packet reception. 
		   (GIG only- supported by GMAC-D2 and later)"
          ::= { etherPortEntry 36 }
		  			 
--
          etherPortRxDelSeqErrors OBJECT-TYPE
		  SYNTAX Counter
		  MAX-ACCESS read-only
		  STATUS current
		  DESCRIPTION
		  " The total number of packets dropped due to delimiter sequence errors as detected 
		    by the GMAC during packet reception. (GIG only- supported by GMAC-D2 and later)"
          ::= { etherPortEntry 37 }

--			 
          etherPortRxFifoOverrunErrors OBJECT-TYPE
		  SYNTAX Counter
		  MAX-ACCESS read-only
		  STATUS current
		  DESCRIPTION
		  " The total number of packets dropped by the GMAC due to the occurence of a receive
		    FIFO overrun (gig only- supported by GMAC-D2 and later)"
          ::= { etherPortEntry 38 }
			 
          etherPortRxControlFrames OBJECT-TYPE
		  SYNTAX Counter
		  MAX-ACCESS read-only
		  STATUS current
		  DESCRIPTION
		  " Number of control frames received by this port "
          ::= { etherPortEntry 39 }

--			 
          etherPortRxThreshOvrszFrames OBJECT-TYPE
		  SYNTAX Counter
		  MAX-ACCESS read-only
		  STATUS current
		  DESCRIPTION
		  " The total number of threshold oversized frames received by the GMAC (gig only - 
		    supported by GMAC-D2 and later)"
          ::= { etherPortEntry 40 }
			 
		  etherPortStatsRxPkts1519to1530Octets OBJECT-TYPE
		  SYNTAX Counter
		  MAX-ACCESS read-only
		  STATUS current
		  DESCRIPTION
		  " The total number of packets (including bad packets) received 
		    that were between 1519 and 1530 octets in length inclusive (excluding
		    framing bits but including FCS octets)."
          ::= { etherPortEntry 41 }
			           

          -- The DS1 TDM IO port table

          tdmIoDS1PortTable OBJECT-TYPE
          SYNTAX SEQUENCE OF TdmIoDS1PortEntry
          MAX-ACCESS not-accessible
          STATUS current
          DESCRIPTION
          "The DS1 TDM IO Port Table"
          ::= { port 4 }

          tdmIoDS1PortEntry OBJECT-TYPE
          SYNTAX TdmIoDS1PortEntry
          MAX-ACCESS not-accessible
          STATUS current
          DESCRIPTION
          "Entry containing information about TDM IO DS1 ports"
          INDEX { slotNo, portNo }
          ::= { tdmIoDS1PortTable 1 }

          TdmIoDS1PortEntry ::= SEQUENCE {
            tdmIoDS1PortType
            INTEGER,
            tdmIoDS1PortTiming
            INTEGER,
            tdmIoDS1PortBuildOut
            INTEGER,
            tdmIoDS1PortFraming
            INTEGER,
            tdmIoDS1PortCoding
            INTEGER,
            tdmIoDS1PortLoopbackState
            INTEGER,
            tdmIoDS1PortLoopbackType
            INTEGER,
            tdmIoDS1PortLoopbackResults
            INTEGER,
            tdmIoDS1PortLoopbackLLbActCode
            INTEGER,
            tdmIoDS1PortLoopbackLLbDeactCode
            INTEGER,
            tdmIoDS1PortLoopbackLlbActCodeLen
            INTEGER,
            tdmIoDS1PortLoopbackLlbDeactCodeLen
            INTEGER,
            tdmIoDS1PortLoopbackLlbControl
            INTEGER,
            tdmIoDS1PortLoopbackLlbGenPath
            INTEGER,
            tdmIoDS1PortLoopbackLlbMonPath
            INTEGER,
            tdmIoDS1PortPrbsAlgorithm
            INTEGER,
            tdmIoDS1PortPrbsInversion
            INTEGER,
            tdmIoDS1PortPrbsGenPath
            INTEGER,
            tdmIoDS1PortPrbsMonPath
            INTEGER,
            tdmIoDS1PortPrbsMonitor
            INTEGER,
            tdmIoDS1PortPrbsTransmit
            INTEGER,
            tdmIoDS1PortPrbsBec
            Counter,
            tdmIoDS1PortBertState
            INTEGER,
            tdmIoDS1PortBertPattern
            INTEGER,
            tdmIoDS1PortBertDuration
            INTEGER,
            tdmIoDS1PortBertResults
            INTEGER,
            tdmIoDS1PortLineESS15Min
			INTEGER,
			tdmIoDS1PortPathESS15Min
			INTEGER,
			tdmIoDS1PortLineESS1Day
			INTEGER,
			tdmIoDS1PortPathESS1Day
			INTEGER,
			tdmIoDS1PortPathCVS15Min
			INTEGER,
			tdmIoDS1PortPathCVS1Day
			INTEGER,
			tdmIoDS1PortPathSESS15Min
			INTEGER,
			tdmIoDS1PortPathSESS1Day
			INTEGER,
			tdmIoDS1PortPathSASS15Min
			INTEGER,
			tdmIoDS1PortPathSASS1Day
			INTEGER,
			tdmIoDS1PortPathCSS15Min
			INTEGER,
			tdmIoDS1PortPathCSS1Day
			INTEGER,
			tdmIoDS1PortPathUASS15Min
			INTEGER,
			tdmIoDS1PortRowStatus
			INTEGER,
			dsxStatus
			INTEGER,
			tdmIoDS1PortLCVCount
			INTEGER
            }

            tdmIoDS1PortType OBJECT-TYPE
            SYNTAX INTEGER {
              ds1(1)
            }
            MAX-ACCESS read-write
            STATUS current
            DESCRIPTION
            " The type of TDM IO DS1 port"
            ::= {tdmIoDS1PortEntry 1}

            tdmIoDS1PortTiming OBJECT-TYPE
			SYNTAX INTEGER {
              loopTiming(1),
              localTiming(2),
              throughTiming(3)
            }
            MAX-ACCESS read-write
            STATUS current
            DESCRIPTION
            " Clock source for the DS1 port

             'loopTiming' indicates that the recovered re-
            ceive clock is used as the transmit clock.

             'localTiming' indicates that a local clock
            source is used or when an external clock is
            attached to the box containing the interface.

             'throughTiming' indicates that recovered re-
            ceive clock from another interface is used as
            the transmit clock."
            ::= {tdmIoDS1PortEntry 2}

            tdmIoDS1PortBuildOut OBJECT-TYPE
            SYNTAX INTEGER {
              shortHaulMax133Feet(1),          
              shortHaulMax266Feet(2),
              shortHaulMax399Feet(3),
              shortHaulMax533Feet(4),
              shortHaulMax655Feet(5),          
              longHaulZeroDB(6),
              longHaulSevenFiveDB(7),
              longHaulOneFiveDB(8),
              longHaulTwentyTwoDB(9)
            }
            MAX-ACCESS read-write
            STATUS current
            DESCRIPTION
            "Line Build Out for Signal Strength. For short haul, a distance (in feet)
             is chosen. For long haul, an attenuation strength is chosen in Decibels. "
            ::= {tdmIoDS1PortEntry 5}

            tdmIoDS1PortFraming OBJECT-TYPE
            SYNTAX INTEGER {
              ds1unframed(1)
            }
            MAX-ACCESS read-only
            STATUS current
            DESCRIPTION
            "Framing type implemented for this interface."
            ::= {tdmIoDS1PortEntry 6}

            tdmIoDS1PortCoding OBJECT-TYPE
			SYNTAX INTEGER {
			   b8zs(2),
			   ami(5)
            }
            MAX-ACCESS read-write
            STATUS current
            DESCRIPTION
            "The type of Zero Code Suppression used on this interface.
             
             B8ZS refers to the use of a specified pattern
             of normal bits and bipolar violations which are
             used to replace a sequence of eight zero bits.

             AMI refers to a mode wherein no zero code
             suppression is present and the line encoding does
             not solve the problem directly.  In this
             application, the higher layer must provide data
             which meets or exceeds the pulse density
             requirements, such as inverting HDLC data."
            ::= {tdmIoDS1PortEntry 7}

            tdmIoDS1PortLoopbackState OBJECT-TYPE
            SYNTAX INTEGER {
              idle(1),
			  running(2)
            }
            MAX-ACCESS read-only
            STATUS current
            DESCRIPTION
            "This object indicates the state of loopback on this
             interface. 'Idle' indicates that there is no loopback
             running and 'running' indicates that this interface is
             in loopback mode."
            ::= {tdmIoDS1PortEntry 8}

            tdmIoDS1PortLoopbackType OBJECT-TYPE
            SYNTAX INTEGER { 
              noLoop(1),
			  localOn(8),
			  digitalOn(9),
			  remoteOn(10)
            }
            MAX-ACCESS read-write
            STATUS current
            DESCRIPTION
            "This object indicates the type of loopback on this
             interface. 

            noLoop    - the interface is not in loopBack mode.
            localOn   - the interface is running in internal loop.
            digitalOn - the interface is running in internal loop.
            remoteOn  - the interface is looping away external data."
            ::= {tdmIoDS1PortEntry 9}

            tdmIoDS1PortLoopbackResults OBJECT-TYPE
            SYNTAX INTEGER {
              failure(1),
			  success(2)
            }
            MAX-ACCESS read-only
            STATUS current
            DESCRIPTION
            "Results from previous loopback on this port"
            ::= {tdmIoDS1PortEntry 10}

            tdmIoDS1PortLoopbackLLbActCode OBJECT-TYPE
            SYNTAX INTEGER
            MAX-ACCESS read-write
            STATUS current
            DESCRIPTION
            "User code to enable Automatic Remote Loopback(ARL)"
            ::= {tdmIoDS1PortEntry 11}

            tdmIoDS1PortLoopbackLLbDeactCode OBJECT-TYPE
            SYNTAX INTEGER
            MAX-ACCESS read-write
            STATUS current
            DESCRIPTION
            "User code to disable Automatic Remote Loopback(ARL)"
            ::= {tdmIoDS1PortEntry 12}

            tdmIoDS1PortLoopbackLlbActCodeLen OBJECT-TYPE
            SYNTAX INTEGER {
              up5Bit(1),
              up6Bit(2),
              up7Bit(3),
              up8Bit(4)
            }
            MAX-ACCESS read-write
            STATUS current
            DESCRIPTION
            "Length of user code to enable Automatic Remote Loopback(ARL)"
            ::= {tdmIoDS1PortEntry 13}

            tdmIoDS1PortLoopbackLlbDeactCodeLen OBJECT-TYPE
            SYNTAX INTEGER {
              down5Bit(1),
              down6Bit(2),
              down7Bit(3),
              down8Bit(4)
            }
            MAX-ACCESS read-write
            STATUS current
            DESCRIPTION
            "Length of user code to disable Automatic Remote Loopback(ARL)"
            ::= {tdmIoDS1PortEntry 14}

            tdmIoDS1PortLoopbackLlbControl OBJECT-TYPE
            SYNTAX INTEGER {
              genOff(1),
              genActOn(2),
              genDeActOn(3),
              monOff(4),
              monOn(5)
            }
            MAX-ACCESS read-write
            STATUS current
            DESCRIPTION
            "LLBCODE(activate/deactivate) generation/monitoring control"
            ::= {tdmIoDS1PortEntry 15}

            tdmIoDS1PortLoopbackLlbGenPath OBJECT-TYPE
            SYNTAX INTEGER {
              genRcv(1),
              genXmit(2)
            }
            MAX-ACCESS read-write
            STATUS current
            DESCRIPTION
            "The path (xmit/rcv) for LLBCODE generation"
            ::= {tdmIoDS1PortEntry 16}

            tdmIoDS1PortLoopbackLlbMonPath OBJECT-TYPE
            SYNTAX INTEGER {
              monRcv(1),
              monXmit(2)
            }
            MAX-ACCESS read-write
            STATUS current
            DESCRIPTION
            "The path (xmit/rcv) for LLBCODE monitoring"
            ::= {tdmIoDS1PortEntry 17}


            tdmIoDS1PortPrbsAlgorithm OBJECT-TYPE
            SYNTAX INTEGER {
              algo215(1),
              algo220(2)
            }
            MAX-ACCESS read-write
            STATUS current
            DESCRIPTION
            "The PRBS Algorithm"
            ::= {tdmIoDS1PortEntry 18}

            tdmIoDS1PortPrbsInversion OBJECT-TYPE
            SYNTAX INTEGER {
              off(1),
              on(2)
            }
            MAX-ACCESS read-only
            STATUS current
            DESCRIPTION
            "Whether the PRBS stream will be inverted"
            ::= {tdmIoDS1PortEntry 19}

            tdmIoDS1PortPrbsGenPath OBJECT-TYPE
            SYNTAX INTEGER {
              genRcv(1),
              genXmit(2)
            }
            MAX-ACCESS read-write
            STATUS current
            DESCRIPTION
            " The PRBS generator path"
            ::= {tdmIoDS1PortEntry 20}

            tdmIoDS1PortPrbsMonPath OBJECT-TYPE
            SYNTAX INTEGER {
              monRcv(1),
              monXmit(2)
            }
            MAX-ACCESS read-write
            STATUS current
            DESCRIPTION
            "The PRBS monitor path"
            ::= {tdmIoDS1PortEntry 21}

            tdmIoDS1PortPrbsMonitor OBJECT-TYPE
            SYNTAX INTEGER {
              off(1),
              on(2)
            }
            MAX-ACCESS read-write
            STATUS current
            DESCRIPTION
            "PRBS monitor - is it off or on?"
            ::= {tdmIoDS1PortEntry 22}

            tdmIoDS1PortPrbsTransmit OBJECT-TYPE
            SYNTAX INTEGER {
              off(1),
              on(2)
            }
            MAX-ACCESS read-write
            STATUS current
            DESCRIPTION
            "PRBS or normal transmission on transmission line"
            ::= {tdmIoDS1PortEntry 23}

            tdmIoDS1PortPrbsBec OBJECT-TYPE
            SYNTAX Counter
            MAX-ACCESS read-only
            STATUS current
            DESCRIPTION
            "The PRBS bit error counter"
            ::= {tdmIoDS1PortEntry 24}

            tdmIoDS1PortBertState OBJECT-TYPE
            SYNTAX INTEGER {
              idle(1),
              running(2),
              other(3)
            }
            MAX-ACCESS read-only
            STATUS current
            DESCRIPTION
            "User specified BERT status"
            ::= {tdmIoDS1PortEntry 25}

            tdmIoDS1PortBertPattern OBJECT-TYPE
            SYNTAX INTEGER {
              pattern223(1),          
              pattern220(2),          
              patternQrss(3),          
              pattern215(4),           
              pattern211(5),           
              patternAllZeros(6),      
              patternAllOnes(7),       
              patternAlternate(8)     
            }
            MAX-ACCESS read-write
            STATUS current
            DESCRIPTION
            "User specified BERT type"
            ::= {tdmIoDS1PortEntry 26}

            tdmIoDS1PortBertDuration OBJECT-TYPE
            SYNTAX INTEGER {
              oneMin(1),
              fiveMin(2),
              thirtyMin(3),
              oneHour(4),
              twelveHour(5),
              twentyfourHour(6)
            }
            MAX-ACCESS read-write 
            STATUS current
            DESCRIPTION
            "User specified BERT duration"
            ::= {tdmIoDS1PortEntry 27}

            tdmIoDS1PortBertResults OBJECT-TYPE
            SYNTAX INTEGER {
              timeLeft(1),
              totalBitErrs(2),
              totalBits(3)
            }
            MAX-ACCESS read-only
            STATUS current
            DESCRIPTION
            "Results from previous BERT test on this port"
            ::= {tdmIoDS1PortEntry 28}

			tdmIoDS1PortLineESS15Min OBJECT-TYPE
			SYNTAX INTEGER(1..900)
			MAX-ACCESS read-write
            STATUS current
            DESCRIPTION
            "The 15 minute Line Errored Seconds Threshold"
            ::= {tdmIoDS1PortEntry 29}

			tdmIoDS1PortPathESS15Min OBJECT-TYPE
			SYNTAX INTEGER(1..900)
			MAX-ACCESS read-write
            STATUS current
            DESCRIPTION
            "The 15 minute Path Errored Seconds Threshold"
            ::= {tdmIoDS1PortEntry 30}
			
			tdmIoDS1PortLineESS1Day OBJECT-TYPE
			SYNTAX INTEGER(1..65535)
			MAX-ACCESS read-write
            STATUS current
            DESCRIPTION
            "The 1 Day Line Errored Seconds Threshold"
            ::= {tdmIoDS1PortEntry 31}
			
			tdmIoDS1PortPathESS1Day OBJECT-TYPE
			SYNTAX INTEGER(1..65535)
			MAX-ACCESS read-write
            STATUS current
            DESCRIPTION
            "The 1 Day Path Errored Seconds Threshold"
            ::= {tdmIoDS1PortEntry 32}
			
			tdmIoDS1PortPathCVS15Min OBJECT-TYPE
			SYNTAX INTEGER(1..16383)
			MAX-ACCESS read-write
            STATUS current
            DESCRIPTION
            "The 15 minute Path Coding Violations Threshold"
            ::= {tdmIoDS1PortEntry 33}
			
			tdmIoDS1PortPathCVS1Day OBJECT-TYPE
			SYNTAX INTEGER(1..1048575)
			MAX-ACCESS read-write
            STATUS current
            DESCRIPTION
            "The 1 day Path Coding Violations Threshold"
            ::= {tdmIoDS1PortEntry 34}
			
			tdmIoDS1PortPathSESS15Min OBJECT-TYPE
			SYNTAX INTEGER(1..900)
			MAX-ACCESS read-write
            STATUS current
            DESCRIPTION
            "The 15 minute Path Severely Errored Seconds Threshold"
            ::= {tdmIoDS1PortEntry 35}
			
			tdmIoDS1PortPathSESS1Day OBJECT-TYPE
			SYNTAX INTEGER(1..65535)
			MAX-ACCESS read-write
            STATUS current
            DESCRIPTION
            "The 1 day Path Severely Errored Seconds Threshold"
            ::= {tdmIoDS1PortEntry 36}
			
			tdmIoDS1PortPathSASS15Min OBJECT-TYPE
			SYNTAX INTEGER(1..900)
			MAX-ACCESS read-write
            STATUS current
            DESCRIPTION
            "The 15 minute Path AIS seconds Threshold"
            ::= {tdmIoDS1PortEntry 37}
			
			tdmIoDS1PortPathSASS1Day OBJECT-TYPE
			SYNTAX INTEGER(1..65535)
			MAX-ACCESS read-write
            STATUS current
            DESCRIPTION
            "The 1 day Path AIS seconds Threshold"
            ::= {tdmIoDS1PortEntry 38}
			
			tdmIoDS1PortPathCSS15Min OBJECT-TYPE
			SYNTAX INTEGER(1..900)
			MAX-ACCESS read-write
            STATUS current
            DESCRIPTION
            "The 15 minute path controlled slip seconds threshold"
            ::= {tdmIoDS1PortEntry 39}
			
			tdmIoDS1PortPathCSS1Day OBJECT-TYPE
			SYNTAX INTEGER(1..65535)
			MAX-ACCESS read-write
            STATUS current
            DESCRIPTION
            "The 1 day path controlled slip seconds threshold"
            ::= {tdmIoDS1PortEntry 40}
			
			tdmIoDS1PortPathUASS15Min OBJECT-TYPE
			SYNTAX INTEGER(1..900)
			MAX-ACCESS read-write
            STATUS current
            DESCRIPTION
            "The 15 minute path unavailable seconds threshold"
            ::= {tdmIoDS1PortEntry 41}

		    tdmIoDS1PortRowStatus OBJECT-TYPE
            SYNTAX INTEGER {
            active(1),
            notInService(2),
            createAndGo(4),
            createAndWait(5),
            destroy(6)
            }
            MAX-ACCESS read-write
            STATUS current
            DESCRIPTION
           " This variable is used to create or delete instances of TDM IO DS1 ports.
             This variable subsumes the admin state variable, and once the row is
             created, its value returns the admin state of the port"
            ::= {tdmIoDS1PortEntry 42}

	dsxStatus	OBJECT-TYPE
	    SYNTAX	INTEGER {
	                dsx-rcvrai-failure-declared   (1),
			dsx-rcvrai-failure-cleared    (2),
			dsx-xmitrai-failure-declared  (3),
			dsx-xmitrai-failure-cleared   (4),
			dsx-rcvais-failure-declared   (5),
			dsx-rcvais-failure-cleared    (6),
			dsx-xmitais-failure-declared  (7),
			dsx-xmitais-failure-cleared   (8),
			dsx-los-failure-declared      (9),
			dsx-los-failure-cleared       (10),
			dsx-lof-failure-declared      (11),
			dsx-lof-failure-cleared       (12),
			dsx-other-failure-declared    (13),
			dsx-other-failure-cleared     (14),
			dsx-uas-failure-declared      (15),
			dsx-uas-failure-cleared       (16),
			dsx-exz-failure-declared      (17),
			dsx-exz-failure-cleared       (18),
			dsx-pden-failure-declared     (19),
			dsx-pden-failure-cleared      (20)
	    }
	    MAX-ACCESS	accessible-for-notify
	    STATUS	current
	    DESCRIPTION
		"DSx line status."
	    ::= {tdmIoDS1PortEntry 43 }

          tdmIoDS1PortLCVCount OBJECT-TYPE
          SYNTAX INTEGER
          MAX-ACCESS read-only
          STATUS current
          DESCRIPTION
          "Count of Line Code Violations."
          ::= { tdmIoDS1PortEntry 44 }


		  -- The proprietary SONET port table

          sonetPortTable OBJECT-TYPE
          SYNTAX SEQUENCE OF SonetPortEntry
          MAX-ACCESS not-accessible
          STATUS current
          DESCRIPTION
          "The proprietary SONET Port Table"
          ::= { port 5}

          sonetPortEntry OBJECT-TYPE
          SYNTAX SonetPortEntry
          MAX-ACCESS not-accessible
          STATUS current
          DESCRIPTION
          "Entry containing information about SONET ports"
          INDEX { slotNo, portNo }
          ::= { sonetPortTable 1 }

          SonetPortEntry ::= SEQUENCE {
		    sonetPortType
			INTEGER,
			sonetPortIdString
			OCTET STRING,
			sonetPortTiming
			INTEGER,
			sonetPortLoopback
			INTEGER,
			sonetPortScrambling
			INTEGER,
			sonetPortChannelization
			INTEGER,
			sonetPortConfigedChans
			Unsigned32,
			sonetPortSectESS15Min
			INTEGER,
			sonetPortLineESS15Min
			INTEGER,
			sonetPortPathESS15Min
			INTEGER,
			sonetPortSectESS1Day
			INTEGER,
			sonetPortLineESS1Day
			INTEGER,
			sonetPortPathESS1Day
			INTEGER,
			sonetPortSectCVS15Min
			INTEGER,
			sonetPortLineCVS15Min
			INTEGER,
			sonetPortPathCVS15Min
			INTEGER,
			sonetPortSectCVS1Day
			INTEGER,
			sonetPortLineCVS1Day
			INTEGER,
			sonetPortPathCVS1Day
			INTEGER,
			sonetPortSectSESS15Min
			INTEGER,
			sonetPortLineSESS15Min
			INTEGER,
			sonetPortPathSESS15Min
			INTEGER,
		    sonetPortSectSESS1Day
			INTEGER,
			sonetPortLineSESS1Day
			INTEGER,
			sonetPortPathSESS1Day
			INTEGER,
			sonetPortLineUASS15Min
			INTEGER,
			sonetPortPathUASS15Min
			INTEGER,
			sonetPortLineUASS1Day
			INTEGER,
			sonetPortPathUASS1Day
			INTEGER,
			sonetPortRowStatus
			INTEGER,
			sonetTCAStatus
			INTEGER
			}

			sonetPortType OBJECT-TYPE
			SYNTAX INTEGER {
			   oc12c(1),
            oc12sts1(2)
            }
			MAX-ACCESS read-write
            STATUS current
            DESCRIPTION
           "The type of SONET port"
            ::= { sonetPortEntry 1 }

			sonetPortIdString OBJECT-TYPE
			SYNTAX OCTET STRING
			MAX-ACCESS read-write
            STATUS current
            DESCRIPTION
           "The identifier string for the SONET port"
            ::= { sonetPortEntry 2 }
						
			sonetPortTiming OBJECT-TYPE
			SYNTAX INTEGER {
			 internal(1),
			 external(2)
            }
			MAX-ACCESS read-write
            STATUS current
            DESCRIPTION
           "Clock source for the port"
            ::= { sonetPortEntry 3 }

			sonetPortLoopback OBJECT-TYPE
			SYNTAX INTEGER {
			  slle(1),
			  sdle(2),
			  pdle(3),
			  sllben(4),
			  none(5)
            }
			MAX-ACCESS read-write
            STATUS current
            DESCRIPTION
           " The types of loopback available on the SONET interface."
            ::= { sonetPortEntry 4 }
			
			sonetPortScrambling OBJECT-TYPE
			SYNTAX INTEGER {
			  enable(1),
			  disable(2)
            }
			MAX-ACCESS read-write
            STATUS current
            DESCRIPTION
           " Whether port scrambling is enabled or disabled "
            ::= { sonetPortEntry 5 }

			sonetPortChannelization OBJECT-TYPE
			SYNTAX INTEGER {
			  concatenated(1),
			  nonConcatenated(2)
            }
			MAX-ACCESS read-write
            STATUS current
            DESCRIPTION
           " Whether the physical port is concatenated or not "
            ::= { sonetPortEntry 6 }

			sonetPortConfigedChans OBJECT-TYPE
			SYNTAX Unsigned32
			MAX-ACCESS read-only
            STATUS current
            DESCRIPTION
           " The channels configured on the port "
            ::= { sonetPortEntry 7 }
			
			sonetPortSectESS15Min OBJECT-TYPE
			SYNTAX INTEGER(1..900) 
			MAX-ACCESS read-write
            STATUS current
            DESCRIPTION
           " 15 minute section errored seconds threshold"
            ::= { sonetPortEntry 8}
			
			sonetPortLineESS15Min OBJECT-TYPE
            SYNTAX INTEGER(1..900) 
			MAX-ACCESS read-write
            STATUS current
            DESCRIPTION
           " 15 minute line errored seconds threshold"
            ::= { sonetPortEntry 9}
			
			sonetPortPathESS15Min OBJECT-TYPE
			SYNTAX INTEGER(1..900) 
			MAX-ACCESS read-write
            STATUS current
            DESCRIPTION
           " 15 minute path errored seconds threshold"
            ::= { sonetPortEntry 10}
		
			sonetPortSectESS1Day OBJECT-TYPE
			SYNTAX INTEGER(1..65535) 
			MAX-ACCESS read-write
            STATUS current
            DESCRIPTION
           " 1 day section errored seconds threshold"
            ::= { sonetPortEntry 11}
		
			sonetPortLineESS1Day OBJECT-TYPE
			SYNTAX INTEGER(1..65535) 
			MAX-ACCESS read-write
            STATUS current
            DESCRIPTION
           " 1 day line errored seconds threshold"
            ::= { sonetPortEntry 12}
		
			sonetPortPathESS1Day OBJECT-TYPE
			SYNTAX INTEGER(1..65535) 
			MAX-ACCESS read-write
            STATUS current
            DESCRIPTION
           " 1 day path errored seconds threshold"
            ::= { sonetPortEntry 13}
		
			sonetPortSectCVS15Min OBJECT-TYPE
			SYNTAX INTEGER(1..16383) 
			MAX-ACCESS read-write
            STATUS current
            DESCRIPTION
           "15 minute section coding violations threshold "
            ::= { sonetPortEntry 14}
		
			sonetPortLineCVS15Min OBJECT-TYPE
			SYNTAX INTEGER(1..16383) 
			MAX-ACCESS read-write
            STATUS current
            DESCRIPTION
           "15 minute line coding violations threshold"
            ::= { sonetPortEntry 15}
		
			sonetPortPathCVS15Min OBJECT-TYPE
			SYNTAX INTEGER(1..16383) 
			MAX-ACCESS read-write
            STATUS current
            DESCRIPTION
           " 15 minutes path coding violations threshold"
            ::= { sonetPortEntry 16}
		
			sonetPortSectCVS1Day OBJECT-TYPE
			SYNTAX INTEGER(1..1048575) 
			MAX-ACCESS read-write
            STATUS current
            DESCRIPTION
           "1 day section coding violations threshold"
            ::= { sonetPortEntry 17}
			
			sonetPortLineCVS1Day OBJECT-TYPE
			SYNTAX INTEGER(1..1048575) 
			MAX-ACCESS read-write
            STATUS current
            DESCRIPTION
           "1 day line coding violations threshold "
            ::= { sonetPortEntry 18}
		
			sonetPortPathCVS1Day OBJECT-TYPE
			SYNTAX INTEGER(1..1048575) 
			MAX-ACCESS read-write
            STATUS current
            DESCRIPTION
           " 1 day path coding violations threshold"
            ::= { sonetPortEntry 19}
		
			sonetPortSectSESS15Min OBJECT-TYPE
			SYNTAX INTEGER(1..900) 
			MAX-ACCESS read-write
            STATUS current
            DESCRIPTION
           " 15 minutes section severely errored seconds threshold "
            ::= { sonetPortEntry 20}
		
			sonetPortLineSESS15Min OBJECT-TYPE
			SYNTAX INTEGER(1..900) 
			MAX-ACCESS read-write
            STATUS current
            DESCRIPTION
           " 15 minutes line severely errored seconds threshold "
            ::= { sonetPortEntry 21}
		
			sonetPortPathSESS15Min OBJECT-TYPE
			SYNTAX INTEGER(1..900) 
			MAX-ACCESS read-write
            STATUS current
            DESCRIPTION
           " 15 minutes path severely errored seconds threshold"
            ::= { sonetPortEntry 22}
		
		    sonetPortSectSESS1Day OBJECT-TYPE
			SYNTAX INTEGER(1..65535) 
			MAX-ACCESS read-write
            STATUS current
            DESCRIPTION
           " 1 day section severely errored seconds threshold "
            ::= { sonetPortEntry 23}
		
			sonetPortLineSESS1Day OBJECT-TYPE
			SYNTAX INTEGER(1..65535) 
			MAX-ACCESS read-write
            STATUS current
            DESCRIPTION
           " 1 day line severely errored seconds threshold "
            ::= { sonetPortEntry 24}
		
			sonetPortPathSESS1Day OBJECT-TYPE
			SYNTAX INTEGER(1..65535) 
			MAX-ACCESS read-write
            STATUS current
            DESCRIPTION
           " 1 day path severely errored seconds threshold "
            ::= { sonetPortEntry 25}
		
			sonetPortLineUASS15Min OBJECT-TYPE
			SYNTAX INTEGER(1..900) 
			MAX-ACCESS read-write
            STATUS current
            DESCRIPTION
           " 15 minutes line unavailable seconds threshold "
            ::= { sonetPortEntry 26}
		
			sonetPortPathUASS15Min OBJECT-TYPE
			SYNTAX INTEGER(1..900) 
			MAX-ACCESS read-write
            STATUS current
            DESCRIPTION
           " 15 minutes path unavailable seconds threshold "
            ::= { sonetPortEntry 27}
		
			sonetPortLineUASS1Day OBJECT-TYPE
			SYNTAX INTEGER(1..65535) 
			MAX-ACCESS read-write
            STATUS current
            DESCRIPTION
           " 1 day line unavailable seconds threshold "
            ::= { sonetPortEntry 28}
		
			sonetPortPathUASS1Day OBJECT-TYPE
			SYNTAX INTEGER(1..65535) 
			MAX-ACCESS read-write
            STATUS current
            DESCRIPTION
           " 1 day path unavailable seconds threshold "
            ::= { sonetPortEntry 29}

	        sonetPortRowStatus OBJECT-TYPE
            SYNTAX INTEGER {
            active(1),
            notInService(2),
            createAndGo(4),
            createAndWait(5),
            destroy(6)
            }
            MAX-ACCESS read-write
            STATUS current
            DESCRIPTION
            " This variable is used to create or delete instances of SONET ports
              This variable subsumes the admin state variable, and once the row is
              created, its value returns the admin state of the port"
            ::= {sonetPortEntry 30}

	sonetTCAStatus	OBJECT-TYPE
	    SYNTAX		INTEGER {
	                        sonet-section-cv-tca-declared		(1),
				sonet-section-ses-tca-declared		(2),
				sonet-section-es-tca-declared		(3),
				sonet-line-cv-tca-declared		(4),
				sonet-line-ses-tca-declared		(5),
				sonet-line-es-tca-declared		(6),
				sonet-line-uas-tca-declared		(7),
				sonet-line-farend-cv-tca-declared	(8),
				sonet-line-farend-ses-tca-declared	(9),
				sonet-line-farend-es-tca-declared	(10),
				sonet-line-farend-uas-tca-declared	(11),
				sonet-path-cv-tca-declared		(12),
				sonet-path-ses-tca-declared		(13),
				sonet-path-es-tca-declared		(14),
				sonet-path-uas-tca-declared		(15),
				sonet-path-farend-cv-tca-declared	(16),
				sonet-path-farend-ses-tca-declared	(17),
				sonet-path-farend-es-tca-declared	(18),
				sonet-path-farend-uas-tca-declared	(19),
				sonet-vt-cv-tca-declared		(20),
				sonet-vt-ses-tca-declared		(21),
				sonet-vt-es-tca-declared		(22),
				sonet-vt-uas-tca-declared		(23),
				sonet-vt-farend-cv-tca-declared		(24),
				sonet-vt-farend-ses-tca-declared	(25),
				sonet-vt-farend-es-tca-declared		(26),
				sonet-vt-farend-uas-tca-declared	(27)
            }
	    MAX-ACCESS	accessible-for-notify
	    STATUS	current
	    DESCRIPTION
		"Represents the Threshold Crossing Alarm."
	    ::= {sonetPortEntry 31}

		
          -- The ATM port table

          atmPortTable OBJECT-TYPE
          SYNTAX SEQUENCE OF AtmPortEntry
          MAX-ACCESS not-accessible
          STATUS current
          DESCRIPTION
          "The ATM Port Table"
          ::= { port 6 }

          atmPortEntry OBJECT-TYPE
          SYNTAX AtmPortEntry
          MAX-ACCESS not-accessible
          STATUS current
          DESCRIPTION
          "Entry containing information about atm ports"
          INDEX { slotNo, portNo }
          ::= { atmPortTable 1 }

          AtmPortEntry ::= SEQUENCE {
		    atmPortVPTunnel
			TruthValue,
			atmPortMaxTotalBits
			INTEGER,
			atmPortTiming
			INTEGER,
			atmPortInCells
			Counter32,
			atmPortOutCells
			Counter32,
			atmPortCDVT
			INTEGER,
			atmPortMaxActvBits
			OCTET STRING,
			atmPortHCInCells
			Counter64,
			atmPortHCOutCells
			Counter64,
			atmPortRowStatus
			INTEGER
          }

		  atmPortVPTunnel OBJECT-TYPE
          SYNTAX TruthValue
          MAX-ACCESS read-write
          STATUS current
          DESCRIPTION
          " Whether this port is a VP Tunnel "
          ::= { atmPortEntry 1}

		  atmPortMaxTotalBits OBJECT-TYPE
          SYNTAX INTEGER
          MAX-ACCESS read-only
          STATUS current
          DESCRIPTION
          " Max Total Bits of VPI & VCI "
          ::= { atmPortEntry 2}

		  atmPortTiming OBJECT-TYPE
          SYNTAX INTEGER {
		    internal(1),
			loop(2)
          }
          MAX-ACCESS read-write
          STATUS current
          DESCRIPTION
          " Timing Mode "
          ::= { atmPortEntry 3 }

		  atmPortInCells OBJECT-TYPE
          SYNTAX Counter32
          MAX-ACCESS read-only
          STATUS current
          DESCRIPTION
          " Input Cell Count "
          ::= { atmPortEntry 4}

		  atmPortOutCells OBJECT-TYPE
          SYNTAX Counter32
          MAX-ACCESS read-only
          STATUS current
          DESCRIPTION
          " Output Cell Count "
          ::= { atmPortEntry 5 }

		  atmPortCDVT OBJECT-TYPE
          SYNTAX INTEGER(5000..100000)
          MAX-ACCESS read-write
          STATUS current
          DESCRIPTION
          " Cell Delay Variation Tolerance (CDVT) is measured 
            in units of seconds per cell. For OC12c ATM the 
            link rate is approximately 1.4 million cells per 
            second, each cell time being approximately 700 
            nanoseconds. Its value is initialized to 50,000 
            which is approximately 0.7% of the OC12c line rate.  
            The value ranges from 5,000 to 100,000 which gives 
            us a CDVT range of 7 to 141 cell times."
          ::= { atmPortEntry 6 }

		  atmPortMaxActvBits OBJECT-TYPE
          SYNTAX OCTET STRING
          MAX-ACCESS read-write
          STATUS current
          DESCRIPTION
          " Maximum active VPI/VCI bits "
          ::= { atmPortEntry 7 }

		  atmPortHCInCells OBJECT-TYPE
		  SYNTAX Counter64
		  MAX-ACCESS read-only
		  STATUS current
		  DESCRIPTION
		  " 64 bit input cell count "
		  ::= { atmPortEntry 8 }

		  atmPortHCOutCells OBJECT-TYPE
		  SYNTAX Counter64
		  MAX-ACCESS read-only
		  STATUS current
		  DESCRIPTION
		  " 64 bit output cell count "
		  ::= { atmPortEntry 9 }

		  atmPortRowStatus OBJECT-TYPE
          SYNTAX INTEGER {
            active(1),
            notInService(2),
            createAndGo(4),
            createAndWait(5),
            destroy(6)
          }
          MAX-ACCESS read-write
          STATUS current
          DESCRIPTION
          " This variable is used to create or delete instances of atm ports
            This variable subsumes the admin state variable, and once the row is
            created, its value returns the admin state of the port"
          ::= {atmPortEntry 10 }

          -- The optical port table

          opticalPortTable OBJECT-TYPE
          SYNTAX SEQUENCE OF OpticalPortEntry
          MAX-ACCESS not-accessible
          STATUS current
          DESCRIPTION
          "The Optical Port Table"
          ::= { port 7 }

          opticalPortEntry OBJECT-TYPE
          SYNTAX OpticalPortEntry
          MAX-ACCESS not-accessible
          STATUS current
          DESCRIPTION
          "This describes the attributes of optical ports in the system "
          INDEX { slotNo, portNo, lambda }
          ::= { opticalPortTable 1 }

          OpticalPortEntry ::= SEQUENCE {
		    lambda
			INTEGER,
            opticalPortMode
			INTEGER,
			opticalPortRxSMselect
			INTEGER,
            opticalPortTxSMselect
			INTEGER,
			opticalPortRxSignalState
			INTEGER,
			opticalPortRxFrameState
			INTEGER,
			opticalPortTxStatus
			INTEGER,
			opticalPortTxEnable
			INTEGER,
			opticalPortLaserPowerLevel
			INTEGER,
			opticalPortLaserWavelength
			INTEGER,
			opticalPortRowStatus
			INTEGER
		  } 

		  lambda OBJECT-TYPE
		  SYNTAX INTEGER
		  MAX-ACCESS not-accessible
		  STATUS current
		  DESCRIPTION
		  " The purpose of this variable is to be used as the third component of the
		    index into the optical port table "
		  ::= { opticalPortEntry 1 }
		 
           opticalPortMode OBJECT-TYPE
		   SYNTAX INTEGER {
            disabled(1),
		     working(2),
			 protected(3)
           }
		   MAX-ACCESS read-write
		   STATUS current
		   DESCRIPTION
		   " The mode of operation of the port. This is set initially by the user
           and can only be changed by the user. It is not a status. By default, 
           all optical ports in the system come up as working. They have to be explicitly
			 configured to work in a protected mode or to be turned off." 
		   ::= { opticalPortEntry 2 }

		   opticalPortRxSMselect OBJECT-TYPE
		   SYNTAX INTEGER {
             primary(1),
			 reserve(2),
			 both(3),
			 none(4)
           }
		   MAX-ACCESS not-accessible
		   STATUS current
		   DESCRIPTION
		   " This object selects which lambda to send over the back-plane to
           the different switch module." 
		   ::= { opticalPortEntry 3 }
			
           opticalPortTxSMselect OBJECT-TYPE
		   SYNTAX INTEGER {
             primary(1),
			 reserve(2)
           }
		   MAX-ACCESS read-write
		   STATUS current
		   DESCRIPTION
		   " Selects between lambda feeds on the back plane wich originate
           in different switch module." 
		   ::= { opticalPortEntry 4 }
			
		   opticalPortRxSignalState OBJECT-TYPE
		   SYNTAX INTEGER {
             detected(1),
			 lossOfSignal(2)
           }
		   MAX-ACCESS read-only
		   STATUS current
		   DESCRIPTION
		   " Provides the status of the received optical signal - whether
		     it is detected or not." 
		   ::= { opticalPortEntry 5 }
		
		   opticalPortRxFrameState OBJECT-TYPE
		   SYNTAX INTEGER {
             lossOfFrame(1),
			 detected(2)
           }
		   MAX-ACCESS read-only
		   STATUS current
		   DESCRIPTION
		   " Frame state of signal as detected by SW at SONET framer. This 
            state is auto set by software."
		   ::= { opticalPortEntry 6 }

		   opticalPortTxStatus OBJECT-TYPE
		   SYNTAX INTEGER {
             good(1),
			 bad(2)
           }
		   MAX-ACCESS read-only
		   STATUS current
		   DESCRIPTION
		   " Provides the status of the transmitter for the optical port. This
           provides the operational condition of the transmitter. The value
           of it could be 'Good' even though it is not transmitting any
           signal due to some reason." 
		   ::= { opticalPortEntry 7 }
		
		   opticalPortTxEnable OBJECT-TYPE
		   SYNTAX INTEGER {
             enable(1),
			 disable(2)
           }
		   MAX-ACCESS read-write
		   STATUS current
		   DESCRIPTION
		   " Whether the transmission of data and interrupts on the optical port
		     is enabled or disabled " 
		   ::= { opticalPortEntry 8 }
		
		   opticalPortLaserPowerLevel OBJECT-TYPE
		   SYNTAX INTEGER {
             high(1),
			 low(2)
           }
		   MAX-ACCESS not-accessible
		   STATUS current
		   DESCRIPTION
		   " The laser power level on the port - this variable is useful for
		     tunable lasers. Currently will return a value of high(1) " 
		   ::= { opticalPortEntry 9 }
		
		   opticalPortLaserWavelength OBJECT-TYPE
		   SYNTAX INTEGER {
		     fifteenXX(1),
             thirteenTen(2),
            fifteenFifty(3),
            thirteenTenFifteenFifty(4)
           }
		   MAX-ACCESS read-write
		   STATUS current
		   DESCRIPTION
		   " Laser wavelength on the optical port. Currently will return
		     1 for DWDM ports, 2 for 1310 ports, 3 for 1550 ports and 4
           for ports that support both 1310 and 1550 nm wavelengths. This value
           however will be overshadowed by a 1310 or 1550 wavelength card present in 
           that system. The list will be expanded later to give the exact 15xx
            wavelength. Useful for tunable lasers to control the 15xx wavelength "
		   ::= { opticalPortEntry 10 }

		  opticalPortRowStatus OBJECT-TYPE
          SYNTAX INTEGER {
            createAndGo(4),
            destroy(6)
          }
          MAX-ACCESS read-write
          STATUS current
          DESCRIPTION
          " This variable is used to create or delete instances of optical port"
          ::= { opticalPortEntry 11 }


          -- The Ring Port Table

          ringPortTable OBJECT-TYPE
	      SYNTAX 	    SEQUENCE OF RingPortEntry
	      MAX-ACCESS    not-accessible
	      STATUS	    current
	      DESCRIPTION
		  "A table containing ring port variables."
	      ::= { port 8 }

	      ringPortEntry OBJECT-TYPE
	      SYNTAX	    RingPortEntry
	      MAX-ACCESS    not-accessible
	      STATUS	    current
	      DESCRIPTION
		  "Entry in the table for a single ring port."
	      INDEX	{ slotNo, portNo }
	      ::= {ringPortTable 1 }

	      RingPortEntry ::= SEQUENCE {
	                   ringPortArbiterEnabled TruthValue,
					   ringPortFrameMode   INTEGER,
					   ringPortMaxChannels INTEGER,
					   ringPortMaxSubChannels INTEGER,
					   ringPortAutoQueueSizing TruthValue,
					   ringPortRingMode    INTEGER,
					   ringPortNodeId      INTEGER,
					   ringPortAdminStatus INTEGER,
					   ringPortOperStatus  INTEGER,
					   ringPortRxFrames    Counter,
					   ringPortRxFrameErrors Counter,
					   ringPortTxFrames    Counter,
					   ringPortMaxTDMChannels INTEGER,
		               ringPortK1K2Status  INTEGER,
					   ringPortAISStatus   INTEGER,
					   ringPortPHYStatus   INTEGER
				      }  

	      ringPortArbiterEnabled OBJECT-TYPE
		  SYNTAX	TruthValue 
		  MAX-ACCESS	read-write
		  STATUS	current
		  DESCRIPTION
			"The arbiter enabled Boolean defines whether the ring port Arbitration 
          Logic is enabled or not. The Arbitration Logic services requests for 
          extra data columns from an elastic bandwidth pool."
		  ::= { ringPortEntry 1 }

	      ringPortFrameMode	 OBJECT-TYPE
		  SYNTAX	INTEGER  {
			 axson  (1),
			 pos    (2)
		  }
		  MAX-ACCESS    read-write
		  STATUS	current
		  DESCRIPTION
			"The frame mode defines the data path mode of the ring port. The 
          choices include AXSON and POS. AXSON frame mode means the ring 
          encapsulates data inside AXSON frames, and POS means data is 
          encapsulated using the Packet over SONET standard HDLC mechanism."
		  ::= { ringPortEntry 2 }    	

	      ringPortMaxChannels		OBJECT-TYPE
	      SYNTAX	INTEGER(0..63)
	      MAX-ACCESS   read-write
	      STATUS	current
	      DESCRIPTION
		   "The max channels parameter sizes the number of AxSON channels 
         supported on the ring port. This determines number of ingress and 
         egress queues and the amount of queue memory available."
		  ::= { ringPortEntry 3 }

	      ringPortMaxSubChannels	OBJECT-TYPE
	      SYNTAX	INTEGER (0..4095)
	      MAX-ACCESS   read-write
	      STATUS	current
	      DESCRIPTION
		   "The max sub-channels parameter sizes the number of AxSON sub-channels 
         supported in a particular AxSON channel. This determines the amount of 
         queue memory required."
		  ::= { ringPortEntry 4 }

	      ringPortAutoQueueSizing	OBJECT-TYPE
	      SYNTAX 	TruthValue 
	      MAX-ACCESS   read-write
	      STATUS	current
	      DESCRIPTION
		   "Defines whether Axson channel queues may be automatically resized 
          during provisioning."
		  ::= { ringPortEntry 5 }  

	      ringPortRingMode	OBJECT-TYPE
	      SYNTAX 	INTEGER {
	        working (1),
		    protected (2)
          }
	      MAX-ACCESS   read-write
	      STATUS	current
	      DESCRIPTION
		 "Whether the ring port is connected to the working ring or the protected ring"
		  ::= { ringPortEntry 6 }
	  
          ringPortNodeId	OBJECT-TYPE
	      SYNTAX 	INTEGER(0..31)
	      MAX-ACCESS   read-write
	      STATUS	current
	      DESCRIPTION
		 "This defines the temporal discovery of the node in the logical ring"
		  ::= { ringPortEntry 7 }

          ringPortAdminStatus OBJECT-TYPE
	      SYNTAX 	INTEGER {
		    up (1),
		    down (2),
			redundant (3),
			diagnostic (4)
          }
	      MAX-ACCESS   read-write
	      STATUS	current
	      DESCRIPTION
		 "Gives the possible ringPort Administration Status ."
		  ::= { ringPortEntry 8 }

	      ringPortOperStatus OBJECT-TYPE
	      SYNTAX 	INTEGER {
			up (1),
			down (2)
          }
	      MAX-ACCESS   read-only
	      STATUS	current
	      DESCRIPTION
		 "Gives the ringPortNodeId operational status of the AXSON interface ."
		  ::= { ringPortEntry 9 }
  
                     
	      ringPortRxFrames OBJECT-TYPE
	      SYNTAX 	Counter 
	      MAX-ACCESS   read-only
	      STATUS	current
	      DESCRIPTION
		 "This object sepcifies the number of frames received at this interface."
		  ::= { ringPortEntry 10 }

          ringPortRxFrameErrors OBJECT-TYPE
	      SYNTAX 	Counter 
	      MAX-ACCESS   read-only
	      STATUS	current
	      DESCRIPTION
		 "Number of errored frames received at this interface."
		  ::= { ringPortEntry 11 }

	      ringPortTxFrames OBJECT-TYPE
	      SYNTAX 	Counter
	      MAX-ACCESS   read-only
	      STATUS	current
	      DESCRIPTION
		 "This object sepcifies the number of frames transmitted from this interface."
		  ::= { ringPortEntry 12 }

		  ringPortMaxTDMChannels OBJECT-TYPE
	      SYNTAX 	INTEGER(0..499)
	      MAX-ACCESS   read-write
	      STATUS	current
	      DESCRIPTION
		  " The maximum number of TDM channels supported on the ring"
		  ::= { ringPortEntry 13}

	      ringPortK1K2Status	OBJECT-TYPE
		  SYNTAX		INTEGER {
		    set   (1),
			clear (2)
		  }
		  MAX-ACCESS   		accessible-for-notify
		  STATUS		current
		  DESCRIPTION
		      " The status indicated by the K1,K2 bytes in the SONET
                        frame overhead "
		  ::= { ringPortEntry 14}

	      ringPortAISStatus	OBJECT-TYPE
		  SYNTAX		INTEGER {
		    set   (1),
			clear (2)
		  }
		  MAX-ACCESS   		accessible-for-notify
		  STATUS		current
		  DESCRIPTION
		      " The status indicated by the AIS bytes in the SONET
                        frame overhead "
		  ::= { ringPortEntry 15}

	      ringPortPHYStatus	OBJECT-TYPE
		  SYNTAX		INTEGER {
		    up   		 (1),
			down 		 (2),
			lower-layer-down (3),
			unknown		 (4)
		  }			
		  MAX-ACCESS   		accessible-for-notify
		  STATUS		current
		  DESCRIPTION
		      " The physical status of the ring port."
		  ::= { ringPortEntry 16}

          -- The DS3 TDM IO port table

          tdmIoDS3PortTable OBJECT-TYPE
          SYNTAX SEQUENCE OF TdmIoDS3PortEntry
          MAX-ACCESS not-accessible
          STATUS current
          DESCRIPTION
          "The DS3 TDM IO Port Table"
          ::= { port 9 }

          tdmIoDS3PortEntry OBJECT-TYPE
          SYNTAX TdmIoDS3PortEntry
          MAX-ACCESS not-accessible
          STATUS current
          DESCRIPTION
          "Entry containing information about TDM IO DS3 ports"
          INDEX { slotNo, portNo }
          ::= { tdmIoDS3PortTable 1 }

          TdmIoDS3PortEntry ::= SEQUENCE {
            tdmIoDS3PortPBitESS15Min
			INTEGER,
			tdmIoDS3PortPBitESS1Day
			INTEGER,
			tdmIoDS3PortPBitSESS15Min
			INTEGER,
			tdmIoDS3PortPBitSESS1Day
			INTEGER,
			tdmIoDS3PortSEFSS15Min
			INTEGER,
			tdmIoDS3PortSEFSS1Day
			INTEGER,
			tdmIoDS3PortUASS15Min
			INTEGER,
			tdmIoDS3PortUASS1Day
			INTEGER,
			tdmIoDS3PortLineCVS15Min
			INTEGER,
			tdmIoDS3PortLineCVS1Day
			INTEGER,
			tdmIoDS3PortPBitCVS15Min
			INTEGER,
			tdmIoDS3PortPBitCVS1Day
			INTEGER,
			tdmIoDS3PortLineESS15Min
			INTEGER,
			tdmIoDS3PortLineESS1Day
			INTEGER,
			tdmIoDS3PortCBitCVS15Min
			INTEGER,
			tdmIoDS3PortCBitCVS1Day
			INTEGER,
			tdmIoDS3PortCBitESS15Min
			INTEGER,
			tdmIoDS3PortCBitESS1Day
			INTEGER,
			tdmIoDS3PortCBitSESS15Min
			INTEGER,
			tdmIoDS3PortCBitSESS1Day
			INTEGER,
			tdmIoDS3PortRowStatus
            INTEGER
            }

            tdmIoDS3PortPBitESS15Min OBJECT-TYPE
			SYNTAX INTEGER(1..900)
			MAX-ACCESS read-write
			STATUS current
			DESCRIPTION
			"15 minute threshold for P-Bit Errored Seconds"
			::= { tdmIoDS3PortEntry 1 }

			tdmIoDS3PortPBitESS1Day OBJECT-TYPE
			SYNTAX INTEGER(1..65535)
			MAX-ACCESS read-write
			STATUS current
			DESCRIPTION
			"1 day threshold for P-Bit Errored Seconds"
			::= { tdmIoDS3PortEntry 2 }

			tdmIoDS3PortPBitSESS15Min OBJECT-TYPE
			SYNTAX INTEGER(1..900)
			MAX-ACCESS read-write
			STATUS current
			DESCRIPTION
			"15 minute threshold for P-Bit Severely Errored Seconds"
			::= { tdmIoDS3PortEntry 3 }

			tdmIoDS3PortPBitSESS1Day OBJECT-TYPE
			SYNTAX INTEGER(1..65535)
			MAX-ACCESS read-write
			STATUS current
			DESCRIPTION
			"1 day threshold for P-Bit Severely Errored Seconds"
			::= { tdmIoDS3PortEntry 4 }

			tdmIoDS3PortSEFSS15Min OBJECT-TYPE
			SYNTAX INTEGER(1..900)
			MAX-ACCESS read-write
			STATUS current
			DESCRIPTION
			"15 minute threshold for Severely Errored Framing Seconds"
			::= { tdmIoDS3PortEntry 5 }

			tdmIoDS3PortSEFSS1Day OBJECT-TYPE
			SYNTAX INTEGER(1..65535)
			MAX-ACCESS read-write
			STATUS current
			DESCRIPTION
			"1 day threshold for Severely Errored Framing Seconds"
			::= { tdmIoDS3PortEntry 6 }

			tdmIoDS3PortUASS15Min OBJECT-TYPE
			SYNTAX INTEGER(1..900)
			MAX-ACCESS read-write
			STATUS current
			DESCRIPTION
			"15 minute threshold for Severely Errored Framing Seconds"
			::= { tdmIoDS3PortEntry 7 }

			tdmIoDS3PortUASS1Day OBJECT-TYPE
			SYNTAX INTEGER(1..65535)
			MAX-ACCESS read-write
			STATUS current
			DESCRIPTION
			"1 day threshold for Unavailable Seconds"
			::= { tdmIoDS3PortEntry 8 }

			tdmIoDS3PortLineCVS15Min OBJECT-TYPE
			SYNTAX INTEGER(1..16383)
			MAX-ACCESS read-write
			STATUS current
			DESCRIPTION
			"15 minute threshold for Line-Coding Violations"
			::= { tdmIoDS3PortEntry 9 }

			tdmIoDS3PortLineCVS1Day OBJECT-TYPE
			SYNTAX INTEGER(1..1048575)
			MAX-ACCESS read-write
			STATUS current
			DESCRIPTION
			"1 day threshold for Line-Coding Violations"
			::= { tdmIoDS3PortEntry 10 }

			tdmIoDS3PortPBitCVS15Min OBJECT-TYPE
			SYNTAX INTEGER(1..16383)
			MAX-ACCESS read-write
			STATUS current
			DESCRIPTION
			"15 minute threshold for P-Bit Coding Violations"
			::= { tdmIoDS3PortEntry 11 }

			tdmIoDS3PortPBitCVS1Day OBJECT-TYPE
			SYNTAX INTEGER(1..1048575)
			MAX-ACCESS read-write
			STATUS current
			DESCRIPTION
			"1 day threshold for P-Bit Coding Violations"
			::= { tdmIoDS3PortEntry 12 }

			tdmIoDS3PortLineESS15Min OBJECT-TYPE
			SYNTAX INTEGER(1..900)
			MAX-ACCESS read-write
			STATUS current
			DESCRIPTION
			"15 minute threshold for Line Errored Seconds"
			::= { tdmIoDS3PortEntry 13 }

			tdmIoDS3PortLineESS1Day OBJECT-TYPE
			SYNTAX INTEGER(1..65535)
			MAX-ACCESS read-write
			STATUS current
			DESCRIPTION
			"1 day threshold for Line Errored Seconds"
			::= { tdmIoDS3PortEntry 14 }

			tdmIoDS3PortCBitCVS15Min OBJECT-TYPE
			SYNTAX INTEGER(1..16383)
			MAX-ACCESS read-write
			STATUS current
			DESCRIPTION
			"15 minute threshold for C-Bit Coding Violations"
			::= { tdmIoDS3PortEntry 15 }

			tdmIoDS3PortCBitCVS1Day OBJECT-TYPE
			SYNTAX INTEGER(1..1048575)
			MAX-ACCESS read-write
			STATUS current
			DESCRIPTION
			"1 day threshold for C-Bit Coding Violations"
			::= { tdmIoDS3PortEntry 16 }

			tdmIoDS3PortCBitESS15Min OBJECT-TYPE
			SYNTAX INTEGER(1..900)
			MAX-ACCESS read-write
			STATUS current
			DESCRIPTION
			"15 minute threshold for C-Bit Errored Seconds"
			::= { tdmIoDS3PortEntry 17 }

			tdmIoDS3PortCBitESS1Day OBJECT-TYPE
			SYNTAX INTEGER(1..65535)
			MAX-ACCESS read-write
			STATUS current
			DESCRIPTION
			"1 day threshold for C-Bit Errored Seconds"
			::= { tdmIoDS3PortEntry 18 }

			tdmIoDS3PortCBitSESS15Min OBJECT-TYPE
			SYNTAX INTEGER(1..900)
			MAX-ACCESS read-write
			STATUS current
			DESCRIPTION
			"15 minute threshold for C-Bit Severely Errored Seconds"
			::= { tdmIoDS3PortEntry 19 }

			tdmIoDS3PortCBitSESS1Day OBJECT-TYPE
			SYNTAX INTEGER(1..65535)
			MAX-ACCESS read-write
			STATUS current
			DESCRIPTION
			"1 day threshold for C-Bit Severely Errored Seconds"
			::= { tdmIoDS3PortEntry 20 }

		    tdmIoDS3PortRowStatus OBJECT-TYPE
            SYNTAX INTEGER {
            active(1),
            notInService(2),
            createAndGo(4),
            createAndWait(5),
            destroy(6)
            }
            MAX-ACCESS read-write
            STATUS current
            DESCRIPTION
           " This variable is used to create or delete instances of TDM IO DS3 ports.
             This variable subsumes the admin state variable, and once the row is
             created, its value returns the admin state of the port"
            ::= {tdmIoDS3PortEntry 21}

          -- The POS Port table

          posPortTable OBJECT-TYPE
          SYNTAX SEQUENCE OF PosPortEntry
          MAX-ACCESS not-accessible
          STATUS current
          DESCRIPTION
          "The POS Port Table"
          ::= { port 10 }

          posPortEntry OBJECT-TYPE
          SYNTAX PosPortEntry
          MAX-ACCESS not-accessible
          STATUS current
          DESCRIPTION
          "Entry containing information about POS ports"
          INDEX { slotNo, portNo }
          ::= { posPortTable 1 }

          PosPortEntry ::= SEQUENCE {
            posPortTransportSegmentCount Counter32,
            posPortMode INTEGER,
            posPortDefaultVID Unsigned32,
            posPortMinPktSize INTEGER,
            posPortMaxPktSize INTEGER,
            posPortMinPktViolations Counter32,
            posPortMaxPktViolations Counter32
            } 

			posPortTransportSegmentCount OBJECT-TYPE
			SYNTAX Counter32
			MAX-ACCESS read-only
			STATUS current
			DESCRIPTION
			"Number of provisioned connections on port."
			::= { posPortEntry 1 }

			posPortMode OBJECT-TYPE
			SYNTAX INTEGER {
            transparent(1), 
            bridgedDataMode(2),   
            vlan(3),
            macAddr(4),
            ipAddr(5),
            mpls(6),
            mapOS(7)
         }  
			MAX-ACCESS read-write
			STATUS current
			DESCRIPTION
			"mode of operation."
			::= { posPortEntry 2 }

			posPortDefaultVID OBJECT-TYPE
			SYNTAX Unsigned32
			MAX-ACCESS read-write
			STATUS current
			DESCRIPTION
			"Port's default VLAN ID."
			::= { posPortEntry 3 }

			posPortMinPktSize OBJECT-TYPE
			SYNTAX INTEGER (4..4096)
			MAX-ACCESS read-write   
			STATUS current
			DESCRIPTION
			"It is defined as the minimum number of bytes encapsulated in 
          the POS frame including the FCS, but excluding byte stuffing."
			::= { posPortEntry 4 }

			posPortMaxPktSize OBJECT-TYPE
			SYNTAX INTEGER (4..4096)
			MAX-ACCESS read-write
			STATUS current
			DESCRIPTION
			"It is defined as the maximum number of bytes encapsulated in 
          the POS frame including the FCS, but excluding byte stuffing."
			::= { posPortEntry 5 }

			posPortMinPktViolations OBJECT-TYPE
			SYNTAX Counter32
			MAX-ACCESS read-only
			STATUS current
			DESCRIPTION
			"This object gives the number of times the system had detected
          a packet of size less than the acceptable minimum."
			::= { posPortEntry 6 }

			posPortMaxPktViolations OBJECT-TYPE
			SYNTAX Counter32
			MAX-ACCESS read-only
			STATUS current
			DESCRIPTION
			"This object gives the number of times the system had detected
          a packet of size greater than the acceptable minimum."
			::= { posPortEntry 7 } 
		 
          -- Port traps are defined here
  
          portPhyStatusChange TRAP-TYPE
	      ENTERPRISE coriolisMibs
	      VARIABLES {ifOperStatus}
	      DESCRIPTION
		  " Change in the operational status of a port, 1 means the port came up, 
         2 means it went down "
	      ::= 0
         
          portAdminStatusChange TRAP-TYPE
	      ENTERPRISE coriolisMibs
	      VARIABLES {ifAdminStatus}
	      DESCRIPTION
		  " Change in the admin status of a port, 1 means the port came up, 
         2 means it went down "
	      ::= 1

	      portSpeedStatusTrap TRAP-TYPE
	      ENTERPRISE coriolisMibs
	      VARIABLES {ifSpeed}
	      DESCRIPTION
		  " Change in speed of an interface e.g. 10 or 100 for a Fast Ethernet port"
	      ::= 20

	      etherPortDuplexStatusTrap TRAP-TYPE
	      ENTERPRISE coriolisMibs
	      VARIABLES {dot3StatsDuplexStatus}
	      DESCRIPTION
		  " Change in the duplex status of an ethernet port , 2 means half-duplex, 
         3 means full duplex"
		  ::= 21

	      etherPortAutonegStatusTrap TRAP-TYPE
	      ENTERPRISE coriolisMibs
	      VARIABLES {ifMauAutoNegConfig}
	      DESCRIPTION
		  " Change in status of the autoneg process, 3 means it has completed "
	      ::= 22

          sonetSectionLOSChange TRAP-TYPE
	      ENTERPRISE coriolisMibs
	      VARIABLES {sonetSectionCurrentStatus}
	      DESCRIPTION
		  " Change in the SONET LOS status."
	      ::= 27

          sonetSectionLOFChange TRAP-TYPE
	      ENTERPRISE coriolisMibs
	      VARIABLES {sonetSectionCurrentStatus}
	      DESCRIPTION
		  " Change in the SONET LOF status."
	      ::= 28
	      
	      sonetLineAISChange TRAP-TYPE
	      ENTERPRISE coriolisMibs
	      VARIABLES {sonetLineCurrentStatus}
	      DESCRIPTION
		  " Change in the SONET Line AIS status."
	      ::= 29

          sonetLineRDIChange TRAP-TYPE
	      ENTERPRISE coriolisMibs
	      VARIABLES {sonetLineCurrentStatus}
	      DESCRIPTION
		  " Change in the SONET Line RDI status."
	      ::= 30

          sonetPathLOPChange TRAP-TYPE
	      ENTERPRISE coriolisMibs
	      VARIABLES {sonetPathCurrentStatus}
	      DESCRIPTION
		  " Change in the SONET Path LOP status."
	      ::= 31

          sonetPathAISChange TRAP-TYPE
	      ENTERPRISE coriolisMibs
	      VARIABLES {sonetPathCurrentStatus}
	      DESCRIPTION
		  " Change in the SONET Path AIS status."
	      ::= 32

          sonetPathRDIChange TRAP-TYPE
	      ENTERPRISE coriolisMibs
	      VARIABLES {sonetPathCurrentStatus}
	      DESCRIPTION
		  " Change in the SONET Path RDI status."
	      ::= 33

          sonetPathUNEQPChange TRAP-TYPE
	      ENTERPRISE coriolisMibs
	      VARIABLES {sonetPathCurrentStatus}
	      DESCRIPTION
		  "Indicates whether the SONET path is equipped or not."
	      ::= 34

          sonetPathPSLMChange TRAP-TYPE
	      ENTERPRISE coriolisMibs
	      VARIABLES {sonetPathCurrentStatus}
	      DESCRIPTION
		  "Indicates if there is any mismatch in the SONET signal label."
	      ::= 35

          sonetVTLOPChange TRAP-TYPE
	      ENTERPRISE coriolisMibs
	      VARIABLES {sonetVTCurrentStatus}
	      DESCRIPTION
		  " Change in the SONET VT LOP status."
	      ::= 36

          sonetVTAISChange TRAP-TYPE
	      ENTERPRISE coriolisMibs
	      VARIABLES {sonetVTCurrentStatus}
	      DESCRIPTION
		  " Change in the SONET VT AIS status."
	      ::= 37

          sonetVTRDIChange TRAP-TYPE
	      ENTERPRISE coriolisMibs
	      VARIABLES {sonetVTCurrentStatus}
	      DESCRIPTION
		  " Change in the SONET VT RDI status."
	      ::= 38

          sonetVTRFIChange TRAP-TYPE
	      ENTERPRISE coriolisMibs
	      VARIABLES {sonetVTCurrentStatus}
	      DESCRIPTION
		  " Change in the SONET VT RFI status."
	      ::= 39

          sonetVTUNEQPChange TRAP-TYPE
	      ENTERPRISE coriolisMibs
	      VARIABLES {sonetVTCurrentStatus}
	      DESCRIPTION
		  "Indicates whether the SONET VT is equipped or not."
	      ::= 40

          sonetVTPSLMChange TRAP-TYPE
	      ENTERPRISE coriolisMibs
	      VARIABLES {sonetVTCurrentStatus}
	      DESCRIPTION
		  "Indicates if there is any mismatch in the SONET signal label."
	      ::= 41

          ringPortK1K2Change TRAP-TYPE
	      ENTERPRISE coriolisMibs
	      VARIABLES {ringPortK1K2Status}
	      DESCRIPTION
		  "Indicates the change in status indicated by K1,K2 bytes"
	      ::= 47

          ringPortAISChange TRAP-TYPE
	      ENTERPRISE coriolisMibs
	      VARIABLES {ringPortAISStatus}
	      DESCRIPTION
		  "A signal indicating a change of status indicated by the AIS bytes"
	      ::=   48

          ringPortPHYChange 	TRAP-TYPE
	      ENTERPRISE 	coriolisMibs
	      VARIABLES 	{ringPortPHYStatus}
	      DESCRIPTION
		  " A trap indicating the change in phy status of ring port"
	      ::=  49

	  sonetPortTCAlarm 	TRAP-TYPE
	      ENTERPRISE  	coriolisMibs
	      VARIABLES		{sonetTCAStatus}
	      DESCRIPTION
		  "A SONET alarm threshold has been crossed."
	      ::= 50

	  dsxAlarm	 	TRAP-TYPE
	      ENTERPRISE  	coriolisMibs
	      VARIABLES		{dsxStatus}
	      DESCRIPTION
		  "The status of a DSx line has changed."
	      ::= 55

     END
