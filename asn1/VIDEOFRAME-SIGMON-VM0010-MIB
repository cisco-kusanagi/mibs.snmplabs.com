VIDEOFRAME-SIGMON-VM0010-MIB DEFINITIONS ::= BEGIN

	--  Relationship to Other MIBs
	--
	--
	--  The objects defined in this MIB are located under the
	--  private.enterprises subtree as shown below:
	--
	--               iso(1).org(3).dod(6).internet(1)
	--                            |
	--                         private(4)
	--                            |
	--                       enterprises(1)
	--                            |
	--                       videoframe(4596)
	--                            |
	--                      vfProducts(4)
	--							  |
	--						vfSigmonFrame(2)
	--							  |
	--					  vfSigmonFrameModules(1)
	--							  |
	--					   vm0010GPOInterface(10)
	--                                 
	--
	--  References
	--
	--  [1]  RFC 1902.  McCloghrie, K., and M. Rose, "Structure 
	--       of Management Information for Version 2 of the Simple
	--       Network Management Protocol (SNMPv2)".  
	--       January, 1996.
	--
	--  [2]  RFC 1903.  McCloghrie, K., and M. Rose, "Textual
	--       Conventions for Version 2 of the Simple Network
	--       Management Protocol (SNMPv2)".  
	--       January, 1996.
	--
	--  [3]  RFC 1904.  McCloghrie, K., and M. Rose, "Conformance
	--       Statements for Version 2 of the Simple Network
	--       Management Protocol (SNMPv2)".  
	--       January, 1996.
	--
	--  [4]  RFC 1907.  McCloghrie, K., and M. Rose, "Management 
	--       Information Base for Version 2 of the Simple Network
	--       Management Protocol (SNMPv2)".  
	--       January, 1996.
	--
	--	[5]  Perkins, David and McGinnis, Evan; "Understanding SNMP
	--		 MIBs".  Prentice Hall, ISBN 0-13-437708-7, 1997.
	--
	--
	--  Object Synopsis
	--  
	--
	--  All objects within this MIB are prefixed with the OBJECT
	--  IDENTIFIER "p", where "p" is:
	--
	--  iso(1).org(3).dod(6).internet(1).private(4).enterprises(1).
	--          videoframe(4596).vfProducts(4).vfSigmonFrame(2).
	--			vfSigmonFrameModuleTypes(1)
	--	
	--  or, 1.3.6.1.4.1.4596.4.2.1
	--
	--
	--  Object Name                               Object Id         
	--  --------------------------------          --------------
	--
	--	vm0006TransferSwitch						p.10
	--		vm0006Table								p.10.1
	--		vm0006TableEntry						p.10.1.1
	--			vm0006SlotNumber					p.10.1.1.1.m	m = slot #
	--			vm0006Active						p.10.1.1.2.m
	--			vm0006Locate						p.10.1.1.3.m
	--		vm0006GPORelayTable						p.10.2
	--		vm0006GPORelayEntry						p.10.2.1
	--			vm0006GPORelaySlotNumber			p.10.2.1.1.m.n	m = slot #, n = relay #
	--			vm0006GPORelayNumber				p.10.2.1.2.m.n
	--			vm0006GPOClosureState				p.10.2.1.3.m.n
	--			vm0006GPOClosureName				p.10.2.1.4.m.n
	--			vm0006GPOClosureDescription			p.10.2.1.5.m.n
	--    

	IMPORTS
		OBJECT-TYPE FROM RFC1155-SMI
		MODULE-IDENTITY, OBJECT-IDENTITY, NOTIFICATION-TYPE,
		IpAddress
			FROM SNMPv2-SMI
		DisplayString, RowStatus
			FROM SNMPv2-TC
		MODULE-COMPLIANCE, OBJECT-GROUP
			FROM SNMPv2-CONF
		vfMIBModules
			FROM VIDEOFRAME-REGISTRATIONS-MIB
		vfBoxId
			FROM VIDEOFRAME-GENERIC-MIB
		vfSigmonFrameModuleTypes, vfProductsVF200Reg, vfFrameSlotNumber
			FROM VIDEOFRAME-SIGMON-MIB;

	videoframeSigmonVm0010MIB MODULE-IDENTITY
		LAST-UPDATED "0109110000Z"
		ORGANIZATION "Videoframe Systems"
		CONTACT-INFO
			"Videoframe Systems
			P.O. Box 1991,
			Grass Valley, CA 95945, USA.

			+1 (530) 477-2000

			http://www.videoframesystems.com"
	DESCRIPTION
		"This MIB describes the device specific objects of the VM0010
		GPO Module, and augments MIB-2, VF-GENERIC, and VF-SIGMON
		in the identification of this Videoframe Systems managed device.

		This module will be extended or modified as required.

		Videoframe Systems reserves the right to
		make changes in specification and other 
		information contained in this document without 
		prior notice. The reader should consult Videoframe Systems
		to determine whether any such changes have been made.

		In no event shall Videoframe Systems be 
		liable for any incidental, indirect, special, 
		or consequential damages whatsoever (including 
		but not limited to lost profits) arising out of 
		or related to this document or the information 
		contained in it.

		Videoframe Systems grants vendors, end users, 
		and other interested parties a non-exclusive 
		license to use this specification in connection 
		with the management of Videoframe Systems products.

		Copyright 2001 Videoframe, Inc."
	REVISION      "0109110000Z"
	DESCRIPTION
		"First release."
	::= { vfMIBModules 8 }

	--
	-- VM0010 product registration. vfProductsVF200Reg is from
	-- vf-sigmon
	--

	vfProductsVM0010 OBJECT-IDENTITY
		STATUS	current
		DESCRIPTION
			"Videoframe VM0010 GPI (Input) Module."
	::= { vfProductsVF200Reg 10 }


	--
	--  The VM0010 MIB top-level groups
	--

	-- root of this MIB module
vm0010GPOInterface		OBJECT IDENTIFIER ::= { vfSigmonFrameModuleTypes 10 }

	--
	-- Other signal monitoring modules, whose management information is defined in
	-- other MIB modules.
	--
	--		vm0001AnalogAudio		OBJECT IDENTIFIER ::= { vfSigmonFrameModuleTypes 1 }
	--		vm0002AnalogVideo		OBJECT IDENTIFIER ::= { vfSigmonFrameModuleTypes 2 }
	--		vm0003AESEBUAudio		OBJECT IDENTIFIER ::= { vfSigmonFrameModuleTypes 3 }
	--		vm0004SDIVideo			OBJECT IDENTIFIER ::= { vfSigmonFrameModuleTypes 4 }
	--		vm0005SerialIO			OBJECT IDENTIFIER ::= { vfSigmonFrameModuleTypes 5 }
	--		vm0006GPIInterface		OBJECT IDENTIFIER ::= { vfSigmonFrameModuleTypes 6 }
	--		vm0007TransferSwitch	OBJECT IDENTIFIER ::= { vfSigmonFrameModuleTypes 7 }
	--		vm0008CPU				OBJECT IDENTIFIER ::= { vfSigmonFrameModuleTypes 8 }
	--		vm0009DTMFTransceiver	OBJECT IDENTIFIER ::= { vfSigmonFrameModuleTypes 9 }
	--		vm0011GPIOInterface		OBJECT IDENTIFIER ::= { vfSigmonFrameModuleTypes 11 }
	--

vm0010Table	OBJECT-TYPE
	SYNTAX	SEQUENCE OF Vm0010Entry
	MAX-ACCESS	not-accessible
	STATUS	current
	DESCRIPTION
		"Each row contains information about one VM0010 GPI Interface
		 module in the managed VF200 frame."

	::=	{ vm0010GPOInterface 1}


vm0010Entry	OBJECT-TYPE
	SYNTAX	Vm0010Entry
    MAX-ACCESS not-accessible
    STATUS     current
    DESCRIPTION
        "A GPO Interface module entry."
	INDEX { vfFrameSlotNumber }
    ::= { vm0010Table 1 } 
		
Vm0010Entry   ::= 
    SEQUENCE	{
		vm0010SlotNumber					INTEGER,
		vm0010Active						INTEGER,
		vm0010Locate						INTEGER
				}	

vm0010SlotNumber OBJECT-TYPE
		SYNTAX	INTEGER (1..12)				
		MAX-ACCESS	read-only
		STATUS		current
		DESCRIPTION
			"The slot that this entry represents."
	::= { vm0010Entry 1 }

vm0010Active OBJECT-TYPE
		SYNTAX	INTEGER
					{
						active(1),
						inactive(2)
					}				
		MAX-ACCESS	read-only
		STATUS		current
		DESCRIPTION
			"Indicates whether this entry is active (this module is in
			 this slot)."
	::= { vm0010Entry 2 }

vm0010Locate OBJECT-TYPE
		SYNTAX	INTEGER
					{
						flash(1),
						off(2)
					}				
		MAX-ACCESS	read-write
		STATUS		current
		DESCRIPTION
			"Controls the locate indicator on the module and indicates its
			 current state.  Set to flash (1) to cause the locate LED on the
			 front of the module to begin flashing.  Set to off to stop flashing."
	::= { vm0010Entry 3 }

vm0010GPORelayTable	OBJECT-TYPE
	SYNTAX	SEQUENCE OF Vm0010GPORelayEntry
	MAX-ACCESS	not-accessible
	STATUS	current
	DESCRIPTION
		"Each row contains information about one GPO relay of one
		 VM0010 GPO Interface module in the managed VF200 frame."

	::=	{ vm0010GPOInterface 2}

vm0010GPORelayEntry	OBJECT-TYPE
	SYNTAX	Vm0010GPORelayEntry
    MAX-ACCESS not-accessible
    STATUS     current
    DESCRIPTION
        "A GPI Interface module GPI signal entry."
	INDEX { vfFrameSlotNumber, vm0010GPORelayNumber }
    ::= { vm0010GPORelayTable 1 } 
		
Vm0010GPORelayEntry   ::= 
    SEQUENCE	{
		vm0010GPORelaySlotNumber			INTEGER,
		vm0010GPORelayNumber				INTEGER,
		vm0010GPOClosureState				INTEGER,
		vm0010GPOClosureName				DisplayString,
		vm0010GPOClosureDescription			DisplayString
		}

vm0010GPORelaySlotNumber OBJECT-TYPE
		SYNTAX	INTEGER (1..12)				
		MAX-ACCESS	read-only
		STATUS		current
		DESCRIPTION
			"The frame slot number that this entry represents."
	::= { vm0010GPORelayEntry 1 }

vm0010GPORelayNumber OBJECT-TYPE
		SYNTAX		INTEGER(1..16)
		MAX-ACCESS	read-only
		STATUS		current
		DESCRIPTION
			"The Relay number within the module."
	::= { vm0010GPORelayEntry 2 }

vm0010GPOClosureState OBJECT-TYPE
		SYNTAX	INTEGER
					{
						open(1),
						closed(2)
					}				
		MAX-ACCESS	read-write
		STATUS		current
		DESCRIPTION
			"Controls and indicates the current state of this GPO closure."
	::= { vm0010GPORelayEntry 3 }

vm0010GPOClosureName OBJECT-TYPE
		SYNTAX		DisplayString (SIZE(0..20))
		MAX-ACCESS	read-write
		STATUS		current
		DESCRIPTION
			"The name of this GPO closure."
	::= { vm0010GPORelayEntry 4 }

vm0010GPOClosureDescription OBJECT-TYPE
		SYNTAX		DisplayString (SIZE(0..120))
		MAX-ACCESS	read-write
		STATUS		current
		DESCRIPTION
			"Descriptive identification of this GPO closure."
	::= { vm0010GPORelayEntry 5 }

	--
	-- vm0010 Events - there are no events defined for this module
	--

END
