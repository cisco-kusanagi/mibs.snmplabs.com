--
-- HW-IMAPV1NORTHBOUND-TRAP-MIB.mib
-- MIB generated by MG-SOFT Visual MIB Builder Version 4.0 Build 349
-- Tuesday, June 20, 2006 at 15:41:25
--

-- HW-IMAPV1NORTHBOUND-TRAP-MIB.mib
-- MIB generated by MG-SOFT Visual MIB Builder Version 4.0 Build 349
-- Thursday, July 24, 2003 at 16:05:08
-- 

	HW-IMAPV1NORTHBOUND-TRAP-MIB DEFINITIONS ::= BEGIN
 
		IMPORTS
			OBJECT-TYPE			
				FROM RFC-1212			
			TRAP-TYPE			
				FROM RFC-1215			
			IpAddress			
				FROM RFC1155-SMI			
			enterprises			
				FROM SNMPv2-SMI;
	
	
--
-- Node definitions
--
	
--  Node definitions
-- 
-- 1.3.6.1.4.1.2011
		-- 1.3.6.1.4.1.2011
		huawei OBJECT IDENTIFIER ::= { enterprises 2011 }

		
--  1.3.6.1.4.1.2011.2
		-- 1.3.6.1.4.1.2011.2
		products OBJECT IDENTIFIER ::= { huawei 2 }

		
--  1.3.6.1.4.1.2011.2.15
		-- 1.3.6.1.4.1.2011.2.15
		hwNetManagement OBJECT IDENTIFIER ::= { products 15 }

		
--  1.3.6.1.4.1.2011.2.15.1
		-- 1.3.6.1.4.1.2011.2.15.1
		hwNmAgent OBJECT IDENTIFIER ::= { hwNetManagement 1 }

		
		-- 1.3.6.1.4.1.2011.2.15.1.3
		hwNmFault OBJECT IDENTIFIER ::= { hwNmAgent 3 }

		
		-- 1.3.6.1.4.1.2011.2.15.1.3.5
		thirdNMSFaultFilter OBJECT-TYPE
			SYNTAX OCTET STRING (SIZE (14..32))
			ACCESS read-write
			STATUS mandatory
			DESCRIPTION
				"This is to add the filter condition by the upper NMS
					the syntax is IP:Port:Alarm Level
					Example : 127.0.0.1:161:0011
					          In this IP is 127.0.0.1
					          Port is 161
					          Alarm Level - Minor and warning should not be sent 
				                                as the bit is set for them"
			::= { hwNmFault 5 }

		
--  1.3.6.1.4.1.2011.2.15.1.7
		-- 1.3.6.1.4.1.2011.2.15.1.7
		hwNmNorthboundEvent OBJECT IDENTIFIER ::= { hwNmAgent 7 }

		
--  1.3.6.1.4.1.2011.2.15.1.7.1
		-- 1.3.6.1.4.1.2011.2.15.1.7.1
		hwNmNorthboundEventInfo OBJECT IDENTIFIER ::= { hwNmNorthboundEvent 1 }

		
--  1.3.6.1.4.1.2011.2.15.1.7.1.1
		-- 1.3.6.1.4.1.2011.2.15.1.7.1.1
		hwNmNorthboundNEName OBJECT-TYPE
			SYNTAX OCTET STRING (SIZE (1..255))
			ACCESS read-only
			STATUS mandatory
			DESCRIPTION
				"The name of network element,string (255)"
			::= { hwNmNorthboundEventInfo 1 }

		
--  1.3.6.1.4.1.2011.2.15.1.7.1.2
		-- 1.3.6.1.4.1.2011.2.15.1.7.1.2
		hwNmNorthboundNEType OBJECT-TYPE
			SYNTAX OCTET STRING (SIZE (0..64))
			ACCESS read-only
			STATUS mandatory
			DESCRIPTION
				"Device type of element,string(64)"
			::= { hwNmNorthboundEventInfo 2 }

		
--  1.3.6.1.4.1.2011.2.15.1.7.1.3
		-- 1.3.6.1.4.1.2011.2.15.1.7.1.3
		hwNmNorthboundObjectInstance OBJECT-TYPE
			SYNTAX OCTET STRING (SIZE (0..255))
			ACCESS read-only
			STATUS mandatory
			DESCRIPTION
				"Instance of element,such as number of Rack, Frame, Slot, Subslot, Port and so on,string(255)"
			::= { hwNmNorthboundEventInfo 3 }

		
--  1.3.6.1.4.1.2011.2.15.1.7.1.4
		-- 1.3.6.1.4.1.2011.2.15.1.7.1.4
		hwNmNorthboundEventType OBJECT-TYPE
			SYNTAX OCTET STRING (SIZE (0..64))
			ACCESS read-only
			STATUS mandatory
			DESCRIPTION
				"Event type of Network management,string(64)"
			::= { hwNmNorthboundEventInfo 4 }

		
--  1.3.6.1.4.1.2011.2.15.1.7.1.5
		-- 1.3.6.1.4.1.2011.2.15.1.7.1.5
		hwNmNorthboundEventTime OBJECT-TYPE
			SYNTAX OCTET STRING (SIZE (0..64))
			ACCESS read-only
			STATUS mandatory
			DESCRIPTION
				"Alarm generate time,string(64),format: 2003/03/14 00:00:00"
			::= { hwNmNorthboundEventInfo 5 }

		
--  1.3.6.1.4.1.2011.2.15.1.7.1.6
		-- 1.3.6.1.4.1.2011.2.15.1.7.1.6
		hwNmNorthboundProbableCause OBJECT-TYPE
			SYNTAX OCTET STRING (SIZE (0..64))
			ACCESS read-only
			STATUS mandatory
			DESCRIPTION
				"Reason of Probable caused alarm, string(64)"
			::= { hwNmNorthboundEventInfo 6 }

		
--  1.3.6.1.4.1.2011.2.15.1.7.1.7
		-- 1.3.6.1.4.1.2011.2.15.1.7.1.7
		hwNmNorthboundSeverity OBJECT-TYPE
			SYNTAX OCTET STRING (SIZE (0..64))
			ACCESS read-only
			STATUS mandatory
			DESCRIPTION
				"Level of Alarm, string(64)"
			::= { hwNmNorthboundEventInfo 7 }

		
--  1.3.6.1.4.1.2011.2.15.1.7.1.8
		-- 1.3.6.1.4.1.2011.2.15.1.7.1.8
		hwNmNorthboundEventDetail OBJECT-TYPE
			SYNTAX OCTET STRING (SIZE (0..255))
			ACCESS read-only
			STATUS mandatory
			DESCRIPTION
				"Alarm ID and detail information, format: ID+detail infomation, string(255)"
			::= { hwNmNorthboundEventInfo 8 }

		
--  1.3.6.1.4.1.2011.2.15.1.7.1.9
		-- 1.3.6.1.4.1.2011.2.15.1.7.1.9
		hwNmNorthboundAdditionalInfo OBJECT-TYPE
			SYNTAX OCTET STRING (SIZE (0..255))
			ACCESS read-only
			STATUS mandatory
			DESCRIPTION
				"Additional infomation of device, such as Country, City and so on, string(255)"
			::= { hwNmNorthboundEventInfo 9 }

		
--  1.3.6.1.4.1.2011.2.15.1.7.1.10
		-- 1.3.6.1.4.1.2011.2.15.1.7.1.10
		hwNmNorthboundFaultFlag OBJECT-TYPE
			SYNTAX OCTET STRING (SIZE (0..64))
			ACCESS read-only
			STATUS mandatory
			DESCRIPTION
				"The flag of the fault.Show whether the alarm is an event ,a fault alarm or a recovery alarm."
			::= { hwNmNorthboundEventInfo 10 }

		
--  1.3.6.1.4.1.2011.2.15.1.7.1.11
		-- 1.3.6.1.4.1.2011.2.15.1.7.1.11
		hwNmNorthboundFaultFunction OBJECT-TYPE
			SYNTAX OCTET STRING (SIZE (0..64))
			ACCESS read-only
			STATUS mandatory
			DESCRIPTION
				"The function type of the alarm.It can be one of these values:'Power','Environment','Signal','Relay','Hardware','Software','Run','Communication','Service','Processerror','UNKNOWN_FUC_TYPE'"
			::= { hwNmNorthboundEventInfo 11 }

		
--  1.3.6.1.4.1.2011.2.15.1.7.1.12
		-- 1.3.6.1.4.1.2011.2.15.1.7.1.12
		hwNmNorthboundDeviceIP OBJECT-TYPE
			SYNTAX IpAddress
			ACCESS read-only
			STATUS mandatory
			DESCRIPTION
				"The IP address of the device"
			::= { hwNmNorthboundEventInfo 12 }

		
--  1.3.6.1.4.1.2011.2.15.1.7.1.13
		-- 1.3.6.1.4.1.2011.2.15.1.7.1.13
		hwNmNorthboundSerialNo OBJECT-TYPE
			SYNTAX INTEGER
			ACCESS read-only
			STATUS mandatory
			DESCRIPTION
				"The serial number of alarm."
			::= { hwNmNorthboundEventInfo 13 }

		
--  1.3.6.1.4.1.2011.2.15.1.7.1.14
		-- 1.3.6.1.4.1.2011.2.15.1.7.1.14
		hwNmNorthboundProbableRepair OBJECT-TYPE
			SYNTAX OCTET STRING (SIZE (0..64))
			ACCESS read-only
			STATUS mandatory
			DESCRIPTION
				"The probable repair advice of the alarm."
			::= { hwNmNorthboundEventInfo 14 }

		
--  1.3.6.1.4.1.2011.2.15.1.7.1.15
		-- 1.3.6.1.4.1.2011.2.15.1.7.1.15
		hwNmNorthboundResourceIDs OBJECT-TYPE
			SYNTAX OCTET STRING (SIZE (1..255))
			ACCESS read-only
			STATUS mandatory
			DESCRIPTION
				"The ID of the resource."
			::= { hwNmNorthboundEventInfo 15 }

		
--  1.3.6.1.4.1.2011.2.15.1.7.1.16
		-- 1.3.6.1.4.1.2011.2.15.1.7.1.16
		hwNmNorthboundsAdditionalVB1 OBJECT-TYPE
			SYNTAX OCTET STRING (SIZE (1..255))
			ACCESS read-only
			STATUS mandatory
			DESCRIPTION
				"Addtional information of the alarm"
			::= { hwNmNorthboundEventInfo 16 }

		
--  1.3.6.1.4.1.2011.2.15.1.7.1.17
		-- 1.3.6.1.4.1.2011.2.15.1.7.1.17
		hwNmNorthboundsAdditionalVB2 OBJECT-TYPE
			SYNTAX OCTET STRING (SIZE (1..255))
			ACCESS read-only
			STATUS mandatory
			DESCRIPTION
				"Addtional information of the alarm"
			::= { hwNmNorthboundEventInfo 17 }

		
--  1.3.6.1.4.1.2011.2.15.1.7.1.18
		-- 1.3.6.1.4.1.2011.2.15.1.7.1.18
		hwNmNorthboundsAdditionalVB3 OBJECT-TYPE
			SYNTAX OCTET STRING (SIZE (1..255))
			ACCESS read-only
			STATUS mandatory
			DESCRIPTION
				"Addtional information of the alarm"
			::= { hwNmNorthboundEventInfo 18 }

		
--  1.3.6.1.4.1.2011.2.15.1.7.1.19
		-- 1.3.6.1.4.1.2011.2.15.1.7.1.19
		hwNmNorthboundsAdditionalVB4 OBJECT-TYPE
			SYNTAX OCTET STRING (SIZE (1..255))
			ACCESS read-only
			STATUS mandatory
			DESCRIPTION
				"Addtional information of the alarm"
			::= { hwNmNorthboundEventInfo 19 }

		
--  1.3.6.1.4.1.2011.2.15.1.7.1.20
		-- 1.3.6.1.4.1.2011.2.15.1.7.1.20
		hwNmNorthboundsAdditionalVB5 OBJECT-TYPE
			SYNTAX OCTET STRING (SIZE (1..255))
			ACCESS read-only
			STATUS mandatory
			DESCRIPTION
				"Addtional information of the alarm"
			::= { hwNmNorthboundEventInfo 20 }

		
--  1.3.6.1.4.1.2011.2.15.1.7.1.21
		-- 1.3.6.1.4.1.2011.2.15.1.7.1.21
		hwNmNorthboundsAdditionalVB6 OBJECT-TYPE
			SYNTAX OCTET STRING (SIZE (1..255))
			ACCESS read-only
			STATUS mandatory
			DESCRIPTION
				"Addtional information of the alarm"
			::= { hwNmNorthboundEventInfo 21 }

		
--  1.3.6.1.4.1.2011.2.15.1.7.1.22
		-- 1.3.6.1.4.1.2011.2.15.1.7.1.22
		hwNmNorthboundsAdditionalVB7 OBJECT-TYPE
			SYNTAX OCTET STRING (SIZE (1..255))
			ACCESS read-only
			STATUS mandatory
			DESCRIPTION
				"Addtional information of the alarm"
			::= { hwNmNorthboundEventInfo 22 }

		
--  1.3.6.1.4.1.2011.2.15.1.7.1.23
		-- 1.3.6.1.4.1.2011.2.15.1.7.1.23
		hwNmNorthboundsAdditionalVB8 OBJECT-TYPE
			SYNTAX OCTET STRING (SIZE (1..255))
			ACCESS read-only
			STATUS mandatory
			DESCRIPTION
				"Addtional information of the alarm"
			::= { hwNmNorthboundEventInfo 23 }

		
--  1.3.6.1.4.1.2011.2.15.1.7.1.1
		-- 1.3.6.1.4.1.2011.2.15.1.7.1.24
		hwNmNorthboundEventName OBJECT-TYPE
			SYNTAX OCTET STRING (SIZE (1..255))
			ACCESS read-only
			STATUS mandatory
			DESCRIPTION
				"The name of event,string (255)"
			::= { hwNmNorthboundEventInfo 24 }

		
		-- 1.3.6.1.4.1.2011.2.15.1.7.2
		hwNmNorthboundEventKeepAliveInfo OBJECT IDENTIFIER ::= { hwNmNorthboundEvent 2 }

		
		-- 1.3.6.1.4.1.2011.2.15.1.7.7
		hwNmNorthboundEventSynchronization OBJECT IDENTIFIER ::= { hwNmNorthboundEvent 7 }

		
		-- 1.3.6.1.4.1.2011.2.15.1.7.7.1
		hwNmNorthboundEventSynchronizationStart OBJECT IDENTIFIER ::= { hwNmNorthboundEventSynchronization 1 }

		
		-- 1.3.6.1.4.1.2011.2.15.1.7.7.2
		hwNmNorthboundEventSynchronizationQueryResult OBJECT IDENTIFIER ::= { hwNmNorthboundEventSynchronization 2 }

		
		-- 1.3.6.1.4.1.2011.2.15.1.7.7.3
		hwNmNorthboundEventSynchronizationEnd OBJECT IDENTIFIER ::= { hwNmNorthboundEventSynchronization 3 }

		
		-- 1.3.6.1.4.1.2011.2.15.1.7.7.3.1
		hwNmNorthboundEventSynchronizationEndStatus OBJECT-TYPE
			SYNTAX INTEGER
				{
				normalEnd(1),
				stopped(2),
				error(3)
				}
			ACCESS read-only
			STATUS mandatory
			DESCRIPTION
				"It shows the result of alarm synchronization.
				1 means the alarm synchronization successfully ended.
				2 means the alarm synchronization is stopped by the NMS's command.
				3 means some error occured during the alarm synchronization."
			::= { hwNmNorthboundEventSynchronizationEnd 1 }

		
		-- 1.3.6.1.4.1.2011.2.15.1.7.7.3.2
		hwNmNorthboundEventSynchronizationEndStatusDetail OBJECT-TYPE
			SYNTAX OCTET STRING
			ACCESS read-only
			STATUS mandatory
			DESCRIPTION
				"The detail description of the alarm synchronization end status."
			::= { hwNmNorthboundEventSynchronizationEnd 2 }

		
		-- 1.3.6.1.4.1.2011.2.15.1.7.7.4
		hwNmNorthboundEventSynchronizationCommandStart OBJECT-TYPE
			SYNTAX OCTET STRING
			ACCESS read-write
			STATUS mandatory
			DESCRIPTION
				"This node is to be set to start the alarm synchronization.
				It should be set as 'NMS's IP:port',and the agent will send alarm synchronization result to the IP and port specified.
				If there is already an running alarm synchronization for that IP and port,it will return a commit fail error. "
			::= { hwNmNorthboundEventSynchronization 4 }

		
		-- 1.3.6.1.4.1.2011.2.15.1.7.7.5
		hwNmNorthboundEventSynchronizationCommandStop OBJECT-TYPE
			SYNTAX OCTET STRING
			ACCESS read-write
			STATUS mandatory
			DESCRIPTION
				"This node is to be set to stop the alarm synchronization.
				It should be set as 'NMS's IP:port',and the agent will stop alarm synchronization for the IP and port specified.
				If there is no such an running alarm synchronization for that IP and port,it will return a commit fail error. "
			::= { hwNmNorthboundEventSynchronization 5 }

		
	
--
-- Trap definitions
--
	
--  Trap definitions
-- 
		hwNmNorthboundEventNotify TRAP-TYPE 
			ENTERPRISE hwNmNorthboundEventInfo
			VARIABLES { hwNmNorthboundNEName, hwNmNorthboundNEType, hwNmNorthboundObjectInstance, hwNmNorthboundEventType, hwNmNorthboundEventTime, 
				hwNmNorthboundProbableCause, hwNmNorthboundSeverity, hwNmNorthboundEventDetail, hwNmNorthboundAdditionalInfo, hwNmNorthboundFaultFlag, 
				hwNmNorthboundFaultFunction, hwNmNorthboundDeviceIP, hwNmNorthboundSerialNo, hwNmNorthboundProbableRepair, hwNmNorthboundResourceIDs, 
				hwNmNorthboundsAdditionalVB1, hwNmNorthboundsAdditionalVB2, hwNmNorthboundsAdditionalVB3, hwNmNorthboundsAdditionalVB4, hwNmNorthboundsAdditionalVB5, 
				hwNmNorthboundsAdditionalVB6, hwNmNorthboundsAdditionalVB7, hwNmNorthboundsAdditionalVB8, hwNmNorthboundEventName }
			DESCRIPTION 
				"Notification for real-time alarm."
			::=  1

		hwNmNorthboundEventKeepAlive TRAP-TYPE 
			ENTERPRISE hwNmNorthboundEventKeepAliveInfo
			DESCRIPTION 
				"Notification for keep alive traps."
			::=  2

--  Trap definitions
-- 
		hwNmNorthboundEventNotifyCritical TRAP-TYPE 
			ENTERPRISE hwNmNorthboundEventInfo
			VARIABLES { hwNmNorthboundNEName, hwNmNorthboundNEType, hwNmNorthboundObjectInstance, hwNmNorthboundEventType, hwNmNorthboundEventTime, 
				hwNmNorthboundProbableCause, hwNmNorthboundSeverity, hwNmNorthboundEventDetail, hwNmNorthboundAdditionalInfo, hwNmNorthboundFaultFlag, 
				hwNmNorthboundFaultFunction, hwNmNorthboundDeviceIP, hwNmNorthboundSerialNo, hwNmNorthboundProbableRepair, hwNmNorthboundResourceIDs, 
				hwNmNorthboundsAdditionalVB1, hwNmNorthboundsAdditionalVB2, hwNmNorthboundsAdditionalVB3, hwNmNorthboundsAdditionalVB4, hwNmNorthboundsAdditionalVB5, 
				hwNmNorthboundsAdditionalVB6, hwNmNorthboundsAdditionalVB7, hwNmNorthboundsAdditionalVB8, hwNmNorthboundEventName }
			DESCRIPTION 
				"Notification for real-time alarm whose level is Critical."
			::=  3

--  Trap definitions
-- 
		hwNmNorthboundEventNotifyMajor TRAP-TYPE 
			ENTERPRISE hwNmNorthboundEventInfo
			VARIABLES { hwNmNorthboundNEName, hwNmNorthboundNEType, hwNmNorthboundObjectInstance, hwNmNorthboundEventType, hwNmNorthboundEventTime, 
				hwNmNorthboundProbableCause, hwNmNorthboundSeverity, hwNmNorthboundEventDetail, hwNmNorthboundAdditionalInfo, hwNmNorthboundFaultFlag, 
				hwNmNorthboundFaultFunction, hwNmNorthboundDeviceIP, hwNmNorthboundSerialNo, hwNmNorthboundProbableRepair, hwNmNorthboundResourceIDs, 
				hwNmNorthboundsAdditionalVB1, hwNmNorthboundsAdditionalVB2, hwNmNorthboundsAdditionalVB3, hwNmNorthboundsAdditionalVB4, hwNmNorthboundsAdditionalVB5, 
				hwNmNorthboundsAdditionalVB6, hwNmNorthboundsAdditionalVB7, hwNmNorthboundsAdditionalVB8, hwNmNorthboundEventName }
			DESCRIPTION 
				"Notification for real-time alarm whose level is Major."
			::=  4

--  Trap definitions
-- 
		hwNmNorthboundEventNotifyMinor TRAP-TYPE 
			ENTERPRISE hwNmNorthboundEventInfo
			VARIABLES { hwNmNorthboundNEName, hwNmNorthboundNEType, hwNmNorthboundObjectInstance, hwNmNorthboundEventType, hwNmNorthboundEventTime, 
				hwNmNorthboundProbableCause, hwNmNorthboundSeverity, hwNmNorthboundEventDetail, hwNmNorthboundAdditionalInfo, hwNmNorthboundFaultFlag, 
				hwNmNorthboundFaultFunction, hwNmNorthboundDeviceIP, hwNmNorthboundSerialNo, hwNmNorthboundProbableRepair, hwNmNorthboundResourceIDs, 
				hwNmNorthboundsAdditionalVB1, hwNmNorthboundsAdditionalVB2, hwNmNorthboundsAdditionalVB3, hwNmNorthboundsAdditionalVB4, hwNmNorthboundsAdditionalVB5, 
				hwNmNorthboundsAdditionalVB6, hwNmNorthboundsAdditionalVB7, hwNmNorthboundsAdditionalVB8, hwNmNorthboundEventName }
			DESCRIPTION 
				"Notification for real-time alarm whose level is Minor."
			::=  5

--  Trap definitions
-- 
		hwNmNorthboundEventNotifyWarning TRAP-TYPE 
			ENTERPRISE hwNmNorthboundEventInfo
			VARIABLES { hwNmNorthboundNEName, hwNmNorthboundNEType, hwNmNorthboundObjectInstance, hwNmNorthboundEventType, hwNmNorthboundEventTime, 
				hwNmNorthboundProbableCause, hwNmNorthboundSeverity, hwNmNorthboundEventDetail, hwNmNorthboundAdditionalInfo, hwNmNorthboundFaultFlag, 
				hwNmNorthboundFaultFunction, hwNmNorthboundDeviceIP, hwNmNorthboundSerialNo, hwNmNorthboundProbableRepair, hwNmNorthboundResourceIDs, 
				hwNmNorthboundsAdditionalVB1, hwNmNorthboundsAdditionalVB2, hwNmNorthboundsAdditionalVB3, hwNmNorthboundsAdditionalVB4, hwNmNorthboundsAdditionalVB5, 
				hwNmNorthboundsAdditionalVB6, hwNmNorthboundsAdditionalVB7, hwNmNorthboundsAdditionalVB8, hwNmNorthboundEventName }
			DESCRIPTION 
				"Notification for real-time alarm whose level is Warning."
			::=  6

--  Trap definitions
-- 
		hwNmNorthboundEventNotifyIndefinitely TRAP-TYPE 
			ENTERPRISE hwNmNorthboundEventInfo
			VARIABLES { hwNmNorthboundNEName, hwNmNorthboundNEType, hwNmNorthboundObjectInstance, hwNmNorthboundEventType, hwNmNorthboundEventTime, 
				hwNmNorthboundProbableCause, hwNmNorthboundSeverity, hwNmNorthboundEventDetail, hwNmNorthboundAdditionalInfo, hwNmNorthboundFaultFlag, 
				hwNmNorthboundFaultFunction, hwNmNorthboundDeviceIP, hwNmNorthboundSerialNo, hwNmNorthboundProbableRepair, hwNmNorthboundResourceIDs, 
				hwNmNorthboundsAdditionalVB1, hwNmNorthboundsAdditionalVB2, hwNmNorthboundsAdditionalVB3, hwNmNorthboundsAdditionalVB4, hwNmNorthboundsAdditionalVB5, 
				hwNmNorthboundsAdditionalVB6, hwNmNorthboundsAdditionalVB7, hwNmNorthboundsAdditionalVB8, hwNmNorthboundEventName }
			DESCRIPTION 
				"Notification for real-time alarm whose level is Indefinitely."
			::=  7

--  Trap definitions
-- 
		hwNmNorthboundEventNotifyUnknownSeverity TRAP-TYPE 
			ENTERPRISE hwNmNorthboundEventInfo
			VARIABLES { hwNmNorthboundNEName, hwNmNorthboundNEType, hwNmNorthboundObjectInstance, hwNmNorthboundEventType, hwNmNorthboundEventTime, 
				hwNmNorthboundProbableCause, hwNmNorthboundSeverity, hwNmNorthboundEventDetail, hwNmNorthboundAdditionalInfo, hwNmNorthboundFaultFlag, 
				hwNmNorthboundFaultFunction, hwNmNorthboundDeviceIP, hwNmNorthboundSerialNo, hwNmNorthboundProbableRepair, hwNmNorthboundResourceIDs, 
				hwNmNorthboundsAdditionalVB1, hwNmNorthboundsAdditionalVB2, hwNmNorthboundsAdditionalVB3, hwNmNorthboundsAdditionalVB4, hwNmNorthboundsAdditionalVB5, 
				hwNmNorthboundsAdditionalVB6, hwNmNorthboundsAdditionalVB7, hwNmNorthboundsAdditionalVB8, hwNmNorthboundEventName }
			DESCRIPTION 
				"Notification for real-time alarm whose level is UnknownSeverity."
			::=  8

		hwNmNorthboundEventSynchronizationStartNotify TRAP-TYPE 
			ENTERPRISE hwNmNorthboundEventSynchronizationStart
			DESCRIPTION 
				"Notification indicates the beginning of alarm synchronization."
			::=  9

		hwNmNorthboundEventSynchronizationQueryResultNotify TRAP-TYPE 
			ENTERPRISE hwNmNorthboundEventSynchronizationQueryResult
			VARIABLES { hwNmNorthboundNEName, hwNmNorthboundNEType, hwNmNorthboundObjectInstance, hwNmNorthboundEventType, hwNmNorthboundEventTime, 
				hwNmNorthboundProbableCause, hwNmNorthboundSeverity, hwNmNorthboundEventDetail, hwNmNorthboundAdditionalInfo, hwNmNorthboundFaultFlag, 
				hwNmNorthboundFaultFunction, hwNmNorthboundDeviceIP, hwNmNorthboundSerialNo, hwNmNorthboundProbableRepair, hwNmNorthboundResourceIDs, 
				hwNmNorthboundsAdditionalVB1, hwNmNorthboundsAdditionalVB2, hwNmNorthboundsAdditionalVB3, hwNmNorthboundsAdditionalVB4, hwNmNorthboundsAdditionalVB5, 
				hwNmNorthboundsAdditionalVB6, hwNmNorthboundsAdditionalVB7, hwNmNorthboundsAdditionalVB8, hwNmNorthboundEventName }
			DESCRIPTION 
				"Notification carries the query result of alarm synchronization."
			::=  10

		hwNmNorthboundEventSynchronizationEndNotify TRAP-TYPE 
			ENTERPRISE hwNmNorthboundEventSynchronizationEnd
			VARIABLES { hwNmNorthboundEventSynchronizationEndStatus, hwNmNorthboundEventSynchronizationEndStatusDetail }
			DESCRIPTION 
				"Notification indicates the end of alarm synchronization."
			::=  11

	
	END

--
-- HW-IMAPV1NORTHBOUND-TRAP-MIB.mib
--
