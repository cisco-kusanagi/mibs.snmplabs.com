--
--  Title:  Appian-LPORT-PRIVATE-MIB
--
--  Date:   11/13/99
--
--  Description:
--
--  This file contains the ASN.1 MIB definition for the private logical port
--  parameters for the OSAP platform.
--
--  Information in these tables are NOT SHARED by the OSAPs.
--

APPIAN-LPORT-PRIVATE-MIB DEFINITIONS ::= BEGIN

    IMPORTS

        acLport, AcOpStatus, AcNodeId             FROM APPIAN-SMI-MIB
        
        MODULE-IDENTITY, OBJECT-TYPE              FROM SNMPv2-SMI;


acLportPrivate   MODULE-IDENTITY
    LAST-UPDATED    "0003190000Z"
    ORGANIZATION    "Appian Communications, Inc."
    CONTACT-INFO    "Brian Johnson"

    DESCRIPTION
                    "Draft engineering version.  Not for release."

    ::= { acLport 1 }

--
-- Logical Port Table
--

acLportTable  OBJECT-TYPE
    SYNTAX  SEQUENCE OF AcLportEntry
    MAX-ACCESS  not-accessible
    STATUS      current
    DESCRIPTION
    "The logical table is an abstraction of the entity that uses a time slot.
    For an example, a VT1.5 time slot can be used as a DS1 and this DS1
    entity is refered to as a logical port.

    Rows in this table are created automatically when a trunk is activated
    for this OSAP.  The information in this table is local to this OSAP and
    not shared.  Before the trunk was activated, it was configured with 
    a list of logical port index(es).   A logical port index maps directly 
    to a timeslot index from the shared timeslot table.  A row in the Lport 
    table will be created for each logical port / timeslot that is defined 
    in the lport list for a trunk that is used/dropped by this OSAP."
    
    ::= {acLportPrivate 1 }

acLportEntry  OBJECT-TYPE
    SYNTAX      AcLportEntry
    MAX-ACCESS  not-accessible
    STATUS      current
    DESCRIPTION
    "A row in the logical port table."
        
    INDEX { acLportNodeId, acLportIndex }
        
    ::= {acLportTable 1 }


    AcLportEntry ::= 
        SEQUENCE {
            acLportNodeId             AcNodeId,
            acLportIndex              INTEGER,
            acLportOpStatus           AcOpStatus
        }

acLportNodeId  OBJECT-TYPE
    SYNTAX  AcNodeId
    MAX-ACCESS  accessible-for-notify
    STATUS  current
    DESCRIPTION
    "The node id is the id for this specific node in the OSAP ring."

    ::= {acLportEntry 1 }

acLportIndex  OBJECT-TYPE
    SYNTAX      INTEGER
    MAX-ACCESS  accessible-for-notify
    STATUS      current
    DESCRIPTION
    "The row index. This is the same as the index int the timeslot table 
    that this instance corresponds. It provides a mapping between the 
    shared and private tables."
        
    ::= {acLportEntry 2 }

acLportOpStatus OBJECT-TYPE
    SYNTAX  AcOpStatus
    MAX-ACCESS  read-only
    STATUS      current
    DESCRIPTION
    "The current operational status of the logical port that corresponds
    to this entity."
        
    ::= { acLportEntry 3 }

END
