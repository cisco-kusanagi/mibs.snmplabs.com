--
-- This MIB is the IBM 6611 enterprise specific MIB and can be
-- used to manage the 6611 router for the following releases:
--
--  Version 1 Release 1.0
--  Version 1 Release 1.1
--  Version 1 Release 1.2
--  Version 1 Release 2.0
--  Version 1 Release 3.0
--
-- The MIB will be periodically updated and expanded, but the
-- intent is to provide one enterprise MIB that can be used for
-- the latest release and also for all prior releases.
--
-- This enterprise MIB provides management support for functions
-- specific to the router and for functions that do not have
-- Internet standard MIB definitions. Along with this enterprise
-- MIB, the IBM 6611 supports the following Internet standard MIBs:
--
--  RFC 1213 - MIB-II
--  RFC 1229 - Interface Extensions
--  RFC 1231 - Token-Ring
--  RFC 1232 - DS1
--  RFC 1243 - Appletalk
--  RFC 1253 - OSPF
--  RFC 1269 - BGP
--  RFC 1284 - Ethernet
--  RFC 1286 - Obsolete - Replaced by RFC's 1493 and 1525
--  RFC 1289 - DECnet
--  RFC 1315 - Frame Relay
--  RFC 1354 - IP Forwarding
--  RFC 1389 - RIP Version 2
--  RFC 1493 - Bridge MIB
--  RFC 1525 - Source Route Bridge MIB
--
-- static char sccsid_ibm6611_mib[] = "@(#) snmp/samples/r66.my, SNMP, v1r3 1.11  8/12/93 13:55:18";

IBM6611-MIB DEFINITIONS ::= BEGIN

IMPORTS
          enterprises, Counter, Gauge, TimeTicks, IpAddress
                  FROM RFC1155-SMI
          DisplayString
                  FROM RFC1158-MIB
          OBJECT-TYPE
                  FROM RFC-1212;

-- Path to ibm6611 product

ibm       OBJECT IDENTIFIER ::= { enterprises 2 }
ibmProd   OBJECT IDENTIFIER ::= { ibm 6 }
ibm6611   OBJECT IDENTIFIER ::= { ibmProd 2 }

-- This MIB module uses the extended OBJECT-TYPE macro as
-- defined in RFC 1212.

-- IBM 6611 Extension Groups

ibmSubagents   OBJECT IDENTIFIER ::= { ibm6611 1 }
ibmChipSets    OBJECT IDENTIFIER ::= { ibm6611 2 }
ibmDSUs        OBJECT IDENTIFIER ::= { ibm6611 3 }

ibmsystem      OBJECT IDENTIFIER ::= { ibm6611 4 }
ibmicmp        OBJECT IDENTIFIER ::= { ibm6611 5 }
ibmsnmp        OBJECT IDENTIFIER ::= { ibm6611 6 }
ibmbridge      OBJECT IDENTIFIER ::= { ibm6611 7 }
ibmfr          OBJECT IDENTIFIER ::= { ibm6611 8 }
ibmdls         OBJECT IDENTIFIER ::= { ibm6611 9 }
ibmppp         OBJECT IDENTIFIER ::= { ibm6611 10 }
ibmxns         OBJECT IDENTIFIER ::= { ibm6611 11 }
ibmipx         OBJECT IDENTIFIER ::= { ibm6611 12 }
ibmappn        OBJECT IDENTIFIER ::= { ibm6611 13 }
ibmrpq         OBJECT IDENTIFIER ::= { ibm6611 14 }
ibmtb          OBJECT IDENTIFIER ::= { ibm6611 15 }   -- Added for 6611 V1R1.1
ibmapple       OBJECT IDENTIFIER ::= { ibm6611 16 }   -- Added for 6611 V1R1.1
ibmdec         OBJECT IDENTIFIER ::= { ibm6611 17 }   -- Added for 6611 V1R1.2
ibmvines       OBJECT IDENTIFIER ::= { ibm6611 18 }   -- Added for 6611 V1R2.0
ibminterfaces  OBJECT IDENTIFIER ::= { ibm6611 19 }   -- Added for 6611 V1R2.0


--
-- IBM 6611 System Extensions
--

ibmMainProcessorLoadTable OBJECT-TYPE
        SYNTAX  SEQUENCE OF IbmMainProcessorLoadEntry
        ACCESS  not-accessible
        STATUS  mandatory
        DESCRIPTION
                "A table containing the average main processor
                load over each minute for the last 60 minutes."
        ::= { ibmsystem 1 }

ibmMainProcessorLoadEntry OBJECT-TYPE
        SYNTAX  IbmMainProcessorLoadEntry
        ACCESS  not-accessible
        STATUS  mandatory
        DESCRIPTION
                "An entry in the main processor load table."
        INDEX   { ibmMainProcessorLoadIndex }
        ::= { ibmMainProcessorLoadTable 1 }

IbmMainProcessorLoadEntry ::=
    SEQUENCE {
        ibmMainProcessorLoadIndex
            INTEGER,
        ibmMainProcessorLoad
            Gauge
    }

ibmMainProcessorLoadIndex OBJECT-TYPE
        SYNTAX  INTEGER (1..60)
        ACCESS  read-only
        STATUS  mandatory
        DESCRIPTION
                "Indicates the number of minutes ago that this
                entry contains main processor load information for."
        ::= { ibmMainProcessorLoadEntry 1 }

ibmMainProcessorLoad OBJECT-TYPE
        SYNTAX  Gauge
        ACCESS  read-only
        STATUS  mandatory
        DESCRIPTION
                "The main processor load averaged over one minute.
                The load is given as a percentage. For example, 25% is 25."
        ::= { ibmMainProcessorLoadEntry 2 }

--
-- IBM 6611 Software Vital Product Data
--

ibmswvpd     OBJECT IDENTIFIER ::= { ibmsystem 2 }

swVpdTable OBJECT-TYPE
    SYNTAX SEQUENCE OF SwVpdEntry
    ACCESS not-accessible
    STATUS mandatory
    DESCRIPTION
        "A table containing software vital product data information."
    ::= { ibmswvpd 1 }

swVpdEntry OBJECT-TYPE
    SYNTAX SwVpdEntry
    ACCESS not-accessible
    STATUS mandatory
    DESCRIPTION
           "An entry for a piece of software installed on this router."
    INDEX { swvpdIndex }
    ::= { swVpdTable 1 }

SwVpdEntry ::= SEQUENCE {
    swvpdIndex      INTEGER,
    swvpdName       DisplayString,
    swvpdPtfName    DisplayString,
    swvpdVerId      INTEGER,
    swvpdRelId      INTEGER,
    swvpdModId      INTEGER,
    swvpdFixId      INTEGER,
    swvpdState      INTEGER,
    swvpdAction     INTEGER,
    swvpdPath       INTEGER,
    swvpdDateTime   DisplayString
}

swvpdIndex OBJECT-TYPE
    SYNTAX INTEGER
    ACCESS read-only
    STATUS mandatory
    DESCRIPTION
           "A unique value for each entry in this table."
    ::= { swVpdEntry 1 }

swvpdName OBJECT-TYPE
    SYNTAX DisplayString
    ACCESS read-only
    STATUS mandatory
    DESCRIPTION
           "The name of this software product."
    ::= { swVpdEntry 2 }

swvpdPtfName OBJECT-TYPE
    SYNTAX DisplayString
    ACCESS read-only
    STATUS mandatory
    DESCRIPTION
           "If this entry represents a PTF, this object contains
            the name of the PTF. Otherwise this object contains
            a string of zero length."
    ::= { swVpdEntry 3 }

swvpdVerId OBJECT-TYPE
    SYNTAX INTEGER
    ACCESS read-only
    STATUS mandatory
    DESCRIPTION
           "The version identifier for this piece of software."
    ::= { swVpdEntry 4 }

swvpdRelId OBJECT-TYPE
    SYNTAX INTEGER
    ACCESS read-only
    STATUS mandatory
    DESCRIPTION
           "The release identifier for this piece of software."
    ::= { swVpdEntry 5 }

swvpdModId OBJECT-TYPE
    SYNTAX INTEGER
    ACCESS read-only
    STATUS mandatory
    DESCRIPTION
           "The modification level identifier for this piece of software."
    ::= { swVpdEntry 6 }

swvpdFixId OBJECT-TYPE
    SYNTAX INTEGER
    ACCESS read-only
    STATUS mandatory
    DESCRIPTION
           "The fix level identifier for this piece of software."
    ::= { swVpdEntry 7 }

swvpdState OBJECT-TYPE
    SYNTAX INTEGER {
            complete(1),
            pending(2),
            broken(3),
            cancelled(4),
            unknown(5)
        }
    ACCESS read-only
    STATUS mandatory
    DESCRIPTION
           "The state of the action in swvpdAction being performed
            on this software."
    ::= { swVpdEntry 8 }

swvpdAction OBJECT-TYPE
    SYNTAX INTEGER {
            apply(1),
            commit(2),
            reject(3),
            decommit(4),
            cleanup(5),
            unknown(6)
        }
    ACCESS read-only
    STATUS mandatory
    DESCRIPTION
           "The action being performed on this software."
    ::= { swVpdEntry 9 }

swvpdPath OBJECT-TYPE
    SYNTAX INTEGER {
            root(1),
            usr(2),
            share(3)
        }
    ACCESS read-only
    STATUS mandatory
    DESCRIPTION
           "An indication of which part of the system this
            software is installed on. The values correspond to
            the following paths:

               root(1)   /etc/objrepos
               usr(2)    /usr/lib/objrepos
               share(3)  /usr/share/lib/objrepos"

    ::= { swVpdEntry 10 }

swvpdDateTime OBJECT-TYPE
    SYNTAX DisplayString
    ACCESS read-only
    STATUS mandatory
    DESCRIPTION
           "A string indicating the date and time that the action in
            swvpdAction was performed on this software."
    ::= { swVpdEntry 11 }

--
-- IBM 6611 System Maintenance Support
--

ibmmaint    OBJECT IDENTIFIER ::= {ibmsystem 4}

ibmmaintShutdown OBJECT-TYPE
    SYNTAX  INTEGER {
                running(1),
                shutdown-noipl(2),
                shutdown-ipl-local(4)
            }
    ACCESS  read-write
    STATUS  mandatory
    DESCRIPTION
            "When read, an active 6611 will return the value
             running(1).

             To force a shutdown, without a subsequent re-ipl
             of the 6611, this value should be set to
             shutdown-noipl(2).

             To recyle the 6611, (i.e.- shutdown with a
             subsequent re-ipl), and use the currently installed
             configuration, this variable should be set
             to shutdown-ipl-local(4)."
    ::= { ibmmaint 1 }

--
-- IBM 6611 Operating System Information
--

ibmsysInfo   OBJECT IDENTIFIER ::= { ibmmaint 7 }

ibmsysMBUFs   OBJECT IDENTIFIER ::= { ibmsysInfo 1 }

ibmsysMBUFsInUses OBJECT-TYPE
   SYNTAX  Gauge
   ACCESS  read-only
   STATUS  mandatory
   DESCRIPTION
           "Number of kernel MBUFs currently in use."
   ::= { ibmsysMBUFs 1 }

ibmsysMBUFsKbytes OBJECT-TYPE
   SYNTAX  Gauge
   ACCESS  read-only
   STATUS  mandatory
   DESCRIPTION
           "Kbytes of MBUFs currently allocated to the network."
   ::= { ibmsysMBUFs 2 }

ibmsysMBUFsPercents OBJECT-TYPE
   SYNTAX  Gauge
   ACCESS  read-only
   STATUS  mandatory
   DESCRIPTION
           "Percentage of total MBUFs available that are currently
            allocated to the network"
   ::= { ibmsysMBUFs 3 }

ibmsysMBUFsDeniedRequests OBJECT-TYPE
   SYNTAX  Counter
   ACCESS  read-only
   STATUS  mandatory
   DESCRIPTION
           "Number of MBUF requests that were denied
            due to lack of resources."
   ::= { ibmsysMBUFs 4 }

ibmsysMBUFsDelayedRequests OBJECT-TYPE
   SYNTAX  Counter
   ACCESS  read-only
   STATUS  mandatory
   DESCRIPTION
           "Number of MBUF requests that were delayed
            due to lack of resources."
   ::= { ibmsysMBUFs 5 }


ibmsysPageSpace   OBJECT IDENTIFIER ::= { ibmsysInfo 2 }

ibmsysPageSpaceTotal OBJECT-TYPE
   SYNTAX  INTEGER
   ACCESS  read-only
   STATUS  mandatory
   DESCRIPTION
           "Total number of paging space pages available on the 6611.
            A page is defined as 4096 bytes, so for example, an
            ibmsysPageSpaceTotal value of 12288 equals
            12288 * 4096 = 50331648 bytes of paging space."
   ::= { ibmsysPageSpace 1 }

ibmsysPageSpaceInUse OBJECT-TYPE
   SYNTAX  Gauge
   ACCESS  read-only
   STATUS  mandatory
   DESCRIPTION
           "Total number of paging space pages currently in use
            on the 6611. A page is defined as 4096 bytes, so for
            example, an ibmsysPageSpaceInUse value of 8839 equals
            8839 * 4096 = 36204544 bytes of paging space in use."
   ::= { ibmsysPageSpace 2 }


ibmsysRealMem   OBJECT IDENTIFIER ::= { ibmsysInfo 3 }

ibmsysRealMemSize OBJECT-TYPE
   SYNTAX  INTEGER
   ACCESS  read-only
   STATUS  mandatory
   DESCRIPTION
           "Total number of real memory frames available on the 6611.
            A frame is defined as 4096 bytes, so for example, an
            ibmsysRealMemSize value of 4096 equals
            4096 * 4096 = 16777216 bytes of real memory."
   ::= { ibmsysRealMem 1 }

ibmsysRealMemInUse OBJECT-TYPE
   SYNTAX  Gauge
   ACCESS  read-only
   STATUS  mandatory
   DESCRIPTION
           "Total number of real memory frames currently in use
            on the 6611. A frame is defined as 4096 bytes, so for
            example, an ibmsysRealMemInUse value of 4025 equals
            4025 * 4096 = 16486400 bytes of real memory in use."
   ::= { ibmsysRealMem 2 }

ibmsysRealMemFree OBJECT-TYPE
   SYNTAX  Gauge
   ACCESS  read-only
   STATUS  mandatory
   DESCRIPTION
           "Total number of real memory frames currently free
            on the 6611. A frame is defined as 4096 bytes, so for
            example, an ibmsysRealMemFree value of 71 equals
            71 * 4096 = 290816 bytes of real memory free."
   ::= { ibmsysRealMem 3 }



--
-- IBM 6611 SNMP Extensions
--     Objects containing information about enterprise
--     specific SNMP traps generated by this node.

ibmTrapNum OBJECT-TYPE
   SYNTAX  Counter
   ACCESS  read-only
   STATUS  mandatory
   DESCRIPTION
           "Number of IBM enterprise specific traps
           generated by this node."
   ::= { ibmsnmp 1 }

ibmTrapThrottleCount OBJECT-TYPE
   SYNTAX  Counter
   ACCESS  read-only
   STATUS  mandatory
   DESCRIPTION
           "Number of traps throttled since last trap."
   ::= { ibmsnmp 2 }

ibmTrapThrottleId OBJECT-TYPE
   SYNTAX  INTEGER
   ACCESS  read-only
   STATUS  mandatory
   DESCRIPTION
           "Trap ID of throttled traps. All throttled traps counted
           by ibmTrapThrottleCount have the this ID."
   ::= { ibmsnmp 3 }

ibmTrapThrottleTime OBJECT-TYPE
   SYNTAX  INTEGER
   ACCESS  read-only
   STATUS  mandatory
   DESCRIPTION
           "Number of seconds which must separate consecutive
           enterprise-specific traps with identical ID in order to not
           throttle them.  If the value of this object is 0, then
           trap throttling is inactive."
   ::= { ibmsnmp 4 }

--
-- IBM 6611 Hardware Chip Sets
--

ibmChipSetIntel        OBJECT IDENTIFIER ::= { ibmChipSets 1 }
ibmChipSetIntel82596B  OBJECT IDENTIFIER ::= { ibmChipSetIntel 1 }

ibmChipSetIBM          OBJECT IDENTIFIER ::= { ibmChipSets 2 }
ibmChipSetIBM8025A     OBJECT IDENTIFIER ::= { ibmChipSetIBM 1 }
ibmChipSetIBM8025B     OBJECT IDENTIFIER ::= { ibmChipSetIBM 2 }

ibmChipSetSignetics    OBJECT IDENTIFIER ::= { ibmChipSets 3 }
ibmChipSetSigneticsSCN68562 OBJECT IDENTIFIER ::= { ibmChipSetSignetics 1 }

-- Local Variables:
-- tab-width: 4
-- case-fold-search: nil
-- End:

-- static char sccsid_bridgefilter[] = "@(#) snmp/samples/bridgefilter.my, SNMP, v1r3  1/27/94 18:07:47";

------------------------------------------------------------------------
-- The IBM 6611 Source Route Bridge Filtering Extension                -
------------------------------------------------------------------------



-- All representations of MAC addresses in this MIB Module use,
-- as a textual convention (i.e. this convention does not affect
-- their encoding), the data type:

-- SRMacAddress ::= OCTET STRING (SIZE(6))


--
-- Filter tables use the following type to determine what
-- type of frames to apply the filter to.
--

-- BcastType  ::= INTEGER {
--            filterARB(1),   ## apply filter to ARB frames
--            filterSRB(2),   ## apply filter to SRB frames
--            filterBoth(3)   ## apply filter to both ARB and SRB frames
--        }


--
-- Filter tables use the following type to determine whether
-- entries are permit entries or deny entries.
--

-- SRFilterType ::= INTEGER {
--              deny(1),    ## frames matching the filter criteria
--                          ## are denied
--              permit(2)   ## frames matching the filter criteria
--                          ## are permitted
--          }

-- CharType ::= OCTET STRING (SIZE(1))
-- ShortType ::= OCTET STRING (SIZE(2))


ibmbridgeMACAddressFilters  OBJECT IDENTIFIER ::= { ibmbridge 1 }
ibmbridgeSAPFilters         OBJECT IDENTIFIER ::= { ibmbridge 2 }
ibmbridgeSNAPFilters        OBJECT IDENTIFIER ::= { ibmbridge 3 }
ibmbridgeRingFilters        OBJECT IDENTIFIER ::= { ibmbridge 4 }
ibmbridgeHopCountFilters    OBJECT IDENTIFIER ::= { ibmbridge 5 }
ibmbridgeWindowFilters      OBJECT IDENTIFIER ::= { ibmbridge 6 }
ibmbridgeFiltOrderTable     OBJECT IDENTIFIER ::= { ibmbridge 7 }
ibmbridgeRIFFilters         OBJECT IDENTIFIER ::= { ibmbridge 8 }     -- Replaces ibmbridgeRingFilters

--
-- MAC Address Filter Information Table
--

ibmmacAddrFilterInfoTable OBJECT-TYPE
    SYNTAX  SEQUENCE OF MacAddrFilterInfoEntry
    ACCESS  not-accessible
    STATUS  mandatory
    DESCRIPTION
            "Table of MAC address filtering information."
    ::= { ibmbridgeMACAddressFilters 1 }

ibmmacAddrFilterInfoEntry OBJECT-TYPE
    SYNTAX  MacAddrFilterInfoEntry
    ACCESS  not-accessible
    STATUS  mandatory
    DESCRIPTION
            "MAC address filtering information for a single interface."
    INDEX   { ibmmacAddrFilterType , ibmmacAddrFilterIfIndex }
    ::= { ibmmacAddrFilterInfoTable 1 }

MacAddrFilterInfoEntry ::=
    SEQUENCE {
        ibmmacAddrFilterIfIndex
            INTEGER,
        ibmmacAddrFilterInBcastType
            INTEGER,
        ibmmacAddrFilterOutBcastType
            INTEGER,
        ibmmacAddrFilterInFilterType
            INTEGER,
        ibmmacAddrFilterOutFilterType
            INTEGER,
        ibmmacAddrFilterInNotForwarded
            Counter,
        ibmmacAddrFilterOutNotForwarded
            Counter,
        ibmmacAddrFilterType
            INTEGER
    }

ibmmacAddrFilterIfIndex OBJECT-TYPE
    SYNTAX  INTEGER
    ACCESS  read-only
    STATUS  mandatory
    DESCRIPTION
            "The value of this object identifies the interface for which
            this entry contains management information.  The value of
            this object for a particular interface has the same value
            as the ifIndex object for the same interface."
    ::= { ibmmacAddrFilterInfoEntry 1 }


ibmmacAddrFilterInBcastType OBJECT-TYPE
    SYNTAX     INTEGER {
                filterARB(1),   -- apply filter to ARB frames
                filterSRB(2),   -- apply filter to SRB frames
                filterBoth(3)   -- apply filter to both ARB and SRB frames
            }

    ACCESS  read-only
    STATUS  mandatory
    DESCRIPTION
            "For the incoming MAC address filter table, determines
            what type of frames will be filtered."
    ::= { ibmmacAddrFilterInfoEntry 2 }

ibmmacAddrFilterOutBcastType OBJECT-TYPE
    SYNTAX     INTEGER {
                filterARB(1),   -- apply filter to ARB frames
                filterSRB(2),   -- apply filter to SRB frames
                filterBoth(3)   -- apply filter to both ARB and SRB frames
            }

    ACCESS  read-only
    STATUS  mandatory
    DESCRIPTION
            "For the outgoing MAC address filter table, determines
            what type of frames will be filtered."
    ::= { ibmmacAddrFilterInfoEntry 3 }

ibmmacAddrFilterInFilterType OBJECT-TYPE
    SYNTAX  INTEGER {
                deny(1),    -- frames matching the filter criteria
                            -- are denied
                permit(2)   -- frames matching the filter criteria
                            -- are permitted
            }
    ACCESS  read-only
    STATUS  mandatory
    DESCRIPTION
            "For the incoming filter table, determines whether
            the entries are permit or deny entries."
    ::= { ibmmacAddrFilterInfoEntry 4 }

ibmmacAddrFilterOutFilterType OBJECT-TYPE
    SYNTAX  INTEGER {
                deny(1),    -- frames matching the filter criteria
                            -- are denied
                permit(2)   -- frames matching the filter criteria
                            -- are permitted
            }
    ACCESS  read-only
    STATUS  mandatory
    DESCRIPTION
            "For the outgoing filter table, determines whether
            the entries are permit or deny entries."
    ::= { ibmmacAddrFilterInfoEntry 5 }

ibmmacAddrFilterInNotForwarded OBJECT-TYPE
    SYNTAX  Counter
    ACCESS  read-only
    STATUS  mandatory
    DESCRIPTION
            "Number of packets not forwarded, in the incoming
            direction, because they were filtered out."
    ::= { ibmmacAddrFilterInfoEntry 6 }

ibmmacAddrFilterOutNotForwarded OBJECT-TYPE
    SYNTAX  Counter
    ACCESS  read-only
    STATUS  mandatory
    DESCRIPTION
            "Number of packets not forwarded, in the outgoing
            direction, because they were filtered out."
    ::= { ibmmacAddrFilterInfoEntry 7 }

ibmmacAddrFilterType OBJECT-TYPE
    SYNTAX     INTEGER {
                sr(1),   --  sr filter
                tb(2)   --  tb filter
            }
    ACCESS  read-only
    STATUS  mandatory
    DESCRIPTION
            "The type of entry, either sr or tb."
    ::= { ibmmacAddrFilterInfoEntry 8 }


--
-- The Incoming MAC Address Filter Table
--

ibmmacAddrFilterInTable OBJECT-TYPE
    SYNTAX  SEQUENCE OF MacAddrFilterInEntry
    ACCESS  not-accessible
    STATUS  mandatory
    DESCRIPTION
            "Table of MAC address filtering information
            for incoming frames."
    ::= { ibmbridgeMACAddressFilters 2 }

ibmmacAddrFilterInEntry OBJECT-TYPE
    SYNTAX  MacAddrFilterInEntry
    ACCESS  not-accessible
    STATUS  mandatory
    DESCRIPTION
            "Filtering information for incoming frames."
    INDEX   { ibmmacAddrFilterInType, ibmmacAddrFilterInIfIndex,
              ibmmacAddrFilterInSrcAddress, ibmmacAddrFilterInDestAddress }
    ::= { ibmmacAddrFilterInTable 1 }

MacAddrFilterInEntry ::=
    SEQUENCE {
        ibmmacAddrFilterInIfIndex
            INTEGER,
        ibmmacAddrFilterInSrcAddress
            OCTET STRING,
        ibmmacAddrFilterInSrcMask
            OCTET STRING,
        ibmmacAddrFilterInDestAddress
            OCTET STRING,
        ibmmacAddrFilterInDestMask
            OCTET STRING,
        ibmmacAddrFilterInType
            INTEGER
    }

ibmmacAddrFilterInIfIndex OBJECT-TYPE
    SYNTAX  INTEGER
    ACCESS  read-only
    STATUS  mandatory
    DESCRIPTION
            "The value of this object identifies the interface for which
            this entry contains management information.  The value of
            this object for a particular interface has the same value
            as the ifIndex object for the same interface."
    ::= { ibmmacAddrFilterInEntry 1 }


ibmmacAddrFilterInSrcAddress OBJECT-TYPE
    SYNTAX  OCTET STRING (SIZE(6))
    ACCESS  read-only
    STATUS  mandatory
    DESCRIPTION
            "MAC source address to be filtered."
    ::= { ibmmacAddrFilterInEntry 2 }

ibmmacAddrFilterInSrcMask OBJECT-TYPE
    SYNTAX  OCTET STRING (SIZE(6))
    ACCESS  read-only
    STATUS  mandatory
    DESCRIPTION
            "Mask to allow ibmmacAddrFilterInSrcAddress to be used
            as a range of values."
    ::= { ibmmacAddrFilterInEntry 3 }

ibmmacAddrFilterInDestAddress OBJECT-TYPE
    SYNTAX  OCTET STRING (SIZE(6))
    ACCESS  read-only
    STATUS  mandatory
    DESCRIPTION
            "MAC destination address to be filtered."
    ::= { ibmmacAddrFilterInEntry 4 }

ibmmacAddrFilterInDestMask OBJECT-TYPE
    SYNTAX  OCTET STRING (SIZE(6))
    ACCESS  read-only
    STATUS  mandatory
    DESCRIPTION
            "Mask to allow ibmmacAddrFilterInDestAddress to be used
            as a range of values."
    ::= { ibmmacAddrFilterInEntry 5 }

ibmmacAddrFilterInType  OBJECT-TYPE
    SYNTAX     INTEGER {
                sr(1),   --  sr filter
                tb(2)   --  tb filter
            }
    ACCESS  read-only
    STATUS  mandatory
    DESCRIPTION
            "The type of entry, either sr or tb."
    ::= { ibmmacAddrFilterInEntry 6 }


--
-- The Outgoing MAC Address Filter Table
--

ibmmacAddrFilterOutTable OBJECT-TYPE
    SYNTAX  SEQUENCE OF MacAddrFilterOutEntry
    ACCESS  not-accessible
    STATUS  mandatory
    DESCRIPTION
            "Table of MAC address filtering information
            for outgoing frames."
    ::= { ibmbridgeMACAddressFilters 3 }

ibmmacAddrFilterOutEntry OBJECT-TYPE
    SYNTAX  MacAddrFilterOutEntry
    ACCESS  not-accessible
    STATUS  mandatory
    DESCRIPTION
            "Filtering information for outgoing frames."
    INDEX   { ibmmacAddrFilterOutType, ibmmacAddrFilterOutIfIndex,
              ibmmacAddrFilterOutSrcAddress,
              ibmmacAddrFilterOutDestAddress }
    ::= { ibmmacAddrFilterOutTable 1 }

MacAddrFilterOutEntry ::=
    SEQUENCE {
        ibmmacAddrFilterOutIfIndex
            INTEGER,
        ibmmacAddrFilterOutSrcAddress
            OCTET STRING,
        ibmmacAddrFilterOutSrcMask
            OCTET STRING,
        ibmmacAddrFilterOutDestAddress
            OCTET STRING,
        ibmmacAddrFilterOutDestMask
            OCTET STRING,
        ibmmacAddrFilterOutType
            INTEGER
    }

ibmmacAddrFilterOutIfIndex OBJECT-TYPE
    SYNTAX  INTEGER
    ACCESS  read-only
    STATUS  mandatory
    DESCRIPTION
            "The value of this object identifies the interface for which
            this entry contains management information.  The value of
            this object for a particular interface has the same value
            as the ifIndex object for the same interface."
    ::= { ibmmacAddrFilterOutEntry 1 }


ibmmacAddrFilterOutSrcAddress OBJECT-TYPE
    SYNTAX  OCTET STRING (SIZE(6))
    ACCESS  read-only
    STATUS  mandatory
    DESCRIPTION
            "MAC source address to be filtered."
    ::= { ibmmacAddrFilterOutEntry 2 }

ibmmacAddrFilterOutSrcMask OBJECT-TYPE
    SYNTAX  OCTET STRING (SIZE(6))
    ACCESS  read-only
    STATUS  mandatory
    DESCRIPTION
            "Mask to allow ibmmacAddrFilterOutSrcAddress to be used
            as a range of values."
    ::= { ibmmacAddrFilterOutEntry 3 }

ibmmacAddrFilterOutDestAddress OBJECT-TYPE
    SYNTAX  OCTET STRING (SIZE(6))
    ACCESS  read-only
    STATUS  mandatory
    DESCRIPTION
            "MAC destination address to be filtered."
    ::= { ibmmacAddrFilterOutEntry 4 }

ibmmacAddrFilterOutDestMask OBJECT-TYPE
    SYNTAX  OCTET STRING (SIZE(6))
    ACCESS  read-only
    STATUS  mandatory
    DESCRIPTION
            "Mask to allow ibmmacAddrFilterOutDestAddress to be used
            as a range of values."
    ::= { ibmmacAddrFilterOutEntry 5 }

ibmmacAddrFilterOutType OBJECT-TYPE
    SYNTAX     INTEGER {
                sr(1),   --  sr filter
                tb(2)   --  tb filter
            }
    ACCESS  read-only
    STATUS  mandatory
    DESCRIPTION
            "Type type of entry either sr or tb"
    ::= { ibmmacAddrFilterOutEntry 6 }


--
-- The SAP Filter Information Table
--
-- NOTE: The SAP filter tables themselves are included in this
-- table because they are encoded as octet strings.  Permit/deny
-- information is implicit in these tables.
--

ibmsapFilterInfoTable OBJECT-TYPE
    SYNTAX  SEQUENCE OF SapFilterInfoEntry
    ACCESS  not-accessible
    STATUS  mandatory
    DESCRIPTION
            "Table of SAP filtering information."
    ::= { ibmbridgeSAPFilters 1 }

ibmsapFilterInfoEntry OBJECT-TYPE
    SYNTAX  SapFilterInfoEntry
    ACCESS  not-accessible
    STATUS  mandatory
    DESCRIPTION
            "SAP filtering information for a single interface."
    INDEX   { ibmsapFilterType , ibmsapFilterIfIndex }
    ::= { ibmsapFilterInfoTable 1 }

SapFilterInfoEntry ::=
    SEQUENCE {
        ibmsapFilterIfIndex
            INTEGER,
        ibmsapFilterInBcastType
            INTEGER,
        ibmsapFilterOutBcastType
            INTEGER,
        ibmsapFilterIn
            OCTET STRING,
        ibmsapFilterOut
            OCTET STRING,
        ibmsapFilterInNotForwarded
            Counter,
        ibmsapFilterOutNotForwarded
            Counter,
        ibmsapFilterType
            INTEGER
    }

ibmsapFilterIfIndex OBJECT-TYPE
    SYNTAX  INTEGER
    ACCESS  read-only
    STATUS  mandatory
    DESCRIPTION
            "The value of this object identifies the interface for which
            this entry contains management information.  The value of
            this object for a particular interface has the same value
            as the ifIndex object for the same interface."
    ::= { ibmsapFilterInfoEntry 1 }

ibmsapFilterInBcastType OBJECT-TYPE
    SYNTAX     INTEGER {
                filterARB(1),   -- apply filter to ARB frames
                filterSRB(2),   -- apply filter to SRB frames
                filterBoth(3)   -- apply filter to both ARB and SRB frames
            }

    ACCESS  read-only
    STATUS  mandatory
    DESCRIPTION
            "For the incoming SAP filter table, determines
            what type of frames will be filtered."
    ::= { ibmsapFilterInfoEntry 2 }

ibmsapFilterOutBcastType OBJECT-TYPE
    SYNTAX     INTEGER {
                filterARB(1),   -- apply filter to ARB frames
                filterSRB(2),   -- apply filter to SRB frames
                filterBoth(3)   -- apply filter to both ARB and SRB frames
            }

    ACCESS  read-only
    STATUS  mandatory
    DESCRIPTION
            "For the outgoing SAP filter table, determines
            what type of frames will be filtered."
    ::= { ibmsapFilterInfoEntry 3 }

ibmsapFilterIn OBJECT-TYPE
    SYNTAX  OCTET STRING (SIZE (16))
    ACCESS  read-only
    STATUS  mandatory
    DESCRIPTION
            "A bitmap of all possible source SAPs (even) that will
            be on or off depending on whether or not an incoming
            frame with that SAP is to be forwarded."
    ::= { ibmsapFilterInfoEntry 4 }

ibmsapFilterOut OBJECT-TYPE
    SYNTAX  OCTET STRING (SIZE (16))
    ACCESS  read-only
    STATUS  mandatory
    DESCRIPTION
            "A bitmap of all possible source SAPs (even) that will
            be on or off depending on whether or not an outgoing
            frame with that SAP is to be forwarded."
    ::= { ibmsapFilterInfoEntry 5 }

ibmsapFilterInNotForwarded OBJECT-TYPE
    SYNTAX  Counter
    ACCESS  read-only
    STATUS  mandatory
    DESCRIPTION
            "Number of packets not forwarded, in the incoming
            direction, because they were filtered out."
    ::= { ibmsapFilterInfoEntry 6 }

ibmsapFilterOutNotForwarded OBJECT-TYPE
    SYNTAX  Counter
    ACCESS  read-only
    STATUS  mandatory
    DESCRIPTION
            "Number of packets not forwarded, in the outgoing
            direction, because they were filtered out."
    ::= { ibmsapFilterInfoEntry 7 }

ibmsapFilterType  OBJECT-TYPE
    SYNTAX     INTEGER {
                sr(1),   --  sr filter
                tb(2)   --  tb filter
            }
    ACCESS  read-only
    STATUS  mandatory
    DESCRIPTION
            "The type of entry, either sr or tb."
    ::= { ibmsapFilterInfoEntry 8 }


--
-- The SNAP Filter Information Table
--

ibmsnapFilterInfoTable OBJECT-TYPE
    SYNTAX  SEQUENCE OF SnapFilterInfoEntry
    ACCESS  not-accessible
    STATUS  mandatory
    DESCRIPTION
            "Table of SNAP filtering information.   Note that
            SNAP filtering only comes into play if packets with
            source SAP 0xAA are being forwarded."
    ::= { ibmbridgeSNAPFilters 1 }

ibmsnapFilterInfoEntry OBJECT-TYPE
    SYNTAX  SnapFilterInfoEntry
    ACCESS  not-accessible
    STATUS  mandatory
    DESCRIPTION
            "SNAP filtering information for a single interface."
    INDEX   { ibmsnapFilterType, ibmsnapFilterIfIndex }
    ::= { ibmsnapFilterInfoTable 1 }

SnapFilterInfoEntry ::=
    SEQUENCE {
        ibmsnapFilterIfIndex
            INTEGER,
        ibmsnapFilterInFilterType
            INTEGER,
        ibmsnapFilterOutFilterType
            INTEGER,
        ibmsnapFilterInNotForwarded
            Counter,
        ibmsnapFilterOutNotForwarded
            Counter,
        ibmsnapFilterType
            INTEGER
    }

ibmsnapFilterIfIndex OBJECT-TYPE
    SYNTAX  INTEGER
    ACCESS  read-only
    STATUS  mandatory
    DESCRIPTION
            "The value of this object identifies the interface for which
            this entry contains management information.  The value of
            this object for a particular interface has the same value
            as the ifIndex object for the same interface."
    ::= { ibmsnapFilterInfoEntry 1 }


ibmsnapFilterInFilterType OBJECT-TYPE
    SYNTAX  INTEGER {
                deny(1),    -- frames matching the filter criteria
                            -- are denied
                permit(2)   -- frames matching the filter criteria
                            -- are permitted
            }
    ACCESS  read-only
    STATUS  mandatory
    DESCRIPTION
            "For the incoming SNAP filter table, determines whether
            the entries are permit or deny entries."
    ::= { ibmsnapFilterInfoEntry 2 }

ibmsnapFilterOutFilterType OBJECT-TYPE
    SYNTAX  INTEGER {
                deny(1),    -- frames matching the filter criteria
                            -- are denied
                permit(2)   -- frames matching the filter criteria
                            -- are permitted
            }
    ACCESS  read-only
    STATUS  mandatory
    DESCRIPTION
            "For the outgoing SNAP filter table, determines whether
            the entries are permit or deny entries."
    ::= { ibmsnapFilterInfoEntry 3 }

ibmsnapFilterInNotForwarded OBJECT-TYPE
    SYNTAX  Counter
    ACCESS  read-only
    STATUS  mandatory
    DESCRIPTION
            "Number of packets not forwarded, in the incoming
            direction, because they were filtered out."
    ::= { ibmsnapFilterInfoEntry 4 }

ibmsnapFilterOutNotForwarded OBJECT-TYPE
    SYNTAX  Counter
    ACCESS  read-only
    STATUS  mandatory
    DESCRIPTION
            "Number of packets not forwarded, in the outgoing
            direction, because they were filtered out."
    ::= { ibmsnapFilterInfoEntry 5 }

ibmsnapFilterType OBJECT-TYPE
    SYNTAX     INTEGER {
                sr(1),   --  sr filter
                tb(2)   --  tb filter
            }
    ACCESS  read-only
    STATUS  mandatory
    DESCRIPTION
            "The type of entry, either sr or tb."
    ::= { ibmsnapFilterInfoEntry 6 }


--
-- The Incoming SNAP Filter Table
--

ibmsnapFilterInTable OBJECT-TYPE
    SYNTAX  SEQUENCE OF SnapFilterInEntry
    ACCESS  not-accessible
    STATUS  mandatory
    DESCRIPTION
            "Table of SNAP type filtering information
            for incoming frames.  Note that the entries in
            this table only come into play if packets with
            source SAP 0xAA are being forwarded."
    ::= { ibmbridgeSNAPFilters 2 }

ibmsnapFilterInEntry OBJECT-TYPE
    SYNTAX  SnapFilterInEntry
    ACCESS  not-accessible
    STATUS  mandatory
    DESCRIPTION
            "Filtering information for a single SNAP value on a
            single interface."
    INDEX   { ibmsnapFilterInType, ibmsnapFilterInIfIndex,
              ibmsnapFilterInValue }
    ::= { ibmsnapFilterInTable 1 }

SnapFilterInEntry ::=
    SEQUENCE {
        ibmsnapFilterInIfIndex
            INTEGER,
        ibmsnapFilterInValue
            INTEGER,
        ibmsnapFilterInMask
            INTEGER,
        ibmsnapFilterInType
            INTEGER
    }

ibmsnapFilterInIfIndex OBJECT-TYPE
    SYNTAX  INTEGER
    ACCESS  read-only
    STATUS  mandatory
    DESCRIPTION
            "The value of this object identifies the interface for which
            this entry contains management information.  The value of
            this object for a particular interface has the same value
            as the ifIndex object for the same interface."
    ::= { ibmsnapFilterInEntry 1 }


ibmsnapFilterInValue OBJECT-TYPE
    SYNTAX  INTEGER
    ACCESS  read-only
    STATUS  mandatory
    DESCRIPTION
            "Indicates which SNAP value to filter."
    ::= { ibmsnapFilterInEntry 2 }

ibmsnapFilterInMask OBJECT-TYPE
    SYNTAX  INTEGER
    ACCESS  read-only
    STATUS  mandatory
    DESCRIPTION
            "Mask to allow ibmsnapFilterInValue to be used as a range of
            values."
    ::= { ibmsnapFilterInEntry 3 }

ibmsnapFilterInType OBJECT-TYPE
    SYNTAX     INTEGER {
                sr(1),   --  sr filter
                tb(2)   --  tb filter
            }
    ACCESS  read-only
    STATUS  mandatory
    DESCRIPTION
            "The type of entry, either sr or tb."
    ::= { ibmsnapFilterInEntry 4 }


--
-- The Outgoing SNAP Filter Table
--

ibmsnapFilterOutTable OBJECT-TYPE
    SYNTAX  SEQUENCE OF SnapFilterOutEntry
    ACCESS  not-accessible
    STATUS  mandatory
    DESCRIPTION
            "Table of SNAP filtering information
            for outgoing frames.  Note that the entries in
            this table only come into play if packets with
            source SAP 0xAA are being forwarded."
    ::= { ibmbridgeSNAPFilters 3 }

ibmsnapFilterOutEntry OBJECT-TYPE
    SYNTAX  SnapFilterOutEntry
    ACCESS  not-accessible
    STATUS  mandatory
    DESCRIPTION
            "Filtering information for a single SNAP value on a
            single interface."
    INDEX   { ibmsnapFilterOutType, ibmsnapFilterOutIfIndex,
              ibmsnapFilterOutValue }
    ::= { ibmsnapFilterOutTable 1 }

SnapFilterOutEntry ::=
    SEQUENCE {
        ibmsnapFilterOutIfIndex
            INTEGER,
        ibmsnapFilterOutValue
            INTEGER,
        ibmsnapFilterOutMask
            INTEGER,
        ibmsnapFilterOutType
            INTEGER
    }

ibmsnapFilterOutIfIndex OBJECT-TYPE
    SYNTAX  INTEGER
    ACCESS  read-only
    STATUS  mandatory
    DESCRIPTION
            "The value of this object identifies the interface for which
            this entry contains management information.  The value of
            this object for a particular interface has the same value
            as the ifIndex object for the same interface."
    ::= { ibmsnapFilterOutEntry 1 }


ibmsnapFilterOutValue OBJECT-TYPE
    SYNTAX  INTEGER
    ACCESS  read-only
    STATUS  mandatory
    DESCRIPTION
            "Indicates which SNAP values to filter."
    ::= { ibmsnapFilterOutEntry 2 }

ibmsnapFilterOutMask OBJECT-TYPE
    SYNTAX  INTEGER
    ACCESS  read-only
    STATUS  mandatory
    DESCRIPTION
            "Mask to allow ibmsnapFilterOutValue to be used as a
            range of values."
    ::= { ibmsnapFilterOutEntry 3 }

ibmsnapFilterOutType OBJECT-TYPE
    SYNTAX     INTEGER {
                sr(1),   --  sr filter
                tb(2)   --  tb filter
            }
    ACCESS  read-only
    STATUS  mandatory
    DESCRIPTION
            "The type of entry, either sr or tb."
    ::= { ibmsnapFilterOutEntry 4 }


--
-- The Ring Filter Information Table
--
-- This table is now deprecated and is being replaced by the "ibmbridgeRIFFilters" group.
-- This new MIB mirrors an enhancement to the capabilities of the Source Route bridge
-- filters to now allow filtering on the ring number AND bridge number.
--
-- The STATUS clause of the following table, however, is not being changed to "DEPRECATED"
-- so it can still be used to manage previous releases of the 6611 with the old style ring
-- number filtering.
--

ibmringFilterInfoTable OBJECT-TYPE
    SYNTAX  SEQUENCE OF RingFilterInfoEntry
    ACCESS  not-accessible
    STATUS  mandatory
    DESCRIPTION
            "Table of ring filtering information."
    ::= { ibmbridgeRingFilters 1 }

ibmringFilterInfoEntry OBJECT-TYPE
    SYNTAX  RingFilterInfoEntry
    ACCESS  not-accessible
    STATUS  mandatory
    DESCRIPTION
            "Ring filtering information for a single interface."
    INDEX   { ibmringFilterIfIndex }
    ::= { ibmringFilterInfoTable 1 }

RingFilterInfoEntry ::=
    SEQUENCE {
        ibmringFilterIfIndex
            INTEGER,
        ibmringFilterInBcastType
            INTEGER,
        ibmringFilterOutBcastType
            INTEGER,
        ibmringFilterInFilterType
            INTEGER,
        ibmringFilterOutFilterType
            INTEGER,
        ibmringFilterInNotForwarded
            Counter,
        ibmringFilterOutNotForwarded
            Counter
    }

ibmringFilterIfIndex OBJECT-TYPE
    SYNTAX  INTEGER
    ACCESS  read-only
    STATUS  mandatory
    DESCRIPTION
            "The value of this object identifies the interface for which
            this entry contains management information.  The value of
            this object for a particular interface has the same value
            as the ifIndex object for the same interface."
    ::= { ibmringFilterInfoEntry 1 }

ibmringFilterInBcastType OBJECT-TYPE
    SYNTAX     INTEGER {
                filterARB(1),   -- apply filter to ARB frames
                filterSRB(2),   -- apply filter to SRB frames
                filterBoth(3)   -- apply filter to both ARB and SRB frames
            }

    ACCESS  read-only
    STATUS  mandatory
    DESCRIPTION
            "For the incoming ring filter table, determines
            what type of frames will be filtered."
    ::= { ibmringFilterInfoEntry 2 }

ibmringFilterOutBcastType OBJECT-TYPE
    SYNTAX     INTEGER {
                filterARB(1),   -- apply filter to ARB frames
                filterSRB(2),   -- apply filter to SRB frames
                filterBoth(3)   -- apply filter to both ARB and SRB frames
            }

    ACCESS  read-only
    STATUS  mandatory
    DESCRIPTION
            "For the outgoing ring filter table, determines
            what type of frames will be filtered."
    ::= { ibmringFilterInfoEntry 3 }

ibmringFilterInFilterType OBJECT-TYPE
    SYNTAX  INTEGER {
                deny(1),    -- frames matching the filter criteria
                            -- are denied
                permit(2)   -- frames matching the filter criteria
                            -- are permitted
            }
    ACCESS  read-only
    STATUS  mandatory
    DESCRIPTION
            "For the incoming ring filter table, determines whether
            the entries are permit or deny entries."
    ::= { ibmringFilterInfoEntry 4 }

ibmringFilterOutFilterType OBJECT-TYPE
    SYNTAX  INTEGER {
                deny(1),    -- frames matching the filter criteria
                            -- are denied
                permit(2)   -- frames matching the filter criteria
                            -- are permitted
            }
    ACCESS  read-only
    STATUS  mandatory
    DESCRIPTION
            "For the outgoing ring filter table, determines whether
            the entries are permit or deny entries."
    ::= { ibmringFilterInfoEntry 5 }

ibmringFilterInNotForwarded OBJECT-TYPE
    SYNTAX  Counter
    ACCESS  read-only
    STATUS  mandatory
    DESCRIPTION
            "Number of packets not forwarded, in the incoming
            direction, because they were filtered out."
    ::= { ibmringFilterInfoEntry 6 }

ibmringFilterOutNotForwarded OBJECT-TYPE
    SYNTAX  Counter
    ACCESS  read-only
    STATUS  mandatory
    DESCRIPTION
            "Number of packets not forwarded, in the outgoing
            direction, because they were filtered out."
    ::= { ibmringFilterInfoEntry 7 }


--
-- The Incoming Ring Number Filter Table
--
-- This table is now deprecated and is being replaced by the "ibmbridgeRIFFilters" group.
-- This new MIB mirrors an enhancement to the capabilities of the Source Route bridge
-- filters to now allow filtering on the ring number AND bridge number.
--
-- The STATUS clause of the following table, however, is not being changed to "DEPRECATED"
-- so it can still be used to manage previous releases of the 6611 with the old style ring
-- number filtering.
--

ibmringFilterInTable OBJECT-TYPE
    SYNTAX  SEQUENCE OF RingFilterInEntry
    ACCESS  not-accessible
    STATUS  mandatory
    DESCRIPTION
            "Table of ring number filtering information
            for incoming frames."
    ::= { ibmbridgeRingFilters 2 }

ibmringFilterInEntry OBJECT-TYPE
    SYNTAX  RingFilterInEntry
    ACCESS  not-accessible
    STATUS  mandatory
    DESCRIPTION
            "Filtering information for a single ring number
            on a single interface."
    INDEX   { ibmringFilterInIfIndex, ibmringFilterInNumber }
    ::= { ibmringFilterInTable 1 }

RingFilterInEntry ::=
    SEQUENCE {
        ibmringFilterInIfIndex
            INTEGER,
        ibmringFilterInNumber
            INTEGER,
        ibmringFilterInMask
            INTEGER
    }

ibmringFilterInIfIndex OBJECT-TYPE
    SYNTAX  INTEGER
    ACCESS  read-only
    STATUS  mandatory
    DESCRIPTION
            "The value of this object identifies the interface for which
            this entry contains management information.  The value of
            this object for a particular interface has the same value
            as the ifIndex object for the same interface."
    ::= { ibmringFilterInEntry 1 }

ibmringFilterInNumber OBJECT-TYPE
    SYNTAX  INTEGER
    ACCESS  read-only
    STATUS  mandatory
    DESCRIPTION
            "Indicates which ring number to filter."
    ::= { ibmringFilterInEntry 2 }

ibmringFilterInMask OBJECT-TYPE
    SYNTAX  INTEGER
    ACCESS  read-only
    STATUS  mandatory
    DESCRIPTION
            "Mask to allow ibmringFilterInNumber to be used as a
            range of values."
    ::= { ibmringFilterInEntry 3 }


--
-- The Outgoing Ring Number Filter Table
--
-- This table is now deprecated and is being replaced by the "ibmbridgeRIFFilters" group.
-- This new MIB mirrors an enhancement to the capabilities of the Source Route bridge
-- filters to now allow filtering on the ring number AND bridge number.
--
-- The STATUS clause of the following table, however, is not being changed to "DEPRECATED"
-- so it can still be used to manage previous releases of the 6611 with the old style ring
-- number filtering.
--

ibmringFilterOutTable OBJECT-TYPE
    SYNTAX  SEQUENCE OF RingFilterOutEntry
    ACCESS  not-accessible
    STATUS  mandatory
    DESCRIPTION
            "Table of ring number filtering information
            for outgoing frames."
    ::= { ibmbridgeRingFilters 3 }

ibmringFilterOutEntry OBJECT-TYPE
    SYNTAX  RingFilterOutEntry
    ACCESS  not-accessible
    STATUS  mandatory
    DESCRIPTION
            "Filtering information for a single ring number
            on a single interface."
    INDEX   { ibmringFilterOutIfIndex, ibmringFilterOutNumber }
    ::= { ibmringFilterOutTable 1 }

RingFilterOutEntry ::=
    SEQUENCE {
        ibmringFilterOutIfIndex
            INTEGER,
        ibmringFilterOutNumber
            INTEGER,
        ibmringFilterOutMask
            INTEGER
    }

ibmringFilterOutIfIndex OBJECT-TYPE
    SYNTAX  INTEGER
    ACCESS  read-only
    STATUS  mandatory
    DESCRIPTION
            "The value of this object identifies the interface for which
            this entry contains management information.  The value of
            this object for a particular interface has the same value
            as the ifIndex object for the same interface."
    ::= { ibmringFilterOutEntry 1 }

ibmringFilterOutNumber OBJECT-TYPE
    SYNTAX  INTEGER
    ACCESS  read-only
    STATUS  mandatory
    DESCRIPTION
            "Indicates which ring number to filter."
    ::= { ibmringFilterOutEntry 2 }

ibmringFilterOutMask OBJECT-TYPE
    SYNTAX  INTEGER
    ACCESS  read-only
    STATUS  mandatory
    DESCRIPTION
            "Mask to allow ibmringFilterOutNumber to be used as a
            range of values."
    ::= { ibmringFilterOutEntry 3 }


--
-- The Hop Count Filter Table
--

ibmhopCountFilterInfoTable OBJECT-TYPE
    SYNTAX  SEQUENCE OF HopCountFilterInfoEntry
    ACCESS  not-accessible
    STATUS  mandatory
    DESCRIPTION
            "Table of hop count filtering information."
    ::= { ibmbridgeHopCountFilters 1 }

ibmhopCountFilterInfoEntry OBJECT-TYPE
    SYNTAX  HopCountFilterInfoEntry
    ACCESS  not-accessible
    STATUS  mandatory
    DESCRIPTION
            "Hop count filtering information for a single interface."
    INDEX   { ibmhopCountFilterIfIndex }
    ::= { ibmhopCountFilterInfoTable 1 }

HopCountFilterInfoEntry ::=
    SEQUENCE {
        ibmhopCountFilterIfIndex
            INTEGER,
        ibmhopCountFilterBcastType
            INTEGER,
        ibmhopCountFilterCount
            INTEGER
    }

ibmhopCountFilterIfIndex OBJECT-TYPE
    SYNTAX  INTEGER
    ACCESS  read-only
    STATUS  mandatory
    DESCRIPTION
            "The value of this object identifies the interface for which
            this entry contains management information.  The value of
            this object for a particular interface has the same value
            as the ifIndex object for the same interface."
    ::= { ibmhopCountFilterInfoEntry 1 }

ibmhopCountFilterBcastType OBJECT-TYPE
    SYNTAX     INTEGER {
                filterARB(1),   -- apply filter to ARB frames
                filterSRB(2),   -- apply filter to SRB frames
                filterBoth(3)   -- apply filter to both ARB and SRB frames
            }

    ACCESS  read-only
    STATUS  mandatory
    DESCRIPTION
            "Determines what type of incoming frames will be filtered."
    ::= { ibmhopCountFilterInfoEntry 2 }

ibmhopCountFilterCount OBJECT-TYPE
    SYNTAX  INTEGER
    ACCESS  read-only
    STATUS  mandatory
    DESCRIPTION
            "The number of hops allowed for incoming frames."
    ::= { ibmhopCountFilterInfoEntry 3 }


--
-- Window Filter Information Table
--

ibmwindowFilterInfoTable OBJECT-TYPE
    SYNTAX  SEQUENCE OF WindowFilterInfoEntry
    ACCESS  not-accessible
    STATUS  mandatory
    DESCRIPTION
            "Table of Window filtering information."
    ::= { ibmbridgeWindowFilters 1 }

ibmwindowFilterInfoEntry OBJECT-TYPE
    SYNTAX  WindowFilterInfoEntry
    ACCESS  not-accessible
    STATUS  mandatory
    DESCRIPTION
            "Window filtering information for a single interface."
    INDEX   { ibmwindowFilterType, ibmwindowFilterIfIndex }
    ::= { ibmwindowFilterInfoTable 1 }

WindowFilterInfoEntry ::=
    SEQUENCE {
        ibmwindowFilterIfIndex
            INTEGER,
        ibmwindowFilterInBcastType
            INTEGER,
        ibmwindowFilterOutBcastType
            INTEGER,
        ibmwindowFilterInFilterType
            INTEGER,
        ibmwindowFilterOutFilterType
            INTEGER,
        ibmwindowFilterInNotForwarded
            Counter,
        ibmwindowFilterOutNotForwarded
            Counter,
        ibmwindowFilterType
            INTEGER
    }

ibmwindowFilterIfIndex OBJECT-TYPE
    SYNTAX  INTEGER
    ACCESS  read-only
    STATUS  mandatory
    DESCRIPTION
            "The value of this object identifies the interface for which
            this entry contains management information.  The value of
            this object for a particular interface has the same value
            as the ifIndex object for the same interface."
    ::= { ibmwindowFilterInfoEntry 1 }

ibmwindowFilterInBcastType OBJECT-TYPE
    SYNTAX     INTEGER {
                filterARB(1),   -- apply filter to ARB frames
                filterSRB(2),   -- apply filter to SRB frames
                filterBoth(3)   -- apply filter to both ARB and SRB frames
            }

    ACCESS  read-only
    STATUS  mandatory
    DESCRIPTION
            "For the incoming Window filter table, determines
            what type of frames will be filtered."
    ::= { ibmwindowFilterInfoEntry 2 }

ibmwindowFilterOutBcastType OBJECT-TYPE
    SYNTAX     INTEGER {
                filterARB(1),   -- apply filter to ARB frames
                filterSRB(2),   -- apply filter to SRB frames
                filterBoth(3)   -- apply filter to both ARB and SRB frames
            }

    ACCESS  read-only
    STATUS  mandatory
    DESCRIPTION
            "For the outgoing Window filter table, determines
            what type of frames will be filtered."
    ::= { ibmwindowFilterInfoEntry 3 }

ibmwindowFilterInFilterType OBJECT-TYPE
    SYNTAX  INTEGER {
                deny(1),    -- frames matching the filter criteria
                            -- are denied
                permit(2)   -- frames matching the filter criteria
                            -- are permitted
            }
    ACCESS  read-only
    STATUS  mandatory
    DESCRIPTION
            "For the incoming filter table, determines whether
            the entries are permit or deny entries."
    ::= { ibmwindowFilterInfoEntry 4 }

ibmwindowFilterOutFilterType OBJECT-TYPE
    SYNTAX  INTEGER {
                deny(1),    -- frames matching the filter criteria
                            -- are denied
                permit(2)   -- frames matching the filter criteria
                            -- are permitted
            }
    ACCESS  read-only
    STATUS  mandatory
    DESCRIPTION
            "For the outgoing filter table, determines whether
            the entries are permit or deny entries."
    ::= { ibmwindowFilterInfoEntry 5 }

ibmwindowFilterInNotForwarded OBJECT-TYPE
    SYNTAX  Counter
    ACCESS  read-only
    STATUS  mandatory
    DESCRIPTION
            "Number of packets not forwarded, in the incoming
            direction, because they were filtered out."
    ::= { ibmwindowFilterInfoEntry 6 }

ibmwindowFilterOutNotForwarded OBJECT-TYPE
    SYNTAX  Counter
    ACCESS  read-only
    STATUS  mandatory
    DESCRIPTION
            "Number of packets not forwarded, in the outgoing
            direction, because they were filtered out."
    ::= { ibmwindowFilterInfoEntry 7 }

ibmwindowFilterType OBJECT-TYPE
    SYNTAX     INTEGER {
                sr(1),   --  sr filter
                tb(2)   --  tb filter
            }
    ACCESS  read-only
    STATUS  mandatory
    DESCRIPTION
            "The type of entry, either sr or tb."
    ::= { ibmwindowFilterInfoEntry 8 }

--
-- The Incoming Window Filter Table
--

ibmwindowFilterInTable OBJECT-TYPE
    SYNTAX  SEQUENCE OF WindowFilterInEntry
    ACCESS  not-accessible
    STATUS  mandatory
    DESCRIPTION
            "Table of Window filtering information
            for incoming frames."
    ::= { ibmbridgeWindowFilters 2 }

ibmwindowFilterInEntry OBJECT-TYPE
    SYNTAX  WindowFilterInEntry
    ACCESS  not-accessible
    STATUS  mandatory
    DESCRIPTION
            "Filtering information for incoming frames."
    INDEX   { ibmwindowFilterInType, ibmwindowFilterInIfIndex,  ibmwindowFilterInId, ibmwindowFilterInContents }
    ::= { ibmwindowFilterInTable 1 }

WindowFilterInEntry ::=
    SEQUENCE {
        ibmwindowFilterInIfIndex
            INTEGER,
        ibmwindowFilterInContents
            OCTET STRING,
        ibmwindowFilterInMaskString
            OCTET STRING,
        ibmwindowFilterInOffsetStart
            DisplayString,
        ibmwindowFilterInNumBytes
            OCTET STRING,
        ibmwindowFilterInOffset
            OCTET STRING,
        ibmwindowFilterInId
            INTEGER,
        ibmwindowFilterInType
            INTEGER
    }

ibmwindowFilterInIfIndex OBJECT-TYPE
    SYNTAX  INTEGER
    ACCESS  read-only
    STATUS  mandatory
    DESCRIPTION
            "The value of this object identifies the interface for which
            this entry contains management information.  The value of
            this object for a particular interface has the same value
            as the ifIndex object for the same interface."
    ::= { ibmwindowFilterInEntry 1 }

ibmwindowFilterInContents OBJECT-TYPE
    SYNTAX  OCTET STRING
    ACCESS  read-only
    STATUS  mandatory
    DESCRIPTION
            "String of bytes that will be compared with bytes in the
             frame. "
    ::= { ibmwindowFilterInEntry 2 }

ibmwindowFilterInMaskString OBJECT-TYPE
    SYNTAX  OCTET STRING
    ACCESS  read-only
    STATUS  mandatory
    DESCRIPTION
            "String of bytes that will be masked with bytes in the
             contents field."
    ::= { ibmwindowFilterInEntry 3 }

ibmwindowFilterInOffsetStart OBJECT-TYPE
    SYNTAX  DisplayString
    ACCESS  read-only
    STATUS  mandatory
    DESCRIPTION
            "Determines the starting point where the contents field should be
            applied. A value of 'MAC' means the base is at the beginning of
            the destination MAC address field, whereas, a value of 'SAP' means
            it is applied at the beginning of the destination SAP field."
    ::= { ibmwindowFilterInEntry 4 }

ibmwindowFilterInNumBytes OBJECT-TYPE
    SYNTAX  OCTET STRING (SIZE(1))
    ACCESS  read-only
    STATUS  mandatory
    DESCRIPTION
            "Number of bytes in the contents field that are used
             for filtering. "
    ::= { ibmwindowFilterInEntry 5 }

ibmwindowFilterInOffset  OBJECT-TYPE
    SYNTAX  OCTET STRING (SIZE(2))
    ACCESS  read-only
    STATUS  mandatory
    DESCRIPTION
            "Number of bytes offset into the frame from the offset start point
             to begin the compare."
    ::= { ibmwindowFilterInEntry 6 }

ibmwindowFilterInId OBJECT-TYPE
    SYNTAX  INTEGER
    ACCESS  read-only
    STATUS  mandatory
    DESCRIPTION
            "A unique identifier associated with this window filter
            entry."
    ::= { ibmwindowFilterInEntry 7 }

ibmwindowFilterInType OBJECT-TYPE
    SYNTAX     INTEGER {
                sr(1),   --  sr filter
                tb(2)   --  tb filter
            }
    ACCESS  read-only
    STATUS  mandatory
    DESCRIPTION
            "The type of entry, either sr or tb."
    ::= { ibmwindowFilterInEntry 8 }


--
-- The Outgoing Window Filter Table
--

ibmwindowFilterOutTable OBJECT-TYPE
    SYNTAX  SEQUENCE OF WindowFilterOutEntry
    ACCESS  not-accessible
    STATUS  mandatory
    DESCRIPTION
            "Table of Window filtering information
            for outgoing frames."
    ::= { ibmbridgeWindowFilters 3 }

ibmwindowFilterOutEntry OBJECT-TYPE
    SYNTAX  WindowFilterOutEntry
    ACCESS  not-accessible
    STATUS  mandatory
    DESCRIPTION
            "Filtering information for outgoing frames."
    INDEX   { ibmwindowFilterOutType, ibmwindowFilterOutIfIndex,  ibmwindowFilterOutId, ibmwindowFilterOutContents }
    ::= { ibmwindowFilterOutTable 1 }

WindowFilterOutEntry ::=
    SEQUENCE {
        ibmwindowFilterOutIfIndex
            INTEGER,
        ibmwindowFilterOutContents
            OCTET STRING,
        ibmwindowFilterOutMaskString
            OCTET STRING,
        ibmwindowFilterOutOffsetStart
            DisplayString,
        ibmwindowFilterOutNumBytes
            OCTET STRING,
        ibmwindowFilterOutOffset
            OCTET STRING,
        ibmwindowFilterOutId
            INTEGER,
        ibmwindowFilterOutType
            INTEGER
    }

ibmwindowFilterOutIfIndex OBJECT-TYPE
    SYNTAX  INTEGER
    ACCESS  read-only
    STATUS  mandatory
    DESCRIPTION
            "The value of this object identifies the interface for which
            this entry contains management information.  The value of
            this object for a particular interface has the same value
            as the ifIndex object for the same interface."
    ::= { ibmwindowFilterOutEntry 1 }

ibmwindowFilterOutContents OBJECT-TYPE
    SYNTAX  OCTET STRING
    ACCESS  read-only
    STATUS  mandatory
    DESCRIPTION
            "String of bytes that will be compared with bytes in the
             frame. "
    ::= { ibmwindowFilterOutEntry 2 }

ibmwindowFilterOutMaskString OBJECT-TYPE
    SYNTAX  OCTET STRING
    ACCESS  read-only
    STATUS  mandatory
    DESCRIPTION
            "String of bytes that will be masked with bytes in the
             contents field. "
    ::= { ibmwindowFilterOutEntry 3 }

ibmwindowFilterOutOffsetStart OBJECT-TYPE
    SYNTAX  DisplayString
    ACCESS  read-only
    STATUS  mandatory
    DESCRIPTION
            "Determines the starting point where the contents field should be
            applied. A value of 'MAC' means the base is at the beginning of
            the destination MAC address field, whereas, a value of 'SAP' means
            it is applied at the beginning of the destination SAP field."
    ::= { ibmwindowFilterOutEntry 4 }

ibmwindowFilterOutNumBytes OBJECT-TYPE
    SYNTAX  OCTET STRING (SIZE(1))
    ACCESS  read-only
    STATUS  mandatory
    DESCRIPTION
            "Number of bytes in the contents field that are used
             for filtering. "
    ::= { ibmwindowFilterOutEntry 5 }

ibmwindowFilterOutOffset  OBJECT-TYPE
    SYNTAX  OCTET STRING (SIZE(2))
    ACCESS  read-only
    STATUS  mandatory
    DESCRIPTION
            "Number of bytes offset into the frame from the offset start point
             to begin the compare."
    ::= { ibmwindowFilterOutEntry 6 }

ibmwindowFilterOutId OBJECT-TYPE
    SYNTAX  INTEGER
    ACCESS  read-only
    STATUS  mandatory
    DESCRIPTION
            "A unique identifier associated with this window filter
            entry."
    ::= { ibmwindowFilterOutEntry 7 }

ibmwindowFilterOutType OBJECT-TYPE
    SYNTAX     INTEGER {
                sr(1),   --  sr filter
                tb(2)   --  tb filter
            }
    ACCESS  read-only
    STATUS  mandatory
    DESCRIPTION
            "The type of entry, either sr or tb."
    ::= { ibmwindowFilterOutEntry 8 }


--
-- The Incoming Filter Order Table
--

ibmFiltOrderInTable OBJECT-TYPE
    SYNTAX  SEQUENCE OF FiltOrderInEntry
    ACCESS  not-accessible
    STATUS  mandatory
    DESCRIPTION
            "Table of information describing which order
            the filters are applied for incoming frames."
    ::= { ibmbridgeFiltOrderTable 1 }

ibmFiltOrderInEntry OBJECT-TYPE
    SYNTAX  FiltOrderInEntry
    ACCESS  not-accessible
    STATUS  mandatory
    DESCRIPTION
            "Filter order information for incoming frames."
    INDEX   { ibmFiltOrderInType, ibmFiltOrderInIfIndex, ibmFiltOrderInPriority }
    ::= { ibmFiltOrderInTable 1 }

FiltOrderInEntry ::=
    SEQUENCE {
        ibmFiltOrderInIfIndex
            INTEGER,
        ibmFiltOrderInPriority
            INTEGER,
        ibmFiltOrderInName
            DisplayString,
        ibmFiltOrderInType
            INTEGER
    }

ibmFiltOrderInIfIndex OBJECT-TYPE
    SYNTAX  INTEGER
    ACCESS  read-only
    STATUS  mandatory
    DESCRIPTION
            "The value of this object identifies the interface for which
            this entry contains management information.  The value of
            this object for a particular interface has the same value
            as the ifIndex object for the same interface."
    ::= { ibmFiltOrderInEntry 1 }

ibmFiltOrderInPriority OBJECT-TYPE
    SYNTAX  INTEGER
    ACCESS  read-only
    STATUS  mandatory
    DESCRIPTION
            "The priority of when a filter is applied to an incoming
            frame. A value of 1 signifies that it is applied first."
    ::= { ibmFiltOrderInEntry 2 }

ibmFiltOrderInName OBJECT-TYPE
    SYNTAX  DisplayString
    ACCESS  read-only
    STATUS  mandatory
    DESCRIPTION
            "The name of the filter applied to incoming frames
            that is associated with the priority, ibmFiltOrderInPriority."
    ::= { ibmFiltOrderInEntry 3 }

ibmFiltOrderInType  OBJECT-TYPE
    SYNTAX     INTEGER {
                sr(1),   --  sr filter
                tb(2)   --  tb filter
            }
    ACCESS  read-only
    STATUS  mandatory
    DESCRIPTION
            "The type of entry, either sr or tb."
    ::= { ibmFiltOrderInEntry 4 }


--
-- The Outgoing Filter Order Table
--

ibmFiltOrderOutTable OBJECT-TYPE
    SYNTAX  SEQUENCE OF FiltOrderOutEntry
    ACCESS  not-accessible
    STATUS  mandatory
    DESCRIPTION
            "Table of information describing which order
            the filters are applied for outgoing frames."
    ::= { ibmbridgeFiltOrderTable 2 }

ibmFiltOrderOutEntry OBJECT-TYPE
    SYNTAX  FiltOrderOutEntry
    ACCESS  not-accessible
    STATUS  mandatory
    DESCRIPTION
            "Filter order information for outgoing frames."
    INDEX   { ibmFiltOrderOutType, ibmFiltOrderOutIfIndex, ibmFiltOrderOutPriority }
    ::= { ibmFiltOrderOutTable 1 }

FiltOrderOutEntry ::=
    SEQUENCE {
        ibmFiltOrderOutIfIndex
            INTEGER,
        ibmFiltOrderOutPriority
            INTEGER,
        ibmFiltOrderOutName
            DisplayString,
        ibmFiltOrderOutType
            INTEGER
    }

ibmFiltOrderOutIfIndex OBJECT-TYPE
    SYNTAX  INTEGER
    ACCESS  read-only
    STATUS  mandatory
    DESCRIPTION
            "The value of this object identifies the interface for which
            this entry contains management information.  The value of
            this object for a particular interface has the same value
            as the ifIndex object for the same interface."
    ::= { ibmFiltOrderOutEntry 1 }

ibmFiltOrderOutPriority OBJECT-TYPE
    SYNTAX  INTEGER
    ACCESS  read-only
    STATUS  mandatory
    DESCRIPTION
            "The priority of when a filter is applied to an outgoing
            frame. A value of 1 signifies that it is applied first."
    ::= { ibmFiltOrderOutEntry 2 }

ibmFiltOrderOutName OBJECT-TYPE
    SYNTAX  DisplayString
    ACCESS  read-only
    STATUS  mandatory
    DESCRIPTION
            "The name of the filter applied to outgoing frames
            that is associated with the priority, ibmFiltOrderOutPriority."
    ::= { ibmFiltOrderOutEntry 3 }

ibmFiltOrderOutType OBJECT-TYPE
    SYNTAX     INTEGER {
                sr(1),   --  sr filter
                tb(2)   --  tb filter
            }
    ACCESS  read-only
    STATUS  mandatory
    DESCRIPTION
            "The type of entry, either sr or tb."
    ::= { ibmFiltOrderOutEntry 4 }


--
-- The Routing Information Field Filter Information Table
--
-- This new MIB mirrors an enhancement to the capabilities of the Source Route bridge
-- filters to now allow filtering on the ring number AND bridge number of the
-- routing information field.
--

ibmRIFFilterInfoTable OBJECT-TYPE
    SYNTAX  SEQUENCE OF RIFFilterInfoEntry
    ACCESS  not-accessible
    STATUS  mandatory
    DESCRIPTION
            "Table of routing information field filtering information."
    ::= { ibmbridgeRIFFilters 1 }

ibmRIFFilterInfoEntry OBJECT-TYPE
    SYNTAX  RIFFilterInfoEntry
    ACCESS  not-accessible
    STATUS  mandatory
    DESCRIPTION
            "Routing information field filtering information for a single interface."
    INDEX   { ibmRIFFilterIfIndex }
    ::= { ibmRIFFilterInfoTable 1 }

RIFFilterInfoEntry ::=
    SEQUENCE {
        ibmRIFFilterIfIndex
            INTEGER,
        ibmRIFFilterInBcastType
            INETGER,
        ibmRIFFilterOutBcastType
            INTEGER,
        ibmRIFFilterInFilterType
            INTEGER,
        ibmRIFFilterOutFilterType
            INTEGER,
        ibmRIFFilterInNotForwarded
            Counter,
        ibmRIFFilterOutNotForwarded
            Counter
    }

ibmRIFFilterIfIndex OBJECT-TYPE
    SYNTAX  INTEGER
    ACCESS  read-only
    STATUS  mandatory
    DESCRIPTION
            "The value of this object identifies the interface for which
            this entry contains management information.  The value of
            this object for a particular interface has the same value
            as the ifIndex object for the same interface."
    ::= { ibmRIFFilterInfoEntry 1 }

ibmRIFFilterInBcastType OBJECT-TYPE
    SYNTAX  INTEGER {
               filterARB(1),
               filterSRB(2),
               filterBoth(3)
            }
    ACCESS  read-only
    STATUS  mandatory
    DESCRIPTION
            "For the incoming routing information field filter table, determines
            what type of frames will be filtered."
    ::= { ibmRIFFilterInfoEntry 2 }

ibmRIFFilterOutBcastType OBJECT-TYPE
    SYNTAX  INTEGER {
               filterARB(1),
               filterSRB(2),
               filterBoth(3)
            }
    ACCESS  read-only
    STATUS  mandatory
    DESCRIPTION
            "For the outgoing routing information field filter table, determines
            what type of frames will be filtered."
    ::= { ibmRIFFilterInfoEntry 3 }

ibmRIFFilterInFilterType OBJECT-TYPE
    SYNTAX  INTEGER {
                deny(1),
                permit(2)
            }
    ACCESS  read-only
    STATUS  mandatory
    DESCRIPTION
            "For the incoming routing information filter table, determines whether
            the entries are permit or deny entries."
    ::= { ibmRIFFilterInfoEntry 4 }

ibmRIFFilterOutFilterType OBJECT-TYPE
    SYNTAX  INTEGER {
                deny(1),
                permit(2)
            }
    ACCESS  read-only
    STATUS  mandatory
    DESCRIPTION
            "For the outgoing routing information field filter table, determines whether
            the entries are permit or deny entries."
    ::= { ibmRIFFilterInfoEntry 5 }

ibmRIFFilterInNotForwarded OBJECT-TYPE
    SYNTAX  Counter
    ACCESS  read-only
    STATUS  mandatory
    DESCRIPTION
            "Number of packets not forwarded, in the incoming
            direction, because they were filtered out."
    ::= { ibmRIFFilterInfoEntry 6 }

ibmRIFFilterOutNotForwarded OBJECT-TYPE
    SYNTAX  Counter
    ACCESS  read-only
    STATUS  mandatory
    DESCRIPTION
            "Number of packets not forwarded, in the outgoing
            direction, because they were filtered out."
    ::= { ibmRIFFilterInfoEntry 7 }


--
-- The Incoming Routing Information Field Filter Table
--
-- This new MIB mirrors an enhancement to the capabilities of the Source Route bridge
-- filters to now allow filtering on the ring number AND bridge number of the
-- routing information field.
--

ibmRIFFilterInTable OBJECT-TYPE
    SYNTAX  SEQUENCE OF RIFFilterInEntry
    ACCESS  not-accessible
    STATUS  mandatory
    DESCRIPTION
            "Table of routing information field filtering information
            for incoming frames."
    ::= { ibmbridgeRIFFilters 2 }

ibmRIFFilterInEntry OBJECT-TYPE
    SYNTAX  RIFFilterInEntry
    ACCESS  not-accessible
    STATUS  mandatory
    DESCRIPTION
            "Filtering information for a single routing information
            field on a single interface."
    INDEX   { ibmRIFFilterInIfIndex,  ibmRIFFilterInRingNumber, ibmRIFFilterInBridgeNumber }
    ::= { ibmRIFFilterInTable 1 }

RIFFilterInEntry ::=
    SEQUENCE {
        ibmRIFFilterInIfIndex
            INTEGER,
        ibmRIFFilterInRingNumber
            INTEGER,
        ibmRIFFilterInRingMask
            INTEGER,
        ibmRIFFilterInBridgeNumber
            INTEGER,
        ibmRIFFilterInBridgeMask
            INTEGER,
        ibmRIFFilterInRouteDesignator
            INTEGER
    }

ibmRIFFilterInIfIndex OBJECT-TYPE
    SYNTAX  INTEGER
    ACCESS  read-only
    STATUS  mandatory
    DESCRIPTION
            "The value of this object identifies the interface for which
            this entry contains management information.  The value of
            this object for a particular interface has the same value
            as the ifIndex object for the same interface."
    ::= { ibmRIFFilterInEntry 1 }

ibmRIFFilterInRingNumber OBJECT-TYPE
    SYNTAX  INTEGER
    ACCESS  read-only
    STATUS  mandatory
    DESCRIPTION
            "Indicates which ring number to filter."
    ::= { ibmRIFFilterInEntry 2 }

ibmRIFFilterInRingMask OBJECT-TYPE
    SYNTAX  INTEGER
    ACCESS  read-only
    STATUS  mandatory
    DESCRIPTION
            "Mask to allow ibmRIFFilterInRingNumber to be used as a
            range of values."
    ::= { ibmRIFFilterInEntry 3 }

ibmRIFFilterInBridgeNumber OBJECT-TYPE
    SYNTAX  INTEGER
    ACCESS  read-only
    STATUS  mandatory
    DESCRIPTION
            "Indicates which bridge number to filter."
    ::= { ibmRIFFilterInEntry 4 }

ibmRIFFilterInBridgeMask OBJECT-TYPE
    SYNTAX  INTEGER
    ACCESS  read-only
    STATUS  mandatory
    DESCRIPTION
            "Mask to allow ibmRIFFilterInBridgeNumber to be used as a
            range of values."
    ::= { ibmRIFFilterInEntry 5 }

ibmRIFFilterInRouteDesignator OBJECT-TYPE
    SYNTAX  INTEGER {
                firstroutedesignator(1),
                nexttolastroutedesignator(2),
                allroutedesignators(3)
            }
    ACCESS  read-only
    STATUS  mandatory
    DESCRIPTION
            "Indicates which route designators in the routing information
            field are to be used for filtering."
    ::= { ibmRIFFilterInEntry 6 }


--
-- The Outgoing RIF Number Filter Table
--
-- This new MIB mirrors an enhancement to the capabilities of the Source Route bridge
-- filters to now allow filtering on the ring number AND bridge number of the
-- routing information field.
--

ibmRIFFilterOutTable OBJECT-TYPE
    SYNTAX  SEQUENCE OF RIFFilterOutEntry
    ACCESS  not-accessible
    STATUS  mandatory
    DESCRIPTION
            "Table of routing information field filtering information
            for outgoing frames."
    ::= { ibmbridgeRIFFilters 3 }

ibmRIFFilterOutEntry OBJECT-TYPE
    SYNTAX  RIFFilterOutEntry
    ACCESS  not-accessible
    STATUS  mandatory
    DESCRIPTION
            "Filtering information for a single routing information
            field on a single interface."
    INDEX   { ibmRIFFilterOutIfIndex,  ibmRIFFilterOutRingNumber, ibmRIFFilterOutBridgeNumber }
    ::= { ibmRIFFilterOutTable 1 }

RIFFilterOutEntry ::=
    SEQUENCE {
        ibmRIFFilterOutIfIndex
            INTEGER,
        ibmRIFFilterOutRingNumber
            INTEGER,
        ibmRIFFilterOutRingMask
            INTEGER,
        ibmRIFFilterOutBridgeNumber
            INTEGER,
        ibmRIFFilterOutBridgeMask
            INTEGER,
        ibmRIFFilterOutRouteDesignator
            INTEGER
    }

ibmRIFFilterOutIfIndex OBJECT-TYPE
    SYNTAX  INTEGER
    ACCESS  read-only
    STATUS  mandatory
    DESCRIPTION
            "The value of this object identifies the interface for which
            this entry contains management information.  The value of
            this object for a particular interface has the same value
            as the ifIndex object for the same interface."
    ::= { ibmRIFFilterOutEntry 1 }

ibmRIFFilterOutRingNumber OBJECT-TYPE
    SYNTAX  INTEGER
    ACCESS  read-only
    STATUS  mandatory
    DESCRIPTION
            "Indicates which ring number to filter."
    ::= { ibmRIFFilterOutEntry 2 }

ibmRIFFilterOutRingMask OBJECT-TYPE
    SYNTAX  INTEGER
    ACCESS  read-only
    STATUS  mandatory
    DESCRIPTION
            "Mask to allow ibmRIFFilterOutRingNumber to be used as a
            range of values."
    ::= { ibmRIFFilterOutEntry 3 }

ibmRIFFilterOutBridgeNumber OBJECT-TYPE
    SYNTAX  INTEGER
    ACCESS  read-only
    STATUS  mandatory
    DESCRIPTION
            "Indicates which bridge number to filter."
    ::= { ibmRIFFilterOutEntry 4 }

ibmRIFFilterOutBridgeMask OBJECT-TYPE
    SYNTAX  INTEGER
    ACCESS  read-only
    STATUS  mandatory
    DESCRIPTION
            "Mask to allow ibmRIFFilterOutBridgeNumber to be used as a
            range of values."
    ::= { ibmRIFFilterOutEntry 5 }

ibmRIFFilterOutRouteDesignator OBJECT-TYPE
    SYNTAX  INTEGER {
                firstroutedesignator(1),
                nexttolastroutedesignator(2),
                allroutedesignators(3)
            }
    ACCESS  read-only
    STATUS  mandatory
    DESCRIPTION
            "Indicates which route designators in the routing information
            field are to be used for filtering."
    ::= { ibmRIFFilterOutEntry 6 }


-- static char sccsid_framerelay_mib[] = "@(#) snmp/samples/fr.my, SNMP, v1r3, r3d48  3/14/94 17:36:13";

------------------------------------------------------------------------
-- The Frame Relay Extension                                           -
------------------------------------------------------------------------
-- (Based on Internet draft dated December 5, 1991)


--  This MIB module uses the extended OBJECT-TYPE macro as
--  defined in RFC 1212, and the TRAP-TYPE macro as defined in RFC 1215.

--
--      the range of ifIndex
--
--Index ::= INTEGER       ## 1..ifNumber

--
--      the range of a Data Link Connection Identifier
--
--DLCI ::= INTEGER        ## 0..DLCINumber


--  Data Link Connection Management Interface

--      The variables that configure the DLC Management Interface.

ibmfrDlcmiTable OBJECT-TYPE
    SYNTAX   SEQUENCE OF IbmfrDlcmiEntry
    ACCESS   not-accessible
    STATUS   mandatory
    DESCRIPTION
       "The Parameters for the Data Link Connection Management
       Interface corresponding to any given ifEntry."
    REFERENCE
       "Draft American National Standard T1.617-1991, Annex D"
    ::= { ibmfr 1 }

    ibmfrDlcmiEntry OBJECT-TYPE
        SYNTAX   IbmfrDlcmiEntry
        ACCESS   not-accessible
        STATUS   mandatory
        DESCRIPTION
           "The Parameters for the  Data  Link  Connection
           Management Interface."
       INDEX { ibmfrDlcmiIfIndex }
       ::= { ibmfrDlcmiTable 1 }

    IbmfrDlcmiEntry ::=
        SEQUENCE {
            ibmfrDlcmiIfIndex
                INTEGER,
            ibmfrDlcmiState
                INTEGER,
            ibmfrDlcmiAddress
                INTEGER,
            ibmfrDlcmiAddressLen
                INTEGER,
            ibmfrDlcmiPollingInterval
                INTEGER,
            ibmfrDlcmiFullEnquiryInterval
                INTEGER,
            ibmfrDlcmiErrorThreshold
                INTEGER,
            ibmfrDlcmiMonitoredEvents
                INTEGER,
            ibmfrDlcmiMaxSupportedVCs
                INTEGER,
            ibmfrDlcmiMulticast
                INTEGER
    }

    ibmfrDlcmiIfIndex OBJECT-TYPE
        SYNTAX   INTEGER       -- 1..ifNumber
        ACCESS   read-only
        STATUS   mandatory
        DESCRIPTION
           "The ifIndex value of the  corresponding  ifEn-
           try."
       ::= { ibmfrDlcmiEntry 1 }

    ibmfrDlcmiState OBJECT-TYPE
        SYNTAX INTEGER {
            noLmiConfigured(1),
            lmiRev1(2),
            ansiT1-617-D(3),    -- ANSI T1.617 Annex D
            ansiT1-617-B(4)     -- ANSI T1.617 Annex B
        }
        ACCESS   read-only
        STATUS   mandatory
        DESCRIPTION
           "This variable states which Data  Link  Connec-
           tion Management scheme is active (and by impli-
           cation, what DLCI it uses) on the  Frame  Relay
           interface."
       REFERENCE
          "Draft American National Standard T1.617-1991"
      ::= { ibmfrDlcmiEntry 2 }

    ibmfrDlcmiAddress OBJECT-TYPE
        SYNTAX      INTEGER {
                    q921(1),            -- 13 bit DLCI
                    q922March90(2),     -- 11 bit DLCI
                    q922November90(3),  -- 10 bit DLCI
                    q922(4)             -- Final Standard
        }
        ACCESS  read-only
        STATUS  mandatory
        DESCRIPTION
           "This variable states which address  format  is
           in use on the Frame Relay interface."
       ::= { ibmfrDlcmiEntry 3 }

    ibmfrDlcmiAddressLen OBJECT-TYPE
        SYNTAX  INTEGER {
                two-octets(2),
                three-octets(3),
                four-octets(4)
        }
        ACCESS  read-only
        STATUS  mandatory
        DESCRIPTION
           "This variable states which address  length  in
           octets.  In the case of Q922 format, the length
           indicates the entire length of the address  in-
           cluding the control portion."
       ::= { ibmfrDlcmiEntry 4 }

    ibmfrDlcmiPollingInterval OBJECT-TYPE
        SYNTAX   INTEGER (5..30)
        ACCESS   read-only
        STATUS   mandatory
        DESCRIPTION
           "This is the number of seconds between  succes-
           sive status enquiry messages."
       REFERENCE
          "Draft American National  Standard  T1.617-1991,
          Section D.7 Timer T391."
      DEFVAL { 10 }
      ::= { ibmfrDlcmiEntry 5 }

    ibmfrDlcmiFullEnquiryInterval OBJECT-TYPE
        SYNTAX   INTEGER (1..255)
        ACCESS   read-only
        STATUS   mandatory
        DESCRIPTION
           "Number of status enquiry intervals  that  pass
           before  issuance  of a full status enquiry mes-
           sage."
       REFERENCE
          "Draft American National  Standard  T1.617-1991,
          Section D.7 Counter N391."
      DEFVAL { 6 }
      ::= { ibmfrDlcmiEntry 6 }

    ibmfrDlcmiErrorThreshold OBJECT-TYPE
        SYNTAX   INTEGER (1..10)
        ACCESS   read-only
        STATUS   mandatory
        DESCRIPTION
           "This  is  the  maximum  number  of  unanswered
           Status Enquiries the equipment shall accept be-
           fore declaring the interface down."
       REFERENCE
          "Draft American National  Standard  T1.617-1991,
          Section D.5.1 Counter N392."
      DEFVAL { 3 }
      ::= { ibmfrDlcmiEntry 7 }

    ibmfrDlcmiMonitoredEvents OBJECT-TYPE
        SYNTAX   INTEGER (1..10)
        ACCESS   read-only
        STATUS   mandatory
        DESCRIPTION
           "This is the maximum  number  of  responses  to
           FULL  STATUS  or  LINK  INTEGERITY VERIFICATION
           messages missed before the device will mark the
           interface down."
       REFERENCE
          "Draft American National  Standard  T1.617-1991,
          Section D.5.2 Counter T393."
      DEFVAL { 4 }
      ::= { ibmfrDlcmiEntry 8 }

    ibmfrDlcmiMaxSupportedVCs OBJECT-TYPE
        SYNTAX   INTEGER
        ACCESS   read-only
        STATUS   mandatory
        DESCRIPTION
           "The maximum number of Virtual Circuits allowed
           for  this  interface.   Usually dictated by the
           Frame Relay network.

           In response to a SET, if a value less than zero
           or  higher  than the agent's maximal capability
           is configured, the agent  should  respond  bad-
           Value"
       ::= { ibmfrDlcmiEntry 9 }

    ibmfrDlcmiMulticast OBJECT-TYPE
        SYNTAX   INTEGER {
                    nonBroadcast(1),
                    broadcast(2)
                    }
        ACCESS   read-only
        STATUS   mandatory
        DESCRIPTION
           "This indicates whether the Frame Relay provid-
           er offers a Multicast Service."
       ::= { ibmfrDlcmiEntry 10 }


-- A Frame Relay service is a multiplexing service.  Data
-- Link Connection Identifiers enumerate virtual circuits
-- (permanent or dynamic) which are layered onto the underlying
-- circuit.  Therefore, it is to be expected that a few
-- interfaces (ifEntries) will each support a number of DLCs.

--   Circuit Table

-- The table describing the use of the DLCIs attached to
-- each Frame Relay Interface.

ibmfrCircuitTable OBJECT-TYPE
    SYNTAX   SEQUENCE OF IbmfrCircuitEntry
    ACCESS   not-accessible
    STATUS   mandatory
    DESCRIPTION
       "A table containing information about specific Data
       Link Connection Identifiers and corresponding virtual
       circuits."
    ::= { ibmfr 2 }

    ibmfrCircuitEntry OBJECT-TYPE
        SYNTAX   IbmfrCircuitEntry
        ACCESS   not-accessible
        STATUS   mandatory
        DESCRIPTION
           "The information regarding a single  Data  Link
           Connection Identifier."
       INDEX { ibmfrCircuitIfIndex, ibmfrCircuitDlci }
       ::= { ibmfrCircuitTable 1 }

    IbmfrCircuitEntry ::=
        SEQUENCE {
            ibmfrCircuitIfIndex
                INTEGER,
            ibmfrCircuitDlci
                INTEGER,
            ibmfrCircuitState
                INTEGER,
            ibmfrCircuitReceivedFECNs
                Counter,
            ibmfrCircuitReceivedBECNs
                Counter,
            ibmfrCircuitSentFrames
                Counter,
            ibmfrCircuitSentOctets
                Counter,
            ibmfrCircuitReceivedFrames
                Counter,
            ibmfrCircuitReceivedOctets
                Counter,
            ibmfrCircuitCreationTime
                TimeTicks,
            ibmfrCircuitLastTimeChange
                TimeTicks,
            ibmfrCircuitCommittedBurst
                INTEGER,
            ibmfrCircuitExcessBurst
                INTEGER,
            ibmfrCircuitThroughput
                INTEGER
    }

    ibmfrCircuitIfIndex OBJECT-TYPE
        SYNTAX   INTEGER       -- 1..ifNumber
        ACCESS   read-only
        STATUS   mandatory
        DESCRIPTION
           "The ifIndex Value of the ifEntry this  virtual
           circuit is layered onto."
       ::= { ibmfrCircuitEntry 1 }

    ibmfrCircuitDlci OBJECT-TYPE
        SYNTAX   INTEGER
        ACCESS   read-only
        STATUS   mandatory
        DESCRIPTION
           "The Data Link Connection Identifier  for  this
           virtual circuit."
       REFERENCE
          "Draft American National  Standard  T1.618-1991,
          Section 3.3.6"
      ::= { ibmfrCircuitEntry 2 }

    ibmfrCircuitState OBJECT-TYPE
        SYNTAX   INTEGER {
                    invalid(1),
                    active(2),
                    inactive(3)
                 }
        ACCESS   read-only
        STATUS   mandatory
        DESCRIPTION
           "Indicates whether the particular virtual  cir-
           cuit  is operational.  In the absence of a Data
           Link Connection Management  Interface,  virtual
           circuit  entries  (rows) may be created by set-
           ting virtual circuit state to active, or delet-
           ed   by  changing  Circuit  state  to  deleted.
           Whether or not the row actually  disappears  is
           let  to  the implementation, so this object may
           actually read as 'invalid' for  some  arbitrary
           length  of  time.   It is also legal to set the
           state of a virtual circuit to inactive to  tem-
           porarily disable a given circuit."
       DEFVAL { active }
       ::= { ibmfrCircuitEntry 3 }

    ibmfrCircuitReceivedFECNs OBJECT-TYPE
        SYNTAX   Counter
        ACCESS   read-only
        STATUS   mandatory
        DESCRIPTION
           "Number of frames received from the network in-
           dicating  forward  congestion since the virtual
           circuit was created."
       REFERENCE
          "Draft American National  Standard  T1.618-1991,
          Section 3.3.3"
      ::= { ibmfrCircuitEntry 4 }

    ibmfrCircuitReceivedBECNs OBJECT-TYPE
        SYNTAX   Counter
        ACCESS   read-only
        STATUS   mandatory
        DESCRIPTION
           "Number of frames received from the network in-
           dicating  backward congestion since the virtual
           circuit was created."
       REFERENCE
          "Draft American National  Standard  T1.618-1991,
          Section 3.3.4"
      ::= { ibmfrCircuitEntry 5 }

    ibmfrCircuitSentFrames OBJECT-TYPE
        SYNTAX   Counter
        ACCESS   read-only
        STATUS   mandatory
        DESCRIPTION
           "The number of frames sent  from  this  virtual
           circuit since it was created."
       ::= { ibmfrCircuitEntry 6 }

    ibmfrCircuitSentOctets OBJECT-TYPE
        SYNTAX   Counter
        ACCESS   read-only
        STATUS   mandatory
        DESCRIPTION
           "The number of octets sent  from  this  virtual
           circuit since it was created."
       ::= { ibmfrCircuitEntry 7 }

    ibmfrCircuitReceivedFrames OBJECT-TYPE
        SYNTAX   Counter
        ACCESS   read-only
        STATUS   mandatory
        DESCRIPTION
           "Number of frames received  over  this  virtual
           circuit since it was created."
       ::= { ibmfrCircuitEntry 8 }

    ibmfrCircuitReceivedOctets OBJECT-TYPE
        SYNTAX   Counter
        ACCESS   read-only
        STATUS   mandatory
        DESCRIPTION
           "Number of octets received  over  this  virtual
           circuit since it was created."
       ::= { ibmfrCircuitEntry 9 }

    ibmfrCircuitCreationTime OBJECT-TYPE
        SYNTAX   TimeTicks
        ACCESS   read-only
        STATUS   mandatory
        DESCRIPTION
           "The time when this virtual circuit
           was created, whether by the Data Link Connection
           Management Interface or by a SetRequest.
           The time value is relative to other
           times on this interface only."
       ::= { ibmfrCircuitEntry 10 }

    ibmfrCircuitLastTimeChange OBJECT-TYPE
        SYNTAX   TimeTicks
        ACCESS   read-only
        STATUS   mandatory
        DESCRIPTION
           "The time when last there was a
           change in the virtual circuit state.
           The time value is relative to other
           times on this interface only."
       ::= { ibmfrCircuitEntry 11 }

    ibmfrCircuitCommittedBurst OBJECT-TYPE
        SYNTAX   INTEGER
        ACCESS   read-only
        STATUS   mandatory
        DESCRIPTION
           "This variable indicates the maximum amount  of
           data,  in  bits,  that  the  network  agrees to
           transfer under normal  conditions,  during  the
           measurement interval."
       REFERENCE
          "Draft American National  Standard  T1.617-1991,
          Section 6.5.19"
      DEFVAL   { 0 }  -- the default indicates no commitment
      ::= { ibmfrCircuitEntry 12 }

    ibmfrCircuitExcessBurst OBJECT-TYPE
        SYNTAX   INTEGER
        ACCESS   read-only
        STATUS   mandatory
        DESCRIPTION
           "This variable indicates the maximum amount  of
           uncommitted data bits that the network will at-
           tempt to deliver over the measurement interval.

           By default, if not configured when creating the
           entry, the Excess Information Burst Size is set
           to the value of ifSpeed."
       REFERENCE
          "Draft American National  Standard  T1.617-1991,
          Section 6.5.19"
              ::= { ibmfrCircuitEntry 13 }

    ibmfrCircuitThroughput OBJECT-TYPE
        SYNTAX   INTEGER
        ACCESS   read-only
        STATUS   mandatory
        DESCRIPTION
           "Throughput is the average number of 'Frame Re-
           lay  Information  Field'  bits  transferred per
           second across a user network interface  in  one
           direction, measured over the measurement inter-
           val.

           If the  configured  committed  burst  rate  and
           throughput  are  both non-zero, the measurement
           interval
           T=ibmfrCircuitCommittedBurst/ibmfrCircuitThroughput.

           If the  configured  committed  burst  rate  and
           throughput  are  both zero, the measurement in-
           terval
                  T=ibmfrCircuitExcessBurst/ifSpeed."
       REFERENCE
          "Draft American National  Standard  T1.617-1991,
          Section 6.5.19"
      DEFVAL {0}  -- the default value of Throughput is
                  -- "no commitment".
      ::= { ibmfrCircuitEntry 14 }


--  Error Table

-- The table describing errors encountered on each Frame
-- Relay Interface.

ibmfrErrTable OBJECT-TYPE
    SYNTAX   SEQUENCE OF IbmfrErrEntry
    ACCESS   not-accessible
    STATUS   mandatory
    DESCRIPTION
       "A table containing information about Errors on the
       Frame Relay interface."
    ::= { ibmfr 3 }

    ibmfrErrEntry OBJECT-TYPE
        SYNTAX   IbmfrErrEntry
        ACCESS   not-accessible
        STATUS   mandatory
        DESCRIPTION
           "The error information for a single frame relay
           interface."
       INDEX { ibmfrErrIfIndex }
       ::= { ibmfrErrTable 1 }

    IbmfrErrEntry ::=
        SEQUENCE {
            ibmfrErrIfIndex
                INTEGER,
            ibmfrErrType
                INTEGER,
            ibmfrErrData
                OCTET STRING,
            ibmfrErrTime
                TimeTicks
    }

    ibmfrErrIfIndex OBJECT-TYPE
        SYNTAX   INTEGER       -- 1..ifNumber
        ACCESS   read-only
        STATUS   mandatory
        DESCRIPTION
           "The ifIndex Value of the  corresponding  ifEn-
           try."
       ::= { ibmfrErrEntry 1 }

    ibmfrErrType OBJECT-TYPE
        SYNTAX   INTEGER {
                    unknownError(1),
                    receiveShort(2),
                    receiveLong(3),
                    illegalDLCI(4),
                    unknownDLCI(5),
                    dlcmiProtoErr(6),
                    dlcmiUnknownIE(7),
                    dlcmiSequenceErr(8),
                    dlcmiUnknownRpt(9)
                 }
        ACCESS   read-only
        STATUS   mandatory
        DESCRIPTION
           "The type of error that was last seen  on  this
           interface."
       ::= { ibmfrErrEntry 2 }

    ibmfrErrData OBJECT-TYPE
        SYNTAX   OCTET STRING
        ACCESS   read-only
        STATUS   mandatory
        DESCRIPTION
           "An octet string containing as much of the  er-
           ror  packet as possible.  As a minimum, it must
           contain the Q.922 Address or  as  much  as  was
           delivered.   It is desirable to include all in-
           formation up to the PDU."
       ::= { ibmfrErrEntry 3 }

    ibmfrErrTime OBJECT-TYPE
        SYNTAX   TimeTicks
        ACCESS   read-only
        STATUS   mandatory
        DESCRIPTION
           "The time at which the error was detected.
           The time value is relative to other
           times on this interface only."
       ::= { ibmfrErrEntry 4 }


    --  Data Link Connection Management Interface Related Traps

--  ibmfrDLCIStatusChange TRAP-TYPE
--      ENTERPRISE ibmfr
--      VARIABLES  { ibmfrCircuitIfIndex, ibmfrCircuitDlci, ibmfrCircuitState }
--      DESCRIPTION
--         "This trap indicates that the indicated Virtual
--         Circuit  has changed state.  It has either been
--         created or invalidated, or has toggled  between
--         the active and inactive states."
--    ::= 1


-- static char sccsid[] = "@(#) snmp/samples/dls.my, SNMP, t960e  11/12/93 16:22:22";

------------------------------------------------------------------------
-- The IBM 6611 Data Link Switch (DLS) Extension                       -
------------------------------------------------------------------------


--  This MIB module uses the extended OBJECT-TYPE macro as
--  defined in RFC 1212.

-- All representations of MAC addresses in this MIB Module use,
-- as a textual convention (i.e. this convention does not affect
-- their encoding), the data type:

--MacAddress ::= OCTET STRING (SIZE(6))


-- All DLS filter tables use the following type to decide what
-- kind of filtering to do:

--FilterType ::= INTEGER { deny(1), permit(2) }


--
-- Virtual Ring Segment Number
--

ibmdlsVirtualRingSegmentNumber OBJECT-TYPE
    SYNTAX  INTEGER (0..4095)
    ACCESS  read-only
    STATUS  mandatory
    DESCRIPTION
            "The token ring segment number used in all frames passed
            to or from the IBM 6611 Data Link Switching function."
    ::= { ibmdls 1 }


--
-- Filter types
--

ibmdlsFrameFilterType OBJECT-TYPE
    SYNTAX  INTEGER { deny(1), permit(2) }
    ACCESS  read-only
    STATUS  mandatory
    DESCRIPTION
            "The type of SNA filtering applied using the
            ibmdlsLocalFrameFilterTable and ibmdlsRemoteFrameFilterTable.

            If this field = permit(2), then all filters defined
            for SNA use the action of permitting frames to be
            forwarded if they meet the criteria given by the
            source and destination address values.

            If this field = deny(1), then all filters defined
            for SNA use the action of denying frames to be
            forwarded if they meet the criteria given
            by the source and destination address values."
    ::= { ibmdls 2 }


ibmdlsNameFilterType OBJECT-TYPE
    SYNTAX  INTEGER { deny(1), permit(2) }
    ACCESS  read-only
    STATUS  mandatory
    DESCRIPTION
            "The type of NetBIOS filtering applied using the
            ibmdlsLocalNameFilterTable and ibmdlsRemoteNameFilterTable.

            If this field = permit(2), then all filters defined
            for NetBIOS use the action of permitting frames
            to be forwarded if they meet the criteria given
            by the source and destination address values.

            If this field = deny(1), then all filters defined
            for NetBIOS use the action of denying frames
            to be forwarded if they meet the criteria given
            by the source and destination address values."
    ::= { ibmdls 3 }


------------------------------------------------------------------------
-- Participating Router Table
------------------------------------------------------------------------

ibmdlsRouterTable OBJECT-TYPE
    SYNTAX  SEQUENCE OF IbmdlsRouterEntry
    ACCESS  not-accessible
    STATUS  mandatory
    DESCRIPTION
            "A table of information regarding all routers
            participating in Data Link Switching."

    ::= { ibmdls 4 }

ibmdlsRouterEntry OBJECT-TYPE
    SYNTAX  IbmdlsRouterEntry
    ACCESS  not-accessible
    STATUS  mandatory
    DESCRIPTION
            "Information for a single participating router."
    INDEX   { ibmdlsRouterAddress }
    ::= { ibmdlsRouterTable 1 }

IbmdlsRouterEntry ::=
    SEQUENCE {
        ibmdlsRouterAddress
            IpAddress,
        ibmdlsRouterStatus
            INTEGER,
        ibmdlsRouterDefinedBy
            INTEGER,
        ibmdlsRouterInFrames
            INTEGER,
        ibmdlsRouterOutFrames
            INTEGER
    }

ibmdlsRouterAddress OBJECT-TYPE
    SYNTAX  IpAddress
    ACCESS  read-only
    STATUS  mandatory
    DESCRIPTION
            "The IP address of the router participating in Data
            Link Switching."
    ::= { ibmdlsRouterEntry 1 }

ibmdlsRouterStatus OBJECT-TYPE
    SYNTAX  INTEGER {
                notActive(1),
                active(2)
            }
    ACCESS  read-only
    STATUS  mandatory
    DESCRIPTION
            "The current state of the remote connection"
    ::= { ibmdlsRouterEntry 2 }

ibmdlsRouterDefinedBy OBJECT-TYPE
    SYNTAX  INTEGER {
                user(1),
                system(2)
            }
    ACCESS  read-only
    STATUS  mandatory
    DESCRIPTION
            "The origin of this entry. user(1) indicates that
            this router is defined via the Configuration Program.
            system(2) indicates that this router was defined
            automatically as a result of a connection request from
            another router."
    ::= { ibmdlsRouterEntry 3 }

ibmdlsRouterInFrames OBJECT-TYPE
    SYNTAX  Counter
    ACCESS  read-only
    STATUS  mandatory
    DESCRIPTION
            "Number of frames received from the partner router."
    ::= { ibmdlsRouterEntry 4 }

ibmdlsRouterOutFrames OBJECT-TYPE
    SYNTAX  Counter
    ACCESS  read-only
    STATUS  mandatory
    DESCRIPTION
            "Number of frames sent to the partner router."
    ::= { ibmdlsRouterEntry 5 }


------------------------------------------------------------------------
-- SNA Local Frame Filter Table
------------------------------------------------------------------------

ibmdlsLocalFrameFilterTable OBJECT-TYPE
    SYNTAX  SEQUENCE OF IbmdlsLocalFrameFilterEntry
    ACCESS  not-accessible
    STATUS  mandatory
    DESCRIPTION
            "The SNA local frame filter table.  This table contains
            information regarding the filtering of SNA frames received
            from local LAN segments."
    ::= { ibmdls 5 }

ibmdlsLocalFrameFilterEntry OBJECT-TYPE
    SYNTAX  IbmdlsLocalFrameFilterEntry
    ACCESS  not-accessible
    STATUS  mandatory
    DESCRIPTION
            "Filter information for a MAC address source-destination pair."
    INDEX   { ibmdlsLocalFrameFilterID }
    ::= { ibmdlsLocalFrameFilterTable 1 }

IbmdlsLocalFrameFilterEntry ::=
    SEQUENCE {
        ibmdlsLocalFrameFilterID
            INTEGER,
        ibmdlsLocalFrameFilterSrcAddress
            OCTET STRING,
        ibmdlsLocalFrameFilterSrcMask
            OCTET STRING,
        ibmdlsLocalFrameFilterDestAddress
            OCTET STRING,
        ibmdlsLocalFrameFilterDestMask
            OCTET STRING
    }

ibmdlsLocalFrameFilterID OBJECT-TYPE
    SYNTAX  INTEGER (1..100)
    ACCESS  read-only
    STATUS  mandatory
    DESCRIPTION
            "A unique identifier for this filter."
    ::= { ibmdlsLocalFrameFilterEntry 1 }

ibmdlsLocalFrameFilterSrcAddress OBJECT-TYPE
    SYNTAX  OCTET STRING (SIZE(6))
    ACCESS  read-only
    STATUS  mandatory
    DESCRIPTION
            "The source MAC address that this filter is
            applied to."
    ::= { ibmdlsLocalFrameFilterEntry 2 }

ibmdlsLocalFrameFilterSrcMask OBJECT-TYPE
    SYNTAX  OCTET STRING (SIZE(6))
    ACCESS  read-only
    STATUS  mandatory
    DESCRIPTION
            "A mask indicating the bits of the source address
            considered significant when using the filter.
            For every bit equal to one in the mask, the same bit
            in the source address is considered significant."
    ::= { ibmdlsLocalFrameFilterEntry 3 }

ibmdlsLocalFrameFilterDestAddress OBJECT-TYPE
    SYNTAX  OCTET STRING (SIZE(6))
    ACCESS  read-only
    STATUS  mandatory
    DESCRIPTION
            "The destination MAC address that this filter is
            applied to."
    ::= { ibmdlsLocalFrameFilterEntry 4 }

ibmdlsLocalFrameFilterDestMask OBJECT-TYPE
    SYNTAX  OCTET STRING (SIZE(6))
    ACCESS  read-only
    STATUS  mandatory
    DESCRIPTION
            "A mask indicating the bits of the destination address
            considered significant when using the filter.
            For every bit equal to one in the mask, the same bit
            in the destination address is considered significant."
    ::= { ibmdlsLocalFrameFilterEntry 5 }


------------------------------------------------------------------------
-- SNA Remote Frame Filter Table
------------------------------------------------------------------------

ibmdlsRemoteFrameFilterTable OBJECT-TYPE
    SYNTAX  SEQUENCE OF IbmdlsRemoteFrameFilterEntry
    ACCESS  not-accessible
    STATUS  mandatory
    DESCRIPTION
            "The SNA remote frame filter table.  This table contains
            information regarding the filtering of SNA frames received
            from other participating DLS routers."
    ::= { ibmdls 6 }

ibmdlsRemoteFrameFilterEntry OBJECT-TYPE
    SYNTAX  IbmdlsRemoteFrameFilterEntry
    ACCESS  not-accessible
    STATUS  mandatory
    DESCRIPTION
            "Filter information for a MAC address source-destination pair."
    INDEX   { ibmdlsRemoteFrameFilterID }
    ::= { ibmdlsRemoteFrameFilterTable 1 }

IbmdlsRemoteFrameFilterEntry ::=
    SEQUENCE {
        ibmdlsRemoteFrameFilterID
            INTEGER,
        ibmdlsRemoteFrameFilterSrcAddress
            OCTET STRING,
        ibmdlsRemoteFrameFilterSrcMask
            OCTET STRING,
        ibmdlsRemoteFrameFilterDestAddress
            OCTET STRING,
        ibmdlsRemoteFrameFilterDestMask
            OCTET STRING
    }

ibmdlsRemoteFrameFilterID OBJECT-TYPE
    SYNTAX  INTEGER (1..100)
    ACCESS  read-only
    STATUS  mandatory
    DESCRIPTION
            "A unique identifier for this filter."
    ::= { ibmdlsRemoteFrameFilterEntry 1 }

ibmdlsRemoteFrameFilterSrcAddress OBJECT-TYPE
    SYNTAX  OCTET STRING (SIZE(6))
    ACCESS  read-only
    STATUS  mandatory
    DESCRIPTION
            "The source MAC address that this filter is
            applied to."
    ::= { ibmdlsRemoteFrameFilterEntry 2 }

ibmdlsRemoteFrameFilterSrcMask OBJECT-TYPE
    SYNTAX  OCTET STRING (SIZE(6))
    ACCESS  read-only
    STATUS  mandatory
    DESCRIPTION
            "A mask indicating the bits of the source address
            considered significant when using the filter.
            For every bit equal to one in the mask, the same bit
            in the source address is considered significant."
    ::= { ibmdlsRemoteFrameFilterEntry 3 }

ibmdlsRemoteFrameFilterDestAddress OBJECT-TYPE
    SYNTAX  OCTET STRING (SIZE(6))
    ACCESS  read-only
    STATUS  mandatory
    DESCRIPTION
            "The destination MAC address that this filter is
            applied to."
    ::= { ibmdlsRemoteFrameFilterEntry 4 }

ibmdlsRemoteFrameFilterDestMask OBJECT-TYPE
    SYNTAX  OCTET STRING (SIZE(6))
    ACCESS  read-only
    STATUS  mandatory
    DESCRIPTION
            "A mask indicating the bits of the destination address
            considered significant when using the filter.
            For every bit equal to one in the mask, the same bit
            in the destination address is considered significant."
    ::= { ibmdlsRemoteFrameFilterEntry 5 }


------------------------------------------------------------------------
-- NetBIOS Local Name Filter Table
------------------------------------------------------------------------

ibmdlsLocalNameFilterTable OBJECT-TYPE
    SYNTAX  SEQUENCE OF IbmdlsLocalNameFilterEntry
    ACCESS  not-accessible
    STATUS  mandatory
    DESCRIPTION
            "The NetBIOS local name filter table.  This table contains
            information regarding the filtering of NetBIOS frames
            received from local LAN segments."
    ::= { ibmdls 7 }

ibmdlsLocalNameFilterEntry OBJECT-TYPE
    SYNTAX  IbmdlsLocalNameFilterEntry
    ACCESS  not-accessible
    STATUS  mandatory
    DESCRIPTION
            "Filter information for a NetBIOS source-destination
            name pair."
    INDEX   { ibmdlsLocalNameFilterID }
    ::= { ibmdlsLocalNameFilterTable 1 }

IbmdlsLocalNameFilterEntry ::=
    SEQUENCE {
        ibmdlsLocalNameFilterID
            INTEGER,
        ibmdlsLocalNameFilterSrcAddress
            DisplayString,
        ibmdlsLocalNameFilterDestAddress
            DisplayString
    }

ibmdlsLocalNameFilterID OBJECT-TYPE
    SYNTAX  INTEGER (1..100)
    ACCESS  read-only
    STATUS  mandatory
    DESCRIPTION
            "A unique identifier for this filter."
    ::= { ibmdlsLocalNameFilterEntry 1 }

ibmdlsLocalNameFilterSrcAddress OBJECT-TYPE
    SYNTAX  DisplayString (SIZE (1..16))
    ACCESS  read-only
    STATUS  mandatory
    DESCRIPTION
            "The source NetBIOS name that this filter is
            applied to."
    ::= { ibmdlsLocalNameFilterEntry 2 }

ibmdlsLocalNameFilterDestAddress OBJECT-TYPE
    SYNTAX  DisplayString  (SIZE (1..16))
    ACCESS  read-only
    STATUS  mandatory
    DESCRIPTION
            "The destination NetBIOS name that this filter is
            applied to."
    ::= { ibmdlsLocalNameFilterEntry 3 }


------------------------------------------------------------------------
-- NetBIOS Remote Name Filter Table
------------------------------------------------------------------------

ibmdlsRemoteNameFilterTable OBJECT-TYPE
    SYNTAX  SEQUENCE OF IbmdlsRemoteNameFilterEntry
    ACCESS  not-accessible
    STATUS  mandatory
    DESCRIPTION
            "The NetBIOS name filter table.   This table contains
            information regarding the filtering of NetBIOS frames
            received from other participating DLS routers."
    ::= { ibmdls 8 }

ibmdlsRemoteNameFilterEntry OBJECT-TYPE
    SYNTAX  IbmdlsRemoteNameFilterEntry
    ACCESS  not-accessible
    STATUS  mandatory
    DESCRIPTION
            "Filter information for a NetBIOS source-destination
            name pair."
    INDEX   { ibmdlsRemoteNameFilterID }
    ::= { ibmdlsRemoteNameFilterTable 1 }

IbmdlsRemoteNameFilterEntry ::=
    SEQUENCE {
        ibmdlsRemoteNameFilterID
            INTEGER,
        ibmdlsRemoteNameFilterSrcAddress
            DisplayString,
        ibmdlsRemoteNameFilterDestAddress
            DisplayString
    }

ibmdlsRemoteNameFilterID OBJECT-TYPE
    SYNTAX  INTEGER (1..100)
    ACCESS  read-only
    STATUS  mandatory
    DESCRIPTION
            "A unique identifier for this filter."
    ::= { ibmdlsRemoteNameFilterEntry 1 }

ibmdlsRemoteNameFilterSrcAddress OBJECT-TYPE
    SYNTAX  DisplayString (SIZE (1..16))
    ACCESS  read-only
    STATUS  mandatory
    DESCRIPTION
            "The source NetBIOS name that this filter is
            applied to."
    ::= { ibmdlsRemoteNameFilterEntry 2 }

ibmdlsRemoteNameFilterDestAddress OBJECT-TYPE
    SYNTAX  DisplayString (SIZE (1..16))
    ACCESS  read-only
    STATUS  mandatory
    DESCRIPTION
            "The destination NetBIOS name that this filter is
            applied to."
    ::= { ibmdlsRemoteNameFilterEntry 3 }


------------------------------------------------------------------------
-- SNA Default Destination Table
------------------------------------------------------------------------

ibmdlsDefaultDestTable OBJECT-TYPE
    SYNTAX  SEQUENCE OF IbmdlsDefaultDestEntry
    ACCESS  not-accessible
    STATUS  mandatory
    DESCRIPTION
            "Table of default routers for MAC addresses."
    ::= { ibmdls 9 }

ibmdlsDefaultDestEntry OBJECT-TYPE
    SYNTAX  IbmdlsDefaultDestEntry
    ACCESS  not-accessible
    STATUS  mandatory
    DESCRIPTION
            "Mapping of a MAC address to a default router."
    INDEX   { ibmdlsDefaultDestAddress }
    ::= { ibmdlsDefaultDestTable 1 }

IbmdlsDefaultDestEntry ::=
    SEQUENCE {
        ibmdlsDefaultDestAddress
            OCTET STRING,
        ibmdlsDefaultRouterAddress
            IpAddress
    }

ibmdlsDefaultDestAddress OBJECT-TYPE
    SYNTAX  OCTET STRING (SIZE(6))
    ACCESS  read-only
    STATUS  mandatory
    DESCRIPTION
            "The destination address that this table entry applies
            to."
    ::= { ibmdlsDefaultDestEntry 1 }

ibmdlsDefaultRouterAddress OBJECT-TYPE
    SYNTAX  IpAddress
    ACCESS  read-only
    STATUS  mandatory
    DESCRIPTION
            "The default router used for reaching the destination
            address in ibmdlsDefaultDestAddress."
    ::= { ibmdlsDefaultDestEntry 2 }


------------------------------------------------------------------------
-- NetBios Default Destination Table
------------------------------------------------------------------------

ibmdlsDefaultNBDestTable OBJECT-TYPE
    SYNTAX  SEQUENCE OF IbmdlsDefaultNBDestEntry
    ACCESS  not-accessible
    STATUS  mandatory
    DESCRIPTION
            "Table of default routers for NetBIOS names."
    ::= { ibmdls 10 }

ibmdlsDefaultNBDestEntry OBJECT-TYPE
    SYNTAX  IbmdlsDefaultNBDestEntry
    ACCESS  not-accessible
    STATUS  mandatory
    DESCRIPTION
            "Mapping of a NetBIOS name to a default router."
    INDEX   { ibmdlsDefaultNBDestName }
    ::= { ibmdlsDefaultNBDestTable 1 }

IbmdlsDefaultNBDestEntry ::=
    SEQUENCE {
        ibmdlsDefaultNBDestName
            DisplayString,
        ibmdlsDefaultNBRouterAddress
            IpAddress
    }

ibmdlsDefaultNBDestName OBJECT-TYPE
    SYNTAX  DisplayString (SIZE (1..16))
    ACCESS  read-only
    STATUS  mandatory
    DESCRIPTION
            "The destination NetBIOS name that this table entry
            applies to."
    ::= { ibmdlsDefaultNBDestEntry 1 }

ibmdlsDefaultNBRouterAddress OBJECT-TYPE
    SYNTAX  IpAddress
    ACCESS  read-only
    STATUS  mandatory
    DESCRIPTION
            "The default router used for reaching the destination
            name in ibmdlsDefaultNBDestName."
    ::= { ibmdlsDefaultNBDestEntry 2 }


------------------------------------------------------------------------
-- SNA Station Table
------------------------------------------------------------------------

ibmdlsStationTable OBJECT-TYPE
    SYNTAX  SEQUENCE OF IbmdlsStationEntry
    ACCESS  not-accessible
    STATUS  mandatory
    DESCRIPTION
            "Table of configuration information on SNA stations
            attached to this router."
    ::= { ibmdls 11 }

ibmdlsStationEntry OBJECT-TYPE
    SYNTAX  IbmdlsStationEntry
    ACCESS  not-accessible
    STATUS  mandatory
    DESCRIPTION
            "Information on a single SNA station attached to this router."
    INDEX   { ibmdlsStationIfIndex, ibmdlsStationAddress }
    ::= { ibmdlsStationTable 1 }

IbmdlsStationEntry ::=
    SEQUENCE {
        ibmdlsStationIfIndex
            INTEGER,
        ibmdlsStationAddress
            INTEGER,
        ibmdlsStationTransmitWindowCount
            INTEGER,
        ibmdlsStationRetransmitCount
            INTEGER,
        ibmdlsStationRetransmitThreshold
            INTEGER,
        ibmdlsStationForceDisconnectTimeout
            INTEGER,
        ibmdlsStationMaxIfieldSize
            INTEGER,
        ibmdlsStationPrimaryRepollTimeout
            INTEGER,
        ibmdlsStationPrimaryRepollCount
            INTEGER,
        ibmdlsStationPrimaryRepollThreshold
            INTEGER,
        ibmdlsStationPrimarySlowListTimeout
            INTEGER,
        ibmdlsStationSrcAddress
            OCTET STRING,
        ibmdlsStationDestAddress
            OCTET STRING
    }

ibmdlsStationIfIndex OBJECT-TYPE
    SYNTAX  INTEGER
    ACCESS  read-only
    STATUS  mandatory
    DESCRIPTION
            "The value of IfIndex for the port to which this station
            is attached."
    ::= { ibmdlsStationEntry 1 }

ibmdlsStationAddress OBJECT-TYPE
    SYNTAX  INTEGER (1..255)
    ACCESS  read-only
    STATUS  mandatory
    DESCRIPTION
            "The SDLC address of this station."
    ::= { ibmdlsStationEntry 2 }

ibmdlsStationTransmitWindowCount OBJECT-TYPE
    SYNTAX  INTEGER (1..7)
    ACCESS  read-only
    STATUS  mandatory
    DESCRIPTION
            "The number of SDLC information frames to send to this
            station before turning the line around to get a response."
    DEFVAL  { 7 }
    ::= { ibmdlsStationEntry 3 }

ibmdlsStationRetransmitCount OBJECT-TYPE
    SYNTAX  INTEGER (1..50)
    ACCESS  read-only
    STATUS  mandatory
    DESCRIPTION
            "The number of contiguous information frame bursts that
            will be transmitted to this station before declaring a
            permanent transmission error."
    DEFVAL  { 10 }
    ::= { ibmdlsStationEntry 4 }

ibmdlsStationRetransmitThreshold OBJECT-TYPE
    SYNTAX  INTEGER (1..100)
    ACCESS  read-only
    STATUS  mandatory
    DESCRIPTION
            "The number of information frame transmissions allowed as
            a percentage of total information frame transmissions.
            The specified rate is the maximum rate of retransmissions
            allowed above which an error log entry will be make."
    DEFVAL  { 10 }
    ::= { ibmdlsStationEntry 5 }

ibmdlsStationForceDisconnectTimeout OBJECT-TYPE
    SYNTAX  INTEGER (1..600)
    ACCESS  read-only
    STATUS  mandatory
    DESCRIPTION
            "The number of seconds that the IBM 6611 will wait after
            requesting a disconnect from the link (DISC) before forcing
            a disconnect."
    DEFVAL  { 120 }
    ::= { ibmdlsStationEntry 6 }

ibmdlsStationMaxIfieldSize OBJECT-TYPE
    SYNTAX  INTEGER (265..30729)
    ACCESS  read-only
    STATUS  mandatory
    DESCRIPTION
            "The value in bytes of the maximum I-field size
            (a multiple of 256 plus 9)."
    DEFVAL  { 265 }
    ::= { ibmdlsStationEntry 7 }

ibmdlsStationPrimaryRepollTimeout OBJECT-TYPE
    SYNTAX  INTEGER (1..250)
    ACCESS  read-only
    STATUS  mandatory
    DESCRIPTION
            "The length of time (in tenths of seconds) that the primary
            station will wait for a response from the secondary station."
    DEFVAL  { 30 }
    ::= { ibmdlsStationEntry 8 }

ibmdlsStationPrimaryRepollCount OBJECT-TYPE
    SYNTAX  INTEGER (3..50)
    ACCESS  read-only
    STATUS  mandatory
    DESCRIPTION
            "The number of times that the primary station will poll
            the secondary station unsuccessfully before marking the
            station as not working."
    DEFVAL  { 15 }
    ::= { ibmdlsStationEntry 9 }

ibmdlsStationPrimaryRepollThreshold OBJECT-TYPE
    SYNTAX  INTEGER (1..100)
    ACCESS  read-only
    STATUS  mandatory
    DESCRIPTION
            "The number of repolls as a percentage of the total polls
            sent to the secondary station.  The specified percentage equals
            the maximum rate of repolls allowed, above which the IBM 6611
            declares that a temporary error has occurred and logs an
            entry in the system error log."
    DEFVAL  { 10 }
    ::= { ibmdlsStationEntry 10 }

ibmdlsStationPrimarySlowListTimeout OBJECT-TYPE
    SYNTAX  INTEGER (1..60)
    ACCESS  read-only
    STATUS  mandatory
    DESCRIPTION
            "The number of seconds that the primary station will wait
            between polls to stations on the slow list."
    DEFVAL  { 1 }
    ::= { ibmdlsStationEntry 11 }

ibmdlsStationSrcAddress OBJECT-TYPE
    SYNTAX  OCTET STRING (SIZE(6))
    ACCESS  read-only
    STATUS  mandatory
    DESCRIPTION
            "The token ring physical address used for this station."
    ::= { ibmdlsStationEntry 12 }

ibmdlsStationDestAddress OBJECT-TYPE
    SYNTAX  OCTET STRING (SIZE(6))
    ACCESS  read-only
    STATUS  mandatory
    DESCRIPTION
            "The token ring physical address to which this station
            should be connected.  If this information is not
            available the IBM 6611 Network Processor will return
            a length of zero for this object."
    ::= { ibmdlsStationEntry 13 }


------------------------------------------------------------------------
-- Circuit Table
------------------------------------------------------------------------
-- A unique circuit is identified by a port number (on a specific router),
-- source address, source SAP, destination address, and destination SAP.
-- In the DLS MIB, ifIndex is used instead of port number.
--

ibmdlsCirTable OBJECT-TYPE
    SYNTAX  SEQUENCE OF IbmdlsCirEntry
    ACCESS  not-accessible
    STATUS  mandatory
    DESCRIPTION
            "Table of information on DLS circuits active on this router."
    ::= { ibmdls 12 }

ibmdlsCirEntry OBJECT-TYPE
    SYNTAX  IbmdlsCirEntry
    ACCESS  not-accessible
    STATUS  mandatory
    DESCRIPTION
            "Information on a DLS circuit."
    INDEX   { ibmdlsCirIfIndex, ibmdlsCirSrcAddress,
              ibmdlsCirSrcSap, ibmdlsCirDestAddress,
              ibmdlsCirDestSap }
    ::= { ibmdlsCirTable 1 }

IbmdlsCirEntry ::=
    SEQUENCE {
        ibmdlsCirIfIndex
            INTEGER,
        ibmdlsCirSrcAddress
            OCTET STRING,
        ibmdlsCirSrcSap
            INTEGER,
        ibmdlsCirDestAddress
            OCTET STRING,
        ibmdlsCirDestSap
            INTEGER,
        ibmdlsCirPartnerRouterAddress
            IpAddress,
        ibmdlsCirLocalLinkState
            INTEGER,
        ibmdlsCirLocalLinkSubState
            INTEGER,
        ibmdlsCirLocalLinkRouting
            OCTET STRING,
        ibmdlsCirLocalLinkTestCmdsSent
            Counter,
        ibmdlsCirLocalLinkTestCmdsFail
            Counter,
        ibmdlsCirLocalLinkTestCmdsRcv
            Counter,
        ibmdlsCirLocalLinkDataPktSent
            Counter,
        ibmdlsCirLocalLinkDataPktResent
            Counter,
        ibmdlsCirLocalLinkMaxContResent
            Counter,
        ibmdlsCirLocalLinkDataPktRcv
            Counter,
        ibmdlsCirLocalLinkInvalidPktRcv
            Counter,
        ibmdlsCirLocalLinkAdpRcvErr
            Counter,
        ibmdlsCirLocalLinkAdpSendErr
            Counter,
        ibmdlsCirLocalLinkRcvInactiveTimeouts
            Counter,
        ibmdlsCirLocalLinkCmdPollsSent
            Counter,
        ibmdlsCirLocalLinkCmdRepollsSent
            Counter,
        ibmdlsCirLocalLinkCmdContRepolls
            Counter,
        ibmdlsCirLocalAddress
            INTEGER,
        ibmdlsCirLocalConnectionState
            INTEGER
    }

ibmdlsCirIfIndex OBJECT-TYPE
    SYNTAX  INTEGER
    ACCESS  read-only
    STATUS  mandatory
    DESCRIPTION
            "The value of IfIndex for the interface supporting this
             circuit."
    ::= { ibmdlsCirEntry 1 }

ibmdlsCirSrcAddress OBJECT-TYPE
    SYNTAX  OCTET STRING (SIZE(6))
    ACCESS  read-only
    STATUS  mandatory
    DESCRIPTION
            "The MAC address of the source of this circuit."
    ::= { ibmdlsCirEntry 2 }

ibmdlsCirSrcSap OBJECT-TYPE
    SYNTAX  INTEGER
    ACCESS  read-only
    STATUS  mandatory
    DESCRIPTION
            "The SAP identifier of the source of this circuit."
    ::= { ibmdlsCirEntry 3 }

ibmdlsCirDestAddress OBJECT-TYPE
    SYNTAX  OCTET STRING (SIZE(6))
    ACCESS  read-only
    STATUS  mandatory
    DESCRIPTION
            "The MAC address of the destination of this circuit."
    ::= { ibmdlsCirEntry 4 }

ibmdlsCirDestSap OBJECT-TYPE
    SYNTAX  INTEGER
    ACCESS  read-only
    STATUS  mandatory
    DESCRIPTION
            "The SAP identifier of the destination of this circuit."
    ::= { ibmdlsCirEntry 5 }

ibmdlsCirPartnerRouterAddress OBJECT-TYPE
    SYNTAX  IpAddress
    ACCESS  read-only
    STATUS  mandatory
    DESCRIPTION
            "The IP address of the partner router used by
            this circuit."
    ::= { ibmdlsCirEntry 6 }

ibmdlsCirLocalLinkState OBJECT-TYPE
    SYNTAX  INTEGER {
                opening(1),
                opened(2),
                closing(3),
                inactive(4)
            }
    ACCESS  read-only
    STATUS  mandatory
    DESCRIPTION
            "The state of the local link station used by
            this circuit."
    ::= { ibmdlsCirEntry 7 }

ibmdlsCirLocalLinkSubState OBJECT-TYPE
    SYNTAX  INTEGER {
                calling(1),
                listening(2),
                contacted(3),
                localBusy(4),
                remoteBusy(5)
            }
    ACCESS  read-only
    STATUS  mandatory
    DESCRIPTION
            "The sub-state of the local link station used by
            this circuit."
    ::= { ibmdlsCirEntry 8 }

ibmdlsCirLocalLinkRouting OBJECT-TYPE
    SYNTAX  OCTET STRING (SIZE (4..18))
    ACCESS  read-only
    STATUS  mandatory
    DESCRIPTION
            "The routing information field used by the
            local link portion of this circuit.  The routing
            information field consists of a 2-byte routing
            control field and up to eight 2-byte route
            designators."
    REFERENCE
            "IBM Token-ring Network:  Architecture Reference
            (SC30-3374), see 'Routing Information Field'."
    ::= { ibmdlsCirEntry 9 }

ibmdlsCirLocalLinkTestCmdsSent OBJECT-TYPE
    SYNTAX  Counter
    ACCESS  read-only
    STATUS  mandatory
    DESCRIPTION
            "The number of test commands sent by the
            local link station used by this circuit."
    ::= { ibmdlsCirEntry 10}

ibmdlsCirLocalLinkTestCmdsFail OBJECT-TYPE
    SYNTAX  Counter
    ACCESS  read-only
    STATUS  mandatory
    DESCRIPTION
            "The number of test commands failed by the
            local link station used by this circuit."
    ::= { ibmdlsCirEntry 11 }

ibmdlsCirLocalLinkTestCmdsRcv OBJECT-TYPE
    SYNTAX  Counter
    ACCESS  read-only
    STATUS  mandatory
    DESCRIPTION
            "The number of test commands received by the
            local link station used by this circuit."
    ::= { ibmdlsCirEntry 12 }

ibmdlsCirLocalLinkDataPktSent OBJECT-TYPE
    SYNTAX  Counter
    ACCESS  read-only
    STATUS  mandatory
    DESCRIPTION
            "The number of sequenced data packets sent
            by the local link station used by this circuit."
    ::= { ibmdlsCirEntry 13 }

ibmdlsCirLocalLinkDataPktResent OBJECT-TYPE
    SYNTAX  Counter
    ACCESS  read-only
    STATUS  mandatory
    DESCRIPTION
            "The number of sequenced data packets resent by
            the local link station used by this circuit."
    ::= { ibmdlsCirEntry 14 }

ibmdlsCirLocalLinkMaxContResent OBJECT-TYPE
    SYNTAX  Counter
    ACCESS  read-only
    STATUS  mandatory
    DESCRIPTION
            "The maximum number of contiguous resendings by
            the local link station used by this circuit."
    ::= { ibmdlsCirEntry 15 }

ibmdlsCirLocalLinkDataPktRcv OBJECT-TYPE
    SYNTAX  Counter
    ACCESS  read-only
    STATUS  mandatory
    DESCRIPTION
            "The number of sequenced data packets received
            by the local link station used by this circuit."
    ::= { ibmdlsCirEntry 16 }

ibmdlsCirLocalLinkInvalidPktRcv OBJECT-TYPE
    SYNTAX  Counter
    ACCESS  read-only
    STATUS  mandatory
    DESCRIPTION
            "The number of invalid packets received by
            the local link station used by this circuit."
    ::= { ibmdlsCirEntry 17 }

ibmdlsCirLocalLinkAdpRcvErr OBJECT-TYPE
    SYNTAX  Counter
    ACCESS  read-only
    STATUS  mandatory
    DESCRIPTION
            "The number of data-detected receive errors by
            the local link station used by this circuit."
    ::= { ibmdlsCirEntry 18 }

ibmdlsCirLocalLinkAdpSendErr OBJECT-TYPE
    SYNTAX  Counter
    ACCESS  read-only
    STATUS  mandatory
    DESCRIPTION
            "The number of data-detected transmit errors by
            the local link station used by this circuit."
    ::= { ibmdlsCirEntry 19 }

ibmdlsCirLocalLinkRcvInactiveTimeouts OBJECT-TYPE
    SYNTAX  Counter
    ACCESS  read-only
    STATUS  mandatory
    DESCRIPTION
            "The number of inactivity timeouts received by
            the local link station used by this circuit."
    ::= { ibmdlsCirEntry 20 }

ibmdlsCirLocalLinkCmdPollsSent OBJECT-TYPE
    SYNTAX  Counter
    ACCESS  read-only
    STATUS  mandatory
    DESCRIPTION
            "The number of command polls sent by
            the local link station used by this circuit."
    ::= { ibmdlsCirEntry 21 }

ibmdlsCirLocalLinkCmdRepollsSent OBJECT-TYPE
    SYNTAX  Counter
    ACCESS  read-only
    STATUS  mandatory
    DESCRIPTION
            "The number of command repolls sent by
            the local link station used by this circuit."
    ::= { ibmdlsCirEntry 22 }

ibmdlsCirLocalLinkCmdContRepolls OBJECT-TYPE
    SYNTAX  Counter
    ACCESS  read-only
    STATUS  mandatory
    DESCRIPTION
            "The number of continuous repolls sent by
            the local link station used by this circuit."
    ::= { ibmdlsCirEntry 23 }

ibmdlsCirLocalAddress OBJECT-TYPE
    SYNTAX  INTEGER {
                sourceIsLocal(1),
                destinationIsLocal(2)
            }
    ACCESS  read-only
    STATUS  mandatory
    DESCRIPTION
            "The address (ibmdlsCirSrcAddress or
            ibmdlsCirDestAddress) that is local
            on this circuit."
    ::= { ibmdlsCirEntry 24 }

ibmdlsCirLocalConnectionState OBJECT-TYPE
    SYNTAX  INTEGER {
                discontacted(1),
                contactPending(2),
                contacted(3),
                discontactPending(4),
                connected(5)
            }
    ACCESS  read-only
    STATUS  mandatory
    DESCRIPTION
            "The state of the DLSw circuit connection based
             upon the progression of events as a logical link
             station and its associated DLSw connection is
             brought up or down."
    ::= { ibmdlsCirEntry 25 }



-- static char sccsid_ppp_mib[] = "@(#) snmp/samples/ppp.my, SNMP, 6611R2, r2d18a  10/1/92 17:38:28";


------------------------------------------------------------------------
-- The Point to Point (PPP) Extension                                  -
------------------------------------------------------------------------
-- (Based on Internet draft dated September 1990)


-- PPP Link Control Table

ibmpppLinkControlTable OBJECT-TYPE
        SYNTAX  SEQUENCE OF IbmpppLinkControlEntry
        ACCESS  not-accessible
        STATUS  mandatory
        DESCRIPTION
            "A table containing PPP-link specific control variables
            for this managed object.  An entry in this table is
            uniquely identified by the ibmpppLinkControlIndex value
            comprised by said entry."
        ::= { ibmppp 1 }

ibmpppLinkControlEntry   OBJECT-TYPE
        SYNTAX  IbmpppLinkControlEntry
        ACCESS  not-accessible
        STATUS  mandatory
        DESCRIPTION
            "Management control information about a particular PPP
            Link."
        INDEX   { ibmpppLinkControlIndex }
        ::= { ibmpppLinkControlTable 1 }

IbmpppLinkControlEntry ::= SEQUENCE {
        ibmpppLinkControlIndex
                INTEGER,
        ibmpppLinkCRCSize
                INTEGER,
        ibmpppLinkRestartTimerValue
                INTEGER,
        ibmpppLinkMaxRestarts
                INTEGER,
        ibmpppLinkLocalMRU
                INTEGER,
        ibmpppLinkRemoteMRU
                INTEGER,
        ibmpppLinkLocalACCMap
                OCTET STRING (SIZE(4)),
        ibmpppLinkRemoteACCMap
                OCTET STRING (SIZE(4)),
        ibmpppLinkMagicLoopCount
                INTEGER,
        ibmpppLinkCommand
                INTEGER
        }

ibmpppLinkControlIndex  OBJECT-TYPE
        SYNTAX  INTEGER
        ACCESS  read-only
        STATUS  mandatory
        DESCRIPTION
            "A unique value for each PPP link. Its value ranges
            between 1 and the value of ifNumber. The interface
            identified by a particular value of this index is that
            identified by the same value of an ifIndex object
            instance. The value for each link must remain constant at
            least from one re-initialization of the entity's network
            management system to the next re-initialization."
        ::= { ibmpppLinkControlEntry 1 }

ibmpppLinkCRCSize  OBJECT-TYPE
        SYNTAX  INTEGER {
                    ppp-crc-16(16),
                    ppp-crc-32(32)
            }
        ACCESS  read-only
        STATUS  mandatory
        DESCRIPTION
            "Number of bits used in the CRC on this link.  See section
            3.1, 'Frame Check Sequence (FCS) Field' on page 5 of
            RFC 1171.  Setting this object to a new value will have
            effect when this link is next restarted."
        ::= { ibmpppLinkControlEntry 2 }

ibmpppLinkRestartTimerValue OBJECT-TYPE
        SYNTAX  INTEGER
        ACCESS  read-only
        STATUS  mandatory
        DESCRIPTION
            "The value used for the Restart Timer. It is in units of
            hundredths of a second.  See section 4.3, 'Timers and
            Counters' on page 20 of RFC 1171."
        ::= { ibmpppLinkControlEntry 3 }

ibmpppLinkMaxRestarts OBJECT-TYPE
        SYNTAX  INTEGER
        ACCESS  read-only
        STATUS  mandatory
        DESCRIPTION
            "The Max-Restarts parameter described in section 4.3,
            'Timers and Counters' on page 20 of RFC 1171."
        ::= { ibmpppLinkControlEntry 4 }

ibmpppLinkLocalMRU OBJECT-TYPE
        SYNTAX  INTEGER
        ACCESS  read-only
        STATUS  mandatory
        DESCRIPTION
            "The MRU (Maximum Receive Unit) of this node on the link.
            See section 2.1, page 2, 'Maximum Receive Unit' of
            RFC 1172.  Changing this object will have effect when
            the link is next restarted."
        ::= { ibmpppLinkControlEntry 5 }

ibmpppLinkRemoteMRU OBJECT-TYPE
        SYNTAX  INTEGER
        ACCESS  read-only
        STATUS  mandatory
        DESCRIPTION
            "What this node believes is the MRU for the node on the
            other end of the link. See section 2.1, page 2, 'Maximum
            Receive Unit' of RFC 1172.  Changing this object will
            immediately cause the local node to use the new MRU when
            transmitting packets. If this number is increased, then
            the sender MAY elect to use the new MRU. If the MRU is
            decreased then the sender MUST use the new MRU."
        ::= { ibmpppLinkControlEntry 6 }

ibmpppLinkLocalACCMap OBJECT-TYPE
        SYNTAX  OCTET STRING (SIZE (4))
        ACCESS  read-only
        STATUS  mandatory
        DESCRIPTION
            "The (ACC) Asynchronous-Control-Character-Map for this
            node.  This is the ACC Map that the node on the other end
            of the link will use when building a packet to send to
            this node.  See section 2.2, page 3, 'Async-Control-
            Character-Map' of RFC 1172.

            The IBM 6611 Network Processor always provides a
            value of zero for this object."
        ::= { ibmpppLinkControlEntry 7 }

ibmpppLinkRemoteACCMap OBJECT-TYPE
        SYNTAX  OCTET STRING (SIZE (4))
        ACCESS  read-only
        STATUS  mandatory
        DESCRIPTION
            "The (ACC) Asynchronous-Control-Character-Map that this
            node uses when building a packet to send to the node on
            the other end of the link. See section 2.2, page 3,
            'Async-Control-Character-Map' of RFC 1172.

            The IBM 6611 Network Processor always provides a
            value of zero for this object."
        ::= { ibmpppLinkControlEntry 8 }

ibmpppLinkMagicLoopCount OBJECT-TYPE
        SYNTAX  INTEGER
        ACCESS  read-only
        STATUS  mandatory
        DESCRIPTION
            "The number of times that this node will do a Magic Number
            Configuration before deciding that the link is looped
            back.  0 indicates that the node does not do Magic Number
            Configuration. -1 indicates that it tries forever.
            Changing this object takes effect the next time that the
            link is restarted."
        ::= { ibmpppLinkControlEntry 9 }

ibmpppLinkCommand OBJECT-TYPE
        SYNTAX  INTEGER {
                    no-op(1),
                    close(2)
                }
        ACCESS  read-only
        STATUS  mandatory
        DESCRIPTION
            "See section 4.14 on page 13 of RFC 1171.
            Reading from this variable will return no-op(1).

            The IBM 6611 Network Processor always provides a
            value of no-op(1) for this object."
        ::= { ibmpppLinkControlEntry 10 }

-- PPP Link Status Table

ibmpppLinkStatusTable OBJECT-TYPE
        SYNTAX  SEQUENCE OF IbmpppLinkStatusEntry
        ACCESS  not-accessible
        STATUS  mandatory
        DESCRIPTION
            "A table containing PPP-link status specific information
            for this managed object.  An entry in this table is
            uniquely identified by the ibmpppLinkStatusIndex value
            comprised by said entry."
        ::= { ibmppp 2 }

ibmpppLinkStatusEntry   OBJECT-TYPE
        SYNTAX  IbmpppLinkStatusEntry
        ACCESS  not-accessible
        STATUS  mandatory
        DESCRIPTION
            "Status information about a particular PPP Link."
        INDEX   { ibmpppLinkStatusIndex }
        ::= { ibmpppLinkStatusTable 1 }

IbmpppLinkStatusEntry ::= SEQUENCE {
        ibmpppLinkStatusIndex
                INTEGER,
        ibmpppLinkVersion
                INTEGER,
        ibmpppLinkCurrentState
                INTEGER,
        ibmpppLinkPreviousState
                INTEGER,
        ibmpppLinkChangeTime
                TimeTicks,
        ibmpppLinkMagicNumber
                INTEGER,
        ibmpppLinkLocalQualityPeriod
                INTEGER,
        ibmpppLinkRemoteQualityPeriod
                INTEGER,
        ibmpppLinkProtocolCompression
                INTEGER,
        ibmpppLinkACCompression
                INTEGER,
        ibmpppLinkMeasurementsValid
                INTEGER,
        ibmpppLinkQuality
                INTEGER,
        ibmpppLinkPhysical
                OBJECT IDENTIFIER
        }

ibmpppLinkStatusIndex  OBJECT-TYPE
        SYNTAX  INTEGER
        ACCESS  read-only
        STATUS  mandatory
        DESCRIPTION
            "A unique value for each PPP link. Its value ranges
            between 1 and the value of ifNumber. The interface
            identified by a particular value of this index is that
            identified by the same value of an ifIndex object
            instance. The value for each link must remain constant at
            least from one re-initialization of the entity's network
            management system to the next re-initialization."
        ::= { ibmpppLinkStatusEntry 1 }

ibmpppLinkVersion  OBJECT-TYPE
        SYNTAX  INTEGER
        ACCESS  read-only
        STATUS  mandatory
        DESCRIPTION
            "The version of LCP that is being run over this link
            (per RFC 1171).  This value currently must be 1."
        ::= { ibmpppLinkStatusEntry 2 }

ibmpppLinkCurrentState OBJECT-TYPE
        SYNTAX  INTEGER {
                     closed(1),
                     listen(2),
                     reqsent(3),
                     ackrecvd(4),
                     acksent(5),
                     open(6),
                     closing(7)
               }

        ACCESS  read-only
        STATUS  mandatory
        DESCRIPTION
            "The current state of the link automaton. See section
            4.1.3.  'State Transition Table' on page 13 of RFC 1171."
        ::= { ibmpppLinkStatusEntry 3 }

ibmpppLinkPreviousState OBJECT-TYPE
        SYNTAX  INTEGER {
                    closed(1),
                    listen(2),
                    reqsent(3),
                    ackrecvd(4),
                    acksent(5),
                    open(6),
                    closing(7)
               }
        ACCESS  read-only
        STATUS  mandatory
        DESCRIPTION
            "The immediately previous state of the link automaton. See
            section 4.1.3. 'State Transition Table' on page 13 of
            RFC 1171."
        ::= { ibmpppLinkStatusEntry 4 }

ibmpppLinkChangeTime OBJECT-TYPE
        SYNTAX  TimeTicks
        ACCESS  read-only
        STATUS  mandatory
        DESCRIPTION
            "The value of sysUpTime when the state of the link
            automaton last changed."
        ::= { ibmpppLinkStatusEntry 5 }

ibmpppLinkMagicNumber OBJECT-TYPE
        SYNTAX  INTEGER
        ACCESS  read-only
        STATUS  mandatory
        DESCRIPTION
            "This node's Magic Number. See section 2.4, page 7, 'Magic
            Number' of RFC 1172."
        ::= { ibmpppLinkStatusEntry 6 }

ibmpppLinkLocalQualityPeriod OBJECT-TYPE
        SYNTAX  INTEGER
        ACCESS  read-only
        STATUS  mandatory
        DESCRIPTION
            "This is the maximum interval at which this node will
            transmit Link-Quality-Report Packets. See section 2.5, on
            page 10 of RFC 1172.  This object is in units of
            microseconds."
        ::= { ibmpppLinkStatusEntry 7 }

ibmpppLinkRemoteQualityPeriod OBJECT-TYPE
        SYNTAX  INTEGER
        ACCESS  read-only
        STATUS  mandatory
        DESCRIPTION
            "This is the maximum interval at which this node expects
            that the other node will transmit Link-Quality-Report
            Packets.  See section 2.5, on page 10 of RFC 1172.  This
            object is in units of microseconds."
        ::= { ibmpppLinkStatusEntry 8 }

ibmpppLinkProtocolCompression OBJECT-TYPE
        SYNTAX  INTEGER {
                    receive-only(1),
                    send-only(2),
                    receive-and-send(3),
                    none(4)
               }
        ACCESS  read-only
        STATUS  mandatory
        DESCRIPTION
            "Indicates the Protocol compression that has been
            configured on the link. Receive-only(1) indicates that
            this node can receive compressed packets but won't send
            them. Send-only(2) indicates that this node will send
            compressed packets but can not receive them.
            Receive-and-send(3) indicates that the node will send and
            can receive compressed packets. None(4) indicates that
            this node will neither send nor receive compressed
            packets. See section 2.6, on page 11 of RFC 1172.

            The IBM 6611 Network Processor always provides a
            value of none(4) for this object."
        ::= { ibmpppLinkStatusEntry 9 }

ibmpppLinkACCompression OBJECT-TYPE
        SYNTAX  INTEGER {
                    receive-only(1),
                    send-only(2),
                    receive-and-send(3),
                    none(4)
                }
        ACCESS  read-only
        STATUS  mandatory
        DESCRIPTION
            "Indicates the Address/Control Field compression that has
            been configured on the link. Receive-only(1) indicates
            that this node can receive compressed packets but won't
            send them. Send-only(2) indicates that this node will
            send compressed packets but can not receive them.
            Receive-and- send(3) indicates that the node will send
            and can receive compressed packets. None(4) indicates
            that this node will neither send nor receive compressed
            packets. See section 2.7, on page 13 of RFC 1172.

            The IBM 6611 Network Processor always provides a
            value of none(4) for this object."
        ::= { ibmpppLinkStatusEntry 10 }

ibmpppLinkMeasurementsValid OBJECT-TYPE
        SYNTAX  INTEGER
        ACCESS  read-only
        STATUS  mandatory
        DESCRIPTION
            "The current value of the Measurements-Valid state
            variable used for Link-Quality Management. See section
            3.5, page 19, of RFC 1172."
        ::= { ibmpppLinkStatusEntry 11 }

ibmpppLinkQuality OBJECT-TYPE
        SYNTAX  INTEGER {
                    good(1),
                    bad(2)
                }
        ACCESS  read-only
        STATUS  mandatory
        DESCRIPTION
            "The current quality of the link as declared by the nodes
            Link-Quality Management modules. No effort is made to
            define good or bad, nor the policy used to determine it."
        ::= { ibmpppLinkStatusEntry 12 }

ibmpppLinkPhysical OBJECT-TYPE
        SYNTAX  OBJECT IDENTIFIER
        ACCESS  read-only
        STATUS  mandatory
        DESCRIPTION
            "A reference to MIB definitions specific to the particular
            physical interface type (e.g. T1) being used by the PPP
            Link.  If the agent is unable to obtain this information,
            the value of this object will be set to the OBJECT
            IDENTIFIER { 0 0 }, which is a syntatically valid
            object identifier, and any conformant
            implementation of ASN.1 and BER must be able to
            generate and recognize this value."
        ::= { ibmpppLinkStatusEntry 13 }

-- PPP Link Errors Table

ibmpppLinkErrorsTable OBJECT-TYPE
        SYNTAX  SEQUENCE OF IbmpppLinkErrorsEntry
        ACCESS  not-accessible
        STATUS  mandatory
        DESCRIPTION
            "A table containing PPP-link specific statistical
            information for this managed object.  An entry in this
            table is uniquely identified by the ibmpppLinkErrorsIndex
            value comprised by said entry."
        ::= { ibmppp 3 }

ibmpppLinkErrorsEntry   OBJECT-TYPE
        SYNTAX  IbmpppLinkErrorsEntry
        ACCESS  not-accessible
        STATUS  mandatory
        DESCRIPTION
            "Error information about a particular PPP Link."
        INDEX   { ibmpppLinkErrorsIndex }
        ::= { ibmpppLinkErrorsTable 1 }

IbmpppLinkErrorsEntry ::= SEQUENCE {
        ibmpppLinkErrorsIndex
                INTEGER,
        ibmpppLinkBadAddresses
                Counter,
        ibmpppLinkLastBadAddress
                OCTET STRING,
        ibmpppLinkBadControls
                Counter,
        ibmpppLinkLastBadControl
                OCTET STRING,
        ibmpppLinkLastUnknownProtocol
                OCTET STRING,
        ibmpppLinkInvalidProtocols
                Counter,
        ibmpppLinkLastInvalidProtocol
                OCTET STRING,
        ibmpppLinkPacketTooLongs
                Counter,
        ibmpppLinkBadCRCs
                Counter,
        ibmpppLinkConfigTimeouts
                Counter,
        ibmpppLinkTerminateTimeouts
                Counter
        }

ibmpppLinkErrorsIndex  OBJECT-TYPE
        SYNTAX  INTEGER
        ACCESS  read-only
        STATUS  mandatory
        DESCRIPTION
            "A unique value for each PPP link. Its value ranges
            between 1 and the value of ifNumber. The interface
            identified by a particular value of this index is that
            identified by the same value of an ifIndex object
            instance. The value for each link must remain constant at
            least from one re-initialization of the entity's network
            management system to the next re-initialization."
        ::= { ibmpppLinkErrorsEntry 1 }

ibmpppLinkBadAddresses OBJECT-TYPE
        SYNTAX  Counter
        ACCESS  read-only
        STATUS  mandatory
        DESCRIPTION
            "The number of packets received with an incorrect Address
            Field. See section 3.1, Page 5, 'Address Field' of RFC 1171."
        ::= { ibmpppLinkErrorsEntry 2 }

ibmpppLinkLastBadAddress OBJECT-TYPE
        SYNTAX  OCTET STRING
        ACCESS  read-only
        STATUS  mandatory
        DESCRIPTION
            "The most recent incorrect address received on this link."
        ::= { ibmpppLinkErrorsEntry 3 }

ibmpppLinkBadControls OBJECT-TYPE
        SYNTAX  Counter
        ACCESS  read-only
        STATUS  mandatory
        DESCRIPTION
            "The number of packets received on this link with an
            incorrect Control Field. See Section 3.1, Page 5, 'Flag
            Sequence' of RFC 1171."
        ::= { ibmpppLinkErrorsEntry 4 }

ibmpppLinkLastBadControl OBJECT-TYPE
        SYNTAX  OCTET STRING
        ACCESS  read-only
        STATUS  mandatory
        DESCRIPTION
            "The most recent incorrect Control Field received on this
            link."
        ::= { ibmpppLinkErrorsEntry 5 }

ibmpppLinkLastUnknownProtocol OBJECT-TYPE
        SYNTAX  OCTET STRING
        ACCESS  read-only
        STATUS  mandatory
        DESCRIPTION
            "The most recently received unknown Protocol. An unknown
            Protocol is one which has a well-formed Protocol number,
            but which the PPP implementation does not know how to
            handle."
        ::= { ibmpppLinkErrorsEntry 6 }

ibmpppLinkInvalidProtocols OBJECT-TYPE
        SYNTAX  Counter
        ACCESS  read-only
        STATUS  mandatory
        DESCRIPTION
            "The number of times that a packet has been received with
            an invalid Protocol specified in the Protocol Field. An
            invalid Protocol is one which does not conform to the
            requirements of section 3.1, page 5 of RFC 1171."
        ::= { ibmpppLinkErrorsEntry 7 }

ibmpppLinkLastInvalidProtocol OBJECT-TYPE
        SYNTAX  OCTET STRING
        ACCESS  read-only
        STATUS  mandatory
        DESCRIPTION
            "The most recently received invalid Protocol."
        ::= { ibmpppLinkErrorsEntry 8 }

ibmpppLinkPacketTooLongs OBJECT-TYPE
        SYNTAX  Counter
        ACCESS  read-only
        STATUS  mandatory
        DESCRIPTION
            "The number of received packets that have been discarded
            because their length exceeded the MRU."
        ::= { ibmpppLinkErrorsEntry 9 }

ibmpppLinkBadCRCs OBJECT-TYPE
        SYNTAX  Counter
        ACCESS  read-only
        STATUS  mandatory
        DESCRIPTION
            "The number of received packets that have been discarded
            due to having an incorrect CRC."
        ::= { ibmpppLinkErrorsEntry 10 }

ibmpppLinkConfigTimeouts OBJECT-TYPE
        SYNTAX  Counter
        ACCESS  read-only
        STATUS  mandatory
        DESCRIPTION
            "The number of Configure Request packets that have timed
            out."
        ::= { ibmpppLinkErrorsEntry 11 }

ibmpppLinkTerminateTimeouts OBJECT-TYPE
        SYNTAX  Counter
        ACCESS  read-only
        STATUS  mandatory
        DESCRIPTION
            "The number of Terminate Request packets that have timed
            out."
        ::= { ibmpppLinkErrorsEntry 12 }

-- PPP Link Quality Management Table

ibmpppLinkQualityTable OBJECT-TYPE
        SYNTAX  SEQUENCE OF IbmpppLinkQualityEntry
        ACCESS  not-accessible
        STATUS  mandatory
        DESCRIPTION
            "A table containing PPP-link specific statistical
            information for this managed object.  An entry in this
            table is uniquely identified by the ibmpppLinkQualityIndex
            value comprised by said entry."
        ::= { ibmppp 4 }

ibmpppLinkQualityEntry   OBJECT-TYPE
        SYNTAX  IbmpppLinkQualityEntry
        ACCESS  not-accessible
        STATUS  mandatory
        DESCRIPTION
            "Link Quality Management information about a particular
            PPP Link."
        INDEX   { ibmpppLinkQualityIndex }
        ::= { ibmpppLinkQualityTable 1 }

IbmpppLinkQualityEntry ::= SEQUENCE {
        ibmpppLinkQualityIndex
                INTEGER,
        ibmpppLinkInTxLQRs
                Counter,
        ibmpppLinkInTxPackets
                Counter,
        ibmpppLinkLastOutTxPackets
                Counter,
        ibmpppLinkInTxOctets
                Counter,
        ibmpppLinkLastOutTxOctets
                Counter,
        ibmpppLinkInRxPackets
                Counter,
        ibmpppLinkLastInRxPackets
                Counter,
        ibmpppLinkInRxOctets
                Counter,
        ibmpppLinkLastInRxOctets
                Counter
        }

ibmpppLinkQualityIndex  OBJECT-TYPE
        SYNTAX  INTEGER
        ACCESS  read-only
        STATUS  mandatory
        DESCRIPTION
            "A unique value for each PPP link. Its value ranges
            between 1 and the value of ifNumber. The interface
            identified by a particular value of this index is that
            identified by the same value of an ifIndex object
            instance. The value for each link must remain constant at
            least from one re-initialization of the entity's network
            management system to the next re-initialization."
        ::= { ibmpppLinkQualityEntry 1 }

ibmpppLinkInTxLQRs OBJECT-TYPE
        SYNTAX  Counter
        ACCESS  read-only
        STATUS  mandatory
        DESCRIPTION
            "The current value of In-Tx-LQRs used in Link-Quality
            Management.  See section 3.5, page 19, of RFC 1172."
        ::= { ibmpppLinkQualityEntry 2 }

ibmpppLinkInTxPackets OBJECT-TYPE
        SYNTAX  Counter
        ACCESS  read-only
        STATUS  mandatory
        DESCRIPTION
            "The current value of the In-Tx-Packets counter used for
            Link-Quality Management.  See section 3.5, page 19, of
            RFC 1172."
        ::= { ibmpppLinkQualityEntry 3 }

ibmpppLinkLastOutTxPackets OBJECT-TYPE
        SYNTAX  Counter
        ACCESS  read-only
        STATUS  mandatory
        DESCRIPTION
            "The current value of the Last-Out-Tx-Packets-Ctr counter
            used bu Link-Quality Management. See section 3.5, page
            19, of RFC 1172."
        ::= { ibmpppLinkQualityEntry 4 }

ibmpppLinkInTxOctets OBJECT-TYPE
        SYNTAX  Counter
        ACCESS  read-only
        STATUS  mandatory
        DESCRIPTION
            "The current value of the In-Tx-Octets counter used for
            Link-Quality Management. See section 3.5, page 19, of
            RFC 1172."
        ::= { ibmpppLinkQualityEntry 5 }

ibmpppLinkLastOutTxOctets OBJECT-TYPE
        SYNTAX  Counter
        ACCESS  read-only
        STATUS  mandatory
        DESCRIPTION
            "The current value of the Last-Out-Tx-Octets-Counter
            counter used for Link-Quality Management. See section
            3.5, page 19, of RFC 1172."
        ::= { ibmpppLinkQualityEntry 6 }

ibmpppLinkInRxPackets OBJECT-TYPE
        SYNTAX  Counter
        ACCESS  read-only
        STATUS  mandatory
        DESCRIPTION
            "The current value of the In-Rx-Packets counter used for
            Link-Quality Management. See section 3.5, page 19, of
            RFC 1172."
        ::= { ibmpppLinkQualityEntry 7 }

ibmpppLinkLastInRxPackets OBJECT-TYPE
        SYNTAX  Counter
        ACCESS  read-only
        STATUS  mandatory
        DESCRIPTION
            "The current value of the Last-In-Rx-Packets-Ctr counter
            used for Link-Quality Management. See section 3.5, page
            19, of RFC 1172."
        ::= { ibmpppLinkQualityEntry 8 }

ibmpppLinkInRxOctets OBJECT-TYPE
        SYNTAX  Counter
        ACCESS  read-only
        STATUS  mandatory
        DESCRIPTION
            "The current value of the In-Rx-Octets counter used for
            Link-Quality Management. See section 3.5, page 19, of
            RFC 1172."
        ::= { ibmpppLinkQualityEntry 9 }

ibmpppLinkLastInRxOctets OBJECT-TYPE
        SYNTAX  Counter
        ACCESS  read-only
        STATUS  mandatory
        DESCRIPTION
            "The current value of the Last-In-Rx-Octets-Ctr counter
            used for Link-Quality Management. See section 3.5, page
            19, of RFC 1172."
        ::= { ibmpppLinkQualityEntry 10 }

-- PPP protocol tables

ibmpppProtocolTables   OBJECT IDENTIFIER ::= { ibmppp 5 }


-- IP Over PPP Table

ibmpppIPTable OBJECT-TYPE
        SYNTAX  SEQUENCE OF IbmpppIPEntry
        ACCESS  not-accessible
        STATUS  mandatory
        DESCRIPTION
            "A table containing specific information for the running
            of the IP over PPP in this managed object.  An entry in
            this table is uniquely identified by the ibmpppIPLinkNumber
            value comprised by said entry."
        ::= { ibmpppProtocolTables 1 }

ibmpppIPEntry OBJECT-TYPE
        SYNTAX  IbmpppIPEntry
        ACCESS  not-accessible
        STATUS  mandatory
        DESCRIPTION
            "All information pertinant to running the IP over a single
            PPP link."
        INDEX   { ibmpppIPLinkNumber }
        ::= { ibmpppIPTable 1 }

IbmpppIPEntry ::= SEQUENCE {
        ibmpppIPLinkNumber
                INTEGER,
        ibmpppIPRejects
                Counter,
        ibmpppIPInPackets
                Counter,
        ibmpppIPInOctets
                Counter,
        ibmpppIPOutPackets
                Counter,
        ibmpppIPOutOctets
                Counter
}

ibmpppIPLinkNumber OBJECT-TYPE
        SYNTAX  INTEGER
        ACCESS  read-only
        STATUS  mandatory
        DESCRIPTION
            "The value of ibmpppLinkIndex for the link over which this
            instance of the IP is being run."
        ::= { ibmpppIPEntry 1 }

ibmpppIPRejects OBJECT-TYPE
        SYNTAX  Counter
        ACCESS  read-only
        STATUS  mandatory
        DESCRIPTION
            "The number of Protocol Reject Messages received when
            attempting to send an IP packet over the link identified
            by ibmpppIPLinkNumber."
        ::= { ibmpppIPEntry 2 }

ibmpppIPInPackets OBJECT-TYPE
        SYNTAX  Counter
        ACCESS  read-only
        STATUS  mandatory
        DESCRIPTION
            "The number of IP packets received on the link identified
            by ibmpppIPLinkNumber."
        ::= { ibmpppIPEntry 3 }

ibmpppIPInOctets OBJECT-TYPE
        SYNTAX  Counter
        ACCESS  read-only
        STATUS  mandatory
        DESCRIPTION
            "The number of octets received in IP packets received on
            the link identified by ibmpppIPLinkNumber. Only octets in
            the PPP Information Field are counted. Octets inserted
            for transparency are not counted. Padding octets are not
            counted."
        ::= { ibmpppIPEntry 4 }

ibmpppIPOutPackets OBJECT-TYPE
        SYNTAX  Counter
        ACCESS  read-only
        STATUS  mandatory
        DESCRIPTION
            "The number of IP packets sent on the link identified by
            ibmpppIPLinkNumber."
        ::= { ibmpppIPEntry 5 }


ibmpppIPOutOctets OBJECT-TYPE
        SYNTAX  Counter
        ACCESS  read-only
        STATUS  mandatory
        DESCRIPTION
            "The number of octets all in IP Packets sent on the link
            identified by ibmpppIPLinkNumber. Only octets in the PPP
            Information Field are counted. Octets inserted for
            transparency are not counted. Padding octets are not
            counted."
        ::= { ibmpppIPEntry 6 }


-- IP Control Protocol Table

ibmpppIPCPTable OBJECT-TYPE
        SYNTAX  SEQUENCE OF IbmpppIPCPEntry
        ACCESS  not-accessible
        STATUS  mandatory
        DESCRIPTION
            "A table containing specific information for the running
            of the IPCP over PPP in this managed object.  An entry in
            this table is uniquely identified by the
            ibmpppIPCPLinkNumber value comprised by said entry."
        ::= { ibmpppProtocolTables 2 }

ibmpppIPCPEntry OBJECT-TYPE
        SYNTAX  IbmpppIPCPEntry
        ACCESS  not-accessible
        STATUS  mandatory
        DESCRIPTION
            "All information pertinant to running the IPCP over a
            single PPP link."
        INDEX   { ibmpppIPCPLinkNumber }
        ::= { ibmpppIPCPTable 1 }

IbmpppIPCPEntry ::= SEQUENCE {
        ibmpppIPCPLinkNumber
                INTEGER,
        ibmpppIPCPRejects
                Counter,
        ibmpppIPCPInPackets
                Counter,
        ibmpppIPCPInOctets
                Counter,
        ibmpppIPCPOutPackets
                Counter,
        ibmpppIPCPOutOctets
                Counter,
        ibmpppIPCPCompressionType
                INTEGER
        }

ibmpppIPCPLinkNumber OBJECT-TYPE
        SYNTAX  INTEGER
        ACCESS  read-only
        STATUS  mandatory
        DESCRIPTION
            "The value of ibmpppLinkIndex for the link over which this
            instance of the IPCP is being run."
        ::= { ibmpppIPCPEntry 1 }


ibmpppIPCPRejects OBJECT-TYPE
        SYNTAX  Counter
        ACCESS  read-only
        STATUS  mandatory
        DESCRIPTION
            "The number of Protocol Reject Messages received when
            attempting to send an IPCP Packet over the link
            identified by ibmpppIPCPLinkNumber."
        ::= { ibmpppIPCPEntry 2 }

ibmpppIPCPInPackets OBJECT-TYPE
        SYNTAX  Counter
        ACCESS  read-only
        STATUS  mandatory
        DESCRIPTION
            "The number of IPCP packets received on the link
            identified by ibmpppIPCPLinkNumber."
        ::= { ibmpppIPCPEntry 3 }

ibmpppIPCPInOctets OBJECT-TYPE
        SYNTAX  Counter
        ACCESS  read-only
        STATUS  mandatory
        DESCRIPTION
            "The number of octets received in IPCP packets received on
            the link identified by ibmpppIPCPLinkNumber. Only octets in
            the PPP Information Field are counted. Octets inserted
            for transparency are not counted. Padding octets are not
            counted."
        ::= { ibmpppIPCPEntry 4 }

ibmpppIPCPOutPackets OBJECT-TYPE
        SYNTAX  Counter
        ACCESS  read-only
        STATUS  mandatory
        DESCRIPTION
            "The number of IPCP packets sent on the link identified by
            ibmpppIPLinkNumber."
        ::= { ibmpppIPCPEntry 5 }

ibmpppIPCPOutOctets OBJECT-TYPE
        SYNTAX  Counter
        ACCESS  read-only
        STATUS  mandatory
        DESCRIPTION
            "The number of octets all in IPCP packets sent on the link
            identified by ibmpppIPCPLinkNumber. Only octets in the PPP
            Information Field are counted. Octets inserted for
            transparency are not counted. Padding octets are not
            counted."
        ::= { ibmpppIPCPEntry 6 }

ibmpppIPCPCompressionType OBJECT-TYPE
        SYNTAX  INTEGER {
                     none(1),
                     van-jacobson-compressed-tcp(2)
                }
        ACCESS  read-only
        STATUS  mandatory
        DESCRIPTION
            "The compression type used on this link as defined in
            section 5.2 of RFC 1172.  The numerical values that this
            object can be are the same as the numerical values that
            are included in the IPCP compression option configuration
            packets.

            The IBM 6611 Network Processor always provides a
            value of none(1) for this object."
        ::= { ibmpppIPCPEntry 7 }


-- Link Control Protocol table

ibmpppLCPTable OBJECT-TYPE
        SYNTAX  SEQUENCE OF IbmpppLCPEntry
        ACCESS  not-accessible
        STATUS  mandatory
        DESCRIPTION
            "A table containing specific information for the running
            of LCP over PPP in this managed object.  An entry in this
            table is uniquely identified by the ibmpppLCPLinkNumber
            value comprised by said entry."
        ::= { ibmpppProtocolTables 3 }

ibmpppLCPEntry OBJECT-TYPE
        SYNTAX  IbmpppLCPEntry
        ACCESS  not-accessible
        STATUS  mandatory
        DESCRIPTION
            "All information pertinant to running LCP over a single
            PPP link."
        INDEX   { ibmpppLCPLinkNumber }
        ::= { ibmpppLCPTable 1 }

IbmpppLCPEntry ::= SEQUENCE {
        ibmpppLCPLinkNumber
                INTEGER,
        ibmpppLCPRejects
                Counter,
        ibmpppLCPInPackets
                Counter,
        ibmpppLCPInOctets
                Counter,
        ibmpppLCPOutPackets
                Counter,
        ibmpppLCPOutOctets
                Counter,
        ibmpppLCPOutCRs
                Counter,
        ibmpppLCPInCRs
                Counter,
        ibmpppLCPOutCAs
                Counter,
        ibmpppLCPInCAs
                Counter,
        ibmpppLCPOutCNs
                Counter,
        ibmpppLCPInCNs
                Counter,
        ibmpppLCPOutCRejs
                Counter,
        ibmpppLCPInCRejs
                Counter,
        ibmpppLCPOutTRs
                Counter,
        ibmpppLCPInTRs
                Counter,
        ibmpppLCPOutTAs
                Counter,
        ibmpppLCPInTAs
                Counter,
        ibmpppLCPOutCodeRejs
                Counter,
        ibmpppLCPInCodeRejs
                Counter,
        ibmpppLCPOutEchoReqs
                Counter,
        ibmpppLCPInEchoReqs
                Counter,
        ibmpppLCPOutEchoReps
                Counter,
        ibmpppLCPInEchoReps
                Counter,
        ibmpppLCPOutDiscReqs
                Counter,
        ibmpppLCPInDiscReqs
                Counter
}

ibmpppLCPLinkNumber OBJECT-TYPE
        SYNTAX  INTEGER
        ACCESS  read-only
        STATUS  mandatory
        DESCRIPTION
            "The value of ibmpppLinkIndex for the link over which this
            instance of LCP is being run."
        ::= { ibmpppLCPEntry 1 }

ibmpppLCPRejects OBJECT-TYPE
        SYNTAX  Counter
        ACCESS  read-only
        STATUS  mandatory
        DESCRIPTION
            "The number of Protocol Reject Messages received when
            attempting to send an LCP packet over the link identified
            by ibmpppLCPLinkNumber. This really ought not to happen."
        ::= { ibmpppLCPEntry 2 }

ibmpppLCPInPackets OBJECT-TYPE
        SYNTAX  Counter
        ACCESS  read-only
        STATUS  mandatory
        DESCRIPTION
            "The number of LCP packets received on the link identified
            by ibmpppLCPLinkNumber."
        ::= { ibmpppLCPEntry 3 }

ibmpppLCPInOctets OBJECT-TYPE
        SYNTAX  Counter
        ACCESS  read-only
        STATUS  mandatory
        DESCRIPTION
            "The number of octets received in LCP packets received on
            the link identified by ibmpppLCPLinkNumber. Only octets in
            the PPP Information Field are counted. Octets inserted
            for transparency are not counted. Padding octets are not
            counted."
        ::= { ibmpppLCPEntry 4 }

ibmpppLCPOutPackets OBJECT-TYPE
        SYNTAX  Counter
        ACCESS  read-only
        STATUS  mandatory
        DESCRIPTION
            "The number of LCP packets sent on the link identified by
            ibmpppLCPLinkNumber."
        ::= { ibmpppLCPEntry 5 }

ibmpppLCPOutOctets OBJECT-TYPE
        SYNTAX  Counter
        ACCESS  read-only
        STATUS  mandatory
        DESCRIPTION
            "The number of octets all in LCP packets sent on the link
            identified by ibmpppLCPLinkNumber. Only octets in the PPP
            Information Field are counted. Octets inserted for
            transparency are not counted. Padding octets are not
            counted."
        ::= { ibmpppLCPEntry 6 }

ibmpppLCPOutCRs OBJECT-TYPE
        SYNTAX  Counter
        ACCESS  read-only
        STATUS  mandatory
        DESCRIPTION
            "Number of Configuration Request packets sent on this
            link."
        ::= { ibmpppLCPEntry 7 }

ibmpppLCPInCRs OBJECT-TYPE
        SYNTAX  Counter
        ACCESS  read-only
        STATUS  mandatory
        DESCRIPTION
            "Number of Configuration Request packets received on this
            link."
        ::= { ibmpppLCPEntry 8 }

ibmpppLCPOutCAs OBJECT-TYPE
        SYNTAX  Counter
        ACCESS  read-only
        STATUS  mandatory
        DESCRIPTION
            "Number of Configuration Acknowledge packets sent on this
            link."
        ::= { ibmpppLCPEntry 9 }

ibmpppLCPInCAs OBJECT-TYPE
        SYNTAX  Counter
        ACCESS  read-only
        STATUS  mandatory
        DESCRIPTION
            "Number of Configuration Acknowledge packets received on
            this link."
        ::= { ibmpppLCPEntry 10 }

ibmpppLCPOutCNs OBJECT-TYPE
        SYNTAX  Counter
        ACCESS  read-only
        STATUS  mandatory
        DESCRIPTION
            "Number of Configuration NAK packets sent on this link."
        ::= { ibmpppLCPEntry 11 }

ibmpppLCPInCNs OBJECT-TYPE
        SYNTAX  Counter
        ACCESS  read-only
        STATUS  mandatory
        DESCRIPTION
            "Number of Configuration NAK packets received on this
            link."
        ::= { ibmpppLCPEntry 12 }

ibmpppLCPOutCRejs OBJECT-TYPE
        SYNTAX  Counter
        ACCESS  read-only
        STATUS  mandatory
        DESCRIPTION
            "Number of Configuration Reject packets sent on this link."
        ::= { ibmpppLCPEntry 13 }

ibmpppLCPInCRejs OBJECT-TYPE
        SYNTAX  Counter
        ACCESS  read-only
        STATUS  mandatory
        DESCRIPTION
            "Number of Configuration Reject packets received on this
            link."
        ::= { ibmpppLCPEntry 14 }

ibmpppLCPOutTRs OBJECT-TYPE
        SYNTAX  Counter
        ACCESS  read-only
        STATUS  mandatory
        DESCRIPTION
            "Number of Terminate Request packets sent on this link."
        ::= { ibmpppLCPEntry 15 }

ibmpppLCPInTRs OBJECT-TYPE
        SYNTAX  Counter
        ACCESS  read-only
        STATUS  mandatory
        DESCRIPTION
            "Number of Terminate Request packets received on this
            link."
        ::= { ibmpppLCPEntry 16 }

ibmpppLCPOutTAs OBJECT-TYPE
        SYNTAX  Counter
        ACCESS  read-only
        STATUS  mandatory
        DESCRIPTION
            "Number of Terminate Acknowledge packets sent on this
            link."
        ::= { ibmpppLCPEntry 17 }

ibmpppLCPInTAs OBJECT-TYPE
        SYNTAX  Counter
        ACCESS  read-only
        STATUS  mandatory
        DESCRIPTION
            "Number of Terminate Acknowledge packets received on this
            link."
        ::= { ibmpppLCPEntry 18 }

ibmpppLCPOutCodeRejs OBJECT-TYPE
        SYNTAX  Counter
        ACCESS  read-only
        STATUS  mandatory
        DESCRIPTION
            "Number of Code Reject packets sent on this link."
        ::= { ibmpppLCPEntry 19 }

ibmpppLCPInCodeRejs OBJECT-TYPE
        SYNTAX  Counter
        ACCESS  read-only
        STATUS  mandatory
        DESCRIPTION
            "Number of Code Reject packets received on this link."
        ::= { ibmpppLCPEntry 20 }

ibmpppLCPOutEchoReqs OBJECT-TYPE
        SYNTAX  Counter
        ACCESS  read-only
        STATUS  mandatory
        DESCRIPTION
            "Number of Echo Request packets sent on this link."
        ::= { ibmpppLCPEntry 21 }

ibmpppLCPInEchoReqs OBJECT-TYPE
        SYNTAX  Counter
        ACCESS  read-only
        STATUS  mandatory
        DESCRIPTION
            "Number of Echo Request packets received on this link."
        ::= { ibmpppLCPEntry 22 }

ibmpppLCPOutEchoReps OBJECT-TYPE
        SYNTAX  Counter
        ACCESS  read-only
        STATUS  mandatory
        DESCRIPTION
            "Number of Echo Reply packets sent on this link."
        ::= { ibmpppLCPEntry 23 }

ibmpppLCPInEchoReps OBJECT-TYPE
        SYNTAX  Counter
        ACCESS  read-only
        STATUS  mandatory
        DESCRIPTION
            "Number of Echo Reply packets received on this link."
        ::= { ibmpppLCPEntry 24 }

ibmpppLCPOutDiscReqs OBJECT-TYPE
        SYNTAX  Counter
        ACCESS  read-only
        STATUS  mandatory
        DESCRIPTION
            "Number of Discard Request packets sent on this link."
        ::= { ibmpppLCPEntry 25 }

ibmpppLCPInDiscReqs OBJECT-TYPE
        SYNTAX  Counter
        ACCESS  read-only
        STATUS  mandatory
        DESCRIPTION
            "Number of Discard Request packets received on this link."
        ::= { ibmpppLCPEntry 26 }

-- The Password Authentication Protocol Table is not supported by
-- the IBM 6611 Network Processor.

-- static char sccsid_xns_mib[] = "@(#) snmp/samples/xns.my, SNMP, v1r3, r3d48  3/14/94 17:35:35";

------------------------------------------------------------------------
-- The IBM 6611 XNS Extension                                          -
------------------------------------------------------------------------


--IbmXnsAddress ::= OCTET STRING (SIZE(12))

--IbmXnsNetworkAddress ::= OCTET STRING (SIZE(4))



ibmxnsidpForwarding OBJECT-TYPE
    SYNTAX  INTEGER {
                forwarding(1),
                not-forwarding(2)
            }
    ACCESS  read-only
    STATUS  mandatory
    DESCRIPTION
            "Indicates if this node is acting as an XNS router."
    ::= { ibmxns 1 }


------------------------------------------------------------------------
-- The XNS Port Configuration Table
------------------------------------------------------------------------

ibmxnsConfigTable OBJECT-TYPE
    SYNTAX  SEQUENCE OF IbmXnsConfigEntry
    ACCESS  not-accessible
    STATUS  mandatory
    DESCRIPTION
        "The table of XNS configuration information gathered on a
         per-interface basis."
    ::= { ibmxns 4 }

ibmxnsConfigEntry OBJECT-TYPE
    SYNTAX  IbmXnsConfigEntry
    ACCESS  not-accessible
    STATUS  mandatory
    DESCRIPTION
            "XNS configuration information for a single interface."
    INDEX   { ibmxnsPortIfIndex }
    ::= { ibmxnsConfigTable 1 }

IbmXnsConfigEntry ::=
    SEQUENCE {
        ibmxnsPortIfIndex
            INTEGER,
        ibmxnsPortStatus
            INTEGER,
        ibmxnsidpChecksum
            INTEGER,
        ibmxnsErrpActive
            INTEGER,
        ibmxnsLoopbackActive
            INTEGER
    }

ibmxnsPortIfIndex OBJECT-TYPE
    SYNTAX  INTEGER
    ACCESS  read-only
    STATUS  mandatory
    DESCRIPTION
            "The value of this object identifies the interface for which
            this entry contains management information.  The value of
            this object for a particular interface has the same value
            as the ifIndex object for the same interface."
    ::= { ibmxnsConfigEntry 1 }

ibmxnsPortStatus OBJECT-TYPE
    SYNTAX  INTEGER {
                active(1),
                inactive(2)
            }
    ACCESS  read-only
    STATUS  mandatory
    DESCRIPTION
            "The status of the XNS protocol stack on this interface."
    ::= { ibmxnsConfigEntry 2 }

ibmxnsidpChecksum OBJECT-TYPE
    SYNTAX  INTEGER {
                off(1),     -- no checksumming
                header(2),  -- checksumming header only
                packet(3)   -- checksumming done on entire packet
            }
    ACCESS  read-only
    STATUS  mandatory
    DESCRIPTION
            "Indicates the type of checksumming being done by IDP."
    ::= { ibmxnsConfigEntry 3 }

ibmxnsErrpActive OBJECT-TYPE
    SYNTAX  INTEGER {
                active(1),
                suppressed(2)
            }
    ACCESS  read-only
    STATUS  mandatory
    DESCRIPTION
            "Indicates if this port is originating error protocol packets."
    ::= { ibmxnsConfigEntry 4 }

ibmxnsLoopbackActive OBJECT-TYPE
    SYNTAX  INTEGER {
                software-loopback-active(1),
                hardware-loopback-active(2)
            }
    ACCESS  read-only
    STATUS  mandatory
    DESCRIPTION
            "Indicates if this port will use the hardware to loopback
             locally addressed packets or return the packet to the
             system via a software loopback."

    ::= { ibmxnsConfigEntry 5 }


------------------------------------------------------------------------
-- XNS IDP Statistics
------------------------------------------------------------------------

ibmxnsidpInReceives OBJECT-TYPE
    SYNTAX  Counter
    ACCESS  read-only
    STATUS  mandatory
    DESCRIPTION
            "Total number of IDP datagrams received."
    ::= { ibmxns 5 }

ibmxnsidpBcastInReceives OBJECT-TYPE
    SYNTAX  Counter
    ACCESS  read-only
    STATUS  mandatory
    DESCRIPTION
            "Number of IDP broadcast datagrams received."
    ::= { ibmxns 6 }

ibmxnsidpMcastInReceives OBJECT-TYPE
    SYNTAX  Counter
    ACCESS  read-only
    STATUS  mandatory
    DESCRIPTION
            "Number of IDP multicast datagrams received."
    ::= { ibmxns 7 }

ibmxnsidpInDiscards OBJECT-TYPE
    SYNTAX  Counter
    ACCESS  read-only
    STATUS  mandatory
    DESCRIPTION
            "Number of incoming IDP datagrams discarded due to lack
            of resources."
    ::= { ibmxns 8 }

-- { ibmxns 9 } unused

-- { ibmxns 10 } unused

ibmxnsidpOutRequests OBJECT-TYPE
    SYNTAX  Counter
    ACCESS  read-only
    STATUS  mandatory
    DESCRIPTION
            "Number of IDP datagrams generated by local IDP
            user protocols.  This counter does not include
            any datagrams counted in ibmxnsidpForwDatagrams."
    ::= { ibmxns 11 }

ibmxnsidpBcastOutRequests OBJECT-TYPE
    SYNTAX  Counter
    ACCESS  read-only
    STATUS  mandatory
    DESCRIPTION
            "Number of IDP broadcast datagrams generated by local IDP
            user protocols.  This counter does not include
            any datagrams counted in ibmxnsidpForwDatagrams."
    ::= { ibmxns 12 }

ibmxnsidpMcastOutRequests OBJECT-TYPE
    SYNTAX  Counter
    ACCESS  read-only
    STATUS  mandatory
    DESCRIPTION
            "Number of IDP multicast datagrams generated by
            local IDP user protocols.  This counter does not
            include any datagrams counted in ibmxnsidpForwDatagrams."
    ::= { ibmxns 13 }

ibmxnsidpForwDatagrams OBJECT-TYPE
    SYNTAX  Counter
    ACCESS  read-only
    STATUS  mandatory
    DESCRIPTION
            "Number of IDP datagrams for which an attempt was made
            to forward."
    ::= { ibmxns 14 }

ibmxnsidpOutDiscards OBJECT-TYPE
    SYNTAX  Counter
    ACCESS  read-only
    STATUS  mandatory
    DESCRIPTION
            "Total number of outgoing IDP datagrams discarded."
    ::= { ibmxns 15 }

ibmxnsidpOutNoRoutes OBJECT-TYPE
    SYNTAX  Counter
    ACCESS  read-only
    STATUS  mandatory
    DESCRIPTION
            "Number of outgoing IDP datagrams discarded because
            no route was available to the specified destination."
    ::= { ibmxns 16 }

ibmxnsidpRoutingDiscards OBJECT-TYPE
    SYNTAX  Counter
    ACCESS  read-only
    STATUS  mandatory
    DESCRIPTION
            "Number of routing entries discarded even though they
            were valid."
    ::= { ibmxns 17 }

-- { ibmxns 18 } unused

ibmxnsidpZeroDirBcast OBJECT-TYPE
    SYNTAX  Counter
    ACCESS  read-only
    STATUS  mandatory
    DESCRIPTION
            "Number of IDP datagrams forwarded to the system due
            to zeronet broadcast."
    ::= { ibmxns 19 }

ibmxnsidpTooSmall OBJECT-TYPE
    SYNTAX  Counter
    ACCESS  read-only
    STATUS  mandatory
    DESCRIPTION
            "Number of IDP datagrams with len < the size of an IDP header."
    ::= { ibmxns 20 }

ibmxnsidpBadLen OBJECT-TYPE
    SYNTAX  Counter
    ACCESS  read-only
    STATUS  mandatory
    DESCRIPTION
            "Number of IDP datagrams with
             number of bytes in the packet less than the
             number of bytes specified in the IDP header field."
    ::= { ibmxns 21 }

ibmxnsidpBadSum OBJECT-TYPE
    SYNTAX  Counter
    ACCESS  read-only
    STATUS  mandatory
    DESCRIPTION
            "Number of IDP datagrams with a bad checksum"
    ::= { ibmxns 22 }

ibmxnsidpBadTTL OBJECT-TYPE
    SYNTAX  Counter
    ACCESS  read-only
    STATUS  mandatory
    DESCRIPTION
            "Number of IDP datagrams with
             TTL value > IDP maximum hopcount of 16."
    ::= { ibmxns 23 }


------------------------------------------------------------------------
-- XNS Error Statistics
------------------------------------------------------------------------

ibmxnsErrUnspec OBJECT-TYPE
    SYNTAX  Counter
    ACCESS  read-only
    STATUS  mandatory
    DESCRIPTION
            "Number of Error packets generated because an IDP
            datagram was dropped for unspecified reasons."
    ::= { ibmxns 24 }

ibmxnsErrChecksum OBJECT-TYPE
    SYNTAX  Counter
    ACCESS  read-only
    STATUS  mandatory
    DESCRIPTION
            "Number of Error packets generated because an IDP
            datagram was dropped due a bad checksum."
    ::= { ibmxns 25 }

ibmxnsErrUnreach OBJECT-TYPE
    SYNTAX  Counter
    ACCESS  read-only
    STATUS  mandatory
    DESCRIPTION
            "Number of Error packets generated because an IDP
            datagram was dropped due to an unreachable host."
    ::= { ibmxns 26 }

ibmxnsErrTTLExpired OBJECT-TYPE
    SYNTAX  Counter
    ACCESS  read-only
    STATUS  mandatory
    DESCRIPTION
            "Number of Error packets generated because an IDP
            datagram was dropped because its time-to-live
            counter had expired."
    ::= { ibmxns 27 }

ibmxnsErrTooBig OBJECT-TYPE
    SYNTAX  Counter
    ACCESS  read-only
    STATUS  mandatory
    DESCRIPTION
            "Number of Error packets generated because an IDP
            datagram was dropped because it was too large
            to be forwarded through this node."
    ::= { ibmxns 28 }

ibmxnsErrResources OBJECT-TYPE
    SYNTAX  Counter
    ACCESS  read-only
    STATUS  mandatory
    DESCRIPTION
            "Number of Error packets generated because an IDP
            datagram was dropped due to lack of resources."
    ::= { ibmxns 29 }

ibmxnsErrCongWarn OBJECT-TYPE
    SYNTAX  Counter
    ACCESS  read-only
    STATUS  mandatory
    DESCRIPTION
            "Number of Error packets generated for congestion
            warnings."
    ::= { ibmxns 30 }

ibmxnsErrCongDiscard OBJECT-TYPE
    SYNTAX  Counter
    ACCESS  read-only
    STATUS  mandatory
    DESCRIPTION
            "Number of Error packets generated for congestion
            discards."
    ::= { ibmxns 31 }

ibmxnsErrSquelched OBJECT-TYPE
    SYNTAX  Counter
    ACCESS  read-only
    STATUS  mandatory
    DESCRIPTION
        "Number of error packets that would have been generated,
        except that the faulted datagram had one of the following
        conditions:

            - was sent as link layer broadcast
            - NS destination was broadcast
            - NS source was 0, loopback, or broadcast"
    ::= { ibmxns 32 }

ibmxnsErrOutMsgs OBJECT-TYPE
    SYNTAX  Counter
    ACCESS  read-only
    STATUS  mandatory
    DESCRIPTION
            "Total number of error packets generated."
    ::= { ibmxns 33 }


------------------------------------------------------------------------
-- The XNS Address Table
------------------------------------------------------------------------

ibmxnsAddrTable OBJECT-TYPE
    SYNTAX  SEQUENCE OF IbmXnsAddrEntry
    ACCESS  not-accessible
    STATUS  mandatory
    DESCRIPTION
            "The XNS Address Table."
    ::= { ibmxns 34 }

ibmxnsAddrEntry OBJECT-TYPE
    SYNTAX  IbmXnsAddrEntry
    ACCESS  not-accessible
    STATUS  mandatory
    DESCRIPTION
            "An entry in the XNS address table."
    INDEX   { ibmxnsAddrAddress }
    ::= { ibmxnsAddrTable 1 }

IbmXnsAddrEntry ::=
    SEQUENCE {
        ibmxnsAddrAddress
            OCTET STRING,
        ibmxnsAddrIfIndex
            INTEGER
    }

ibmxnsAddrAddress OBJECT-TYPE
    SYNTAX  OCTET STRING (SIZE(12))
    ACCESS  read-only
    STATUS  mandatory
    DESCRIPTION
            "The XNS address to which this entry's addressing
            information pertains."
    ::= { ibmxnsAddrEntry 1 }

ibmxnsAddrIfIndex OBJECT-TYPE
    SYNTAX  INTEGER
    ACCESS  read-only
    STATUS  mandatory
    DESCRIPTION
            "The interface index which identifies the
            interface to which this entry is applicable."
    ::= { ibmxnsAddrEntry 2 }


------------------------------------------------------------------------
-- The XNS Route Table
------------------------------------------------------------------------

ibmxnsRouteTable OBJECT-TYPE
    SYNTAX  SEQUENCE OF IbmXnsRouteEntry
    ACCESS  not-accessible
    STATUS  mandatory
    DESCRIPTION
            "The XNS Route Table."
    ::= { ibmxns 35 }

ibmxnsRouteEntry OBJECT-TYPE
    SYNTAX  IbmXnsRouteEntry
    ACCESS  not-accessible
    STATUS  mandatory
    DESCRIPTION
            "An entry in the XNS route table."
    INDEX   { ibmxnsRouteDest }
    ::= { ibmxnsRouteTable 1 }

IbmXnsRouteEntry ::=
    SEQUENCE {
        ibmxnsRouteDest
            OCTET STRING,
        ibmxnsRouteIfIndex
            INTEGER,
        ibmxnsRouteNextHop
            OCTET STRING,
        ibmxnsRouteMetric
            INTEGER,
        ibmxnsRouteUse
            Counter
    }

ibmxnsRouteDest OBJECT-TYPE
    SYNTAX  OCTET STRING (SIZE(12))
    ACCESS  read-only
    STATUS  mandatory
    DESCRIPTION
            "The desination network of this route."
    ::= { ibmxnsRouteEntry 1 }

ibmxnsRouteIfIndex OBJECT-TYPE
    SYNTAX  INTEGER
    ACCESS  read-only
    STATUS  mandatory
    DESCRIPTION
            "The index value which identifies the local interface
             through which the next hop of this route should be
             reached."
    ::= { ibmxnsRouteEntry 2 }

ibmxnsRouteNextHop OBJECT-TYPE
    SYNTAX  OCTET STRING (SIZE(4))
    ACCESS  read-only
    STATUS  mandatory
    DESCRIPTION
            "The XNS network address of the next hop of this route."
    ::= { ibmxnsRouteEntry 3 }

ibmxnsRouteMetric OBJECT-TYPE
    SYNTAX  INTEGER
    ACCESS  read-only
    STATUS  mandatory
    DESCRIPTION
            "The hop count to the destination."
    ::= { ibmxnsRouteEntry 4 }

ibmxnsRouteUse OBJECT-TYPE
    SYNTAX  Counter
    ACCESS  read-only
    STATUS  mandatory
    DESCRIPTION
            "Reference counter for this route."
    ::= { ibmxnsRouteEntry 5 }


------------------------------------------------------------------------
-- The XNS Filter Table
------------------------------------------------------------------------

ibmxnsFilterTable OBJECT-TYPE
    SYNTAX  SEQUENCE OF IbmXnsFilterEntry
    ACCESS  not-accessible
    STATUS  mandatory
    DESCRIPTION
            "The XNS Filter Table."
    ::= { ibmxns 36 }

ibmxnsFilterEntry OBJECT-TYPE
    SYNTAX  IbmXnsFilterEntry
    ACCESS  not-accessible
    STATUS  mandatory
    DESCRIPTION
            "An entry in the XNS filter table."
    INDEX   { ibmxnsFilterIfIndex, ibmxnsFilterNumber }
    ::= { ibmxnsFilterTable 1 }

IbmXnsFilterEntry ::=
    SEQUENCE {
        ibmxnsFilterIfIndex
            INTEGER,
        ibmxnsFilterNumber
            INTEGER,
        ibmxnsFilterValue
            OCTET STRING,
        ibmxnsFilterMask
            OCTET STRING,
        ibmxnsFilterType
            INTEGER,
        ibmxnsFilterHCCompare
            INTEGER,
        ibmxnsFilterUse
            Counter
    }

ibmxnsFilterIfIndex OBJECT-TYPE
    SYNTAX  INTEGER
    ACCESS  read-only
    STATUS  mandatory
    DESCRIPTION
            "The value of this object identifies the interface for which
            this entry contains management information.  The value of
            this object for a particular interface has the same value
            as the ifIndex object for the same interface."
    ::= { ibmxnsFilterEntry 1 }

ibmxnsFilterNumber OBJECT-TYPE
    SYNTAX  INTEGER
    ACCESS  read-only
    STATUS  mandatory
    DESCRIPTION
            "A unique integer identifying this filter entry for this
            interface."
    ::= { ibmxnsFilterEntry 2 }

ibmxnsFilterValue OBJECT-TYPE
    SYNTAX  OCTET STRING (SIZE (30))
    ACCESS  read-only
    STATUS  mandatory
    DESCRIPTION
            "An octet string representing the IDP header information
            required by this filter entry. Incoming IDP packets will
            be bitwise ANDed with the value of ibmxnsFilterMask, and
            if the result is equal to the value of this object, the
            packet will be filtered according to the value of
            ibmxnsFilterType.

            The structure of an IDP header is as follows:

                BIT16   checksum
                BIT16   length
                BIT8    transport control (ie. hop count)
                BIT8    packet type
                BIT32   destination network address
                BIT48   destination host address
                BIT16   destination socket
                BIT32   source network address
                BIT48   source host address
                BIT16   source socket
            "
    ::= { ibmxnsFilterEntry 3 }

ibmxnsFilterMask OBJECT-TYPE
    SYNTAX  OCTET STRING (SIZE (30))
    ACCESS  read-only
    STATUS  mandatory
    DESCRIPTION
            "An octet string indicating the parts of the IDP header
            relevant to this filter entry. This mask will be bitwise
            ANDed with the IDP packet; if the result is equal to
            the value of ibmxnsFilterValue, the packet will be filtered
            according to the value of ibmxnsFilterType."
    ::= { ibmxnsFilterEntry 4 }

ibmxnsFilterType OBJECT-TYPE
    SYNTAX  INTEGER {
                deny(1),    -- frames matching filter criteria are denied
                permit(2)   -- frames matching filter criteria are permitted
            }
    ACCESS  read-only
    STATUS  mandatory
    DESCRIPTION
            "Determines whether this filter is a deny entry
            or a permit entry."
    ::= { ibmxnsFilterEntry 5 }

ibmxnsFilterHCCompare OBJECT-TYPE
    SYNTAX  INTEGER {
                none(1),
                less-than(2),
                less-than-equal(3),
                equal(4),
                greater-than-equal(5),
                greater-than(6)
            }
    ACCESS  read-only
    STATUS  mandatory
    DESCRIPTION
            "Indicates the relational association desired if filtering
            is being done based on hop count. If filtering is not being
            done based on hop count (that is, if the hop count portion
            of ibmxnsFilterMask is 0) the value of this object will
            be none(1)."
    ::= { ibmxnsFilterEntry 6 }

ibmxnsFilterUse OBJECT-TYPE
    SYNTAX  Counter
    ACCESS  read-only
    STATUS  mandatory
    DESCRIPTION
            "Usage count for this filter entry."
    ::= { ibmxnsFilterEntry 7 }


-- Local Variables:
-- tab-width: 4
-- case-fold-search: nil
-- End:

-- static char sccsid_ipx_mib[] = "@(#) snmp/samples/ipx.my, SNMP, v1r3, r3d48  3/14/94 17:35:48";

------------------------------------------------------------------------
-- The IBM 6611 IPX Extension                                          -
------------------------------------------------------------------------


--IbmIpxAddress ::= OCTET STRING (SIZE(12))
--IbmIpxNetworkAddress ::= OCTET STRING (SIZE(4))
--IbmIpxHostAddress ::= OCTET STRING (SIZE(6))

ibmipxidpForwarding OBJECT-TYPE
    SYNTAX  INTEGER {
                forwarding(1),
                not-forwarding(2)
            }
    ACCESS  read-only
    STATUS  mandatory
    DESCRIPTION
            "Indicates if this node is acting as an IPX router."
    ::= { ibmipx 1 }

------------------------------------------------------------------------
-- The IPX Port Configuration Table
------------------------------------------------------------------------

ibmipxConfigTable OBJECT-TYPE
    SYNTAX  SEQUENCE OF IbmIpxConfigEntry
    ACCESS  not-accessible
    STATUS  mandatory
    DESCRIPTION
        "The table of IPX configuration information gathered on a
         per-interface basis."
    ::= { ibmipx 4 }

ibmipxConfigEntry OBJECT-TYPE
    SYNTAX  IbmIpxConfigEntry
    ACCESS  not-accessible
    STATUS  mandatory
    DESCRIPTION
            "IPX configuration information for a single interface."
    INDEX   { ibmipxPortIfIndex }
    ::= { ibmipxConfigTable 1 }

IbmIpxConfigEntry ::=
    SEQUENCE {
        ibmipxPortIfIndex
            INTEGER,
        ibmipxPortStatus
            INTEGER,
        ibmipxidpChecksum
            INTEGER,
        ibmipxLoopbackActive
            INTEGER
    }

ibmipxPortIfIndex OBJECT-TYPE
    SYNTAX  INTEGER
    ACCESS  read-only
    STATUS  mandatory
    DESCRIPTION
            "The value of this object identifies the interface for which
            this entry contains management information.  The value of
            this object for a particular interface has the same value
            as the ifIndex object for the same interface."
    ::= { ibmipxConfigEntry 1 }

ibmipxPortStatus OBJECT-TYPE
    SYNTAX  INTEGER {
                active(1),
                inactive(2)
            }
    ACCESS  read-only
    STATUS  mandatory
    DESCRIPTION
            "The status of the IPX protocol stack on this interface."
    ::= { ibmipxConfigEntry 2 }

ibmipxidpChecksum OBJECT-TYPE
    SYNTAX  INTEGER {
                off(1),     -- no checksumming
                header(2),  -- checksumming header only
                packet(3)   -- checksumming done on entire packet
            }
    ACCESS  read-only
    STATUS  mandatory
    DESCRIPTION
            "Indicates the type of checksumming being done by IDP."
    ::= { ibmipxConfigEntry 3 }

-- { ibmipxConfigEntry 4 } unused

ibmipxLoopbackActive OBJECT-TYPE
    SYNTAX  INTEGER {
                software-loopback-active(1),
                hardware-loopback-active(2)
            }
    ACCESS  read-only
    STATUS  mandatory
    DESCRIPTION
            "Indicates if this port will use the hardware to loopback
             locally addressed packets or return the packet to the
             system via a software loopback."

    ::= { ibmipxConfigEntry 5 }


------------------------------------------------------------------------
-- IPX IDP Statistics
------------------------------------------------------------------------

ibmipxidpInReceives OBJECT-TYPE
    SYNTAX  Counter
    ACCESS  read-only
    STATUS  mandatory
    DESCRIPTION
            "Total number of IDP datagrams received."
    ::= { ibmipx 5 }

ibmipxidpBcastInReceives OBJECT-TYPE
    SYNTAX  Counter
    ACCESS  read-only
    STATUS  mandatory
    DESCRIPTION
            "Number of IDP broadcast datagrams received."
    ::= { ibmipx 6 }

-- { ibmipx 7 } unused

ibmipxidpInDiscards OBJECT-TYPE
    SYNTAX  Counter
    ACCESS  read-only
    STATUS  mandatory
    DESCRIPTION
            "Number of incoming IDP datagrams discarded due to lack
            of resources."
    ::= { ibmipx 8 }

-- { ibmipx 9 } unused

ibmipxidpInAddrErrors OBJECT-TYPE
    SYNTAX  Counter
    ACCESS  read-only
    STATUS  mandatory
    DESCRIPTION
            "Number of incoming IDP datagrams discarded because the
            network portion of the address did not match the configured
            address for this host."
    ::= { ibmipx 10 }

ibmipxidpOutRequests OBJECT-TYPE
    SYNTAX  Counter
    ACCESS  read-only
    STATUS  mandatory
    DESCRIPTION
            "Number of IDP datagrams generated by local IDP
            user protocols.  This counter does not include
            any datagrams counted in ibmipxidpForwDatagrams."
    ::= { ibmipx 11 }

ibmipxidpBcastOutRequests OBJECT-TYPE
    SYNTAX  Counter
    ACCESS  read-only
    STATUS  mandatory
    DESCRIPTION
            "Number of IDP broadcast datagrams generated by local IDP
            user protocols.  This counter does not include
            any datagrams counted in ibmipxidpForwDatagrams."
    ::= { ibmipx 12 }

-- { ibmipx 13 } unused

ibmipxidpForwDatagrams OBJECT-TYPE
    SYNTAX  Counter
    ACCESS  read-only
    STATUS  mandatory
    DESCRIPTION
            "Number of IDP datagrams for which an attempt was made
            to forward."
    ::= { ibmipx 14 }

ibmipxidpOutDiscards OBJECT-TYPE
    SYNTAX  Counter
    ACCESS  read-only
    STATUS  mandatory
    DESCRIPTION
            "Total number of outgoing IDP datagrams discarded."
    ::= { ibmipx 15 }

ibmipxidpOutNoRoutes OBJECT-TYPE
    SYNTAX  Counter
    ACCESS  read-only
    STATUS  mandatory
    DESCRIPTION
            "Number of outgoing IDP datagrams discarded because
            no route was available to the specified destination."
    ::= { ibmipx 16 }

ibmipxidpRoutingDiscards OBJECT-TYPE
    SYNTAX  Counter
    ACCESS  read-only
    STATUS  mandatory
    DESCRIPTION
            "Number of routing entries discarded even though they
            were valid."
    ::= { ibmipx 17 }

-- { ibmipx 18 } unused

ibmipxidpZeroDirBcast OBJECT-TYPE
    SYNTAX  Counter
    ACCESS  read-only
    STATUS  mandatory
    DESCRIPTION
            "Number of IDP datagrams forwarded to the system due
            to zeronet broadcast."
    ::= { ibmipx 19 }

ibmipxidpTooSmall OBJECT-TYPE
    SYNTAX  Counter
    ACCESS  read-only
    STATUS  mandatory
    DESCRIPTION
            "Number of IDP datagrams with len < the size of an IDP header."
    ::= { ibmipx 20 }

ibmipxidpBadLen OBJECT-TYPE
    SYNTAX  Counter
    ACCESS  read-only
    STATUS  mandatory
    DESCRIPTION
            "Number of IDP datagrams with
             number of bytes in the packet less than the
             number of bytes specified in the IDP header field."
    ::= { ibmipx 21 }

ibmipxidpBadSum OBJECT-TYPE
    SYNTAX  Counter
    ACCESS  read-only
    STATUS  mandatory
    DESCRIPTION
            "Number of IDP datagrams with a bad checksum"
    ::= { ibmipx 22 }

ibmipxidpBadTTL OBJECT-TYPE
    SYNTAX  Counter
    ACCESS  read-only
    STATUS  mandatory
    DESCRIPTION
            "Number of IDP datagrams with
             TTL value > IDP maximum hopcount of 16."
    ::= { ibmipx 23 }

-- { ibmipx 24 } through { ibmipx 33 } unused


------------------------------------------------------------------------
-- The IPX Address Table
------------------------------------------------------------------------

ibmipxAddrTable OBJECT-TYPE
    SYNTAX  SEQUENCE OF IbmIpxAddrEntry
    ACCESS  not-accessible
    STATUS  mandatory
    DESCRIPTION
            "The IPX Address Table."
    ::= { ibmipx 34 }

ibmipxAddrEntry OBJECT-TYPE
    SYNTAX  IbmIpxAddrEntry
    ACCESS  not-accessible
    STATUS  mandatory
    DESCRIPTION
            "An entry in the IPX address table."
    INDEX   { ibmipxAddrAddress }
    ::= { ibmipxAddrTable 1 }

IbmIpxAddrEntry ::=
    SEQUENCE {
        ibmipxAddrAddress
            OCTET STRING,
        ibmipxAddrIfIndex
            INTEGER
    }

ibmipxAddrAddress OBJECT-TYPE
    SYNTAX  OCTET STRING (SIZE(12))
    ACCESS  read-only
    STATUS  mandatory
    DESCRIPTION
            "The IPX address to which this entry's addressing
            information pertains."
    ::= { ibmipxAddrEntry 1 }

ibmipxAddrIfIndex OBJECT-TYPE
    SYNTAX  INTEGER
    ACCESS  read-only
    STATUS  mandatory
    DESCRIPTION
            "The interface index which identifies the
            interface to which this entry is applicable."
    ::= { ibmipxAddrEntry 2 }


------------------------------------------------------------------------
-- The IPX Route Table
------------------------------------------------------------------------

ibmipxRouteTable OBJECT-TYPE
    SYNTAX  SEQUENCE OF IbmIpxRouteEntry
    ACCESS  not-accessible
    STATUS  mandatory
    DESCRIPTION
            "The IPX Route Table."
    ::= { ibmipx 35 }

ibmipxRouteEntry OBJECT-TYPE
    SYNTAX  IbmIpxRouteEntry
    ACCESS  not-accessible
    STATUS  mandatory
    DESCRIPTION
            "An entry in the IPX route table."
    INDEX   { ibmipxRouteDest }
    ::= { ibmipxRouteTable 1 }

IbmIpxRouteEntry ::=
    SEQUENCE {
        ibmipxRouteDest
            OCTET STRING,
        ibmipxRouteIfIndex
            INTEGER,
        ibmipxRouteNextHop
            OCTET STRING,
        ibmipxRouteMetric
            INTEGER,
        ibmipxRouteUse
            Counter
    }

ibmipxRouteDest OBJECT-TYPE
    SYNTAX  OCTET STRING (SIZE(12))
    ACCESS  read-only
    STATUS  mandatory
    DESCRIPTION
            "The desination network of this route."
    ::= { ibmipxRouteEntry 1 }

ibmipxRouteIfIndex OBJECT-TYPE
    SYNTAX  INTEGER
    ACCESS  read-only
    STATUS  mandatory
    DESCRIPTION
            "The index value which identifies the local interface
             through which the next hop of this route should be
             reached."
    ::= { ibmipxRouteEntry 2 }

ibmipxRouteNextHop OBJECT-TYPE
    SYNTAX  OCTET STRING (SIZE(4))
    ACCESS  read-only
    STATUS  mandatory
    DESCRIPTION
            "The IPX network address of the next hop of this route."
    ::= { ibmipxRouteEntry 3 }

ibmipxRouteMetric OBJECT-TYPE
    SYNTAX  INTEGER
    ACCESS  read-only
    STATUS  mandatory
    DESCRIPTION
            "The hop count to the destination."
    ::= { ibmipxRouteEntry 4 }

ibmipxRouteUse OBJECT-TYPE
    SYNTAX  Counter
    ACCESS  read-only
    STATUS  mandatory
    DESCRIPTION
            "Reference counter for this route."
    ::= { ibmipxRouteEntry 5 }


------------------------------------------------------------------------
-- The IPX Filter Table
------------------------------------------------------------------------

ibmipxFilterTable OBJECT-TYPE
    SYNTAX  SEQUENCE OF IbmIpxFilterEntry
    ACCESS  not-accessible
    STATUS  mandatory
    DESCRIPTION
            "The IPX Filter Table."
    ::= { ibmipx 36 }

ibmipxFilterEntry OBJECT-TYPE
    SYNTAX  IbmIpxFilterEntry
    ACCESS  not-accessible
    STATUS  mandatory
    DESCRIPTION
            "An entry in the IPX filter table."
    INDEX   { ibmipxFilterIfIndex, ibmipxFilterNumber }
    ::= { ibmipxFilterTable 1 }

IbmIpxFilterEntry ::=
    SEQUENCE {
        ibmipxFilterIfIndex
            INTEGER,
        ibmipxFilterNumber
            INTEGER,
        ibmipxFilterValue
            OCTET STRING,
        ibmipxFilterMask
            OCTET STRING,
        ibmipxFilterType
            INTEGER,
        ibmipxFilterHCCompare
            INTEGER,
        ibmipxFilterUse
            Counter
    }

ibmipxFilterIfIndex OBJECT-TYPE
    SYNTAX  INTEGER
    ACCESS  read-only
    STATUS  mandatory
    DESCRIPTION
            "The value of this object identifies the interface for which
            this entry contains management information.  The value of
            this object for a particular interface has the same value
            as the ifIndex object for the same interface."
    ::= { ibmipxFilterEntry 1 }

ibmipxFilterNumber OBJECT-TYPE
    SYNTAX  INTEGER
    ACCESS  read-only
    STATUS  mandatory
    DESCRIPTION
            "A unique integer identifying this filter entry for this
            interface."
    ::= { ibmipxFilterEntry 2 }

ibmipxFilterValue OBJECT-TYPE
    SYNTAX  OCTET STRING (SIZE (30))
    ACCESS  read-only
    STATUS  mandatory
    DESCRIPTION
            "An octet string representing the IDP header information
            required by this filter entry. Incoming IDP packets will
            be bitwise ANDed with the value of ibmipxFilterMask, and
            if the result is equal to the value of this object, the
            packet will be filtered according to the value of
            ibmipxFilterType.

            The structure of an IDP header is as follows:

                BIT16   checksum
                BIT16   length
                BIT8    transport control (ie. hop count)
                BIT8    packet type
                BIT32   destination network address
                BIT48   destination host address
                BIT16   destination socket
                BIT32   source network address
                BIT48   source host address
                BIT16   source socket
            "
    ::= { ibmipxFilterEntry 3 }

ibmipxFilterMask OBJECT-TYPE
    SYNTAX  OCTET STRING (SIZE (30))
    ACCESS  read-only
    STATUS  mandatory
    DESCRIPTION
            "An octet string indicating the parts of the IDP header
            relevant to this filter entry. This mask will be bitwise
            ANDed with the IDP packet; if the result is equal to
            the value of ibmipxFilterValue, the packet will be filtered
            according to the value of ibmipxFilterType."
    ::= { ibmipxFilterEntry 4 }

ibmipxFilterType OBJECT-TYPE
    SYNTAX  INTEGER {
            deny(1),    -- frames matching filter criteria are denied
            permit(2)   -- frames matching filter criteria are permitted
            }
    ACCESS  read-only
    STATUS  mandatory
    DESCRIPTION
            "Determines whether this filter is a deny entry
            or a permit entry."
    ::= { ibmipxFilterEntry 5 }

ibmipxFilterHCCompare OBJECT-TYPE
    SYNTAX  INTEGER {
                none(1),
                less-than(2),
                less-than-equal(3),
                equal(4),
                greater-than-equal(5),
                greater-than(6)
            }
    ACCESS  read-only
    STATUS  mandatory
    DESCRIPTION
            "Indicates the relational association desired if filtering
            is being done based on hop count. If filtering is not being
            done based on hop count (that is, if the hop count portion
            of ibmipxFilterMask is 0) the value of this object will
            be none(1)."
    ::= { ibmipxFilterEntry 6 }

ibmipxFilterUse OBJECT-TYPE
    SYNTAX  Counter
    ACCESS  read-only
    STATUS  mandatory
    DESCRIPTION
            "Usage count for this filter entry."
    ::= { ibmipxFilterEntry 7 }


------------------------------------------------------------------------
-- IPX SAP Statistics
------------------------------------------------------------------------

ibmipxsapStatInRequests OBJECT-TYPE
    SYNTAX  Counter
    ACCESS  read-only
    STATUS  mandatory
    DESCRIPTION
            "Number of SAP requests received by this entity."
    ::= { ibmipx 37 }

ibmipxsapStatOutRequests OBJECT-TYPE
    SYNTAX  Counter
    ACCESS  read-only
    STATUS  mandatory
    DESCRIPTION
            "Number of SAP requests sent by this entity."
    ::= { ibmipx 38 }

ibmipxsapStatInResponses OBJECT-TYPE
    SYNTAX  Counter
    ACCESS  read-only
    STATUS  mandatory
    DESCRIPTION
            "Number of SAP responses received by this entity."
    ::= { ibmipx 39 }

ibmipxsapStatOutResponses OBJECT-TYPE
    SYNTAX  Counter
    ACCESS  read-only
    STATUS  mandatory
    DESCRIPTION
            "Number of SAP responses sent by this entity."
    ::= { ibmipx 40 }

ibmipxsapStatInErrors OBJECT-TYPE
    SYNTAX  Counter
    ACCESS  read-only
    STATUS  mandatory
    DESCRIPTION
            "Number of incoming SAP packets discarded due to errors."
    ::= { ibmipx 41 }

ibmipxsapStatOutDiscards OBJECT-TYPE
    SYNTAX  Counter
    ACCESS  read-only
    STATUS  mandatory
    DESCRIPTION
            "Number of outgoing SAP packets discarded due
            to lack of resources."
    ::= { ibmipx 42 }


------------------------------------------------------------------------
-- The IPX SAP Server Table
------------------------------------------------------------------------

ibmipxsapServerTable OBJECT-TYPE
    SYNTAX  SEQUENCE OF IbmIpxsapServerEntry
    ACCESS  not-accessible
    STATUS  mandatory
    DESCRIPTION
            "Table of IPX servers."
    ::= { ibmipx 43 }

ibmipxsapServerEntry OBJECT-TYPE
    SYNTAX  IbmIpxsapServerEntry
    ACCESS  not-accessible
    STATUS  mandatory
    DESCRIPTION
            "Information on a single server."
    INDEX   { ibmipxsapServerType, ibmipxsapServerNet, ibmipxsapServerHost,
              ibmipxsapServerSocket, ibmipxsapServerIndex }
    ::= { ibmipxsapServerTable 1 }

IbmIpxsapServerEntry ::=
    SEQUENCE {
        ibmipxsapServerType
            INTEGER,
        ibmipxsapServerNet
            OCTET STRING,
        ibmipxsapServerHost
            OCTET STRING,
        ibmipxsapServerSocket
            INTEGER,
        ibmipxsapServerName
            DisplayString,
        ibmipxsapServerAge
            INTEGER,
        ibmipxsapServerHops
            INTEGER,
        ibmipxsapServerIfIndex
            INTEGER,
        ibmipxsapServerIndex
            INTEGER,
        ibmipxsapServerRequestsFiltered
            Counter
    }

ibmipxsapServerType OBJECT-TYPE
    SYNTAX  INTEGER
    ACCESS  read-only
    STATUS  mandatory
    DESCRIPTION
            "The type of this server."
    ::= { ibmipxsapServerEntry 1 }

ibmipxsapServerNet OBJECT-TYPE
    SYNTAX  OCTET STRING (SIZE(4))
    ACCESS  read-only
    STATUS  mandatory
    DESCRIPTION
            "The IPX network number of this server."
    ::= { ibmipxsapServerEntry 2 }

ibmipxsapServerHost OBJECT-TYPE
    SYNTAX  OCTET STRING (SIZE(6))
    ACCESS  read-only
    STATUS  mandatory
    DESCRIPTION
            "The IPX host address of this server."
    ::= { ibmipxsapServerEntry 3 }

ibmipxsapServerSocket OBJECT-TYPE
    SYNTAX  INTEGER
    ACCESS  read-only
    STATUS  mandatory
    DESCRIPTION
            "The IPX socket number this server uses to advertise
            its service."
    ::= { ibmipxsapServerEntry 4 }

ibmipxsapServerName OBJECT-TYPE
    SYNTAX  DisplayString
    ACCESS  read-only
    STATUS  mandatory
    DESCRIPTION
            "The name of this server."
    ::= { ibmipxsapServerEntry 5 }

ibmipxsapServerAge OBJECT-TYPE
    SYNTAX  INTEGER
    ACCESS  read-only
    STATUS  mandatory
    DESCRIPTION
            "The number of seconds since this server entry
            was updated by the SAP protocol."
    ::= { ibmipxsapServerEntry 6 }

ibmipxsapServerHops OBJECT-TYPE
    SYNTAX  INTEGER
    ACCESS  read-only
    STATUS  mandatory
    DESCRIPTION
            "The number of network hops required to reach this server."
    ::= { ibmipxsapServerEntry 7 }

ibmipxsapServerIfIndex OBJECT-TYPE
    SYNTAX  INTEGER
    ACCESS  read-only
    STATUS  mandatory
    DESCRIPTION
            "The interface which is used to reach this server.  The
            value of this object for a particular interface has the
            same value as the ifIndex object for the same interface."
    ::= { ibmipxsapServerEntry 8 }

ibmipxsapServerIndex OBJECT-TYPE
    SYNTAX  INTEGER
    ACCESS  read-only
    STATUS  mandatory
    DESCRIPTION
            "A unique number identifying servers advertised at the
            same IPX network and host address."
    ::= { ibmipxsapServerEntry 9 }

ibmipxsapServerRequestsFiltered OBJECT-TYPE
    SYNTAX  Counter
    ACCESS  read-only
    STATUS  mandatory
    DESCRIPTION
            "Number of times a request for this server has been
            filtered."
    ::= { ibmipxsapServerEntry 10 }

-- Local Variables:
-- tab-width: 4
-- case-fold-search: nil
-- End:
-- static char sccsid_cylink_mib[] = "@(#) snmp/samples/cylink.my, SNMP, 6611R2, r2d18a  10/1/92 17:38:32";



------------------------------------------------------------------------------
--
-- IBM MIB for Cylink 4201 DSU/CSUs
--
--
-- This MIB externalizes information provided by the Cylink DSU/CSU
-- via its network management interface.
--
------------------------------------------------------------------------------



--  private MIB for Cylink 4201 DSU/CSU

cylink OBJECT IDENTIFIER ::= { ibmDSUs 1 }


-- the cylink Status Group

cylinkStatusTable OBJECT-TYPE
   SYNTAX  SEQUENCE OF CYLINKStatusEntry
   ACCESS  not-accessible
   STATUS  mandatory
   DESCRIPTION
       "The cylink Status table.  This table contains
       information about the current state of the
       Cylink CSUs attached to the system."
   ::= { cylink 1 }

cylinkStatusEntry OBJECT-TYPE
   SYNTAX  CYLINKStatusEntry
   ACCESS  not-accessible
   STATUS  mandatory
   DESCRIPTION
       "An entry in the cylink Status table."
   INDEX { cylinkIndex }
   ::= { cylinkStatusTable 1 }

CYLINKStatusEntry ::=
   SEQUENCE {
       cylinkIndex     INTEGER,
       cylinkLinkState     INTEGER,
       cylinkLoopback      INTEGER,
       cylinkQRSS      INTEGER
   }

cylinkIndex OBJECT-TYPE
   SYNTAX  INTEGER
   ACCESS  read-only
   STATUS  mandatory
   DESCRIPTION
       "An index value that uniquely identifies a cylink
       system interface. The interface identified by a
       particular value of this index is the same
       interface as identified by the same value in an
       ifIndex object instance."
   ::= { cylinkStatusEntry 1 }

cylinkLinkState OBJECT-TYPE
   SYNTAX  INTEGER {
           cylinkNotConnected(1),
           cylinkNoInput(2),
           cylinkNoOutput(3),
           cylinkConnected(4)
       }
   ACCESS  read-only
   STATUS  mandatory
   DESCRIPTION
       "The current state of the link.  The meanings
       of the values are:

       cylinkNotConnected(1)
           The link is not physically connected
           to the CSU.  This may be due to loss of
           input circuit or loss of output circuit.

       cylinkNoInput(2)
           The input circuit is not connected.

       cylinkNoOutput(3)
           The output circuit is not connected.

       cylinkConnected(4)
           The link is connected to the CSU."
   ::= { cylinkStatusEntry 2 }

cylinkLoopback OBJECT-TYPE
   SYNTAX  INTEGER {
           cylinkNoLoopback(1),
           cylinkNearEndLoopback(2),
           cylinkFarEndLoopback(3)
       }
   ACCESS  read-only
   STATUS  mandatory
   DESCRIPTION
       "The loopback mode of the link.  The meaning of
       values are:

       cylinkNoLoopback(1)
           The link is not in loopback mode.

       cylinkNearEndLoopback(2)
           The link has been placed in loopback mode at
           the near end: data is being looped back within
           the local CSU.

       cylinkFarEndLoopback(3)
           The link has been placed in loopback mode at the
           far end: data is being looped across the link to
           the remote CSU and back."
   ::= { cylinkStatusEntry 3 }

cylinkQRSS OBJECT-TYPE
   SYNTAX  INTEGER {
           cylinkNoQRSS(1),
           cylinkQRSSMaster(2),
           cylinkQRSSSlave(3)
       }
   ACCESS  read-only
   STATUS  mandatory
   DESCRIPTION
       "The Quasi-Random Signal Sequence test mode of the
       CSU.  The value of the meanings are:

       cylinkNoQRSS(1)
           The CSU is not in QRSS mode.

       cylinkQRSSMaster(2)
           The CSU is transmitting a QRSS test
           pattern.

       cylinkQRSSSlave(3)
           The CSU is receiving a QRSS test pattern."
   ::= { cylinkStatusEntry 4 }


-- the cylink Configuration group

cylinkConfigTable OBJECT-TYPE
   SYNTAX  SEQUENCE OF CYLINKConfigEntry
   ACCESS  not-accessible
   STATUS  mandatory
   DESCRIPTION
       "The cylink Configuration table.  This table contains
       information about the configuration of the Cylink CSUs
       attached to the system."
   ::= { cylink 3 }

cylinkConfigEntry OBJECT-TYPE
   SYNTAX  CYLINKConfigEntry
   ACCESS  not-accessible
   STATUS  mandatory
   DESCRIPTION
       "An entry in the cylink Configuration table."
   INDEX { cylinkConfigIndex }
   ::= { cylinkConfigTable 1 }

CYLINKConfigEntry ::=
   SEQUENCE {
       cylinkConfigIndex   INTEGER,
       cylinkSerialNumber  INTEGER,
       cylinkSoftwareVersion   DisplayString (SIZE (0..4)),
       cylinkDTEFraming    INTEGER,
       cylinkNetworkFraming    INTEGER,
       cylinkDTEDS1Mode        INTEGER,
       cylinkNetworkDS1Mode    INTEGER,
       cylinkOnesResponsibility INTEGER,
       cylinkOnesControl   INTEGER,
       cylinkZeroProtection    INTEGER,
       cylinkClockSource   INTEGER,
       cylinkClockFrequency    INTEGER,
       cylinkClockBackup   INTEGER,
       cylinkDIUFrequency  INTEGER,
       cylinkDIUTiming     INTEGER,
       cylinkDialoutCapability INTEGER,
       cylinkDialoutHoldoff    INTEGER (1..99),
       cylinkPrimaryPhone  DisplayString (SIZE (0..19)),
       cylinkSecondaryPhone    DisplayString (SIZE (0..19)),
       cylinkAlarmRepeatTime   INTEGER (1..99),
       cylinkESThreshold   INTEGER (1..99),
       cylinkSecondaryContact  INTEGER
   }

cylinkConfigIndex OBJECT-TYPE
   SYNTAX  INTEGER
   ACCESS  read-only
   STATUS  mandatory
   DESCRIPTION
       "The index value which uniquely identifies the
       CSU to which this entry is applicable. The
       CSU identified by a particular value of
       this index is the same CSU as identified
       by the same value in a cylinkIndex object
       instance."
   ::= { cylinkConfigEntry 1 }

cylinkSerialNumber OBJECT-TYPE
   SYNTAX  INTEGER
   ACCESS  read-only
   STATUS  mandatory
   DESCRIPTION
       "The manufacturer's serial number of this CSU."
   ::= { cylinkConfigEntry 2 }

cylinkSoftwareVersion OBJECT-TYPE
   SYNTAX  DisplayString (SIZE (0..4))
   ACCESS  read-only
   STATUS  mandatory
   DESCRIPTION
       "The version number of the microcode running in the CSU."
   ::= { cylinkConfigEntry 3 }

cylinkDTEFraming   OBJECT-TYPE
   SYNTAX  INTEGER {
           cylinkDTEFramingD4(1),
           cylinkDTEFramingESF(2)
       }
   ACCESS  read-only
   STATUS  mandatory
   DESCRIPTION
       "The DTE framing selected (D4, or ESF).  Framing conversion is
       automatically performed at both ends if the DTE is D4 framed and
       the network interface is ESF framed."
   ::= { cylinkConfigEntry 4 }

cylinkNetworkFraming   OBJECT-TYPE
   SYNTAX  INTEGER {
           cylinkNetworkFramingD4(1),
           cylinkNetworkFramingESF(2)
       }
   ACCESS  read-only
   STATUS  mandatory
   DESCRIPTION
       "The network framing selected (D4, or ESF).  Framing conversion is
       automatically performed at both ends if the DTE is D4 framed and
       the network interface is ESF framed."
   ::= { cylinkConfigEntry 5 }

cylinkDTEDS1Mode       OBJECT-TYPE
   SYNTAX  INTEGER {
           cylinkDTEDS1ModeB8ZS(1),
           cylinkDTEDS1ModeAMI(2)
       }
   ACCESS  read-only
   STATUS  mandatory
   DESCRIPTION
       "The DTE DS-1 mode selected (B8ZS, or AMI)."
   ::= { cylinkConfigEntry 6 }

cylinkNetworkDS1Mode   OBJECT-TYPE
   SYNTAX  INTEGER {
           cylinkNetworkDS1ModeB8ZS(1),
           cylinkNetworkDS1ModeAMI(2)
       }
   ACCESS  read-only
   STATUS  mandatory
   DESCRIPTION
       "The network DS-1 mode selected (B8ZS, or AMI)."
   ::= { cylinkConfigEntry 7 }

cylinkOnesResponsibility OBJECT-TYPE
   SYNTAX  INTEGER {
           cylinkOnesResponsibilityDTE(1),
           cylinkOnesResponsibilityACSU(2)
       }
   ACCESS  read-only
   STATUS  mandatory
   DESCRIPTION
       "The component selected for Ones Density Responsibility (DTE,
       or CSU."
   ::= { cylinkConfigEntry 8 }

cylinkOnesControl  OBJECT-TYPE
   SYNTAX  INTEGER {
           cylinkOnesControlLSB24(1),
           cylinkOnesControlD4FRM(2),
           cylinkOnesControlESFDL(3)
       }
   ACCESS  read-only
   STATUS  mandatory
   DESCRIPTION
       "The Ones Density Control selected (LSB 24, D4 FRM, or ESF DL)."
   ::= { cylinkConfigEntry 9 }

cylinkZeroProtection   OBJECT-TYPE
   SYNTAX  INTEGER {
           cylinkZeroProtection80(1),
           cylinkZeroProtection15(2)
       }
   ACCESS  read-only
   STATUS  mandatory
   DESCRIPTION
       "The Consecutive Zero Control selected (15, or 80).
       This determines the the maximum number of consecutive
       zeros allowed in the data stream before a one is forced."
   ::= { cylinkConfigEntry 10 }

cylinkClockSource  OBJECT-TYPE
   SYNTAX  INTEGER {
           cylinkClockSourceNetwork(1),
           cylinkClockSourceDTE(2),
           cylinkClockSourceExternal(3),
           cylinkClockSourceInternal(4)
       }
   ACCESS  read-only
   STATUS  mandatory
   DESCRIPTION
       "The transmit clock source selected for NRZ DIUs
       (network, DTE, an external clock, or the CSU's
       internal clock)."
   ::= { cylinkConfigEntry 11 }

cylinkClockFrequency   OBJECT-TYPE
   SYNTAX  INTEGER {
       cylinkClockFreq-56kHz(1),
       cylinkClockFreq-256kHz(2),
       cylinkClockFreq-1-344MHz(3), -- 1.344 MHz
       cylinkClockFreq-1-544MHz(4)  -- 1.544 MHz
       }
   ACCESS  read-only
   STATUS  mandatory
   DESCRIPTION
       "The external clock frequency selected (56 kHz, 256 kHz,
        1.344 MHz, 1.544 MHz)."
   ::= { cylinkConfigEntry 12 }

cylinkClockBackup  OBJECT-TYPE
   SYNTAX  INTEGER {
           cylinkClockBackupNetwork(1),
           cylinkClockBackupDTE(2),
           cylinkClockBackupExternal(3),
           cylinkClockBackupInternal(4)
       }
   ACCESS  read-only
   STATUS  mandatory
   DESCRIPTION
       "The transmit clock backup source selected for NRZ DIUs
       (network, DTE, an external clock, or the CSU's internal
       clock)."
   ::= { cylinkConfigEntry 13 }

cylinkDIUFrequency OBJECT-TYPE
   SYNTAX  INTEGER {
           cylinkDIUFreq-768kbps(1),   -- 767 kbps
           cylinkDIUFreq-1-344Mbps(2), -- 1.244 Mbps
           cylinkDIUFreq-1-528Mbps(3), -- 1.528 Mbps
           cylinkDIUFreq-1-536Mbps(4)  -- 1.536 Mbps
       }
   ACCESS  read-only
   STATUS  mandatory
   DESCRIPTION
       "The DIU frequency selected for NRZ DIUs
       (767 kbps, 1.244 Mbps, 1.528 Mbps, 1.536 Mbps)."
   ::= { cylinkConfigEntry 14 }

cylinkDIUTiming        OBJECT-TYPE
   SYNTAX  INTEGER {
           cylinkDIUTimingTT(1),
           cylinkDIUTimingST(2)
       }
   ACCESS  read-only
   STATUS  mandatory
   DESCRIPTION
       "The DIU transmit timing  selected for NRZ DIUs
       (Send Timing, or Terminal Timing)."
   ::= { cylinkConfigEntry 15 }

cylinkDialoutCapability    OBJECT-TYPE
   SYNTAX  INTEGER {
           cylinkDialoutCapabilityPolled(1),
           cylinkDialoutCapabilityTone(2),
           cylinkDialoutCapabilityPulse(3)
       }
   ACCESS  read-only
   STATUS  mandatory
   DESCRIPTION
       "The DIU dial-out capability selected (polled,
       tone, or pulse)."

   ::= { cylinkConfigEntry 16 }

cylinkDialoutHoldoff   OBJECT-TYPE
   SYNTAX  INTEGER (1..99)
   ACCESS  read-only
   STATUS  mandatory
   DESCRIPTION
       "The mininum time, in minutes, between successful
       CSU-to-NMS connections to report alarm conditions."
   ::= { cylinkConfigEntry 17 }

cylinkPrimaryPhone OBJECT-TYPE
   SYNTAX  DisplayString (SIZE (0..19))
   ACCESS  read-only
   STATUS  mandatory
   DESCRIPTION
       "The primary telephone number used by by the CSU to contact
       the NMS."
   ::= { cylinkConfigEntry 18 }

cylinkSecondaryPhone   OBJECT-TYPE
   SYNTAX  DisplayString (SIZE (0..19))
   ACCESS  read-only
   STATUS  mandatory
   DESCRIPTION
       "The secondary telephone number used by by the CSU
       to contact the NMS."
   ::= { cylinkConfigEntry 19 }

cylinkAlarmRepeatTime  OBJECT-TYPE
   SYNTAX  INTEGER (1..99)
   ACCESS  read-only
   STATUS  mandatory
   DESCRIPTION
       "The interval, in minutes, that the CSU will insert
       duplicate messages in the alarm queue for persistant
       alarm conditions."
   ::= { cylinkConfigEntry 20 }

cylinkESThreshold  OBJECT-TYPE
   SYNTAX  INTEGER (1..99)
   ACCESS  read-only
   STATUS  mandatory
   DESCRIPTION
       "The threshold, in seconds, for the errored second
       value in the current 15-minute interval."
   ::= { cylinkConfigEntry 21 }

cylinkSecondaryContact OBJECT-TYPE
   SYNTAX  INTEGER {
           cylinkSecondaryContactOpen(1),
           cylinkSecondaryContactClosed(2)
       }
   ACCESS  read-only
   STATUS  mandatory
   DESCRIPTION
       "The state of the CSU secondary contact (open or closed)."
   ::= { cylinkConfigEntry 22 }

------------------------------------------------------------------------------
-- Traps and error log entries
------------------------------------------------------------------------------

-- Alarms and informational messages from the Cylink CSUs are processed
-- by the IBM 6611.  Those that result in enterprise-specific traps
-- and/or error log entries will provide the following Cylink codes as
-- detailed data labeled 'product alert reference code':

-- 120 - sending loopback to far end (front-panel)
-- 121 - sending loopdown to far end (front-panel)
-- 122 - line loopback (front panel)
-- 123 - line loopback (in-band)
-- 124 - DTE loopback (ESF)
-- 125 - line loopback (NMS)
-- 126 - sending loopback to far end (NMS)
-- 127 - sending loopdown to far end (NMS)
--
-- 242 - number of alarms overflow
-- 254 - DTE loss of signal
-- 255 - network loss of signal
-- 256 - entered QRSS (front panel)
-- 257 - exited QRSS (front panel)
-- 258 - entered QRSS (NMS)
-- 259 - exited QRSS (NMS)
-- 260 - entered QRSS (far end)
-- 261 - exited QRSS (far end)
--
-- 324 - secondary contact closed
-- 330 - reboot from power fail
-- 340 - DTE yellow alarm
-- 341 - network yellow alarm
-- 342 - external clock loss
-- 343 - DTE out of frame
-- 344 - network out of frame
-- 345 - auxiliary input 1 alarm
-- 346 - auxiliary input 2 alarm
-- 347 - network blue alarm
-- 348 - errored seconds greater than threshold
-- 349 - network red alarm
-- 350 - loopdown (front panel)
-- 351 - loopdown (in-band)
-- 352 - loopdown (ESF)
-- 353 - loopdown (NMS)
-- 354 - DTE clock loss
-- 355 - connect with network manager failed
-- 356 - far end loop - internal timing

-- static char sccsid_tb_mib[] = "@(#) tb.my, SNMP, v1r3  3/14/94 17:36:21";

------------------------------------------------------------------------------

-- The IBM 6611 Transparent Bridging MIB                                    --
------------------------------------------------------------------------------


-- --------------------------------------------------------------------------
-- This MIB extension is based on the RFC 1286 bridge MIB and provides     --
-- management of the Transparent Bridge function of the IBM 6611. The 6611 --
-- provides the capability to have both a Source Route bridge and a        --
-- Transparent Bridge concurrently and independently active within a single--
-- bridge/router. Because the RFC 1286 bridge MIB can provide management   --
-- for only a single bridge, this private IBM extension is used to manage  --
-- the Transparent Bridge while the RFC 1286 MIB is used to manage the     --
-- Source Route bridge.                                                    --
-- --------------------------------------------------------------------------

-- All representations of MAC addresses in this MIB Module use,
-- as a textual convention (i.e. this convention does not affect
-- their encoding), the data type:

--TBMacAddress ::= OCTET STRING (SIZE(6))
-- a 6 octet address in the "canonical" order
-- defined by IEEE 802.1a, i.e., as if it were transmitted least
-- significant bit first, even though 802.5 (in contrast to other
-- 802.x protocols) requires MAC addresses to be transmitted most
-- significant bit first.
--
-- 16-bit addresses, if needed, are represented by setting their
-- upper 4 octets to all 0's, i.e., AAFF would be represented
-- as 00000000AAFF.


-- Similarly, all representations of Bridge-Id in this MIB Module
-- use, as a textual convention (i.e. this convention does not affect
-- their encoding), the data type:
--BridgeId ::= OCTET STRING (SIZE(8))
-- the Bridge-Identifier as used in the Spanning Tree
-- Protocol to uniquely identify a bridge.  Its first two octets
-- (in network byte order) contain a priority value and its last
-- 6 octets contain the MAC address used to refer to a bridge in a
-- unique fashion (typically, the numerically smallest MAC address
-- of all ports on the bridge).
-- Several objects in this MIB module represent values of timers
-- used by the Spanning Tree Protocol.  In this MIB, these timers
-- have values in units of hundreths of a second (i.e. 1/100 secs).
-- These timers, when stored in a Spanning Tree Protocol's BPDU,
-- are in units of 1/256 seconds.  Note, however, that 802.1d/D9
-- specifies a settable granularity of no more than 1 second for
-- these timers.  To avoid ambiguity, a data type is defined here
-- as a textual convention and all representation of these timers
-- in this MIB module are defined using this data type.  An algorithm
-- is also defined for converting between the different units, to
-- ensure a timer's value is not distorted by multiple conversions.
-- The data type is:

--Timeout ::= INTEGER
-- a STP timer in units of 1/100 seconds
-- To convert a Timeout value into a value in units of
-- 1/256 seconds, the following algorithm should be used:
--
--      b  = floor( (n * 256) / 100)
--
-- where:
--      floor   =  quotient (ignore remainder)
--      n is the value in 1/100 second units
--      b is the value in 1/256 second units
--
-- To convert the value from 1/256 second units back to
-- 1/100 seconds, the following algorithm should be used:
--
--      n = ceiling( (b * 100) / 256)
--
-- where:
--      ceiling =  quotient (if remainder is 0), or
--                 quotient + 1 (if remainder is non-zero)
--      n is the value in 1/100 second units
--      b is the value in 1/256 second units
--
-- Note: it is important that the arithmetic operations are done
-- in the order specified (i.e., multiply first, divide second).

--
-- Filter tables use the following type to determine whether
-- entries are permit entries or deny entries.
--

--TBFilterType ::= INTEGER {
--                deny(1),    ## frames matching the filter criteria
--                            ## are denied
--                permit(2)   ## frames matching the filter criteria
--                            ## are permitted
--            }

--TBCharType ::= OCTET STRING (SIZE(1))    ##  size of character

--TBShortType ::= OCTET STRING (SIZE(2))    ##  size of short



ibmdot1dBase     OBJECT IDENTIFIER ::= { ibmtb 1 }

ibmdot1dStp      OBJECT IDENTIFIER ::= { ibmtb 2 }

ibmdot1dTp       OBJECT IDENTIFIER ::= { ibmtb 3 }

ibmdot1dStatic   OBJECT IDENTIFIER ::= { ibmtb 4 }

ibmtbMACAddressFilters  OBJECT IDENTIFIER ::= { ibmtb 5 }

ibmtbSAPFilters         OBJECT IDENTIFIER ::= { ibmtb 6 }

ibmtbEthTypeFilters     OBJECT IDENTIFIER ::= { ibmtb 7 }

ibmtbWindowFilters      OBJECT IDENTIFIER ::= { ibmtb 8 }

ibmtbFiltOrderTable     OBJECT IDENTIFIER ::= { ibmtb 9 }

-- the ibmdot1dBase group

-- Implementation of the ibmdot1dBase group is mandatory for all
-- bridges.

ibmdot1dBaseBridgeAddress OBJECT-TYPE
    SYNTAX  OCTET STRING (SIZE(6))    -- a 6 octet address in
    ACCESS  read-only
    STATUS  mandatory
    DESCRIPTION
            "The MAC address used by this bridge when it must
            be referred to in a unique fashion.   It is
            recommended that this be the numerically smallest
            MAC address of all ports that belong to this
            bridge.  However it is only required to be unique.
            When concatenated with ibmdot1dStpPriority a unique
            BridgeIdentifier is formed which is used in the
            Spanning Tree Protocol."
    REFERENCE
            "P802.1d/D9, July 14, 1989: Sections 6.4.1.1.3 and 3.12.5"
    ::= { ibmdot1dBase 1 }

ibmdot1dBaseNumPorts OBJECT-TYPE
    SYNTAX  INTEGER
    ACCESS  read-only
    STATUS  mandatory
    DESCRIPTION
            "The number of TB ports controlled by this bridging
            entity."
    REFERENCE
            "P802.1d/D9, July 14, 1989: Section 6.4.1.1.3"
    ::= { ibmdot1dBase 2 }

ibmdot1dBaseType OBJECT-TYPE
    SYNTAX  INTEGER {
                unknown(1),
                transparent-only(2),
                sourceroute-only(3),
                srt(4)
            }
    ACCESS  read-only
    STATUS  mandatory
    DESCRIPTION
            "Indicates what type of bridging this bridge can
            perform.  If a bridge is actually performing a
            certain type of bridging this will be indicated by
            entries in the port table for the given type."
    ::= { ibmdot1dBase 3 }

-- The Generic Bridge Port Table

ibmdot1dBasePortTable OBJECT-TYPE
    SYNTAX  SEQUENCE OF IbmDot1dBasePortEntry
    ACCESS  not-accessible
    STATUS  mandatory
    DESCRIPTION
            "A table that contains generic information about
            every port that is associated with this bridge."
    ::= { ibmdot1dBase 4 }

ibmdot1dBasePortEntry OBJECT-TYPE
    SYNTAX  IbmDot1dBasePortEntry
    ACCESS  not-accessible
    STATUS  mandatory
    DESCRIPTION
            "A list of information for each port of the
            bridge."
    REFERENCE
            "P802.1d/D9, July 14, 1989: Section 6.4.2, 6.6.1"
    INDEX  { ibmdot1dBasePort }
    ::= { ibmdot1dBasePortTable 1 }

IbmDot1dBasePortEntry ::=
    SEQUENCE {
        ibmdot1dBasePort
            INTEGER,
        ibmdot1dBasePortIfIndex
            INTEGER,
        ibmdot1dBasePortCircuit
            OBJECT IDENTIFIER,
        ibmdot1dBasePortDelayExceededDiscards
            Counter,
        ibmdot1dBasePortMtuExceededDiscards
            Counter
    }

ibmdot1dBasePort OBJECT-TYPE
    SYNTAX  INTEGER
    ACCESS  read-only
    STATUS  mandatory
    DESCRIPTION
            "The port number of the port for which this entry
            contains bridge management information."
    ::= { ibmdot1dBasePortEntry 1 }

ibmdot1dBasePortIfIndex OBJECT-TYPE
    SYNTAX  INTEGER
    ACCESS  read-only
    STATUS  mandatory
    DESCRIPTION
            "The value of the instance of the ifIndex object,
            defined in RFC 1156, RFC 1213 for the interface
            corresponding to this port."
    ::= { ibmdot1dBasePortEntry 2 }

ibmdot1dBasePortCircuit OBJECT-TYPE
    SYNTAX  OBJECT IDENTIFIER
    ACCESS  read-only
    STATUS  mandatory
    DESCRIPTION
            "For a port which potentially has the same value
            of ibmdot1dBasePortIfIndex as another port on the
            same bridge, this object contains an identifier
            unique to this port.  For example, in the case
            where multiple ports correspond one-to-one
            with multiple Frame Relay circuit's, this
            value provides the object identifier for the
            frame relay MIB.

            Fpr a port which has a unique value of
            ibmdot1dBasePortIfIndex, this object can
            have the value {0.0}."
    ::= { ibmdot1dBasePortEntry 3 }

ibmdot1dBasePortDelayExceededDiscards OBJECT-TYPE
    SYNTAX  Counter
    ACCESS  read-only
    STATUS  mandatory
    DESCRIPTION
            "The number of frames discarded by this port due
            to excessive transit delay through the bridge."
    REFERENCE
             "P802.1d/D9, July 14, 1989: Section 6.6.1.1.3"
    ::= { ibmdot1dBasePortEntry 4 }

ibmdot1dBasePortMtuExceededDiscards OBJECT-TYPE
    SYNTAX  Counter
    ACCESS  read-only
    STATUS  mandatory
    DESCRIPTION
            "The number of frames discarded by this port due
            to an excessive size."
    REFERENCE
            "P802.1d/D9, July 14, 1989: Section 6.6.1.1.3"
    ::= { ibmdot1dBasePortEntry 5 }


-- the ibmdot1dStp group  (Spanning Tree Protocol)

-- Implementation of the ibmdot1dStp group is optional.  It is
-- implemented by those bridges that support the Spanning Tree
-- Protocol.  Transparent, Source Route, and SRT bridges will
-- implement this group only if they support the Spanning Tree
-- Protocol.


ibmdot1dStpProtocolSpecification OBJECT-TYPE
    SYNTAX  INTEGER {
                unknown(1),
                decLb100(2),
                ieee8021d(3)
            }
    ACCESS  read-only
    STATUS  mandatory
    DESCRIPTION
            "An indication of what version of the Spanning
            Tree Protocol is being run.  The value
            'decLb100(2)' indicates the DEC LANbridge 100
            Spanning Tree protocol.  IEEE 802.1d
            implementations will return 'ieee8021d(3)'.  If
            future versions of the IEEE Spanning Tree Protocol
            are released that are incompatible with the
            current version a new value will be defined."
    ::= { ibmdot1dStp 1 }

ibmdot1dStpPriority OBJECT-TYPE
    SYNTAX  INTEGER (0..65535)
    ACCESS  read-write
    STATUS  mandatory
    DESCRIPTION
"The value of the write-able portion of the Bridge
            ID, i.e., the first two octets of the (8 octet
            long) Bridge ID.  The other (last) 6 octets of the
            Bridge ID are given by the value of
            ibmdot1dBaseBridgeAddress."
    REFERENCE
"P802.1d/D9, July 14, 1989: Section 4.5.3.7"
    ::= { ibmdot1dStp 2 }

ibmdot1dStpTimeSinceTopologyChange OBJECT-TYPE
    SYNTAX  TimeTicks
    ACCESS  read-only
    STATUS  mandatory
    DESCRIPTION
            "The time (in hundredths of a second) since the
            last time a topology change was detected by the
            bridge entity."
    REFERENCE
            "P802.1d/D9, July 14, 1989: Section 6.8.1.1.3"
    ::= { ibmdot1dStp 3 }

ibmdot1dStpTopChanges OBJECT-TYPE
    SYNTAX  Counter
    ACCESS  read-only
    STATUS  mandatory
    DESCRIPTION
            "The total number of topology changes detected by
            this bridge since the management entity was last
            reset or initialized."
    REFERENCE
            "P802.1d/D9, July 14, 1989: Section 6.8.1.1.3"
    ::= { ibmdot1dStp 4 }

ibmdot1dStpDesignatedRoot OBJECT-TYPE
    SYNTAX  OCTET STRING (SIZE(8))   -- the Bridge-Identifier as
    ACCESS  read-only
    STATUS  mandatory
    DESCRIPTION
            "The bridge identifier of the root of the spanning
            tree as determined by the Spanning Tree Protocol
            as executed by this node.  This value is used as
            the Root Identifier parameter in all Configuration
            Bridge PDUs originated by this node."
    REFERENCE
            "P802.1d/D9, July 14, 1989: Section 4.5.3.1"
    ::= { ibmdot1dStp 5 }

ibmdot1dStpRootCost OBJECT-TYPE
    SYNTAX  INTEGER
    ACCESS  read-only
    STATUS  mandatory
    DESCRIPTION
            "The cost of the path to the root as seen from
            this bridge."
    REFERENCE
            "P802.1d/D9, July 14, 1989: Section 4.5.3.2"
    ::= { ibmdot1dStp 6 }

ibmdot1dStpRootPort OBJECT-TYPE
    SYNTAX  INTEGER
    ACCESS  read-only
    STATUS  mandatory
    DESCRIPTION
"The port number of the port which offers the
            lowest cost path from this bridge to the root
            bridge."
    REFERENCE
"P802.1d/D9, July 14, 1989: Section 4.5.3.3"
    ::= { ibmdot1dStp 7 }

ibmdot1dStpMaxAge OBJECT-TYPE
    SYNTAX  INTEGER      -- a STP timer in units of 1/100 seconds
    ACCESS  read-only
    STATUS  mandatory
    DESCRIPTION
            "The maximum age of Spanning Tree Protocol
            information learned from the network on any port
            before it is discarded, in units of hundredths of
            a second.  This is the actual value that this
            bridge is currently using."
    REFERENCE
            "P802.1d/D9, July 14, 1989: Section 4.5.3.4"
    ::= { ibmdot1dStp 8 }

ibmdot1dStpHelloTime OBJECT-TYPE
    SYNTAX  INTEGER      -- a STP timer in units of 1/100 seconds
    ACCESS  read-only
    STATUS  mandatory
    DESCRIPTION
            "The amount of time between the transmission of
            Configuration bridge PDUs by this node on any port
            when it is the root of the spanning tree or trying
            to become so, in units of hundredths of a second.
            This is the actual value that this bridge is
            currently using."
    REFERENCE
            "P802.1d/D9, July 14, 1989: Section 4.5.3.5"
    ::= { ibmdot1dStp 9 }

ibmdot1dStpHoldTime OBJECT-TYPE
    SYNTAX  INTEGER
    ACCESS  read-only
    STATUS  mandatory
    DESCRIPTION
            "This time value determines the interval length
            during which no more than two Configuration bridge
            PDUs shall be transmitted by this node, in units
            of hundredths of a second."
    REFERENCE
            "P802.1d/D9, July 14, 1989: Section 4.5.3.14"
    ::= { ibmdot1dStp 10 }

ibmdot1dStpForwardDelay OBJECT-TYPE
    SYNTAX  INTEGER      -- a STP timer in units of 1/100 seconds
    ACCESS  read-only
    STATUS  mandatory
    DESCRIPTION
            "This time value, measured in units of hundredths
            of a second, controls how fast a port changes its
            spanning state when moving towards the Forwarding
            state.  The value determines how long the port
            stays in a particular state before moving to the
            next state.  For example, how long a port stays in
            the Listening state when moving from Blocking to
            Learning.  This value is also used, when a
            topology change has been detected and is underway,
            to age all dynamic entries in the Forwarding
            Database.  (Note that this value is the one that
            this bridge is currently using, in contrast to
            ibmdot1dStpBridgeForwardDelay which is the value that
            this bridge and all others would start using
            if/when this bridge were to become the root.)"
    REFERENCE
            "P802.1d/D9, July 14, 1989: Section 4.5.3.6"
    ::= { ibmdot1dStp 11 }

ibmdot1dStpBridgeMaxAge OBJECT-TYPE
--  SYNTAX  Timeout(600..4000)
    SYNTAX  INTEGER      -- a STP timer in units of 1/100 seconds
    ACCESS  read-write
    STATUS  mandatory
    DESCRIPTION
            "The value that all bridges use for MaxAge when
            this bridge is acting as the root.  Note that
            802.1d/D9 specifies that the range for this
            parameter is related to the value of
            ibmdot1dStpBridgeHelloTime. The granularity of this
            timer is specified by 802.1d/D9 to be 1 second.
            An agent may return a badValue error if a set is
            attempted to a value which is not a whole number
            of seconds.

            The IBM 6611 Network Processor obtains this value
            from the 'Max Age' parameter provided to
            the configuration program."
    REFERENCE
            "P802.1d/D9, July 14, 1989: Section 4.5.3.8"
    ::= { ibmdot1dStp 12 }

ibmdot1dStpBridgeHelloTime OBJECT-TYPE
--  SYNTAX  Timeout(100..1000)
    SYNTAX  INTEGER      -- a STP timer in units of 1/100 seconds
    ACCESS  read-write
    STATUS  mandatory
    DESCRIPTION
            "The value that all bridges use for HelloTime when
            this bridge is acting as the root.  The
            granularity of this timer is specified by
            802.1d/D9 to be 1 second.  An agent may return a
            badValue error if a set is attempted to a value
            which is not a whole number of seconds.

            The IBM 6611 Network Processor obtains this value
            from the 'Hello Time' parameter provided to
            the configuration program."
    REFERENCE
            "P802.1d/D9, July 14, 1989: Section 4.5.3.9"
    ::= { ibmdot1dStp 13 }

ibmdot1dStpBridgeForwardDelay OBJECT-TYPE
--  SYNTAX  Timeout(400..3000)
    SYNTAX  INTEGER      -- a STP timer in units of 1/100 seconds
    ACCESS  read-write
    STATUS  mandatory
    DESCRIPTION
            "The value that all bridges use for ForwardDelay
            when this bridge is acting as the root.  Note that
            802.1d/D9 specifies that the range for this
            parameter is related to the value of
            ibmdot1dStpBridgeMaxAge.  The granularity of this
            timer is specified by 802.1d/D9 to be 1 second.
            An agent may return a badValue error if a set is
            attempted to a value which is not a whole number
            of seconds.

            The IBM 6611 Network Processor obtains this value
            from the 'Forward Delay Time' parameter provided to
            the configuration program."
    REFERENCE
            "P802.1d/D9, July 14, 1989: Section 4.5.3.10"
    ::= { ibmdot1dStp 14 }


-- The Spanning Tree Port Table

ibmdot1dStpPortTable OBJECT-TYPE
    SYNTAX  SEQUENCE OF IbmDot1dStpPortEntry
    ACCESS  not-accessible
    STATUS  mandatory
    DESCRIPTION
            "A table that contains port-specific information
            for the Spanning Tree Protocol."
    ::= { ibmdot1dStp 15 }

ibmdot1dStpPortEntry OBJECT-TYPE
    SYNTAX  IbmDot1dStpPortEntry
    ACCESS  not-accessible
    STATUS  mandatory
    DESCRIPTION
            "A list of information maintained by every port
            about the Spanning Tree Protocol state for that
            port."
    INDEX   { ibmdot1dStpPort }
    ::= { ibmdot1dStpPortTable 1 }

IbmDot1dStpPortEntry ::=
    SEQUENCE {
        ibmdot1dStpPort
            INTEGER,
        ibmdot1dStpPortPriority
            INTEGER,
        ibmdot1dStpPortState
            INTEGER,
        ibmdot1dStpPortEnable
            INTEGER,
        ibmdot1dStpPortPathCost
            INTEGER,
        ibmdot1dStpPortDesignatedRoot
            OCTET STRING,
        ibmdot1dStpPortDesignatedCost
            INTEGER,
        ibmdot1dStpPortDesignatedBridge
            OCTET STRING,
        ibmdot1dStpPortDesignatedPort
            OCTET STRING,
        ibmdot1dStpPortForwardTransitions
            Counter
    }

ibmdot1dStpPort OBJECT-TYPE
    SYNTAX  INTEGER
    ACCESS  read-only
    STATUS  mandatory
    DESCRIPTION
            "The port number of the port for which this entry
            contains Spanning Tree Protocol management
            information.

            This port number is the same as that reported by
            ibmdot1dBasePort."
    REFERENCE
            "P802.1d/D9, July 14, 1989: Section 6.8.2.1.2"
    ::= { ibmdot1dStpPortEntry 1 }

ibmdot1dStpPortPriority OBJECT-TYPE
    SYNTAX  INTEGER (0..255)
    ACCESS  read-write
    STATUS  mandatory
    DESCRIPTION
            "The value of the priority field which is
            contained in the first (in network byte order)
            octet of the (2 octet long) Port ID.  The other
            octet of the Port ID is given by the value of
            ibmdot1dStpPort."
    REFERENCE
            "P802.1d/D9, July 14, 1989: Section 4.5.5.1"
    ::= { ibmdot1dStpPortEntry 2 }

ibmdot1dStpPortState OBJECT-TYPE
    SYNTAX  INTEGER {
                disabled(1),
                blocking(2),
                listening(3),
                learning(4),
                forwarding(5),
                broken(6)
            }
    ACCESS  read-only
    STATUS  mandatory
    DESCRIPTION
            "The port's current state as defined by
            application of the Spanning Tree Protocol.  This
            state controls what action a port takes on
            reception of a frame.  If the bridge has detected
            a port that is malfunctioning it will place that
            port into the broken(6) state.  For ports which
            are disabled (see ibmdot1dStpPortEnable), this object
            will have a value of disabled(1)."
    REFERENCE
            "P802.1d/D9, July 14, 1989: Section 4.5.5.2"
    ::= { ibmdot1dStpPortEntry 3 }

ibmdot1dStpPortEnable OBJECT-TYPE
    SYNTAX  INTEGER {
                enabled(1),
                disabled(2)
            }
    ACCESS  read-write
    STATUS  mandatory
    DESCRIPTION
            "The enabled/disabled status of the port."
    REFERENCE
            "P802.1d/D9, July 14, 1989: Section 4.5.5.2"
    ::= { ibmdot1dStpPortEntry 4 }

ibmdot1dStpPortPathCost OBJECT-TYPE
    SYNTAX  INTEGER (1..65535)
    ACCESS  read-write
    STATUS  mandatory
    DESCRIPTION
            "The contribution of this port to the path cost of
            paths towards the spanning tree root which include
            this port.

            The IBM 6611 Network Processor obtains this value
            from the 'Path Cost' parameter provided to
            the configuration program."
    REFERENCE
            "P802.1d/D9, July 14, 1989: Section 4.5.5.3"
    ::= { ibmdot1dStpPortEntry 5 }

ibmdot1dStpPortDesignatedRoot OBJECT-TYPE
    SYNTAX  OCTET STRING (SIZE(8))   -- the Bridge-Identifier as
    ACCESS  read-only
    STATUS  mandatory
    DESCRIPTION
            "The unique Bridge Identifier of the Bridge
            recorded as the Root in the Configuration BPDUs
            transmitted by the Designated Bridge for the
            segment to which the port is attached."
    REFERENCE
            "P802.1d/D9, July 14, 1989: Section 4.5.5.4"
    ::= { ibmdot1dStpPortEntry 6 }

ibmdot1dStpPortDesignatedCost OBJECT-TYPE
    SYNTAX  INTEGER
    ACCESS  read-only
    STATUS  mandatory
    DESCRIPTION
            "The path cost of the Designated Port of the
            segment connected to this port.  This value is
            compared to the Root Path Cost field in received
            bridge PDUs."
    REFERENCE
            "P802.1d/D9, July 14, 1989: Section 4.5.5.5"
    ::= { ibmdot1dStpPortEntry 7 }

ibmdot1dStpPortDesignatedBridge OBJECT-TYPE
    SYNTAX  OCTET STRING (SIZE(8))   -- the Bridge-Identifier as
    ACCESS  read-only
    STATUS  mandatory
    DESCRIPTION
            "The Bridge Identifier of the bridge which this
            port considers to be the Designated Bridge for
            this port's segment."
    REFERENCE
            "P802.1d/D9, July 14, 1989: Section 4.5.5.6"
    ::= { ibmdot1dStpPortEntry 8 }

ibmdot1dStpPortDesignatedPort OBJECT-TYPE
    SYNTAX  OCTET STRING (SIZE (2))
    ACCESS  read-only
    STATUS  mandatory
    DESCRIPTION
            "The Port Identifier of the port on the Designated
            Bridge for this port's segment."
    REFERENCE
            "P802.1d/D9, July 14, 1989: Section 4.5.5.7"
    ::= { ibmdot1dStpPortEntry 9 }

ibmdot1dStpPortForwardTransitions OBJECT-TYPE
    SYNTAX  Counter
    ACCESS  read-only
    STATUS  mandatory
    DESCRIPTION
            "The number of times this port has transitioned
            from the Learning state to the Forwarding state."
    ::= { ibmdot1dStpPortEntry 10 }


-- the ibmdot1dTp group (Transparent Bridging)

-- Implementation of the ibmdot1dTp group is optional.  It is
-- implemented by those bridges that support the transparent
-- bridging mode.  A transparent or SRT bridge will implement
-- this group.


ibmdot1dTpLearnedEntryDiscards OBJECT-TYPE
    SYNTAX  Counter
    ACCESS  read-only
    STATUS  mandatory
    DESCRIPTION
            "The total number of Forwarding Database entries,
            which have been or would have been learnt, but
            have been discarded due to a lack of space to
            store them in the Forwarding Database.  If this
            counter is increasing, it indicates that the
            Forwarding Database is regularly becoming full (a
            condition which has unpleasant performance effects
            on the subnetwork).  If this counter has a
            significant value but is not presently increasing,
            it indicates that the problem has been occurring
            but is not persistent."
    REFERENCE
            "P802.1d/D9, July 14, 1989: Section 6.7.1.1.3"
    ::= { ibmdot1dTp 1 }

ibmdot1dTpAgingTime OBJECT-TYPE
    SYNTAX   INTEGER
    ACCESS   read-write
    STATUS   mandatory
    DESCRIPTION
            "The timeout period in seconds for aging out
            dynamically learned forwarding information.

            The IBM 6611 Network Processor obtains this value
            from the 'Aging Time' parameter provided to
            the configuration program."
    REFERENCE
            "P802.1d/D9, July 14, 1989: Section 6.7.1.1.3"
    ::= { ibmdot1dTp 2 }


--  The Forwarding Database for Transparent Bridges

ibmdot1dTpFdbTable OBJECT-TYPE
    SYNTAX  SEQUENCE OF IbmDot1dTpFdbEntry
    ACCESS  not-accessible
    STATUS  mandatory
    DESCRIPTION
            "A table that contains information about unicast
            entries for which the bridge has forwarding and/or
            filtering information.  This information is used
            by the transparent bridging function in
            determining how to propagate a received frame."
    ::= { ibmdot1dTp 3 }

ibmdot1dTpFdbEntry OBJECT-TYPE
    SYNTAX  IbmDot1dTpFdbEntry
    ACCESS  not-accessible
    STATUS  mandatory
    DESCRIPTION
            "Information about a specific unicast MAC address
            for which the bridge has some forwarding and/or
            filtering information."
    INDEX   { ibmdot1dTpFdbAddress }
    ::= { ibmdot1dTpFdbTable 1 }

IbmDot1dTpFdbEntry ::=
    SEQUENCE {
        ibmdot1dTpFdbAddress
            OCTET STRING,
        ibmdot1dTpFdbPort
            INTEGER,
        ibmdot1dTpFdbStatus
            INTEGER
    }

ibmdot1dTpFdbAddress OBJECT-TYPE
    SYNTAX  OCTET STRING (SIZE(6))    -- a 6 octet address in
    ACCESS  read-only
    STATUS  mandatory
    DESCRIPTION
            "A unicast MAC address for which the bridge has
            forwarding and/or filtering information."
    REFERENCE
            "P802.1d/D9, July 14, 1989: Section 3.9.1, 3.9.2"
    ::= { ibmdot1dTpFdbEntry 1 }

ibmdot1dTpFdbPort OBJECT-TYPE
    SYNTAX  INTEGER
    ACCESS  read-only
    STATUS  mandatory
    DESCRIPTION
            "Either the value '0', or the port number of the
            port on which a frame having a source address
            equal to the value of the corresponding instance
            of ibmdot1dTpFdbAddress has been seen.  A value of
            '0' indicates that the port number has not been
            learned but that the bridge does have some
            forwarding/filtering information about this
            address (e.g. in the ibmdot1dStaticTable).
            Implementors are encouraged to assign the port
            value to this object whenever it is learned even
            for addresses for which the corresponding value of
            ibmdot1dTpFdbStatus is not learned(3)."

    ::= { ibmdot1dTpFdbEntry 2 }

ibmdot1dTpFdbStatus OBJECT-TYPE
    SYNTAX  INTEGER {
                other(1),
                invalid(2),
                learned(3),
                self(4),
                mgmt(5)
            }
    ACCESS  read-only
    STATUS  mandatory
    DESCRIPTION
            "The status of this entry.  The meanings of the
            values are:

              other(1)   : none of the following.  This would
                           include the case where some other
                           MIB object (not the corresponding
                           instance of ibmdot1dTpFdbPort, nor an
                           entry in the ibmdot1dStaticTable) is
                           being used to determine if and how
                           frames addressed to the value of
                           the corresponding instance of
                           ibmdot1dTpFdbAddress are being
                           forwarded.

              invalid(2) : this entry is not longer valid
                           (e.g., it was learned but has since
                           aged-out), but has not yet been
                           flushed from the table.

              learned(3) : the value of the corresponding
                           instance of ibmdot1dTpFdbPort was
                           learned, and is being used.

              self(4)    : the value of the corresponding
                           instance of ibmdot1dTpFdbAddress
                           represents one of the bridge's
                           addresses.  The corresponding
                           instance of ibmdot1dTpFdbPort
                           indicates which of the bridge's
                           ports has this address.

              mgmt(5)    : the value of the corresponding
                           instance of ibmdot1dTpFdbAddress is
                           also the value of an existing
                           instance of ibmdot1dStaticAddress."
    ::= { ibmdot1dTpFdbEntry 3 }


--  Port Table for Transparent Bridges

ibmdot1dTpPortTable OBJECT-TYPE
    SYNTAX  SEQUENCE OF IbmDot1dTpPortEntry
    ACCESS  not-accessible
    STATUS  mandatory
    DESCRIPTION
            "A table that contains information about every
            port that is associated with this transparent
            bridge."
    ::= { ibmdot1dTp 4 }

ibmdot1dTpPortEntry OBJECT-TYPE
    SYNTAX  IbmDot1dTpPortEntry
    ACCESS  not-accessible
    STATUS  mandatory
    DESCRIPTION
            "A list of information for each port of a
            transparent bridge."
    INDEX   { ibmdot1dTpPort }
    ::= { ibmdot1dTpPortTable 1 }

IbmDot1dTpPortEntry ::=
    SEQUENCE {
        ibmdot1dTpPort
            INTEGER,
        ibmdot1dTpPortMaxInfo
            INTEGER,
        ibmdot1dTpPortInFrames
            Counter,
        ibmdot1dTpPortOutFrames
            Counter,
        ibmdot1dTpPortInDiscards
            Counter
    }

ibmdot1dTpPort OBJECT-TYPE
    SYNTAX  INTEGER
    ACCESS  read-only
    STATUS  mandatory
    DESCRIPTION
            "The port number of the port for which this entry
            contains Transparent bridging management
            information."
    ::= { ibmdot1dTpPortEntry 1 }

-- It would be nice if we could use ifMtu as the size of the
-- largest INFO field, but we can't because ifMtu is defined
-- to be the size that the (inter-)network layer can use which
-- can differ from the MAC layer (especially if several layers
-- of encapsulation are used).

ibmdot1dTpPortMaxInfo OBJECT-TYPE
    SYNTAX  INTEGER
    ACCESS  read-only
    STATUS  mandatory
    DESCRIPTION
            "The maximum size of the INFO (non-MAC) field that
            this port will receive or transmit."
    ::= { ibmdot1dTpPortEntry 2 }

ibmdot1dTpPortInFrames OBJECT-TYPE
    SYNTAX  Counter
    ACCESS  read-only
    STATUS  mandatory
    DESCRIPTION
            "The number of frames that have been received by
            this port from its segment. Note that a frame
            received on the interface corresponding to this
            port is only counted by this object if and only if
            it is for a protocol being processed by the local
            bridging function."
    REFERENCE
            "P802.1d/D9, July 14, 1989: Section 6.6.1.1.3"
    ::= { ibmdot1dTpPortEntry 3 }

ibmdot1dTpPortOutFrames OBJECT-TYPE
    SYNTAX  Counter
    ACCESS  read-only
    STATUS  mandatory
    DESCRIPTION
            "The number of frames that have been transmitted
            by this port to its segment.  Note that a frame
            transmitted on the interface corresponding to this
            port is only counted by this object if and only if
            it is for a protocol being processed by the local
            bridging function."
    REFERENCE
            "P802.1d/D9, July 14, 1989: Section 6.6.1.1.3"
    ::= { ibmdot1dTpPortEntry 4 }

ibmdot1dTpPortInDiscards OBJECT-TYPE
    SYNTAX   Counter
    ACCESS   read-only
    STATUS   mandatory
    DESCRIPTION
            "Count of valid frames received which were
            discarded (i.e., filtered) by the Forwarding
            Process."
    REFERENCE
            "P802.1d/D9, July 14, 1989: Section 6.6.1.1.3"
    ::= { ibmdot1dTpPortEntry 5 }



-- The Static (Destination-Address Filtering) Database

-- Implementation of this group is optional.


ibmdot1dStaticTable OBJECT-TYPE
    SYNTAX  SEQUENCE OF IbmDot1dStaticEntry
    ACCESS  not-accessible
    STATUS  mandatory
    DESCRIPTION
            "A table containing filtering information
            configured into the bridge by (local or network)
            management specifying the set of ports to which
            frames received from specific ports and containing
            specific destination addresses are allowed to be
            forwarded.  The value of zero in this table as the
            port number from which frames with a specific
            destination address are received, is used to
            specify all ports for which there is no specific
            entry in this table for that particular
            destination address.  Entries are valid for
            unicast and for group/broadcast addresses."
    REFERENCE
            "P802.1d/D9, July 14, 1989: Section 6.7.2"
    ::= { ibmdot1dStatic 1 }

ibmdot1dStaticEntry OBJECT-TYPE
    SYNTAX  IbmDot1dStaticEntry
    ACCESS  not-accessible
    STATUS  mandatory
    DESCRIPTION
            "Filtering information configured into the bridge
            by (local or network) management specifying the
            set of ports to which frames received from a
            specific port and containing a specific
            destination address are allowed to be forwarded."
    REFERENCE
            "P802.1d/D9, July 14,1989: Section 6.7.2"
    INDEX   { ibmdot1dStaticAddress, ibmdot1dStaticReceivePort }
    ::= { ibmdot1dStaticTable 1 }

IbmDot1dStaticEntry ::=
    SEQUENCE {
        ibmdot1dStaticAddress
            OCTET STRING,
        ibmdot1dStaticReceivePort
            INTEGER,
        ibmdot1dStaticAllowedToGoTo
            OCTET STRING,
        ibmdot1dStaticStatus
            INTEGER
    }

ibmdot1dStaticAddress OBJECT-TYPE
    SYNTAX  OCTET STRING (SIZE(6))    -- a 6 octet address in
    ACCESS  read-write
    STATUS  mandatory
    DESCRIPTION
            "The destination MAC address in a frame to which
            this entry's filtering information applies.  This
            object can take the value of a unicast address, a
            group address or the broadcast address."
    REFERENCE
            "P802.1d/D9, July 14, 1989: Section 3.9.1, 3.9.2"
    ::= { ibmdot1dStaticEntry 1 }

ibmdot1dStaticReceivePort OBJECT-TYPE
    SYNTAX  INTEGER
    ACCESS  read-write
    STATUS  mandatory
    DESCRIPTION
            "Either the value '0', or the port number of the
            port from which a frame must be received in order
            for this entry's filtering information to apply.
            A value of zero indicates that this entry applies
            on all ports of the bridge for which there is no
            other applicable entry."
    ::= { ibmdot1dStaticEntry 2 }

ibmdot1dStaticAllowedToGoTo OBJECT-TYPE
    SYNTAX  OCTET STRING
    ACCESS  read-write
    STATUS  mandatory
    DESCRIPTION
            "The set of ports to which frames received from a
            specific port and destined for a specific MAC
            address, are allowed to be forwarded.  Each octet
            within the value of this object specifies a set of
            eight ports, with the first octet specifying ports
            1 through 8, the second octet specifying ports 9
            through 16, etc.  Within each octet, the most
            significant bit represents the lowest numbered
            port, and the least significant bit represents the
            highest numbered port.  Thus, each port of the
            bridge is represented by a single bit within the
            value of this object.  If that bit has a value of
            '1' then that port is included in the set of
            ports; the port is not included if its bit has a
            value of '0'.  (Note that the setting of the bit
            corresponding to the port from which a frame is
            received is irrelevant.)"
    ::= { ibmdot1dStaticEntry 3 }

ibmdot1dStaticStatus OBJECT-TYPE
    SYNTAX  INTEGER {
                other(1),
                invalid(2),
                permanent(3),
                deleteOnReset(4),
                deleteOnTimeout(5)
            }
    ACCESS  read-write
    STATUS  mandatory
    DESCRIPTION
            "This object indicates the status of this entry.
                 other(1) - this entry is currently in use but
                      the conditions under which it will
                      remain so are different from each of the
                      following values.
                 invalid(2) - writing this value to the object
                      removes the corresponding entry.
                 permanent(3) - this entry is currently in use
                      and will remain so after the next reset
                      of the bridge.
                 deleteOnReset(4) - this entry is currently in
                      use and will remain so until the next
                      reset of the bridge.
                 deleteOnTimeout(5) - this entry is currently
                      in use and will remain so until it is
                      aged out."
    ::= { ibmdot1dStaticEntry 4 }


--
-- MAC Address Filter Information Table
--

ibmtbmacFiltInfoTable OBJECT-TYPE
    SYNTAX  SEQUENCE OF TBMacAddrFilterInfoEntry
    ACCESS  not-accessible
    STATUS  mandatory
    DESCRIPTION
            "Table of MAC address filtering information."
    ::= { ibmtbMACAddressFilters 1 }

ibmtbmacFiltInfoEntry OBJECT-TYPE
    SYNTAX  TBMacAddrFilterInfoEntry
    ACCESS  not-accessible
    STATUS  mandatory
    DESCRIPTION
            "MAC address filtering information for a single interface."
    INDEX   { ibmtbmacFiltIfIndex }
    ::= { ibmtbmacFiltInfoTable 1 }

TBMacAddrFilterInfoEntry ::=
    SEQUENCE {
        ibmtbmacFiltIfIndex
            INTEGER,
        ibmtbmacFiltInFilterType
            INTEGER,
        ibmtbmacFiltOutFilterType
            INTEGER,
        ibmtbmacFiltInNotForwarded
            Counter,
        ibmtbmacFiltOutNotForwarded
            Counter
    }

ibmtbmacFiltIfIndex OBJECT-TYPE
    SYNTAX  INTEGER
    ACCESS  read-only
    STATUS  mandatory
    DESCRIPTION
            "The value of this object identifies the interface for which
            this entry contains management information.  The value of
            this object for a particular interface has the same value
            as the ifIndex object for the same interface."
    ::= { ibmtbmacFiltInfoEntry 1 }

ibmtbmacFiltInFilterType OBJECT-TYPE
    SYNTAX  INTEGER {
                deny(1),    -- frames matching the filter criteria
                            -- are denied
                permit(2)   -- frames matching the filter criteria
                            -- are permitted
            }
    ACCESS  read-only
    STATUS  mandatory
    DESCRIPTION
            "For the incoming filter table, determines whether
            the entries are permit or deny entries."
    ::= { ibmtbmacFiltInfoEntry 2 }

ibmtbmacFiltOutFilterType OBJECT-TYPE
    SYNTAX  INTEGER {
                deny(1),    -- frames matching the filter criteria
                            -- are denied
                permit(2)   -- frames matching the filter criteria
                            -- are permitted
            }
    ACCESS  read-only
    STATUS  mandatory
    DESCRIPTION
            "For the outgoing filter table, determines whether
            the entries are permit or deny entries."
    ::= { ibmtbmacFiltInfoEntry 3 }

ibmtbmacFiltInNotForwarded OBJECT-TYPE
    SYNTAX  Counter
    ACCESS  read-only
    STATUS  mandatory
    DESCRIPTION
            "Number of packets not forwarded, in the incoming
            direction, because they were filtered out."
    ::= { ibmtbmacFiltInfoEntry 4 }

ibmtbmacFiltOutNotForwarded OBJECT-TYPE
    SYNTAX  Counter
    ACCESS  read-only
    STATUS  mandatory
    DESCRIPTION
            "Number of packets not forwarded, in the outgoing
            direction, because they were filtered out."
    ::= { ibmtbmacFiltInfoEntry 5 }

--
-- The Incoming MAC Address Filter Table
--

ibmtbmacFiltInTable OBJECT-TYPE
    SYNTAX  SEQUENCE OF TBMacAddrFilterInEntry
    ACCESS  not-accessible
    STATUS  mandatory
    DESCRIPTION
            "Table of MAC address filtering information
            for incoming frames."
    ::= { ibmtbMACAddressFilters 2 }

ibmtbmacFiltInEntry OBJECT-TYPE
    SYNTAX  TBMacAddrFilterInEntry
    ACCESS  not-accessible
    STATUS  mandatory
    DESCRIPTION
            "Filtering information for incoming frames."
    INDEX   { ibmtbmacFiltInIfIndex, ibmtbmacFiltInSrcAddress,
              ibmtbmacFiltInDestAddress }
    ::= { ibmtbmacFiltInTable 1 }

TBMacAddrFilterInEntry ::=
    SEQUENCE {
        ibmtbmacFiltInIfIndex
            INTEGER,
        ibmtbmacFiltInSrcAddress
            OCTET STRING,
        ibmtbmacFiltInSrcMask
            OCTET STRING,
        ibmtbmacFiltInDestAddress
            OCTET STRING,
        ibmtbmacFiltInDestMask
            OCTET STRING
    }

ibmtbmacFiltInIfIndex OBJECT-TYPE
    SYNTAX  INTEGER
    ACCESS  read-only
    STATUS  mandatory
    DESCRIPTION
            "The value of this object identifies the interface for which
            this entry contains management information.  The value of
            this object for a particular interface has the same value
            as the ifIndex object for the same interface."
    ::= { ibmtbmacFiltInEntry 1 }

ibmtbmacFiltInSrcAddress OBJECT-TYPE
    SYNTAX  OCTET STRING (SIZE(6))    -- a 6 octet address in
    ACCESS  read-only
    STATUS  mandatory
    DESCRIPTION
            "MAC source address to be filtered."
    ::= { ibmtbmacFiltInEntry 2 }

ibmtbmacFiltInSrcMask OBJECT-TYPE
    SYNTAX  OCTET STRING (SIZE(6))    -- a 6 octet address in
    ACCESS  read-only
    STATUS  mandatory
    DESCRIPTION
            "Mask to allow ibmtbmacFiltInSrcAddress to be used
            as a range of values."
    ::= { ibmtbmacFiltInEntry 3 }

ibmtbmacFiltInDestAddress OBJECT-TYPE
    SYNTAX  OCTET STRING (SIZE(6))    -- a 6 octet address in
    ACCESS  read-only
    STATUS  mandatory
    DESCRIPTION
            "MAC destination address to be filtered."
    ::= { ibmtbmacFiltInEntry 4 }

ibmtbmacFiltInDestMask OBJECT-TYPE
    SYNTAX  OCTET STRING (SIZE(6))    -- a 6 octet address in
    ACCESS  read-only
    STATUS  mandatory
    DESCRIPTION
            "Mask to allow ibmtbmacFiltInDestAddress to be used
            as a range of values."
    ::= { ibmtbmacFiltInEntry 5 }


--
-- The Outgoing MAC Address Filter Table
--

ibmtbmacFiltOutTable OBJECT-TYPE
    SYNTAX  SEQUENCE OF TBMacAddrFilterOutEntry
    ACCESS  not-accessible
    STATUS  mandatory
    DESCRIPTION
            "Table of MAC address filtering information
            for outgoing frames."
    ::= { ibmtbMACAddressFilters 3 }

ibmtbmacFiltOutEntry OBJECT-TYPE
    SYNTAX  TBMacAddrFilterOutEntry
    ACCESS  not-accessible
    STATUS  mandatory
    DESCRIPTION
            "Filtering information for outgoing frames."
    INDEX   { ibmtbmacFiltOutIfIndex, ibmtbmacFiltOutSrcAddress,
              ibmtbmacFiltOutDestAddress }
    ::= { ibmtbmacFiltOutTable 1 }

TBMacAddrFilterOutEntry ::=
    SEQUENCE {
        ibmtbmacFiltOutIfIndex
            INTEGER,
        ibmtbmacFiltOutSrcAddress
            OCTET STRING,
        ibmtbmacFiltOutSrcMask
            OCTET STRING,
        ibmtbmacFiltOutDestAddress
            OCTET STRING,
        ibmtbmacFiltOutDestMask
            OCTET STRING
    }

ibmtbmacFiltOutIfIndex OBJECT-TYPE
    SYNTAX  INTEGER
    ACCESS  read-only
    STATUS  mandatory
    DESCRIPTION
            "The value of this object identifies the interface for which
            this entry contains management information.  The value of
            this object for a particular interface has the same value
            as the ifIndex object for the same interface."
    ::= { ibmtbmacFiltOutEntry 1 }

ibmtbmacFiltOutSrcAddress OBJECT-TYPE
    SYNTAX  OCTET STRING (SIZE(6))    -- a 6 octet address in
    ACCESS  read-only
    STATUS  mandatory
    DESCRIPTION
            "MAC source address to be filtered."
    ::= { ibmtbmacFiltOutEntry 2 }

ibmtbmacFiltOutSrcMask OBJECT-TYPE
    SYNTAX  OCTET STRING (SIZE(6))    -- a 6 octet address in
    ACCESS  read-only
    STATUS  mandatory
    DESCRIPTION
            "Mask to allow ibmtbmacFiltOutSrcAddress to be used
            as a range of values."
    ::= { ibmtbmacFiltOutEntry 3 }

ibmtbmacFiltOutDestAddress OBJECT-TYPE
    SYNTAX  OCTET STRING (SIZE(6))    -- a 6 octet address in
    ACCESS  read-only
    STATUS  mandatory
    DESCRIPTION
            "MAC destination address to be filtered."
    ::= { ibmtbmacFiltOutEntry 4 }

ibmtbmacFiltOutDestMask OBJECT-TYPE
    SYNTAX  OCTET STRING (SIZE(6))    -- a 6 octet address in
    ACCESS  read-only
    STATUS  mandatory
    DESCRIPTION
            "Mask to allow ibmtbmacFiltOutDestAddress to be used
            as a range of values."
    ::= { ibmtbmacFiltOutEntry 5 }


--
-- The SAP Filter Information Table
--
-- NOTE: The SAP filter tables themselves are included in this
-- table because they are encoded as octet strings.  Permit/deny
-- information is implicit in these tables.
--

ibmtbsapFiltInfoTable OBJECT-TYPE
    SYNTAX  SEQUENCE OF TBSapFilterInfoEntry
    ACCESS  not-accessible
    STATUS  mandatory
    DESCRIPTION
            "Table of SAP filtering information."
    ::= { ibmtbSAPFilters 1 }

ibmtbsapFiltInfoEntry OBJECT-TYPE
    SYNTAX  TBSapFilterInfoEntry
    ACCESS  not-accessible
    STATUS  mandatory
    DESCRIPTION
            "SAP filtering information for a single interface."
    INDEX   { ibmtbsapFiltIfIndex }
    ::= { ibmtbsapFiltInfoTable 1 }

TBSapFilterInfoEntry ::=
    SEQUENCE {
        ibmtbsapFiltIfIndex
            INTEGER,
        ibmtbsapFiltIn
            OCTET STRING,
        ibmtbsapFiltOut
            OCTET STRING,
        ibmtbsapFiltInNotForwarded
            Counter,
        ibmtbsapFiltOutNotForwarded
            Counter
    }

ibmtbsapFiltIfIndex OBJECT-TYPE
    SYNTAX  INTEGER
    ACCESS  read-only
    STATUS  mandatory
    DESCRIPTION
            "The value of this object identifies the interface for which
            this entry contains management information.  The value of
            this object for a particular interface has the same value
            as the ifIndex object for the same interface."
    ::= { ibmtbsapFiltInfoEntry 1 }

ibmtbsapFiltIn OBJECT-TYPE
    SYNTAX  OCTET STRING (SIZE (16))
    ACCESS  read-only
    STATUS  mandatory
    DESCRIPTION
            "A bitmap of all possible source SAPs (even) that will
            be on or off depending on whether or not an incoming
            frame with that SAP is to be forwarded."
    ::= { ibmtbsapFiltInfoEntry 2 }

ibmtbsapFiltOut OBJECT-TYPE
    SYNTAX  OCTET STRING (SIZE (16))
    ACCESS  read-only
    STATUS  mandatory
    DESCRIPTION
            "A bitmap of all possible source SAPs (even) that will
            be on or off depending on whether or not an outgoing
            frame with that SAP is to be forwarded."
    ::= { ibmtbsapFiltInfoEntry 3 }

ibmtbsapFiltInNotForwarded OBJECT-TYPE
    SYNTAX  Counter
    ACCESS  read-only
    STATUS  mandatory
    DESCRIPTION
            "Number of packets not forwarded, in the incoming
            direction, because they were filtered out."
    ::= { ibmtbsapFiltInfoEntry 4 }

ibmtbsapFiltOutNotForwarded OBJECT-TYPE
    SYNTAX  Counter
    ACCESS  read-only
    STATUS  mandatory
    DESCRIPTION
            "Number of packets not forwarded, in the outgoing
            direction, because they were filtered out."
    ::= { ibmtbsapFiltInfoEntry 5 }


--
-- The Ethernet Type Filter Information Table
--

ibmtbEthTypeFiltInfoTable OBJECT-TYPE
    SYNTAX  SEQUENCE OF TBEthTypeFilterInfoEntry
    ACCESS  not-accessible
    STATUS  mandatory
    DESCRIPTION
            "Table of Ethernet type filtering information. Note that
             this filtering only applies to:
               1) The Ethernet TYPE field for DIX version 2 frames.
               2) The Ethernet TYPE field contained in the SNAP
                  header of 802.3 frames, if the frame contains a
                  SNAP header (SSAP = DSAP = 0xAA)"
    ::= { ibmtbEthTypeFilters 1 }

ibmtbEthTypeFiltInfoEntry OBJECT-TYPE
    SYNTAX  TBEthTypeFilterInfoEntry
    ACCESS  not-accessible
    STATUS  mandatory
    DESCRIPTION
            "Ethernet type filtering information for a single interface."
    INDEX   { ibmtbEthTypeFiltIfIndex }
    ::= { ibmtbEthTypeFiltInfoTable 1 }

TBEthTypeFilterInfoEntry ::=
    SEQUENCE {
        ibmtbEthTypeFiltIfIndex
            INTEGER,
        ibmtbEthTypeFiltInFilterType
            INTEGER,
        ibmtbEthTypeFiltOutFilterType
            INTEGER,
        ibmtbEthTypeFiltInNotForwarded
            Counter,
        ibmtbEthTypeFiltOutNotForwarded
            Counter
    }

ibmtbEthTypeFiltIfIndex OBJECT-TYPE
    SYNTAX  INTEGER
    ACCESS  read-only
    STATUS  mandatory
    DESCRIPTION
            "The value of this object identifies the interface for which
            this entry contains management information.  The value of
            this object for a particular interface has the same value
            as the ifIndex object for the same interface."
    ::= { ibmtbEthTypeFiltInfoEntry 1 }

ibmtbEthTypeFiltInFilterType OBJECT-TYPE
    SYNTAX  INTEGER {
                deny(1),    -- frames matching the filter criteria
                            -- are denied
                permit(2)   -- frames matching the filter criteria
                            -- are permitted
            }
    ACCESS  read-only
    STATUS  mandatory
    DESCRIPTION
            "For the incoming Ethernet type filter table, determines whether
            the entries are permit or deny entries."
    ::= { ibmtbEthTypeFiltInfoEntry 2 }

ibmtbEthTypeFiltOutFilterType OBJECT-TYPE
    SYNTAX  INTEGER {
                deny(1),    -- frames matching the filter criteria
                            -- are denied
                permit(2)   -- frames matching the filter criteria
                            -- are permitted
            }
    ACCESS  read-only
    STATUS  mandatory
    DESCRIPTION
            "For the outgoing Ethernet type filter table, determines whether
            the entries are permit or deny entries."
    ::= { ibmtbEthTypeFiltInfoEntry 3 }

ibmtbEthTypeFiltInNotForwarded OBJECT-TYPE
    SYNTAX  Counter
    ACCESS  read-only
    STATUS  mandatory
    DESCRIPTION
            "Number of packets not forwarded, in the incoming
            direction, because they were filtered out."
    ::= { ibmtbEthTypeFiltInfoEntry 4 }

ibmtbEthTypeFiltOutNotForwarded OBJECT-TYPE
    SYNTAX  Counter
    ACCESS  read-only
    STATUS  mandatory
    DESCRIPTION
            "Number of packets not forwarded, in the outgoing
            direction, because they were filtered out."
    ::= { ibmtbEthTypeFiltInfoEntry 5 }


--
-- The Incoming Ethernet Type Filter Table
--

ibmtbEthTypeFiltInTable OBJECT-TYPE
    SYNTAX  SEQUENCE OF TBEthTypeFilterInEntry
    ACCESS  not-accessible
    STATUS  mandatory
    DESCRIPTION
            "Table of Ethernet type filtering information
             for incoming frames.  Note that
             this filtering only applies to:
               1) The Ethernet TYPE field for DIX version 2 frames.
               2) The Ethernet TYPE field contained in the SNAP
                  header of 802.3 frames, if the frame contains a
                  SNAP header (SSAP = DSAP = 0xAA)"
    ::= { ibmtbEthTypeFilters 2 }

ibmtbEthTypeFiltInEntry OBJECT-TYPE
    SYNTAX  TBEthTypeFilterInEntry
    ACCESS  not-accessible
    STATUS  mandatory
    DESCRIPTION
            "Filtering information for a single Ethernet type on a
            single interface."
    INDEX   { ibmtbEthTypeFiltInIfIndex, ibmtbEthTypeFiltInValue }
    ::= { ibmtbEthTypeFiltInTable 1 }

TBEthTypeFilterInEntry ::=
    SEQUENCE {
        ibmtbEthTypeFiltInIfIndex
            INTEGER,
        ibmtbEthTypeFiltInValue
            OCTET STRING (SIZE(2)),
        ibmtbEthTypeFiltInMask
            OCTET STRING (SIZE(2))
    }

ibmtbEthTypeFiltInIfIndex OBJECT-TYPE
    SYNTAX  INTEGER
    ACCESS  read-only
    STATUS  mandatory
    DESCRIPTION
            "The value of this object identifies the interface for which
            this entry contains management information.  The value of
            this object for a particular interface has the same value
            as the ifIndex object for the same interface."
    ::= { ibmtbEthTypeFiltInEntry 1 }

ibmtbEthTypeFiltInValue OBJECT-TYPE
    SYNTAX  OCTET STRING (SIZE(2))
    ACCESS  read-only
    STATUS  mandatory
    DESCRIPTION
            "Indicates which Ethernet type to filter."
    ::= { ibmtbEthTypeFiltInEntry 2 }

ibmtbEthTypeFiltInMask OBJECT-TYPE
    SYNTAX  OCTET STRING (SIZE(2))
    ACCESS  read-only
    STATUS  mandatory
    DESCRIPTION
            "Mask to allow ibmtbEthTypeFiltInValue to be used as a range of
            values."
    ::= { ibmtbEthTypeFiltInEntry 3 }


--
-- The Outgoing Ethernet Type Filter Table
--

ibmtbEthTypeFiltOutTable OBJECT-TYPE
    SYNTAX  SEQUENCE OF TBEthTypeFilterOutEntry
    ACCESS  not-accessible
    STATUS  mandatory
    DESCRIPTION
            "Table of Ethernet type filtering information
             for outgoing frames.  Note that
             this filtering only applies to:
               1) The Ethernet TYPE field for DIX version 2 frames.
               2) The Ethernet TYPE field contained in the SNAP
                  header of 802.3 frames, if the frame contains a
                  SNAP header (SSAP = DSAP = 0xAA)"
    ::= { ibmtbEthTypeFilters 3 }

ibmtbEthTypeFiltOutEntry OBJECT-TYPE
    SYNTAX  TBEthTypeFilterOutEntry
    ACCESS  not-accessible
    STATUS  mandatory
    DESCRIPTION
            "Filtering information for a single Ethernet type on a
            single interface."
    INDEX   { ibmtbEthTypeFiltOutIfIndex, ibmtbEthTypeFiltOutValue }
    ::= { ibmtbEthTypeFiltOutTable 1 }

TBEthTypeFilterOutEntry ::=
    SEQUENCE {
        ibmtbEthTypeFiltOutIfIndex
            INTEGER,
        ibmtbEthTypeFiltOutValue
            OCTET STRING (SIZE(2)),
        ibmtbEthTypeFiltOutMask
            OCTET STRING (SIZE(2))
    }

ibmtbEthTypeFiltOutIfIndex OBJECT-TYPE
    SYNTAX  INTEGER
    ACCESS  read-only
    STATUS  mandatory
    DESCRIPTION
            "The value of this object identifies the interface for which
            this entry contains management information.  The value of
            this object for a particular interface has the same value
            as the ifIndex object for the same interface."
    ::= { ibmtbEthTypeFiltOutEntry 1 }

ibmtbEthTypeFiltOutValue OBJECT-TYPE
    SYNTAX  OCTET STRING (SIZE(2))
    ACCESS  read-only
    STATUS  mandatory
    DESCRIPTION
            "Indicates which Ethernet type to filter."
    ::= { ibmtbEthTypeFiltOutEntry 2 }

ibmtbEthTypeFiltOutMask OBJECT-TYPE
    SYNTAX  OCTET STRING (SIZE(2))
    ACCESS  read-only
    STATUS  mandatory
    DESCRIPTION
            "Mask to allow ibmtbEthTypeFiltOutValue to be used as a
            range of values."
    ::= { ibmtbEthTypeFiltOutEntry 3 }


--
-- Window Filter Information Table
--

ibmtbwinFiltInfoTable OBJECT-TYPE
    SYNTAX  SEQUENCE OF TBWindowFilterInfoEntry
    ACCESS  not-accessible
    STATUS  mandatory
    DESCRIPTION
            "Table of Window filtering information."
    ::= { ibmtbWindowFilters 1 }

ibmtbwinFiltInfoEntry OBJECT-TYPE
    SYNTAX  TBWindowFilterInfoEntry
    ACCESS  not-accessible
    STATUS  mandatory
    DESCRIPTION
            "Window filtering information for a single interface."
    INDEX   { ibmtbwinFiltIfIndex }
    ::= { ibmtbwinFiltInfoTable 1 }

TBWindowFilterInfoEntry ::=
    SEQUENCE {
        ibmtbwinFiltIfIndex
            INTEGER,
        ibmtbwinFiltInFilterType
            INTEGER,
        ibmtbwinFiltOutFilterType
            INTEGER,
        ibmtbwinFiltInNotForwarded
            Counter,
        ibmtbwinFiltOutNotForwarded
            Counter
    }

ibmtbwinFiltIfIndex OBJECT-TYPE
    SYNTAX  INTEGER
    ACCESS  read-only
    STATUS  mandatory
    DESCRIPTION
            "The value of this object identifies the interface for which
            this entry contains management information.  The value of
            this object for a particular interface has the same value
            as the ifIndex object for the same interface."
    ::= { ibmtbwinFiltInfoEntry 1 }

ibmtbwinFiltInFilterType OBJECT-TYPE
    SYNTAX  INTEGER {
                deny(1),    -- frames matching the filter criteria
                            -- are denied
                permit(2)   -- frames matching the filter criteria
                            -- are permitted
            }
    ACCESS  read-only
    STATUS  mandatory
    DESCRIPTION
            "For the incoming filter table, determines whether
            the entries are permit or deny entries."
    ::= { ibmtbwinFiltInfoEntry 2 }

ibmtbwinFiltOutFilterType OBJECT-TYPE
    SYNTAX  INTEGER {
                deny(1),    -- frames matching the filter criteria
                            -- are denied
                permit(2)   -- frames matching the filter criteria
                            -- are permitted
            }
    ACCESS  read-only
    STATUS  mandatory
    DESCRIPTION
            "For the outgoing filter table, determines whether
            the entries are permit or deny entries."
    ::= { ibmtbwinFiltInfoEntry 3 }

ibmtbwinFiltInNotForwarded OBJECT-TYPE
    SYNTAX  Counter
    ACCESS  read-only
    STATUS  mandatory
    DESCRIPTION
            "Number of packets not forwarded, in the incoming
            direction, because they were filtered out."
    ::= { ibmtbwinFiltInfoEntry 4 }

ibmtbwinFiltOutNotForwarded OBJECT-TYPE
    SYNTAX  Counter
    ACCESS  read-only
    STATUS  mandatory
    DESCRIPTION
            "Number of packets not forwarded, in the outgoing
            direction, because they were filtered out."
    ::= { ibmtbwinFiltInfoEntry 5 }

--
-- The Incoming Window Filter Table
--

ibmtbwinFiltInTable OBJECT-TYPE
    SYNTAX  SEQUENCE OF TBWindowFilterInEntry
    ACCESS  not-accessible
    STATUS  mandatory
    DESCRIPTION
            "Table of Window filtering information
            for incoming frames."
    ::= { ibmtbWindowFilters 2 }

ibmtbwinFiltInEntry OBJECT-TYPE
    SYNTAX  TBWindowFilterInEntry
    ACCESS  not-accessible
    STATUS  mandatory
    DESCRIPTION
            "Filtering information for incoming frames."
    INDEX   { ibmtbwinFiltInIfIndex, ibmtbwinFiltInId, ibmtbwinFiltInContents }
    ::= { ibmtbwinFiltInTable 1 }

TBWindowFilterInEntry ::=
    SEQUENCE {
        ibmtbwinFiltInIfIndex
            INTEGER,
        ibmtbwinFiltInContents
            OCTET STRING,
        ibmtbwinFiltInMaskString
            OCTET STRING,
        ibmtbwinFiltInOffsetStart
            DisplayString,
        ibmtbwinFiltInNumBytes
            OCTET STRING,
        ibmtbwinFiltInOffset
            OCTET STRING,
        ibmtbwinFiltInId
            INTEGER
    }

ibmtbwinFiltInIfIndex OBJECT-TYPE
    SYNTAX  INTEGER
    ACCESS  read-only
    STATUS  mandatory
    DESCRIPTION
            "The value of this object identifies the interface for which
            this entry contains management information.  The value of
            this object for a particular interface has the same value
            as the ifIndex object for the same interface."
    ::= { ibmtbwinFiltInEntry 1 }

ibmtbwinFiltInContents OBJECT-TYPE
    SYNTAX  OCTET STRING
    ACCESS  read-only
    STATUS  mandatory
    DESCRIPTION
            "String of bytes that will be compared with bytes in the
             frame."
    ::= { ibmtbwinFiltInEntry 2 }

ibmtbwinFiltInMaskString OBJECT-TYPE
    SYNTAX  OCTET STRING
    ACCESS  read-only
    STATUS  mandatory
    DESCRIPTION
            "String of bytes that will be masked with bytes in the
             contents field."
    ::= { ibmtbwinFiltInEntry 3 }

ibmtbwinFiltInOffsetStart OBJECT-TYPE
    SYNTAX  DisplayString
    ACCESS  read-only
    STATUS  mandatory
    DESCRIPTION
            "Determines the starting point where the contents field should be
            applied. A value of 'MAC' means the base is at the beginning of
            the destination MAC address field, whereas, a value of 'DATA' means
            it is applied at the beginning of the data field."
    ::= { ibmtbwinFiltInEntry 4 }

ibmtbwinFiltInNumBytes OBJECT-TYPE
    SYNTAX  OCTET STRING (SIZE(1))    --  size of character
    ACCESS  read-only
    STATUS  mandatory
    DESCRIPTION
            "Number of bytes in the contents field that are used
             for filtering"
    ::= { ibmtbwinFiltInEntry 5 }

ibmtbwinFiltInOffset  OBJECT-TYPE
    SYNTAX  OCTET STRING (SIZE(2))    --  size of character
    ACCESS  read-only
    STATUS  mandatory
    DESCRIPTION
            "Number of bytes offset into the frame from the offset start point
             to begin the compare."
    ::= { ibmtbwinFiltInEntry 6 }

ibmtbwinFiltInId OBJECT-TYPE
    SYNTAX  INTEGER
    ACCESS  read-only
    STATUS  mandatory
    DESCRIPTION
            "A unique identifier associated with this window filter
            entry."
    ::= { ibmtbwinFiltInEntry 7 }


--
-- The Outgoing Window Filter Table
--

ibmtbwinFiltOutTable OBJECT-TYPE
    SYNTAX  SEQUENCE OF TBWindowFilterOutEntry
    ACCESS  not-accessible
    STATUS  mandatory
    DESCRIPTION
            "Table of Window filtering information
            for outgoing frames."
    ::= { ibmtbWindowFilters 3 }

ibmtbwinFiltOutEntry OBJECT-TYPE
    SYNTAX  TBWindowFilterOutEntry
    ACCESS  not-accessible
    STATUS  mandatory
    DESCRIPTION
            "Filtering information for outgoing frames."
    INDEX   { ibmtbwinFiltOutIfIndex, ibmtbwinFiltOutId, ibmtbwinFiltOutContents }
    ::= { ibmtbwinFiltOutTable 1 }

TBWindowFilterOutEntry ::=
    SEQUENCE {
        ibmtbwinFiltOutIfIndex
            INTEGER,
        ibmtbwinFiltOutContents
            OCTET STRING,
        ibmtbwinFiltOutMaskString
            OCTET STRING,
        ibmtbwinFiltOutOffsetStart
            DisplayString,
        ibmtbwinFiltOutNumBytes
            OCTET STRING,
        ibmtbwinFiltOutOffset
            OCTET STRING,
        ibmtbwinFiltOutId
            INTEGER
    }

ibmtbwinFiltOutIfIndex OBJECT-TYPE
    SYNTAX  INTEGER
    ACCESS  read-only
    STATUS  mandatory
    DESCRIPTION
            "The value of this object identifies the interface for which
            this entry contains management information.  The value of
            this object for a particular interface has the same value
            as the ifIndex object for the same interface."
    ::= { ibmtbwinFiltOutEntry 1 }

ibmtbwinFiltOutContents OBJECT-TYPE
    SYNTAX  OCTET STRING
    ACCESS  read-only
    STATUS  mandatory
    DESCRIPTION
            "String of bytes that will be compared with bytes in the
             frame."
    ::= { ibmtbwinFiltOutEntry 2 }

ibmtbwinFiltOutMaskString OBJECT-TYPE
    SYNTAX  OCTET STRING
    ACCESS  read-only
    STATUS  mandatory
    DESCRIPTION
            "String of bytes that will be masked with bytes in the
             contents field."
    ::= { ibmtbwinFiltOutEntry 3 }

ibmtbwinFiltOutOffsetStart  OBJECT-TYPE
    SYNTAX  DisplayString
    ACCESS  read-only
    STATUS  mandatory
    DESCRIPTION
            "Determines the starting point where the contents field should be
            applied. A value of 'MAC' means the base is at the beginning of
            the destination MAC address field, whereas, a value of 'DATA' means
            it is applied at the beginning of the data field."
    ::= { ibmtbwinFiltOutEntry 4 }

ibmtbwinFiltOutNumBytes OBJECT-TYPE
    SYNTAX  OCTET STRING (SIZE(1))    --  size of character
    ACCESS  read-only
    STATUS  mandatory
    DESCRIPTION
            "Number of bytes in the contents field that are used
             for filtering"
    ::= { ibmtbwinFiltOutEntry 5 }

ibmtbwinFiltOutOffset  OBJECT-TYPE
    SYNTAX  OCTET STRING (SIZE(2))    --  size of character
    ACCESS  read-only
    STATUS  mandatory
    DESCRIPTION
            "Number of bytes offset into the frame from the offset start point
             to begin the compare."
    ::= { ibmtbwinFiltOutEntry 6 }

ibmtbwinFiltOutId OBJECT-TYPE
    SYNTAX  INTEGER
    ACCESS  read-only
    STATUS  mandatory
    DESCRIPTION
            "A unique identifier associated with this window filter
            entry."
    ::= { ibmtbwinFiltOutEntry 7 }


--
-- The Incoming Filter Order Table
--

ibmtbFiltOrderInTable OBJECT-TYPE
    SYNTAX  SEQUENCE OF TBFiltOrderInEntry
    ACCESS  not-accessible
    STATUS  mandatory
    DESCRIPTION
            "Table of information describing which order
            the filters are applied for incoming frames."
    ::= { ibmtbFiltOrderTable 1 }

ibmtbFiltOrderInEntry OBJECT-TYPE
    SYNTAX  TBFiltOrderInEntry
    ACCESS  not-accessible
    STATUS  mandatory
    DESCRIPTION
            "Filter order information for incoming frames."
    INDEX   { ibmtbFiltOrderInPriority }
    ::= { ibmtbFiltOrderInTable 1 }

TBFiltOrderInEntry ::=
    SEQUENCE {
        ibmtbFiltOrderInIfIndex
            INTEGER,
        ibmtbFiltOrderInPriority
            INTEGER,
        ibmtbFiltOrderInName
            DisplayString
    }

ibmtbFiltOrderInIfIndex OBJECT-TYPE
    SYNTAX  INTEGER
    ACCESS  read-only
    STATUS  mandatory
    DESCRIPTION
            "The value of this object identifies the interface for which
            this entry contains management information.  The value of
            this object for a particular interface has the same value
            as the ifIndex object for the same interface."
    ::= { ibmtbFiltOrderInEntry 1 }

ibmtbFiltOrderInPriority OBJECT-TYPE
    SYNTAX  INTEGER
    ACCESS  read-only
    STATUS  mandatory
    DESCRIPTION
            "The priority of when a filter is applied to an incoming
            frame. A value of 1 signifies that it is applied first."
    ::= { ibmtbFiltOrderInEntry 2 }

ibmtbFiltOrderInName OBJECT-TYPE
    SYNTAX  DisplayString
    ACCESS  read-only
    STATUS  mandatory
    DESCRIPTION
            "The name of the filter applied to incoming frames
            that is associated with the priority, ibmtbFiltOrderInPriority."
    ::= { ibmtbFiltOrderInEntry 3 }


--
-- The Outgoing Filter Order Table
--

ibmtbFiltOrderOutTable OBJECT-TYPE
    SYNTAX  SEQUENCE OF TBFiltOrderOutEntry
    ACCESS  not-accessible
    STATUS  mandatory
    DESCRIPTION
            "Table of information describing which order
            the filters are applied for outgoing frames."
    ::= { ibmtbFiltOrderTable 2 }

ibmtbFiltOrderOutEntry OBJECT-TYPE
    SYNTAX  TBFiltOrderOutEntry
    ACCESS  not-accessible
    STATUS  mandatory
    DESCRIPTION
            "Filter order information for outgoing frames."
    INDEX   { ibmtbFiltOrderOutPriority }
    ::= { ibmtbFiltOrderOutTable 1 }

TBFiltOrderOutEntry ::=
    SEQUENCE {
        ibmtbFiltOrderOutIfIndex
            INTEGER,
        ibmtbFiltOrderOutPriority
            INTEGER,
        ibmtbFiltOrderOutName
            DisplayString
    }

ibmtbFiltOrderOutIfIndex OBJECT-TYPE
    SYNTAX  INTEGER
    ACCESS  read-only
    STATUS  mandatory
    DESCRIPTION
            "The value of this object identifies the interface for which
            this entry contains management information.  The value of
            this object for a particular interface has the same value
            as the ifIndex object for the same interface."
    ::= { ibmtbFiltOrderOutEntry 1 }

ibmtbFiltOrderOutPriority OBJECT-TYPE
    SYNTAX  INTEGER
    ACCESS  read-only
    STATUS  mandatory
    DESCRIPTION
            "The priority of when a filter is applied to an outgoing
            frame. A value of 1 signifies that it is applied first."
    ::= { ibmtbFiltOrderOutEntry 2 }

ibmtbFiltOrderOutName OBJECT-TYPE
    SYNTAX  DisplayString
    ACCESS  read-only
    STATUS  mandatory
    DESCRIPTION
            "The name of the filter applied to outgoing frames
            that is associated with the priority, ibmtbFiltOrderOutPriority."
    ::= { ibmtbFiltOrderOutEntry 3 }

-- static char sccsid_appleext_mib[] = "@(#) snmp/samples/appleext.my, SNMP, 6611R2  10/1/92 15:57:19";

----------------------------------------------------------------------
-- The IBM 6611 Appletalk Extension MIB
----------------------------------------------------------------------



--  AppleTalk Extension MIB

ibmSelectNet       OBJECT IDENTIFIER ::= { ibmapple 1 }
ibmnbpFilter       OBJECT IDENTIFIER ::= { ibmapple 2 }
ibmatportFilter    OBJECT IDENTIFIER ::= { ibmapple 3 }
ibmSelectNetFilter OBJECT IDENTIFIER ::= { ibmapple 4 }


--
-- The Selected Network Definition Group
--

ibmSelectNetTable OBJECT-TYPE
        SYNTAX SEQUENCE OF SelectNetEntry
        ACCESS not-accessible
        STATUS mandatory
        DESCRIPTION
            "The list of selected network definition entries."
        ::= { ibmSelectNet 1 }

ibmSelectNetEntry OBJECT-TYPE
        SYNTAX SelectNetEntry
        ACCESS not-accessible
        STATUS mandatory
        DESCRIPTION
            "The description of a selected network definition."
        INDEX { ibmSelectNetIndex }
        ::= { ibmSelectNetTable 1 }

SelectNetEntry ::= SEQUENCE {
        ibmSelectNetIndex             INTEGER,
        ibmSelectNetZone              OCTET STRING,
        ibmSelectNetNetStart          OCTET STRING,
        ibmSelectNetNetEnd            OCTET STRING,
        ibmSelectNetInterfaceNetStart OCTET STRING
}

ibmSelectNetIndex OBJECT-TYPE
        SYNTAX INTEGER
        ACCESS read-only
        STATUS mandatory
        DESCRIPTION
            "An identifier that is unique to the default zone name
            that is present in this entry."
        ::= { ibmSelectNetEntry 1 }

ibmSelectNetZone OBJECT-TYPE
        SYNTAX OCTET STRING
        ACCESS read-only
        STATUS mandatory
        DESCRIPTION
            "The ASCII default zone name of this entry."
        ::= { ibmSelectNetEntry 2 }

ibmSelectNetNetStart OBJECT-TYPE
        SYNTAX OCTET STRING (SIZE(2))
        ACCESS read-only
        STATUS mandatory
        DESCRIPTION
            "The network address that starts the range for this entry.
             This address is a two octet DDP network address in network
             byte order."
        ::= { ibmSelectNetEntry 3 }

ibmSelectNetNetEnd OBJECT-TYPE
        SYNTAX OCTET STRING (SIZE(2))
        ACCESS read-only
        STATUS mandatory
        DESCRIPTION
            "The network address that ends the range for this entry.
             This address is a two octet DDP network address in network
             byte order."
        ::= { ibmSelectNetEntry 4 }

ibmSelectNetInterfaceNetStart OBJECT-TYPE
        SYNTAX OCTET STRING (SIZE(2))
        ACCESS read-only
        STATUS mandatory
        DESCRIPTION
            "The network address that starts the range for the interface
             associated with this definition."
        ::= { ibmSelectNetEntry 5 }


--
-- The Name Binding Protocol Filter Group
--

ibmnbpFilterPacketsFiltered OBJECT-TYPE
        SYNTAX Counter
        ACCESS read-only
        STATUS mandatory
        DESCRIPTION
            "The number of packets filtered by nbp filters."
        ::= { ibmnbpFilter 1 }

ibmnbpFilterPacketsSent OBJECT-TYPE
        SYNTAX Counter
        ACCESS read-only
        STATUS mandatory
        DESCRIPTION
            "The number of packets not filtered by nbp filters."
        ::= { ibmnbpFilter 2 }



--
-- The Port Destination Network Filter Group
--

ibmatportFilterTable OBJECT-TYPE
        SYNTAX SEQUENCE OF AtportFilterEntry
        ACCESS not-accessible
        STATUS mandatory
        DESCRIPTION
            "The list of Appletalk port destination network filter entries."
        ::= { ibmatportFilter 1 }

ibmatportFilterEntry OBJECT-TYPE
        SYNTAX AtportFilterEntry
        ACCESS not-accessible
        STATUS mandatory
        DESCRIPTION
            "The description of a filter on this Appletalk port."
        INDEX { ibmatportFilterIndex, ibmatportFilterNetStart }
        ::= { ibmatportFilterTable 1 }

AtportFilterEntry ::= SEQUENCE {
        ibmatportFilterIndex             INTEGER,
        ibmatportFilterNetStart          OCTET STRING,
        ibmatportFilterNetEnd            OCTET STRING
}

ibmatportFilterIndex OBJECT-TYPE
        SYNTAX INTEGER
        ACCESS read-only
        STATUS mandatory
        DESCRIPTION
            "An identifier that is unique to the Appletalk
            port to which this filter applies. The port identified
            by this value is the same port as identified by
            atportIndex."
        ::= { ibmatportFilterEntry 1 }

ibmatportFilterNetStart OBJECT-TYPE
        SYNTAX OCTET STRING (SIZE(2))
        ACCESS read-only
        STATUS mandatory
        DESCRIPTION
            "The network address that starts the range for this
             destination network filter.
             This address is a two octet DDP network address in network
             byte order."
        ::= { ibmatportFilterEntry 2 }

ibmatportFilterNetEnd OBJECT-TYPE
        SYNTAX OCTET STRING (SIZE(2))
        ACCESS read-only
        STATUS mandatory
        DESCRIPTION
            "The network address that ends the range for this
             destination network filter.
             This address is a two octet DDP network address in network
             byte order."
        ::= { ibmatportFilterEntry 3 }



--
-- The Selected Network Destination Network Filter Group
--

ibmSelectNetFilterTable OBJECT-TYPE
        SYNTAX SEQUENCE OF SelectNetFilterEntry
        ACCESS not-accessible
        STATUS mandatory
        DESCRIPTION
            "The list of selected network destination network filter entries."
        ::= { ibmSelectNetFilter 1 }

ibmSelectNetFilterEntry OBJECT-TYPE
        SYNTAX SelectNetFilterEntry
        ACCESS not-accessible
        STATUS mandatory
        DESCRIPTION
            "The description of a filter for this selected network definition."
        INDEX { ibmSelectNetFilterIndex, ibmSelectNetFilterNetStart }
        ::= { ibmSelectNetFilterTable 1 }

SelectNetFilterEntry ::= SEQUENCE {
        ibmSelectNetFilterIndex             INTEGER,
        ibmSelectNetFilterNetStart          OCTET STRING,
        ibmSelectNetFilterNetEnd            OCTET STRING
}

ibmSelectNetFilterIndex OBJECT-TYPE
        SYNTAX INTEGER
        ACCESS read-only
        STATUS mandatory
        DESCRIPTION
            "An identifier that is unique to the selected network
            definition to which this filter applies. This value
            is the same as that provided by ibmSelectNetIndex."
        ::= { ibmSelectNetFilterEntry 1 }

ibmSelectNetFilterNetStart OBJECT-TYPE
        SYNTAX OCTET STRING (SIZE(2))
        ACCESS read-only
        STATUS mandatory
        DESCRIPTION
            "The network address that starts the range for this
             destination network filter.
             This address is a two octet DDP network address in network
             byte order."
        ::= { ibmSelectNetFilterEntry 2 }

ibmSelectNetFilterNetEnd OBJECT-TYPE
        SYNTAX OCTET STRING (SIZE(2))
        ACCESS read-only
        STATUS mandatory
        DESCRIPTION
            "The network address that ends the range for this
             destination network filter.
             This address is a two octet DDP network address in network
             byte order."
        ::= { ibmSelectNetFilterEntry 3 }


-- static char sccsid_decext_mib[] = "%Z %W %Q %G %U";

----------------------------------------------------------------------
-- The IBM 6611 DECnet Extension MIB
----------------------------------------------------------------------



--  DECnet Extension MIB

--
-- Box level parameters.
--

ibmdecAllRoutersFuncAddr OBJECT-TYPE
        SYNTAX OCTET STRING (SIZE(6))
        ACCESS read-only
        STATUS mandatory
        DESCRIPTION
            "The functional address used in communicating with
             with all DECnet Phase IV and DECnet Phase IV-Prime
             routers on a token ring LAN."
        ::= { ibmdec 1 }

ibmdecAllEndNodesFuncAddr OBJECT-TYPE
        SYNTAX OCTET STRING (SIZE(6))
        ACCESS read-only
        STATUS mandatory
        DESCRIPTION
            "The functional address used in communicating with
             with all DECnet Phase IV and DECnet Phase IV-Prime
             end nodes on a token ring LAN."
        ::= { ibmdec 2 }

ibmdecSplitHorPoisonRev OBJECT-TYPE
        SYNTAX INTEGER {
                   enabled(1),
                   disabled(2)
               }
        ACCESS read-only
        STATUS mandatory
        DESCRIPTION
            "Defines whether the Split Horizon with Poison
             Reverse option is enabled or not"
        ::= { ibmdec 3 }

ibmdecNodeType OBJECT-TYPE
        SYNTAX INTEGER {
            routing-III (1),
            nonrouting-III (2),
            area (3),
            routing-IV (4),
            nonrouting-IV (5),
            area-IV-Prime (6),
            routing-IV-Prime (7),
            nonrouting-IV-Prime (8)
        }
        ACCESS read-only
        STATUS mandatory
        DESCRIPTION
           "This parameter indicates the node type of the
           router. This object is the same as the phivRouteType
           object defined by RFC 1289, however, this definition
           extends the enumerations to provide new values."
        ::= { ibmdec 4 }

--
-- Circuit parameters pertaining to LAN interfaces.
--

ibmdecLANCircuitTable OBJECT-TYPE
        SYNTAX SEQUENCE OF IbmdecLANCircuitEntry
        ACCESS not-accessible
        STATUS mandatory
        DESCRIPTION
            "The list of information relevant to LAN circuits.
             This table extends the information provided by the
             phivCircuitParametersTable defined by RFC 1289."
        ::= { ibmdec 5 }

ibmdecLANCircuitEntry OBJECT-TYPE
        SYNTAX IbmdecLANCircuitEntry
        ACCESS not-accessible
        STATUS mandatory
        DESCRIPTION
            "Table entry with information relevant to LAN circuits."
        INDEX { ibmdecLANCircuitIndex }
        ::= { ibmdecLANCircuitTable 1 }

IbmdecLANCircuitEntry ::= SEQUENCE {
        ibmdecLANCircuitIndex       INTEGER,
        ibmdecLANCircuitType        INTEGER,
        ibmdecLANCircuitSourceRoute INTEGER,
        ibmdecLANCircuitAddrType    INTEGER
}

ibmdecLANCircuitIndex OBJECT-TYPE
        SYNTAX INTEGER
        ACCESS read-only
        STATUS mandatory
        DESCRIPTION
            "A unique index value for each known circuit
             on a LAN interface. The value of this variable
             is the same as that provided by phivCircuitIndex."
        ::= { ibmdecLANCircuitEntry 1 }

ibmdecLANCircuitType OBJECT-TYPE
        SYNTAX INTEGER {
            bilingual (1),
            ama (2),
            phaseIV (3)
        }
        ACCESS read-only
        STATUS mandatory
        DESCRIPTION
            "If the CircuitType is Bilingual for a circuit, the router
             would use a Phase_IV compliant locally administered MAC address
             for that circuit and would be configured to communicate
             with Phase_IV and Phase_IV-Prime nodes over that circuit.
             A bilingual router can help communication between the
             Phase_IV and the Phase_IV-Prime nodes over the same
             extended LAN segment, and prevents a partitioned network.

             If the CircuitType is AMA ( Arbitrary MAC Address ) for a
             circuit, the router would use an arbitrary MAC address
             for that circuit, and would be configured to communicate
             with Phase_IV-Prime nodes over that circuit.

             If the CircuitType is PhaseIV for a circuit, the router
             would use the Phase_IV compliant locally administered MAC
             address for that circuit, and would be configured to
             communicate with Phase_IV nodes over that circuit."

        ::= { ibmdecLANCircuitEntry 2 }

ibmdecLANCircuitSourceRoute OBJECT-TYPE
        SYNTAX INTEGER {
            enabled (1),
            disabled (2),
            notapplicable (3)
        }
        ACCESS read-only
        STATUS mandatory
        DESCRIPTION
            "This parameter indicates if source routing is enabled
             on a token-ring circuit.

            A value of 3 is returned for circuits which are not
            of the 802.5/token-ring type."

        ::= { ibmdecLANCircuitEntry 3 }

ibmdecLANCircuitAddrType OBJECT-TYPE
        SYNTAX INTEGER {
            decnet (1),
            hardware (2),
            user (3)
        }
        ACCESS read-only
        STATUS mandatory
        DESCRIPTION
            "This parameter indicates the type of MAC address
             used on this circuit.

             The value returned is decnet(1), if a DECnet
             Phase_IV compliant locally administered MAC address
             is being used.

             The value returned is hardware(2), if the unique
             assigned ROM address is used.

             The value returned is user(3), if a non
             DECnet Phase_IV compliant locally administered
             MAC address is being used."

        ::= { ibmdecLANCircuitEntry 4 }




-- static char sccsid_ipext_mib[] = "@(#) snmp/samples/ipext.my, SNMP, v1r3, r3d48  3/14/94 17:36:05";


ibmipext    OBJECT IDENTIFIER ::= {ibminterfaces 1 }
ibmptyqueue OBJECT IDENTIFIER ::= {ibminterfaces 2 }
ibmTG       OBJECT IDENTIFIER ::= {ibminterfaces 3 }

--------------------------------------------------------------------
--
-- The IBM 6611 Interface Extension MIB
--
--  * Serial Interface Queue Priority MIB
--
--    This function defines the various characteristics
--    of the serial interface transmission queues.
--
--  * IP Priority MIB
--
--    This function allows the assignment of TCP/IP and UDP/IP
--    traffic to specific serial interface transmission queues.
--    This, therefore, allows the user to provide a certain
--    level of prioritization based on traffic type.
--
--  * IP Filter MIB
--
--    Filter definitions for IP traffic, both address/mask and
--    port number filters.
--
--  * 2 T1 in a Transmission Group (TG) MIB
--
--    This function provides an alternative route while balancing
--    the load among serial point-to-point links.
--
------------------------------------------------------------------

------------------------------------------------------------------
-- IP Priority MIB - Priority Queue Enable Table
----------------------------------------------------------------

ibmipPtyQueueEnableTable OBJECT-TYPE
    SYNTAX  SEQUENCE OF IbmipPtyQueueEnableEntry
    ACCESS  not-accessible
    STATUS  mandatory
    DESCRIPTION
            "This table defines which interfaces are
             enabled for IP prioritization.

             It also defines the default serial
             transmission priority queue to be used
             for IP packets which are not assigned to use
             a specific transmission queue."
    ::= { ibmipext 1 }

ibmipPtyQueueEnableEntry OBJECT-TYPE
    SYNTAX  IbmipPtyQueueEnableEntry
    ACCESS  not-accessible
    STATUS  mandatory
    DESCRIPTION
            "Each entry defines whether IP prioritization is
             enabled on a particular interface and the default
             transmission queue."
   INDEX   { ibmipPtyQueueEnableIfIndex }
    ::= { ibmipPtyQueueEnableTable 1 }

IbmipPtyQueueEnableEntry ::=
    SEQUENCE {
        ibmipPtyQueueEnableIfIndex
            INTEGER,
        ibmipPtyQueueEnable
            INTEGER,
        ibmipPtyQueueDefault
            INTEGER
    }

ibmipPtyQueueEnableIfIndex OBJECT-TYPE
    SYNTAX  INTEGER  (0..65535)
    ACCESS  read-only
    STATUS  mandatory
    DESCRIPTION
            "Defines the interface associated with IP
             prioritization. This interface is the same
             interface as defined by the ifIndex variable
             of the MIB-II interfaces group."
    ::= { ibmipPtyQueueEnableEntry 1 }

ibmipPtyQueueEnable OBJECT-TYPE
    SYNTAX  INTEGER {
              enable(1),
              disable(2)
            }
    ACCESS  read-only
    STATUS  mandatory
    DESCRIPTION
            "The value of this object identifies if IP prioritization
             is enabled on this interface."
    ::= { ibmipPtyQueueEnableEntry 2 }

ibmipPtyQueueDefault OBJECT-TYPE
    SYNTAX  INTEGER {
               high(1),
               medium(2),
               low(3)
            }
    ACCESS  read-only
    STATUS  mandatory
    DESCRIPTION
            "Identifies the transmission queue to be used
             for IP packets which are not assigned to use
             a specific transmission queue."
    ::= { ibmipPtyQueueEnableEntry 3 }

------------------------------------------------------------------
-- IP Priority MIB  - Priority Queue Definition Table
------------------------------------------------------------------

ibmipPtyQueueTable OBJECT-TYPE
    SYNTAX  SEQUENCE OF IbmipPtyQueueEntry
    ACCESS  not-accessible
    STATUS  mandatory
    DESCRIPTION
            "This table contains the assignments of UDP/TCP
             port numbers to specific transmission queues
             for a given serial interface."
    ::= { ibmipext 2 }

ibmipPtyQueueEntry OBJECT-TYPE
    SYNTAX  IbmipPtyQueueEntry
    ACCESS  not-accessible
    STATUS  mandatory
    DESCRIPTION
            "Each entry defines the UDP/TCP port number and
             its associated transmission priority queue for
             a given interface."
   INDEX   { ibmipPtyQueueIfIndex, ibmipPtyQueuePort, ibmipPtyQueueType }
    ::= { ibmipPtyQueueTable 1 }

IbmipPtyQueueEntry ::=
    SEQUENCE {
        ibmipPtyQueueIfIndex
            INTEGER,
        ibmipPtyQueuePort
            INTEGER,
        ibmipPtyQueueType
            INTEGER,
        ibmipPtyQueueNumber
            INTEGER
    }

ibmipPtyQueueIfIndex OBJECT-TYPE
    SYNTAX  INTEGER  (0..65535)
    ACCESS  read-only
    STATUS  mandatory
    DESCRIPTION
            "Defines the interface on which a UDP/TCP port
             is associated with a specific transmission
             priority queue. This interface is the same
             interface as defined by the ifIndex variable
             of the MIB-II interfaces group."
    ::= { ibmipPtyQueueEntry 1 }

ibmipPtyQueuePort OBJECT-TYPE
    SYNTAX  INTEGER  (0..65535)
    ACCESS  read-only
    STATUS  mandatory
    DESCRIPTION
            "Identifies a UDP or TCP port number."
    ::= { ibmipPtyQueueEntry 2 }

ibmipPtyQueueType OBJECT-TYPE
    SYNTAX  INTEGER {
               tcp(1),
               udp(2)
            }
    ACCESS  read-only
    STATUS  mandatory
    DESCRIPTION
            "Indicates the port type of the port number
             defined by ibmipPtyQueuePort."
    ::= { ibmipPtyQueueEntry 3 }

ibmipPtyQueueNumber OBJECT-TYPE
    SYNTAX  INTEGER {
               high(1),
               medium(2),
               low(3)
            }
    ACCESS  read-only
    STATUS  mandatory
    DESCRIPTION
            "Indicates which transmission queue will be used to
             transmit a packet which has a port number as specified
             by ibmipPtyQueuePort."
    ::= { ibmipPtyQueueEntry 4 }

------------------------------------------------------
-- IP Address/Mask Filter
------------------------------------------------------

ibmipFilterTable OBJECT-TYPE
    SYNTAX  SEQUENCE OF IbmipFilterEntry
    ACCESS  not-accessible
    STATUS  mandatory
    DESCRIPTION
            "Table of IP address/mask filter definitions."
    ::= { ibmipext 3 }

ibmipFilterEntry OBJECT-TYPE
    SYNTAX  IbmipFilterEntry
    ACCESS  not-accessible
    STATUS  mandatory
    DESCRIPTION
            "An entry in the IP address/mask filter table."
    INDEX   { ibmipFilterIfIndex, ibmipFilterId }
    ::= { ibmipFilterTable 1 }

IbmipFilterEntry ::=
    SEQUENCE {
        ibmipFilterIfIndex
            INTEGER,
        ibmipFilterId
            INTEGER,
        ibmipFilterScope
            INTEGER,
        ibmipFilterType
            INTEGER,
        ibmipPermitDeny
            INTEGER,
        ibmipFilterAddr1
            IpAddress,
        ibmipFilterMask1
            IpAddress,
        ibmipFilterAddr2
            IpAddress,
        ibmipFilterMask2
            IpAddress
    }

ibmipFilterIfIndex OBJECT-TYPE
    SYNTAX  INTEGER (0..65535)
    ACCESS  read-only
    STATUS  mandatory
    DESCRIPTION
            "Defines the interface associated with this
             address/mask filter definition. This interface is
             the same interface as defined by the ifIndex
             variable of the MIB-II interfaces group."
    ::= { ibmipFilterEntry 1 }

ibmipFilterId OBJECT-TYPE
    SYNTAX  INTEGER (1..50)
    ACCESS  read-only
    STATUS  mandatory
    DESCRIPTION
            "An id that defines this filter entry.
             This number is unique within this interface."
    ::= { ibmipFilterEntry 2 }

ibmipFilterScope OBJECT-TYPE
    SYNTAX  INTEGER {
               system(1),
               interface(2)
            }
    ACCESS  read-only
    STATUS  mandatory
    DESCRIPTION
            "Defines whether this filter is applied to
             all interfaces or just this one."
     ::= { ibmipFilterEntry 3 }

ibmipFilterType OBJECT-TYPE
    SYNTAX  INTEGER {
              singular(1),
              dual(2)
            }
    ACCESS  read-only
    STATUS  mandatory
    DESCRIPTION
            "Defines the type of filtering."
       ::= { ibmipFilterEntry 4 }

ibmipPermitDeny OBJECT-TYPE
    SYNTAX  INTEGER {
              permit(1),
              deny(2)
            }
    ACCESS  read-only
    STATUS  mandatory
    DESCRIPTION
            "Identifies whether traffic for a specified filter ID
             is to be permitted to pass through the IBM 6611 or
             whether it is to be discarded."
    ::= { ibmipFilterEntry 5 }

ibmipFilterAddr1 OBJECT-TYPE
    SYNTAX  IpAddress
    ACCESS  read-only
    STATUS  mandatory
    DESCRIPTION
            "A valid IP address of the host, subnet or network
             for this filter. For singular filters, this is the only
             end point, however, for dual filters this is the source
             end point."
    ::= { ibmipFilterEntry 6 }

ibmipFilterMask1 OBJECT-TYPE
    SYNTAX  IpAddress
    ACCESS  read-only
    STATUS  mandatory
    DESCRIPTION
            "A valid IP address mask used for this filter.
             In conjunction with the IP address defined by
             ibmipFilterAddr1, it defines the range of IP
             addresses to be filtered."
    ::= { ibmipFilterEntry 7 }

ibmipFilterAddr2 OBJECT-TYPE
    SYNTAX  IpAddress
    ACCESS  read-only
    STATUS  mandatory
    DESCRIPTION
            "Defines the destination IP address if ibmipFilterType is
            dual. This value is undefined for singular filters."
    ::= { ibmipFilterEntry 8 }

ibmipFilterMask2 OBJECT-TYPE
    SYNTAX  IpAddress
    ACCESS  read-only
    STATUS  mandatory
    DESCRIPTION
            "A valid IP address mask used for this filter.
             In conjunction with the IP address defined by
             ibmipFilterAddr2, it defines the range of IP
             addresses to be filtered."
    ::= { ibmipFilterEntry 9 }

------------------------------------------------------
-- IP Port Number Filter
------------------------------------------------------

ibmipFilterExtTable OBJECT-TYPE
    SYNTAX  SEQUENCE OF IbmipFilterExtEntry
    ACCESS  not-accessible
    STATUS  mandatory
    DESCRIPTION
            "Table of IP port number filter definitions."
    ::= { ibmipext 4 }

ibmipFilterExtEntry OBJECT-TYPE
    SYNTAX  IbmipFilterExtEntry
    ACCESS  not-accessible
    STATUS  mandatory
    DESCRIPTION
            "An entry in the IP port number filter table."
    INDEX   { ibmipFilterExtIfIndex, ibmipFilterExtFilterId,
              ibmipFilterExtValue, ibmipFilterExtProtocol }
    ::= { ibmipFilterExtTable 1 }

IbmipFilterExtEntry ::=
    SEQUENCE {
        ibmipFilterExtIfIndex
            INTEGER,
        ibmipFilterExtFilterId
            INTEGER,
        ibmipFilterExtValue
            INTEGER,
        ibmipFilterExtProtocol
            INTEGER
    }

ibmipFilterExtIfIndex OBJECT-TYPE
    SYNTAX  INTEGER  (0..65535)
    ACCESS  read-only
    STATUS  mandatory
    DESCRIPTION
            "Defines the interface associated with this
             IP port number filter definition. This interface is
             the same interface as defined by the ifIndex
             variable of the MIB-II interfaces group."
    ::= { ibmipFilterExtEntry 1 }

ibmipFilterExtFilterId OBJECT-TYPE
    SYNTAX  INTEGER  (1..50)
    ACCESS  read-only
    STATUS  mandatory
    DESCRIPTION
            "An id that defines this filter entry.
             This number is unique within this interface
             and is the same filter ID as defined by
             ibmipFilterId."
    ::= { ibmipFilterExtEntry 2 }

ibmipFilterExtValue OBJECT-TYPE
    SYNTAX  INTEGER (0..65535)
    ACCESS  read-only
    STATUS  mandatory
    DESCRIPTION
            "Defines a TCP or UDP port number that will be filtered
            using this filter specification."
    ::= { ibmipFilterExtEntry 3 }

ibmipFilterExtProtocol OBJECT-TYPE
    SYNTAX  INTEGER {
                none(1),
                tcpudp(2)
            }
    ACCESS  read-only
    STATUS  mandatory
    DESCRIPTION
            "Specifies the protocol associated with the value
             defined by ibmipFilterExtValue for this filter
             specification."
    ::= { ibmipFilterExtEntry 4 }

------------------------------------------------------------------
--  Serial Interface Queue Priority MIB
------------------------------------------------------------------

ibmPtyQueueingTable OBJECT-TYPE
    SYNTAX  SEQUENCE OF IbmPtyQueueingEntry
    ACCESS  not-accessible
    STATUS  mandatory
    DESCRIPTION
        "This table provides information on a specific
         transmission queue of a serial interface.

         Information includes:

           - Link Bandwidth Allocation (LBA):
              Identifies the number of packets transmitted
              from a particular queue before a lower priority
              transmission queue will be serviced.

           - Queue Bandwidth Reservation (QBR):
              Identifies the percentage of buffer space on
              a serial adapter that is allotted to a
              particular queue for transmission of packets."
   ::= { ibmptyqueue 1 }

ibmPtyQueueingEntry OBJECT-TYPE
    SYNTAX  IbmPtyQueueingEntry
    ACCESS  not-accessible
    STATUS  mandatory
    DESCRIPTION
        "Each entry defines the Link Bandwidth Allocation (LBA)
         and Queue Bandwidth Reservation (QBR) definitions for
         a specific transmission queue on a serial interface.
         Additionally, a counter is provided indicating
         the number of packets discarded on this queue due to
         a queue overflow."
   INDEX   { ibmPtyQueueingIfIndex, ibmPtyQueueingQnum }
    ::= { ibmPtyQueueingTable 1 }

IbmPtyQueueingEntry ::=
    SEQUENCE {
        ibmPtyQueueingIfIndex
            INTEGER,
        ibmPtyQueueingQnum
            INTEGER,
        ibmPtyQueueingLBA
            INTEGER,
        ibmPtyQueueingQBR
            INTEGER,
        ibmPtyQueueingDiscards
            Counter
    }

ibmPtyQueueingIfIndex OBJECT-TYPE
    SYNTAX  INTEGER  (0..65535)
    ACCESS  read-only
    STATUS  mandatory
    DESCRIPTION
            "Defines the interface associated with this
             priority queue information. This interface is
             the same interface as defined by the ifIndex
             variable of the MIB-II interfaces group."
    ::= { ibmPtyQueueingEntry 1 }

ibmPtyQueueingQnum OBJECT-TYPE
    SYNTAX  INTEGER {
               high(1),
               medium(2),
               low(3)
            }
    ACCESS  read-only
    STATUS  mandatory
    DESCRIPTION
            "Identifies the priority queue associated
             with this interface and its priority queue
             information."
    ::= { ibmPtyQueueingEntry 2 }

ibmPtyQueueingLBA OBJECT-TYPE
    SYNTAX  INTEGER  (1..10)
    ACCESS  read-only
    STATUS  mandatory
    DESCRIPTION
            "Link Bandwidth Allocation (LBA):

            Identifies the number of packets that will be transmitted
            from this queue before a lower priority queue will be
            serviced."
    ::= { ibmPtyQueueingEntry 3 }

ibmPtyQueueingQBR OBJECT-TYPE
    SYNTAX  INTEGER
    ACCESS  read-only
    STATUS  mandatory
    DESCRIPTION
            "Queue Bandwidth Reservation (QBR):

             Identifies the percentage of buffer space on
             a serial adapter that is allotted to a
             particular queue for transmission of packets.
             The sum of all QBR values on an interface
             must add up to 100%."
    ::= { ibmPtyQueueingEntry 4 }

ibmPtyQueueingDiscards OBJECT-TYPE
    SYNTAX  Counter
    ACCESS  read-only
    STATUS  mandatory
    DESCRIPTION
            "Identifies the number of packets discarded
            from this queue due to a queue overflow."
    ::= { ibmPtyQueueingEntry 5 }


---------------------------------------------------------------
-- Serial point-to-point "2 T1 in a TG" table.
---------------------------------------------------------------

ibmTGTable OBJECT-TYPE
    SYNTAX  SEQUENCE OF IbmTGEntry
    ACCESS  not-accessible
    STATUS  mandatory
    DESCRIPTION
            "This table provides information about serial
             point-to-point links which are participating
             in the 2 T1 in a transmission group (TG)
             function."
    ::= { ibmTG 1 }

ibmTGEntry OBJECT-TYPE
    SYNTAX  IbmTGEntry
    ACCESS  not-accessible
    STATUS  mandatory
    DESCRIPTION
            "Each entry identifies an interface participating
             in the 2 T1 in a TG function, along with its
             associated TG name and which protocol is
             using the function."
    INDEX   { ibmTGProtocol, ibmTGIfIndex }
    ::= { ibmTGTable 1 }

IbmTGEntry ::=
    SEQUENCE {
        ibmTGProtocol
            INTEGER,
        ibmTGIfIndex
            INTEGER,
        ibmTGEnable
            INTEGER,
        ibmTGGroupName
            DisplayString,
        ibmTGSwitchOuts
            Counter
    }

ibmTGProtocol OBJECT-TYPE
    SYNTAX  INTEGER  {
               ip(2048)
            }
    ACCESS  read-only
    STATUS  mandatory
    DESCRIPTION
            "Defines the protocol that is supported for
             this particular interface and TG name.

             Currently, only the IP protocol is supported"
    ::= { ibmTGEntry 1 }

ibmTGIfIndex OBJECT-TYPE
    SYNTAX  INTEGER  (0..65535)
    ACCESS  read-only
    STATUS  mandatory
    DESCRIPTION
            "Defines the interface associated with this
             particular TG name and protocol. This interface
             is the same interface as defined by the ifIndex
             variable of the MIB-II interfaces group."
    ::= { ibmTGEntry  2 }

ibmTGEnable OBJECT-TYPE
    SYNTAX  INTEGER  {
               enable(1),
               disable(2)
            }
    ACCESS  read-only
    STATUS  mandatory
    DESCRIPTION
            "Defines whether the 2 T1 in a TG function
             is enabled on this interface"
    ::= { ibmTGEntry 3 }

ibmTGGroupName OBJECT-TYPE
    SYNTAX  DisplayString (SIZE (1..8))
    ACCESS  read-only
    STATUS  mandatory
    DESCRIPTION
            "Defines the common TG name assigned to all interfaces in this group.
             All interfaces with the same TG name will belong to the same group."
    ::= { ibmTGEntry 4 }

ibmTGSwitchOuts OBJECT-TYPE
    SYNTAX  Counter
    ACCESS  read-only
    STATUS  mandatory
    DESCRIPTION
            "Counts the number of times a packet had to be switched
             to another interface in the transmission group."
    ::= { ibmTGEntry 5 }
-- static char sccsid_vn_mib[] = "%Z %W %I %Q %G %U";

------------------------------------------------------------------------
-- The IBM 6611 VINES Router MIB--
------------------------------------------------------------------------



------------------------------------------------------------------------
------------------------------------------------------------------------
-- MIB Structure --
--
-- (ibmvSysConfig) VINES System Configuration
-- (ibmvIP) VINES Internet Protocol
-- -  Normal IP packets
-- -  Error IP packets
-- (ibmvNeighbor) VINES Neighbor Information
-- -  Address Resolution Protocol (ARP)
-- -  Number of entries in Neighbor Table
-- -  Neighbor Table
-- (ibmvRouting) VINES Routing Information
-- -  Routing configuration
-- -  -  Inbound RTP Filters
-- -  -  Outbound RTP Filters
-- -  -  RTP Router Filters
-- -  Routing Update Protocol (RTP)
-- -  Number of entries in Routing Table
-- -  Routing Table
-- (ibmvICP) VINES Internet Control Protocol
-- (ibmvFRP) VINES Fragmentation Protocol
-- (ibmvInterface) VINES Interface Information
-- -  Port Configuration
-- -  -  Inbound & Outbound Port Filters
-- -  Interface Table
------------------------------------------------------------------------
------------------------------------------------------------------------
-- A note on the thinking behind the organization of the MIB.  The
-- guideline followed is that all objects within a group must be implemented to
-- implement the group. From this viewpoint, objects were logically grouped.
-- But as the MIB developed, one noticed subgroups which had a tighter
-- relationship than the group.  It seems appropriate that all objects in a
-- subgroup must be implemented to implement the subgroup.  It also seems
-- possible to implement a group by implement one or more of the subgroups;
-- not necessarily all the subgroups of a group.  Subgroups were organized
-- so they could be pulled out of a group without disrupting the relationship
-- of the group.  When working with subgroups, there is usually one subgroup
-- which is mandatory to the group and the rest are optional.
------------------------------------------------------------------------

ibmvSysConfig  OBJECT IDENTIFIER ::= {ibmvines 1}
ibmvIP         OBJECT IDENTIFIER ::= {ibmvines 2}
ibmvNeighbor   OBJECT IDENTIFIER ::= {ibmvines 3}
ibmvRouting    OBJECT IDENTIFIER ::= {ibmvines 4}
ibmvICP        OBJECT IDENTIFIER ::= {ibmvines 5}
ibmvFRP        OBJECT IDENTIFIER ::= {ibmvines 6}
ibmvInterface  OBJECT IDENTIFIER ::= {ibmvines 7}

------------------------------------------------------------------------
------------------------------------------------------------------------
--
-- Group: The VINES System Configuration
--
-- Description: VINES system configuration are those configuration
--              objects which pertain to the system (local box) and
--              do not logically fit under another group.
--
------------------------------------------------------------------------
------------------------------------------------------------------------
ibmvSysRtr OBJECT-TYPE
    SYNTAX  INTEGER {enable (1),
                     disable (2)}
    ACCESS  read-only
    STATUS  mandatory
    DESCRIPTION
            "Indicates whether this node is acting as a VINES router."
    ::= { ibmvSysConfig 1 }

ibmvRouterName OBJECT-TYPE
   SYNTAX  DisplayString
   ACCESS  read-only
   STATUS  mandatory
   DESCRIPTION
           "The name of the router node, up to 15 characters long."
   ::= { ibmvSysConfig 2 }

ibmvRouterNetid OBJECT-TYPE
   SYNTAX  INTEGER
   ACCESS  read-only
   STATUS  mandatory
   DESCRIPTION
           "The VINES network ID of the router node equal to the router
           node's serial number.  This id may be up to 4 bytes in length."
   ::= { ibmvSysConfig 3 }


------------------------------------------------------------------------
------------------------------------------------------------------------
--
-- Group: VINES Internet Protocol - VIP
--
-- Description: Objects which gather VINES IP packets statistics. The
--              following are objects which count normal and error IP
--              packets.
--
-- Note: All counters were started when the node was last booted.
------------------------------------------------------------------------
------------------------------------------------------------------------

------------------------------------------------------------------------
-- VINES Internet Protocol Statistics - Normal Packets
------------------------------------------------------------------------
ibmvipTotalIn OBJECT-TYPE
    SYNTAX  Counter
    ACCESS  read-only
    STATUS  mandatory
    DESCRIPTION
            "The total number of VINES IP packets that the router node has
            received since the last reboot."
    ::= { ibmvIP 1 }

ibmvipTotalOut OBJECT-TYPE
    SYNTAX  Counter
    ACCESS  read-only
    STATUS  mandatory
    DESCRIPTION
            "The total number of VINES IP packets that the router node has
            sent since the last reboot."
    ::= { ibmvIP 2 }

ibmvipRouted OBJECT-TYPE
    SYNTAX  Counter
    ACCESS  read-only
    STATUS  mandatory
    DESCRIPTION
            "The total number of packets that were routed to another
             node since the last reboot."
    ::= { ibmvIP 3 }

ibmvipBcast OBJECT-TYPE
    SYNTAX  Counter
    ACCESS  read-only
    STATUS  mandatory
    DESCRIPTION
            "The number of VINES IP broadcast packets sent, both generated
            from the router node and routed from other nodes, since the last
            reboot."
    ::= { ibmvIP 4 }


ibmvipInReceives OBJECT-TYPE
    SYNTAX  Counter
    ACCESS  read-only
    STATUS  mandatory
    DESCRIPTION
            "The number of unicast VINES IP packets received since the last
            reboot.  A unicast packet is destined for this particular
            router node.  It is not being forwarded, multicasted or
            broadcasted."
    ::= { ibmvIP 5 }

ibmvipBcastInReceives OBJECT-TYPE
    SYNTAX  Counter
    ACCESS  read-only
    STATUS  mandatory
    DESCRIPTION
            "The number of VINES IP broadcast packets received since the
            last reboot."
    ::= { ibmvIP 6 }


------------------------------------------------------------------------
-- VINES Internet Protocol Statistics - Errors
------------------------------------------------------------------------
ibmvipBad OBJECT-TYPE
        SYNTAX  Counter
        ACCESS  read-only
        STATUS  mandatory
        DESCRIPTION
                "The total number of badly formed packets that the router
                node has received since the last booted."
        ::= { ibmvIP 7 }

ibmvipBadHeaders OBJECT-TYPE
    SYNTAX  Counter
    ACCESS  read-only
    STATUS  mandatory
    DESCRIPTION
            "The number of incoming VINES IP packets received since the last
            reboot which contained a header error; excluding the following
            errors: length, checksum and time to live."
    ::= { ibmvIP 8 }

ibmvipTooSmalls OBJECT-TYPE
    SYNTAX  Counter
    ACCESS  read-only
    STATUS  mandatory
    DESCRIPTION
            "The number of VINES IP packets received since the last reboot
            with len < the size of a VINES IP header."
    ::= { ibmvIP 9 }

ibmvipBadLens OBJECT-TYPE
    SYNTAX  Counter
    ACCESS  read-only
    STATUS  mandatory
    DESCRIPTION
            "The number of VINES IP packets received since the last reboot
            whose packet size is not equal to the number of bytes specified
            in the VINES IP header field."
    ::= { ibmvIP 10}

ibmvipBadSums OBJECT-TYPE
    SYNTAX  Counter
    ACCESS  read-only
    STATUS  mandatory
    DESCRIPTION
            "The number of VINES IP packets received since the last reboot
            with a bad checksum."
    ::= { ibmvIP 11}

ibmvipInDiscards OBJECT-TYPE
    SYNTAX  Counter
    ACCESS  read-only
    STATUS  mandatory
    DESCRIPTION
            "The number of incoming VINES IP packets discarded since the last
            reboot due to lack of resources."
    ::= { ibmvIP 12}

ibmvipZeroHops OBJECT-TYPE
    SYNTAX  Counter
    ACCESS  read-only
    STATUS  mandatory
    DESCRIPTION
            "The number of VINES IP packets discarded since the last reboot
            because the hop count equals zero and the current node is not
            the destination."
    ::= { ibmvIP 13}

ibmvipOutNoRoutes OBJECT-TYPE
    SYNTAX  Counter
    ACCESS  read-only
    STATUS  mandatory
    DESCRIPTION
            "The number of outgoing VINES IP packets discarded since the
            last reboot because no route is available."
    ::= { ibmvIP 14}


------------------------------------------------------------------------
------------------------------------------------------------------------
-- Group: VINES Neighbor Information
--
-- Description: All information related to the neighbor table.  This
--              includes related, ARP statistics (since ARP information
--              helps create the neighbor table) and the neighbor table
--              itself.
--
------------------------------------------------------------------------
------------------------------------------------------------------------

------------------------------------------------------------------------
-- Subgroup: VINES Address Resolution Protocol
--
-- Description: Statistical information regarding the VINES address
--              resolution protocol.
------------------------------------------------------------------------
ibmvARP  OBJECT IDENTIFIER ::= {ibmvNeighbor 1}

ibmvarpQueryReqs OBJECT-TYPE
    SYNTAX  Counter
    ACCESS  read-only
    STATUS  mandatory
    DESCRIPTION
            "The number of query requests received from clients since the
            last reboot.  When a client is first booted up, it sends out a
            broadcast query request packet on its LAN segment."
    ::= { ibmvARP 1 }

ibmvarpServiceResps OBJECT-TYPE
    SYNTAX  Counter
    ACCESS  read-only
    STATUS  mandatory
    DESCRIPTION
            "The number of ARP query responses sent out from this router node
            since the last reboot.  Each router node on the same LAN
            segment that is providing address assignments will respond."
    ::= { ibmvARP 2}

ibmvarpAssignReqs OBJECT-TYPE
    SYNTAX  Counter
    ACCESS  read-only
    STATUS  mandatory
    DESCRIPTION
            "The number of ARP assignment request received from clients
            since the last reboot. The client issues an assignment request
            packet to the router node that responded first to the query
            request."
    ::= { ibmvARP 3 }

ibmvarpAssignResps OBJECT-TYPE
    SYNTAX  Counter
    ACCESS  read-only
    STATUS  mandatory
    DESCRIPTION
            "The number of ARP assignment responses sent to clients since
            the last reboot.  The router node issues a VINES internet
            address for the client and sends it back in an assignment
            response packet."
    ::= { ibmvARP 4 }

ibmvarpHeaderError OBJECT-TYPE
    SYNTAX  Counter
    ACCESS  read-only
    STATUS  mandatory
    DESCRIPTION
            "The number of ARP packets received since the last reboot
            with a header error."
    ::= { ibmvARP 5 }

------------------------------------------------------------------------
-- Subgroup: VINES Neighbor Count
--
-- Description: Number of Neighbor entries in the Neighbor table.
------------------------------------------------------------------------
ibmvNbrNumber  OBJECT-TYPE
    SYNTAX  INTEGER
    ACCESS  read-only
    STATUS  mandatory
    DESCRIPTION
            "The number of entries in the neighbor table."
    ::= { ibmvNeighbor 2 }

------------------------------------------------------------------------
--                            T A B L E
--                            ---------
--
-- Subgroup: VINES Neighbor Table
--
-- Description: The MIB neighbor table contains objects which define
--              the variables found in the actual VINES neighbor table.
--
------------------------------------------------------------------------
ibmvNbrTable OBJECT-TYPE
    SYNTAX  SEQUENCE OF IbmvNbrEntry
    ACCESS  not-accessible
    STATUS  mandatory
    DESCRIPTION
            "A list of information about IBM's VINES router neighbor table."
    ::= { ibmvNeighbor 3 }

ibmvNbrEntry OBJECT-TYPE
        SYNTAX  IbmvNbrEntry
        ACCESS  not-accessible
        STATUS  mandatory
        DESCRIPTION
                "The information for each entry in the neighbor table."
        INDEX   { ibmvNbrNetid,
                  ibmvNbrSubNetid,
                  ibmvNbrIfType,
                  ibmvNbrLocSlot,
                  ibmvNbrLocPort }
        ::= { ibmvNbrTable 1 }


IbmvNbrEntry ::= SEQUENCE {
    ibmvNbrNetid       OCTET STRING,
    ibmvNbrSubNetid    OCTET STRING,
    ibmvNbrType        INTEGER,
    ibmvNbrIfType      INTEGER,
    ibmvNbrRemAddress  OCTET STRING,
    ibmvNbrLocAddress  OCTET STRING,
    ibmvNbrLocSlot     INTEGER,
    ibmvNbrLocPort     INTEGER,
    ibmvNbrAging       INTEGER,
    ibmvNbrFlags       INTEGER,
    ibmvNbrRIF         OCTET STRING,
    ibmvNbrIfIndex     INTEGER,
    ibmvNbrMetric      INTEGER
}

ibmvNbrNetid OBJECT-TYPE
        SYNTAX  OCTET STRING
        ACCESS  read-only
        STATUS  mandatory
        DESCRIPTION
                "The network ID of the neighbor. The VINES internet address
                has the following form: 'nnnnnnnn.ssss'hex, where n = network
                ID and s = subnetwork ID. If the neighbor is a router, then
                network ID is the router node's (the neighbor's) serial number."
        ::= { ibmvNbrEntry 1 }

ibmvNbrSubNetid OBJECT-TYPE
        SYNTAX  OCTET STRING
        ACCESS  read-only
        STATUS  mandatory
        DESCRIPTION
                "The subnetwork ID of the neighbor. The VINES internet address
                has the following form: 'nnnnnnnn.ssss'hex, where n = network ID
                and s = subnetwork ID. If the neighbor is a router node,
                then the subnetwork ID for the router node (the neighbor) is 1."
        ::= { ibmvNbrEntry 2 }

ibmvNbrType OBJECT-TYPE
        SYNTAX  INTEGER {server(1),
                         workstation(2)}
        ACCESS  read-only
        STATUS  mandatory
        DESCRIPTION
                "The type of the neighbor (workstation = pc)."
        ::= { ibmvNbrEntry 3 }

ibmvNbrIfType OBJECT-TYPE
        SYNTAX  INTEGER {
          other(1),
          regular1822(2),
          hdh1822(3),
          ddn-x25(4),
          rfc877-x25(5),
          ethernet-csmacd(6),
          iso88023-csmacd(7),
          iso88024-tokenBus(8),
          iso88025-tokenRing(9),
          iso88026-man(10),
          starLan(11),
          proteon-10Mbit(12),
          proteon-80Mbit(13),
          hyperchannel(14),
          fddi(15),
          lapb(16),
          sdlc(17),
          ds1(18),
          cept(19),
          basicISDN(20),
          primaryISDN(21),
          propPointToPointSerial(22),
          ppp(23),
          loopback(24),
          eon(25),
          ethernet-3Mbit(26),
          nsip(27),
          slip(28),
          ultra(29),
          ds3(30),
          sip(31),
          frame-relay(32)}
        ACCESS  read-only
        STATUS  mandatory
        DESCRIPTION
                "The type of interface that the server uses to reach the
                neighbor."
        ::= { ibmvNbrEntry 4 }

ibmvNbrRemAddress OBJECT-TYPE
        SYNTAX  OCTET STRING
        ACCESS  read-only
        STATUS  mandatory
        DESCRIPTION
                "The address of the neighbor's physical interface.  For LAN's,
                it is the hardware address of the neighbor."
        ::= { ibmvNbrEntry 5 }

ibmvNbrLocAddress OBJECT-TYPE
        SYNTAX  OCTET STRING
        ACCESS  read-only
        STATUS  mandatory
        DESCRIPTION
                "The address of the router node's physical interface,
                such as a LAN address."
        ::= { ibmvNbrEntry 6 }

ibmvNbrLocSlot OBJECT-TYPE
        SYNTAX  INTEGER (1..7)
        ACCESS  read-only
        STATUS  mandatory
        DESCRIPTION
                "The slot number of the interface card that the router node
                uses to reach the neighbor."
        ::= { ibmvNbrEntry 7 }

ibmvNbrLocPort OBJECT-TYPE
        SYNTAX  INTEGER (0..3)
        ACCESS  read-only
        STATUS  mandatory
        DESCRIPTION
                "The port number on the interface card that the router node
                used to reach the neighbor."
        ::= { ibmvNbrEntry 8 }

ibmvNbrAging OBJECT-TYPE
    SYNTAX  INTEGER
    ACCESS  read-only
    STATUS  mandatory
    DESCRIPTION
            "The amount of time left before a neighbor entry
            will be removed because of aging.  For a WAN link, which is
            defined to be permanent, this object is not applicable."
    ::= { ibmvNbrEntry 9 }

ibmvNbrFlags OBJECT-TYPE
    SYNTAX  INTEGER {permanent(1),
                     nonpermanent(2)}
    ACCESS  read-only
    STATUS  mandatory
    DESCRIPTION
            "Only applicable to a WAN link; states if the link is
            permanent or non-permanent."
    ::= { ibmvNbrEntry 10}

ibmvNbrRIF OBJECT-TYPE
    SYNTAX  OCTET STRING
    ACCESS  read-only
    STATUS  mandatory
    DESCRIPTION
            "LAN - MAC address and if applicable, source routing
                   information.
             Frame Relay - n/a
             PPP - n/a"
    ::= { ibmvNbrEntry 11 }

ibmvNbrIfIndex OBJECT-TYPE
    SYNTAX  INTEGER
    ACCESS  read-only
    STATUS  mandatory
    DESCRIPTION
            "The interface (using the MIB II standard) used to reach the
            neighbor.  This number corresponds to the IfIndex object found
            in MIB II."
    ::= { ibmvNbrEntry 12 }

ibmvNbrMetric OBJECT-TYPE
    SYNTAX  INTEGER
    ACCESS  read-only
    STATUS  mandatory
    DESCRIPTION
            "The cost to reach the neighbor."
    ::= { ibmvNbrEntry 13 }


------------------------------------------------------------------------
------------------------------------------------------------------------
--
-- Group: VINES Routing Information
--
-- Description: All information related to the routing table.
--              This includes related configuration questions,
--              RTP statistics, and the routing table itself.
--
------------------------------------------------------------------------
------------------------------------------------------------------------

------------------------------------------------------------------------
-- Subgroup: VINES Routing configuration
--
-- Description:  Configuration questions related to the routing table
------------------------------------------------------------------------
ibmvRtConfig  OBJECT IDENTIFIER ::= {ibmvRouting 1}

ibmvRtCfgMax OBJECT-TYPE
    SYNTAX  INTEGER
    ACCESS  read-only
    STATUS  mandatory
    DESCRIPTION
            "The maximum number of entries allowed in the routing table.
            This value is not defined by administrator."
    ::= { ibmvRtConfig 1 }

------------------------------------------------------------------------
-- Name: Inbound RTP Filters
--
-- Description: The inbound filters operate on network numbers contained in
--              the topological entries in the RTP update, response, and
--              redirect packets received over a specified interface.
--              In deny mode, the IBM 6611 ignores route information for
--              a network if the network number and the interface on which
--              the route information was received matches any inbound RTP
--              filter.  In permit mode, the IBM 6611 processes route
--              information for a network only if the network number and the
--              interface on which the route information was received matches
--              any inbound RTP filter.
------------------------------------------------------------------------
ibmvRtCfgInFlt OBJECT-TYPE
    SYNTAX  INTEGER {enable (1),
                     disable (2)}
    ACCESS  read-only
    STATUS  mandatory
    DESCRIPTION
            "Enables or disables all inbound RTP filters defined.  If no
            inbound RTP filters are defined, then this object has no effect.
            If a filter is defined, then the default value is 'enabled'."
    ::= { ibmvRtConfig 2 }

ibmvRtCfgInFltNum OBJECT-TYPE
    SYNTAX  INTEGER
    ACCESS  read-only
    STATUS  mandatory
    DESCRIPTION
            "The number of inbound RTP filters currently defined."
    ::= { ibmvRtConfig 3 }

------------------------------------------------------------------------
--                            T A B L E
--                            ---------
--
-- Name: VINES Inbound RTP Filter Table
--
------------------------------------------------------------------------
ibmvRtCfgInFltTable OBJECT-TYPE
    SYNTAX  SEQUENCE OF IbmvRtCfgInFltEntry
    ACCESS  not-accessible
    STATUS  mandatory
    DESCRIPTION
            "A list of information about the inbound RTP filters which
            are specified for this router node."
    ::= { ibmvRtConfig 4 }

ibmvRtCfgInFltEntry OBJECT-TYPE
    SYNTAX  IbmvRtCfgInFltEntry
    ACCESS  not-accessible
    STATUS  mandatory
    DESCRIPTION
            "The information for each entry in the inbound RTP filter table."
    INDEX { ibmvRtCfgInFltNetID,
            ibmvRtCfgInFltIfIndex }
    ::= { ibmvRtCfgInFltTable 1 }

IbmvRtCfgInFltEntry ::= SEQUENCE {
        ibmvRtCfgInFltNetID    OCTET STRING,
        ibmvRtCfgInFltIfIndex  INTEGER,
        ibmvRtCfgInFltMode     INTEGER,
        ibmvRtCfgInFltUses     Counter
}

ibmvRtCfgInFltNetID OBJECT-TYPE
    SYNTAX  OCTET STRING
    ACCESS  read-only
    STATUS  mandatory
    DESCRIPTION
            "Administrator defined object which specifies the VINES network
            number to be filtered on the port.  The range of the network
            number is 00000000 - FFFFFFFE.  If the network number,
            0xFFFFFFFF, is defined, then all network numbers will be filtered."
    ::= { ibmvRtCfgInFltEntry 1 }

ibmvRtCfgInFltIfIndex OBJECT-TYPE
    SYNTAX  INTEGER
    ACCESS  read-only
    STATUS  mandatory
    DESCRIPTION
            "The interface (using the MIB II standard) for which the
            inbound RTP filters were defined.  This number corresponds to
            the IfIndex object found in MIB II."
    ::= { ibmvRtCfgInFltEntry 2 }

ibmvRtCfgInFltMode OBJECT-TYPE
    SYNTAX  INTEGER {permit (1),
                     deny (2)}
    ACCESS  read-only
    STATUS  mandatory
    DESCRIPTION
            "The filtering action for the inbound RTP filter. The inbound RTP
            filters operate on network numbers contained in the topological
            entries in the RTP update, response, and redirect packets received
            over a specified interface.  In deny mode, the 6611 ignores route
            information for a network if the network number and the
            port on which the route information was received matches any
            inbound RTP filter.  In permit mode, the IBM 6611 processes route
            information for a network only if the network number and the port
            on which the route information was received matches any inbound
            RTP filter. The default for this object is 'deny'."
    ::= { ibmvRtCfgInFltEntry 3 }

ibmvRtCfgInFltUses OBJECT-TYPE
    SYNTAX  Counter
    ACCESS  read-only
    STATUS  mandatory
    DESCRIPTION
            "The number of times the defined filter was used."
    ::= { ibmvRtCfgInFltEntry 4 }

------------------------------------------------------------------------
-- Name: Outbound RTP Filters
--
-- Description: The outbound RTP filters operate on the network numbers
--              contained in the topological entries in RTP update and
--              response packets transmitted over a specified interface.
--              In deny mode, the IBM 6611 does not advertise route
--              information for a network if the network number and the
--              interface on which the route information is to be transmitted
--              matches any outbound RTP filter.  In permit mode, the 6611
--              advertises route information for a network only if the network
--              number and the interface on which the route information is to
--              be transmitted matches any outbound RTP filter.
------------------------------------------------------------------------
ibmvRtCfgOutFlt OBJECT-TYPE
    SYNTAX  INTEGER {enable (1),
                     disable (2)}
    ACCESS  read-only
    STATUS  mandatory
    DESCRIPTION
            "Enables or disables all outbound RTP filters defined.  If no
            outbound RTP filters are defined, then this object has no effect.
            If a filter is defined, then the default value is 'enabled'."
    ::= { ibmvRtConfig 5 }

ibmvRtCfgOutFltNum OBJECT-TYPE
    SYNTAX  INTEGER
    ACCESS  read-only
    STATUS  mandatory
    DESCRIPTION
            "The number of outbound RTP filters currently defined."
    ::= { ibmvRtConfig 6 }

------------------------------------------------------------------------
--                            T A B L E
--                            ---------
--
-- Name: VINES Outbound RTP Filter Table
--
------------------------------------------------------------------------
ibmvRtCfgOutFltTable OBJECT-TYPE
    SYNTAX  SEQUENCE OF IbmvRtCfgOutFltEntry
    ACCESS  not-accessible
    STATUS  mandatory
    DESCRIPTION
            "A list of information about the outbound RTP filters which
            are specified for this router node."
    ::= { ibmvRtConfig 7 }

ibmvRtCfgOutFltEntry OBJECT-TYPE
    SYNTAX  IbmvRtCfgOutFltEntry
    ACCESS  not-accessible
    STATUS  mandatory
    DESCRIPTION
            "The information for each entry in the outbound RTP filter table."
    INDEX { ibmvRtCfgOutFltNetID,
            ibmvRtCfgOutFltIfIndex }
    ::= { ibmvRtCfgOutFltTable 1 }

IbmvRtCfgOutFltEntry ::= SEQUENCE {
        ibmvRtCfgOutFltNetID    OCTET STRING,
        ibmvRtCfgOutFltIfIndex  INTEGER,
        ibmvRtCfgOutFltMode     INTEGER,
        ibmvRtCfgOutFltUses     Counter
}


ibmvRtCfgOutFltNetID OBJECT-TYPE
    SYNTAX  OCTET STRING
    ACCESS  read-only
    STATUS  mandatory
    DESCRIPTION
            "Administrator defined object which specifies the VINES network
            number to be filtered on the port.  The range of the network
            number is 00000000 - FFFFFFFE.  If the network number,
            0xFFFFFFFF, is defined, then all network numbers will be filtered."
    ::= { ibmvRtCfgOutFltEntry 1 }

ibmvRtCfgOutFltIfIndex OBJECT-TYPE
    SYNTAX  INTEGER
    ACCESS  read-only
    STATUS  mandatory
    DESCRIPTION
            "The interface (using the MIB II standard) for which the
            outbound RTP filters were defined.  This number corresponds to
            the IfIndex object found in MIB II."
    ::= { ibmvRtCfgOutFltEntry 2 }

ibmvRtCfgOutFltMode OBJECT-TYPE
    SYNTAX  INTEGER {permit (1),
                     deny (2)}
    ACCESS  read-only
    STATUS  mandatory
    DESCRIPTION
            "The filtering action for the outbound RTP filter. The outbound
            RTP filters operate on the network numbers contained in the
            topological entries in RTP update and response packets
            transmitted over a specified interface.  In deny mode,
            filters operate on interface names and network numbers (that is,
            the network numbers contained in the topological entries in the
            RTP packets).  In deny mode, the IBM 6611 does not advertise
            route information for a network if the network number and the
            interface on which the route information is to be transmitted
            matches any outbound RTP filter.  In permit mode, the 6611
            advertises route information for a network only if the network
            number and the interface on which the route information is to be
            transmitted matches any outbound RTP filter. The default for this
            object is 'Deny'."
    ::= { ibmvRtCfgOutFltEntry 3 }

ibmvRtCfgOutFltUses OBJECT-TYPE
    SYNTAX  Counter
    ACCESS  read-only
    STATUS  mandatory
    DESCRIPTION
            "The number of times the defined filter was used."
    ::= { ibmvRtCfgOutFltEntry 4 }

------------------------------------------------------------------------
-- Name: RTP Router Filters
--
-- Description: The RTP router filters operate on the network number contained
--              in the source network number field in the IP header of any RTP
--              packet (update, request, response, and redirect).  (The
--              subnetwork ID is assumed to be 0x0001.)  In deny mode,
--              the IBM 6611 ignores route information from a service node
--              if the sending router's network number matches any RTP router
--              filter.  In permit mode, the IBM 6611 processes route
--              information from a router only if the sending router's
--              network number matches any RTP router filter.
------------------------------------------------------------------------
ibmvRtCfgFlt OBJECT-TYPE
    SYNTAX  INTEGER {enable (1),
                     disable (2)}
    ACCESS  read-only
    STATUS  mandatory
    DESCRIPTION
            "Enables or disables all RTP router filters defined.  If no
            RTP router filters are defined, then this object has no effect.
            If a filter is defined, then the default value is 'enabled'."
    ::= { ibmvRtConfig 8 }


ibmvRtCfgFltNum OBJECT-TYPE
    SYNTAX  INTEGER
    ACCESS  read-only
    STATUS  mandatory
    DESCRIPTION
            "The number of RTP router filters currently defined."
    ::= { ibmvRtConfig 9 }

------------------------------------------------------------------------
--                            T A B L E
--                            ---------
--
-- Name: VINES RTP Router Filter Table
--
------------------------------------------------------------------------
ibmvRtCfgFltTable OBJECT-TYPE
    SYNTAX  SEQUENCE OF IbmvRtCfgFltEntry
    ACCESS  not-accessible
    STATUS  mandatory
    DESCRIPTION
            "A list of information about the RTP router filters which
            are specified for this router node."
    ::= { ibmvRtConfig 10 }

ibmvRtCfgFltEntry OBJECT-TYPE
    SYNTAX  IbmvRtCfgFltEntry
    ACCESS  not-accessible
    STATUS  mandatory
    DESCRIPTION
            "The information for each entry in the RTP router filter table."
    INDEX { ibmvRtCfgFltNetID }
    ::= { ibmvRtCfgFltTable 1 }

IbmvRtCfgFltEntry ::= SEQUENCE {
        ibmvRtCfgFltNetID  OCTET STRING,
        ibmvRtCfgFltMode   INTEGER,
        ibmvRtCfgFltUses   Counter
}


ibmvRtCfgFltNetID OBJECT-TYPE
    SYNTAX  OCTET STRING
    ACCESS  read-only
    STATUS  mandatory
    DESCRIPTION
            "Administrator defined object which specifies the VINES network
            number to be filtered on the port.  The range of the network
            number is 00000000 - FFFFFFFE.  If the network number,
            0xFFFFFFFF, is defined, then all network numbers will be filtered."
    ::= { ibmvRtCfgFltEntry 1 }

ibmvRtCfgFltMode OBJECT-TYPE
    SYNTAX  INTEGER {permit (1),
                     deny (2)}
    ACCESS  read-only
    STATUS  mandatory
    DESCRIPTION
            "The filtering action for the RTP router filter. The RTP router
            filters operate on the network number contained in the source
            network number field in the IP header of any RTP packet (update,
            request, response, and redirect).  (The subnetwork ID is assumed
            to be 0x0001.)  In deny mode, the IBM 6611 ignores route
            information from a service node if the sending router's network
            number matches any RTP router filter.  In permit mode, the IBM 6611
            processes route information from a router only if the sending
            router's network number matches any RTP router filter.  The default
            for this object is 'deny'."
    ::= { ibmvRtCfgFltEntry 2 }

ibmvRtCfgFltUses OBJECT-TYPE
    SYNTAX  Counter
    ACCESS  read-only
    STATUS  mandatory
    DESCRIPTION
            "The number of times the defined filter was used."
    ::= { ibmvRtCfgFltEntry 3 }




------------------------------------------------------------------------
-- Subgroup: VINES Routing Update Protocol
--
-- Description:  Statistical information on the following RTP packets:
--               - Routing update packets
--               - Routing request packets
--               - Routing response packets
--               - Routing redirect packets
------------------------------------------------------------------------
ibmvRTP  OBJECT IDENTIFIER ::= {ibmvRouting 2}

ibmvrtpUpdSents OBJECT-TYPE
    SYNTAX  Counter
    ACCESS  read-only
    STATUS  mandatory
    DESCRIPTION
            "The number of routing update packets sent since the last reboot.
            The routing update packets are periodically broadcast by nodes
            to notify neighboring nodes of their existence.  Router nodes
            include network topology information in these updates."
    ::= { ibmvRTP 1 }

ibmvrtpUpdRecs OBJECT-TYPE
    SYNTAX  Counter
    ACCESS  read-only
    STATUS  mandatory
    DESCRIPTION
            "The number of routing update packets received since the last
            reboot.  The routing update packets are sent from neighboring node
            making known their existence.  Packets received from router
            nodes include network topology information."
    ::= { ibmvRTP 2 }

ibmvrtpReqSents OBJECT-TYPE
    SYNTAX  Counter
    ACCESS  read-only
    STATUS  mandatory
    DESCRIPTION
            "The number of routing request packets sent since the last reboot.
            Routing request packets are sent by a node when it requires an
            immediate update."
    ::= { ibmvRTP 3 }

ibmvrtpReqRecs OBJECT-TYPE
    SYNTAX  Counter
    ACCESS  read-only
    STATUS  mandatory
    DESCRIPTION
            "The number of routing request packets received since the last
            reboot.  The 6611 receives routing request packets when another
            node requires an immediate update.  The 6611 will send the update
            in a routing response packet."
    ::= { ibmvRTP 4 }

ibmvrtpResSents OBJECT-TYPE
    SYNTAX  Counter
    ACCESS  read-only
    STATUS  mandatory
    DESCRIPTION
            "The number of routing response packets sent since the last reboot.
            Routing response packets are sent in response to a routing request
            packet."
    ::= { ibmvRTP 5 }

ibmvrtpResRecs OBJECT-TYPE
    SYNTAX  Counter
    ACCESS  read-only
    STATUS  mandatory
    DESCRIPTION
            "The number of routing response packets received since the last
            reboot.  When a node sends out a routing request packet, it
            receives a routing response packet which contains all the routing
            information requested."
    ::= { ibmvRTP 6 }

ibmvrtpRedSents OBJECT-TYPE
    SYNTAX  Counter
    ACCESS  read-only
    STATUS  mandatory
    DESCRIPTION
            "The number of routing redirect packets sent since the last reboot.
            The routing redirect packets are sent by a node to notify another
            node of a more direct path to a destination node."
    ::= { ibmvRTP 7 }

ibmvrtpRedRecs OBJECT-TYPE
    SYNTAX  Counter
    ACCESS  read-only
    STATUS  mandatory
    DESCRIPTION
            "The number of routing redirect packets received since the last
            reboot.  A 6611 receives a routing redirect packet when another
            node knows a more direct path to the destination node."
    ::= { ibmvRTP 8 }

ibmvrtpHeaderError OBJECT-TYPE
    SYNTAX  Counter
    ACCESS  read-only
    STATUS  mandatory
    DESCRIPTION
            "The number of RTP packets received since the last reboot
            with a RTP header error."
    ::= { ibmvRTP 9 }

------------------------------------------------------------------------
-- Subgroup: VINES Router Table Count
--
-- Description: Number of entries in the Router Table.
------------------------------------------------------------------------
ibmvRtNumber  OBJECT-TYPE
    SYNTAX  INTEGER
    ACCESS  read-only
    STATUS  mandatory
    DESCRIPTION
            "The number of entires in the route table."
    ::= { ibmvRouting 3 }

------------------------------------------------------------------------
--                            T A B L E
--                            ---------
--
-- Subgroup: The VINES Routing Table
--
-- Description: The MIB routing table contains objects which define
--              the variables found in the actual VINES routing table.
--
------------------------------------------------------------------------
ibmvRtTable OBJECT-TYPE
    SYNTAX  SEQUENCE OF IbmvRtEntry
    ACCESS  not-accessible
    STATUS  mandatory
    DESCRIPTION
            "A list of information about IBM's VINES router table."
    ::= { ibmvRouting 4 }

ibmvRtEntry OBJECT-TYPE
    SYNTAX  IbmvRtEntry
    ACCESS  not-accessible
    STATUS  mandatory
    DESCRIPTION
            "The information for each entry in the router table."
    INDEX   { ibmvRtNetid }
    ::= { ibmvRtTable 1 }

IbmvRtEntry ::=
    SEQUENCE {
        ibmvRtNetid        OCTET STRING,
        ibmvRtMetric       INTEGER,
        ibmvRtIdle         INTEGER,
        ibmvRtGateNetid    OCTET STRING,
        ibmvRtIfIndex      INTEGER,
        ibmvRtState        INTEGER
}

ibmvRtNetid OBJECT-TYPE
        SYNTAX  OCTET STRING
        ACCESS  read-only
        STATUS  mandatory
        DESCRIPTION
                "The network ID of the router node's destination router node."
        ::= { ibmvRtEntry 1 }

ibmvRtMetric OBJECT-TYPE
        SYNTAX  INTEGER
        ACCESS  read-only
        STATUS  mandatory
        DESCRIPTION
                "The routing metric used by the called router node to reach the
                destination.  A routing metric is an estimated round-trip
                delay time associated with the router that maximum sized
                VINES IP packets will take to reach the destination.
                The metric reflects the cost of the path to the destination,
                it is in 200-millisecond units."
        ::= { ibmvRtEntry 2 }

ibmvRtIdle OBJECT-TYPE
        SYNTAX  INTEGER
        ACCESS  read-only
        STATUS  mandatory
        DESCRIPTION
                "The time to live timer for this router node's entry.  This
                value indicates the amount of time before the entry is removed
                from the called router node's routing table.  The value is
                returned in 90 second units."
        ::= { ibmvRtEntry 3 }

ibmvRtGateNetid OBJECT-TYPE
        SYNTAX  OCTET STRING
        ACCESS  read-only
        STATUS  mandatory
        DESCRIPTION
                "The network ID of the router node that acts as the router for
                reaching the destination router node."
        ::= { ibmvRtEntry 4 }

ibmvRtIfIndex OBJECT-TYPE
    SYNTAX  INTEGER
    ACCESS  read-only
    STATUS  mandatory
    DESCRIPTION
            "The interface (using the MIB II standard) which identifies the
            local interface through which the next hop of this route should
            be reached.  This number corresponds to the IfIndex object found
            in MIB II."
    ::= { ibmvRtEntry 5 }

ibmvRtState OBJECT-TYPE
    SYNTAX  INTEGER {permanent(1),
                     nonpermanent(2)}
    ACCESS  read-only
    STATUS  mandatory
    DESCRIPTION
            "The state the routing entry; permanent or not permanent."
    ::= { ibmvRtEntry 6 }


------------------------------------------------------------------------
------------------------------------------------------------------------
--
-- Group: VINES Internet Control Protocol
--
-- Description: Statistical information on internet control protocol
--              packets which provide exception notification and
--              metric notification support.
--
------------------------------------------------------------------------
------------------------------------------------------------------------
ibmvicpExcGens OBJECT-TYPE
    SYNTAX  Counter
    ACCESS  read-only
    STATUS  mandatory
    DESCRIPTION
            "Number of exception notifications generated from this router
            node since the last reboot."
    ::= { ibmvICP 1 }

ibmvicpMetricGens OBJECT-TYPE
    SYNTAX  Counter
    ACCESS  read-only
    STATUS  mandatory
    DESCRIPTION
            "The number of metric notifications generated from this router
            node since the last reboot. The ICP packet contains metric
            information about the final transmission medium used to reach
            a client node."
    ::= { ibmvICP 2 }

ibmvicpHeaderError OBJECT-TYPE
    SYNTAX  Counter
    ACCESS  read-only
    STATUS  mandatory
    DESCRIPTION
            "The number of ICP packets received since the last reboot
            with an ICP header error."
    ::= { ibmvICP 3 }



------------------------------------------------------------------------
------------------------------------------------------------------------
--
-- Group: VINES Fragmentation Protocol
--
-- Description: Statistical information on fragmentation protocol
--              which provides fragmentation and reassembly of
--              network layer packets.
--
------------------------------------------------------------------------
------------------------------------------------------------------------
ibmvFRPreassembles OBJECT-TYPE
        SYNTAX  Counter
        ACCESS  read-only
        STATUS  mandatory
        DESCRIPTION
                "The number of times packets were reassembled since the
                last reboot.  One VINES IP packet being broken into
                three message fragments is counted as one fragmentation.
                The three fragments being reassembled into one VINES
                IP packet counts as one reassembly."
        ::= { ibmvFRP 1 }

ibmvFRPfragsReassembled OBJECT-TYPE
    SYNTAX  Counter
    ACCESS  read-only
    STATUS  mandatory
    DESCRIPTION
            "The number of fragments that were reassembled since the last
            reboot.  If three fragments are to be reassembled into one
            packet, then this object value will add three to its total."
    ::= { ibmvFRP 2}

ibmvFRPreasFails OBJECT-TYPE
    SYNTAX  Counter
    ACCESS  read-only
    STATUS  mandatory
    DESCRIPTION
            "The number of times the reassembly of fragments fails since the
            last reboot."
    ::= { ibmvFRP 3}

ibmvFRPfragmented OBJECT-TYPE
        SYNTAX  Counter
        ACCESS  read-only
        STATUS  mandatory
        DESCRIPTION
                "The number of packet fragmentations performed since the last
                reboot."
        ::= { ibmvFRP 4}

ibmvFRPfrgCreated OBJECT-TYPE
    SYNTAX  Counter
    ACCESS  read-only
    STATUS  mandatory
    DESCRIPTION
            "The number of fragments created since the last reboot when
            fragmenting VINES IP packets. If a VINES IP packet is fragmented
            into three fragments, then this object value will add three to
            its total."
    ::= { ibmvFRP 5}

ibmvFRPfrgFails OBJECT-TYPE
    SYNTAX  Counter
    ACCESS  read-only
    STATUS  mandatory
    DESCRIPTION
            "The number of times the fragmentation of a VINES IP packets
            fails since the last reboot."
    ::= { ibmvFRP 6}

------------------------------------------------------------------------
------------------------------------------------------------------------
--
-- Group: VINES Interface
--
-- Description: The following tables:
--                VINES port configuration table
--                VINES port filter table
--                VINES interface table
--
--              Gather all the VINES information which is related to the
--              ports or the interfaces within the router node.
--
------------------------------------------------------------------------
------------------------------------------------------------------------

------------------------------------------------------------------------
--                            T A B L E
--                            ---------
--
-- Subgroup: The VINES Port Configuration Table
--
-- Description: Configuration questions which must be defined for
--              each port within the Router Node.
--
------------------------------------------------------------------------
ibmvPortCfgTable OBJECT-TYPE
    SYNTAX  SEQUENCE OF IbmvPortCfgEntry
    ACCESS  not-accessible
    STATUS  mandatory
    DESCRIPTION
            "The list of information about port configuration at
            each interface."
    ::= { ibmvInterface 1 }

ibmvPortCfgEntry OBJECT-TYPE
    SYNTAX  IbmvPortCfgEntry
    ACCESS  not-accessible
    STATUS  mandatory
    DESCRIPTION
            "The information for each entry in the port configuration
            table."
    INDEX   { ibmvPortCfgIfIndex }
    ::= { ibmvPortCfgTable 1 }

IbmvPortCfgEntry ::=
    SEQUENCE {
        ibmvPortCfgIfIndex   INTEGER,
        ibmvPortCfgARP       INTEGER,
        ibmvPortCfgServ      INTEGER,
        ibmvPortCfgHCtoServ  INTEGER,
        ibmvPortCfgPerUpdate INTEGER,
        ibmvPortCfgMetric    INTEGER,
        ibmvPortCfgTR        INTEGER,
        ibmvPortCfgEN        INTEGER,
        ibmvPortCfgInFlt     INTEGER,
        ibmvPortCfgInFltNum  INTEGER,
        ibmvPortCfgOutFlt    INTEGER,
        ibmvPortCfgOutFltNum INTEGER
    }

ibmvPortCfgIfIndex OBJECT-TYPE
    SYNTAX  INTEGER
    ACCESS  read-only
    STATUS  mandatory
    DESCRIPTION
            "The interface (using the MIB II standard) which uniquely
            identifies each interface and allows multiple tables to be
            associated with a given interface. This number corresponds to
            the IfIndex object found in MIB II."
    ::= { ibmvPortCfgEntry 1 }

ibmvPortCfgARP OBJECT-TYPE
    SYNTAX  INTEGER {enable (1),
                     disable (2)}
    ACCESS  read-only
    STATUS  mandatory
    DESCRIPTION
            "Administrator defined value which specifies whether the router
            node will assign VINES addresses to clients that reside on the LAN
            attached to this port.  The default value for this object is
            'disable'."
    ::= { ibmvPortCfgEntry 2 }

ibmvPortCfgServ OBJECT-TYPE
    SYNTAX  INTEGER {enable (1),
                     disable (2)}
    ACCESS  read-only
    STATUS  mandatory
    DESCRIPTION
            "Administrator defined value specifying whether the serverless
            option is enables or disabled.  When the serverless option is
            enabled; the router looks for particular broadcasts that clients
            use in finding the services on the VINES server. This allows
            client nodes on a serverless LAN to communicate with a VINES
            server more than one hop away. The default value for this object
            is 'disable'."
    ::= { ibmvPortCfgEntry 3 }

ibmvPortCfgHCtoServ OBJECT-TYPE
    SYNTAX  INTEGER
    ACCESS  read-only
    STATUS  mandatory
    DESCRIPTION
            "Administrator defined value which specifies the number of hops
            from the client to the router node."
    ::= { ibmvPortCfgEntry 4 }

ibmvPortCfgPerUpdate OBJECT-TYPE
    SYNTAX  INTEGER {
              enabled  (1),
              disabled (2),
              na       (3)
            }
    ACCESS  read-only
    STATUS  mandatory
    DESCRIPTION
            "Administrator defined value which specifies whether periodic
            updates will be sent over a WAN link."
    ::= { ibmvPortCfgEntry 5 }

ibmvPortCfgMetric OBJECT-TYPE
    SYNTAX  INTEGER
    ACCESS  read-only
    STATUS  mandatory
    DESCRIPTION
            "Administrator defined value for port metric.  This value
            overrides the metric which is used by the IBM 6611 to make
            routing decisions.  If no response is provided to this parameter,
            the IBM 6611 will use defaults contained within the MPNP program.
            These defaults are based on values assigned by Banyan Systems for
            its VINES servers.
            The port metric is a rough estimate of the round trip delay for a
            maximum sized VINES IP packet to travel to any neighbor on this
            port.  The unit for the metric value is 200 milliseconds.  The
            default metric for an Ethernet port is 2.  The default metric for a
            Token-Ring is determined by the response to the Token-Ring
            Data Rate parameter.  The default metric for a serial port is
            determined by the response to the Serial-Line Speed parameter."
    ::= { ibmvPortCfgEntry 6 }

ibmvPortCfgTR OBJECT-TYPE
    SYNTAX  INTEGER {
              na      (1),
              snap    (2),
              vines-tr(3)
            }
    ACCESS  read-only
    STATUS  mandatory
    DESCRIPTION
            "Administrator defined value which determines the encapsulation
            method used for receiving and transmitting VINES packets on
            this port. IEEE 802.5 LLC uses 802.2 encapsulation followed by
            an LLC field using SAP value 0xBC  You cannot use IEEE 802.5
            LLC encapsulation on the same port that performs data link
            switching, if the 0xBC SAP has been configured for frame
            forwarding by the data link switching function. IEEE 802.5 SNAP
            uses 802.2 encapsulation followed by a SNAP header using the
            organizationally unique ID 0x08 00 4A, the protocol id 0x80C4
            for VINES IP and the protocol id 0x80C5 for VINES Link Level Echo."
    ::= { ibmvPortCfgEntry 7 }

ibmvPortCfgEN OBJECT-TYPE
    SYNTAX  INTEGER
            {
              na   (1),
              snap (2),
              v2   (3)
            }
    ACCESS  read-only
    STATUS  mandatory
    DESCRIPTION
            "Administrator defined value which determines the encapsulation
            method used for receiving and transmitting VINES packets on
            this port. Ethernet II uses DIX encapsulation with a packet
            type 0x0BAD for VINES IP and 0x0BAF for VINES Link Level Echo.
            IEEE 802.3 SNAP uses 802.2 encapsulation followed by a SNAP
            header using the organizationally unique ID 0x08 00 4A, the
            protocol id 0x80C4 for VINES IP and the protocol id 0x80C5 for
            VINES Link Level Echo."
    ::= { ibmvPortCfgEntry 8 }

ibmvPortCfgInFlt OBJECT-TYPE
    SYNTAX  INTEGER {enable (1),
                     disable (2)}
    ACCESS  read-only
    STATUS  mandatory
    DESCRIPTION
            "Administrator defined value which allows inbound port filters
            to be defined.  The default value is 'disabled'."
    ::= { ibmvPortCfgEntry 9 }

ibmvPortCfgInFltNum OBJECT-TYPE
    SYNTAX  INTEGER
    ACCESS  read-only
    STATUS  mandatory
    DESCRIPTION
            "The number of inbound port filters defined for this port."
    ::= { ibmvPortCfgEntry 10 }

ibmvPortCfgOutFlt OBJECT-TYPE
    SYNTAX  INTEGER {enable (1),
                     disable (2)}
    ACCESS  read-only
    STATUS  mandatory
    DESCRIPTION
            "Administrator defined value which allows outbound port filters
            to be defined.  The default value is 'disabled'."
    ::= { ibmvPortCfgEntry 11 }

ibmvPortCfgOutFltNum OBJECT-TYPE
    SYNTAX  INTEGER
    ACCESS  read-only
    STATUS  mandatory
    DESCRIPTION
            "The number of outbound port filters defined for this port."
    ::= { ibmvPortCfgEntry 12 }



------------------------------------------------------------------------
--                            T A B L E
--                            ---------
--
-- Subgroup: The VINES Port Filter Configuration Table
--
-- Description: The port level filters operate on information contained
--              in the IP, IPC and SPP headers.
--
------------------------------------------------------------------------
ibmvFltTable OBJECT-TYPE
    SYNTAX  SEQUENCE OF IbmvFltEntry
    ACCESS  not-accessible
    STATUS  mandatory
    DESCRIPTION
            "The list of information about port filter configurations at
            each interface ."
    ::= { ibmvInterface 2  }

ibmvFltEntry OBJECT-TYPE
    SYNTAX  IbmvFltEntry
    ACCESS  not-accessible
    STATUS  mandatory
    DESCRIPTION
            "The information for each entry in the port filter configuration
            table."
    INDEX   { ibmvFltIfIndex,
              ibmvFltNo
            }
    ::= { ibmvFltTable 1 }


IbmvFltEntry ::=
    SEQUENCE {
        ibmvFltIfIndex   INTEGER,
        ibmvFltNo        INTEGER,
        ibmvFltMode      INTEGER,
        ibmvFltValue     OCTET STRING,
        ibmvFltMask      OCTET STRING,
        ibmvFltType      INTEGER,
        ibmvFltHCCompare INTEGER,
        ibmvFltUses      Counter
    }

ibmvFltIfIndex OBJECT-TYPE
    SYNTAX  INTEGER
    ACCESS  read-only
    STATUS  mandatory
    DESCRIPTION
            "The value of this object identifies the interface for which
            this entry contains management information. The IfIndex allows
            a subset of the filter table to be associated with a particular
            interface."
    ::= { ibmvFltEntry 1 }

ibmvFltNo OBJECT-TYPE
    SYNTAX  INTEGER
    ACCESS  read-only
    STATUS  mandatory
    DESCRIPTION
            "A unique integer identifying this filter entry for this
            interface."
    ::= { ibmvFltEntry 2 }

ibmvFltMode OBJECT-TYPE
    SYNTAX  INTEGER
            {
              inbound  (1),
              outbound (2)
            }
    ACCESS  read-only
    STATUS  mandatory
    DESCRIPTION
            "Identifies if the port filter is an inbound or outbound filter."
    ::= { ibmvFltEntry 3 }

ibmvFltValue OBJECT-TYPE
    SYNTAX  OCTET STRING (SIZE (18))
    ACCESS  read-only
    STATUS  mandatory
    DESCRIPTION
            "An octet string representing the concatenation of
            VINES IP header fields and VINES transport header fields
            required by this filter entry. Incoming packets will
            be bitwise ANDed with the value of ibmvFltMask, and
            if the result is equal to the value of this object, the
            packet will be filtered according to the value of
            ibmvFltValue.

            Fields from VINES IP and transport headers used for filtering:

            field length    field name
            ------------    ------------------------------
               8 BITS       protocol type
               4 BITS       hop count
              32 BITS       destination network number
              16 BITS       destination subnetwork number
              16 BITS       destination port number
              32 BITS       source network number
              16 BITS       source subnetwork number
              16 BITS       source port number"
    ::= { ibmvFltEntry 4 }

ibmvFltMask OBJECT-TYPE
    SYNTAX  OCTET STRING (SIZE (18))
    ACCESS  read-only
    STATUS  mandatory
    DESCRIPTION
            "An octet string indicating the parts of the VIP header and
            transport header relevant to this filter entry. This mask will
            be bitwise ANDed with the appropriate header fields; if the result
            is equal to the value of ibmvnFilterValue, the packet will be
            filtered according to the value of ibmvnFilterType."
    ::= { ibmvFltEntry 5 }

ibmvFltType OBJECT-TYPE
    SYNTAX  INTEGER {permit (1),
                     deny (2)}
    ACCESS  read-only
    STATUS  mandatory
    DESCRIPTION
            "Administrator defined value which determines the filtering mode
            for all filters defined on this port.  If the port is using
            Deny mode, then all packets matching a defined port filter
            will be discarded.  If the port is using Permit mode, then only
            the packets matching a defined port filter will be forwarded.
            The default value is Deny."
    ::= { ibmvFltEntry 6 }


ibmvFltHCCompare OBJECT-TYPE
    SYNTAX  INTEGER {
                less-than(1),
                less-than-equal(2),
                equal(3),
                greater-than-equal(4),
                greater-than(5),
                na (6)
            }
    ACCESS  read-only
    STATUS  mandatory
    DESCRIPTION
            "Administrator defined value which indicates the relational
            association desired if filtering is being done based on hop
            count. If filtering is not being done based on hop count (that
            is, if the hop count portion of IBM VINES Port Mask is 0) the
            value of this object will be none(1)."
    ::= { ibmvFltEntry 7 }

ibmvFltUses OBJECT-TYPE
    SYNTAX  Counter
    ACCESS  read-only
    STATUS  mandatory
    DESCRIPTION
            "This object counts how many times the defined filter was
            used."
    ::= { ibmvFltEntry 8 }
------------------------------------------------------------------------
-- Subgroup: VINES Interface Count
--
-- Description: Number of interfaces configured for VINES
------------------------------------------------------------------------
ibmvifNumber OBJECT-TYPE
    SYNTAX  INTEGER
    ACCESS  read-only
    STATUS  mandatory
    DESCRIPTION
            "The number of VINES interfaces configured on the router node."
    ::= { ibmvInterface 3  }

------------------------------------------------------------------------
--                            T A B L E
--                            ---------
--
-- Subgroup: The VINES Interface Table
--
-- Description: The MIB interface table contains information related to
--              each interface running vines.
--
------------------------------------------------------------------------
ibmvifTable OBJECT-TYPE
    SYNTAX  SEQUENCE OF IbmvifEntry
    ACCESS  not-accessible
    STATUS  mandatory
    DESCRIPTION
            "List of interfaces with some statistics about each interface."
    ::= { ibmvInterface 4  }

ibmvifEntry OBJECT-TYPE
    SYNTAX  IbmvifEntry
    ACCESS  not-accessible
    STATUS  mandatory
    DESCRIPTION
            "Information about one interface."
    INDEX   { ibmvifSlot,
              ibmvifPort }
    ::= { ibmvifTable 1 }

IbmvifEntry ::=
    SEQUENCE {
        ibmvifSlot    INTEGER,
        ibmvifPort    INTEGER,
        ibmvifDescr   DisplayString,
        ibmvifAddress OCTET STRING,
        ibmvifInPkts  Counter,
        ibmvifInErrs  Counter,
        ibmvifOutPkts Counter,
        ibmvifOutErrs Counter
   }

ibmvifSlot OBJECT-TYPE
    SYNTAX  INTEGER (1..7)
    ACCESS  read-only
    STATUS  mandatory
    DESCRIPTION
            "The slot number of the interface's communications card."
    ::= { ibmvifEntry 1 }

ibmvifPort OBJECT-TYPE
    SYNTAX  INTEGER (0..3)
    ACCESS  read-only
    STATUS  mandatory
    DESCRIPTION
            "The port number of the interface."
    ::= { ibmvifEntry 2 }

ibmvifDescr OBJECT-TYPE
    SYNTAX  DisplayString
    ACCESS  read-only
    STATUS  mandatory
    DESCRIPTION
            "A textual description of the interface."
    ::= { ibmvifEntry 3 }

ibmvifAddress OBJECT-TYPE
    SYNTAX  OCTET STRING
    ACCESS  read-only
    STATUS  mandatory
    DESCRIPTION
            "The physical address of the interface, applies to LAN
            interfaces only."
    ::= { ibmvifEntry 4 }

ibmvifInPkts OBJECT-TYPE
    SYNTAX  Counter
    ACCESS  read-only
    STATUS  mandatory
    DESCRIPTION
            "The total number of VINES IP packets that the router node
            received since the last reboot."
    ::= { ibmvifEntry 5 }

ibmvifInErrs OBJECT-TYPE
    SYNTAX  Counter
    ACCESS  read-only
    STATUS  mandatory
    DESCRIPTION
            "The total number of received VINES IP packets that contained
            errors since the last reboot."
    ::= { ibmvifEntry 6 }

ibmvifOutPkts OBJECT-TYPE
    SYNTAX  Counter
    ACCESS  read-only
    STATUS  mandatory
    DESCRIPTION
            "The total number of VINES IP packets that the router node
            sent since the last reboot."
    ::= { ibmvifEntry 7 }

ibmvifOutErrs OBJECT-TYPE
    SYNTAX  Counter
    ACCESS  read-only
    STATUS  mandatory
    DESCRIPTION
            "The total number of transmitted VINES IP packets that
            contained errors since the last reboot."
    ::= { ibmvifEntry 8 }


-- static char sccsid_appn_mib[] = "@(#) snmp/samples/appn.my, SNMP, v1r3, r3d48 1.21  5/19/94 09:56:23";


-- ******************** The APPN Node Group *************************

ibmappnNode                    OBJECT IDENTIFIER ::= { ibmappn 1 }
ibmappnGeneralInfoAndCaps      OBJECT IDENTIFIER ::= { ibmappnNode 1 }
ibmappnNnUniqueInfoAndCaps     OBJECT IDENTIFIER ::= { ibmappnNode 2 }
ibmappnEnUniqueCaps            OBJECT IDENTIFIER ::= { ibmappnNode 3 }
ibmappnPortInformation         OBJECT IDENTIFIER ::= { ibmappnNode 4 }
ibmappnLinkStationInformation  OBJECT IDENTIFIER ::= { ibmappnNode 5 }
ibmappnSnmpInformation         OBJECT IDENTIFIER ::= { ibmappnNode 6 }
ibmappnMemoryUse               OBJECT IDENTIFIER ::= { ibmappnNode 7 }
ibmappnXidInformation          OBJECT IDENTIFIER ::= { ibmappnNode 8 }

-- This group provides global information about the
-- APPN node, which is either a network node or an end node.


-- The first section applies to all APPN nodes.
-- The second section applies only to network nodes.
-- The third section applies only to end nodes.
-- The fourth section applies to Port information.
-- The fifth section applies to SNA link station Information.
-- The sixth section applies to SNMP traffic for this APPN sub-agent
-- The seventh section applies to APPN memory usage.

-- APPN General Information
-- This section applies to both network and end nodes.


ibmappnNodeCpName   OBJECT-TYPE
      SYNTAX DisplayString (SIZE (3..17))
      ACCESS read-only
      STATUS mandatory
      DESCRIPTION
          "Administratively-assigned network name
          for this node in the format NETID.CPNAME."

      ::=  { ibmappnGeneralInfoAndCaps 1 }

ibmappnNodeNetid    OBJECT-TYPE
      SYNTAX DisplayString  (SIZE (1..8))
      ACCESS read-only
      STATUS mandatory
      DESCRIPTION
          "Administratively-assigned APPN network identification,
           which can be from one to eight characters.
           This ID is used with the control point name
           to create a fully-qualified control point name."

      ::=  { ibmappnGeneralInfoAndCaps 2 }

ibmappnNodeBlockNum OBJECT-TYPE
      SYNTAX DisplayString   (SIZE (3))
      ACCESS read-only
      STATUS mandatory
      DESCRIPTION
         "The block number is the first three digits of the node_id.
          These 3 hexadecimal digits identify the product and are not
          configurable."

      ::=  { ibmappnGeneralInfoAndCaps 3 }

ibmappnNodeIdNum OBJECT-TYPE
      SYNTAX DisplayString  (SIZE (5))
      ACCESS read-only
      STATUS mandatory
      DESCRIPTION
         "The ID number is the last 5 digits of the node_id.
          These 5 hexadecimal digits are administratively defined and
          combined with the 3 digit block number form the node_id.
          This node_id is used to identify the local node and is include
          in APPN alerts as well as being included in XIDs.  A unique
          value is required for connections to SNA sub-area."

      ::=  { ibmappnGeneralInfoAndCaps 4 }

ibmappnNodeType  OBJECT-TYPE
      SYNTAX INTEGER {
                     networkNode(1),
                     endNode(2),
                     len(4)
                     }
      ACCESS read-only
      STATUS mandatory
      DESCRIPTION
           "Type of APPN node, either network, len, or end node."

      ::=  { ibmappnGeneralInfoAndCaps 5 }

ibmappnNodeUpTime  OBJECT-TYPE
      SYNTAX TimeTicks
      ACCESS read-only
      STATUS mandatory
      DESCRIPTION
          "Time (in hundredths of a second) since this APPN node
           was initialized."

      ::=  { ibmappnGeneralInfoAndCaps 6 }

ibmappnNodeNegotLs   OBJECT-TYPE
      SYNTAX INTEGER {yes(1), no(2)}
      ACCESS read-only
      STATUS mandatory
      DESCRIPTION
           "Indicates whether this node supports negotiable
            link stations."

      ::=  { ibmappnGeneralInfoAndCaps 7 }

ibmappnNodeSegReasm OBJECT-TYPE
      SYNTAX INTEGER {yes(1), no(2)}
      ACCESS read-only
      STATUS mandatory
      DESCRIPTION
           "Indicates whether this node supports segment
            reassembly.  This is only supported when
            segment generation is also supported."

      ::=  { ibmappnGeneralInfoAndCaps 8 }

ibmappnNodeBindReasm OBJECT-TYPE
      SYNTAX INTEGER {yes(1), no(2)}
      ACCESS read-only
      STATUS mandatory
      DESCRIPTION
           "Indicates whether this node supports Bind segment
            reassembly.  This will only be supported when Bind
            segment generation is also supported."

      ::=  { ibmappnGeneralInfoAndCaps 9 }

ibmappnNodeParallelTg   OBJECT-TYPE
      SYNTAX INTEGER {yes(1), no(2)}
      ACCESS read-only
      STATUS mandatory
      DESCRIPTION
           "Indicates whether this node supports parallel TGs."

      ::=  { ibmappnGeneralInfoAndCaps 10 }

ibmappnNodeService    OBJECT-TYPE
      SYNTAX INTEGER {yes(1), no(2)}
      ACCESS read-only
      STATUS mandatory
      DESCRIPTION
           "Indicates whether this node allows call-in from nodes not
            defined locally."

      ::=  { ibmappnGeneralInfoAndCaps 11 }

ibmappnNodeAdaptiveBindPacing  OBJECT-TYPE
      SYNTAX INTEGER {yes(1), no(2)}
      ACCESS read-only
      STATUS mandatory
      DESCRIPTION
           "Indicates whether this node supports adaptive bind pacing."

      ::=  { ibmappnGeneralInfoAndCaps 12 }


-- *****************************************************************
-- APPN Network Node Information
-- This section provides global information about the
-- APPN network node.

ibmappnNodeNnRcvRegChar OBJECT-TYPE
      SYNTAX INTEGER {yes(1), no(2)}
      ACCESS read-only
      STATUS mandatory
      DESCRIPTION
           "Indicates whether this node supports receiving registered
            characteristics."

      ::=  { ibmappnNnUniqueInfoAndCaps 1 }

ibmappnNodeNnGateway    OBJECT-TYPE
      SYNTAX INTEGER {yes(1), no(2)}
      ACCESS read-only
      STATUS mandatory
      DESCRIPTION
           "Indicates whether this is a gateway node."

      ::=  { ibmappnNnUniqueInfoAndCaps 2 }

ibmappnNodeNnCentralDirectory  OBJECT-TYPE
      SYNTAX INTEGER {yes(1), no(2)}
      ACCESS read-only
      STATUS mandatory
      DESCRIPTION
           "Indicates whether this node supports central directory
            cache."
      ::=  { ibmappnNnUniqueInfoAndCaps 3 }

ibmappnNodeNnTreeCache OBJECT-TYPE
      SYNTAX INTEGER {yes(1), no(2)}
      ACCESS read-only
      STATUS mandatory
      DESCRIPTION
           "Indicates whether this node supports route tree cache."

      ::=  { ibmappnNnUniqueInfoAndCaps 4 }

ibmappnNodeNnTreeUpdate  OBJECT-TYPE
      SYNTAX INTEGER {yes(1), no(2)}
      ACCESS read-only
      STATUS mandatory
      DESCRIPTION
           "Indicates whether this node supports
            incremental_tree_update, which is only
            supported when tree caching is supported."

      ::=  { ibmappnNnUniqueInfoAndCaps 5 }

ibmappnNodeNnRouteAddResist   OBJECT-TYPE
      SYNTAX INTEGER
      ACCESS read-only
      STATUS mandatory
      DESCRIPTION
          "Route addition resistance is a value that
          indicates the relative desirability
          of using this node for intermediate session traffic.
          The value, which can be any integer 0-255,
          is used in route computation.  The lower the value,
          the more desirable the node is for intermediate routing."

      ::=  { ibmappnNnUniqueInfoAndCaps 6 }

ibmappnNodeNnIsr   OBJECT-TYPE
      SYNTAX INTEGER {yes(1), no(2)}
      ACCESS read-only
      STATUS mandatory
      DESCRIPTION
           "Indicates whether the node supports intermediate
            session routing."

      ::=  { ibmappnNnUniqueInfoAndCaps 7 }

ibmappnNodeNnFrsn             OBJECT-TYPE
      SYNTAX INTEGER (0..65535)
      ACCESS read-only
      STATUS mandatory
      DESCRIPTION
          "Flow reduction sequence numbers (FRSNs) are associated
           with Topology Database Updates (TDUs) and are unique
           only within each APPN network node.  A TDU can be
           associated with multiple APPN resources. This object
           is the last FRSN sent in a topology update to
           adjacent network nodes."

      ::=  { ibmappnNnUniqueInfoAndCaps 8 }

-- *****************************************************************
-- APPN End Node Information

ibmappnNodeEnSegGen     OBJECT-TYPE
      SYNTAX INTEGER {yes(1), no(2)}
      ACCESS read-only
      STATUS mandatory
      DESCRIPTION
          "Indicates whether this end node supports segment generation."

      ::=  { ibmappnEnUniqueCaps 1 }

ibmappnNodeEnModeCosMap    OBJECT-TYPE
      SYNTAX INTEGER {yes(1), no(2)}
      ACCESS read-only
      STATUS mandatory
      DESCRIPTION
           "Indicates whether this end node supports
            mode name to COS name mapping."

      ::=  { ibmappnEnUniqueCaps 2 }

ibmappnNodeEnLocateCdinit  OBJECT-TYPE
      SYNTAX INTEGER {yes(1), no(2)}
      ACCESS read-only
      STATUS mandatory
      DESCRIPTION
           "Indicates whether this end node supports Locate Cdinit."

      ::=  { ibmappnEnUniqueCaps 3 }

ibmappnNodeEnSendRegNames OBJECT-TYPE
      SYNTAX INTEGER {yes(1), no(2)}
      ACCESS read-only
      STATUS mandatory
      DESCRIPTION
           "Indicates whether the node will register its LUs with the
            adjacent serving network node:

              NO  - do not register names
              YES - register names"

      ::=  { ibmappnEnUniqueCaps 4 }

ibmappnNodeEnSendRegChar OBJECT-TYPE
      SYNTAX INTEGER {yes(1), no(2)}
      ACCESS read-only
      STATUS mandatory
      DESCRIPTION
           "Indicates whether this node supports
            send register characteristics, which is only
            supported when send registered names is also
            supported."

      ::=  { ibmappnEnUniqueCaps 5 }


-- *****************************************************************************
-- APPN Port information
--

ibmappnNodePortTable OBJECT-TYPE
      SYNTAX SEQUENCE OF IbmappnNodePortEntry
      ACCESS not-accessible
      STATUS mandatory
      DESCRIPTION
           "The Port table describes the configuration and current
            status of the ports used by APPN.  The type of DLC is
            included in this table as a pointer to the DLC port
            specific tables."

      ::= { ibmappnPortInformation 1 }

ibmappnNodePortEntry OBJECT-TYPE
      SYNTAX IbmappnNodePortEntry
      ACCESS not-accessible
      STATUS mandatory
      DESCRIPTION
           "The Port Name is used as the index to this table."

      INDEX
             { ibmappnNodePortName }

      ::= { ibmappnNodePortTable 1 }

IbmappnNodePortEntry ::= SEQUENCE {
      ibmappnNodePortName            DisplayString,
      ibmappnNodePortState           INTEGER,

      ibmappnNodePortDlcType         INTEGER,
      ibmappnNodePortPortType        INTEGER,
      ibmappnNodePortSIMRIM          INTEGER,
      ibmappnNodePortLsRole          INTEGER,
      ibmappnNodePortMaxRcvBtuSize   INTEGER,
      ibmappnNodePortMaxIframeWindow INTEGER,
      ibmappnNodePortDefLsGoodXids   Counter,
      ibmappnNodePortDefLsBadXids    Counter,
      ibmappnNodePortDynLsGoodXids   Counter,
      ibmappnNodePortDynLsBadXids    Counter,
      ibmappnNodePortSpecific        OBJECT IDENTIFIER
                                   }


ibmappnNodePortName OBJECT-TYPE
      SYNTAX DisplayString (SIZE (1..8))
      ACCESS read-only
      STATUS mandatory
      DESCRIPTION
          "Administratively-assigned name for this APPN port.
           The name can be from one to eight characters."

      ::=  { ibmappnNodePortEntry 1 }

ibmappnNodePortState        OBJECT-TYPE
      SYNTAX INTEGER    {
                         inactive(1),
                         pendactive(2),
                         active(3),
                         pendinact(4)
                         }
      ACCESS read-write
      STATUS mandatory
      DESCRIPTION
           "Indicates the current state of this port."

      ::=  { ibmappnNodePortEntry 2 }

ibmappnNodePortDlcType OBJECT-TYPE
      SYNTAX INTEGER {
                      other(1),          -- none of the following
                      sdlc(2),
                      dls(3),
                      socket(4),
                      ethernet(5),
                      tokenRing(6)
                     }
          ACCESS  read-only
          STATUS  mandatory
          DESCRIPTION
                  "The type of DLC interface, distinguished according to
                  the protocol immediately 'below' this layer."

      ::=  { ibmappnNodePortEntry 3 }

ibmappnNodePortPortType  OBJECT-TYPE
      SYNTAX INTEGER {
                     leased(1),
                     switched(2),
                     sharedAccessFacilities(3)
              }
      ACCESS read-only
      STATUS mandatory
      DESCRIPTION
           "Identifies the type of line used by this port."

      ::=  { ibmappnNodePortEntry 4 }

ibmappnNodePortSIMRIM  OBJECT-TYPE
      SYNTAX INTEGER {yes(1), no(2)}
      ACCESS read-only
      STATUS mandatory
      DESCRIPTION
           "Indicates whether Set Initialization Mode (SIM) and
            Receive Initialization Mode (RIM) are supported."

      ::=  { ibmappnNodePortEntry 5 }

ibmappnNodePortLsRole OBJECT-TYPE
      SYNTAX INTEGER {
                     primary(1),
                     secondary(2),
                     negotiable(3),
                     abm(4)
             }
      ACCESS read-only
      STATUS mandatory
      DESCRIPTION
          "Initial role for LSs activated through this port,
           where 'abm' indicates asynchronous balance mode."

      ::=  { ibmappnNodePortEntry 6 }

ibmappnNodePortMaxRcvBtuSize OBJECT-TYPE
      SYNTAX INTEGER
      ACCESS read-only
      STATUS mandatory
      DESCRIPTION
          "Maximum Basic Transmission Size (BTU) that a
           link station on this port can receive."

      ::=  { ibmappnNodePortEntry 7 }

ibmappnNodePortMaxIframeWindow OBJECT-TYPE
      SYNTAX INTEGER
      ACCESS read-only
      STATUS mandatory
      DESCRIPTION
          "Maximum number of I-frames that can be received
           by the XID sender before an acknowledgement is received."

      ::=  { ibmappnNodePortEntry 8 }

ibmappnNodePortDefLsGoodXids    OBJECT-TYPE
    SYNTAX  Counter
    ACCESS  read-only
    STATUS  mandatory
    DESCRIPTION
            "The total number of successfull XIDs that have occurred
             on all defined link stations on this port since the last
             time this port was started."

      ::=  { ibmappnNodePortEntry 9 }

ibmappnNodePortDefLsBadXids    OBJECT-TYPE
    SYNTAX  Counter
    ACCESS  read-only
    STATUS  mandatory
    DESCRIPTION
            "The total number of unsuccessfull XIDs that have occurred
             on all defined link stations on this port since the last
             time this port was started."

      ::=  { ibmappnNodePortEntry 10 }

ibmappnNodePortDynLsGoodXids    OBJECT-TYPE
    SYNTAX  Counter
    ACCESS  read-only
    STATUS  mandatory
    DESCRIPTION
            "The total number of successfull XIDs that have occurred
             on all dynamic link stations on this port since the last
             time this port was started."

      ::=  { ibmappnNodePortEntry 11 }

ibmappnNodePortDynLsBadXids    OBJECT-TYPE
    SYNTAX  Counter
    ACCESS  read-only
    STATUS  mandatory
    DESCRIPTION
            "The total number of unsuccessfull XIDs that have occurred
             on all dynamic link stations on this port since the last
             time this port was started."

      ::=  { ibmappnNodePortEntry 12 }

ibmappnNodePortSpecific OBJECT-TYPE
      SYNTAX OBJECT IDENTIFIER
      ACCESS read-only
      STATUS mandatory
      DESCRIPTION
           "Identifies the port specific OBJECT IDENTIFIER
            that can provide additional information."

      ::=  { ibmappnNodePortEntry 13 }


-- *****************************************************************************
--
--

ibmappnNodePortIpTable OBJECT-TYPE
      SYNTAX SEQUENCE OF IbmappnNodePortIpEntry
      ACCESS not-accessible
      STATUS mandatory
      DESCRIPTION
           "Port table (TCP/IP specific)."

      ::= { ibmappnPortInformation 2 }

ibmappnNodePortIpEntry OBJECT-TYPE
      SYNTAX IbmappnNodePortIpEntry
      ACCESS not-accessible
      STATUS mandatory
      DESCRIPTION
           "The IP Name is used as the index to this table."

      INDEX
             {ibmappnNodePortIpName }

      ::= { ibmappnNodePortIpTable 1 }

IbmappnNodePortIpEntry ::= SEQUENCE {
      ibmappnNodePortIpName         DisplayString,
      ibmappnNodePortIpPortNum      INTEGER
                                   }

ibmappnNodePortIpName OBJECT-TYPE
      SYNTAX DisplayString (SIZE (1..8))
      ACCESS read-only
      STATUS mandatory
      DESCRIPTION
          "Administratively-assigned name for this APPN port.
           The name can be from one to eight characters."

      ::=  { ibmappnNodePortIpEntry 1 }

ibmappnNodePortIpPortNum OBJECT-TYPE
      SYNTAX INTEGER
      ACCESS read-only
      STATUS mandatory
      DESCRIPTION
           "Local TCP/IP port number."

      ::=  { ibmappnNodePortIpEntry 2 }


-- *****************************************************************************
--
--

ibmappnNodePortDlsTable OBJECT-TYPE
      SYNTAX SEQUENCE OF IbmappnNodePortDlsEntry
      ACCESS not-accessible
      STATUS mandatory
      DESCRIPTION
           "Port table (DLS specific)."

      ::= { ibmappnPortInformation 3 }

ibmappnNodePortDlsEntry OBJECT-TYPE
      SYNTAX IbmappnNodePortDlsEntry
      ACCESS not-accessible
      STATUS mandatory
      DESCRIPTION
           "The DLS Name is used as the index to this table."

      INDEX
             {ibmappnNodePortDlsName }
      ::= { ibmappnNodePortDlsTable 1 }

IbmappnNodePortDlsEntry ::= SEQUENCE {
      ibmappnNodePortDlsName         DisplayString,
      ibmappnNodePortDlsMac          OCTET STRING,
      ibmappnNodePortDlsSap          OCTET STRING
                                   }

ibmappnNodePortDlsName OBJECT-TYPE
      SYNTAX DisplayString (SIZE (1..8))
      ACCESS read-only
      STATUS mandatory
      DESCRIPTION
          "Administratively-assigned name for this APPN DLS port.
           The name can be from one to eight characters."

      ::=  { ibmappnNodePortDlsEntry 1 }

ibmappnNodePortDlsMac OBJECT-TYPE
      SYNTAX OCTET STRING (SIZE (6))
      ACCESS read-only
      STATUS mandatory
      DESCRIPTION
           "Local DLS MAC address."

      ::=  { ibmappnNodePortDlsEntry 2 }

ibmappnNodePortDlsSap OBJECT-TYPE
      SYNTAX OCTET STRING (SIZE (1))
      ACCESS read-only
      STATUS mandatory
      DESCRIPTION
           "Local DLS Sap address."

      ::=  { ibmappnNodePortDlsEntry 3 }


-- *****************************************************************************
--
--

ibmappnNodePortTrTable OBJECT-TYPE
      SYNTAX SEQUENCE OF IbmappnNodePortTrEntry
      ACCESS not-accessible
      STATUS mandatory
      DESCRIPTION
           "Port table (Token Ring specific)."

      ::= { ibmappnPortInformation 4 }

ibmappnNodePortTrEntry OBJECT-TYPE
      SYNTAX IbmappnNodePortTrEntry
      ACCESS not-accessible
      STATUS mandatory
      DESCRIPTION
           "The TR Name is used as the index to this table."

      INDEX
             {ibmappnNodePortTrName }
      ::= { ibmappnNodePortTrTable 1 }

IbmappnNodePortTrEntry ::= SEQUENCE {
      ibmappnNodePortTrName         DisplayString,
      ibmappnNodePortTrMac          OCTET STRING,
      ibmappnNodePortTrSap          OCTET STRING
                                   }

ibmappnNodePortTrName OBJECT-TYPE
      SYNTAX DisplayString (SIZE (1..8))
      ACCESS read-only
      STATUS mandatory
      DESCRIPTION
          "Administratively-assigned name for this APPN port.
           The name can be from one to eight characters."

      ::=  { ibmappnNodePortTrEntry 1 }

ibmappnNodePortTrMac OBJECT-TYPE
      SYNTAX OCTET STRING (SIZE (6))
      ACCESS read-only
      STATUS mandatory
      DESCRIPTION
           "Local Token Ring MAC address."

      ::=  { ibmappnNodePortTrEntry 2 }

ibmappnNodePortTrSap OBJECT-TYPE
      SYNTAX OCTET STRING (SIZE (1))
      ACCESS read-only
      STATUS mandatory
      DESCRIPTION
           "Local Token Ring Sap address."

      ::=  { ibmappnNodePortTrEntry 3 }


-- *****************************************************************************
-- APPN generic DLC Trace
--

ibmappnNodePortDlcTraceTable OBJECT-TYPE
      SYNTAX SEQUENCE OF IbmappnNodePortDlcTraceEntry
      ACCESS not-accessible
      STATUS mandatory
      DESCRIPTION
           "Port table generic DLC trace table."

      ::= { ibmappnPortInformation 5 }

ibmappnNodePortDlcTraceEntry OBJECT-TYPE
      SYNTAX IbmappnNodePortDlcTraceEntry
      ACCESS not-accessible
      STATUS mandatory
      DESCRIPTION
           "The Port name and a dynamic integer are the index to this table."

      INDEX
             {ibmappnNodePortDlcTracPortName,
              ibmappnNodePortDlcTracIndex}

      ::= { ibmappnNodePortDlcTraceTable 1 }

IbmappnNodePortDlcTraceEntry ::= SEQUENCE {
       ibmappnNodePortDlcTracPortName     DisplayString,
       ibmappnNodePortDlcTracIndex        INTEGER,
       ibmappnNodePortDlcTracDlcType      INTEGER,
       ibmappnNodePortDlcTracLocalAddr    DisplayString,
       ibmappnNodePortDlcTracRemoteAddr   DisplayString,
       ibmappnNodePortDlcTracMsgType      INTEGER,
       ibmappnNodePortDlcTracCmdType      INTEGER,
       ibmappnNodePortDlcTracUseWan       INTEGER
                                   }

ibmappnNodePortDlcTracPortName OBJECT-TYPE
      SYNTAX  DisplayString
      ACCESS read-only
      STATUS mandatory
      DESCRIPTION
            "The Port name associated with this this trace table entry."

      ::=  { ibmappnNodePortDlcTraceEntry 1 }

ibmappnNodePortDlcTracIndex OBJECT-TYPE
      SYNTAX INTEGER
      ACCESS read-only
      STATUS mandatory
      DESCRIPTION
            "This index value is updated every time a new trace entry
             is created which provides a means to retrieve only the
             updated entries and also provides a simple method of
             correlating the entries.  The table will wrap when the
             table is full, which will result in previous entries being
             written over.  The mangement station can over come this by
             retrieving the table using this index to retrieve only the
             new table entries."

      ::=  { ibmappnNodePortDlcTraceEntry 2 }

ibmappnNodePortDlcTracDlcType OBJECT-TYPE
      SYNTAX INTEGER {
                      other(1),          -- none of the following
                      sdlc(2),
                      dls(3),
                      socket(4),
                      ethernet(5),
                      tokenRing(6)
                     }
          ACCESS  read-only
          STATUS  mandatory
          DESCRIPTION
                  "The type of DLC interface, distinguished according to
                  the protocol immediately 'below' this layer."

      ::=  { ibmappnNodePortDlcTraceEntry 3 }

ibmappnNodePortDlcTracLocalAddr OBJECT-TYPE
      SYNTAX DisplayString
      ACCESS read-only
      STATUS mandatory
      DESCRIPTION
           "Local address in format described below:

           other    = free form DisplayString
           ip       = ld.ld.ld.ld/2d
           tr       = lx:lx:lx:lx:lx:lx.lx
           dlsw     = lx:lx:lx:lx:lx:lx.lx
           ethernet = lx:lx:lx:lx:lx:lx.lx
           "

      ::=  { ibmappnNodePortDlcTraceEntry 4 }


ibmappnNodePortDlcTracRemoteAddr OBJECT-TYPE
      SYNTAX DisplayString
      ACCESS read-only
      STATUS mandatory
      DESCRIPTION
           "Remote Address in the format described below:

           other    = free form DisplayString
           ip       = ld.ld.ld.ld/2d
           tr       = lx:lx:lx:lx:lx:lx.lx
           dlsw     = lx:lx:lx:lx:lx:lx.lx
           ethernet = lx:lx:lx:lx:lx:lx.lx
           "

      ::=  { ibmappnNodePortDlcTraceEntry 5 }


ibmappnNodePortDlcTracMsgType OBJECT-TYPE
      SYNTAX INTEGER    {
--              enumeration values between 1 and 1999 are reserved for
--              potential undefined message types.
                         other(1),
                         unknown(2),
                         request(3),
                         confirm(4),
                         indication(5),
                         response(6)

--              enumeration values between 2000 and 3999 are reserved for
--              IP socket traces,



--              enumeration values between 4000 and 5999 are reserved for
--              DLS traces,



--              enumeration values between 6000 and 7999 are reserved for
--              TR  traces,


                         }
      ACCESS read-only
      STATUS mandatory
      DESCRIPTION
            "Indicates the type of trace record entry"

      ::=  { ibmappnNodePortDlcTraceEntry 6 }

ibmappnNodePortDlcTracCmdType OBJECT-TYPE
      SYNTAX INTEGER    {
--              enumeration values between 1 and 1999 are reserved for
--              potential undefined message types.

                         testFrame(1),
                         respFrame(2),
                         curFrame(3),
                         icrFrame(4),
                         respAck(5),
                         dgrmFrame(6),
                         xidFrame(7),
                         contFrame(8),
                         contedFrame(9),
                         iFrame(10),
                         enterBusy(12),
                         exitBusy(13),
                         haltFrame(14),
                         lsHalted(15),
                         restartLs(16),
                         lsRestarted(17),
                         netBioSnq(18),
                         netBioSnr(19),
                         gnetFrame(20),
                         netdFrame(21),
                         oobFrame(22),
                         alterSap(23),
                         testRsp(24),
                         haltLsNow(25),
                         netBioAnq(26),
                         netBioAnr(27),
                         mibLsFrame(28),
                         iamOkay(29),

--              enumeration values between 2000 and 3999 are reserved for
--              IP socket traces.
                         ipTestFrame(2001),
                         ipRespFrame(2002),
                         ipCurFrame(2003),
                         ipIcrFrame(2004),
                         ipRespAck(2005),
                         ipDgrmFrame(2006),
                         ipXidFrame(2007),
                         ipContFrame(2008),
                         ipContedFrame(2009),
                         ipIFrame(2010),
                         ipEnterBusy(2012),
                         ipExitBusy(2013),
                         ipHaltFrame(2014),
                         ipLsHalted(2015),
                         ipRestartLs(2016),
                         ipLsRestarted(2017),
                         ipNetBioSnq(2018),
                         ipNetBioSnr(2019),
                         ipGnetFrame(2020),
                         ipNetdFrame(2021),
                         ipOobFrame(2022),
                         ipAlterSap(2023),
                         ipTestRsp(2024),
                         ipHaltLsNow(2025),
                         ipNetBioAnq(2026),
                         ipNetBioAnr(2027),
                         ipMibLsFrame(2028),
                         ipIamOkay(2029),

--              enumeration values between 4000 and 5999 are reserved for
--              DLS traces.

                         dlsTestReq(4122),
                         dlsTestRsp(4123),
                         dlsIpm(4124),

--              enumeration values between 6000 and 7999 are reserved for
--              TR traces.
                         trTestFrame(6001),
                         trRespFrame(6002),
                         trCurFrame(6003),
                         trIcrFrame(6004),
                         trRespAck(6005),
                         trDgrmFrame(6006),
                         trXidFrame(6007),
                         trContFrame(6008),
                         trContedFrame(6009),
                         trIFrame(6010),
                         trEnterBusy(6012),
                         trExitBusy(6013),
                         trHaltFrame(6014),
                         trLsHalted(6015),
                         trRestartLs(6016),
                         trLsRestarted(6017),
                         trNetBioSnq(6018),
                         trNetBioSnr(6019),
                         trGnetFrame(6020),
                         trNetdFrame(6021),
                         trOobFrame(6022),
                         trAlterSap(6023),
                         trTestRsp(6024),
                         trHaltLsNow(6025),
                         trNetBioAnq(6026),
                         trNetBioAnr(6027),
                         trMibLsFrame(6028),
                         trIamOkay(6029)

                         }
      ACCESS read-only
      STATUS mandatory
      DESCRIPTION
            "Indicates the command type of the trace entry."

      ::=  { ibmappnNodePortDlcTraceEntry 7 }

ibmappnNodePortDlcTracUseWan OBJECT-TYPE
      SYNTAX INTEGER    {
                         other(1),
                         notApplicable(2),
                         useUnknown(3),
                         useWan(4),
                         useLan(5)
                         }
      ACCESS read-only
      STATUS mandatory
      DESCRIPTION
            "    "
      ::=  { ibmappnNodePortDlcTraceEntry 8 }


-- *****************************************************************************
-- APPN Link Station Information
--

ibmappnNodeLsTable OBJECT-TYPE
      SYNTAX SEQUENCE OF IbmappnNodeLsEntry
      ACCESS not-accessible
      STATUS mandatory
      DESCRIPTION
           "This table contains detail information about the
            link station configuration and current status."

      ::= { ibmappnLinkStationInformation 1 }

ibmappnNodeLsEntry OBJECT-TYPE
      SYNTAX IbmappnNodeLsEntry
      ACCESS not-accessible
      STATUS mandatory
      DESCRIPTION
           "This table is indexed by the link station name."

      INDEX
             { ibmappnNodeLsName }

      ::= { ibmappnNodeLsTable 1 }

IbmappnNodeLsEntry ::= SEQUENCE {
      ibmappnNodeLsName             DisplayString,
      ibmappnNodeLsPortName         DisplayString,
      ibmappnNodeLsDlcType          INTEGER,
      ibmappnNodeLsDynamic          INTEGER,
      ibmappnNodeLsState            INTEGER,
-- ls_defined_data_t / xid_info_t
      ibmappnNodeLsCpName           DisplayString,
      ibmappnNodeLsTgNum            INTEGER,
      ibmappnNodeLsLimResource      INTEGER,
      ibmappnNodeLsMigration        INTEGER,
      ibmappnNodeLsBlockNum         DisplayString,
      ibmappnNodeLsIdNum            DisplayString,
      ibmappnNodeLsCpCpSession      INTEGER,
-- ls_parms_t (common) / xid_info_t
      ibmappnNodeLsTargetPacingCount INTEGER,
      ibmappnNodeLsMaxSendBtuSize    INTEGER,
-- tg_characteristics_t
      ibmappnNodeLsEffCap           INTEGER,
      ibmappnNodeLsConnCost         INTEGER,
      ibmappnNodeLsByteCost         INTEGER,
      ibmappnNodeLsSecurity         INTEGER,
      ibmappnNodeLsDelay            INTEGER,
      ibmappnNodeLsUsr1             INTEGER,
      ibmappnNodeLsUsr2             INTEGER,
      ibmappnNodeLsUsr3             INTEGER,
-- ls_cb_t (performance data)
      ibmappnNodeLsInXidBytes       Counter,
      ibmappnNodeLsInMsgBytes       Counter,
      ibmappnNodeLsInXidFrames      Counter,
      ibmappnNodeLsInMsgFrames      Counter,
      ibmappnNodeLsOutXidBytes      Counter,
      ibmappnNodeLsOutMsgBytes      Counter,
      ibmappnNodeLsOutXidFrames     Counter,
      ibmappnNodeLsOutMsgFrames     Counter,
-- ls_cb_xx (propgation delay)
      ibmappnNodeLsEchoRsps         Counter,
      ibmappnNodeLsCurrentDelay     INTEGER,
      ibmappnNodeLsMaxDelay         INTEGER,
      ibmappnNodeLsMinDelay         INTEGER,
      ibmappnNodeLsMaxDelayTime     TimeTicks,
-- ls_cb_t (Xid Statistics)
      ibmappnNodeLsGoodXids         Counter,
      ibmappnNodeLsBadXids          Counter,
-- Dlc specific
      ibmappnNodeLsSpecific         OBJECT IDENTIFIER,
      ibmappnNodeLsSubState         INTEGER,
      ibmappnNodeLsStartTime        TimeTicks,
      ibmappnNodeLsActiveTime       TimeTicks,
      ibmappnNodeLsCurrentStateTime TimeTicks
                                   }


ibmappnNodeLsName OBJECT-TYPE
      SYNTAX DisplayString (SIZE (1..8))
      ACCESS read-only
      STATUS mandatory
      DESCRIPTION
          "Administratively-assigned name for the link station.
           The name can be from one to eight characters."

      ::=  { ibmappnNodeLsEntry 1 }

ibmappnNodeLsPortName OBJECT-TYPE
      SYNTAX DisplayString (SIZE (1..8))
      ACCESS read-only
      STATUS mandatory
      DESCRIPTION
          "Administratively-assigned name for the port.
           The name can be from one to eight characters."

      ::=  { ibmappnNodeLsEntry 2 }


ibmappnNodeLsDlcType OBJECT-TYPE
      SYNTAX INTEGER {
                      other(1),          -- none of the following
                      sdlc(2),
                      dls(3),
                      socket(4),
                      ethernet(5),
                      tokenRing(6)
                     }
          ACCESS  read-only
          STATUS  mandatory
          DESCRIPTION
                  "The type of DLC interface, distinguished according to
                  the protocol immediately 'below' this layer."

      ::=  { ibmappnNodeLsEntry 3 }

ibmappnNodeLsDynamic  OBJECT-TYPE
      SYNTAX INTEGER {yes(1), no(2)}
      ACCESS read-only
      STATUS mandatory
      DESCRIPTION
          "Identifies whether this resource is a dynamic link station.
          Dynamic link stations are created when adjacent nodes
          that have not been locally defined establish a connection
          with this node."

      ::=  { ibmappnNodeLsEntry 4 }


ibmappnNodeLsState        OBJECT-TYPE
      SYNTAX INTEGER    {
                         inactive(1),
                         pendactive(2),
                         active(3),
                         pendinact(4)
                         }
      ACCESS read-write
      STATUS mandatory
      DESCRIPTION
           "State of this link station."

      ::=  { ibmappnNodeLsEntry 5 }

ibmappnNodeLsCpName       OBJECT-TYPE
      SYNTAX DisplayString (SIZE (3..17))
      ACCESS read-only
      STATUS mandatory
      DESCRIPTION
          "Fully-qualified name of the adjacent node for this link
           station.  The name can be from three to seventeen characters.
           Format is netid.cpname."

      ::=  { ibmappnNodeLsEntry 6 }

ibmappnNodeLsTgNum        OBJECT-TYPE
      SYNTAX INTEGER
      ACCESS read-only
      STATUS mandatory
      DESCRIPTION
          "Number associated with the TG to this link station."

      ::=  { ibmappnNodeLsEntry 7 }

ibmappnNodeLsLimResource  OBJECT-TYPE
      SYNTAX INTEGER {yes(1), no(2)}
      ACCESS read-only
      STATUS mandatory
      DESCRIPTION
           "Indicates whether the link station is
           a limited resource.  If it is, the TG
           is deactivated when there are no sessions."

      ::=  { ibmappnNodeLsEntry 8 }

ibmappnNodeLsMigration  OBJECT-TYPE
      SYNTAX INTEGER {yes(1), no(2)}
      ACCESS read-only
      STATUS mandatory
      DESCRIPTION
           "Indicates whether this link station will be used
            for connections to down-level or migration partners."

      ::=  { ibmappnNodeLsEntry 9 }

ibmappnNodeLsBlockNum OBJECT-TYPE
      SYNTAX DisplayString   (SIZE (3))
      ACCESS read-only
      STATUS mandatory
      DESCRIPTION
         "The block number is the first three digits of the node_id.
          These 3 hexideimal digits identify the product and are not
          configurable."

      ::=  { ibmappnNodeLsEntry 10 }

ibmappnNodeLsIdNum OBJECT-TYPE
      SYNTAX DisplayString  (SIZE (5))
      ACCESS read-only
      STATUS mandatory
      DESCRIPTION
         "The ID number is the last 5 digits of the node_id.
          These 5 hexadecimal digits are administratively defined and
          combined with the 3 digit block number form the node_id.
          This node_id is used to identify the local node and is include
          in APPN alerts as well as being included in XIDs.  A unique
          value is required for connections to SNA sub-area."

      ::=  { ibmappnNodeLsEntry 11 }

ibmappnNodeLsCpCpSession  OBJECT-TYPE
      SYNTAX INTEGER {yes(1), no(2)}
      ACCESS read-only
      STATUS mandatory
      DESCRIPTION
          "Indicates whether CP-CP sessions are
          supported by this link station."

      ::=  { ibmappnNodeLsEntry 12 }

ibmappnNodeLsTargetPacingCount  OBJECT-TYPE
      SYNTAX INTEGER
      ACCESS read-only
      STATUS mandatory
      DESCRIPTION
           "Numeric value between 0 and 32767 inclusive indicating
            the desired pacing window size for BINDs on this TG.
            The number is significant only when fixed bind pacing
            is being performed."

      ::=  { ibmappnNodeLsEntry 13 }

ibmappnNodeLsMaxSendBtuSize  OBJECT-TYPE
      SYNTAX INTEGER
      ACCESS read-only
      STATUS mandatory
      DESCRIPTION
           "Numeric value between 0 and 32767 inclusive indicating
            the desired number of bytes in a Basic Transmission Unit
            (BTU) that can be sent on this TG.
            This is an administratively assigned value."

      ::=  { ibmappnNodeLsEntry 14 }

ibmappnNodeLsEffCap   OBJECT-TYPE
      SYNTAX INTEGER
      ACCESS read-only
      STATUS mandatory
      DESCRIPTION
          "The effective capacity is an integer value that indicates
           the kilo bits per second.
           It is derived from the link bandwidth and maximum load
           factor with the range of 0 thru 603,979,776.
           This is an administratively assigned value associated
           with the TG using this link station."

      ::=  { ibmappnNodeLsEntry 15 }

ibmappnNodeLsConnCost OBJECT-TYPE
      SYNTAX INTEGER (0..255)
      ACCESS read-only
      STATUS mandatory
      DESCRIPTION
          "Cost per connect time: a value representing
           the relative cost per unit of time to use
           the TG. Range is from 0, which means no cost,
           to 255, which indicates maximum cost.
           This is an administratively assigned value associated
           with the TG using this link station."

      ::=  { ibmappnNodeLsEntry 16 }

ibmappnNodeLsByteCost  OBJECT-TYPE
      SYNTAX INTEGER (0..255)
      ACCESS read-only
      STATUS mandatory
      DESCRIPTION
          "Relative cost of transmitting a byte over this link.
           Range is from 0 (lowest cost) to 255.
           This is an administratively assigned value associated
           with the TG using this link station."

      ::=  { ibmappnNodeLsEntry 17 }

ibmappnNodeLsSecurity  OBJECT-TYPE
      SYNTAX INTEGER {
                     nonsecure(1),                --X'01'
                     publicSwitchedNetwork(32),   --X'20'
                     undergroundCable(64),        --X'40'
                     secureConduit(96),           --X'60'
                     guardedConduit(128),         --X'80'
                     encrypted(160),              --X'A0'
                     guardedRadiation(192)        --X'C0'
             }
      ACCESS read-only
      STATUS mandatory
      DESCRIPTION
          "The security is represented as an integer with a range of
           1 thru 255 with the most common values enumerated as
           defined above.
           This is an administratively assigned value associated
           with the TG using this link station."

      ::=  { ibmappnNodeLsEntry 18 }

ibmappnNodeLsDelay  OBJECT-TYPE
      SYNTAX INTEGER {
                     minimum(1),                 --X'00'
                     negligible(384),            --X'4C'
                     terrestrial(9216),          --X'71'
                     packet(147456),             --X'91'
                     long(294912),               --X'99'
                     maximum(2013265920)         --X'FF'
             }
      ACCESS read-only
      STATUS mandatory
      DESCRIPTION
           "Relative amount of time that it takes for a signal to
            travel the length of the logical link.  This time is
            represented in micro seconds, with some of the more
            common values enumerated.
            This is an administratively assigned value associated
            with the TG using this link station."

      ::=  { ibmappnNodeLsEntry 19 }

ibmappnNodeLsUsr1  OBJECT-TYPE
      SYNTAX INTEGER (0..255)
      ACCESS read-only
      STATUS mandatory
      DESCRIPTION
          "First user-defined TG characteristic for this TG with
           a range of 0-255.
           This is an administratively assigned value associated
           with the TG using this link station."

      ::=  { ibmappnNodeLsEntry 20 }

ibmappnNodeLsUsr2  OBJECT-TYPE
      SYNTAX INTEGER (0..255)
      ACCESS read-only
      STATUS mandatory
      DESCRIPTION
          "Second user-defined TG characteristic for this TG with
           a range of 0-255.
           This is an administratively assigned value associated
           with the TG using this link station."

      ::=  { ibmappnNodeLsEntry 21 }

ibmappnNodeLsUsr3  OBJECT-TYPE
      SYNTAX INTEGER (0..255)
      ACCESS read-only
      STATUS mandatory
      DESCRIPTION
          "Third user-defined TG characteristic for this TG with
           a range of 0-255.
           This is an administratively assigned value associated
           with the TG using this link station."

      ::=  { ibmappnNodeLsEntry 22 }

ibmappnNodeLsInXidBytes OBJECT-TYPE
      SYNTAX Counter
      ACCESS read-only
      STATUS mandatory
      DESCRIPTION
           "Number of XID bytes received."

      ::=  { ibmappnNodeLsEntry 23 }

ibmappnNodeLsInMsgBytes OBJECT-TYPE
      SYNTAX Counter
      ACCESS read-only
      STATUS mandatory
      DESCRIPTION
           "Number of message (I-frame) bytes received."

      ::=  { ibmappnNodeLsEntry 24 }

ibmappnNodeLsInXidFrames OBJECT-TYPE
      SYNTAX Counter
      ACCESS read-only
      STATUS mandatory
      DESCRIPTION
           "Number of XID frames received."

      ::=  { ibmappnNodeLsEntry 25 }

ibmappnNodeLsInMsgFrames OBJECT-TYPE
      SYNTAX Counter
      ACCESS read-only
      STATUS mandatory
      DESCRIPTION
           "Number of message (I-frame) frames received."

      ::=  { ibmappnNodeLsEntry 26 }

ibmappnNodeLsOutXidBytes OBJECT-TYPE
      SYNTAX Counter
      ACCESS read-only
      STATUS mandatory
      DESCRIPTION
           "Number of XID bytes sent."

      ::=  { ibmappnNodeLsEntry 27 }

ibmappnNodeLsOutMsgBytes OBJECT-TYPE
      SYNTAX Counter
      ACCESS read-only
      STATUS mandatory
      DESCRIPTION
           "Number of message (I-frame) bytes sent."

      ::=  { ibmappnNodeLsEntry 28 }

ibmappnNodeLsOutXidFrames OBJECT-TYPE
      SYNTAX Counter
      ACCESS read-only
      STATUS mandatory
      DESCRIPTION
           "Number of XID frames sent."

      ::=  { ibmappnNodeLsEntry 29 }

ibmappnNodeLsOutMsgFrames OBJECT-TYPE
      SYNTAX Counter
      ACCESS read-only
      STATUS mandatory
      DESCRIPTION
           "Number of message (I-frame) frames sent."

      ::=  { ibmappnNodeLsEntry 30 }

ibmappnNodeLsEchoRsps     OBJECT-TYPE
      SYNTAX Counter
      ACCESS read-only
      STATUS mandatory
      DESCRIPTION
           "Number of responses returned from adjacent link station.
            A response should be returned for each test frame sent by
            this node.
            Test frames are sent to adjacent nodes periodically to
            verify connectivity and to measure that actual round trip
            time, that is the time the test frame is sent until the
            response is received."


      ::=  { ibmappnNodeLsEntry 31 }

ibmappnNodeLsCurrentDelay  OBJECT-TYPE
      SYNTAX INTEGER
      ACCESS read-only
      STATUS mandatory
      DESCRIPTION
           "The time that it took for the last test signal to be
            sent and returned from this link station to the
            adjacent links station.
            This time is represented in milliseconds."

      ::=  { ibmappnNodeLsEntry 32 }

ibmappnNodeLsMaxDelay      OBJECT-TYPE
      SYNTAX INTEGER
      ACCESS read-only
      STATUS mandatory
      DESCRIPTION
           "The longest time it took for a test signal
            to be sent and returned from this link station to the
            adjacent links station.
            This time is represented in milliseconds ."

      ::=  { ibmappnNodeLsEntry 33 }

ibmappnNodeLsMinDelay      OBJECT-TYPE
      SYNTAX INTEGER
      ACCESS read-only
      STATUS mandatory
      DESCRIPTION
           "The shortest time it took for a test signal
            to be sent and returned from this link station to the
            adjacent links station.
            This time is represented in milliseconds."

      ::=  { ibmappnNodeLsEntry 34 }

ibmappnNodeLsMaxDelayTime  OBJECT-TYPE
      SYNTAX TimeTicks
      ACCESS read-only
      STATUS mandatory
      DESCRIPTION
           "The time (since system up in hundredth of seconds)
            when the longest delay occurred.
            This time can be used to identify when this high
            water mark occurred in relation to the last initialization
            of the APPN node."

      ::=  { ibmappnNodeLsEntry 35 }

ibmappnNodeLsGoodXids    OBJECT-TYPE
    SYNTAX  Counter
    ACCESS  read-only
    STATUS  mandatory
    DESCRIPTION
            "The total number of successful XIDs that have occurred
             on this link station since the time it was started."

      ::=  { ibmappnNodeLsEntry 36 }

ibmappnNodeLsBadXids    OBJECT-TYPE
    SYNTAX  Counter
    ACCESS  read-only
    STATUS  mandatory
    DESCRIPTION
            "The total number of unsuccessful XIDs that have occurred
             on this link station since the time it was started."

      ::=  { ibmappnNodeLsEntry 37 }

ibmappnNodeLsSpecific  OBJECT-TYPE
      SYNTAX OBJECT IDENTIFIER
      ACCESS read-only
      STATUS mandatory
      DESCRIPTION
           "Identifies the DLC specific OBJECT IDENTIFIER
            that can provide additional information."

      ::=  { ibmappnNodeLsEntry 38 }

ibmappnNodeLsSubState     OBJECT-TYPE
      SYNTAX INTEGER    {
                         inactive(1),
                         sentReqOpnstn(2),
                         pendXidExch(3),
                         sentActAs(4),
                         sentSetMode(5),
                         active(6),
                         sentDeactAsOrd(7),
                         sentDiscOrd(8),
                         sentDestroyTg(9),
                         sentCreateTg(10),
                         sentConnReq(11),
                         pendRcvConnInd(12),
                         pendSendConnRsp(13),
                         sentConnRsp(14),
                         pendDeact(15)
                         }
      ACCESS read-only
      STATUS mandatory
      DESCRIPTION
           "State of this link station."

      ::=  { ibmappnNodeLsEntry 39 }

ibmappnNodeLsStartTime     OBJECT-TYPE
      SYNTAX TimeTicks
      ACCESS read-only
      STATUS mandatory
      DESCRIPTION
           "The time (in hundredth of seconds) this link station
            has been active the last time since the time APPN was
            initialized."

      ::=  { ibmappnNodeLsEntry 40 }

ibmappnNodeLsActiveTime    OBJECT-TYPE
      SYNTAX TimeTicks
      ACCESS read-only
      STATUS mandatory
      DESCRIPTION
           "The time (in hundredth of seconds) this link station
            has been in the active state.
            A zero value indicates the link station has never been
            active."

      ::=  { ibmappnNodeLsEntry 41 }

ibmappnNodeLsCurrentStateTime  OBJECT-TYPE
      SYNTAX TimeTicks
      ACCESS read-only
      STATUS mandatory
      DESCRIPTION
           "The time (in hundredth of seconds) the link station is
            in the current state."

      ::=  { ibmappnNodeLsEntry 42 }

-- *****************************************************************************
--
--

ibmappnNodeLsIpTable OBJECT-TYPE
      SYNTAX SEQUENCE OF IbmappnNodeLsIpEntry
      ACCESS not-accessible
      STATUS mandatory
      DESCRIPTION
          "Link station table (TCP/IP specific)."

      ::= { ibmappnLinkStationInformation 2 }

ibmappnNodeLsIpEntry OBJECT-TYPE
      SYNTAX IbmappnNodeLsIpEntry
      ACCESS not-accessible
      STATUS mandatory
      DESCRIPTION
           "The IP Name is used as the index to this table."

      INDEX
             {ibmappnNodeLsIpName }
      ::= { ibmappnNodeLsIpTable 1 }

IbmappnNodeLsIpEntry ::= SEQUENCE {
      ibmappnNodeLsIpName             DisplayString,
      ibmappnNodeLsIpState            INTEGER,
      ibmappnNodeLsLocalIpAddr        IpAddress,
      ibmappnNodeLsLocalIpPortNum     INTEGER,
      ibmappnNodeLsRemoteIpAddr       IpAddress,
      ibmappnNodeLsRemoteIpPortNum    INTEGER
                                   }

ibmappnNodeLsIpName OBJECT-TYPE
      SYNTAX DisplayString (SIZE (1..8))
      ACCESS read-only
      STATUS mandatory
      DESCRIPTION
          "Administratively-assigned name for this link station. The
           name can be from one to eight characters."

      ::=  { ibmappnNodeLsIpEntry 1 }

ibmappnNodeLsIpState        OBJECT-TYPE
      SYNTAX INTEGER    {
                         inactive(1),
                         pendactive(2),
                         active(3),
                         pendinact(4)
                         }
      ACCESS read-only
      STATUS mandatory
      DESCRIPTION
           "State of this link station."

      ::=  { ibmappnNodeLsIpEntry 2 }

ibmappnNodeLsLocalIpAddr OBJECT-TYPE
      SYNTAX IpAddress
      ACCESS read-only
      STATUS mandatory
      DESCRIPTION
           "Local IP address."

      ::=  { ibmappnNodeLsIpEntry 3 }

ibmappnNodeLsLocalIpPortNum OBJECT-TYPE
      SYNTAX INTEGER
      ACCESS read-only
      STATUS mandatory
      DESCRIPTION
           "Local TCP/IP port number.
            The default listening port will be administratively
            assigned and will dynamically change if this node
            initiates a session with adjacent node."

      ::=  { ibmappnNodeLsIpEntry 4 }



ibmappnNodeLsRemoteIpAddr OBJECT-TYPE
      SYNTAX IpAddress
      ACCESS read-only
      STATUS mandatory
      DESCRIPTION
           "Remote IP address."

      ::=  { ibmappnNodeLsIpEntry 5 }

ibmappnNodeLsRemoteIpPortNum OBJECT-TYPE
      SYNTAX INTEGER
      ACCESS read-only
      STATUS mandatory
      DESCRIPTION
           "Remote TCP/IP port number."

      ::=  { ibmappnNodeLsIpEntry 6 }


-- *****************************************************************************
--
--

ibmappnNodeLsDlsTable OBJECT-TYPE
      SYNTAX SEQUENCE OF IbmappnNodeLsDlsEntry
      ACCESS not-accessible
      STATUS mandatory
      DESCRIPTION
           "Ls Table (DLS specific)."

      ::= { ibmappnLinkStationInformation 3 }

ibmappnNodeLsDlsEntry OBJECT-TYPE
      SYNTAX IbmappnNodeLsDlsEntry
      ACCESS not-accessible
      STATUS mandatory
      DESCRIPTION
           "The DLS Name is used as the index to this table."

      INDEX
             {ibmappnNodeLsDlsName }
      ::= { ibmappnNodeLsDlsTable 1 }

IbmappnNodeLsDlsEntry ::= SEQUENCE {
      ibmappnNodeLsDlsName            DisplayString,
      ibmappnNodeLsDlsState           INTEGER,
      ibmappnNodeLsLocalDlsMac        OCTET STRING,
      ibmappnNodeLsLocalDlsSap        OCTET STRING,
      ibmappnNodeLsRemoteDlsMac       OCTET STRING,
      ibmappnNodeLsRemoteDlsSap       OCTET STRING
                                   }

ibmappnNodeLsDlsName OBJECT-TYPE
      SYNTAX DisplayString (SIZE (1..8))
      ACCESS read-only
      STATUS mandatory
      DESCRIPTION
          "Administratively-assigned name for this link station.
           The name can be from one to eight characters."

      ::=  { ibmappnNodeLsDlsEntry 1 }

ibmappnNodeLsDlsState        OBJECT-TYPE
      SYNTAX INTEGER    {
                         inactive(1),
                         pendactive(2),
                         active(3),
                         pendinact(4)
                         }
      ACCESS read-only
      STATUS mandatory
      DESCRIPTION
           "State of this link station."

      ::=  { ibmappnNodeLsDlsEntry 2 }

ibmappnNodeLsLocalDlsMac OBJECT-TYPE
      SYNTAX OCTET STRING (SIZE (6))
      ACCESS read-only
      STATUS mandatory
      DESCRIPTION
           "Local MAC address."

      ::=  { ibmappnNodeLsDlsEntry 3 }

ibmappnNodeLsLocalDlsSap OBJECT-TYPE
      SYNTAX OCTET STRING (SIZE (1))
      ACCESS read-only
      STATUS mandatory
      DESCRIPTION
           "Local SAP address."

      ::=  { ibmappnNodeLsDlsEntry 4 }

ibmappnNodeLsRemoteDlsMac OBJECT-TYPE
      SYNTAX OCTET STRING (SIZE (6))
      ACCESS read-only
      STATUS mandatory
      DESCRIPTION
           "Remote MAC address."

      ::=  { ibmappnNodeLsDlsEntry 5 }

ibmappnNodeLsRemoteDlsSap OBJECT-TYPE
      SYNTAX OCTET STRING (SIZE (1))
      ACCESS read-only
      STATUS mandatory
      DESCRIPTION
           "Remote SAP address."

      ::=  { ibmappnNodeLsDlsEntry 6 }


-- *****************************************************************************
--
--

ibmappnNodeLsTrTable OBJECT-TYPE
      SYNTAX SEQUENCE OF IbmappnNodeLsTrEntry
      ACCESS not-accessible
      STATUS mandatory
      DESCRIPTION
           "Ls Table (Token Ring specific)."

      ::= { ibmappnLinkStationInformation 4 }

ibmappnNodeLsTrEntry OBJECT-TYPE
      SYNTAX IbmappnNodeLsTrEntry
      ACCESS not-accessible
      STATUS mandatory
      DESCRIPTION
           "The TR Name is used as the index to this table."

      INDEX
             {ibmappnNodeLsTrName }
      ::= { ibmappnNodeLsTrTable 1 }

IbmappnNodeLsTrEntry ::= SEQUENCE {
      ibmappnNodeLsTrName            DisplayString,
      ibmappnNodeLsTrState           INTEGER,
      ibmappnNodeLsLocalTrMac        OCTET STRING,
      ibmappnNodeLsLocalTrSap        OCTET STRING,
      ibmappnNodeLsRemoteTrMac       OCTET STRING,
      ibmappnNodeLsRemoteTrSap       OCTET STRING
                                   }

ibmappnNodeLsTrName OBJECT-TYPE
      SYNTAX DisplayString (SIZE (1..8))
      ACCESS read-only
      STATUS mandatory
      DESCRIPTION
          "Administratively-assigned name for this link station.
           The name can be from one to eight characters."

      ::=  { ibmappnNodeLsTrEntry 1 }

ibmappnNodeLsTrState        OBJECT-TYPE
      SYNTAX INTEGER    {
                         inactive(1),
                         pendactive(2),
                         active(3),
                         pendinact(4)
                         }
      ACCESS read-only
      STATUS mandatory
      DESCRIPTION
           "State of this link station."

      ::=  { ibmappnNodeLsTrEntry 2 }

ibmappnNodeLsLocalTrMac OBJECT-TYPE
      SYNTAX OCTET STRING (SIZE (6))
      ACCESS read-only
      STATUS mandatory
      DESCRIPTION
           "Local MAC address."

      ::=  { ibmappnNodeLsTrEntry 3 }

ibmappnNodeLsLocalTrSap OBJECT-TYPE
      SYNTAX OCTET STRING (SIZE (1))
      ACCESS read-only
      STATUS mandatory
      DESCRIPTION
           "Local SAP address."

      ::=  { ibmappnNodeLsTrEntry 4 }

ibmappnNodeLsRemoteTrMac OBJECT-TYPE
      SYNTAX OCTET STRING (SIZE (6))
      ACCESS read-only
      STATUS mandatory
      DESCRIPTION
           "Remote MAC address."

      ::=  { ibmappnNodeLsTrEntry 5 }

ibmappnNodeLsRemoteTrSap OBJECT-TYPE
      SYNTAX OCTET STRING (SIZE (1))
      ACCESS read-only
      STATUS mandatory
      DESCRIPTION
           "Remote SAP address."

      ::=  { ibmappnNodeLsTrEntry 6 }

--********************************************************************
-- This table provides information about errors this node encountered
-- with connections to adjacent nodes.  This includes all exceptional
-- conditions encountered establishing connections and all exceptional
-- conditions that result in terminating the connection.
--********************************************************************

ibmappnNodeLsStatusTable OBJECT-TYPE
      SYNTAX SEQUENCE OF IbmappnNodeLsStatusEntry
      ACCESS not-accessible
      STATUS mandatory
      DESCRIPTION
           "This table contains information related to exceptional
            and potential exceptional conditions that occur during
            the activation, XID exchange, and termination of the
            connection."

      ::= { ibmappnLinkStationInformation 5 }

ibmappnNodeLsStatusEntry OBJECT-TYPE
      SYNTAX IbmappnNodeLsStatusEntry
      ACCESS not-accessible
      STATUS mandatory
      DESCRIPTION
           "This table is indexed by the LsStatusIndex, which is an
            integer that is continuously updated until it eventually
            wraps.  This provides the management station the ability
            to retrieve only the updates to the table by using the
            standard GET NEXT."

      INDEX
             { ibmappnNodeLsStatusIndex }

      ::= { ibmappnNodeLsStatusTable 1 }

IbmappnNodeLsStatusEntry ::= SEQUENCE {
      ibmappnNodeLsStatusIndex              INTEGER,
      ibmappnNodeLsStatusTime               TimeTicks,
      ibmappnNodeLsStatusLsName             DisplayString,
      ibmappnNodeLsStatusCpName             DisplayString,
      ibmappnNodeLsStatusNodeId             OCTET STRING,
      ibmappnNodeLsStatusTgNum              INTEGER,
      ibmappnNodeLsStatusGeneralSense       OCTET STRING,
      ibmappnNodeLsStatusNofRetry           INTEGER,
      ibmappnNodeLsStatusEndSense           OCTET STRING,
      ibmappnNodeLsStatusXidLocalSense      OCTET STRING,
      ibmappnNodeLsStatusXidRemoteSense     OCTET STRING,
      ibmappnNodeLsStatusXidByteInError     INTEGER,
      ibmappnNodeLsStatusXidBitInError      INTEGER,
      ibmappnNodeLsStatusDlcType            INTEGER,
      ibmappnNodeLsStatusLocalAddr          DisplayString,
      ibmappnNodeLsStatusRemoteAddr         DisplayString
                                   }


ibmappnNodeLsStatusIndex       OBJECT-TYPE
      SYNTAX INTEGER
      ACCESS read-only
      STATUS mandatory
      DESCRIPTION
          "Table index.  The value of the index begins at zero
           and is incremented up to a maximum value of 2**31-1
           (2,147,483,647) before wrapping."

      ::=  { ibmappnNodeLsStatusEntry 1 }

ibmappnNodeLsStatusTime    OBJECT-TYPE
      SYNTAX TimeTicks
      ACCESS read-only
      STATUS mandatory
      DESCRIPTION
          "Time (in hundreds of a second) since this node was last
           initialized."

      ::=  { ibmappnNodeLsStatusEntry 2 }


ibmappnNodeLsStatusLsName       OBJECT-TYPE
      SYNTAX DisplayString (SIZE (3..17))
      ACCESS read-only
      STATUS mandatory
      DESCRIPTION
          "Administratively-assigned name for this link station."


      ::=  { ibmappnNodeLsStatusEntry 3 }

ibmappnNodeLsStatusCpName    OBJECT-TYPE
      SYNTAX DisplayString (SIZE (3..18))
      ACCESS read-only
      STATUS mandatory
      DESCRIPTION
          "Administratively-assigned fully-qualified name of the
           adjacent node partner.  This will be provided when the
           adjacent node has been defined at this node or when the
           XID sequence has proceeded far enough to to identify the
           adjacent node.  A blank CP name will indicate the name is
           unknown."

      ::=  { ibmappnNodeLsStatusEntry 4 }

ibmappnNodeLsStatusNodeId       OBJECT-TYPE
      SYNTAX OCTET STRING
      ACCESS read-only
      STATUS mandatory
      DESCRIPTION
          "Adjacent Node id"


      ::=  { ibmappnNodeLsStatusEntry 5 }

ibmappnNodeLsStatusTgNum   OBJECT-TYPE
      SYNTAX INTEGER (0..256)
      ACCESS read-only
      STATUS mandatory
      DESCRIPTION
          "Number associated with the TG to this link station
           with a range from 0 to 256.  A value of 256 indicates
           the tg number has not been negotiated and is unknown at
           this time."

      ::=  { ibmappnNodeLsStatusEntry 6 }

ibmappnNodeLsStatusGeneralSense OBJECT-TYPE
      SYNTAX OCTET STRING
      ACCESS read-only
      STATUS mandatory
      DESCRIPTION
          "The error sense code associated with the start sequence of
           activation of a link up to the beginning of the XID sequence."

      ::=  { ibmappnNodeLsStatusEntry 7 }

ibmappnNodeLsStatusNofRetry OBJECT-TYPE
      SYNTAX INTEGER    {
                          retry(1),
                          noretry(2)
                         }
      ACCESS read-only
      STATUS mandatory
      DESCRIPTION
          "Indicates whether NOF will retry the start request to
           activate the link."

      ::=  { ibmappnNodeLsStatusEntry 8 }

ibmappnNodeLsStatusEndSense OBJECT-TYPE
      SYNTAX OCTET STRING
      ACCESS read-only
      STATUS mandatory
      DESCRIPTION
          "The sense code associated with the termination of the link
           connection to adjacent node.  This includes all sense
           information included in the disconnect recieved from the
           lower layer DLCs and also sense information indicating the
           link termination originated by upper layer APPN components."

      ::=  { ibmappnNodeLsStatusEntry 9 }

ibmappnNodeLsStatusXidLocalSense   OBJECT-TYPE
      SYNTAX OCTET STRING
      ACCESS read-only
      STATUS mandatory
      DESCRIPTION
          "The error sense code associated with the rejection of the
           XID."

      ::=  { ibmappnNodeLsStatusEntry 10 }

ibmappnNodeLsStatusXidRemoteSense   OBJECT-TYPE
      SYNTAX OCTET STRING
      ACCESS read-only
      STATUS mandatory
      DESCRIPTION
          "The error sense code adjacent node returned to this node
           indicating the reason the XID was rejected."

      ::=  { ibmappnNodeLsStatusEntry 11 }

ibmappnNodeLsStatusXidByteInError      OBJECT-TYPE
      SYNTAX INTEGER    {
                         na(1000)
                        }
      ACCESS read-only
      STATUS mandatory
      DESCRIPTION
          "This identifies the actual byte in the XID that caused the
           error.  The value of zero (0) indicates that the variable
           has no meaning."

      ::=  { ibmappnNodeLsStatusEntry 12 }

ibmappnNodeLsStatusXidBitInError      OBJECT-TYPE
      SYNTAX INTEGER    {
                         na(8)   -- not applicable
                        }
      ACCESS read-only
      STATUS mandatory
      DESCRIPTION
          "This identifies the actual bit within the error byte of the
           XID.  This only has meaning when the byte in error is greater
           than zero."

      ::=  { ibmappnNodeLsStatusEntry 13 }

ibmappnNodeLsStatusDlcType  OBJECT-TYPE
      SYNTAX INTEGER    {
                         other(1),
                         sdlc(2),
                         dls(3),
                         socket(4),
                         ethernet(5),
                         tr(6)
                         }
      ACCESS read-only
      STATUS mandatory
      DESCRIPTION
-- the following is just a swag at a possible way to convey various
-- DLC address formats using a single MIB object.
-- DisplayString can contain any ASCII characters and will require
-- the APPN component (CS) to convert addresses, such as MACs and SAPs
-- to ASCII strings.  IP is already in ASCII string format, so no
-- conversion is required.


          "This identifies DLC type that was being used when error
           occurred.  This also is used to the format of the
           local and remote address provided.

           other    = free form DisplayString

           ip       = ld.ld.ld.ld/2d

           tr       = lx:lx:lx:lx:lx:lx.lx

           dlsw     = lx:lx:lx:lx:lx:lx.lx

           ethernet = lx:lx:lx:lx:lx:lx.lx

           "

      ::=  { ibmappnNodeLsStatusEntry 14 }

ibmappnNodeLsStatusLocalAddr   OBJECT-TYPE
      SYNTAX DisplayString
      ACCESS read-only
      STATUS mandatory
      DESCRIPTION
          "This contains a displayable string that identifies the
           DLC type and appropriate address.  See DlcType above for
           details of the format."

      ::=  { ibmappnNodeLsStatusEntry 15 }

ibmappnNodeLsStatusRemoteAddr  OBJECT-TYPE
      SYNTAX DisplayString
      ACCESS read-only
      STATUS mandatory
      DESCRIPTION
          "This contains a displayable string that identifies the
           DLC type and appropriate address.  See DlcType above for
           details of the format."

      ::=  { ibmappnNodeLsStatusEntry 16 }


-- *****************************************************************************
-- APPN SNMP Performance Information
--

ibmappnSnmpInPkts OBJECT-TYPE
      SYNTAX Counter
      ACCESS read-only
      STATUS mandatory
      DESCRIPTION
        "Total number of messages delivered to the APPN SNMP sub-agent."

      ::=  { ibmappnSnmpInformation 1 }

ibmappnSnmpInGetRequests OBJECT-TYPE
      SYNTAX Counter
      ACCESS read-only
      STATUS mandatory
      DESCRIPTION
          "Total number of GET requests delivered to the APPN SNMP
           sub-agent."

      ::=  { ibmappnSnmpInformation 2 }

ibmappnSnmpInGetNexts OBJECT-TYPE
      SYNTAX Counter
      ACCESS read-only
      STATUS mandatory
      DESCRIPTION
          "Total number of GETNEXT requests delivered to the APPN SNMP
           sub-agent."

      ::=  { ibmappnSnmpInformation 3 }

ibmappnSnmpInSetRequests OBJECT-TYPE
      SYNTAX Counter
      ACCESS read-only
      STATUS mandatory
      DESCRIPTION
          "Total number of SET requests delivered to the APPN SNMP
           sub-agent."

      ::=  { ibmappnSnmpInformation 4 }

ibmappnSnmpInTotalVars OBJECT-TYPE
      SYNTAX Counter
      ACCESS read-only
      STATUS mandatory
      DESCRIPTION
          "Total number of VARIABLES included in both
           GET and GETNEXT requests to the APPN SNMP sub-agent."

      ::=  { ibmappnSnmpInformation 5 }

ibmappnSnmpInGetVars OBJECT-TYPE
      SYNTAX Counter
      ACCESS read-only
      STATUS mandatory
      DESCRIPTION
          "Total number of VARIBLES included in all
           GET requests to the APPN SNMP sub-agent."

      ::=  { ibmappnSnmpInformation 6 }

ibmappnSnmpInGetNextVars OBJECT-TYPE
      SYNTAX Counter
      ACCESS read-only
      STATUS mandatory
      DESCRIPTION
          "Total number of VARIABLES included in all
           GETNEXT requests to the APPN SNMP sub-agent."

      ::=  { ibmappnSnmpInformation 7 }

ibmappnSnmpInSetVars OBJECT-TYPE
      SYNTAX Counter
      ACCESS read-only
      STATUS mandatory
      DESCRIPTION
           "Total number of VARIBLES included in all
            SET requests to the APPN SNMP sub-agent."

      ::=  { ibmappnSnmpInformation 8 }

ibmappnSnmpOutNoSuchNames OBJECT-TYPE
      SYNTAX Counter
      ACCESS read-only
      STATUS mandatory
      DESCRIPTION
           "Total number of VARIABLES that could not
            be found by the APPN SNMP sub-agent."

      ::=  { ibmappnSnmpInformation 9 }

ibmappnSnmpOutGenErrs OBJECT-TYPE
      SYNTAX Counter
      ACCESS read-only
      STATUS mandatory
      DESCRIPTION
           "Total number of undefined errors that
            occurred processing SNMP request to the
            APPN SNMP sub-agent."

      ::=  { ibmappnSnmpInformation 10 }

-- ****************************************************************

-- This group provides global information about the
-- APPN node performance.

-- The first section applies to the APPN control point
-- storage utilization.


ibmappnMemorySize OBJECT-TYPE
      SYNTAX INTEGER
      ACCESS read-only
      STATUS mandatory
      DESCRIPTION
           "Size of the shared storage segment, as obtained
            by storage management from the underlying operating
            system."

      ::=  { ibmappnMemoryUse 1 }

ibmappnMemoryUsed OBJECT-TYPE
      SYNTAX INTEGER
      ACCESS read-only
      STATUS mandatory
      DESCRIPTION
           "Number of bytes in the segment that are currently
            allocated to process."

      ::=  { ibmappnMemoryUse 2 }

ibmappnMemoryWarnThresh OBJECT-TYPE
      SYNTAX INTEGER
      ACCESS read-only
      STATUS mandatory
      DESCRIPTION
           "Allocation threshold beyond which storage
            management considers the storage resources
            to be constrained."

      ::=  { ibmappnMemoryUse 3 }

ibmappnMemoryCritThresh OBJECT-TYPE
      SYNTAX INTEGER
      ACCESS read-only
      STATUS mandatory
      DESCRIPTION
           "Allocation threshold beyond which storage
            management considers the storage resources
            to be critically constrained."

      ::=  { ibmappnMemoryUse 4 }

-- ****************************************************************
-- The following are Counters maintained by the APPN CS component that
-- relate to total overall XID activity.
------------------------------------------------------------------------
ibmappnNodeDefLsGoodXids    OBJECT-TYPE
    SYNTAX  Counter
    ACCESS  read-only
    STATUS  mandatory
    DESCRIPTION
            "The current number of successfull XIDs that have occurred
             on all defined link stations since the last time this node
             was initialized."

    ::= { ibmappnXidInformation 1 }

ibmappnNodeDefLsBadXids    OBJECT-TYPE
    SYNTAX  Counter
    ACCESS  read-only
    STATUS  mandatory
    DESCRIPTION
            "The current number of unsuccessfull XIDs that have occurred
             on all defined link stations since the last time this node
             was initialized."

    ::= { ibmappnXidInformation 2 }

ibmappnNodeDynLsGoodXids    OBJECT-TYPE
    SYNTAX  Counter
    ACCESS  read-only
    STATUS  mandatory
    DESCRIPTION
            "The current number of successfull XIDs that have occurred
             on all dynamic link stations since the last time this node
             was initialized."

    ::= { ibmappnXidInformation 3 }

ibmappnNodeDynLsBadXids    OBJECT-TYPE
    SYNTAX  Counter
    ACCESS  read-only
    STATUS  mandatory
    DESCRIPTION
            "The current number of unsuccessfull XIDs that have occurred
             on all dynamic link stations since the last time this node
             was initialized."

    ::= { ibmappnXidInformation 4 }


-- ************** The APPN Topology Group ************

ibmappnNn             OBJECT IDENTIFIER ::= { ibmappn 2  }
ibmappnNnTopo         OBJECT IDENTIFIER ::= { ibmappnNn 1  }
ibmappnNnTopology     OBJECT IDENTIFIER ::= { ibmappnNn 3  }


-- This group will be used to represent the entire APPN network
-- topology, including Network nodes, virtual nodes and
-- all TGs associated with these nodes.
--

-- Network nodes
-- The APPN topology database consists of information about every
-- APPN network node.  This information is learned over time
-- as each network node exchanges topology information with
-- each of its adjacent network nodes.  The database consists
-- of information about each node and all of the transmissions
-- groups used by each node.

-- Virtual nodes
-- Information about virtual nodes (connection networks) is treated
-- the same as information about network node
-- and is replicated at each network node.
-- The node name is the only meaningful information. The other
-- node objects use default values.  Each node that has defined
-- a TG with this virtual node as the destination also defines a
-- TG on this virtual node.  There is a TG record for each node
-- that uses this virtual node.
--
--
-- The APPN node table represents the APPN topology
-- database with the APPN CP fully-qualified name
-- being used as the index to this table.
-- This entire table could be retrieved using the GET NEXT command,
-- however, due to the dynamics of APPN, nodes could come and
-- go and status could change as the table is being
-- retrieved.  Although in most cases the data retrieved will be valid,
-- missing and invalid status could cause problems for
-- a management application that was graphically displaying
-- this data.
-- This potential problem can be eliminated by
-- retrieving the FRSN before and after completion
-- of retrieval of the APPN topology table.
-- If the FRSN has changed, then repeat the
-- retrieval of the entire topology table
-- until the FRSN remains unchanged.
-- Object 'appnNnFrsn' represents the last
-- change or update to this node's topology
-- database.
--
--
-- The format of the actual database is as follows:
--
-- Node table (entry for each node in network)
--  TG table (entry for each TG owned by node)
--
-- Due to SNMP ASN.1 limitations, we cannot represent
-- the TG table within the node table.  We define
-- separate tables for nodes and TGs, adding the node
-- name to each TG entry to provide a means of
-- correlating each TG with its originating node.


ibmappnNnTopoMaxNodes   OBJECT-TYPE
      SYNTAX INTEGER
      ACCESS read-only
      STATUS mandatory
      DESCRIPTION
          "Maximum number of nodes allowed in the APPN topology database
          This administratively assigned value must be equal to or
          greater than the maximum total number of end nodes and
          network nodes.
          If the number of nodes exceeds this value, APPN will issue
          an Alert and the node can no longer participate as a network
          node."

      ::=  { ibmappnNnTopo 1 }

ibmappnNnTopoCurNumNodes OBJECT-TYPE
      SYNTAX Gauge
      ACCESS read-only
      STATUS mandatory
      DESCRIPTION
          "Current number of nodes in this node's topology database.
           If this value exceeds the maximum number of nodes allowed
           (NnTopoMaxNodes), APPN alert CPDB002 is
           issued."
--APPN ALERT/TRAP CPDB002 will be generated when this exceeds
--the value specified for the topology table.

      ::=  { ibmappnNnTopo 2 }

ibmappnNnTopoInTdus OBJECT-TYPE
      SYNTAX Counter
      ACCESS read-only
      STATUS mandatory
      DESCRIPTION
           "Total number of TDUs received from
           all adjacent NN since last initialization."

      ::=  { ibmappnNnTopo 3 }

ibmappnNnTopoOutTdus OBJECT-TYPE
      SYNTAX Counter
      ACCESS read-only
      STATUS mandatory
      DESCRIPTION
           "Total number of TDUs built by this node to be sent to
           all adjacent NN since last initialization."

      ::=  { ibmappnNnTopo 4 }

ibmappnNnTopoNodeLowRsns         OBJECT-TYPE
      SYNTAX Counter
      ACCESS read-only
      STATUS mandatory
      DESCRIPTION
           "Total number of topology node updates received by this
           node with a RSN less than the current RSN.  Both even and
           odd RSN are included in this count.
           These TDUs are not errors, but result when TDUs are
           broadcast to all adjacent network nodes.  No update to
           this node's topology database occurs, but this node will
           send a TDU with it's higher RSN to the adjacent node that
           sent this low RSN."

      ::=  { ibmappnNnTopo 5 }

ibmappnNnTopoNodeEqualRsns      OBJECT-TYPE
      SYNTAX Counter
      ACCESS read-only
      STATUS mandatory
      DESCRIPTION
           "Total number of topology node updates received by this
           node with a RSN equal to the current RSN.  Both even and
           odd RSN are included in this count.
           These TDUs are not errors, but result when TDUs are
           broadcast to all adjacent network nodes.  No update to
           this node's topology database occurs."

      ::=  { ibmappnNnTopo 6 }

ibmappnNnTopoNodeGoodHighRsns      OBJECT-TYPE
      SYNTAX Counter
      ACCESS read-only
      STATUS mandatory
      DESCRIPTION
           "Total number of topology node updates received by this
           node with a RSN greater than the current RSN.
           This results in updating this nodes topology and broadcasting
           a TDU to all adjacent network nodes.  It is not required to
           send a TDU to the sender of this update because that node
           already has the update."

      ::=  { ibmappnNnTopo 7 }



ibmappnNnTopoNodeBadHighRsns       OBJECT-TYPE
      SYNTAX Counter
      ACCESS read-only
      STATUS mandatory
      DESCRIPTION
           "Total number of topology node updates received by this
           node with an odd RSN greater than the current RSN.
           These updates represent a topology inconsistency detected
           by one of the APPN network nodes.
           This results in updating this nodes topology and broadcasting
           a TDU to all adjacent network nodes."

      ::=  { ibmappnNnTopo 8 }


ibmappnNnTopoNodeStateUpdates  OBJECT-TYPE
      SYNTAX Counter
      ACCESS read-only
      STATUS mandatory
      DESCRIPTION
           "Total number of topology Node records built as a result
            of internally detected node state changes that affect APPN
            topology and routing.  Updates are sent via TDUs to all
            adjacent network nodes."

      ::=  { ibmappnNnTopo 9 }

ibmappnNnTopoNodeErrors     OBJECT-TYPE
      SYNTAX Counter
      ACCESS read-only
      STATUS mandatory
      DESCRIPTION
           "Total number of topology node records inconsistencies
            detected by this node.  This occurs when this node attempts
            to update its topology database and detects a data
            inconsistency.  This node will create a TDU with the
            current RSN incremented to the next odd number and
            broadcast it to all adjacent NNs."

      ::=  { ibmappnNnTopo 10 }

ibmappnNnTopoNodeTimerUpdates OBJECT-TYPE
      SYNTAX Counter
      ACCESS read-only
      STATUS mandatory
      DESCRIPTION
           "Total number of topology node records built for this
            node's resource due to timer updates. Updates are sent via
            TDUs to all adjacent network nodes. These updates insure
            other network nodes do not delete this node's resources
            from their topology database."

      ::=  { ibmappnNnTopo 11 }

ibmappnNnTopoNodePurges     OBJECT-TYPE
      SYNTAX Counter
      ACCESS read-only
      STATUS mandatory
      DESCRIPTION
           "Total number of topology node records purged from this
            node's topology database.  This occurs when a node has not
            been updated in a specified amount of time.  The owning
            node is responsible for broadcasting updates for its resource
            that it wants kept in the network topology."

      ::=  { ibmappnNnTopo 12 }


ibmappnNnTopoTgLowRsns         OBJECT-TYPE
      SYNTAX Counter
      ACCESS read-only
      STATUS mandatory
      DESCRIPTION
           "Total number of topology TG updates received by this
           node with a RSN less than the current RSN.  Both even and
           odd RSN are included in this count.
           These TDUs are not errors, but result when TDUs are
           broadcast to all adjacent network nodes.  No update to
           this node's topology database occurs, but this node will
           send a TDU with it's higher RSN to the sender of the low
           RSN."

      ::=  { ibmappnNnTopo 13 }

ibmappnNnTopoTgEqualRsns       OBJECT-TYPE
      SYNTAX Counter
      ACCESS read-only
      STATUS mandatory
      DESCRIPTION
           "Total number of topology TG updates received by this
           node with a RSN equal to the current RSN.  Both even and
           odd RSN are included in this count.
           These TDUs are not errors, but result when TDUs are
           broadcast to all adjacent network nodes.  No update to
           this node's topology database occurs."

      ::=  { ibmappnNnTopo 14 }

ibmappnNnTopoTgGoodHighRsns       OBJECT-TYPE
      SYNTAX Counter
      ACCESS read-only
      STATUS mandatory
      DESCRIPTION
           "Total number of topology TG updates received by this
           node with a RSN greater than the current RSN.
           This results in updating this nodes topology and broadcasting
           the update to all adjacent network nodes."

      ::=  { ibmappnNnTopo 15 }



ibmappnNnTopoTgBadHighRsns      OBJECT-TYPE
      SYNTAX Counter
      ACCESS read-only
      STATUS mandatory
      DESCRIPTION
           "Total number of topology TG updates received by this
           node with an odd RSN greater than the current RSN.
           These updates represent a topology inconsistency detected
           by one of the APPN network nodes.
           This results in updating this nodes topology and broadcasting
           a TDU to all adjacent network nodes."

      ::=  { ibmappnNnTopo 16 }


ibmappnNnTopoTgStateUpdates  OBJECT-TYPE
      SYNTAX Counter
      ACCESS read-only
      STATUS mandatory
      DESCRIPTION
           "Total number of topology TG records built as a result
            of internally detected node state changes that affect APPN
            topology and routing.  Updates are sent via TDUs to all
            adjacent network nodes."

      ::=  { ibmappnNnTopo 17 }

ibmappnNnTopoTgErrors     OBJECT-TYPE
      SYNTAX Counter
      ACCESS read-only
      STATUS mandatory
      DESCRIPTION
           "Total number of topology TG records inconsistencies
            detected by this node.  This occurs when this node attempts
            to update its topology database and detects a data
            inconsistency.  This node will create a TDU with the
            current RSN incremented to the next odd number and
            broadcast it to all adjacent NNs."

      ::=  { ibmappnNnTopo 18 }

ibmappnNnTopoTgTimerUpdates OBJECT-TYPE
      SYNTAX Counter
      ACCESS read-only
      STATUS mandatory
      DESCRIPTION
           "Total number of topology TG records built for this
            node's resource due to timer updates. Updates are sent via
            TDUs to all adjacent network nodes. These updates insure
            other network nodes do not delete this node's resources
            from their topology database."

      ::=  { ibmappnNnTopo 19 }


ibmappnNnTopoTgPurges     OBJECT-TYPE
      SYNTAX Counter
      ACCESS read-only
      STATUS mandatory
      DESCRIPTION
           "Total number of topology TG records purged from this
            node's topology database.  This occurs when a TG has not
            been updated in a specified amount of time.  The owning
            node is responsible for broadcasting updates for its resource
            that it wants to keep in the network topology."

      ::=  { ibmappnNnTopo 20 }


ibmappnNnTopoTotalRouteCalcs OBJECT-TYPE
      SYNTAX Counter
      ACCESS read-only
      STATUS mandatory
      DESCRIPTION
           "Number of routes calculated  for all class of services
            since the last initialization."

      ::=  { ibmappnNnTopo 21 }

ibmappnNnTopoTotalRouteRejs OBJECT-TYPE
      SYNTAX Counter
      ACCESS read-only
      STATUS mandatory
      DESCRIPTION
           "Number of route requests for all class of services that
            could not be calculated since last initialization."

      ::=  { ibmappnNnTopo 22 }


ibmappnNnTopoRouteTable OBJECT-TYPE
      SYNTAX SEQUENCE OF IbmappnNnTopoRouteEntry
      ACCESS not-accessible
      STATUS mandatory
      DESCRIPTION
           "Table containing an entry for every Class of Service
            that it has calculated a route for."

      ::= { ibmappnNnTopo 23 }


ibmappnNnTopoRouteEntry OBJECT-TYPE
      SYNTAX IbmappnNnTopoRouteEntry
      ACCESS not-accessible
      STATUS mandatory
      DESCRIPTION
            "The Class of Service name is the index for this table."

      INDEX
             {ibmappnNnTopoRouteCos}

      ::= { ibmappnNnTopoRouteTable 1 }

IbmappnNnTopoRouteEntry ::= SEQUENCE {
      ibmappnNnTopoRouteCos                  DisplayString,
      ibmappnNnTopoRouteTrees                Counter,
      ibmappnNnTopoRouteCalcs                Counter,
      ibmappnNnTopoRouteRejs                 Counter
}


ibmappnNnTopoRouteCos   OBJECT-TYPE
      SYNTAX DisplayString
      ACCESS read-only
      STATUS mandatory
      DESCRIPTION
           "The Class of Service for the route."

      ::=  { ibmappnNnTopoRouteEntry 1 }

ibmappnNnTopoRouteTrees OBJECT-TYPE
      SYNTAX Counter
      ACCESS read-only
      STATUS mandatory
      DESCRIPTION
           "Number of routes tree caches built for this Class of
            Service since the last initialization."

      ::=  { ibmappnNnTopoRouteEntry 2 }


ibmappnNnTopoRouteCalcs OBJECT-TYPE
      SYNTAX Counter
      ACCESS read-only
      STATUS mandatory
      DESCRIPTION
           "Number of routes calculated since last initialization."

      ::=  { ibmappnNnTopoRouteEntry 3 }

ibmappnNnTopoRouteRejs OBJECT-TYPE
      SYNTAX Counter
      ACCESS read-only
      STATUS mandatory
      DESCRIPTION
           "Number of route requests that could not
           be calculated since last initialization."

      ::=  { ibmappnNnTopoRouteEntry 4 }



--Adjacent node table
--  Node name (only applies to adjacent nodes)
--  Number of out of sequence TDUs
--  Status of CP-CP sessions (ConWinner/ConLoser)
--  Last FRSN sent
--  Last FRSN received


ibmappnNnAdjNodeTable OBJECT-TYPE
      SYNTAX SEQUENCE OF IbmappnNnAdjNodeEntry
      ACCESS not-accessible
      STATUS mandatory
      DESCRIPTION
           "Table containing an entry for every node.  The information
            kept in this table is the last FRSN sent and received,
            the status of the CP-CP sessions, and a gauge that indicates
            the number of outstanding TDUs."

      ::= { ibmappnNn 2 }


ibmappnNnAdjNodeEntry OBJECT-TYPE
      SYNTAX IbmappnNnAdjNodeEntry
      ACCESS not-accessible
      STATUS mandatory
      DESCRIPTION
            "The adjacent node name is the index for this table."

      INDEX
             {ibmappnNnAdjNodeAdjName}

      ::= { ibmappnNnAdjNodeTable 1 }

IbmappnNnAdjNodeEntry ::= SEQUENCE {
      ibmappnNnAdjNodeAdjName            DisplayString,
      ibmappnNnAdjNodeCpCpSessStatus     INTEGER,
      ibmappnNnAdjNodeOutOfSeqTdus       Gauge,
      ibmappnNnAdjNodeLastFrsnSent       INTEGER,
      ibmappnNnAdjNodeLastFrsnRcvd       INTEGER
                                   }

ibmappnNnAdjNodeAdjName              OBJECT-TYPE
      SYNTAX DisplayString (SIZE (3..17))
      ACCESS read-only
      STATUS mandatory
      DESCRIPTION
           "An administratively-assigned fully-qualified
            name of this node's adjacent network node."

      ::=  { ibmappnNnAdjNodeEntry 1 }

ibmappnNnAdjNodeCpCpSessStatus    OBJECT-TYPE
      SYNTAX INTEGER {
                     active(1),
                     conLoserActive(2),
                     conWinnerActive(3),
                     inactive(4)
                     }
      ACCESS read-only
      STATUS mandatory
      DESCRIPTION
          "Indicates the state of CP-CP sessions between this node
           and adjacent network and end nodes.  Incative indicates no
           CP-CP sessions exists between this node and the adjacent
           node.  Active indicates CP-CP sessons are active using both
           the ConWinner and ConLoser sessions. The session initiated
           by this node is refered to as the ConWinner session and is
           used by this node to send to the adjacent node.  The ConLoserr
           session is initiated by the adjacent node and is used by this
           node to receive from the adjacent node."

      ::=  { ibmappnNnAdjNodeEntry 2 }

ibmappnNnAdjNodeOutOfSeqTdus  OBJECT-TYPE
      SYNTAX Gauge
      ACCESS read-only
      STATUS mandatory
      DESCRIPTION
           "Number of out of sequence Topology Database
           Updates (TDUs).  In a quiesced state, this value is
           zero.  In normal operation, the value varies
           depending on the network environment."

      ::=  { ibmappnNnAdjNodeEntry 3 }


ibmappnNnAdjNodeLastFrsnSent  OBJECT-TYPE
      SYNTAX INTEGER (0..65535)
      ACCESS read-only
      STATUS mandatory
      DESCRIPTION
          "Flow reduction sequence numbers (FRSNs) are associated
           with Topology Database Updates (TDUs) and are unique
           only within each APPN network node.  A TDU can be
           associated with multiple APPN resources. This FRSN
           indicates the last TDU sent to this adjacent node."


      ::=  { ibmappnNnAdjNodeEntry 4 }

ibmappnNnAdjNodeLastFrsnRcvd OBJECT-TYPE
      SYNTAX INTEGER (0..65535)
      ACCESS read-only
      STATUS mandatory
      DESCRIPTION
          "Flow reduction sequence numbers (FRSNs) are associated
           with Topology Database Updates (TDUs) and are unique
           only within each APPN network node.  A TDU can be
           associated with multiple APPN resources. This FRSN
           indicates the last TDU received from this adjacent node."


      ::=  { ibmappnNnAdjNodeEntry 5 }


--APPN Node Topology table

-- This table describes every known APPN Network node
-- and Virtual node.


ibmappnNnTopologyTable OBJECT-TYPE
      SYNTAX SEQUENCE OF IbmappnNnTopologyEntry
      ACCESS not-accessible
      STATUS mandatory
      DESCRIPTION
           "Portion of the APPN routing table
            that describes all of the APPN network nodes
            and virtual nodes known to this node."

      ::= { ibmappnNnTopology 1 }

ibmappnNnTopologyEntry OBJECT-TYPE
      SYNTAX IbmappnNnTopologyEntry
      ACCESS not-accessible
      STATUS mandatory
      DESCRIPTION
           "The fully-qualified node name is used to
            index this table."

      INDEX
             {ibmappnNnNodeName}

      ::= { ibmappnNnTopologyTable 1 }

IbmappnNnTopologyEntry  ::= SEQUENCE {

      ibmappnNnNodeName                     DisplayString,
      ibmappnNnNodeFrsn                     INTEGER,
      ibmappnNnNodeEntryTimeLeft            INTEGER,
      ibmappnNnNodeType                     INTEGER,

      ibmappnNnNodeRsn                      INTEGER,
      ibmappnNnNodeRouteAddResist           INTEGER,
      ibmappnNnNodeCongested                INTEGER,
      ibmappnNnNodeIsrDepleted              INTEGER,
      ibmappnNnNodeEndptDepleted            INTEGER,
      ibmappnNnNodeQuiescing                INTEGER,
      ibmappnNnNodeGateway                  INTEGER,
      ibmappnNnNodeCentralDirectory         INTEGER,
      ibmappnNnNodeIsr                      INTEGER,
      ibmappnNnNodeChainSupport             INTEGER
}

ibmappnNnNodeName    OBJECT-TYPE
      SYNTAX DisplayString (SIZE (3..17))
      ACCESS read-only
      STATUS mandatory
      DESCRIPTION
          "Administratively-assigned network name that is locally
          defined at each network node in the format NETID.CPNAME."

      ::=  { ibmappnNnTopologyEntry 1 }

ibmappnNnNodeFrsn             OBJECT-TYPE
      SYNTAX INTEGER (0..65535)
      ACCESS read-only
      STATUS mandatory
      DESCRIPTION
          "Flow reduction sequence numbers (FRSNs) are associated
           with Topology Database Updates (TDUs) and are unique
           only within each APPN network node.  A TDU can be
           associated with multiple APPN resources. This FRSN
           indicates the last time this resource was updated at
           this node."

      ::=  { ibmappnNnTopologyEntry 2 }

ibmappnNnNodeEntryTimeLeft    OBJECT-TYPE
      SYNTAX INTEGER (0..31)
      ACCESS read-only
      STATUS mandatory
      DESCRIPTION
           "Number of days before deletion of this
            network node entry. Range is 0-31."

      ::=  { ibmappnNnTopologyEntry 3 }

ibmappnNnNodeType    OBJECT-TYPE
      SYNTAX INTEGER {
                     networknode(1),
                     virtualnode(3)
                     }
      ACCESS read-only
      STATUS mandatory
      DESCRIPTION
           "Type of APPN node."

      ::=  { ibmappnNnTopologyEntry 4 }

ibmappnNnNodeRsn       OBJECT-TYPE
      SYNTAX INTEGER
      ACCESS read-only
      STATUS mandatory
      DESCRIPTION
           "Resource sequence number that is assigned and
            controlled by the network node that owns this
            resource. This is always an even 32-bit number
            unless an error has occurred."

      ::=  { ibmappnNnTopologyEntry 5 }

ibmappnNnNodeRouteAddResist   OBJECT-TYPE
      SYNTAX INTEGER
      ACCESS read-only
      STATUS mandatory
      DESCRIPTION
          "Route addition resistance
          indicates the relative desirability
          of using this node for intermediate session traffic.
          The value, which can be any integer 0-255,
          is used in route computation.  The lower the value,
          the more desirable the node is for intermediate routing."

      ::=  { ibmappnNnTopologyEntry 6 }

ibmappnNnNodeCongested        OBJECT-TYPE
      SYNTAX INTEGER {yes(1), no(2)}
      ACCESS read-only
      STATUS mandatory
      DESCRIPTION
          "Indicates whether this node is congested.
           This node is not be included in route selection
           by other nodes when this congestion exists."

       ::= { ibmappnNnTopologyEntry 7 }

ibmappnNnNodeIsrDepleted OBJECT-TYPE
      SYNTAX INTEGER {yes(1), no(2)}
      ACCESS read-only
      STATUS mandatory
      DESCRIPTION
          "Indicates whether intermediate session
           routing resources are depleted.  This node is
           not included in intermediate route selection
           by other nodes when resources are depleted."

      ::=  { ibmappnNnTopologyEntry 8 }

ibmappnNnNodeEndptDepleted OBJECT-TYPE
      SYNTAX INTEGER {yes(1), no(2)}
      ACCESS read-only
      STATUS mandatory
      DESCRIPTION
           "Indicates whether session endpoint resources are depleted."

      ::=  { ibmappnNnTopologyEntry 9 }

ibmappnNnNodeQuiescing     OBJECT-TYPE
      SYNTAX INTEGER {yes(1), no(2)}
      ACCESS read-only
      STATUS mandatory
      DESCRIPTION
          "Indicates whether the node is quiescing.
           This node is not included in route selection
           by other nodes when the node is quiescing."

      ::=  { ibmappnNnTopologyEntry 10 }

ibmappnNnNodeGateway       OBJECT-TYPE
      SYNTAX INTEGER {yes(1), no(2)}
      ACCESS read-only
      STATUS mandatory
      DESCRIPTION
           "Indicates whether the node provide gateway functions."

      ::=  { ibmappnNnTopologyEntry 11 }

ibmappnNnNodeCentralDirectory OBJECT-TYPE
      SYNTAX INTEGER {yes(1), no(2)}
      ACCESS read-only
      STATUS mandatory
      DESCRIPTION
           "Indicates whether the node is central directory."

      ::=  { ibmappnNnTopologyEntry 12 }

ibmappnNnNodeIsr   OBJECT-TYPE
      SYNTAX INTEGER {yes(1), no(2)}
      ACCESS read-only
      STATUS mandatory
      DESCRIPTION
           "Indicates whether the node supports intermediate session
            routing (ISR)."

      ::=  { ibmappnNnTopologyEntry 13 }

ibmappnNnNodeChainSupport OBJECT-TYPE
      SYNTAX INTEGER {yes(1), no(2)}
      ACCESS read-only
      STATUS mandatory
      DESCRIPTION
           "Indicates whether the node supports chaining."

      ::=  { ibmappnNnTopologyEntry 14 }

--APPN transmission group (TG) table

-- This table describes the TGs associated with
-- the APPN network nodes.
-- The originating node is repeated here to provide a
-- means of correlating the TGs with the nodes.


ibmappnNnTgTopologyTable OBJECT-TYPE
      SYNTAX SEQUENCE OF IbmappnNnTgTopologyEntry
      ACCESS not-accessible
      STATUS mandatory
      DESCRIPTION
           "Portion of the APPN topology database
           that describes all of the APPN transmissions groups
           used by the APPN network nodes."

      ::= { ibmappnNnTopology 2 }

ibmappnNnTgTopologyEntry OBJECT-TYPE
      SYNTAX IbmappnNnTgTopologyEntry
      ACCESS not-accessible
      STATUS mandatory
      DESCRIPTION
           "This table requires three indexes to provide a
            unique index.  The indexes are the owning or originating
            CPname, the destination CPname, and the TG number."

      INDEX
             {ibmappnNnTgOwner,
              ibmappnNnTgDest,
              ibmappnNnTgNum}

      ::= { ibmappnNnTgTopologyTable 1 }

IbmappnNnTgTopologyEntry ::= SEQUENCE {

      ibmappnNnTgOwner      DisplayString,
      ibmappnNnTgDest       DisplayString,
      ibmappnNnTgNum        INTEGER,
      ibmappnNnTgFrsn       INTEGER,
      ibmappnNnTgEntryTimeLeft INTEGER,

      ibmappnNnTgDestVirtual INTEGER,
      ibmappnNnTgDlcData    OCTET STRING,

      ibmappnNnTgRsn        INTEGER,
      ibmappnNnTgOperational INTEGER,
      ibmappnNnTgQuiescing   INTEGER,
      ibmappnNnTgCpCpSession INTEGER,
      ibmappnNnTgEffCap     INTEGER,
      ibmappnNnTgConnCost   INTEGER,
      ibmappnNnTgByteCost   INTEGER,
      ibmappnNnTgSecurity   INTEGER,
      ibmappnNnTgDelay      INTEGER,
      ibmappnNnTgModemClass INTEGER,
      ibmappnNnTgUsr1       INTEGER,
      ibmappnNnTgUsr2       INTEGER,
      ibmappnNnTgUsr3       INTEGER}


ibmappnNnTgOwner  OBJECT-TYPE
      SYNTAX DisplayString (SIZE (3..17))
      ACCESS read-only
      STATUS mandatory
      DESCRIPTION
          "Administratively-assigned name for the
          originating node for this TG. The format
          is NETID.CPNAME and is the same name
          specified in the node table."

      ::=  { ibmappnNnTgTopologyEntry 1 }

ibmappnNnTgDest  OBJECT-TYPE
      SYNTAX DisplayString (SIZE (3..17))
      ACCESS read-only
      STATUS mandatory
      DESCRIPTION
          "Administratively-assigned fully-qualified
          network name for the destination node for this TG."

      ::=  { ibmappnNnTgTopologyEntry 2 }

ibmappnNnTgNum  OBJECT-TYPE
      SYNTAX INTEGER  (0..255)
      ACCESS read-only
      STATUS mandatory
      DESCRIPTION
          "Number associated with this
          transmission group. Range is 0-255."

      ::=  { ibmappnNnTgTopologyEntry 3 }

ibmappnNnTgFrsn             OBJECT-TYPE
      SYNTAX INTEGER (0..65535)
      ACCESS read-only
      STATUS mandatory
      DESCRIPTION
           "Flow reduction sequence numbers (FRSNs) are associated
            with Topology Database Updates (TDUs) and are unique
            only within each APPN network node.  A TDU can be
            associated with multiple APPN resources.  This FRSN
            indicates the last time this resource was updated at
            this node."

      ::=  { ibmappnNnTgTopologyEntry 4 }

ibmappnNnTgEntryTimeLeft    OBJECT-TYPE
      SYNTAX INTEGER (0..31)
      ACCESS read-only
      STATUS mandatory
      DESCRIPTION
           "Number of days before deletion of this
            network node TG entry. Range is 0-31."

      ::=  { ibmappnNnTgTopologyEntry 5 }

ibmappnNnTgDestVirtual  OBJECT-TYPE
      SYNTAX INTEGER {yes(1), no(2)}
      ACCESS read-only
      STATUS mandatory
      DESCRIPTION
           "Indicates whether the destination node is
           a virtual node."

      ::=  { ibmappnNnTgTopologyEntry 6 }

ibmappnNnTgDlcData  OBJECT-TYPE
      SYNTAX OCTET STRING  (SIZE (0..9))
      ACCESS read-only
      STATUS mandatory
      DESCRIPTION
           "DLC specific data related to the link connection
           network.
           Token-Ring    - MAC/SAP
           X.25 Switched - dial digits
           X.21 Switched - dial digits
           Circuit Swtch - dial digits"

      ::=  { ibmappnNnTgTopologyEntry 7 }

ibmappnNnTgRsn      OBJECT-TYPE
      SYNTAX INTEGER
      ACCESS read-only
      STATUS mandatory
      DESCRIPTION
           "Current owning node's resource sequence number
            for this resource."

      ::=  { ibmappnNnTgTopologyEntry 8 }

ibmappnNnTgOperational OBJECT-TYPE
      SYNTAX INTEGER {yes(1), no(2)}
      ACCESS read-only
      STATUS mandatory
      DESCRIPTION
           "Indicates whether the transmission group
           is operational."

      ::=  { ibmappnNnTgTopologyEntry 9 }

ibmappnNnTgQuiescing OBJECT-TYPE
      SYNTAX INTEGER {yes(1), no(2)}
      ACCESS read-only
      STATUS mandatory
      DESCRIPTION
           "Indicates whether the transmission group
           is quiescing."

      ::=  { ibmappnNnTgTopologyEntry 10 }

ibmappnNnTgCpCpSession OBJECT-TYPE
      SYNTAX INTEGER {yes(1), no(2)}
      ACCESS read-only
      STATUS mandatory
      DESCRIPTION
           "Indicates whether CP-CP sessions are supported on this TG."

      ::=  { ibmappnNnTgTopologyEntry 11 }


ibmappnNnTgEffCap   OBJECT-TYPE
      SYNTAX INTEGER
      ACCESS read-only
      STATUS mandatory
      DESCRIPTION
          "The effective capacity is an integer value that indicates
           the kilo bits per second.
           It is derived from the link bandwidth and maximum load
           factor with the range of 0 thru 603,979,776.
           This is an administratively assigned value associated
           with this TG."

      ::=  { ibmappnNnTgTopologyEntry 12 }

ibmappnNnTgConnCost OBJECT-TYPE
      SYNTAX INTEGER (0..255)
      ACCESS read-only
      STATUS mandatory
      DESCRIPTION
          "Cost per connect time: a value representing
           the relative cost per unit of time to use
           the TG. Range is from 0, which means no cost,
           to 255, which indicates maximum cost.
           This is an administratively assigned value associated
           with this TG."


      ::=  { ibmappnNnTgTopologyEntry 13 }

ibmappnNnTgByteCost  OBJECT-TYPE
      SYNTAX INTEGER (0..255)
      ACCESS read-only
      STATUS mandatory
      DESCRIPTION
          "Relative cost of transmitting a byte over this link.
           Range is from 0 (lowest cost) to 255.
           This is an administratively assigned value associated
           with this TG."

      ::=  { ibmappnNnTgTopologyEntry 14 }

ibmappnNnTgSecurity  OBJECT-TYPE
      SYNTAX INTEGER {
                     nonsecure(1),                --X'01'
                     publicSwitchedNetwork(32),   --X'20'
                     undergroundCable(64),        --X'40'
                     secureConduit(96),           --X'60'
                     guardedConduit(128),         --X'80'
                     encrypted(160),              --X'A0'
                     guardedRadiation(192)        --X'C0'
             }
      ACCESS read-only
      STATUS mandatory
      DESCRIPTION
          "The security is represented as an integer with a range of
           1 thru 255 with the most common values enumerated as
           defined above.
           This is an administratively assigned value associated
           with this TG."

      ::=  { ibmappnNnTgTopologyEntry 15 }

ibmappnNnTgDelay  OBJECT-TYPE
      SYNTAX INTEGER {
                     minimum(1),                 --X'00'
                     negligible(384),            --X'4C'
                     terrestrial(9216),          --X'71'
                     packet(147456),             --X'91'
                     long(294912),               --X'99'
                     maximum(2013265920)         --X'FF'
             }
      ACCESS read-only
      STATUS mandatory
      DESCRIPTION
           "Relative amount of time that it takes for a signal to
            travel the length of the logical link.  This time is
            represented in micro seconds, with some of the more
            common values enumerated.
            This is an administratively assigned value associated
            with this TG."


      ::=  { ibmappnNnTgTopologyEntry 16 }

ibmappnNnTgModemClass        OBJECT-TYPE
      SYNTAX INTEGER (0..65535)
      ACCESS read-only
      STATUS mandatory
      DESCRIPTION
           "This is used to have multiple images for a
            connection network.  For a connection network
           it is the same as in the TG vector; for
           a non-connection network it is X'00'."

      ::=  { ibmappnNnTgTopologyEntry 17 }

ibmappnNnTgUsr1  OBJECT-TYPE
      SYNTAX INTEGER (0..255)
      ACCESS read-only
      STATUS mandatory
      DESCRIPTION
          "First user-defined TG characteristic for this TG with
           a range of 0-255.
           This is an administratively assigned value associated
           with this TG."

      ::=  { ibmappnNnTgTopologyEntry 18 }

ibmappnNnTgUsr2  OBJECT-TYPE
      SYNTAX INTEGER (0..255)
      ACCESS read-only
      STATUS mandatory
      DESCRIPTION
          "Second user-defined TG characteristic for this TG with
           a range of 0-255.
           This is an administratively assigned value associated
           with this TG."

      ::=  { ibmappnNnTgTopologyEntry 19 }

ibmappnNnTgUsr3  OBJECT-TYPE
      SYNTAX INTEGER (0..255)
      ACCESS read-only
      STATUS mandatory
      DESCRIPTION
          "Third user-defined TG characteristic for this TG with
           a range of 0-255.
           This is an administratively assigned value associated
           with this TG."

      ::=  { ibmappnNnTgTopologyEntry 20 }


--APPN Node Topology table (using FRSN as index)

-- This table describes every known APPN Network node
-- and Virtual node.


ibmappnNnTopologyFRTable OBJECT-TYPE
      SYNTAX SEQUENCE OF IbmappnNnTopologyFREntry
      ACCESS not-accessible
      STATUS mandatory
      DESCRIPTION
           "Portion of the APPN routing table
            that describes all of the APPN network nodes
            and virtual nodes known to this node."

      ::= { ibmappnNnTopology 3 }

ibmappnNnTopologyFREntry OBJECT-TYPE
      SYNTAX IbmappnNnTopologyFREntry
      ACCESS not-accessible
      STATUS mandatory
      DESCRIPTION
           "The fully-qualified node name is used to
            index this table."

      INDEX
             {ibmappnNnNodeFRFrsn,
              ibmappnNnNodeFRName}

      ::= { ibmappnNnTopologyFRTable 1 }

IbmappnNnTopologyFREntry ::= SEQUENCE {
      ibmappnNnNodeFRName                     DisplayString,
      ibmappnNnNodeFRFrsn                     INTEGER,
      ibmappnNnNodeFREntryTimeLeft            INTEGER,
      ibmappnNnNodeFRType                     INTEGER,

      ibmappnNnNodeFRRsn                      INTEGER,
      ibmappnNnNodeFRRouteAddResist           INTEGER,
      ibmappnNnNodeFRCongested                INTEGER,
      ibmappnNnNodeFRIsrDepleted              INTEGER,
      ibmappnNnNodeFREndptDepleted            INTEGER,
      ibmappnNnNodeFRQuiescing                INTEGER,
      ibmappnNnNodeFRGateway                  INTEGER,
      ibmappnNnNodeFRCentralDirectory         INTEGER,
      ibmappnNnNodeFRIsr                      INTEGER,
      ibmappnNnNodeFRChainSupport             INTEGER
}

ibmappnNnNodeFRName    OBJECT-TYPE
      SYNTAX DisplayString (SIZE (3..17))
      ACCESS read-only
      STATUS mandatory
      DESCRIPTION
          "Administratively-assigned network name that is locally
          defined at each network node in the format NETID.CPNAME."

      ::=  { ibmappnNnTopologyFREntry 1 }

ibmappnNnNodeFRFrsn             OBJECT-TYPE
      SYNTAX INTEGER (0..65535)
      ACCESS read-only
      STATUS mandatory
      DESCRIPTION
          "Flow reduction sequence numbers (FRSNs) are associated
           with Topology Database Updates (TDUs) and are unique
           only within each APPN network node.  A TDU can be
           associated with multiple APPN resources. This FRSN
           indicates the last time this resource was updated at
           this node."

      ::=  { ibmappnNnTopologyFREntry 2 }

ibmappnNnNodeFREntryTimeLeft    OBJECT-TYPE
      SYNTAX INTEGER (0..31)
      ACCESS read-only
      STATUS mandatory
      DESCRIPTION
           "Number of days before deletion of this
            network node entry. Range is 0-31."

      ::=  { ibmappnNnTopologyFREntry 3 }

ibmappnNnNodeFRType    OBJECT-TYPE
      SYNTAX INTEGER {
                     networknode(1),
                     virtualnode(3)
                     }
      ACCESS read-only
      STATUS mandatory
      DESCRIPTION
           "Type of APPN node."

      ::=  { ibmappnNnTopologyFREntry 4 }

ibmappnNnNodeFRRsn       OBJECT-TYPE
      SYNTAX INTEGER
      ACCESS read-only
      STATUS mandatory
      DESCRIPTION
           "Resource sequence number that is assigned and
            controlled by the network node that owns this
            resource. This is always an even 32-bit number
            unless an error has occurred."

      ::=  { ibmappnNnTopologyFREntry 5 }

ibmappnNnNodeFRRouteAddResist   OBJECT-TYPE
      SYNTAX INTEGER
      ACCESS read-only
      STATUS mandatory
      DESCRIPTION
          "Route addition resistance
          indicates the relative desirability
          of using this node for intermediate session traffic.
          The value, which can be any integer 0-255,
          is used in route computation.  The lower the value,
          the more desirable the node is for intermediate routing."

      ::=  { ibmappnNnTopologyFREntry 6 }

ibmappnNnNodeFRCongested        OBJECT-TYPE
      SYNTAX INTEGER {yes(1), no(2)}
      ACCESS read-only
      STATUS mandatory
      DESCRIPTION
          "Indicates whether this node is congested.
           This node is not be included in route selection
           by other nodes when this congestion exists."

       ::= { ibmappnNnTopologyFREntry 7 }

ibmappnNnNodeFRIsrDepleted OBJECT-TYPE
      SYNTAX INTEGER {yes(1), no(2)}
      ACCESS read-only
      STATUS mandatory
      DESCRIPTION
          "Indicates whether intermediate session
           routing resources are depleted.  This node is
           not included in intermediate route selection
           by other nodes when resources are depleted."

      ::=  { ibmappnNnTopologyFREntry 8 }

ibmappnNnNodeFREndptDepleted OBJECT-TYPE
      SYNTAX INTEGER {yes(1), no(2)}
      ACCESS read-only
      STATUS mandatory
      DESCRIPTION
           "Indicates whether session endpoint resources are depleted."

      ::=  { ibmappnNnTopologyFREntry 9 }

ibmappnNnNodeFRQuiescing     OBJECT-TYPE
      SYNTAX INTEGER {yes(1), no(2)}
      ACCESS read-only
      STATUS mandatory
      DESCRIPTION
          "Indicates whether the node is quiescing.
           This node is not included in route selection
           by other nodes when the node is quiescing."

      ::=  { ibmappnNnTopologyFREntry 10 }

ibmappnNnNodeFRGateway       OBJECT-TYPE
      SYNTAX INTEGER {yes(1), no(2)}
      ACCESS read-only
      STATUS mandatory
      DESCRIPTION
           "Indicates whether the node provide gateway functions."

      ::=  { ibmappnNnTopologyFREntry 11 }

ibmappnNnNodeFRCentralDirectory OBJECT-TYPE
      SYNTAX INTEGER {yes(1), no(2)}
      ACCESS read-only
      STATUS mandatory
      DESCRIPTION
           "Indicates whether the node is central directory."

      ::=  { ibmappnNnTopologyFREntry 12 }

ibmappnNnNodeFRIsr   OBJECT-TYPE
      SYNTAX INTEGER {yes(1), no(2)}
      ACCESS read-only
      STATUS mandatory
      DESCRIPTION
           "Indicates whether the node supports intermediate session
            routing (ISR)."

      ::=  { ibmappnNnTopologyFREntry 13 }

ibmappnNnNodeFRChainSupport OBJECT-TYPE
      SYNTAX INTEGER {yes(1), no(2)}
      ACCESS read-only
      STATUS mandatory
      DESCRIPTION
           "Indicates whether the node supports chaining."

      ::=  { ibmappnNnTopologyFREntry 14 }

--APPN transmission group (TG) table

-- This table describes the TGs associated with
-- the APPN network nodes.
-- The originating node is repeated here to provide a
-- means of correlating the TGs with the nodes.


ibmappnNnTgTopologyFRTable OBJECT-TYPE
      SYNTAX SEQUENCE OF IbmappnNnTgTopologyFREntry
      ACCESS not-accessible
      STATUS mandatory
      DESCRIPTION
           "Portion of the APPN topology database
           that describes all of the APPN transmissions groups
           used by the APPN network nodes."

      ::= { ibmappnNnTopology 4 }

ibmappnNnTgTopologyFREntry OBJECT-TYPE
      SYNTAX IbmappnNnTgTopologyFREntry
      ACCESS not-accessible
      STATUS mandatory
      DESCRIPTION
           "This table is indexed by four columns:
            FRSN, TG owner fully-qualified node name,
            TG destination fully-qualified node name, TG number."

      INDEX
             {ibmappnNnTgFRFrsn,
              ibmappnNnTgFROwner,
              ibmappnNnTgFRDest,
              ibmappnNnTgFRNum}

      ::= { ibmappnNnTgTopologyFRTable 1 }

IbmappnNnTgTopologyFREntry ::= SEQUENCE {

      ibmappnNnTgFROwner      DisplayString,
      ibmappnNnTgFRDest       DisplayString,
      ibmappnNnTgFRNum        INTEGER,
      ibmappnNnTgFRFrsn       INTEGER,
      ibmappnNnTgFREntryTimeLeft INTEGER,

      ibmappnNnTgFRDestVirtual INTEGER,
      ibmappnNnTgFRDlcData    OCTET STRING,

      ibmappnNnTgFRRsn        INTEGER,
      ibmappnNnTgFROperational INTEGER,
      ibmappnNnTgFRQuiescing   INTEGER,
      ibmappnNnTgFRCpCpSession INTEGER,
      ibmappnNnTgFREffCap     INTEGER,
      ibmappnNnTgFRConnCost   INTEGER,
      ibmappnNnTgFRByteCost   INTEGER,
      ibmappnNnTgFRSecurity   INTEGER,
      ibmappnNnTgFRDelay      INTEGER,
      ibmappnNnTgFRModemClass INTEGER,
      ibmappnNnTgFRUsr1       INTEGER,
      ibmappnNnTgFRUsr2       INTEGER,
      ibmappnNnTgFRUsr3       INTEGER}


ibmappnNnTgFROwner  OBJECT-TYPE
      SYNTAX DisplayString (SIZE (3..17))
      ACCESS read-only
      STATUS mandatory
      DESCRIPTION
          "Administratively-assigned name for the
          originating node for this TG. The format
          is NETID.CPNAME and is the same name
          specified in the node table."

      ::=  { ibmappnNnTgTopologyFREntry 1 }

ibmappnNnTgFRDest  OBJECT-TYPE
      SYNTAX DisplayString (SIZE (3..17))
      ACCESS read-only
      STATUS mandatory
      DESCRIPTION
          "Administratively-assigned fully-qualified
          network name for the destination node for this TG."

      ::=  { ibmappnNnTgTopologyFREntry 2 }

ibmappnNnTgFRNum  OBJECT-TYPE
      SYNTAX INTEGER  (0..255)
      ACCESS read-only
      STATUS mandatory
      DESCRIPTION
          "Number associated with this
          transmission group. Range is 0-255."

      ::=  { ibmappnNnTgTopologyFREntry 3 }

ibmappnNnTgFRFrsn             OBJECT-TYPE
      SYNTAX INTEGER (0..65535)
      ACCESS read-only
      STATUS mandatory
      DESCRIPTION
           "Flow reduction sequence numbers (FRSNs) are associated
            with Topology Database Updates (TDUs) and are unique
            only within each APPN network node.  A TDU can be
            associated with multiple APPN resources.  This FRSN
            indicates the last time this resource was updated at
            this node."

      ::=  { ibmappnNnTgTopologyFREntry 4 }

ibmappnNnTgFREntryTimeLeft    OBJECT-TYPE
      SYNTAX INTEGER (0..31)
      ACCESS read-only
      STATUS mandatory
      DESCRIPTION
           "Number of days before deletion of this
            network node TG entry. Range is 0-31."

      ::=  { ibmappnNnTgTopologyFREntry 5 }

ibmappnNnTgFRDestVirtual  OBJECT-TYPE
      SYNTAX INTEGER {yes(1), no(2)}
      ACCESS read-only
      STATUS mandatory
      DESCRIPTION
           "Indicates whether the destination node is
           a virtual node."

      ::=  { ibmappnNnTgTopologyFREntry 6 }

ibmappnNnTgFRDlcData  OBJECT-TYPE
      SYNTAX OCTET STRING  (SIZE (0..9))
      ACCESS read-only
      STATUS mandatory
      DESCRIPTION
           "DLC specific data related to the link connection
           network.
           Token-Ring    - MAC/SAP
           X.25 Switched - dial digits
           X.21 Switched - dial digits
           Circuit Swtch - dial digits"

      ::=  { ibmappnNnTgTopologyFREntry 7 }

ibmappnNnTgFRRsn      OBJECT-TYPE
      SYNTAX INTEGER
      ACCESS read-only
      STATUS mandatory
      DESCRIPTION
           "Current owning node's resource sequence number
            for this resource."

      ::=  { ibmappnNnTgTopologyFREntry 8 }

ibmappnNnTgFROperational OBJECT-TYPE
      SYNTAX INTEGER {yes(1), no(2)}
      ACCESS read-only
      STATUS mandatory
      DESCRIPTION
           "Indicates whether the transmission group
           is operational."

      ::=  { ibmappnNnTgTopologyFREntry 9 }

ibmappnNnTgFRQuiescing OBJECT-TYPE
      SYNTAX INTEGER {yes(1), no(2)}
      ACCESS read-only
      STATUS mandatory
      DESCRIPTION
           "Indicates whether the transmission group
           is quiescing."

      ::=  { ibmappnNnTgTopologyFREntry 10 }

ibmappnNnTgFRCpCpSession OBJECT-TYPE
      SYNTAX INTEGER {yes(1), no(2)}
      ACCESS read-only
      STATUS mandatory
      DESCRIPTION
           "Indicates whether CP-CP sessions are supported on this TG."

      ::=  { ibmappnNnTgTopologyFREntry 11 }


ibmappnNnTgFREffCap   OBJECT-TYPE
      SYNTAX INTEGER
      ACCESS read-only
      STATUS mandatory
      DESCRIPTION
          "The effective capacity is an integer value that indicates
           the kilo bits per second.
           It is derived from the link bandwidth and maximum load
           factor with the range of 0 thru 603,979,776.
           This is an administratively assigned value associated
           with this TG."

      ::=  { ibmappnNnTgTopologyFREntry 12 }

ibmappnNnTgFRConnCost OBJECT-TYPE
      SYNTAX INTEGER (0..255)
      ACCESS read-only
      STATUS mandatory
      DESCRIPTION
          "Cost per connect time: a value representing
           the relative cost per unit of time to use
           the TG. Range is from 0, which means no cost,
           to 255, which indicates maximum cost.
           This is an administratively assigned value associated
           with this TG."


      ::=  { ibmappnNnTgTopologyFREntry 13 }

ibmappnNnTgFRByteCost  OBJECT-TYPE
      SYNTAX INTEGER (0..255)
      ACCESS read-only
      STATUS mandatory
      DESCRIPTION
          "Relative cost of transmitting a byte over this link.
           Range is from 0 (lowest cost) to 255.
           This is an administratively assigned value associated
           with this TG."

      ::=  { ibmappnNnTgTopologyFREntry 14 }

ibmappnNnTgFRSecurity  OBJECT-TYPE
      SYNTAX INTEGER {
                     nonsecure(1),                --X'01'
                     publicSwitchedNetwork(32),   --X'20'
                     undergroundCable(64),        --X'40'
                     secureConduit(96),           --X'60'
                     guardedConduit(128),         --X'80'
                     encrypted(160),              --X'A0'
                     guardedRadiation(192)        --X'C0'
             }
      ACCESS read-only
      STATUS mandatory
      DESCRIPTION
          "The security is represented as an integer with a range of
           1 thru 255 with the most common values enumerated as
           defined above.
           This is an administratively assigned value associated
           with this TG."

      ::=  { ibmappnNnTgTopologyFREntry 15 }

ibmappnNnTgFRDelay  OBJECT-TYPE
      SYNTAX INTEGER {
                     minimum(1),                 --X'00'
                     negligible(384),            --X'4C'
                     terrestrial(9216),          --X'71'
                     packet(147456),             --X'91'
                     long(294912),               --X'99'
                     maximum(2013265920)         --X'FF'
             }
      ACCESS read-only
      STATUS mandatory
      DESCRIPTION
           "Relative amount of time that it takes for a signal to
            travel the length of the logical link.  This time is
            represented in micro seconds, with some of the more
            common values enumerated.
            This is an administratively assigned value associated
            with this TG."

      ::=  { ibmappnNnTgTopologyFREntry 16 }

ibmappnNnTgFRModemClass        OBJECT-TYPE
      SYNTAX INTEGER (0..65535)
      ACCESS read-only
      STATUS mandatory
      DESCRIPTION
           "This is used to have multiple images for a
            connection network.  For a connection network
           it is the same as in the TG vector; for
           a non-connection network it is X'00'."

      ::=  { ibmappnNnTgTopologyFREntry 17 }

ibmappnNnTgFRUsr1  OBJECT-TYPE
      SYNTAX INTEGER (0..255)
      ACCESS read-only
      STATUS mandatory
      DESCRIPTION
          "First user-defined TG characteristic for this TG with
           a range of 0-255.
           This is an administratively assigned value associated
           with this TG."

      ::=  { ibmappnNnTgTopologyFREntry 18 }

ibmappnNnTgFRUsr2  OBJECT-TYPE
      SYNTAX INTEGER (0..255)
      ACCESS read-only
      STATUS mandatory
      DESCRIPTION
          "Second user-defined TG characteristic for this TG with
           a range of 0-255.
           This is an administratively assigned value associated
           with this TG."

      ::=  { ibmappnNnTgTopologyFREntry 19 }

ibmappnNnTgFRUsr3  OBJECT-TYPE
      SYNTAX INTEGER (0..255)
      ACCESS read-only
      STATUS mandatory
      DESCRIPTION
          "Third user-defined TG characteristic for this TG with
           a range of 0-255.
           This is an administratively assigned value associated
           with this TG."

      ::=  { ibmappnNnTgTopologyFREntry 20 }


-- ************** The APPN Local Topology Group ************

ibmappnLocalTopology   OBJECT IDENTIFIER ::= { ibmappn 3 }
ibmappnLocalThisNode   OBJECT IDENTIFIER ::= { ibmappnLocalTopology 1 }
ibmappnLocalGeneral    OBJECT IDENTIFIER ::= { ibmappnLocalThisNode   1}
ibmappnLocalNnSpecific OBJECT IDENTIFIER ::= { ibmappnLocalThisNode   2}
ibmappnLocalTg         OBJECT IDENTIFIER ::= { ibmappnLocalThisNode   3}
ibmappnLocalEnTopology OBJECT IDENTIFIER ::= { ibmappnLocalTopology 2 }

-- The LocalEnNodeTable and LocalEnTgTable will replace these OIs
--ibmappnLocalEnNode   OBJECT IDENTIFIER ::= { ibmappnLocalEnTopology 1}
--ibmappnLocalEnTg     OBJECT IDENTIFIER ::= { ibmappnLocalEnTopology 2}

--This MIB Group represents the local topology
--maintained in both APPN end nodes and network nodes.
--Although the same control vectors are used for both network
--and local topology, many of the attributes only apply to network
--nodes.  This MIB group defines the required objects for retrieval
--of information about this node and the objects that represent
--the local topology about end nodes.
--
--This node could be either an network node or an end node. The
--definition must address both cases.
--
--1  Information about this node
--   a  General information about this node, both NN and ENs.
--   b  Information about this node that applies only to NNs.
--   c  TG table      (repeated for each TG this node owns)
--
--2  Information about the end nodes known to this network node
--   (THIS SECTION ONLY APPLIES TO NETWORK NODES)
--   a  End node table (entry for each end node )
--   b  TG table      (repeated for each TG owned by the end nodes)
--
--
----
-- General information section

ibmappnLocalNodeName    OBJECT-TYPE
      SYNTAX DisplayString (SIZE (3..17))
      ACCESS read-only
      STATUS mandatory
      DESCRIPTION
          "Administratively-assigned fully-qualified name
          for this node. Format is NETID.CPNAME."

      ::=  { ibmappnLocalGeneral 1 }

ibmappnLocalNodeType    OBJECT-TYPE
      SYNTAX INTEGER {
                     networknode(1),
                     endnode(2),
                     len(4)
                     }
      ACCESS read-only
      STATUS mandatory
      DESCRIPTION
           "Type of APPN node."

      ::=  { ibmappnLocalGeneral 2 }

-- Network node unique information
ibmappnLocalNnRsn       OBJECT-TYPE
      SYNTAX INTEGER
      ACCESS read-only
      STATUS mandatory
      DESCRIPTION
           "Resource sequence number is assigned and
            controlled by the network node that owns this
            resource.  This is always an even unsigned
            number unless an error has occurred."

      ::=  { ibmappnLocalNnSpecific  1 }

ibmappnLocalNnRouteAddResist   OBJECT-TYPE
      SYNTAX INTEGER
      ACCESS read-only
      STATUS mandatory
      DESCRIPTION
          "Route addition resistance
          indicates the relative desirability
          of using this node for intermediate session traffic.
          The value, which can be any integer 0-255,
          is used in route computation.  The lower the value,
          the more desirable the node is for intermediate routing."

      ::=  { ibmappnLocalNnSpecific 2 }

ibmappnLocalNnCongested        OBJECT-TYPE
      SYNTAX INTEGER {yes(1), no(2)}
      ACCESS read-only
      STATUS mandatory
      DESCRIPTION
           "Indicates whether this node is congested.
            Other network nodes stop routing traffic to
            this node while this flag is on."

       ::= { ibmappnLocalNnSpecific 3 }

ibmappnLocalNnIsrDepleted OBJECT-TYPE
      SYNTAX INTEGER {yes(1), no(2)}
      ACCESS read-only
      STATUS mandatory
      DESCRIPTION
           "Indicate whether intermediated session
            routing resources are depleted.
            Other network nodes stop routing traffic through
            this node while this flag is on."

      ::=  { ibmappnLocalNnSpecific 4 }

ibmappnLocalNnEndptDepleted OBJECT-TYPE
      SYNTAX INTEGER {yes(1), no(2)}
      ACCESS read-only
      STATUS mandatory
      DESCRIPTION
           "Indicates whether session endpoint resources
            are depleted."

      ::=  { ibmappnLocalNnSpecific 5 }

ibmappnLocalNnQuiescing     OBJECT-TYPE
      SYNTAX INTEGER {yes(1), no(2)}
      ACCESS read-only
      STATUS mandatory
      DESCRIPTION
           "Indicates whether the node is quiescing."

      ::=  { ibmappnLocalNnSpecific 6 }

ibmappnLocalNnGateway       OBJECT-TYPE
      SYNTAX INTEGER {yes(1), no(2)}
      ACCESS read-only
      STATUS mandatory
      DESCRIPTION
           "Indicates whether the node is a gateway."

      ::=  { ibmappnLocalNnSpecific 7 }

ibmappnLocalNnCentralDirectory OBJECT-TYPE
      SYNTAX INTEGER {yes(1), no(2)}
      ACCESS read-only
      STATUS mandatory
      DESCRIPTION
           "Indicates whether the node is a central directory."

      ::=  { ibmappnLocalNnSpecific 8 }

ibmappnLocalNnIsr   OBJECT-TYPE
      SYNTAX INTEGER {yes(1), no(2)}
      ACCESS read-only
      STATUS mandatory
      DESCRIPTION
           "Indicates whether the node supports intermediate session routing."

      ::=  { ibmappnLocalNnSpecific 9 }

ibmappnLocalNnChainSupport OBJECT-TYPE
      SYNTAX INTEGER {yes(1), no(2)}
      ACCESS read-only
      STATUS mandatory
      DESCRIPTION
           "Indicates whether the node supports chaining."

      ::=  { ibmappnLocalNnSpecific 10 }

ibmappnLocalNnFrsn     OBJECT-TYPE
      SYNTAX INTEGER
      ACCESS read-only
      STATUS mandatory
      DESCRIPTION
          "Flow reduction sequence numbers (FRSNs) are associated
           with Topology Database Updates (TDUs) and are unique
           only within each APPN network node.  A TDU can be
           associated with multiple APPN resources. This object
           is the last FRSN sent in a topology update to
           adjacent network nodes."

      ::=  { ibmappnLocalNnSpecific 11 }

-- Local TG information
-- APPN Transmission Group (TG) Table

-- This table describes the TGs associated with
-- this node only.

ibmappnLocalTgTable OBJECT-TYPE
      SYNTAX SEQUENCE OF IbmappnLocalTgEntry
      ACCESS not-accessible
      STATUS mandatory
      DESCRIPTION
           "TG Table describes all of the TGs owned by this
            node.  The TG destination can be a virtual
            node, network node, len, or end node."

      ::= { ibmappnLocalTg 1 }

ibmappnLocalTgEntry OBJECT-TYPE
      SYNTAX IbmappnLocalTgEntry
      ACCESS not-accessible
      STATUS mandatory
      DESCRIPTION
           "This table is indexed by the destination CPname
            and the TG number."

      INDEX
             {ibmappnLocalTgDest,
              ibmappnLocalTgNum}

      ::= { ibmappnLocalTgTable 1 }

IbmappnLocalTgEntry ::= SEQUENCE {

      ibmappnLocalTgDest       DisplayString,
      ibmappnLocalTgNum        INTEGER,
      ibmappnLocalTgDestVirtual INTEGER,
      ibmappnLocalTgDlcData    OCTET STRING,

      ibmappnLocalTgRsn        INTEGER,
      ibmappnLocalTgQuiescing  INTEGER,
      ibmappnLocalTgOperational INTEGER,
      ibmappnLocalTgCpCpSession INTEGER,
      ibmappnLocalTgEffCap     INTEGER,
      ibmappnLocalTgConnCost   INTEGER,
      ibmappnLocalTgByteCost   INTEGER,
      ibmappnLocalTgSecurity   INTEGER,
      ibmappnLocalTgDelay      INTEGER,
      ibmappnLocalTgModemClass INTEGER,
      ibmappnLocalTgUsr1       INTEGER,
      ibmappnLocalTgUsr2       INTEGER,
      ibmappnLocalTgUsr3       INTEGER
                                   }

ibmappnLocalTgDest  OBJECT-TYPE
      SYNTAX DisplayString (SIZE (3..17))
      ACCESS read-only
      STATUS mandatory
      DESCRIPTION
           "Administratively-assigned name for the
           destination node for this TG.
           This is the fully-qualified network node
           name."

      ::=  { ibmappnLocalTgEntry 1 }

ibmappnLocalTgNum  OBJECT-TYPE
      SYNTAX INTEGER
      ACCESS read-only
      STATUS mandatory
      DESCRIPTION
           "Number associated with this transmission group."

      ::=  { ibmappnLocalTgEntry 2 }

ibmappnLocalTgDestVirtual  OBJECT-TYPE
      SYNTAX INTEGER {yes(1), no(2)}
      ACCESS read-only
      STATUS mandatory
      DESCRIPTION
           "Indicates whether the destination node is
           a Virtual node."
      ::=  { ibmappnLocalTgEntry 3 }

ibmappnLocalTgDlcData  OBJECT-TYPE
      SYNTAX OCTET STRING  (SIZE (0..9))
      ACCESS read-only
      STATUS mandatory
      DESCRIPTION
           "DLC specific data related to the link connection
           network.
           Token-Ring    - MAC/SAP
           X.25 Switched - dial digits
           X.21 Switched - dial digits
           Circuit Swtch - dial digits"

      ::=  { ibmappnLocalTgEntry 4 }

ibmappnLocalTgRsn       OBJECT-TYPE
      SYNTAX INTEGER
      ACCESS read-only
      STATUS mandatory
      DESCRIPTION
           "The resource sequence number is assigned and
            controlled by the network node that owns this
            resource.  This is always an even unsigned
            number unless an error has occurred."

      ::=  { ibmappnLocalTgEntry 5 }

ibmappnLocalTgQuiescing OBJECT-TYPE
      SYNTAX INTEGER {yes(1), no(2)}
      ACCESS read-only
      STATUS mandatory
      DESCRIPTION
           "Indicates whether the Transmission Group
           is quiescing."

      ::=  { ibmappnLocalTgEntry 6 }

ibmappnLocalTgOperational OBJECT-TYPE
      SYNTAX INTEGER {yes(1), no(2)}
      ACCESS read-only
      STATUS mandatory
      DESCRIPTION
           "Indicates whether the Transmission Group
           is operational."

      ::=  { ibmappnLocalTgEntry 7 }

ibmappnLocalTgCpCpSession OBJECT-TYPE
      SYNTAX INTEGER {yes(1), no(2)}
      ACCESS read-only
      STATUS mandatory
      DESCRIPTION
           "Indicates whether the CP-CP Sessions are
           supported on this TG."

      ::=  { ibmappnLocalTgEntry 8 }

ibmappnLocalTgEffCap   OBJECT-TYPE
      SYNTAX INTEGER
      ACCESS read-only
      STATUS mandatory
      DESCRIPTION
          "The effective capacity is an integer value that indicates
           the actual kilo bits per second.
           It is derived from the link bandwidth and maximum load
           factor with the range of 0 thru 603,979,776."

      ::=  { ibmappnLocalTgEntry 9 }

ibmappnLocalTgConnCost OBJECT-TYPE
      SYNTAX INTEGER (0..255)
      ACCESS read-only
      STATUS mandatory
      DESCRIPTION
           "Cost per connect time: a value representing
           the relative cost per unit of time to use
           the TG. Range is from 0, which means no cost,
           to 255."

      ::=  { ibmappnLocalTgEntry 10 }

ibmappnLocalTgByteCost  OBJECT-TYPE
      SYNTAX INTEGER (0..255)
      ACCESS read-only
      STATUS mandatory
      DESCRIPTION
          "Relative cost of transmitting a byte over this link.
          Range is from 0 (lowest cost) to 255."

      ::=  { ibmappnLocalTgEntry 11 }

ibmappnLocalTgSecurity  OBJECT-TYPE
      SYNTAX INTEGER {
                     nonsecure(1),                --X'01'
                     publicSwitchedNetwork(32),   --X'20'
                     undergroundCable(64),        --X'40'
                     secureConduit(96),           --X'60'
                     guardedConduit(128),         --X'80'
                     encrypted(160),              --X'A0'
                     guardedRadiation(192)        --X'C0'
             }
      ACCESS read-only
      STATUS mandatory
      DESCRIPTION
           "Security level for this TG."

      ::=  { ibmappnLocalTgEntry 12 }

ibmappnLocalTgDelay  OBJECT-TYPE
      SYNTAX INTEGER {
                     minimum(1),                 --X'00'
                     negligible(384),            --X'4C'
                     terrestrial(9216),          --X'71'
                     packet(147456),             --X'91'
                     long(294912),               --X'99'
                     maximum(2013265920)         --X'FF'
             }
      ACCESS read-only
      STATUS mandatory
      DESCRIPTION
           "Relative amount of time that it takes for a signal to
            travel the length of the logical link.  This time is
            represented in micro seconds, with some of the more
            common values enumerated."

      ::=  { ibmappnLocalTgEntry 13 }

ibmappnLocalTgModemClass  OBJECT-TYPE
      SYNTAX INTEGER
      ACCESS read-only
      STATUS mandatory
      DESCRIPTION
           "This is used to have multiple images for a
            connection network.  For a connection network
            it is the same as in the TG vector and for
            a non-connection network it is zero."

      ::=  { ibmappnLocalTgEntry 14 }

ibmappnLocalTgUsr1  OBJECT-TYPE
      SYNTAX INTEGER (0..255)
      ACCESS read-only
      STATUS mandatory
      DESCRIPTION
          "Value of the first user-defined TG
          characteristic for this TG.
          Range is 0-255."

      ::=  { ibmappnLocalTgEntry 15 }

ibmappnLocalTgUsr2  OBJECT-TYPE
      SYNTAX INTEGER (0..255)
      ACCESS read-only
      STATUS mandatory
      DESCRIPTION
          "Value of the second user-defined TG
          characteristic for this TG.
          Range is 0-255."

      ::=  { ibmappnLocalTgEntry 16 }

ibmappnLocalTgUsr3  OBJECT-TYPE
      SYNTAX INTEGER (0..255)
      ACCESS read-only
      STATUS mandatory
      DESCRIPTION
          "Value of the third user-defined TG
          characteristic for this TG.
          Range is 0-255."

      ::=  { ibmappnLocalTgEntry 17 }

-- This section applies only to network nodes
-- End node topology known to serving network node
--  The first table contains information about all end nodes
--  known to this node.
--
--  The TG  table contains information about all of the TGs owned
--  by these end nodes.

ibmappnLocalEnTable OBJECT-TYPE
      SYNTAX SEQUENCE OF IbmappnLocalEnEntry
      ACCESS not-accessible
      STATUS mandatory
      DESCRIPTION
           "Portion of the APPN topology
            database that describes the end
            nodes known to this node."

      ::= { ibmappnLocalEnTopology 1 }

ibmappnLocalEnEntry OBJECT-TYPE
      SYNTAX IbmappnLocalEnEntry
      ACCESS not-accessible
      STATUS mandatory
      DESCRIPTION
           "This table is indexed by the end node CPname."

      INDEX
             {ibmappnLocalEnName}

      ::= { ibmappnLocalEnTable 1 }

IbmappnLocalEnEntry ::= SEQUENCE {

      ibmappnLocalEnName                     DisplayString,
      ibmappnLocalEnEntryTimeLeft            INTEGER,
      ibmappnLocalEnType                     INTEGER
                          }

ibmappnLocalEnName    OBJECT-TYPE
      SYNTAX DisplayString (SIZE (3..17))
      ACCESS read-only
      STATUS mandatory
      DESCRIPTION
          "Administratively-assigned fully-qualified
          name of end node in the format NETID.CPNAME."

      ::=  { ibmappnLocalEnEntry 1 }

ibmappnLocalEnEntryTimeLeft   OBJECT-TYPE
      SYNTAX INTEGER (0..31)
      ACCESS read-only
      STATUS mandatory
      DESCRIPTION
          "Number of days before deletion of this
           end node entry. Range is 0-31."

      ::=  { ibmappnLocalEnEntry 2 }

ibmappnLocalEnType    OBJECT-TYPE
      SYNTAX INTEGER {
                     endnode(2),
                     len(4)
                     }
      ACCESS read-only
      STATUS mandatory
      DESCRIPTION
          "Type of APPN node (must always be a len or end node)."

      ::=  { ibmappnLocalEnEntry 3 }

--APPN Local End node Transmission Group (TG) table

-- This table describes the TGs associated with
-- all of the end nodes known to this node.

ibmappnLocalEnTgTable OBJECT-TYPE
      SYNTAX SEQUENCE OF IbmappnLocalEnTgEntry
      ACCESS not-accessible
      STATUS mandatory
      DESCRIPTION
           "Table describing all of the TGs owned by the
            end nodes known to this node.
            The TG destination can be a virtual
            node, network node, or end node."

      ::= { ibmappnLocalEnTopology 2 }

ibmappnLocalEnTgEntry OBJECT-TYPE
      SYNTAX IbmappnLocalEnTgEntry
      ACCESS not-accessible
      STATUS mandatory
      DESCRIPTION
           "This table requires multiple indexes to uniquely
            identify each TG. They are originating CPname,
            destination CPname, and the TG number."

      INDEX
             {ibmappnLocalEnTgOrigin,
              ibmappnLocalEnTgDest,
              ibmappnLocalEnTgNum}

      ::= { ibmappnLocalEnTgTable 1 }

IbmappnLocalEnTgEntry ::= SEQUENCE {
      ibmappnLocalEnTgOrigin     DisplayString,
      ibmappnLocalEnTgDest       DisplayString,
      ibmappnLocalEnTgNum        INTEGER,
      ibmappnLocalEnTgEntryTimeLeft INTEGER,

      ibmappnLocalEnTgDestVirtual INTEGER,
      ibmappnLocalEnTgDlcData    OCTET STRING,

      ibmappnLocalEnTgOperational INTEGER,
      ibmappnLocalEnTgCpCpSession INTEGER,
      ibmappnLocalEnTgEffCap     INTEGER,
      ibmappnLocalEnTgConnCost   INTEGER,
      ibmappnLocalEnTgByteCost   INTEGER,
      ibmappnLocalEnTgSecurity   INTEGER,
      ibmappnLocalEnTgDelay      INTEGER,
      ibmappnLocalEnTgModemClass INTEGER,
      ibmappnLocalEnTgUsr1       INTEGER,
      ibmappnLocalEnTgUsr2       INTEGER,
      ibmappnLocalEnTgUsr3       INTEGER
                                    }

ibmappnLocalEnTgOrigin      OBJECT-TYPE
      SYNTAX DisplayString (SIZE (3..17))
      ACCESS read-only
      STATUS mandatory
      DESCRIPTION
          "Administratively-assigned name for the
           origination node for this TG.
           This is the fully-qualified network name."

      ::=  { ibmappnLocalEnTgEntry 1 }

ibmappnLocalEnTgDest        OBJECT-TYPE
      SYNTAX DisplayString (SIZE (3..17))
      ACCESS read-only
      STATUS mandatory
      DESCRIPTION
          "Administratively-assigned name for the
           destination node for this TG.
           This is the fully-qualified network name."

      ::=  { ibmappnLocalEnTgEntry 2 }

ibmappnLocalEnTgNum  OBJECT-TYPE
      SYNTAX INTEGER
      ACCESS read-only
      STATUS mandatory
      DESCRIPTION
           "Number associated with this transmission group."

      ::=  { ibmappnLocalEnTgEntry 3 }

ibmappnLocalEnTgEntryTimeLeft   OBJECT-TYPE
      SYNTAX INTEGER (0..31)
      ACCESS read-only
      STATUS mandatory
      DESCRIPTION
          "Number of days before deletion of this
           end node TG entry. Range is 0-31."

      ::=  { ibmappnLocalEnTgEntry 4 }

ibmappnLocalEnTgDestVirtual  OBJECT-TYPE
      SYNTAX INTEGER {yes(1), no(2)}
      ACCESS read-only
      STATUS mandatory
      DESCRIPTION
           "Indicates whether the destination node is
           a virtual node."

      ::=  { ibmappnLocalEnTgEntry 5 }

ibmappnLocalEnTgDlcData  OBJECT-TYPE
      SYNTAX OCTET STRING
      ACCESS read-only
      STATUS mandatory
      DESCRIPTION
           "DLC specific data related to the link connection
           network.
           Token-Ring    - MAC/SAP
           X.25 Switched - dial digits
           X.21 Switched - dial digits
           Circuit Swtch - dial digits"

      ::=  { ibmappnLocalEnTgEntry 6 }

ibmappnLocalEnTgOperational OBJECT-TYPE
      SYNTAX INTEGER {yes(1), no(2)}
      ACCESS read-only
      STATUS mandatory
      DESCRIPTION
           "Indicates whether the Transmission Group is operational."

      ::=  { ibmappnLocalEnTgEntry 7 }

ibmappnLocalEnTgCpCpSession OBJECT-TYPE
      SYNTAX INTEGER {yes(1), no(2)}
      ACCESS read-only
      STATUS mandatory
      DESCRIPTION
          "Indicates whether CP-CP sessions are supported on this TG."

      ::=  { ibmappnLocalEnTgEntry 8 }

ibmappnLocalEnTgEffCap   OBJECT-TYPE
      SYNTAX INTEGER
      ACCESS read-only
      STATUS mandatory
      DESCRIPTION
          "The effective capacity is an integer value that indicates
           the actual kilo bits per second.
           It is derived from the link bandwidth and maximum load
           factor with the range of 0 thru 603,979,776."

      ::=  { ibmappnLocalEnTgEntry 9 }

ibmappnLocalEnTgConnCost OBJECT-TYPE
      SYNTAX INTEGER (0..255)
      ACCESS read-only
      STATUS mandatory
      DESCRIPTION
           "Cost per connect time: a value representing
           the relative cost per unit of time to use
           the TG. Range is from 0, which means no cost,
           to 255."

      ::=  { ibmappnLocalEnTgEntry 10 }

ibmappnLocalEnTgByteCost  OBJECT-TYPE
      SYNTAX INTEGER (0..255)
      ACCESS read-only
      STATUS mandatory
      DESCRIPTION
          "Relative cost of transmitting a byte over this link.
          Range is from 0, which means no cost, to 255."

      ::=  { ibmappnLocalEnTgEntry 11 }

ibmappnLocalEnTgSecurity  OBJECT-TYPE
      SYNTAX INTEGER {
                     nonsecure(1),                --X'01'
                     publicSwitchedNetwork(32),   --X'20'
                     undergroundCable(64),        --X'40'
                     secureConduit(96),           --X'60'
                     guardedConduit(128),         --X'80'
                     encrypted(160),              --X'A0'
                     guardedRadiation(192)        --X'C0'
                     }
      ACCESS read-only
      STATUS mandatory
      DESCRIPTION
           "Security level for this TG."

      ::=  { ibmappnLocalEnTgEntry 12 }

ibmappnLocalEnTgDelay  OBJECT-TYPE
      SYNTAX INTEGER {
                     minimum(1),                 --X'00'
                     negligible(384),            --X'4C'
                     terrestrial(9216),          --X'71'
                     packet(147456),             --X'91'
                     long(294912),               --X'99'
                     maximum(2013265920)         --X'FF'
             }
      ACCESS read-only
      STATUS mandatory
      DESCRIPTION
           "Relative amount of time that it takes for a signal to
            travel the length of the logical link.  This time is
            represented in micro seconds, with some of the more
            common values enumerated."

      ::=  { ibmappnLocalEnTgEntry 13 }

ibmappnLocalEnTgModemClass  OBJECT-TYPE
      SYNTAX INTEGER (0..65535)
      ACCESS read-only
      STATUS mandatory
      DESCRIPTION
           "This is used to have multiple images for a
            connection network.  For a connection network
            it is the same as in the TG vector and for
             a non connection network it is zero."

      ::=  { ibmappnLocalEnTgEntry 14 }

ibmappnLocalEnTgUsr1  OBJECT-TYPE
      SYNTAX INTEGER (0..255)
      ACCESS read-only
      STATUS mandatory
      DESCRIPTION
          "First user-defined TG characteristic
          for this TG. Range of values is 0-255."

      ::=  { ibmappnLocalEnTgEntry 15 }

ibmappnLocalEnTgUsr2  OBJECT-TYPE
      SYNTAX INTEGER (0..255)
      ACCESS read-only
      STATUS mandatory
      DESCRIPTION
          "Second user-defined TG characteristic
           for this TG. Range of values is 0-255."

      ::=  { ibmappnLocalEnTgEntry 16 }

ibmappnLocalEnTgUsr3  OBJECT-TYPE
      SYNTAX INTEGER (0..255)
      ACCESS read-only
      STATUS mandatory
      DESCRIPTION
          "Third user-defined TG characteristic
           for this TG. Range of values is 0-255."

      ::=  { ibmappnLocalEnTgEntry 17 }

-- ************** The APPN Directory group ************
ibmappnDir      OBJECT IDENTIFIER ::= { ibmappn 5  }
ibmappnDirPerf  OBJECT IDENTIFIER ::= { ibmappnDir 1 }

-- The APPN Directory Group

-- The APPN Directory Database

-- Each APPN network node maintains directories containing
-- information on which LUs (applications) are available and
-- where they are located.  LUs can be located within an APPN
-- network node or in any of the attached end nodes.

--  Max Cache Directory Entries
--  Current Number of Cache Entries
--  Current Number Home Entries
--  Current Number of Registered Entries
--  number of directed locates sent
--  number of directed locates received
--  number of broadcast locates sent
--  number of broadcast locates received
--  Number of locates returned with a found
--  Number of locates returned with a not found
--  Number of outstanding Locates
--  Directory table  (Repeated for each Serving NN)

  --  Serving Network Node Fully Qualified CP Name

--  LU Groups within Directory table (one for each LU)

  --  Fully-qualified LU Name
  --  Owning fully-qualified CP Name
 --  TP Name
  --  Resource location     (local/domain/cross-domain)
  --  Entry type (home,Register/cache)
  --  Wildcard              (yes/no)

ibmappnDirMaxCaches OBJECT-TYPE
      SYNTAX INTEGER
      ACCESS read-only
      STATUS mandatory
      DESCRIPTION
           "Maximum number of cache entries allowed. This
           is an administratively assigned value."

      ::=  { ibmappnDirPerf 1 }

ibmappnDirCurCaches OBJECT-TYPE
      SYNTAX Gauge
      ACCESS read-only
      STATUS mandatory
      DESCRIPTION
           "Current number of cache entries."

      ::=  { ibmappnDirPerf 2 }

ibmappnDirCurHomeEntries  OBJECT-TYPE
      SYNTAX Gauge
      ACCESS read-only
      STATUS mandatory
      DESCRIPTION
           "Current number of home entries."

      ::=  { ibmappnDirPerf 3 }

ibmappnDirRegEntries OBJECT-TYPE
      SYNTAX Gauge
      ACCESS read-only
      STATUS mandatory
      DESCRIPTION
           "Current number of registered entries."

      ::=  { ibmappnDirPerf 4 }

ibmappnDirInLocates    OBJECT-TYPE
      SYNTAX Counter
      ACCESS read-only
      STATUS mandatory
      DESCRIPTION
           "Number of directed locates received."

      ::=  { ibmappnDirPerf 5 }

ibmappnDirInBcastLocates  OBJECT-TYPE
      SYNTAX Counter
      ACCESS read-only
      STATUS mandatory
      DESCRIPTION
           "Number of broadcast locates received."

      ::=  { ibmappnDirPerf 6 }

ibmappnDirOutLocates   OBJECT-TYPE
      SYNTAX Counter
      ACCESS read-only
      STATUS mandatory
      DESCRIPTION
           "Number of directed locates sent."

      ::=  { ibmappnDirPerf 7 }

ibmappnDirOutBcastLocates   OBJECT-TYPE
      SYNTAX Counter
      ACCESS read-only
      STATUS mandatory
      DESCRIPTION
           "Number of broadcast locates sent."

      ::=  { ibmappnDirPerf 8 }

ibmappnDirNotFoundLocates   OBJECT-TYPE
      SYNTAX Counter
      ACCESS read-only
      STATUS mandatory
      DESCRIPTION
           "Number of directed locates returned with a 'not found'."

      ::=  { ibmappnDirPerf 9 }

ibmappnDirNotFoundBcastLocates OBJECT-TYPE
      SYNTAX Counter
      ACCESS read-only
      STATUS mandatory
      DESCRIPTION
           "Number of broadcast locates returned with
           a not found."

      ::=  { ibmappnDirPerf 10 }

ibmappnDirLocateOutstands  OBJECT-TYPE
      SYNTAX Gauge
      ACCESS read-only
      STATUS mandatory
      DESCRIPTION
          "Current number of outstanding locates,
          both directed and broadcast.  This value
          varies. A value of zero indicates
          that no locates are unanswered."

      ::=  { ibmappnDirPerf 11 }


--APPN Directory table

-- This table contains information about all known
-- LUs and TPs.

ibmappnDirTable OBJECT-TYPE
      SYNTAX SEQUENCE OF IbmappnDirEntry
      ACCESS not-accessible
      STATUS mandatory
      DESCRIPTION
           "Table containing information about
           all known LUs and TPs."

      ::= { ibmappnDir 2 }

ibmappnDirEntry OBJECT-TYPE
      SYNTAX IbmappnDirEntry
      ACCESS not-accessible
      STATUS mandatory
      DESCRIPTION
           "This table is indexed by the LU name."

      INDEX
             {ibmappnDirLuName}

      ::= { ibmappnDirTable 1 }

IbmappnDirEntry ::= SEQUENCE {
      ibmappnDirLuName                   DisplayString,
      ibmappnDirServerName               DisplayString,
      ibmappnDirLuOwnerName              DisplayString,
      ibmappnDirLuLocation               INTEGER,
      ibmappnDirType                     INTEGER,
      ibmappnDirWildCard                 INTEGER
                             }

ibmappnDirLuName          OBJECT-TYPE
      SYNTAX DisplayString  (SIZE (3..17))
      ACCESS read-only
      STATUS mandatory
      DESCRIPTION
          "Fully-qualified network LU name in the
           domain of the serving network node."

      ::=  { ibmappnDirEntry 1 }

ibmappnDirServerName        OBJECT-TYPE
      SYNTAX DisplayString (SIZE (3..17))
      ACCESS read-only
      STATUS mandatory
      DESCRIPTION
           "Fully-qualified control point (CP) name of the
            network node server.  For unassociated end node
            entries, the end node fully-qualified name
            is returned."

      ::=  { ibmappnDirEntry 2 }


ibmappnDirLuOwnerName    OBJECT-TYPE
      SYNTAX DisplayString (SIZE (3..17))
      ACCESS read-only
      STATUS mandatory
      DESCRIPTION
          "Fully-qualified CP name of the node at which
           the LU is located.  This name is the same as the
           serving NN name when the LU is located at a
           network node or an unassociated end node.  It is
           also the same as the fully-qualified LU name
           when this is the control point LU for this node."

      ::=  { ibmappnDirEntry 3 }


ibmappnDirLuLocation        OBJECT-TYPE
      SYNTAX INTEGER {
                     local(1),     --Local
                     domain(2),    --Domain
                     xdomain(3)    --Cross Domain
                     }
      ACCESS read-only
      STATUS mandatory
      DESCRIPTION
          "Specifies the location of the LU."

      ::=  { ibmappnDirEntry 4 }

ibmappnDirType             OBJECT-TYPE
      SYNTAX INTEGER {
                     home(1),      --defined as home entry
                     cache(2),     --learned over time
                     registered(3) --registered by end node
                     }
      ACCESS read-only
      STATUS mandatory
      DESCRIPTION
           "Directory types are:
            1 - Home
                  The LU is in the domain of the local network node
                  and the LU information has been configured at the
                  local node.

            2 - Cache
                  The LU has previously been located by a broadcast
                  search and the location information has been saved.

            3 - Register
                  The LU is at an end node that is in the domain
                  of the local network node.  Registered entries
                  are registered by the served end node."

      ::=  { ibmappnDirEntry 5 }


ibmappnDirWildCard         OBJECT-TYPE
      SYNTAX INTEGER {
                      other(1),
                      explicit-entry(2),
                      partial-wildcard(3),
                      full-wildcard(4)
                     }
      ACCESS read-only
      STATUS mandatory
      DESCRIPTION
          "1 - Other means unknown type of LU entry.
           2 - Expliced-entry means the full LUNAME will be used
               for locating this LU.
           3 - Partial-wildcard means only the non-blank portions
               of the LUNAME will be used for locating this LU.
           4 - Full-wildcard means all LUNAMES will be directed
               to this LU."

      ::=  { ibmappnDirEntry 6 }

-- ************** The APPN Class of Service group ************

ibmappnCos  OBJECT IDENTIFIER ::= { ibmappn 6  } --APPN COS

-- The APPN Class of Service (COS)

-- Class of Service is a means of expressing the quality of the routes
-- and the transmission priority of traffic which flows on these routes.
-- The quality of routes is specified by two tables, a COS weight table
-- for TGs and a COS weight table for nodes.  These COS tables are
-- administratively assigned at each APPN node. Seven default tables

-- for TGs and a COS weight table for Nodes.  These COS tables are
-- administratively assigned at each APPN node with seven default tables
-- being provided by IBM.
--
--
--  COS Name
--        Unqualified name identifying the class of service.
--  Transmission priority
--        Transmission priority associated with this class of service
--   COS Node Row Table
--          At least one node row must be specified. The default
--          COS tables specify 8 rows.
--     Node Row Weight
--            Numeric value between 0 and 255 inclusive indicating
--            the weight associated with this row.
--     Route addition resist (min)
--            Numeric value between 0 and 255 inclusive indicating
--            the minimum route addition resistance for this row.
--     Route addition resist (max)
--            Numeric value between 0 and 255 inclusive indicating
--            the maximum route addition resistance for this row.
--     Congestion          (min)
--            Indicates whether this class of service for this row
--            will accept congestion. Yes or No must be specified.
--     Congestion          (max)
--            Indicates whether this Class of Service for this row
--            will accept congestion. Yes or No must be specified.
--
--   COS TG Row table
--          At least one TG row must be specified with the defaults
--          COS tables specify 8 rows.
--     TG Row Weight
--            Numeric value between 0 and 255 inclusive indicating
--            the weight associated with this row.
--     Effective capacity  (min)
--            Indicates the lowest acceptable value for this row.
--     Effective capacity  (max)
--            Indicates the highest required value for this row.
--     Cost per connect time  (min)
--            Indicates the lowest connect cost per unit time value
--            for this row.  This value is between 0 and 255 inclusive.
--     Cost per connect time  (max)
--            Indicates the highest connect cost per unit time value
--            for this row.  This value is between 0 and 255 inclusive.
--     Cost per byte       (min)
--            Indicates the lowest cost per byte value
--            for this row.  This value is between 0 and 255 inclusive.
--     Cost per byte       (max)
--            Indicates the highest cost per byte value
--            for this row.  This value is between 0 and 255 inclusive.
--     Security            (min)
--            Indicates the lowest acceptable value for security
--            for this row.  This value is one of seven values.
--     Security            (max)
--            Indicates the highest acceptable value for security
--            for this row.  This value is one of seven values.
--     Propagation delay   (min)
--            Indicates the lowest acceptable propagation delay value
--            for this row.
--     Propagation delay   (max)
--            Indicates the highest acceptable propagation delay value
--            for this row.
--     User defined 1      (min)
--            Indicates the lowest acceptable value
--            for this row.  This value is between 0 and 255 inclusive.
--     User defined 1      (max)
--            Indicates the highest acceptable value
--            for this row.  This value is between 0 and 255 inclusive.
--     User defined 2      (min)
--            Same as user defined 1
--     User defined 2      (max)
--            Same as user defined 1
--     User defined 3      (min)
--            Same as user defined 1
--     User defined 3      (max)
--            Same as user defined 1
--
--
--
--Due to SNMP ASN.1 limitations the COS table is defined
--in the following format.
--
-- MODE name table
--  MODE Name (index)
--  COS Name
--
-- COS name table
--  COS Name (index)
--  Transmission priority
--
-- COS node row table
--  COS Name (index1)
--  Index2
--  Node Row Weight
--  Rte addition resist (min)
--  Rte addition resist (max)
--  Congestion          (min)
--  Congestion          (max)
--
-- COS TG row table
--  COS Name (index1)
--  Index
--  TG Row Weight
--  Effective capacity  (min)
--  Effective capacity  (max)
--  Cost per conn time  (min)
--  Cost per conn time  (max)
--  cost per byte       (min)
--  cost per byte       (max)
--  Security            (min)
--  Security            (max)
--  Propagation delay   (min)
--  Propagation delay   (max)
--  User defined 1      (min)
--  User defined 1      (max)
--  User defined 2      (min)
--  User defined 2      (max)
--  User defined 3      (min)
--  User defined 3      (max)
--
-- *****************************************************************************

ibmappnCosModeTable OBJECT-TYPE
      SYNTAX SEQUENCE OF IbmappnCosModeEntry
      ACCESS not-accessible
      STATUS mandatory
      DESCRIPTION
          "Table representing all of the defined
          mode names for this node.  The table
          contains the matching COS name."

      ::= { ibmappnCos 1 }

ibmappnCosModeEntry OBJECT-TYPE
      SYNTAX IbmappnCosModeEntry
      ACCESS not-accessible
      STATUS mandatory
      DESCRIPTION
           "This table is indexed by the Mode Name."

      INDEX
             {ibmappnCosModeName}

      ::= { ibmappnCosModeTable 1 }

IbmappnCosModeEntry ::= SEQUENCE {
      ibmappnCosModeName                  DisplayString,
      ibmappnCosModeCosName               DisplayString
                                     }

ibmappnCosModeName              OBJECT-TYPE
      SYNTAX DisplayString (SIZE (1..8))
      ACCESS read-only
      STATUS mandatory
      DESCRIPTION
           "Administratively-assigned name for this
            mode entry."

      ::=  { ibmappnCosModeEntry 1 }

ibmappnCosModeCosName    OBJECT-TYPE
      SYNTAX DisplayString (SIZE (1..8))
      ACCESS read-only
      STATUS mandatory
      DESCRIPTION
           "An administratively assigned name for this
           Class of Service."

      ::=  { ibmappnCosModeEntry 2 }

-- *****************************************************************************

ibmappnCosNameTable OBJECT-TYPE
      SYNTAX SEQUENCE OF IbmappnCosNameEntry
      ACCESS not-accessible
      STATUS mandatory
      DESCRIPTION
          "Table representing all of the defined class-of-service
           names for this node.  The COS node and TG tables are
           accessed using the same index, which is the COS name."

      ::= { ibmappnCos 2 }

ibmappnCosNameEntry OBJECT-TYPE
      SYNTAX IbmappnCosNameEntry
      ACCESS not-accessible
      STATUS mandatory
      DESCRIPTION
           "The COS name is the index to this table."

      INDEX
             {ibmappnCosName}

      ::= { ibmappnCosNameTable 1 }

IbmappnCosNameEntry ::= SEQUENCE {
      ibmappnCosName                     DisplayString,
      ibmappnCosTransPriority            INTEGER
                                 }


ibmappnCosName              OBJECT-TYPE
      SYNTAX DisplayString (SIZE (1..8))
      ACCESS read-only
      STATUS mandatory
      DESCRIPTION
          "Administratively-assigned name for this
           class of service."

      ::=  { ibmappnCosNameEntry 1 }

ibmappnCosTransPriority OBJECT-TYPE
      SYNTAX INTEGER {
                     low(1),               --X'01'
                     medium(2),            --X'02'
                     high(3),              --X'03'
                     network(4)            --X'04'
                     }
      ACCESS read-only
      STATUS mandatory
      DESCRIPTION
           "Transmission priority for this
            class of service.  Values are:
              Low
              Medium
              High
              Network                                      "

      ::=  { ibmappnCosNameEntry 2 }

ibmappnCosNodeRowTable OBJECT-TYPE
      SYNTAX SEQUENCE OF IbmappnCosNodeRowEntry
      ACCESS not-accessible
      STATUS mandatory
      DESCRIPTION
           "This table contains all node-row information for all
            class of service in this node."

      ::= { ibmappnCos 3 }

ibmappnCosNodeRowEntry OBJECT-TYPE
      SYNTAX IbmappnCosNodeRowEntry
      ACCESS not-accessible
      STATUS mandatory
      DESCRIPTION
           "The COS name is the first index and a integer
            is the second index to insure a unique index."

      INDEX
             {ibmappnCosNodeRowName,
              ibmappnCosNodeRowIndex}

      ::= { ibmappnCosNodeRowTable 1 }

IbmappnCosNodeRowEntry ::= SEQUENCE {
      ibmappnCosNodeRowName                 DisplayString,
      ibmappnCosNodeRowIndex                INTEGER,
--Node Row Group
      ibmappnCosNodeRowWgt                  DisplayString,
      ibmappnCosNodeRowResistMin            INTEGER,
      ibmappnCosNodeRowResistMax            INTEGER,
      ibmappnCosNodeRowMinCongestAllow      INTEGER,
      ibmappnCosNodeRowMaxCongestAllow      INTEGER
                                 }

ibmappnCosNodeRowName              OBJECT-TYPE
      SYNTAX DisplayString (SIZE (1..8))
      ACCESS read-only
      STATUS mandatory
      DESCRIPTION
           "Administratively-assigned name for this
           class of service."

      ::=  { ibmappnCosNodeRowEntry 1 }

ibmappnCosNodeRowIndex     OBJECT-TYPE
      SYNTAX INTEGER (0..255)
      ACCESS read-only
      STATUS mandatory
      DESCRIPTION
           "Index of COS name.  This same value is used
            to access the node and TG COS tables.
            Range of values is 0-255."

      ::=  { ibmappnCosNodeRowEntry 2 }

--Node Row Group

ibmappnCosNodeRowWgt     OBJECT-TYPE
      SYNTAX DisplayString
      ACCESS read-only
      STATUS mandatory
      DESCRIPTION
           "Weight to be associated with the nodes
            that fit the criteria specified by this node row."

      ::=  { ibmappnCosNodeRowEntry 3 }

ibmappnCosNodeRowResistMin       OBJECT-TYPE
      SYNTAX INTEGER   (0..255)
      ACCESS read-only
      STATUS mandatory
      DESCRIPTION
          "Minimum route addition resistance value
           for this node. Range of values is 0-255.
           The lower the value, the more desirable
           the node is for intermediate routing."

      ::=  { ibmappnCosNodeRowEntry 4 }

ibmappnCosNodeRowResistMax  OBJECT-TYPE
      SYNTAX INTEGER   (0..255)
      ACCESS read-only
      STATUS mandatory
      DESCRIPTION
          "Maximum route addition resistance value
           for this node. Range of values is 0-255.
           The lower the value, the more desirable
           the node is for intermediate routing."

      ::=  { ibmappnCosNodeRowEntry 5 }

ibmappnCosNodeRowMinCongestAllow OBJECT-TYPE
      SYNTAX INTEGER {yes(1), no(2)}
      ACCESS read-only
      STATUS mandatory
      DESCRIPTION
           "Indicates whether low congestion will be
            tolerated.  The minimum and maximum parameters
            will allow specifying either low-congested,
            high-congested, or either to be used."

      ::=  { ibmappnCosNodeRowEntry 6 }

ibmappnCosNodeRowMaxCongestAllow OBJECT-TYPE
      SYNTAX INTEGER {yes(1), no(2)}
      ACCESS read-only
      STATUS mandatory
      DESCRIPTION
           "Indicates whether high congestion will be
            tolerated.  The minimum and maximum parameters
            will allow specifying either low-congested,
            high-congested, or either to be used."

      ::=  { ibmappnCosNodeRowEntry 7 }

-- COS TG row table
--  Index
--  TG Row Weight
--  Effective capacity  (min)
--  Effective capacity  (max)
--  Cost per conn time  (min)
--  Cost per conn time  (max)
--  cost per byte       (min)
--  cost per byte       (max)
--  Security            (min)
--  Security            (max)
--  Propagation delay   (min)
--  Propagation delay   (max)
--  User defined 1      (min)
--  User defined 1      (max)
--  User defined 2      (min)
--  User defined 2      (max)
--  User defined 3      (min)
--  User defined 3      (max)
--

ibmappnCosTgRowTable OBJECT-TYPE
      SYNTAX SEQUENCE OF IbmappnCosTgRowEntry
      ACCESS not-accessible
      STATUS mandatory
      DESCRIPTION
           "Table containing all the Tg-row information for all
            class of service defined in this node."

      ::= { ibmappnCos 4 }

ibmappnCosTgRowEntry OBJECT-TYPE
      SYNTAX IbmappnCosTgRowEntry
      ACCESS not-accessible
      STATUS mandatory
      DESCRIPTION
           "The TgRowName and the TgRowIndex are the index
           for this table."

      INDEX
             {ibmappnCosTgRowName,
              ibmappnCosTgRowIndex}

      ::= { ibmappnCosTgRowTable 1 }

IbmappnCosTgRowEntry ::= SEQUENCE {
      ibmappnCosTgRowName                 DisplayString,
      ibmappnCosTgRowIndex                INTEGER,
--TG Row Group
      ibmappnCosTgRowWgt                   DisplayString,
      ibmappnCosTgRowEffCapMin             INTEGER,
      ibmappnCosTgRowEffCapMax             INTEGER,
      ibmappnCosTgRowConnCostMin           INTEGER,
      ibmappnCosTgRowConnCostMax           INTEGER,
      ibmappnCosTgRowByteCostMin           INTEGER,
      ibmappnCosTgRowByteCostMax           INTEGER,
      ibmappnCosTgRowSecurityMin           INTEGER,
      ibmappnCosTgRowSecurityMax           INTEGER,
      ibmappnCosTgRowDelayMin              INTEGER,
      ibmappnCosTgRowDelayMax              INTEGER,
      ibmappnCosTgRowUsr1Min               INTEGER,
      ibmappnCosTgRowUsr1Max               INTEGER,
      ibmappnCosTgRowUsr2Min               INTEGER,
      ibmappnCosTgRowUsr2Max               INTEGER,
      ibmappnCosTgRowUsr3Min               INTEGER,
      ibmappnCosTgRowUsr3Max               INTEGER
                              }

ibmappnCosTgRowName              OBJECT-TYPE
      SYNTAX DisplayString (SIZE (1..8))
      ACCESS read-only
      STATUS mandatory
      DESCRIPTION
           "Administratively-assigned name for this
           class of service."

      ::=  { ibmappnCosTgRowEntry 1 }

ibmappnCosTgRowIndex     OBJECT-TYPE
      SYNTAX INTEGER (0..255)
      ACCESS read-only
      STATUS mandatory
      DESCRIPTION
           "Index of COS name.  This same value is used
            to access the node and TG COS tables."

      ::=  { ibmappnCosTgRowEntry 2 }

--TG Row

ibmappnCosTgRowWgt       OBJECT-TYPE
      SYNTAX DisplayString
      ACCESS read-only
      STATUS mandatory
      DESCRIPTION
           "Weight to be associated with the nodes
            that fit the criteria specified by this tg-row."

      ::=  { ibmappnCosTgRowEntry 3 }

ibmappnCosTgRowEffCapMin   OBJECT-TYPE
      SYNTAX INTEGER
      ACCESS read-only
      STATUS mandatory
      DESCRIPTION
          "Minimum acceptable speed for this Class of Service.
           The effective capacity is an integer value that indicates
           the actual kilo bits per second.
           It is derived from the link bandwidth and maximum load
           factor with the range of 0 thru 603,979,776."

      ::=  { ibmappnCosTgRowEntry 4 }

ibmappnCosTgRowEffCapMax   OBJECT-TYPE
      SYNTAX INTEGER
      ACCESS read-only
      STATUS mandatory
      DESCRIPTION
          "Maximum acceptable speed for this Class of Service.
           The effective capacity is an integer value that indicates
           the actual kilo bits per second.
           It is derived from the link bandwidth and maximum load
           factor with the range of 0 thru 603,979,776."

      ::=  { ibmappnCosTgRowEntry 5 }

ibmappnCosTgRowConnCostMin OBJECT-TYPE
      SYNTAX INTEGER (0..255)
      ACCESS read-only
      STATUS mandatory
      DESCRIPTION
          "Minimum acceptable cost per connect time
           for this Class of Service.
           Cost per connect time: a value representing
           the relative cost per unit of time to use
           the TG. Range is from 0, which means no cost,
           to 255."

      ::=  { ibmappnCosTgRowEntry 6 }

ibmappnCosTgRowConnCostMax OBJECT-TYPE
      SYNTAX INTEGER (0..255)
      ACCESS read-only
      STATUS mandatory
      DESCRIPTION
          "Maximum acceptable cost per connect time
           for this Class of Service.
           Cost per connect time: a value representing
           the relative cost per unit of time to use
           the TG. Range is from 0, which means no cost,
           to 255."

      ::=  { ibmappnCosTgRowEntry 7 }

ibmappnCosTgRowByteCostMin  OBJECT-TYPE
      SYNTAX INTEGER (0..255)
      ACCESS read-only
      STATUS mandatory
      DESCRIPTION
           "Minimum acceptable cost per byte
            for this Class of Service."

      ::=  { ibmappnCosTgRowEntry 8 }

ibmappnCosTgRowByteCostMax  OBJECT-TYPE
      SYNTAX INTEGER (0..255)
      ACCESS read-only
      STATUS mandatory
      DESCRIPTION
           "Maximum acceptable cost per byte
            for this Class of Service."

      ::=  { ibmappnCosTgRowEntry 9 }

ibmappnCosTgRowSecurityMin  OBJECT-TYPE
      SYNTAX INTEGER {
                     nonsecure(1),                --X'01'
                     publicSwitchedNetwork(32),   --X'20'
                     undergroundCable(64),        --X'40'
                     secureConduit(96),           --X'60'
                     guardedConduit(128),         --X'80'
                     encrypted(160),              --X'A0'
                     guardedRadiation(192)        --X'C0'
             }
      ACCESS read-only
      STATUS mandatory
      DESCRIPTION
           "Minimum acceptable security
            for this Class of Service."

      ::=  { ibmappnCosTgRowEntry 10 }

ibmappnCosTgRowSecurityMax  OBJECT-TYPE
      SYNTAX INTEGER {
                     nonsecure(1),                --X'01'
                     publicSwitchedNetwork(32),   --X'20'
                     undergroundCable(64),        --X'40'
                     secureConduit(96),           --X'60'
                     guardedConduit(128),         --X'80'
                     encrypted(160),              --X'A0'
                     guardedRadiation(192)        --X'C0'
             }
      ACCESS read-only
      STATUS mandatory
      DESCRIPTION
           "Maximum acceptable security
            for this Class of Service."

      ::=  { ibmappnCosTgRowEntry 11 }

ibmappnCosTgRowDelayMin  OBJECT-TYPE
      SYNTAX INTEGER {
                     minimum(1),                 --X'00'
                     negligible(384),            --X'4C'
                     terrestrial(9216),          --X'71'
                     packet(147456),             --X'91'
                     long(294912),               --X'99'
                     maximum(2013265920)         --X'FF'
             }
      ACCESS read-only
      STATUS mandatory
      DESCRIPTION
        "Minimum acceptable propagation delay for this class of service.
         Relative amount of time that it takes for a signal to travel
         the length of the logical link.  This time is represented in
         micro seconds, with the more values enumerated."

      ::=  { ibmappnCosTgRowEntry 12 }

ibmappnCosTgRowDelayMax  OBJECT-TYPE
      SYNTAX INTEGER {
                     minimum(1),                 --X'00'
                     negligible(384),            --X'4C'
                     terrestrial(9216),          --X'71'
                     packet(147456),             --X'91'
                     long(294912),               --X'99'
                     maximum(2013265920)         --X'FF'
             }
      ACCESS read-only
      STATUS mandatory
      DESCRIPTION
        "Maximum acceptable propagation delay for this class of service.
         Relative amount of time that it takes for a signal to travel
         the length of the logical link.  This time is represented in
         micro seconds, with the more values enumerated."

      ::=  { ibmappnCosTgRowEntry 13 }

ibmappnCosTgRowUsr1Min  OBJECT-TYPE
      SYNTAX INTEGER (0..255)
      ACCESS read-only
      STATUS mandatory
      DESCRIPTION
           "Minimum acceptable value for this
            user defined characteristic.
            Range of values is 0-255."

      ::=  { ibmappnCosTgRowEntry 14 }

ibmappnCosTgRowUsr1Max  OBJECT-TYPE
      SYNTAX INTEGER (0..255)
      ACCESS read-only
      STATUS mandatory
      DESCRIPTION
           "Maximum acceptable value for this
            user defined characteristic.
            Range of values is 0-255."

      ::=  { ibmappnCosTgRowEntry 15 }

ibmappnCosTgRowUsr2Min  OBJECT-TYPE
      SYNTAX INTEGER (0..255)
      ACCESS read-only
      STATUS mandatory
      DESCRIPTION
           "Minimum acceptable value for this
            user defined characteristic.
            Range of values is 0-255."

      ::=  { ibmappnCosTgRowEntry 16 }

ibmappnCosTgRowUsr2Max  OBJECT-TYPE
      SYNTAX INTEGER (0..255)
      ACCESS read-only
      STATUS mandatory
      DESCRIPTION
           "A Maximum acceptable value for this
            user defined characteristic."

      ::=  { ibmappnCosTgRowEntry 17 }

ibmappnCosTgRowUsr3Min  OBJECT-TYPE
      SYNTAX INTEGER (0..255)
      ACCESS read-only
      STATUS mandatory
      DESCRIPTION
           "Minimum acceptable value for this
            user defined characteristic.
            Range of values is 0-255."

      ::=  { ibmappnCosTgRowEntry 18 }

ibmappnCosTgRowUsr3Max  OBJECT-TYPE
      SYNTAX INTEGER (0..255)
      ACCESS read-only
      STATUS mandatory
      DESCRIPTION
           "Maximum acceptable value for this
            user defined characteristic.
            Range of values is 0-255."

      ::=  { ibmappnCosTgRowEntry 19 }

-- *********************************************************************

ibmappnSession           OBJECT IDENTIFIER ::= { ibmappn 7  }
ibmappnConversation      OBJECT IDENTIFIER ::= { ibmappn 8  }

ibmappnSessGeneral       OBJECT IDENTIFIER ::= { ibmappnSession   1 }
ibmappnSessEndPoint      OBJECT IDENTIFIER ::= { ibmappnSession   2 }
ibmappnSessIntermediate  OBJECT IDENTIFIER ::= { ibmappnSession   3 }

ibmappnConvGeneral       OBJECT IDENTIFIER ::= { ibmappnConversation 1 }
ibmappnConvEndPoint      OBJECT IDENTIFIER ::= { ibmappnConversation 2 }

-- *********************************************************************
-- Intermediate Session Information and Accounting
-- *********************************************************************
ibmappnIsInformation     OBJECT IDENTIFIER
                         ::= { ibmappnSessIntermediate 1 }
ibmappnIsAccounting      OBJECT IDENTIFIER
                         ::= { ibmappnSessIntermediate 2 }

-- *********************************************************************
-- *********************************************************************
-- *********************************************************************
-- Intermediate Session Information
-- *********************************************************************
-- *********************************************************************
-- *********************************************************************

-- *********************************************************************
-- Intermediate Session Information Global Objects
-- ---------------------------------------------------------------------
-- The following simple objects allow:
--    * the collection of Intermediate Session Information
--      to be started and stopped
-- *********************************************************************
ibmappnIsInGlobal OBJECT IDENTIFIER ::= { ibmappnIsInformation 1 }

ibmappnIsInGlobeStatus  OBJECT-TYPE
      SYNTAX INTEGER  {
                      notActive(1),
                      active(2)
                      }
      ACCESS read-write
      STATUS mandatory
      DESCRIPTION
          "Indicates the current collection options in effect:
           1. notActive: collection of counters and some names
                         is not active.
           2. active:    collection of counters and some names
                         is active."

      ::= { ibmappnIsInGlobal  1 }

ibmappnIsInGlobeRscv    OBJECT-TYPE
      SYNTAX INTEGER  {
                      notActive(1),
                      active(2)
                      }
      ACCESS read-write
      STATUS mandatory
      DESCRIPTION
          "Indicates the current collection options in effect:
           1. notActive: collection of route selection control vectors
                         is not active.
           2. active:    collection of route selection control vectors
                         is active."

      ::= { ibmappnIsInGlobal  2 }

ibmappnIsInGlobeRscvTime OBJECT-TYPE
      SYNTAX TimeTicks
      ACCESS read-only
      STATUS mandatory
      DESCRIPTION
          "Time when the ibmappnIsInGlobeRscv object last changed.
           This time is in hundreds of a second."

      ::=  { ibmappnIsInGlobal 3  }

ibmappnIsInGlobeCtrStatus  OBJECT-TYPE
      SYNTAX INTEGER  {
                      notActive(1),
                      active(2)
                      }
      ACCESS read-write
      STATUS mandatory
      DESCRIPTION
          "Indicates whether or not the intermediate session counters
           are active.  This object reflects the combination of the
           ibmappnIsInGlobeStatus object and the ibmappnIsAcBtypeActive
           object.  The values are:
           1. notActive: collection of counters and some names
                         is not active.
           2. active:    collection of counters and some names
                         is active."

      ::= { ibmappnIsInGlobal  4 }

ibmappnIsInGlobeCtrStatusTime OBJECT-TYPE
      SYNTAX TimeTicks
      ACCESS read-only
      STATUS mandatory
      DESCRIPTION
          "Time when the ibmappnIsInGlobeCtrStatus object last changed.
           This time is in hundreds of a second."

      ::=  { ibmappnIsInGlobal 5  }

-- *********************************************************************
-- Intermediate Session Information Table
-- ---------------------------------------------------------------------
-- This table contains information on intermediate sessions
-- which are currently active.
-- *********************************************************************
ibmappnIsInTable OBJECT-TYPE
      SYNTAX SEQUENCE OF IbmappnIsInEntry
      ACCESS not-accessible
      STATUS mandatory
      DESCRIPTION
           "Intermediate Session Information Table"

      ::= { ibmappnIsInformation 2 }

ibmappnIsInEntry OBJECT-TYPE
      SYNTAX IbmappnIsInEntry
      ACCESS not-accessible
      STATUS mandatory
      DESCRIPTION
           "Entry of Intermediate Session Information Table."

      INDEX
             { ibmappnIsInFqLuName,
               ibmappnIsInPcid }

      ::= { ibmappnIsInTable 1 }

IbmappnIsInEntry ::= SEQUENCE {
      ibmappnIsInFqLuName            DisplayString,
      ibmappnIsInPcid                OCTET STRING,

      ibmappnIsInPriLuName           DisplayString,
      ibmappnIsInSecLuName           DisplayString,
      ibmappnIsInModeName            DisplayString,
      ibmappnIsInCosName             DisplayString,
      ibmappnIsInTransPriority       INTEGER,

      ibmappnIsInSessType            INTEGER,
      ibmappnIsInSessState           INTEGER,
      ibmappnIsInSessStartTime       TimeTicks,
      ibmappnIsInSessUpTime          TimeTicks,
      ibmappnIsInCtrUpTime           TimeTicks,

      ibmappnIsInP2SFmdPius          Counter,
      ibmappnIsInS2PFmdPius          Counter,
      ibmappnIsInP2SNonFmdPius       Counter,
      ibmappnIsInS2PNonFmdPius       Counter,
      ibmappnIsInP2SFmdBytes         Counter,
      ibmappnIsInS2PFmdBytes         Counter,
      ibmappnIsInP2SNonFmdBytes      Counter,
      ibmappnIsInS2PNonFmdBytes      Counter,

      ibmappnIsInPsAdjCpName         DisplayString,
      ibmappnIsInPsAdjTgNum          INTEGER,
      ibmappnIsInPsSendMaxBtuSize    INTEGER,
      ibmappnIsInPsSendPacingType    INTEGER,
      ibmappnIsInPsSendRpc           Gauge,
      ibmappnIsInPsSendNxWndwSize    Gauge,
      ibmappnIsInPsRecvPacingType    INTEGER,
      ibmappnIsInPsRecvRpc           Gauge,
      ibmappnIsInPsRecvNxWndwSize    Gauge,

      ibmappnIsInSsAdjCpName         DisplayString,
      ibmappnIsInSsAdjTgNum          INTEGER,
      ibmappnIsInSsSendMaxBtuSize    INTEGER,
      ibmappnIsInSsSendPacingType    INTEGER,
      ibmappnIsInSsSendRpc           Gauge,
      ibmappnIsInSsSendNxWndwSize    Gauge,
      ibmappnIsInSsRecvPacingType    INTEGER,
      ibmappnIsInSsRecvRpc           Gauge,
      ibmappnIsInSsRecvNxWndwSize    Gauge,

      ibmappnIsInRouteInfo           OCTET STRING
                               }

ibmappnIsInFqLuName OBJECT-TYPE
      SYNTAX DisplayString (SIZE (3..17))
      ACCESS read-only
      STATUS mandatory
      DESCRIPTION
          "The network-qualified CP name or PU name of the
           node at which the session and cid originated.  For APPN
           and LEN nodes, this is either CP name of the APPN node at
           which the origin LU is located or the CP name of the
           NN serving the LEN node at which the origin LU is
           located.  This field is from 3 to 17 characters in
           length, including a period (.) which separates the
           NetId from the NAU name."

      ::=  { ibmappnIsInEntry 1 }

ibmappnIsInPcid OBJECT-TYPE
      SYNTAX OCTET STRING  (SIZE (8))
      ACCESS read-only
      STATUS mandatory
      DESCRIPTION
          "The procedure correlation identifier (pcid) of a
           session.  It is an 8-octet value assigned
           by the primary LU."

      ::=  { ibmappnIsInEntry 2 }

ibmappnIsInPriLuName OBJECT-TYPE
      SYNTAX DisplayString (SIZE (3..17))
      ACCESS read-only
      STATUS mandatory
      DESCRIPTION
          "The primary LU name of the session."

      ::=  { ibmappnIsInEntry 3 }

ibmappnIsInSecLuName OBJECT-TYPE
      SYNTAX DisplayString (SIZE (3..17))
      ACCESS read-only
      STATUS mandatory
      DESCRIPTION
          "The secondary LU name of the session."

      ::=  { ibmappnIsInEntry 4 }

ibmappnIsInModeName OBJECT-TYPE
      SYNTAX DisplayString  (SIZE (1..8))
      ACCESS read-only
      STATUS mandatory
      DESCRIPTION
          "The Mode Name name used for this session.
           This is a 1-8 character name."

      ::=  { ibmappnIsInEntry 5 }

ibmappnIsInCosName OBJECT-TYPE
      SYNTAX DisplayString  (SIZE (1..8))
      ACCESS read-only
      STATUS mandatory
      DESCRIPTION
          "The Class of Service (COS) name used for this session.
           This is a 1-8 character name."

      ::=  { ibmappnIsInEntry 6 }

ibmappnIsInTransPriority OBJECT-TYPE
      SYNTAX INTEGER
      ACCESS read-only
      STATUS mandatory
      DESCRIPTION
          "The transmission priority of this session."

      ::=  { ibmappnIsInEntry 7 }

ibmappnIsInSessType  OBJECT-TYPE
      SYNTAX INTEGER {
                     lu62(1),
                     lu0thru3(2)
                     }
      ACCESS read-only
      STATUS mandatory
      DESCRIPTION
          "The type of intermediate session."

      ::=  { ibmappnIsInEntry 8 }

ibmappnIsInSessState OBJECT-TYPE
      SYNTAX INTEGER    {
                         inactive(1),
                         pendactive(2),
                         active(3),
                         pendinact(4)
                         }
      ACCESS read-write
      STATUS mandatory
      DESCRIPTION
          "Indicates the state of the session.
           1. session is pending inactive or,
           2. session is pending active or,
           3. session is active or,
           4. session is inactive

           Existing sessions can be deactivated by setting
           this object to inactive."

      ::=  { ibmappnIsInEntry 9 }

ibmappnIsInSessStartTime  OBJECT-TYPE
      SYNTAX TimeTicks
      ACCESS read-only
      STATUS mandatory
      DESCRIPTION
          "Time when the session started in hundreds of a second."

      ::=  { ibmappnIsInEntry 10 }


ibmappnIsInSessUpTime   OBJECT-TYPE
      SYNTAX TimeTicks
      ACCESS read-only
      STATUS mandatory
      DESCRIPTION
          "Length of time the session has been active
           in hundreds of a second."

      ::=  { ibmappnIsInEntry 11 }

ibmappnIsInCtrUpTime   OBJECT-TYPE
      SYNTAX TimeTicks
      ACCESS read-only
      STATUS mandatory
      DESCRIPTION
          "Length of time the session counters have been active
           in hundreds of a second."

      ::=  { ibmappnIsInEntry 12 }

ibmappnIsInP2SFmdPius OBJECT-TYPE
      SYNTAX Counter
      ACCESS read-only
      STATUS mandatory
      DESCRIPTION
          "Number of FMD PIUs sent from the Primary LU
           to the Secondary LU"

      ::=  { ibmappnIsInEntry 13 }

ibmappnIsInS2PFmdPius OBJECT-TYPE
      SYNTAX Counter
      ACCESS read-only
      STATUS mandatory
      DESCRIPTION
          "Number of FMD PIUs sent from the Secondary LU
           to the Primary LU"

      ::=  { ibmappnIsInEntry 14 }

ibmappnIsInP2SNonFmdPius OBJECT-TYPE
      SYNTAX Counter
      ACCESS read-only
      STATUS mandatory
      DESCRIPTION
          "Number of non-FMD PIUs sent from the Primary LU
           to the Secondary LU"

      ::=  { ibmappnIsInEntry 15 }

ibmappnIsInS2PNonFmdPius OBJECT-TYPE
      SYNTAX Counter
      ACCESS read-only
      STATUS mandatory
      DESCRIPTION
          "Number of non-FMD PIUs sent from the Secondary LU
           to the Primary LU"

      ::=  { ibmappnIsInEntry 16 }

ibmappnIsInP2SFmdBytes  OBJECT-TYPE
      SYNTAX Counter
      ACCESS read-only
      STATUS mandatory
      DESCRIPTION
          "Number of FMD Bytes sent from the Primary LU
           to the Secondary LU"

      ::=  { ibmappnIsInEntry 17 }

ibmappnIsInS2PFmdBytes  OBJECT-TYPE
      SYNTAX Counter
      ACCESS read-only
      STATUS mandatory
      DESCRIPTION
          "Number of FMD Bytes sent from the Secondary LU
           to the Primary LU"

      ::=  { ibmappnIsInEntry 18 }

ibmappnIsInP2SNonFmdBytes  OBJECT-TYPE
      SYNTAX Counter
      ACCESS read-only
      STATUS mandatory
      DESCRIPTION
          "Number of non-FMD Bytes sent from the Primary LU
           to the Secondary LU"

      ::=  { ibmappnIsInEntry 19 }

ibmappnIsInS2PNonFmdBytes  OBJECT-TYPE
      SYNTAX Counter
      ACCESS read-only
      STATUS mandatory
      DESCRIPTION
          "Number of non-FMD Bytes sent from the Secondary LU
           to the Primary LU"

      ::=  { ibmappnIsInEntry 20 }

ibmappnIsInPsAdjCpName OBJECT-TYPE
      SYNTAX DisplayString (SIZE (3..17))
      ACCESS read-only
      STATUS mandatory
      DESCRIPTION
          "The primary stage adjacent CP name of this session."

      ::=  { ibmappnIsInEntry 21 }

ibmappnIsInPsAdjTgNum OBJECT-TYPE
      SYNTAX INTEGER
      ACCESS read-only
      STATUS mandatory
      DESCRIPTION
          "The primary stage adjacent transmission group (TG) number
           associated with this session."

      ::=  { ibmappnIsInEntry 22 }

ibmappnIsInPsSendMaxBtuSize OBJECT-TYPE
      SYNTAX INTEGER
      ACCESS read-only
      STATUS mandatory
      DESCRIPTION
          "The primary stage maximum basic transmission size (BTU)
           for sending data."

      ::=  { ibmappnIsInEntry 23 }

ibmappnIsInPsSendPacingType OBJECT-TYPE
      SYNTAX INTEGER {
                     fixed(1),
                     adaptive(2)
                     }
      ACCESS read-only
      STATUS mandatory
      DESCRIPTION
          "The primary stage type of pacing being used
           for sending data."

      ::=  { ibmappnIsInEntry 24 }

ibmappnIsInPsSendRpc OBJECT-TYPE
      SYNTAX Gauge
      ACCESS read-only
      STATUS mandatory
      DESCRIPTION
          "The primary stage send residual pace count.  This represents
            the primary stage number of MU's that can still be sent
            in the current session window."

      ::=  { ibmappnIsInEntry 25 }

ibmappnIsInPsSendNxWndwSize OBJECT-TYPE
      SYNTAX Gauge
      ACCESS read-only
      STATUS mandatory
      DESCRIPTION
          "The primary stage size of the next window which will
           be used to send data."

      ::=  { ibmappnIsInEntry 26 }

ibmappnIsInPsRecvPacingType OBJECT-TYPE
      SYNTAX INTEGER {
                     fixed(1),
                     adaptive(2)
                     }
      ACCESS read-only
      STATUS mandatory
      DESCRIPTION
          "The primary stage type of pacing being used
           for receiving data."

      ::=  { ibmappnIsInEntry 27 }

ibmappnIsInPsRecvRpc OBJECT-TYPE
      SYNTAX Gauge
      ACCESS read-only
      STATUS mandatory
      DESCRIPTION
          "The primary stage receive residual pace count.  This represents
           the primary stage number of MU's that can still be
           received in the current session window."

      ::=  { ibmappnIsInEntry 28 }

ibmappnIsInPsRecvNxWndwSize OBJECT-TYPE
      SYNTAX Gauge
      ACCESS read-only
      STATUS mandatory
      DESCRIPTION
          "The primary stage size of the next window which will
           be used to receive data."

      ::=  { ibmappnIsInEntry 29 }

ibmappnIsInSsAdjCpName OBJECT-TYPE
      SYNTAX DisplayString (SIZE (3..17))
      ACCESS read-only
      STATUS mandatory
      DESCRIPTION
          "The secondary stage adjacent CP name of this session."

      ::=  { ibmappnIsInEntry 30 }

ibmappnIsInSsAdjTgNum OBJECT-TYPE
      SYNTAX INTEGER
      ACCESS read-only
      STATUS mandatory
      DESCRIPTION
          "The secondary stage adjacent transmission group (TG) number
           associated with this session."

      ::=  { ibmappnIsInEntry 31 }

ibmappnIsInSsSendMaxBtuSize OBJECT-TYPE
      SYNTAX INTEGER
      ACCESS read-only
      STATUS mandatory
      DESCRIPTION
          "The secondary stage maximum basic transmission size (BTU)
           for sending data."

      ::=  { ibmappnIsInEntry 32 }

ibmappnIsInSsSendPacingType OBJECT-TYPE
      SYNTAX INTEGER {
                     fixed(1),
                     adaptive(2)
                     }
      ACCESS read-only
      STATUS mandatory
      DESCRIPTION
          "The secondary stage type of pacing being used
           for sending data."

      ::=  { ibmappnIsInEntry 33 }

ibmappnIsInSsSendRpc OBJECT-TYPE
      SYNTAX Gauge
      ACCESS read-only
      STATUS mandatory
      DESCRIPTION
          "The secondary stage send residual pace count.  This represents
           the secondary stage number of MU's that can still be sent
           in the current session window."

      ::=  { ibmappnIsInEntry 34 }

ibmappnIsInSsSendNxWndwSize OBJECT-TYPE
      SYNTAX Gauge
      ACCESS read-only
      STATUS mandatory
      DESCRIPTION
          "The secondary stage size of the next window which will
           be used to send data."

      ::=  { ibmappnIsInEntry 35 }

ibmappnIsInSsRecvPacingType OBJECT-TYPE
      SYNTAX INTEGER {
                     fixed(1),
                     adaptive(2)
                     }
      ACCESS read-only
      STATUS mandatory
      DESCRIPTION
          "The secondary stage type of pacing being used
           for receiving data."

      ::=  { ibmappnIsInEntry 36 }

ibmappnIsInSsRecvRpc OBJECT-TYPE
      SYNTAX Gauge
      ACCESS read-only
      STATUS mandatory
      DESCRIPTION
          "The secondary stage send residual pace count.  This represents
           the secondary stage number of MU's that can still be
           received in the current session window."

      ::=  { ibmappnIsInEntry 37 }

ibmappnIsInSsRecvNxWndwSize OBJECT-TYPE
      SYNTAX Gauge
      ACCESS read-only
      STATUS mandatory
      DESCRIPTION
          "The secondary stage size of the next window which will
           be used to receive data."

      ::=  { ibmappnIsInEntry 38 }

ibmappnIsInRouteInfo  OBJECT-TYPE
      SYNTAX OCTET STRING
      ACCESS read-only
      STATUS mandatory
      DESCRIPTION
          "The route selection control vector (RSCV x'2B')
           used for this session.  It is present for APPN nodes;
           but is not present for LEN nodes.  The format of this
           vector is described in SNA Formats."

      ::=  { ibmappnIsInEntry 39 }

-- *********************************************************************
-- *********************************************************************
-- *********************************************************************
-- Intermediate Session Accounting
-- *********************************************************************
-- *********************************************************************
-- *********************************************************************

-- *********************************************************************
-- Intermediate Session Accounting Global Objects
-- ---------------------------------------------------------------------
-- The following simple objects allow:
--    * monitoring of the global acccounting status
--    * setting of a byte threshold for recording statistics on
--      active sessions
--    * requesting checkpoint records of active sessions to be
--      be recorded
--    * setting the manager time and name
-- *********************************************************************
ibmappnIsAcGlobal OBJECT IDENTIFIER ::= { ibmappnIsAccounting  1 }

ibmappnIsAcGlobeStatus         OBJECT-TYPE
      SYNTAX INTEGER  {
                      notActive(1),
                      activeNotFull(2),
                      activeButFull(3)
                      }
      ACCESS read-only
      STATUS mandatory
      DESCRIPTION
          "This object indicates the current status for accounting
           type.
           1. indicates collection is not active for any media type.
           2. indicates collection is active for at least one media
              type; and that media is not full.
           3. indicates collection is active for at least one media
              type; but all active medias are full."

      ::=  { ibmappnIsAcGlobal 1 }

ibmappnIsAcGlobeByteThresh  OBJECT-TYPE
      SYNTAX INTEGER
      ACCESS read-write
      STATUS mandatory
      DESCRIPTION
          "The byte threshold for recording accounting information
           for an active session.

           If the total of the byte counters (FmdBytes and NonFmdBtyes)
           is an even multiple of this non-zero value, statistics for
           this session will be recorded to all active buffers.

           A value of zero indicates that no byte threshold has been set."

      ::=  { ibmappnIsAcGlobal 2 }

ibmappnIsAcGlobeCheckPt        OBJECT-TYPE
      SYNTAX INTEGER {
                     ready(1),
                     yes(2)
                     }
      ACCESS read-write
      STATUS mandatory
      DESCRIPTION
          "By setting this value to yes, the agent will collect
           accounting information for all active sessions.  This
           information will be recorded to all active buffers."

      ::=  { ibmappnIsAcGlobal 3 }

ibmappnIsAcGlobeMgrUtcSecs           OBJECT-TYPE
      SYNTAX INTEGER
      ACCESS read-write
      STATUS mandatory
      DESCRIPTION
          "The managers Coordinated Universal Time (UTC) seconds.
           It contains an integer from 0 to 59.
           By setting this value, the agent will create time record
           with its corresponding time and name.  When setting this object,
           the manager should also set all other ibmappnIsAcGlobeMgr objects
           with the same SET operation."

      ::=  { ibmappnIsAcGlobal 4 }

ibmappnIsAcGlobeMgrUtcMins           OBJECT-TYPE
      SYNTAX INTEGER
      ACCESS read-write
      STATUS mandatory
      DESCRIPTION
          "The managers Coordinated Universal Time (UTC) minutes.
           It contains an integer from 0 to 59.
           By setting this value, the agent will create time record
           with its corresponding time and name.  When setting this object,
           the manager should also set all other ibmappnIsAcGlobeMgr objects
           with the same SET operation."

      ::=  { ibmappnIsAcGlobal 5 }

ibmappnIsAcGlobeMgrUtcHours          OBJECT-TYPE
      SYNTAX INTEGER
      ACCESS read-write
      STATUS mandatory
      DESCRIPTION
          "The managers Coordinated Universal Time (UTC) hours.
           It contains an integer from 0 to 23.
           By setting this value, the agent will create time record
           with its corresponding time and name.  When setting this object,
           the manager should also set all other ibmappnIsAcGlobeMgr objects
           with the same SET operation."

      ::=  { ibmappnIsAcGlobal 6 }

ibmappnIsAcGlobeMgrUtcMdays          OBJECT-TYPE
      SYNTAX INTEGER
      ACCESS read-write
      STATUS mandatory
      DESCRIPTION
          "The managers Coordinated Universal Time (UTC) day of
           the month.
           It contains an integer from 1 to 31; or 0 if
           the manager has not set this object.
           By setting this value, the agent will create time record
           with its corresponding time and name.  When setting this object,
           the manager should also set all other ibmappnIsAcGlobeMgr objects
           with the same SET operation."

      ::=  { ibmappnIsAcGlobal 7 }

ibmappnIsAcGlobeMgrUtcMonths         OBJECT-TYPE
      SYNTAX INTEGER {
                     january(12),
                     february(1),
                     march(2),
                     april(3),
                     may(4),
                     june(5),
                     july(6),
                     august(7),
                     september(8),
                     october(9),
                     november(10),
                     december(11)
                     }
      ACCESS read-write
      STATUS mandatory
      DESCRIPTION
          "The managers Coordinated Universal Time (UTC) months
           since January.
           It contains an integer from 0 to 11.
           By setting this value, the agent will create time record
           with its corresponding time and name.  When setting this object,
           the manager should also set all other ibmappnIsAcGlobeMgr objects
           with the same SET operation."

      ::=  { ibmappnIsAcGlobal 8 }

ibmappnIsAcGlobeMgrUtcYears          OBJECT-TYPE
      SYNTAX INTEGER
      ACCESS read-write
      STATUS mandatory
      DESCRIPTION
          "The managers Coordinated Universal Time (UTC) years
           since 1900.
           By setting this value, the agent will create time record
           with its corresponding time and name.  When setting this object,
           the manager should also set all other ibmappnIsAcGlobeMgr objects
           with the same SET operation."

      ::=  { ibmappnIsAcGlobal 9 }

ibmappnIsAcGlobeMgrUtcWdays          OBJECT-TYPE
      SYNTAX INTEGER {
                     sunday(7),
                     monday(1),
                     tuesday(2),
                     wednesday(3),
                     thursday(4),
                     friday(5),
                     saturday(6)
                     }
      ACCESS read-write
      STATUS mandatory
      DESCRIPTION
          "The managers Coordinated Universal Time (UTC) days since
           Sunday.
           It contains an integer from 0 to 6.
           By setting this value, the agent will create time record
           with its corresponding time and name.  When setting this object,
           the manager should also set all other ibmappnIsAcGlobeMgr objects
           with the same SET operation."

      ::=  { ibmappnIsAcGlobal 10 }

ibmappnIsAcGlobeMgrUtcYdays          OBJECT-TYPE
      SYNTAX INTEGER
      ACCESS read-write
      STATUS mandatory
      DESCRIPTION
          "The managers Coordinated Universal Time (UTC) days since
           January 1.
           It contains an integer from 0 to 365.
           By setting this value, the agent will create time record
           with its corresponding time and name.  When setting this object,
           the manager should also set all other ibmappnIsAcGlobeMgr objects
           with the same SET operation."

      ::=  { ibmappnIsAcGlobal 11 }

ibmappnIsAcGlobeMgrUtcIsdst          OBJECT-TYPE
      SYNTAX INTEGER
      ACCESS read-write
      STATUS mandatory
      DESCRIPTION
          "The managers Coordinated Universal Time (UTC) daylight
           saving time flag.
           It is positive if daylight saving time is in effect.
           It is zero if daylight saving time is not in effect.
           By setting this value, the agent will create time record
           with its corresponding time and name.  When setting this object,
           the manager should also set all other ibmappnIsAcGlobeMgr objects
           with the same SET operation."

      ::=  { ibmappnIsAcGlobal 12 }

ibmappnIsAcGlobeMgrName              OBJECT-TYPE
      SYNTAX DisplayString (SIZE (3..17))
      ACCESS read-write
      STATUS mandatory
      DESCRIPTION
          "The name of the manager who set the manager UTC times or NULL if
           the manager name has not been set.
           It contains:
           a. the network id of the manager,
           b. a period (.)
           c. the cp name of the manager.
           By setting this value, the agent will create time record
           with its corresponding time and name.  When setting this object,
           the manager should also set all other ibmappnIsAcGlobeMgr objects
           with the same SET operation."

      ::=  { ibmappnIsAcGlobal 13 }

-- *********************************************************************
-- Intermediate Session Accounting Buffer Type Table
-- ---------------------------------------------------------------------
-- This table contains information on the accounting buffer types
-- (recording medias).  It provides:
-- * monitoring of buffer type (media) statistics
-- * starting and stoping recording
-- * setting of buffer type (media) recording characteristics:
--   - maximum number of buffers
--   - maximum number of records/buffer
--   - recording format
--   - full action
-- * reseting of statistics
-- *********************************************************************

ibmappnIsAcBtypeTable OBJECT-TYPE
      SYNTAX SEQUENCE OF IbmappnIsAcBtypeEntry
      ACCESS not-accessible
      STATUS mandatory
      DESCRIPTION
           "Intermediate Session Accounting Buffer Type Table"

      ::= { ibmappnIsAccounting 2 }

ibmappnIsAcBtypeEntry OBJECT-TYPE
      SYNTAX IbmappnIsAcBtypeEntry
      ACCESS not-accessible
      STATUS mandatory
      DESCRIPTION
           "Entry of Intermediate Session Accounting
            Buffer Type Table."

      INDEX
             { ibmappnIsAcBtypeMedia }

      ::= { ibmappnIsAcBtypeTable 1 }

IbmappnIsAcBtypeEntry ::= SEQUENCE {
      ibmappnIsAcBtypeMedia          INTEGER,
      ibmappnIsAcBtypeActive         INTEGER,
      ibmappnIsAcBtypeDirName        DisplayString,
      ibmappnIsAcBtypePrdMaxBufs     INTEGER,
      ibmappnIsAcBtypeMaxBufs        INTEGER,
      ibmappnIsAcBtypeCurBufs        Gauge,
      ibmappnIsAcBtypePrdRecPerBuf   INTEGER,
      ibmappnIsAcBtypeRecPerBuf      INTEGER,
      ibmappnIsAcBtypeRecFormat      INTEGER,
      ibmappnIsAcBtypeFullAction     INTEGER,
      ibmappnIsAcBtypeFullTime       TimeTicks,
      ibmappnIsAcBtypeFullReason     INTEGER,
      ibmappnIsAcBtypeFullWraps      INTEGER,
      ibmappnIsAcBtypeFullLosts      INTEGER,
      ibmappnIsAcBtypeErrorWraps     INTEGER,
      ibmappnIsAcBtypeErrorLosts     INTEGER,
      ibmappnIsAcBtypeCheckPts       INTEGER,
      ibmappnIsAcBtypePurges         INTEGER,
      ibmappnIsAcBtypeDeletes        INTEGER,
      ibmappnIsAcBtypeResets         INTEGER,
      ibmappnIsAcBtypeClearStats     INTEGER
                       }

ibmappnIsAcBtypeMedia OBJECT-TYPE
      SYNTAX INTEGER {
                     memory(1),
                     dasd(2)
                     }
      ACCESS read-only
      STATUS mandatory
      DESCRIPTION
           "The media for storing the intermediate session
            accounting records."

      ::= { ibmappnIsAcBtypeEntry 1 }

ibmappnIsAcBtypeActive OBJECT-TYPE
      SYNTAX INTEGER {
                     no(1),
                     yes(2)
                     }
      ACCESS read-write
      STATUS mandatory
      DESCRIPTION
          "Indicates whether or not the buffer media is active.
           1. no:  indicates the buffer media is not currently
                   used for recording.
           2. yes: indicates the buffer media is currently being
                   used for recording."

      ::= { ibmappnIsAcBtypeEntry 2 }

ibmappnIsAcBtypeDirName             OBJECT-TYPE
      SYNTAX DisplayString
      ACCESS read-only
      STATUS mandatory
      DESCRIPTION
          "The name of the directory which will be used to allocate
           and write buffers of this type.  For memory buffer types,
           this field will be NULL."

      ::= { ibmappnIsAcBtypeEntry 3 }

ibmappnIsAcBtypePrdMaxBufs       OBJECT-TYPE
      SYNTAX INTEGER
      ACCESS read-only
      STATUS mandatory
      DESCRIPTION
           "The maximum number of buffer medias supported by the product."

      ::= { ibmappnIsAcBtypeEntry 4 }

ibmappnIsAcBtypeMaxBufs       OBJECT-TYPE
      SYNTAX INTEGER
      ACCESS read-write
      STATUS mandatory
      DESCRIPTION
           "The maximum number of buffer medias which will be used for
            recording accounting information.  This value must be
            in the range of zero to the Product Maximum."

      ::= { ibmappnIsAcBtypeEntry 5 }

ibmappnIsAcBtypeCurBufs       OBJECT-TYPE
      SYNTAX Gauge
      ACCESS read-only
      STATUS mandatory
      DESCRIPTION
           "The current number of buffer media.  This is the sum
            of all full and in use buffers of this type."

      ::= { ibmappnIsAcBtypeEntry 6 }

ibmappnIsAcBtypePrdRecPerBuf OBJECT-TYPE
      SYNTAX INTEGER
      ACCESS read-only
      STATUS mandatory
      DESCRIPTION
           "The maximum number of records supported by the product."

      ::= { ibmappnIsAcBtypeEntry 7 }

ibmappnIsAcBtypeRecPerBuf OBJECT-TYPE
      SYNTAX INTEGER
      ACCESS read-write
      STATUS mandatory
      DESCRIPTION
           "The maximum number of records which will be recorded
            in an individual buffer.  This value must be
            in the range of zero to the Product Maximum."

      ::= { ibmappnIsAcBtypeEntry 8 }

ibmappnIsAcBtypeRecFormat      OBJECT-TYPE
      SYNTAX INTEGER {
                     ascii(1),
                     binary(2)
                     }
      ACCESS read-write
      STATUS mandatory
      DESCRIPTION
           "This defines the recording format of records.
            (1) ascii:   records are recorded in ascii
                         (english text format)
            (2) binary:  records are recorded in binary
                         (machine readable format)"

      ::= { ibmappnIsAcBtypeEntry 9 }

ibmappnIsAcBtypeFullAction OBJECT-TYPE
      SYNTAX INTEGER {
                     halt(1),
                     wrap(2)
                     }
      ACCESS read-write
      STATUS mandatory
      DESCRIPTION
           "This defines the behaviour used when all buffer medias
            are full.
            (1) halt: stop creating new records
            (2) wrap: overwrite the existing records."

      ::= { ibmappnIsAcBtypeEntry 10 }

ibmappnIsAcBtypeFullTime            OBJECT-TYPE
      SYNTAX TimeTicks
      ACCESS read-only
      STATUS mandatory
      DESCRIPTION
          "The time which the full condition was encountered.
           This time is represented in hundreds of a second
           since the node was started.
           2**32-1 (4,294,967,295), and wraps."

      ::= { ibmappnIsAcBtypeEntry 11 }

ibmappnIsAcBtypeFullReason OBJECT-TYPE
      SYNTAX INTEGER {
                     notFull(1),
                     physicallyFull(2),
                     logicallyFull(3),
                     ioErrors(4)
                     }
      ACCESS read-only
      STATUS mandatory
      DESCRIPTION
           "The reason the buffer media is full.
            (1) The media is not full.
            (2) The maximum number of buffers have been reach,
                all buffers are full and
                the full action is halt.
            (3) The maximum number of buffers is zero or
                the maximum number of records is less than 5 or
                a unique record number cannot be generated.
            (4) Unable to write to the media due to I/O errors."

      ::= { ibmappnIsAcBtypeEntry 12 }

ibmappnIsAcBtypeFullWraps OBJECT-TYPE
      SYNTAX INTEGER
      ACCESS read-only
      STATUS mandatory
      DESCRIPTION
           "The number of accounting records being overwritten due
            to buffer full situation."

      ::= { ibmappnIsAcBtypeEntry 13 }

ibmappnIsAcBtypeFullLosts OBJECT-TYPE
      SYNTAX INTEGER
      ACCESS read-only
      STATUS mandatory
      DESCRIPTION
           "The number of new accounting records lost due to
            the buffer full situation."

      ::= { ibmappnIsAcBtypeEntry 14 }

ibmappnIsAcBtypeErrorWraps OBJECT-TYPE
      SYNTAX INTEGER
      ACCESS read-only
      STATUS mandatory
      DESCRIPTION
           "The number of accounting records lost to due to other
            reasons, (e.g. I/O error, software error) while in
            a wrap condition."

      ::= { ibmappnIsAcBtypeEntry 15 }

ibmappnIsAcBtypeErrorLosts OBJECT-TYPE
      SYNTAX INTEGER
      ACCESS read-only
      STATUS mandatory
      DESCRIPTION
           "The number of accounting records lost to due to other
            reasons, (e.g. I/O error, software error) while not in
            a full condition."

      ::= { ibmappnIsAcBtypeEntry 16 }

ibmappnIsAcBtypeCheckPts    OBJECT-TYPE
      SYNTAX INTEGER
      ACCESS read-only
      STATUS mandatory
      DESCRIPTION
          "The number of times a buffer of this type has been
           recorded to for checkpointing active intermediate
           sessions."

      ::= { ibmappnIsAcBtypeEntry 17 }

ibmappnIsAcBtypePurges        OBJECT-TYPE
      SYNTAX INTEGER
      ACCESS read-only
      STATUS mandatory
      DESCRIPTION
          "The number of times a buffer of this type has been purged."

      ::= { ibmappnIsAcBtypeEntry 18 }

ibmappnIsAcBtypeDeletes       OBJECT-TYPE
      SYNTAX INTEGER
      ACCESS read-only
      STATUS mandatory
      DESCRIPTION
          "The number of times an entry has been deleted from
           a buffer of this type."

      ::= { ibmappnIsAcBtypeEntry 19 }

ibmappnIsAcBtypeResets        OBJECT-TYPE
      SYNTAX INTEGER
      ACCESS read-only
      STATUS mandatory
      DESCRIPTION
          "The number of times the Btype counters have been
           reset as a result of a SET."

      ::= { ibmappnIsAcBtypeEntry 20 }

ibmappnIsAcBtypeClearStats  OBJECT-TYPE
      SYNTAX INTEGER {
                     ready(1),
                     yes(2)
                     }
      ACCESS read-write
      STATUS mandatory
      DESCRIPTION
          "By setting this object to yes, all statistics for this media type
           will be cleared (set to zero); and the Btype reset counter
           will be incremented.  Objects affected by this
           include:
           - ibmappnIsAcBtypeFullTime
           - ibmappnIsAcBtypeFullReason
           - ibmappnIsAcBtypeFullWraps
           - ibmappnIsAcBtypeFullLosts
           - ibmappnIsAcBtypeErrorWraps
           - ibmappnIsAcBtypeErrorLosts
           - ibmappnIsAcBtypeCheckPts
           - ibmappnIsAcBtypePurges
           - ibmappnIsAcBtypeDeletes"

      ::= { ibmappnIsAcBtypeEntry 21 }

-- *********************************************************************
-- Intermediate Session Accounting Buffer Table
-- ---------------------------------------------------------------------
-- This table contains information on accounting buffers of a
-- a specific buffer type.  It provides:
-- * deleting of records
-- * purging of buffers
-- * switching active buffers
-- *********************************************************************

ibmappnIsAcBufTable OBJECT-TYPE
      SYNTAX SEQUENCE OF IbmappnIsAcBufEntry
      ACCESS not-accessible
      STATUS mandatory
      DESCRIPTION
           "Intermediate Session Accounting Buffer Table"

      ::= { ibmappnIsAccounting 3 }

ibmappnIsAcBufEntry OBJECT-TYPE
      SYNTAX IbmappnIsAcBufEntry
      ACCESS not-accessible
      STATUS mandatory
      DESCRIPTION
           "Entry of Intermediate Session Accounting
            Buffer Table."

      INDEX
             { ibmappnIsAcBufMedia,
               ibmappnIsAcBufNumber }

      ::= { ibmappnIsAcBufTable 1 }

IbmappnIsAcBufEntry ::= SEQUENCE {
      ibmappnIsAcBufMedia            INTEGER,
      ibmappnIsAcBufNumber           INTEGER,
      ibmappnIsAcBufState            INTEGER,
      ibmappnIsAcBufRecFormat        INTEGER,
      ibmappnIsAcBufMaxRecords       INTEGER,
      ibmappnIsAcBufOldestIndex      INTEGER,
      ibmappnIsAcBufNewestIndex      INTEGER,
      ibmappnIsAcBufName             DisplayString
                       }

ibmappnIsAcBufMedia OBJECT-TYPE
      SYNTAX INTEGER {
                     memory(1),
                     dasd(2)
                     }
      ACCESS read-only
      STATUS mandatory
      DESCRIPTION
           "The media for storing the intermediate session
            accounting records."

      ::= { ibmappnIsAcBufEntry 1 }

ibmappnIsAcBufNumber OBJECT-TYPE
      SYNTAX INTEGER
      ACCESS read-only
      STATUS mandatory
      DESCRIPTION
          "Number of the buffer.  Each time a new
           buffer is used for recording,  an incremented number
           will be assigned. Thus, the order of in which
           the buffers filled can be determined."

      ::=  { ibmappnIsAcBufEntry 2 }

ibmappnIsAcBufState OBJECT-TYPE
      SYNTAX INTEGER {
                     complete(1),
                     active(2),
                     purge(3)
                     }
      ACCESS read-write
      STATUS mandatory
      DESCRIPTION
          "The current buffer state.
           1. complete: indicates the buffer is full or
                        recording is not active for this buffer.
                        In either case, the buffer is ready to
                        be retrieved.
                        This value may be specified in a SET operation to
                        change a buffers state from active to complete.
           2. active:   indicates the buffer is currently being
                        used for recording.
                        This value is not valid for use in a SET operation.
           3. purge:    indicates the buffer should be purged.
                        This value may be specified in a SET operation to
                        remove a buffer.  Specification of this value is only
                        valid for complete buffers.  It is not valid
                        for active buffers."

      ::=  { ibmappnIsAcBufEntry 3 }

ibmappnIsAcBufRecFormat      OBJECT-TYPE
      SYNTAX INTEGER {
                     ascii(1),
                     binary(2)
                     }
      ACCESS read-only
      STATUS mandatory
      DESCRIPTION
           "This defines the recording format of records.
            (1) ascii:   records are recorded in ascii
                         (english text format)
            (2) binary:  records are recorded in binary
                         (machine readable format)"

      ::= { ibmappnIsAcBufEntry 4 }

ibmappnIsAcBufMaxRecords OBJECT-TYPE
      SYNTAX INTEGER
      ACCESS read-only
      STATUS mandatory
      DESCRIPTION
          "The maximum number of records this buffer may contain.  It is
           derived from the number of records per buffer set in the buffer
           type table."

      ::=  { ibmappnIsAcBufEntry 5 }

ibmappnIsAcBufOldestIndex OBJECT-TYPE
      SYNTAX INTEGER
      ACCESS read-write
      STATUS mandatory
      DESCRIPTION
          "The oldest accounting index contained in this buffer.
           By setting this object, all records with indexes less than
           this value will be deleted.  The set value must be greater
           than or equal to the current oldest index and less than or
           equal to the current newest index.  Setting of this object
           will not be honored for all types of buffers."

      ::=  { ibmappnIsAcBufEntry 6 }

ibmappnIsAcBufNewestIndex OBJECT-TYPE
      SYNTAX INTEGER
      ACCESS read-only
      STATUS mandatory
      DESCRIPTION
          "The newest accounting index contained in this buffer."

      ::=  { ibmappnIsAcBufEntry 7 }

ibmappnIsAcBufName OBJECT-TYPE
      SYNTAX DisplayString
      ACCESS read-only
      STATUS mandatory
      DESCRIPTION
          "The name of the buffer."

      ::=  { ibmappnIsAcBufEntry 8 }

-- *********************************************************************
-- Intermediate Session Accounting Time Table
-- ---------------------------------------------------------------------
-- This table contains information on accounting events
-- *********************************************************************

ibmappnIsAcTimeTable OBJECT-TYPE
      SYNTAX SEQUENCE OF IbmappnIsAcTimeEntry
      ACCESS not-accessible
      STATUS mandatory
      DESCRIPTION
           "Intermediate Session Accounting Time Table"

      ::= { ibmappnIsAccounting 4 }

ibmappnIsAcTimeEntry OBJECT-TYPE
      SYNTAX IbmappnIsAcTimeEntry
      ACCESS not-accessible
      STATUS mandatory
      DESCRIPTION
           "Entry of Intermediate Session Accounting Time Table."

      INDEX
             { ibmappnIsAcTimeIndex }

      ::= { ibmappnIsAcTimeTable 1 }

IbmappnIsAcTimeEntry ::= SEQUENCE {
      ibmappnIsAcTimeIndex                INTEGER,
      ibmappnIsAcTimeEntryType            INTEGER,
      ibmappnIsAcTimeForMedia             INTEGER,
      ibmappnIsAcTimeRecTime              TimeTicks,

      ibmappnIsAcTimeAgtUtcSecs           INTEGER,
      ibmappnIsAcTimeAgtUtcMins           INTEGER,
      ibmappnIsAcTimeAgtUtcHours          INTEGER,
      ibmappnIsAcTimeAgtUtcMdays          INTEGER,
      ibmappnIsAcTimeAgtUtcMonths         INTEGER,
      ibmappnIsAcTimeAgtUtcYears          INTEGER,
      ibmappnIsAcTimeAgtUtcWdays          INTEGER,
      ibmappnIsAcTimeAgtUtcYdays          INTEGER,
      ibmappnIsAcTimeAgtUtcIsdst          INTEGER,
      ibmappnIsAcTimeAgtName              DisplayString,

      ibmappnIsAcTimeMgrUtcSecs           INTEGER,
      ibmappnIsAcTimeMgrUtcMins           INTEGER,
      ibmappnIsAcTimeMgrUtcHours          INTEGER,
      ibmappnIsAcTimeMgrUtcMdays          INTEGER,
      ibmappnIsAcTimeMgrUtcMonths         INTEGER,
      ibmappnIsAcTimeMgrUtcYears          INTEGER,
      ibmappnIsAcTimeMgrUtcWdays          INTEGER,
      ibmappnIsAcTimeMgrUtcYdays          INTEGER,
      ibmappnIsAcTimeMgrUtcIsdst          INTEGER,
      ibmappnIsAcTimeMgrName              DisplayString,
      ibmappnIsAcTimeMgrTimeValid         INTEGER
                               }

ibmappnIsAcTimeIndex                OBJECT-TYPE
      SYNTAX INTEGER
      ACCESS read-only
      STATUS mandatory
      DESCRIPTION
          "Intermediate Session Time record index.  It starts
           with 0, and increase up to maximum value of
           2**31-1 (2,147,483,647), and wraps."

      ::=  { ibmappnIsAcTimeEntry 1 }

ibmappnIsAcTimeEntryType  OBJECT-TYPE
      SYNTAX INTEGER {
                     startCollection(1),
                     endCollection(2),
                     createdMedia(3),
                     wrappedMedia(4),
                     timeChange(5),
                     managerSetTime(6),
                     recordFormatChanged(7),
                     timeReference(8)
                     }
      ACCESS read-only
      STATUS mandatory
      DESCRIPTION
          "Indicates whether the entry was made as the result of:
           1. a SET to start collecting accounting data, or
           2. a SET to stop  collecting accounting data, or
           3. the creation of a new media to store accounting data, or
           4. a media was full and wrapped (over writing records), or
           5. the system time changed, or
           6. a manager set the manager times and/or manager name, or
           7. the record format for this media changed, or
           8. time reference for the media"

      ::=  { ibmappnIsAcTimeEntry 2 }

ibmappnIsAcTimeForMedia             OBJECT-TYPE
      SYNTAX INTEGER {
                     memoryMedia(1),
                     dasdMedia(2),
                     allMedias(99)
                     }
      ACCESS read-only
      STATUS mandatory
      DESCRIPTION
          "This object qualifies the time entry type.  It indicates
           the media type for which the entry occured."

      ::=  { ibmappnIsAcTimeEntry 3 }

ibmappnIsAcTimeRecTime              OBJECT-TYPE
      SYNTAX TimeTicks
      ACCESS read-only
      STATUS mandatory
      DESCRIPTION
          "Intermediate Session Record time.  It represents
           the time in hundreds of a second since the node
           was started.  2**32-1 (4,294,967,295), and wraps."

      ::=  { ibmappnIsAcTimeEntry 4 }

ibmappnIsAcTimeAgtUtcSecs           OBJECT-TYPE
      SYNTAX INTEGER
      ACCESS read-only
      STATUS mandatory
      DESCRIPTION
          "The agents Coordinated Universal Time (UTC) seconds.
           It contains an integer from 0 to 59."

      ::=  { ibmappnIsAcTimeEntry 5 }

ibmappnIsAcTimeAgtUtcMins           OBJECT-TYPE
      SYNTAX INTEGER
      ACCESS read-only
      STATUS mandatory
      DESCRIPTION
          "The agents Coordinated Universal Time (UTC) minutes.
           It contains an integer from 0 to 59."

      ::=  { ibmappnIsAcTimeEntry 6 }

ibmappnIsAcTimeAgtUtcHours          OBJECT-TYPE
      SYNTAX INTEGER
      ACCESS read-only
      STATUS mandatory
      DESCRIPTION
          "The agents Coordinated Universal Time (UTC) hours.
           It contains an integer from 0 to 23."

      ::=  { ibmappnIsAcTimeEntry 7 }

ibmappnIsAcTimeAgtUtcMdays          OBJECT-TYPE
      SYNTAX INTEGER
      ACCESS read-only
      STATUS mandatory
      DESCRIPTION
          "The agents Coordinated Universal Time (UTC) day of
           the month.
           It contains an integer from 1 to 31."

      ::=  { ibmappnIsAcTimeEntry 8 }


ibmappnIsAcTimeAgtUtcMonths         OBJECT-TYPE
      SYNTAX INTEGER {
                     january(12),
                     february(1),
                     march(2),
                     april(3),
                     may(4),
                     june(5),
                     july(6),
                     august(7),
                     september(8),
                     october(9),
                     november(10),
                     december(11)
                     }
      ACCESS read-only
      STATUS mandatory
      DESCRIPTION
          "The agents Coordinated Universal Time (UTC) months
           since January.
           It contains an integer from 0 to 11."

      ::=  { ibmappnIsAcTimeEntry 9 }

ibmappnIsAcTimeAgtUtcYears          OBJECT-TYPE
      SYNTAX INTEGER
      ACCESS read-only
      STATUS mandatory
      DESCRIPTION
          "The agents Coordinated Universal Time (UTC) years
           since 1900."

      ::=  { ibmappnIsAcTimeEntry 10 }

ibmappnIsAcTimeAgtUtcWdays          OBJECT-TYPE
      SYNTAX INTEGER {
                     sunday(7),
                     monday(1),
                     tuesday(2),
                     wednesday(3),
                     thursday(4),
                     friday(5),
                     saturday(6)
                     }
      ACCESS read-only
      STATUS mandatory
      DESCRIPTION
          "The agents Coordinated Universal Time (UTC) days since
           Sunday.
           It contains an integer from 0 to 6."

      ::=  { ibmappnIsAcTimeEntry 11 }

ibmappnIsAcTimeAgtUtcYdays          OBJECT-TYPE
      SYNTAX INTEGER
      ACCESS read-only
      STATUS mandatory
      DESCRIPTION
          "The agents Coordinated Universal Time (UTC) days since
           January 1.
           It contains an integer from 0 to 365."

      ::=  { ibmappnIsAcTimeEntry 12 }

ibmappnIsAcTimeAgtUtcIsdst          OBJECT-TYPE
      SYNTAX INTEGER
      ACCESS read-only
      STATUS mandatory
      DESCRIPTION
          "The agents Coordinated Universal Time (UTC) daylight
           saving time flag.
           It is positive if daylight saving time is in effect.
           It is zero if daylight saving time is not in effect."

      ::=  { ibmappnIsAcTimeEntry 13 }

ibmappnIsAcTimeAgtName              OBJECT-TYPE
      SYNTAX DisplayString (SIZE (3..17))
      ACCESS read-only
      STATUS mandatory
      DESCRIPTION
          "The name of the agent who set the agent UTC times.
           It contains:
           a. the network id of the agent,
           b. a period (.)
           c. the cp name of the agent."

      ::=  { ibmappnIsAcTimeEntry 14 }

ibmappnIsAcTimeMgrUtcSecs           OBJECT-TYPE
      SYNTAX INTEGER
      ACCESS read-only
      STATUS mandatory
      DESCRIPTION
          "The managers Coordinated Universal Time (UTC) seconds.
           It contains an integer from 0 to 59."

      ::=  { ibmappnIsAcTimeEntry 15 }

ibmappnIsAcTimeMgrUtcMins           OBJECT-TYPE
      SYNTAX INTEGER
      ACCESS read-only
      STATUS mandatory
      DESCRIPTION
          "The managers Coordinated Universal Time (UTC) minutes.
           It contains an integer from 0 to 59."

      ::=  { ibmappnIsAcTimeEntry 16 }

ibmappnIsAcTimeMgrUtcHours          OBJECT-TYPE
      SYNTAX INTEGER
      ACCESS read-only
      STATUS mandatory
      DESCRIPTION
          "The managers Coordinated Universal Time (UTC) hours.
           It contains an integer from 0 to 23."

      ::=  { ibmappnIsAcTimeEntry 17 }

ibmappnIsAcTimeMgrUtcMdays          OBJECT-TYPE
      SYNTAX INTEGER
      ACCESS read-only
      STATUS mandatory
      DESCRIPTION
          "The managers Coordinated Universal Time (UTC) day of
           the month.
           It contains an integer from 1 to 31; or 0 if
           the manager has not set this object."

      ::=  { ibmappnIsAcTimeEntry 18 }

ibmappnIsAcTimeMgrUtcMonths         OBJECT-TYPE
      SYNTAX INTEGER {
                     january(12),
                     february(1),
                     march(2),
                     april(3),
                     may(4),
                     june(5),
                     july(6),
                     august(7),
                     september(8),
                     october(9),
                     november(10),
                     december(11)
                     }
      ACCESS read-only
      STATUS mandatory
      DESCRIPTION
          "The managers Coordinated Universal Time (UTC) months
           since January.
           It contains an integer from 0 to 11."

      ::=  { ibmappnIsAcTimeEntry 19 }

ibmappnIsAcTimeMgrUtcYears          OBJECT-TYPE
      SYNTAX INTEGER
      ACCESS read-only
      STATUS mandatory
      DESCRIPTION
          "The managers Coordinated Universal Time (UTC) years
           since 1900."

      ::=  { ibmappnIsAcTimeEntry 20 }

ibmappnIsAcTimeMgrUtcWdays          OBJECT-TYPE
      SYNTAX INTEGER {
                     sunday(7),
                     monday(1),
                     tuesday(2),
                     wednesday(3),
                     thursday(4),
                     friday(5),
                     saturday(6)
                     }
      ACCESS read-only
      STATUS mandatory
      DESCRIPTION
          "The managers Coordinated Universal Time (UTC) days since
           Sunday.
           It contains an integer from 0 to 6."

      ::=  { ibmappnIsAcTimeEntry 21 }

ibmappnIsAcTimeMgrUtcYdays          OBJECT-TYPE
      SYNTAX INTEGER
      ACCESS read-only
      STATUS mandatory
      DESCRIPTION
          "The managers Coordinated Universal Time (UTC) days since
           January 1.
           It contains an integer from 0 to 365."

      ::=  { ibmappnIsAcTimeEntry 22 }

ibmappnIsAcTimeMgrUtcIsdst          OBJECT-TYPE
      SYNTAX INTEGER
      ACCESS read-only
      STATUS mandatory
      DESCRIPTION
          "The managers Coordinated Universal Time (UTC) daylight
           saving time flag.
           It is positive if daylight saving time is in effect.
           It is zero if daylight saving time is not in effect."

      ::=  { ibmappnIsAcTimeEntry 23 }

ibmappnIsAcTimeMgrName              OBJECT-TYPE
      SYNTAX DisplayString (SIZE (0..17))
      ACCESS read-only
      STATUS mandatory
      DESCRIPTION
          "The name of the manager who set the manager UTC times or NULL if
           the manager name has not been set.
           It contains:
           a. the network id of the manager,
           b. a period (.)
           c. the cp name of the manager."

      ::=  { ibmappnIsAcTimeEntry 24 }

ibmappnIsAcTimeMgrTimeValid         OBJECT-TYPE
      SYNTAX INTEGER  {
                      notvalid(1),
                      valid(2)
                      }
      ACCESS read-write
      STATUS mandatory
      DESCRIPTION
          "This indicates whether or not the the manager UTC times
           are valid.  It is set by the manager if the manager
           determines the manager UTC times are valid."

      ::=  { ibmappnIsAcTimeEntry 25 }

-- *********************************************************************
-- Intermediate Session Accounting Data Table
-- ---------------------------------------------------------------------
-- This table contains accounting data for intermediate sessions
-- *********************************************************************

ibmappnIsAcDataTable OBJECT-TYPE
      SYNTAX SEQUENCE OF IbmappnIsAcDataEntry
      ACCESS not-accessible
      STATUS mandatory
      DESCRIPTION
           "Intermediate Session Accounting Data Table"

      ::= { ibmappnIsAccounting 5 }

ibmappnIsAcDataEntry OBJECT-TYPE
      SYNTAX IbmappnIsAcDataEntry
      ACCESS not-accessible
      STATUS mandatory
      DESCRIPTION
           "Entry of Intermediate Session Accounting Data Table."

      INDEX
             { ibmappnIsAcIndex }

      ::= { ibmappnIsAcDataTable 1 }

IbmappnIsAcDataEntry ::= SEQUENCE {
      ibmappnIsAcIndex                  INTEGER,
      ibmappnIsAcEntryType              INTEGER,
      ibmappnIsAcRecTime                TimeTicks,

      ibmappnIsAcFqLuName               DisplayString,
      ibmappnIsAcPcid                   OCTET STRING,
      ibmappnIsAcPriLuName              DisplayString,
      ibmappnIsAcSecLuName              DisplayString,
      ibmappnIsAcCosName                DisplayString,
      ibmappnIsAcModeName               DisplayString,
      ibmappnIsAcTransPriority          INTEGER,

      ibmappnIsAcSessType               INTEGER,
      ibmappnIsAcSessState              INTEGER,
      ibmappnIsAcSessStartTime          TimeTicks,
      ibmappnIsAcSessUpTime             TimeTicks,
      ibmappnIsAcCtrUpTime              TimeTicks,
      ibmappnIsAcEndReason              OCTET STRING,

      ibmappnIsAcP2SFmdPius             Counter,
      ibmappnIsAcS2PFmdPius             Counter,
      ibmappnIsAcP2SNonFmdPius          Counter,
      ibmappnIsAcS2PNonFmdPius          Counter,
      ibmappnIsAcP2SFmdBytes            Counter,
      ibmappnIsAcS2PFmdBytes            Counter,
      ibmappnIsAcP2SNonFmdBytes         Counter,
      ibmappnIsAcS2PNonFmdBytes         Counter,

      ibmappnIsAcRouteInfo              OCTET STRING
                               }

ibmappnIsAcIndex  OBJECT-TYPE
      SYNTAX INTEGER
      ACCESS read-only
      STATUS mandatory
      DESCRIPTION
          "Session accounting record index.  Upon initial startup, it
           will begin with 0, and increase up to maximum value of
           2**31-1 (2,147,483,647), and wraps. Upon subsequent startups,
           it will be initialized with the value of the oldest index
           in any media type; or 0 if no indices are found."

      ::=  { ibmappnIsAcDataEntry 1 }

ibmappnIsAcEntryType    OBJECT-TYPE
      SYNTAX INTEGER {
                     startEntry(1),
                     endEntry(2),
                     thresholdEntry(3),
                     checkpointEntry(4)
                     }
      ACCESS read-only
      STATUS mandatory
      DESCRIPTION
          "Indicates whether the entry was made as the result of:
           1. a session starting or,
           2. a session ending or,
           3. a session threshold reached or
           4. a session checkpoint request"

      ::=  { ibmappnIsAcDataEntry 2 }

ibmappnIsAcRecTime              OBJECT-TYPE
      SYNTAX TimeTicks
      ACCESS read-only
      STATUS mandatory
      DESCRIPTION
          "Intermediate Session Record time.  It represents
           the time in hundreds of a second since the node
           was started.  2**32-1 (4,294,967,295), and wraps."

      ::=  { ibmappnIsAcDataEntry 3 }

ibmappnIsAcFqLuName OBJECT-TYPE
      SYNTAX DisplayString (SIZE (3..17))
      ACCESS read-only
      STATUS mandatory
      DESCRIPTION
          "The network-qualified CP name or PU name of the
           node at which the session and pcid originated.  For APPN
           and LEN nodes, this is either CP name of the APPN node at
           which the origin LU is located or the CP name of the
           NN serving the LEN node at which the origin LU is
           located.  This field is from 3 to 17 characters in
           length, including a period (.) which separates the
           NetId from the NAU name."

      ::=  { ibmappnIsAcDataEntry 4 }

ibmappnIsAcPcid OBJECT-TYPE
      SYNTAX OCTET STRING  (SIZE (8))
      ACCESS read-only
      STATUS mandatory
      DESCRIPTION
          "The procedure correlation identifier (pcid) of a
           session.  It is an 8-octet value assigned
           by the primary LU."

      ::=  { ibmappnIsAcDataEntry 5 }

ibmappnIsAcPriLuName  OBJECT-TYPE
      SYNTAX DisplayString (SIZE (3..17))
      ACCESS read-only
      STATUS mandatory
      DESCRIPTION
          "Primary LU Name of the session."

      ::=  { ibmappnIsAcDataEntry 6 }

ibmappnIsAcSecLuName  OBJECT-TYPE
      SYNTAX DisplayString (SIZE (3..17))
      ACCESS read-only
      STATUS mandatory
      DESCRIPTION
          "Secondary LU Name of the session."

      ::=  { ibmappnIsAcDataEntry 7 }

ibmappnIsAcModeName        OBJECT-TYPE
      SYNTAX DisplayString  (SIZE (1..8))
      ACCESS read-only
      STATUS mandatory
      DESCRIPTION
          "The mode name used for this session"

      ::=  { ibmappnIsAcDataEntry 8 }

ibmappnIsAcCosName         OBJECT-TYPE
      SYNTAX DisplayString  (SIZE (1..8))
      ACCESS read-only
      STATUS mandatory
      DESCRIPTION
          "The class of service (cos) used for this session"

      ::=  { ibmappnIsAcDataEntry 9 }

ibmappnIsAcTransPriority OBJECT-TYPE
      SYNTAX INTEGER {
                     low(1),               --X'01'
                     medium(2),            --X'02'
                     high(3),              --X'03'
                     network(4)            --X'04'
                     }
      ACCESS read-only
      STATUS mandatory
      DESCRIPTION
           "Transmission priority for this session.
            The values are:
            1. Low
            2. Medium
            3. High
            4. Network"

      ::=  { ibmappnIsAcDataEntry 10 }

ibmappnIsAcSessType  OBJECT-TYPE
      SYNTAX INTEGER {
                     lu62(1),
                     lu0thru3(2)
                     }
      ACCESS read-only
      STATUS mandatory
      DESCRIPTION
          "The type of intermediate session."

      ::=  { ibmappnIsAcDataEntry 11 }

ibmappnIsAcSessState OBJECT-TYPE
      SYNTAX INTEGER    {
                         inactive(1),
                         pendactive(2),
                         active(3),
                         pendinact(4)
                         }
      ACCESS read-only
      STATUS mandatory
      DESCRIPTION
          "Indicates the state of the session.
           1. session is pending inactive or,
           2. session is pending active or,
           3. session is active or,
           4. session is inactive "

      ::=  { ibmappnIsAcDataEntry 12 }

ibmappnIsAcSessStartTime  OBJECT-TYPE
      SYNTAX TimeTicks
      ACCESS read-only
      STATUS mandatory
      DESCRIPTION
          "Time when the session started in hundreds of a second."

      ::=  { ibmappnIsAcDataEntry 13 }

ibmappnIsAcSessUpTime   OBJECT-TYPE
      SYNTAX TimeTicks
      ACCESS read-only
      STATUS mandatory
      DESCRIPTION
          "Length of time the session has been active
           in hundreds of a second."

      ::=  { ibmappnIsAcDataEntry 14 }

ibmappnIsAcCtrUpTime   OBJECT-TYPE
      SYNTAX TimeTicks
      ACCESS read-only
      STATUS mandatory
      DESCRIPTION
          "Length of time the session counters have been active
           in hundreds of a second."

      ::=  { ibmappnIsAcDataEntry 15 }

ibmappnIsAcEndReason       OBJECT-TYPE
      SYNTAX OCTET STRING  (SIZE (4))
      ACCESS read-only
      STATUS mandatory
      DESCRIPTION
          "The SNA sense code which resulted when the session
           ended."

      ::=  { ibmappnIsAcDataEntry 16 }

ibmappnIsAcP2SFmdPius             OBJECT-TYPE
      SYNTAX Counter
      ACCESS read-only
      STATUS mandatory
      DESCRIPTION
          "The number of FMD PIU's sent from the primary LU
           to the secondary LU.  The counter has a range of
           of 0 to 2**32; and then wraps."

      ::=  { ibmappnIsAcDataEntry 17 }

ibmappnIsAcS2PFmdPius             OBJECT-TYPE
      SYNTAX Counter
      ACCESS read-only
      STATUS mandatory
      DESCRIPTION
          "The number of FMD PIU's sent from the secondary LU
           to the primary LU.  The counter has a range of
           of 0 to 2**32; and then wraps."

      ::=  { ibmappnIsAcDataEntry 18 }

ibmappnIsAcP2SNonFmdPius          OBJECT-TYPE
      SYNTAX Counter
      ACCESS read-only
      STATUS mandatory
      DESCRIPTION
          "The number of non-FMD PIU's sent from the primary LU
           to the secondary LU.  The counter has a range of
           of 0 to 2**32; and then wraps."

      ::=  { ibmappnIsAcDataEntry 19 }

ibmappnIsAcS2PNonFmdPius          OBJECT-TYPE
      SYNTAX Counter
      ACCESS read-only
      STATUS mandatory
      DESCRIPTION
          "The number of non-FMD PIU's sent from the secondary LU
           to the primary LU.  The counter has a range of
           of 0 to 2**32; and then wraps."

      ::=  { ibmappnIsAcDataEntry 20 }

ibmappnIsAcP2SFmdBytes            OBJECT-TYPE
      SYNTAX Counter
      ACCESS read-only
      STATUS mandatory
      DESCRIPTION
          "The number of FMD bytes sent from the primary LU
           to the secondary LU.  The counter has a range of
           of 0 to 2**32; and then wraps."

      ::=  { ibmappnIsAcDataEntry 21 }

ibmappnIsAcS2PFmdBytes            OBJECT-TYPE
      SYNTAX Counter
      ACCESS read-only
      STATUS mandatory
      DESCRIPTION
          "The number of FMD bytes sent from the secondary LU
           to the primary LU.  The counter has a range of
           of 0 to 2**32; and then wraps."

      ::=  { ibmappnIsAcDataEntry 22 }

ibmappnIsAcP2SNonFmdBytes         OBJECT-TYPE
      SYNTAX Counter
      ACCESS read-only
      STATUS mandatory
      DESCRIPTION
          "The number of non-FMD bytes sent from the primary LU
           to the secondary LU.  The counter has a range of
           of 0 to 2**32; and then wraps."

      ::=  { ibmappnIsAcDataEntry 23 }

ibmappnIsAcS2PNonFmdBytes         OBJECT-TYPE
      SYNTAX Counter
      ACCESS read-only
      STATUS mandatory
      DESCRIPTION
          "The number of non-FMD bytes sent from the secondary LU
           to the primary LU.  The counter has a range of
           of 0 to 2**32; and then wraps."

      ::=  { ibmappnIsAcDataEntry 24 }

ibmappnIsAcRouteInfo  OBJECT-TYPE
      SYNTAX OCTET STRING
      ACCESS read-only
      STATUS mandatory
      DESCRIPTION
          "The route selection control vector (RSCV x'2B')
           used for this session.  It is present for APPN nodes;
           but is not present for LEN nodes."

      ::=  { ibmappnIsAcDataEntry 25 }

-- *********************************************************************
-- APPC Information
-- *********************************************************************
ibmappcInformation       OBJECT IDENTIFIER
                         ::= { ibmappnSessEndPoint 1 }

-- *********************************************************************
-- 1.   APPC Global Objects
-- 2.   APPC Defined Lu Table
-- 3.   APPC Defined Partner Lu Table
-- 4.   APPC Mode Table
-- 5.   APPC TP Table
-- 6.   APPC Session Table
-- 7.   APPC Session Error Table
-- *********************************************************************

-- *********************************************************************
-- APPC Global Objects
-- ---------------------------------------------------------------------
-- The following simple objects allow:
--    * the collection of APPC Session Information counters
--      to be started and stopped
--    * the collection of APPC Session RSCV's
--      to be started and stopped
-- *********************************************************************
ibmappcInGlobal OBJECT IDENTIFIER ::= { ibmappcInformation 1 }

ibmappcInGlobeStatus  OBJECT-TYPE
      SYNTAX INTEGER  {
                      notActive(1),
                      active(2)
                      }
      ACCESS read-write
      STATUS mandatory
      DESCRIPTION
          "Indicates the current collection options in effect:
           1. notActive: collection of counters and some names
                         is not active.
           2. active:    collection of counters and some names
                         is active."

      ::= { ibmappcInGlobal  1 }

ibmappcInGlobeRscv    OBJECT-TYPE
      SYNTAX INTEGER  {
                      notActive(1),
                      active(2)
                      }
      ACCESS read-write
      STATUS mandatory
      DESCRIPTION
          "Indicates the current collection options in effect:
           1. notActive: collection of route selection control vectors
                         is not active.
           2. active:    collection of route selection control vectors
                         is active."

      ::= { ibmappcInGlobal  2 }

ibmappcInGlobeRscvTime OBJECT-TYPE
      SYNTAX TimeTicks
      ACCESS read-only
      STATUS mandatory
      DESCRIPTION
          "Time when the ibmappcInGlobeRscv object last changed.
           This time is in hundreds of a second."

      ::=  { ibmappcInGlobal 3  }

ibmappcInGlobeCtrStatus  OBJECT-TYPE
      SYNTAX INTEGER  {
                      notActive(1),
                      active(2)
                      }
      ACCESS read-write
      STATUS mandatory
      DESCRIPTION
          "Indicates whether or not the appc session counters
           are active.  This object reflects the combination of the
           ibmappcInGlobeStatus object and any other product
           dependant object(s).  The values are:
           1. notActive: collection of counters and some names
                         is not active.
           2. active:    collection of counters and some names
                         is active."

      ::= { ibmappcInGlobal  4 }

ibmappcInGlobeCtrStatusTime OBJECT-TYPE
      SYNTAX TimeTicks
      ACCESS read-only
      STATUS mandatory
      DESCRIPTION
          "Time when the ibmappcInGlobeCtrStatus object last changed.
           This time is in hundreds of a second."

      ::=  { ibmappcInGlobal 5  }


ibmappcInGlobeActSess OBJECT-TYPE
      SYNTAX Gauge
      ACCESS read-only
      STATUS mandatory
      DESCRIPTION
          "Number of currently active APPC sessions"

      ::= { ibmappcInGlobal  6 }

-- *********************************************************************
--    APPC Local Lu Table
-- ---------------------------------------------------------------------
-- This table contains information about local LU's
-- *********************************************************************
ibmappcInLluTable OBJECT-TYPE
      SYNTAX SEQUENCE OF IbmappcInLluEntry
      ACCESS not-accessible
      STATUS mandatory
      DESCRIPTION
           "APPC Local Lu Table"

      ::= { ibmappcInformation 2 }

ibmappcInLluEntry OBJECT-TYPE
      SYNTAX IbmappcInLluEntry
      ACCESS not-accessible
      STATUS mandatory
      DESCRIPTION
           "Entry of APPC Local Lu Information Table."

      INDEX
             { ibmappcInLluLuName }

      ::= { ibmappcInLluTable 1 }

IbmappcInLluEntry     ::= SEQUENCE {
   ibmappcInLluLuName          DisplayString,
   ibmappcInLluDefType         INTEGER,
   ibmappcInLluSessLimit       INTEGER,
   ibmappcInLluBindRspMayQ     INTEGER,
   ibmappcInLluDefaultLu       INTEGER,
   ibmappcInLluCntlPtLu        INTEGER,
   ibmappcInLluCurActSess      Gauge
                                   }

ibmappcInLluLuName OBJECT-TYPE
      SYNTAX DisplayString (SIZE (3..17))
      ACCESS read-only
      STATUS mandatory
      DESCRIPTION
          "The network-qualified LU name.
           This field is from 3 to 17 characters in
           length, including a period (.) which separates the
           NetId from the NAU name."

      ::= { ibmappcInLluEntry 1 }

ibmappcInLluDefType   OBJECT-TYPE
      SYNTAX INTEGER {
                     sysdef(1),
                     dynamic(2)
                     }
      ACCESS read-only
      STATUS mandatory
      DESCRIPTION
          "Indicates whether the LU definition was specified in the
           nodes system definitions or was dynamically created."

      ::= { ibmappcInLluEntry 2 }

ibmappcInLluSessLimit OBJECT-TYPE
      SYNTAX INTEGER
      ACCESS read-only
      STATUS mandatory
      DESCRIPTION
          "The maximum number of session supported by this LU."

      ::= { ibmappcInLluEntry 3 }

ibmappcInLluBindRspMayQ OBJECT-TYPE
      SYNTAX INTEGER {
                     yes(1),
                     no(2)
                     }
      ACCESS read-only
      STATUS mandatory
      DESCRIPTION
          "Indicates whether or not a received bind response will
           be queued if the LU is not currently active."

      ::= { ibmappcInLluEntry 4 }

ibmappcInLluDefaultLu OBJECT-TYPE
      SYNTAX INTEGER {
                     yes(1),
                     no(2)
                     }
      ACCESS read-only
      STATUS mandatory
      DESCRIPTION
          "Indicates whether the LU is the default LU for the node."

      ::= { ibmappcInLluEntry 5 }

ibmappcInLluCntlPtLu  OBJECT-TYPE
      SYNTAX INTEGER {
                     yes(1),
                     no(2)
                     }
      ACCESS read-only
      STATUS mandatory
      DESCRIPTION
          "Indicates whether or not the LU is the control point (CP)
           LU."

      ::= { ibmappcInLluEntry 6 }

ibmappcInLluCurActSess OBJECT-TYPE
      SYNTAX Gauge
      ACCESS read-only
      STATUS mandatory
      DESCRIPTION
          "The number of currently active sessions."

      ::= { ibmappcInLluEntry 7 }

-- *********************************************************************
--    APPC Remote Partner Lu Table
-- ---------------------------------------------------------------------
-- This table contains information about remote partner LU's
-- *********************************************************************
ibmappcInRluTable OBJECT-TYPE
      SYNTAX SEQUENCE OF IbmappcInRluEntry
      ACCESS not-accessible
      STATUS mandatory
      DESCRIPTION
           "APPC Remote Partner Lu Table"

      ::= { ibmappcInformation 3 }

ibmappcInRluEntry OBJECT-TYPE
      SYNTAX IbmappcInRluEntry
      ACCESS not-accessible
      STATUS mandatory
      DESCRIPTION
           "Entry of APPC Remote Partner Lu Information Table."

      INDEX
             { ibmappcInRluLocLuName,
               ibmappcInRluParLuName }

      ::= { ibmappcInRluTable 1 }

IbmappcInRluEntry     ::= SEQUENCE {

   ibmappcInRluLocLuName       DisplayString,
   ibmappcInRluParLuName       DisplayString,

   ibmappcInRluParLuLocName    DisplayString,

   ibmappcInRluDefType         INTEGER,
   ibmappcInRluDefParaSessSup  INTEGER,
   ibmappcInRluDefCnosSup      INTEGER,
   ibmappcInRluDefAllVerSup    INTEGER,
   ibmappcInRluDefAttSecSup    INTEGER,
   ibmappcInRluDefSessSecSup   INTEGER,
   ibmappcInRluDefEnhanSecSup  INTEGER,

   ibmappcInRluActType         INTEGER,
   ibmappcInRluActParaSessSup  INTEGER,
   ibmappcInRluActCnosSup      INTEGER,
   ibmappcInRluActAllVerSup    INTEGER,
   ibmappcInRluActAttSecSup    INTEGER,
   ibmappcInRluActSessSecSup   INTEGER,
   ibmappcInRluActEnhanSecSup  INTEGER
                                   }

ibmappcInRluLocLuName OBJECT-TYPE
      SYNTAX DisplayString (SIZE (3..17))
      ACCESS read-only
      STATUS mandatory
      DESCRIPTION
          "The network-qualified local LU name.
           This field is from 3 to 17 characters in
           length, including a period (.) which separates the
           NetId from the NAU name."

      ::= { ibmappcInRluEntry 1 }

ibmappcInRluParLuName OBJECT-TYPE
      SYNTAX DisplayString (SIZE (3..17))
      ACCESS read-only
      STATUS mandatory
      DESCRIPTION
          "The network-qualified partner LU name.
           This field is from 3 to 17 characters in
           length, including a period (.) which separates the
           NetId from the NAU name."

      ::= { ibmappcInRluEntry 2 }

ibmappcInRluParLuLocName OBJECT-TYPE
      SYNTAX DisplayString (SIZE (3..17))
      ACCESS read-only
      STATUS mandatory
      DESCRIPTION
          "The network-qualified partner LU local name.
           This field is from 3 to 17 characters in
           length, including a period (.) which separates the
           NetId from the NAU name."

      ::= { ibmappcInRluEntry 3 }

ibmappcInRluDefType   OBJECT-TYPE
      SYNTAX INTEGER {
                     sysdef(1),
                     dynamic(2)
                     }
      ACCESS read-only
      STATUS mandatory
      DESCRIPTION
          "Indicates whether the LU definition was specified in the
           nodes system definitions or was dynamically created."

      ::= { ibmappcInRluEntry 4 }

ibmappcInRluDefParaSessSup OBJECT-TYPE
      SYNTAX INTEGER {
                     yes(1),
                     no(2)
                     }
      ACCESS read-only
      STATUS mandatory
      DESCRIPTION
          "Defined Parallel Sessions Supported.
           Indicates whether or not multiple session between
           the partner LU and its associated local LU are
           permitted."

      ::= { ibmappcInRluEntry 5 }

ibmappcInRluDefCnosSup OBJECT-TYPE
      SYNTAX INTEGER {
                     yes(1),
                     no(2)
                     }
      ACCESS read-only
      STATUS mandatory
      DESCRIPTION
          "Defined CNOS Supported.
           Indicates whether or not Change Number of Sessions (CNOS)
           will be used to negotiate session limits between the
           logical points."

      ::= { ibmappcInRluEntry 6 }

ibmappcInRluDefAllVerSup   OBJECT-TYPE
      SYNTAX INTEGER {
                     yes(1),
                     no(2)
                     }
      ACCESS read-only
      STATUS mandatory
      DESCRIPTION
          "Defined Already Verified Accepted.
           Indicates whether or not an attach, specifying that TP
           security has already been verified, is accepted by the
           adjacent CP LU."

      ::= { ibmappcInRluEntry 7 }

ibmappcInRluDefAttSecSup   OBJECT-TYPE
      SYNTAX INTEGER {
                     yes(1),
                     no(2)
                     }
      ACCESS read-only
      STATUS mandatory
      DESCRIPTION
          "Defined Attach Security Supported.
           Indicates whether or not the adjacent CP LU supports
           attach security."

      ::= { ibmappcInRluEntry 8 }

ibmappcInRluDefSessSecSup OBJECT-TYPE
      SYNTAX INTEGER {
                     yes(1),
                     no(2)
                     }
      ACCESS read-only
      STATUS mandatory
      DESCRIPTION
          "Defined Session Security Supported.
           Indicates whether or not the adjacent CP LU may omit
           a password in the user data portion of the BIND."

      ::= { ibmappcInRluEntry 9 }

ibmappcInRluDefEnhanSecSup OBJECT-TYPE
      SYNTAX INTEGER {
                     none(1),
                     level1(2),
                     level2(3)
                     }
      ACCESS read-only
      STATUS mandatory
      DESCRIPTION
          "Defined Enhance Security Supported.
           Indicates the level of enhance security support:
           1 = none
           2 = level 1
           3 = level 2"

      ::= { ibmappcInRluEntry 10 }

ibmappcInRluActType   OBJECT-TYPE
      SYNTAX INTEGER {
                     active(1),
                     notActive(2)
                     }
      ACCESS read-only
      STATUS mandatory
      DESCRIPTION
          "Indicates whether the LU active definitions are
           currently active or not currently active."

      ::= { ibmappcInRluEntry 11 }

ibmappcInRluActParaSessSup OBJECT-TYPE
      SYNTAX INTEGER {
                     yes(1),
                     no(2)
                     }
      ACCESS read-only
      STATUS mandatory
      DESCRIPTION
          "Active Parallel Sessions Supported.
           Indicates whether or not multiple session between
           the partner LU and its associated local LU are
           permitted."

      ::= { ibmappcInRluEntry 12 }

ibmappcInRluActCnosSup OBJECT-TYPE
      SYNTAX INTEGER {
                     yes(1),
                     no(2)
                     }
      ACCESS read-only
      STATUS mandatory
      DESCRIPTION
          "Active CNOS Supported.
           Indicates whether or not Change Number of Sessions (CNOS)
           will be used to negotiate session limits between the
           logical points."

      ::= { ibmappcInRluEntry 13 }

ibmappcInRluActAllVerSup   OBJECT-TYPE
      SYNTAX INTEGER {
                     yes(1),
                     no(2)
                     }
      ACCESS read-only
      STATUS mandatory
      DESCRIPTION
          "Active Already Verified Accepted.
           Indicates whether or not an attach, specifying that TP
           security has already been verified, is accepted by the
           adjacent CP LU."

      ::= { ibmappcInRluEntry 14 }

ibmappcInRluActAttSecSup   OBJECT-TYPE
      SYNTAX INTEGER {
                     yes(1),
                     no(2)
                     }
      ACCESS read-only
      STATUS mandatory
      DESCRIPTION
          "Active Attach Security Supported.
           Indicates whether or not the adjacent CP LU supports
           attach security."

      ::= { ibmappcInRluEntry 15 }

ibmappcInRluActSessSecSup OBJECT-TYPE
      SYNTAX INTEGER {
                     yes(1),
                     no(2)
                     }
      ACCESS read-only
      STATUS mandatory
      DESCRIPTION
          "Active Session Security Supported.
           Indicates whether or not the adjacent CP LU may omit
           a password in the user data portion of the BIND."

      ::= { ibmappcInRluEntry 16 }

ibmappcInRluActEnhanSecSup OBJECT-TYPE
      SYNTAX INTEGER {
                     none(1),
                     level1(2),
                     level2(3)
                     }
      ACCESS read-only
      STATUS mandatory
      DESCRIPTION
          "Active Enhance Security Supported.
           Indicates the level of enhance security support:
           1 = none
           2 = level 1
           3 = level 2"

      ::= { ibmappcInRluEntry 17 }

-- *********************************************************************
--    APPC Mode Table
-- ---------------------------------------------------------------------
-- This table contains information about session mode entries
-- *********************************************************************
ibmappcInMdTable OBJECT-TYPE
      SYNTAX SEQUENCE OF IbmappcInMdEntry
      ACCESS not-accessible
      STATUS mandatory
      DESCRIPTION
           "APPC Mode Table"

      ::= { ibmappcInformation 4 }

ibmappcInMdEntry OBJECT-TYPE
      SYNTAX IbmappcInMdEntry
      ACCESS not-accessible
      STATUS mandatory
      DESCRIPTION
           "Entry of APPC Mode Information Table."

      INDEX
             { ibmappcInMdLluName,
               ibmappcInMdRluName,
               ibmappcInMdModeName }

      ::= { ibmappcInMdTable 1 }


IbmappcInMdEntry     ::= SEQUENCE {
   ibmappcInMdLluName         DisplayString,
   ibmappcInMdRluName         DisplayString,
   ibmappcInMdModeName        DisplayString,

   ibmappcInMdDefType         INTEGER,

   ibmappcInMdSessEndTpName   DisplayString,

   ibmappcInMdSessLimit       INTEGER,
   ibmappcInMdMaxSessLimit    INTEGER,
   ibmappcInMdAutoActLimit    INTEGER,
   ibmappcInMdDrainSelf       INTEGER,
   ibmappcInMdDrainPart       INTEGER,

   ibmappcInMdMinCwinLimit    INTEGER,
   ibmappcInMdMinClosLimit    INTEGER,
   ibmappcInMdRecvPacWinSz    INTEGER,
   ibmappcInMdSendPacWinSz    INTEGER,
   ibmappcInMdPrefRecvRuSz    INTEGER,
   ibmappcInMdPrefSendRuSz    INTEGER,
   ibmappcInMdRecvRuSzUpBnd   INTEGER,
   ibmappcInMdSendRuSzUpBnd   INTEGER,
   ibmappcInMdRecvRuSzLoBnd   INTEGER,
   ibmappcInMdSendRuSzLoBnd   INTEGER,

   ibmappcInMdDfSyncLvl       INTEGER,
   ibmappcInMdAcSyncLvl       INTEGER,
   ibmappcInMdDfCrypto        INTEGER,
   ibmappcInMdAcCrypto        INTEGER,
   ibmappcInMdReinit          INTEGER,
   ibmappcInMdAltCode         INTEGER,

   ibmappcInMdActCwin         Gauge,
   ibmappcInMdActClos         Gauge,
   ibmappcInMdPndCwin         Gauge,
   ibmappcInMdPndClos         Gauge,
   ibmappcInMdPtmCwin         Gauge,
   ibmappcInMdPtmClos         Gauge,

   ibmappcInMdFreeSessLst     Gauge,
   ibmappcInMdWaitReqLst      Gauge
                                   }

ibmappcInMdLluName OBJECT-TYPE
      SYNTAX DisplayString (SIZE (3..17))
      ACCESS read-only
      STATUS mandatory
      DESCRIPTION
          "The network-qualified local LU name.
           This field is from 3 to 17 characters in
           length, including a period (.) which separates the
           NetId from the NAU name."

      ::= { ibmappcInMdEntry 1 }

ibmappcInMdRluName OBJECT-TYPE
      SYNTAX DisplayString (SIZE (3..17))
      ACCESS read-only
      STATUS mandatory
      DESCRIPTION
          "The network-qualified remote LU name.
           This field is from 3 to 17 characters in
           length, including a period (.) which separates the
           NetId from the NAU name."

      ::= { ibmappcInMdEntry 2 }

ibmappcInMdModeName OBJECT-TYPE
      SYNTAX DisplayString (SIZE (1..8))
      ACCESS read-only
      STATUS mandatory
      DESCRIPTION
          "The mode name."

      ::= { ibmappcInMdEntry 3 }

ibmappcInMdDefType   OBJECT-TYPE
      SYNTAX INTEGER {
                     sysdef(1),
                     dynamic(2)
                     }
      ACCESS read-only
      STATUS mandatory
      DESCRIPTION
          "Indicates whether the mode definition was specified in the
           nodes system definitions or was dynamically created."

      ::= { ibmappcInMdEntry 4 }

ibmappcInMdSessEndTpName OBJECT-TYPE
      SYNTAX DisplayString (SIZE (1..64))
      ACCESS read-only
      STATUS mandatory
      DESCRIPTION
          "The session end point transaction program name."

      ::= { ibmappcInMdEntry 5 }

ibmappcInMdSessLimit    OBJECT-TYPE
      SYNTAX INTEGER
      ACCESS read-only
      STATUS mandatory
      DESCRIPTION
          "Session Limit.
           Identifies the total number of sessions that can
           be established with the partner LU."

      ::= { ibmappcInMdEntry 6 }

ibmappcInMdMaxSessLimit    OBJECT-TYPE
      SYNTAX INTEGER
      ACCESS read-only
      STATUS mandatory
      DESCRIPTION
          "Maximum Session Limit.
           Specifies the maximum number of sessions supported
           by the LU pair using this mode name."

      ::= { ibmappcInMdEntry 7 }

ibmappcInMdAutoActLimit    OBJECT-TYPE
      SYNTAX INTEGER
      ACCESS read-only
      STATUS mandatory
      DESCRIPTION
          "Auto Activate Limit.
           Specifies the maximum number of sessions which can
           be activated when this mode is active."

      ::= { ibmappcInMdEntry 8 }

ibmappcInMdDrainSelf    OBJECT-TYPE
      SYNTAX INTEGER {
                     yes(1),
                     no(2)
                     }
      ACCESS read-only
      STATUS mandatory
      DESCRIPTION
          "Drain Self.
           Indicates whether or not the local LU can be drained."

      ::= { ibmappcInMdEntry 9 }

ibmappcInMdDrainPart    OBJECT-TYPE
      SYNTAX INTEGER {
                     yes(1),
                     no(2)
                     }
      ACCESS read-only
      STATUS mandatory
      DESCRIPTION
          "Drain Partner.
           Indicates whether or not the partner LU can be drained."

      ::= { ibmappcInMdEntry 10 }

ibmappcInMdMinCwinLimit OBJECT-TYPE
      SYNTAX INTEGER
      ACCESS read-only
      STATUS mandatory
      DESCRIPTION
          "Minimum Conwinners Limit.
           Identifies the minimum number of conwinner sessions."

      ::= { ibmappcInMdEntry 11 }

ibmappcInMdMinClosLimit OBJECT-TYPE
      SYNTAX INTEGER
      ACCESS read-only
      STATUS mandatory
      DESCRIPTION
          "Minimum Conlossers Limit.
           Identifies the minimum number of conloser sessions."

      ::=  { ibmappcInMdEntry 12 }

ibmappcInMdRecvPacWinSz OBJECT-TYPE
      SYNTAX INTEGER
      ACCESS read-only
      STATUS mandatory
      DESCRIPTION
          "The size of the receive pacing window."

      ::=  { ibmappcInMdEntry 13 }

ibmappcInMdSendPacWinSz OBJECT-TYPE
      SYNTAX INTEGER
      ACCESS read-only
      STATUS mandatory
      DESCRIPTION
          "The size of the send pacing window."

      ::=  { ibmappcInMdEntry 14 }

ibmappcInMdPrefRecvRuSz OBJECT-TYPE
      SYNTAX INTEGER
      ACCESS read-only
      STATUS mandatory
      DESCRIPTION
          "The preferred receive ru size."

      ::=  { ibmappcInMdEntry 15 }

ibmappcInMdPrefSendRuSz OBJECT-TYPE
      SYNTAX INTEGER
      ACCESS read-only
      STATUS mandatory
      DESCRIPTION
          "The preferred send ru size."

      ::=  { ibmappcInMdEntry 16 }

ibmappcInMdRecvRuSzUpBnd OBJECT-TYPE
      SYNTAX INTEGER
      ACCESS read-only
      STATUS mandatory
      DESCRIPTION
          "The receive ru upper boundary size."

      ::=  { ibmappcInMdEntry 17 }

ibmappcInMdSendRuSzUpBnd OBJECT-TYPE
      SYNTAX INTEGER
      ACCESS read-only
      STATUS mandatory
      DESCRIPTION
          "The send ru upper boundary size."

      ::=  { ibmappcInMdEntry 18 }

ibmappcInMdRecvRuSzLoBnd OBJECT-TYPE
      SYNTAX INTEGER
      ACCESS read-only
      STATUS mandatory
      DESCRIPTION
          "The receive ru lower boundary size."

      ::=  { ibmappcInMdEntry 19 }

ibmappcInMdSendRuSzLoBnd OBJECT-TYPE
      SYNTAX INTEGER
      ACCESS read-only
      STATUS mandatory
      DESCRIPTION
          "The send ru lower boundary size."

      ::=  { ibmappcInMdEntry 20 }

ibmappcInMdDfSyncLvl      OBJECT-TYPE
      SYNTAX INTEGER {
                     none(1),
                     confirm(2),
                     syncPoint(3)
                     }
      ACCESS read-only
      STATUS mandatory
      DESCRIPTION
          "The defined sync level."

      ::=  { ibmappcInMdEntry 21 }

ibmappcInMdAcSyncLvl      OBJECT-TYPE
      SYNTAX INTEGER {
                     none(1),
                     confirm(2),
                     syncPoint(3)
                     }
      ACCESS read-only
      STATUS mandatory
      DESCRIPTION
          "The active sync level."

      ::=  { ibmappcInMdEntry 22 }

ibmappcInMdDfCrypto      OBJECT-TYPE
      SYNTAX INTEGER {
                     yes(1),
                     no(2)
                     }
      ACCESS read-only
      STATUS mandatory
      DESCRIPTION
          "Defined cryoptograhy supported."

      ::=  { ibmappcInMdEntry 23 }

ibmappcInMdAcCrypto      OBJECT-TYPE
      SYNTAX INTEGER {
                     yes(1),
                     no(2)
                     }
      ACCESS read-only
      STATUS mandatory
      DESCRIPTION
          "Active cryptography supported."

      ::=  { ibmappcInMdEntry 24 }

ibmappcInMdReinit        OBJECT-TYPE
      SYNTAX INTEGER {
                     operatorControlled(1),
                     primaryOnly(2),
                     secondaryOnly(3),
                     primaryOrSecondary(4)
                     }
      ACCESS read-only
      STATUS mandatory
      DESCRIPTION
          "The reinitialization parameter."

      ::=  { ibmappcInMdEntry 25 }

ibmappcInMdAltCode       OBJECT-TYPE
      SYNTAX INTEGER {
                     yes(1),
                     no(2)
                     }
      ACCESS read-only
      STATUS mandatory
      DESCRIPTION
          "Alternate code supported."

      ::=  { ibmappcInMdEntry 26 }

ibmappcInMdActCwin        OBJECT-TYPE
      SYNTAX Gauge
      ACCESS read-only
      STATUS mandatory
      DESCRIPTION
          "The number of active conwinners."

      ::=  { ibmappcInMdEntry 27 }

ibmappcInMdActClos        OBJECT-TYPE
      SYNTAX Gauge
      ACCESS read-only
      STATUS mandatory
      DESCRIPTION
          "The number of active conlosers."

      ::=  { ibmappcInMdEntry 28 }

ibmappcInMdPndCwin        OBJECT-TYPE
      SYNTAX Gauge
      ACCESS read-only
      STATUS mandatory
      DESCRIPTION
          "The number of pending conwinners."

      ::=  { ibmappcInMdEntry 29 }

ibmappcInMdPndClos        OBJECT-TYPE
      SYNTAX Gauge
      ACCESS read-only
      STATUS mandatory
      DESCRIPTION
          "The number of pending conlosers."

      ::=  { ibmappcInMdEntry 30 }

ibmappcInMdPtmCwin        OBJECT-TYPE
      SYNTAX Gauge
      ACCESS read-only
      STATUS mandatory
      DESCRIPTION
          "The number of pending termination conlosers."

      ::=  { ibmappcInMdEntry 31 }

ibmappcInMdPtmClos        OBJECT-TYPE
      SYNTAX Gauge
      ACCESS read-only
      STATUS mandatory
      DESCRIPTION
          "The number of pending termination conwinners."

      ::=  { ibmappcInMdEntry 32 }

ibmappcInMdFreeSessLst    OBJECT-TYPE
      SYNTAX Gauge
      ACCESS read-only
      STATUS mandatory
      DESCRIPTION
          "The size of the free seesion list."

      ::=  { ibmappcInMdEntry 33 }

ibmappcInMdWaitReqLst     OBJECT-TYPE
      SYNTAX Gauge
      ACCESS read-only
      STATUS mandatory
      DESCRIPTION
          "The size of the waiting request list."

      ::=  { ibmappcInMdEntry 34 }

-- *********************************************************************
--    APPC Local TP Table
-- ---------------------------------------------------------------------
-- This table contains information about local transaction programs
-- *********************************************************************
ibmappcInLtpTable OBJECT-TYPE
      SYNTAX SEQUENCE OF IbmappcInLtpEntry
      ACCESS not-accessible
      STATUS mandatory
      DESCRIPTION
           "APPC Local TP Table"

      ::= { ibmappcInformation 5 }

ibmappcInLtpEntry OBJECT-TYPE
      SYNTAX IbmappcInLtpEntry
      ACCESS not-accessible
      STATUS mandatory
      DESCRIPTION
           "Entry of APPC Local TP Information Table."

      INDEX
             { ibmappcInLtpLuName,
               ibmappcInLtpTpName }

      ::= { ibmappcInLtpTable 1 }


IbmappcInLtpEntry     ::= SEQUENCE {

   ibmappcInLtpLuName         DisplayString,
   ibmappcInLtpTpName         DisplayString,

   ibmappcInLtpDefType        INTEGER,

   ibmappcInLtpSyncLvl        INTEGER,
   ibmappcInLtpInstLmt        INTEGER,
   ibmappcInLtpInstNum        Gauge,
   ibmappcInLtpStatus         INTEGER,
   ibmappcInLtpLongRun        INTEGER,
   ibmappcInLtpPfCnos         INTEGER,
   ibmappcInLtpPfSessCntl     INTEGER,
   ibmappcInLtpPfDefine       INTEGER,
   ibmappcInLtpPfDisplay      INTEGER,
   ibmappcInLtpPfAllocSer     INTEGER,
   ibmappcInLtpRescSup        INTEGER,
   ibmappcInLtpRecoSup        INTEGER,
   ibmappcInLtpSecReq         INTEGER,
   ibmappcInLtpSecLvl         INTEGER,
   ibmappcInLtpVerPip         INTEGER,
   ibmappcInLtpPipSubNum      INTEGER
                                   }

ibmappcInLtpLuName OBJECT-TYPE
      SYNTAX DisplayString (SIZE (3..17))
      ACCESS read-only
      STATUS mandatory
      DESCRIPTION
          "The network-qualified local LU name.
           This field is from 3 to 17 characters in
           length, including a period (.) which separates the
           NetId from the NAU name."

      ::= { ibmappcInLtpEntry 1 }

ibmappcInLtpTpName OBJECT-TYPE
      SYNTAX DisplayString (SIZE (1..64))
      ACCESS read-only
      STATUS mandatory
      DESCRIPTION
          "The local transaction program name."

      ::= { ibmappcInLtpEntry 2 }

ibmappcInLtpDefType      OBJECT-TYPE
      SYNTAX INTEGER {
                     sysdef(1),
                     dynamic(2)
                     }
      ACCESS read-only
      STATUS mandatory
      DESCRIPTION
          "The TP definition type.
           Indicates whether the TP was specified in the nodes system
           definitions or was dynamically created."

      ::= { ibmappcInLtpEntry 3 }

ibmappcInLtpSyncLvl       OBJECT-TYPE
      SYNTAX INTEGER {
                     none(1),
                     confirm(2),
                     syncPoint(3)
                     }
      ACCESS read-only
      STATUS mandatory
      DESCRIPTION
          "The TP synchroniztion level."

      ::= { ibmappcInLtpEntry 4 }

ibmappcInLtpInstLmt       OBJECT-TYPE
      SYNTAX INTEGER
      ACCESS read-only
      STATUS mandatory
      DESCRIPTION
          "The TP instance limit."

      ::= { ibmappcInLtpEntry 5 }

ibmappcInLtpInstNum        OBJECT-TYPE
      SYNTAX Gauge
      ACCESS read-only
      STATUS mandatory
      DESCRIPTION
          "The number of TP instances."

      ::= { ibmappcInLtpEntry 6 }

ibmappcInLtpStatus        OBJECT-TYPE
      SYNTAX INTEGER {
                     enabled(1),
                     tempDisabled(2),
                     permDisabled(3)
                     }
      ACCESS read-only
      STATUS mandatory
      DESCRIPTION
          "The TP status."

      ::= { ibmappcInLtpEntry 7 }

ibmappcInLtpLongRun       OBJECT-TYPE
      SYNTAX INTEGER {
                     yes(1),
                     no(2)
                     }
      ACCESS read-only
      STATUS mandatory
      DESCRIPTION
          "The long running transaction program."

      ::= { ibmappcInLtpEntry 8 }

ibmappcInLtpPfCnos        OBJECT-TYPE
      SYNTAX INTEGER {
                     yes(1),
                     no(2)
                     }
      ACCESS read-only
      STATUS mandatory
      DESCRIPTION
          "The TP Change Number of Sessions (CNOS) privileged
           function. This parameter specifies whether or not
           this program is allowed to issue CNOS verbs."

      ::= { ibmappcInLtpEntry 9 }


ibmappcInLtpPfSessCntl    OBJECT-TYPE
      SYNTAX INTEGER {
                     yes(1),
                     no(2)
                     }
      ACCESS read-only
      STATUS mandatory
      DESCRIPTION
          "The TP Session Control privileged
           function. This parameter specifies whether or not
           this program is allowed to issue ACTIVATE_SESSION
           and DEACTIVATE_SESSION verbs."

      ::= { ibmappcInLtpEntry 10 }

ibmappcInLtpPfDefine      OBJECT-TYPE
      SYNTAX INTEGER {
                     yes(1),
                     no(2)
                     }
      ACCESS read-only
      STATUS mandatory
      DESCRIPTION
          "The TP Define privileged
           function. This parameter specifies whether or not
           this program is allowed to issue DEFINE and
           DELETE verbs."

      ::= { ibmappcInLtpEntry 11 }

ibmappcInLtpPfDisplay     OBJECT-TYPE
      SYNTAX INTEGER {
                     yes(1),
                     no(2)
                     }
      ACCESS read-only
      STATUS mandatory
      DESCRIPTION
          "The TP Display privileged
           function. This parameter specifies whether or not
           this program is allowed to issue DISPLAY verbs."

      ::= { ibmappcInLtpEntry 12 }

ibmappcInLtpPfAllocSer    OBJECT-TYPE
      SYNTAX INTEGER {
                     yes(1),
                     no(2)
                     }
      ACCESS read-only
      STATUS mandatory
      DESCRIPTION
          "The TP Allocate Service privileged
           function. This parameter specifies whether or not
           this program is allowed to issue the ALLOCATE
           verb with its TPN parameter specifying an SNA
           service transmission program."

      ::= { ibmappcInLtpEntry 13 }

ibmappcInLtpRescSup       OBJECT-TYPE
      SYNTAX INTEGER {
                     basicConv(1),
                     mappedConv(2),
                     allConv(3)
                     }
      ACCESS read-only
      STATUS mandatory
      DESCRIPTION
          "The TP resources supported parameter.
           1. basic conversations
           2. mapped conversations
           3. all conversations"

      ::= { ibmappcInLtpEntry 14 }

ibmappcInLtpRecoSup       OBJECT-TYPE
      SYNTAX INTEGER {
                     yes(1),
                     no(2)
                     }
      ACCESS read-only
      STATUS mandatory
      DESCRIPTION
          "The TP reconnect supported parameter."

      ::= { ibmappcInLtpEntry 15 }

ibmappcInLtpSecReq        OBJECT-TYPE
      SYNTAX INTEGER {
                     yes(1),
                     no(2)
                     }
      ACCESS read-only
      STATUS mandatory
      DESCRIPTION
          "The TP security required parameter."

      ::= { ibmappcInLtpEntry 16 }

ibmappcInLtpSecLvl        OBJECT-TYPE
      SYNTAX INTEGER {
                     noAdditional(1),
                     specificUsers(2),
                     specificProfiles(3),
                     specificUserProfiles(4),
                     specificUserLus(5),
                     specificUserProfLus(6)
                     }
      ACCESS read-only
      STATUS mandatory
      DESCRIPTION
          "The TP security level parameter."

      ::= { ibmappcInLtpEntry 17 }

ibmappcInLtpVerPip        OBJECT-TYPE
      SYNTAX INTEGER {
                     yes(1),
                     no(2)
                     }
      ACCESS read-only
      STATUS mandatory
      DESCRIPTION
          "The TP verify pip parameter."

      ::= { ibmappcInLtpEntry 18 }

ibmappcInLtpPipSubNum     OBJECT-TYPE
      SYNTAX INTEGER
      ACCESS read-only
      STATUS mandatory
      DESCRIPTION
          "The TP number of pip subfields."

      ::= { ibmappcInLtpEntry 19 }

-- *********************************************************************
--    APPC Session Table
-- ---------------------------------------------------------------------
-- This table contains information about APPC sessions
-- *********************************************************************
ibmappcInSsTable OBJECT-TYPE
      SYNTAX SEQUENCE OF IbmappcInSsEntry
      ACCESS not-accessible
      STATUS mandatory
      DESCRIPTION
           "APPC Session Table"

      ::= { ibmappcInformation 6 }

ibmappcInSsEntry OBJECT-TYPE
      SYNTAX IbmappcInSsEntry
      ACCESS not-accessible
      STATUS mandatory
      DESCRIPTION
           "Entry of APPC Session Information Table."

      INDEX
             { ibmappcInSsFqLuName,
               ibmappcInSsPcid }

      ::= { ibmappcInSsTable 1 }

IbmappcInSsEntry     ::= SEQUENCE {
   ibmappcInSsFqLuName        DisplayString,
   ibmappcInSsPcid            OCTET STRING,

   ibmappcInSsPluName         DisplayString,
   ibmappcInSsSluName         DisplayString,
   ibmappcInSsModeName        DisplayString,
   ibmappcInSsCosName         DisplayString,

   ibmappcInSsSessType        INTEGER,
   ibmappcInSsSessState       INTEGER,
   ibmappcInSsTransPriority   INTEGER,
   ibmappcInSsPaceType        INTEGER,
   ibmappcInSsSendMaxRuSz     INTEGER,
   ibmappcInSsRecvMaxRuSz     INTEGER,
   ibmappcInSsEnhanceSecSup   INTEGER,

   ibmappcInSsSendPacingType  INTEGER,
   ibmappcInSsSendRpc         Gauge,
   ibmappcInSsSendNxWndwSize  Gauge,
   ibmappcInSsRecvPacingType  INTEGER,
   ibmappcInSsRecvRpc         Gauge,
   ibmappcInSsRecvNxWndwSize  Gauge,

   ibmappcInSsSessStartTime   TimeTicks,
   ibmappcInSsSessUpTime      TimeTicks,
   ibmappcInSsCtrUpTime       TimeTicks,

   ibmappcInSsP2SFmdPius      Counter,
   ibmappcInSsS2PFmdPius      Counter,
   ibmappcInSsP2SNonFmdPius   Counter,
   ibmappcInSsS2PNonFmdPius   Counter,
   ibmappcInSsP2SFmdBytes     Counter,
   ibmappcInSsS2PFmdBytes     Counter,
   ibmappcInSsP2SNonFmdBytes  Counter,
   ibmappcInSsS2PNonFmdBytes  Counter,

   ibmappcInSsRscv            OCTET STRING
                                   }

ibmappcInSsFqLuName OBJECT-TYPE
      SYNTAX DisplayString (SIZE (3..17))
      ACCESS read-only
      STATUS mandatory
      DESCRIPTION
          "The network-qualified CP name or PU name of the
           node at which the session and cid originated.  For APPN
           and LEN nodes, this is either CP name of the APPN node at
           which the origin LU is located or the CP name of the
           NN serving the LEN node at which the origin LU is
           located.  This field is from 3 to 17 characters in
           length, including a period (.) which separates the
           NetId from the NAU name."

      ::=  { ibmappcInSsEntry 1 }

ibmappcInSsPcid OBJECT-TYPE
      SYNTAX OCTET STRING  (SIZE (8))
      ACCESS read-only
      STATUS mandatory
      DESCRIPTION
          "The procedure correlation identifier (pcid) of a
           session.  It is an 8-octet value assigned
           by the primary LU."

      ::=  { ibmappcInSsEntry 2 }


ibmappcInSsPluName OBJECT-TYPE
      SYNTAX DisplayString (SIZE (3..17))
      ACCESS read-only
      STATUS mandatory
      DESCRIPTION
          "The primary LU name of the session."

      ::=  { ibmappcInSsEntry 3 }

ibmappcInSsSluName OBJECT-TYPE
      SYNTAX DisplayString (SIZE (3..17))
      ACCESS read-only
      STATUS mandatory
      DESCRIPTION
          "The secondary LU name of the session."

      ::=  { ibmappcInSsEntry 4 }

ibmappcInSsModeName OBJECT-TYPE
      SYNTAX DisplayString  (SIZE (1..8))
      ACCESS read-only
      STATUS mandatory
      DESCRIPTION
          "The Mode Name name used for this session.
           This is a 1-8 character name."

      ::=  { ibmappcInSsEntry 5 }

ibmappcInSsCosName OBJECT-TYPE
      SYNTAX DisplayString  (SIZE (1..8))
      ACCESS read-only
      STATUS mandatory
      DESCRIPTION
          "The Class of Service (COS) name used for this session.
           This is a 1-8 character name."

      ::=  { ibmappcInSsEntry 6 }

ibmappcInSsSessType  OBJECT-TYPE
      SYNTAX INTEGER {
                     lu62(1)
                     }
      ACCESS read-only
      STATUS mandatory
      DESCRIPTION
          "The type of session."

      ::=  { ibmappcInSsEntry 7 }

ibmappcInSsSessState OBJECT-TYPE
      SYNTAX INTEGER    {
                        inactive(1),
                        pendactive(2),
                        active(3),
                        pendinact(4)
                        }
      ACCESS read-only
      STATUS mandatory
      DESCRIPTION
          "Indicates the state of the session.
           1. session is pending inactive or,
           2. session is pending active or,
           3. session is active or,
           4. session is inactive"

      ::=  { ibmappcInSsEntry 8 }

ibmappcInSsTransPriority OBJECT-TYPE
      SYNTAX INTEGER
      ACCESS read-only
      STATUS mandatory
      DESCRIPTION
          "The transmission priority of this session."

      ::=  { ibmappcInSsEntry 9 }

ibmappcInSsPaceType     OBJECT-TYPE
      SYNTAX INTEGER {
                     none(1),
                     fixed(2),
                     adaptive(3)
                     }
      ACCESS read-only
      STATUS mandatory
      DESCRIPTION
          "The type of pacing used for this session."

      ::=  { ibmappcInSsEntry 10 }

ibmappcInSsSendMaxRuSz  OBJECT-TYPE
      SYNTAX INTEGER
      ACCESS read-only
      STATUS mandatory
      DESCRIPTION
          "The maximum ru size which can be sent."

      ::=  { ibmappcInSsEntry 11 }

ibmappcInSsRecvMaxRuSz  OBJECT-TYPE
      SYNTAX INTEGER
      ACCESS read-only
      STATUS mandatory
      DESCRIPTION
          "The maximum ru size which can be received."

      ::=  { ibmappcInSsEntry 12 }

ibmappcInSsEnhanceSecSup OBJECT-TYPE
      SYNTAX INTEGER {
                     none(1),
                     level1(2),
                     level2(3)
                     }
      ACCESS read-only
      STATUS mandatory
      DESCRIPTION
          "Enhanced security supported.
           Indicates the level of enhance security support:
           1 = none
           2 = level 1
           3 = level 2"

      ::=  { ibmappcInSsEntry 13 }

ibmappcInSsSendPacingType OBJECT-TYPE
      SYNTAX INTEGER {
                     none(1),
                     fixed(2),
                     adaptive(3)
                     }
      ACCESS read-only
      STATUS mandatory
      DESCRIPTION
          "The type of pacing being used for sending data."

      ::=  { ibmappcInSsEntry 14 }

ibmappcInSsSendRpc OBJECT-TYPE
      SYNTAX Gauge
      ACCESS read-only
      STATUS mandatory
      DESCRIPTION
          "The send residual pace count.  This represents
           the number of MU's that can still be
           sent in the current session window."

      ::=  { ibmappcInSsEntry 15 }

ibmappcInSsSendNxWndwSize OBJECT-TYPE
      SYNTAX Gauge
      ACCESS read-only
      STATUS mandatory
      DESCRIPTION
          "The size of the next window which will
           be used to send data."

      ::=  { ibmappcInSsEntry 16 }

ibmappcInSsRecvPacingType OBJECT-TYPE
      SYNTAX INTEGER {
                     none(1),
                     fixed(2),
                     adaptive(3)
                     }
      ACCESS read-only
      STATUS mandatory
      DESCRIPTION
          "The type of pacing being used for receiving data."

      ::=  { ibmappcInSsEntry 17 }

ibmappcInSsRecvRpc OBJECT-TYPE
      SYNTAX Gauge
      ACCESS read-only
      STATUS mandatory
      DESCRIPTION
          "The receive residual pace count.  This represents
           the number of MU's that can still be
           received in the current session window."

      ::=  { ibmappcInSsEntry 18 }

ibmappcInSsRecvNxWndwSize OBJECT-TYPE
      SYNTAX Gauge
      ACCESS read-only
      STATUS mandatory
      DESCRIPTION
          "The size of the next window which will
           be used to receive data."

      ::=  { ibmappcInSsEntry 19 }

ibmappcInSsSessStartTime  OBJECT-TYPE
      SYNTAX TimeTicks
      ACCESS read-only
      STATUS mandatory
      DESCRIPTION
          "Time when the session started in hundreds of a second."

      ::=  { ibmappcInSsEntry 20 }

ibmappcInSsSessUpTime   OBJECT-TYPE
      SYNTAX TimeTicks
      ACCESS read-only
      STATUS mandatory
      DESCRIPTION
          "Length of time the session has been active
           in hundreds of a second."

      ::=  { ibmappcInSsEntry 21 }

ibmappcInSsCtrUpTime   OBJECT-TYPE
      SYNTAX TimeTicks
      ACCESS read-only
      STATUS mandatory
      DESCRIPTION
          "Length of time the session counters have been active
           in hundreds of a second."

      ::=  { ibmappcInSsEntry 22 }

ibmappcInSsP2SFmdPius OBJECT-TYPE
      SYNTAX Counter
      ACCESS read-only
      STATUS mandatory
      DESCRIPTION
          "Number of FMD PIUs sent from the Primary LU
           to the Secondary LU"

      ::=  { ibmappcInSsEntry 23 }

ibmappcInSsS2PFmdPius OBJECT-TYPE
      SYNTAX Counter
      ACCESS read-only
      STATUS mandatory
      DESCRIPTION
          "Number of FMD PIUs sent from the Secondary LU
           to the Primary LU"

      ::=  { ibmappcInSsEntry 24 }

ibmappcInSsP2SNonFmdPius OBJECT-TYPE
      SYNTAX Counter
      ACCESS read-only
      STATUS mandatory
      DESCRIPTION
          "Number of non-FMD PIUs sent from the Primary LU
           to the Secondary LU"

      ::=  { ibmappcInSsEntry 25 }

ibmappcInSsS2PNonFmdPius OBJECT-TYPE
      SYNTAX Counter
      ACCESS read-only
      STATUS mandatory
      DESCRIPTION
          "Number of non-FMD PIUs sent from the Secondary LU
           to the Primary LU"

      ::=  { ibmappcInSsEntry 26 }

ibmappcInSsP2SFmdBytes  OBJECT-TYPE
      SYNTAX Counter
      ACCESS read-only
      STATUS mandatory
      DESCRIPTION
          "Number of FMD Bytes sent from the Primary LU
           to the Secondary LU"

      ::=  { ibmappcInSsEntry 27 }

ibmappcInSsS2PFmdBytes  OBJECT-TYPE
      SYNTAX Counter
      ACCESS read-only
      STATUS mandatory
      DESCRIPTION
          "Number of FMD Bytes sent from the Secondary LU
           to the Primary LU"

      ::=  { ibmappcInSsEntry 28 }

ibmappcInSsP2SNonFmdBytes  OBJECT-TYPE
      SYNTAX Counter
      ACCESS read-only
      STATUS mandatory
      DESCRIPTION
          "Number of non-FMD Bytes sent from the Primary LU
           to the Secondary LU"

      ::=  { ibmappcInSsEntry 29 }

ibmappcInSsS2PNonFmdBytes  OBJECT-TYPE
      SYNTAX Counter
      ACCESS read-only
      STATUS mandatory
      DESCRIPTION
          "Number of non-FMD Bytes sent from the Secondary LU
           to the Primary LU"

      ::=  { ibmappcInSsEntry 30 }

ibmappcInSsRscv     OBJECT-TYPE
      SYNTAX OCTET STRING
      ACCESS read-only
      STATUS mandatory
      DESCRIPTION
          "The route selection control vector (RSCV x'2B')
           used for this session.  It is not present for APPN CP-CP
           sessions and also not present for LEN nodes.  The
           format of this vector is described in SNA Formats."

      ::=  { ibmappcInSsEntry 31 }

-- *********************************************************************
--    APPC Session Status Table
-- ---------------------------------------------------------------------
-- This table contains information about APPC session problems
-- *********************************************************************
ibmappcInSsStatusTable OBJECT-TYPE
      SYNTAX SEQUENCE OF IbmappcInSsStatusEntry
      ACCESS not-accessible
      STATUS mandatory
      DESCRIPTION
           "APPC Session Status Table"

      ::= { ibmappcInformation 7 }

ibmappcInSsStatusEntry OBJECT-TYPE
      SYNTAX IbmappcInSsStatusEntry
      ACCESS not-accessible
      STATUS mandatory
      DESCRIPTION
           "Entry of APPC Session Status Information Table.
            This table is indexed by the SsStatusIndex, which is an
            integer that is continuously updated until it eventually
            wraps.  This provides the management station the ability
            to retrieve only the updates to the table by using the
            standard GET NEXT."

      INDEX
             { ibmappcInSsStatusIndex }

      ::= { ibmappcInSsStatusTable 1 }

IbmappcInSsStatusEntry     ::= SEQUENCE {
      ibmappcInSsStatusIndex                INTEGER,
      ibmappcInSsStatusTime                 TimeTicks,
      ibmappcInSsStatusType                 INTEGER,
      ibmappcInSsStatusLocLuName            DisplayString,
      ibmappcInSsStatusParLuName            DisplayString,
      ibmappcInSsStatusModeName             DisplayString,
      ibmappcInSsStatusUnbindType           OCTET STRING,
      ibmappcInSsStatusSenseCode            OCTET STRING,
      ibmappcInSsStatusComponentId          DisplayString,
      ibmappcInSsStatusDetectModule         DisplayString
                                        }


ibmappcInSsStatusIndex       OBJECT-TYPE
      SYNTAX INTEGER
      ACCESS read-only
      STATUS mandatory
      DESCRIPTION
          "Table index.  The value of the index begins at zero
           and is incremented up to a maximum value of 2**31-1
           (2,147,483,647) before wrapping."

      ::=  { ibmappcInSsStatusEntry   1 }

ibmappcInSsStatusTime    OBJECT-TYPE
      SYNTAX TimeTicks
      ACCESS read-only
      STATUS mandatory
      DESCRIPTION
          "Time (in hundreds of a second) since this node was last
           initialized."

      ::=  { ibmappcInSsStatusEntry   2 }

ibmappcInSsStatusType        OBJECT-TYPE
      SYNTAX INTEGER  {
                      recvNegBindRsp(1),
                      sendNegBindRsp(2),
                      sessActRejected(3),
                      unbindSent(4),
                      unbindReceived(5)
                      }
      ACCESS read-only
      STATUS mandatory
      DESCRIPTION
          "Indicates the entry type:
           1. Received a negative bind response from the partner LU.
           2. Sent a negative bind response to the partner LU.
           3. Session activation rejected by the partner LU.
           4. Unbind sent to the partner LU.
           5. Unbind received from the partner LU."

      ::=  { ibmappcInSsStatusEntry   3 }

ibmappcInSsStatusLocLuName OBJECT-TYPE
      SYNTAX DisplayString (SIZE (3..17))
      ACCESS read-only
      STATUS mandatory
      DESCRIPTION
          "The network-qualified local LU name.
           This field is from 3 to 17 characters in
           length, including a period (.) which separates the
           NetId from the NAU name."

      ::=  { ibmappcInSsStatusEntry   4 }

ibmappcInSsStatusParLuName OBJECT-TYPE
      SYNTAX DisplayString (SIZE (3..17))
      ACCESS read-only
      STATUS mandatory
      DESCRIPTION
          "The network-qualified partner LU name.
           This field is from 3 to 17 characters in
           length, including a period (.) which separates the
           NetId from the NAU name."

      ::=  { ibmappcInSsStatusEntry   5 }

ibmappcInSsStatusModeName OBJECT-TYPE
      SYNTAX DisplayString (SIZE (1..8))
      ACCESS read-only
      STATUS mandatory
      DESCRIPTION
          "The mode name."

      ::=  { ibmappcInSsStatusEntry   6 }

ibmappcInSsStatusUnbindType OBJECT-TYPE
      SYNTAX OCTET STRING (SIZE (1))
      ACCESS read-only
      STATUS mandatory
      DESCRIPTION
          "The type of unbind which terminated the session.  This
           value is consists of one (1) octet; and its meaning
           is defined in SNA Formats."

      ::=  { ibmappcInSsStatusEntry   7 }

ibmappcInSsStatusSenseCode  OBJECT-TYPE
      SYNTAX OCTET STRING (SIZE (4))
      ACCESS read-only
      STATUS mandatory
      DESCRIPTION
          "The sense code associated with the termination of the
           session.  This value consists of four (4) octets; and
           its meaning is defined in SNA Formats."

      ::=  { ibmappcInSsStatusEntry   8 }


ibmappcInSsStatusComponentId OBJECT-TYPE
      SYNTAX DisplayString (SIZE (1..8))
      ACCESS read-only
      STATUS mandatory
      DESCRIPTION
          "The name of the component which sent the entry."

      ::=  { ibmappcInSsStatusEntry   9 }

ibmappcInSsStatusDetectModule  OBJECT-TYPE
      SYNTAX DisplayString (SIZE (1..8))
      ACCESS read-only
      STATUS mandatory
      DESCRIPTION
          "The name of the module which detected the condition
           and sent the entry."

      ::=  { ibmappcInSsStatusEntry  10 }

END
