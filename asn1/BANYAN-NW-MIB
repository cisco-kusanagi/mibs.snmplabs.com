BANYAN-NW-MIB --{ iso org(3) dod(6) internet(1) private(4) enterprises(1) 130 2 1 1 }

DEFINITIONS ::= BEGIN

IMPORTS
	enterprises, OBJECT-TYPE, NetworkAddress, IpAddress, Counter, 
	Gauge, TimeTicks
		FROM RFC1155-SMI;

-- banyan tags

banyan  OBJECT IDENTIFIER ::= { enterprises 130 }
others  OBJECT IDENTIFIER ::= { banyan 2 }

-- netware specific objects

netware OBJECT IDENTIFIER ::= { others 1 }
nwmib1	OBJECT IDENTIFIER ::= { netware 1 }

nwfsinfo	OBJECT IDENTIFIER ::= { nwmib1 1 }
nwperipherals	OBJECT IDENTIFIER ::= { nwmib1 2 }
nwinterfaces	OBJECT	IDENTIFIER ::= { nwmib1 3 }
nwprotocols	OBJECT	IDENTIFIER ::= { nwmib1 4 }

-- object types

-- the netware fileserver info group

nwName OBJECT-TYPE
	SYNTAX  OCTET STRING
	ACCESS  read-only
	STATUS  mandatory
	DESCRIPTION
		"The name of the NetWare file server."
	::= { nwfsinfo 1 }

nwCompany OBJECT-TYPE
	SYNTAX  OCTET STRING
	ACCESS  read-only
	STATUS  mandatory
	DESCRIPTION
		"The company name."
	::= { nwfsinfo 2 }

nwRev OBJECT-TYPE
	SYNTAX  OCTET STRING
	ACCESS  read-only
	STATUS  mandatory
	DESCRIPTION
		"The NetWare software revision for this server."
	::= { nwfsinfo 3 }

nwRevDate OBJECT-TYPE
	SYNTAX  OCTET STRING
	ACCESS  read-only
	STATUS  mandatory
	DESCRIPTION
		"The release date of the NetWare software revision."
	::= { nwfsinfo 4 }

nwCopyRight OBJECT-TYPE
	SYNTAX  OCTET STRING
	ACCESS  read-only
	STATUS  mandatory
	DESCRIPTION
		"The copyright for NetWare software."
	::= { nwfsinfo 5 }

nwConnsSupp OBJECT-TYPE
	SYNTAX  INTEGER
	ACCESS  read-only
	STATUS  mandatory
	DESCRIPTION
		"The number of connections supported."
	::= { nwfsinfo 6 }

nwConnsInUse OBJECT-TYPE
	SYNTAX  INTEGER
	ACCESS  read-only
	STATUS  mandatory
	DESCRIPTION
                "The current number of connections in use."
	::= { nwfsinfo 7 }

nwPeakConnectionsUsed OBJECT-TYPE
	SYNTAX  INTEGER
	ACCESS  read-only
	STATUS  mandatory
	DESCRIPTION
                "The highest number of connections used since server came up."
	::= { nwfsinfo 8 }

nwMaxVolsSupp OBJECT-TYPE
	SYNTAX  INTEGER
	ACCESS  read-only
	STATUS  mandatory
	DESCRIPTION
		"Maximum number of volumes supported."
	::= { nwfsinfo 9 }

nwRevArray OBJECT-TYPE
	SYNTAX  OCTET STRING
	ACCESS  read-only
	STATUS  mandatory
	DESCRIPTION
		"The Revision of the NetWare software displayed in hex."
	::= { nwfsinfo 10 }

-- the peripherals group

nwVolNumber OBJECT-TYPE
	SYNTAX	INTEGER
	ACCESS	read-only
	STATUS	mandatory
	DESCRIPTION
		"The number of volumes."
	::= { nwperipherals 1 }

nwVolTable OBJECT-TYPE
	SYNTAX	SEQUENCE OF NwVolEntry
	ACCESS	not-accessible
	STATUS	mandatory
	DESCRIPTION
		"The Table containing entries for each volume."
	::= { nwperipherals 2 }

nwVolEntry OBJECT-TYPE
	SYNTAX	NwVolEntry
	ACCESS	not-accessible
	STATUS	mandatory
	DESCRIPTION
		"Entry into the volume table."
	INDEX	{ nwVolIndex }
	::= { nwVolTable 1 }

NwVolEntry ::= SEQUENCE {
    nwVolIndex
        INTEGER,
    nwVolName
        OCTET STRING,
    nwVolDrive
        INTEGER,
    nwVolSectorsPerBlk
        INTEGER,
    nwVolStartBlk
        INTEGER,
    nwVolTotalBlks
        INTEGER,
    nwVolAvailBlks
        INTEGER,
    nwVolTotalDirSlots
        INTEGER,
    nwVolAvailDirSlots
        INTEGER,
    nwVolMaxDirSlots
        INTEGER,
    nwVolHashing
        INTEGER,
    nwVolRemovable
        INTEGER,
    nwVolMounted
        INTEGER,
    nwVolPurgeBlks
        INTEGER,
    nwVolNotPurgeBlks
        INTEGER
}

nwVolIndex OBJECT-TYPE
	SYNTAX	INTEGER
	ACCESS	read-only
	STATUS	mandatory
	DESCRIPTION
		"A unique value for each volume on the server, used to order
		the list."
	::= { nwVolEntry 1 }

nwVolName OBJECT-TYPE
	SYNTAX	OCTET STRING
	ACCESS	read-only
	STATUS	mandatory
	DESCRIPTION
		"A string containing the name of the volume."
	::= { nwVolEntry 2 }

nwVolDrive OBJECT-TYPE
	SYNTAX	INTEGER
	ACCESS	read-only
	STATUS	mandatory
	DESCRIPTION
		"The logical drive number."
	::= { nwVolEntry 3 }

nwVolSectorsPerBlk OBJECT-TYPE
	SYNTAX	INTEGER
	ACCESS	read-only
	STATUS	mandatory
	DESCRIPTION
		"The number of sectors per block. This is the number
		of 512-byte sectors contained in each block of the
		volume."
	::= { nwVolEntry 4 }

nwVolStartBlk OBJECT-TYPE
	SYNTAX	INTEGER
	ACCESS	read-only
	STATUS	mandatory
	DESCRIPTION
		"The first block available for you to use for data."
	::= { nwVolEntry 5 }

nwVolTotalBlks OBJECT-TYPE
	SYNTAX	INTEGER
	ACCESS	read-only
	STATUS	mandatory
	DESCRIPTION
		"The total number of blocks for this volume."
	::= { nwVolEntry 6 }

nwVolAvailBlks OBJECT-TYPE
	SYNTAX	INTEGER
	ACCESS	read-only
	STATUS	mandatory
	DESCRIPTION
		"The number of available blocks for this volume."
	::= { nwVolEntry 7 }

nwVolTotalDirSlots OBJECT-TYPE
	SYNTAX	INTEGER
	ACCESS	read-only
	STATUS	mandatory
	DESCRIPTION
		"The total number of directory slots for this volume."
	::= { nwVolEntry 8 }

nwVolAvailDirSlots OBJECT-TYPE
	SYNTAX	INTEGER
	ACCESS	read-only
	STATUS	mandatory
	DESCRIPTION
		"The number of currently available directory slots for this
                volume."
	::= { nwVolEntry 9 }

nwVolMaxDirSlots OBJECT-TYPE
	SYNTAX	INTEGER
	ACCESS	read-only
	STATUS	mandatory
	DESCRIPTION
		"The peak number of directory slots for this volume."
	::= { nwVolEntry 10 }

nwVolHashing OBJECT-TYPE
	SYNTAX	INTEGER
	ACCESS	read-only
	STATUS	mandatory
	DESCRIPTION
		"The flag to indicate whether hashing is in use."
	::= { nwVolEntry 11 }

nwVolRemovable OBJECT-TYPE
	SYNTAX	INTEGER
	ACCESS	read-only
	STATUS	mandatory
	DESCRIPTION
		"The flag to indicate if the media is removable."
	::= { nwVolEntry 12 }

nwVolMounted OBJECT-TYPE
	SYNTAX	INTEGER
	ACCESS	read-only
	STATUS	mandatory
	DESCRIPTION
		"The flag to indicate if the volume is mounted."
	::= { nwVolEntry 13 }

nwVolPurgeBlks OBJECT-TYPE
	SYNTAX	INTEGER
	ACCESS	read-only
	STATUS	mandatory
	DESCRIPTION
		"The number of blocks waiting to be purged."
	::= { nwVolEntry 14 }

nwVolNotPurgeBlks OBJECT-TYPE
	SYNTAX	INTEGER
	ACCESS	read-only
	STATUS	mandatory
	DESCRIPTION
		"The number of blocks which cannot be purged."
	::= { nwVolEntry 15 }

-- NOTE:  The rest of the information that follows is mostly relevant to 
-- NetWare 3.1x servers.  ( ODI information is relevant to NetWare 3.1x 
-- servers only).

-- the nwinterfaces group

nwIfNumber OBJECT-TYPE
	SYNTAX  INTEGER
	ACCESS  read-only
	STATUS  mandatory
	DESCRIPTION
		"The number of interfaces for this NetWare file server."
	::= { nwinterfaces 1 }

nwIfCfgTable OBJECT-TYPE
	SYNTAX  SEQUENCE OF NwIfCfgEntry
	ACCESS  not-accessible
	STATUS  mandatory
	DESCRIPTION
		"The Table containing entries for interface configuration
		information."
	::= { nwinterfaces 2 }

nwIfCfgEntry OBJECT-TYPE
	SYNTAX  NwIfCfgEntry
	ACCESS  not-accessible
	STATUS  mandatory
	DESCRIPTION
		"Entry into the interface configuration table."
	INDEX	{ nwIfCfgBoardNo }
	::= { nwIfCfgTable 1 }

NwIfCfgEntry ::= SEQUENCE {
    nwIfCfgSignature
	OCTET STRING,
    nwIfCfgMajVer
	INTEGER,
    nwIfCfgMinVer
	INTEGER,
    nwIfCfgNodeAddress
	OCTET STRING,
    nwIfCfgModeFlags
	INTEGER,
    nwIfCfgBoardNo
	INTEGER,
    nwIfCfgBoardInst
	INTEGER,
    nwIfCfgMaxDataSz
	INTEGER,
    nwIfCfgMaxRcvSz
	INTEGER,
    nwIfCfgRcvSz
	INTEGER,
    nwIfCfgCardName
	OCTET STRING,
    nwIfCfgShortName
	OCTET STRING,
    nwIfCfgMediaType
	OCTET STRING,
    nwIfCfgCardId
	INTEGER,
    nwIfCfgMediaId
	INTEGER,
    nwIfCfgTransportTM
	INTEGER,
    nwIfCfgMlidMajVer
	INTEGER,
    nwIfCfgMlidMinVer
	INTEGER,
    nwIfCfgFlags
	INTEGER,
    nwIfCfgSendRetries
	INTEGER,
    nwIfCfgShareFlags
	INTEGER,
    nwIfCfgSlot
	INTEGER,
    nwIfCfgIoAddr1
	INTEGER,
    nwIfCfgIoRange1
	INTEGER,
    nwIfCfgIoAddr2
	INTEGER,
    nwIfCfgIoRange2
	INTEGER,
    nwIfCfgMemAddr1
	INTEGER,
    nwIfCfgMemSize1
	INTEGER,
    nwIfCfgMemAddr2
	INTEGER,
    nwIfCfgMemSize2
	INTEGER,
    nwIfCfgInt1
	INTEGER,
    nwIfCfgInt2
	INTEGER,
    nwIfCfgDma1
	INTEGER,
    nwIfCfgDma2
	INTEGER
}

nwIfCfgSignature OBJECT-TYPE
	SYNTAX  OCTET STRING
	ACCESS  read-only
	STATUS  mandatory
	DESCRIPTION
		"The string 'HardwareDriverMLID' followed by 8 spaces
		 is the first entry in the configuration table."
	::= { nwIfCfgEntry 1 }

nwIfCfgMajVer OBJECT-TYPE
	SYNTAX  INTEGER
	ACCESS  read-only
	STATUS  mandatory
	DESCRIPTION
		"The current major version number of the configuration table
		structure."
	::= { nwIfCfgEntry 2 }

nwIfCfgMinVer OBJECT-TYPE
	SYNTAX  INTEGER
	ACCESS  read-only
	STATUS  mandatory
	DESCRIPTION
		"The current minor version number of the configuration 
		table structure.(0..99 decimal)."
	::= { nwIfCfgEntry 3 }

nwIfCfgNodeAddress OBJECT-TYPE
	SYNTAX  OCTET STRING
	ACCESS  read-only
	STATUS  mandatory
	DESCRIPTION
		"The node address of the LAN board.  An MLID can call 
		ParseDriverParameters to prompt a console operator to
		configure this address at the command line.  Otherwise
		the MLID can read the hardware to determine a board's 
		node address."
	::= { nwIfCfgEntry 4 }

nwIfCfgModeFlags OBJECT-TYPE
	SYNTAX  INTEGER
	ACCESS  read-only
	STATUS  mandatory
	DESCRIPTION
		"The mode flags with bit map as follows:
		bit 0 - set to 1.  It indicates if a real driver.
                bit 1 - set driver uses DMA,
		bit 2 - reserved for NetWare; must be 0.
		bit 3 - set if driver supports multicasting,
		bit 4 - set to 0.
		bit 5 - set to 0.
		bit 6 - set if driver supports raw sends.
		bit 7 - set to 0.
		Unused bits are reserved and should always be set to 0."
	::= { nwIfCfgEntry 5 }

nwIfCfgBoardNo OBJECT-TYPE
	SYNTAX  INTEGER
	ACCESS  read-only
	STATUS  mandatory
	DESCRIPTION
		"A unique value for each board in the configuration table
		used by SNMP to order the list.  This corresponds to 
		the logical board number (1- 63) assigned to this LAN board
		by the Link Support Layer (LSL)."
	::= { nwIfCfgEntry 6 }

nwIfCfgBoardInst OBJECT-TYPE
	SYNTAX  INTEGER
	ACCESS  read-only
	STATUS  mandatory
	DESCRIPTION
		"The (physical) board instance. The number of the physical
		card that the logical board is using.  If your driver 
		is driving one physical card, all the logical boards
		using this card would put a value 1 in this field. If
		you load a second physical card, the value 2 would be
		the board instance."
	::= { nwIfCfgEntry 7 }

nwIfCfgMaxDataSz OBJECT-TYPE
	SYNTAX  INTEGER
	ACCESS  read-only
	STATUS  mandatory
	DESCRIPTION
		"The largest possible packet size (in bytes) 
		that can be transmitted and/or received 
		by the LAN board."
	::= { nwIfCfgEntry 8 }

nwIfCfgMaxRcvSz OBJECT-TYPE
	SYNTAX  INTEGER
	ACCESS  read-only
	STATUS  mandatory
	DESCRIPTION
		"The maximum size (or best receive size) a packet 
		could be."
	::= { nwIfCfgEntry 9 }

nwIfCfgRcvSz OBJECT-TYPE
	SYNTAX  INTEGER
	ACCESS  read-only
	STATUS  mandatory
	DESCRIPTION
		"The maximum size a protocol stack can send or receive 
		using this board."
	::= { nwIfCfgEntry 10 }

nwIfCfgCardName OBJECT-TYPE
	SYNTAX  OCTET STRING
	ACCESS  read-only
	STATUS  mandatory
	DESCRIPTION
		"A string containing a name which uniquely
		identifies the interface card hardware."  
	::= { nwIfCfgEntry 11 }

nwIfCfgShortName OBJECT-TYPE
	SYNTAX  OCTET STRING
	ACCESS  read-only
	STATUS  mandatory
	DESCRIPTION
		"A string describing the LAN board in 8 characters 
		or less."
	::= { nwIfCfgEntry 12 }


nwIfCfgMediaType OBJECT-TYPE
	SYNTAX  OCTET STRING
	ACCESS  read-only
	STATUS  mandatory
	DESCRIPTION
		"A string describing the MLID's frame type.
		Examples include `ETHERNET_802.3` and `ETHERNET_II`."
	::= { nwIfCfgEntry 13 }

nwIfCfgCardId OBJECT-TYPE
	SYNTAX  INTEGER
	ACCESS  read-only
	STATUS  mandatory
	DESCRIPTION
		"A reserved field.  The Independent Manufacture Support Program
		(IMSP) assigns a number to each make of LAN board
		and/or drver if the table version is 1.0.  This field
		is reserved if the table version is 1.1."
	::= { nwIfCfgEntry 14 }

nwIfCfgMediaId OBJECT-TYPE
	SYNTAX  INTEGER
	ACCESS  read-only
	STATUS  mandatory
	DESCRIPTION
		"This number identifies the link-level envelope
		used by the MLID.  The ID is associated with 
		a FrameType (nwIfCfgMediaType) string and is assigned 
		with the string.  A few examples:
		MediaId  FrameTypeString
		01 - LocalTalk
		02 - Ethernet_II
		03 - Ethernet_802.2
		04 - TokenRing
		05 - 802.3
		For more information contact Novell."
	::= { nwIfCfgEntry 15 }

nwIfCfgTransportTM OBJECT-TYPE
	SYNTAX  INTEGER
	ACCESS  read-only
	STATUS  mandatory
	DESCRIPTION
		"The time (in ticks) it takes the LAN board
		to transmit a 576 byte packet.
		This field cannot be 0.  Most MLIDs will set this
		to a value of 1."
	::= { nwIfCfgEntry 16 }


nwIfCfgMlidMajVer OBJECT-TYPE
	SYNTAX  INTEGER
	ACCESS  read-only
	STATUS  mandatory
	DESCRIPTION
		"The current revision level of the MLID.
		It should match the revision level displayed by
		the MLID."
	::= { nwIfCfgEntry 17 }

nwIfCfgMlidMinVer OBJECT-TYPE
	SYNTAX  INTEGER
	ACCESS  read-only
	STATUS  mandatory
	DESCRIPTION
		"The current minor version number of the MLID."
	::= { nwIfCfgEntry 18 }

nwIfCfgFlags OBJECT-TYPE
	SYNTAX  INTEGER
	ACCESS  read-only
	STATUS  mandatory
	DESCRIPTION
		"The bus types of physical cards that the MLID
		supports. Unused bits must be set to 0.
		EISA 0001h; set if supports EISA type physical card
		ISA  0002h; set if supports PC/AT type physical card
		MCA  0004h; set if supports Micro Channel type 
		physical card.  
		Bits 3 - 7 are set to 0."
	::= { nwIfCfgEntry 19 }

nwIfCfgSendRetries OBJECT-TYPE
	SYNTAX  INTEGER
	ACCESS  read-only
	STATUS  mandatory
	DESCRIPTION
		"Number of times the MLID should retry send events
		before aborting the send."
	::= { nwIfCfgEntry 20 }


nwIfCfgShareFlags OBJECT-TYPE
	SYNTAX  INTEGER
	ACCESS  read-only
	STATUS  mandatory
	DESCRIPTION
		"Bits which inform the system which hardware
		resources a driver/physical card can share with
		other driver/physical cards.  
		bit 0	set if LAN board is currently shutdown;
		bit 1	set if LAN board can share I/O port #1;
		bit 2	set if LAN board can share I/O port #2;
		bit 3	set if LAN board can share memory range #1;
		bit 4	set if LAN board can share memory range #2;
		bit 5	set if LAN board can share interrupt #1;
		bit 6	set if LAN board can share interrupt #2;
		bit 7	set if LAN board can share DMA channel #1;
		bit 8	set if LAN board can share DMA channel #2;
		bit 9	set if driver has its own command line info
			to put in the AUTOEXEC.NCF file.
		bit 10	set if driver doesn't want any of default info
			put in the AUTOEXEC.NCF file.
		bits 11-15 - set to 0."
	::= { nwIfCfgEntry 21 }

nwIfCfgSlot OBJECT-TYPE
	SYNTAX  INTEGER
	ACCESS  read-only
	STATUS  mandatory
	DESCRIPTION
		"If a LAN board is running in Micro Channel or EISA 
		machine, this field holds the slot number where the 
		board is installed.  If not used, it should be set to 0."
	::= { nwIfCfgEntry 22 }

nwIfCfgIoAddr1 OBJECT-TYPE
	SYNTAX  INTEGER
	ACCESS  read-only
	STATUS  mandatory
	DESCRIPTION
		"The primary I/O address for the interface card. 
		If not used, it should be set to 0."
	::= { nwIfCfgEntry 23 }

nwIfCfgIoRange1 OBJECT-TYPE
	SYNTAX  INTEGER
	ACCESS  read-only
	STATUS  mandatory
	DESCRIPTION
		"The number of I/O ports used at IOAddr1.
		If not used, it should be set to 0."
	::= { nwIfCfgEntry 24 }

nwIfCfgIoAddr2 OBJECT-TYPE
	SYNTAX  INTEGER
	ACCESS  read-only
	STATUS  mandatory
	DESCRIPTION
		"The secondary I/O address for the interface card.
		If not used, it should be set to 0."
	::= { nwIfCfgEntry 25 }

nwIfCfgIoRange2 OBJECT-TYPE
	SYNTAX  INTEGER
	ACCESS  read-only
	STATUS  mandatory
	DESCRIPTION
		"The number of I/O ports used at IOAddr2.
		If not used, it should be set to 0."
	::= { nwIfCfgEntry 26 }

nwIfCfgMemAddr1 OBJECT-TYPE
	SYNTAX  INTEGER
	ACCESS  read-only
	STATUS  mandatory
	DESCRIPTION
		"The absolute primary memory address used by the LAN board.
		If not used, this is set to 0."
	::= { nwIfCfgEntry 27 }

nwIfCfgMemSize1 OBJECT-TYPE
	SYNTAX  INTEGER
	ACCESS  read-only
	STATUS  mandatory
	DESCRIPTION
		"The number of paragraphs (16 bytes) the LAN board
		uses, starting at nwIfCfgMemAddr1.  If not used, it is
		set to 0."
	::= { nwIfCfgEntry 28 }

nwIfCfgMemAddr2 OBJECT-TYPE
	SYNTAX  INTEGER
	ACCESS  read-only
	STATUS  mandatory
	DESCRIPTION
		"The absolute secondary memory address used by the LAN board.
		If not used, this is set to 0."
	::= { nwIfCfgEntry 29 }

nwIfCfgMemSize2 OBJECT-TYPE
	SYNTAX  INTEGER
	ACCESS  read-only
	STATUS  mandatory
	DESCRIPTION
		"The number of paragraphs (16 bytes) the LAN board
		uses, starting at nwIfCfgMemAddr2.  If not used, it is
		set to 0."
	::= { nwIfCfgEntry 30 }

nwIfCfgInt1 OBJECT-TYPE
	SYNTAX  INTEGER
	ACCESS  read-only
	STATUS  mandatory
	DESCRIPTION
		"The primary interrupt vector number.  FFh = not used."
	::= { nwIfCfgEntry 31 }

nwIfCfgInt2 OBJECT-TYPE
	SYNTAX  INTEGER
	ACCESS  read-only
	STATUS  mandatory
	DESCRIPTION
		"The secondary interrupt vector number.  FFh = not used."
	::= { nwIfCfgEntry 32 }

nwIfCfgDma1 OBJECT-TYPE
	SYNTAX  INTEGER
	ACCESS  read-only
	STATUS  mandatory
	DESCRIPTION
		"The primary DMA channel used by the LAN board.
                 FFh = not used."
	::= { nwIfCfgEntry 33 }

nwIfCfgDma2 OBJECT-TYPE
	SYNTAX  INTEGER
	ACCESS  read-only
	STATUS  mandatory
	DESCRIPTION
		"The secondary DMA channel used by the LAN board.
		 FFh = not used."
	::= { nwIfCfgEntry 34 }

nwIfStatsTable OBJECT-TYPE
	SYNTAX  SEQUENCE OF NwIfStatsEntry
	ACCESS  not-accessible
	STATUS  mandatory
	DESCRIPTION
		"The Table containing MLID module statistics."
	::= { nwinterfaces 3 }

nwIfStatsEntry OBJECT-TYPE
	SYNTAX  NwIfStatsEntry
	ACCESS  not-accessible
	STATUS  mandatory
	DESCRIPTION
		"The entry in the table containing MLID module statistics."
	INDEX	{ nwIfStatsBoardNo }
	::= { nwIfStatsTable 1 }

NwIfStatsEntry ::= SEQUENCE {
    nwIfStatsMajVer
	INTEGER,
    nwIfStatsMinVer
	INTEGER,
    nwIfStatsValidMask
	INTEGER,
    nwIfStatsTotalTxPkts
	Counter,
    nwIfStatsTotalRxPkts
	Counter,
    nwIfStatsNoAvailEcbs
	Counter,
    nwIfStatsTxTooBigs
	Counter,
    nwIfStatsTxTooSmalls
	Counter,
    nwIfStatsRxOverFlows
	Counter,
    nwIfStatsRxTooBigs
	Counter,
    nwIfStatsRxTooSmalls
	Counter,
    nwIfStatsTxMiscErrs
	Counter,
    nwIfStatsRxMiscErrs
	Counter,
    nwIfStatsTxRetrys
	Counter,
    nwIfStatsRxChkSumErrs
	Counter,
    nwIfStatsRxMismatchs
	Counter,
    nwIfStatsBoardNo
	INTEGER,
    nwIfStatsCustom
	INTEGER
}

nwIfStatsMajVer OBJECT-TYPE
	SYNTAX  INTEGER
	ACCESS  read-only
	STATUS  mandatory
	DESCRIPTION
		"The current major version number of the 
		generic portion of the statistics table. 
		The current major version number is 2 for
		a Netware v3.1x Server.
		The number is defined by Novell."
	::= { nwIfStatsEntry 1 }

nwIfStatsMinVer OBJECT-TYPE
	SYNTAX  INTEGER
	ACCESS  read-only
	STATUS  mandatory
	DESCRIPTION
		"The current minor version number of the 
		generic portion of the statistics table.
		The current minor version number is 0 for
		a Netware v3.1x Server.
		The number is defined by Novell."
	::= { nwIfStatsEntry 2 }


nwIfStatsValidMask OBJECT-TYPE
	SYNTAX  INTEGER
	ACCESS  read-only
	STATUS  mandatory
	DESCRIPTION
		"The bit mask indicating which counters are valid.
		The first 13 bits (starting with most significant bit)
		represent fields in this statistics table.
		The value 0 indicates it is supported, the value 1 
		indicates it is not supported.
		The bit/counter correlations are determined by
		shifting left, as you move down the counters in the
		table."
	::= { nwIfStatsEntry 3 }

nwIfStatsTotalTxPkts OBJECT-TYPE
	SYNTAX  Counter
	ACCESS  read-only
	STATUS  mandatory
	DESCRIPTION
		"The total number of packets transmitted by this LAN board."
	::= { nwIfStatsEntry 4 }

nwIfStatsTotalRxPkts OBJECT-TYPE
	SYNTAX  Counter
	ACCESS  read-only
	STATUS  mandatory
	DESCRIPTION
		"Total number of incoming packets received by this LAN board."
	::= { nwIfStatsEntry 5 }

nwIfStatsNoAvailEcbs OBJECT-TYPE
	SYNTAX  Counter
	ACCESS  read-only
	STATUS  mandatory
	DESCRIPTION
		"Number of incoming packets that were lost because
		of unavailable ECBs."
	::= { nwIfStatsEntry 6 }

nwIfStatsTxTooBigs OBJECT-TYPE
	SYNTAX  Counter
	ACCESS  read-only
	STATUS  mandatory
	DESCRIPTION
		"Number of times the send packet was too big for this
		LAN board to send."
	::= { nwIfStatsEntry 7 }

nwIfStatsTxTooSmalls OBJECT-TYPE
	SYNTAX  Counter
	ACCESS  read-only
	STATUS  mandatory
	DESCRIPTION
		"Number of times the send packet was too small for this
		LAN board to send."
	::= { nwIfStatsEntry 8 }

nwIfStatsRxOverFlows OBJECT-TYPE
	SYNTAX  Counter
	ACCESS  read-only
	STATUS  mandatory
	DESCRIPTION
		"Number of times the LAN board's receive buffers 
		overflowed."
	::= { nwIfStatsEntry 9 }

nwIfStatsRxTooBigs OBJECT-TYPE
	SYNTAX  Counter
	ACCESS  read-only
	STATUS  mandatory
	DESCRIPTION
		"Number of times the LAN board could not receive
		a packet because the packet was too big."
	::= { nwIfStatsEntry 10 }

nwIfStatsRxTooSmalls OBJECT-TYPE
	SYNTAX  Counter
	ACCESS  read-only
	STATUS  mandatory
	DESCRIPTION
		"Number of times the LAN board could not receive
		a packet because the packet was too small."
	::= { nwIfStatsEntry 11 }

nwIfStatsTxMiscErrs OBJECT-TYPE
	SYNTAX  Counter
	ACCESS  read-only
	STATUS  mandatory
	DESCRIPTION
		"The number of transmit errors for the LAN board.  This
		is MLID dependent."
	::= { nwIfStatsEntry 12 }

nwIfStatsRxMiscErrs OBJECT-TYPE
	SYNTAX  Counter
	ACCESS  read-only
	STATUS  mandatory
	DESCRIPTION
		"The number of receive errors for the LAN board.
		This is MLID dependent."
	::= { nwIfStatsEntry 13 }

nwIfStatsTxRetrys OBJECT-TYPE
	SYNTAX  Counter
	ACCESS  read-only
	STATUS  mandatory
	DESCRIPTION
		"Number of times the LAN board retried a transmit
		because of a failure."
	::= { nwIfStatsEntry 14 }

nwIfStatsRxChkSumErrs OBJECT-TYPE
	SYNTAX  Counter
	ACCESS  read-only
	STATUS  mandatory
	DESCRIPTION
		"Number of times a checksum error occured for this LAN
		board."
	::= { nwIfStatsEntry 15 }

nwIfStatsRxMismatchs OBJECT-TYPE
	SYNTAX  Counter
	ACCESS  read-only
	STATUS  mandatory
	DESCRIPTION
		"This is LAN medium-specific."
	::= { nwIfStatsEntry 16 }

nwIfStatsBoardNo OBJECT-TYPE
	SYNTAX  INTEGER
	ACCESS  read-only
	STATUS  mandatory
	DESCRIPTION
		"A unique value for each board configured, used by SNMP to 
		order the list of interface statistics.
		This corresponds to the the logical board number (1 - 63) 
		assigned to this LAN board by the Link Support Layer (LSL)."
	::= { nwIfStatsEntry 17 }

nwIfStatsCustom OBJECT-TYPE
	SYNTAX  INTEGER
	ACCESS  read-only
	STATUS  mandatory
	DESCRIPTION
		"The total number of custom variables which follow this word."
	::= { nwIfStatsEntry 18 }

nwIfCustomStatsTable OBJECT-TYPE
	SYNTAX  SEQUENCE OF NwIfCustomStatsEntry
	ACCESS  not-accessible
	STATUS  mandatory
	DESCRIPTION
		"The Table containing custom variables.  These are
		custom counters."
	::= { nwinterfaces 4 }

nwIfCustomStatsEntry OBJECT-TYPE
	SYNTAX  NwIfCustomStatsEntry
	ACCESS  not-accessible
	STATUS  mandatory
	DESCRIPTION
		"The entry in the table containing custom variables
		indexed by the board number and index of the 
		custom variables."
	INDEX	{ nwIfCustomStatsBoardNo, nwIfCustomStatsIndex }
	::= { nwIfCustomStatsTable 1 }

NwIfCustomStatsEntry ::= SEQUENCE {
    nwIfCustomStatsBoardNo
	INTEGER,
    nwIfCustomStatsIndex
	INTEGER,
    nwIfCustomStatsDescr
	OCTET STRING,
    nwIfCustomStatsValue
	Counter
}

nwIfCustomStatsBoardNo OBJECT-TYPE
	SYNTAX  INTEGER
	ACCESS  read-only
	STATUS  mandatory
	DESCRIPTION
		"A unique value for each board configured, used by SNMP
		to order the list of custom statistics.
		This corresponds to the the logical board number (1 - 63) 
		assigned to this LAN board by the Link Support Layer (LSL)."
	::= { nwIfCustomStatsEntry 1 }

nwIfCustomStatsIndex OBJECT-TYPE
	SYNTAX  INTEGER
	ACCESS  read-only
	STATUS  mandatory
	DESCRIPTION
		"A unique value for each custom variable in the table.
		(There are a total of nwIfCustom variables)."
	::= { nwIfCustomStatsEntry 2 }

nwIfCustomStatsDescr OBJECT-TYPE
	SYNTAX  OCTET STRING
	ACCESS  read-only
	STATUS  mandatory
	DESCRIPTION
		"A descriptive text string for the custom variable/counter."
	::= { nwIfCustomStatsEntry 3 }

nwIfCustomStatsValue OBJECT-TYPE
	SYNTAX  Counter
	ACCESS  read-only
	STATUS  mandatory
	DESCRIPTION
		"The value associated with the custom variable/counter."
	::= { nwIfCustomStatsEntry 4 }

-- the nwprotocols group

nwProtNumber OBJECT-TYPE
	SYNTAX  INTEGER
	ACCESS  read-only
	STATUS  mandatory
	DESCRIPTION
		"The number of protocols supported by this server."
	::= { nwprotocols 1 }

nwProtCfgTable OBJECT-TYPE
	SYNTAX  SEQUENCE OF NwProtCfgEntry
	ACCESS  not-accessible
	STATUS  mandatory
	DESCRIPTION
		"The Table containing protocol configuration information."
	::= { nwprotocols 2 }

nwProtCfgEntry OBJECT-TYPE
	SYNTAX  NwProtCfgEntry
	ACCESS  not-accessible
	STATUS  mandatory
	DESCRIPTION
		"The entry in the protocol configuration table."
	INDEX	{ nwProtCfgProtNo }
	::= { nwProtCfgTable 1 }

NwProtCfgEntry ::= SEQUENCE {
    nwProtCfgProtNo
	INTEGER,
    nwProtCfgMajVer
	INTEGER,
    nwProtCfgMinVer
	INTEGER,
    nwProtCfgName
	OCTET STRING,
    nwProtCfgRegName
	OCTET STRING,
    nwProtCfgStkMajVer
	INTEGER,
    nwProtCfgStkMinVer
	INTEGER
}

nwProtCfgProtNo OBJECT-TYPE
	SYNTAX  INTEGER
	ACCESS  read-only
	STATUS  mandatory
	DESCRIPTION
		"A unique value for each protocol configured, used by
		SNMP to order the list. "
	::= { nwProtCfgEntry 1 }


nwProtCfgMajVer OBJECT-TYPE
	SYNTAX  INTEGER
	ACCESS  read-only
	STATUS  mandatory
	DESCRIPTION
		"The major version number of the configuration table."
	::= { nwProtCfgEntry 2 }

nwProtCfgMinVer OBJECT-TYPE
	SYNTAX  INTEGER
	ACCESS  read-only
	STATUS  mandatory
	DESCRIPTION
		"The minor version number of the configuration table."
	::= { nwProtCfgEntry 3 }

nwProtCfgName OBJECT-TYPE
	SYNTAX  OCTET STRING
	ACCESS  read-only
	STATUS  mandatory
	DESCRIPTION
		"A string used to register the protocol stack with
		the Link Support Lanyer (LSL).  This string 
		cannot have more than 15 characters (not including the 
		length byte or zero terminator) and cannot be 0."
	::= { nwProtCfgEntry 4 }

nwProtCfgRegName OBJECT-TYPE
	SYNTAX  OCTET STRING
	ACCESS  read-only
	STATUS  mandatory
	DESCRIPTION
		"A string containing the name of the protocol stack. It
		is a length-preceded, zero-terminated string."
	::= { nwProtCfgEntry 5 }

nwProtCfgStkMajVer OBJECT-TYPE
	SYNTAX  INTEGER
	ACCESS  read-only
	STATUS  mandatory
	DESCRIPTION
		"The major version number of the protocol stack.
		The number in this field is a decimal number."
	::= { nwProtCfgEntry 6 }

nwProtCfgStkMinVer OBJECT-TYPE
	SYNTAX  INTEGER
	ACCESS  read-only
	STATUS  mandatory
	DESCRIPTION
		"The minor version number of the protocol stack.
		The number in this field is a decimal number."
	::= { nwProtCfgEntry 7 }

nwProtStatsTable OBJECT-TYPE
	SYNTAX  SEQUENCE OF NwProtStatsEntry
	ACCESS  not-accessible
	STATUS  mandatory
	DESCRIPTION
		"The table containing protocol statistics information."
	::= { nwprotocols 3 }

nwProtStatsEntry OBJECT-TYPE
	SYNTAX  NwProtStatsEntry
	ACCESS  not-accessible
	STATUS  mandatory
	DESCRIPTION
		"The entry in the protocol statistics table indexed by
		the protocol statistics number."
	INDEX	{ nwProtStatsProtNo }
	::= { nwProtStatsTable 1 }

NwProtStatsEntry ::= SEQUENCE {
    nwProtStatsProtNo
	INTEGER,
    nwProtStatsMajVer
	INTEGER,
    nwProtStatsMinVer
	INTEGER,
    nwProtStatsValidMask
	INTEGER,
    nwProtStatsTotalTxPkts
	Counter,
    nwProtStatsTotalRxPkts
	Counter,
    nwProtStatsIgnoredRxPkts
	Counter,
    nwProtStatsCustom
        Counter
}

nwProtStatsProtNo OBJECT-TYPE
	SYNTAX  INTEGER
	ACCESS  read-only
	STATUS  mandatory
	DESCRIPTION
		"A unique value for each protocol supported on the
		server, used by SNMP to order the list."
	::= { nwProtStatsEntry 1 }

nwProtStatsMajVer OBJECT-TYPE
	SYNTAX  INTEGER
	ACCESS  read-only
	STATUS  mandatory
	DESCRIPTION
		"The major version number of the protocol stack 
		statistics table."
	::= { nwProtStatsEntry 2 }

nwProtStatsMinVer OBJECT-TYPE
	SYNTAX  INTEGER
	ACCESS  read-only
	STATUS  mandatory
	DESCRIPTION
		"The minor version number of the protocol stack 
		statistics table."
	::= { nwProtStatsEntry 3 }

nwProtStatsValidMask OBJECT-TYPE
	SYNTAX  INTEGER
	ACCESS  read-only
	STATUS  mandatory
	DESCRIPTION
		"A bit mask indicating which counters are used.
		The value 0 indicates Yes; the value 1 indicates No.
		The bit/counter correlations are determine by shifting
		left, as you move down the counters in the table."
	::= { nwProtStatsEntry 4 }

nwProtStatsTotalTxPkts OBJECT-TYPE
	SYNTAX  Counter
	ACCESS  read-only
	STATUS  mandatory
	DESCRIPTION
		"The total number of packets that were requested to be 
		transmitted (whether they were actually transmitted
		or not)."
	::= { nwProtStatsEntry 5 }

nwProtStatsTotalRxPkts OBJECT-TYPE
	SYNTAX  Counter
	ACCESS  read-only
	STATUS  mandatory
	DESCRIPTION
		"The total number of incoming packets that were
		received."
	::= { nwProtStatsEntry 6 }

nwProtStatsIgnoredRxPkts OBJECT-TYPE
	SYNTAX  Counter
	ACCESS  read-only
	STATUS  mandatory
	DESCRIPTION
		"The total number of incoming packets that were
		ignored by the stack."
	::= { nwProtStatsEntry 7 }

nwProtStatsCustom OBJECT-TYPE
	SYNTAX  Counter
	ACCESS  read-only
	STATUS  mandatory
	DESCRIPTION
		"The total number of custom counters following
		this field."
	::= { nwProtStatsEntry 8 }


nwProtCustomStatsTable OBJECT-TYPE
	SYNTAX  SEQUENCE OF NwProtCustomStatsEntry
	ACCESS  not-accessible
	STATUS  mandatory
	DESCRIPTION
		"The table of custom statistics for the protocol."
	::= { nwprotocols 4 }

nwProtCustomStatsEntry OBJECT-TYPE
	SYNTAX  NwProtCustomStatsEntry
	ACCESS  not-accessible
	STATUS  mandatory
	DESCRIPTION
		"The entry  in table of custom statistics 
		indexed by the protocol number and the index. "
	INDEX	{ nwProtCustomStatsProtNo, nwProtCustomStatsIndex }
	::= { nwProtCustomStatsTable 1 }

NwProtCustomStatsEntry ::= SEQUENCE {
    nwProtCustomStatsProtNo
	INTEGER,
    nwProtCustomStatsIndex
	INTEGER,
    nwProtCustomStatsDescr
	OCTET STRING,
    nwProtCustomStatsValue
	Counter
}

nwProtCustomStatsProtNo OBJECT-TYPE
	SYNTAX  INTEGER
	ACCESS  read-only
	STATUS  mandatory
	DESCRIPTION
		"A unique value for each protocol supported, used by
		SNMP to order the list."
	::= { nwProtCustomStatsEntry 1 }

nwProtCustomStatsIndex OBJECT-TYPE
	SYNTAX  INTEGER
	ACCESS  read-only
	STATUS  mandatory
	DESCRIPTION
		"A unique value for each statistic in the custom statistics 
		table."
	::= { nwProtCustomStatsEntry 2 }

nwProtCustomStatsDescr OBJECT-TYPE
	SYNTAX  OCTET STRING
	ACCESS  read-only
	STATUS  mandatory
	DESCRIPTION
		"A string describing for the custom statistic."
	::= { nwProtCustomStatsEntry 3 }

nwProtCustomStatsValue OBJECT-TYPE
	SYNTAX  Counter
	ACCESS  read-only
	STATUS  mandatory
	DESCRIPTION
		"The value of the custom statistic."
	::= { nwProtCustomStatsEntry 4 }

END
