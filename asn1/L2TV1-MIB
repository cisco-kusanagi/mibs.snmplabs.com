L2TV1-MIB DEFINITIONS ::= BEGIN
 
------------------------------------------------------------------
-- IBM L2T MIB
------------------------------------------------------------------
--
-- The MIB module that describes managed objects of
-- general use by the Layer Two Transport Protocol. 
--
-- Level 1: Initial Version (July 29, 1998)     - cc4
-- Level 2: Add Addition Groups (Jan 12, 1998)  - cc5
--          - l2tAuthentication
--          - l2tHistory
--          - l2tHosts 
--          - l2tTests  
--          - l2tTrapCntl
--
--
-- CONTACT-INFO
--    Gregg Miller
--       Postal: IBM Corporation
--               800 Park, Highway 54
--               Research Triangle Park, NC 27709-9990
--       Tel:    +1 919 543 3326
--       Email:  gwmiller@us.ibm.com"
------------------------------------------------------------------

   IMPORTS
      TimeTicks, Counter, Gauge, IpAddress, enterprises
         FROM RFC1155-SMI
      TRAP-TYPE
	FROM RFC-1215
      OBJECT-TYPE
        FROM RFC-1212
      DisplayString
        FROM RFC1213-MIB;

-- ----------------------------------------------------------------------------
-- Definitions of significant branches
-- ----------------------------------------------------------------------------
   ibmIROCroutingl2t      OBJECT IDENTIFIER  ::= 
      { enterprises ibm(2) ibmProd(6) ibmIROC(119) ibmIROCrouting(4) 7 }

   l2tScalar              OBJECT IDENTIFIER  ::= { ibmIROCroutingl2t 1 }
   l2tStats               OBJECT IDENTIFIER  ::= { ibmIROCroutingl2t 2 }
   l2tUdp                 OBJECT IDENTIFIER  ::= { ibmIROCroutingl2t 3 }
   l2tAuthentication      OBJECT IDENTIFIER  ::= { ibmIROCroutingl2t 4 }
   l2tHistory             OBJECT IDENTIFIER  ::= { ibmIROCroutingl2t 5 }
   l2tHosts               OBJECT IDENTIFIER  ::= { ibmIROCroutingl2t 6 }
   l2tTests               OBJECT IDENTIFIER  ::= { ibmIROCroutingl2t 7 }
   l2tTrapCntl            OBJECT IDENTIFIER  ::= { ibmIROCroutingl2t 8 }

-- ----------------------------------------------------------------------------
-- The L2T Scalar Configuration Group
--
-- This group of objects is used to manage configuration of
-- the L2T protocol environment. Many of these objects determine
-- the default behavior of tunnels when created.
-- ----------------------------------------------------------------------------

   l2tScalarConfig        OBJECT IDENTIFIER  ::= { l2tScalar 1 }

   l2tAdminState OBJECT-TYPE
      SYNTAX INTEGER {
                enabled(1),
                disabled(2)
             }
      ACCESS read-only 
      STATUS mandatory
      DESCRIPTION
         "This object defines the administrative state of
          the L2T protocol stack."
      DEFVAL { enabled }
      ::= { l2tScalarConfig 1 }

   l2tAuthenticateIncomingTunnelSetupRequests OBJECT-TYPE
      SYNTAX INTEGER {
                true(1),
                false(2)
             }
      ACCESS read-only 
      STATUS mandatory
      DESCRIPTION
         "Defines whether the L2T protocol stack will REQUIRE the
          CHAP-like authentication mechanism to be present in all
          tunnel setup requests."
      DEFVAL { false }
      ::= { l2tScalarConfig 2 }

   l2tTunnelDataFlowControl OBJECT-TYPE
      SYNTAX INTEGER { 
                true(1),
                false(2)
             }
      ACCESS read-only 
      STATUS mandatory
      DESCRIPTION
         "This object determines whether or not L2T is
          to use flow control on the tunneled data packets."
      DEFVAL { false }
      ::= { l2tScalarConfig 3 }

   l2tControlRecvPacketWindow OBJECT-TYPE
      SYNTAX INTEGER
      ACCESS read-only 
      STATUS mandatory
      DESCRIPTION
         "This object defines the Control Channel receive window
          size which is transmitted to the L2T peers."
      DEFVAL { 4 }
      ::= { l2tScalarConfig 4 }

   l2tDataRecvPacketWindow OBJECT-TYPE
      SYNTAX INTEGER
      ACCESS read-only 
      STATUS mandatory
      DESCRIPTION
         "This object defines the Data Channel receive window
          size which is transmitted to the L2T peers."
      DEFVAL { 6 }
      ::= { l2tScalarConfig 5 }

   l2tHelloTimer OBJECT-TYPE
      SYNTAX INTEGER
      ACCESS read-only 
      STATUS mandatory
      DESCRIPTION
         "This object defines the length of the inactivity timer
          in seconds which causes the L2T stack to transmit a
          keep-alive packet (known as a Hello packet)."
      DEFVAL { 60 }
      ::= { l2tScalarConfig 6 }

   l2tControlRetransmissions OBJECT-TYPE
      SYNTAX INTEGER(0..65535)
      ACCESS read-only 
      STATUS mandatory
      DESCRIPTION
         "This object defines the number of retransmissions
          which the L2T stack will attempt before assuming that
          the peer is no longer reachable. The default value for
          this object is zero (0) which results in the L2T stack
          not doing retransmissions."
      DEFVAL { 0 }
      ::= { l2tScalarConfig 7 }

   l2tSecurityExtensions OBJECT-TYPE
      SYNTAX INTEGER { 
                true(1),
                false(2)
             }
      ACCESS read-only 
      STATUS mandatory
      DESCRIPTION
         "This object defines whether the L2T protocol stack will
          require the L2T Security for all incoming tunnel setup
          requests."
      DEFVAL { false }
      ::= { l2tScalarConfig 8 }

   l2tHistoryWindowSize  OBJECT-TYPE
      SYNTAX INTEGER 
      ACCESS read-write
      STATUS mandatory
      DESCRIPTION
         "The window size of the L2T Tunnel History Table         
          (l2tHistTunnelTable) and the L2T Session History Table
          (l2tHistSessTable).  

          When retrieved by an SNMP GET or GET-NEXT request, this
          number specifies the maximum number of entries which 
          will be maintained in each of these tables. 

          When modified by an SNMP SET request, the device will
          set the value of this object as close as possible to 
          the requested value based on implementation and
          available resources."
      ::= { l2tScalarConfig 9 }

   l2tAuthFailWindowSize  OBJECT-TYPE
      SYNTAX INTEGER 
      ACCESS read-write
      STATUS mandatory
      DESCRIPTION
         "The window size of the L2T Tunnel Authentication Failure Table
          (l2tAuthFailTunnelTable) and the L2T User Authentication Failure 
          Table (l2tAuthFailUserTable).  

          When retrieved by an SNMP GET or GET-NEXT request, this
          number specifies the maximum number of entries which 
          will be maintained in each of these tables. 

          When modified by an SNMP SET request, the device will
          set the value of this object as close as possible to 
          the requested value based on implementation and
          available resources."
      ::= { l2tScalarConfig 10 }

-- ----------------------------------------------------------------------------
-- The L2T Scalar Status and Statistics Group
--
-- This group of objects describe the mandatory state and
-- statistics of L2T.
-- ----------------------------------------------------------------------------

   l2tScalarStat OBJECT IDENTIFIER ::= { l2tScalar 2 }

   l2tMibVersion OBJECT-TYPE
      SYNTAX INTEGER                
      ACCESS read-only
      STATUS mandatory
      DESCRIPTION
         "The level of the IBM L2T MIB."
      ::= { l2tScalarStat 1 }

   l2tProtocolVersion OBJECT-TYPE
      SYNTAX OCTET STRING(SIZE(2))
      ACCESS read-only 
      STATUS mandatory
      DESCRIPTION
         "This object describes the protocol version and revision
          of the L2T protocol stack. The first octet contains the
          protocol version. The second octet contains the protocol
          revision."
      ::= { l2tScalarStat 2 }

   l2tNumActiveTunnels OBJECT-TYPE
      SYNTAX INTEGER
      ACCESS read-only 
      STATUS mandatory
      DESCRIPTION
         "This object returns the number of L2T tunnels
          that are mandatory active."
      ::= { l2tScalarStat 3 }

   l2tStatsNumActiveSessions OBJECT-TYPE
      SYNTAX INTEGER
      ACCESS read-only 
      STATUS mandatory
      DESCRIPTION
         "This object returns the number of L2T sessions
          that are mandatory active."
      ::= { l2tScalarStat 4 }

-- ----------------------------------------------------------------------------
-- The L2T Tunnel Status and Statistics Table
--
-- This table contains objects that can be used to describe
-- the mandatory status and statistics of a single L2T tunnel.
-- ----------------------------------------------------------------------------

   l2tTunnelStatsTable OBJECT-TYPE
      SYNTAX SEQUENCE OF L2tTunnelStatsEntry
      ACCESS not-accessible
      STATUS mandatory
      DESCRIPTION
         "The L2T tunnel status and statistics table."
      ::= { l2tStats 1 }

   l2tTunnelStatsEntry OBJECT-TYPE
      SYNTAX L2tTunnelStatsEntry
      ACCESS not-accessible
      STATUS mandatory
      DESCRIPTION
         "An L2T tunnel interface stats entry."
      INDEX { l2tTunnelLocalTunnelControlId }
      ::= { l2tTunnelStatsTable 1 }

   L2tTunnelStatsEntry ::= SEQUENCE {
      l2tTunnelLocalTunnelControlId    INTEGER,
      l2tTunnelPeerTunnelControlId     INTEGER,
      l2tTunnelControlState            INTEGER,
      l2tTunnelLocalInitConnection     INTEGER,
      l2tTunnelLocalRecvPktWindow      INTEGER,
      l2tTunnelRemoteRecvPktWindow     INTEGER,
      l2tTunnelCtlTunnelFlwCtlTimeouts Counter,
      l2tTunnelRemoteHostName          DisplayString,
      l2tTunnelNextSendSeq             INTEGER,
      l2tTunnelNextRecvSeq             INTEGER,
      l2tTunnelRemoteVendorName        DisplayString,
      l2tTunnelRemoteFirmwareRevision  INTEGER,
      l2tTunnelRemoteProtocolVersion   OCTET STRING,
      l2tTunnelActiveSessions          Gauge,
      l2tTunnelPrevSessions            Counter,
      l2tTunnelUpTime                  TimeTicks, 
      l2tTunnelType                    INTEGER,     
      l2tTunnelInOctets                Counter,
      l2tTunnelInPkts                  Counter,
      l2tTunnelInDiscards              Counter,
      l2tTunnelOutOctets               Counter,
      l2tTunnelOutPkts                 Counter,
      l2tTunnelOutDiscards             Counter,
      l2tTunnelStatus                  INTEGER 
   }


   l2tTunnelLocalTunnelControlId OBJECT-TYPE
      SYNTAX INTEGER
      ACCESS read-only 
      STATUS mandatory
      DESCRIPTION
         "This object contains the local tunnel Identifier."
      ::= { l2tTunnelStatsEntry 1 }

   l2tTunnelPeerTunnelControlId OBJECT-TYPE
      SYNTAX INTEGER
      ACCESS read-only 
      STATUS mandatory
      DESCRIPTION
         "This object contains the remote tunnel Identifier. "
      ::= { l2tTunnelStatsEntry 2 }

   l2tTunnelControlState OBJECT-TYPE
      SYNTAX INTEGER {
                l2ttunnelidle(1),
                l2ttunnelwaitctrlreply(2),
                l2ttunnelwaitctrlconn(3),
                l2ttunnelestablished(4),
                l2ttunnelhold(5)
            }
      ACCESS read-only 
      STATUS mandatory
      DESCRIPTION
         "This field contains the mandatory state of
          the control tunnel."
      ::= { l2tTunnelStatsEntry 3 }

   l2tTunnelLocalInitConnection OBJECT-TYPE
      SYNTAX INTEGER { 
                true(1),
                false(2)
             }
      ACCESS read-only 
      STATUS mandatory
      DESCRIPTION
         "This object indicates whether the tunnel was
          generated locally or not.  When this object
          returns a value of true(1) the tunnel was
          locally generated."
      ::= { l2tTunnelStatsEntry 4 }

   l2tTunnelLocalRecvPktWindow OBJECT-TYPE
      SYNTAX INTEGER
      ACCESS read-only 
      STATUS mandatory
      DESCRIPTION
         "This object contains the local receive window size."
      ::= { l2tTunnelStatsEntry 5 }

   l2tTunnelRemoteRecvPktWindow OBJECT-TYPE
      SYNTAX INTEGER
      ACCESS read-only 
      STATUS mandatory
      DESCRIPTION
         "This object contains the remote receive window size."
      ::= { l2tTunnelStatsEntry 6 }

   l2tTunnelCtlTunnelFlwCtlTimeouts OBJECT-TYPE
      SYNTAX Counter
      ACCESS read-only 
      STATUS mandatory
      DESCRIPTION
         "This object contains the number of timeouts due to
          flow control."
      ::= { l2tTunnelStatsEntry 7 }

   l2tTunnelRemoteHostName OBJECT-TYPE
      SYNTAX DisplayString
      ACCESS read-only 
      STATUS mandatory
      DESCRIPTION
         "This object contains the host name of the L2T peer."
      ::= { l2tTunnelStatsEntry 8 }

   l2tTunnelNextSendSeq OBJECT-TYPE
      SYNTAX INTEGER
      ACCESS read-only 
      STATUS mandatory
      DESCRIPTION
         "This object contains the next send sequence number for
          the control channel."
      ::= { l2tTunnelStatsEntry 9 }

   l2tTunnelNextRecvSeq OBJECT-TYPE
      SYNTAX INTEGER
      ACCESS read-only 
      STATUS mandatory
      DESCRIPTION
         "This object contains the next receive sequence number
          for the control channel."
      ::= { l2tTunnelStatsEntry 10 }


   l2tTunnelRemoteVendorName OBJECT-TYPE
      SYNTAX DisplayString
      ACCESS read-only 
      STATUS mandatory
      DESCRIPTION
         "This object identifies the vendor name of the
          peer's L2T implementation."
      ::= { l2tTunnelStatsEntry 11 }

   l2tTunnelRemoteFirmwareRevision OBJECT-TYPE
      SYNTAX INTEGER(0..65535)
      ACCESS read-only 
      STATUS mandatory
      DESCRIPTION
         "This object contains the L2T peer's firmware
          revision number."
      ::= { l2tTunnelStatsEntry 12 }

   l2tTunnelRemoteProtocolVersion OBJECT-TYPE
      SYNTAX OCTET STRING
      ACCESS read-only 
      STATUS mandatory
      DESCRIPTION
         "This object describes the protocol version and revision
          of the L2T protocol stack. The first octet contains the
          protocol version. The second octet contains the protocol
          revision."
      ::= { l2tTunnelStatsEntry 13 }

   l2tTunnelActiveSessions OBJECT-TYPE
      SYNTAX Gauge
      ACCESS read-only 
      STATUS mandatory
      DESCRIPTION
         "This object contains the total number of
          sessions in use for this tunnel."
      ::= { l2tTunnelStatsEntry 14 }

   l2tTunnelPrevSessions OBJECT-TYPE
      SYNTAX Counter
      ACCESS read-only 
      STATUS mandatory
      DESCRIPTION
         "The total number of previously actively sessions  
          which used this tunnel."
      ::= { l2tTunnelStatsEntry 15 }

   l2tTunnelUpTime OBJECT-TYPE
      SYNTAX TimeTicks 
      ACCESS read-only 
      STATUS mandatory
      DESCRIPTION
         "The length of time the tunnel has been active in  
          hundredths of seconds."
      ::= { l2tTunnelStatsEntry 16 }

   l2tTunnelType OBJECT-TYPE
      SYNTAX INTEGER { 
                l2tpTunnel(1),              
                l2fTunnel(2),              
                pptpTunnel(3)
             }
      ACCESS read-only 
      STATUS mandatory
      DESCRIPTION
         "The type of Layer-2 Tunnel.  Possible values are:
          1 = Layer-2 Tunnel Protocol Tunnel,
          2 = Layer-2 Forwarding Tunnel,
          3 = Point-to-Point Tunnel Protocol Tunnel."
      ::= { l2tTunnelStatsEntry 17 }

   l2tTunnelInOctets OBJECT-TYPE
      SYNTAX Counter
      ACCESS read-only 
      STATUS mandatory
      DESCRIPTION
         "The number of octets received by this tunnel."
      ::= { l2tTunnelStatsEntry 18 }

   l2tTunnelInPkts OBJECT-TYPE
      SYNTAX Counter
      ACCESS read-only 
      STATUS mandatory
      DESCRIPTION
         "The number of packets received by this tunnel."
      ::= { l2tTunnelStatsEntry 19 }

   l2tTunnelInDiscards OBJECT-TYPE
      SYNTAX Counter
      ACCESS read-only 
      STATUS mandatory
      DESCRIPTION
         "The number of packets which were discarded during
          receive processing."
      ::= { l2tTunnelStatsEntry 20 }

   l2tTunnelOutOctets OBJECT-TYPE
      SYNTAX Counter
      ACCESS read-only 
      STATUS mandatory
      DESCRIPTION
         "The number of octets sent by this tunnel."
      ::= { l2tTunnelStatsEntry 21 }

   l2tTunnelOutPkts OBJECT-TYPE
      SYNTAX Counter
      ACCESS read-only 
      STATUS mandatory
      DESCRIPTION
         "The number of packets sent by this tunnel."
      ::= { l2tTunnelStatsEntry 22 }

   l2tTunnelOutDiscards OBJECT-TYPE
      SYNTAX Counter
      ACCESS read-only 
      STATUS mandatory
      DESCRIPTION
         "The number of packets which were discarded during
          send processing."
      ::= { l2tTunnelStatsEntry 23 }

   l2tTunnelStatus OBJECT-TYPE
      SYNTAX INTEGER {
                active(1),
                destroy(2)
             }
      ACCESS read-write
      STATUS mandatory
      DESCRIPTION
         "The status of the MIB table row.  This object
          can be used to bring the tunnel down by setting
          value of this object to destroy(2).  
          This object cannot be used to create a MIB table row."
      ::= { l2tTunnelStatsEntry 24 }

-- ----------------------------------------------------------------------------
-- The L2T Session Status and Statistics Table
--
-- This table contains the objects that can be used to describe
-- the current status and statistics of a single L2T tunneled
-- session.
-- ----------------------------------------------------------------------------

   l2tSessionStatsTable OBJECT-TYPE
      SYNTAX SEQUENCE OF L2tSessionStatsEntry
      ACCESS not-accessible
      STATUS mandatory
      DESCRIPTION
         "The L2T session status and statistics table. "
      ::= { l2tStats 2 }

   l2tSessionStatsEntry OBJECT-TYPE
      SYNTAX L2tSessionStatsEntry
      ACCESS not-accessible
      STATUS mandatory
      DESCRIPTION
         "An L2T session interface stats entry. "
      INDEX { l2tSessionLocalControlTunnelId, 
              l2tSessionLocalCallId }
      ::= { l2tSessionStatsTable 1 }

   L2tSessionStatsEntry ::= SEQUENCE {
      l2tSessionLocalControlTunnelId    INTEGER,
      l2tSessionLocalCallId             INTEGER,
      l2tSessionRemoteCallId            INTEGER,
      l2tSessionPeerName                DisplayString,
      l2tSessionLineState               INTEGER,
      l2tSessionCallDeviceNumber        INTEGER,
      l2tSessionCallSerialNumber        DisplayString,
      l2tSessionConnectBps              INTEGER,
      l2tSessionCallBearerType          INTEGER,
      l2tSessionFramingType             INTEGER,
      l2tSessionLocalRecvPacketWindow   INTEGER,
      l2tSessionRemoteRecvPacketWindow  INTEGER,
      l2tSessionDataRecvOctets          Counter,
      l2tSessionDataRecvDecompOctets    Counter,
      l2tSessionDataRecvPackets         Counter,
      l2tSessionDataRecvDiscards        Counter,
      l2tSessionDataSendOctets          Counter,
      l2tSessionDataSendUncompOctets    Counter,
      l2tSessionDataSendPackets         Counter,
      l2tSessionDataSendDiscards        Counter,
      l2tSessionDataFlowControlTimeouts Counter,
      l2tSessionNextSendSeq             INTEGER,
      l2tSessionNextRecvSeq             INTEGER,
      l2tSessionRemotePPD               INTEGER,
      l2tSessionAuthMethod              INTEGER,
      l2tSessionEncryptDecrypt          INTEGER,
      l2tSessionUpTime                  TimeTicks,
      l2tSessionStatus                  INTEGER
   }


   l2tSessionLocalControlTunnelId OBJECT-TYPE
      SYNTAX INTEGER
      ACCESS read-only
      STATUS mandatory
      DESCRIPTION
         "This object contains the control Channel Tunnel
          identifier for this session."
      ::= { l2tSessionStatsEntry 1 }

   l2tSessionLocalCallId OBJECT-TYPE
      SYNTAX INTEGER
      ACCESS read-only
      STATUS mandatory
      DESCRIPTION
         "This object contains the local call identifier
          for the session."
      ::= { l2tSessionStatsEntry 2 }

   l2tSessionRemoteCallId OBJECT-TYPE
      SYNTAX INTEGER
      ACCESS read-only
      STATUS mandatory
      DESCRIPTION
         "This object contains the remote call identifier
          for the session."
      ::= { l2tSessionStatsEntry 3 }

   l2tSessionPeerName OBJECT-TYPE
      SYNTAX DisplayString
      ACCESS read-only
      STATUS mandatory
      DESCRIPTION
         "This object identifies the peer session name on this
          interface. This is typically the login name of the
          remote user."
      ::= { l2tSessionStatsEntry 4 }

   l2tSessionLineState OBJECT-TYPE
      SYNTAX INTEGER {
                callwaittunnel(1),
                callidle(2),
                callwaitreply(3),
                callwaitconnect(4),
                callwaitcsanswer(5),
                callestablished(6)
             }  
      ACCESS read-only
      STATUS mandatory
      DESCRIPTION
         "This object contains the current state of the
          session. "
      ::= { l2tSessionStatsEntry 5 }

   l2tSessionCallDeviceNumber OBJECT-TYPE
      SYNTAX INTEGER
      ACCESS read-only
      STATUS mandatory
      DESCRIPTION
         "The internal interface number used for the session."
      ::= { l2tSessionStatsEntry 6 }

   l2tSessionCallSerialNumber OBJECT-TYPE
      SYNTAX DisplayString
      ACCESS read-only
      STATUS mandatory
      DESCRIPTION
         "This object contains the serial number that applies
          to the session."
      ::= { l2tSessionStatsEntry 7 }

   l2tSessionConnectBps OBJECT-TYPE
      SYNTAX INTEGER
      ACCESS read-only
      STATUS mandatory
      DESCRIPTION
         "This object returns the baud rate which this session
          was established at."
      ::= { l2tSessionStatsEntry 8 }

   l2tSessionCallBearerType OBJECT-TYPE
      SYNTAX INTEGER {
                 digital(1),
                 analog(2)
             }
      ACCESS read-only
      STATUS mandatory
      DESCRIPTION
         "This object returns the bearer type that applies to
          this session."
      ::= { l2tSessionStatsEntry 9 }

   l2tSessionFramingType OBJECT-TYPE
      SYNTAX INTEGER {
                 synchronous(1),
                 asynchronous(2)
             }
      ACCESS read-only
      STATUS mandatory
      DESCRIPTION
         "This object returns the framing type used for this
          session."
      ::= { l2tSessionStatsEntry 10 }

   l2tSessionLocalRecvPacketWindow OBJECT-TYPE
      SYNTAX INTEGER
      ACCESS read-only
      STATUS mandatory
      DESCRIPTION
         "This object returns the local receive window size for
          this session."
      ::= { l2tSessionStatsEntry 11 }

   l2tSessionRemoteRecvPacketWindow OBJECT-TYPE
      SYNTAX INTEGER
      ACCESS read-only
      STATUS mandatory
      DESCRIPTION
         "This object returns the remote receive window size for
          this session."
      ::= { l2tSessionStatsEntry 12 }

   l2tSessionDataRecvOctets OBJECT-TYPE
      SYNTAX Counter
      ACCESS read-only
      STATUS mandatory
      DESCRIPTION
         "The number of octets received on the data tunnel for
          this session.  This value is accumulated BEFORE 
          determining whether or not the packet should be 
          uncompressed."
      ::= { l2tSessionStatsEntry 13 }

   l2tSessionDataRecvDecompOctets OBJECT-TYPE
      SYNTAX Counter
      ACCESS read-only
      STATUS mandatory
      DESCRIPTION
         "The number of uncompressed octets received on the 
          data tunnel for this session.  This value is 
          accumulated AFTER the packet is uncompressed.
          If compression is not in use, this value will
          match the value of l2tSessionDataRecvOctets."
      ::= { l2tSessionStatsEntry 14 }

   l2tSessionDataRecvPackets OBJECT-TYPE
      SYNTAX Counter
      ACCESS read-only
      STATUS mandatory
      DESCRIPTION
         "The number packets received on the data tunnel for
          this session."    
      ::= { l2tSessionStatsEntry 15 }

   l2tSessionDataRecvDiscards OBJECT-TYPE
      SYNTAX Counter
      ACCESS read-only
      STATUS mandatory
      DESCRIPTION
         "The number packets which were discarded during
          the data tunnels receive processing for this session."
      ::= { l2tSessionStatsEntry 16 }

   l2tSessionDataSendOctets OBJECT-TYPE
      SYNTAX Counter
      ACCESS read-only
      STATUS mandatory
      DESCRIPTION
         "The number of octets sent on the data tunnel for
          this session.  This value is accumulated AFTER 
          the packet was compressed. If compression is 
          not in use, this value will match the value 
          of l2tSessionDataRecvUncompOctets."
      ::= { l2tSessionStatsEntry 17 }

   l2tSessionDataSendUncompOctets OBJECT-TYPE
      SYNTAX Counter
      ACCESS read-only
      STATUS mandatory
      DESCRIPTION
         "The number of uncompressed octets sent on the
          data tunnel for this session.  This value is
          is accumulated BEFORE determining whether or 
          not the packet should be compressed."
      ::= { l2tSessionStatsEntry 18 }

   l2tSessionDataSendPackets OBJECT-TYPE
      SYNTAX Counter
      ACCESS read-only
      STATUS mandatory
      DESCRIPTION
         "The number packets sent on the data tunnel for
          this session."
      ::= { l2tSessionStatsEntry 19 }

   l2tSessionDataSendDiscards OBJECT-TYPE
      SYNTAX Counter
      ACCESS read-only
      STATUS mandatory
      DESCRIPTION
         "The number packets which were discarded during
          the data tunnels send processing for this session."
      ::= { l2tSessionStatsEntry 20 }

   l2tSessionDataFlowControlTimeouts OBJECT-TYPE
      SYNTAX Counter
      ACCESS read-only
      STATUS mandatory
      DESCRIPTION
         "This object returns the total number of flow
          control time-outs seen on the data Tunnel for
          this session."
      ::= { l2tSessionStatsEntry 21 }

   l2tSessionNextSendSeq OBJECT-TYPE
      SYNTAX INTEGER
      ACCESS read-only
      STATUS mandatory
      DESCRIPTION
         "This object contains the next send sequence number for
          for this session."
      ::= { l2tSessionStatsEntry 22 }

   l2tSessionNextRecvSeq OBJECT-TYPE
      SYNTAX INTEGER
      ACCESS read-only
      STATUS mandatory
      DESCRIPTION
         "This object contains the next receive sequence number
          for this session."
      ::= { l2tSessionStatsEntry 23 }

   l2tSessionRemotePPD OBJECT-TYPE
      SYNTAX INTEGER
      ACCESS read-only
      STATUS mandatory
      DESCRIPTION
         "This object contains the Packet Processing Delay
          for the session."
      ::= { l2tSessionStatsEntry 24 }

   l2tSessionAuthMethod OBJECT-TYPE
      SYNTAX INTEGER {
                 text(1),
                 pppchap(2),
                 ppppap(3),
                 none(4)
             }
      ACCESS read-only
      STATUS mandatory
      DESCRIPTION
         "This object contains the proxy authentication method
          employed by the LAC for the session."
      ::= { l2tSessionStatsEntry 25 }

   l2tSessionEncryptDecrypt OBJECT-TYPE
      SYNTAX INTEGER {
                 true(1), 
                 false(2)       
             }
      ACCESS read-only
      STATUS mandatory
      DESCRIPTION
         "This object reflects whether or not the encryption and
          and decryption is being performed for the session." 
      ::= { l2tSessionStatsEntry 26 }

   l2tSessionUpTime OBJECT-TYPE
      SYNTAX TimeTicks
      ACCESS read-only
      STATUS mandatory
      DESCRIPTION
         "The length of time the session has been active in
          hundredths of seconds. "
      ::= { l2tSessionStatsEntry 27 }

   l2tSessionStatus OBJECT-TYPE
      SYNTAX INTEGER {
                active(1),
                destroy(2)
             }
      ACCESS read-write
      STATUS mandatory
      DESCRIPTION
         "The status of the MIB table row.  This object
          can be used to bring the session down by setting
          value of this object to destroy(2).
          This object cannot be used to create a MIB table row."
      ::= { l2tSessionStatsEntry 28 }

-- ----------------------------------------------------------------------------
-- The L2T IP/UDP Transport Configuration Table
--
-- This table contains objects that can be used to configure
-- the operational characteristics of the IP/UDP transport
-- layer for L2T.
-- ----------------------------------------------------------------------------

   l2tUdpConfigTable OBJECT-TYPE
      SYNTAX SEQUENCE OF L2tUdpConfigEntry
      ACCESS not-accessible
      STATUS mandatory
      DESCRIPTION
         "The L2T session configuration table."
      ::= { l2tUdp 1 }

   l2tUdpConfigEntry OBJECT-TYPE
      SYNTAX L2tUdpConfigEntry
      ACCESS not-accessible
      STATUS mandatory
      DESCRIPTION
         "An L2T session interface configuration entry."
      INDEX { l2tTunnelLocalTunnelControlId } -- from l2tTunnelStatsTable
      ::= { l2tUdpConfigTable 1 }

   L2tUdpConfigEntry ::= SEQUENCE {
      l2tUdpPeerAddress   IpAddress,
      l2tUdpPeerPort      INTEGER
   }


   l2tUdpPeerAddress OBJECT-TYPE
      SYNTAX IpAddress
      ACCESS read-only      
      STATUS mandatory
      DESCRIPTION
         "This object is used to configure the remote tunnel
          endpoints IP address. "
      ::= { l2tUdpConfigEntry 1 }

   l2tUdpPeerPort OBJECT-TYPE
      SYNTAX INTEGER
      ACCESS read-only      
      STATUS mandatory
      DESCRIPTION
         "This object is used to configure the remote tunnel
          endpoints UDP port. "
      DEFVAL          { 1701 }
      ::= { l2tUdpConfigEntry 2 }

-- ----------------------------------------------------------------------------
-- The L2T IP/UDP Transport Status and Statistics Table
--
-- This table contains objects that can be used to describe
-- the current status and statistics of the IP/UDP L2T
-- tunnel transport.
-- ----------------------------------------------------------------------------

   l2tUdpStatsTable OBJECT-TYPE
      SYNTAX SEQUENCE OF L2tUdpStatsEntry
      ACCESS not-accessible
      STATUS mandatory
      DESCRIPTION
         "The L2T session configuration table."
      ::= { l2tUdp 2 }

   l2tUdpStatsEntry OBJECT-TYPE
      SYNTAX L2tUdpStatsEntry
      ACCESS not-accessible
      STATUS mandatory
      DESCRIPTION
         "An L2T session interface configuration entry."
      INDEX { l2tTunnelLocalTunnelControlId } -- from l2tTunnelStatsTable
      ::= { l2tUdpStatsTable 1 }

   L2tUdpStatsEntry ::= SEQUENCE {
      l2tUdpPeerIpAddress   IpAddress,
      l2tUdpLocalIpAddress  IpAddress,
      l2tUdpSrcPort         INTEGER,
      l2tUdpDstPort         INTEGER
   }

   l2tUdpPeerIpAddress OBJECT-TYPE
      SYNTAX IpAddress
      ACCESS read-only      
      STATUS mandatory
      DESCRIPTION
         "The peer IP Address of the tunnel."
      ::= { l2tUdpStatsEntry 1 }

   l2tUdpLocalIpAddress OBJECT-TYPE
      SYNTAX IpAddress
      ACCESS read-only      
      STATUS mandatory
      DESCRIPTION
         "The local IP Address of the tunnel." 
      ::= { l2tUdpStatsEntry 2 }

   l2tUdpSrcPort OBJECT-TYPE
      SYNTAX INTEGER
      ACCESS read-only      
      STATUS mandatory
      DESCRIPTION
         "The peer port of tunnel."
      ::= { l2tUdpStatsEntry 3 }

   l2tUdpDstPort OBJECT-TYPE
      SYNTAX INTEGER
      ACCESS read-only      
      STATUS mandatory
      DESCRIPTION
         "The local port of tunnel."
      ::= { l2tUdpStatsEntry 4 }

-- ----------------------------------------------------------------------------
-- The L2T Authentication Statistics Group
--
-- This group of objects is used to manage authentication   
-- processing of the L2T protocol environment.
-- ----------------------------------------------------------------------------

   l2tAuthStats OBJECT IDENTIFIER ::= { l2tAuthentication 1 }

   l2tAuthTunnelSuccesses OBJECT-TYPE
      SYNTAX Counter 
      ACCESS read-only      
      STATUS mandatory
      DESCRIPTION
      "The number of successful tunnel authentications performed."
      ::= { l2tAuthStats 1 }

   l2tAuthTunnelFailures OBJECT-TYPE
      SYNTAX Counter 
      ACCESS read-only      
      STATUS mandatory
      DESCRIPTION
      "The number of tunnel authentications which failed."
      ::= { l2tAuthStats 2 }

   l2tAuthUserSuccesses OBJECT-TYPE
      SYNTAX Counter 
      ACCESS read-only      
      STATUS mandatory
      DESCRIPTION
      "The number of successful user authentications performed."
      ::= { l2tAuthStats 3 }

   l2tAuthUserFailures OBJECT-TYPE
      SYNTAX Counter 
      ACCESS read-only      
      STATUS mandatory
      DESCRIPTION
      "The number of user authentications which failed."
           ::= { l2tAuthStats 4 }

-- ----------------------------------------------------------------------------
-- The L2T Tunnel Authentication Failure Table
--
-- This table contains objects that can be used to monitor 
-- tunnel authentication failures.                       
-- ----------------------------------------------------------------------------

   l2tAuthFailures OBJECT IDENTIFIER ::= { l2tAuthentication 2 }

   l2tAuthFailTunnelTable OBJECT-TYPE
      SYNTAX SEQUENCE OF L2tAuthFailTunnelEntry
      ACCESS not-accessible
      STATUS mandatory
      DESCRIPTION
         "The L2T tunnel authentication failure table."
      ::= { l2tAuthFailures 1 }

   l2tAuthFailTunnelEntry OBJECT-TYPE
      SYNTAX L2tAuthFailTunnelEntry
      ACCESS not-accessible
      STATUS mandatory
      DESCRIPTION
         "An L2T tunnel authentication failure entry. "
      INDEX { l2tAuthFailTunnelIndex }
      ::= { l2tAuthFailTunnelTable 1 }

   L2tAuthFailTunnelEntry ::= SEQUENCE {
      l2tAuthFailTunnelIndex     INTEGER,      
      l2tAuthFailTunnelHostName  DisplayString,
      l2tAuthFailTunnelIpAddress IpAddress,
      l2tAuthFailTunnelTime      TimeTicks     
   }

   l2tAuthFailTunnelIndex OBJECT-TYPE
      SYNTAX INTEGER(1..65535)
      ACCESS read-only      
      STATUS mandatory
      DESCRIPTION
         "The index of the tunnel authentication failure  
          table.  The value of the index is a number which
          begins at one and is incremented with each tunnel
          authentication failure.  It will wrap at 65535."
      ::= { l2tAuthFailTunnelEntry 1 }

   l2tAuthFailTunnelHostName OBJECT-TYPE
      SYNTAX DisplayString       
      ACCESS read-only      
      STATUS mandatory
      DESCRIPTION
         "The host name used on the failed tunnel 
          authentication attempt."
      ::= { l2tAuthFailTunnelEntry 2 }

   l2tAuthFailTunnelIpAddress OBJECT-TYPE
      SYNTAX IpAddress
      ACCESS read-only      
      STATUS mandatory
      DESCRIPTION
         "The IP address associated with the failed 
          tunnel authentication attempt."
      ::= { l2tAuthFailTunnelEntry 3 }

   l2tAuthFailTunnelTime      OBJECT-TYPE
      SYNTAX TimeTicks      
      ACCESS read-only
      STATUS mandatory
      DESCRIPTION
         "The time of the failure in hundredths of seconds."
      ::= { l2tAuthFailTunnelEntry 4 }


-- ----------------------------------------------------------------------------
-- The L2T User Authentication Failure Table
--
-- This table contains objects that can be used to monitor
-- user authentication failures.
-- ----------------------------------------------------------------------------

   l2tAuthFailUserTable OBJECT-TYPE
      SYNTAX SEQUENCE OF L2tAuthFailUserEntry
      ACCESS not-accessible
      STATUS mandatory
      DESCRIPTION
         "The L2T user authentication failure table."
      ::= { l2tAuthFailures 2 }

   l2tAuthFailUserEntry OBJECT-TYPE
      SYNTAX L2tAuthFailUserEntry
      ACCESS not-accessible
      STATUS mandatory
      DESCRIPTION
         "An L2T user authentication failure entry. "
      INDEX { l2tAuthFailUserIndex }
      ::= { l2tAuthFailUserTable 1 }

   L2tAuthFailUserEntry ::= SEQUENCE {
      l2tAuthFailUserIndex INTEGER,
      l2tAuthFailUserId    DisplayString,
      l2tAuthFailUserTime  TimeTicks      
   }

   l2tAuthFailUserIndex OBJECT-TYPE
      SYNTAX INTEGER(1..65535)
      ACCESS read-only      
      STATUS mandatory
      DESCRIPTION
         "The index of the user authentication failure
          table.  The value of the index is a number which
          begins at one and is incremented with each user
          authentication failure.  It will wrap at 65535."
      ::= { l2tAuthFailUserEntry 1 }

   l2tAuthFailUserId OBJECT-TYPE
      SYNTAX DisplayString
      ACCESS read-only      
      STATUS mandatory
      DESCRIPTION
         "The user name used on the failed 
          authentication attempt."
      ::= { l2tAuthFailUserEntry 2 }

   l2tAuthFailUserTime        OBJECT-TYPE
      SYNTAX TimeTicks
      ACCESS read-only
      STATUS mandatory
      DESCRIPTION
         "The time of the failure in hundredths of seconds."
      ::= { l2tAuthFailUserEntry 3 }    

-- ----------------------------------------------------------------------------
-- The L2T Tunnel History Table
--
-- This table contains objects that can be used to monitor
-- previously active tunnels. 
-- ----------------------------------------------------------------------------
                
   l2tHistTunnelTable OBJECT-TYPE
      SYNTAX SEQUENCE OF L2tHistTunnelEntry
      ACCESS not-accessible
      STATUS mandatory
      DESCRIPTION
         "The L2T tunnel history table."
      ::= { l2tHistory 1 }       

   l2tHistTunnelEntry OBJECT-TYPE
      SYNTAX L2tHistTunnelEntry
      ACCESS not-accessible
      STATUS mandatory
      DESCRIPTION
         "An L2T tunnel history entry. "
      INDEX { l2tHistTunnelIndex }
      ::= { l2tHistTunnelTable 1 }

   L2tHistTunnelEntry ::= SEQUENCE {
      l2tHistTunnelIndex            INTEGER,
      l2tHistTunnelTunnelIndex      INTEGER,
      l2tHistTunnelRemoteHostName   DisplayString,
      l2tHistTunnelRemoteIpAddress  IpAddress, 
      l2tHistTunnelRemotePort       INTEGER,     
      l2tHistTunnelLocalIpAddress   IpAddress, 
      l2tHistTunnelLocalPort        INTEGER,     
      l2tHistTunnelUpTime           TimeTicks,
      l2tHistTunnelTotalSessions    Counter,
      l2tHistTunnelType             INTEGER,
      l2tHistTunnelInOctets         Counter,
      l2tHistTunnelInPkts           Counter,
      l2tHistTunnelInDiscards       Counter,
      l2tHistTunnelOutOctets        Counter,
      l2tHistTunnelOutPkts          Counter,
      l2tHistTunnelOutDiscards      Counter
  }

   l2tHistTunnelIndex OBJECT-TYPE
      SYNTAX INTEGER(1..65535)
      ACCESS read-only      
      STATUS mandatory
      DESCRIPTION
         "The index of the tunnel history table.
          The value of the index is a number which
          begins at one and is incremented with each tunnel
          that ends. The value of this object will wrap at 65535."
      ::= { l2tHistTunnelEntry 1 }

   l2tHistTunnelTunnelIndex OBJECT-TYPE
      SYNTAX INTEGER
      ACCESS read-only      
      STATUS mandatory
      DESCRIPTION
         "The value which was used as the tunnel stats table
          index."          
      ::= { l2tHistTunnelEntry 2 }

   l2tHistTunnelRemoteHostName OBJECT-TYPE
      SYNTAX DisplayString 
      ACCESS read-only      
      STATUS mandatory
      DESCRIPTION
         "The remote host name which was used for this 
          previous tunnel."
      ::= { l2tHistTunnelEntry 3 }

   l2tHistTunnelRemoteIpAddress OBJECT-TYPE
      SYNTAX IpAddress  
      ACCESS read-only      
      STATUS mandatory
      DESCRIPTION
         "The remote IP address which was used for this 
          previous tunnel."
      ::= { l2tHistTunnelEntry 4 }

   l2tHistTunnelRemotePort OBJECT-TYPE
      SYNTAX INTEGER
      ACCESS read-only
      STATUS mandatory
      DESCRIPTION
         "The remote UDP port which was used for this
          previous tunnel."
      ::= { l2tHistTunnelEntry 5 }

   l2tHistTunnelLocalIpAddress OBJECT-TYPE
      SYNTAX IpAddress  
      ACCESS read-only      
      STATUS mandatory
      DESCRIPTION
         "The local IP address which was used for this
          previous tunnel."
      ::= { l2tHistTunnelEntry 6 }

   l2tHistTunnelLocalPort OBJECT-TYPE
      SYNTAX INTEGER
      ACCESS read-only
      STATUS mandatory
      DESCRIPTION
         "The local UDP port which was used for this
          previous tunnel."
      ::= { l2tHistTunnelEntry 7 }

   l2tHistTunnelUpTime OBJECT-TYPE
      SYNTAX TimeTicks
      ACCESS read-only      
      STATUS mandatory
      DESCRIPTION
         "The length of time the tunnel was active in
          hundredths of seconds. "
      ::= { l2tHistTunnelEntry 8 }

   l2tHistTunnelTotalSessions  OBJECT-TYPE
      SYNTAX Counter
      ACCESS read-only      
      STATUS mandatory
      DESCRIPTION
         "The total number of sessions which used this tunnel."
      ::= { l2tHistTunnelEntry 9 }

   l2tHistTunnelType OBJECT-TYPE
      SYNTAX INTEGER {
                l2tpTunnel(1),
                l2fTunnel(2),
                pptpTunnel(3)
             }
      ACCESS read-only      
      STATUS mandatory
      DESCRIPTION
         "The type of Layer-2 Tunnel.  Possible values are 
            1 = Layer-2 Tunnel Protocol Tunnel,
            2 = Layer-2 Forwarding Tunnel,
            3 = Point-to-Point Tunnel Protocol Tunnel."
      ::= { l2tHistTunnelEntry 10 }

   l2tHistTunnelInOctets OBJECT-TYPE
      SYNTAX Counter
      ACCESS read-only      
      STATUS mandatory
      DESCRIPTION
         "The number of octets received by this tunnel."
      ::= { l2tHistTunnelEntry 11 }

   l2tHistTunnelInPkts OBJECT-TYPE
      SYNTAX Counter
      ACCESS read-only      
      STATUS mandatory
      DESCRIPTION
         "The number of packets received by this tunnel."
      ::= { l2tHistTunnelEntry 12 }

   l2tHistTunnelInDiscards OBJECT-TYPE
      SYNTAX Counter
      ACCESS read-only      
      STATUS mandatory
      DESCRIPTION
         "The number of packets which were discarded during
          receive processing."
      ::= { l2tHistTunnelEntry 13 }

   l2tHistTunnelOutOctets OBJECT-TYPE
      SYNTAX Counter
      ACCESS read-only      
      STATUS mandatory
      DESCRIPTION
         "The number of octets sent by this tunnel."
      ::= { l2tHistTunnelEntry 14 }

   l2tHistTunnelOutPkts OBJECT-TYPE
      SYNTAX Counter
      ACCESS read-only      
      STATUS mandatory
      DESCRIPTION
         "The number of packets sent by this tunnel."
      ::= { l2tHistTunnelEntry 15 }

   l2tHistTunnelOutDiscards OBJECT-TYPE
      SYNTAX Counter
      ACCESS read-only      
      STATUS mandatory
      DESCRIPTION
         "The number of packets which were discarded during
          send processing."
      ::= { l2tHistTunnelEntry 16 }

-- ----------------------------------------------------------------------------
-- The L2T Session History Table
--
-- This table contains objects that can be used to monitor
-- previously active sessions.
-- ----------------------------------------------------------------------------

   l2tHistSessTable OBJECT-TYPE
      SYNTAX SEQUENCE OF L2tHistSessEntry
      ACCESS not-accessible
      STATUS mandatory
      DESCRIPTION
         "The L2T session history table."
      ::= { l2tHistory 2 }

   l2tHistSessEntry OBJECT-TYPE
      SYNTAX L2tHistSessEntry
      ACCESS not-accessible
      STATUS mandatory
      DESCRIPTION
         "An L2T session history entry. "
      INDEX { l2tHistSessIndex }
      ::= { l2tHistSessTable 1 }

   L2tHistSessEntry ::= SEQUENCE {
      l2tHistSessIndex            INTEGER,
      l2tHistSessTunnelIndex      INTEGER,
      l2tHistSessLocalCallId      INTEGER,
      l2tHistSessRemoteIpAddress  IpAddress, 
      l2tHistSessLocalIpAddress   IpAddress, 
      l2tHistSessUpTime           TimeTicks,
      l2tHistSessDataRecvOctets   Counter,
      l2tHistSessDataRecvPackets  Counter,
      l2tHistSessDataRecvDiscards Counter,
      l2tHistSessDataSendOctets   Counter,
      l2tHistSessDataSendPackets  Counter,
      l2tHistSessDataSendDiscards Counter,
      l2tHistSessAuthMethod       INTEGER,
      l2tHistSessEncryptDecrypt   INTEGER
  }

   l2tHistSessIndex OBJECT-TYPE
      SYNTAX INTEGER(1..65535)
      ACCESS read-only      
      STATUS mandatory
      DESCRIPTION
         "The index of the session history table.
          The value of the index is a number which
          begins at one and is incremented with each tunnel
          that ends. The value of this object will wrap at 65535."
      ::= { l2tHistSessEntry 1 }

   l2tHistSessTunnelIndex OBJECT-TYPE
      SYNTAX INTEGER
      ACCESS read-only      
      STATUS mandatory
      DESCRIPTION
         "The value which was used as the tunnel stats table
          index."
      ::= { l2tHistSessEntry 2 }

   l2tHistSessLocalCallId OBJECT-TYPE
      SYNTAX INTEGER
      ACCESS read-only      
      STATUS mandatory
      DESCRIPTION
         "The value which was used as the session stats table
          index."
      ::= { l2tHistSessEntry 3 }

   l2tHistSessRemoteIpAddress OBJECT-TYPE
      SYNTAX IpAddress
      ACCESS read-only      
      STATUS mandatory
      DESCRIPTION
         "The remote IP address which was used for this
          session."
      ::= { l2tHistSessEntry 4 }

   l2tHistSessLocalIpAddress OBJECT-TYPE
      SYNTAX IpAddress
      ACCESS read-only      
      STATUS mandatory
      DESCRIPTION
         "The local IP address which was used for this
          session."
      ::= { l2tHistSessEntry 5 }

   l2tHistSessUpTime OBJECT-TYPE
      SYNTAX TimeTicks
      ACCESS read-only      
      STATUS mandatory
      DESCRIPTION
         "The length of time the session was been active in
          hundredths of seconds. "
      ::= { l2tHistSessEntry 6 }

   l2tHistSessDataRecvOctets OBJECT-TYPE
      SYNTAX Counter
      ACCESS read-only      
      STATUS mandatory
      DESCRIPTION
         "The number of octets received on the data tunnel for
          this session.  This value was accumulated BEFORE
          determining whether or not the packet should be
          uncompressed."
      ::= { l2tHistSessEntry 7 }

   l2tHistSessDataRecvPackets OBJECT-TYPE
      SYNTAX Counter
      ACCESS read-only      
      STATUS mandatory
      DESCRIPTION
         "The number packets received on the data tunnel for
          this session."
      ::= { l2tHistSessEntry 8 }

   l2tHistSessDataRecvDiscards OBJECT-TYPE
      SYNTAX Counter
      ACCESS read-only      
      STATUS mandatory
      DESCRIPTION
         "The number packets which were discarded during
          the data tunnels receive processing for this session."
      ::= { l2tHistSessEntry 9 }

   l2tHistSessDataSendOctets OBJECT-TYPE
      SYNTAX Counter
      ACCESS read-only      
      STATUS mandatory
      DESCRIPTION
         "The number of octets sent on the data tunnel for
          this session.  This value is accumulated AFTER
          the packet was compressed."
      ::= { l2tHistSessEntry 10 }

   l2tHistSessDataSendPackets OBJECT-TYPE
      SYNTAX Counter
      ACCESS read-only      
      STATUS mandatory
      DESCRIPTION
         "The number packets sent on the data tunnel for
          this session."
      ::= { l2tHistSessEntry 11 }

   l2tHistSessDataSendDiscards OBJECT-TYPE
      SYNTAX Counter
      ACCESS read-only      
      STATUS mandatory
      DESCRIPTION
         "The number packets which were discarded during
          the data tunnels send processing for this session."
      ::= { l2tHistSessEntry 12 }

   l2tHistSessAuthMethod OBJECT-TYPE
      SYNTAX INTEGER {
                 text(1),
                 pppchap(2),
                 ppppap(3),
                 none(4)
             }
      ACCESS read-only      
      STATUS mandatory
      DESCRIPTION
         "This object contains the proxy authentication method
          which was employed by the LAC for the session."
      ::= { l2tHistSessEntry 13 }

   l2tHistSessEncryptDecrypt  OBJECT-TYPE
      SYNTAX INTEGER {
                 yes(1),
                 no(2)
             }
      ACCESS read-only      
      STATUS mandatory
      DESCRIPTION
         "This object reflects whether or not the encryption and
          and decryption is being performed for the session."
      ::= { l2tHistSessEntry 14 }


-- ----------------------------------------------------------------------------
-- The L2T Host Table                       
--
-- This table permits the monitoring of potential L2T hosts.      
-- ----------------------------------------------------------------------------

   l2tHostTable OBJECT-TYPE
      SYNTAX SEQUENCE OF L2tHostEntry
      ACCESS not-accessible
      STATUS mandatory
      DESCRIPTION
         "The L2T host table."
      ::= { l2tHosts 1 }

   l2tHostEntry OBJECT-TYPE
      SYNTAX L2tHostEntry
      ACCESS not-accessible
      STATUS mandatory
      DESCRIPTION
         "An L2T host entry." 
      INDEX { l2tHostIndex }
      ::= { l2tHostTable 1 }

   L2tHostEntry ::= SEQUENCE {
      l2tHostIndex             INTEGER,
      l2tHostName              DisplayString,
      l2tHostIpAddress         IpAddress,
      l2tHostTunnelStatus      INTEGER
   }

   l2tHostIndex OBJECT-TYPE
      SYNTAX INTEGER(1..65535)
      ACCESS read-only
      STATUS mandatory
      DESCRIPTION
         "The index of the host table." 
      ::= { l2tHostEntry 1 }

   l2tHostName OBJECT-TYPE
      SYNTAX DisplayString
      ACCESS read-only 
      STATUS mandatory
      DESCRIPTION
         "The host name which may used for a Layer-2 tunnel."
      ::= { l2tHostEntry 2 }

   l2tHostIpAddress OBJECT-TYPE
      SYNTAX IpAddress 
      ACCESS read-only 
      STATUS mandatory
      DESCRIPTION
         "The IP Address associated with the host name."
      ::= { l2tHostEntry 3 }

   l2tHostTunnelStatus OBJECT-TYPE
      SYNTAX INTEGER {
                 active(1),
                 inactive(2)
             }
      ACCESS read-only
      STATUS mandatory
      DESCRIPTION
         "The current tunnel status of the host."
      ::= { l2tHostEntry 4 }


-- ----------------------------------------------------------------------------
-- The L2T Tunnel Connectivity Test Table
--
-- This table permits the testing of connectively for protential
-- L2T Tunnels.
-- ----------------------------------------------------------------------------

   l2tTunnelConnectTestTable OBJECT-TYPE
      SYNTAX SEQUENCE OF L2tTunnelConnectTestEntry
      ACCESS not-accessible
      STATUS mandatory
      DESCRIPTION
         "The L2T tunnel connectivity test table."
      ::= { l2tTests 1 }

   l2tTunnelConnectTestEntry OBJECT-TYPE
      SYNTAX L2tTunnelConnectTestEntry
      ACCESS not-accessible
      STATUS mandatory
      DESCRIPTION
         "An L2T tunnel connectivity test entry."
      INDEX { l2tTunnelConnectTestIndex }
      ::= { l2tTunnelConnectTestTable 1 }

   L2tTunnelConnectTestEntry ::= SEQUENCE {
      l2tTunnelConnectTestIndex       INTEGER,
      l2tTunnelConnectTestHostName    DisplayString,
      l2tTunnelConnectTestResult      INTEGER,
      l2tTunnelConnectTestType        INTEGER,
      l2tTunnelConnectTestStatus      INTEGER
   }

   l2tTunnelConnectTestIndex OBJECT-TYPE
      SYNTAX INTEGER(1..65535)
      ACCESS read-only
      STATUS mandatory
      DESCRIPTION
         "The index of the tunnel connectivity test table.
          The value of the index is a number which was used
          during row creation."
      ::= { l2tTunnelConnectTestEntry 1 }

   l2tTunnelConnectTestHostName OBJECT-TYPE
      SYNTAX DisplayString
      ACCESS read-write
      STATUS mandatory
      DESCRIPTION
         "The host name used to establish a Layer-2 tunnel.
      
          This object is used to trigger a connectivity test
          to a specific host.  A new test is triggered by 
          SETTING this object using a non-existent index    
          and SETTING l2tTunnelConnectTestStatus to createAndGo.
          For example to trigger a new connectivity test 
          when the table currently contains row 1 through 4,
          one would send a SET as follows:                    
           SNMP SET l2tTunnelConnectHostName.5   = Host-To-Test
                    l2tTunnelConnectTestStatus.5 = createAndGo
          See l2tHostName for the possible host names which
          may be specified.
          
          Existing entries may NOT be modified."             
      ::= { l2tTunnelConnectTestEntry 2 }

   l2tTunnelConnectTestResult OBJECT-TYPE
      SYNTAX INTEGER {
                 inProgress(1),
                 successful(2),
                 tunnelAlreadyUp(3),
                 hostNotResponding(4),
                 localAuthFailure(5),
                 remoteAuthFailure(6)
             }
      ACCESS read-only
      STATUS mandatory
      DESCRIPTION
         "The result of the tunnel connectivity test.           
          1 = test is in progress
          2 = test ended successfully
          3 = tunnel is already active
          4 = host did not respond
          5 = local authentication failure
          6 = remote authentication failure."
      ::= { l2tTunnelConnectTestEntry 3 }

   l2tTunnelConnectTestType OBJECT-TYPE
      SYNTAX INTEGER {
                l2tpTunnel(1),
                l2fTunnel(2),
                pptpTunnel(3),
                none(99)
             }
      ACCESS read-only
      STATUS mandatory
      DESCRIPTION
         "The type of Layer-2 Tunnel.  Possible values are:
          1  = Layer-2 Tunnel Protocol Tunnel
          2  = Layer-2 Forwarding Tunnel
          3  = Point-to-Point Tunnel Protocol Tunnel
          99 = no tunnel created."                    
      ::= { l2tTunnelConnectTestEntry 4 }

   l2tTunnelConnectTestStatus OBJECT-TYPE
      SYNTAX INTEGER {
                active(1),     
                createAndGo(4) 
             }
      ACCESS read-write
      STATUS mandatory
      DESCRIPTION
         "The status of the test entry. Possible values are:
          1  = active entry                    
          4  = createAndGo              
         
          This object is used to trigger a connectivity test
          to a specific host.  A new test is triggered by
          SETTING this object to createAndGo using a non-existent
          index and SETTING l2tTunnelConnectTestHostName to a 
          specific host name.  For example to trigger a new 
          connectivity test when the table currently contains 
          row 1 through 4, one would send a SET as follows:
           SNMP SET l2tTunnelConnectHostName.5   = Host-To-Test
                    l2tTunnelConnectTestStatus.5 = createAndGo
          See l2tHostName for the possible host names which
          may be specified.

          Existing entries may NOT be modified."
      ::= { l2tTunnelConnectTestEntry 5 }

-- ----------------------------------------------------------------------------
-- The L2T Tunnel Response Time Test Table
--
-- This table permits the testing the response time of an existing
-- L2T Tunnel.
-- ----------------------------------------------------------------------------

   l2tTunnelRspTimeTestTable OBJECT-TYPE
      SYNTAX SEQUENCE OF L2tTunnelRspTimeTestEntry
      ACCESS not-accessible
      STATUS mandatory
      DESCRIPTION
         "The L2T tunnel response time test table."
      ::= { l2tTests 2 }

   l2tTunnelRspTimeTestEntry OBJECT-TYPE
      SYNTAX L2tTunnelRspTimeTestEntry
      ACCESS not-accessible
      STATUS mandatory
      DESCRIPTION
         "An L2T tunnel response time test entry."
      INDEX { l2tTunnelRspTimeTestIndex }
      ::= { l2tTunnelRspTimeTestTable 1 }

   L2tTunnelRspTimeTestEntry ::= SEQUENCE {
      l2tTunnelRspTimeTestIndex       INTEGER,
      l2tTunnelRspTimeTestHostName    DisplayString,
      l2tTunnelRspTimeTestResult      INTEGER,
      l2tTunnelRspTimeTestRtripTime   INTEGER,
      l2tTunnelRspTimeTestStatus      INTEGER
   }

   l2tTunnelRspTimeTestIndex OBJECT-TYPE
      SYNTAX INTEGER(1..65535)
      ACCESS read-only
      STATUS mandatory
      DESCRIPTION
         "The index of the tunnel connectivity test table.
          The value of the index is a number which was used
          during row creation."
      ::= { l2tTunnelRspTimeTestEntry 1 }

   l2tTunnelRspTimeTestHostName OBJECT-TYPE
      SYNTAX DisplayString
      ACCESS read-write
      STATUS mandatory
      DESCRIPTION
         "The host name used to test the round-trip response
          time of an existing Layer-2 Tunnel.

          This object is used to trigger a response time test
          of an existing Layer-2 to a specific host.  A new test
          is triggered by SETTING this object using a non-existent
          index and SETTING l2tTunnelRspTimeTestStatus to createAndGo.
          For example to trigger a new connectivity test
          when the table currently contains row 1 through 4,
          one would send a SET as follows:
           SNMP SET l2tTunnelRspTimeHostName.5   = Host-To-Test
                    l2tTunnelRspTimeTestStatus.5 = createAndGo
          See l2tHistTunnelRemoteHostName for the possible host
          names which may be specified.

          Existing entries may NOT be modified."
      ::= { l2tTunnelRspTimeTestEntry 2 }

   l2tTunnelRspTimeTestResult OBJECT-TYPE
      SYNTAX INTEGER {
                 inProgress(1),
                 successful(2),
                 hostNotResponding(3),
                 tunnelDown(4)
             }
      ACCESS read-only
      STATUS mandatory
      DESCRIPTION
         "The result of the tunnel connectivity test.
          1 = test is in progress
          2 = test ended successfully
          3 = host did not respond
          4 = a tunnel to this host is NOT available."
      ::= { l2tTunnelRspTimeTestEntry 3 }

   l2tTunnelRspTimeTestRtripTime OBJECT-TYPE
      SYNTAX INTEGER
      ACCESS read-only
      STATUS mandatory
      DESCRIPTION
         "The round time in milliseconds of response time test."
      ::= { l2tTunnelRspTimeTestEntry 4 }

   l2tTunnelRspTimeTestStatus OBJECT-TYPE
      SYNTAX INTEGER {
                active(1),
                createAndGo(4)
             }
      ACCESS read-write
      STATUS mandatory
      DESCRIPTION
         "The status of the test entry. Possible values are:
          1  = active entry
          4  = createAndGo

          This object is used to trigger a response time test
          of an existing Layer-2 to a specific host.  A new test
          is triggered by SETTING this object using a non-existent
          index to createAndGo and SETTING l2tTunnelRspTimeHostName
          to a specific host.  For example to trigger a new response
          time test when the table currently contains row 1 through 4,
          one would send a SET as follows:
           SNMP SET l2tTunnelRspTimeHostName.5   = Host-To-Test
                    l2tTunnelRspTimeTestStatus.5 = createAndGo
          See l2tHistTunnelRemoteHostName for the possible host
          names which may be specified.

          Existing entries may NOT be modified."
      ::= { l2tTunnelRspTimeTestEntry 5 }

 
-- ----------------------------------------------------------------------------
-- The L2T TRAP Control Group         
--
-- This group of objects controls the sending L2T TRAPs.   
-- ----------------------------------------------------------------------------

   l2tTrapCntlTunnelStart OBJECT-TYPE
      SYNTAX INTEGER {
                enabled(1),
                disabled(2)
             }
      ACCESS read-write
      STATUS mandatory
      DESCRIPTION
         "This object defines the administrative state of sending the L2T
          Tunnel Start TRAP "
      DEFVAL { enabled }
      ::= { l2tTrapCntl 1 }      

   l2tTrapCntlTunnelStop OBJECT-TYPE
      SYNTAX INTEGER {
                enabled(1),
                disabled(2)
             }
      ACCESS read-write
      STATUS mandatory
      DESCRIPTION
         "This object defines the administrative state of sending the L2T
          Tunnel Stop TRAP "
      DEFVAL { enabled }
      ::= { l2tTrapCntl 2 }      

   l2tTrapCntlAuthFailTunnel OBJECT-TYPE
      SYNTAX INTEGER {
                enabled(1),
                disabled(2)
             }
      ACCESS read-write
      STATUS mandatory
      DESCRIPTION
         "This object defines the administrative state of sending the L2T
          Tunnel Authentication Failure TRAP "
      DEFVAL { enabled }
      ::= { l2tTrapCntl 3 }      

   l2tTrapCntlAuthFailUser OBJECT-TYPE
      SYNTAX INTEGER {
                enabled(1),
                disabled(2)
             }
      ACCESS read-write
      STATUS mandatory
      DESCRIPTION
         "This object defines the administrative state of sending the L2T
          User Authentication Failure TRAP "
      DEFVAL { enabled }
      ::= { l2tTrapCntl 4 }      

-- ----------------------------------------------------------------------------
-- The L2T TRAP Group
-- Describes TRAPs which can be generated by the Layer Two Transport Protocol
-- ----------------------------------------------------------------------------

l2tTunnelStart TRAP-TYPE
    ENTERPRISE ibmIROCroutingl2t
    VARIABLES  { l2tTunnelLocalTunnelControlId,
                 l2tTunnelType }
    DESCRIPTION
       "This TRAP is generated when a Layer-2 Tunnel 
        is created."
    ::= 1

l2tTunnelStop TRAP-TYPE
    ENTERPRISE ibmIROCroutingl2t
    VARIABLES  { l2tTunnelLocalTunnelControlId,
                 l2tTunnelType,
                 l2tTunnelUpTime }
    DESCRIPTION
       "This TRAP is generated when a Layer-2 Tunnel 
        ends."       
    ::= 2

l2tAuthFailTunnel TRAP-TYPE
    ENTERPRISE ibmIROCroutingl2t
    VARIABLES  { l2tAuthFailTunnelHostName,
                 l2tAuthFailTunnelIpAddress }
    DESCRIPTION
       "This TRAP is generated when a Layer-2 Tunnel 
        is NOT created due to an authentication failure."
    ::= 3

l2tAuthFailUser TRAP-TYPE
    ENTERPRISE ibmIROCroutingl2t
    VARIABLES  { l2tAuthFailUserId }
    DESCRIPTION
       "This TRAP is generated when a Session for a   
        Layer-2 Tunnel is NOT created due to an 
        authentication failure."
    ::= 4

END
