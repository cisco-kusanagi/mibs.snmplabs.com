--
-- PBC-CMTS-MIB.mib
-- MIB generated by MG-SOFT Visual MIB Builder Version 3.0 Build 253
-- Thursday, October 10, 2002 at 16:59:13
--

	PBC-CMTS-MIB DEFINITIONS ::= BEGIN
 
		IMPORTS
			docsDevEvLevel, docsDevEvId, docsDevEvText			
				FROM DOCS-CABLE-DEVICE-MIB			
			docsIfCmtsCmStatusIndex, docsIfCmtsCmStatusEntry			
				FROM DOCS-IF-MIB			
			ifIndex, InterfaceIndex			
				FROM IF-MIB			
			pacificBroadband, pbcModuleRegs, pbcManagement, pbcCaps			
				FROM PBC-ENT-MIB			
			pbcCardIfPortIndex			
				FROM PBC-GENERIC-MIB			
			OBJECT-GROUP, MODULE-COMPLIANCE, NOTIFICATION-GROUP			
				FROM SNMPv2-CONF			
			IpAddress, Integer32, Unsigned32, Gauge32, Counter32, 
			OBJECT-TYPE, MODULE-IDENTITY, NOTIFICATION-TYPE			
				FROM SNMPv2-SMI			
			MacAddress, DateAndTime, TruthValue, TimeInterval, TEXTUAL-CONVENTION			
				FROM SNMPv2-TC;
	
	
		pbcCmtsMib MODULE-IDENTITY 
			LAST-UPDATED "200106211721Z"		-- June 21, 2001 at 17:21 GMT
			ORGANIZATION 
				"Pacific Broadband Communications"
			CONTACT-INFO 
				"Contact-info."
			DESCRIPTION 
				"This module defines all management objects which
				are common to PBC CMTS products."
			::= { pbcModuleRegs 2 }
		
	
--
-- Textual conventions
--
	
		TenthdBmV ::= TEXTUAL-CONVENTION
			DISPLAY-HINT 
				"d-1"
			STATUS current
			DESCRIPTION 
				"This data type represents power levels that are normally
				expressed in dBmV. Units are in tenths of a dBmV;
				for example, 5.1 dBmV will be represented as 51."
			SYNTAX Integer32
			
		TenthdB ::= TEXTUAL-CONVENTION
			STATUS current
			DESCRIPTION 
				"his data type represents relationships which are
				normally expressed in decibels (dB). Units are in
				tenths of a dB; for example, 15.3 dB will be
				represented as 153."
			SYNTAX Integer32
			
		OneHundredthdBmVPerHz ::= TEXTUAL-CONVENTION
			STATUS current
			DESCRIPTION 
				"his data type represents power levels that are normally
				expressed in dBmV/Hz. Units are in hundredths of a dBmV/Hz;
				for example, 15.3 dBmV/Hz will be represented as 1530."
			SYNTAX Integer32
			
	
--
-- Node definitions
--
	
		-- 1.3.6.1.4.1.5987.2.2
		pbcCmts OBJECT IDENTIFIER ::= { pbcManagement 2 }
		
		-- 1.3.6.1.4.1.5987.2.2.1
		pbcCmtsIfMibExtendedObjects OBJECT IDENTIFIER ::= { pbcCmts 1 }
		
		-- 1.3.6.1.4.1.5987.2.2.1.1
		pbcGeneral OBJECT IDENTIFIER ::= { pbcCmtsIfMibExtendedObjects 1 }
		
		-- 1.3.6.1.4.1.5987.2.2.1.2
		pbcDownStreamMgmt OBJECT IDENTIFIER ::= { pbcCmtsIfMibExtendedObjects 2 }
		
		-- 1.3.6.1.4.1.5987.2.2.1.2.1
		pbcCmtsIfDownstreamNumEntries OBJECT-TYPE
			SYNTAX Unsigned32
			MAX-ACCESS read-only
			STATUS current
			DESCRIPTION
				"Number of downstream channels represented in
				the downstream channel table."
			::= { pbcDownStreamMgmt 1 }
		
		-- 1.3.6.1.4.1.5987.2.2.1.2.2
		pbcCmtsIfDownstreamChannelTable OBJECT-TYPE
			SYNTAX SEQUENCE OF PbcCmtsIfDownstreamChannelEntry
			MAX-ACCESS not-accessible
			STATUS current
			DESCRIPTION
				"PBC-specific management objects associated with
				downstream channels."
			::= { pbcDownStreamMgmt 2 }
		
		-- 1.3.6.1.4.1.5987.2.2.1.2.2.1
		pbcCmtsIfDownstreamChannelEntry OBJECT-TYPE
			SYNTAX PbcCmtsIfDownstreamChannelEntry
			MAX-ACCESS not-accessible
			STATUS current
			DESCRIPTION
				"PBC-specific management objects associated with one
				downstream channel."
			INDEX { ifIndex }
			::= { pbcCmtsIfDownstreamChannelTable 1 }
		
		PbcCmtsIfDownstreamChannelEntry ::=
			SEQUENCE { 
				pbcCmtsIfDownstreamIfTxPower
					INTEGER
			 }

		-- 1.3.6.1.4.1.5987.2.2.1.2.2.1.1
		pbcCmtsIfDownstreamIfTxPower OBJECT-TYPE
			SYNTAX INTEGER
				{
				dBmV32(1),
				dBmV38(2)
				}
			MAX-ACCESS read-only
			STATUS current
			DESCRIPTION
				"Intermediate Frequency (IF) signal power being
				supplied to the upconverter on this channel."
			::= { pbcCmtsIfDownstreamChannelEntry 1 }
		
		-- 1.3.6.1.4.1.5987.2.2.1.3
		pbcUpStreamMgmt OBJECT IDENTIFIER ::= { pbcCmtsIfMibExtendedObjects 3 }
		
		-- 1.3.6.1.4.1.5987.2.2.1.3.1
		pbcCmtsIfUpstreamNumEntries OBJECT-TYPE
			SYNTAX Unsigned32
			MAX-ACCESS read-only
			STATUS current
			DESCRIPTION
				"Number of upstream channels in the
				upstream channel table."
			::= { pbcUpStreamMgmt 1 }
		
		-- 1.3.6.1.4.1.5987.2.2.1.3.2
		pbcCmtsIfUpstreamChannelTable OBJECT-TYPE
			SYNTAX SEQUENCE OF PbcCmtsIfUpstreamChannelEntry
			MAX-ACCESS not-accessible
			STATUS current
			DESCRIPTION
				"PBC-specific management objects associated with
				upstream channels."
			::= { pbcUpStreamMgmt 2 }
		
		-- 1.3.6.1.4.1.5987.2.2.1.3.2.1
		pbcCmtsIfUpstreamChannelEntry OBJECT-TYPE
			SYNTAX PbcCmtsIfUpstreamChannelEntry
			MAX-ACCESS not-accessible
			STATUS current
			DESCRIPTION
				"PBC extended US management objects for one US channel."
			INDEX { ifIndex }
			::= { pbcCmtsIfUpstreamChannelTable 1 }
		
		PbcCmtsIfUpstreamChannelEntry ::=
			SEQUENCE { 
				pbcCmtsIfUpstreamPort
					Integer32,
				pbcCmtsIfUpstreamOperMode
					INTEGER,
				pbcCmtsIfUpstreamCmdRcvdPwr
					TenthdBmV,
				pbcCmtsIfUpstreamPowerLevel
					TenthdBmV,
				pbcCmtsIfUpstreamMER
					TenthdB,
				pbcCmtsIfUpstreamHcsErrors
					Counter32,
				pbcCmtsIfUpstreamCrcErrors
					Counter32,
				pbcCmtsIfUpstreamCER
					Gauge32,
				pbcCmtsIfUpstreamCmTotal
					Unsigned32,
				pbcCmtsIfUpstreamCmRangeAborted
					Unsigned32,
				pbcCmtsIfUpstreamCmRanging
					Unsigned32,
				pbcCmtsIfUpstreamCmRangingComplete
					Unsigned32,
				pbcCmtsIfUpstreamCmIpComplete
					Unsigned32,
				pbcCmtsIfUpstreamCmRegistered
					Unsigned32,
				pbcCmtsIfUpstreamCmRogue
					Unsigned32
			 }

		-- 1.3.6.1.4.1.5987.2.2.1.3.2.1.1
		pbcCmtsIfUpstreamPort OBJECT-TYPE
			SYNTAX Integer32
			MAX-ACCESS read-write
			STATUS current
			DESCRIPTION
				"Associates the upstream channel with one
				of the physical upstream cable connectors.
				A value of -1 indicates that the channel
				currently is not associated with any port."
			::= { pbcCmtsIfUpstreamChannelEntry 1 }
		
		-- 1.3.6.1.4.1.5987.2.2.1.3.2.1.2
		pbcCmtsIfUpstreamOperMode OBJECT-TYPE
			SYNTAX INTEGER
				{
				available(1),
				standby(2),
				inUse(3),
				scanning(4),
				unlicensed(5)
				}
			MAX-ACCESS read-write
			STATUS current
			DESCRIPTION
				"Controls the usage of this channel as follows:
				
				1 = available (for use)
				2 = standby (for redundancy purposes)
				3 = inUse (channel is configured for data)
				4 = scanning (doing dedicated spectral analysis)
				5 = unlicensed (a 'key' is required to access the channel)
				"
			::= { pbcCmtsIfUpstreamChannelEntry 2 }
		
		-- 1.3.6.1.4.1.5987.2.2.1.3.2.1.3
		pbcCmtsIfUpstreamCmdRcvdPwr OBJECT-TYPE
			SYNTAX TenthdBmV
			MAX-ACCESS read-write
			STATUS current
			DESCRIPTION
				"Commanded received power."
			DEFVAL { 0 }
			::= { pbcCmtsIfUpstreamChannelEntry 3 }
		
		-- 1.3.6.1.4.1.5987.2.2.1.3.2.1.4
		pbcCmtsIfUpstreamPowerLevel OBJECT-TYPE
			SYNTAX TenthdBmV
			MAX-ACCESS read-only
			STATUS current
			DESCRIPTION
				"Upstream's sample-based measured received signal power."
			::= { pbcCmtsIfUpstreamChannelEntry 4 }
		
		-- 1.3.6.1.4.1.5987.2.2.1.3.2.1.5
		pbcCmtsIfUpstreamMER OBJECT-TYPE
			SYNTAX TenthdB
			MAX-ACCESS read-only
			STATUS current
			DESCRIPTION
				"Upstream channel's modulation error ratio expressed in dB."
			::= { pbcCmtsIfUpstreamChannelEntry 5 }
		
		-- 1.3.6.1.4.1.5987.2.2.1.3.2.1.6
		pbcCmtsIfUpstreamHcsErrors OBJECT-TYPE
			SYNTAX Counter32
			MAX-ACCESS read-only
			STATUS current
			DESCRIPTION
				"Channel's HCS errors detected."
			::= { pbcCmtsIfUpstreamChannelEntry 6 }
		
		-- 1.3.6.1.4.1.5987.2.2.1.3.2.1.7
		pbcCmtsIfUpstreamCrcErrors OBJECT-TYPE
			SYNTAX Counter32
			MAX-ACCESS read-only
			STATUS current
			DESCRIPTION
				"CRC errors detected on this channel."
			::= { pbcCmtsIfUpstreamChannelEntry 7 }
		
		-- 1.3.6.1.4.1.5987.2.2.1.3.2.1.8
		pbcCmtsIfUpstreamCER OBJECT-TYPE
			SYNTAX Gauge32 (0..100)
			MAX-ACCESS read-only
			STATUS current
			DESCRIPTION
				"Percentage of codewords that had unrecoverable errors."
			::= { pbcCmtsIfUpstreamChannelEntry 8 }
		
		-- 1.3.6.1.4.1.5987.2.2.1.3.2.1.9
		pbcCmtsIfUpstreamCmTotal OBJECT-TYPE
			SYNTAX Unsigned32
			MAX-ACCESS read-only
			STATUS current
			DESCRIPTION
				"Total Number of CMs in this Upstream Channel."
			::= { pbcCmtsIfUpstreamChannelEntry 9 }
		
		-- 1.3.6.1.4.1.5987.2.2.1.3.2.1.10
		pbcCmtsIfUpstreamCmRangeAborted OBJECT-TYPE
			SYNTAX Unsigned32
			MAX-ACCESS read-only
			STATUS current
			DESCRIPTION
				"Total Number of CMs with Range Abort Status in this Upstream Channel."
			::= { pbcCmtsIfUpstreamChannelEntry 10 }
		
		-- 1.3.6.1.4.1.5987.2.2.1.3.2.1.11
		pbcCmtsIfUpstreamCmRanging OBJECT-TYPE
			SYNTAX Unsigned32
			MAX-ACCESS read-only
			STATUS current
			DESCRIPTION
				"Total Number of Ranging CMs in this Upstream Channel."
			::= { pbcCmtsIfUpstreamChannelEntry 11 }
		
		-- 1.3.6.1.4.1.5987.2.2.1.3.2.1.12
		pbcCmtsIfUpstreamCmRangingComplete OBJECT-TYPE
			SYNTAX Unsigned32
			MAX-ACCESS read-only
			STATUS current
			DESCRIPTION
				"Total Number of CMs with Ranging Complete Status in this Upstream Channel."
			::= { pbcCmtsIfUpstreamChannelEntry 12 }
		
		-- 1.3.6.1.4.1.5987.2.2.1.3.2.1.13
		pbcCmtsIfUpstreamCmIpComplete OBJECT-TYPE
			SYNTAX Unsigned32
			MAX-ACCESS read-only
			STATUS current
			DESCRIPTION
				"Total Number of CMs with IP Complete Status in this Upstream Channel."
			::= { pbcCmtsIfUpstreamChannelEntry 13 }
		
		-- 1.3.6.1.4.1.5987.2.2.1.3.2.1.14
		pbcCmtsIfUpstreamCmRegistered OBJECT-TYPE
			SYNTAX Unsigned32
			MAX-ACCESS read-only
			STATUS current
			DESCRIPTION
				"Total Number of Registered CMs in this Upstream Channel."
			::= { pbcCmtsIfUpstreamChannelEntry 14 }
		
		-- 1.3.6.1.4.1.5987.2.2.1.3.2.1.15
		pbcCmtsIfUpstreamCmRogue OBJECT-TYPE
			SYNTAX Unsigned32
			MAX-ACCESS read-only
			STATUS current
			DESCRIPTION
				"Total Number of Rogue CMs in this Upstream Channel."
			::= { pbcCmtsIfUpstreamChannelEntry 15 }
		
		-- 1.3.6.1.4.1.5987.2.2.1.4
		pbcMacMgmt OBJECT IDENTIFIER ::= { pbcCmtsIfMibExtendedObjects 4 }
		
		-- 1.3.6.1.4.1.5987.2.2.1.4.1
		pbcCmtsIfMacTable OBJECT-TYPE
			SYNTAX SEQUENCE OF PbcCmtsIfMacEntry
			MAX-ACCESS not-accessible
			STATUS current
			DESCRIPTION
				"Description."
			::= { pbcMacMgmt 1 }
		
		-- 1.3.6.1.4.1.5987.2.2.1.4.1.1
		pbcCmtsIfMacEntry OBJECT-TYPE
			SYNTAX PbcCmtsIfMacEntry
			MAX-ACCESS not-accessible
			STATUS current
			DESCRIPTION
				"Description."
			INDEX { ifIndex }
			::= { pbcCmtsIfMacTable 1 }
		
		PbcCmtsIfMacEntry ::=
			SEQUENCE { 
				pbcCmtsIfMacCmTotal
					Unsigned32,
				pbcCmtsIfMacCmRangeAborted
					Unsigned32,
				pbcCmtsIfMacCmRanging
					Unsigned32,
				pbcCmtsIfMacCmRangingComplete
					Unsigned32,
				pbcCmtsIfMacCmIpComplete
					Unsigned32,
				pbcCmtsIfMacCmRegistered
					Unsigned32,
				pbcCmtsIfMacCmRogue
					Unsigned32
			 }

		-- 1.3.6.1.4.1.5987.2.2.1.4.1.1.1
		pbcCmtsIfMacCmTotal OBJECT-TYPE
			SYNTAX Unsigned32
			MAX-ACCESS read-only
			STATUS current
			DESCRIPTION
				"Number of CMs in this MAC domain."
			::= { pbcCmtsIfMacEntry 1 }
		
		-- 1.3.6.1.4.1.5987.2.2.1.4.1.1.2
		pbcCmtsIfMacCmRangeAborted OBJECT-TYPE
			SYNTAX Unsigned32
			MAX-ACCESS read-only
			STATUS current
			DESCRIPTION
				"Number of CMs with Ranging aborted status in this MAC domain."
			::= { pbcCmtsIfMacEntry 2 }
		
		-- 1.3.6.1.4.1.5987.2.2.1.4.1.1.3
		pbcCmtsIfMacCmRanging OBJECT-TYPE
			SYNTAX Unsigned32
			MAX-ACCESS read-only
			STATUS current
			DESCRIPTION
				"Number of CMs with Ranging status in this MAC domain."
			::= { pbcCmtsIfMacEntry 3 }
		
		-- 1.3.6.1.4.1.5987.2.2.1.4.1.1.4
		pbcCmtsIfMacCmRangingComplete OBJECT-TYPE
			SYNTAX Unsigned32
			MAX-ACCESS read-only
			STATUS current
			DESCRIPTION
				"Number of Ranging completed CMs in this MAC domain."
			::= { pbcCmtsIfMacEntry 4 }
		
		-- 1.3.6.1.4.1.5987.2.2.1.4.1.1.5
		pbcCmtsIfMacCmIpComplete OBJECT-TYPE
			SYNTAX Unsigned32
			MAX-ACCESS read-only
			STATUS current
			DESCRIPTION
				"Number of CMs with IP Complete status in this MAC domain."
			::= { pbcCmtsIfMacEntry 5 }
		
		-- 1.3.6.1.4.1.5987.2.2.1.4.1.1.6
		pbcCmtsIfMacCmRegistered OBJECT-TYPE
			SYNTAX Unsigned32
			MAX-ACCESS read-only
			STATUS current
			DESCRIPTION
				"Number of Registered CMs in this MAC domain."
			::= { pbcCmtsIfMacEntry 6 }
		
		-- 1.3.6.1.4.1.5987.2.2.1.4.1.1.7
		pbcCmtsIfMacCmRogue OBJECT-TYPE
			SYNTAX Unsigned32
			MAX-ACCESS read-only
			STATUS current
			DESCRIPTION
				"Number of Rogue CMs in this MAC domain."
			::= { pbcCmtsIfMacEntry 7 }
		
		-- 1.3.6.1.4.1.5987.2.2.1.5
		pbcCmtsCmMgmt OBJECT IDENTIFIER ::= { pbcCmtsIfMibExtendedObjects 5 }
		
		-- 1.3.6.1.4.1.5987.2.2.1.5.1
		pbcCmtsCmStatusTable OBJECT-TYPE
			SYNTAX SEQUENCE OF PbcCmtsCmStatusEntry
			MAX-ACCESS not-accessible
			STATUS current
			DESCRIPTION
				"Extention of docsIfCmtsCmStatusTable.
				"
			::= { pbcCmtsCmMgmt 1 }
		
		-- 1.3.6.1.4.1.5987.2.2.1.5.1.1
		pbcCmtsCmStatusEntry OBJECT-TYPE
			SYNTAX PbcCmtsCmStatusEntry
			MAX-ACCESS not-accessible
			STATUS current
			DESCRIPTION
				"Extention of docsIfCmtsCmStatusEntry."
			AUGMENTS { docsIfCmtsCmStatusEntry }
			::= { pbcCmtsCmStatusTable 1 }
		
		PbcCmtsCmStatusEntry ::=
			SEQUENCE { 
				pbcCmtsCmStatusFirstOnline
					DateAndTime,
				pbcCmtsCmStatusLastOnline
					DateAndTime,
				pbcCmtsCmStatusTimesOnline
					Counter32,
				pbcCmtsCmStatusPercentOnline
					Unsigned32,
				pbcCmtsCmStatusMinOnline
					TimeInterval,
				pbcCmtsCmStatusMaxOnline
					TimeInterval,
				pbcCmtsCmStatusAvgOnline
					TimeInterval,
				pbcCmtsCmStatusMinOffline
					TimeInterval,
				pbcCmtsCmStatusMaxOffline
					TimeInterval,
				pbcCmtsCmStatusAvgOffline
					TimeInterval
			 }

		-- 1.3.6.1.4.1.5987.2.2.1.5.1.1.1
		pbcCmtsCmStatusFirstOnline OBJECT-TYPE
			SYNTAX DateAndTime
			MAX-ACCESS read-only
			STATUS current
			DESCRIPTION
				"Date and Time when CM was seen by the system for the first time."
			::= { pbcCmtsCmStatusEntry 1 }
		
		-- 1.3.6.1.4.1.5987.2.2.1.5.1.1.2
		pbcCmtsCmStatusLastOnline OBJECT-TYPE
			SYNTAX DateAndTime
			MAX-ACCESS read-only
			STATUS current
			DESCRIPTION
				"Date and Time when the CM came online recently."
			::= { pbcCmtsCmStatusEntry 2 }
		
		-- 1.3.6.1.4.1.5987.2.2.1.5.1.1.3
		pbcCmtsCmStatusTimesOnline OBJECT-TYPE
			SYNTAX Counter32
			MAX-ACCESS read-only
			STATUS current
			DESCRIPTION
				"Number of times the CM came online."
			::= { pbcCmtsCmStatusEntry 3 }
		
		-- 1.3.6.1.4.1.5987.2.2.1.5.1.1.4
		pbcCmtsCmStatusPercentOnline OBJECT-TYPE
			SYNTAX Unsigned32 (0..100)
			MAX-ACCESS read-only
			STATUS current
			DESCRIPTION
				"Percent of time for the CM has been online."
			::= { pbcCmtsCmStatusEntry 4 }
		
		-- 1.3.6.1.4.1.5987.2.2.1.5.1.1.5
		pbcCmtsCmStatusMinOnline OBJECT-TYPE
			SYNTAX TimeInterval
			MAX-ACCESS read-only
			STATUS current
			DESCRIPTION
				"Minimum time interval the CM was online."
			::= { pbcCmtsCmStatusEntry 5 }
		
		-- 1.3.6.1.4.1.5987.2.2.1.5.1.1.6
		pbcCmtsCmStatusMaxOnline OBJECT-TYPE
			SYNTAX TimeInterval
			MAX-ACCESS read-only
			STATUS current
			DESCRIPTION
				"Maximum time interval the CM was online."
			::= { pbcCmtsCmStatusEntry 6 }
		
		-- 1.3.6.1.4.1.5987.2.2.1.5.1.1.7
		pbcCmtsCmStatusAvgOnline OBJECT-TYPE
			SYNTAX TimeInterval
			MAX-ACCESS read-only
			STATUS current
			DESCRIPTION
				"Average time interval the CM was online."
			::= { pbcCmtsCmStatusEntry 7 }
		
		-- 1.3.6.1.4.1.5987.2.2.1.5.1.1.8
		pbcCmtsCmStatusMinOffline OBJECT-TYPE
			SYNTAX TimeInterval
			MAX-ACCESS read-only
			STATUS current
			DESCRIPTION
				"Minimum time interval the CM was offline."
			::= { pbcCmtsCmStatusEntry 8 }
		
		-- 1.3.6.1.4.1.5987.2.2.1.5.1.1.9
		pbcCmtsCmStatusMaxOffline OBJECT-TYPE
			SYNTAX TimeInterval
			MAX-ACCESS read-only
			STATUS current
			DESCRIPTION
				"Maximum time interval the CM was offline."
			::= { pbcCmtsCmStatusEntry 9 }
		
		-- 1.3.6.1.4.1.5987.2.2.1.5.1.1.10
		pbcCmtsCmStatusAvgOffline OBJECT-TYPE
			SYNTAX TimeInterval
			MAX-ACCESS read-only
			STATUS current
			DESCRIPTION
				"Average time interval the CM was offline."
			::= { pbcCmtsCmStatusEntry 10 }
		
		-- 1.3.6.1.4.1.5987.2.2.1.5.2
		pbcCmtsRogueCmTable OBJECT-TYPE
			SYNTAX SEQUENCE OF PbcCmtsRogueCmEntry
			MAX-ACCESS not-accessible
			STATUS current
			DESCRIPTION
				"Contain information associated with all the Rogue Cable Modems detected by the CMTS."
			::= { pbcCmtsCmMgmt 2 }
		
		-- 1.3.6.1.4.1.5987.2.2.1.5.2.1
		pbcCmtsRogueCmEntry OBJECT-TYPE
			SYNTAX PbcCmtsRogueCmEntry
			MAX-ACCESS not-accessible
			STATUS current
			DESCRIPTION
				"An entry would be created for every rogue Cable Modem detected by CMTS."
			INDEX { pbcCmtsRogueCmMacAddress }
			::= { pbcCmtsRogueCmTable 1 }
		
		PbcCmtsRogueCmEntry ::=
			SEQUENCE { 
				pbcCmtsRogueCmMacAddress
					MacAddress,
				pbcCmtsRogueCmIpAddress
					IpAddress,
				pbcCmtsRogueCmPtr
					Integer32,
				pbcCmtsRogueCmType
					INTEGER,
				pbcCmtsRogueCmFirstActive
					DateAndTime,
				pbcCmtsRogueCmLastActive
					DateAndTime
			 }

		-- 1.3.6.1.4.1.5987.2.2.1.5.2.1.1
		pbcCmtsRogueCmMacAddress OBJECT-TYPE
			SYNTAX MacAddress
			MAX-ACCESS read-only
			STATUS current
			DESCRIPTION
				"MAC Address of the Rogue CM."
			::= { pbcCmtsRogueCmEntry 1 }
		
		-- 1.3.6.1.4.1.5987.2.2.1.5.2.1.2
		pbcCmtsRogueCmIpAddress OBJECT-TYPE
			SYNTAX IpAddress
			MAX-ACCESS read-only
			STATUS current
			DESCRIPTION
				"IP Address of the Rogue CM."
			::= { pbcCmtsRogueCmEntry 2 }
		
		-- 1.3.6.1.4.1.5987.2.2.1.5.2.1.3
		pbcCmtsRogueCmPtr OBJECT-TYPE
			SYNTAX Integer32
			MAX-ACCESS read-only
			STATUS current
			DESCRIPTION
				"An row index into docsIfCmtsCmStatusTable. When queried with the correct instance value (e.g. a CM's MAC address), returns the index in docsIfCmtsCmStatusTable which represents that CM."
			::= { pbcCmtsRogueCmEntry 3 }
		
		-- 1.3.6.1.4.1.5987.2.2.1.5.2.1.4
		pbcCmtsRogueCmType OBJECT-TYPE
			SYNTAX INTEGER
				{
				unProvisioned(1),
				rigged(2),
				configured(3)
				}
			MAX-ACCESS read-only
			STATUS current
			DESCRIPTION
				"Type of the Rogue CM. Valid Values are unProvisioned (1), rigged (2), configured (3)."
			::= { pbcCmtsRogueCmEntry 4 }
		
		-- 1.3.6.1.4.1.5987.2.2.1.5.2.1.5
		pbcCmtsRogueCmFirstActive OBJECT-TYPE
			SYNTAX DateAndTime
			MAX-ACCESS read-only
			STATUS current
			DESCRIPTION
				"Date and Time when CM was seen by the system for the first time."
			::= { pbcCmtsRogueCmEntry 5 }
		
		-- 1.3.6.1.4.1.5987.2.2.1.5.2.1.6
		pbcCmtsRogueCmLastActive OBJECT-TYPE
			SYNTAX DateAndTime
			MAX-ACCESS read-only
			STATUS current
			DESCRIPTION
				"Date and Time when the last time an IM was seen from this CM. The LastActive tells the latest time when CM was detected as rogue and put to rest."
			::= { pbcCmtsRogueCmEntry 6 }
		
		-- 1.3.6.1.4.1.5987.2.2.2
		pbcCmtsCableSpectrumManagement OBJECT IDENTIFIER ::= { pbcCmts 2 }
		
		-- 1.3.6.1.4.1.5987.2.2.2.2
		pbcCmtsSpectrumAnalysisMgmt OBJECT IDENTIFIER ::= { pbcCmtsCableSpectrumManagement 2 }
		
		-- 1.3.6.1.4.1.5987.2.2.2.2.1
		pbcCmtsSpectrumAnalysisObjects OBJECT IDENTIFIER ::= { pbcCmtsSpectrumAnalysisMgmt 1 }
		
		-- 1.3.6.1.4.1.5987.2.2.2.2.1.1
		pbcSpectrumAnalysisRFInputTable OBJECT-TYPE
			SYNTAX SEQUENCE OF PbcSpectrumAnalysisRFInputEntry
			MAX-ACCESS not-accessible
			STATUS current
			DESCRIPTION
				"There is an entry in this table for each
				upstream input connector on each DOCSIS module
				in the CMTS.  Each port is uniquely identified within
				the CMTS by its pbcCardIfPortIndex value.
				
				This index object is defined under the generic
				chassis management section of the PBC private
				MIB tree."
			::= { pbcCmtsSpectrumAnalysisObjects 1 }
		
		-- 1.3.6.1.4.1.5987.2.2.2.2.1.1.1
		pbcSpectrumAnalysisRFInputEntry OBJECT-TYPE
			SYNTAX PbcSpectrumAnalysisRFInputEntry
			MAX-ACCESS not-accessible
			STATUS current
			DESCRIPTION
				"An entry in the RF monitoring input (port) table."
			INDEX { pbcCardIfPortIndex }
			::= { pbcSpectrumAnalysisRFInputTable 1 }
		
		PbcSpectrumAnalysisRFInputEntry ::=
			SEQUENCE { 
				pbcSpectrumAnalysisEnable
					TruthValue,
				pbcSpectrumAnalysisCmdStatus
					INTEGER,
				pbcSpectrumAnalysisIntegrationLen
					Unsigned32,
				pbcSpectrumAnalysisFreqStep
					INTEGER,
				pbcSpectrumAnalysisFreqMin
					Unsigned32,
				pbcSpectrumAnalysisFreqMax
					Unsigned32,
				pbcSpectrumAnalysisArraySize
					Unsigned32,
				pbcSpectrumAnalysisActiveArray
					Unsigned32
			 }

		-- 1.3.6.1.4.1.5987.2.2.2.2.1.1.1.1
		pbcSpectrumAnalysisEnable OBJECT-TYPE
			SYNTAX TruthValue
			MAX-ACCESS read-write
			STATUS current
			DESCRIPTION
				"True ('1') enables spectrum estimation.  This
				should be set only after setting the other
				parameters affecting the scan.  After setting
				this 'true', pbcSpectrumAnalysisCmdStatus will
				reflect initial and, ultimately, final status
				of the sweep attempt."
			DEFVAL { false }
			::= { pbcSpectrumAnalysisRFInputEntry 1 }
		
		-- 1.3.6.1.4.1.5987.2.2.2.2.1.1.1.2
		pbcSpectrumAnalysisCmdStatus OBJECT-TYPE
			SYNTAX INTEGER
				{
				available(1),
				scanInProgress(2),
				complete(3),
				generalFailure(4),
				noResources(5)
				}
			MAX-ACCESS read-write
			STATUS current
			DESCRIPTION
				"Result of pbcSpectrumAnalysisEnable command."
			DEFVAL { available }
			::= { pbcSpectrumAnalysisRFInputEntry 2 }
		
		-- 1.3.6.1.4.1.5987.2.2.2.2.1.1.1.3
		pbcSpectrumAnalysisIntegrationLen OBJECT-TYPE
			SYNTAX Unsigned32
			MAX-ACCESS read-write
			STATUS current
			DESCRIPTION
				"This specifies the number of estimates over
				which the peak of the noise power is
				calculated."
			DEFVAL { 1 }
			::= { pbcSpectrumAnalysisRFInputEntry 3 }
		
		-- 1.3.6.1.4.1.5987.2.2.2.2.1.1.1.4
		pbcSpectrumAnalysisFreqStep OBJECT-TYPE
			SYNTAX INTEGER
				{
				kHz20(1),
				kHz40(2),
				kHz80(3),
				kHz160(4)
				}
			MAX-ACCESS read-write
			STATUS current
			DESCRIPTION
				"The frequency step for scanning which defines
				the frequency resolution.  The choices are:
				20KHz, 40KHz, 80KHz and 160KHz."
			DEFVAL { kHz160 }
			::= { pbcSpectrumAnalysisRFInputEntry 4 }
		
		-- 1.3.6.1.4.1.5987.2.2.2.2.1.1.1.5
		pbcSpectrumAnalysisFreqMin OBJECT-TYPE
			SYNTAX Unsigned32
			MAX-ACCESS read-write
			STATUS current
			DESCRIPTION
				"The low end of the frequency range being
				scanned.  The lowest legal value, per both
				the DOCSIS and Euro-DOCSIS standards, is
				5MHz."
			DEFVAL { 5000000 }
			::= { pbcSpectrumAnalysisRFInputEntry 5 }
		
		-- 1.3.6.1.4.1.5987.2.2.2.2.1.1.1.6
		pbcSpectrumAnalysisFreqMax OBJECT-TYPE
			SYNTAX Unsigned32
			MAX-ACCESS read-write
			STATUS current
			DESCRIPTION
				"Top end of the frequency range being scanned.
				For DOCSIS, the maximum is 42MHz and for
				Euro-DOCSIS it is 65MHz."
			DEFVAL { 42000000 }
			::= { pbcSpectrumAnalysisRFInputEntry 6 }
		
		-- 1.3.6.1.4.1.5987.2.2.2.2.1.1.1.7
		pbcSpectrumAnalysisArraySize OBJECT-TYPE
			SYNTAX Unsigned32 (2..32)
			MAX-ACCESS read-write
			STATUS current
			DESCRIPTION
				"This variable holds/specifies the number of scan
				data tables to be allocated to this particular
				scan instance.  The size of each table and,
				therefore, the total amount of buffer space
				required is determined by the other scan parameters.
				If the agent is unable to allocate that amount of
				space, a status of 'noResources' will be returned
				in pbcSpectrumAnalysisCmdStatus following the
				setting of pbcSpectrumAnalysisEnable.
				
				If successful, this becomes the total number of
				table entries in pbcSpectrumAnalysisArrayIndexTable.
				
				A size of '2' is the absolute minimum to permit the
				agent to fill one table with data points while the
				management application is 'draining' the other."
			::= { pbcSpectrumAnalysisRFInputEntry 7 }
		
		-- 1.3.6.1.4.1.5987.2.2.2.2.1.1.1.8
		pbcSpectrumAnalysisActiveArray OBJECT-TYPE
			SYNTAX Unsigned32
			MAX-ACCESS read-only
			STATUS current
			DESCRIPTION
				"Contains the pbcSpectrumAnalysisArrayIndex number
				of the data table currently being filled with
				spectral data points."
			DEFVAL { 0 }
			::= { pbcSpectrumAnalysisRFInputEntry 8 }
		
		-- 1.3.6.1.4.1.5987.2.2.2.2.1.2
		pbcSpectrumAnalysisArrayIndexTable OBJECT-TYPE
			SYNTAX SEQUENCE OF PbcSpectrumAnalysisArrayIndexEntry
			MAX-ACCESS not-accessible
			STATUS current
			DESCRIPTION
				"The table serves as an index, with status, into
				the pbcSpectrumAnalysisDataTable, thus uniquely
				identifying all of the data points which constitute
				one spectral sweep."
			::= { pbcCmtsSpectrumAnalysisObjects 2 }
		
		-- 1.3.6.1.4.1.5987.2.2.2.2.1.2.1
		pbcSpectrumAnalysisArrayIndexEntry OBJECT-TYPE
			SYNTAX PbcSpectrumAnalysisArrayIndexEntry
			MAX-ACCESS not-accessible
			STATUS current
			DESCRIPTION
				"An entry in the pbcSpectrumAnalysisArrayIndexTable."
			INDEX { pbcCardIfPortIndex, pbcSpectrumAnalysisArrayIndex }
			::= { pbcSpectrumAnalysisArrayIndexTable 1 }
		
		PbcSpectrumAnalysisArrayIndexEntry ::=
			SEQUENCE { 
				pbcSpectrumAnalysisArrayIndex
					Unsigned32,
				pbcSpectrumAnalysisArrayStatus
					INTEGER,
				pbcSpectrumAnalysisArrayScanStart
					DateAndTime,
				pbcSpectrumAnalysisArrayScanStop
					DateAndTime
			 }

		-- 1.3.6.1.4.1.5987.2.2.2.2.1.2.1.1
		pbcSpectrumAnalysisArrayIndex OBJECT-TYPE
			SYNTAX Unsigned32
			MAX-ACCESS read-only
			STATUS current
			DESCRIPTION
				"Index number of this data table."
			::= { pbcSpectrumAnalysisArrayIndexEntry 1 }
		
		-- 1.3.6.1.4.1.5987.2.2.2.2.1.2.1.2
		pbcSpectrumAnalysisArrayStatus OBJECT-TYPE
			SYNTAX INTEGER
				{
				available(1),
				scanning(2),
				scanComplete(3),
				abort(4)
				}
			MAX-ACCESS read-write
			STATUS current
			DESCRIPTION
				"The operational status of this data table.  The
				management application which is reading the
				spectrum monitoring data should, after reading
				all the data entries associated with this array
				(table),set this variable back to 'available'."
			DEFVAL { available }
			::= { pbcSpectrumAnalysisArrayIndexEntry 2 }
		
		-- 1.3.6.1.4.1.5987.2.2.2.2.1.2.1.3
		pbcSpectrumAnalysisArrayScanStart OBJECT-TYPE
			SYNTAX DateAndTime
			MAX-ACCESS read-only
			STATUS current
			DESCRIPTION
				"The date and time when this table's spectral
				sweep began."
			::= { pbcSpectrumAnalysisArrayIndexEntry 3 }
		
		-- 1.3.6.1.4.1.5987.2.2.2.2.1.2.1.4
		pbcSpectrumAnalysisArrayScanStop OBJECT-TYPE
			SYNTAX DateAndTime
			MAX-ACCESS read-only
			STATUS current
			DESCRIPTION
				"The date and time when this table's spectral
				sweep was completed or stopped for some other
				reason."
			::= { pbcSpectrumAnalysisArrayIndexEntry 4 }
		
		-- 1.3.6.1.4.1.5987.2.2.2.2.1.3
		pbcSpectrumAnalysisDataTable OBJECT-TYPE
			SYNTAX SEQUENCE OF PbcSpectrumAnalysisDataEntry
			MAX-ACCESS not-accessible
			STATUS current
			DESCRIPTION
				"The Frequency-Power tuples are stored in
				this table.  The maximum number of elements
				is determined by the size of the frequency
				step and the RF range to be scanned and can
				therefore not exceed 1850."
			::= { pbcCmtsSpectrumAnalysisObjects 3 }
		
		-- 1.3.6.1.4.1.5987.2.2.2.2.1.3.1
		pbcSpectrumAnalysisDataEntry OBJECT-TYPE
			SYNTAX PbcSpectrumAnalysisDataEntry
			MAX-ACCESS not-accessible
			STATUS current
			DESCRIPTION
				"An entry in the spectrum analysis data table."
			INDEX { pbcCardIfPortIndex, pbcSpectrumAnalysisArrayIndex, pbcSpectrumAnalysisFrequency }
			::= { pbcSpectrumAnalysisDataTable 1 }
		
		PbcSpectrumAnalysisDataEntry ::=
			SEQUENCE { 
				pbcSpectrumAnalysisFrequency
					Unsigned32,
				pbcSpectrumAnalysisPower
					OneHundredthdBmVPerHz
			 }

		-- 1.3.6.1.4.1.5987.2.2.2.2.1.3.1.1
		pbcSpectrumAnalysisFrequency OBJECT-TYPE
			SYNTAX Unsigned32
			MAX-ACCESS read-only
			STATUS current
			DESCRIPTION
				"The frequency that was sampled."
			::= { pbcSpectrumAnalysisDataEntry 1 }
		
		-- 1.3.6.1.4.1.5987.2.2.2.2.1.3.1.2
		pbcSpectrumAnalysisPower OBJECT-TYPE
			SYNTAX OneHundredthdBmVPerHz
			MAX-ACCESS read-only
			STATUS current
			DESCRIPTION
				"Measured power in hundredths of a dBmV/Hz."
			::= { pbcSpectrumAnalysisDataEntry 2 }
		
		-- 1.3.6.1.4.1.5987.2.2.2.2.2
		pbcCmtsSpectrumAnalysisNotificationEnables OBJECT IDENTIFIER ::= { pbcCmtsSpectrumAnalysisMgmt 2 }
		
		-- 1.3.6.1.4.1.5987.2.2.2.2.2.1
		pbcCmtsSpectrumAnalysisNotificationTable OBJECT-TYPE
			SYNTAX SEQUENCE OF PbcCmtsSpectrumAnalysisNotificationEntry
			MAX-ACCESS not-accessible
			STATUS current
			DESCRIPTION
				"Allows specific 'sweep complete' trap recipients to be
				specified on a per-port basis."
			::= { pbcCmtsSpectrumAnalysisNotificationEnables 1 }
		
		-- 1.3.6.1.4.1.5987.2.2.2.2.2.1.1
		pbcCmtsSpectrumAnalysisNotificationEntry OBJECT-TYPE
			SYNTAX PbcCmtsSpectrumAnalysisNotificationEntry
			MAX-ACCESS not-accessible
			STATUS current
			DESCRIPTION
				"Contains the IP address of the desired trap recipient
				of 'sweep complete' notifications generated by active
				spectral monitoring on a specific US port."
			INDEX { pbcCardIfPortIndex }
			::= { pbcCmtsSpectrumAnalysisNotificationTable 1 }
		
		PbcCmtsSpectrumAnalysisNotificationEntry ::=
			SEQUENCE { 
				pbcCmtsSpectrumAnalysisEnableSweepNotification
					TruthValue,
				pbcSweepNotificationRecipient
					IpAddress,
				pbcSweepNotificationRecipientPort
					Integer32,
				pbcCmtsSpectrumAnalysisNotificationType
					INTEGER
			 }

		-- 1.3.6.1.4.1.5987.2.2.2.2.2.1.1.1
		pbcCmtsSpectrumAnalysisEnableSweepNotification OBJECT-TYPE
			SYNTAX TruthValue
			MAX-ACCESS read-write
			STATUS current
			DESCRIPTION
				"True ('1') enables 'sweep complete' notifications
				so that the receiver knows it may/should retrieve
				the current spectral data points."
			DEFVAL { false }
			::= { pbcCmtsSpectrumAnalysisNotificationEntry 1 }
		
		-- 1.3.6.1.4.1.5987.2.2.2.2.2.1.1.2
		pbcSweepNotificationRecipient OBJECT-TYPE
			SYNTAX IpAddress
			MAX-ACCESS read-write
			STATUS current
			DESCRIPTION
				"The IP address of the management station wishing to
				receive the 'sweep complete' notifications from this
				system for this monitored port."
			::= { pbcCmtsSpectrumAnalysisNotificationEntry 2 }
		
		-- 1.3.6.1.4.1.5987.2.2.2.2.2.1.1.3
		pbcSweepNotificationRecipientPort OBJECT-TYPE
			SYNTAX Integer32 (0..65535)
			MAX-ACCESS read-write
			STATUS current
			DESCRIPTION
				"Port that recipient is listening on for notifications."
			DEFVAL { 162 }
			::= { pbcCmtsSpectrumAnalysisNotificationEntry 3 }
		
		-- 1.3.6.1.4.1.5987.2.2.2.2.2.1.1.4
		pbcCmtsSpectrumAnalysisNotificationType OBJECT-TYPE
			SYNTAX INTEGER
				{
				snmpv2c(1),
				snmpv3(2)
				}
			MAX-ACCESS read-write
			STATUS current
			DESCRIPTION
				"Selects between SNMPv2c and SNMPv3 traps."
			::= { pbcCmtsSpectrumAnalysisNotificationEntry 4 }
		
		-- 1.3.6.1.4.1.5987.2.2.2.2.3
		pbcCmtsSpectrumAnalysisNotificationPrefix OBJECT IDENTIFIER ::= { pbcCmtsSpectrumAnalysisMgmt 3 }
		
		-- 1.3.6.1.4.1.5987.2.2.2.2.3.1
		pbcCmtsSpectrumAnalysisNotifications OBJECT IDENTIFIER ::= { pbcCmtsSpectrumAnalysisNotificationPrefix 1 }
		

-- 1.3.6.1.4.1.5987.2.2.2.2.3.1.2
		pbcCardIfPortIndexID OBJECT-TYPE
			SYNTAX Integer32
			MAX-ACCESS accessible-for-notify
			STATUS current
			DESCRIPTION
				"Instance of the pbcCardIfPortIndex to be bound with the
				Trap/Notify PDU."
			::= { pbcCmtsSpectrumAnalysisNotifications 2 }
		
		-- 1.3.6.1.4.1.5987.2.2.2.2.3.1.3
		pbcSpectrumAnalysisArrayIndexID OBJECT-TYPE
			SYNTAX Integer32
			MAX-ACCESS accessible-for-notify
			STATUS current
			DESCRIPTION
				"Instance of the pbcSpectrumAnalysisArrayIndex to be bound with the
				Trap/Notify PDU."
			::= { pbcCmtsSpectrumAnalysisNotifications 3 }
		
		-- 1.3.6.1.4.1.5987.2.2.2.2.3.1.4
		pbcSpectrumAnalysisArrayStatusID OBJECT-TYPE
			SYNTAX Integer32
			MAX-ACCESS accessible-for-notify
			STATUS current
			DESCRIPTION
				"Instance of the pbcSpectrumAnalysisArrayStatus to be bound with the
				Trap/Notify PDU."
			::= { pbcCmtsSpectrumAnalysisNotifications 4 }


		-- 1.3.6.1.4.1.5987.2.2.2.2.3.1.1
		pbcCmtsSpectrumAnalysisSweepComplete NOTIFICATION-TYPE
			OBJECTS { pbcSpectrumAnalysisArrayIndexID, pbcCardIfPortIndexID, pbcSpectrumAnalysisArrayStatusID }
			STATUS current
			DESCRIPTION 
				"Denotes the conclusion, with status and data table
				identification, of an RF sweep operation."
			::= { pbcCmtsSpectrumAnalysisNotifications 1 }
		
		
		
		-- 1.3.6.1.4.1.5987.2.2.3
		pbcCmtsNotificationManagement OBJECT IDENTIFIER ::= { pbcCmts 3 }
		
		-- 1.3.6.1.4.1.5987.2.2.3.1
		pbcCmtsEventsEnable OBJECT-TYPE
			SYNTAX TruthValue
			MAX-ACCESS read-write
			STATUS current
			DESCRIPTION
				"Enables or disables vendor specific event generation."
			DEFVAL { true }
			::= { pbcCmtsNotificationManagement 1 }
		
		-- 1.3.6.1.4.1.5987.2.2.3.2
		pbcCmtsNotificationsControl OBJECT-TYPE
			SYNTAX BITS
				{
				envMon(0),
				chassis(1),
				software(2),
				access(3),
				config(4),
				dataPath(5),
				rfInterface(6),
				flapList(7),
				debug(8),
				cmStateChange(9)
				}
			MAX-ACCESS read-write
			STATUS current
			DESCRIPTION
				"A '1' in a given bit position enables that class of notifications."
			::= { pbcCmtsNotificationManagement 2 }
		
		-- 1.3.6.1.4.1.5987.2.2.3.3
		pbcCmtsSystemNotifications OBJECT IDENTIFIER ::= { pbcCmtsNotificationManagement 3 }
		
		-- 1.3.6.1.4.1.5987.2.2.3.3.1
		pbcCmtsEnvMonNotification NOTIFICATION-TYPE
			OBJECTS { docsDevEvLevel, docsDevEvId, docsDevEvText }
			STATUS current
			DESCRIPTION 
				"Notifications generated by environmental monitoring."
			::= { pbcCmtsSystemNotifications 1 }
		
		-- 1.3.6.1.4.1.5987.2.2.3.3.2
		pbcCmtsChassisNotification NOTIFICATION-TYPE
			OBJECTS { docsDevEvLevel, docsDevEvId, docsDevEvText }
			STATUS current
			DESCRIPTION 
				"Chassis-related notifications."
			::= { pbcCmtsSystemNotifications 2 }
		
		-- 1.3.6.1.4.1.5987.2.2.3.3.3
		pbcCmtsSoftwareNotification NOTIFICATION-TYPE
			OBJECTS { docsDevEvLevel, docsDevEvId, docsDevEvText }
			STATUS current
			DESCRIPTION 
				"Notifications from the software management system."
			::= { pbcCmtsSystemNotifications 3 }
		
		-- 1.3.6.1.4.1.5987.2.2.3.3.4
		pbcCmtsAccessNotification NOTIFICATION-TYPE
			OBJECTS { docsDevEvLevel, docsDevEvId, docsDevEvText }
			STATUS current
			DESCRIPTION 
				"Access-related notifications."
			::= { pbcCmtsSystemNotifications 4 }
		
		-- 1.3.6.1.4.1.5987.2.2.3.3.5
		pbcCmtsConfigNotification NOTIFICATION-TYPE
			OBJECTS { docsDevEvLevel, docsDevEvId, docsDevEvText }
			STATUS current
			DESCRIPTION 
				"Notifications related to configuration changes."
			::= { pbcCmtsSystemNotifications 5 }
		
		-- 1.3.6.1.4.1.5987.2.2.3.3.6
		pbcCmtsDataPathNotification NOTIFICATION-TYPE
			OBJECTS { docsDevEvLevel, docsDevEvId, docsDevEvText }
			STATUS current
			DESCRIPTION 
				"Notifications related to datapath events."
			::= { pbcCmtsSystemNotifications 6 }
		
		-- 1.3.6.1.4.1.5987.2.2.3.3.7
		pbcCmtsRfInterfaceNotification NOTIFICATION-TYPE
			OBJECTS { docsDevEvLevel, docsDevEvId, docsDevEvText }
			STATUS current
			DESCRIPTION 
				"Notifications related to datapath events."
			::= { pbcCmtsSystemNotifications 7 }
		
		-- 1.3.6.1.4.1.5987.2.2.3.3.8
		pbcCmtsFlapListNotification NOTIFICATION-TYPE
			OBJECTS { docsDevEvLevel, docsDevEvId, docsDevEvText }
			STATUS current
			DESCRIPTION 
				"Notifications related to datapath events."
			::= { pbcCmtsSystemNotifications 8 }
		
		-- 1.3.6.1.4.1.5987.2.2.3.3.9
		pbcCmtsDebugNotification NOTIFICATION-TYPE
			OBJECTS { docsDevEvLevel, docsDevEvId, docsDevEvText }
			STATUS current
			DESCRIPTION 
				"Notifications generated for internal debugging. This can be enabled by 
				setting debug class of CMTS notifications."
			::= { pbcCmtsSystemNotifications 9 }
		
		-- 1.3.6.1.4.1.5987.2.2.3.3.10
		pbcCmtsCmStateChangeNotification NOTIFICATION-TYPE
			OBJECTS { docsDevEvLevel, docsDevEvId, docsDevEvText }
			STATUS current
			DESCRIPTION 
				"Notifications generated to track MODEM state. This event can be enabled 
				by setting cmStateChange bit of the CMTS Notification Control."
			::= { pbcCmtsSystemNotifications 10 }
		
		-- 1.3.6.1.4.1.5987.2.2.3.4
		pbcCmtsModemEventsEnable OBJECT-TYPE
			SYNTAX BITS
				{
				deRanging(0),
				registration(1)
				}
			MAX-ACCESS read-write
			STATUS current
			DESCRIPTION
				"Enables or disables Modem De-Ranging and Registration event 
				Generation."
			::= { pbcCmtsNotificationManagement 4 }
		
		-- 1.3.6.1.4.1.5987.2.2.4
		pbcCmtsConformance OBJECT IDENTIFIER ::= { pbcCmts 4 }
		
		-- 1.3.6.1.4.1.5987.2.2.4.1
		pbcCmtsGroups OBJECT IDENTIFIER ::= { pbcCmtsConformance 1 }
		
		-- 1.3.6.1.4.1.5987.2.2.4.1.1
		pbcCmtsGroup OBJECT-GROUP
			OBJECTS { pbcCmtsIfDownstreamNumEntries, pbcCmtsIfDownstreamIfTxPower, pbcCmtsIfUpstreamNumEntries, pbcCmtsIfUpstreamPort, pbcCmtsIfUpstreamOperMode, 
				pbcCmtsIfUpstreamCmdRcvdPwr, pbcCmtsIfUpstreamPowerLevel, pbcCmtsIfUpstreamHcsErrors, pbcCmtsIfUpstreamCrcErrors, pbcCmtsIfMacCmTotal, 
				pbcCmtsIfMacCmRangeAborted, pbcCmtsIfMacCmRanging, pbcCmtsIfMacCmRangingComplete, pbcCmtsIfMacCmIpComplete, pbcCmtsIfMacCmRegistered, 
				pbcCmtsIfUpstreamCmTotal, pbcCmtsIfUpstreamCmRangeAborted, pbcCmtsIfUpstreamCmRanging, pbcCmtsIfUpstreamCmRangingComplete, pbcCmtsIfUpstreamCmIpComplete, 
				pbcCmtsRogueCmMacAddress, pbcCmtsRogueCmIpAddress, pbcCmtsRogueCmPtr, pbcCmtsRogueCmType, pbcCmtsRogueCmFirstActive, 
				pbcCmtsRogueCmLastActive, pbcCmtsCmStatusFirstOnline, pbcCmtsCmStatusLastOnline, pbcCmtsCmStatusTimesOnline, pbcCmtsCmStatusPercentOnline, 
				pbcCmtsCmStatusMinOnline, pbcCmtsCmStatusMaxOnline, pbcCmtsCmStatusAvgOnline, pbcCmtsCmStatusMinOffline, pbcCmtsCmStatusMaxOffline, 
				pbcCmtsCmStatusAvgOffline, pbcCmtsIfUpstreamCmRogue, pbcCmtsIfMacCmRogue, pbcCmtsIfUpstreamCER, pbcCmtsIfUpstreamMER, 
				pbcCmtsIfUpstreamCmRegistered }
			STATUS current
			DESCRIPTION 
				"Generic PBC CMTS registrations."
			::= { pbcCmtsGroups 1 }
		
		-- 1.3.6.1.4.1.5987.2.2.4.1.2
		pbcCableSpectrumManagementGroup OBJECT-GROUP
			OBJECTS { pbcSpectrumAnalysisEnable, pbcSpectrumAnalysisCmdStatus, pbcSpectrumAnalysisIntegrationLen, pbcSpectrumAnalysisFreqStep, pbcSpectrumAnalysisFreqMin, 
				pbcSpectrumAnalysisFreqMax, pbcSpectrumAnalysisArraySize, pbcSpectrumAnalysisActiveArray, pbcSpectrumAnalysisArrayIndex, pbcSpectrumAnalysisArrayStatus, 
				pbcSpectrumAnalysisFrequency, pbcSpectrumAnalysisPower, pbcCmtsSpectrumAnalysisEnableSweepNotification, pbcSweepNotificationRecipient, pbcSpectrumAnalysisArrayScanStart, 
				pbcSpectrumAnalysisArrayScanStop, pbcSpectrumAnalysisArrayIndexID, pbcCardIfPortIndexID, pbcSpectrumAnalysisArrayStatusID, pbcCmtsSpectrumAnalysisNotificationType, 
				pbcSweepNotificationRecipientPort }
			STATUS current
			DESCRIPTION 
				"Group of objects implemented in Cable Modem Termination Systems
				providing Flap List information."
			::= { pbcCmtsGroups 2 }
		
		-- 1.3.6.1.4.1.5987.2.2.4.1.3
		pbcCmtsNotificationManagementGroup OBJECT-GROUP
			OBJECTS { pbcCmtsModemEventsEnable, pbcCmtsNotificationsControl, pbcCmtsEventsEnable }
			STATUS current
			DESCRIPTION 
				"Group of objects associated with vendor-specific notification
				control."
			::= { pbcCmtsGroups 3 }
		
		-- 1.3.6.1.4.1.5987.2.2.4.1.4
		pbcCmtsNotificationGroup NOTIFICATION-GROUP
			NOTIFICATIONS { pbcCmtsEnvMonNotification, pbcCmtsSpectrumAnalysisSweepComplete, pbcCmtsChassisNotification, pbcCmtsSoftwareNotification, pbcCmtsAccessNotification, 
				pbcCmtsCmStateChangeNotification, pbcCmtsRfInterfaceNotification, pbcCmtsFlapListNotification, pbcCmtsDataPathNotification, pbcCmtsConfigNotification, 
				pbcCmtsDebugNotification }
			STATUS current
			DESCRIPTION 
				"Generic PBC Notifications."
			::= { pbcCmtsGroups 4 }
		
		-- 1.3.6.1.4.1.5987.2.2.4.1.5
		pbcFlapListManagementGroup OBJECT-GROUP
			OBJECTS { pbcCmtsFlapListAgeMinutes, pbcCmtsFlapListIMRetryInterval, pbcCmtsFlapListCERThreshold, pbcCmtsFlapListMERThreshold, pbcCmtsFlapListQPSKSNRThreshold, 
				pbcCmtsFlapListQAM16SNRThreshold, pbcCmtsFlapListPowerAdjustThreshold, pbcCmtsFlapListSMMissThreshold, pbcCmtsFlapListFreqThreshold, pbcCmtsFlapListSize, 
				pbcUsFlapListControlIMRetryInterval, pbcUsFlapListControlCERThreshold, pbcUsFlapListControlMERThreshold, pbcUsFlapListControlQPSKSNRThreshold, pbcUsFlapListControlQAM16SNRThreshold, 
				pbcUsFlapListControlPowerAdjustThreshold, pbcUsFlapListControlSMMissThreshold, pbcUsFlapListControlFreqThreshold, pbcCmtsFlapListMacAddr, pbcCmtsFlapListUpstreamIfIndex, 
				pbcCmtsFlapListDownstreamIfIndex, pbcCmtsFlapListFlapCount, pbcCmtsFlapListFlapCause, pbcCmtsFlapListFreqDrift, pbcCmtsFlapListEventsEnable
				 }
			STATUS current
			DESCRIPTION 
				"Description."
			::= { pbcCmtsGroups 5 }
		
		-- 1.3.6.1.4.1.5987.2.2.4.2
		pbcCmtsCompliances OBJECT IDENTIFIER ::= { pbcCmtsConformance 2 }
		
		-- 1.3.6.1.4.1.5987.2.2.4.2.1
		pbcCmtsBasicCompliance MODULE-COMPLIANCE
			STATUS current
			DESCRIPTION 
				"Object groups which must be supported."
			MODULE -- this module
				MANDATORY-GROUPS { pbcCmtsGroup, pbcCableSpectrumManagementGroup, pbcCmtsNotificationGroup, pbcFlapListManagementGroup }
			::= { pbcCmtsCompliances 1 }
		
		-- 1.3.6.1.4.1.5987.2.2.5
		pbcFlapListManagement OBJECT IDENTIFIER ::= { pbcCmts 5 }
		
		-- 1.3.6.1.4.1.5987.2.2.5.1
		pbcFlapListObjects OBJECT IDENTIFIER ::= { pbcFlapListManagement 1 }
		
		-- 1.3.6.1.4.1.5987.2.2.5.1.1
		pbcCmtsFlapListAgeMinutes OBJECT-TYPE
			SYNTAX Unsigned32 (1..86400)
			MAX-ACCESS read-write
			STATUS current
			DESCRIPTION
				"Aging time in minutes (From 1 minute to 60 days)."
			DEFVAL { 1440 }
			::= { pbcFlapListObjects 1 }
		
		-- 1.3.6.1.4.1.5987.2.2.5.1.2
		pbcCmtsFlapListIMRetryInterval OBJECT-TYPE
			SYNTAX Unsigned32 (60..86400)
			MAX-ACCESS read-write
			STATUS current
			DESCRIPTION
				"Duration between two consecutive IM Retries that is considered a flap 
				event in seconds."
			DEFVAL { 180 }
			::= { pbcFlapListObjects 2 }
		
		-- 1.3.6.1.4.1.5987.2.2.5.1.3
		pbcCmtsFlapListCERThreshold OBJECT-TYPE
			SYNTAX Unsigned32 (1..1000000)
			MAX-ACCESS read-write
			STATUS current
			DESCRIPTION
				"CER Threshold 1 in millionth."
			DEFVAL { 1 }
			::= { pbcFlapListObjects 3 }
		
		-- 1.3.6.1.4.1.5987.2.2.5.1.4
		pbcCmtsFlapListMERThreshold OBJECT-TYPE
			SYNTAX TenthdB (1..1000)
			MAX-ACCESS read-write
			STATUS current
			DESCRIPTION
				"MER Threshold (in tenth of dB)."
			DEFVAL { 180 }
			::= { pbcFlapListObjects 4 }
		
		-- 1.3.6.1.4.1.5987.2.2.5.1.5
		pbcCmtsFlapListQPSKSNRThreshold OBJECT-TYPE
			SYNTAX TenthdB (1..1000)
			MAX-ACCESS read-write
			STATUS current
			DESCRIPTION
				"QPSK SNR Threshold (in tenth of dB)."
			DEFVAL { 180 }
			::= { pbcFlapListObjects 5 }
		
		-- 1.3.6.1.4.1.5987.2.2.5.1.6
		pbcCmtsFlapListQAM16SNRThreshold OBJECT-TYPE
			SYNTAX TenthdB (1..1000)
			MAX-ACCESS read-write
			STATUS current
			DESCRIPTION
				"QAM16 SNR Threshold (in tenth of dB)."
			DEFVAL { 180 }
			::= { pbcFlapListObjects 6 }
		
		-- 1.3.6.1.4.1.5987.2.2.5.1.7
		pbcCmtsFlapListPowerAdjustThreshold OBJECT-TYPE
			SYNTAX TenthdB (1..1000)
			MAX-ACCESS read-write
			STATUS current
			DESCRIPTION
				"Power Adjust Threshold (in tenth of a dB)."
			DEFVAL { 30 }
			::= { pbcFlapListObjects 7 }
		
		-- 1.3.6.1.4.1.5987.2.2.5.1.8
		pbcCmtsFlapListSMMissThreshold OBJECT-TYPE
			SYNTAX Unsigned32 (1..100)
			MAX-ACCESS read-write
			STATUS current
			DESCRIPTION
				"SM Miss Quantity Threshold."
			DEFVAL { 2 }
			::= { pbcFlapListObjects 8 }
		
		-- 1.3.6.1.4.1.5987.2.2.5.1.9
		pbcCmtsFlapListFreqThreshold OBJECT-TYPE
			SYNTAX Unsigned32 (0..10000000)
			MAX-ACCESS read-write
			STATUS current
			DESCRIPTION
				"Upstream Frequency drift Threshold (in Hertz). A non zero value of 
				pbcCmtsUsFlapListFreqThreshold overrides this value for an upstream 
				channel."
			DEFVAL { 0 }
			::= { pbcFlapListObjects 9 }
		
		-- 1.3.6.1.4.1.5987.2.2.5.1.10
		pbcCmtsFlapListSize OBJECT-TYPE
			SYNTAX Unsigned32 (1..8192)
			MAX-ACCESS read-write
			STATUS current
			DESCRIPTION
				"Maximum number of entries in the Flap List Table."
			DEFVAL { 8192 }
			::= { pbcFlapListObjects 10 }
		
		-- 1.3.6.1.4.1.5987.2.2.5.1.11
		pbcUsFlapListControlTable OBJECT-TYPE
			SYNTAX SEQUENCE OF PbcUsFlapListControlEntry
			MAX-ACCESS not-accessible
			STATUS current
			DESCRIPTION
				"Various flap thresholds to be applied per upstream channel."
			::= { pbcFlapListObjects 11 }
		
		-- 1.3.6.1.4.1.5987.2.2.5.1.11.1
		pbcUsFlapListControlEntry OBJECT-TYPE
			SYNTAX PbcUsFlapListControlEntry
			MAX-ACCESS not-accessible
			STATUS current
			DESCRIPTION
				"An entry for every upstream channel in the system."
			INDEX { ifIndex }
			::= { pbcUsFlapListControlTable 1 }
		
		PbcUsFlapListControlEntry ::=
			SEQUENCE { 
				pbcUsFlapListControlIMRetryInterval
					Unsigned32,
				pbcUsFlapListControlCERThreshold
					Unsigned32,
				pbcUsFlapListControlMERThreshold
					TenthdB,
				pbcUsFlapListControlQPSKSNRThreshold
					TenthdB,
				pbcUsFlapListControlQAM16SNRThreshold
					TenthdB,
				pbcUsFlapListControlPowerAdjustThreshold
					TenthdB,
				pbcUsFlapListControlSMMissThreshold
					Unsigned32,
				pbcUsFlapListControlFreqThreshold
					Unsigned32
			 }

		-- 1.3.6.1.4.1.5987.2.2.5.1.11.1.1
		pbcUsFlapListControlIMRetryInterval OBJECT-TYPE
			SYNTAX Unsigned32 (60..86400)
			MAX-ACCESS read-write
			STATUS current
			DESCRIPTION
				"Duration in seconds between two consecutive IM Retries that is 
				considered a flap event. A non zero value overrides the global 
				pbcCmtsFlapListIMRetryInterval for this upstream channel."
			DEFVAL { 180 }
			::= { pbcUsFlapListControlEntry 1 }
		
		-- 1.3.6.1.4.1.5987.2.2.5.1.11.1.2
		pbcUsFlapListControlCERThreshold OBJECT-TYPE
			SYNTAX Unsigned32 (1..1000000)
			MAX-ACCESS read-write
			STATUS current
			DESCRIPTION
				"CER Threshold (in millionth, normalized 0 to 1). A non zero value 
				overrides the global pbcCmtsFlapListCERThreshold for this upstream 
				channel."
			DEFVAL { 1 }
			::= { pbcUsFlapListControlEntry 2 }
		
		-- 1.3.6.1.4.1.5987.2.2.5.1.11.1.3
		pbcUsFlapListControlMERThreshold OBJECT-TYPE
			SYNTAX TenthdB (1..1000)
			MAX-ACCESS read-write
			STATUS current
			DESCRIPTION
				"MER Threshold (in Tenth of a dB). A non zero value overrides the global 
				pbcCmtsFlapListMERThreshold for this upstream channel."
			DEFVAL { 180 }
			::= { pbcUsFlapListControlEntry 3 }
		
		-- 1.3.6.1.4.1.5987.2.2.5.1.11.1.4
		pbcUsFlapListControlQPSKSNRThreshold OBJECT-TYPE
			SYNTAX TenthdB (1..1000)
			MAX-ACCESS read-write
			STATUS current
			DESCRIPTION
				"QPSK SNR Threshold (in tenth of dB). A non zero value overrides the 
				global pbcCmtsFlapListQPSKSNRThreshold for this upstream channel."
			DEFVAL { 180 }
			::= { pbcUsFlapListControlEntry 4 }
		
		-- 1.3.6.1.4.1.5987.2.2.5.1.11.1.5
		pbcUsFlapListControlQAM16SNRThreshold OBJECT-TYPE
			SYNTAX TenthdB (1..1000)
			MAX-ACCESS read-write
			STATUS current
			DESCRIPTION
				"QAM16 SNR Threshold (in tenth of dB). A non zero value overrides the 
				global pbcCmtsFlapListQPSKSNRThreshold for this upstream channel."
			DEFVAL { 180 }
			::= { pbcUsFlapListControlEntry 5 }
		
		-- 1.3.6.1.4.1.5987.2.2.5.1.11.1.6
		pbcUsFlapListControlPowerAdjustThreshold OBJECT-TYPE
			SYNTAX TenthdB (1..1000)
			MAX-ACCESS read-write
			STATUS current
			DESCRIPTION
				"Power Adjust Threshold (in dB). A non zero value overrides the global 
				pbcCmtsFlapListPowerAdjustThreshold for this upstream channel."
			DEFVAL { 30 }
			::= { pbcUsFlapListControlEntry 6 }
		
		-- 1.3.6.1.4.1.5987.2.2.5.1.11.1.7
		pbcUsFlapListControlSMMissThreshold OBJECT-TYPE
			SYNTAX Unsigned32 (1..100)
			MAX-ACCESS read-write
			STATUS current
			DESCRIPTION
				"SM Miss Quantity Threshold. A non zero value overrides the global 
				pbcCmtsFlapListSMMissThreshold for this upstream channel."
			DEFVAL { 2 }
			::= { pbcUsFlapListControlEntry 7 }
		
		-- 1.3.6.1.4.1.5987.2.2.5.1.11.1.8
		pbcUsFlapListControlFreqThreshold OBJECT-TYPE
			SYNTAX Unsigned32 (0..10000000)
			MAX-ACCESS read-write
			STATUS current
			DESCRIPTION
				"Upstream Frequency drift Threshold (in Hertz). A non zero value 
				overrides the global pbcCmtsFlapListFreqThreshold for this upstream 
				channel."
			DEFVAL { 0 }
			::= { pbcUsFlapListControlEntry 8 }
		
		-- 1.3.6.1.4.1.5987.2.2.5.1.12
		pbcCmtsFlapListTable OBJECT-TYPE
			SYNTAX SEQUENCE OF PbcCmtsFlapListEntry
			MAX-ACCESS not-accessible
			STATUS current
			DESCRIPTION
				"information about the recently flapping cable modems according to the 
				various thresholds set in the pbcCmtsFlapListObjects."
			::= { pbcFlapListObjects 12 }
		
		-- 1.3.6.1.4.1.5987.2.2.5.1.12.1
		pbcCmtsFlapListEntry OBJECT-TYPE
			SYNTAX PbcCmtsFlapListEntry
			MAX-ACCESS not-accessible
			STATUS current
			DESCRIPTION
				"An entry for every Flapping modem in the system."
			INDEX { pbcCmtsFlapListMacAddr }
			::= { pbcCmtsFlapListTable 1 }
		
		PbcCmtsFlapListEntry ::=
			SEQUENCE { 
				pbcCmtsFlapListMacAddr
					MacAddress,
				pbcCmtsFlapListUpstreamIfIndex
					InterfaceIndex,
				pbcCmtsFlapListDownstreamIfIndex
					InterfaceIndex,
				pbcCmtsFlapListFlapCount
					Counter32,
				pbcCmtsFlapListFlapCause
					INTEGER,
				pbcCmtsFlapListFreqDrift
					Unsigned32
			 }

		-- 1.3.6.1.4.1.5987.2.2.5.1.12.1.1
		pbcCmtsFlapListMacAddr OBJECT-TYPE
			SYNTAX MacAddress
			MAX-ACCESS read-only
			STATUS current
			DESCRIPTION
				"MAC address of the Flapping modem."
			::= { pbcCmtsFlapListEntry 1 }
		
		-- 1.3.6.1.4.1.5987.2.2.5.1.12.1.2
		pbcCmtsFlapListUpstreamIfIndex OBJECT-TYPE
			SYNTAX InterfaceIndex
			MAX-ACCESS read-only
			STATUS current
			DESCRIPTION
				"Upstream Interface Index of the Flapping modem."
			::= { pbcCmtsFlapListEntry 2 }
		
		-- 1.3.6.1.4.1.5987.2.2.5.1.12.1.3
		pbcCmtsFlapListDownstreamIfIndex OBJECT-TYPE
			SYNTAX InterfaceIndex
			MAX-ACCESS read-only
			STATUS current
			DESCRIPTION
				"Downstream Interface Index of the Flapping modem."
			::= { pbcCmtsFlapListEntry 3 }
		
		-- 1.3.6.1.4.1.5987.2.2.5.1.12.1.4
		pbcCmtsFlapListFlapCount OBJECT-TYPE
			SYNTAX Counter32
			MAX-ACCESS read-only
			STATUS current
			DESCRIPTION
				"Number of times the modem has Flapped."
			::= { pbcCmtsFlapListEntry 4 }
		
		-- 1.3.6.1.4.1.5987.2.2.5.1.12.1.5
		pbcCmtsFlapListFlapCause OBJECT-TYPE
			SYNTAX INTEGER
				{
				imRetry(1),
				cer(2),
				mer(3),
				snrQpsk(4),
				snrQam16(5),
				powerAdjust(6),
				smMiss(7),
				freqDrift(8)
				}
			MAX-ACCESS read-only
			STATUS current
			DESCRIPTION
				"Last flap cause for the modem."
			::= { pbcCmtsFlapListEntry 5 }
		
		-- 1.3.6.1.4.1.5987.2.2.5.1.12.1.6
		pbcCmtsFlapListFreqDrift OBJECT-TYPE
			SYNTAX Unsigned32
			MAX-ACCESS read-only
			STATUS current
			DESCRIPTION
				"Amount of Frequency Drift in case pbcCmtsFlapListFlapCause is freqDrift (8).
				Form othe flap causes, this value should be 0."
			::= { pbcCmtsFlapListEntry 6 }
		
		-- 1.3.6.1.4.1.5987.2.2.5.1.13
		pbcCmtsFlapListEventsEnable OBJECT-TYPE
			SYNTAX TruthValue
			MAX-ACCESS read-write
			STATUS current
			DESCRIPTION
				"Enables or disables the Flap List event generation."
			::= { pbcFlapListObjects 13 }
		
		-- 1.3.6.1.4.1.5987.1001
		pbcG10CMTS OBJECT IDENTIFIER ::= { pacificBroadband 1001 }
		
		-- 1.3.6.1.4.1.5987.1002
		pbcG1CMTS OBJECT IDENTIFIER ::= { pacificBroadband 1002 }
		
	
	END

--
-- PBC-CMTS-MIB.mib
--
