-- extracted from draft-shield-eos-capabilities-00.txt
-- at Wed Aug 28 06:10:43 2002

   EXTENDED-CAPABILITIES-MIB DEFINITIONS ::= BEGIN

   IMPORTS
          MODULE-IDENTITY,
          OBJECT-TYPE,
          enterprises             FROM SNMPv2-SMI
          ExtendedCapabilities    FROM EXTENDED-CAPABILITIES-TC
          MODULE-COMPLIANCE,
          TEXTUAL-CONVENTION      FROM SNMPv2-TC
          OBJECT-GROUP            FROM SNMPv2-CONF;

   extendedCapabilitiesMib MODULE-IDENTITY
          LAST-UPDATED "200208170000Z"
          ORGANIZATION "University of Liverpool"
          CONTACT-INFO
              "Postal:    Dave Shield
                          Computer Science
                          University of Liverpool
                          Peach Street
                          Liverpool
                          L69 7ZF
                          United Kingdom

              E-Mail: D.T.Shield@csc.liv.ac.uk"
          DESCRIPTION
              "This MIB module defines a framework for advertising
               and negotiating the use of extended SNMP capabilities."
          ::= { enterprises liv(1579) compsci(42) dts(1) eCap(3) 2 }


   eCapObjects     OBJECT IDENTIFIER ::= { extendedCapabilitiesMib 1 }
   eCapConformance OBJECT IDENTIFIER ::= { extendedCapabilitiesMib 2 }

   --
   --  MIB objects to advertise support for extended capabilities
   --

   eCapGeneral OBJECT-TYPE
        SYNTAX     ExtendedCapabilities
        MAX-ACCESS read-only
        STATUS     current
        DESCRIPTION
            "The basic set of extended capabilities supported by
             an agent as a whole.  The eCapTable can be used to
             override this setting for individual MIB subtrees."
        ::= { eCapObjects 1 }

   eCapTable OBJECT-TYPE
        SYNTAX      SEQUENCE OF ECapEntry
        MAX-ACCESS  not-accessible
        STATUS      current
        DESCRIPTION
            "A table of alternative sets of extended capabilities,
             supported by particular MIB subtrees of the agent."
        ::= { eCapObjects 2 }

   eCapEntry OBJECT-TYPE
        SYNTAX      ECapEntry
        MAX-ACCESS  not-accessible
        STATUS      current
        DESCRIPTION ""
        INDEX       { eCapIndex }
        ::= { eCapTable 1 }

   ECapEntry ::= SEQUENCE {
        eCapIndex            Unsigned32,
        eCapSubtree          OBJECT IDENTIFIER,
        eCapSettings         ExtendedCapabilities
        }

   eCapIndex OBJECT-TYPE
        SYNTAX      Unsigned32
        MAX-ACCESS  not-accessible
        STATUS      current
        DESCRIPTION
            "An arbitrary index into the eCapTable."
        ::= { eCapEntry 1 }

   eCapSubtree OBJECT-TYPE
        SYNTAX      OBJECT IDENTIFIER
        MAX-ACCESS  read-only
        STATUS      current
        DESCRIPTION
           "The OID that identifies the root of a MIB subtree,
            supporting different extended capabilities to
            the agent as a whole."
        ::= { eCapEntry 2 }

   eCapSettings OBJECT-TYPE
        SYNTAX     ExtendedCapabilities
        MAX-ACCESS read-only
        STATUS     current
        DESCRIPTION
            "The set of extended capabilities supported by the
             agent for the MIB subtree rooted at eCapSubtree.
             This value replaces the eCapGeneral for objects
             within this subtree."
        ::= { eCapEntry 3 }

   --
   --  MIB objects to negotiate use of extended capabilities
   --

   eReqCapTable OBJECT-TYPE
        SYNTAX      SEQUENCE OF EReqCapEntry
        MAX-ACCESS  not-accessible
        STATUS      current
        DESCRIPTION
            "A 'pseudo-table', used to indicate which varbinds
             in a request should involve particular extended
             capabilities.  This is not a conventional MIB table,
             and will not appear in the output of walking the agent."
        ::= { eCapObjects 3 }

   eReqCapEntry OBJECT-TYPE
        SYNTAX      EReqCapEntry
        MAX-ACCESS  not-accessible
        STATUS      current
        DESCRIPTION ""
        INDEX       { eReqCapVBIndex, IMPLIED eReqCapability }
        ::= { eReqCapTable 1 }

   EReqCapEntry ::= SEQUENCE {
        eReqCapVBIndex          Unsigned32,
        eReqCapabilities        ExtendedCapabilities
        eReqCapRangeStart       INTEGER
        eReqCapRangeEnd         INTEGER
        eReqCapVarBind          INTEGER
        eReqCapAllBar           INTEGER
        }

   eReqCapIndex OBJECT-TYPE
        SYNTAX      Unsigned32
        MAX-ACCESS  not-accessible
        STATUS      current
        DESCRIPTION
            "The index of a particular VarBind in the request list,
             indicating the range of varbinds to which the specified
             extended capabilit(ies) should be applied."
        ::= { eReqCapEntry 1 }

   eReqCapabilities OBJECT-TYPE
        SYNTAX      ExtendedCapabilities
        MAX-ACCESS  read-only
        STATUS      current
        DESCRIPTION
            "The extended capabilit(ies) that should be applied
             to the indicated range of varbinds in the request list."
        ::= { eReqCapEntry 2 }

   eReqCapRangeStart OBJECT-TYPE
        SYNTAX      INTEGER {
            other(1),
            supported(2),
            unsupported(3),
            notUsed(4)
        }
        MAX-ACCESS  read-only
        STATUS      current
        DESCRIPTION
            "Indicates that the specified extended capabilit(ies)
             should be applied to all varbinds in the request list
             from the indicated varbind, up to and including the
             varbind indicated by the corresponding eReqCapRangeEnd
             (or the end of the varbind list).  The value returned
             in the response may indicate whether this capability
             was supported and/or used in processing the request."
        ::= { eReqCapEntry 3 }

   eReqCapRangeEnd OBJECT-TYPE
        SYNTAX      INTEGER {
            other(1),
            supported(2),
            unsupported(3),
            notUsed(4)
        }
        MAX-ACCESS  read-only
        STATUS      current
        DESCRIPTION
            "Indicates that the specified extended capabilit(ies)
             should be applied to all varbinds in the request list
             up to and including the indicated varbind, starting from
             the varbind indicated by the corresponding eReqCapRangeStart
             (or the beginning of the varbind list).  The value returned
             in the response may indicate whether this capability
             was supported and/or used in processing the request."
        ::= { eReqCapEntry 4 }

   eReqCapVarBind OBJECT-TYPE
        SYNTAX      INTEGER {
            other(1),
            supported(2),
            unsupported(3),
            notUsed(4)
        }
        MAX-ACCESS  read-only
        STATUS      current
        DESCRIPTION
            "Indicates that the specified extended capabilit(ies)
             should be applied to the indicated varbind.  The value
             returned in the response may indicate whether the capability
             was supported and/or used in processing the request."
        ::= { eReqCapEntry 5 }

   eReqCapAllBar OBJECT-TYPE
        SYNTAX      INTEGER {
            other(1),
            supported(2),
            unsupported(3),
            notUsed(4)
        }
        MAX-ACCESS  read-only
        STATUS      current
        DESCRIPTION
            "Indicates that the specified extended capabilit(ies)
             should be applied to all varbinds in the request list
             except the indicated varbind(s). The value returned
             in the response may indicate whether the capability
             was supported and/or used in processing the request."
        ::= { eReqCapEntry 6 }

   --
   --  MIB objects to advertise support for extended capabilities
   --

   eCapGroups OBJECT IDENTIFIER ::= { eCapConformance 1 }	

   eCapGeneralGroup OBJECT-GROUP
      OBJECTS { eCapGeneral }
      STATUS   current
      DESCRIPTION
          "Advertising of core extended capabilities."
      ::= { eCapGroups 1}

   eCapSubtreeGroup OBJECT-GROUP
      OBJECTS { eCapSubtree, eCapSettings }
      STATUS   current
      DESCRIPTION
          "Advertising of subtree-specific extended capabilities."
      ::= { eCapGroups 2}

   eCapRequetGroup OBJECT-GROUP
      OBJECTS {
          eReqCapRangeStart,
          eReqCapRangeEnd,
          eReqCapVarBind,
          eReqCapAllBar
      }
      STATUS   current
      DESCRIPTION
          "Negotiation of extended capabilities to use."
      ::= { eCapGroups 3}

   END

--  
--    Copyright (C) The Internet Society (2002). All Rights Reserved. 
--     
--    This document and translations of it may be copied and furnished to 
--    others, and derivative works that comment on or otherwise explain it   
--    or assist in its implementation may be prepared, copied, published 
--    and distributed, in whole or in part, without restriction of any 
--    kind, provided that the above copyright notice and this paragraph 
--    are included on all such copies and derivative works.  However, this 
--    document itself may not be modified in any way, such as by removing 
--    the copyright notice or references to the Internet Society or other 
--    Internet organizations, except as needed for the purpose of 
--    developing Internet standards in which case the procedures for 
--    copyrights defined in the Internet Standards process must be 
--    followed, or as required to translate it into languages other than 
--    English. 
--     
--    The limited permissions granted above are perpetual and will not be 
--    revoked by the Internet Society or its successors or assigns. 
--     
--    This document and the information contained herein is provided on an 
--    "AS IS" basis and THE INTERNET SOCIETY AND THE INTERNET ENGINEERING 
--    TASK FORCE DISCLAIMS ALL WARRANTIES, EXPRESS OR IMPLIED, INCLUDING 
--    BUT NOT LIMITED TO ANY WARRANTY THAT THE USE OF THE INFORMATION 
--    HEREIN WILL NOT INFRINGE ANY RIGHTS OR ANY IMPLIED WARRANTIES OF 
--    MERCHANTABILITY OR FITNESS FOR A PARTICULAR PURPOSE. 
--  
-- 
-- 
-- This Internet Draft expires: February 2003
