Wellfleet-ASR-MIB DEFINITIONS ::= BEGIN

IMPORTS
   
   IpAddress, Counter
     FROM RFC1155-SMI
   OBJECT-TYPE
     FROM RFC-1212
   DisplayString
     FROM RFC1213-MIB
   wfAsrGroup
     FROM Wellfleet-COMMON-MIB;

wfAsrBase  OBJECT IDENTIFIER ::= { wfAsrGroup 1 }

wfAsrBaseCreate OBJECT-TYPE
     SYNTAX  INTEGER {
                 created(1),
                 deleted(2)
             }
         ACCESS  read-write
         STATUS  mandatory
         DESCRIPTION
                 "Create/Delete parameter.  Default is created.
                 Users perform a set operation on this
                 object in order to create/delete ASR."
         DEFVAL  { created }
         ::= { wfAsrBase 1 }

    wfAsrBaseEnable OBJECT-TYPE
        SYNTAX  INTEGER {
                    enabled(1),
                    disabled(2)
                }
        ACCESS  read-write
        STATUS  mandatory
        DESCRIPTION
                "Enable/Disable parameter. Default is enabled.
                Users perform a set operation on this
                object in order to enable/disable ASR."
        DEFVAL  { enabled }
        ::= { wfAsrBase 2 }

   wfAsrBaseState OBJECT-TYPE
        SYNTAX  INTEGER {
                    up(1),
                    down(2),
                    init(3),
                    notpres(4)
                }
        ACCESS  read-only
        STATUS  mandatory
        DESCRIPTION
                "The current state of the entire ASR."
        DEFVAL  { notpres }
        ::= { wfAsrBase 3 }


   wfAsrNextHopRetryLimit OBJECT-TYPE
        SYNTAX INTEGER (1..10)
        ACCESS read-write
        STATUS mandatory
        DESCRIPTION
               "Set the number of next hop entries to try to establish 
                the SVC should the first next hop entry fail."
        DEFVAL  { 2 }
        ::= { wfAsrBase 4 }

   wfAsrSecureInFilter OBJECT-TYPE
        SYNTAX INTEGER {
                   enable(1),
                   disable(2)
               }
        ACCESS read-write
        STATUS mandatory
        DESCRIPTION 
               "Enable or disable inbound packet filtering.  
                This  object will be implemented as part of the
                follow on project."
        DEFVAL { disable }
        ::= {wfAsrBase 5}

   wfAsrSecureInValid OBJECT-TYPE
        SYNTAX INTEGER {
                   enable(1),
                   disable(2)
               }
        ACCESS read-write
        STATUS mandatory
        DESCRIPTION
               "Enable or disable inbound call validation. This object will
                be implemented as part of a follow on project."
        DEFVAL { disable }
        ::= { wfAsrBase 6 }

   wfAsrHoldDownTimer OBJECT-TYPE
       SYNTAX INTEGER 
       ACCESS read-write
       STATUS mandatory
       DESCRIPTION
               "The hold down timer is used to prevent retries to a destination
                that the SVC setup process has failed on.  This value would be
                used if filter/flow spec information is not returned from NHS."
       DEFVAL { 5 }
       ::= { wfAsrBase 7 }

   wfAsrActiveSvcs OBJECT-TYPE
       SYNTAX   Counter
       ACCESS   read-only
       STATUS   mandatory
       DESCRIPTION
               "A count of the SVCs currently active on this router slot."
       ::= { wfAsrBase 8 }

   wfAsrFwdTblEntries OBJECT-TYPE
       SYNTAX  Counter
       ACCESS  read-only
       STATUS  mandatory
       DESCRIPTION
               "A count of entries in the ASR forward table."
       ::= { wfAsrBase 9 }

  wfAsrFwdTblSeq OBJECT-TYPE
      SYNTAX  Counter
      ACCESS  read-only
      STATUS  mandatory
      DESCRIPTION
              "Sequence number used to determine changes to the ASR forward
               table."
      ::= { wfAsrBase 10 }

  wfAsrDnsProxyPort OBJECT-TYPE
       SYNTAX  INTEGER {
               min(1),
               default(500),
               max(32550)
       }
       ACCESS  read-write
       STATUS  mandatory
       DESCRIPTION
               "DNS proxy port for QOS translation queries"
       DEFVAL  { default }
       ::= { wfAsrBase 11 }

   wfAsrMaxSessions OBJECT-TYPE
       SYNTAX  INTEGER {
               default(500) 
               } 
       ACCESS  read-write
       STATUS  mandatory
       DESCRIPTION
              "Maximum number of TCP/IP sessions which are to be managed by ASR."
       DEFVAL { default }
       ::= { wfAsrBase 12 }

    wfAsrDebugLevel OBJECT-TYPE
        SYNTAX  INTEGER 
        ACCESS  read-write
        STATUS  mandatory
        DESCRIPTION
                "Debug level in which to enable log messages.  The
                greater the value, the more detailed the log messages."
        DEFVAL  { 0 }
        ::= { wfAsrBase 13 }
   
    wfAsrUseDynRdiscPref OBJECT-TYPE
        SYNTAX  INTEGER {
                    enable(1),
                    disable(2)
                }
        ACCESS  read-write
        STATUS  mandatory
        DESCRIPTION
                "Enable/Disable parameter for ASR to update 
  	         the Dynamic Router Discovery Preference value. 
		 If enabled, wfRdiscInterfacePref must be 0 in 
	         order to advertise the ASR Dynamic Preference."
        DEFVAL  { disable }
        ::= { wfAsrBase 14 }


   wfAsrX213PriTable OBJECT-TYPE
       SYNTAX   SEQUENCE OF WfAsrX213PriEntry
       ACCESS   not-accessible
       STATUS   mandatory
       DESCRIPTION
               "A table used by ASR to convert the X.213 priority value returned
                by NHS to a switch specific Value."
       ::= { wfAsrGroup 2 } 
 
   wfAsrX213PriEntry OBJECT-TYPE
        SYNTAX  WfAsrX213PriEntry
        ACCESS  not-accessible
        STATUS  mandatory
        DESCRIPTION
                "X.213 conversion table." 
        INDEX   { wfAsrX213PriLowVal,
                  wfAsrX213PriHiVal }
        ::= { wfAsrX213PriTable 1 }
  
   WfAsrX213PriEntry ::= SEQUENCE {
       wfAsrX213PriDelete
       INTEGER,
       wfAsrX213PriLowVal
       INTEGER,
       wfAsrX213PriHiVal
       INTEGER,
       wfAsrX213PriSwVal
       INTEGER
   }

   wfAsrX213PriDelete OBJECT-TYPE
        SYNTAX  INTEGER {
                created (1),
                deleted (2)
               }
       ACCESS   read-write
       STATUS   mandatory
       DESCRIPTION
               "Create/delete indicator for X.213 priority table entry."
       DEFVAL { created }
       ::= { wfAsrX213PriEntry 1 }


   wfAsrX213PriLowVal OBJECT-TYPE
        SYNTAX  INTEGER
        ACCESS  read-only
        STATUS  mandatory
        DESCRIPTION
                "Low value of X.213 priority range."
        ::= {  wfAsrX213PriEntry 2 }

   wfAsrX213PriHiVal OBJECT-TYPE
        SYNTAX  INTEGER
        ACCESS  read-only
        STATUS  mandatory
        DESCRIPTION
                "High  value of X.213 priority range."
        ::= {  wfAsrX213PriEntry 3 }

   wfAsrX213PriSwVal OBJECT-TYPE
        SYNTAX  INTEGER
        ACCESS  read-write
        STATUS  mandatory
        DESCRIPTION
                "Switch specific X.213 priority value."
        ::= {  wfAsrX213PriEntry 4 }


   wfAsrRtrPriTable OBJECT-TYPE
       SYNTAX   SEQUENCE OF WfAsrRtrPriEntry
       ACCESS   not-accessible
       STATUS   mandatory
       DESCRIPTION
               "A table used by ASR to convert the router  priority value
                returned  by NHS to a router priority queue."
       ::= { wfAsrGroup 3 }

   wfAsrRtrPriEntry OBJECT-TYPE
        SYNTAX  WfAsrRtrPriEntry
        ACCESS  not-accessible
        STATUS  mandatory
        DESCRIPTION
                "Router priority conversion table." 
        INDEX   { wfAsrRtrPriLowVal,
                  wfAsrRtrPriHiVal }
        ::= { wfAsrRtrPriTable 1 }

   WfAsrRtrPriEntry ::= SEQUENCE {
        wfAsrRtrPriDelete
        INTEGER,
        wfAsrRtrPriLowVal
        INTEGER,
        wfAsrRtrPriHiVal
        INTEGER,
        wfAsrRtrPriCvtVal
        INTEGER
   }

   wfAsrRtrPriDelete OBJECT-TYPE
        SYNTAX  INTEGER {
                created (1),
                deleted (2)
               }
       ACCESS   read-write
       STATUS   mandatory
       DESCRIPTION
               "Create/delete indicator for Router  priority table entry."
       DEFVAL { created }
       ::= { wfAsrRtrPriEntry 1 }


   wfAsrRtrPriLowVal OBJECT-TYPE
        SYNTAX  INTEGER
        ACCESS  read-only
        STATUS  mandatory
        DESCRIPTION
                "Low value of router priority range."
        ::= {  wfAsrRtrPriEntry 2 }

   wfAsrRtrPriHiVal OBJECT-TYPE
        SYNTAX  INTEGER
        ACCESS  read-only
        STATUS  mandatory
        DESCRIPTION
                "High value of router priority range."
        ::= {  wfAsrRtrPriEntry 3 }

   wfAsrRtrPriCvtVal OBJECT-TYPE
        SYNTAX  INTEGER
        ACCESS  read-write
        STATUS  mandatory
        DESCRIPTION
                "Router priority Queue value."
        ::= {  wfAsrRtrPriEntry 4 }

   wfAsrMultiHopTable OBJECT-TYPE
        SYNTAX  SEQUENCE OF WfAsrMultiHopEntry
        ACCESS  not-accessible
        STATUS  mandatory
        DESCRIPTION
                "A table used by ASR to identify those PVCs that can be used
                 as a multi hop path or overlay network."
       ::= { wfAsrGroup 4 }

  wfAsrMultiHopEntry OBJECT-TYPE
       SYNTAX  WfAsrMultiHopEntry
       ACCESS  not-accessible
       STATUS  mandatory
       DESCRIPTION
               "Multi Hop PVC identification."
       INDEX  { wfAsrMhCircuitNumber,
                wfAsrMhVcid1,
                wfAsrMhVcid2}
       ::= { wfAsrMultiHopTable 1 }

   WfAsrMultiHopEntry ::= SEQUENCE {
        wfAsrMultiHopDelete
        INTEGER,
        wfAsrMhCircuitNumber
        INTEGER,
        wfAsrMhVcid1
        INTEGER,
        wfAsrMhVcid2
        INTEGER
   }
  
  wfAsrMultiHopDelete OBJECT-TYPE
        SYNTAX  INTEGER {
                created (1),
                deleted (2)
               }
       ACCESS   read-write
       STATUS   mandatory
       DESCRIPTION
               "Create/delete indicator for multi hop  table entry."
       DEFVAL { created }
       ::= { wfAsrMultiHopEntry 1 }

    wfAsrMhCircuitNumber OBJECT-TYPE
        SYNTAX  INTEGER
        ACCESS  read-only
        STATUS  mandatory
        DESCRIPTION
                "Instance identifier.  The circuit number of this interface."
        ::= { wfAsrMultiHopEntry 2 }

    wfAsrMhVcid1 OBJECT-TYPE
        SYNTAX  INTEGER
        ACCESS  read-only
        STATUS  mandatory
        DESCRIPTION
              "VCID 1 value. The Dlci number for Frame Relay, the VPI for ATM."
        ::= { wfAsrMultiHopEntry 3 } 

    wfAsrMhVcid2 OBJECT-TYPE
        SYNTAX  INTEGER
        ACCESS  read-only
        STATUS  mandatory
        DESCRIPTION
              "VCID 2 value. The VCI for ATM, NULL for Frame Relay."
        ::= { wfAsrMultiHopEntry 4 }
   
   wfAsrDirectExceptTable OBJECT-TYPE
       SYNTAX  SEQUENCE OF WfAsrDirectExceptEntry
       ACCESS  not-accessible
       STATUS  mandatory
       DESCRIPTION
               "The directional exception asymmetric route avoidance table.
                This tables index is made up of the protocol and service field."
       ::= { wfAsrGroup 5 }
   
   wfAsrDirectExceptEntry OBJECT-TYPE
       SYNTAX  WfAsrDirectExceptEntry
       ACCESS  not-accessible
       STATUS  mandatory
       DESCRIPTION
               "The ASR directional exception table."
       INDEX    { wfAsrServiceProtocol,
                  wfAsrServicePort}
       ::= { wfAsrDirectExceptTable 1 }

   WfAsrDirectExceptEntry ::= SEQUENCE {
          wfAsrServiceProtocol
              INTEGER,
          wfAsrServicePort
              INTEGER,
          wfAsrSrcPortLow
              INTEGER,
          wfAsrSrcPortHigh
              INTEGER,
          wfAsrDestPortLow
              INTEGER,
          wfAsrDestPortHigh
              INTEGER
   }     
   wfAsrServiceProtocol OBJECT-TYPE
        SYNTAX  INTEGER {
                   tcp(6),
                   udp(17)
                }
        ACCESS  read-write
        STATUS  mandatory
        DESCRIPTION
                "Service protocol indicates what protocol this entry is
                 for. Coices are UDP or TCP."
        ::= { wfAsrDirectExceptEntry 1 }

   wfAsrServicePort OBJECT-TYPE
        SYNTAX  INTEGER
        ACCESS  read-write
        STATUS  mandatory
        DESCRIPTION
                "Application port number of service connecting to."
        ::= {  wfAsrDirectExceptEntry 2 }

   wfAsrSrcPortLow OBJECT-TYPE
        SYNTAX  INTEGER
        ACCESS  read-write 
        STATUS  mandatory
        DESCRIPTION
                "Low port number of application serving as source used 
                 at host site."
        ::= {  wfAsrDirectExceptEntry 3 }

  wfAsrSrcPortHigh OBJECT-TYPE
        SYNTAX  INTEGER
        ACCESS  read-write
        STATUS  mandatory
        DESCRIPTION
                "High port number of application serving as source used 
                 at host site."
        ::= {  wfAsrDirectExceptEntry 4 }

  wfAsrDestPortLow OBJECT-TYPE
        SYNTAX  INTEGER
        ACCESS  read-write
        STATUS  mandatory
        DESCRIPTION
                "Low port number of application serving as destination used 
                 at client site."
        ::= {  wfAsrDirectExceptEntry 5 }

  wfAsrDestPortHigh OBJECT-TYPE
        SYNTAX  INTEGER
        ACCESS  read-write
        STATUS  mandatory
        DESCRIPTION
                "High port number of application serving as destination used
                 at client site."
        ::= {  wfAsrDirectExceptEntry 6 }


   wfAsrCircuitTable OBJECT-TYPE
        SYNTAX  SEQUENCE OF WfAsrCircuitEntry
        ACCESS  not-accessible
        STATUS  mandatory
        DESCRIPTION
                "A table which contains configuration information for
                 each circuit defined to ASR but not specific to a
                 specific circuit.  The table is indexed by
                 circuit number."
        ::= { wfAsrGroup 6 }

    wfAsrCircuitEntry OBJECT-TYPE
        SYNTAX  WfAsrCircuitEntry
        ACCESS  not-accessible
        STATUS  mandatory
        DESCRIPTION
                "An ASR circuit description"
        INDEX   { wfAsrCircuitNumber }
        ::= { wfAsrCircuitTable 1 }


   WfAsrCircuitEntry ::= SEQUENCE {
            wfAsrCircuitCreate 
                INTEGER,
            wfAsrCircuitEnable
                INTEGER,
            wfAsrCircuitState
                INTEGER,
            wfAsrCircuitNumber
                INTEGER,
            wfAsrCircuitCallCtrl
                INTEGER,
            wfAsrCircuitInReceives
                Counter,
            wfAsrCircuitInDiscards
                Counter,
            wfAsrCircuitSetupRequests
                Counter,
            wfAsrCircuitSetupSucc
                Counter,
            wfAsrCircuitSetupFail
                Counter,
            wfAsrCircuitSVCsEstablished
                Counter,
            wfAsrNegativeNHR
                Counter,
            wfAsrSvcOutboundReqFail
                Counter,
            wfAsrSvcInboundFilterFail
                Counter,
           wfAsrSvcInboundCallValFail
                Counter

        }

    wfAsrCircuitCreate OBJECT-TYPE
        SYNTAX  INTEGER {
                    create(1),
                    delete(2)
                }
        ACCESS  read-write
        STATUS  mandatory
        DESCRIPTION
                "Create/Delete parameter. Default is created.
                Users perform a set operation on this
                object in order to create/delete an ASR circuit."
        DEFVAL  { create }
        ::= { wfAsrCircuitEntry 1 }

    wfAsrCircuitEnable OBJECT-TYPE
        SYNTAX  INTEGER {
                    enable(1),
                    disable(2)
                }
        ACCESS  read-write
        STATUS  mandatory
        DESCRIPTION
                "Enable/Disable parameter. Default is enabled.
                Users perform a set operation on this
                object in order to enable/disable an ASR circuit."
        DEFVAL  { enable }
        ::= { wfAsrCircuitEntry 2 }

    wfAsrCircuitState OBJECT-TYPE
        SYNTAX  INTEGER {
                    up(1),
                    down(2),
                    init(3),
                    invalid(4),
                    notpres(5)
                }
        ACCESS  read-only
        STATUS  mandatory
        DESCRIPTION
                "Invalid indicates an error in processing the cfg record"
        DEFVAL  { notpres }
        ::= { wfAsrCircuitEntry 3 }


    wfAsrCircuitNumber OBJECT-TYPE
        SYNTAX  INTEGER
        ACCESS  read-only
        STATUS  mandatory
        DESCRIPTION
                "Instance identifier.  The circuit number of this interface."
        ::= { wfAsrCircuitEntry 4 }

    wfAsrCircuitCallCtrl OBJECT-TYPE
        SYNTAX  INTEGER
               {
                    inboundonly (1),
                    outboundonly (2),
                    inboundandoutbound (3),
                    none (4)
                }
  
        ACCESS  read-write
        STATUS  mandatory
        DESCRIPTION
                "Define call policy for this SVC circuit. 1) allow inbound calls                 only 2) allow outbound calls only 3)allow inbound and outbound                  calls 4) allow neither inbound or outbound calls."
        DEFVAL { outboundonly }
       ::= { wfAsrCircuitEntry 5 } 

    wfAsrCircuitInReceives OBJECT-TYPE
        SYNTAX  Counter
        ACCESS  read-only
        STATUS  mandatory
        DESCRIPTION
                "The total number of input datagrams received at the circuit,
                including those received in error."
        ::= { wfAsrCircuitEntry 6 }

    wfAsrCircuitInDiscards OBJECT-TYPE
        SYNTAX  Counter
        ACCESS  read-only
        STATUS  mandatory
        DESCRIPTION
                "The total number of input datagrams discarded due to failed
                setup attempts, unreachable destinations, etc."
        ::= { wfAsrCircuitEntry 7 }

    wfAsrCircuitSetupRequests OBJECT-TYPE
        SYNTAX  Counter
        ACCESS  read-only
        STATUS  mandatory
        DESCRIPTION
                "The total number of SVC setup requests attempted on the circuit
,
                including those which failed."
        ::= { wfAsrCircuitEntry 8 }

    wfAsrCircuitSetupSucc OBJECT-TYPE
        SYNTAX  Counter
        ACCESS  read-only
        STATUS  mandatory
        DESCRIPTION
                "The total number of SVC setup requests attempted on the circuit
                which resulted in an SVC being established."
        ::= { wfAsrCircuitEntry 9 }

    wfAsrCircuitSetupFail OBJECT-TYPE
        SYNTAX  Counter
        ACCESS  read-only
        STATUS  mandatory
        DESCRIPTION
                "The total number of SVC setup requests attempted on the circuit
                which resulted in an SVC not being established."
        ::= { wfAsrCircuitEntry 10 }

   wfAsrCircuitSVCsEstablished OBJECT-TYPE
        SYNTAX  Counter
        ACCESS  read-only
        STATUS  mandatory
        DESCRIPTION
                "The total number of SVCs currently established on the circuit."
        ::= { wfAsrCircuitEntry 11 }

   wfAsrNegativeNHR OBJECT-TYPE
        SYNTAX  Counter
        ACCESS  read-only	
        STATUS  mandatory
        DESCRIPTION	
                "Count of negative NHR responses received from NHRP."
        ::= { wfAsrCircuitEntry 12 }

   wfAsrSvcOutboundReqFail OBJECT-TYPE
        SYNTAX  Counter
        ACCESS  read-only
        STATUS  mandatory
        DESCRIPTION
                "Count of outbound requests for SVCs that failed."
        ::= { wfAsrCircuitEntry 13 }

   wfAsrSvcInboundFilterFail OBJECT-TYPE
        SYNTAX   Counter
        ACCESS   read-only
        STATUS   mandatory
        DESCRIPTION
                "Count of inbound packets failing inbound packet filtering."
        ::= { wfAsrCircuitEntry 14 }
  
   wfAsrSvcInboundCallValFail OBJECT-TYPE
        SYNTAX    Counter
        ACCESS    read-only
        STATUS    mandatory
        DESCRIPTION
                "Count of inbound SVC call validation failures."
        ::= { wfAsrCircuitEntry 15 }

   wfAsrFiltTable OBJECT-TYPE
        SYNTAX  SEQUENCE OF WfAsrFiltEntry
        ACCESS  not-accessible
        STATUS  mandatory
        DESCRIPTION
                "A table containing setup information related to an SVC.
                 The table is indexed by slot,dest ip addr and mask, source
                 ip addr and mask, source and dest port ranges and protocol."
        ::= { wfAsrGroup 7 }

   wfAsrFiltEntry OBJECT-TYPE
        SYNTAX  WfAsrFiltEntry
        ACCESS  not-accessible
        STATUS  mandatory
        DESCRIPTION
               "ASR SVC setup information."
        INDEX  {  wfAsrFilterSlot,
                  wfAsrDestIpAddr,
                  wfAsrDestIpMask,
                  wfAsrSourceIpAddr,
                  wfAsrSourceIpMask,
                  wfAsrDestPortRangeLow,
                  wfAsrDestPortRangeHigh,
                  wfAsrSourcePortRangeLow,
                  wfAsrSourcePortRangeHigh,
                  wfAsrIPProtocol
                  }
        ::= { wfAsrFiltTable 1 }

   WfAsrFiltEntry ::= SEQUENCE {

          wfAsrFilterCreate
              INTEGER,
          wfAsrFilterSlot
              INTEGER,
          wfAsrDestIpAddr
              IpAddress,
          wfAsrDestIpMask
              IpAddress,
          wfAsrSourceIpAddr
              IpAddress,
          wfAsrSourceIpMask
              IpAddress,
          wfAsrDestPortRangeLow
              INTEGER,
          wfAsrDestPortRangeHigh
              INTEGER,
          wfAsrSourcePortRangeLow
              INTEGER,
          wfAsrSourcePortRangeHigh
              INTEGER,
          wfAsrIPProtocol
              INTEGER,
          wfAsrFilterTtl
              INTEGER,
          wfAsrFilterType
              DisplayString,

          wfAsrSvcCircuitNumber
              INTEGER,
          wfAsrSvcVcid1
              INTEGER,
          wfAsrSvcVcid2
              INTEGER,
          wfAsrSvcCalledAddr
              DisplayString,
          wfAsrSvcSetupTime
              INTEGER,
          wfAsrSvcType
              INTEGER,
          wfAsrSvcMTU
              INTEGER,
          wfAsrSvcRouterPriOut
              INTEGER,

          wfAsrFrSvcCIRIn
              INTEGER,
          wfAsrFrSvcCIROut
              INTEGER,
          wfAsrFrSvcBCIn
              INTEGER,
          wfAsrFrSvcBCOut
              INTEGER,
          wfAsrFrSvcBEIn
              INTEGER,
          wfAsrFrSvcBEOut
              INTEGER,
          wfAsrFrSvcX213Pri
              INTEGER,

          wfAsrAtmSvcPCRIn
              INTEGER,
          wfAsrAtmSvcPCROut
              INTEGER,
          wfAsrAtmSvcSCRIn
              INTEGER,
          wfAsrAtmSvcSCROut
              INTEGER,
          wfAsrAtmSvcMBSIn
              INTEGER,
          wfAsrAtmSvcMBSOut
              INTEGER,
          wfAsrAtmSvcQOSClassIn
              INTEGER,
          wfAsrAtmSvcQOSClassOut
              INTEGER,
          wfAsrAtmSvcCDVTIn
              INTEGER,
          wfAsrAtmSvcCDVTOut
              INTEGER,
          wfAsrAtmSvcCLRIn
              INTEGER,
          wfAsrAtmSvcCLROut
              INTEGER
    }

    wfAsrFilterCreate OBJECT-TYPE
      SYNTAX  INTEGER {
              created(1),
              deleted(2)
             }
      ACCESS  read-write
      STATUS  mandatory
      DESCRIPTION
              "Create/delete this filter entry."
      ::= { wfAsrFiltEntry 1 }

    wfAsrFilterSlot OBJECT-TYPE
         SYNTAX  INTEGER
         ACCESS  read-only
         STATUS  mandatory
         DESCRIPTION
                 "The router slot on which this filter exists."
         ::= { wfAsrFiltEntry 2 }

     wfAsrDestIpAddr OBJECT-TYPE
         SYNTAX  IpAddress
         ACCESS  read-only
         STATUS  mandatory
         DESCRIPTION
                 "Filter destination IP address reference value."
     ::= { wfAsrFiltEntry 3 }

     wfAsrDestIpMask OBJECT-TYPE
         SYNTAX  IpAddress
         ACCESS  read-only
         STATUS  mandatory
         DESCRIPTION
                 "Filter destination IP address mask."
     ::= { wfAsrFiltEntry 4 }

   wfAsrSourceIpAddr OBJECT-TYPE
         SYNTAX  IpAddress
         ACCESS  read-only
         STATUS  mandatory
         DESCRIPTION
                 "Filter source IP address reference value."
    ::= { wfAsrFiltEntry 5 }

    wfAsrSourceIpMask OBJECT-TYPE
         SYNTAX  IpAddress
         ACCESS  read-only
         STATUS  mandatory
         DESCRIPTION
                 "Filter source IP address mask."
    ::= { wfAsrFiltEntry 6 }

    wfAsrDestPortRangeLow OBJECT-TYPE
         SYNTAX  INTEGER
         ACCESS  read-only
         STATUS  mandatory
         DESCRIPTION
                "The low value for the range of TCP/UDP destination ports."
    ::= { wfAsrFiltEntry 7 }

    wfAsrDestPortRangeHigh OBJECT-TYPE
         SYNTAX  INTEGER
         ACCESS  read-only
         STATUS  mandatory
         DESCRIPTION
                 "The high value for the range of TCP/UDP destination ports."
    ::= { wfAsrFiltEntry 8 }

    wfAsrSourcePortRangeLow OBJECT-TYPE
         SYNTAX  INTEGER
         ACCESS  read-only
         STATUS  mandatory
         DESCRIPTION
                 "The low value for the range of TCP/UDP source ports."
    ::= { wfAsrFiltEntry 9 }

   wfAsrSourcePortRangeHigh OBJECT-TYPE
         SYNTAX  INTEGER
         ACCESS  read-only
         STATUS  mandatory
         DESCRIPTION
                 "The high value for the range of TCP/UDP source ports."
    ::= { wfAsrFiltEntry 10 }

    wfAsrIPProtocol OBJECT-TYPE
         SYNTAX  INTEGER
         ACCESS  read-only
         STATUS  mandatory
         DESCRIPTION
                 "IP protocol for this filter (TCP or UDP)."
    ::= { wfAsrFiltEntry 11 }

    wfAsrFilterTtl  OBJECT-TYPE
        SYNTAX  INTEGER
        ACCESS  read-only
        STATUS  mandatory
        DESCRIPTION
                "For SVC filters, this is the SVC idle time (seconds).  
                 For all other filter types, this is the filter expiration 
                 time (seconds)."
    ::= { wfAsrFiltEntry 12 }

    wfAsrFilterType OBJECT-TYPE
       SYNTAX DisplayString
       ACCESS read-only
       STATUS mandatory
       DESCRIPTION
               "Type of filter (SVC, NOSVC, in-progress, dest unreachable)."
       ::= { wfAsrFiltEntry 13 }

    wfAsrSvcCircuitNumber OBJECT-TYPE
         SYNTAX  INTEGER
         ACCESS  read-only
         STATUS  mandatory
         DESCRIPTION
                 "Circuit number on which the SVC is created."
    ::= { wfAsrFiltEntry 14 }

    wfAsrSvcVcid1 OBJECT-TYPE
         SYNTAX  INTEGER
         ACCESS  read-only
         STATUS  mandatory
         DESCRIPTION
                 "For Frame Relay SVCs, this is the DLCI value. 
                  For ATM SVCs, this is the VPI value."
   ::= { wfAsrFiltEntry 15 }

    wfAsrSvcVcid2 OBJECT-TYPE
         SYNTAX  INTEGER
         ACCESS  read-only
         STATUS  mandatory
         DESCRIPTION
                 "For ATM SVCs, this is the VCI value."
   ::= { wfAsrFiltEntry 16 }

    wfAsrSvcCalledAddr OBJECT-TYPE
        SYNTAX DisplayString
        ACCESS  read-only
        STATUS  mandatory
        DESCRIPTION
                "SVC Called Party Address"
    ::= { wfAsrFiltEntry 17 }

    wfAsrSvcSetupTime OBJECT-TYPE
       SYNTAX  INTEGER
       ACCESS  read-only
       STATUS  mandatory
       DESCRIPTION
               "Time stamp of when the SVC was created."
    ::= { wfAsrFiltEntry 18 }

    wfAsrSvcType OBJECT-TYPE
        SYNTAX  INTEGER {
                   fr(1),
                   atm(2)
                }
        ACCESS  read-write
        STATUS  mandatory
        DESCRIPTION
                "Type of SVC created (Frame Relay or ATM)."
       ::= { wfAsrFiltEntry 19 }

    wfAsrSvcMTU OBJECT-TYPE
         SYNTAX  INTEGER
         ACCESS  read-only
         STATUS  mandatory
         DESCRIPTION
                 "The maximum transmission unit for this SVC."
    ::= { wfAsrFiltEntry 20 }

    wfAsrSvcRouterPriOut OBJECT-TYPE
         SYNTAX  INTEGER
         ACCESS  read-only
         STATUS  mandatory
         DESCRIPTION
                 "The router priority queue to be used for the packets
                  sent on this SVC."
    ::= { wfAsrFiltEntry 21 }

    wfAsrFrSvcCIRIn OBJECT-TYPE
         SYNTAX  INTEGER
         ACCESS  read-only
         STATUS  mandatory
         DESCRIPTION
                 "Frame Relay SVC commited information rate - inbound (bps)."
    ::= { wfAsrFiltEntry 22 }

    wfAsrFrSvcCIROut OBJECT-TYPE
         SYNTAX  INTEGER
         ACCESS  read-only
         STATUS  mandatory
         DESCRIPTION
                 "Frame Relay SVC commited information rate - outbound (bps)."
    ::= { wfAsrFiltEntry 23 }

    wfAsrFrSvcBCIn OBJECT-TYPE
         SYNTAX  INTEGER
         ACCESS  read-only
         STATUS  mandatory
         DESCRIPTION
                 "Frame Relay commited burst rate for SVC - inbound (bps)."
    ::= { wfAsrFiltEntry 24 }

    wfAsrFrSvcBCOut OBJECT-TYPE
         SYNTAX  INTEGER
         ACCESS  read-only
         STATUS  mandatory
         DESCRIPTION
                 "Frame Relay commited burst rate for the SVC - outbound (bps)."
    ::= { wfAsrFiltEntry 25 }

    wfAsrFrSvcBEIn OBJECT-TYPE
         SYNTAX  INTEGER
         ACCESS  read-only
         STATUS  mandatory
         DESCRIPTION
                 "Frame Relay excess burst rate for the SVC - inbound (bps)."
    ::= { wfAsrFiltEntry 26 }

    wfAsrFrSvcBEOut OBJECT-TYPE
         SYNTAX  INTEGER
         ACCESS  read-only
         STATUS  mandatory
         DESCRIPTION
                 "Frame Relay excess burst rate for the SVC - outbound (bps)."
    ::= { wfAsrFiltEntry 27 }

    wfAsrFrSvcX213Pri OBJECT-TYPE
         SYNTAX  INTEGER
         ACCESS  read-only
         STATUS  mandatory
         DESCRIPTION
                 "Frame Relay SVC X.213 data priority value passed 
                  to the switch during call setup."
    ::= { wfAsrFiltEntry 28 }

    wfAsrAtmSvcPCRIn OBJECT-TYPE
         SYNTAX  INTEGER
         ACCESS  read-only
         STATUS  mandatory
         DESCRIPTION
                 "ATM SVC Peak Cell Rate - inbound."
    ::= { wfAsrFiltEntry 29 }

    wfAsrAtmSvcPCROut OBJECT-TYPE
         SYNTAX  INTEGER
         ACCESS  read-only
         STATUS  mandatory
         DESCRIPTION
                 "ATM SVC Peak Cell Rate - outbound."
    ::= { wfAsrFiltEntry 30 }

    wfAsrAtmSvcSCRIn OBJECT-TYPE
         SYNTAX  INTEGER
         ACCESS  read-only
         STATUS  mandatory
         DESCRIPTION
                 "ATM SVC Sustainable Cell Rate - inbound."
    ::= { wfAsrFiltEntry 31 }

    wfAsrAtmSvcSCROut OBJECT-TYPE
         SYNTAX  INTEGER
         ACCESS  read-only
         STATUS  mandatory
         DESCRIPTION
                 "ATM SVC Sustainable Cell Rate - outbound."
    ::= { wfAsrFiltEntry 32 }

    wfAsrAtmSvcMBSIn OBJECT-TYPE
         SYNTAX  INTEGER
         ACCESS  read-only
         STATUS  mandatory
         DESCRIPTION
                 "ATM SVC Maximum Burst Size - inbound."
    ::= { wfAsrFiltEntry 33 }

    wfAsrAtmSvcMBSOut OBJECT-TYPE
         SYNTAX  INTEGER
         ACCESS  read-only
         STATUS  mandatory
         DESCRIPTION
                 "ATM SVC Maximum Burst Size - outbound."
    ::= { wfAsrFiltEntry 34 }

    wfAsrAtmSvcQOSClassIn OBJECT-TYPE
         SYNTAX  INTEGER
         ACCESS  read-only
         STATUS  mandatory
         DESCRIPTION
                 "ATM SVC Quality of Service - inbound.  Class 0 through 4."
    ::= { wfAsrFiltEntry 35 }

    wfAsrAtmSvcQOSClassOut OBJECT-TYPE
         SYNTAX  INTEGER
         ACCESS  read-only
         STATUS  mandatory
         DESCRIPTION
                 "ATM SVC Quality of Service - outbound.  Class 0 through 4."
    ::= { wfAsrFiltEntry 36 }

    wfAsrAtmSvcCDVTIn OBJECT-TYPE
         SYNTAX  INTEGER
         ACCESS  read-only
         STATUS  mandatory
         DESCRIPTION
                 "ATM SVC Cell Delay Variation Tolerance - inbound."
    ::= { wfAsrFiltEntry 37 }

    wfAsrAtmSvcCDVTOut OBJECT-TYPE
         SYNTAX  INTEGER
         ACCESS  read-only
         STATUS  mandatory
         DESCRIPTION
                 "ATM SVC Cell Delay Variation Tolerance - outbound."
    ::= { wfAsrFiltEntry 38 }

    wfAsrAtmSvcCLRIn OBJECT-TYPE
         SYNTAX  INTEGER
         ACCESS  read-only
         STATUS  mandatory
         DESCRIPTION
                 "ATM SVC Cell Loss Ratio - inbound."
    ::= { wfAsrFiltEntry 39 }

    wfAsrAtmSvcCLROut OBJECT-TYPE
         SYNTAX  INTEGER
         ACCESS  read-only
         STATUS  mandatory
         DESCRIPTION
                 "ATM SVC Cell Loss Ratio - outbound."
    ::= { wfAsrFiltEntry 40 }


wfAsrTest  OBJECT IDENTIFIER ::= { wfAsrGroup 8 }

wfAsrTestCreate OBJECT-TYPE
     SYNTAX  INTEGER {
                 created(1),
                 deleted(2)
             }
         ACCESS  read-write
         STATUS  mandatory
         DESCRIPTION
                 "Create/Delete parameter.  Default is created.
                 Users perform a set operation on this
                 object in order to create/delete ASR Test Object."
         DEFVAL  { created }
         ::= { wfAsrTest 1 }

    wfAsrTestChangeVal OBJECT-TYPE
        SYNTAX  INTEGER
        ACCESS  read-write
        STATUS  mandatory
        DESCRIPTION
                "Value to set the protocol field in the ASR
                Fwd Table. This will take the SVC entry
                matching the Dlci and Cct number and change
                the filter. This is used only for Inbound Pkt
                Filtering tests"
        DEFVAL  { 6 }
        ::= { wfAsrTest 2 }

    wfAsrTestDlci OBJECT-TYPE
        SYNTAX  INTEGER
        ACCESS  read-write
        STATUS  mandatory
        DESCRIPTION
                "Dlci of SVC Filter entry to change"
        ::= { wfAsrTest 3 }

    wfAsrTestCct OBJECT-TYPE
        SYNTAX  INTEGER
        ACCESS  read-write
        STATUS  mandatory
        DESCRIPTION
                "Circuit number of SVC Filter to change"
        ::= { wfAsrTest 4 }

END -- Wellfleet-ASR-MIB
