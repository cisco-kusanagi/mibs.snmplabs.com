-- $Header:   K:/WanSuite/archives/include/pvcs/ds8200.mib,v   1.7   08 Mar 2000 19:28:58   richardm  $

INTERFACES-MIB DEFINITIONS ::= BEGIN

IMPORTS enterprises, TimeTicks				FROM RFC1155-SMI
	OBJECT-TYPE					FROM RFC-1212
	DisplayString					FROM RFC1213-MIB;

txport          OBJECT IDENTIFIER ::= { enterprises 425}
companyinfo     OBJECT IDENTIFIER ::= { txport 1 }
products        OBJECT IDENTIFIER ::= { txport 2 }
temporary       OBJECT IDENTIFIER ::= { txport 3 }
traps           OBJECT IDENTIFIER ::= { txport 4 }
revision        OBJECT IDENTIFIER ::= { txport 5 }
pdc             OBJECT IDENTIFIER ::= { txport 6 }
utilities       OBJECT IDENTIFIER ::= { txport 7 }

-- Above are pre-existing.  That is, created prior to August 1998.
-- Following were created after August 1998, and are intended to
-- be generic in that they can be used across multiple products
-- to define and manage technologies.  Each generic group is optional,
-- in that a given device need not support all technologies.

tinterfaces     OBJECT IDENTIFIER ::= { txport 8 }
mgmtPorts       OBJECT IDENTIFIER ::= { tinterfaces 1 }
dbu             OBJECT IDENTIFIER ::= { tinterfaces 2 }
t1e1            OBJECT IDENTIFIER ::= { tinterfaces 3 }
ddsNet          OBJECT IDENTIFIER ::= { tinterfaces 4 }
serialDte       OBJECT IDENTIFIER ::= { tinterfaces 5 }
analogDte       OBJECT IDENTIFIER ::= { tinterfaces 6 }
connection      OBJECT IDENTIFIER ::= { tinterfaces 7 }
maintenance     OBJECT IDENTIFIER ::= { tinterfaces 8 }
performance     OBJECT IDENTIFIER ::= { tinterfaces 9 }
itable          OBJECT IDENTIFIER ::= { tinterfaces 10 }
traplog         OBJECT IDENTIFIER ::= { tinterfaces 11 }
unitUtilities   OBJECT IDENTIFIER ::= { tinterfaces 12 }


-- mgmtPorts section
-- this section contains the configuration settings for the management ports 

mgmtPortsTable  OBJECT-TYPE
	SYNTAX  SEQUENCE OF MgmtPortsTableEntry
	ACCESS  not-accessible
	STATUS  optional
	DESCRIPTION
		"The Management Ports table."
	::= { mgmtPorts 1 }

mgmtPortsTableEntry     OBJECT-TYPE
	SYNTAX  MgmtPortsTableEntry
	ACCESS  not-accessible
	STATUS  mandatory
	DESCRIPTION
		"An entry in the Management Ports table."
	INDEX   { mgmtPortsTableIndex }
	::= { mgmtPortsTable 1 }

MgmtPortsTableEntry ::=
	SEQUENCE
	{
	mgmtPortsTableIndex             INTEGER,
	mgmtPortsDescription            DisplayString,
	mgmtPortsElementID              DisplayString,
	mgmtPortsMode                   INTEGER,
	mgmtPortsDialPrefix             DisplayString,
	mgmtPortsPrimaryDialString      DisplayString,
	mgmtPortsSecondaryDialString    DisplayString,
	mgmtPortsExtInitString          DisplayString,
	mgmtPortsCompressedSlip         INTEGER,
	mgmtPortsInternalModem          INTEGER
	}

mgmtPortsTableIndex     OBJECT-TYPE
	SYNTAX  INTEGER
	ACCESS  read-only
	STATUS  mandatory
	DESCRIPTION
		"The index into the Management Ports table."
	::= { mgmtPortsTableEntry 1 }

mgmtPortsDescription    OBJECT-TYPE
	SYNTAX  DisplayString( SIZE(0..40) )
	ACCESS  read-only
	STATUS  mandatory
	DESCRIPTION
		"Contains a textual description of the port."
	::= { mgmtPortsTableEntry 2 }

mgmtPortsElementID      OBJECT-TYPE
	SYNTAX  DisplayString( SIZE(0..27) )
	ACCESS  read-write
	STATUS  mandatory
	DESCRIPTION
		"This object signifies the name of the device."
	::= { mgmtPortsTableEntry 3 }

mgmtPortsMode   OBJECT-TYPE
	SYNTAX  INTEGER
		{
		other(1),
		disabled(2),
		coadial(3),
		coadirect(4),
		extAlarmOnOpen(5),
		extAlarmOnClosed(6),
		slipdial(7),
		slipdirect(8)
		}
	ACCESS  read-write
	STATUS  mandatory
	DESCRIPTION
		"This object signifies the method used by the port to report alarms."
	::= { mgmtPortsTableEntry 4 }

mgmtPortsDialPrefix     OBJECT-TYPE
	SYNTAX  DisplayString( SIZE(0..38) )
	ACCESS  read-write
	STATUS  mandatory
	DESCRIPTION
		"This object contains the dial string prefix for a modem connected to the port."
	::= { mgmtPortsTableEntry 5 }

mgmtPortsPrimaryDialString      OBJECT-TYPE
	SYNTAX  DisplayString( SIZE(0..30) )
	ACCESS  read-write
	STATUS  mandatory
	DESCRIPTION
		"This object contains the primary dial string for a modem connected to the port."
	::= { mgmtPortsTableEntry 6 }

mgmtPortsSecondaryDialString    OBJECT-TYPE
	SYNTAX  DisplayString( SIZE(0..30) )
	ACCESS  read-write
	STATUS  mandatory
	DESCRIPTION
		"This object contains the secondary dial string for a modem connected to the port."
	::= { mgmtPortsTableEntry 7 }

mgmtPortsExtInitString  OBJECT-TYPE
	SYNTAX  DisplayString( SIZE(0..38) )
	ACCESS  read-write
	STATUS  mandatory
	DESCRIPTION
		"This object contains the init string for a modem connected to the port."
	::= { mgmtPortsTableEntry 8 }
	
mgmtPortsCompressedSlip OBJECT-TYPE
	SYNTAX  INTEGER
		{
		other(1),
		enabled(2),
		disabled(3),
		auto(4)
		}
	ACCESS  read-write
	STATUS  mandatory
	DESCRIPTION
		"This object specifies if SLIP compression is to be used."
	::= { mgmtPortsTableEntry 9 }

mgmtPortsInternalModem OBJECT-TYPE
	SYNTAX  INTEGER
		{
		other(1),
		notPresent(2),
		enabled(3),
		disabled(4)
		}
	ACCESS  read-write
	STATUS  mandatory
	DESCRIPTION
		"This object signifies if the internal modem (when present) is enabled."
	::= { mgmtPortsTableEntry 10 }

-- dbu section
-- dial backup options for TxPort devices which have integrated or 
-- optional dial backup units

dbuConfigTable  OBJECT-TYPE
	SYNTAX  SEQUENCE OF DbuConfigTableEntry
	ACCESS  not-accessible
	STATUS  optional
	DESCRIPTION
		"The Dial Backup Configuration Table."
	::= { dbu 1 }

dbuConfigTableEntry     OBJECT-TYPE
	SYNTAX  DbuConfigTableEntry
	ACCESS  not-accessible
	STATUS  mandatory
	DESCRIPTION
		"An entry in the Dial Backup Configuration table."
	INDEX   { dbuNearIndex, dbuFarIndex, dbuConfigTableIndex }
	::= { dbuConfigTable 1 }

DbuConfigTableEntry ::=
	SEQUENCE
	{
	dbuNearIndex            INTEGER,
	dbuFarIndex             INTEGER,
	dbuConfigTableIndex     INTEGER,
	dbuDescription          DisplayString,
	dbuRate                 INTEGER,
	dbuMode                 INTEGER,
	dbuFormat               INTEGER,
	dbuNumber               DisplayString,
	dbuStatus               INTEGER,
	dbuCommand              INTEGER,
	dbuActivator1           INTEGER,
	dbuActivator2           INTEGER,
	dbuDialStr              DisplayString,
	dbuInitStr              DisplayString,
	dbuHangupStr            DisplayString,
	dbuPasswordStr          DisplayString,
	dbuSecurity             INTEGER,
	dbuDtrDial              INTEGER,
	dbuISDNSwitchType       INTEGER,
	dbuISDNSwitchVersion    INTEGER,
	dbuISDNTEI              INTEGER,
	dbuISDNSPID             DisplayString,
	dbuISDNDDNUM            DisplayString
	}

dbuNearIndex            OBJECT-TYPE
	SYNTAX  INTEGER
	ACCESS  read-only
	STATUS  mandatory
	DESCRIPTION
		"Selects the near device."
	::= { dbuConfigTableEntry 1 }

dbuFarIndex             OBJECT-TYPE
	SYNTAX  INTEGER
	ACCESS  read-only
	STATUS  mandatory
	DESCRIPTION
		"Selects the far device."
	::= { dbuConfigTableEntry 2 }
 
dbuConfigTableIndex     OBJECT-TYPE
	SYNTAX  INTEGER
	ACCESS  read-only
	STATUS  mandatory
	DESCRIPTION
		"The index into the Dial Backup table."
	::= { dbuConfigTableEntry 3 }

dbuDescription  OBJECT-TYPE
	SYNTAX  DisplayString( SIZE(0..40) )
	ACCESS  read-only
	STATUS  mandatory
	DESCRIPTION
		"Contains a textual description of the dbu."
	::= { dbuConfigTableEntry 4 }

dbuRate OBJECT-TYPE
	SYNTAX  INTEGER 
		{
		dbuRateOther(1),
		dbuRate2400(2),
		dbuRate4800(3),
		dbuRate9600(4),
		dbuRate19200(5),
		dbuRate38400(6),
		dbuRate56000(7),
		dbuRate57600(8),
		dbuRate64000(9)
		}
	ACCESS  read-write
	STATUS  mandatory
	DESCRIPTION
		"This object is the identifier of the current DDS
DBU rate. The values mean:
dbuRate2400
   the DBU interface is operating at 2400bps
dbuRate4800
   the DBU interface is operating at 4800bps
dbuRate9600
   the DBU interface is operating at 9600bps
dbuRate19200
   the DBU interface is operating at 19200bps
dbuRate38400
   the DBU interface is operating at 38400bps
dbuRate56000
   the DBU interface is operating at 56000bps
dbuRate57600
   the DBU interface is operating at 57600bps
dbuRate64000
   the DBU interface is operating at 64000bps"
	::=  { dbuConfigTableEntry 5 }

dbuMode OBJECT-TYPE
	SYNTAX  INTEGER 
		{
		dbuModeOther(1),
		dbuModeOrig(2),
		dbuModeAnsw(3),
		dbuModeNotAvail(4),
		dbuModeCallbackOrig(5),
		dbuModeCallbackAnsw(6),
		dbuModeMaster(7),
		dbuModeSlave(8)
		}
	ACCESS  read-write
	STATUS  mandatory
	DESCRIPTION
		"This object is the identifier of the current
mode that the Dial Backup Unit is operating
in. The values mean:
dbuModeOrig
   The dial backup unit is operating in the
   originate mode
dbuModeAnsw
   The dial backup unit is operating in the
   answer mode
dbuModeNotAvail
   The dial backup unit's mode is not
   available
dbuModeCallbackOrig
   The dial backup unit is operating in the
   callback originate mode
dbuModeCallbackAnsw
   The dial backup unit is operating in the
   callback mode
dbuModeMaster
   The dial backup unit is configured as a 
   master unit 
dbuModeSlave
   The dial backup unit is configured as a
   slave unit"
	::=  { dbuConfigTableEntry 6 }

dbuFormat       OBJECT-TYPE
	SYNTAX  INTEGER 
		{
		dbuFormatOther(1),
		dbuFormatSync(2),
		dbuFormatAsync(3),
		dbuFormatNotAvail(4)
		}
	ACCESS  read-write
	STATUS  mandatory
	DESCRIPTION
		"This object is the identifier of the current
format that the Dial Backup Unit is operating
in. The values mean:
dbuFormatSync
   The dial backup unit is operating in the
   synchronous format
dbuFormatAsync
   The dial backup unit is operating in the
   asynchronous format
dbuFormatNotAvail
   The dial backup unit's format is
   not available"
	::=  { dbuConfigTableEntry 7 }

dbuNumber       OBJECT-TYPE
	SYNTAX  DisplayString( SIZE(0..100) )
	ACCESS  read-write
	STATUS  mandatory
	DESCRIPTION
		"This string is the currently programmed number
for the dial backup unit to call"
	::=  { dbuConfigTableEntry 8 }

dbuStatus       OBJECT-TYPE
	SYNTAX  INTEGER 
		{
		dbuStatusOther(1),
		dbuStatusDisabled(2),
		dbuStatusEnabled(3),
		dbuStatusActive(4),
		dbuStatusLocked(5),
		dbuStatusConnecting(6),
		dbuStatusDisallowed(7),
		dbuStatusAwaitingCall(8),
		dbuStatusDialing(9),
		dbuStatusDisconnecting(10),
		dbuStatusTesting(11),
		dbuStatusTestPassed(12),
		dbuStatusTestFailed(13)
		}
	ACCESS  read-only
	STATUS  mandatory
	DESCRIPTION
		"This object is the identifier of the current
Dial Backup Unit operating status.
The values mean:
dbuStatusDisabled
   The dial backup unit is either not
   installed or disabled
dbuStatusEnabled
   The dial backup unit is installed
   and enabled
dbuStatusActive
   The dial backup unit is currently
   active
dbuStatusLocked
   The dial backup unit is in a locked
   state
dbuStatusConnecting
   The dial backup unit is in the process
   of connecting
dbuStatusDisallowed
   The dial backup unit is currently not
   allowed to activate due to the Time
   Of Day Enable settings
dbuStatusAwaitingCall
   The dial backup unit is in the process
   of waiting for an incoming call
dbuStatusDialing
   The dial backup unit is in the process
   of placing a call
dbuStatusDisconnecting
   The dial backup unit is in the process
   of disconnecting
dbuStatusTesting
   The dial backup unit is in the process 
   of testing
dbuStatusTestPassed
   The dial backup unit has passed a self-test
dbuStatusTestFailed
   The dial backup unit has failed a self-test"
	::=  { dbuConfigTableEntry 9 }

dbuCommand      OBJECT-TYPE
	SYNTAX  INTEGER 
		{
		dbuCommandOther(1),
		dbuCommandDisable(2),
		dbuCommandEnable(3),
		dbuCommandActivate(4),
		dbuCommandLock(5),
		dbuCommandEnableDaily(6),
		dbuCommandTest(7)
		}
	ACCESS  read-write
	STATUS  mandatory
	DESCRIPTION
		"This object is the identifier of the current
setting that the Dial Backup Unit is operating
in. The values mean:
dbuCommandDisable
   The dial backup unit is not to operate
dbuCommandEnable
   The dial backup unit is to operate, subject
   to Activator and line conditions only
dbuCommandActivate
   The dial backup unit is to operate,
   irregardless of line conditions
dbuCommandLock
   The dial backup unit is to continue operating,
   irregardless of line conditions
dbuCommandEnableDaily
   The dial backup unit is to operate, subject
   to Activator, line conditions, and the Time
   Of Day Enable fields
dbuCommandTest
   The dial backup unit is commanded to test
   the link."
	::=  { dbuConfigTableEntry 10 }

dbuActivator1   OBJECT-TYPE
	SYNTAX  INTEGER 
		{
		dbuActivatorOther(1),
		dbuActivatorLOS(2),
		dbuActivatorOOS(3),
		dbuActivatorOOF(4),
		dbuActivatorAny(5),
		dbuActivatorES(6),
		dbuActivatorSES(7),
		dbuActivatorUAS(8),
		dbuActivatorLOF(9),
		dbuActivatorRAS(10),
		dbuActivatorAIS(11),
		dbuActivatorBPV(12)
		}
	ACCESS  read-write
	STATUS  mandatory
	DESCRIPTION
		"This object is the identifier of the current
trigger that will activate the Dial Backup
Unit. The values mean:
dbuActivatorLOS
   The dial backup unit is activated by a
   LOS alarm condition
dbuActivatorOOS
   The dial backup unit is activated by an
   OOS alarm condition
dbuActivatorOOF
   The dial backup unit is activated by an
   OOF alarm condition
dbuActivatorAny
   The dial backup unit is activated by a
   LOS, OOS, or OOF alarm condition
dbuActivatorES
   The dial backup unit is activated by an
   ES alarm condition
dbuActivatorSES
   The dial backup unit is activated by an
   SES alarm condition
dbuActivatorUAS
   The dial backup unit is activated by an
   UAS alarm condition
dbuActivatorLOF
   The dial backup unit is activated by an
   LOF alarm condition
dbuActivatorRAS
   The dial backup unit is activated by an
   RAS alarm condition
dbuActivatorAIS
   The dial backup unit is activated by an
   AIS alarm condition
dbuActivatorBPV
   The dial backup unit is activated by an
   BPV alarm condition"
	::=  { dbuConfigTableEntry 11 }

dbuActivator2   OBJECT-TYPE
	SYNTAX  INTEGER 
		{
		dbuActivatorOther(1),
		dbuActivatorLOS(2),
		dbuActivatorOOS(3),
		dbuActivatorOOF(4),
		dbuActivatorAny(5),
		dbuActivatorES(6),
		dbuActivatorSES(7),
		dbuActivatorUAS(8),
		dbuActivatorLOF(9),
		dbuActivatorRAS(10),
		dbuActivatorAIS(11),
		dbuActivatorBPV(12)
		}
	ACCESS  read-write
	STATUS  mandatory
	DESCRIPTION
		"This object is the identifier of the current
trigger that will activate the Dial Backup
Unit. The values mean:
dbuActivatorLOS
   The dial backup unit is activated by a
   LOS alarm condition
dbuActivatorOOS
   The dial backup unit is activated by a
   OOS alarm condition
dbuActivatorOOF
   The dial backup unit is activated by a
   OOF alarm condition
dbuActivatorAny
   The dial backup unit is activated by a
   LOS, OOS, or OOF alarm condition
dbuActivatorES
   The dial backup unit is activated by an
   ES alarm condition
dbuActivatorSES
   The dial backup unit is activated by an
   SES alarm condition
dbuActivatorUAS
   The dial backup unit is activated by an
   UAS alarm condition
dbuActivatorLOF
   The dial backup unit is activated by an
   LOF alarm condition
dbuActivatorRAS
   The dial backup unit is activated by an
   RAS alarm condition
dbuActivatorAIS
   The dial backup unit is activated by an
   AIS alarm condition
dbuActivatorBPV
   The dial backup unit is activated by an
   BPV alarm condition"
	::=  { dbuConfigTableEntry 12 }

dbuDialStr      OBJECT-TYPE
	SYNTAX  DisplayString( SIZE(0..50) )
	ACCESS  read-write
	STATUS  mandatory
	DESCRIPTION
		"This string is the dial string sent to the dial backup unit during every connection attempt"
	::=  { dbuConfigTableEntry 13 }
	
dbuInitStr      OBJECT-TYPE
	SYNTAX  DisplayString( SIZE(0..50) )
	ACCESS  read-write
	STATUS  mandatory
	DESCRIPTION
		"This string is the initialization string sent to the dial backup unit before every connection attempt"
	::=  { dbuConfigTableEntry 14 }

dbuHangupStr    OBJECT-TYPE
	SYNTAX  DisplayString( SIZE(0..50) )
	ACCESS  read-write
	STATUS  mandatory
	DESCRIPTION
		"This string is the hangup command string sent to the dial backup unit after every successful call"
	::=  { dbuConfigTableEntry 15 }

dbuPasswordStr  OBJECT-TYPE
	SYNTAX  DisplayString( SIZE(0..8) )
	ACCESS  read-write
	STATUS  mandatory
	DESCRIPTION
		"This string is the prompt character and password string for the dial backup unit in Callback DBU"
	::=  { dbuConfigTableEntry 16 }

dbuSecurity     OBJECT-TYPE
	SYNTAX  INTEGER
		{
		dbuSecurityOther(1),
		dbuSecurityDisable(2),
		dbuSecurityEnable(3)
		}
	ACCESS  read-write
	STATUS  mandatory
	DESCRIPTION
		"Enables security on dial backup unit."
	::= { dbuConfigTableEntry 17 }
	
dbuDtrDial      OBJECT-TYPE
	SYNTAX  INTEGER
		{
		dbuDtrDialOther(1),
		dbuDtrDialDisable(2),
		dbuDtrDialEnable(3)
		}
	ACCESS  read-write
	STATUS  mandatory
	DESCRIPTION
		"Enables DTR dial feature on dial backup unit."
	::= { dbuConfigTableEntry 18 }

dbuISDNSwitchType       OBJECT-TYPE
	SYNTAX  INTEGER
	ACCESS  read-write
	STATUS  mandatory
	DESCRIPTION
		"Specifies the switch type for the ISDN DBU."
	::= { dbuConfigTableEntry 19 }

dbuISDNSwitchVersion    OBJECT-TYPE
	SYNTAX  INTEGER
		{
		dbuISDNSwitchVersionOther(1),
		dbuISDNSwitchVersionNational1(2),
		dbuISDNSwitchVersionATTP2P(3),
		dbuISDNSwitchVersionATTMP(4),
		dbuISDNSwitchVersionDMS100PVCIC0(5),
		dbuISDNSwitchVersionDMS100PVCIC1(6)
		}
	ACCESS  read-write
	STATUS  mandatory
	DESCRIPTION
		"Specifies the switch version for the ISDN DBU."
	::= { dbuConfigTableEntry 20 }

dbuISDNTEI      OBJECT-TYPE
	SYNTAX  INTEGER
		{
		dbuISDNTEIOther(1),
		dbuISDNTEIDisable(2),
		dbuISDNTEIAuto(3),
		dbuISDNTEI0(4),
		dbuISDNTEI1(5),
		dbuISDNTEI2(6),
		dbuISDNTEI3(7),
		dbuISDNTEI4(8),
		dbuISDNTEI5(9),
		dbuISDNTEI6(10),
		dbuISDNTEI7(11),
		dbuISDNTEI8(12),
		dbuISDNTEI9(13),
		dbuISDNTEI10(14),
		dbuISDNTEI11(15),
		dbuISDNTEI12(16),
		dbuISDNTEI13(17),
		dbuISDNTEI14(18),
		dbuISDNTEI15(19),
		dbuISDNTEI16(20),
		dbuISDNTEI17(21),
		dbuISDNTEI18(22),
		dbuISDNTEI19(23),
		dbuISDNTEI20(24),
		dbuISDNTEI21(25),
		dbuISDNTEI22(26),
		dbuISDNTEI23(27),
		dbuISDNTEI24(28),
		dbuISDNTEI25(29),
		dbuISDNTEI26(30),
		dbuISDNTEI27(31),
		dbuISDNTEI28(32),
		dbuISDNTEI29(33),
		dbuISDNTEI30(34),
		dbuISDNTEI31(35),
		dbuISDNTEI32(36),
		dbuISDNTEI33(37),
		dbuISDNTEI34(38),
		dbuISDNTEI35(39),
		dbuISDNTEI36(40),
		dbuISDNTEI37(41),
		dbuISDNTEI38(42),
		dbuISDNTEI39(43),
		dbuISDNTEI40(44),
		dbuISDNTEI41(45),
		dbuISDNTEI42(46),
		dbuISDNTEI43(47),
		dbuISDNTEI44(48),
		dbuISDNTEI45(49),
		dbuISDNTEI46(50),
		dbuISDNTEI47(51),
		dbuISDNTEI48(52),
		dbuISDNTEI49(53),
		dbuISDNTEI50(54),
		dbuISDNTEI51(55),
		dbuISDNTEI52(56),
		dbuISDNTEI53(57),
		dbuISDNTEI54(58),
		dbuISDNTEI55(59),
		dbuISDNTEI56(60),
		dbuISDNTEI57(61),
		dbuISDNTEI58(62),
		dbuISDNTEI59(63),
		dbuISDNTEI60(64),
		dbuISDNTEI61(65),
		dbuISDNTEI62(66),
		dbuISDNTEI63(67)
		}
	ACCESS  read-write
	STATUS  mandatory
	DESCRIPTION
		"Specifies the ISDN DBU TEI."
	::= { dbuConfigTableEntry 21 }

dbuISDNSPID     OBJECT-TYPE
	SYNTAX  DisplayString(SIZE(0..20))
	ACCESS  read-write
	STATUS  mandatory
	DESCRIPTION
		"Specifies the SPID for the ISDN DBU."
	::= { dbuConfigTableEntry 22 }

dbuISDNDDNUM    OBJECT-TYPE
	SYNTAX  DisplayString(SIZE(0..20))
	ACCESS  read-write
	STATUS  mandatory
	DESCRIPTION
		"Specifies the Data Directory Number for the ISDN DBU."
	::= { dbuConfigTableEntry 23 }

dbuResetStringsTable    OBJECT-TYPE
	SYNTAX  SEQUENCE OF DbuResetStringsEntry
	ACCESS  not-accessible
	STATUS  mandatory
	DESCRIPTION
		"A table of COLD START reprogramming strings for the dial backup unit."
	::= { dbu 2 }

dbuResetStringsEntry    OBJECT-TYPE
	SYNTAX  DbuResetStringsEntry
	ACCESS  not-accessible
	STATUS  mandatory
	DESCRIPTION
		"An entry in the dbuResetStringsTable."
	INDEX   { dbuResetNearIndex, dbuResetFarIndex, dbuResetConfigEntryIndex, dbuResetStringsIndex }
	::= { dbuResetStringsTable 1 }

DbuResetStringsEntry ::=
	SEQUENCE
	{
	dbuResetNearIndex               INTEGER,
	dbuResetFarIndex                INTEGER,
	dbuResetConfigEntryIndex        INTEGER,
	dbuResetStringsIndex            INTEGER,
	dbuResetString                  DisplayString
	}

dbuResetNearIndex               OBJECT-TYPE
	SYNTAX  INTEGER
	ACCESS  read-only
	STATUS  mandatory
	DESCRIPTION
		"Selects the near device."
	::= { dbuResetStringsEntry 1 }

dbuResetFarIndex                OBJECT-TYPE
	SYNTAX  INTEGER
	ACCESS  read-only
	STATUS  mandatory
	DESCRIPTION
		"Selects the far device."
	::= { dbuResetStringsEntry 2 }

dbuResetConfigEntryIndex        OBJECT-TYPE
	SYNTAX  INTEGER
	ACCESS  read-only
	STATUS  mandatory
	DESCRIPTION
		"The index into the Dial Backup table."
	::= { dbuResetStringsEntry 3 }

dbuResetStringsIndex    OBJECT-TYPE
	SYNTAX  INTEGER
	ACCESS  read-only
	STATUS  mandatory
	DESCRIPTION
		"The index into the dbuResetStringsTable."
	::= { dbuResetStringsEntry 4 }

dbuResetString  OBJECT-TYPE
	SYNTAX  DisplayString( SIZE(0..50) )
	ACCESS  read-write
	STATUS  mandatory
	DESCRIPTION
		"This string is one of the dial backup unit's COLD START reprogramming strings"
	::=  { dbuResetStringsEntry 5 }

dbuStartStopTable       OBJECT-TYPE
	SYNTAX  SEQUENCE OF DbuStartStopTableEntry
	ACCESS  not-accessible
	STATUS  optional
	DESCRIPTION
		"The Dial Backup StartStop Table."
	::= { dbu 3 }

dbuStartStopTableEntry  OBJECT-TYPE
	SYNTAX  DbuStartStopTableEntry
	ACCESS  not-accessible
	STATUS  mandatory
	DESCRIPTION
		"An entry in the Dial Backup Start Stop table."
	INDEX   { dbuStartStopNearIndex, dbuStartStopFarIndex, dbuStartStopConfigEntryIndex, dbuStartStopDayOfWeek }
	::= { dbuStartStopTable 1 }

DbuStartStopTableEntry ::=
	SEQUENCE
	{
	dbuStartStopNearIndex           INTEGER,
	dbuStartStopFarIndex            INTEGER,
	dbuStartStopConfigEntryIndex    INTEGER,
	dbuStartStopDayOfWeek           INTEGER,
	dbuStart                        INTEGER,
	dbuStop                         INTEGER
	}

dbuStartStopNearIndex           OBJECT-TYPE
	SYNTAX  INTEGER
	ACCESS  read-only
	STATUS  mandatory
	DESCRIPTION
		"Selects the near device."
	::= { dbuStartStopTableEntry 1 }

dbuStartStopFarIndex            OBJECT-TYPE
	SYNTAX  INTEGER
	ACCESS  read-only
	STATUS  mandatory
	DESCRIPTION
		"Selects the far device."
	::= { dbuStartStopTableEntry 2 }

dbuStartStopConfigEntryIndex    OBJECT-TYPE
	SYNTAX  INTEGER
	ACCESS  read-only
	STATUS  mandatory
	DESCRIPTION
		"The index into the Dial Backup table."
	::= { dbuStartStopTableEntry 3 }

dbuStartStopDayOfWeek   OBJECT-TYPE
	SYNTAX  INTEGER
		{
		dbuStartStopSunday(1),
		dbuStartStopMonday(2),
		dbuStartStopTuesday(3),
		dbuStartStopWednesday(4),
		dbuStartStopThursday(5),
		dbuStartStopFriday(6),
		dbuStartStopSaturday(7)
		}
	ACCESS  read-only
	STATUS  mandatory
	DESCRIPTION
		"The index into the Dial Backup Start Stop times table."
	::= { dbuStartStopTableEntry 4 }

dbuStart        OBJECT-TYPE
	SYNTAX  INTEGER 
		{
		dbuStartHour00(1),
		dbuStartHour01(2),
		dbuStartHour02(3),
		dbuStartHour03(4),
		dbuStartHour04(5),
		dbuStartHour05(6),
		dbuStartHour06(7),
		dbuStartHour07(8),
		dbuStartHour08(9),
		dbuStartHour09(10),
		dbuStartHour10(11),
		dbuStartHour11(12),
		dbuStartHour12(13),
		dbuStartHour13(14),
		dbuStartHour14(15),
		dbuStartHour15(16),
		dbuStartHour16(17),
		dbuStartHour17(18),
		dbuStartHour18(19),
		dbuStartHour19(20),
		dbuStartHour20(21),
		dbuStartHour21(22),
		dbuStartHour22(23),
		dbuStartHour23(24)
		}
	ACCESS  read-write
	STATUS  mandatory
	DESCRIPTION
		"This object is the beginning of an allowable window for Dial Backup Activation."
	::=  { dbuStartStopTableEntry 5 }

dbuStop OBJECT-TYPE
	SYNTAX  INTEGER 
		{
		dbuStopHour00(1),
		dbuStopHour01(2),
		dbuStopHour02(3),
		dbuStopHour03(4),
		dbuStopHour04(5),
		dbuStopHour05(6),
		dbuStopHour06(7),
		dbuStopHour07(8),
		dbuStopHour08(9),
		dbuStopHour09(10),
		dbuStopHour10(11),
		dbuStopHour11(12),
		dbuStopHour12(13),
		dbuStopHour13(14),
		dbuStopHour14(15),
		dbuStopHour15(16),
		dbuStopHour16(17),
		dbuStopHour17(18),
		dbuStopHour18(19),
		dbuStopHour19(20),
		dbuStopHour20(21),
		dbuStopHour21(22),
		dbuStopHour22(23),
		dbuStopHour23(24)
		}
	ACCESS  read-write
	STATUS  mandatory
	DESCRIPTION
		"This object is the end of an allowable window for Dial Backup Activation."
	::=  { dbuStartStopTableEntry 6 }

-- t1e1 section, contains T1 and E1 Network and DTE interface table

t1e1ConfigTable OBJECT-TYPE
	SYNTAX  SEQUENCE OF T1e1ConfigTableEntry
	ACCESS  not-accessible
	STATUS  optional
	DESCRIPTION
		"The T1 and E1 Configuration Table."
	::= { t1e1 1 }

t1e1ConfigTableEntry    OBJECT-TYPE
	SYNTAX  T1e1ConfigTableEntry
	ACCESS  not-accessible
	STATUS  mandatory
	DESCRIPTION
		"An entry in the t1e1Table."
	INDEX   { t1e1ConfigNearIndex, t1e1ConfigFarIndex, t1e1ConfigIndex }
	::= { t1e1ConfigTable 1 }

T1e1ConfigTableEntry ::=
	SEQUENCE
	{
	t1e1ConfigNearIndex     INTEGER,
	t1e1ConfigFarIndex      INTEGER,
	t1e1ConfigIndex         INTEGER,
	t1e1Description         DisplayString,
	t1e1Mode                INTEGER,
	t1e1FrameType           INTEGER,
	t1e1LineCode            INTEGER,
	t1e1LineBuildOut        INTEGER,
	t1e1Timing              INTEGER,
	t1e1StationInTiming     INTEGER,
	t1e1StationTiming       INTEGER,
	t1e1PRM                 INTEGER,
	t1e1ZeroSuppress        INTEGER,
	t1e1NationalBit         INTEGER,
	t1e1KeepAlive           INTEGER,
	t1e1CRC4Mode            INTEGER,
	t1e1DSXLevel            INTEGER,
	t1e1CRC                 INTEGER,
	t1e1FDLPassThrough      INTEGER,
	t1e1AudibleAlarm        INTEGER
	}

t1e1ConfigNearIndex             OBJECT-TYPE
	SYNTAX  INTEGER
	ACCESS  read-only
	STATUS  mandatory
	DESCRIPTION
		"Selects the near device."
	::= { t1e1ConfigTableEntry 1 }

t1e1ConfigFarIndex              OBJECT-TYPE
	SYNTAX  INTEGER
	ACCESS  read-only
	STATUS  mandatory
	DESCRIPTION
		"Selects the far device."
	::= { t1e1ConfigTableEntry 2 }

t1e1ConfigIndex         OBJECT-TYPE
	SYNTAX  INTEGER
	ACCESS  read-only
	STATUS  mandatory
	DESCRIPTION
		"This object is the index into the t1e1Table."
	::= { t1e1ConfigTableEntry 3 }

t1e1Description OBJECT-TYPE
	SYNTAX  DisplayString( SIZE(0..40) )
	ACCESS  read-only
	STATUS  mandatory
	DESCRIPTION
		"Contains a textual description of the port."
	::= { t1e1ConfigTableEntry 4 }

t1e1Mode        OBJECT-TYPE
	SYNTAX  INTEGER
		{
		t1e1ModeOther(1),
		t1e1ModeDTE(2),
		t1e1ModeNetwork(3)
		}
	ACCESS  read-write
	STATUS  mandatory
	DESCRIPTION
		"This object identifies the port as either a Network (long-haul) or DTE (short-haul) port."
	::= { t1e1ConfigTableEntry 5 }

t1e1FrameType   OBJECT-TYPE
	SYNTAX  INTEGER
		{
		t1e1FrameTypeOther(1),
		t1e1FrameTypeESF(2),
		t1e1FrameTypeD4(3),
		t1e1FrameTypeCCSCRC(4),
		t1e1FrameTypeCCS(5),
		t1e1FrameTypeCAS(6),
		t1e1FrameTypeCASCRC(7),
		t1e1FrameTypeUnframed(8)
		}
	ACCESS  read-write
	STATUS  mandatory
	DESCRIPTION     
		"Selects the framing for the network side of the DSU/CSU."
	::= { t1e1ConfigTableEntry 6 }

t1e1LineCode    OBJECT-TYPE
	SYNTAX  INTEGER
		{
		t1e1LineCodeOther(1),
		t1e1LineCodeAMI(2),
		t1e1LineCodeB8ZS(3),
		t1e1LineCodeHDB3(4)     
		}
	ACCESS  read-write
	STATUS  mandatory
	DESCRIPTION
		"Selects the network side line coding."
	::= { t1e1ConfigTableEntry 7 }

t1e1LineBuildOut        OBJECT-TYPE
	SYNTAX  INTEGER
		{
		t1e1LineBuildOutOther(1),
		t1e1LineBuildOut0db(2),
		t1e1LineBuildOut75db(3),
		t1e1LineBuildOut15db(4),
		t1e1LineBuildOut225db(5)
		}
	ACCESS  read-write
	STATUS  mandatory
	DESCRIPTION
		"Selects the line build out for the network interface.  The options are:
t1e1LineBuildOut0db     indicates a line build out of 0db
t1e1LineBuildOut75db   indicates a line build out of -7.5db
t1e1LineBuildOut15db    indicates a line build out of -15db
t1e1LineBuildOut225db  indicates a line build out of -22.5db"
	::= { t1e1ConfigTableEntry 8 }

t1e1Timing      OBJECT-TYPE
	SYNTAX  INTEGER
		{
		t1e1TimingOther(1),
		t1e1TimingInternal(2),
		t1e1TimingNetwork(3),
		t1e1TimingT1DTE(4),
		t1e1TimingStation(5),
		t1e1TimingStaClock(6),

		t1e1TimingPort1(7),
		t1e1TimingPort2(8),
		t1e1TimingPort3(9),
		t1e1TimingPort4(10),
		t1e1TimingPort5(11),
		t1e1TimingPort6(12),
		t1e1TimingPort7(13),
		t1e1TimingPort8(14),
		t1e1TimingPort9(15),
		t1e1TimingPort10(16),
		t1e1TimingPort11(17),
		t1e1TimingPort12(18),
		t1e1TimingPort13(19),
		t1e1TimingPort14(20),
		t1e1TimingPort15(21),
		t1e1TimingPort16(22),
		t1e1TimingPort17(23),
		t1e1TimingPort18(24),
		t1e1TimingPort19(25),
		t1e1TimingPort20(26),
		t1e1TimingPort21(27),
		t1e1TimingPort22(28),
		t1e1TimingPort23(29),
		t1e1TimingPort24(30),
		t1e1TimingPort25(31),
		t1e1TimingPort26(32),
		t1e1TimingPort27(33),
		t1e1TimingPort28(34),
		t1e1TimingPort29(35),
		t1e1TimingPort30(36),
		t1e1TimingPort31(37),
		t1e1TimingPort32(38),

		t1e1TimingSlot2PortA(39),
		t1e1TimingSlot2PortB(40),
		t1e1TimingSlot3PortA(41),
		t1e1TimingSlot3PortB(42),
		t1e1TimingSlot4PortA(43),
		t1e1TimingSlot4PortB(44),
		t1e1TimingSlot5PortA(45),
		t1e1TimingSlot5PortB(46),
		t1e1TimingSlot6PortA(47),
		t1e1TimingSlot6PortB(48),

		t1e1TimingSlot2Dsu1PortA(49),
		t1e1TimingSlot2Dsu1PortB(50),
		t1e1TimingSlot2Dsu2PortA(51),
		t1e1TimingSlot2Dsu2PortB(52),
		t1e1TimingSlot2Dsu3PortA(53),
		t1e1TimingSlot2Dsu3PortB(54),
		t1e1TimingSlot2Dsu4PortA(55),
		t1e1TimingSlot2Dsu4PortB(56),
		t1e1TimingSlot2Dsu5PortA(57),
		t1e1TimingSlot2Dsu5PortB(58),
		t1e1TimingSlot2Dsu6PortA(59),
		t1e1TimingSlot2Dsu6PortB(60),

		t1e1TimingSlot3Dsu1PortA(61),
		t1e1TimingSlot3Dsu1PortB(62),
		t1e1TimingSlot3Dsu2PortA(63),
		t1e1TimingSlot3Dsu2PortB(64),
		t1e1TimingSlot3Dsu3PortA(65),
		t1e1TimingSlot3Dsu3PortB(66),
		t1e1TimingSlot3Dsu4PortA(67),
		t1e1TimingSlot3Dsu4PortB(68),
		t1e1TimingSlot3Dsu5PortA(69),
		t1e1TimingSlot3Dsu5PortB(70),
		t1e1TimingSlot3Dsu6PortA(71),
		t1e1TimingSlot3Dsu6PortB(72),

		t1e1TimingSlot4Dsu1PortA(73),
		t1e1TimingSlot4Dsu1PortB(74),
		t1e1TimingSlot4Dsu2PortA(75),
		t1e1TimingSlot4Dsu2PortB(76),
		t1e1TimingSlot4Dsu3PortA(77),
		t1e1TimingSlot4Dsu3PortB(78),
		t1e1TimingSlot4Dsu4PortA(79),
		t1e1TimingSlot4Dsu4PortB(80),
		t1e1TimingSlot4Dsu5PortA(81),
		t1e1TimingSlot4Dsu5PortB(82),
		t1e1TimingSlot4Dsu6PortA(83),
		t1e1TimingSlot4Dsu6PortB(84),

		t1e1TimingSlot5Dsu1PortA(85),
		t1e1TimingSlot5Dsu1PortB(86),
		t1e1TimingSlot5Dsu2PortA(87),
		t1e1TimingSlot5Dsu2PortB(88),
		t1e1TimingSlot5Dsu3PortA(89),
		t1e1TimingSlot5Dsu3PortB(90),
		t1e1TimingSlot5Dsu4PortA(91),
		t1e1TimingSlot5Dsu4PortB(92),
		t1e1TimingSlot5Dsu5PortA(93),
		t1e1TimingSlot5Dsu5PortB(94),
		t1e1TimingSlot5Dsu6PortA(95),
		t1e1TimingSlot5Dsu6PortB(96),

		t1e1TimingSlot6Dsu1PortA(97),
		t1e1TimingSlot6Dsu1PortB(98),
		t1e1TimingSlot6Dsu2PortA(99),
		t1e1TimingSlot6Dsu2PortB(100),
		t1e1TimingSlot6Dsu3PortA(101),
		t1e1TimingSlot6Dsu3PortB(102),
		t1e1TimingSlot6Dsu4PortA(103),
		t1e1TimingSlot6Dsu4PortB(104),
		t1e1TimingSlot6Dsu5PortA(105),
		t1e1TimingSlot6Dsu5PortB(106),
		t1e1TimingSlot6Dsu6PortA(107),
		t1e1TimingSlot6Dsu6PortB(108)
		}
	ACCESS  read-write
	STATUS  mandatory
	DESCRIPTION
		"Sets the timing source to synchronize the unit's internal timing generators."
	::= { t1e1ConfigTableEntry 9 }

t1e1StationInTiming OBJECT-TYPE
	SYNTAX  INTEGER
		{
		t1e1StationInTimingOther(1),
		t1e1StationInTimingNX56(2),
		t1e1StationInTimingNX64(3),
		t1e1StationInTiming1544(4),
		t1e1StationInTiming2048(5)
		}
	ACCESS  read-write
	STATUS  mandatory
	DESCRIPTION
		"Selects the input timing if t1e1Timing is set to Station."
	::= { t1e1ConfigTableEntry 10 }

t1e1StationTiming OBJECT-TYPE
	SYNTAX  INTEGER
	ACCESS  read-write
	STATUS  mandatory
	DESCRIPTION
		"Selects the N-multiple when Station Input Timing is set to either NX56 or NX65.  The N range is 1..24"
	::= { t1e1ConfigTableEntry 11 }

t1e1PRM OBJECT-TYPE
	SYNTAX  INTEGER
		{
		t1e1PRMOther(1),
		t1e1PRMDisable(2),
		t1e1PRMEnable(3)
		}
	ACCESS  read-write
	STATUS  mandatory
	DESCRIPTION
		"Enables the ANSI T1.403 Performance Report Message functions."
	::= { t1e1ConfigTableEntry 12 }

t1e1ZeroSuppress        OBJECT-TYPE
	SYNTAX  INTEGER
		{
		t1e1ZeroOther(1),
		t1e1ZeroDisable(2),
		t1e1ZeroEnable(3)
		}
	ACCESS  read-write
	STATUS  mandatory
	DESCRIPTION
		"Determines whether ones density insertion is activated after 15 zeros .  To ensure compliance with TR54016, this field must be enabled."
	::= { t1e1ConfigTableEntry 13 }

t1e1NationalBit OBJECT-TYPE
	SYNTAX  INTEGER
		{
		t1e1NationalOther(1),
		t1e1NationalNone(2),
		t1e1NationalSA4(3),
		t1e1NationalSA5(4),
		t1e1NationalSA6(5),
		t1e1NationalSA7(6),
		t1e1NationalSA8(7)
		}
	ACCESS  read-write
	STATUS  mandatory
	DESCRIPTION
		"Selects a national bit to create a 4-kpbs datalink between the endpoint units."
	::= { t1e1ConfigTableEntry 14 }

t1e1KeepAlive   OBJECT-TYPE
	SYNTAX  INTEGER
		{
		t1e1KeepAliveOther(1),
		t1e1KeepAliveUnframedOnes(2),
		t1e1KeepAliveFramedOnes(3),
		t1e1KeepAliveLoop(4)
		}
	ACCESS  read-write
	STATUS  mandatory
	DESCRIPTION
		"Selects keep alive framed and unframed ones when the unit detects LOS or OOF."
	::= { t1e1ConfigTableEntry 15 }

t1e1CRC4Mode            OBJECT-TYPE
	SYNTAX  INTEGER
		{
		t1e1CRC4Other(1),
		t1e1CRC4Disabled(2),
		t1e1CRC4Enabled(3)
		}
	ACCESS  read-write
	STATUS  mandatory
	DESCRIPTION
		"Selects whether CRC4 is enabled or disabled."
	::= { t1e1ConfigTableEntry 16 }

t1e1DSXLevel            OBJECT-TYPE
	SYNTAX  INTEGER
		{
		t1e1DSXOther(1),
		t1e1DSX0110(2),
		t1e1DSX111220(3),
		t1e1DSX221330(4),
		t1e1DSX331440(5),
		t1e1DSX441550(6),
		t1e1DSX551660(7),
		t1e1DSX661up(8)
		}
	ACCESS  read-write
	STATUS  mandatory
	DESCRIPTION
		"Selects the DSX1 interface output level."
	::= { t1e1ConfigTableEntry 17 }

t1e1CRC OBJECT-TYPE
	SYNTAX  INTEGER
		{
		t1e1CRCOther(1),
		t1e1CRCPass(2),
		t1e1CRCRegenerate(3)
		}
	ACCESS  read-write
	STATUS  mandatory
	DESCRIPTION
		"Determines whether received CRC data is passed through or regenerated."
	::= { t1e1ConfigTableEntry 18 }

t1e1FDLPassThrough      OBJECT-TYPE
	SYNTAX  INTEGER
		{
		t1e1FDLPassThroughOther(1),
		t1e1FDLPassThroughPass(2),
		t1e1FDLPassThroughTerminate(3)
		}
	ACCESS  read-write
	STATUS  mandatory
	DESCRIPTION
		"Determines whether the ESF FDL passes through the CSU or terminates."
	::= { t1e1ConfigTableEntry 19 }

t1e1AudibleAlarm        OBJECT-TYPE
	SYNTAX  INTEGER
		{
		t1e1AudibleAlarmOther(1),
		t1e1AudibleAlarmDisabled(2),
		t1e1AudibleAlarmEnabled(3)
		}
	ACCESS  read-write
	STATUS  mandatory
	DESCRIPTION
		"If applicable, Enables or Disables the CSU's internal buzzer which alerts users of an alarm condition."
	::= { t1e1ConfigTableEntry 20 }

t1e1AlarmTable  OBJECT-TYPE
	SYNTAX  SEQUENCE OF T1e1AlarmTableEntry
	ACCESS  not-accessible
	STATUS  optional
	DESCRIPTION
		"The T1 and E1 Alarm Table."
	::= { t1e1 2 }

t1e1AlarmTableEntry     OBJECT-TYPE
	SYNTAX  T1e1AlarmTableEntry
	ACCESS  not-accessible
	STATUS  mandatory
	DESCRIPTION
		"An entry in the t1e1Table."
	INDEX   { t1e1AlarmNearIndex, t1e1AlarmFarIndex, t1e1AlarmIndex }
	::= { t1e1AlarmTable 1 }

T1e1AlarmTableEntry ::=
	SEQUENCE
	{
	t1e1AlarmNearIndex      INTEGER,
	t1e1AlarmFarIndex       INTEGER,
	t1e1AlarmIndex          INTEGER,

	t1e1StatusSummary       DisplayString,
	t1e1AlarmSummary        DisplayString,

	t1e1ESStatus            INTEGER,
	t1e1ESCount             INTEGER,
	t1e1ESThreshold         INTEGER,
	t1e1ESAlarm             INTEGER,

	t1e1SESStatus           INTEGER,
	t1e1SESCount            INTEGER,
	t1e1SESThreshold        INTEGER,
	t1e1SESAlarm            INTEGER,

	t1e1LOSSStatus          INTEGER,
	t1e1LOSSCount           INTEGER,
	t1e1LOSSThreshold       INTEGER,
	t1e1LOSSAlarm           INTEGER,

	t1e1UASStatus           INTEGER,
	t1e1UASCount            INTEGER,
	t1e1UASThreshold        INTEGER,
	t1e1UASAlarm            INTEGER,

	t1e1CSSStatus           INTEGER,
	t1e1CSSCount            INTEGER,
	t1e1CSSThreshold        INTEGER,
	t1e1CSSAlarm            INTEGER,
	
	t1e1BPVSStatus          INTEGER,
	t1e1BPVSCount           INTEGER,
	t1e1BPVSThreshold       INTEGER,
	t1e1BPVSAlarm           INTEGER,
	
	t1e1OOFSStatus          INTEGER,
	t1e1OOFSCount           INTEGER,
	t1e1OOFSThreshold       INTEGER,
	t1e1OOFSAlarm           INTEGER,

	t1e1AISStatus           INTEGER,
	t1e1AISCount            INTEGER,
	t1e1AISThreshold        INTEGER,
	t1e1AISAlarm            INTEGER,

	t1e1RASStatus           INTEGER,
	t1e1RASCount            INTEGER,
	t1e1RASThreshold        INTEGER,
	t1e1RASAlarm            INTEGER,

	t1e1AlarmResetTimer     INTEGER,
	t1e1AlarmReset          INTEGER
	}

t1e1AlarmNearIndex              OBJECT-TYPE
	SYNTAX  INTEGER
	ACCESS  read-only
	STATUS  mandatory
	DESCRIPTION
		"Selects the near device."
	::= { t1e1AlarmTableEntry 1 }

t1e1AlarmFarIndex               OBJECT-TYPE
	SYNTAX  INTEGER
	ACCESS  read-only
	STATUS  mandatory
	DESCRIPTION
		"Selects the far device."
	::= { t1e1AlarmTableEntry 2 }

t1e1AlarmIndex          OBJECT-TYPE
	SYNTAX  INTEGER
	ACCESS  read-only
	STATUS  mandatory
	DESCRIPTION
		"This object is the index into the t1e1Table."
	::= { t1e1AlarmTableEntry 3 }

t1e1StatusSummary       OBJECT-TYPE
	SYNTAX  DisplayString (SIZE(0..80))
	ACCESS  read-only
	STATUS  mandatory
	DESCRIPTION
		"This object provides a summary of the port status."
	::= { t1e1AlarmTableEntry 4 }

t1e1AlarmSummary        OBJECT-TYPE
	SYNTAX  DisplayString (SIZE(0..80))
	ACCESS  read-only
	STATUS  mandatory
	DESCRIPTION
		"This object provides a summary of the port alarms."
	::= { t1e1AlarmTableEntry 5 }

t1e1ESStatus    OBJECT-TYPE
	SYNTAX  INTEGER
		{
		t1e1StatusOther(1),
		t1e1StatusNoES(2),
		t1e1StatusES(3)
		}
	ACCESS  read-only
	STATUS  mandatory
	DESCRIPTION
		"Reports if a Errorred Seconds condition exists."
	::= { t1e1AlarmTableEntry 6 }

t1e1ESCount     OBJECT-TYPE
	SYNTAX  INTEGER
	ACCESS  read-only
	STATUS  mandatory
	DESCRIPTION
		"This count contains the number of consecutive seconds an Errored Seconds condition has existed."
	::= { t1e1AlarmTableEntry 7 }

t1e1ESThreshold OBJECT-TYPE
	SYNTAX  INTEGER
	ACCESS  read-write
	STATUS  mandatory
	DESCRIPTION     
		"Sets the Errored Seconds alarm threshold.  Setting this field to 0 disables the alarm.  The threshold can be set to any value in the range 0 to 900."
	::= { t1e1AlarmTableEntry 8 }

t1e1ESAlarm     OBJECT-TYPE
	SYNTAX  INTEGER
		{
		t1e1ESAlarmOther(1),
		t1e1ESAlarmNone(2),
		t1e1ESAlarmThresholdExceeded(3)
		}
	ACCESS  read-only
	STATUS  mandatory
	DESCRIPTION     
		"This status indicates if the Errors Seconds threshold is exceeded."
	::= { t1e1AlarmTableEntry 9 }

t1e1SESStatus   OBJECT-TYPE
	SYNTAX  INTEGER
		{
		t1e1StatusOther(1),
		t1e1StatusNoSES(2),
		t1e1StatusSES(3)
		}
	ACCESS  read-only
	STATUS  mandatory
	DESCRIPTION
		"Reports if a Severely Errorred condition exists."
	::= { t1e1AlarmTableEntry 10 }

t1e1SESCount    OBJECT-TYPE
	SYNTAX  INTEGER
	ACCESS  read-only
	STATUS  mandatory
	DESCRIPTION
		"This count contains the number of consecutive seconds a Severely Errored condition has existed."
	::= { t1e1AlarmTableEntry 11 }

t1e1SESThreshold        OBJECT-TYPE
	SYNTAX  INTEGER
	ACCESS  read-write
	STATUS  mandatory
	DESCRIPTION     
		"Sets the Severely Errored seconds alarm threshold.  Setting this field to 0 disables the alarm.  The threshold can be set to any value in the range 0 to 900."
	::= { t1e1AlarmTableEntry 12 }

t1e1SESAlarm    OBJECT-TYPE
	SYNTAX  INTEGER
		{
		t1e1SESAlarmOther(1),
		t1e1SESAlarmNone(2),
		t1e1SESAlarmThresholdExceeded(3)
		}
	ACCESS  read-only
	STATUS  mandatory
	DESCRIPTION     
		"This status indicates if the Severely Errors Seconds threshold is exceeded."
	::= { t1e1AlarmTableEntry 13 }

t1e1LOSSStatus  OBJECT-TYPE
	SYNTAX  INTEGER
		{
		t1e1StatusOther(1),
		t1e1StatusNoLOSS(2),
		t1e1StatusLOSS(3)
		}
	ACCESS  read-only
	STATUS  mandatory
	DESCRIPTION
		"Reports if a Loss of Signal condition exists."
	::= { t1e1AlarmTableEntry 14 }

t1e1LOSSCount   OBJECT-TYPE
	SYNTAX  INTEGER
	ACCESS  read-only
	STATUS  mandatory
	DESCRIPTION
		"This count contains the number of consecutive seconds a Loss of Signal condition has existed."
	::= { t1e1AlarmTableEntry 15 }

t1e1LOSSThreshold       OBJECT-TYPE
	SYNTAX  INTEGER
	ACCESS  read-write
	STATUS  mandatory
	DESCRIPTION     
		"Sets the Loss of Signal seconds alarm threshold.  Setting this field to 0 disables the alarm.  The threshold can be set to any value in the range 0 to 900."
	::= { t1e1AlarmTableEntry 16 }

t1e1LOSSAlarm   OBJECT-TYPE
	SYNTAX  INTEGER
		{
		t1e1LOSSAlarmOther(1),
		t1e1LOSSAlarmNone(2),
		t1e1LOSSAlarmThresholdExceeded(3)
		}
	ACCESS  read-only
	STATUS  mandatory
	DESCRIPTION     
		"This status indicates if the Loss of Signal Seconds threshold is exceeded."
	::= { t1e1AlarmTableEntry 17 }

t1e1UASStatus   OBJECT-TYPE
	SYNTAX  INTEGER
		{
		t1e1StatusOther(1),
		t1e1StatusNoUAS(2),
		t1e1StatusUAS(3)
		}
	ACCESS  read-only
	STATUS  mandatory
	DESCRIPTION
		"Reports if an Unavailable condition exists."
	::= { t1e1AlarmTableEntry 18 }

t1e1UASCount    OBJECT-TYPE
	SYNTAX  INTEGER
	ACCESS  read-only
	STATUS  mandatory
	DESCRIPTION
		"This count contains the number of consecutive seconds an Unavailable condition has existed."
	::= { t1e1AlarmTableEntry 19 }

t1e1UASThreshold        OBJECT-TYPE
	SYNTAX  INTEGER
	ACCESS  read-write
	STATUS  mandatory
	DESCRIPTION     
		"Sets the unavailable seconds alarm threshold.  Setting this field to 0 disables the alarm.  The threshold can be set to any value in the range 0 to 900."
	::= { t1e1AlarmTableEntry 20 }

t1e1UASAlarm    OBJECT-TYPE
	SYNTAX  INTEGER
		{
		t1e1UASAlarmOther(1),
		t1e1UASAlarmNone(2),
		t1e1UASAlarmThresholdExceeded(3)
		}
	ACCESS  read-only
	STATUS  mandatory
	DESCRIPTION     
		"This status indicates if the Unavailable Seconds threshold is exceeded."
	::= { t1e1AlarmTableEntry 21 }

t1e1CSSStatus   OBJECT-TYPE
	SYNTAX  INTEGER
		{
		t1e1StatusOther(1),
		t1e1StatusNoCSS(2),
		t1e1StatusCSS(3)
		}
	ACCESS  read-only
	STATUS  mandatory
	DESCRIPTION
		"Reports if a Controlled Slip condition exists."
	::= { t1e1AlarmTableEntry 22 }

t1e1CSSCount    OBJECT-TYPE
	SYNTAX  INTEGER
	ACCESS  read-only
	STATUS  mandatory
	DESCRIPTION
		"This count contains the number of consecutive seconds in which at least one Controlled Slip occurred."
	::= { t1e1AlarmTableEntry 23 }

t1e1CSSThreshold        OBJECT-TYPE
	SYNTAX  INTEGER
	ACCESS  read-write
	STATUS  mandatory
	DESCRIPTION     
		"Sets the Controlled Slip seconds alarm threshold.  Setting this field to 0 disables the alarm.  The threshold can be set to any value in the range 0 to 900."
	::= { t1e1AlarmTableEntry 24 }

t1e1CSSAlarm    OBJECT-TYPE
	SYNTAX  INTEGER
		{
		t1e1CSSAlarmOther(1),
		t1e1CSSAlarmNone(2),
		t1e1CSSAlarmThresholdExceeded(3)
		}
	ACCESS  read-only
	STATUS  mandatory
	DESCRIPTION     
		"This status indicates if the Controlled Slip seconds threshold is exceeded."
	::= { t1e1AlarmTableEntry 25 }

t1e1BPVSStatus  OBJECT-TYPE
	SYNTAX  INTEGER
		{
		t1e1StatusOther(1),
		t1e1StatusNoBPVS(2),
		t1e1StatusBPVS(3)
		}
	ACCESS  read-only
	STATUS  mandatory
	DESCRIPTION
		"Reports if a Bipolar Violation Error condition exists."
	::= { t1e1AlarmTableEntry 26 }

t1e1BPVSCount   OBJECT-TYPE
	SYNTAX  INTEGER
	ACCESS  read-only
	STATUS  mandatory
	DESCRIPTION
		"This count contains the number of consecutive seconds a Bipolar Violation Error condition has existed."
	::= { t1e1AlarmTableEntry 27 }

t1e1BPVSThreshold       OBJECT-TYPE
	SYNTAX  INTEGER
	ACCESS  read-write
	STATUS  mandatory
	DESCRIPTION     
		"Sets the Bipolar Violation Error seconds alarm threshold.  Setting this field to 0 disables the alarm.  The threshold can be set to any value in the range 0 to 900."
	::= { t1e1AlarmTableEntry 28 }

t1e1BPVSAlarm   OBJECT-TYPE
	SYNTAX  INTEGER
		{
		t1e1BPVSAlarmOther(1),
		t1e1BPVSAlarmNone(2),
		t1e1BPVSAlarmThresholdExceeded(3)
		}
	ACCESS  read-only
	STATUS  mandatory
	DESCRIPTION     
		"This status indicates if the Bipolar Violation Error seconds threshold is exceeded."
	::= { t1e1AlarmTableEntry 29 }

t1e1OOFSStatus  OBJECT-TYPE
	SYNTAX  INTEGER
		{
		t1e1StatusOther(1),
		t1e1StatusNoOOF(2),
		t1e1StatusOOF(3)
		}
	ACCESS  read-only
	STATUS  mandatory
	DESCRIPTION
		"Indicates that the unit is unable to synchronize on the incoming framing pattern."
	::= { t1e1AlarmTableEntry 30 }

t1e1OOFSCount   OBJECT-TYPE
	SYNTAX  INTEGER
	ACCESS  read-only
	STATUS  mandatory
	DESCRIPTION
		"This count contains the number of consecutive seconds an OOF condition has existed."
	::= { t1e1AlarmTableEntry 31 }

t1e1OOFSThreshold       OBJECT-TYPE
	SYNTAX  INTEGER
	ACCESS  read-write
	STATUS  mandatory
	DESCRIPTION     
		"Sets the OOF seconds alarm threshold.  Setting this field to 0 disables the alarm.  The threshold can be set to any value in the range 0 to 900."
	::= { t1e1AlarmTableEntry 32 }

t1e1OOFSAlarm   OBJECT-TYPE
	SYNTAX  INTEGER
		{
		t1e1OOFSAlarmOther(1),
		t1e1OOFSAlarmNone(2),
		t1e1OOFSAlarmExists(3)
		}
	ACCESS  read-only
	STATUS  mandatory
	DESCRIPTION
		"Indicates if an OOF seconds alarm condition exists."
	::= { t1e1AlarmTableEntry 33 }

t1e1AISStatus   OBJECT-TYPE
	SYNTAX  INTEGER
		{
		t1e1StatusOther(1),
		t1e1StatusNoAIS(2),
		t1e1StatusAIS(3)
		}
	ACCESS  read-only
	STATUS  mandatory
	DESCRIPTION
		"Indicates that the unit is receiving an unframed all ones pattern."
	::= { t1e1AlarmTableEntry 34 }

t1e1AISCount   OBJECT-TYPE
	SYNTAX  INTEGER
	ACCESS  read-only
	STATUS  mandatory
	DESCRIPTION
		"This count contains the number of consecutive seconds an Unframed All Ones condition has existed."
	::= { t1e1AlarmTableEntry 35 }

t1e1AISThreshold       OBJECT-TYPE
	SYNTAX  INTEGER
	ACCESS  read-write
	STATUS  mandatory
	DESCRIPTION     
		"Sets the AIS seconds alarm threshold.  Setting this field to 0 disables the alarm.  The threshold can be set to any value in the range 0 to 900."
	::= { t1e1AlarmTableEntry 36 }

t1e1AISAlarm    OBJECT-TYPE
	SYNTAX  INTEGER
		{
		t1e1AISAlarmOther(1),
		t1e1AISAlarmNone(2),
		t1e1AISAlarmExists(3)
		}
	ACCESS  read-only
	STATUS  mandatory
	DESCRIPTION
		"Indicates if an Unframed All Ones alarm condition exists."
	::= { t1e1AlarmTableEntry 37 }

t1e1RASStatus   OBJECT-TYPE
	SYNTAX  INTEGER
		{
		t1e1RASStatusOther(1),
		t1e1RASStatusNoRAS(2),
		t1e1RASStatusRAS(3)
		}
	ACCESS  read-only
	STATUS  mandatory
	DESCRIPTION
		"Reports if a Remote (Yellow) Alarm condition exists."
	::= { t1e1AlarmTableEntry 38 }

t1e1RASCount   OBJECT-TYPE
	SYNTAX  INTEGER
	ACCESS  read-only
	STATUS  mandatory
	DESCRIPTION
		"This count contains the number of consecutive seconds a Remote (Yellow) Alarm condition has existed."
	::= { t1e1AlarmTableEntry 39 }

t1e1RASThreshold       OBJECT-TYPE
	SYNTAX  INTEGER
	ACCESS  read-write
	STATUS  mandatory
	DESCRIPTION     
		"Sets the RAS seconds alarm threshold.  Setting this field to 0 disables the alarm.  The threshold can be set to any value in the range 0 to 900."
	::= { t1e1AlarmTableEntry 40 }

t1e1RASAlarm    OBJECT-TYPE
	SYNTAX  INTEGER
		{
		t1e1RASAlarmOther(1),
		t1e1RASAlarmNone(2),
		t1e1RASAlarmExists(3)
		}
	ACCESS  read-only
	STATUS  mandatory
	DESCRIPTION     
		"This status indicates if a Remote (Yellow) Alarm exists."
	::= { t1e1AlarmTableEntry 41 }

t1e1AlarmResetTimer       OBJECT-TYPE
	SYNTAX  INTEGER
	ACCESS  read-write
	STATUS  mandatory
	DESCRIPTION     
		"Sets the Alarm Reset Timer, this field can be set to any value in the range 0 to 900."
	::= { t1e1AlarmTableEntry 42 }


t1e1AlarmReset    OBJECT-TYPE
	SYNTAX  INTEGER
		{
		t1e1AlarmResetOther(1),
		t1e1AlarmResetClearAlarms(2)
		}
	ACCESS  read-write
	STATUS  mandatory
	DESCRIPTION     
		"This is used to clear the current alarm counts."
	::= { t1e1AlarmTableEntry 43 }


-- ddsNet section, contains DDS Network interface table

ddsNetConfigTable       OBJECT-TYPE
	SYNTAX  SEQUENCE OF DdsNetConfigTableEntry
	ACCESS  not-accessible
	STATUS  optional
	DESCRIPTION
		"The dds Network Interface Configuration Table."
	::= { ddsNet 1 }

ddsNetConfigTableEntry  OBJECT-TYPE
	SYNTAX  DdsNetConfigTableEntry
	ACCESS  not-accessible
	STATUS  mandatory
	DESCRIPTION
		"An entry in the Network Interface Table."
	INDEX   { ddsNetConfigNearIndex, ddsNetConfigFarIndex, ddsNetConfigIndex }
	::= { ddsNetConfigTable 1 }

DdsNetConfigTableEntry ::=
	SEQUENCE
	{
	ddsNetConfigNearIndex   INTEGER,
	ddsNetConfigFarIndex    INTEGER,
	ddsNetConfigIndex       INTEGER,

	ddsNetDescription       DisplayString,
	ddsNetRate              INTEGER,
	ddsNetMode              INTEGER,
	ddsNetTimingSource      INTEGER,
	ddsNetRemComm           INTEGER,
	ddsNetCircuitAssur      INTEGER,
	ddsNetAntiStrTimer      INTEGER
	}

ddsNetConfigNearIndex           OBJECT-TYPE
	SYNTAX  INTEGER
	ACCESS  read-only
	STATUS  mandatory
	DESCRIPTION
		"Selects the near device."
	::= { ddsNetConfigTableEntry 1 }

ddsNetConfigFarIndex            OBJECT-TYPE
	SYNTAX  INTEGER
	ACCESS  read-only
	STATUS  mandatory
	DESCRIPTION
		"Selects the far device."
	::= { ddsNetConfigTableEntry 2 }

ddsNetConfigIndex       OBJECT-TYPE
	SYNTAX  INTEGER
	ACCESS  read-only
	STATUS  mandatory
	DESCRIPTION
		"Index into the ddsNetConfigTable."
	::= { ddsNetConfigTableEntry 3 }

ddsNetDescription       OBJECT-TYPE
	SYNTAX  DisplayString( SIZE(0..40) )
	ACCESS  read-write
	STATUS  mandatory
	DESCRIPTION
		"Contains a textual description of the port."
	::= { ddsNetConfigTableEntry 4 }

ddsNetRate  OBJECT-TYPE
	SYNTAX  INTEGER  
		{
		ddsNetRate2400(1),
		ddsNetRate4800(2),
		ddsNetRate9600(3),
		ddsNetRate19200(4),
		ddsNetRate38400(5),
		ddsNetRate56000(6),
		ddsNetRate64000(7)
		}
	ACCESS  read-write
	STATUS  mandatory
	DESCRIPTION
		"This object is the identifier of the current DDS network rate. The values mean:
ddsNetRate2400
   the DDS network interface is operating at
   2400bps
ddsNetRate4800
   the DDS network interface is operating at
   4800bps
ddsNetRate9600
   the DDS network interface is operating at
   9600bps
ddsNetRate19200
   the DDS network interface is operating at
   19200bps
ddsNetRate38400
   the DDS network interface is operating at
   38400bps
ddsNetRate56000
   the DDS network interface is operating at
   56000bps
ddsNetRate64000
   the DDS network interface is operating at
   64000bps"
	::=  { ddsNetConfigTableEntry 5 }

ddsNetMode  OBJECT-TYPE
	SYNTAX  INTEGER 
		{
		ddsNetModeNormal(1),
		ddsNetModeProprietaryTXPI(2),
		ddsNetMode64KClearChannel(3),
		ddsNetMode64KCCProprietaryTXPII(4)
		}
	ACCESS  read-write
	STATUS  mandatory
	DESCRIPTION
		"This variable describes mode in which data is
being sent from the DDS unit back towards the
network. Changing the value of this variable can
cause a loss of remote communications.
The values mean:
ddsNetModeNormal (DDS-I)
   normal data mode of operation
ddsNetModeProprietaryTXPI (DDS-I)
   data being sent out on the DDS network is
   in a proprietary mode to allow for remote
   communications, rate adaption, and SYNC to
   ASYNC modes
ddsNetMode64KClearChannel (DDS-II)
   A special case of DDS-II, where the line rate is 72K,
   the data rate is 64K, and there is no secondary channel.
ddsNetMode64KCCProprietaryTXPII (DDS-II)
   A special case of DDS-II, where the line rate is 72K,
   the data rate is 64K, and there is no secondary channel.
   In addition, the data being sent out on the DDS network
   is in a proprietary mode to allow for remote communications,
   rate adaption, SYNC to ASYNC, and/or TDM modes."
	::=  { ddsNetConfigTableEntry 6 }
	

ddsNetTimingSource  OBJECT-TYPE
	SYNTAX  INTEGER 
		{
		ddsNetTimingNet(1),
		ddsNetTimingInt(2),
		ddsNetTimingDTE(3)
		}
	ACCESS  read-write
	STATUS  mandatory
	DESCRIPTION
		"This variable describes the current timing source for
the DDS network interface. The values mean:
ddsNetTimingNet
   unit dependant upon network for DDS network
   interface timing
ddsNetTimingInt
   unit supplying timing for DDS network
   interface
ddsNetTimingDTE
   unit dependant upon DTE device for network
   interface timing"
	::=  { ddsNetConfigTableEntry 7 }
	
ddsNetRemComm  OBJECT-TYPE
	SYNTAX  INTEGER 
		{
		ddsNetRemCommEnabled(1),
		ddsNetRemCommDisabled(2),
		ddsNetRemCommNotAvailable(3)
		}
	ACCESS  read-only
	STATUS  mandatory
	DESCRIPTION
		"This variable describes the current setting for the
remote communications link. The values mean:
ddsNetRemCommEnabled
   remote communications can be carried out end
   to end
ddsNetRemCommDisabled
   remote communications are not allowed
ddsNetRemCommNotAvailable
   this unit does not support remote
   communications"
	::=  { ddsNetConfigTableEntry 8 }

ddsNetCircuitAssur  OBJECT-TYPE
	SYNTAX  INTEGER 
		{
		ddsNetCircuitAssurEnabled(1),
		ddsNetCircuitAssurDisabled(2),
		ddsNetCircuitAssurNotAvailable(3)
		}
	ACCESS  read-write
	STATUS  mandatory
	DESCRIPTION
		"This variable describes the current setting for the
circuit assurance option. The values mean:
ddsNetCircuitAssurEnabled
   Circuit Assurance is enabled and the
   integrity of the DDS loop will be maintained
ddsNetCircuitAssurDisabled
   Circuit Assurance is disabled
ddsNetCircuitAssurNotAvailable
   this unit does not support Circuit Assurance"
	::=  { ddsNetConfigTableEntry 9 }

ddsNetAntiStrTimer  OBJECT-TYPE
	SYNTAX  INTEGER 
		{
		ddsNetAntiStrTimerOff(1),
		ddsNetAntiStrTimer10(2),
		ddsNetAntiStrTimer30(3),
		ddsNetAntiStrTimer60(4)
		}
	ACCESS  read-write
	STATUS  mandatory
	DESCRIPTION
		"This variable describes the current setting for the
anti streaming timer. The values mean:
ddsNetAntiStrTimerOff
   the AntiStreaming Timer is off
ddsNetAntiStrTimer10
   the AntiStreaming Timer is set to 10 seconds
ddsNetAntiStrTimer30
   the AntiStreaming Timer is set to 30 seconds
ddsNetAntiStrTimer60
   ths AntiStreaming Timer is set to 60 seconds"
	::=  { ddsNetConfigTableEntry 10 }

ddsNetAlarmTable        OBJECT-TYPE
	SYNTAX  SEQUENCE OF DdsNetAlarmTableEntry
	ACCESS  not-accessible
	STATUS  optional
	DESCRIPTION
		"The dds Network Interface Alarm Table."
	::= { ddsNet 2 }

ddsNetAlarmTableEntry   OBJECT-TYPE
	SYNTAX  DdsNetAlarmTableEntry
	ACCESS  not-accessible
	STATUS  mandatory
	DESCRIPTION
		"An entry in the ddsNetAlarmTable."
	INDEX   { ddsNetAlarmNearIndex, ddsNetAlarmFarIndex, ddsNetAlarmIndex }
	::= { ddsNetAlarmTable 1 }

DdsNetAlarmTableEntry ::=
	SEQUENCE
	{
	ddsNetAlarmNearIndex    INTEGER,
	ddsNetAlarmFarIndex     INTEGER,
	ddsNetAlarmIndex        INTEGER,

	ddsNetStatusSummary     DisplayString,
	ddsNetAlarmSummary      DisplayString,

	ddsNetLOSStatus         INTEGER,
	ddsNetLOSCount          INTEGER,
	ddsNetLOSThreshold      INTEGER,
	ddsNetLOSAlarm          INTEGER,

	ddsNetOOFStatus         INTEGER,
	ddsNetOOFCount          INTEGER,
	ddsNetOOFThreshold      INTEGER,
	ddsNetOOFAlarm          INTEGER,

	ddsNetOOSStatus         INTEGER,
	ddsNetOOSCount          INTEGER,
	ddsNetOOSThreshold      INTEGER,
	ddsNetOOSAlarm          INTEGER,

	ddsNetFDLStatus         INTEGER,
	ddsNetFDLCount          INTEGER,
	ddsNetFDLThreshold      INTEGER,
	ddsNetFDLAlarm          INTEGER,

	ddsNetAlarmResetTimer   INTEGER,
	ddsNetAlarmReset        INTEGER
	}

ddsNetAlarmNearIndex            OBJECT-TYPE
	SYNTAX  INTEGER
	ACCESS  read-only
	STATUS  mandatory
	DESCRIPTION
		"Selects the near device."
	::= { ddsNetAlarmTableEntry 1 }

ddsNetAlarmFarIndex             OBJECT-TYPE
	SYNTAX  INTEGER
	ACCESS  read-only
	STATUS  mandatory
	DESCRIPTION
		"Selects the far device."
	::= { ddsNetAlarmTableEntry 2 }

ddsNetAlarmIndex        OBJECT-TYPE
	SYNTAX  INTEGER
	ACCESS  read-only
	STATUS  mandatory
	DESCRIPTION
		"Index into the ddsNetAlarmTable."
	::= { ddsNetAlarmTableEntry 3 }


ddsNetStatusSummary     OBJECT-TYPE
	SYNTAX  DisplayString (SIZE(0..80))
	ACCESS  read-only
	STATUS  mandatory
	DESCRIPTION
		"This object provides a summary of the port status."
	::= { ddsNetAlarmTableEntry 4 }

ddsNetAlarmSummary      OBJECT-TYPE
	SYNTAX  DisplayString (SIZE(0..80))
	ACCESS  read-only
	STATUS  mandatory
	DESCRIPTION
		"This object provides a summary of the port alarms."
	::= { ddsNetAlarmTableEntry 5 }

ddsNetLOSStatus OBJECT-TYPE
	SYNTAX  INTEGER
		{
		ddsNetStatusLOSOther(1),
		ddsNetStatusNoLOS(2),
		ddsNetStatusLOS(3)
		}
	ACCESS  read-only
	STATUS  mandatory
	DESCRIPTION
		"Reports if a Loss of Signal condition exists."
	::= { ddsNetAlarmTableEntry 6 }

ddsNetLOSCount  OBJECT-TYPE
	SYNTAX  INTEGER
	ACCESS  read-only
	STATUS  mandatory
	DESCRIPTION
		"This count contains the number of consecutive seconds the unit received signal has been interrupted."
	::= { ddsNetAlarmTableEntry 7 }

ddsNetLOSThreshold      OBJECT-TYPE
	SYNTAX  INTEGER
		{
		ddsNetLOSThresholdOther(1),
		ddsNetLOSThresholdNone(2),
		ddsNetLOSThreshold1(3),
		ddsNetLOSThreshold2(4),
		ddsNetLOSThreshold3(5),
		ddsNetLOSThreshold4(6),
		ddsNetLOSThreshold5(7),
		ddsNetLOSThreshold10(8),
		ddsNetLOSThreshold20(9),
		ddsNetLOSThreshold30(10)
		}
	ACCESS  read-write
	STATUS  mandatory
	DESCRIPTION
		"A period, measured in seconds, in which the DDS received signal is interrupted."
	::= { ddsNetAlarmTableEntry 8 }

ddsNetLOSAlarm  OBJECT-TYPE
	SYNTAX  INTEGER
		{
		ddsNetLOSAlarmOther(1),
		ddsNetLOSAlarmNone(2),
		ddsNetLOSAlarmThresholdExceeded(3)
		}
	ACCESS  read-only
	STATUS  mandatory
	DESCRIPTION     
		"This status indicates if the Loss of Signal Seconds threshold is exceeded."
	::= { ddsNetAlarmTableEntry 9 }

ddsNetOOFStatus OBJECT-TYPE
	SYNTAX  INTEGER
		{
		ddsNetStatusOOFOther(1),
		ddsNetStatusNoOOF(2),
		ddsNetStatusOOF(3)
		}
	ACCESS  read-only
	STATUS  mandatory
	DESCRIPTION
		"Reports if an Out of Frame condition exists."
	::= { ddsNetAlarmTableEntry 10 }

ddsNetOOFCount          OBJECT-TYPE
	SYNTAX  INTEGER
	ACCESS  read-only
	STATUS  mandatory
	DESCRIPTION
		"This count contains the number of consecutive seconds the unit has received the out of frame code."
	::= { ddsNetAlarmTableEntry 11 }

ddsNetOOFThreshold      OBJECT-TYPE
	SYNTAX  INTEGER
		{
		ddsNetOOFThresholdOther(1),
		ddsNetOOFThresholdNone(2),
		ddsNetOOFThreshold1(3),
		ddsNetOOFThreshold2(4),
		ddsNetOOFThreshold3(5),
		ddsNetOOFThreshold4(6),
		ddsNetOOFThreshold5(7),
		ddsNetOOFThreshold10(8),
		ddsNetOOFThreshold20(9),
		ddsNetOOFThreshold30(10)
		}
	ACCESS  read-write
	STATUS  mandatory
	DESCRIPTION
		"A period, measured in seconds, in which the Out Of Frame code is received or a frame sync loss occurred."
	::= { ddsNetAlarmTableEntry 12 }

ddsNetOOFAlarm OBJECT-TYPE
	SYNTAX  INTEGER
		{
		ddsNetOOFSAlarmOther(1),
		ddsNetOOFSAlarmNone(2),
		ddsNetOOFSAlarmThresholdExceeded(3)
		}
	ACCESS  read-only
	STATUS  mandatory
	DESCRIPTION     
		"This status indicates if the Out of Frame Seconds threshold is exceeded."
	::= { ddsNetAlarmTableEntry 13 }

ddsNetOOSStatus OBJECT-TYPE
	SYNTAX  INTEGER
		{
		ddsNetStatusOOSOther(1),
		ddsNetStatusNoOOS(2),
		ddsNetStatusOOS(3)
		}
	ACCESS  read-only
	STATUS  mandatory
	DESCRIPTION
		"Reports if Out of Service codes are received."
	::= { ddsNetAlarmTableEntry 14 }

ddsNetOOSCount  OBJECT-TYPE
	SYNTAX  INTEGER
	ACCESS  read-only
	STATUS  mandatory
	DESCRIPTION
		"This count contains the number of consecutive seconds the unit has received the out of service code."
	::= { ddsNetAlarmTableEntry 15 }

ddsNetOOSThreshold      OBJECT-TYPE
	SYNTAX  INTEGER
		{
		ddsNetOOSThresholdOther(1),
		ddsNetOOSThresholdNone(2),
		ddsNetOOSThreshold1(3),
		ddsNetOOSThreshold2(4),
		ddsNetOOSThreshold3(5),
		ddsNetOOSThreshold4(6),
		ddsNetOOSThreshold5(7),
		ddsNetOOSThreshold10(8),
		ddsNetOOSThreshold20(9),
		ddsNetOOSThreshold30(10)
		}
	ACCESS  read-write
	STATUS  mandatory
	DESCRIPTION
		"A period, measured in seconds, in which the Out Of Service code is received."
	::= { ddsNetAlarmTableEntry 16 }

ddsNetOOSAlarm  OBJECT-TYPE
	SYNTAX  INTEGER
		{
		ddsNetOOSAlarmOther(1),
		ddsNetOOSAlarmNone(2),
		ddsNetOOSAlarmThresholdExceeded(3)
		}
	ACCESS  read-only
	STATUS  mandatory
	DESCRIPTION     
		"This status indicates if the Out of Service Seconds threshold is exceeded."
	::= { ddsNetAlarmTableEntry 17 }

ddsNetFDLStatus OBJECT-TYPE
	SYNTAX  INTEGER
		{
		ddsNetStatusFDLOther(1),
		ddsNetStatusNoFDL(2),
		ddsNetStatusFDL(3)
		}
	ACCESS  read-only
	STATUS  mandatory
	DESCRIPTION
		"Reports if Facility Data Link errors have occurred."
	::= { ddsNetAlarmTableEntry 18 }

ddsNetFDLCount  OBJECT-TYPE
	SYNTAX  INTEGER
	ACCESS  read-only
	STATUS  mandatory
	DESCRIPTION
		"This count contains the number of consecutive seconds in which FDL errors have occurred."
	::= { ddsNetAlarmTableEntry 19 }

ddsNetFDLThreshold      OBJECT-TYPE
	SYNTAX  INTEGER
		{
		ddsNetFDLThresholdOther(1),
		ddsNetFDLThresholdNone(2),
		ddsNetFDLThreshold1(3),
		ddsNetFDLThreshold2(4),
		ddsNetFDLThreshold3(5),
		ddsNetFDLThreshold4(6),
		ddsNetFDLThreshold5(7),
		ddsNetFDLThreshold10(8),
		ddsNetFDLThreshold20(9),
		ddsNetFDLThreshold30(10)
		}
	ACCESS  read-write
	STATUS  mandatory
	DESCRIPTION
		"A period, measured in seconds, in which FDL errors have occurred."
	::= { ddsNetAlarmTableEntry 20 }

ddsNetFDLAlarm  OBJECT-TYPE
	SYNTAX  INTEGER
		{
		ddsNetFDLAlarmOther(1),
		ddsNetFDLAlarmNone(2),
		ddsNetFDLAlarmThresholdExceeded(3)
		}
	ACCESS  read-only
	STATUS  mandatory
	DESCRIPTION     
		"This status indicates if the Facility Data Link threshold is exceeded."
	::= { ddsNetAlarmTableEntry 21 }

ddsNetAlarmResetTimer       OBJECT-TYPE
	SYNTAX  INTEGER
	ACCESS  read-write
	STATUS  mandatory
	DESCRIPTION     
		"Sets the Alarm Reset Timer, this field can be set to any value in the range 0 to 900."
	::= { ddsNetAlarmTableEntry 22 }


ddsNetAlarmReset    OBJECT-TYPE
	SYNTAX  INTEGER
		{
		ddsNetAlarmResetOther(1),
		ddsNetAlarmResetClearAlarms(2)
		}
	ACCESS  read-write
	STATUS  mandatory
	DESCRIPTION     
		"This is used to clear the current alarm counts."
	::= { ddsNetAlarmTableEntry 23 }



-- serialDte section

serialDteConfigTable    OBJECT-TYPE
	SYNTAX  SEQUENCE OF SerialDteConfigTableEntry
	ACCESS  not-accessible
	STATUS  optional
	DESCRIPTION
		"The Serial DTE Config Table."
	::= { serialDte 1 }

serialDteConfigTableEntry       OBJECT-TYPE
	SYNTAX  SerialDteConfigTableEntry
	ACCESS  not-accessible
	STATUS  mandatory
	DESCRIPTION
		"An entry in the serial DTE Config Table."
	INDEX   { serialDteConfigNearIndex, serialDteConfigFarIndex, serialDteConfigIndex }
	::= { serialDteConfigTable 1 }

SerialDteConfigTableEntry ::=
	SEQUENCE
	{
	serialDteConfigNearIndex        INTEGER,
	serialDteConfigFarIndex INTEGER,
	serialDteConfigIndex    INTEGER,

	serialDteDescription    DisplayString,
	serialDteType           INTEGER,
	serialDteRate           INTEGER,
	serialDteInvertData     INTEGER,

	serialDteFormat         INTEGER,
	serialDteParity         INTEGER,
	serialDteStopBit        INTEGER,
	serialDteMode           INTEGER,

	serialDteDSR            INTEGER,
	serialDteDCD            INTEGER,
	serialDteRTS            INTEGER,
	serialDteRTSDelay       INTEGER,
	serialDteDTR            INTEGER,
	serialDteCTS            INTEGER,
	serialDteV54            INTEGER,
	serialDteLL             INTEGER,
	serialDteRL             INTEGER,
	serialDteStartChannel	INTEGER,
	serialDteNumberOfChannels	INTEGER,
	serialDteTxClock	INTEGER,
	serialDteBundle        INTEGER,
	serialDteChannelRate    INTEGER,
    serialDteInvertClock    INTEGER
	}

serialDteConfigNearIndex        OBJECT-TYPE
	SYNTAX  INTEGER
	ACCESS  read-only
	STATUS  mandatory
	DESCRIPTION
		"Selects the near device."
	::= { serialDteConfigTableEntry 1 }

serialDteConfigFarIndex         OBJECT-TYPE
	SYNTAX  INTEGER
	ACCESS  read-only
	STATUS  mandatory
	DESCRIPTION
		"Selects the far device."
	::= { serialDteConfigTableEntry 2 }

serialDteConfigIndex    OBJECT-TYPE
	SYNTAX  INTEGER
	ACCESS  read-only
	STATUS  mandatory
	DESCRIPTION
		"Index into the DteTable."
	::= { serialDteConfigTableEntry 3 }

serialDteDescription    OBJECT-TYPE
	SYNTAX  DisplayString( SIZE(0..40) )
	ACCESS  read-only
	STATUS  mandatory
	DESCRIPTION
		"Contains a textual description of the port."
	::= { serialDteConfigTableEntry 4 }

serialDteType   OBJECT-TYPE
	SYNTAX  INTEGER
		{
		serialDteTypeOther(1),
		serialDteTypeV35(2),
		serialDteTypeRS232(3),
		serialDteTypeEIA530(4)
		}
	ACCESS  read-write
	STATUS  mandatory
	DESCRIPTION
		"Selects the DTE port type if applicable."
	::= { serialDteConfigTableEntry 5 }

serialDteRate   OBJECT-TYPE
	SYNTAX  INTEGER
		{
		serialDteRateOther(1),
		serialDteRate2400(2),
		serialDteRate4800(3),
		serialDteRate9600(4),
		serialDteRate19200(5),
		serialDteRate38400(6),
		serialDteRate52000(7),
		serialDteRate56000(8),
		serialDteRate57600(9),
		serialDteRate60000(10),
		serialDteRate64000(11),
		serialDteRate112000(12),
		serialDteRate128000(13),
		serialDteRate168000(14),
		serialDteRate192000(15),
		serialDteRate224000(16),
		serialDteRate256000(17),
		serialDteRate280000(18),
		serialDteRate320000(19),
		serialDteRate336000(20),
		serialDteRate384000(21),
		serialDteRate392000(22),
		serialDteRate448000(23),
		serialDteRate504000(24),
		serialDteRate512000(25),
		serialDteRate560000(26),
		serialDteRate576000(27),
		serialDteRate616000(28),
		serialDteRate640000(29),
		serialDteRate672000(30),
		serialDteRate704000(31),
		serialDteRate728000(32),
		serialDteRate768000(33),
		serialDteRate784000(34),
		serialDteRate832000(35),
		serialDteRate840000(36),
		serialDteRate896000(37),
		serialDteRate952000(38),
		serialDteRate960000(39),
		serialDteRate1008000(40),
		serialDteRate1024000(41),
		serialDteRate1064000(42),
		serialDteRate1088000(43),
		serialDteRate1120000(44),
		serialDteRate1152000(45),
		serialDteRate1176000(46),
		serialDteRate1216000(47),
		serialDteRate1232000(48),
		serialDteRate1280000(49),
		serialDteRate1288000(50),
		serialDteRate1344000(51),
		serialDteRate1400000(52),
		serialDteRate1408000(53),
		serialDteRate1456000(54),
		serialDteRate1472000(55),
		serialDteRate1512000(56),
		serialDteRate1536000(57),
		serialDteRate1568000(58),
		serialDteRate1600000(59),
		serialDteRate1624000(60),
		serialDteRate1664000(61),
		serialDteRate1680000(62),
		serialDteRate1728000(63),
		serialDteRate1736000(64),
		serialDteRate1792000(65),
		serialDteRate1856000(66),
		serialDteRate1920000(67),
		serialDteRate1984000(68),
		serialDteRate2048000(69),
		serialDteRate1200(70),
		serialDteRate14400(71),
		serialDteRate28800(72),
		serialDteRate48000(73),
		serialDteRate31200(74),
		serialDteRate115200(75)
		}
	ACCESS  read-write
	STATUS  mandatory
	DESCRIPTION
		"Selects the DTE port bit."
	::= { serialDteConfigTableEntry 6 }

serialDteInvertData             OBJECT-TYPE
	SYNTAX  INTEGER
		{
		serialDteInvertDataOther(1),
		serialDteInvertDataDisabled(2),
		serialDteInvertDataEnabled(3)
		}
	ACCESS  read-write
	STATUS  mandatory
	DESCRIPTION
		"Specifies whether transmit and receive are inverted at the port."
	::= { serialDteConfigTableEntry 7 }

serialDteFormat OBJECT-TYPE
	SYNTAX  INTEGER 
		{
		serialDteFormatOther(1),
		serialDteFormatSync(2),
		serialDteFormatAsync(3),
		serialDteFormatNotAvail(4)
		}
		ACCESS  read-write
		STATUS  mandatory
		DESCRIPTION
		"This variable describes the current operations format
of the DTE interface. The values mean:
serialDteFormatSync
   The DTE interface is currently set to operate
   in Syncronous clocking format
serialDteFormatAsync
   The DTE interface is currently set to operate
   in the Asyncronous clocking format
serialDteFormatNotAvail
   The DTE interface operating format is not
   available"
	::=  { serialDteConfigTableEntry 8 }

-- The DTE Parity is only valid when the DTE Mode is set to ASYNC

serialDteParity OBJECT-TYPE
	SYNTAX  INTEGER 
		{
		serialDteParityOther(1),
		serialDteParityNone(2),
		serialDteParityOdd(3),
		serialDteParityEven(4),
		serialDteParityMark(5),
		serialDteParitySpace(6),
		serialDteParityNotAvail(7)
		}
	ACCESS  read-write
	STATUS  mandatory
	DESCRIPTION
		"This variable describes the current parity selected
for the DTE interface. This variable is only valid
when the DTE Mode is set to ASYNC. The values mean:
serialDteParityNone
   The DTE interface is currently set for
   no parity bit checking or generation
serialDteParityOdd
   The DTE interface is currently set
   for odd parity
serialDteParityEven
   The DTE interface is currently set
   for even parity
serialDteParityMark
   The DTE interface is currently set
   for mark parity
serialDteParitySpace
   The DTE interface is currently set
   for space parity
serialDteParityNotAvail
   The parity setting on the DTE interface is not
   available."
	::=  { serialDteConfigTableEntry 9 }

-- The Stop bit setting is only valid when the DTE interface is set to
-- ASYNC operation.

serialDteStopBit  OBJECT-TYPE
	SYNTAX  INTEGER 
		{
		serialDteStopBitOther(1),
		serialDteStopBit1(2),
		serialDteStopBit2(3),
		serialDteStopBitNotAvail(4)
		}
	ACCESS  read-write
	STATUS  mandatory
	DESCRIPTION
		"This variable describes the stop bit setting for the
DTE interface. This variable is only valid when the
DTE interface is set to ASYNC. The values mean:
serialDteStopBit1
   The DTE interface is configured to operate in
   the ASYNC mode with 1 stop bit
serialDteStopBit2
   The DTE interface is configured to operate in
   the ASYNC mode with 2 stop bits
serialDteStopBitNotAvail
   The stop bit information is not available. The
   DTE interface is probably configured for
   synchronous operation."
	::= { serialDteConfigTableEntry 10 }

serialDteMode  OBJECT-TYPE
	SYNTAX  INTEGER 
		{
		serialDteModeOther(1),
		serialDteModeDDSI(2),
		serialDteModeDDSII(3),
		serialDteModeTxpINormal(4),
		serialDteModeTxpITDM(5),
		serialDteModeTxpIINormal(6),
		serialDteModeTxpIITDM(7)
		}
	ACCESS  read-write
	STATUS  mandatory
	DESCRIPTION
		"This variable describes mode in which data is
being sent from the DDS unit back towards the network. "
	::=  { serialDteConfigTableEntry 11 }

serialDteDSR    OBJECT-TYPE
	SYNTAX  INTEGER
		{
		serialDteDSROther(1),
		serialDteDSRTestOff(2),
		serialDteDSRForcedOn(3),
		serialDteDSRForcedOff(4),
		serialDteDSRInternal(5)
		}
	ACCESS  read-write
	STATUS  mandatory
	DESCRIPTION
		"Selects DSR behavior."
	::= { serialDteConfigTableEntry 12 }

serialDteDCD    OBJECT-TYPE
	SYNTAX  INTEGER
		{
		serialDteDCDOther(1),
		serialDteDCDIdleOff(2),
		serialDteDCDForcedOn(3),
		serialDteDCDForcedOff(4),
		serialDteDCDInternal(5),
		serialDteDCDFarRTS(6)
		}
	ACCESS  read-write
	STATUS  mandatory
	DESCRIPTION
		"Selects DCD behavior."
	::= { serialDteConfigTableEntry 13 }

serialDteRTS    OBJECT-TYPE
	SYNTAX  INTEGER
		{
		serialDteRTSOther(1),
		serialDteRTSNormal(2),
		serialDteRTSForcedOn(3),
		serialDteRTSExternal(4)
		}
	ACCESS  read-write
	STATUS  mandatory
	DESCRIPTION
		"Selects RTS behavior."
	::= { serialDteConfigTableEntry 14 }

serialDteRTSDelay       OBJECT-TYPE
	SYNTAX  INTEGER
		{
		serialDteRTSDelayOther(1),
		serialDteRTSDelayNormal(2),
		serialDteRTSDelayLong(3)
		}
	ACCESS  read-write
	STATUS  mandatory
	DESCRIPTION
		"Selects RTS to CTS transition delay."
	::= { serialDteConfigTableEntry 15 }
	
serialDteDTR    OBJECT-TYPE
	SYNTAX  INTEGER
		{
		serialDteDTROther(1),
		serialDteDTRFalse(2),
		serialDteDTRTrue(3)
		}
	ACCESS  read-only
	STATUS  mandatory
	DESCRIPTION
		"Reports if DTR from the DTE device is false."
	::= { serialDteConfigTableEntry 16 }

serialDteCTS    OBJECT-TYPE
	SYNTAX  INTEGER
		{
		serialDteCTSOther(1),
		serialDteCTSForceTrue(2),
		serialDteCTSForceFalse(3),
		serialDteCTSInternal(4)
		}
	ACCESS  read-write
	STATUS  mandatory
	DESCRIPTION
		"Specifies the control of the CTS signal at the port."
	::= { serialDteConfigTableEntry 17 }

serialDteV54    OBJECT-TYPE
	SYNTAX  INTEGER
		{
		serialDteV54Other(1),
		serialDteV54Disable(2),
		serialDteV54Enable(3)
		}
	ACCESS  read-write
	STATUS  mandatory
	DESCRIPTION
		"Specifies if the unit should respond to inband V.54 loop commands."
	::= { serialDteConfigTableEntry 18 }

serialDteLL     OBJECT-TYPE
	SYNTAX  INTEGER
		{
		serialDteLLOther(1),
		serialDteLLDisable(2),
		serialDteLLEnable(3)
		}
	ACCESS  read-write
	STATUS  mandatory
	DESCRIPTION
		"Specifies if the unit should respond to local loop activation by the local loopback signal (EIA530 or RS-232 pin 18)."
	::= { serialDteConfigTableEntry 19 }

serialDteRL     OBJECT-TYPE
	SYNTAX  INTEGER
		{
		serialDteRLOther(1),
		serialDteRLDisable(2),
		serialDteRLEnable(3)
		}
	ACCESS  read-write
	STATUS  mandatory
	DESCRIPTION
		"Specifies if the unit should respond to remote loop activation by the remote loopback signal (EIA530 or RS-232 pin 21)."
	::= { serialDteConfigTableEntry 20 }

serialDteStartChannel OBJECT-TYPE
	SYNTAX  INTEGER
	ACCESS  read-write
	STATUS  mandatory
	DESCRIPTION
		"Specifies the starting channel for the interface."
	::= { serialDteConfigTableEntry 21 }

serialDteNumberOfChannels OBJECT-TYPE
	SYNTAX  INTEGER
	ACCESS  read-write
	STATUS  mandatory
	DESCRIPTION
		"Specifies the number of channels allocated to the interface."
	::= { serialDteConfigTableEntry 22 }

serialDteTxClock OBJECT-TYPE
	SYNTAX  INTEGER
		{
		serialDteTxClockOther(1),
		serialDteTxClockInternal(2),
		serialDteTxClockExternal(3),
		serialDteTxClockOversample(4)
		}
	ACCESS  read-write
	STATUS  mandatory
	DESCRIPTION
		"Specifies how the interface derives its transmit clock."
	::= { serialDteConfigTableEntry 23 }

serialDteBundle  OBJECT-TYPE
	SYNTAX  INTEGER
		{
		other(1),
        contiguous(2),
		alternate(3)
		}
	ACCESS  read-write
	STATUS  mandatory
	DESCRIPTION
		"Specifies the allocation pattern of channels assigned
         to the serial port."
	::= { serialDteConfigTableEntry 24 }

serialDteChannelRate    OBJECT-TYPE
	SYNTAX  INTEGER
		{
		other(1),
		nx56k(2),
		nx64k(3)
		}
	ACCESS  read-write
	STATUS  mandatory
	DESCRIPTION
		"Specifies the rate of all channels assigned to the serial port."
	::= { serialDteConfigTableEntry 25 }

serialDteInvertClock    OBJECT-TYPE
    SYNTAX    INTEGER
		{
        other(1),
		disabled(2),
		enabled(3)
		}
	ACCESS  read-write
	STATUS  mandatory
	DESCRIPTION
		"Specifies if an inverted clock is used to send data from the serial port."
	::= { serialDteConfigTableEntry 26 }


serialDteAlarmTable     OBJECT-TYPE
	SYNTAX  SEQUENCE OF SerialDteAlarmTableEntry
	ACCESS  not-accessible
	STATUS  optional
	DESCRIPTION
		"The Serial DTE Alarm Table."
	::= { serialDte 2 }

serialDteAlarmTableEntry        OBJECT-TYPE
	SYNTAX  SerialDteAlarmTableEntry
	ACCESS  not-accessible
	STATUS  mandatory
	DESCRIPTION
		"An entry in the serial DTE Alarm Table."
	INDEX   { serialDteAlarmNearIndex, serialDteAlarmFarIndex, serialDteAlarmIndex }
	::= { serialDteAlarmTable 1 }

SerialDteAlarmTableEntry ::=
	SEQUENCE
	{
	serialDteAlarmNearIndex         INTEGER,
	serialDteAlarmFarIndex          INTEGER,
	serialDteAlarmIndex             INTEGER,
	serialDteDTRAlarmControl        INTEGER,
	serialDteDTRAlarmStatus         INTEGER,

	serialDteStatusSummary     DisplayString,
	serialDteAlarmSummary      DisplayString,

	serialDteASCStatus         INTEGER,
	serialDteASCCount          INTEGER,
	serialDteASCThreshold      INTEGER,
	serialDteASCAlarm          INTEGER,

	serialDteFDLStatus         INTEGER,
	serialDteFDLCount          INTEGER,
	serialDteFDLThreshold      INTEGER,
	serialDteFDLAlarm          INTEGER,

	serialDteLOSStatus         INTEGER,
	serialDteLOSCount          INTEGER,
	serialDteLOSThreshold      INTEGER,
	serialDteLOSAlarm          INTEGER
	}

serialDteAlarmNearIndex         OBJECT-TYPE
	SYNTAX  INTEGER
	ACCESS  read-only
	STATUS  mandatory
	DESCRIPTION
		"Selects the near device."
	::= { serialDteAlarmTableEntry 1 }

serialDteAlarmFarIndex          OBJECT-TYPE
	SYNTAX  INTEGER
	ACCESS  read-only
	STATUS  mandatory
	DESCRIPTION
		"Selects the far device."
	::= { serialDteAlarmTableEntry 2 }

serialDteAlarmIndex     OBJECT-TYPE
	SYNTAX  INTEGER
	ACCESS  read-only
	STATUS  mandatory
	DESCRIPTION
		"Index into the serialDteAlarmTable."
	::= { serialDteAlarmTableEntry 3 }

serialDteDTRAlarmControl        OBJECT-TYPE
	SYNTAX  INTEGER
		{
		serialDteDTRAlarmOther(1),
		serialDteDTRAlarmDisable(2),
		serialDteDTRAlarmEnable(3)
		}
	ACCESS  read-write
	STATUS  mandatory
	DESCRIPTION
		"Specifies if the unit should alarm on loss of DTR."
	::= { serialDteAlarmTableEntry 4 }

serialDteDTRAlarmStatus OBJECT-TYPE
	SYNTAX  INTEGER
		{
		serialDteDTRAlarmOther(1),
		serialDteDTRAlarmNone(2),
		serialDteDTRAlarmActive(3)
		}
	ACCESS  read-only
	STATUS  mandatory
	DESCRIPTION     
		"This status indicates a DTR Loss alarm is active."
	::= { serialDteAlarmTableEntry 5 }

serialDteStatusSummary     OBJECT-TYPE
	SYNTAX  DisplayString (SIZE(0..80))
	ACCESS  read-only
	STATUS  mandatory
	DESCRIPTION
		"This object provides a summary of the port status."
	::= { serialDteAlarmTableEntry 6 }

serialDteAlarmSummary      OBJECT-TYPE
	SYNTAX  DisplayString (SIZE(0..80))
	ACCESS  read-only
	STATUS  mandatory
	DESCRIPTION
		"This object provides a summary of the port alarms."
	::= { serialDteAlarmTableEntry 7 }

serialDteASCStatus OBJECT-TYPE
	SYNTAX  INTEGER
		{
		serialDteStatusASCOther(1),
		serialDteStatusNoASC(2),
		serialDteStatusASC(3)
		}
	ACCESS  read-only
	STATUS  mandatory
	DESCRIPTION
		"Reports if an ASC condition exists on the interface."
	::= { serialDteAlarmTableEntry 8 }

serialDteASCCount  OBJECT-TYPE
	SYNTAX  INTEGER
	ACCESS  read-only
	STATUS  mandatory
	DESCRIPTION
		"This count contains the number of ASC seconds received by the interface."
	::= { serialDteAlarmTableEntry 9 }

serialDteASCThreshold      OBJECT-TYPE
	SYNTAX  INTEGER
	ACCESS  read-write
	STATUS  mandatory
	DESCRIPTION
		"The number of ASC seconds that must be received before an alarm is declared."
	::= { serialDteAlarmTableEntry 10 }

serialDteASCAlarm  OBJECT-TYPE
	SYNTAX  INTEGER
		{
		serialDteASCAlarmOther(1),
		serialDteASCAlarmNone(2),
		serialDteASCAlarmThresholdExceeded(3)
		}
	ACCESS  read-only
	STATUS  mandatory
	DESCRIPTION     
		"This status indicates if the ASC Seconds threshold is exceeded."
	::= { serialDteAlarmTableEntry 11 }

serialDteFDLStatus OBJECT-TYPE
	SYNTAX  INTEGER
		{
		serialDteStatusFDLOther(1),
		serialDteStatusNoFDL(2),
		serialDteStatusFDL(3)
		}
	ACCESS  read-only
	STATUS  mandatory
	DESCRIPTION
		"Reports if an FDL error condition exists on the interface."
	::= { serialDteAlarmTableEntry 12 }

serialDteFDLCount  OBJECT-TYPE
	SYNTAX  INTEGER
	ACCESS  read-only
	STATUS  mandatory
	DESCRIPTION
		"This count contains the number of FDL errored seconds received by the interface."
	::= { serialDteAlarmTableEntry 13 }

serialDteFDLThreshold      OBJECT-TYPE
	SYNTAX  INTEGER
	ACCESS  read-write
	STATUS  mandatory
	DESCRIPTION
		"The number of FDL errored seconds that must be received before an alarm is declared."
	::= { serialDteAlarmTableEntry 14 }

serialDteFDLAlarm  OBJECT-TYPE
	SYNTAX  INTEGER
		{
		serialDteFDLAlarmOther(1),
		serialDteFDLAlarmNone(2),
		serialDteFDLAlarmThresholdExceeded(3)
		}
	ACCESS  read-only
	STATUS  mandatory
	DESCRIPTION     
		"This status indicates if the FDL Errored Seconds threshold is exceeded."
	::= { serialDteAlarmTableEntry 15 }

serialDteLOSStatus OBJECT-TYPE
	SYNTAX  INTEGER
		{
		serialDteStatusLOSOther(1),
		serialDteStatusNoLOS(2),
		serialDteStatusLOS(3)
		}
	ACCESS  read-only
	STATUS  mandatory
	DESCRIPTION
		"Reports if an LOS condition exists on the interface."
	::= { serialDteAlarmTableEntry 16 }

serialDteLOSCount  OBJECT-TYPE
	SYNTAX  INTEGER
	ACCESS  read-only
	STATUS  mandatory
	DESCRIPTION
		"This count contains the number of LOS seconds received by the interface."
	::= { serialDteAlarmTableEntry 17 }

serialDteLOSThreshold      OBJECT-TYPE
	SYNTAX  INTEGER
	ACCESS  read-write
	STATUS  mandatory
	DESCRIPTION
		"The number of LOS seconds that must be received before an alarm is declared."
	::= { serialDteAlarmTableEntry 18 }

serialDteLOSAlarm  OBJECT-TYPE
	SYNTAX  INTEGER
		{
		serialDteLOSAlarmOther(1),
		serialDteLOSAlarmNone(2),
		serialDteLOSAlarmThresholdExceeded(3)
		}
	ACCESS  read-only
	STATUS  mandatory
	DESCRIPTION     
		"This status indicates if the LOS Seconds threshold is exceeded."
	::= { serialDteAlarmTableEntry 19 }



-- analog DTE section

analogDteTable  OBJECT-TYPE
	SYNTAX  SEQUENCE OF AnalogDteTableEntry
	ACCESS  not-accessible
	STATUS  optional
	DESCRIPTION
		"The Analog DTE Table."
	::= { analogDte 1 }

analogDteTableEntry     OBJECT-TYPE
	SYNTAX  AnalogDteTableEntry
	ACCESS  not-accessible
	STATUS  mandatory
	DESCRIPTION
		"An entry in the Analog DTE Table."
	INDEX   { analogDteNearIndex, analogDteFarIndex, analogDteIndex }
	::= { analogDteTable 1 }

AnalogDteTableEntry ::=
	SEQUENCE
	{
	analogDteNearIndex      INTEGER,
	analogDteFarIndex       INTEGER,
	analogDteIndex          INTEGER,

	analogDteDescription    DisplayString,
	analogDteCardType       INTEGER,        
	analogDteMode           INTEGER,
	analogDteState          INTEGER,
	analogDteElementID      DisplayString,
	analogDteSignalling     INTEGER,
	analogDteDNISDelay      INTEGER,
	analogDteTxGain         INTEGER,
	analogDteRxGain         INTEGER
	}

analogDteNearIndex              OBJECT-TYPE
	SYNTAX  INTEGER
	ACCESS  read-only
	STATUS  mandatory
	DESCRIPTION
		"Selects the near device."
	::= { analogDteTableEntry 1 }

analogDteFarIndex               OBJECT-TYPE
	SYNTAX  INTEGER
	ACCESS  read-only
	STATUS  mandatory
	DESCRIPTION
		"Selects the far device."
	::= { analogDteTableEntry 2 }

analogDteIndex  OBJECT-TYPE
	SYNTAX  INTEGER
	ACCESS  read-only
	STATUS  mandatory
	DESCRIPTION
		"Index into the analogDteTable."
	::= { analogDteTableEntry 3 }

analogDteDescription    OBJECT-TYPE
	SYNTAX  DisplayString( SIZE(0..40) )
	ACCESS  read-only
	STATUS  mandatory
	DESCRIPTION
		"Contains a textual description of the port."
	::= { analogDteTableEntry 4 }

analogDteCardType       OBJECT-TYPE
	SYNTAX  INTEGER
		{
		analogDteCardTypeOther(1),
		analogDteCardTypeFXS(2),
		analogDteCardTypeFXO(3),
		analogDteCardType4WEM(4)
		}
	ACCESS  read-only
	STATUS  mandatory
	DESCRIPTION
		"Identifies the analog DTE card type."
	::= { analogDteTableEntry 5 }

analogDteMode   OBJECT-TYPE
	SYNTAX  INTEGER
		{
		analogDteModeOther(1),
		analogDteModeSpare(2),
		analogDteModeActive(3)
		}
	ACCESS  read-write
	STATUS  mandatory
	DESCRIPTION
		"Selects whether the port is actively assigned to a netowrk channel or not used."
	::= { analogDteTableEntry 6 }

analogDteState  OBJECT-TYPE
	SYNTAX  INTEGER
		{
		analogDteStateOther(1),
		analogDteStateIdle(2),
		analogDteStateBusy(3)
		}
	ACCESS  read-only
	STATUS  mandatory
	DESCRIPTION
		"Displays the port status as either in the Busy or Idle state."
	::= { analogDteTableEntry 7 }

analogDteElementID      OBJECT-TYPE
	SYNTAX  DisplayString( SIZE(0..20) )
	ACCESS  read-write
	STATUS  mandatory
	DESCRIPTION
		"This object signifies the name of the device."
	::= { analogDteTableEntry 8 }

analogDteSignalling     OBJECT-TYPE
	SYNTAX  INTEGER
		{
		analogDteSignallingOther(1),
		analogDteSignallingFXSLS(2),
		analogDteSignallingFXSGS(3),
		analogDteSignallingUVG(4),
		analogDteSignallingMEGLS(5),
		analogDteSignallingMEGGS(6),
		analogDteSignallingMEGRLS(7),
		analogDteSignallingMEGRGS(8),
		analogDteSignallingPLAR(9),
		analogDteSignallingSLC96(10),
		analogDteSignallingDIDDNIS(11),
		analogDteSignallingDNISWLS(12),
		analogDteSignallingDNISDLS(13),
		analogDteSignallingDNISWRLS(14),
		analogDteSignallingDNISDRLS(15),
		analogDteSignallingDNISWGS(16),
		analogDteSignallingDNISDGS(17),
		analogDteSignallingDNISWRGS(18),
		analogDteSignallingDNISDRGS(19),
		analogDteSignallingFXOLS(20),
		analogDteSignallingFXOGS(21),
		analogDteSignallingFXOUVG(22),
		analogDteSignallingFXOUVGR(23),
		analogDteSignalling4WEMTYPE1(24),
		analogDteSignalling4WEMTYPE2(25),
		analogDteSignalling4WEMTYPE3(26),
		analogDteSignalling4WEMTYPE4(27),
		analogDteSignalling4WEMTYPE5(28),
		analogDteSignalling4WEMTO(29)
		}
	ACCESS  read-write
	STATUS  mandatory
	DESCRIPTION
		"Selects the supervisory operation of the port."
	::= { analogDteTableEntry 9 }

analogDteDNISDelay      OBJECT-TYPE
	SYNTAX  INTEGER
		{
		analogDteDNISDelayOther(1),
		analogDteDNISDelay1Second(2),
		analogDteDNISDelay2Seconds(3),
		analogDteDNISDelay3Seconds(4),
		analogDteDNISDelay4Seconds(5),
		analogDteDNISDelay5Seconds(6)
		}
	ACCESS  read-write
	STATUS  mandatory
	DESCRIPTION
		"If the signalling mode has a delay, it can be set from 1 to 5 seconds."
	::= { analogDteTableEntry 10 }

analogDteTxGain OBJECT-TYPE
	SYNTAX  INTEGER
		{
		analogDteTxGainOther(1),
		analogDteTxGain3DB(2),
		analogDteTxGain2DB(3),
		analogDteTxGain1DB(4),
		analogDteTxGain0DB(5),
		analogDteTxGainm1DB(6),
		analogDteTxGainm2DB(7),
		analogDteTxGainm3DB(8),
		analogDteTxGainm4DB(9),
		analogDteTxGainm5DB(10),
		analogDteTxGainm6DB(11),
		analogDteTxGainm7DB(12),
		analogDteTxGainm8DB(13),
		analogDteTxGainm9DB(14),
		analogDteTxGainm10DB(15)
		}
	ACCESS  read-write
	STATUS  mandatory
	DESCRIPTION
		"Selects the transmit gain.  Values prefixed with m are negative."
	::= { analogDteTableEntry 11 }

analogDteRxGain         OBJECT-TYPE
	SYNTAX  INTEGER
		{
		analogDteRxGainOther(1),
		analogDteRxGain2DB(2),
		analogDteRxGain1DB(3),
		analogDteRxGain0DB(4),
		analogDteRxGainm1DB(5),
		analogDteRxGainm2DB(6),
		analogDteRxGainm3DB(7),
		analogDteRxGainm4DB(8),
		analogDteRxGainm5DB(9),
		analogDteRxGainm6DB(10),
		analogDteRxGainm7DB(11),
		analogDteRxGainm8DB(12),
		analogDteRxGainm9DB(13),
		analogDteRxGainm10DB(14),
		analogDteRxGainm11DB(15),
		analogDteRxGainm12DB(16),
		analogDteRxGainm13DB(17),
		analogDteRxGainm14DB(18),
		analogDteRxGainm15DB(19),
		analogDteRxGainm16DB(20)
		}
	ACCESS  read-write
	STATUS  mandatory
	DESCRIPTION
		"Selects the receive gain.  Values prefixed with m are negative."
	::= { analogDteTableEntry 12 }

-- connection table
-- allows for configuration/connection of dte ports to network ports

connectionTable OBJECT-TYPE
	SYNTAX  SEQUENCE OF ConnectionTableEntry
	ACCESS  not-accessible
	STATUS  optional
	DESCRIPTION
		"The connection table."
	::= { connection 1 }

connectionTableEntry    OBJECT-TYPE
	SYNTAX  ConnectionTableEntry
	ACCESS  not-accessible
	STATUS  mandatory
	DESCRIPTION
		"An entry in the connection table."
	INDEX   { connectionNearIndex, connectionFarIndex, connectionTableIndex }
	::= { connectionTable 1 }

ConnectionTableEntry ::=
	SEQUENCE
	{
	connectionNearIndex             INTEGER,
	connectionFarIndex              INTEGER,
	connectionTableIndex            INTEGER,
	connectionTableDescription      DisplayString
	}

connectionNearIndex             OBJECT-TYPE
	SYNTAX  INTEGER
	ACCESS  read-only
	STATUS  mandatory
	DESCRIPTION
		"Selects the near device."
	::= { connectionTableEntry 1 }

connectionFarIndex              OBJECT-TYPE
	SYNTAX  INTEGER
	ACCESS  read-only
	STATUS  mandatory
	DESCRIPTION
		"Selects the far device."
	::= { connectionTableEntry 2 }

connectionTableIndex    OBJECT-TYPE
	SYNTAX  INTEGER
	ACCESS  read-only
	STATUS  mandatory
	DESCRIPTION
		"The index into the connection table."
	::= { connectionTableEntry 3 }

connectionTableDescription      OBJECT-TYPE
	SYNTAX  DisplayString(SIZE(0..60))
	ACCESS  read-only
	STATUS  mandatory
	DESCRIPTION
		"A description of the connection."
	::= { connectionTableEntry 4 }

connectionChannelTable  OBJECT-TYPE
	SYNTAX  SEQUENCE OF ConnectionChannelEntry
	ACCESS  not-accessible
	STATUS  mandatory
	DESCRIPTION
		"The channel-level connection table."
	::= { connection 2 }

connectionChannelEntry  OBJECT-TYPE
	SYNTAX  ConnectionChannelEntry
	ACCESS  not-accessible
	STATUS  mandatory
	DESCRIPTION
		"An entry in the connectionChannelTable."
	INDEX   { connectionChannelNearIndex, connectionChannelFarIndex, connectionChannelLineIndex, connectionChannelIndex }
	::= { connectionChannelTable 1 }

ConnectionChannelEntry ::=
	SEQUENCE
	{
	connectionChannelNearIndex      INTEGER,
	connectionChannelFarIndex       INTEGER,
	connectionChannelLineIndex      INTEGER,
	connectionChannelIndex          INTEGER,
	channelInterfaceAssignment      INTEGER,
	channelInterfaceDescription     DisplayString,
	channelInterfaceChannel         INTEGER,
	channelSignalling		INTEGER
	}

connectionChannelNearIndex              OBJECT-TYPE
	SYNTAX  INTEGER
	ACCESS  read-only
	STATUS  mandatory
	DESCRIPTION
		"Selects the near device."
	::= { connectionChannelEntry 1 }

connectionChannelFarIndex               OBJECT-TYPE
	SYNTAX  INTEGER
	ACCESS  read-only
	STATUS  mandatory
	DESCRIPTION
		"Selects the far device."
	::= { connectionChannelEntry 2 }

connectionChannelLineIndex     OBJECT-TYPE
	SYNTAX  INTEGER
	ACCESS  read-only
	STATUS  mandatory
	DESCRIPTION
		"Selects instance of line."
	::= { connectionChannelEntry 3 }

connectionChannelIndex  OBJECT-TYPE
	SYNTAX  INTEGER
	ACCESS  read-only
	STATUS  mandatory
	DESCRIPTION
		"The index into the connection table."
	::= { connectionChannelEntry 4 }

channelInterfaceAssignment  OBJECT-TYPE
	SYNTAX  INTEGER
		{
		other(1),
		unassigned(2),
		dTE(3),
		remComm(4),
		port1(5),
		port2(6),
		port3(7),
		port4(8),
		port5(9),
		port6(10),
		port7(11),
		port8(12),
		port9(13),
		port10(14),
		port11(15),
		port12(16),
		port13(17),
		port14(18),
		port15(19),
		port16(20),
		port17(21),
		port18(22),
		port19(23),
		port20(24),
		port21(25),
		port22(26),
		port23(27),
		port24(28),
		port25(29),
		port26(30),
		port27(31),
		port28(32),
		port29(33),
		port30(34),
		port31(35),
		port32(36),

		slot2PortA(37),
		slot2PortB(38),
		slot3PortA(39),
		slot3PortB(40),
		slot4PortA(41),
		slot4PortB(42),
		slot5PortA(43),
		slot5PortB(44),
		slot6PortA(45),
		slot6PortB(46),

		slot2Dsu1PortA(47),
		slot2Dsu1PortB(48),
		slot2Dsu2PortA(49),
		slot2Dsu2PortB(50),
		slot2Dsu3PortA(51),
		slot2Dsu3PortB(52),
		slot2Dsu4PortA(53),
		slot2Dsu4PortB(54),
		slot2Dsu5PortA(55),
		slot2Dsu5PortB(56),
		slot2Dsu6PortA(57),
		slot2Dsu6PortB(58),

		slot3Dsu1PortA(59),
		slot3Dsu1PortB(60),
		slot3Dsu2PortA(61),
		slot3Dsu2PortB(62),
		slot3Dsu3PortA(63),
		slot3Dsu3PortB(64),
		slot3Dsu4PortA(65),
		slot3Dsu4PortB(66),
		slot3Dsu5PortA(67),
		slot3Dsu5PortB(68),
		slot3Dsu6PortA(69),
		slot3Dsu6PortB(70),

		slot4Dsu1PortA(71),
		slot4Dsu1PortB(72),
		slot4Dsu2PortA(73),
		slot4Dsu2PortB(74),
		slot4Dsu3PortA(75),
		slot4Dsu3PortB(76),
		slot4Dsu4PortA(77),
		slot4Dsu4PortB(78),
		slot4Dsu5PortA(79),
		slot4Dsu5PortB(80),
		slot4Dsu6PortA(81),
		slot4Dsu6PortB(82),

		slot5Dsu1PortA(83),
		slot5Dsu1PortB(84),
		slot5Dsu2PortA(85),
		slot5Dsu2PortB(86),
		slot5Dsu3PortA(87),
		slot5Dsu3PortB(88),
		slot5Dsu4PortA(89),
		slot5Dsu4PortB(90),
		slot5Dsu5PortA(91),
		slot5Dsu5PortB(92),
		slot5Dsu6PortA(93),
		slot5Dsu6PortB(94),

		slot6Dsu1PortA(95),
		slot6Dsu1PortB(96),
		slot6Dsu2PortA(97),
		slot6Dsu2PortB(98),
		slot6Dsu3PortA(99),
		slot6Dsu3PortB(100),
		slot6Dsu4PortA(101),
		slot6Dsu4PortB(102),
		slot6Dsu5PortA(103),
		slot6Dsu5PortB(104),
		slot6Dsu6PortA(105),
		slot6Dsu6PortB(106)
		}

	ACCESS  read-write
	STATUS  mandatory
	DESCRIPTION
		"The channel assignment."
	::= { connectionChannelEntry 5 }

channelInterfaceDescription     OBJECT-TYPE
	SYNTAX  DisplayString(SIZE(0..40))
	ACCESS  read-only
	STATUS  mandatory
	DESCRIPTION
		"Contains a description of the interface channel connection."
	::= { connectionChannelEntry 6 }

channelInterfaceChannel OBJECT-TYPE
	SYNTAX  INTEGER
	ACCESS  read-write
	STATUS  mandatory
	DESCRIPTION
		"Displays the corresponding channel of the interface channel connection."
	::= { connectionChannelEntry 7 }

channelSignalling	OBJECT-TYPE
	SYNTAX	INTEGER
		{
		other(1),
		clearChannel(2),
		robbedBit(3)
		}
	ACCESS	read-write
	STATUS	mandatory
	DESCRIPTION
		"Allows a selection of Clear Channel or Robbed Bit signalling for each DS0."
	::= { connectionChannelEntry 8 }

-- maintenance section
-- controls tests

--
-- BERT Table
--

bertTable       OBJECT-TYPE
	SYNTAX  SEQUENCE OF BertTableEntry
	ACCESS  not-accessible
	STATUS  optional
	DESCRIPTION
		"BERT control table."
	::= { maintenance 1 }

bertTableEntry  OBJECT-TYPE
	SYNTAX  BertTableEntry
	ACCESS  not-accessible
	STATUS  mandatory
	DESCRIPTION
		"An entry in the BERT control table."
	INDEX   { bertNearIndex, bertFarIndex, bertIndex }
	::= { bertTable 1 }

BertTableEntry ::=
	SEQUENCE
	{
	bertNearIndex           INTEGER,
	bertFarIndex            INTEGER,
	bertIndex               INTEGER,
	bertPattern             INTEGER,
	bertLength              INTEGER,
	bertPatternSync         INTEGER,
	bertElapsedTime         INTEGER,
	bertBitErrors           INTEGER,
	bertErroredSeconds      INTEGER,
	bertPercentEFS          INTEGER,
	bertCommand             INTEGER
	}

bertNearIndex           OBJECT-TYPE
	SYNTAX  INTEGER
	ACCESS  read-only
	STATUS  mandatory
	DESCRIPTION
		"Selects the near device."
	::= { bertTableEntry 1 }

bertFarIndex            OBJECT-TYPE
	SYNTAX  INTEGER
	ACCESS  read-only
	STATUS  mandatory
	DESCRIPTION
		"Selects the far device."
	::= { bertTableEntry 2 }

bertIndex       OBJECT-TYPE
	SYNTAX  INTEGER
	ACCESS  read-only
	STATUS  mandatory
	DESCRIPTION
		"The index into the BERT control table.  Selects which BERT chip to use."
	::= { bertTableEntry 3 }

bertPattern     OBJECT-TYPE
	SYNTAX  INTEGER
		{
		bertPatternOther(1),
		bertPatternQRSS(2),
		bertPattern63(3),
		bertPattern511(4),
		bertPattern2047(5),
		bertPattern215(6),
		bertPattern220(7),
		bertPattern223(8),
		bertPattern1in8(9),
		bertPattern3in24(10),
		bertPatternALT(11),
		bertPatternCLEAR(12)
		}
	ACCESS  read-write
	STATUS  mandatory
	DESCRIPTION
		"Selects the test pattern to be used."
	::= { bertTableEntry 4 }

bertLength      OBJECT-TYPE
	SYNTAX  INTEGER
		{
		bertLengthOther(1),
		bertLength15minutes(2),
		bertLength30minutes(3),
		bertLength60minutes(4),
		bertLength24hours(5),
		bertLengthContinuous(6)
		}
	ACCESS  read-write
	STATUS  mandatory
	DESCRIPTION
		"Specifies how long the test should run."
	::= { bertTableEntry 5 }

bertPatternSync OBJECT-TYPE
	SYNTAX  INTEGER
		{
		bertPatternSyncOther(1),
		bertPatternSyncNoTest(2),
		bertPatternSyncNoSync(3),
		bertPatternSyncInsync(4)
		}
	ACCESS  read-only
	STATUS  mandatory
	DESCRIPTION
		"Displays the current state of pattern sync during a test."
	::= { bertTableEntry 6 }

bertElapsedTime OBJECT-TYPE
	SYNTAX  INTEGER
	ACCESS  read-only
	STATUS  mandatory
	DESCRIPTION
		"Displays the amount of time elapsed since a timed test began in seconds."
	::= { bertTableEntry 7 }

bertBitErrors   OBJECT-TYPE
	SYNTAX  INTEGER
	ACCESS  read-only
	STATUS  mandatory
	DESCRIPTION
		"Displays the total number of bit errors detected since the test began."
	::= { bertTableEntry 8 }

bertErroredSeconds      OBJECT-TYPE
	SYNTAX  INTEGER
	ACCESS  read-only
	STATUS  mandatory
	DESCRIPTION
		"Displays the number of asynchronous errored seconds that have been detected since the test began."
	::= { bertTableEntry 9 }

bertPercentEFS  OBJECT-TYPE
	SYNTAX  INTEGER
	ACCESS  read-only
	STATUS  mandatory
	DESCRIPTION
		"Displays a ratio derived from the number of error free seconds divided by the number of seconds accumulated in elapsed time."
	::= { bertTableEntry 10 }

bertCommand     OBJECT-TYPE
	SYNTAX  INTEGER
		{
		bertCommandOther(1),
		bertCommandStart(2),
		bertCommandStop(3),
		bertCommandResetErrors(4),
		bertCommandInjectError(5)
		}
	ACCESS  read-write
	STATUS  mandatory
	DESCRIPTION
		"Issues a test command for the interface."
	::= { bertTableEntry 11 }

bertInterfaceTable      OBJECT-TYPE
	SYNTAX  SEQUENCE OF BertInterfaceTableEntry
	ACCESS  not-accessible
	STATUS  mandatory
	DESCRIPTION
		"BERT control interface table."
	::= { maintenance 2 }

bertInterfaceTableEntry OBJECT-TYPE
	SYNTAX  BertInterfaceTableEntry
	ACCESS  not-accessible
	STATUS  mandatory
	DESCRIPTION
		"An entry in the BERT control interface table."
	INDEX   { bertInterfaceNearIndex, bertInterfaceFarIndex, bertChipIndex, bertInterfaceIndex }
	::= { bertInterfaceTable 1 }

BertInterfaceTableEntry ::=
	SEQUENCE
	{
	bertInterfaceNearIndex  INTEGER,
	bertInterfaceFarIndex   INTEGER,
	bertChipIndex           INTEGER,
	bertInterfaceIndex      INTEGER,
	bertInterfaceSetting    INTEGER
	}

bertInterfaceNearIndex          OBJECT-TYPE
	SYNTAX  INTEGER
	ACCESS  read-only
	STATUS  mandatory
	DESCRIPTION
		"Selects the near device."
	::= { bertInterfaceTableEntry 1 }

bertInterfaceFarIndex           OBJECT-TYPE
	SYNTAX  INTEGER
	ACCESS  read-only
	STATUS  mandatory
	DESCRIPTION
		"Selects the far device."
	::= { bertInterfaceTableEntry 2 }

bertChipIndex           OBJECT-TYPE
	SYNTAX  INTEGER
	ACCESS  read-only
	STATUS  mandatory
	DESCRIPTION
		"Selects which BERT chip to use."
	::= { bertInterfaceTableEntry 3 }

bertInterfaceIndex      OBJECT-TYPE
	SYNTAX  INTEGER
	ACCESS  read-only
	STATUS  mandatory
	DESCRIPTION
		"An index into the MIB-II interfaces table; the interface for the BERT settings."
	::= { bertInterfaceTableEntry 4 }

bertInterfaceSetting    OBJECT-TYPE
	SYNTAX  INTEGER
		{
		bertInterfaceSettingOther(1),
		bertInterfaceSettingIdle(2),
		bertInterfaceSettingChannel1(3),
		bertInterfaceSettingChannel2(4),
		bertInterfaceSettingChannel3(5),
		bertInterfaceSettingChannel4(6),
		bertInterfaceSettingChannel5(7),
		bertInterfaceSettingChannel6(8),
		bertInterfaceSettingChannel7(9),
		bertInterfaceSettingChannel8(10),
		bertInterfaceSettingChannel9(11),
		bertInterfaceSettingChannel10(12),
		bertInterfaceSettingChannel11(13),
		bertInterfaceSettingChannel12(14),
		bertInterfaceSettingChannel13(15),
		bertInterfaceSettingChannel14(16),
		bertInterfaceSettingChannel15(17),
		bertInterfaceSettingChannel16(18),
		bertInterfaceSettingChannel17(19),
		bertInterfaceSettingChannel18(20),
		bertInterfaceSettingChannel19(21),
		bertInterfaceSettingChannel20(22),
		bertInterfaceSettingChannel21(23),
		bertInterfaceSettingChannel22(24),
		bertInterfaceSettingChannel23(25),
		bertInterfaceSettingChannel24(26),
		bertInterfaceSettingChannel25(27),
		bertInterfaceSettingChannel26(28),
		bertInterfaceSettingChannel27(29),
		bertInterfaceSettingChannel28(30),
		bertInterfaceSettingChannel29(31),
		bertInterfaceSettingChannel30(32),
		bertInterfaceSettingChannel31(33),
		bertInterfaceSettingChannel32(34),
 		bertInterfaceSettingNet(35),
		bertInterfaceSettingDTE(36),
		bertInterfaceSettingNotEnabled(37)
		}
	ACCESS  read-write
	STATUS  mandatory
	DESCRIPTION
		"Specifies the interface for the BERT chip."
	::= { bertInterfaceTableEntry 5 }

--
-- Test Table
--

testTable       OBJECT-TYPE
	SYNTAX  SEQUENCE OF TestTableEntry
	ACCESS  not-accessible
	STATUS  optional
	DESCRIPTION
		"Test control table."
	::= { maintenance 3 }

testTableEntry  OBJECT-TYPE
	SYNTAX  TestTableEntry
	ACCESS  not-accessible
	STATUS  mandatory
	DESCRIPTION
		"An entry in the testTable."
	INDEX   { testNearIndex, testFarIndex, testTableIndex }
	::= { testTable 1 }
	
TestTableEntry ::=
	SEQUENCE
	{
	testNearIndex           INTEGER,
	testFarIndex            INTEGER,
	testTableIndex          INTEGER,
	testType                INTEGER,
	testLoopDirection       INTEGER,
	testFarLLBFraming       INTEGER
	}

testNearIndex           OBJECT-TYPE
	SYNTAX  INTEGER
	ACCESS  read-only
	STATUS  mandatory
	DESCRIPTION
		"Selects the near device."
	::= { testTableEntry 1 }

testFarIndex            OBJECT-TYPE
	SYNTAX  INTEGER
	ACCESS  read-only
	STATUS  mandatory
	DESCRIPTION
		"Selects the far device."
	::= { testTableEntry 2 }

testTableIndex  OBJECT-TYPE
	SYNTAX  INTEGER
	ACCESS  read-only
	STATUS  mandatory
	DESCRIPTION
		"The index into the testTable, one entry for each interface."
	::= { testTableEntry 3 }

testType        OBJECT-TYPE
	SYNTAX  INTEGER
		{
		testTypeOther(1),
		testTypeNoTest(2),
		testTypePLB(3),
		testTypeLLB(4),
		testtypeMLB(5),
		testTypeFarPLB(6),
		testTypeFarLLB(7),
		testTypeFarMLB(8),
		testTypePortLoop(9),
		testTypeV54Loop(10),    
		testTypeFarV54Loop(11)  
		}
	ACCESS  read-write
	STATUS  mandatory
	DESCRIPTION
		"Identifies the test type for the interface."
	::= { testTableEntry 4 }

testLoopDirection       OBJECT-TYPE
	SYNTAX INTEGER  
		{
		testLoopOther(1),
		testLoopUnidirectional(2),
		testLoopBidirectional(3)
		}
	ACCESS read-write
	STATUS mandatory
	DESCRIPTION
		"This object is the identifier of the current unit loop mode. The values mean:
testLoopUnidirectional
   Line, Data, and V54 loops will be unidirectional
   Local loop will be bidirectional
testLoopBidirectional
   All loops will be bidirectional"
	::= { testTableEntry 5 }

testFarLLBFraming       OBJECT-TYPE
	SYNTAX  INTEGER
		{
		testFarLLBFramingOther(1),
		testFarLLBFramingUnframed(2),
		testFarLLBFramingFramed(3)
		}
	ACCESS  read-write
	STATUS  mandatory
	DESCRIPTION
		"This setting, for Far LLB tests on T1 lines, must match the far end unit loop code framing."
	::= { testTableEntry 6 }

-- performance section
-- performance section

performance24Table      OBJECT-TYPE
	SYNTAX  SEQUENCE OF Performance24TableEntry
	ACCESS  not-accessible
	STATUS  optional
	DESCRIPTION
		"Performance table, contains TR54016 standard and enhanced data."
	::= { performance 1 }

performance24TableEntry OBJECT-TYPE
	SYNTAX  Performance24TableEntry
	ACCESS  not-accessible
	STATUS  mandatory
	DESCRIPTION
		"An entry in the performance24Table."
	INDEX   { performance24NearIndex, performance24FarIndex, performance24InterfaceIndex, performance24Index }
	::= { performance24Table 1 }

Performance24TableEntry ::=
	SEQUENCE
	{
	performance24NearIndex  INTEGER,
	performance24FarIndex   INTEGER,
	performance24InterfaceIndex      INTEGER,
	performance24Index      INTEGER,
	performance24ES         INTEGER,
	performance24BES        INTEGER,
	performance24SES        INTEGER,
	performance24UAS        INTEGER,
	performance24LOFC       INTEGER,
	performance24CSS        INTEGER,
	performance24CRCES      INTEGER,
	performance24OOFS       INTEGER,
	performance24LOSS       INTEGER,
	performance24AISS       INTEGER,
	performance24RAS        INTEGER,
	performance24BPVS       INTEGER
	}

performance24NearIndex          OBJECT-TYPE
	SYNTAX  INTEGER
	ACCESS  read-only
	STATUS  mandatory
	DESCRIPTION
		"Selects the near device."
	::= { performance24TableEntry 1 }

performance24FarIndex           OBJECT-TYPE
	SYNTAX  INTEGER
	ACCESS  read-only
	STATUS  mandatory
	DESCRIPTION
		"Selects the far device."
	::= { performance24TableEntry 2 }

performance24InterfaceIndex           OBJECT-TYPE
	SYNTAX  INTEGER
	ACCESS  read-only
	STATUS  mandatory
	DESCRIPTION
		"Selects the interface."
	::= { performance24TableEntry 3 }


performance24Index      OBJECT-TYPE
	SYNTAX  INTEGER
		{
		performance24Summary(1),
		performance24Current(2),

		performance24period1(3),
		performance24period2(4),
		performance24period3(5),
		performance24period4(6),
		performance24period5(7),
		performance24period6(8),
		performance24period7(9),
		performance24period8(10),
		performance24period9(11),

		performance24period10(12),
		performance24period11(13),
		performance24period12(14),
		performance24period13(15),
		performance24period14(16),
		performance24period15(17),
		performance24period16(18),
		performance24period17(19),
		performance24period18(20),
		performance24period19(21),

		performance24period20(22),
		performance24period21(23),
		performance24period22(24),
		performance24period23(25),
		performance24period24(26),
		performance24period25(27),
		performance24period26(28),
		performance24period27(29),
		performance24period28(30),
		performance24period29(31),

		performance24period30(32),
		performance24period31(33),
		performance24period32(34),
		performance24period33(35),
		performance24period34(36),
		performance24period35(37),
		performance24period36(38),
		performance24period37(39),
		performance24period38(40),
		performance24period39(41),

		performance24period40(42),
		performance24period41(43),
		performance24period42(44),
		performance24period43(45),
		performance24period44(46),
		performance24period45(47),
		performance24period46(48),
		performance24period47(49),
		performance24period48(50),
		performance24period49(51),

		performance24period50(52),
		performance24period51(53),
		performance24period52(54),
		performance24period53(55),
		performance24period54(56),
		performance24period55(57),
		performance24period56(58),
		performance24period57(59),
		performance24period58(60),
		performance24period59(61),

		performance24period60(62),
		performance24period61(63),
		performance24period62(64),
		performance24period63(65),
		performance24period64(66),
		performance24period65(67),
		performance24period66(68),
		performance24period67(69),
		performance24period68(70),
		performance24period69(71),

		performance24period70(72),
		performance24period71(73),
		performance24period72(74),
		performance24period73(75),
		performance24period74(76),
		performance24period75(77),
		performance24period76(78),
		performance24period77(79),
		performance24period78(80),
		performance24period79(81),

		performance24period80(82),
		performance24period81(83),
		performance24period82(84),
		performance24period83(85),
		performance24period84(86),
		performance24period85(87),
		performance24period86(88),
		performance24period87(89),
		performance24period88(90),
		performance24period89(91),

		performance24period90(92),
		performance24period91(93),
		performance24period92(94),
		performance24period93(95),
		performance24period94(96),
		performance24period95(97),
		performance24period96(98)
		}
	ACCESS  read-only
	STATUS  mandatory
	DESCRIPTION
		"The index into the 24-hour performance table."
	::= { performance24TableEntry 4 }

performance24ES OBJECT-TYPE
	SYNTAX  INTEGER
	ACCESS  read-only
	STATUS  mandatory
	DESCRIPTION
		"The number of Errored Seconds for the 15-minute period."
	::= { performance24TableEntry 5 }

performance24BES        OBJECT-TYPE
	SYNTAX  INTEGER
	ACCESS  read-only
	STATUS  mandatory
	DESCRIPTION
		"The number of Bursty Errored Seconds for the 15-minute period."
	::= { performance24TableEntry 6 }

performance24SES        OBJECT-TYPE
	SYNTAX  INTEGER
	ACCESS  read-only
	STATUS  mandatory
	DESCRIPTION
		"The number of Severely Errored Seconds for the 15-minute period."
	::= { performance24TableEntry 7 }

performance24UAS        OBJECT-TYPE
	SYNTAX  INTEGER
	ACCESS  read-only
	STATUS  mandatory
	DESCRIPTION
		"The number of Unavailable Seconds for the 15-minute period."
	::= { performance24TableEntry 8 }

performance24LOFC       OBJECT-TYPE
	SYNTAX  INTEGER
	ACCESS  read-only
	STATUS  mandatory
	DESCRIPTION
		"The number of Loss of Frame Counts for the 15-minute period."
	::= { performance24TableEntry 9 }

performance24CSS        OBJECT-TYPE
	SYNTAX  INTEGER
	ACCESS  read-only
	STATUS  mandatory
	DESCRIPTION
		"The number of Controlled Slip Seconds for the 15-minute period."
	::= { performance24TableEntry 10 }

performance24CRCES      OBJECT-TYPE
	SYNTAX  INTEGER
	ACCESS  read-only
	STATUS  mandatory
	DESCRIPTION
		"The number of CRC Errored Seconds for the 15-minute period."
	::= { performance24TableEntry 11 }

performance24OOFS       OBJECT-TYPE
	SYNTAX  INTEGER
	ACCESS  read-only
	STATUS  mandatory
	DESCRIPTION
		"The number of Out of Frame Seconds for the 15-minute period."
	::= { performance24TableEntry 12 }

performance24LOSS       OBJECT-TYPE
	SYNTAX  INTEGER
	ACCESS  read-only
	STATUS  mandatory
	DESCRIPTION
		"The number of Loss of Signal Seconds for the 15-minute period."
	::= { performance24TableEntry 13 }

performance24AISS       OBJECT-TYPE
	SYNTAX  INTEGER
	ACCESS  read-only
	STATUS  mandatory
	DESCRIPTION
		"The number of Alarm Indication Signal Seconds for the 15-minute period."
	::= { performance24TableEntry 14 }

performance24RAS        OBJECT-TYPE
	SYNTAX  INTEGER
	ACCESS  read-only
	STATUS  mandatory
	DESCRIPTION
		"The number of Remote Alarm (Yellow) Seconds for the 15-minute period."
	::= { performance24TableEntry 15 }

performance24BPVS       OBJECT-TYPE
	SYNTAX  INTEGER
	ACCESS  read-only
	STATUS  mandatory
	DESCRIPTION
		"The number of Bipolar Violation Seconds for the 15-minute period."
	::= { performance24TableEntry 16 }

performance30Table      OBJECT-TYPE
	SYNTAX  SEQUENCE OF Performance30TableEntry
	ACCESS  not-accessible
	STATUS  optional
	DESCRIPTION
		"Performance table, contains TR54016 standard and enhanced 30-day data."
	::= { performance 2 }

performance30TableEntry OBJECT-TYPE
	SYNTAX  Performance30TableEntry
	ACCESS  not-accessible
	STATUS  mandatory
	DESCRIPTION
		"An entry in the performance30Table."
	INDEX   { performance30NearIndex, performance30FarIndex, performance30InterfaceIndex, performance30Index }
	::= { performance30Table 1 }

Performance30TableEntry ::=
	SEQUENCE
	{
	performance30NearIndex  INTEGER,
	performance30FarIndex   INTEGER,
	performance30InterfaceIndex INTEGER,
	performance30Index      INTEGER,
	performance30ES         INTEGER,
	performance30BES        INTEGER,
	performance30SES        INTEGER,
	performance30UAS        INTEGER,
	performance30LOFC       INTEGER,
	performance30CSS        INTEGER,
	performance30CRCES      INTEGER,
	performance30OOFS       INTEGER,
	performance30LOSS       INTEGER,
	performance30AISS       INTEGER,
	performance30RAS        INTEGER,
	performance30BPVS       INTEGER
	}

performance30NearIndex          OBJECT-TYPE
	SYNTAX  INTEGER
	ACCESS  read-only
	STATUS  mandatory
	DESCRIPTION
		"Selects the near device."
	::= { performance30TableEntry 1 }

performance30FarIndex           OBJECT-TYPE
	SYNTAX  INTEGER
	ACCESS  read-only
	STATUS  mandatory
	DESCRIPTION
		"Selects the far device."
	::= { performance30TableEntry 2 }

performance30InterfaceIndex           OBJECT-TYPE
	SYNTAX  INTEGER
	ACCESS  read-only
	STATUS  mandatory
	DESCRIPTION
		"Selects the interface."
	::= { performance30TableEntry 3 }

performance30Index      OBJECT-TYPE
	SYNTAX  INTEGER
		{
		performance30Summary(1),

		performance30day1(2),
		performance30day2(3),
		performance30day3(4),
		performance30day4(5),
		performance30day5(6),
		performance30day6(7),
		performance30day7(8),
		performance30day8(9),
		performance30day9(10),
		performance30day10(11),
		performance30day11(12),
		performance30day12(13),
		performance30day13(14),
		performance30day14(15),
		performance30day15(16),
		performance30day16(17),
		performance30day17(18),
		performance30day18(19),
		performance30day19(20),
		performance30day20(21),
		performance30day21(22),
		performance30day22(23),
		performance30day23(24),
		performance30day24(25),
		performance30day25(26),
		performance30day26(27),
		performance30day27(28),
		performance30day28(29),
		performance30day29(30),
		performance30day30(31)
		}
	ACCESS  read-only
	STATUS  mandatory
	DESCRIPTION
		"The index into the 30-day performance table."
	::= { performance30TableEntry 4 }

performance30ES OBJECT-TYPE
	SYNTAX  INTEGER
	ACCESS  read-only
	STATUS  mandatory
	DESCRIPTION
		"The number of Errored Seconds for the 1-day period."
	::= { performance30TableEntry 5 }

performance30BES        OBJECT-TYPE
	SYNTAX  INTEGER
	ACCESS  read-only
	STATUS  mandatory
	DESCRIPTION
		"The number of Bursty Errored Seconds for the 1-day period."
	::= { performance30TableEntry 6 }

performance30SES        OBJECT-TYPE
	SYNTAX  INTEGER
	ACCESS  read-only
	STATUS  mandatory
	DESCRIPTION
		"The number of Severely Errored Seconds for the 1-day period."
	::= { performance30TableEntry 7 }

performance30UAS        OBJECT-TYPE
	SYNTAX  INTEGER
	ACCESS  read-only
	STATUS  mandatory
	DESCRIPTION
		"The number of Unavailable Seconds for the 1-day period."
	::= { performance30TableEntry 8 }

performance30LOFC       OBJECT-TYPE
	SYNTAX  INTEGER
	ACCESS  read-only
	STATUS  mandatory
	DESCRIPTION
		"The number of Loss of Frame Counts for the 1-day period."
	::= { performance30TableEntry 9 }

performance30CSS        OBJECT-TYPE
	SYNTAX  INTEGER
	ACCESS  read-only
	STATUS  mandatory
	DESCRIPTION
		"The number of Controlled Slip Seconds for the 1-day period."
	::= { performance30TableEntry 10 }

performance30CRCES      OBJECT-TYPE
	SYNTAX  INTEGER
	ACCESS  read-only
	STATUS  mandatory
	DESCRIPTION
		"The number of CRC Errored Seconds for the 1-day period."
	::= { performance30TableEntry 11 }

performance30OOFS       OBJECT-TYPE
	SYNTAX  INTEGER
	ACCESS  read-only
	STATUS  mandatory
	DESCRIPTION
		"The number of Out of Frame Seconds for the 1-day period."
	::= { performance30TableEntry 12 }

performance30LOSS       OBJECT-TYPE
	SYNTAX  INTEGER
	ACCESS  read-only
	STATUS  mandatory
	DESCRIPTION
		"The number of Loss of Signal Seconds for the 1-day period."
	::= { performance30TableEntry 13 }

performance30AISS       OBJECT-TYPE
	SYNTAX  INTEGER
	ACCESS  read-only
	STATUS  mandatory
	DESCRIPTION
		"The number of Alarm Indication Signal Seconds for the 1-day period."
	::= { performance30TableEntry 14 }

performance30RAS        OBJECT-TYPE
	SYNTAX  INTEGER
	ACCESS  read-only
	STATUS  mandatory
	DESCRIPTION
		"The number of Remote Alarm (Yellow) Seconds for the 1-day period."
	::= { performance30TableEntry 15 }

performance30BPVS       OBJECT-TYPE
	SYNTAX  INTEGER
	ACCESS  read-only
	STATUS  mandatory
	DESCRIPTION
		"The number of Bipolar Violation Seconds for the 1-day period."
	::= { performance30TableEntry 16 }

-- itable
-- requests a list of all interfaces on a device

iTable  OBJECT-TYPE
	SYNTAX  SEQUENCE OF ITableEntry
	ACCESS  not-accessible
	STATUS  optional
	DESCRIPTION
		"The interface table."
	::= { itable 1 }

iTableEntry     OBJECT-TYPE
	SYNTAX  ITableEntry
	ACCESS  not-accessible
	STATUS  mandatory
	DESCRIPTION
		"An entry in the interface table."
	INDEX   { iTableNearIndex, iTableFarIndex, iTableIndex }
	::= { iTable 1 }

ITableEntry ::=
	SEQUENCE
	{
	iTableNearIndex     INTEGER,
	iTableFarIndex      INTEGER,
	iTableIndex         INTEGER,
	iDescription	    DisplayString,
	iType               INTEGER,
	iSlot               INTEGER,
	iPort               INTEGER,
	iStatus 	    INTEGER
	}

iTableNearIndex OBJECT-TYPE
	SYNTAX  INTEGER
	ACCESS  read-only
	STATUS  mandatory
	DESCRIPTION
		"Selects the near device."
	::= { iTableEntry 1 }

iTableFarIndex             OBJECT-TYPE
	SYNTAX  INTEGER
	ACCESS  read-only
	STATUS  mandatory
	DESCRIPTION
		"Selects the far device."
	::= { iTableEntry 2 }
 
iTableIndex     OBJECT-TYPE
	SYNTAX  INTEGER
	ACCESS  read-only
	STATUS  mandatory
	DESCRIPTION
		"The index into the interface table, used for addressing in above tables."
	::= { iTableEntry 3 }

iDescription    OBJECT-TYPE
	SYNTAX  DisplayString( SIZE(0..80) )
	ACCESS  read-only
	STATUS  mandatory
	DESCRIPTION
		"Description of the interface."
	::= { iTableEntry 4 }

iType   OBJECT-TYPE
	SYNTAX  INTEGER
		{
		disabled(0),
		v35(1),
		eia530(2),
		rs232(3),
		voice(4),
		hsdata(5),
		dualt1dte(6),
		dualddsv1(7),
		hexdds(8),
		ocudp(9),
		x21(10),
		dualddsv2(11),

		rfdl(128),
		alt(129),
		t1dte(130),
		didte(131),
		t1ntw(132),
		e1ntw(133),
		ddsntw(134),
		ddsdte(135),
		ddsdbu(136),
		fxs(137),
		fxo(138),
		eandm(139),

		e1sig(192)
		}
	ACCESS  read-only
	STATUS  mandatory
	DESCRIPTION
		"Enumerated interface type."
	::= { iTableEntry 5 }

iSlot   OBJECT-TYPE
	SYNTAX  INTEGER
	ACCESS  read-only
	STATUS  mandatory
	DESCRIPTION
		"Device-dependent slot in which the interface resides."
	::= { iTableEntry 6 }

iPort   OBJECT-TYPE
	SYNTAX  INTEGER 
	ACCESS  read-only
	STATUS  mandatory
	DESCRIPTION
		"Device-dependent port in which the interface resides."
	::= { iTableEntry 7 }

iStatus    OBJECT-TYPE
	SYNTAX  INTEGER
		{
		iStatusOther(1),
		iStatusOK(2),
		iStatusErrored(3),
		iStatusAlarmed(4),
		iStatusTesting(5)
		}
	ACCESS  read-only
	STATUS  mandatory
	DESCRIPTION
		"Status of the interface."
	::= { iTableEntry 8 }

-- traplog
-- a table of the most recent snmp traps
-- note that the near and far indicies are simply elements in the table,
-- not indicies as in the above tables...

traplogTable  OBJECT-TYPE
	SYNTAX  SEQUENCE OF TraplogEntry
	ACCESS  not-accessible
	STATUS  optional
	DESCRIPTION
		"The traplog table."
	::= { traplog 1 }

traplogEntry    OBJECT-TYPE
	SYNTAX  TraplogEntry
	ACCESS  not-accessible
	STATUS  mandatory
	DESCRIPTION
		"An entry in the traplog table."
	INDEX   { traplogIndex }
	::= { traplogTable 1 }

TraplogEntry ::=
	SEQUENCE
	{
	traplogIndex            INTEGER,
	traplogNearIndex        INTEGER,
	traplogFarIndex         INTEGER,
	traplogInterfaceIndex	INTEGER,
	traplogTrapNum          INTEGER,
	traplogTimeStamp        DisplayString,
	traplogDeviceType	INTEGER
	}

traplogIndex     OBJECT-TYPE
	SYNTAX  INTEGER
	ACCESS  read-only
	STATUS  mandatory
	DESCRIPTION
		"The index into the traplog table."
	::= { traplogEntry 1 }

traplogNearIndex        OBJECT-TYPE
	SYNTAX  INTEGER
	ACCESS  read-only
	STATUS  mandatory
	DESCRIPTION
		"Specifies the near device."
	::= { traplogEntry 2 }

traplogFarIndex             OBJECT-TYPE
	SYNTAX  INTEGER
	ACCESS  read-only
	STATUS  mandatory
	DESCRIPTION
		"Specifies the far device."
	::= { traplogEntry 3 }

traplogInterfaceIndex             OBJECT-TYPE
	SYNTAX  INTEGER
	ACCESS  read-only
	STATUS  mandatory
	DESCRIPTION
		"Specifies the interface."
	::= { traplogEntry 4 }
 
traplogTrapNum  OBJECT-TYPE
	SYNTAX  INTEGER
	ACCESS  read-only
	STATUS  mandatory
	DESCRIPTION
		"The SNMP trap id."
	::= { traplogEntry 5 }

traplogTimeStamp        OBJECT-TYPE
	SYNTAX  DisplayString(SIZE(0..40))
	ACCESS  read-only
	STATUS  mandatory
	DESCRIPTION
		"Time the SNMP was generated."
	::= { traplogEntry 6 }

traplogDeviceType	OBJECT-TYPE
	SYNTAX	INTEGER
		{
		other(1),
		none(2),
		t12000(3),
		e12048(4),
		e13021(5),
		t13000(6),
		t13001(7),
		t13002(8),
		t13030(9),
		t13060(10),
		t13101(11),
		t13102(12),
		t13111(13),
		t13112(14),
		dds4001(15),
		dds4101(16),
		dds4051(17),
		dds4151(18),
		dds41TDM(19),
		generic54016(20)
		}
	ACCESS	read-only
	STATUS	mandatory
	DESCRIPTION
		"Specifies the device type for the trap."
	::= { traplogEntry 7 }

traplogDeleteEntry      OBJECT-TYPE
	SYNTAX  INTEGER
	ACCESS  read-write
	STATUS  mandatory
	DESCRIPTION
		"Writing the index of a trap to this object will delete 
		the trap entry.  Writing an index value of 0 will delete
		all entries."
	::= { traplog 2 }

traplogSortOption       OBJECT-TYPE
	SYNTAX  INTEGER
		{
		other(1),
		ascendingtimestamp(2),
		ascendingunit(3)
		}
	ACCESS  read-write
	STATUS  mandatory
	DESCRIPTION
		"Determines the order in which traps are presented."
	::= { traplog 3 }

traplogLastTimeStamp       OBJECT-TYPE
	SYNTAX  TimeTicks
	ACCESS  read-only
	STATUS  mandatory
	DESCRIPTION
		"The timestamp of the newest trap in the trap log."
	::= { traplog 4 }

-- unitUtilities
-- a table of unit utilities options

unitUtilitiesTable  OBJECT-TYPE
	SYNTAX  SEQUENCE OF UnitUtilitiesTableEntry
	ACCESS  not-accessible
	STATUS  optional
	DESCRIPTION
		"The unit utilities table."
	::= { unitUtilities 1 }

unitUtilitiesTableEntry  OBJECT-TYPE
	SYNTAX  UnitUtilitiesTableEntry
	ACCESS  not-accessible
	STATUS  mandatory
	DESCRIPTION
		"An entry in the unit utilities table."
	INDEX   { unitUtilitiesNearIndex, unitUtilitiesFarIndex }
	::= { unitUtilitiesTable 1 }

UnitUtilitiesTableEntry ::=
	SEQUENCE
	{
	unitUtilitiesNearIndex		INTEGER,
	unitUtilitiesFarIndex		INTEGER,
	unitUtilitiesLocalPassword	DisplayString,
	unitUtilitiesTime	 	DisplayString,
	unitUtilitiesDate		DisplayString,
	unitUtilitiesMaintenanceReset	INTEGER,
	unitUtilitiesAlarmResetTimer	INTEGER,
	unitUtilitiesAlarmClear		INTEGER
	}

unitUtilitiesNearIndex   OBJECT-TYPE
	SYNTAX  INTEGER
	ACCESS  read-only
	STATUS  mandatory
	DESCRIPTION
		"Selects the near device."
	::= { unitUtilitiesTableEntry 1 }

unitUtilitiesFarIndex    OBJECT-TYPE
	SYNTAX  INTEGER
	ACCESS  read-only
	STATUS  mandatory
	DESCRIPTION
		"Selects the far device."
	::= { unitUtilitiesTableEntry 2 }

unitUtilitiesLocalPassword       OBJECT-TYPE
	SYNTAX  DisplayString
	ACCESS  read-write
	STATUS  mandatory
	DESCRIPTION
		"The password for local access to a device (VT100, front panel)."
	::= { unitUtilitiesTableEntry 3 }

unitUtilitiesTime OBJECT-TYPE     
	SYNTAX  DisplayString( SIZE(0..6) )
	ACCESS  read-write
	STATUS  mandatory
	DESCRIPTION
	"This string is the current time as known to the device.  The current time may be entered in this field using the HHMMSS format.  For example, 3:45AM is entered as 034500 and 3:45PM is entered as 154500."
	::= { unitUtilitiesTableEntry 4 }

unitUtilitiesDate OBJECT-TYPE     
	SYNTAX  DisplayString( SIZE(0..6) )
	ACCESS  read-write
	STATUS  mandatory
	DESCRIPTION
	"This string is the current date as known to the device.  The current date may be entered in this field using the MMDDYY format.  For example, July 4, 1997 is entered as 070497."
	::= { unitUtilitiesTableEntry 5 }

unitUtilitiesMaintenanceReset OBJECT-TYPE
	SYNTAX  INTEGER
		{
		other(1),
		reset(2),
		restart(3)
		}
	ACCESS  read-write
	STATUS  mandatory
	DESCRIPTION
	"This field allows resetting the device to default values by reloading the start-up default configuration parameters."
	::= { unitUtilitiesTableEntry 6 }

unitUtilitiesAlarmResetTimer	OBJECT-TYPE
	SYNTAX	INTEGER
	ACCESS	read-write
	STATUS	optional
	DESCRIPTION
	"This field allows setting a timer which will cause all existing alarms on the device to be cleared upon expiration.  The counter is in seconds."
	::= { unitUtilitiesTableEntry 7 }

unitUtilitiesAlarmClear	OBJECT-TYPE
	SYNTAX	INTEGER
		{
		utilitiesAlarmClearOther(1),
		utilitiesAlarmClearNow(2)
		}
	ACCESS	read-write
	STATUS	optional
	DESCRIPTION
	"Writing a 2 to this field causes all existing alarms to be cleared immediatedly."
	::= { unitUtilitiesTableEntry 8 }

END
