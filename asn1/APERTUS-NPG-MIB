APERTUS-NPG-MIB DEFINITIONS ::= BEGIN

IMPORTS
    enterprises, Counter, IpAddress, TimeTicks
        FROM RFC1155-SMI
    OBJECT-TYPE
        FROM RFC-1212
    DisplayString
        FROM RFC1213-MIB
    TRAP-TYPE
        FROM RFC-1215;

internet      OBJECT IDENTIFIER ::= { iso org(3) dod(6) 1 }

directory     OBJECT IDENTIFIER ::= { internet 1 }

mgmt          OBJECT IDENTIFIER ::= { internet 2 }

experimental  OBJECT IDENTIFIER ::= { internet 3 }

private       OBJECT IDENTIFIER ::= { internet 4 }
enterprises   OBJECT IDENTIFIER ::= { private 1 }

apertus OBJECT IDENTIFIER ::= { enterprises 543 }
isg OBJECT IDENTIFIER ::= { apertus 3 }
npg OBJECT IDENTIFIER ::= { isg 5 }



-- =====================================================================
-- | Main MIB definition
-- =====================================================================

npgMib OBJECT IDENTIFIER ::= { npg 1 }



-- =====================================================================
-- | MIB Version Number
-- =====================================================================

npgMibVersionNumber OBJECT-TYPE
    SYNTAX      INTEGER
    ACCESS      read-only
    STATUS      mandatory
    DESCRIPTION
       "The version number of this MIB."
    ::= { npgMib 1 }



-- =====================================================================
-- | NPG Version Number
-- =====================================================================

npgVersionNumber OBJECT-TYPE
    SYNTAX      DisplayString
    ACCESS      read-only
    STATUS      mandatory
    DESCRIPTION
       "The version number of NPG."
    ::= { npgMib 2 }



-- =====================================================================
-- | NPG Session Table
-- =====================================================================

npgSessionTable OBJECT-TYPE
    SYNTAX       SEQUENCE OF NpgSessionEntry
    ACCESS       not-accessible
    STATUS       mandatory
    DESCRIPTION  "Table of active sessions"
    ::= { npgMib 3 }

npgSessionEntry OBJECT-TYPE
    SYNTAX       NpgSessionEntry
    ACCESS       not-accessible
    STATUS       mandatory
    DESCRIPTION  "This table contains the list of active print sessions"
    INDEX        {
		     npgSessionName
		 }
    ::= { npgSessionTable 1 }

NpgSessionEntry ::= SEQUENCE
{
    npgSessionName                            DisplayString,
    npgSessionCorrectState                    DisplayString,
    npgSessionCurrentState                    DisplayString,
    npgSessionWhenLastUp                      DisplayString,
    npgSessionWhenLastDown                    DisplayString,
    npgSessionLastErrorCode                   INTEGER,
    npgSessionLastErrorMessage                DisplayString,
    npgSessionTimeOfNextRetry                 DisplayString,
    npgSessionCurrentRetryValue               INTEGER,
    npgSessionRetryCount                      INTEGER,
    npgSessionTimeOfActiveReset               DisplayString,
    
    npgSessionActiveStatsProcessingTime       INTEGER,
    npgSessionActiveStatsBytesPrinted         INTEGER,
    npgSessionActiveStatsLinesPrinted         INTEGER,
    npgSessionActiveStatsPagesPrinted         INTEGER,
    npgSessionActiveStatsJobsPrinted          INTEGER,
    
    npgSessionCumulativeStatsProcessingTime   INTEGER,
    npgSessionCumulativeStatsBytesPrinted     INTEGER,
    npgSessionCumulativeStatsLinesPrinted     INTEGER,
    npgSessionCumulativeStatsPagesPrinted     INTEGER,
    npgSessionCumulativeStatsJobsPrinted      INTEGER,
    
    npgSessionConfigTn3270eServer             DisplayString,
    npgSessionConfigPort                      INTEGER,
    npgSessionConfigPrinterName               DisplayString
}



-- =====================================================================
-- | NPG Session Table objects
-- =====================================================================

npgSessionName OBJECT-TYPE
    SYNTAX       DisplayString
    ACCESS       read-only
    STATUS       mandatory
    DESCRIPTION  "Name of print session"
    ::= { npgSessionEntry 1 }

npgSessionCorrectState OBJECT-TYPE
    SYNTAX       DisplayString
    ACCESS       read-only
    STATUS       mandatory
    DESCRIPTION  "State print session should be in"
    ::= { npgSessionEntry 2 }

npgSessionCurrentState OBJECT-TYPE
    SYNTAX       DisplayString
    ACCESS       read-only
    STATUS       mandatory
    DESCRIPTION  "State print session is in"
    ::= { npgSessionEntry 3 }

npgSessionWhenLastUp OBJECT-TYPE
    SYNTAX       DisplayString
    ACCESS       read-only
    STATUS       mandatory
    DESCRIPTION  "Time print session was last up"
    ::= { npgSessionEntry 4 }

npgSessionWhenLastDown OBJECT-TYPE
    SYNTAX       DisplayString
    ACCESS       read-only
    STATUS       mandatory
    DESCRIPTION  "Time print session was last down"
    ::= { npgSessionEntry 5 }

npgSessionLastErrorCode OBJECT-TYPE
    SYNTAX       INTEGER
    ACCESS       read-only
    STATUS       mandatory
    DESCRIPTION  "Last error code print session generated"
    ::= { npgSessionEntry 6 }

npgSessionLastErrorMessage OBJECT-TYPE
    SYNTAX       DisplayString
    ACCESS       read-only
    STATUS       mandatory
    DESCRIPTION  "Last error message print session generated"
    ::= { npgSessionEntry 7 }

npgSessionTimeOfNextRetry OBJECT-TYPE
    SYNTAX       DisplayString
    ACCESS       read-only
    STATUS       mandatory
    DESCRIPTION  "Time print session attempt re-connect"
    ::= { npgSessionEntry 8 }

npgSessionCurrentRetryValue OBJECT-TYPE
    SYNTAX       INTEGER
    ACCESS       read-only
    STATUS       mandatory
    DESCRIPTION  "Time period print session waits before attempting re-connect"
    ::= { npgSessionEntry 9 }

npgSessionRetryCount OBJECT-TYPE
    SYNTAX       INTEGER
    ACCESS       read-only
    STATUS       mandatory
    DESCRIPTION  "Number of times print session had attempted re-connect so far"
    ::= { npgSessionEntry 10 }

npgSessionTimeOfActiveReset OBJECT-TYPE
    SYNTAX       DisplayString
    ACCESS       read-only
    STATUS       mandatory
    DESCRIPTION  "Time of last active session stats reset"
    ::= { npgSessionEntry 11 }

npgSessionActiveStatsProcessingTime OBJECT-TYPE
    SYNTAX       INTEGER
    ACCESS       read-only
    STATUS       mandatory
    DESCRIPTION  "Active Stats -- time spent processing jobs"
    ::= { npgSessionEntry 12 }

npgSessionActiveStatsBytesPrinted OBJECT-TYPE
    SYNTAX       INTEGER
    ACCESS       read-only
    STATUS       mandatory
    DESCRIPTION  "Active Stats -- total bytes printed"
    ::= { npgSessionEntry 13 }

npgSessionActiveStatsLinesPrinted OBJECT-TYPE
    SYNTAX       INTEGER
    ACCESS       read-only
    STATUS       mandatory
    DESCRIPTION  "Active Stats -- total lines printed"
    ::= { npgSessionEntry 14 }

npgSessionActiveStatsPagesPrinted OBJECT-TYPE
    SYNTAX       INTEGER
    ACCESS       read-only
    STATUS       mandatory
    DESCRIPTION  "Active Stats -- total pages printed"
    ::= { npgSessionEntry 15 }

npgSessionActiveStatsJobsPrinted OBJECT-TYPE
    SYNTAX       INTEGER
    ACCESS       read-only
    STATUS       mandatory
    DESCRIPTION  "Active Stats -- total jobs printed"
    ::= { npgSessionEntry 16 }

npgSessionCumulativeStatsProcessingTime OBJECT-TYPE
    SYNTAX       INTEGER
    ACCESS       read-only
    STATUS       mandatory
    DESCRIPTION  "Cumulative Stats -- time spent processing jobs"
    ::= { npgSessionEntry 17 }

npgSessionCumulativeStatsBytesPrinted OBJECT-TYPE
    SYNTAX       INTEGER
    ACCESS       read-only
    STATUS       mandatory
    DESCRIPTION  "Cumulative Stats -- total bytes printed"
    ::= { npgSessionEntry 18 }

npgSessionCumulativeStatsLinesPrinted OBJECT-TYPE
    SYNTAX       INTEGER
    ACCESS       read-only
    STATUS       mandatory
    DESCRIPTION  "Cumulative Stats -- total lines printed"
    ::= { npgSessionEntry 19 }

npgSessionCumulativeStatsPagesPrinted OBJECT-TYPE
    SYNTAX       INTEGER
    ACCESS       read-only
    STATUS       mandatory
    DESCRIPTION  "Cumulative Stats -- total pages printed"
    ::= { npgSessionEntry 20 }

npgSessionCumulativeStatsJobsPrinted OBJECT-TYPE
    SYNTAX       INTEGER
    ACCESS       read-only
    STATUS       mandatory
    DESCRIPTION  "Cumulative Stats -- total jobs printed"
    ::= { npgSessionEntry 21 }

npgSessionConfigTn3270eServer OBJECT-TYPE
    SYNTAX       DisplayString
    ACCESS       read-only
    STATUS       mandatory
    DESCRIPTION  "Configured TN3270E server"
    ::= { npgSessionEntry 22 }

npgSessionConfigPort OBJECT-TYPE
    SYNTAX       INTEGER
    ACCESS       read-only
    STATUS       mandatory
    DESCRIPTION  "Configured port"
    ::= { npgSessionEntry 23 }

npgSessionConfigPrinterName OBJECT-TYPE
    SYNTAX       DisplayString
    ACCESS       read-only
    STATUS       mandatory
    DESCRIPTION  "Configured printer name"
    ::= { npgSessionEntry 24 }



-- =====================================================================
-- | NPG Destination Table
-- =====================================================================

npgDestinationTable OBJECT-TYPE
    SYNTAX       SEQUENCE OF NpgDestinationEntry
    ACCESS       not-accessible
    STATUS       mandatory
    DESCRIPTION  "Table of active destinations"
    ::= { npgMib 4 }

npgDestinationEntry OBJECT-TYPE
    SYNTAX       NpgDestinationEntry
    ACCESS       not-accessible
    STATUS       mandatory
    DESCRIPTION  "This table contains the list of active print destinations"
    INDEX        {
		     npgDestinationName
		 }
    ::= { npgDestinationTable 1 }

NpgDestinationEntry ::= SEQUENCE
{
    npgDestinationName                            DisplayString,
    npgDestinationTimeOfActiveReset               DisplayString,
    
    npgDestinationActiveStatsProcessingTime       INTEGER,
    npgDestinationActiveStatsBytesPrinted         INTEGER,
    npgDestinationActiveStatsLinesPrinted         INTEGER,
    npgDestinationActiveStatsPagesPrinted         INTEGER,
    npgDestinationActiveStatsJobsPrinted          INTEGER,
    
    npgDestinationCumulativeStatsProcessingTime   INTEGER,
    npgDestinationCumulativeStatsBytesPrinted     INTEGER,
    npgDestinationCumulativeStatsLinesPrinted     INTEGER,
    npgDestinationCumulativeStatsPagesPrinted     INTEGER,
    npgDestinationCumulativeStatsJobsPrinted      INTEGER,
    
    npgDestinationConfigType                      DisplayString,
    npgDestinationConfigProfileName               DisplayString
}



-- =====================================================================
-- | NPG Destination Table Objects
-- =====================================================================

npgDestinationName OBJECT-TYPE
    SYNTAX       DisplayString
    ACCESS       read-only
    STATUS       mandatory
    DESCRIPTION  "Name of print destination"
    ::= { npgDestinationEntry 1 }

npgDestinationTimeOfActiveReset OBJECT-TYPE
    SYNTAX       DisplayString
    ACCESS       read-only
    STATUS       mandatory
    DESCRIPTION  "Time of last active destination stats reset"
    ::= { npgDestinationEntry 2 }

npgDestinationActiveStatsProcessingTime OBJECT-TYPE
    SYNTAX       INTEGER
    ACCESS       read-only
    STATUS       mandatory
    DESCRIPTION  "Active Stats -- time spent processing jobs"
    ::= { npgDestinationEntry 3 }

npgDestinationActiveStatsBytesPrinted OBJECT-TYPE
    SYNTAX       INTEGER
    ACCESS       read-only
    STATUS       mandatory
    DESCRIPTION  "Active Stats -- total bytes printed"
    ::= { npgDestinationEntry 4 }

npgDestinationActiveStatsLinesPrinted OBJECT-TYPE
    SYNTAX       INTEGER
    ACCESS       read-only
    STATUS       mandatory
    DESCRIPTION  "Active Stats -- total lines printed"
    ::= { npgDestinationEntry 5 }

npgDestinationActiveStatsPagesPrinted OBJECT-TYPE
    SYNTAX       INTEGER
    ACCESS       read-only
    STATUS       mandatory
    DESCRIPTION  "Active Stats -- total pages printed"
    ::= { npgDestinationEntry 6 }

npgDestinationActiveStatsJobsPrinted OBJECT-TYPE
    SYNTAX       INTEGER
    ACCESS       read-only
    STATUS       mandatory
    DESCRIPTION  "Active Stats -- total jobs printed"
    ::= { npgDestinationEntry 7 }

npgDestinationCumulativeStatsProcessingTime OBJECT-TYPE
    SYNTAX       INTEGER
    ACCESS       read-only
    STATUS       mandatory
    DESCRIPTION  "Cumulative Stats -- time spent processing jobs"
    ::= { npgDestinationEntry 8 }

npgDestinationCumulativeStatsBytesPrinted OBJECT-TYPE
    SYNTAX       INTEGER
    ACCESS       read-only
    STATUS       mandatory
    DESCRIPTION  "Cumulative Stats -- total bytes printed"
    ::= { npgDestinationEntry 9 }

npgDestinationCumulativeStatsLinesPrinted OBJECT-TYPE
    SYNTAX       INTEGER
    ACCESS       read-only
    STATUS       mandatory
    DESCRIPTION  "Cumulative Stats -- total lines printed"
    ::= { npgDestinationEntry 10 }

npgDestinationCumulativeStatsPagesPrinted OBJECT-TYPE
    SYNTAX       INTEGER
    ACCESS       read-only
    STATUS       mandatory
    DESCRIPTION  "Cumulative Stats -- total pages printed"
    ::= { npgDestinationEntry 11 }

npgDestinationCumulativeStatsJobsPrinted OBJECT-TYPE
    SYNTAX       INTEGER
    ACCESS       read-only
    STATUS       mandatory
    DESCRIPTION  "Cumulative Stats -- total jobs printed"
    ::= { npgDestinationEntry 12 }

npgDestinationConfigType OBJECT-TYPE
    SYNTAX       DisplayString
    ACCESS       read-only
    STATUS       mandatory
    DESCRIPTION  "Print destination type"
    ::= { npgDestinationEntry 13 }

npgDestinationConfigProfileName OBJECT-TYPE
    SYNTAX       DisplayString
    ACCESS       read-only
    STATUS       mandatory
    DESCRIPTION  "Print destination profile name"
    ::= { npgDestinationEntry 14 }



-- =====================================================================
-- | End
-- =====================================================================

END
