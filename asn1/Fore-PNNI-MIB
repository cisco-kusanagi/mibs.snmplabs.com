-- 
-- Copyright 1999 by Fore Systems, Inc. 
-- Converted to SMIv2 rfc 2578,2579,2580 - STD 58
--
-- Copyright 1995 by Fore Systems, Inc.

Fore-PNNI-MIB DEFINITIONS ::= BEGIN

IMPORTS
	ServiceCategory, PnniNodeIndex, AtmAddrPrefix,
	PnniPrefixLength, PnniMetricsTag, TnsPlan, TnsType, 
	PnniNodeId, PnniPortId, pnniMapAddrIndex,
	pnniMapAddrAdvertisingNodeId, pnniMapAddrAdvertisedPortId,
	pnniNodeIndex, pnniMapOriginatingNodeId,
	pnniMapOriginatingPortId, pnniMapIndex, pnniDTLIndex
			  			FROM PNNI-MIB
        InterfaceIndex                          FROM IF-MIB
        NsapPrefix, NsapAddr,
	software				FROM Fore-Common-MIB
	portNumber				FROM Fore-Switch-MIB
	TruthValue, RowStatus, TimeStamp, DisplayString
	                                        FROM SNMPv2-TC
        OBJECT-TYPE, MODULE-IDENTITY, Integer32,
	Unsigned32, 
 	IpAddress                               FROM SNMPv2-SMI;

forePnniGroup              MODULE-IDENTITY
          LAST-UPDATED         "9911050000Z"
          ORGANIZATION         "FORE"
          CONTACT-INFO         
               "      Postal:   FORE Systems Inc.
                                 1000 FORE Drive
                                 Warrendale, PA 15086-7502
                       Tel:      +1 724 742 6900
                       Email:    nm_mibs@fore.com
                       Web:      http://www.fore.com"
          DESCRIPTION
           "This module implements the FORE Systems extentions to
	    the PNNI MIB."
    ::= { software 4 }

pnniGroup	OBJECT IDENTIFIER ::= { forePnniGroup 1 }
atmRoutingGroup OBJECT IDENTIFIER ::= { forePnniGroup 2 }
pnniIfMapGroup  OBJECT IDENTIFIER ::= { forePnniGroup 3 }
pnniCrankbackGroup OBJECT IDENTIFIER ::= { pnniGroup 9 }
pnniParametersGroup OBJECT IDENTIFIER ::= { pnniGroup 12 }

PnniPcProfileIndex ::= INTEGER(1..65535)

pnniPcProfileTable OBJECT-TYPE
    SYNTAX SEQUENCE OF PnniPcProfileEntry
    MAX-ACCESS not-accessible
    STATUS current
    DESCRIPTION
	" profiles for each service catagory "
    ::= { pnniGroup 1 }

pnniPcProfileEntry OBJECT-TYPE
    SYNTAX PnniPcProfileEntry
    MAX-ACCESS not-accessible
    STATUS current
    DESCRIPTION
        ""
    INDEX { pnniNodeIndex, pnniPcProfileIndex }
    ::= { pnniPcProfileTable 1 }

PnniPcProfileEntry ::= SEQUENCE {
    pnniPcProfileIndex                PnniPcProfileIndex,
    pnniPcProfileType                 INTEGER,
    pnniPcProfileServiceCategory      ServiceCategory,
    pnniPcProfileMinFwdCR             Unsigned32,
    pnniPcProfileMinRevCR             Unsigned32,
    pnniPcProfileFwdClpType           INTEGER,
    pnniPcProfileRevClpType           INTEGER,
    pnniPcProfileFwdCLR               Unsigned32,
    pnniPcProfileRevCLR               Unsigned32,
    pnniPcProfileOptCTD               TruthValue,
    pnniPcProfileOptCDV               TruthValue,
    pnniPcProfileOptAdminWeight       INTEGER,
    pnniPcProfileRstrVPOnly           TruthValue,
    pnniPcProfileRstrLoadBalance      TruthValue,
    pnniPcProfileNumberOfAvoidLinks   Unsigned32,
    pnniPcProfileNumberOfPreferLinks  Unsigned32,
    pnniPcProfileNumberOfHits         Unsigned32,
    pnniPcProfileTimeStamp            TimeStamp,
    pnniPcProfileState                INTEGER,
    pnniPcProfileRowStatus            RowStatus,
    pnniPcProfileCongestionBased      TruthValue
}

pnniPcProfileIndex OBJECT-TYPE
    SYNTAX PnniPcProfileIndex
    MAX-ACCESS not-accessible
    STATUS current
    DESCRIPTION
        ""
    ::= { pnniPcProfileEntry 1 }

pnniPcProfileType OBJECT-TYPE
    SYNTAX INTEGER {
	mgmtEntry(1),
	cacheEntry(2)
	}
    MAX-ACCESS read-only
    STATUS current
    DESCRIPTION
        "Indicates whether the profile is dynamic generated or user configured
	 for cache profile there might be avoid node list or prefered node
	 list"
    ::= { pnniPcProfileEntry 2 }

pnniPcProfileServiceCategory OBJECT-TYPE
    SYNTAX ServiceCategory
    MAX-ACCESS read-create
    STATUS current
    DESCRIPTION
        "Service category"
    DEFVAL { ubr }
    ::= { pnniPcProfileEntry 3 }

pnniPcProfileMinFwdCR OBJECT-TYPE
    SYNTAX Unsigned32
    MAX-ACCESS read-create
    STATUS current
    DESCRIPTION
        "Minimum forward cell rate"
    ::= { pnniPcProfileEntry 4 }

pnniPcProfileMinRevCR OBJECT-TYPE
    SYNTAX Unsigned32
    MAX-ACCESS read-create
    STATUS current
    DESCRIPTION
        "Minimum reverse cell rate"
    ::= { pnniPcProfileEntry 5 }

pnniPcProfileFwdClpType OBJECT-TYPE
    SYNTAX INTEGER {
        clpEqual0(1),
        clpEqual0Or1(2)
	}    
    MAX-ACCESS read-create
    STATUS current
    DESCRIPTION
        "for CBR/VBR only"
    DEFVAL { clpEqual0 } 
    ::= { pnniPcProfileEntry 6 }

pnniPcProfileRevClpType OBJECT-TYPE
    SYNTAX INTEGER {
        clpEqual0(1),
        clpEqual0Or1(2)
        }
    MAX-ACCESS read-create
    STATUS current
    DESCRIPTION
        "for CBR/VBR only"
    DEFVAL { clpEqual0 }
    ::= { pnniPcProfileEntry 7 }

pnniPcProfileFwdCLR OBJECT-TYPE
    SYNTAX Unsigned32
    MAX-ACCESS read-create
    STATUS current
    DESCRIPTION
        "for CBR/VBR only"
    ::= { pnniPcProfileEntry 8 } 

pnniPcProfileRevCLR OBJECT-TYPE
    SYNTAX Unsigned32
    MAX-ACCESS read-create
    STATUS current
    DESCRIPTION
        "for CBR/VBR only"
    ::= { pnniPcProfileEntry 9 }

pnniPcProfileOptCTD OBJECT-TYPE
    SYNTAX TruthValue
    MAX-ACCESS read-create
    STATUS current
    DESCRIPTION
        "optimization criteria flag:
	 Multiple trees will be computed for VBR if several are set.
         For ABR profile, only one of these can be set. 
	 If CTD set, CDV is treated as path constraint.
         Only one can be set of AW and CAW"
    DEFVAL { false } 
    ::= { pnniPcProfileEntry 10 }

pnniPcProfileOptCDV OBJECT-TYPE
    SYNTAX TruthValue
    MAX-ACCESS read-create
    STATUS current
    DESCRIPTION
        "see above"
    DEFVAL { false }
    ::= { pnniPcProfileEntry 11 }

pnniPcProfileOptAdminWeight OBJECT-TYPE
    SYNTAX INTEGER {
	   none(1),
	   aw(2),
	   caw(3)
	}
    MAX-ACCESS read-create
    STATUS current
    DESCRIPTION
        "see above"
    DEFVAL { aw } 
    ::= { pnniPcProfileEntry 12 }

pnniPcProfileRstrVPOnly OBJECT-TYPE
    SYNTAX TruthValue
    MAX-ACCESS read-create
    STATUS current
    DESCRIPTION
        "for all categories"
    DEFVAL { false }
    ::= { pnniPcProfileEntry 13 }

pnniPcProfileRstrLoadBalance OBJECT-TYPE
    SYNTAX TruthValue
    MAX-ACCESS read-create
    STATUS current
    DESCRIPTION
        "for ABR/UBR. True means do not load-balance trees"
    DEFVAL { false }
    ::= { pnniPcProfileEntry 14 }

pnniPcProfileNumberOfAvoidLinks OBJECT-TYPE
    SYNTAX Unsigned32
    MAX-ACCESS read-only
    STATUS current
    DESCRIPTION
        "number of avoided links in this profile for cache profile only"
    ::= { pnniPcProfileEntry 15 }

pnniPcProfileNumberOfPreferLinks OBJECT-TYPE
    SYNTAX Unsigned32
    MAX-ACCESS read-only
    STATUS current
    DESCRIPTION
        "number of preferred links in this profile for cache profile only"
    ::= { pnniPcProfileEntry 16 }

pnniPcProfileNumberOfHits OBJECT-TYPE
    SYNTAX Unsigned32
    MAX-ACCESS read-only
    STATUS current
    DESCRIPTION
        "number of hits on this profile since it is configured"
    ::= { pnniPcProfileEntry 17 }

pnniPcProfileTimeStamp OBJECT-TYPE
    SYNTAX TimeStamp
    MAX-ACCESS read-only
    STATUS current
    DESCRIPTION
        "Time elapsed since last hit in seconds"
    ::= { pnniPcProfileEntry 18 }

pnniPcProfileState OBJECT-TYPE
    SYNTAX INTEGER {
	inactive(1),
	computed(2),
	computing(3),
	touched(4)
	}
    MAX-ACCESS read-only
    STATUS current
    DESCRIPTION
        "State of the profile, whether it is computed, in computing or
	 topolgy changed"
    ::= { pnniPcProfileEntry 19 }

pnniPcProfileRowStatus OBJECT-TYPE
    SYNTAX RowStatus
    MAX-ACCESS read-create
    STATUS current
    DESCRIPTION
        "for create, modify and delete a profile entry"
    ::= { pnniPcProfileEntry 20 }

pnniPcProfileCongestionBased OBJECT-TYPE
    SYNTAX TruthValue
    MAX-ACCESS read-create
    STATUS current
    DESCRIPTION 
	"Indicates if the profile describes a congestion
	 based route"
    ::= { pnniPcProfileEntry 21 }

----------------------------------------------------------------------------
-- PNNI export policy table

pnniExportPolicyTable OBJECT-TYPE
    SYNTAX SEQUENCE OF PnniExportPolicyEntry
    MAX-ACCESS not-accessible
    STATUS current
    DESCRIPTION
	" export policy table "
    ::= { pnniGroup 2 }

pnniExportPolicyEntry OBJECT-TYPE
    SYNTAX PnniExportPolicyEntry
    MAX-ACCESS not-accessible
    STATUS current
    DESCRIPTION
        ""
    INDEX { pnniNodeIndex, pnniExportPolicyAddress, pnniExportPolicyPrefixLength }
    ::= { pnniExportPolicyTable 1 }

PnniExportPolicyEntry ::= SEQUENCE {
    pnniExportPolicyAddress		AtmAddrPrefix,
    pnniExportPolicyPrefixLength	PnniPrefixLength,
    pnniExportPolicyType		INTEGER,
    pnniExportPolicyAction		INTEGER,
    pnniExportPolicyState		INTEGER,
    pnniExportPolicyTnsType		TnsType,
    pnniExportPolicyTnsPlan		TnsPlan,
    pnniExportPolicyTnsId 		DisplayString,
    pnniExportPolicyMetricsTag 		PnniMetricsTag,
    pnniExportPolicyRowStatus		RowStatus
}

pnniExportPolicyAddress OBJECT-TYPE
    SYNTAX	AtmAddrPrefix
    MAX-ACCESS      not-accessible
    STATUS	current
    DESCRIPTION
	""
    ::= { pnniExportPolicyEntry 1 }

pnniExportPolicyPrefixLength OBJECT-TYPE
    SYNTAX	PnniPrefixLength
    MAX-ACCESS      not-accessible
    STATUS	current
    DESCRIPTION
	""
    ::= { pnniExportPolicyEntry 2 }

pnniExportPolicyType OBJECT-TYPE
    SYNTAX	INTEGER {
	internal(1),
	exterior(2),
	both(3)
	}
    MAX-ACCESS      read-create
    STATUS	current
    DESCRIPTION
	""
    ::= { pnniExportPolicyEntry 3 }

pnniExportPolicyAction OBJECT-TYPE
    SYNTAX	INTEGER {
	summary(1),
	suppress(2),
	advertise(3)
	}
    MAX-ACCESS      read-create
    STATUS	current
    DESCRIPTION
	""
    ::= { pnniExportPolicyEntry 4 }

pnniExportPolicyState OBJECT-TYPE
    SYNTAX	INTEGER {
	summarizing(1),
        suppressing(2),
        advertising(3),	
        inactive(4)	
	}
    MAX-ACCESS      read-only
    STATUS	current
    DESCRIPTION
	""
    ::= { pnniExportPolicyEntry 5 }

pnniExportPolicyTnsType OBJECT-TYPE
    SYNTAX	TnsType
    MAX-ACCESS      read-create
    STATUS	current
    DESCRIPTION
	""
    ::= { pnniExportPolicyEntry 6 }

pnniExportPolicyTnsPlan OBJECT-TYPE
    SYNTAX	TnsPlan
    MAX-ACCESS      read-create
    STATUS	current
    DESCRIPTION
	""
    ::= { pnniExportPolicyEntry 7 }

pnniExportPolicyTnsId OBJECT-TYPE
    SYNTAX	DisplayString
    MAX-ACCESS      read-create
    STATUS	current
    DESCRIPTION
	""
    ::= { pnniExportPolicyEntry 8 }

pnniExportPolicyMetricsTag OBJECT-TYPE
    SYNTAX	PnniMetricsTag
    MAX-ACCESS      read-create
    STATUS	current
    DESCRIPTION
	""
    ::= { pnniExportPolicyEntry 9 }

pnniExportPolicyRowStatus OBJECT-TYPE
    SYNTAX	RowStatus
    MAX-ACCESS      read-create
    STATUS	current
    DESCRIPTION
	""
    ::= { pnniExportPolicyEntry 10 }

------------------------------------------------------------------------
-- PNNI Node Extension Table

pnniNodeExtnTable OBJECT-TYPE
   SYNTAX SEQUENCE OF PnniNodeExtnEntry
   MAX-ACCESS not-accessible
   STATUS current               
   DESCRIPTION
        " Extension to the PNNI Node Table in the PNNI MIB"
   ::= { pnniGroup 3 }

pnniNodeExtnEntry OBJECT-TYPE
    SYNTAX PnniNodeExtnEntry
    MAX-ACCESS not-accessible
    STATUS current
    DESCRIPTION
        ""
    INDEX { pnniNodeIndex }
    ::= { pnniNodeExtnTable 1 }

PnniNodeExtnEntry ::= SEQUENCE {
    pnniNodeExtnDomainID               Integer32,
    pnniNodeExtnForeLevel              Integer32,
    pnniNodeExtnForeArea               Integer32,
    pnniNodeExtnShutdown	       TruthValue, 
    pnniNodeExtnLoadBalancing          TruthValue, 
    pnniNodeExtnAdvertisedPglPriority  Integer32,
    pnniNodeExtnPcCongestionRange      Integer32
}

pnniNodeExtnDomainID OBJECT-TYPE
    SYNTAX Integer32
    MAX-ACCESS read-write
    STATUS current
    DESCRIPTION
        " The ID of the ATM Routing Domain to which this PNNI Node belongs"
    ::= { pnniNodeExtnEntry 1 }

pnniNodeExtnForeLevel OBJECT-TYPE
    SYNTAX Integer32
    MAX-ACCESS read-write
    STATUS current
    DESCRIPTION
        " The level of the area to which this PNNI node belongs in the FORE hierarchy"
    ::= { pnniNodeExtnEntry 2 }

pnniNodeExtnForeArea OBJECT-TYPE
    SYNTAX Integer32
    MAX-ACCESS read-write
    STATUS current
    DESCRIPTION
        " the ID of the area in the FORE hierarchy to which this PNNI node belongs"
    ::= { pnniNodeExtnEntry 3 }
 
pnniNodeExtnShutdown  OBJECT-TYPE
    SYNTAX TruthValue
    MAX-ACCESS read-only
    STATUS current
    DESCRIPTION
        " Specifies whether the node is shutdown or not due to inconsistencies
          in TDB or due to TDB incremental MALLOC failures.A value of false
          indicates that the PNNI logical node is not shutdown and participates
          in all PNNI Protocol operation(s),and a value of true indicates that
          PNNI logical node is Shutdown and the switch has to be rebooted to
          bring this PNNI logical node up again."
    ::= {  pnniNodeExtnEntry 4 }

pnniNodeExtnLoadBalancing  OBJECT-TYPE
    SYNTAX TruthValue	
    MAX-ACCESS read-write
    STATUS current
    DESCRIPTION	
        " Specifies whether the profiles creating during on demand
	  path computation are load balanced."
    ::= {  pnniNodeExtnEntry 5 }

pnniNodeExtnAdvertisedPglPriority  OBJECT-TYPE
    SYNTAX        Integer32 (0..255)
    MAX-ACCESS        read-only
    STATUS        current
    DESCRIPTION
        " This is the leadership priority value which is actually advertised
          by the node. This can differ from the configured value for reasons
          of PGL/LGN-incapability or stability."
    ::= { pnniNodeExtnEntry 6 }

pnniNodeExtnPcCongestionRange OBJECT-TYPE
    SYNTAX Integer32
    MAX-ACCESS read-write
    STATUS current
    DESCRIPTION
	"The range in congestion that path computation will include in
	 a profile tree"
    ::= { pnniNodeExtnEntry 7 }


------------------------------------------------------------------------
-- PNNI Map Raig Table

pnniMapRaigTable OBJECT-TYPE
   SYNTAX SEQUENCE OF PnniMapRaigEntry
   MAX-ACCESS not-accessible
   STATUS current               
   DESCRIPTION
        "PNNI Map Raig Table"
   ::= { pnniGroup 4 }

pnniMapRaigEntry OBJECT-TYPE
    SYNTAX PnniMapRaigEntry
    MAX-ACCESS not-accessible
    STATUS current
    DESCRIPTION
        ""
    INDEX { pnniNodeIndex,
	    pnniMapOriginatingNodeId,
	    pnniMapOriginatingPortId,
	    pnniMapIndex,
	    pnniMapRaigIndex }
    ::= { pnniMapRaigTable 1 }

PnniMapRaigEntry ::= SEQUENCE {
    pnniMapRaigIndex			Integer32,
    pnniMapRaigDirection		INTEGER,
    pnniMapRaigFlags			Integer32,
    pnniMapRaigAdminWt			Unsigned32,
    pnniMapRaigMaximumCellRate		Unsigned32,
    pnniMapRaigAvailableCellRate	Unsigned32,
    pnniMapRaigCellTransferDelay	Unsigned32,
    pnniMapRaigCellDelayVariation	Unsigned32,
    pnniMapRaigCellLossRatio		Integer32,
    pnniMapRaigCellLossRatio1		Integer32,
    pnniMapRaigCellRateMargin		Integer32,
    pnniMapRaigVarianceFactor		Integer32
}

pnniMapRaigIndex OBJECT-TYPE
    SYNTAX Integer32 (0..12)
    MAX-ACCESS not-accessible
    STATUS current
    DESCRIPTION
	"An index into set of RAIG entries in the MAP entry. For
	 Horizontal Links and Up Links only outgoing RAIG entries are
	 present. For Nodal State IGs RAIG entries are present for both
	 directions."
    ::= { pnniMapRaigEntry 1 }

pnniMapRaigDirection OBJECT-TYPE
   SYNTAX  INTEGER {
		outgoing(1),
		incoming(2)
	   }
    MAX-ACCESS read-only
    STATUS current
    DESCRIPTION
	"The direction of the link for which this particular set of
	 parameters"
    ::= { pnniMapRaigEntry 2 }

pnniMapRaigFlags OBJECT-TYPE
    SYNTAX Integer32 
    MAX-ACCESS read-only
    STATUS current
    DESCRIPTION
	"Bit mask identifying which service category this RAIG
	 describes. The GCAC CLP Attribute bit is also present."	
    ::= { pnniMapRaigEntry 3 }

pnniMapRaigAdminWt OBJECT-TYPE
    SYNTAX Unsigned32
    MAX-ACCESS read-only
    STATUS current
    DESCRIPTION
	"Adminstrative Weight associated with this map entry."
    ::= { pnniMapRaigEntry 4 }

pnniMapRaigMaximumCellRate OBJECT-TYPE
    SYNTAX Unsigned32
    MAX-ACCESS read-only
    STATUS current
    DESCRIPTION
	"Maximum Cell Rate (Units : cells/second )."
    ::= { pnniMapRaigEntry 5 }

pnniMapRaigAvailableCellRate OBJECT-TYPE
    SYNTAX Unsigned32
    MAX-ACCESS read-only
    STATUS current
    DESCRIPTION
	"Available Cell Rate (Units : cells/second )."
    ::= { pnniMapRaigEntry 6 }

pnniMapRaigCellTransferDelay OBJECT-TYPE
    SYNTAX Unsigned32
    MAX-ACCESS read-only
    STATUS current
    DESCRIPTION
	"Cell Transfer Delay (Units : micro seconds )."
    ::= { pnniMapRaigEntry 7 }

pnniMapRaigCellDelayVariation OBJECT-TYPE
    SYNTAX Unsigned32
    MAX-ACCESS read-only
    STATUS current
    DESCRIPTION
	"Cell Delay Variation (Units : micro seconds )."
    ::= { pnniMapRaigEntry 8 }

pnniMapRaigCellLossRatio OBJECT-TYPE
    SYNTAX Integer32
    MAX-ACCESS read-only
    STATUS current
    DESCRIPTION
	"Cell Loss Ratio for CLP=0 encoded as the negative logarithm
	 of the value."
    ::= { pnniMapRaigEntry 9 }

pnniMapRaigCellLossRatio1 OBJECT-TYPE
    SYNTAX Integer32
    MAX-ACCESS read-only
    STATUS current
    DESCRIPTION
	"Cell Loss Ratio for CLP=0+1 encoded as the negative logarithm
	 of the value."
    ::= { pnniMapRaigEntry 10 }

pnniMapRaigCellRateMargin OBJECT-TYPE
    SYNTAX Integer32
    MAX-ACCESS read-only
    STATUS current
    DESCRIPTION
	"Cell Rate Margin in units cells/second. If the optional GCAC
	 related information is not present then this value would be
	 set to zero."
    ::= { pnniMapRaigEntry 11 }

pnniMapRaigVarianceFactor OBJECT-TYPE
    SYNTAX Integer32
    MAX-ACCESS read-only
    STATUS current
    DESCRIPTION
	"Variance Factor in units 2^-8. If the optional GCAC
	 related information is not present then this value would be
	 set to zero."
    ::= { pnniMapRaigEntry 12 }


------------------------------------------------------------------------
-- PNNI MapAddr Raig Table

pnniMapAddrRaigTable OBJECT-TYPE
   SYNTAX SEQUENCE OF PnniMapAddrRaigEntry
   MAX-ACCESS not-accessible
   STATUS current               
   DESCRIPTION
        "PNNI MapAddr Raig Table"
   ::= { pnniGroup 5 }

pnniMapAddrRaigEntry OBJECT-TYPE
    SYNTAX PnniMapAddrRaigEntry
    MAX-ACCESS not-accessible
    STATUS current
    DESCRIPTION
        ""
    INDEX { pnniNodeIndex,
	    pnniMapAddrAdvertisingNodeId,
	    pnniMapAddrAdvertisedPortId,
	    pnniMapAddrIndex,
	    pnniMapAddrRaigIndex }
    ::= { pnniMapAddrRaigTable 1 }

PnniMapAddrRaigEntry ::= SEQUENCE {
    pnniMapAddrRaigIndex		Integer32,
    pnniMapAddrRaigDirection		INTEGER,
    pnniMapAddrRaigFlags		Integer32,
    pnniMapAddrRaigAdminWt		Unsigned32,
    pnniMapAddrRaigMaximumCellRate	Unsigned32,
    pnniMapAddrRaigAvailableCellRate	Unsigned32,
    pnniMapAddrRaigCellTransferDelay	Unsigned32,
    pnniMapAddrRaigCellDelayVariation	Unsigned32,
    pnniMapAddrRaigCellLossRatio	Integer32,
    pnniMapAddrRaigCellLossRatio1	Integer32,
    pnniMapAddrRaigCellRateMargin	Integer32,
    pnniMapAddrRaigVarianceFactor	Integer32
}

pnniMapAddrRaigIndex OBJECT-TYPE
    SYNTAX Integer32 (0..12)
    MAX-ACCESS not-accessible
    STATUS current
    DESCRIPTION
	"An index into set of RAIG entries in the MapAddr entry. For
	 Horizontal Links and Up Links only outgoing RAIG entries are
	 present. For Nodal State IGs RAIG entries are present for both
	 directions."
    ::= { pnniMapAddrRaigEntry 1 }

pnniMapAddrRaigDirection OBJECT-TYPE
   SYNTAX  INTEGER {
		outgoing(1),
		incoming(2)
	   }
    MAX-ACCESS read-only
    STATUS current
    DESCRIPTION
	"The direction of the link for which this particular set of
	 parameters"
    ::= { pnniMapAddrRaigEntry 2 }

pnniMapAddrRaigFlags OBJECT-TYPE
    SYNTAX Integer32 
    MAX-ACCESS read-only
    STATUS current
    DESCRIPTION
	"Bit mask identifying which service category this RAIG
	 describes. The GCAC CLP Attribute bit is also present."	
    ::= { pnniMapAddrRaigEntry 3 }

pnniMapAddrRaigAdminWt OBJECT-TYPE
    SYNTAX Unsigned32
    MAX-ACCESS read-only
    STATUS current
    DESCRIPTION
	"Adminstrative Weight associated with this MapAddr entry."
    ::= { pnniMapAddrRaigEntry 4 }

pnniMapAddrRaigMaximumCellRate OBJECT-TYPE
    SYNTAX Unsigned32
    MAX-ACCESS read-only
    STATUS current
    DESCRIPTION
	"Maximum Cell Rate (Units : cells/second )."
    ::= { pnniMapAddrRaigEntry 5 }

pnniMapAddrRaigAvailableCellRate OBJECT-TYPE
    SYNTAX Unsigned32
    MAX-ACCESS read-only
    STATUS current
    DESCRIPTION
	"Available Cell Rate (Units : cells/second )."
    ::= { pnniMapAddrRaigEntry 6 }

pnniMapAddrRaigCellTransferDelay OBJECT-TYPE
    SYNTAX Unsigned32
    MAX-ACCESS read-only
    STATUS current
    DESCRIPTION
	"Cell Transfer Delay (Units : micro seconds )."
    ::= { pnniMapAddrRaigEntry 7 }

pnniMapAddrRaigCellDelayVariation OBJECT-TYPE
    SYNTAX Unsigned32
    MAX-ACCESS read-only
    STATUS current
    DESCRIPTION
	"Cell Delay Variation (Units : micro seconds )."
    ::= { pnniMapAddrRaigEntry 8 }

pnniMapAddrRaigCellLossRatio OBJECT-TYPE
    SYNTAX Integer32
    MAX-ACCESS read-only
    STATUS current
    DESCRIPTION
	"Cell Loss Ratio for CLP=0 encoded as the negative logarithm
	 of the value."
    ::= { pnniMapAddrRaigEntry 9 }

pnniMapAddrRaigCellLossRatio1 OBJECT-TYPE
    SYNTAX Integer32
    MAX-ACCESS read-only
    STATUS current
    DESCRIPTION
	"Cell Loss Ratio for CLP=0+1 encoded as the negative logarithm
	 of the value."
    ::= { pnniMapAddrRaigEntry 10 }

pnniMapAddrRaigCellRateMargin OBJECT-TYPE
    SYNTAX Integer32
    MAX-ACCESS read-only
    STATUS current
    DESCRIPTION
	"Cell Rate Margin in units cells/second. If the optional GCAC
	 related information is not present then this value would be
	 set to zero."
    ::= { pnniMapAddrRaigEntry 11 }

pnniMapAddrRaigVarianceFactor OBJECT-TYPE
    SYNTAX Integer32
    MAX-ACCESS read-only
    STATUS current
    DESCRIPTION
	"Variance Factor in units 2^-8. If the optional GCAC
	 related information is not present then this value would be
	 set to zero."
    ::= { pnniMapAddrRaigEntry 12 }



------------------------------------------------------------------------
-- PNNI Pc Profile Map Table

pnniPcProfileMapTable OBJECT-TYPE
   SYNTAX SEQUENCE OF PnniPcProfileMapEntry
   MAX-ACCESS not-accessible
   STATUS current               
   DESCRIPTION
        "PNNI Precomputed Paths Map Table."
   ::= { pnniGroup 6 }

pnniPcProfileMapEntry OBJECT-TYPE
    SYNTAX PnniPcProfileMapEntry
    MAX-ACCESS not-accessible
    STATUS current
    DESCRIPTION
        ""
    INDEX { pnniNodeIndex,
	    pnniPcProfileIndex,
	    pnniPcProfileMapOptIndex,
	    pnniPcProfileMapNodeId }
    ::= { pnniPcProfileMapTable 1 }

PnniPcProfileMapEntry ::= SEQUENCE {
    pnniPcProfileMapOptIndex		Integer32,
    pnniPcProfileMapNodeId		PnniNodeId,
    pnniPcProfileMapLocalPort		PnniPortId,
    pnniPcProfileMapParentNode		PnniNodeId,
    pnniPcProfileMapAdminWt		Unsigned32,
    pnniPcProfileMapMaximumCellRate	Unsigned32,
    pnniPcProfileMapAvailableCellRate	Unsigned32,
    pnniPcProfileMapCellTransferDelay	Unsigned32,
    pnniPcProfileMapCellDelayVariation	Unsigned32,
    pnniPcProfileMapCellLossRatio	Integer32,
    pnniPcProfileMapCellLossRatio1	Integer32,
    pnniPcProfileMapCellRateMargin	Integer32,
    pnniPcProfileMapVarianceFactor	Integer32
}

pnniPcProfileMapOptIndex OBJECT-TYPE
    SYNTAX Integer32
    MAX-ACCESS not-accessible
    STATUS current
    DESCRIPTION
	"An index into set of RAIG entries in the MapAddr entry. For
	 Horizontal Links and Up Links only outgoing RAIG entries are
	 present. For Nodal State IGs RAIG entries are present for both
	 directions."
    ::= { pnniPcProfileMapEntry 1 }

pnniPcProfileMapNodeId OBJECT-TYPE
    SYNTAX PnniNodeId 
    MAX-ACCESS not-accessible
    STATUS current
    DESCRIPTION
	"The nodes on the precomputed paths tree."
    ::= { pnniPcProfileMapEntry 2 }

pnniPcProfileMapLocalPort OBJECT-TYPE
    SYNTAX PnniPortId
    MAX-ACCESS read-only
    STATUS current
    DESCRIPTION
	"The local port the this node connects to the remote node"
    ::= { pnniPcProfileMapEntry 3 }

pnniPcProfileMapParentNode OBJECT-TYPE
    SYNTAX PnniNodeId
    MAX-ACCESS read-only
    STATUS current
    DESCRIPTION
	"The remote or parent node"
    ::= { pnniPcProfileMapEntry 4 }

pnniPcProfileMapAdminWt OBJECT-TYPE
    SYNTAX Unsigned32
    MAX-ACCESS read-only
    STATUS current
    DESCRIPTION
	"Adminstrative Weight associated with this MapAddr entry."
    ::= { pnniPcProfileMapEntry 5 }

pnniPcProfileMapMaximumCellRate OBJECT-TYPE
    SYNTAX Unsigned32
    MAX-ACCESS read-only
    STATUS current
    DESCRIPTION
	"Maximum Cell Rate (Units : cells/second )."
    ::= { pnniPcProfileMapEntry 6 }

pnniPcProfileMapAvailableCellRate OBJECT-TYPE
    SYNTAX Unsigned32
    MAX-ACCESS read-only
    STATUS current
    DESCRIPTION
	"Available Cell Rate (Units : cells/second )."
    ::= { pnniPcProfileMapEntry 7 }

pnniPcProfileMapCellTransferDelay OBJECT-TYPE
    SYNTAX Unsigned32
    MAX-ACCESS read-only
    STATUS current
    DESCRIPTION
	"Cell Transfer Delay (Units : micro seconds )."
    ::= { pnniPcProfileMapEntry 8 }

pnniPcProfileMapCellDelayVariation OBJECT-TYPE
    SYNTAX Unsigned32
    MAX-ACCESS read-only
    STATUS current
    DESCRIPTION
	"Cell Delay Variation (Units : micro seconds )."
    ::= { pnniPcProfileMapEntry 9 }


pnniPcProfileMapCellLossRatio OBJECT-TYPE
    SYNTAX Integer32
    MAX-ACCESS read-only
    STATUS current
    DESCRIPTION
	"Cell Loss Ratio for CLP=0 encoded as the negative logarithm
	 of the value."
    ::= { pnniPcProfileMapEntry 10 }

pnniPcProfileMapCellLossRatio1 OBJECT-TYPE
    SYNTAX Integer32
    MAX-ACCESS read-only
    STATUS current
    DESCRIPTION
	"Cell Loss Ratio for CLP=0+1 encoded as the negative logarithm
	 of the value."
    ::= { pnniPcProfileMapEntry 11 }

pnniPcProfileMapCellRateMargin OBJECT-TYPE
    SYNTAX Integer32
    MAX-ACCESS read-only
    STATUS current
    DESCRIPTION
	"Cell Rate Margin in units cells/second. If the optional GCAC
	 related information is not present then this value would be
	 set to zero."
    ::= { pnniPcProfileMapEntry 12 }

pnniPcProfileMapVarianceFactor OBJECT-TYPE
    SYNTAX Integer32
    MAX-ACCESS read-only
    STATUS current
    DESCRIPTION
	"Variance Factor in units 2^-8. If the optional GCAC
	 related information is not present then this value would be
	 set to zero."
    ::= { pnniPcProfileMapEntry 13 }

------------------------------------------------------------------------
-- PNNI Spanning Tree Map Table

pnniSpanningTreeMapTable OBJECT-TYPE
   SYNTAX SEQUENCE OF PnniSpanningTreeMapEntry
   MAX-ACCESS not-accessible
   STATUS current               
   DESCRIPTION
        "PNNI Reachability Tree(SpanningTree) Map Table."
   ::= { pnniGroup 7 }

pnniSpanningTreeMapEntry OBJECT-TYPE
    SYNTAX PnniSpanningTreeMapEntry
    MAX-ACCESS not-accessible
    STATUS current
    DESCRIPTION
        ""
    INDEX { pnniNodeIndex,
	    pnniSpanningTreeMapNodeId }
    ::= { pnniSpanningTreeMapTable 1 }

PnniSpanningTreeMapEntry ::= SEQUENCE {
    pnniSpanningTreeMapNodeId		PnniNodeId,
    pnniSpanningTreeMapStatus		INTEGER,
    pnniSpanningTreeMapParentNode	PnniNodeId,
    pnniSpanningTreeMapPort		PnniPortId,
    pnniSpanningTreeMapLinkType		INTEGER
}

pnniSpanningTreeMapNodeId OBJECT-TYPE
    SYNTAX PnniNodeId 
    MAX-ACCESS not-accessible
    STATUS current
    DESCRIPTION
	"The nodes on the Reachability tree."
    ::= { pnniSpanningTreeMapEntry 1 }

pnniSpanningTreeMapStatus OBJECT-TYPE
   SYNTAX  INTEGER {
		uptodate(1),
		linkadded(2),
		linkdeleted(3),
		treeclean(4),
		pglchanged(5)
	   }
    MAX-ACCESS read-only
    STATUS current
    DESCRIPTION
	"The status of the spanning tree. If links are added or
	removed then the spanning tree may not be up to date for a
	while until the tree is updated. If there are link added
	and deleted, the status will be linkdeleted"
    ::= { pnniSpanningTreeMapEntry 2 }

pnniSpanningTreeMapParentNode OBJECT-TYPE
    SYNTAX PnniNodeId
    MAX-ACCESS read-only
    STATUS current
    DESCRIPTION
	"The parent node or the next hop node on the spanning tree"
    ::= { pnniSpanningTreeMapEntry 3 }

pnniSpanningTreeMapPort OBJECT-TYPE
    SYNTAX PnniPortId
    MAX-ACCESS read-only
    STATUS current
    DESCRIPTION
	"The local port the this node connects to the remote node"
    ::= { pnniSpanningTreeMapEntry 4 }

pnniSpanningTreeMapLinkType OBJECT-TYPE
    SYNTAX INTEGER {
	hlink(1),
	uplink(2)
	}
    MAX-ACCESS read-only
    STATUS current
    DESCRIPTION
	"The type of the link that connects this noe to the remote node"
    ::= { pnniSpanningTreeMapEntry 5 }
------------------------------------------------------------------------
-- PNNI Connectivity Tree Map Table

pnniConnTreeMapTable OBJECT-TYPE
   SYNTAX SEQUENCE OF PnniConnTreeMapEntry
   MAX-ACCESS not-accessible
   STATUS current               
   DESCRIPTION
        "PNNI Connectivity Tree(SpanningTree) Map Table."
   ::= { pnniGroup 18 }

pnniConnTreeMapEntry OBJECT-TYPE
    SYNTAX PnniConnTreeMapEntry
    MAX-ACCESS not-accessible
    STATUS current
    DESCRIPTION
        ""
    INDEX { pnniNodeIndex,
	    pnniConnTreeMapNodeId }
    ::= { pnniConnTreeMapTable 1 }

PnniConnTreeMapEntry ::= SEQUENCE {
    pnniConnTreeMapNodeId		PnniNodeId,
    pnniConnTreeMapStatus		INTEGER,
    pnniConnTreeMapParentNode	PnniNodeId,
    pnniConnTreeMapPort		PnniPortId,
    pnniConnTreeMapLinkType		INTEGER
}

pnniConnTreeMapNodeId OBJECT-TYPE
    SYNTAX PnniNodeId 
    MAX-ACCESS not-accessible
    STATUS current
    DESCRIPTION
	"The nodes on the Connectivity tree."
    ::= { pnniConnTreeMapEntry 1 }

pnniConnTreeMapStatus OBJECT-TYPE
   SYNTAX  INTEGER {
		uptodate(1),
		linkadded(2),
		linkdeleted(3),
		treeclean(4),
		pglchanged(5)
	   }
    MAX-ACCESS read-only
    STATUS current
    DESCRIPTION
	"The status of the connectivity tree. If links are added or
	removed then the tree may not be up to date for a
	while until the tree is updated. If there are link added
	and deleted, the status will be linkdeleted"
    ::= { pnniConnTreeMapEntry 2 }

pnniConnTreeMapParentNode OBJECT-TYPE
    SYNTAX PnniNodeId
    MAX-ACCESS read-only
    STATUS current
    DESCRIPTION
	"The parent node or the next hop node on the  tree"
    ::= { pnniConnTreeMapEntry 3 }

pnniConnTreeMapPort OBJECT-TYPE
    SYNTAX PnniPortId
    MAX-ACCESS read-only
    STATUS current
    DESCRIPTION
	"The local port the this node connects to the remote node"
    ::= { pnniConnTreeMapEntry 4 }

pnniConnTreeMapLinkType OBJECT-TYPE
    SYNTAX INTEGER {
	hlink(1),
	uplink(2)
	}
    MAX-ACCESS read-only
    STATUS current
    DESCRIPTION
	"The type of the link that connects this noe to the remote node"
    ::= { pnniConnTreeMapEntry 5 }

------------------------------------------------------------------------
-- PNNI Node scheduler statistics

pnniNodeScStatsTable OBJECT-TYPE
   SYNTAX SEQUENCE OF PnniNodeScStatsEntry
   MAX-ACCESS not-accessible
   STATUS current               
   DESCRIPTION
        " Scheduler statistics table. "
   ::= { pnniGroup 8 }

pnniNodeScStatsEntry OBJECT-TYPE
    SYNTAX PnniNodeScStatsEntry
    MAX-ACCESS not-accessible
    STATUS current
    DESCRIPTION
        ""
    INDEX { pnniNodeIndex }
    ::= { pnniNodeScStatsTable 1 }

PnniNodeScStatsEntry ::= SEQUENCE {
    pnniNodeScStatsNrOfEvents			Unsigned32,
    pnniNodeScStatsNrOfPurges			Unsigned32,
    pnniNodeScStatsNrOfTimeoutPurges		Unsigned32,
    pnniNodeScStatsNrOfPacketsDropped		Unsigned32,
    pnniNodeScStatsNrOfHiPriPktsDropped		Unsigned32,
    pnniNodeScStatsNrOfLowPriPktsDropped	Unsigned32,
    pnniNodeScStatsNrOfNodalInfoEvents		Unsigned32,
    pnniNodeScStatsNrOfHorizLinkEvents		Unsigned32,
    pnniNodeScStatsNrOfUpLinkEvents		Unsigned32,
    pnniNodeScStatsNrOfNodalStateEvents		Unsigned32
}

pnniNodeScStatsNrOfEvents OBJECT-TYPE
    SYNTAX Unsigned32
    MAX-ACCESS read-only
    STATUS current
    DESCRIPTION
        " The number of scheduler events"
    ::= { pnniNodeScStatsEntry 2 }

pnniNodeScStatsNrOfPurges OBJECT-TYPE
    SYNTAX Unsigned32
    MAX-ACCESS read-only
    STATUS current
    DESCRIPTION
        " The number of scheduler queue purges"
    ::= { pnniNodeScStatsEntry 3 }

pnniNodeScStatsNrOfTimeoutPurges OBJECT-TYPE
    SYNTAX Unsigned32
    MAX-ACCESS read-only
    STATUS current
    DESCRIPTION
        " The number of times scheduler queues were purged due to xxx
	timer expiry."
    ::= { pnniNodeScStatsEntry 4 }

pnniNodeScStatsNrOfPacketsDropped OBJECT-TYPE
    SYNTAX Unsigned32
    MAX-ACCESS read-only
    STATUS current
    DESCRIPTION
        " The number of packets dropped in the scheduler"
    ::= { pnniNodeScStatsEntry 5 }

pnniNodeScStatsNrOfHiPriPktsDropped OBJECT-TYPE
    SYNTAX Unsigned32
    MAX-ACCESS read-only
    STATUS current
    DESCRIPTION
        " The number of high priority packets dropped in the scheduler"
    ::= { pnniNodeScStatsEntry 6 }

pnniNodeScStatsNrOfLowPriPktsDropped OBJECT-TYPE
    SYNTAX Unsigned32
    MAX-ACCESS read-only
    STATUS current
    DESCRIPTION
        " The number of low priority packets dropped in the scheduler"
    ::= { pnniNodeScStatsEntry 7 }

pnniNodeScStatsNrOfNodalInfoEvents OBJECT-TYPE
    SYNTAX Unsigned32
    MAX-ACCESS read-only
    STATUS current
    DESCRIPTION
        " The number of significant changes occurred to
	NodalInformation Information Groups"
    ::= { pnniNodeScStatsEntry 8 }

pnniNodeScStatsNrOfHorizLinkEvents OBJECT-TYPE
    SYNTAX Unsigned32
    MAX-ACCESS read-only
    STATUS current
    DESCRIPTION
        " The number of significant changes occurred to Horizontal
	Link Information Group."
    ::= { pnniNodeScStatsEntry 9 }

pnniNodeScStatsNrOfUpLinkEvents OBJECT-TYPE
    SYNTAX Unsigned32
    MAX-ACCESS read-only
    STATUS current
    DESCRIPTION
        " The number of significant changes occurred to Uplink
	Information Group."
    ::= { pnniNodeScStatsEntry 10 }

pnniNodeScStatsNrOfNodalStateEvents OBJECT-TYPE
    SYNTAX Unsigned32
    MAX-ACCESS read-only
    STATUS current
    DESCRIPTION
        " The number of significant changes occurred to Nodal State
	Information Group."
    ::= { pnniNodeScStatsEntry 11 }


------------------------------------------------------------------------
-- PNNI Node PC profile avoid links table

pnniPcProfileAvoidLinkTable OBJECT-TYPE
    SYNTAX SEQUENCE OF PnniPcProfileAvoidLinkEntry
    MAX-ACCESS not-accessible
    STATUS current
    DESCRIPTION
	" avoid link table for the cache profile"
    ::= { pnniGroup 10 }

pnniPcProfileAvoidLinkEntry OBJECT-TYPE
    SYNTAX PnniPcProfileAvoidLinkEntry
    MAX-ACCESS not-accessible
    STATUS current
    DESCRIPTION
        ""
    INDEX { pnniNodeIndex, pnniPcProfileIndex, pnniPcProfileAvoidLinkIndex }
    ::= { pnniPcProfileAvoidLinkTable 1 }

PnniPcProfileAvoidLinkEntry ::= SEQUENCE {
    pnniPcProfileAvoidLinkIndex         Integer32,
    pnniPcProfileAvoidLinkNodeId        PnniNodeId,
    pnniPcProfileAvoidLinkPortId        PnniPortId,
    pnniPcProfileAvoidLinkType          INTEGER,
    pnniPcProfileAvoidLinkRemoteNodeId  PnniNodeId
}

pnniPcProfileAvoidLinkIndex OBJECT-TYPE
    SYNTAX Integer32
    MAX-ACCESS not-accessible
    STATUS current
    DESCRIPTION
        "The index to the list of to be avoided links in this profile"
    ::= { pnniPcProfileAvoidLinkEntry 1 }

pnniPcProfileAvoidLinkNodeId OBJECT-TYPE
    SYNTAX PnniNodeId
    MAX-ACCESS read-only
    STATUS current
    DESCRIPTION
        "The nodeid of the node to be avoided"
    ::= { pnniPcProfileAvoidLinkEntry 2 }

pnniPcProfileAvoidLinkPortId OBJECT-TYPE
    SYNTAX PnniPortId
    MAX-ACCESS read-only
    STATUS current
    DESCRIPTION
        "Portid of the link. If it is zero, the node is to be avoided which
         means all links of this node should be avoided"
    ::= { pnniPcProfileAvoidLinkEntry 3 }

pnniPcProfileAvoidLinkType OBJECT-TYPE
    SYNTAX INTEGER {
	normalLink(1),
	reverseLink(2)
	}
    MAX-ACCESS read-only
    STATUS current
    DESCRIPTION
        "The link type, normal link will in the form of (node, portid, rmtnode)
         for reverse link it is in form of (node, rmtportid, rmtnode) and it is
         the reverse reprentation of the uplink (rmtnode, rmtportid, node)"
    ::= { pnniPcProfileAvoidLinkEntry 4 }

pnniPcProfileAvoidLinkRemoteNodeId OBJECT-TYPE
    SYNTAX PnniNodeId
    MAX-ACCESS read-only
    STATUS current
    DESCRIPTION
        "The remote node id of the link. If portid is zero, then the node is to
         be avoided not just a link. Remote node id is not available in this
         case"
    ::= { pnniPcProfileAvoidLinkEntry 5 }

------------------------------------------------------------------------
-- PNNI Node PC profile prefered links table

pnniPcProfilePreferLinkTable OBJECT-TYPE
    SYNTAX SEQUENCE OF PnniPcProfilePreferLinkEntry
    MAX-ACCESS not-accessible
    STATUS current
    DESCRIPTION
	" Prefered link table for the cache profile"
    ::= { pnniGroup 11 }

pnniPcProfilePreferLinkEntry OBJECT-TYPE
    SYNTAX PnniPcProfilePreferLinkEntry
    MAX-ACCESS not-accessible
    STATUS current
    DESCRIPTION
        ""
    INDEX { pnniNodeIndex, pnniPcProfileIndex, pnniPcProfilePreferLinkIndex }
    ::= { pnniPcProfilePreferLinkTable 1 }

PnniPcProfilePreferLinkEntry ::= SEQUENCE {
    pnniPcProfilePreferLinkIndex         Integer32,
    pnniPcProfilePreferLinkNodeId        PnniNodeId,
    pnniPcProfilePreferLinkPortId        PnniPortId,
    pnniPcProfilePreferLinkType          INTEGER,
    pnniPcProfilePreferLinkRemoteNodeId  PnniNodeId
}

pnniPcProfilePreferLinkIndex OBJECT-TYPE
    SYNTAX Integer32
    MAX-ACCESS not-accessible
    STATUS current
    DESCRIPTION
        "The index to the list of prefered links in this profile"
    ::= { pnniPcProfilePreferLinkEntry 1 }

pnniPcProfilePreferLinkNodeId OBJECT-TYPE
    SYNTAX PnniNodeId
    MAX-ACCESS read-only
    STATUS current
    DESCRIPTION
        "The nodeid of the node is prefered"
    ::= { pnniPcProfilePreferLinkEntry 2 }

pnniPcProfilePreferLinkPortId OBJECT-TYPE
    SYNTAX PnniPortId
    MAX-ACCESS read-only
    STATUS current
    DESCRIPTION
        "Portid of the link. "
    ::= { pnniPcProfilePreferLinkEntry 3 }

pnniPcProfilePreferLinkType OBJECT-TYPE
    SYNTAX INTEGER {
	normalLink(1),
	reverseLink(2)
	}
    MAX-ACCESS read-only
    STATUS current
    DESCRIPTION
        "The link type, normal link will in the form of (node, portid, rmtnode)
         for reverse link it is in form of (node, rmtportid, rmtnode) and it is
         the reverse reprentation of the uplink (rmtnode, rmtportid, node)"
    ::= { pnniPcProfilePreferLinkEntry 4 }

pnniPcProfilePreferLinkRemoteNodeId OBJECT-TYPE
    SYNTAX PnniNodeId
    MAX-ACCESS read-only
    STATUS current
    DESCRIPTION
        "The remote node id of the link."
    ::= { pnniPcProfilePreferLinkEntry 5 }

------------------------------------------------------------------------
-- Table for list of PNNI Designated Transit Lists (DTLs).
------------------------------------------------------------------------

pnniDtlListTable OBJECT-TYPE
    SYNTAX  SEQUENCE OF PnniDtlListEntry
    MAX-ACCESS  not-accessible
    STATUS  current
    DESCRIPTION
        "This table contains a list of Designated Transit Lists (DTLs)
        and their associated weights."
    ::= { pnniGroup 15 }

pnniDtlListEntry OBJECT-TYPE
    SYNTAX  PnniDtlListEntry
    MAX-ACCESS  not-accessible
    STATUS  current
    DESCRIPTION
        "An entry in the PNNI DTL list table.  A DTL list is formed
        by concatenating rows of the table for which the
        pnniDtlListIndex is the same."
    INDEX   { pnniDtlListTag, pnniDtlListNodeIndex, pnniDtlListDtlIndex }
    ::= { pnniDtlListTable 1 }

PnniDtlListEntry ::= SEQUENCE {
    pnniDtlListTag              INTEGER,
    pnniDtlListNodeIndex        INTEGER,
    pnniDtlListDtlIndex         INTEGER,
    pnniDtlListWeight  	        INTEGER,
    pnniDtlListStatus           RowStatus
}

pnniDtlListTag OBJECT-TYPE
    SYNTAX  INTEGER(1..2147483647)
    MAX-ACCESS  not-accessible
    STATUS  current
    DESCRIPTION
        "The value of this object specifies the tag associated with a PNNI DTL
        list in the table.  A DTL list is a list of source route entries."
    ::= { pnniDtlListEntry 1 }

pnniDtlListNodeIndex OBJECT-TYPE
    SYNTAX  INTEGER(1..2147483647)
    MAX-ACCESS  not-accessible
    STATUS  current
    DESCRIPTION
        "A unique pre-configured DTL on a switch is identified by a
        nodeIndex, dtlIndex pair.  This object corresponds to the nodeIndex
        value of the DTL being referred to."
    ::= { pnniDtlListEntry 2 }

pnniDtlListDtlIndex OBJECT-TYPE
    SYNTAX  INTEGER(1..2147483647)
    MAX-ACCESS  not-accessible
    STATUS  current
    DESCRIPTION
        "A unique pre-configured DTL on a switch is identified by a
        nodeIndex, dtlIndex pair.  This object corresponds to the dtlIndex
        value of the DTL being referred to."
    ::= { pnniDtlListEntry 3 }

pnniDtlListWeight OBJECT-TYPE
    SYNTAX  INTEGER(1..2147483647)
    MAX-ACCESS  read-create
    STATUS  current
    DESCRIPTION
        "The weight specifies the priority of this DTL entry index
        among all the DTL indices that are specified in the list."
    DEFVAL { 1000 }
    ::= { pnniDtlListEntry 4 }

pnniDtlListStatus OBJECT-TYPE
    SYNTAX  RowStatus
    MAX-ACCESS  read-create
    STATUS  current
    DESCRIPTION
        "The status of this DTL entry in the list."
    ::= { pnniDtlListEntry 5 }

------------------------------------------------------------------------
-- PNNI DTL table extension
-- This table is a proprietary extension to the standard PNNI DTL MIBs
-- to provide SNMP access to on-demand validation of the configured DTLs
------------------------------------------------------------------------
forePnniDTLTable OBJECT-TYPE
    SYNTAX  SEQUENCE OF ForePnniDTLEntry
    MAX-ACCESS  not-accessible
    STATUS  current
    DESCRIPTION
        "This table holds the validate object for the DTL entries
        defined in the standard PNNI DTL MIB table."
    ::= { pnniGroup 13 }

forePnniDTLEntry OBJECT-TYPE
    SYNTAX  ForePnniDTLEntry
    MAX-ACCESS  not-accessible
    STATUS  current
    DESCRIPTION
        "Validate command for the DTL indexed by the node and DTL index."
    INDEX { pnniNodeIndex, pnniDTLIndex }
    ::= { forePnniDTLTable 1 }

ForePnniDTLEntry ::= SEQUENCE {
    forePnniDTLName         DisplayString,
    forePnniDTLValidity     DisplayString
}

forePnniDTLName OBJECT-TYPE
	SYNTAX	DisplayString (SIZE (0..31))
	MAX-ACCESS	read-write
	STATUS	current
	DESCRIPTION
		"The Name of this Directed Designated Transit List"
	::= { forePnniDTLEntry 1 }

forePnniDTLValidity OBJECT-TYPE
    SYNTAX  DisplayString (SIZE (0..255))
    MAX-ACCESS  read-only
    STATUS  current
    DESCRIPTION
        "The validity of the DTL referenced by the pnniNodeIndex and
        pnniDtlIndex.  If validation fails, the text describes the
        cause for failure and the hop at which the dtl failed."
    ::= { forePnniDTLEntry 2 }

------------------------------------------------------------------------
-- PNNI DTL Computation Table
-- This table provides SNMP support for calculation and creation
-- of DTLs
------------------------------------------------------------------------
pnniDtlComputationTable OBJECT-TYPE
    SYNTAX  SEQUENCE OF PnniDtlComputationEntry
    MAX-ACCESS  not-accessible
    STATUS  current
    DESCRIPTION
        "This table provides an interface for the calculation and
        creation of a DTL."
    ::= { pnniGroup 14 }

pnniDtlComputationEntry OBJECT-TYPE
    SYNTAX  PnniDtlComputationEntry
    MAX-ACCESS  not-accessible
    STATUS  current
    DESCRIPTION
        "A structure containing the parameters for creation of a
        directed DTL."
    INDEX { pnniDtlComputationNodeIndex, pnniDtlComputationDtlIndex }
    ::= { pnniDtlComputationTable 1 }

PnniDtlComputationEntry ::= SEQUENCE {
    pnniDtlComputationNodeIndex        PnniNodeIndex,
    pnniDtlComputationDtlIndex         Integer32,
    pnniDtlComputationDestNsapAddress  NsapAddr,
    pnniDtlComputationCompute          Integer32
}

pnniDtlComputationNodeIndex OBJECT-TYPE
    SYNTAX  PnniNodeIndex
    MAX-ACCESS  read-write
    STATUS  current
    DESCRIPTION
        "The node index of the DTL to be created."
    ::= { pnniDtlComputationEntry 1 }

pnniDtlComputationDtlIndex OBJECT-TYPE
    SYNTAX  Integer32
    MAX-ACCESS  read-write
    STATUS  current
    DESCRIPTION
        "The DTL index of the DTL to be created."
    ::= { pnniDtlComputationEntry 2 }

pnniDtlComputationDestNsapAddress OBJECT-TYPE
    SYNTAX  NsapAddr
    MAX-ACCESS  read-write
    STATUS  current
    DESCRIPTION
        "The destination NSAP address of the DTL to be created."
    ::= { pnniDtlComputationEntry 3 }

pnniDtlComputationCompute  OBJECT-TYPE
    SYNTAX  Integer32
    MAX-ACCESS  read-write
    STATUS  current
    DESCRIPTION
	"When this object is written to, an attempt will be made to
        compute and create a new DTL with the specified parameters."
    ::= { pnniDtlComputationEntry 4 }

------------------------------------------------------------------------
--pnniCrankbackGroup

pnniMaxCrankbackTries OBJECT-TYPE
    SYNTAX Integer32
    MAX-ACCESS read-write
    STATUS current
    DESCRIPTION
        "The maximum number of tries for a given call in the case of 
         receiving crankbacks when attempting to progress the call. This
         value includes the first attempt at progressing the call also."
    ::= { pnniCrankbackGroup 1 }


------------------------------------------------------------------------
--pnniParametersGroup
--This group contains all global PNNI parameters such
--as the maximum number of hops per PNNI DTL supported by
--this switch. Ideally, the pnniMaxCrankbackTries variable
--should also have been part of this Group                        

pnniMaxDtlSize OBJECT-TYPE
    SYNTAX INTEGER(20..100)
    MAX-ACCESS read-write
    STATUS current
    DESCRIPTION
        "The maximum number of hops per DTL supported by this switch.
        The switch will not process any incoming DTL that has more than
        this number of hops at any level of the PNNI hierarchy. 
        It will also not generate any calls with more than this number 
        of hops in any DTL at any level of PNNI hierarchy."
    DEFVAL { 20 }
    ::= { pnniParametersGroup 1 }        

pnniLoadBalancedUbrEnable OBJECT-TYPE
    SYNTAX Integer32
    MAX-ACCESS read-write
    STATUS current
    DESCRIPTION
	"This value specifies whether LBUBR routing of SPVCs is enabled"
    ::= { pnniParametersGroup 2 }
        
------------------------------------------------------------------------
--atmRoutingGroup

rtDomainTable OBJECT-TYPE
	SYNTAX	SEQUENCE OF RtDomainEntry
	MAX-ACCESS	not-accessible
	STATUS	current
	DESCRIPTION
                "A table of routing domains withing the ATM routing module"
	::= { atmRoutingGroup 1 }

rtDomainEntry OBJECT-TYPE
	SYNTAX	RtDomainEntry
	MAX-ACCESS	not-accessible
	STATUS	current
	DESCRIPTION
		"A table entry containing administrative routing domain information"
	INDEX	{ rtDomainID }
	::= { rtDomainTable 1 }

RtDomainEntry ::=
        SEQUENCE {
                rtDomainID             Integer32,
                rtDomainDefaultProto   INTEGER,
                rtDomainPrefix         NsapPrefix,
                rtDomainName           DisplayString,
                rtDomainDefSumState    INTEGER,
                rtDomainStatus         RowStatus,
                rtDomainDefaultPrefix  NsapPrefix
        }

rtDomainID   OBJECT-TYPE
	SYNTAX	Integer32
	MAX-ACCESS	read-create
	STATUS	current
	DESCRIPTION
		"The ID of this Routing Domain"
	::= { rtDomainEntry 1 }
        

rtDomainDefaultProto OBJECT-TYPE
        SYNTAX  INTEGER {
                        ftpnni(1),
                        pnni(2),
                        gateway(3)
                }
        MAX-ACCESS  read-create
        STATUS  current
        DESCRIPTION
                "The Default routing protocol used by this switch"
        ::= { rtDomainEntry 2 }

rtDomainPrefix OBJECT-TYPE
	SYNTAX	NsapPrefix
	MAX-ACCESS	read-create
	STATUS	current
	DESCRIPTION
		"The Default Prefix associated with this Domain"
	::= { rtDomainEntry 3 }

rtDomainName OBJECT-TYPE
	SYNTAX	DisplayString (SIZE (0..63))
	MAX-ACCESS	read-create
	STATUS	current
	DESCRIPTION
		"The Domain Name of this administrative Routing Domain"
	::= { rtDomainEntry 4 }

rtDomainDefSumState OBJECT-TYPE
	SYNTAX	INTEGER {
                        enable(1),
                        disable(2)
                }
	MAX-ACCESS	read-create
	STATUS	current
	DESCRIPTION
		"The State of the Default Summarization Policy in this 
                domain. If enabled, Default Summarization Policies are
                activated (peergroup ID of each node in this domain is
                used as a summarization policy for all other nodes in 
                the domain). If disabled, the default summarization policies
                are deactivated"
	::= { rtDomainEntry 5 }

rtDomainStatus OBJECT-TYPE
	SYNTAX	RowStatus
	MAX-ACCESS	read-create
	STATUS	current
	DESCRIPTION
		"The entry status of this routing domain"
	::= { rtDomainEntry 6 }
                
rtDomainDefaultPrefix OBJECT-TYPE
	SYNTAX	NsapPrefix
	MAX-ACCESS	read-only
	STATUS	current
	DESCRIPTION
		"The factory-encoded default domain prefix 
		 for this switch"
	::= { rtDomainEntry 7 }


------------------------------------------------------------------------
--atmrPrefixTable
atmrPrefixTable OBJECT-TYPE
	SYNTAX	SEQUENCE OF AtmrPrefixEntry
	MAX-ACCESS	not-accessible
	STATUS	current
	DESCRIPTION
                "The atmrPrefixTable is a collection of all addresses
		 reachable with in a domain. This includes all
		 internal reachable addresses, external reachable
		 addresses and locally registered addresses."
	::= { atmRoutingGroup 2 }

atmrPrefixEntry OBJECT-TYPE
	SYNTAX	AtmrPrefixEntry
	MAX-ACCESS	not-accessible
	STATUS	current
	DESCRIPTION
		"An entry in the table, containing information about a
		 reachable prefix in this switching system."
	INDEX	{ rtDomainID,
		  atmrPrefixAddr, 
		  atmrPrefixLength} 
	::= { atmrPrefixTable 1 }

AtmrPrefixEntry ::=
        SEQUENCE {
		atmrPrefixAddr			AtmAddrPrefix,
		atmrPrefixLength		PnniPrefixLength,
		atmrPrefixFlags			Integer32,
		atmrPrefixOwnerLevel		Integer32,
		atmrPrefixOwnerProtocol		INTEGER,
		atmrPrefixOwnerPathFlags	Integer32,		
		atmrPrefixTimeStamp		Unsigned32
        }

atmrPrefixAddr OBJECT-TYPE
	SYNTAX	AtmAddrPrefix
	MAX-ACCESS	not-accessible
	STATUS	current
	DESCRIPTION
		"The value of the prefix. In the case where multiple
		 nodes advertised reachability to the same prefix, all
		 the PTEs describes the nodes will be collected in
		 this entry."
	::= { atmrPrefixEntry 1 }

atmrPrefixLength OBJECT-TYPE
	SYNTAX	PnniPrefixLength
	MAX-ACCESS	not-accessible
	STATUS	current
	DESCRIPTION
		"Length of the prefix."
	::= { atmrPrefixEntry 2 }

atmrPrefixFlags OBJECT-TYPE
	SYNTAX	Integer32
	MAX-ACCESS	read-only
	STATUS	current
	DESCRIPTION
		"Flags indicate the status of the prefix node, this is
		 a bitmask. The description of bits is as follows.
			Bit	Description
			1	when set indicates that this prefix
				node in on the change list
			2	when set indicates that the prefix
				node has been deleted."
	::= { atmrPrefixEntry 3 }

atmrPrefixOwnerLevel OBJECT-TYPE
	SYNTAX	Integer32
	MAX-ACCESS	read-only
	STATUS	current
	DESCRIPTION
		"The level of the node that owns this prefix. The
		 meaning of owning a prefix can be explained as the
		 preferred node among the nodes advertising this
		 prefix."
	::= { atmrPrefixEntry 4 }

atmrPrefixOwnerProtocol OBJECT-TYPE
	SYNTAX	INTEGER {
                        bogus(1),
                        admin(2),
                        ftpnni(3),
			pnni(4),
			ilmi(5),
			static(6),
			atmfint(7),
			atmfext(8),
			interdom(9)
		}
	MAX-ACCESS	read-only
	STATUS	current
	DESCRIPTION
		"The protocol throught which this prefix was learnt
		 from the owner."
	::= { atmrPrefixEntry 5 }

atmrPrefixOwnerPathFlags OBJECT-TYPE
	SYNTAX	Integer32
	MAX-ACCESS	read-only
	STATUS	current
	DESCRIPTION
		"These flags describe the status of the PTE that owns
		 it.
			Bit	Description
			1	when set indicates that this PTE is
				locally originated and cannot be
				further summarized."
	::= { atmrPrefixEntry 6 }

atmrPrefixTimeStamp OBJECT-TYPE
	SYNTAX	Unsigned32
	MAX-ACCESS	read-only
	STATUS	current
	DESCRIPTION
		"Time this prefix node added/changed."
	::= { atmrPrefixEntry 7 }

------------------------------------------------------------------------
--atmrPteTable

atmrPteTable OBJECT-TYPE
	SYNTAX	SEQUENCE OF AtmrPteEntry
	MAX-ACCESS	not-accessible
	STATUS	current
	DESCRIPTION
                "The atmrPteTable collects all the PTEs that are
		 present in the Prefix Table. There is single row for
		 every address known for each source."
	::= { atmRoutingGroup 3 }

atmrPteEntry OBJECT-TYPE
	SYNTAX	AtmrPteEntry
	MAX-ACCESS	not-accessible
	STATUS	current
	DESCRIPTION
		"An entry in the table, containing information about a
		 reachable address, source and a handle to the source"
	INDEX	{ rtDomainID,
		  atmrPrefixAddr, 
		  atmrPrefixLength,
		  atmrPteIndex}
	::= { atmrPteTable 1 }

AtmrPteEntry ::=
        SEQUENCE {
		atmrPteIndex			Integer32,
		atmrPteProtocolId		Integer32,
		atmrPteProtocolHandle		Unsigned32,
		atmrPteProtocol			INTEGER,
		atmrPtePathFlags		Integer32,
		atmrPteLevel			Integer32,
		atmrPteArea			Unsigned32,
		atmrPteScope			Integer32,
		atmrPteSourceArea		Unsigned32,
		atmrPteType			Integer32,
		atmrPteTnsLen			Integer32,
		atmrPteTnsType			TnsType,
		atmrPteTnsPlan			TnsPlan,
		atmrPteTnsId			Integer32		
        }

atmrPteIndex OBJECT-TYPE
	SYNTAX	Integer32
	MAX-ACCESS	not-accessible
	STATUS	current
	DESCRIPTION
		"Index to list of ptes belong to this prefix node"
	::= { atmrPteEntry 1 }

atmrPteProtocolId OBJECT-TYPE
	SYNTAX	Integer32
	MAX-ACCESS	read-only
	STATUS	current
	DESCRIPTION
		"Protocol's reference/identifier that the exact source
		 of this information. It is tdbhndl for PNNI and
		 nothing for ilmi or other localy registred
		 addresses."
	::= { atmrPteEntry 2 }

atmrPteProtocolHandle OBJECT-TYPE
	SYNTAX	Unsigned32
	MAX-ACCESS	read-only
	STATUS	current
	DESCRIPTION
		"Protocol's internal handle for this PTE, for pnni it
		 is ptsehndl and for local routes it is the rt_node."
	::= { atmrPteEntry 3 }

atmrPteProtocol OBJECT-TYPE
	SYNTAX	INTEGER {
                        bogus(1),
                        admin(2),
                        ftpnni(3),
			pnni(4),
			ilmi(5),
			static(6),
			atmfint(7),
			atmfext(8),
			interdom(9)
		}
	MAX-ACCESS	read-only
	STATUS	current
	DESCRIPTION
		"The protocol through which this prefix was learnt."
	::= { atmrPteEntry 4 }

atmrPtePathFlags OBJECT-TYPE
	SYNTAX	Integer32
	MAX-ACCESS	read-only
	STATUS	current
	DESCRIPTION
		"These flags describe the status of the PTE that owns
		 it.
			Bit	Description
			1	when set indicates that this PTE is
				locally originated and cannot be
				further summarized."
	::= { atmrPteEntry 5 }

atmrPteLevel OBJECT-TYPE
	SYNTAX	Integer32
	MAX-ACCESS	read-only
	STATUS	current
	DESCRIPTION
		"The area level of the registerer."
	::= { atmrPteEntry 6 }

atmrPteArea OBJECT-TYPE
	SYNTAX	Unsigned32
	MAX-ACCESS	read-only
	STATUS	current
	DESCRIPTION
		"The id of are to which registerer belongs to."
	::= { atmrPteEntry 7 }

atmrPteScope OBJECT-TYPE
	SYNTAX	Integer32
	MAX-ACCESS	read-only
	STATUS	current
	DESCRIPTION
		"The advertisement scope of prefix."
	::= { atmrPteEntry 8 }

atmrPteSourceArea OBJECT-TYPE
	SYNTAX	Unsigned32
	MAX-ACCESS	read-only
	STATUS	current
	DESCRIPTION
		"The id of area from which prefix was learned."
	::= { atmrPteEntry 9 }

atmrPteType OBJECT-TYPE
	SYNTAX	Integer32
	MAX-ACCESS	read-only
	STATUS	current
	DESCRIPTION
		"the reachability type of the prefix, its either
		 internal ot external."
	::= { atmrPteEntry 10 }

atmrPteTnsLen OBJECT-TYPE
	SYNTAX	Integer32
	MAX-ACCESS	read-only
	STATUS	current
	DESCRIPTION
		"The length of the TNS ID."
	::= { atmrPteEntry 11 }

atmrPteTnsType OBJECT-TYPE
	SYNTAX	TnsType
	MAX-ACCESS	read-only
	STATUS	current
	DESCRIPTION
		"Indicates the type of network identification of a
		 specified transit network."
	::= { atmrPteEntry 12 }

atmrPteTnsPlan OBJECT-TYPE
	SYNTAX	TnsPlan
	MAX-ACCESS	read-only
	STATUS	current
	DESCRIPTION
		"Indicates the network identification plan of a
		 specified transit network."
	::= { atmrPteEntry 13 }

atmrPteTnsId OBJECT-TYPE
	SYNTAX	Integer32
	MAX-ACCESS	read-only
	STATUS	current
	DESCRIPTION
		"The identifier of the transit network."
	::= { atmrPteEntry 14}

------------------------------------------------------------------------
-- ATMR Inter-Domain Routing Table

atmrInterDomainRouteTable OBJECT-TYPE
	SYNTAX	SEQUENCE OF AtmrInterDomainRouteEntry
	MAX-ACCESS	not-accessible
	STATUS	current
	DESCRIPTION
                "A table of static inter-domain routes within the ATMR module"
	::= { atmRoutingGroup 4 }


atmrInterDomainRouteEntry OBJECT-TYPE
	SYNTAX	AtmrInterDomainRouteEntry
	MAX-ACCESS	not-accessible
	STATUS	current
	DESCRIPTION
		"A table entry containing an inter-domain static route"
	INDEX	{ atmrIDRDomainID, atmrIDRAddr, atmrIDRAddrLen, atmrIDRDestDomainID }
	::= { atmrInterDomainRouteTable 1 }

AtmrInterDomainRouteEntry ::=
        SEQUENCE {
                atmrIDRDomainID         Integer32,
                atmrIDRAddr             AtmAddrPrefix,
                atmrIDRAddrLen          PnniPrefixLength,
                atmrIDRDestDomainID     Integer32,
                atmrIDRRowStatus        RowStatus
        }

atmrIDRDomainID  OBJECT-TYPE
	SYNTAX	Integer32
	MAX-ACCESS	read-create
	STATUS	current
	DESCRIPTION
		"The ID of this Routing Domain to which this static route belongs.
                 This static route gets installed in the Prefix Tree of this domain
                 and gets exported all nodes (PNNI and FT-PNNI) operating in this domain"
	::= { atmrInterDomainRouteEntry 1 }
        
atmrIDRAddr     OBJECT-TYPE
        SYNTAX  AtmAddrPrefix
	MAX-ACCESS	read-create
	STATUS	current
	DESCRIPTION
                "This is the ATM Addr Prefix which is the reachable address prefix"
        ::= { atmrInterDomainRouteEntry 2 }        

atmrIDRAddrLen  OBJECT-TYPE
        SYNTAX  PnniPrefixLength         
        MAX-ACCESS  read-create
	STATUS	current
	DESCRIPTION
                "The prefix length to be applied to the ATM address prefix"
        ::= { atmrInterDomainRouteEntry 3 } 

atmrIDRDestDomainID  OBJECT-TYPE
        SYNTAX  Integer32
        MAX-ACCESS  read-create
	STATUS	current
	DESCRIPTION
                "The ID of the destination Domain in which this reachable prefix
                is actually reachable"
        ::= { atmrInterDomainRouteEntry 4 } 

atmrIDRRowStatus    OBJECT-TYPE
        SYNTAX  RowStatus
        MAX-ACCESS read-create
        STATUS current
        DESCRIPTION
        "To create, delete, activate and de-activate a Inter-Domain
        route entries."
    ::= { atmrInterDomainRouteEntry 5 }
        
------------------------------------------------------------------------
--atmrDestNsapTable

atmrDestNsapTable OBJECT-TYPE
	SYNTAX	SEQUENCE OF AtmrDestNsapEntry
	MAX-ACCESS	not-accessible
	STATUS	current
	DESCRIPTION
		"A table of containing NSAP addresses for each AtmIf
		 in a routing domain. This is used for SPVCCs and SPVPCs."
	::= { atmRoutingGroup 5 }

atmrDestNsapEntry OBJECT-TYPE
	SYNTAX	AtmrDestNsapEntry
	MAX-ACCESS	not-accessible
	STATUS	current
	DESCRIPTION
		"An entry in the table, containing the NSAP address for
		 the AtmIf in a domain."
	INDEX	{ rtDomainID,
		  portNumber }
	::= { atmrDestNsapTable 1 }

AtmrDestNsapEntry ::=
        SEQUENCE {
		atmrDestNsapAddr		NsapAddr
        }

atmrDestNsapAddr OBJECT-TYPE
	SYNTAX	NsapAddr
	MAX-ACCESS	read-only
	STATUS	current
	DESCRIPTION "The NSAP address of this AtmIf in this domain."
	::= { atmrDestNsapEntry 1 }


------------------------------------------------------------------------
-- pnniPortVpiMapTable: for converting port/vpi pair to pnni ifix and portid

pnniPortVpiMapTable OBJECT-TYPE
    SYNTAX SEQUENCE OF PnniPortVpiMapEntry
    MAX-ACCESS not-accessible
    STATUS current
    DESCRIPTION
	" Hardware Port table for converting Port VPI to ifix and portid
	in pnni "
    ::= { pnniIfMapGroup 1 }

pnniPortVpiMapEntry OBJECT-TYPE
    SYNTAX PnniPortVpiMapEntry
    MAX-ACCESS not-accessible
    STATUS current
    DESCRIPTION
        ""
    INDEX { pnniPortVpiMapPort, pnniPortVpiMapVpi }
    ::= { pnniPortVpiMapTable 1 }

PnniPortVpiMapEntry ::= SEQUENCE {
    pnniPortVpiMapPort     Integer32,
    pnniPortVpiMapVpi      Integer32,
    pnniPortVpiMapIfIndex  InterfaceIndex,
    pnniPortVpiMapPortId   PnniPortId
}

pnniPortVpiMapPort OBJECT-TYPE
    SYNTAX Integer32
    MAX-ACCESS not-accessible
    STATUS current
    DESCRIPTION
        "Port index"
    ::= { pnniPortVpiMapEntry 1 }

pnniPortVpiMapVpi OBJECT-TYPE
    SYNTAX Integer32
    MAX-ACCESS not-accessible
    STATUS current
    DESCRIPTION
        "Vpi index"
    ::= { pnniPortVpiMapEntry 2 }

pnniPortVpiMapIfIndex OBJECT-TYPE
    SYNTAX InterfaceIndex
    MAX-ACCESS read-only
    STATUS current
    DESCRIPTION
        "Pnni interface index"
    ::= { pnniPortVpiMapEntry 3 }

pnniPortVpiMapPortId OBJECT-TYPE
    SYNTAX PnniPortId
    MAX-ACCESS read-only
    STATUS current
    DESCRIPTION
        "Port ID corresponding the interface"
    ::= { pnniPortVpiMapEntry 4 }

----------------------------------------------------------------------
-- pnniPortIdMapTable: mapping from portid to port/vpi and ifix

pnniPortIdMapTable OBJECT-TYPE
    SYNTAX SEQUENCE OF PnniPortIdMapEntry
    MAX-ACCESS not-accessible
    STATUS current
    DESCRIPTION
	" Port ID map table for converting Port ID to port/vpi and ifix"
    ::= { pnniIfMapGroup 2 }

pnniPortIdMapEntry OBJECT-TYPE
    SYNTAX PnniPortIdMapEntry
    MAX-ACCESS not-accessible
    STATUS current
    DESCRIPTION
        ""
    INDEX { pnniPortIdMapPortId }
    ::= { pnniPortIdMapTable 1 }

PnniPortIdMapEntry ::= SEQUENCE {
    pnniPortIdMapPortId   PnniPortId,
    pnniPortIdMapPort     Integer32,
    pnniPortIdMapVpi      Integer32,
    pnniPortIdMapIfIndex  InterfaceIndex
}

pnniPortIdMapPortId OBJECT-TYPE
    SYNTAX PnniPortId
    MAX-ACCESS not-accessible
    STATUS current
    DESCRIPTION
        "PNNI Port ID corresponding the interface"
    ::= { pnniPortIdMapEntry 1 }

pnniPortIdMapPort OBJECT-TYPE
    SYNTAX Integer32
    MAX-ACCESS read-only
    STATUS current
    DESCRIPTION
        "Port index on the switch"
    ::= { pnniPortIdMapEntry 2 }

pnniPortIdMapVpi OBJECT-TYPE
    SYNTAX Integer32
    MAX-ACCESS read-only
    STATUS current
    DESCRIPTION
        "VPI index"
    ::= { pnniPortIdMapEntry 3 }

pnniPortIdMapIfIndex OBJECT-TYPE
    SYNTAX InterfaceIndex
    MAX-ACCESS read-only
    STATUS current
    DESCRIPTION
        "Pnni interface index"
    ::= { pnniPortIdMapEntry 4 }


----------------------------------------------------------------------
-- pnniMapNodeExtTable: provides extended info about a mapnode

pnniMapNodeExtTable OBJECT-TYPE
    SYNTAX SEQUENCE OF PnniMapNodeExtEntry
    MAX-ACCESS not-accessible
    STATUS current
    DESCRIPTION
	"A table containing extended map node information for 
	 PNNI nodes running on FORE switches"
    ::= { pnniGroup 16 }

pnniMapNodeExtEntry OBJECT-TYPE
    SYNTAX PnniMapNodeExtEntry
    MAX-ACCESS not-accessible
    STATUS current
    DESCRIPTION
	"An entry in the table, containing the extended map node
	 information for a particular node."
    INDEX { pnniNodeIndex, pnniMapNodeExtRemoteNodeId }
    ::= { pnniMapNodeExtTable 1 }

PnniMapNodeExtEntry ::= SEQUENCE {
    pnniMapNodeExtRemoteNodeId     PnniNodeId,
    pnniMapNodeExtSoftwareVersion  Unsigned32,
    pnniMapNodeExtHardwareVersion  Unsigned32,
    pnniMapNodeExtHardwareId       Unsigned32,
    pnniMapNodeExtSwitchName       DisplayString,
    pnniMapNodeExtRemoteNodeIndex  Integer32,
    pnniMapNodeExtForeNodalFlags   Unsigned32
}

pnniMapNodeExtRemoteNodeId OBJECT-TYPE
    SYNTAX PnniNodeId
    MAX-ACCESS not-accessible
    STATUS current
    DESCRIPTION
	"The PNNI node ID of the node being described."
    ::= { pnniMapNodeExtEntry 1 }

pnniMapNodeExtSoftwareVersion OBJECT-TYPE
    SYNTAX Unsigned32
    MAX-ACCESS read-only 
    STATUS current
    DESCRIPTION
	"The version number of the software on the host switch"
    ::= { pnniMapNodeExtEntry 2 }

pnniMapNodeExtHardwareVersion OBJECT-TYPE
    SYNTAX Unsigned32
    MAX-ACCESS read-only
    STATUS current
    DESCRIPTION
	"The version number of the hardware on the host switch"
    ::= { pnniMapNodeExtEntry 3 }

pnniMapNodeExtHardwareId OBJECT-TYPE
    SYNTAX Unsigned32
    MAX-ACCESS read-only
    STATUS current
    DESCRIPTION
   	"A value uniquely identifying the host switch"
    ::= { pnniMapNodeExtEntry 4 }

pnniMapNodeExtSwitchName OBJECT-TYPE
    SYNTAX DisplayString
    MAX-ACCESS read-only
    STATUS current
    DESCRIPTION
 	"The system name of the host switch"
    ::= { pnniMapNodeExtEntry 5 }    

pnniMapNodeExtRemoteNodeIndex OBJECT-TYPE
    SYNTAX Integer32
    MAX-ACCESS read-only
    STATUS current
    DESCRIPTION
	"The node index of the node on the host switch"
    ::= { pnniMapNodeExtEntry 6 }

pnniMapNodeExtForeNodalFlags OBJECT-TYPE
    SYNTAX Unsigned32
    MAX-ACCESS read-only
    STATUS current
    DESCRIPTION
	"A bit vector indicating the status of several flags on
 	 the node"
    ::= { pnniMapNodeExtEntry 7 }

----------------------------------------------------------------------
-- pnniMapNodeIpAddrTable - table containing the IP if address of the map node

InterfaceLabel ::= OCTET STRING (SIZE(16))	

pnniMapNodeIpAddrTable OBJECT-TYPE
    SYNTAX SEQUENCE OF PnniMapNodeIpAddrEntry
    MAX-ACCESS not-accessible
    STATUS current
    DESCRIPTION
	"A table containing the configured IP address of the map
	 nodes.  The key is formed by combining the local node index, the
	remote node id, and the IP address."
    ::= { pnniGroup 17 }

pnniMapNodeIpAddrEntry OBJECT-TYPE
    SYNTAX PnniMapNodeIpAddrEntry
    MAX-ACCESS not-accessible
    STATUS current
    DESCRIPTION
	"An entry in the switch IP address table."
    INDEX { pnniNodeIndex, pnniMapNodeExtRemoteNodeId, pnniMapNodeIpAddr }
    ::= { pnniMapNodeIpAddrTable 1 }

PnniMapNodeIpAddrEntry ::= SEQUENCE {
    pnniMapNodeIpAddr        IpAddress,
    pnniMapNodeIpAddrIfName  InterfaceLabel
}

pnniMapNodeIpAddr OBJECT-TYPE
    SYNTAX IpAddress
    MAX-ACCESS read-only
    STATUS current
    DESCRIPTION
	"The ip address of an interface"
    ::= { pnniMapNodeIpAddrEntry 1 }

pnniMapNodeIpAddrIfName OBJECT-TYPE
    SYNTAX InterfaceLabel
    MAX-ACCESS read-only
    STATUS current
    DESCRIPTION
	"The name of the IP address interface"
    ::= { pnniMapNodeIpAddrEntry 2 }  
    
END
