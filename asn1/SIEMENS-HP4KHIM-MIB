SIEMENS-HP4KHIM-MIB DEFINITIONS ::= BEGIN

IMPORTS
	enterprises,
	MODULE-IDENTITY,
	OBJECT-TYPE,
	NOTIFICATION-TYPE,
	Counter32,
	Integer32,
	IpAddress,
	Unsigned32
		FROM SNMPv2-SMI
	MacAddress,
	DisplayString,
	TEXTUAL-CONVENTION
		FROM SNMPv2-TC
	OBJECT-GROUP,
	NOTIFICATION-GROUP
		FROM SNMPv2-CONF;

siemens OBJECT IDENTIFIER 	::= { enterprises 4329 }

iandcAdmin OBJECT IDENTIFIER 	::= { siemens 2 }

hp4khim MODULE-IDENTITY
	LAST-UPDATED "200611100000Z"
	ORGANIZATION "Siemens"
	CONTACT-INFO
		"David Nemeskey"
	DESCRIPTION
		""
	REVISION "200606070747Z"
	DESCRIPTION
		"Initial version."
	::= { iandcAdmin 51 }


HimPEN ::= TEXTUAL-CONVENTION
	STATUS  current
	DESCRIPTION
		"Octet String for storing PEN numbers. The format is
		The PEN is displayed in the following format: [LTG]-[LTU]-[EBT].
		                LTG: Line/Trunk Group: always 1
		                LTU: Line/Trunk Unit: a number between 1 and 99
		                EBT: a three-digit number."
	SYNTAX OCTET STRING (SIZE (0..9))


HimPabxId ::= TEXTUAL-CONVENTION
	STATUS  current
	DESCRIPTION
		"Textual convention for the Pabx Id."
	SYNTAX Integer32 (1..2147483647)


HimSwitchNumber ::= TEXTUAL-CONVENTION
	STATUS  current
	DESCRIPTION
		"Data type of the switch number."
	SYNTAX OCTET STRING (SIZE (0..17))


HimYesNo ::= TEXTUAL-CONVENTION
	STATUS  current
	DESCRIPTION
		"Boolean data type:
		1. no
		2. yes
		The order is set like this to comply with the definition of data leaves in the hicom MIB that use this convention implicitly."
	SYNTAX INTEGER {
			yes(1),
			no(2),
			other(0) }


DiscoveryStates ::= INTEGER {
			done(1),
			error(2),
			busy(3),
			finok(4),
			finerr(5),
			kill(6) }


DiscoveryModes ::= INTEGER {
			man(1),
			auto(2),
			undef(9) }


HimPhoneNumber ::= TEXTUAL-CONVENTION
	STATUS  current
	DESCRIPTION
		"Convention that represents phone numbers in a HiPath system."
	SYNTAX OCTET STRING (SIZE (0..22))


HimShelfNWType ::= TEXTUAL-CONVENTION
	STATUS  current
	DESCRIPTION
		"Network type of the shelf."
	SYNTAX INTEGER {
			flex(1),
			local(2),
			apnw(3),
			apdl(4),
			other(0) }


-- Corresponds to the HIM Welcome Page

himWelcomePage OBJECT IDENTIFIER 	::= { hp4khim 1 }

himWelPgTable OBJECT-TYPE
	SYNTAX  SEQUENCE OF HimWelPgEntry
	MAX-ACCESS not-accessible
	STATUS  current
	DESCRIPTION ""
	::= { himWelcomePage 1 }


himWelPgEntry OBJECT-TYPE
	SYNTAX  HimWelPgEntry
	MAX-ACCESS not-accessible
	STATUS  current
	DESCRIPTION ""
	INDEX {
		himWelPgPabxId }
	::= { himWelPgTable 1 }


HimWelPgEntry ::= SEQUENCE {

	himWelPgPabxId        HimPabxId,
	himWelPgSysNo         HimSwitchNumber,
	himHP4KVersion        OCTET STRING,
	himSystemRelease      OCTET STRING,
	himRevisionLevel      OCTET STRING,
	himHWArchitecture     OCTET STRING,
	himHWArchitectureType OCTET STRING,
	himOperationMode      OCTET STRING,
	himSWUProc1           OCTET STRING,
	himSWUMemory1         OCTET STRING,
	himSWUProc2           OCTET STRING,
	himSWUMemory2         OCTET STRING }


himWelPgPabxId OBJECT-TYPE
	SYNTAX  HimPabxId
	MAX-ACCESS read-only
	STATUS  current
	DESCRIPTION ""
	::= { himWelPgEntry 1 }


himWelPgSysNo OBJECT-TYPE
	SYNTAX  HimSwitchNumber
	MAX-ACCESS read-only
	STATUS  current
	DESCRIPTION
		"This field contains the system number (max. 17 characters)."
	::= { himWelPgEntry 2 }


himHP4KVersion OBJECT-TYPE
	SYNTAX  OCTET STRING (SIZE (0..5))
	MAX-ACCESS read-only
	STATUS  current
	DESCRIPTION
		"This field contains the Hicom/HiPath version number of the system (max. 4 characters)."
	::= { himWelPgEntry 3 }


himSystemRelease OBJECT-TYPE
	SYNTAX  OCTET STRING (SIZE (0..2))
	MAX-ACCESS read-only
	STATUS  current
	DESCRIPTION
		"This field contains the system release number of the system (max. 2 characters)."
	::= { himWelPgEntry 4 }


himRevisionLevel OBJECT-TYPE
	SYNTAX  OCTET STRING (SIZE (0..2))
	MAX-ACCESS read-only
	STATUS  current
	DESCRIPTION
		"This field contains the revision number of the system software (max. 2 characters)."
	::= { himWelPgEntry 5 }


himHWArchitecture OBJECT-TYPE
	SYNTAX  OCTET STRING (SIZE (0..25))
	MAX-ACCESS read-only
	STATUS  current
	DESCRIPTION
		"This field contains the information on hardware architecture in the format [hw-architecture][system-variant][hw-design]

		[hw-architecture]
		Abbreviation describing hardware architecture. F.i '4300', '350E', etc.

		[system-variant]
		H40: SYSTEM VARIANT 40
		H80: SYSTEM VARIANT 80
		H600: SYSTEM VARIANT 600

		[hw-design]
		ECX: HARDWARE DESIGN EXTENDED COMPACT EXTENDED
		ECDSC: HARDWARE DESIGN EXTENDED COMPACT DSC
		CXE: HARDWARE DESIGN EXTENDED COMPACT CXE"
	::= { himWelPgEntry 6 }


himHWArchitectureType OBJECT-TYPE
	SYNTAX  OCTET STRING (SIZE (0..3))
	MAX-ACCESS read-only
	STATUS  current
	DESCRIPTION
		"This field contains abbreviation describing hardware architecture type (max. 3 characters)."
	::= { himWelPgEntry 7 }


himOperationMode OBJECT-TYPE
	SYNTAX  OCTET STRING (SIZE (0..7))
	MAX-ACCESS read-only
	STATUS  current
	DESCRIPTION
		"This field contains the operating mode of the system.

		Possible Values:
		SIMPLEX: OPERATING MODE SIMPLEX
		DUPLEX: OPERATING MODE DUPLEX REDUNDANCY"
	::= { himWelPgEntry 8 }


himSWUProc1 OBJECT-TYPE
	SYNTAX  OCTET STRING (SIZE (0..8))
	MAX-ACCESS read-only
	STATUS  current
	DESCRIPTION
		"These fields contains the name of the SWU processor board (max. 8 characters).
		SWU = Switching Unit
		Possible values:
		        -  CC-A
		        -  CC-B"
	::= { himWelPgEntry 9 }


himSWUMemory1 OBJECT-TYPE
	SYNTAX  OCTET STRING (SIZE (0..6))
	MAX-ACCESS read-only
	STATUS  current
	DESCRIPTION
		"These fields contain the size of the SWU memory for each processor card.
		SWU = Switching Unit"
	::= { himWelPgEntry 10 }


himSWUProc2 OBJECT-TYPE
	SYNTAX  OCTET STRING (SIZE (0..8))
	MAX-ACCESS read-only
	STATUS  current
	DESCRIPTION
		"These fields contains the name of the SWU processor board (max. 8 characters).
		SWU = Switching Unit
		Possible values:
		        -  CC-A
		        -  CC-B"
	::= { himWelPgEntry 11 }


himSWUMemory2 OBJECT-TYPE
	SYNTAX  OCTET STRING (SIZE (0..6))
	MAX-ACCESS read-only
	STATUS  current
	DESCRIPTION
		"These fields contain the size of the SWU memory for each processor card.
		SWU = Switching Unit"
	::= { himWelPgEntry 12 }


himSwitchData OBJECT IDENTIFIER 	::= { hp4khim 2 }

himTechInfoTable OBJECT-TYPE
	SYNTAX  SEQUENCE OF HimTechInfoEntry
	MAX-ACCESS not-accessible
	STATUS  current
	DESCRIPTION ""
	::= { himSwitchData 1 }


himTechInfoEntry OBJECT-TYPE
	SYNTAX  HimTechInfoEntry
	MAX-ACCESS not-accessible
	STATUS  current
	DESCRIPTION ""
	INDEX {
		himTechInfoPabxId,
		himTechInfoInfoNo }
	::= { himTechInfoTable 1 }


HimTechInfoEntry ::= SEQUENCE {

	himTechInfoPabxId        HimPabxId,
	himTechInfoInfoNo        OCTET STRING,
	himTechInfoDate          OCTET STRING,
	himTechInfoTechnicalData OCTET STRING,
	himTechInfoNumber        OCTET STRING,
	himTechInfoExtraText     OCTET STRING }


himTechInfoPabxId OBJECT-TYPE
	SYNTAX  HimPabxId
	MAX-ACCESS read-only
	STATUS  current
	DESCRIPTION ""
	::= { himTechInfoEntry 1 }


himTechInfoInfoNo OBJECT-TYPE
	SYNTAX  OCTET STRING (SIZE (0..7))
	MAX-ACCESS read-only
	STATUS  current
	DESCRIPTION
		"This field contains the number of the subsystem. This number can be assigned as required when configuring the subsystem."
	::= { himTechInfoEntry 2 }


himTechInfoDate OBJECT-TYPE
	SYNTAX  OCTET STRING (SIZE (0..10))
	MAX-ACCESS read-only
	STATUS  current
	DESCRIPTION
		"This field contains the date on which the subsystem was configured."
	::= { himTechInfoEntry 3 }


himTechInfoTechnicalData OBJECT-TYPE
	SYNTAX  OCTET STRING (SIZE (0..40))
	MAX-ACCESS read-only
	STATUS  current
	DESCRIPTION
		"This field contains the technical data of the subsystem."
	::= { himTechInfoEntry 4 }


himTechInfoNumber OBJECT-TYPE
	SYNTAX  OCTET STRING (SIZE (0..5))
	MAX-ACCESS read-only
	STATUS  current
	DESCRIPTION
		"This field contains the number of each subsystem configured."
	::= { himTechInfoEntry 5 }


himTechInfoExtraText OBJECT-TYPE
	SYNTAX  OCTET STRING (SIZE (0..10))
	MAX-ACCESS read-only
	STATUS  current
	DESCRIPTION
		"This field contains additional text."
	::= { himTechInfoEntry 6 }


himNotepadDataTable OBJECT-TYPE
	SYNTAX  SEQUENCE OF HimNotepadDataEntry
	MAX-ACCESS not-accessible
	STATUS  current
	DESCRIPTION
		"This node contains the system data entered in a notepad. The table for notepad entries holds a maximum of 30 data records."
	::= { himSwitchData 2 }


himNotepadDataEntry OBJECT-TYPE
	SYNTAX  HimNotepadDataEntry
	MAX-ACCESS not-accessible
	STATUS  current
	DESCRIPTION ""
	INDEX {
		himNotepadDataPabxId,
		himNotepadDataInfoNo }
	::= { himNotepadDataTable 1 }


HimNotepadDataEntry ::= SEQUENCE {

	himNotepadDataPabxId HimPabxId,
	himNotepadDataInfoNo Unsigned32,
	himNotepadDataDate   OCTET STRING,
	himNotepadDataText   OCTET STRING }


himNotepadDataPabxId OBJECT-TYPE
	SYNTAX  HimPabxId
	MAX-ACCESS read-only
	STATUS  current
	DESCRIPTION ""
	::= { himNotepadDataEntry 1 }


himNotepadDataInfoNo OBJECT-TYPE
	SYNTAX  Unsigned32
	MAX-ACCESS read-only
	STATUS  current
	DESCRIPTION
		"This field contains the number of the subsystem. This number is assigned permanently when configuring the subsystem."
	::= { himNotepadDataEntry 2 }


himNotepadDataDate OBJECT-TYPE
	SYNTAX  OCTET STRING (SIZE (0..10))
	MAX-ACCESS read-only
	STATUS  current
	DESCRIPTION
		"This field contains the date on which the subsystem was configured."
	::= { himNotepadDataEntry 3 }


himNotepadDataText OBJECT-TYPE
	SYNTAX  OCTET STRING (SIZE (0..77))
	MAX-ACCESS read-only
	STATUS  current
	DESCRIPTION
		"This field contains the technical data of the subsystem."
	::= { himNotepadDataEntry 4 }


himProjPlanInfoTable OBJECT-TYPE
	SYNTAX  SEQUENCE OF HimProjPlanInfoEntry
	MAX-ACCESS not-accessible
	STATUS  current
	DESCRIPTION
		"This screen makes it possible to generate a file with project planning data."
	::= { himSwitchData 3 }


himProjPlanInfoEntry OBJECT-TYPE
	SYNTAX  HimProjPlanInfoEntry
	MAX-ACCESS not-accessible
	STATUS  current
	DESCRIPTION ""
	INDEX {
		himProjPlanPabxId }
	::= { himProjPlanInfoTable 1 }


HimProjPlanInfoEntry ::= SEQUENCE {

	himProjPlanPabxId           HimPabxId,
	himProjPlanInfoFile         OCTET STRING,
	himProjPlanInfoCreationDate OCTET STRING,
	himProjPlanInfoCreationTime OCTET STRING }


himProjPlanPabxId OBJECT-TYPE
	SYNTAX  HimPabxId
	MAX-ACCESS read-only
	STATUS  current
	DESCRIPTION ""
	::= { himProjPlanInfoEntry 1 }


himProjPlanInfoFile OBJECT-TYPE
	SYNTAX  OCTET STRING (SIZE (0..12))
	MAX-ACCESS read-only
	STATUS  current
	DESCRIPTION
		"This field contains the name of the project planning file."
	DEFVAL { "ProjPlan.txt" }
	::= { himProjPlanInfoEntry 2 }


himProjPlanInfoCreationDate OBJECT-TYPE
	SYNTAX  OCTET STRING (SIZE (0..10))
	MAX-ACCESS read-only
	STATUS  current
	DESCRIPTION
		"This field contains the date on which the project planning file was generated."
	::= { himProjPlanInfoEntry 3 }


himProjPlanInfoCreationTime OBJECT-TYPE
	SYNTAX  OCTET STRING (SIZE (0..8))
	MAX-ACCESS read-only
	STATUS  current
	DESCRIPTION
		"This field contains the time at which the project planning file was generated."
	::= { himProjPlanInfoEntry 4 }


himSpecSwitchData OBJECT IDENTIFIER 	::= { hp4khim 3 }

himSpecShelfDataTable OBJECT-TYPE
	SYNTAX  SEQUENCE OF HimSpecShelfDataEntry
	MAX-ACCESS not-accessible
	STATUS  current
	DESCRIPTION
		"All subscriber and trunk-related lines are grouped within LTU (Line/Trunk Unit) frames. Each frame has several slots for modules. The frame is connected to the system via the LTUC control board.
		This table contains the frame configuration."
	::= { himSpecSwitchData 1 }


himSpecShelfDataEntry OBJECT-TYPE
	SYNTAX  HimSpecShelfDataEntry
	MAX-ACCESS not-accessible
	STATUS  current
	DESCRIPTION ""
	INDEX {
		himSpecShelfDataPabxId,
		himSpecShelfDataAddress }
	::= { himSpecShelfDataTable 1 }


HimSpecShelfDataEntry ::= SEQUENCE {

	himSpecShelfDataPabxId         HimPabxId,
	himSpecShelfDataAddress        OCTET STRING,
	himSpecShelfDataFrameType      OCTET STRING,
	himSpecShelfDataLTU            INTEGER,
	himSpecShelfDataNetworkType    HimShelfNWType,
	himSpecShelfDataNetworkAddress IpAddress,
	himSpecShelfDataRemote         OCTET STRING,
	himSpecShelfDataLocation       OCTET STRING,
	himSpecShelfDataLTUC           OCTET STRING }


himSpecShelfDataPabxId OBJECT-TYPE
	SYNTAX  HimPabxId
	MAX-ACCESS read-only
	STATUS  current
	DESCRIPTION ""
	::= { himSpecShelfDataEntry 1 }


himSpecShelfDataAddress OBJECT-TYPE
	SYNTAX  OCTET STRING (SIZE (0..9))
	MAX-ACCESS read-only
	STATUS  current
	DESCRIPTION
		"This field contains the address of the shelf in format LTG.LTU.
		LTG:Line/Trunk Group
		LTU: Line/Trunk Unit"
	::= { himSpecShelfDataEntry 2 }


himSpecShelfDataFrameType OBJECT-TYPE
	SYNTAX  OCTET STRING (SIZE (0..8))
	MAX-ACCESS read-only
	STATUS  current
	DESCRIPTION
		"This field contains the part number of the frame."
	::= { himSpecShelfDataEntry 3 }


himSpecShelfDataLTU OBJECT-TYPE
	SYNTAX  INTEGER {
			preatl(1),
			cc40f(2),
			cc80w(3),
			cc80f(4),
			l80xf(5),
			l80xw(6),
			ltuw(7),
			inch19(8),
			ap37009(9),
			ap370013(10),
			ext-comp-x(11),
			other(0) }
	MAX-ACCESS read-only
	STATUS  current
	DESCRIPTION
		"This field contains type of LTU (Line/Trunk Unit) frame.
		Possible values for LTU frame type:
		        -  PREATL - frametype for Preatlantic Hicom Types
		        -  CC40F - basisframe for 40CMX
		        -  CC80W - basisframe for 80CMX
		        -  CC80F - basisframe for 80CMX/DSC and CXE
		        -  L80XF - for 80CMX/DSC, CXE, 600ECS and AP shelves
		        -  L80XW - extension frame for 80CMX/DSC
		        -  LTUW - frame for 600ECX and AP shelves
		Possible values for AP shelf type:
		        -  L80XF - for 80CMX/DSC, CXE, 600ECS and AP shelves
		        -  LTUW - frame for 600ECX and AP shelves
		        -  INCH19 - 19 inch frame for AP shelves"
	::= { himSpecShelfDataEntry 4 }


himSpecShelfDataNetworkType OBJECT-TYPE
	SYNTAX  HimShelfNWType
	MAX-ACCESS read-only
	STATUS  current
	DESCRIPTION
		"This field contains connection type of LTU frame / AP shelf."
	::= { himSpecShelfDataEntry 5 }


himSpecShelfDataNetworkAddress OBJECT-TYPE
	SYNTAX  IpAddress
	MAX-ACCESS read-only
	STATUS  current
	DESCRIPTION
		"This field contains network IP address."
	::= { himSpecShelfDataEntry 6 }


himSpecShelfDataRemote OBJECT-TYPE
	SYNTAX  OCTET STRING (SIZE (0..3))
	MAX-ACCESS read-only
	STATUS  current
	DESCRIPTION
		"This field shows if frame is remote.
		Possible values:
		        -  yes - frame is remote
		        -  no - frame is not remote"
	::= { himSpecShelfDataEntry 7 }


himSpecShelfDataLocation OBJECT-TYPE
	SYNTAX  OCTET STRING (SIZE (0..48))
	MAX-ACCESS read-only
	STATUS  current
	DESCRIPTION
		"This field contains postal address (city, street, building, ..) , where a FLEX LTU or an AP shelf is located."
	::= { himSpecShelfDataEntry 8 }


himSpecShelfDataLTUC OBJECT-TYPE
	SYNTAX  OCTET STRING (SIZE (0..14))
	MAX-ACCESS read-only
	STATUS  current
	DESCRIPTION
		"This field contains part number adding LTUC module.
		LTUC: Line/Trunk Unit Control."
	::= { himSpecShelfDataEntry 9 }


himSWUBoardTable OBJECT-TYPE
	SYNTAX  SEQUENCE OF HimSWUBoardEntry
	MAX-ACCESS not-accessible
	STATUS  current
	DESCRIPTION
		"This table contains the configuration of the peripheral boards.

		Periphery Assemblies
		Peripheral and ring generator assemblies as well as SIU are configured in the LTU. The board is entered in the SWU database.
		   LTU = Line/Trunk Unit
		   SIU = Signaling Interface Unit
		   SWU = Switching Unit"
	::= { himSpecSwitchData 2 }


himSWUBoardEntry OBJECT-TYPE
	SYNTAX  HimSWUBoardEntry
	MAX-ACCESS not-accessible
	STATUS  current
	DESCRIPTION ""
	INDEX {
		himSWUBoardPabxId,
		himSWUBoardPEN }
	::= { himSWUBoardTable 1 }


HimSWUBoardEntry ::= SEQUENCE {

	himSWUBoardPabxId     HimPabxId,
	himSWUBoardPEN        HimPEN,
	himSWUBoardOverlayLTU OCTET STRING,
	himSWUBoardType       OCTET STRING,
	himSWUBoardNominal    OCTET STRING,
	himSWUBoardActual     OCTET STRING,
	hhimSWUBoardFirmware  OCTET STRING,
	himSWUBoardRev        OCTET STRING,
	himSWUBoardFunctId    OCTET STRING,
	himSWUBoardMode       OCTET STRING,
	himSWUBoardLWNo       OCTET STRING,
	himSWUBoardLWInterVer OCTET STRING,
	himSWUBoardLWName     OCTET STRING,
	himSWUBoardLWDate     OCTET STRING }


himSWUBoardPabxId OBJECT-TYPE
	SYNTAX  HimPabxId
	MAX-ACCESS read-only
	STATUS  current
	DESCRIPTION ""
	::= { himSWUBoardEntry 1 }


himSWUBoardPEN OBJECT-TYPE
	SYNTAX  HimPEN
	MAX-ACCESS read-only
	STATUS  current
	DESCRIPTION
		"This field contains the name of the board PEN.
		PEN: Port Equipment Number
		The PEN is displayed in the following format: [LTG]-[LTU]-[EBT].
		LTG: Line/Trunk Group
		LTU: Line/Trunk Unit
		EBT: Slot"
	::= { himSWUBoardEntry 2 }


himSWUBoardOverlayLTU OBJECT-TYPE
	SYNTAX  OCTET STRING (SIZE (0..2))
	MAX-ACCESS read-only
	STATUS  current
	DESCRIPTION
		"This field contains the name of the overlay LTU (Line/Trunk Unit)."
	::= { himSWUBoardEntry 3 }


himSWUBoardType OBJECT-TYPE
	SYNTAX  OCTET STRING (SIZE (0..8))
	MAX-ACCESS read-only
	STATUS  current
	DESCRIPTION
		"This field contains the name of the configured board."
	::= { himSWUBoardEntry 4 }


himSWUBoardNominal OBJECT-TYPE
	SYNTAX  OCTET STRING (SIZE (0..10))
	MAX-ACCESS read-only
	STATUS  current
	DESCRIPTION
		"This field contains the name of the nominal board."
	::= { himSWUBoardEntry 5 }


himSWUBoardActual OBJECT-TYPE
	SYNTAX  OCTET STRING (SIZE (0..10))
	MAX-ACCESS read-only
	STATUS  current
	DESCRIPTION
		"This field contains part number of the board that is plugged in."
	::= { himSWUBoardEntry 6 }


hhimSWUBoardFirmware OBJECT-TYPE
	SYNTAX  OCTET STRING (SIZE (0..6))
	MAX-ACCESS read-only
	STATUS  current
	DESCRIPTION
		"This field contains the name of the firmware."
	::= { himSWUBoardEntry 7 }


himSWUBoardRev OBJECT-TYPE
	SYNTAX  OCTET STRING (SIZE (0..2))
	MAX-ACCESS read-only
	STATUS  current
	DESCRIPTION
		"This field contains the revision of the board."
	::= { himSWUBoardEntry 8 }


himSWUBoardFunctId OBJECT-TYPE
	SYNTAX  OCTET STRING (SIZE (0..3))
	MAX-ACCESS read-only
	STATUS  current
	DESCRIPTION
		"Function identification number for boards with more than one functions (e.g. SIUX, STMA, SLMO24)."
	::= { himSWUBoardEntry 9 }


himSWUBoardMode OBJECT-TYPE
	SYNTAX  OCTET STRING (SIZE (0..8))
	MAX-ACCESS read-only
	STATUS  current
	DESCRIPTION
		"This field contains the mode of the board. The mode is only displayed for the RG/ACGEN board."
	::= { himSWUBoardEntry 10 }


himSWUBoardLWNo OBJECT-TYPE
	SYNTAX  OCTET STRING (SIZE (0..1))
	MAX-ACCESS read-only
	STATUS  current
	DESCRIPTION
		"This field contains the number of the loadware."
	::= { himSWUBoardEntry 11 }


himSWUBoardLWInterVer OBJECT-TYPE
	SYNTAX  OCTET STRING (SIZE (0..2))
	MAX-ACCESS read-only
	STATUS  current
	DESCRIPTION
		"This field contains the interface version of the board."
	::= { himSWUBoardEntry 12 }


himSWUBoardLWName OBJECT-TYPE
	SYNTAX  OCTET STRING (SIZE (0..32))
	MAX-ACCESS read-only
	STATUS  current
	DESCRIPTION
		"This field contains the file name of the loadware file or of the initialization file."
	::= { himSWUBoardEntry 13 }


himSWUBoardLWDate OBJECT-TYPE
	SYNTAX  OCTET STRING (SIZE (0..20))
	MAX-ACCESS read-only
	STATUS  current
	DESCRIPTION
		"This field contains the date on which the loadware or the initialization file was generated."
	::= { himSWUBoardEntry 14 }


himSWUPeriphery OBJECT IDENTIFIER 	::= { hp4khim 4 }

himPSIOAssTable OBJECT-TYPE
	SYNTAX  SEQUENCE OF HimPSIOAssEntry
	MAX-ACCESS not-accessible
	STATUS  current
	DESCRIPTION
		"This table contains the PSIO assemblies data."
	::= { himSWUPeriphery 1 }


himPSIOAssEntry OBJECT-TYPE
	SYNTAX  HimPSIOAssEntry
	MAX-ACCESS not-accessible
	STATUS  current
	DESCRIPTION ""
	INDEX {
		himPSIOAssPabxId,
		himPSIOAssPEN }
	::= { himPSIOAssTable 1 }


HimPSIOAssEntry ::= SEQUENCE {

	himPSIOAssPabxId   HimPabxId,
	himPSIOAssPEN      HimPEN,
	himPSIOAssAssembly OCTET STRING,
	himPSIOAssActual   OCTET STRING,
	himPSIOAssFirmware OCTET STRING }


himPSIOAssPabxId OBJECT-TYPE
	SYNTAX  HimPabxId
	MAX-ACCESS read-only
	STATUS  current
	DESCRIPTION ""
	::= { himPSIOAssEntry 1 }


himPSIOAssAssembly OBJECT-TYPE
	SYNTAX  OCTET STRING (SIZE (0..8))
	MAX-ACCESS read-only
	STATUS  current
	DESCRIPTION
		"This field contains the name of the PSIO board.
		PSIO: Peripheral Serial Input Output"
	::= { himPSIOAssEntry 3 }


himPSIOAssPEN OBJECT-TYPE
	SYNTAX  HimPEN
	MAX-ACCESS read-only
	STATUS  current
	DESCRIPTION
		"This field contains the name of the board PEN.
		PEN: Port Equipment Number
		The PEN is displayed in the following format: [LTG]-[LTU]-[EBT].
		LTG: Line/Trunk Group
		LTU: Line/Trunk Unit
		EBT: Slot"
	::= { himPSIOAssEntry 2 }


himPSIOAssActual OBJECT-TYPE
	SYNTAX  OCTET STRING (SIZE (0..10))
	MAX-ACCESS read-only
	STATUS  current
	DESCRIPTION
		"This field contains the part number of the PSIO board."
	::= { himPSIOAssEntry 4 }


himPSIOAssFirmware OBJECT-TYPE
	SYNTAX  OCTET STRING (SIZE (0..6))
	MAX-ACCESS read-only
	STATUS  current
	DESCRIPTION
		"This field contains the firmware name of the PSIO board."
	::= { himPSIOAssEntry 5 }


himSerialLineTable OBJECT-TYPE
	SYNTAX  SEQUENCE OF HimSerialLineEntry
	MAX-ACCESS not-accessible
	STATUS  current
	DESCRIPTION
		"This table contains the serial interfaces data."
	::= { himSWUPeriphery 2 }


himSerialLineEntry OBJECT-TYPE
	SYNTAX  HimSerialLineEntry
	MAX-ACCESS not-accessible
	STATUS  current
	DESCRIPTION ""
	INDEX {
		himSerialLinePabxId,
		himSerialLineNumber }
	::= { himSerialLineTable 1 }


HimSerialLineEntry ::= SEQUENCE {

	himSerialLinePabxId     HimPabxId,
	himSerialLineNumber     Unsigned32,
	himSerialLineBoardType  OCTET STRING,
	himSerialLineSpeed      Unsigned32,
	himSerialLineLogDevName OCTET STRING,
	himSerialLineDevType    OCTET STRING,
	himSerialLineType       INTEGER }


himSerialLinePabxId OBJECT-TYPE
	SYNTAX  HimPabxId
	MAX-ACCESS read-only
	STATUS  current
	DESCRIPTION ""
	::= { himSerialLineEntry 1 }


himSerialLineBoardType OBJECT-TYPE
	SYNTAX  OCTET STRING (SIZE (0..8))
	MAX-ACCESS read-only
	STATUS  current
	DESCRIPTION
		"This field contains abbreviation name of the board type."
	::= { himSerialLineEntry 3 }


himSerialLineNumber OBJECT-TYPE
	SYNTAX  Unsigned32 (8..63)
	MAX-ACCESS read-only
	STATUS  current
	DESCRIPTION
		"This field contains the physical line number of the interface.
		Possible Values: numeric, 8-63"
	::= { himSerialLineEntry 2 }


himSerialLineSpeed OBJECT-TYPE
	SYNTAX  Unsigned32
	MAX-ACCESS read-only
	STATUS  current
	DESCRIPTION
		"This field contains standardized transmission speed (baud rate).
		Possible Values: 50, 100, 200, 300, 600, 1200, 2400, 4800, 9600, 19200."
	::= { himSerialLineEntry 4 }


himSerialLineLogDevName OBJECT-TYPE
	SYNTAX  OCTET STRING (SIZE (0..8))
	MAX-ACCESS read-only
	STATUS  current
	DESCRIPTION
		"This field contains the logical device name of the line.
		Possible Values:

		Value - Description
		CON1  - LOGICAL DEVICE CONNECTION,TERMINAL 1
		CON2  - LOGICAL DEVICE CONNECTION,TERMINAL 2
		CON3  - LOGICAL DEVICE CONNECTION,TERMINAL 3
		CON4  - LOGICAL DEVICE CONNECTION,TERMINAL 4
		CON5  - LOGICAL DEVICE CONNECTION 5
		CON6  - LOGICAL DEVICE CONNECTION 6
		PR1   - LOGICAL DEVICE:LINE PRINTER 1
		PR2   - LOGICAL DEVICE:LINE PRINTER 2
		PR3   - LOGICAL DEVICE:LINE PRINTER 3
		PR4   - LOGICAL DEVICE:LINE PRINTER 4"
	::= { himSerialLineEntry 5 }


himSerialLineDevType OBJECT-TYPE
	SYNTAX  OCTET STRING (SIZE (0..18))
	MAX-ACCESS read-only
	STATUS  current
	DESCRIPTION
		"This field contains the device type of the line.
		Possible Values:

		Value   - Description
		PT88    - DEVICE TYPE
		QUOSC   - QUME-ONLY-SCREEN
		QUOPT   - QUME-ONLY-PT88
		QUSCAPT - QUME-SCREEN-AND-PT88
		PCOSC   - PC-D-ONLY-SCREEN
		PCOPT   - PC-D-ONLY-PT88
		PCSCAPT - PC-D-SCREEN-AND-PT88
		ASC     - ASCII-CODE
		EBC     - EBCDIC CODE
		RSV1    - RESERVED DEVICE TYPE 1
		RSV2    - RESERVED DEVICE TYPE 2
		RSV3    - RESERVED DEVICE TYPE 3"
	::= { himSerialLineEntry 6 }


himSerialLineType OBJECT-TYPE
	SYNTAX  INTEGER {
			asy(1),
			v24(2),
			other(0) }
	MAX-ACCESS read-only
	STATUS  current
	DESCRIPTION
		"This field contains the line type (operation of synchronous lines (terminals) connected via V24 modems).
		Possible values:
		 -  ASY: asynchronous line type
		 -  V24: ccitt rec v24"
	::= { himSerialLineEntry 7 }


himSCSIDevTable OBJECT-TYPE
	SYNTAX  SEQUENCE OF HimSCSIDevEntry
	MAX-ACCESS not-accessible
	STATUS  current
	DESCRIPTION
		"This table contains the data for the SCSI devices connected."
	::= { himSWUPeriphery 3 }


himSCSIDevEntry OBJECT-TYPE
	SYNTAX  HimSCSIDevEntry
	MAX-ACCESS not-accessible
	STATUS  current
	DESCRIPTION ""
	INDEX {
		himSCSIDevPabxId,
		himSCSIDevId }
	::= { himSCSIDevTable 1 }


HimSCSIDevEntry ::= SEQUENCE {

	himSCSIDevPabxId    HimPabxId,
	himSCSIDevId        Unsigned32,
	himSCSIDevType      OCTET STRING,
	himSCSIDevName      OCTET STRING,
	himSCSIDevFirmware  OCTET STRING,
	himSCSIDevLoadDrive OCTET STRING }


himSCSIDevPabxId OBJECT-TYPE
	SYNTAX  HimPabxId
	MAX-ACCESS read-only
	STATUS  current
	DESCRIPTION ""
	::= { himSCSIDevEntry 1 }


himSCSIDevId OBJECT-TYPE
	SYNTAX  Unsigned32 (0..7)
	MAX-ACCESS read-only
	STATUS  current
	DESCRIPTION
		"This field contains the type of SCSI device."
	::= { himSCSIDevEntry 2 }


himSCSIDevType OBJECT-TYPE
	SYNTAX  OCTET STRING (SIZE (0..13))
	MAX-ACCESS read-only
	STATUS  current
	DESCRIPTION
		"This field contains the SCSI ID of the device."
	::= { himSCSIDevEntry 3 }


himSCSIDevName OBJECT-TYPE
	SYNTAX  OCTET STRING (SIZE (0..25))
	MAX-ACCESS read-only
	STATUS  current
	DESCRIPTION
		"This field contains the name of the SCSI device in format: [vendor] [product number]."
	::= { himSCSIDevEntry 4 }


himSCSIDevFirmware OBJECT-TYPE
	SYNTAX  OCTET STRING (SIZE (0..4))
	MAX-ACCESS read-only
	STATUS  current
	DESCRIPTION
		"This field contains the firmware name of the SCSI device."
	::= { himSCSIDevEntry 5 }


himSCSIDevLoadDrive OBJECT-TYPE
	SYNTAX  OCTET STRING (SIZE (0..3))
	MAX-ACCESS read-only
	STATUS  current
	DESCRIPTION
		"This field displays (if activity is in progress) the device from which the operating system and the database are started."
	::= { himSCSIDevEntry 6 }


himCentralSwitchData OBJECT IDENTIFIER 	::= { hp4khim 5 }

himCabinetTable OBJECT-TYPE
	SYNTAX  SEQUENCE OF HimCabinetEntry
	MAX-ACCESS not-accessible
	STATUS  current
	DESCRIPTION
		"This table contains the data for configuring the cabinets and frames in a system. They reflect the physical structure of the system."
	::= { himCentralSwitchData 1 }


himCabinetEntry OBJECT-TYPE
	SYNTAX  HimCabinetEntry
	MAX-ACCESS not-accessible
	STATUS  current
	DESCRIPTION ""
	INDEX {
		himCabPabxId,
		himCabAddr }
	::= { himCabinetTable 1 }


HimCabinetEntry ::= SEQUENCE {

	himCabPabxId   HimPabxId,
	himCabAddr     OCTET STRING,
	himCabPhysAddr OCTET STRING,
	himCabCabinet  OCTET STRING,
	himCabPartNo   OCTET STRING,
	himCabShelfNo  Unsigned32,
	himCabFrame    OCTET STRING,
	himCabPid1     OCTET STRING,
	himCabPid2     OCTET STRING,
	himCabPid3     OCTET STRING,
	himCabLTUNo    OCTET STRING }


himCabPabxId OBJECT-TYPE
	SYNTAX  HimPabxId
	MAX-ACCESS read-only
	STATUS  current
	DESCRIPTION ""
	::= { himCabinetEntry 1 }


himCabAddr OBJECT-TYPE
	SYNTAX  OCTET STRING (SIZE (0..4))
	MAX-ACCESS read-only
	STATUS  current
	DESCRIPTION
		"This field contains the cabinet address.
		Structure of cabinet address:
		P 1 01
		| |  |__Number of cabinet in cabinet row
		| |_____Units, position of cabinet row
		|_______Tens (P=0, Q=1), position of the cabinet"
	::= { himCabinetEntry 2 }


himCabPhysAddr OBJECT-TYPE
	SYNTAX  OCTET STRING (SIZE (0..6))
	MAX-ACCESS read-only
	STATUS  current
	DESCRIPTION ""
	::= { himCabinetEntry 3 }


himCabCabinet OBJECT-TYPE
	SYNTAX  OCTET STRING (SIZE (0..8))
	MAX-ACCESS read-only
	STATUS  current
	DESCRIPTION
		"This field contains the name of the cabinet."
	::= { himCabinetEntry 4 }


himCabPartNo OBJECT-TYPE
	SYNTAX  OCTET STRING (SIZE (0..14))
	MAX-ACCESS read-only
	STATUS  current
	DESCRIPTION
		"This field contains the part number of the cabinet."
	::= { himCabinetEntry 5 }


himCabShelfNo OBJECT-TYPE
	SYNTAX  Unsigned32 (1..14)
	MAX-ACCESS read-only
	STATUS  current
	DESCRIPTION
		"This field contains the number of the shelf."
	::= { himCabinetEntry 6 }


himCabFrame OBJECT-TYPE
	SYNTAX  OCTET STRING (SIZE (0..8))
	MAX-ACCESS read-only
	STATUS  current
	DESCRIPTION
		"This field contains the name of the frame."
	::= { himCabinetEntry 7 }


himCabPid1 OBJECT-TYPE
	SYNTAX  OCTET STRING (SIZE (0..5))
	MAX-ACCESS read-only
	STATUS  current
	DESCRIPTION
		"This field contains the processor ID 1."
	::= { himCabinetEntry 8 }


himCabPid2 OBJECT-TYPE
	SYNTAX  OCTET STRING (SIZE (0..5))
	MAX-ACCESS read-only
	STATUS  current
	DESCRIPTION
		"This field contains the processor ID 2."
	::= { himCabinetEntry 9 }


himCabPid3 OBJECT-TYPE
	SYNTAX  OCTET STRING (SIZE (0..5))
	MAX-ACCESS read-only
	STATUS  current
	DESCRIPTION
		"This field contains the processor ID 2."
	::= { himCabinetEntry 10 }


himCabLTUNo OBJECT-TYPE
	SYNTAX  OCTET STRING (SIZE (0..2))
	MAX-ACCESS read-only
	STATUS  current
	DESCRIPTION
		"This field contains the number of the LTU (Line/Trunk Unit).
		The LTU range is divided in two parts: HHS (HICOM Host System) and AP (Access Point). The available values of the ranges are: HHS 1-15 and AP 17-99. The LTU 16 is forbidden. There are existing shelfes which are allowed only in HHS and others which are allowed only in the AP range."
	::= { himCabinetEntry 11 }


himMemScalingTable OBJECT-TYPE
	SYNTAX  SEQUENCE OF HimMemScalingEntry
	MAX-ACCESS not-accessible
	STATUS  current
	DESCRIPTION
		"This screen contains the memory parameters for each of the devices or features specified.
		The values are only displayed in Configuration Management. See also DIMSU parameter list."
	::= { himCentralSwitchData 2 }


himMemScalingEntry OBJECT-TYPE
	SYNTAX  HimMemScalingEntry
	MAX-ACCESS not-accessible
	STATUS  current
	DESCRIPTION ""
	INDEX {
		himMemScalingPabxId,
		himMemScalingUnit }
	::= { himMemScalingTable 1 }


HimMemScalingEntry ::= SEQUENCE {

	himMemScalingPabxId    HimPabxId,
	himMemScalingUnit      OCTET STRING,
	himMemScalingUsed      Integer32,
	himMemScalingMaxUsed   Integer32,
	himMemScalingAllocated Integer32,
	himMemScalingStandard  Integer32,
	himMemScalingSysMax    Integer32 }


himMemScalingPabxId OBJECT-TYPE
	SYNTAX  HimPabxId
	MAX-ACCESS read-only
	STATUS  current
	DESCRIPTION ""
	::= { himMemScalingEntry 1 }


himMemScalingUnit OBJECT-TYPE
	SYNTAX  OCTET STRING (SIZE (0..3))
	MAX-ACCESS read-only
	STATUS  current
	DESCRIPTION
		"This field contains the parameter name (AMO DIMSU)."
	::= { himMemScalingEntry 2 }


himMemScalingUsed OBJECT-TYPE
	SYNTAX  Integer32
	MAX-ACCESS read-only
	STATUS  current
	DESCRIPTION
		"This value specifies the number of memory elements already used up. The comparison with the value in the Maximum field indicates how much of the allocated memory is still available for configuring devices or features."
	::= { himMemScalingEntry 3 }


himMemScalingMaxUsed OBJECT-TYPE
	SYNTAX  Integer32
	MAX-ACCESS read-only
	STATUS  current
	DESCRIPTION
		"This field contains the number of memory elements allocated."
	::= { himMemScalingEntry 4 }


himMemScalingAllocated OBJECT-TYPE
	SYNTAX  Integer32
	MAX-ACCESS read-only
	STATUS  current
	DESCRIPTION
		"This field displays the maximum number of memory elements that once have been used up during the lifetime of the switch ('high water mark'). It gives an indication how much memory was necessary at one time, so it is advised to not reduce the Maximum value below this value."
	::= { himMemScalingEntry 5 }


himMemScalingStandard OBJECT-TYPE
	SYNTAX  Integer32
	MAX-ACCESS read-only
	STATUS  current
	DESCRIPTION
		"Standard is the advised value to be set in the Maximum field, if you don't have special needs to set it to a specific value. If you set all devices and features to the standard values it is guaranteed that you don't run out of DIMSU memory."
	::= { himMemScalingEntry 6 }


himMemScalingSysMax OBJECT-TYPE
	SYNTAX  Integer32
	MAX-ACCESS read-only
	STATUS  current
	DESCRIPTION
		"This field contains the maximum number of possible memory elements."
	::= { himMemScalingEntry 7 }


himGeneralSwitchData OBJECT IDENTIFIER 	::= { hp4khim 6 }

himDBConfSys OBJECT IDENTIFIER 	::= { himGeneralSwitchData 1 }

himDBConfSysTable OBJECT-TYPE
	SYNTAX  SEQUENCE OF HimDBConfSysEntry
	MAX-ACCESS not-accessible
	STATUS  current
	DESCRIPTION ""
	::= { himDBConfSys 1 }


himDBConfSysEntry OBJECT-TYPE
	SYNTAX  HimDBConfSysEntry
	MAX-ACCESS not-accessible
	STATUS  current
	DESCRIPTION ""
	INDEX {
		himDBConfSysPabxId }
	::= { himDBConfSysTable 1 }


HimDBConfSysEntry ::= SEQUENCE {

	himDBConfSysPabxId     HimPabxId,
	himDBConfSysClass1     OCTET STRING,
	himDBConfSysClass2     OCTET STRING,
	himDBConfSysHWAss1     OCTET STRING,
	himDBConfSysHWAss2     OCTET STRING,
	himDBConfSysDevLine1   OCTET STRING,
	himDBConfSysDevLine2   OCTET STRING,
	himDBConfSysOpMode     INTEGER,
	himDBConfSysResType    OCTET STRING,
	himDBConfSysHWArch     OCTET STRING,
	himDBConfSysHWArchType OCTET STRING,
	himDBConfSysNo         HimSwitchNumber,
	himDBConfSysLoc        INTEGER,
	himDBConfSysBaseApp    OCTET STRING,
	himDBConfSysDBApp      OCTET STRING,
	himDBConfSysID         OCTET STRING }


himDBConfSysPabxId OBJECT-TYPE
	SYNTAX  HimPabxId
	MAX-ACCESS read-only
	STATUS  current
	DESCRIPTION ""
	::= { himDBConfSysEntry 1 }


himDBConfSysClass1 OBJECT-TYPE
	SYNTAX  OCTET STRING (SIZE (0..12))
	MAX-ACCESS read-only
	STATUS  current
	DESCRIPTION
		"This field contains the name of the system."
	::= { himDBConfSysEntry 2 }


himDBConfSysClass2 OBJECT-TYPE
	SYNTAX  OCTET STRING (SIZE (0..6))
	MAX-ACCESS read-only
	STATUS  current
	DESCRIPTION
		"This field contains the coded name of the system."
	::= { himDBConfSysEntry 3 }


himDBConfSysHWAss1 OBJECT-TYPE
	SYNTAX  OCTET STRING (SIZE (0..20))
	MAX-ACCESS read-only
	STATUS  current
	DESCRIPTION
		"This field contains the hardware ID of the system."
	::= { himDBConfSysEntry 4 }


himDBConfSysHWAss2 OBJECT-TYPE
	SYNTAX  OCTET STRING (SIZE (0..7))
	MAX-ACCESS read-only
	STATUS  current
	DESCRIPTION
		"This field contains the shortened hardware ID of the system."
	::= { himDBConfSysEntry 5 }


himDBConfSysDevLine1 OBJECT-TYPE
	SYNTAX  OCTET STRING (SIZE (0..18))
	MAX-ACCESS read-only
	STATUS  current
	DESCRIPTION
		"This field contains the name of the product line."
	::= { himDBConfSysEntry 6 }


himDBConfSysDevLine2 OBJECT-TYPE
	SYNTAX  OCTET STRING (SIZE (0..4))
	MAX-ACCESS read-only
	STATUS  current
	DESCRIPTION
		"This field contains the shortened name of the product line.
		Possible values:
		 -  H300: EUROPE DEVELOPMENT
		 -  HUSA: US DEVELOPMENT"
	::= { himDBConfSysEntry 7 }


himDBConfSysOpMode OBJECT-TYPE
	SYNTAX  INTEGER {
			simplex(1),
			duplex(2),
			other(0) }
	MAX-ACCESS read-only
	STATUS  current
	DESCRIPTION
		"This field contains the operating mode of the system.
		Possible Values:
		 -  SIMPLEX: OPERATING MODE SIMPLEX
		 -  DUPLEX: OPERATING MODE DUPLEX REDUNDANCY"
	::= { himDBConfSysEntry 8 }


himDBConfSysResType OBJECT-TYPE
	SYNTAX  OCTET STRING (SIZE (0..5))
	MAX-ACCESS read-only
	STATUS  current
	DESCRIPTION
		"This field contains the restart identifier."
	::= { himDBConfSysEntry 9 }


himDBConfSysHWArch OBJECT-TYPE
	SYNTAX  OCTET STRING (SIZE (0..10))
	MAX-ACCESS read-only
	STATUS  current
	DESCRIPTION
		"This field contains the name of the hardware architecture."
	::= { himDBConfSysEntry 10 }


himDBConfSysHWArchType OBJECT-TYPE
	SYNTAX  OCTET STRING (SIZE (0..3))
	MAX-ACCESS read-only
	STATUS  current
	DESCRIPTION
		"This field contains the name of the hardware architecture type."
	::= { himDBConfSysEntry 11 }


himDBConfSysNo OBJECT-TYPE
	SYNTAX  HimSwitchNumber
	MAX-ACCESS read-only
	STATUS  current
	DESCRIPTION
		"This field contains the number of the system."
	::= { himDBConfSysEntry 12 }


himDBConfSysLoc OBJECT-TYPE
	SYNTAX  INTEGER {
			customer(1),
			support(2),
			testlab(3),
			other(0) }
	MAX-ACCESS read-only
	STATUS  current
	DESCRIPTION
		"This field contains the name of the location in which the system is installed.
		Possible Values:
		 -  CUSTOMER (customer)
		 -  SUPPORT (support)
		 -  TESTLAB (testlab)"
	::= { himDBConfSysEntry 13 }


himDBConfSysBaseApp OBJECT-TYPE
	SYNTAX  OCTET STRING (SIZE (0..8))
	MAX-ACCESS read-only
	STATUS  current
	DESCRIPTION
		"This field contains the name of the base application."
	::= { himDBConfSysEntry 14 }


himDBConfSysDBApp OBJECT-TYPE
	SYNTAX  OCTET STRING (SIZE (0..8))
	MAX-ACCESS read-only
	STATUS  current
	DESCRIPTION
		"This field contains the name of the database application."
	::= { himDBConfSysEntry 15 }


himDBConfSysID OBJECT-TYPE
	SYNTAX  OCTET STRING (SIZE (0..10))
	MAX-ACCESS read-only
	STATUS  current
	DESCRIPTION
		"This field contains the system identification."
	::= { himDBConfSysEntry 16 }


himDBConfHW OBJECT IDENTIFIER 	::= { himGeneralSwitchData 2 }

himDBConfHWTable OBJECT-TYPE
	SYNTAX  SEQUENCE OF HimDBConfHWEntry
	MAX-ACCESS not-accessible
	STATUS  current
	DESCRIPTION ""
	::= { himDBConfHW 1 }


himDBConfHWEntry OBJECT-TYPE
	SYNTAX  HimDBConfHWEntry
	MAX-ACCESS not-accessible
	STATUS  current
	DESCRIPTION ""
	INDEX {
		himDBConfHWPabxId }
	::= { himDBConfHWTable 1 }


HimDBConfHWEntry ::= SEQUENCE {

	himDBConfHWPabxId      HimPabxId,
	himDBConfHWLTG         Integer32,
	himDBConfHWLTU         Integer32,
	himDBConfHWLines       Integer32,
	himDBConfHWPorts       Integer32,
	himDBConfHWPBC         Integer32,
	himDBConfHWMTSBdPerGSN Integer32,
	himDBConfHWSIUPPerLTU  Integer32,
	himDBConfHWDIUCPerLTU  Integer32,
	himDBConfHWHwyPerMTSBd Integer32,
	himDBConfHWHDLCPerDCL  Integer32,
	himDBConfHWPBCPerDCL   Integer32,
	himDBConfHWStdSIULine  Integer32,
	himDBConfHWConfLine    Integer32,
	himDBConfHWDBDim       OCTET STRING,
	himDBConfHWTableVer    Integer32 }


himDBConfHWPabxId OBJECT-TYPE
	SYNTAX  HimPabxId
	MAX-ACCESS read-only
	STATUS  current
	DESCRIPTION ""
	::= { himDBConfHWEntry 1 }


--Originally OCTET_STRING (SIZE (0..2))

himDBConfHWLTG OBJECT-TYPE
	SYNTAX  Integer32 (1)
	MAX-ACCESS read-only
	STATUS  current
	DESCRIPTION
		"This field contains the number of LTGs in the system.
		LTG: Line/Trunk Group"
	::= { himDBConfHWEntry 2 }


--Originally OCTET_STRING (SIZE (0..2))

himDBConfHWLTU OBJECT-TYPE
	SYNTAX  Integer32 (1..15 | 17..99)
	MAX-ACCESS read-only
	STATUS  current
	DESCRIPTION
		"This field contains the number of LTUs in the system.
		LTU: Line/Trunk Unit"
	::= { himDBConfHWEntry 3 }


--Originally OCTET_STRING (SIZE (0..5))

himDBConfHWLines OBJECT-TYPE
	SYNTAX  Integer32
	MAX-ACCESS read-only
	STATUS  current
	DESCRIPTION
		"This field contains the number of lines in the system."
	::= { himDBConfHWEntry 4 }


--Originally OCTET_STRING (SIZE (0..5))

himDBConfHWPorts OBJECT-TYPE
	SYNTAX  Integer32
	MAX-ACCESS read-only
	STATUS  current
	DESCRIPTION
		"This field contains the number of ports in the system."
	::= { himDBConfHWEntry 5 }


--Originally OCTET_STRING (SIZE (0..2))

himDBConfHWPBC OBJECT-TYPE
	SYNTAX  Integer32
	MAX-ACCESS read-only
	STATUS  current
	DESCRIPTION
		"This field contains the number of peripheral board controllers (PBC) in the system."
	::= { himDBConfHWEntry 6 }


--Originally OCTET_STRING (SIZE (0..3))

himDBConfHWMTSBdPerGSN OBJECT-TYPE
	SYNTAX  Integer32
	MAX-ACCESS read-only
	STATUS  current
	DESCRIPTION
		"This field contains the number of memory time switches (MTS) per group switching network (GSN)."
	::= { himDBConfHWEntry 7 }


--Originally OCTET_STRING (SIZE (0..2))

himDBConfHWSIUPPerLTU OBJECT-TYPE
	SYNTAX  Integer32
	MAX-ACCESS read-only
	STATUS  current
	DESCRIPTION
		"This field contains the number of SIUP boards per LTU (Line/Trunk Unit)."
	::= { himDBConfHWEntry 8 }


--Originally OCTET_STRING (SIZE (0..2))

himDBConfHWDIUCPerLTU OBJECT-TYPE
	SYNTAX  Integer32
	MAX-ACCESS read-only
	STATUS  current
	DESCRIPTION
		"This field contains the number of DIUC boards per LTU (Line/Trunk Unit)."
	::= { himDBConfHWEntry 9 }


--Originally OCTET_STRING (SIZE (0..3))

himDBConfHWHwyPerMTSBd OBJECT-TYPE
	SYNTAX  Integer32
	MAX-ACCESS read-only
	STATUS  current
	DESCRIPTION
		"This field contains the number highways (HYW) per MTS board."
	::= { himDBConfHWEntry 10 }


--Originally OCTET_STRING (SIZE (0..2))

himDBConfHWHDLCPerDCL OBJECT-TYPE
	SYNTAX  Integer32
	MAX-ACCESS read-only
	STATUS  current
	DESCRIPTION
		"This field contains the number of high level data link control (HDLC) channels per data communication link (DCL)."
	::= { himDBConfHWEntry 11 }


--Originally OCTET_STRING (SIZE (0..2))

himDBConfHWPBCPerDCL OBJECT-TYPE
	SYNTAX  Integer32
	MAX-ACCESS read-only
	STATUS  current
	DESCRIPTION
		"This field contains the number of peripheral board controllers (PBC) per data communication link (DCL)."
	::= { himDBConfHWEntry 12 }


--Originally OCTET_STRING (SIZE (0..4))

himDBConfHWStdSIULine OBJECT-TYPE
	SYNTAX  Integer32
	MAX-ACCESS read-only
	STATUS  current
	DESCRIPTION
		"This field contains the number of signaling unit lines.
		SIU: Signaling-Unit"
	::= { himDBConfHWEntry 13 }


--Originally OCTET_STRING (SIZE (0..4))

himDBConfHWConfLine OBJECT-TYPE
	SYNTAX  Integer32
	MAX-ACCESS read-only
	STATUS  current
	DESCRIPTION
		"This field contains the number of lines in the CONFERENCE board."
	::= { himDBConfHWEntry 14 }


himDBConfHWDBDim OBJECT-TYPE
	SYNTAX  OCTET STRING (SIZE (0..8))
	MAX-ACCESS read-only
	STATUS  current
	DESCRIPTION
		"This field contains the name of the database dimensioning."
	::= { himDBConfHWEntry 15 }


--Originally OCTET_STRING (SIZE (0..3))

himDBConfHWTableVer OBJECT-TYPE
	SYNTAX  Integer32
	MAX-ACCESS read-only
	STATUS  current
	DESCRIPTION
		"This field contains the version of the Conf table."
	::= { himDBConfHWEntry 16 }


himHWData OBJECT IDENTIFIER 	::= { himGeneralSwitchData 3 }

himHWDataTable OBJECT-TYPE
	SYNTAX  SEQUENCE OF HimHWDataEntry
	MAX-ACCESS not-accessible
	STATUS  current
	DESCRIPTION ""
	::= { himHWData 1 }


himHWDataEntry OBJECT-TYPE
	SYNTAX  HimHWDataEntry
	MAX-ACCESS not-accessible
	STATUS  current
	DESCRIPTION ""
	INDEX {
		himHWDataPabxId }
	::= { himHWDataTable 1 }


HimHWDataEntry ::= SEQUENCE {

	himHWDataPabxId HimPabxId,
	himHWArch       OCTET STRING,
	himHWArchType   OCTET STRING,
	himHWOpMode     OCTET STRING,
	himHWSWUProc1   OCTET STRING,
	himHWSWUMem1    OCTET STRING,
	himHWSWUProc2   OCTET STRING,
	himHWSWUMem2    OCTET STRING,
	himHWADPProc    OCTET STRING,
	himHWADPMem     OCTET STRING }


himHWDataPabxId OBJECT-TYPE
	SYNTAX  HimPabxId
	MAX-ACCESS read-only
	STATUS  current
	DESCRIPTION ""
	::= { himHWDataEntry 1 }


himHWArch OBJECT-TYPE
	SYNTAX  OCTET STRING (SIZE (0..25))
	MAX-ACCESS read-only
	STATUS  current
	DESCRIPTION
		"This field contains the name of the hardware architecture."
	REFERENCE

		"Same as himDBConfSysHWArch."
	::= { himHWDataEntry 2 }


himHWArchType OBJECT-TYPE
	SYNTAX  OCTET STRING (SIZE (0..3))
	MAX-ACCESS read-only
	STATUS  current
	DESCRIPTION
		"This field contains the name of the hardware architecture type."
	REFERENCE

		"Same as himDBConfSysHWArchType."
	::= { himHWDataEntry 3 }


himHWOpMode OBJECT-TYPE
	SYNTAX  OCTET STRING (SIZE (0..7))
	MAX-ACCESS read-only
	STATUS  current
	DESCRIPTION
		"This field contains the name of the operating mode."
	REFERENCE

		"Should be the same as himDBConfSysOpMode."
	::= { himHWDataEntry 4 }


himHWSWUProc1 OBJECT-TYPE
	SYNTAX  OCTET STRING (SIZE (0..8))
	MAX-ACCESS read-only
	STATUS  current
	DESCRIPTION
		"These fields contain the name of the SWU processor board (max. 8 characters).
		SWU = Switching Unit
		Possible values:
		 -  CC-A
		 -  CC-B

		"
	::= { himHWDataEntry 5 }


himHWSWUMem1 OBJECT-TYPE
	SYNTAX  OCTET STRING (SIZE (0..6))
	MAX-ACCESS read-only
	STATUS  current
	DESCRIPTION
		"These fields contain the size of the SWU memory for each processor board.
		SWU = Switching Unit"
	::= { himHWDataEntry 6 }


himHWSWUProc2 OBJECT-TYPE
	SYNTAX  OCTET STRING (SIZE (0..8))
	MAX-ACCESS read-only
	STATUS  current
	DESCRIPTION
		"These fields contain the name of the SWU processor board (max. 8 characters).
		SWU = Switching Unit
		Possible values:
		 -  CC-A
		 -  CC-B

		"
	::= { himHWDataEntry 7 }


himHWSWUMem2 OBJECT-TYPE
	SYNTAX  OCTET STRING (SIZE (0..6))
	MAX-ACCESS read-only
	STATUS  current
	DESCRIPTION
		"These fields contain the size of the SWU memory for each processor board.
		SWU = Switching Unit"
	::= { himHWDataEntry 8 }


himHWADPProc OBJECT-TYPE
	SYNTAX  OCTET STRING (SIZE (0..8))
	MAX-ACCESS read-only
	STATUS  current
	DESCRIPTION
		"This field contains the name of the ADP processor."
	::= { himHWDataEntry 9 }


himHWADPMem OBJECT-TYPE
	SYNTAX  OCTET STRING (SIZE (0..6))
	MAX-ACCESS read-only
	STATUS  current
	DESCRIPTION
		"This field contains the size of memory used by the ADP."
	::= { himHWDataEntry 10 }


himLWDataOnCB OBJECT IDENTIFIER 	::= { himGeneralSwitchData 4 }

himLWDataOnCBTable OBJECT-TYPE
	SYNTAX  SEQUENCE OF HimLWDataOnCBEntry
	MAX-ACCESS not-accessible
	STATUS  current
	DESCRIPTION ""
	::= { himLWDataOnCB 1 }


himLWDataOnCBEntry OBJECT-TYPE
	SYNTAX  HimLWDataOnCBEntry
	MAX-ACCESS not-accessible
	STATUS  current
	DESCRIPTION ""
	INDEX {
		himLWDataOnCBPabxId }
	::= { himLWDataOnCBTable 1 }


HimLWDataOnCBEntry ::= SEQUENCE {

	himLWDataOnCBPabxId HimPabxId,
	himLWOnCBAss        OCTET STRING,
	himLWOnCBPBCAddr    OCTET STRING,
	himLWOnCBFileName   OCTET STRING,
	himLWOnCBProdTime   OCTET STRING }


himLWDataOnCBPabxId OBJECT-TYPE
	SYNTAX  HimPabxId
	MAX-ACCESS read-only
	STATUS  current
	DESCRIPTION ""
	::= { himLWDataOnCBEntry 1 }


himLWOnCBAss OBJECT-TYPE
	SYNTAX  OCTET STRING (SIZE (0..8))
	MAX-ACCESS read-only
	STATUS  current
	DESCRIPTION
		"This field contains the hardware ID of the board.

		Note: Certain types of processor boards (e. g. DPC5) are using only firmware. Therefore, no loadware data is displayed and this field remains empty."
	::= { himLWDataOnCBEntry 2 }


himLWOnCBPBCAddr OBJECT-TYPE
	SYNTAX  OCTET STRING (SIZE (0..2))
	MAX-ACCESS read-only
	STATUS  current
	DESCRIPTION
		"This field contains the peripheral board controller (PBC) address of the module.

		Note: Certain types of processor boards (e. g. DPC5) are using only firmware. Therefore, no loadware data is displayed and this field remains empty."
	::= { himLWDataOnCBEntry 3 }


himLWOnCBFileName OBJECT-TYPE
	SYNTAX  OCTET STRING (SIZE (0..32))
	MAX-ACCESS read-only
	STATUS  current
	DESCRIPTION
		"This field contains the filename of the loadware file.

		Note: Certain types of processor boards (e. g. DPC5) are using only firmware. Therefore, no loadware data is displayed and this field remains empty."
	::= { himLWDataOnCBEntry 4 }


himLWOnCBProdTime OBJECT-TYPE
	SYNTAX  OCTET STRING (SIZE (0..20))
	MAX-ACCESS read-only
	STATUS  current
	DESCRIPTION
		"This field contains the production date of the loadware.

		Note:Certain types of processor boards (e. g. DPC5) are using only firmware. Therefore, no loadware data is displayed and this field remains empty."
	::= { himLWDataOnCBEntry 5 }


himLWDataOnProc OBJECT IDENTIFIER 	::= { himGeneralSwitchData 5 }

himLWOnProcTable OBJECT-TYPE
	SYNTAX  SEQUENCE OF HimLWOnProcEntry
	MAX-ACCESS not-accessible
	STATUS  current
	DESCRIPTION ""
	::= { himLWDataOnProc 1 }


himLWOnProcEntry OBJECT-TYPE
	SYNTAX  HimLWOnProcEntry
	MAX-ACCESS not-accessible
	STATUS  current
	DESCRIPTION ""
	INDEX {
		himLWOnProcPabxId,
		himLWOnProcAss,
		himLWOnProcInfoType }
	::= { himLWOnProcTable 1 }


HimLWOnProcEntry ::= SEQUENCE {

	himLWOnProcPabxId   HimPabxId,
	himLWOnProcAss      OCTET STRING,
	himLWOnProcInfoType OCTET STRING,
	himLWOnProcLWId     OCTET STRING,
	himLWOnProcLWIdCMP  OCTET STRING,
	himLWOnProcLWIdLP   OCTET STRING }


himLWOnProcPabxId OBJECT-TYPE
	SYNTAX  HimPabxId
	MAX-ACCESS read-only
	STATUS  current
	DESCRIPTION ""
	::= { himLWOnProcEntry 1 }


himLWOnProcAss OBJECT-TYPE
	SYNTAX  OCTET STRING (SIZE (0..3))
	MAX-ACCESS read-only
	STATUS  current
	DESCRIPTION
		"This field contains the name of the directory where the file with information on Loadware resides, e. g. CCA, CCB or ADP (max. 3 characters)."
	::= { himLWOnProcEntry 2 }


himLWOnProcInfoType OBJECT-TYPE
	SYNTAX  OCTET STRING (SIZE (0..8))
	MAX-ACCESS read-only
	STATUS  current
	DESCRIPTION
		"This field contains the boot type. It represents the file name also."
	::= { himLWOnProcEntry 3 }


himLWOnProcLWId OBJECT-TYPE
	SYNTAX  OCTET STRING (SIZE (0..10))
	MAX-ACCESS read-only
	STATUS  current
	DESCRIPTION
		"This field contains the name of the loadware."
	::= { himLWOnProcEntry 4 }


himLWOnProcLWIdCMP OBJECT-TYPE
	SYNTAX  OCTET STRING (SIZE (0..10))
	MAX-ACCESS read-only
	STATUS  current
	DESCRIPTION
		"This field contains the name of the loadware ID for the CMP. This field contains the '-' character if it is not relevant to this board."
	::= { himLWOnProcEntry 5 }


himLWOnProcLWIdLP OBJECT-TYPE
	SYNTAX  OCTET STRING (SIZE (0..10))
	MAX-ACCESS read-only
	STATUS  current
	DESCRIPTION
		"This field contains the name of the loadware ID for the LP. This field contains the '-' character if it is not relevant to this board."
	::= { himLWOnProcEntry 6 }


himLWDataOnCSIU OBJECT IDENTIFIER 	::= { himGeneralSwitchData 6 }

himLWOnCSIUTable OBJECT-TYPE
	SYNTAX  SEQUENCE OF HimLWOnCSIUEntry
	MAX-ACCESS not-accessible
	STATUS  current
	DESCRIPTION
		"This table contains the loadware data on the central SIU (Signaling Interface Unit)."
	::= { himLWDataOnCSIU 1 }


himLWOnCSIUEntry OBJECT-TYPE
	SYNTAX  HimLWOnCSIUEntry
	MAX-ACCESS not-accessible
	STATUS  current
	DESCRIPTION
		""
	INDEX {
		himLWOnCSIUPabxId,
		himLWOnCSIUNominal,
		himLWOnCSIULWNo }
	::= { himLWOnCSIUTable 1 }


HimLWOnCSIUEntry ::= SEQUENCE {

	himLWOnCSIUPabxId   HimPabxId,
	himLWOnCSIUNominal  OCTET STRING,
	himLWOnCSIULWNo     OCTET STRING,
	himLWOnCSIUProc     OCTET STRING,
	himLWOnCSIUSlot     OCTET STRING,
	himLWOnCSIUActual   OCTET STRING,
	himLWOnCSIUFileName OCTET STRING,
	himLWOnCSIUFileProd OCTET STRING }


himLWOnCSIUPabxId OBJECT-TYPE
	SYNTAX  HimPabxId
	MAX-ACCESS read-only
	STATUS  current
	DESCRIPTION ""
	::= { himLWOnCSIUEntry 1 }


himLWOnCSIUNominal OBJECT-TYPE
	SYNTAX  OCTET STRING (SIZE (0..14))
	MAX-ACCESS read-only
	STATUS  current
	DESCRIPTION
		"This field contains the name of the nominal SIU (Signaling Interface Unit)."
	::= { himLWOnCSIUEntry 2 }


himLWOnCSIULWNo OBJECT-TYPE
	SYNTAX  OCTET STRING (SIZE (0..1))
	MAX-ACCESS read-only
	STATUS  current
	DESCRIPTION
		"This field contains the name of the SIU (Signaling Interface Unit) loadware."
	::= { himLWOnCSIUEntry 3 }


himLWOnCSIUProc OBJECT-TYPE
	SYNTAX  OCTET STRING (SIZE (0..3))
	MAX-ACCESS read-only
	STATUS  current
	DESCRIPTION
		"This field contains the name of the processor in the SIU (Signaling Interface Unit)."
	::= { himLWOnCSIUEntry 4 }


himLWOnCSIUSlot OBJECT-TYPE
	SYNTAX  OCTET STRING (SIZE (0..3))
	MAX-ACCESS read-only
	STATUS  current
	DESCRIPTION
		"This field contains the name of the SIU (Signaling Interface Unit) slot."
	::= { himLWOnCSIUEntry 5 }


himLWOnCSIUActual OBJECT-TYPE
	SYNTAX  OCTET STRING (SIZE (0..14))
	MAX-ACCESS read-only
	STATUS  current
	DESCRIPTION
		"This field contains the name of the current SIU (Signaling Interface Unit)."
	::= { himLWOnCSIUEntry 6 }


himLWOnCSIUFileName OBJECT-TYPE
	SYNTAX  OCTET STRING (SIZE (0..32))
	MAX-ACCESS read-only
	STATUS  current
	DESCRIPTION
		"This field contains the file name of the loadware file or of the initialization file."
	::= { himLWOnCSIUEntry 7 }


himLWOnCSIUFileProd OBJECT-TYPE
	SYNTAX  OCTET STRING (SIZE (0..20))
	MAX-ACCESS read-only
	STATUS  current
	DESCRIPTION
		"This field contains the date on which the loadware or the initialization file was generated."
	::= { himLWOnCSIUEntry 8 }


himMacAddress OBJECT IDENTIFIER 	::= { himGeneralSwitchData 7 }

himMacAddrTable OBJECT-TYPE
	SYNTAX  SEQUENCE OF HimMacAddrEntry
	MAX-ACCESS not-accessible
	STATUS  current
	DESCRIPTION
		"This table contains the C-LAN and IPDA MAC addresses which are read during the boot process."
	::= { himMacAddress 1 }


himMacAddrEntry OBJECT-TYPE
	SYNTAX  HimMacAddrEntry
	MAX-ACCESS not-accessible
	STATUS  current
	DESCRIPTION ""
	INDEX {
		himMacAddrPabxId,
		himMacAddrProc,
		himMacAddrInfoType }
	::= { himMacAddrTable 1 }


HimMacAddrEntry ::= SEQUENCE {

	himMacAddrPabxId   HimPabxId,
	himMacAddrProc     OCTET STRING,
	himMacAddrInfoType OCTET STRING,
	himMacAddrCLan     MacAddress,
	himMacAddrIPDA     MacAddress }


himMacAddrPabxId OBJECT-TYPE
	SYNTAX  HimPabxId
	MAX-ACCESS read-only
	STATUS  current
	DESCRIPTION ""
	::= { himMacAddrEntry 1 }


himMacAddrProc OBJECT-TYPE
	SYNTAX  OCTET STRING (SIZE (0..3))
	MAX-ACCESS read-only
	STATUS  current
	DESCRIPTION
		"This field contains the name of the processor (CCA, CCB or ADP - max 3 characters). It is also the name of the Unix directory where the file with information on MAC address resides."
	::= { himMacAddrEntry 2 }


himMacAddrInfoType OBJECT-TYPE
	SYNTAX  OCTET STRING (SIZE (0..8))
	MAX-ACCESS read-only
	STATUS  current
	DESCRIPTION
		"This field contains the condition on which the mac addresses are available."
	::= { himMacAddrEntry 3 }


himMacAddrCLan OBJECT-TYPE
	SYNTAX  MacAddress
	MAX-ACCESS read-only
	STATUS  current
	DESCRIPTION
		"This field contains the MAC address for UW7 part. The format is following: 'xx xx xx xx xx xx'."
	::= { himMacAddrEntry 4 }


himMacAddrIPDA OBJECT-TYPE
	SYNTAX  MacAddress
	MAX-ACCESS read-only
	STATUS  current
	DESCRIPTION
		"This field contains the MAC address for RMX part. The format is following: 'xx xx xx xx xx xx'."
	::= { himMacAddrEntry 5 }


himFeatures OBJECT IDENTIFIER 	::= { hp4khim 7 }

himMarketingFeatures OBJECT IDENTIFIER 	::= { himFeatures 1 }

himMarkFeatTable OBJECT-TYPE
	SYNTAX  SEQUENCE OF HimMarkFeatEntry
	MAX-ACCESS not-accessible
	STATUS  current
	DESCRIPTION ""
	::= { himMarketingFeatures 1 }


himMarkFeatEntry OBJECT-TYPE
	SYNTAX  HimMarkFeatEntry
	MAX-ACCESS not-accessible
	STATUS  current
	DESCRIPTION ""
	INDEX {
		himMarkFeatPabxId }
	::= { himMarkFeatTable 1 }


HimMarkFeatEntry ::= SEQUENCE {

	himMarkFeatPabxId       HimPabxId,
	himMarkFeatVer          OCTET STRING,
	himMarkFeatSerNo        OCTET STRING,
	himMarkFeatHWId         OCTET STRING,
	himMarkFeatInstallDate  OCTET STRING,
	himMarkFeatExpiryDate   OCTET STRING,
	himMarkFeatConfCode     OCTET STRING,
	himMarkFeatTrialModeAct HimYesNo,
	himMarkFeatTrialRemDays Integer32 }


himMarkFeatPabxId OBJECT-TYPE
	SYNTAX  HimPabxId
	MAX-ACCESS read-only
	STATUS  current
	DESCRIPTION ""
	::= { himMarkFeatEntry 1 }


himMarkFeatVer OBJECT-TYPE
	SYNTAX  OCTET STRING (SIZE (0..4))
	MAX-ACCESS read-only
	STATUS  current
	DESCRIPTION
		"This field contains the version of the software package.
		Format explanation:
		H 2 04
		  |  |__SW version (01=EV1.0; 02=EV2.0; 03=EV3.0; 04=HiPath 4000 V1.0; 05=HiPath 4000 V2.0; 06=HiPath 4000 V3.0)
		  |
		  |_____Marketing concept (1=Old, 2=New)"
	::= { himMarkFeatEntry 2 }


himMarkFeatSerNo OBJECT-TYPE
	SYNTAX  OCTET STRING (SIZE (0..5))
	MAX-ACCESS read-only
	STATUS  current
	DESCRIPTION
		"This field contains the serial number of the software package."
	::= { himMarkFeatEntry 3 }


himMarkFeatHWId OBJECT-TYPE
	SYNTAX  OCTET STRING (SIZE (0..8))
	MAX-ACCESS read-only
	STATUS  current
	DESCRIPTION
		"This field contains the dongle ID of the hardware dongle connected."
	::= { himMarkFeatEntry 4 }


himMarkFeatInstallDate OBJECT-TYPE
	SYNTAX  OCTET STRING (SIZE (0..10))
	MAX-ACCESS read-only
	STATUS  current
	DESCRIPTION
		"This field contains the date on which the code word was entered."
	::= { himMarkFeatEntry 5 }


himMarkFeatExpiryDate OBJECT-TYPE
	SYNTAX  OCTET STRING (SIZE (0..10))
	MAX-ACCESS read-only
	STATUS  current
	DESCRIPTION
		"This field contains the date on which the code word will expire."
	::= { himMarkFeatEntry 6 }


himMarkFeatConfCode OBJECT-TYPE
	SYNTAX  OCTET STRING (SIZE (0..5))
	MAX-ACCESS read-only
	STATUS  current
	DESCRIPTION
		"This field contains codeword entry confirmation code."
	::= { himMarkFeatEntry 7 }


himMarkFeatTrialModeAct OBJECT-TYPE
	SYNTAX  HimYesNo
	MAX-ACCESS read-only
	STATUS  current
	DESCRIPTION
		"This field shows whether trial mode is active.
		Possible values:
		 -  yes - trial mode is activated
		 -  no - trial mode is not activated"
	::= { himMarkFeatEntry 8 }


himMarkFeatTrialRemDays OBJECT-TYPE
	SYNTAX  Integer32
	MAX-ACCESS read-only
	STATUS  current
	DESCRIPTION
		"This field contains number of remaining days of an active trial mode."
	::= { himMarkFeatEntry 9 }


himSalesFeatTable OBJECT-TYPE
	SYNTAX  SEQUENCE OF HimSalesFeatEntry
	MAX-ACCESS not-accessible
	STATUS  current
	DESCRIPTION ""
	::= { himMarketingFeatures 2 }


himSalesFeatEntry OBJECT-TYPE
	SYNTAX  HimSalesFeatEntry
	MAX-ACCESS not-accessible
	STATUS  current
	DESCRIPTION ""
	INDEX {
		himSalesFeatPabxId,
		himSalesFeatMarketPackId }
	::= { himSalesFeatTable 1 }


HimSalesFeatEntry ::= SEQUENCE {

	himSalesFeatPabxId       HimPabxId,
	himSalesFeatMarketPackId OCTET STRING,
	himSalesFeatMarketPack   OCTET STRING,
	himSalesFeatContract     OCTET STRING,
	himSalesFeatUsed         OCTET STRING,
	himSalesFeatFree         OCTET STRING,
	himSalesFeatMarkForTrial OCTET STRING }


himSalesFeatPabxId OBJECT-TYPE
	SYNTAX  HimPabxId
	MAX-ACCESS read-only
	STATUS  current
	DESCRIPTION ""
	::= { himSalesFeatEntry 1 }


himSalesFeatMarketPackId OBJECT-TYPE
	SYNTAX  OCTET STRING (SIZE (0..3))
	MAX-ACCESS read-only
	STATUS  current
	DESCRIPTION
		"This column contains the CM ids of the marketing packages."
	::= { himSalesFeatEntry 2 }


himSalesFeatMarketPack OBJECT-TYPE
	SYNTAX  OCTET STRING (SIZE (0..50))
	MAX-ACCESS read-only
	STATUS  current
	DESCRIPTION
		"This column contains the names of the marketing packages."
	::= { himSalesFeatEntry 3 }


himSalesFeatContract OBJECT-TYPE
	SYNTAX  OCTET STRING (SIZE (0..5))
	MAX-ACCESS read-only
	STATUS  current
	DESCRIPTION
		"This column indicates whether the marketing packages have been purchased."
	::= { himSalesFeatEntry 4 }


himSalesFeatUsed OBJECT-TYPE
	SYNTAX  OCTET STRING (SIZE (0..5))
	MAX-ACCESS read-only
	STATUS  current
	DESCRIPTION
		"This column indicates whether the marketing packages have been used."
	::= { himSalesFeatEntry 5 }


himSalesFeatFree OBJECT-TYPE
	SYNTAX  OCTET STRING (SIZE (0..5))
	MAX-ACCESS read-only
	STATUS  current
	DESCRIPTION
		"This field contains the number of free packages."
	::= { himSalesFeatEntry 6 }


himSalesFeatMarkForTrial OBJECT-TYPE
	SYNTAX  OCTET STRING (SIZE (0..5))
	MAX-ACCESS read-only
	STATUS  current
	DESCRIPTION
		"This field contains the number of packages (entites) marked for trial or blocked (if the trial mode is not active)."
	::= { himSalesFeatEntry 7 }


himTechFeatures OBJECT IDENTIFIER 	::= { himFeatures 2 }

himTechFeatTable OBJECT-TYPE
	SYNTAX  SEQUENCE OF HimTechFeatEntry
	MAX-ACCESS not-accessible
	STATUS  current
	DESCRIPTION ""
	::= { himTechFeatures 1 }


himTechFeatEntry OBJECT-TYPE
	SYNTAX  HimTechFeatEntry
	MAX-ACCESS not-accessible
	STATUS  current
	DESCRIPTION
		"This table contains all enabled and disabled customer-specific features. Use the Object List view to display a list of all features availavle."
	INDEX {
		himTechFeatPabxId,
		himTechFeatId }
	::= { himTechFeatTable 1 }


HimTechFeatEntry ::= SEQUENCE {

	himTechFeatPabxId HimPabxId,
	himTechFeatId     OCTET STRING,
	himTechFeatName   OCTET STRING,
	himTechFeatState  HimYesNo }


himTechFeatPabxId OBJECT-TYPE
	SYNTAX  HimPabxId
	MAX-ACCESS read-only
	STATUS  current
	DESCRIPTION ""
	::= { himTechFeatEntry 1 }


himTechFeatId OBJECT-TYPE
	SYNTAX  OCTET STRING (SIZE (0..3))
	MAX-ACCESS read-only
	STATUS  current
	DESCRIPTION
		"This field contains the CM id of the customer-specific feature."
	::= { himTechFeatEntry 2 }


himTechFeatName OBJECT-TYPE
	SYNTAX  OCTET STRING (SIZE (0..70))
	MAX-ACCESS read-only
	STATUS  current
	DESCRIPTION
		"This field contains the name of the customer-specific feature."
	::= { himTechFeatEntry 3 }


himTechFeatState OBJECT-TYPE
	SYNTAX  HimYesNo
	MAX-ACCESS read-only
	STATUS  current
	DESCRIPTION
		"This field contains the status of the customer-specific feature."
	::= { himTechFeatEntry 4 }


himAPSPatches OBJECT IDENTIFIER 	::= { hp4khim 8 }

himSwitchAPS OBJECT IDENTIFIER 	::= { himAPSPatches 1 }

himSwitchAPSTable OBJECT-TYPE
	SYNTAX  SEQUENCE OF HimSwitchAPSEntry
	MAX-ACCESS not-accessible
	STATUS  current
	DESCRIPTION ""
	::= { himSwitchAPS 1 }


himSwitchAPSEntry OBJECT-TYPE
	SYNTAX  HimSwitchAPSEntry
	MAX-ACCESS not-accessible
	STATUS  current
	DESCRIPTION ""
	INDEX {
		himSwitchAPSPabxId,
		himSwitchAPSName }
	::= { himSwitchAPSTable 1 }


HimSwitchAPSEntry ::= SEQUENCE {

	himSwitchAPSPabxId  HimPabxId,
	himSwitchAPSName    OCTET STRING,
	himSwitchAPSCorrVer OCTET STRING,
	himSwitchAPSPartNo  OCTET STRING }


himSwitchAPSPabxId OBJECT-TYPE
	SYNTAX  HimPabxId
	MAX-ACCESS read-only
	STATUS  current
	DESCRIPTION ""
	::= { himSwitchAPSEntry 1 }


himSwitchAPSName OBJECT-TYPE
	SYNTAX  OCTET STRING (SIZE (0..8))
	MAX-ACCESS read-only
	STATUS  current
	DESCRIPTION ""
	::= { himSwitchAPSEntry 2 }


himSwitchAPSCorrVer OBJECT-TYPE
	SYNTAX  OCTET STRING (SIZE (0..3))
	MAX-ACCESS read-only
	STATUS  current
	DESCRIPTION ""
	::= { himSwitchAPSEntry 3 }


himSwitchAPSPartNo OBJECT-TYPE
	SYNTAX  OCTET STRING (SIZE (0..17))
	MAX-ACCESS read-only
	STATUS  current
	DESCRIPTION ""
	::= { himSwitchAPSEntry 4 }


himReplacedAMOs OBJECT IDENTIFIER 	::= { himAPSPatches 2 }

himReplAMOTable OBJECT-TYPE
	SYNTAX  SEQUENCE OF HimReplAMOEntry
	MAX-ACCESS not-accessible
	STATUS  current
	DESCRIPTION
		"This table displays those AMOs that have been changed since the last system correction version."
	::= { himReplacedAMOs 1 }


himReplAMOEntry OBJECT-TYPE
	SYNTAX  HimReplAMOEntry
	MAX-ACCESS not-accessible
	STATUS  current
	DESCRIPTION ""
	INDEX {
		himReplAMOPabxId,
		himReplAMOAPS,
		himReplAMOName }
	::= { himReplAMOTable 1 }


HimReplAMOEntry ::= SEQUENCE {

	himReplAMOPabxId    HimPabxId,
	himReplAMOAPS       OCTET STRING,
	himReplAMOName      OCTET STRING,
	himReplAMOInAPSDir  OCTET STRING,
	himReplAMOSubsystem OCTET STRING }


himReplAMOPabxId OBJECT-TYPE
	SYNTAX  HimPabxId
	MAX-ACCESS read-only
	STATUS  current
	DESCRIPTION ""
	::= { himReplAMOEntry 1 }


himReplAMOAPS OBJECT-TYPE
	SYNTAX  OCTET STRING (SIZE (0..8))
	MAX-ACCESS read-only
	STATUS  current
	DESCRIPTION
		"The APS in which the change has been made."
	::= { himReplAMOEntry 2 }


himReplAMOName OBJECT-TYPE
	SYNTAX  OCTET STRING (SIZE (0..6))
	MAX-ACCESS read-only
	STATUS  current
	DESCRIPTION
		"This field contains the name of the AMO command."
	::= { himReplAMOEntry 3 }


himReplAMOInAPSDir OBJECT-TYPE
	SYNTAX  OCTET STRING (SIZE (0..22))
	MAX-ACCESS read-only
	STATUS  current
	DESCRIPTION
		"This field contains the name of the subsystem in the DIR file."
	::= { himReplAMOEntry 4 }


himReplAMOSubsystem OBJECT-TYPE
	SYNTAX  OCTET STRING (SIZE (0..22))
	MAX-ACCESS read-only
	STATUS  current
	DESCRIPTION
		"This field contains the name of the current subsystem."
	::= { himReplAMOEntry 5 }


himPatchInfo OBJECT IDENTIFIER 	::= { himAPSPatches 3 }

himPatchInfoTable OBJECT-TYPE
	SYNTAX  SEQUENCE OF HimPatchInfoEntry
	MAX-ACCESS not-accessible
	STATUS  current
	DESCRIPTION
		"This table contains information on the software patches that have been implemented."
	::= { himPatchInfo 1 }


himPatchInfoEntry OBJECT-TYPE
	SYNTAX  HimPatchInfoEntry
	MAX-ACCESS not-accessible
	STATUS  current
	DESCRIPTION ""
	INDEX {
		himPatchInfoPabxId,
		himPatchInfoPatchNo }
	::= { himPatchInfoTable 1 }


HimPatchInfoEntry ::= SEQUENCE {

	himPatchInfoPabxId     HimPabxId,
	himPatchInfoPatchNo    OCTET STRING,
	himPatchInfoPatchGroup OCTET STRING,
	himPatchInfoOpt        HimYesNo,
	himPatchInfoActHD      OCTET STRING,
	himPatchInfoActADP     OCTET STRING,
	himPatchInfoActBP      OCTET STRING }


himPatchInfoPabxId OBJECT-TYPE
	SYNTAX  HimPabxId
	MAX-ACCESS read-only
	STATUS  current
	DESCRIPTION ""
	::= { himPatchInfoEntry 1 }


himPatchInfoPatchNo OBJECT-TYPE
	SYNTAX  OCTET STRING (SIZE (0..12))
	MAX-ACCESS read-only
	STATUS  current
	DESCRIPTION
		"This field contains the number of the patch."
	::= { himPatchInfoEntry 2 }


himPatchInfoPatchGroup OBJECT-TYPE
	SYNTAX  OCTET STRING (SIZE (0..10))
	MAX-ACCESS read-only
	STATUS  current
	DESCRIPTION
		"This field contains the name of the patch group."
	::= { himPatchInfoEntry 3 }


himPatchInfoOpt OBJECT-TYPE
	SYNTAX  HimYesNo
	MAX-ACCESS read-only
	STATUS  current
	DESCRIPTION
		"This field represents an indicator that the patch is:
		 -  optional: not part of patch packet,
		 -  not optional: a part of patch packet (represents the whole list of internal
		activated/deactivated patches).
		The purpose of this field is to give user an option to display all patches as well as only optional ones."
	::= { himPatchInfoEntry 4 }


himPatchInfoActHD OBJECT-TYPE
	SYNTAX  OCTET STRING (SIZE (0..1))
	MAX-ACCESS read-only
	STATUS  current
	DESCRIPTION
		"This field indicates whether the patch is enabled on the hard disk."
	::= { himPatchInfoEntry 5 }


himPatchInfoActADP OBJECT-TYPE
	SYNTAX  OCTET STRING (SIZE (0..1))
	MAX-ACCESS read-only
	STATUS  current
	DESCRIPTION
		"This field indicates whether the patch is enabled on the ADP."
	::= { himPatchInfoEntry 6 }


himPatchInfoActBP OBJECT-TYPE
	SYNTAX  OCTET STRING (SIZE (0..2))
	MAX-ACCESS read-only
	STATUS  current
	DESCRIPTION
		"This field indicates whether the patch is enabled on the A/B processor."
	::= { himPatchInfoEntry 7 }


himSWVersion OBJECT IDENTIFIER 	::= { hp4khim 9 }

himSWVerOnProcTable OBJECT-TYPE
	SYNTAX  SEQUENCE OF HimSWVerOnProcEntry
	MAX-ACCESS not-accessible
	STATUS  current
	DESCRIPTION
		"This table contains data on the software versions loaded on the processor boards."
	::= { himSWVersion 1 }


himSWVerOnProcEntry OBJECT-TYPE
	SYNTAX  HimSWVerOnProcEntry
	MAX-ACCESS not-accessible
	STATUS  current
	DESCRIPTION ""
	INDEX {
		himSWVerOnProcPabxId,
		himSWVerOnProcSrc }
	::= { himSWVerOnProcTable 1 }


HimSWVerOnProcEntry ::= SEQUENCE {

	himSWVerOnProcPabxId           HimPabxId,
	himSWVerOnProcSrc              OCTET STRING,
	himSWVerOnProcSWVer            OCTET STRING,
	himSWVerOnProcItemCodeNoPrefix OCTET STRING,
	himSWVerOnProcHP4KVer          OCTET STRING,
	himSWVerOnProcSysRel           OCTET STRING,
	himSWVerOnProcCountry          OCTET STRING,
	himSWVerOnProcCountryCode      OCTET STRING,
	himSWVerOnProcRevNo            OCTET STRING }


himSWVerOnProcPabxId OBJECT-TYPE
	SYNTAX  HimPabxId
	MAX-ACCESS read-only
	STATUS  current
	DESCRIPTION ""
	::= { himSWVerOnProcEntry 1 }


himSWVerOnProcSrc OBJECT-TYPE
	SYNTAX  OCTET STRING (SIZE (0..3))
	MAX-ACCESS read-only
	STATUS  current
	DESCRIPTION
		"This field contains the name of the software source."
	::= { himSWVerOnProcEntry 2 }


himSWVerOnProcSWVer OBJECT-TYPE
	SYNTAX  OCTET STRING (SIZE (0..17))
	MAX-ACCESS read-only
	STATUS  current
	DESCRIPTION
		"This field contains the name of the software version of the ADP software.
		The software version is displayed in the following format:
		[item-code-prefix][hipath-version][release-no][country-id][country-code][revision-no]
		e. g.
		P30252N 43 08 B 000 10"
	::= { himSWVerOnProcEntry 3 }


himSWVerOnProcItemCodeNoPrefix OBJECT-TYPE
	SYNTAX  OCTET STRING (SIZE (0..8))
	MAX-ACCESS read-only
	STATUS  current
	DESCRIPTION
		"This field contains the prefix of the software."
	::= { himSWVerOnProcEntry 4 }


himSWVerOnProcHP4KVer OBJECT-TYPE
	SYNTAX  OCTET STRING (SIZE (0..2))
	MAX-ACCESS read-only
	STATUS  current
	DESCRIPTION
		"This field contains the Hicom/HiPath version."
	::= { himSWVerOnProcEntry 5 }


himSWVerOnProcSysRel OBJECT-TYPE
	SYNTAX  OCTET STRING (SIZE (0..2))
	MAX-ACCESS read-only
	STATUS  current
	DESCRIPTION
		"This field contains the system release number."
	::= { himSWVerOnProcEntry 6 }


himSWVerOnProcCountry OBJECT-TYPE
	SYNTAX  OCTET STRING (SIZE (0..1))
	MAX-ACCESS read-only
	STATUS  current
	DESCRIPTION
		"This field contains the country identifier."
	::= { himSWVerOnProcEntry 7 }


himSWVerOnProcCountryCode OBJECT-TYPE
	SYNTAX  OCTET STRING (SIZE (0..3))
	MAX-ACCESS read-only
	STATUS  current
	DESCRIPTION
		"This field contains the country encoding."
	::= { himSWVerOnProcEntry 8 }


himSWVerOnProcRevNo OBJECT-TYPE
	SYNTAX  OCTET STRING (SIZE (0..2))
	MAX-ACCESS read-only
	STATUS  current
	DESCRIPTION
		"This field contains the revision number of the ADP software."
	::= { himSWVerOnProcEntry 9 }


himSwPkgVersion OBJECT IDENTIFIER 	::= { hp4khim 10 }

himSWPkgVerTable OBJECT-TYPE
	SYNTAX  SEQUENCE OF HimSWPkgVerEntry
	MAX-ACCESS not-accessible
	STATUS  current
	DESCRIPTION
		"This table contains the software versions of the service functions. This data is retrieved using the UNIX command pgkinfo -l."
	::= { himSwPkgVersion 1 }


himSWPkgVerEntry OBJECT-TYPE
	SYNTAX  HimSWPkgVerEntry
	MAX-ACCESS not-accessible
	STATUS  current
	DESCRIPTION ""
	INDEX {
		himSWPkgVerPabxId,
		himSWPkgVerPkgAbbr }
	::= { himSWPkgVerTable 1 }


HimSWPkgVerEntry ::= SEQUENCE {

	himSWPkgVerPabxId  HimPabxId,
	himSWPkgVerPkgAbbr OCTET STRING,
	himSWPkgVerPkgName OCTET STRING,
	himSWPkgVerVersion OCTET STRING,
	himSWPkgVerInstAt  OCTET STRING,
	himSWPkgVerStatus  INTEGER }


himSWPkgVerPabxId OBJECT-TYPE
	SYNTAX  HimPabxId
	MAX-ACCESS read-only
	STATUS  current
	DESCRIPTION ""
	::= { himSWPkgVerEntry 1 }


himSWPkgVerPkgAbbr OBJECT-TYPE
	SYNTAX  OCTET STRING (SIZE (0..16))
	MAX-ACCESS read-only
	STATUS  current
	DESCRIPTION
		"This field contains the abbreviation of the software package."
	::= { himSWPkgVerEntry 2 }


himSWPkgVerPkgName OBJECT-TYPE
	SYNTAX  OCTET STRING (SIZE (0..50))
	MAX-ACCESS read-only
	STATUS  current
	DESCRIPTION
		"This field contains the name of the software package."
	::= { himSWPkgVerEntry 3 }


himSWPkgVerVersion OBJECT-TYPE
	SYNTAX  OCTET STRING (SIZE (0..6))
	MAX-ACCESS read-only
	STATUS  current
	DESCRIPTION
		"This field contains the version of the software package."
	::= { himSWPkgVerEntry 4 }


himSWPkgVerInstAt OBJECT-TYPE
	SYNTAX  OCTET STRING (SIZE (0..20))
	MAX-ACCESS read-only
	STATUS  current
	DESCRIPTION
		"This field contains the date on which the software package was installed."
	::= { himSWPkgVerEntry 5 }


himSWPkgVerStatus OBJECT-TYPE
	SYNTAX  INTEGER {
			partial(1),
			complete(2),
			other(0) }
	MAX-ACCESS read-only
	STATUS  current
	DESCRIPTION
		"This field contains the status of the software package."
	::= { himSWPkgVerEntry 6 }


himSystem OBJECT IDENTIFIER 	::= { hp4khim 11 }

himSysBasicTable OBJECT-TYPE
	SYNTAX  SEQUENCE OF HimSysBasicEntry
	MAX-ACCESS not-accessible
	STATUS  current
	DESCRIPTION
		"This table complements the information about the HiPath 4000 system that is stored in the hicomSystem branch of the hicom MIB."
	::= { himSystem 1 }


himSysBasicEntry OBJECT-TYPE
	SYNTAX  HimSysBasicEntry
	MAX-ACCESS not-accessible
	STATUS  current
	DESCRIPTION ""
	INDEX {
		himSysBasicPabxId }
	::= { himSysBasicTable 1 }


HimSysBasicEntry ::= SEQUENCE {

	himSysBasicPabxId HimPabxId,
	himSysBasicDomain OCTET STRING,
	himSysBasicNodeNo OCTET STRING,
	himSysBasicLEGK   HimYesNo }


himSysBasicPabxId OBJECT-TYPE
	SYNTAX  HimPabxId
	MAX-ACCESS read-only
	STATUS  current
	DESCRIPTION ""
	::= { himSysBasicEntry 1 }


himSysBasicDomain OBJECT-TYPE
	SYNTAX  OCTET STRING (SIZE (0..8))
	MAX-ACCESS read-only
	STATUS  current
	DESCRIPTION
		"This field contains the name of the domain to which the system is belonging."
	::= { himSysBasicEntry 2 }


himSysBasicNodeNo OBJECT-TYPE
	SYNTAX  OCTET STRING (SIZE (0..10))
	MAX-ACCESS read-only
	STATUS  current
	DESCRIPTION
		"HiPath node number.
		This field contains the globally unique number of your own PABX. This has a hierarchical structure containing different levels in Version V1.0 and later.
		Up to three values of the format:
		L2- L1- L0 can be used for numbering a system.
		   -  L2: area number in level 2
		   -  L1: area number in level 1
		   -  L0: area number in level 0 or node number in the old sense.
		If the value '0' is selected for a level, this means that the relevant hierarchical level is not being used for node numbering: '0' is equal to 'nothing' or 'level is not set'.
		With the help of this new node number format it is now possible to implement node numbers in networks in which - just as with dial numbers - the network hierarchy is reflected in the node numbers.

		The same numbering level (= number of levels set in the node number) must be used for all nodes in a network.

		This field will always show a three-level display with leading zeroes for levels not used for systems in Version V1.0 and later.

		Example:
		  - 0-0-100 for 1-level numbering
		  - 0-1-101 for 2-level numbering
		  - 1-2-300 for 3-level numbering

		Values: 0-9 and '-' with format 22-111-000
		Level 0 (000) 0-999
		Level 1 (111) 0-253
		Level 2 (22) 0-29
		Max. 10 digits"
	::= { himSysBasicEntry 3 }


himSysBasicLEGK OBJECT-TYPE
	SYNTAX  HimYesNo
	MAX-ACCESS read-only
	STATUS  current
	DESCRIPTION
		"This field tells if the 'LEGK' feature is activated on the system.
		LEGK is a process within the call processing of HiPath 4000 with the following functions:
		  - Gate keeper function: IP address resolution mechanism for IP trunking requiring the HG3550 board as hardware.
		  - Resource Management:  This function monitors network component usage for controlling IP trunking, IPDA scenarios, HFA and direct media connections.
		The LEGK can be activated at every HiPath 4000 in the network. Alternatively, it can be configured on a specific HiPath 4000 system only."
	::= { himSysBasicEntry 4 }


himSysLANCardsTable OBJECT-TYPE
	SYNTAX  SEQUENCE OF HimSysLANCardsEntry
	MAX-ACCESS not-accessible
	STATUS  current
	DESCRIPTION ""
	::= { himSystem 2 }


himSysLANCardsEntry OBJECT-TYPE
	SYNTAX  HimSysLANCardsEntry
	MAX-ACCESS not-accessible
	STATUS  current
	DESCRIPTION ""
	INDEX {
		himSysLANCardsPabxId,
		himSysLANCardsIPAddr }
	::= { himSysLANCardsTable 1 }


HimSysLANCardsEntry ::= SEQUENCE {

	himSysLANCardsPabxId    HimPabxId,
	himSysLANCardsIPAddr    IpAddress,
	himSysLANCardsNetMask   IpAddress,
	himSysLANCardsBroadCast IpAddress,
	himSysLANCardsType      INTEGER,
	himSysLANCardsStatus    INTEGER }


himSysLANCardsPabxId OBJECT-TYPE
	SYNTAX  HimPabxId
	MAX-ACCESS read-only
	STATUS  current
	DESCRIPTION ""
	::= { himSysLANCardsEntry 1 }


himSysLANCardsIPAddr OBJECT-TYPE
	SYNTAX  IpAddress
	MAX-ACCESS read-only
	STATUS  current
	DESCRIPTION
		"Unique IP address within the Customer LAN."
	::= { himSysLANCardsEntry 2 }


himSysLANCardsNetMask OBJECT-TYPE
	SYNTAX  IpAddress
	MAX-ACCESS read-only
	STATUS  current
	DESCRIPTION
		"The netmask of the LAN card. It depends on the class of the LAN Card address."
	::= { himSysLANCardsEntry 3 }


himSysLANCardsBroadCast OBJECT-TYPE
	SYNTAX  IpAddress
	MAX-ACCESS read-only
	STATUS  current
	DESCRIPTION
		"The broadcast address is used to send a datagram packet to all hosts of a network or subnetwork, e.g. for address propagation from a router.
		The broadcast address also depends on the LAN Card address."
	::= { himSysLANCardsEntry 4 }


himSysLANCardsType OBJECT-TYPE
	SYNTAX  INTEGER {
			ethernet(1),
			tokenring(2),
			other(0) }
	MAX-ACCESS read-only
	STATUS  current
	DESCRIPTION
		"Type of the LAN card. Possible values are Ethernet and Token Ring."
	::= { himSysLANCardsEntry 5 }


himSysLANCardsStatus OBJECT-TYPE
	SYNTAX  INTEGER {
			enabled(1),
			disabled(2),
			stale(3),
			configured(4),
			unconfigured(5),
			other(0) }
	MAX-ACCESS read-only
	STATUS  current
	DESCRIPTION
		"The status of the configured LAN card. Can be one of the following:
		- Unknown (no traffic light lit): The LAN Card is configured, but no reboot has been performed.
		- Enabled (green traffic light lit): The LAN Card is active.
		- Disabled (red traffic light lit): The LAN Card is not active."
	::= { himSysLANCardsEntry 6 }


himSysHostsTable OBJECT-TYPE
	SYNTAX  SEQUENCE OF HimSysHostsEntry
	MAX-ACCESS not-accessible
	STATUS  current
	DESCRIPTION ""
	::= { himSystem 3 }


himSysHostsEntry OBJECT-TYPE
	SYNTAX  HimSysHostsEntry
	MAX-ACCESS not-accessible
	STATUS  current
	DESCRIPTION ""
	INDEX {
		himSysHostsPabxId,
		himSysHostsNo }
	::= { himSysHostsTable 1 }


HimSysHostsEntry ::= SEQUENCE {

	himSysHostsPabxId HimPabxId,
	himSysHostsNo     Integer32,
	himSysHostsIPAddr IpAddress,
	himSysHostsName   OCTET STRING }


himSysHostsPabxId OBJECT-TYPE
	SYNTAX  HimPabxId
	MAX-ACCESS read-only
	STATUS  current
	DESCRIPTION ""
	::= { himSysHostsEntry 1 }


himSysHostsNo OBJECT-TYPE
	SYNTAX  Integer32 (1..2147483647)
	MAX-ACCESS read-only
	STATUS  current
	DESCRIPTION
		"Index of the host entry."
	::= { himSysHostsEntry 2 }


himSysHostsIPAddr OBJECT-TYPE
	SYNTAX  IpAddress
	MAX-ACCESS read-only
	STATUS  current
	DESCRIPTION
		"The IP address of the host."
	::= { himSysHostsEntry 3 }


himSysHostsName OBJECT-TYPE
	SYNTAX  OCTET STRING (SIZE (0..50))
	MAX-ACCESS read-only
	STATUS  current
	DESCRIPTION
		"Unique name of the host."
	::= { himSysHostsEntry 4 }


himSysWAMLConn OBJECT IDENTIFIER 	::= { himSystem 4 }

himSysWAMLConnTable OBJECT-TYPE
	SYNTAX  SEQUENCE OF HimSysWAMLConnEntry
	MAX-ACCESS not-accessible
	STATUS  current
	DESCRIPTION ""
	::= { himSysWAMLConn 1 }


himSysWAMLConnEntry OBJECT-TYPE
	SYNTAX  HimSysWAMLConnEntry
	MAX-ACCESS not-accessible
	STATUS  current
	DESCRIPTION ""
	INDEX {
		himSysWAMLConnPabxId,
		himSysWAMLConnLTG,
		himSysWAMLConnLTU,
		himSysWAMLConnSlot }
	::= { himSysWAMLConnTable 1 }


HimSysWAMLConnEntry ::= SEQUENCE {

	himSysWAMLConnPabxId HimPabxId,
	himSysWAMLConnLTG    Integer32,
	himSysWAMLConnLTU    Integer32,
	himSysWAMLConnSlot   Integer32,
	himSysWAMLConnRufNr  HimPhoneNumber,
	himSysWAMLConnBChl   Unsigned32,
	himSysWAMLConnStatus OCTET STRING }


himSysWAMLConnPabxId OBJECT-TYPE
	SYNTAX  HimPabxId
	MAX-ACCESS read-only
	STATUS  current
	DESCRIPTION ""
	::= { himSysWAMLConnEntry 1 }


himSysWAMLConnLTG OBJECT-TYPE
	SYNTAX  Integer32 (1)
	MAX-ACCESS read-only
	STATUS  current
	DESCRIPTION
		"Line/trunk group number.

		Valid values: 1-1"
	::= { himSysWAMLConnEntry 2 }


himSysWAMLConnLTU OBJECT-TYPE
	SYNTAX  Integer32 (1..99)
	MAX-ACCESS read-only
	STATUS  current
	DESCRIPTION
		"Line/trunk unit.

		Valid values:
		1-15, for
		    IP Gateway
		    DSP HW of NCUI
		    STMI
		    STMA
		    WAML
		1-99, for
		    RG/ACGEN
		    PER
		    DIU
		    SIUP
		    TMD
		17-99, for
		    NCUI
		    STMA
		    WAML"
	::= { himSysWAMLConnEntry 3 }


himSysWAMLConnSlot OBJECT-TYPE
	SYNTAX  Integer32 (1..145)
	MAX-ACCESS read-only
	STATUS  current
	DESCRIPTION
		"Slot number of LTU (Line/Trunk Unit).

		Valid values:
		    1-121, for STMI, IP gateway, PER, RG, ACGEN, DIU, SIUP, TMD
		    1-145, for STMA, WAML"
	::= { himSysWAMLConnEntry 4 }


himSysWAMLConnRufNr OBJECT-TYPE
	SYNTAX  HimPhoneNumber
	MAX-ACCESS read-only
	STATUS  current
	DESCRIPTION
		"Phone number of the WAML board."
	::= { himSysWAMLConnEntry 5 }


himSysWAMLConnBChl OBJECT-TYPE
	SYNTAX  Unsigned32
	MAX-ACCESS read-only
	STATUS  current
	DESCRIPTION
		"Number of b-channels on the WAML board."
	::= { himSysWAMLConnEntry 6 }


himSysWAMLConnStatus OBJECT-TYPE
	SYNTAX  OCTET STRING (SIZE (0..10))
	MAX-ACCESS read-only
	STATUS  current
	DESCRIPTION
		"Status of the WAML board."
	::= { himSysWAMLConnEntry 7 }


himSysWAMLConnIPTable OBJECT-TYPE
	SYNTAX  SEQUENCE OF HimSysWAMLConnIPEntry
	MAX-ACCESS not-accessible
	STATUS  current
	DESCRIPTION ""
	::= { himSysWAMLConn 2 }


himSysWAMLConnIPEntry OBJECT-TYPE
	SYNTAX  HimSysWAMLConnIPEntry
	MAX-ACCESS not-accessible
	STATUS  current
	DESCRIPTION ""
	INDEX {
		himSysWAMLConnIPPabxId,
		himSysWAMLConnIPLTG,
		himSysWAMLConnIPLTU,
		himSysWAMLConnIPSlot,
		himSysWAMLConnIPIfName }
	::= { himSysWAMLConnIPTable 1 }


HimSysWAMLConnIPEntry ::= SEQUENCE {

	himSysWAMLConnIPPabxId  HimPabxId,
	himSysWAMLConnIPLTG     Integer32,
	himSysWAMLConnIPLTU     Integer32,
	himSysWAMLConnIPSlot    Integer32,
	himSysWAMLConnIPIfName  OCTET STRING,
	himSysWAMLConnIPAddr    IpAddress,
	himSysWAMLConnIPNetMask IpAddress }


himSysWAMLConnIPPabxId OBJECT-TYPE
	SYNTAX  HimPabxId
	MAX-ACCESS read-only
	STATUS  current
	DESCRIPTION ""
	::= { himSysWAMLConnIPEntry 1 }


himSysWAMLConnIPLTG OBJECT-TYPE
	SYNTAX  Integer32 (1)
	MAX-ACCESS read-only
	STATUS  current
	DESCRIPTION
		"Line/trunk group number.

		Valid values: 1-1"
	::= { himSysWAMLConnIPEntry 2 }


himSysWAMLConnIPLTU OBJECT-TYPE
	SYNTAX  Integer32 (1..99)
	MAX-ACCESS read-only
	STATUS  current
	DESCRIPTION
		"Line/trunk unit.

		Valid values:
		1-15, for
		    IP Gateway
		    DSP HW of NCUI
		    STMI
		    STMA
		    WAML
		1-99, for
		    RG/ACGEN
		    PER
		    DIU
		    SIUP
		    TMD
		17-99, for
		    NCUI
		    STMA
		    WAML"
	::= { himSysWAMLConnIPEntry 3 }


himSysWAMLConnIPSlot OBJECT-TYPE
	SYNTAX  Integer32 (1..145)
	MAX-ACCESS read-only
	STATUS  current
	DESCRIPTION
		"Slot number of LTU (Line/Trunk Unit).

		Valid values:
		    1-121, for STMI, IP gateway, PER, RG, ACGEN, DIU, SIUP, TMD
		    1-145, for STMA, WAML"
	::= { himSysWAMLConnIPEntry 4 }


himSysWAMLConnIPIfName OBJECT-TYPE
	SYNTAX  OCTET STRING (SIZE (0..8))
	MAX-ACCESS read-only
	STATUS  current
	DESCRIPTION
		"Name of the interface."
	::= { himSysWAMLConnIPEntry 5 }


himSysWAMLConnIPAddr OBJECT-TYPE
	SYNTAX  IpAddress
	MAX-ACCESS read-only
	STATUS  current
	DESCRIPTION
		"IP address of the WAML connection."
	::= { himSysWAMLConnIPEntry 6 }


himSysWAMLConnIPNetMask OBJECT-TYPE
	SYNTAX  IpAddress
	MAX-ACCESS read-only
	STATUS  current
	DESCRIPTION
		"Net mask of the WAML connection."
	::= { himSysWAMLConnIPEntry 7 }


himBoards OBJECT IDENTIFIER 	::= { hp4khim 12 }

himBoardBasicTable OBJECT-TYPE
	SYNTAX  SEQUENCE OF HimBoardBasicEntry
	MAX-ACCESS not-accessible
	STATUS  current
	DESCRIPTION
		"This table contains the boards that are managed by CM.

		It can be viewed as an extension of hicomBCSUTable. Please note that the PEN (LTG, LTU, Slot) of LTU boards is different from what is contained in CM, and uses the same format as in the hicom MIB."
	::= { himBoards 1 }


himBoardBasicEntry OBJECT-TYPE
	SYNTAX  HimBoardBasicEntry
	MAX-ACCESS not-accessible
	STATUS  current
	DESCRIPTION ""
	INDEX {
		himBoardBasicPabxId,
		himBoardBasicLTG,
		himBoardBasicLTU,
		himBoardBasicSlot }
	::= { himBoardBasicTable 1 }


HimBoardBasicEntry ::= SEQUENCE {

	himBoardBasicPabxId  HimPabxId,
	himBoardBasicLTG     Integer32,
	himBoardBasicLTU     Integer32,
	himBoardBasicSlot    Integer32,
	himBoardBasicFuncId  Integer32,
	himBoardBasicCat     INTEGER,
	himBoardBasicName    OCTET STRING,
	himBoardBasicVOIPSec HimYesNo,
	himBoardBasicLWVar   OCTET STRING,
	himBoardBasicNoCirc  Integer32 }


himBoardBasicPabxId OBJECT-TYPE
	SYNTAX  HimPabxId
	MAX-ACCESS read-only
	STATUS  current
	DESCRIPTION ""
	::= { himBoardBasicEntry 1 }


himBoardBasicLTG OBJECT-TYPE
	SYNTAX  Integer32 (1)
	MAX-ACCESS read-only
	STATUS  current
	DESCRIPTION
		"Line/trunk group number.

		Valid values: 1-1"
	::= { himBoardBasicEntry 2 }


himBoardBasicLTU OBJECT-TYPE
	SYNTAX  Integer32 (1..99)
	MAX-ACCESS read-only
	STATUS  current
	DESCRIPTION
		"Line/trunk unit.

		Valid values:
		1-15, for
		    IP Gateway
		    DSP HW of NCUI
		    STMI
		    STMA
		    WAML
		1-99, for
		    RG/ACGEN
		    PER
		    DIU
		    SIUP
		    TMD
		17-99, for
		    NCUI
		    STMA
		    WAML"
	::= { himBoardBasicEntry 3 }


himBoardBasicSlot OBJECT-TYPE
	SYNTAX  Integer32 (1..145)
	MAX-ACCESS read-only
	STATUS  current
	DESCRIPTION
		"Slot number of LTU (Line/Trunk Unit).

		Valid values:
		    1-121, for STMI, IP gateway, PER, RG, ACGEN, DIU, SIUP, TMD
		    1-145, for STMA, WAML"
	::= { himBoardBasicEntry 4 }


himBoardBasicFuncId OBJECT-TYPE
	SYNTAX  Integer32 (0..255)
	MAX-ACCESS read-only
	STATUS  current
	DESCRIPTION
		"Function ID

		Valid values: 0-255
		    2 for SIU type 2 (MFV)
		    3 for SIU type 3 (MFC)
		    4 for SIU - RDS functionality
		    5 for SIU - ANI signaling
		    6 for SIU - CIS multifrequency (MFS)
		    7 for SIU - line testing"
	::= { himBoardBasicEntry 5 }


himBoardBasicCat OBJECT-TYPE
	SYNTAX  INTEGER {
			ltg(1),
			ltu(2),
			per(3),
			perhw(4),
			acgen(5),
			diu(6),
			ipgw(7),
			rg(8),
			siup(9),
			tmd(10),
			other(0) }
	MAX-ACCESS read-only
	STATUS  current
	DESCRIPTION
		"Category

		The board type includes:
		    LTG -- line/trunk group
		    LTU -- line/trunk unit
		    PER -- peripheral module
		    PERHW -- load peripheral hardware
		    ACGEN -- alternating current generator
		    DIU -- digital interface unit
		    IPGW -- IP gateway
		    RG -- ring generator
		    SIUP -- signalling unit periphery
		    TMD -- T1 boards"
	::= { himBoardBasicEntry 6 }


himBoardBasicName OBJECT-TYPE
	SYNTAX  OCTET STRING (SIZE (0..10))
	MAX-ACCESS read-only
	STATUS  current
	DESCRIPTION
		"Name of the setup the board is configured to."
	::= { himBoardBasicEntry 7 }


himBoardBasicVOIPSec OBJECT-TYPE
	SYNTAX  HimYesNo
	MAX-ACCESS read-only
	STATUS  current
	DESCRIPTION ""
	::= { himBoardBasicEntry 8 }


himBoardBasicLWVar OBJECT-TYPE
	SYNTAX  OCTET STRING (SIZE (0..1))
	MAX-ACCESS read-only
	STATUS  current
	DESCRIPTION
		"The loadware variant.

		Default value: 0
		Valid values: 0-9, A-D"
	::= { himBoardBasicEntry 9 }


himBoardBasicNoCirc OBJECT-TYPE
	SYNTAX  Integer32 (1..255)
	MAX-ACCESS read-only
	STATUS  current
	DESCRIPTION
		"Number of circuits to be configured.

		Valid values: 1-255"
	::= { himBoardBasicEntry 10 }


himBoardIPTable OBJECT-TYPE
	SYNTAX  SEQUENCE OF HimBoardIPEntry
	MAX-ACCESS not-accessible
	STATUS  current
	DESCRIPTION
		"This table contains the IP address configuration of the boards.

		Please note that not all fields are used for all boards."
	::= { himBoards 2 }


himBoardIPEntry OBJECT-TYPE
	SYNTAX  HimBoardIPEntry
	MAX-ACCESS not-accessible
	STATUS  current
	DESCRIPTION ""
	AUGMENTS {
		himBoardBasicEntry }
	::= { himBoardIPTable 1 }


HimBoardIPEntry ::= SEQUENCE {

	himBoardIPGwyIPAddr       IpAddress,
	himBoardIPSrcIPAddr       IpAddress,
	himBoardIPNetMask         IpAddress,
	himBoardIPDefRouter       IpAddress,
	himBoardIPCustLANIP       IpAddress,
	himBoardIPSTMI2IGWSubMask IpAddress,
	himBoardIPDefGWIP         IpAddress,
	himBoardIPManStatIP       IpAddress,
	himBoardIPManStatPort     Integer32,
	himBoardIPBckpServIP      IpAddress,
	himBoardIPBckpServPort    Integer32 }


himBoardIPGwyIPAddr OBJECT-TYPE
	SYNTAX  IpAddress
	MAX-ACCESS read-only
	STATUS  current
	DESCRIPTION
		"IP address of the gateway.

		Valid for: STMI"
	::= { himBoardIPEntry 1 }


himBoardIPSrcIPAddr OBJECT-TYPE
	SYNTAX  IpAddress
	MAX-ACCESS read-only
	STATUS  current
	DESCRIPTION
		"Source IP address of STMI-HFA board.
		A valid Source IP address must always be specified in order to enable the IP phones to address the system (SWU)

		Default: 0.0.0.0
		Valid for: HFA"
	::= { himBoardIPEntry 2 }


himBoardIPNetMask OBJECT-TYPE
	SYNTAX  IpAddress
	MAX-ACCESS read-only
	STATUS  current
	DESCRIPTION
		"IP network mask.

		Valid for: HFA"
	::= { himBoardIPEntry 3 }


himBoardIPDefRouter OBJECT-TYPE
	SYNTAX  IpAddress
	MAX-ACCESS read-only
	STATUS  current
	DESCRIPTION
		"IP address of the default router within the LAN segment.
		The default router takes care of routing forward all packets with a destination address with a network part different from the own LAN segment.

		Default: 0.0.0.0
		Valid for: HFA"
	::= { himBoardIPEntry 4 }


himBoardIPCustLANIP OBJECT-TYPE
	SYNTAX  IpAddress
	MAX-ACCESS read-only
	STATUS  current
	DESCRIPTION
		"IP address of customer LAN.

		Default: 0.0.0.0
		Valid for: IGW, SIP"
	::= { himBoardIPEntry 5 }


himBoardIPSTMI2IGWSubMask OBJECT-TYPE
	SYNTAX  IpAddress
	MAX-ACCESS read-only
	STATUS  current
	DESCRIPTION
		"IP subnet mask of LAN segment.

		Default: 0.0.0.0
		Valid for: IGW, SIP"
	::= { himBoardIPEntry 6 }


himBoardIPDefGWIP OBJECT-TYPE
	SYNTAX  IpAddress
	MAX-ACCESS read-only
	STATUS  current
	DESCRIPTION
		"Default gateway IP address.

		Default: 0.0.0.0
		Valid for: IGW, SIP"
	::= { himBoardIPEntry 7 }


himBoardIPManStatIP OBJECT-TYPE
	SYNTAX  IpAddress
	MAX-ACCESS read-only
	STATUS  current
	DESCRIPTION
		"IP address of management station.

		Default: 0.0.0.0
		Valid for: IGW, SIP"
	::= { himBoardIPEntry 8 }


himBoardIPManStatPort OBJECT-TYPE
	SYNTAX  Integer32 (1024..65535)
	MAX-ACCESS read-only
	STATUS  current
	DESCRIPTION
		"Port number of management station.

		Valid values: 1024 - 65535
		Default: 0
		Valid for: IGW, SIP"
	::= { himBoardIPEntry 9 }


himBoardIPBckpServIP OBJECT-TYPE
	SYNTAX  IpAddress
	MAX-ACCESS read-only
	STATUS  current
	DESCRIPTION
		"IP address of backup server.

		Default: 0.0.0.0
		Valid for: IGW, SIP"
	::= { himBoardIPEntry 10 }


himBoardIPBckpServPort OBJECT-TYPE
	SYNTAX  Integer32 (0..65535)
	MAX-ACCESS read-only
	STATUS  current
	DESCRIPTION
		"Port number of backup server.

		Default: 0 (0 means 'undefined port number')
		Valid for: IGW, SIP"
	::= { himBoardIPEntry 11 }


himBoardLocTable OBJECT-TYPE
	SYNTAX  SEQUENCE OF HimBoardLocEntry
	MAX-ACCESS not-accessible
	STATUS  current
	DESCRIPTION
		"This table contains the location data of the boards. It is only available for boards of type DSX, LTUCA, LTUCE and LTUCX."
	::= { himBoards 3 }


himBoardLocEntry OBJECT-TYPE
	SYNTAX  HimBoardLocEntry
	MAX-ACCESS not-accessible
	STATUS  current
	DESCRIPTION ""
	INDEX {
		himBoardBasicPabxId,
		himBoardBasicLTG,
		himBoardBasicLTU,
		himBoardBasicSlot }
	::= { himBoardLocTable 1 }


HimBoardLocEntry ::= SEQUENCE {

	himBoardLocId      Integer32,
	himBoardLocLoc     OCTET STRING,
	himBoardLocPhoneNo HimPhoneNumber,
	himBoardLocFaxNo   HimPhoneNumber }


himBoardLocId OBJECT-TYPE
	SYNTAX  Integer32 (0..999)
	MAX-ACCESS read-only
	STATUS  current
	DESCRIPTION
		"Describes the location of the switch for the system configurator.

		Valid values: 0-999"
	::= { himBoardLocEntry 1 }


himBoardLocLoc OBJECT-TYPE
	SYNTAX  OCTET STRING (SIZE (0..45))
	MAX-ACCESS read-only
	STATUS  current
	DESCRIPTION
		"Postal address of the LTU (Line/Trunk Unit) shelf.
		Applies to the Local Connection Type.

		Valid values: text, up to 45 characters"
	::= { himBoardLocEntry 2 }


himBoardLocPhoneNo OBJECT-TYPE
	SYNTAX  HimPhoneNumber
	MAX-ACCESS read-only
	STATUS  current
	DESCRIPTION
		"Phone number at the shelf location.

		Valid values: 0-9, *, #, A-D, up to 22 characters"
	::= { himBoardLocEntry 3 }


himBoardLocFaxNo OBJECT-TYPE
	SYNTAX  HimPhoneNumber
	MAX-ACCESS read-only
	STATUS  current
	DESCRIPTION
		"Fax number at the shelf location.

		Valid values: 0-9, *, #, A-D, up to 22 characters"
	::= { himBoardLocEntry 4 }


himIPDA OBJECT IDENTIFIER 	::= { hp4khim 13 }

himIPDAGenData OBJECT IDENTIFIER 	::= { himIPDA 1 }

himIPDAGenTable OBJECT-TYPE
	SYNTAX  SEQUENCE OF HimIPDAGenEntry
	MAX-ACCESS not-accessible
	STATUS  current
	DESCRIPTION
		"General settings that are true for all IPDAs."
	::= { himIPDAGenData 1 }


himIPDAGenEntry OBJECT-TYPE
	SYNTAX  HimIPDAGenEntry
	MAX-ACCESS not-accessible
	STATUS  current
	DESCRIPTION ""
	INDEX {
		himIPDAGenPabxId }
	::= { himIPDAGenTable 1 }


HimIPDAGenEntry ::= SEQUENCE {

	himIPDAGenPabxId  HimPabxId,
	himIPDAGenSpeed   Integer32,
	himIPDAGenMode    INTEGER,
	himIPDAGenPayConn Integer32,
	himIPDAGenSigConn Integer32 }


himIPDAGenPabxId OBJECT-TYPE
	SYNTAX  HimPabxId
	MAX-ACCESS read-only
	STATUS  current
	DESCRIPTION ""
	::= { himIPDAGenEntry 1 }


himIPDAGenSpeed OBJECT-TYPE
	SYNTAX  Integer32 (10 | 100)
	MAX-ACCESS read-only
	STATUS  current
	DESCRIPTION
		"Indicates the bit-rate speed.

		Valid values: 10 Mbits/s; 100 Mbits/s"
	::= { himIPDAGenEntry 2 }


himIPDAGenMode OBJECT-TYPE
	SYNTAX  INTEGER {
			fullduplex(1),
			halfduplex(2),
			other(3) }
	MAX-ACCESS read-only
	STATUS  current
	DESCRIPTION
		"Indicates the bit-rate mode.

		Valid values: Full Duplex, Half Duplex"
	::= { himIPDAGenEntry 3 }


himIPDAGenPayConn OBJECT-TYPE
	SYNTAX  Integer32 (0..255)
	MAX-ACCESS read-only
	STATUS  current
	DESCRIPTION
		"TOS for VoIP payload connections to APs (CP).

		Valid values: 0-255"
	::= { himIPDAGenEntry 4 }


himIPDAGenSigConn OBJECT-TYPE
	SYNTAX  Integer32 (0..255)
	MAX-ACCESS read-only
	STATUS  current
	DESCRIPTION
		"TOS for signalling connections to APs (FA).

		Valid values: 0-255"
	::= { himIPDAGenEntry 5 }


himIPDAGenIPTable OBJECT-TYPE
	SYNTAX  SEQUENCE OF HimIPDAGenIPEntry
	MAX-ACCESS not-accessible
	STATUS  current
	DESCRIPTION
		"General IP settings that are true for all IPDAs."
	::= { himIPDAGenData 2 }


himIPDAGenIPEntry OBJECT-TYPE
	SYNTAX  HimIPDAGenIPEntry
	MAX-ACCESS not-accessible
	STATUS  current
	DESCRIPTION ""
	AUGMENTS {
		himIPDAGenEntry }
	::= { himIPDAGenIPTable 1 }


HimIPDAGenIPEntry ::= SEQUENCE {

	himIPDAGenIPNetAddr     IpAddress,
	himIPDAGenIPNetMask     IpAddress,
	himIPDAGenIPCCAAddr     IpAddress,
	himIPDAGenIPCCBAddr     IpAddress,
	himIPDAGenIPDefRoutAddr IpAddress,
	himIPDAGenIPSurvNetAddr IpAddress }


himIPDAGenIPNetAddr OBJECT-TYPE
	SYNTAX  IpAddress
	MAX-ACCESS read-only
	STATUS  current
	DESCRIPTION
		"IP net address of HiPath LAN segment."
	::= { himIPDAGenIPEntry 1 }


himIPDAGenIPNetMask OBJECT-TYPE
	SYNTAX  IpAddress
	MAX-ACCESS read-only
	STATUS  current
	DESCRIPTION
		"IP net mask of HiPath LAN segment."
	::= { himIPDAGenIPEntry 2 }


himIPDAGenIPCCAAddr OBJECT-TYPE
	SYNTAX  IpAddress
	MAX-ACCESS read-only
	STATUS  current
	DESCRIPTION
		"Address of the CC-A processor within the HiPath LAN segment."
	::= { himIPDAGenIPEntry 3 }


himIPDAGenIPCCBAddr OBJECT-TYPE
	SYNTAX  IpAddress
	MAX-ACCESS read-only
	STATUS  current
	DESCRIPTION
		"Address of the CC-B processor within the HiPath LAN segment.

		Default value: 0.0.0.0"
	::= { himIPDAGenIPEntry 4 }


himIPDAGenIPDefRoutAddr OBJECT-TYPE
	SYNTAX  IpAddress
	MAX-ACCESS read-only
	STATUS  current
	DESCRIPTION
		"IP address of the default router within the HiPath LAN segment."
	::= { himIPDAGenIPEntry 5 }


himIPDAGenIPSurvNetAddr OBJECT-TYPE
	SYNTAX  IpAddress
	MAX-ACCESS read-only
	STATUS  current
	DESCRIPTION
		"The IP address of the survivability net.

		Default value: 0.0.0.0"
	::= { himIPDAGenIPEntry 6 }


himIPDAAPData OBJECT IDENTIFIER 	::= { himIPDA 2 }

himIPDABasicTable OBJECT-TYPE
	SYNTAX  SEQUENCE OF HimIPDABasicEntry
	MAX-ACCESS not-accessible
	STATUS  current
	DESCRIPTION
		"This table stores IPDA information from CM."
	::= { himIPDAAPData 1 }


himIPDABasicEntry OBJECT-TYPE
	SYNTAX  HimIPDABasicEntry
	MAX-ACCESS not-accessible
	STATUS  current
	DESCRIPTION ""
	INDEX {
		himIPDABasicPabxId,
		himIPDABasicLTU }
	::= { himIPDABasicTable 1 }


HimIPDABasicEntry ::= SEQUENCE {

	himIPDABasicPabxId    HimPabxId,
	himIPDABasicLTU       Integer32,
	himIPDABasicConnType  HimShelfNWType,
	himIPDABasicBChanNo   Integer32,
	himIPDABasicConvAMLaw HimYesNo }


himIPDABasicPabxId OBJECT-TYPE
	SYNTAX  HimPabxId
	MAX-ACCESS read-only
	STATUS  current
	DESCRIPTION ""
	::= { himIPDABasicEntry 1 }


himIPDABasicLTU OBJECT-TYPE
	SYNTAX  Integer32 (17..99)
	MAX-ACCESS read-only
	STATUS  current
	DESCRIPTION
		"Line/trunk unit.

		Valid values: 17-99"
	::= { himIPDABasicEntry 2 }


himIPDABasicConnType OBJECT-TYPE
	SYNTAX  HimShelfNWType (0 | 3..4)
	MAX-ACCESS read-only
	STATUS  current
	DESCRIPTION
		"Connection type of the shelf.

		Valid values:
		    APDL -- AP shelf via IP - direct linked
		    APNW -- AP shelf via IP - network"
	::= { himIPDABasicEntry 3 }


himIPDABasicBChanNo OBJECT-TYPE
	SYNTAX  Integer32 (1..120)
	MAX-ACCESS read-only
	STATUS  current
	DESCRIPTION
		"Amount of B-Channels.

		Valid values: 1- 120"
	::= { himIPDABasicEntry 4 }


himIPDABasicConvAMLaw OBJECT-TYPE
	SYNTAX  HimYesNo
	MAX-ACCESS read-only
	STATUS  current
	DESCRIPTION ""
	::= { himIPDABasicEntry 5 }


himIPDAIPTable OBJECT-TYPE
	SYNTAX  SEQUENCE OF HimIPDAIPEntry
	MAX-ACCESS not-accessible
	STATUS  current
	DESCRIPTION
		"This table contains the IP address configuration of the IPDAs."
	::= { himIPDAAPData 2 }


himIPDAIPEntry OBJECT-TYPE
	SYNTAX  HimIPDAIPEntry
	MAX-ACCESS not-accessible
	STATUS  current
	DESCRIPTION ""
	AUGMENTS {
		himIPDABasicEntry }
	::= { himIPDAIPTable 1 }


HimIPDAIPEntry ::= SEQUENCE {

	himIPDAIPAccPtAddr        IpAddress,
	himIPDAIPTAccPtAddr       IpAddress,
	himIPDAIPAccPtRoutAddr    IpAddress,
	himIPDAIPNetMaskNW        IpAddress,
	himIPDAIPAccPtPriRoutAddr IpAddress,
	himIPDAIPNetMaskDL        IpAddress }


himIPDAIPAccPtAddr OBJECT-TYPE
	SYNTAX  IpAddress
	MAX-ACCESS read-only
	STATUS  current
	DESCRIPTION
		"IP address of the access point in the AP network."
	::= { himIPDAIPEntry 1 }


himIPDAIPTAccPtAddr OBJECT-TYPE
	SYNTAX  IpAddress
	MAX-ACCESS read-only
	STATUS  current
	DESCRIPTION
		"IP address for the TAP/Service PC link at the access point.
		This IP address must be in the same network as the access point in the AP network."
	::= { himIPDAIPEntry 2 }


himIPDAIPAccPtRoutAddr OBJECT-TYPE
	SYNTAX  IpAddress
	MAX-ACCESS read-only
	STATUS  current
	DESCRIPTION
		"IP address of the gateway (IP address of the router in the AP network)."
	::= { himIPDAIPEntry 3 }


himIPDAIPNetMaskNW OBJECT-TYPE
	SYNTAX  IpAddress
	MAX-ACCESS read-only
	STATUS  current
	DESCRIPTION
		"Netmask of the network to which the respective Access Point in AP network belongs."
	::= { himIPDAIPEntry 4 }


himIPDAIPAccPtPriRoutAddr OBJECT-TYPE
	SYNTAX  IpAddress
	MAX-ACCESS read-only
	STATUS  current
	DESCRIPTION
		"IP address of the primary signalling router for NCUI board (IP address of the router in the HiPath 4000 LAN segment). Required if the connection type is APDL."
	::= { himIPDAIPEntry 5 }


himIPDAIPNetMaskDL OBJECT-TYPE
	SYNTAX  IpAddress
	MAX-ACCESS read-only
	STATUS  current
	DESCRIPTION
		"Netmask of the network to which the Access Point in AP internal network belongs."
	::= { himIPDAIPEntry 6 }


himIPDALocTable OBJECT-TYPE
	SYNTAX  SEQUENCE OF HimIPDALocEntry
	MAX-ACCESS not-accessible
	STATUS  current
	DESCRIPTION
		"This table contains the location data of the boards. It is only available for boards of type DSX, LTUCA, LTUCE and LTUCX."
	::= { himIPDAAPData 3 }


himIPDALocEntry OBJECT-TYPE
	SYNTAX  HimIPDALocEntry
	MAX-ACCESS not-accessible
	STATUS  current
	DESCRIPTION ""
	AUGMENTS {
		himIPDABasicEntry }
	::= { himIPDALocTable 1 }


HimIPDALocEntry ::= SEQUENCE {

	himIPDALocId      Integer32,
	himIPDALocLoc     OCTET STRING,
	himIPDALocPhoneNo HimPhoneNumber,
	himIPDALocFaxNo   HimPhoneNumber }


himIPDALocId OBJECT-TYPE
	SYNTAX  Integer32 (0..999)
	MAX-ACCESS read-only
	STATUS  current
	DESCRIPTION
		"Describes the location of the switch for the system configurator.

		Valid values: 0-999"
	::= { himIPDALocEntry 1 }


himIPDALocLoc OBJECT-TYPE
	SYNTAX  OCTET STRING (SIZE (0..45))
	MAX-ACCESS read-only
	STATUS  current
	DESCRIPTION
		"Postal address of the LTU (Line/Trunk Unit) shelf.
		Applies to the Local Connection Type.

		Valid values: text, up to 45 characters"
	::= { himIPDALocEntry 2 }


himIPDALocPhoneNo OBJECT-TYPE
	SYNTAX  HimPhoneNumber
	MAX-ACCESS read-only
	STATUS  current
	DESCRIPTION
		"Phone number at the shelf location.

		Valid values: 0-9, *, #, A-D, up to 22 characters"
	::= { himIPDALocEntry 3 }


himIPDALocFaxNo OBJECT-TYPE
	SYNTAX  HimPhoneNumber
	MAX-ACCESS read-only
	STATUS  current
	DESCRIPTION
		"Fax number at the shelf location.

		Valid values: 0-9, *, #, A-D, up to 22 characters"
	::= { himIPDALocEntry 4 }


himInfo OBJECT IDENTIFIER 	::= { hp4khim 14 }

-- The himInfo group

himSubagentLastMsgNo OBJECT-TYPE
	SYNTAX  Integer32
	MAX-ACCESS read-only
	STATUS  current
	DESCRIPTION
		"The last message, warning or error number
		issued by the Him subagent."
	::= { himInfo 1 }


himSubagentLastMsgText OBJECT-TYPE
	SYNTAX  OCTET STRING
	MAX-ACCESS read-only
	STATUS  current
	DESCRIPTION
		"The last message, warning or error text
		issued by the Him subagent."
	::= { himInfo 2 }


himResultData OBJECT-TYPE
	SYNTAX  Integer32
	MAX-ACCESS read-write
	STATUS  current
	DESCRIPTION
		"Is used for agent internal communication.
		Contains the PabxId of a Hicom for which
		the last discovery process was conveyed.
		Is SET by the discovery agent and
		indicates the availability of new discovered data.
		The new data is to be incorporated by the subagent
		into the subagent's data base."
	::= { himInfo 3 }


-- BEGIN BLOCK discov

himDiscovery OBJECT IDENTIFIER 	::= { hp4khim 15 }

himChanges OBJECT-TYPE
	SYNTAX  Counter32
	MAX-ACCESS read-only
	STATUS  current
	DESCRIPTION
		"Indicates the number of finished HIM discoveries - corresponds to the number of hicomHWDiscovXXX traps sent out."
	::= { himDiscovery 1 }


-- The himDiscovTable table

himDiscovTable OBJECT-TYPE
	SYNTAX  SEQUENCE OF HimDiscovEntry
	MAX-ACCESS not-accessible
	STATUS  current
	DESCRIPTION
		"The table describing the status concerning
		discovery of HIM information."
	::= { himDiscovery 2 }


himDiscovEntry OBJECT-TYPE
	SYNTAX  HimDiscovEntry
	MAX-ACCESS not-accessible
	STATUS  current
	DESCRIPTION
		"The entry describes the status of the discovery process. It is designed to comply with the structure of discovery entries in the hicom MIB, even though data is only provided for one switch."
	INDEX {
		himDiscovPabxId }
	::= { himDiscovTable 1 }


HimDiscovEntry ::= SEQUENCE {

	himDiscovPabxId       HimPabxId,
	himDiscovPabxMnemonic DisplayString,
	himDiscovStatus       DiscoveryStates,
	himDiscovMode         DiscoveryModes,
	himDiscovTimDat       DisplayString,
	himDiscovErrTimDat    DisplayString }


himDiscovPabxId OBJECT-TYPE
	SYNTAX  HimPabxId
	MAX-ACCESS read-only
	STATUS  current
	DESCRIPTION
		"Unique identifier of the Hicom being discovered."
	::= { himDiscovEntry 1 }


himDiscovPabxMnemonic OBJECT-TYPE
	SYNTAX  DisplayString
	MAX-ACCESS read-only
	STATUS  current
	DESCRIPTION
		"Name of the Hicom system."
	::= { himDiscovEntry 2 }


himDiscovStatus OBJECT-TYPE
	SYNTAX  DiscoveryStates
	MAX-ACCESS read-write
	STATUS  current
	DESCRIPTION
		"Status of discovery process.
		A managment station may initiate a discovery by setting
		this variable to value busy.
		The other values are set by the agent."
	::= { himDiscovEntry 3 }


himDiscovMode OBJECT-TYPE
	SYNTAX  DiscoveryModes
	MAX-ACCESS read-write
	STATUS  current
	DESCRIPTION
		"Mode of discovery process."
	::= { himDiscovEntry 4 }


himDiscovTimDat OBJECT-TYPE
	SYNTAX  DisplayString
	MAX-ACCESS read-only
	STATUS  current
	DESCRIPTION
		"Date and time (year, month, day, hour, minute, second)
		the last successful discovery action was performed for the      Hicom."
	::= { himDiscovEntry 5 }


himDiscovErrTimDat OBJECT-TYPE
	SYNTAX  DisplayString
	MAX-ACCESS read-only
	STATUS  current
	DESCRIPTION
		"Date and time (year, month, day, hour, minute, second)
		the last failed discovery action was performed for the  Hicom."
	::= { himDiscovEntry 6 }


himMibConformance OBJECT IDENTIFIER 	::= { hp4khim 20 }

himMibGroups OBJECT IDENTIFIER 	::= { himMibConformance 1 }

himWelcomePageGroup OBJECT-GROUP
	OBJECTS {
		himWelPgPabxId,
		himWelPgSysNo,
		himHP4KVersion,
		himSystemRelease,
		himRevisionLevel,
		himHWArchitecture,
		himHWArchitectureType,
		himOperationMode,
		himSWUProc1,
		himSWUMemory1,
		himSWUProc2,
		himSWUMemory2 }
	STATUS  current
	DESCRIPTION ""
	::= { himMibGroups 1 }

himSwitchDataGroup OBJECT-GROUP
	OBJECTS {
		himTechInfoPabxId,
		himTechInfoInfoNo,
		himTechInfoDate,
		himTechInfoTechnicalData,
		himTechInfoNumber,
		himTechInfoExtraText,
		himNotepadDataPabxId,
		himNotepadDataInfoNo,
		himNotepadDataDate,
		himNotepadDataText,
		himProjPlanPabxId,
		himProjPlanInfoFile,
		himProjPlanInfoCreationDate,
		himProjPlanInfoCreationTime }
	STATUS  current
	DESCRIPTION ""
	::= { himMibGroups 2 }

himSpecGroup OBJECT-GROUP
	OBJECTS {
		himSpecShelfDataPabxId,
		himSpecShelfDataAddress,
		himSpecShelfDataFrameType,
		himSpecShelfDataLTU,
		himSpecShelfDataNetworkType,
		himSpecShelfDataNetworkAddress,
		himSpecShelfDataRemote,
		himSpecShelfDataLocation,
		himSpecShelfDataLTUC,
		himSWUBoardPabxId,
		himSWUBoardPEN,
		himSWUBoardOverlayLTU,
		himSWUBoardType,
		himSWUBoardNominal,
		himSWUBoardActual,
		hhimSWUBoardFirmware,
		himSWUBoardRev,
		himSWUBoardFunctId,
		himSWUBoardMode,
		himSWUBoardLWNo,
		himSWUBoardLWInterVer,
		himSWUBoardLWName,
		himSWUBoardLWDate }
	STATUS  current
	DESCRIPTION ""
	::= { himMibGroups 3 }

himSWUPeripheryGroup OBJECT-GROUP
	OBJECTS {
		himPSIOAssPabxId,
		himPSIOAssAssembly,
		himPSIOAssPEN,
		himPSIOAssActual,
		himPSIOAssFirmware,
		himSerialLinePabxId,
		himSerialLineBoardType,
		himSerialLineNumber,
		himSerialLineSpeed,
		himSerialLineLogDevName,
		himSerialLineDevType,
		himSerialLineType,
		himSCSIDevPabxId,
		himSCSIDevId,
		himSCSIDevType,
		himSCSIDevName,
		himSCSIDevFirmware,
		himSCSIDevLoadDrive }
	STATUS  current
	DESCRIPTION ""
	::= { himMibGroups 4 }

himCentralSwitchGroup OBJECT-GROUP
	OBJECTS {
		himCabPabxId,
		himCabAddr,
		himCabPhysAddr,
		himCabCabinet,
		himCabPartNo,
		himCabShelfNo,
		himCabFrame,
		himCabPid1,
		himCabPid2,
		himCabPid3,
		himCabLTUNo,
		himMemScalingPabxId,
		himMemScalingUnit,
		himMemScalingUsed,
		himMemScalingMaxUsed,
		himMemScalingAllocated,
		himMemScalingStandard,
		himMemScalingSysMax }
	STATUS  current
	DESCRIPTION ""
	::= { himMibGroups 5 }

himGeneralSwitchGroup OBJECT-GROUP
	OBJECTS {
		himDBConfSysPabxId,
		himDBConfSysClass1,
		himDBConfSysClass2,
		himDBConfSysHWAss1,
		himDBConfSysHWAss2,
		himDBConfSysDevLine1,
		himDBConfSysDevLine2,
		himDBConfSysOpMode,
		himDBConfSysResType,
		himDBConfSysHWArch,
		himDBConfSysHWArchType,
		himDBConfSysNo,
		himDBConfSysLoc,
		himDBConfSysBaseApp,
		himDBConfSysDBApp,
		himDBConfSysID,
		himDBConfHWPabxId,
		himDBConfHWLTG,
		himDBConfHWLTU,
		himDBConfHWLines,
		himDBConfHWPorts,
		himDBConfHWPBC,
		himDBConfHWMTSBdPerGSN,
		himDBConfHWSIUPPerLTU,
		himDBConfHWDIUCPerLTU,
		himDBConfHWHwyPerMTSBd,
		himDBConfHWHDLCPerDCL,
		himDBConfHWPBCPerDCL,
		himDBConfHWStdSIULine,
		himDBConfHWConfLine,
		himDBConfHWDBDim,
		himDBConfHWTableVer,
		himHWDataPabxId,
		himHWArch,
		himHWArchType,
		himHWOpMode,
		himHWSWUProc1,
		himHWSWUMem1,
		himHWSWUProc2,
		himHWSWUMem2,
		himHWADPProc,
		himHWADPMem,
		himLWDataOnCBPabxId,
		himLWOnCBAss,
		himLWOnCBPBCAddr,
		himLWOnCBFileName,
		himLWOnCBProdTime,
		himLWOnProcPabxId,
		himLWOnProcAss,
		himLWOnProcInfoType,
		himLWOnProcLWId,
		himLWOnProcLWIdCMP,
		himLWOnProcLWIdLP,
		himLWOnCSIUPabxId,
		himLWOnCSIUProc,
		himLWOnCSIUSlot,
		himLWOnCSIUNominal,
		himLWOnCSIUActual,
		himLWOnCSIULWNo,
		himLWOnCSIUFileName,
		himLWOnCSIUFileProd,
		himMacAddrPabxId,
		himMacAddrProc,
		himMacAddrInfoType,
		himMacAddrCLan,
		himMacAddrIPDA }
	STATUS  current
	DESCRIPTION ""
	::= { himMibGroups 6 }

himFeaturesGroup OBJECT-GROUP
	OBJECTS {
		himMacAddrPabxId,
		himMacAddrProc,
		himMacAddrCLan,
		himMacAddrIPDA,
		himMarkFeatPabxId,
		himMarkFeatVer,
		himMarkFeatSerNo,
		himMarkFeatHWId,
		himMarkFeatInstallDate,
		himMarkFeatExpiryDate,
		himMarkFeatConfCode,
		himMarkFeatTrialModeAct,
		himMarkFeatTrialRemDays,
		himSalesFeatPabxId,
		himSalesFeatMarketPackId,
		himSalesFeatMarketPack,
		himSalesFeatContract,
		himSalesFeatUsed,
		himSalesFeatFree,
		himSalesFeatMarkForTrial,
		himTechFeatPabxId,
		himTechFeatId,
		himTechFeatName,
		himTechFeatState }
	STATUS  current
	DESCRIPTION ""
	::= { himMibGroups 7 }

himAPSPatchesGroup OBJECT-GROUP
	OBJECTS {
		himSwitchAPSPabxId,
		himSwitchAPSName,
		himSwitchAPSCorrVer,
		himSwitchAPSPartNo,
		himReplAMOPabxId,
		himReplAMOAPS,
		himReplAMOName,
		himReplAMOInAPSDir,
		himReplAMOSubsystem,
		himPatchInfoPabxId,
		himPatchInfoPatchNo,
		himPatchInfoPatchGroup,
		himPatchInfoOpt,
		himPatchInfoActHD,
		himPatchInfoActADP,
		himPatchInfoActBP }
	STATUS  current
	DESCRIPTION ""
	::= { himMibGroups 8 }

himSWVersionGroup OBJECT-GROUP
	OBJECTS {
		himSWVerOnProcPabxId,
		himSWVerOnProcSrc,
		himSWVerOnProcSWVer,
		himSWVerOnProcItemCodeNoPrefix,
		himSWVerOnProcHP4KVer,
		himSWVerOnProcSysRel,
		himSWVerOnProcCountry,
		himSWVerOnProcCountryCode,
		himSWVerOnProcRevNo }
	STATUS  current
	DESCRIPTION ""
	::= { himMibGroups 9 }

himSWPkgVersionGroup OBJECT-GROUP
	OBJECTS {
		himSWPkgVerPabxId,
		himSWPkgVerPkgAbbr,
		himSWPkgVerPkgName,
		himSWPkgVerVersion,
		himSWPkgVerInstAt,
		himSWPkgVerStatus }
	STATUS  current
	DESCRIPTION ""
	::= { himMibGroups 10 }

himSystemGroup OBJECT-GROUP
	OBJECTS {
		himSysBasicPabxId,
		himSysBasicDomain,
		himSysBasicNodeNo,
		himSysBasicLEGK,
		himSysLANCardsPabxId,
		himSysLANCardsIPAddr,
		himSysLANCardsNetMask,
		himSysLANCardsBroadCast,
		himSysLANCardsType,
		himSysLANCardsStatus,
		himSysHostsPabxId,
		himSysHostsNo,
		himSysHostsIPAddr,
		himSysHostsName,
		himSysWAMLConnPabxId,
		himSysWAMLConnLTG,
		himSysWAMLConnLTU,
		himSysWAMLConnSlot,
		himSysWAMLConnRufNr,
		himSysWAMLConnBChl,
		himSysWAMLConnStatus,
		himSysWAMLConnIPPabxId,
		himSysWAMLConnIPLTG,
		himSysWAMLConnIPLTU,
		himSysWAMLConnIPSlot,
		himSysWAMLConnIPIfName,
		himSysWAMLConnIPAddr,
		himSysWAMLConnIPNetMask }
	STATUS  current
	DESCRIPTION ""
	::= { himMibGroups 11 }

himBoardsGroup OBJECT-GROUP
	OBJECTS {
		himBoardBasicPabxId,
		himBoardBasicLTG,
		himBoardBasicLTU,
		himBoardBasicSlot,
		himBoardBasicFuncId,
		himBoardBasicCat,
		himBoardBasicName,
		himBoardBasicVOIPSec,
		himBoardBasicLWVar,
		himBoardBasicNoCirc,
		himBoardIPGwyIPAddr,
		himBoardIPSrcIPAddr,
		himBoardIPNetMask,
		himBoardIPDefRouter,
		himBoardIPCustLANIP,
		himBoardIPSTMI2IGWSubMask,
		himBoardIPDefGWIP,
		himBoardIPManStatIP,
		himBoardIPManStatPort,
		himBoardIPBckpServIP,
		himBoardIPBckpServPort,
		himBoardLocId,
		himBoardLocLoc,
		himBoardLocPhoneNo,
		himBoardLocFaxNo }
	STATUS  current
	DESCRIPTION ""
	::= { himMibGroups 12 }

himIPDAGroup OBJECT-GROUP
	OBJECTS {
		himIPDABasicPabxId,
		himIPDABasicLTU,
		himIPDABasicConnType,
		himIPDABasicBChanNo,
		himIPDABasicConvAMLaw,
		himIPDAGenPabxId,
		himIPDAGenSpeed,
		himIPDAGenMode,
		himIPDAGenPayConn,
		himIPDAGenSigConn,
		himIPDAGenIPNetAddr,
		himIPDAGenIPNetMask,
		himIPDAGenIPCCAAddr,
		himIPDAGenIPCCBAddr,
		himIPDAGenIPDefRoutAddr,
		himIPDAGenIPSurvNetAddr,
		himIPDAIPAccPtAddr,
		himIPDAIPTAccPtAddr,
		himIPDAIPAccPtRoutAddr,
		himIPDAIPNetMaskNW,
		himIPDAIPAccPtPriRoutAddr,
		himIPDAIPNetMaskDL,
		himIPDALocId,
		himIPDALocLoc,
		himIPDALocPhoneNo,
		himIPDALocFaxNo }
	STATUS  current
	DESCRIPTION ""
	::= { himMibGroups 13 }

himInfoGroup OBJECT-GROUP
	OBJECTS {
		himSubagentLastMsgNo,
		himSubagentLastMsgText,
		himResultData }
	STATUS  current
	DESCRIPTION ""
	::= { himMibGroups 14 }

himDiscoveryGroup OBJECT-GROUP
	OBJECTS {
		himChanges,
		himDiscovPabxId,
		himDiscovPabxMnemonic,
		himDiscovStatus,
		himDiscovMode,
		himDiscovTimDat,
		himDiscovErrTimDat }
	STATUS  current
	DESCRIPTION ""
	::= { himMibGroups 15 }

himTrapsGroup NOTIFICATION-GROUP
	NOTIFICATIONS {
		internalMessageHimSubagent,
		internalWarningHimSubagent,
		internalErrorHimSubagent,
		himDiscovSucc,
		himDiscovErr,
		himDiscovBusy }
	STATUS  current
	DESCRIPTION ""
	::= { himMibGroups 16 }

-- Traps / Notifications

himTrapGroup OBJECT IDENTIFIER 	::= { hp4khim 21 }

himTrapVariables OBJECT IDENTIFIER 	::= { himTrapGroup 1 }

-- Trap Variables

himTrapPabxId OBJECT-TYPE
	SYNTAX  Integer32
	MAX-ACCESS not-accessible
	STATUS  current
	DESCRIPTION
		"Unique identifier of a Hicom system."
	::= { himTrapVariables 1 }


himTrapPabxMnemonic OBJECT-TYPE
	SYNTAX  DisplayString
	MAX-ACCESS not-accessible
	STATUS  current
	DESCRIPTION
		"Mnemonic name of the Hicom system."
	::= { himTrapVariables 2 }


-- Message Traps

himTraps OBJECT IDENTIFIER 	::= { himTrapGroup 2 }


internalMessageHimSubagent NOTIFICATION-TYPE
	OBJECTS {
		himSubagentLastMsgNo,
		himSubagentLastMsgText}
	STATUS  current
	DESCRIPTION
		"An internalMessage trap contains an informational
		message generated by the subagent."
	::= { himTraps 0 }


-- Warning Traps

internalWarningHimSubagent NOTIFICATION-TYPE
	OBJECTS {
		himSubagentLastMsgNo,
		himSubagentLastMsgText}
	STATUS  current
	DESCRIPTION
		"An internalWarning trap contains a warning message
		generated by a subagent."
	::= { himTraps 1 }


-- Error Traps

internalErrorHimSubagent NOTIFICATION-TYPE
	OBJECTS {
		himSubagentLastMsgNo,
		himSubagentLastMsgText}
	STATUS  current
	DESCRIPTION
		"An internalError trap contains an error message
		generated by a subagent.
		After issuing this trap, the agent terminates."
	::= { himTraps 2 }


-- him discovery successfully terminated

himDiscovSucc NOTIFICATION-TYPE
	OBJECTS {
		himTrapPabxId,
		himTrapPabxMnemonic}
	STATUS  current
	DESCRIPTION
		"A himDiscovSucc trap indicates the
		successful termination of a discovery process."
	::= { himTraps 10 }


-- him discovery unsuccessfully terminated

himDiscovErr NOTIFICATION-TYPE
	OBJECTS {
		himTrapPabxId,
		himTrapPabxMnemonic}
	STATUS  current
	DESCRIPTION
		"A himDiscovErr trap signifies the
		unsuccessful termination of a discovery process."
	::= { himTraps 11 }


-- him discovery is busy

himDiscovBusy NOTIFICATION-TYPE
	OBJECTS {
		himTrapPabxId,
		himTrapPabxMnemonic}
	STATUS  current
	DESCRIPTION
		"A himDiscovBusy trap signifies
		that a sw discovery process is running."
	::= { himTraps 19 }

END
