--			Ascend mibt3int MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBT3INT-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibt3InterfaceProfile  OBJECT IDENTIFIER ::= { configuration 156}

	-- The mibt3InterfaceProfile table
	--
	-- This table contains parameters for the mibt3InterfaceProfile profile
	--

    mibt3InterfaceProfileTable	OBJECT-TYPE
	SYNTAX		SEQUENCE OF Mibt3InterfaceProfileEntry
	ACCESS		not-accessible
	STATUS		mandatory
	DESCRIPTION	"A list of mibt3InterfaceProfile profile entries."
	::= { mibt3InterfaceProfile 1 }

    mibt3InterfaceProfileEntry	OBJECT-TYPE
	SYNTAX		Mibt3InterfaceProfileEntry
	ACCESS		not-accessible
	STATUS		mandatory
	DESCRIPTION	"A mibt3InterfaceProfile entry containing objects that
			 maps to the parameters of mibt3InterfaceProfile profile."
	INDEX		{ t3InterfaceProfile-Shelf-o, t3InterfaceProfile-Slot-o, t3InterfaceProfile-Item-o }
	::= { mibt3InterfaceProfileTable 1 }

    Mibt3InterfaceProfileEntry ::=
	SEQUENCE {
	    t3InterfaceProfile-Shelf-o
		INTEGER,
	    t3InterfaceProfile-Slot-o
		INTEGER,
	    t3InterfaceProfile-Item-o
		INTEGER,
	    t3InterfaceProfile-Name
		DisplayString,
	    t3InterfaceProfile-PhysicalAddress-Shelf
		INTEGER,
	    t3InterfaceProfile-PhysicalAddress-Slot
		INTEGER,
	    t3InterfaceProfile-PhysicalAddress-ItemNumber
		INTEGER,
	    t3InterfaceProfile-LimControl-PrimaryLpm
		INTEGER,
	    t3InterfaceProfile-LimControl-ActiveLine
		INTEGER,
	    t3InterfaceProfile-Ds3Profile-Name
		DisplayString,
	    t3InterfaceProfile-Ds3Profile-PhysicalAddress-Shelf
		INTEGER,
	    t3InterfaceProfile-Ds3Profile-PhysicalAddress-Slot
		INTEGER,
	    t3InterfaceProfile-Ds3Profile-PhysicalAddress-ItemNumber
		INTEGER,
	    t3InterfaceProfile-Ds3Profile-Enabled
		INTEGER,
	    t3InterfaceProfile-Ds3Profile-FrameType
		INTEGER,
	    t3InterfaceProfile-Ds3Profile-LineLength
		INTEGER,
	    t3InterfaceProfile-Ds3Profile-Loopback
		INTEGER,
	    t3InterfaceProfile-Ds3Profile-StatusChangeTrapEnable
		INTEGER,
	    t3InterfaceProfile-Action-o
		INTEGER
	}

    t3InterfaceProfile-Shelf-o	OBJECT-TYPE
	SYNTAX	INTEGER
	ACCESS	read-only
	STATUS	mandatory
	DESCRIPTION	""
	::= { mibt3InterfaceProfileEntry 1 }

    t3InterfaceProfile-Slot-o	OBJECT-TYPE
	SYNTAX	INTEGER
	ACCESS	read-only
	STATUS	mandatory
	DESCRIPTION	""
	::= { mibt3InterfaceProfileEntry 2 }

    t3InterfaceProfile-Item-o	OBJECT-TYPE
	SYNTAX	INTEGER
	ACCESS	read-only
	STATUS	mandatory
	DESCRIPTION	""
	::= { mibt3InterfaceProfileEntry 3 }

    t3InterfaceProfile-Name	OBJECT-TYPE
	SYNTAX	DisplayString
	ACCESS	read-write
	STATUS	mandatory
	DESCRIPTION	"Name of T3 Interface profile"
	::= { mibt3InterfaceProfileEntry 4 }

    t3InterfaceProfile-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibt3InterfaceProfileEntry 5 }

    t3InterfaceProfile-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibt3InterfaceProfileEntry 6 }

    t3InterfaceProfile-PhysicalAddress-ItemNumber	OBJECT-TYPE
	SYNTAX	INTEGER
	ACCESS	read-write
	STATUS	mandatory
	DESCRIPTION	"A number that specifies an addressable entity within the context of shelf and slot."
	::= { mibt3InterfaceProfileEntry 7 }

    t3InterfaceProfile-LimControl-PrimaryLpm	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"Which LPM is the primary control for the interface"
	::= { mibt3InterfaceProfileEntry 8 }

    t3InterfaceProfile-LimControl-ActiveLine	OBJECT-TYPE
	SYNTAX	INTEGER {
		    workingLine (1),
		    protectionLine (2),
		    backupLine (3)
		}
	ACCESS	read-write
	STATUS	mandatory
	DESCRIPTION	"Administrative request for current active line or line interface"
	::= { mibt3InterfaceProfileEntry 9 }

    t3InterfaceProfile-Ds3Profile-Name	OBJECT-TYPE
	SYNTAX	DisplayString
	ACCESS	read-write
	STATUS	mandatory
	DESCRIPTION	"Name of DS3 line."
	::= { mibt3InterfaceProfileEntry 10 }

    t3InterfaceProfile-Ds3Profile-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibt3InterfaceProfileEntry 11 }

    t3InterfaceProfile-Ds3Profile-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibt3InterfaceProfileEntry 12 }

    t3InterfaceProfile-Ds3Profile-PhysicalAddress-ItemNumber	OBJECT-TYPE
	SYNTAX	INTEGER
	ACCESS	read-write
	STATUS	mandatory
	DESCRIPTION	"A number that specifies an addressable entity within the context of shelf and slot."
	::= { mibt3InterfaceProfileEntry 13 }

    t3InterfaceProfile-Ds3Profile-Enabled	OBJECT-TYPE
	SYNTAX	INTEGER {
		    no (1),
		    yes (2)
		}
	ACCESS	read-write
	STATUS	mandatory
	DESCRIPTION	"TRUE if the line is enabled, otherwise FALSE."
	::= { mibt3InterfaceProfileEntry 14 }

    t3InterfaceProfile-Ds3Profile-FrameType	OBJECT-TYPE
	SYNTAX	INTEGER {
		    m13 (1),
		    cBitParity (2)
		}
	ACCESS	read-write
	STATUS	mandatory
	DESCRIPTION	"Determines the DS3 frame format, also known as the DS3 application."
	::= { mibt3InterfaceProfileEntry 15 }

    t3InterfaceProfile-Ds3Profile-LineLength	OBJECT-TYPE
	SYNTAX	INTEGER {
		    n-0225 (1),
		    n-226450 (2)
		}
	ACCESS	read-write
	STATUS	mandatory
	DESCRIPTION	"The length in feet of the Rx and Tx lines to a DSX-3 cross connect. Double these values for direct connection."
	::= { mibt3InterfaceProfileEntry 16 }

    t3InterfaceProfile-Ds3Profile-Loopback	OBJECT-TYPE
	SYNTAX	INTEGER {
		    noLoopback (1),
		    lineLoopback (2),
		    localLoopback (3)
		}
	ACCESS	read-write
	STATUS	mandatory
	DESCRIPTION	"Loopback mode."
	::= { mibt3InterfaceProfileEntry 17 }

    t3InterfaceProfile-Ds3Profile-StatusChangeTrapEnable	OBJECT-TYPE
	SYNTAX	INTEGER {
		    no (1),
		    yes (2)
		}
	ACCESS	read-write
	STATUS	mandatory
	DESCRIPTION	"When set to No, do not send dsx3LineStatusChangeTrapEnable trap. If Yes, send traps. The default is No."
	::= { mibt3InterfaceProfileEntry 20 }

    t3InterfaceProfile-Action-o	OBJECT-TYPE
	SYNTAX	INTEGER {
		    noAction (1),
		    createProfile (2),
		    deleteProfile (3)
		}
	ACCESS	read-write
	STATUS	mandatory
	DESCRIPTION	""
	::= { mibt3InterfaceProfileEntry 19 }


	-- The mibt3InterfaceProfile__master_ds1_index table
	--
	-- This table contains parameters for the mibt3InterfaceProfile__master_ds1_index profile
	--

    mibt3InterfaceProfile-MasterDs1IndexTable	OBJECT-TYPE
	SYNTAX		SEQUENCE OF Mibt3InterfaceProfile-MasterDs1IndexEntry
	ACCESS		not-accessible
	STATUS		mandatory
	DESCRIPTION	"A list of mibt3InterfaceProfile__master_ds1_index profile entries."
	::= { mibt3InterfaceProfile 18 }

    mibt3InterfaceProfile-MasterDs1IndexEntry	OBJECT-TYPE
	SYNTAX		Mibt3InterfaceProfile-MasterDs1IndexEntry
	ACCESS		not-accessible
	STATUS		mandatory
	DESCRIPTION	"A mibt3InterfaceProfile__master_ds1_index entry containing objects that
			 maps to the parameters of mibt3InterfaceProfile__master_ds1_index profile."
	INDEX		{ t3InterfaceProfile-MasterDs1Index-Shelf-o, t3InterfaceProfile-MasterDs1Index-Slot-o, t3InterfaceProfile-MasterDs1Index-Item-o, t3InterfaceProfile-MasterDs1Index-Index-o }
	::= { mibt3InterfaceProfile-MasterDs1IndexTable 1 }

    Mibt3InterfaceProfile-MasterDs1IndexEntry ::=
	SEQUENCE {
	    t3InterfaceProfile-MasterDs1Index-Shelf-o
		INTEGER,
	    t3InterfaceProfile-MasterDs1Index-Slot-o
		INTEGER,
	    t3InterfaceProfile-MasterDs1Index-Item-o
		INTEGER,
	    t3InterfaceProfile-MasterDs1Index-Index-o
		INTEGER,
	    t3InterfaceProfile-MasterDs1Index
		INTEGER
	}

    t3InterfaceProfile-MasterDs1Index-Shelf-o	OBJECT-TYPE
	SYNTAX	INTEGER
	ACCESS	read-only
	STATUS	mandatory
	DESCRIPTION	""
	::= { mibt3InterfaceProfile-MasterDs1IndexEntry 1 }

    t3InterfaceProfile-MasterDs1Index-Slot-o	OBJECT-TYPE
	SYNTAX	INTEGER
	ACCESS	read-only
	STATUS	mandatory
	DESCRIPTION	""
	::= { mibt3InterfaceProfile-MasterDs1IndexEntry 2 }

    t3InterfaceProfile-MasterDs1Index-Item-o	OBJECT-TYPE
	SYNTAX	INTEGER
	ACCESS	read-only
	STATUS	mandatory
	DESCRIPTION	""
	::= { mibt3InterfaceProfile-MasterDs1IndexEntry 3 }

    t3InterfaceProfile-MasterDs1Index-Index-o	OBJECT-TYPE
	SYNTAX	INTEGER
	ACCESS	read-only
	STATUS	mandatory
	DESCRIPTION	""
	::= { mibt3InterfaceProfile-MasterDs1IndexEntry 4 }

    t3InterfaceProfile-MasterDs1Index	OBJECT-TYPE
	SYNTAX	INTEGER
	ACCESS	read-write
	STATUS	mandatory
	DESCRIPTION	"The item index of the Master T1 profile to use on the DS1 link"
	::= { mibt3InterfaceProfile-MasterDs1IndexEntry 5 }

END
