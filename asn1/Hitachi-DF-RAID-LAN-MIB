--/*******************************************************************/
--/* Copyright (C) 2001,Hitachi,Ltd.                                 */
--/*******************************************************************/
--  Hitachi DF Disk Array
--  Version 8.0
--        (2001.10.16)

--  This MIB details the Hitachi Disk Array (RAID)

Hitachi-DF-RAID-LAN-MIB DEFINITIONS ::= BEGIN

IMPORTS
     enterprises, IpAddress, Counter, Gauge, TimeTicks
          FROM RFC1155-SMI
     DisplayString
          FROM RFC1213-MIB
     OBJECT-TYPE
          FROM RFC-1212 
     TRAP-TYPE
          FROM RFC-1215;


-- Note: Below the 'hitachi' subtree follows Hitachi internal standards.
--       enterprises = iso(1).org(3).dod(6).internet(1).private(4).1

hitachi                OBJECT IDENTIFIER ::= { enterprises 116 }
system                 OBJECT IDENTIFIER ::= { hitachi 3 }
storage                OBJECT IDENTIFIER ::= { system 11 } 
dfraid                 OBJECT IDENTIFIER ::= { storage 1 }
dfraidLan              OBJECT IDENTIFIER ::= { dfraid 2 }
systemExMib            OBJECT IDENTIFIER ::= { hitachi 5 }
storageExMib           OBJECT IDENTIFIER ::= { systemExMib 11 } 
dfraidExMib            OBJECT IDENTIFIER ::= { storageExMib 1 }
dfraidLanExMib           OBJECT IDENTIFIER ::= { dfraidExMib 2 }


-- Note: Below the 'dfraidLanExMib' subtree is controlled by this MIB document.      

dfSystemParameter    OBJECT IDENTIFIER ::= {dfraidLanExMib 1 }
dfWarningCondition    OBJECT IDENTIFIER ::= {dfraidLanExMib 2 }
dfCommandExecutionCondition    OBJECT IDENTIFIER ::= {dfraidLanExMib 3 }
dfCacheLoadCondition    OBJECT IDENTIFIER ::= {dfraidLanExMib 4 }
-- LUN Security information
dfLUNS               OBJECT IDENTIFIER ::= { dfraidLanExMib 5 }
-- Port information
dfPort               OBJECT IDENTIFIER ::= { dfraidLanExMib 6 }
dfCommandExecutionInternalCondition    OBJECT IDENTIFIER ::= {dfraidLanExMib 7 }





dfSystemProductName OBJECT-TYPE
                  SYNTAX    DisplayString (SIZE (0..24))
                  ACCESS    read-only
                  STATUS    mandatory
                  DESCRIPTION
                             "The description of the product name.
                              It is mandatory that this only contain
                              printable ASCII characters."
                  ::= { dfSystemParameter 1 }

dfSystemMicroRevision OBJECT-TYPE
                  SYNTAX    DisplayString (SIZE (0..6))
                  ACCESS    read-only
                  STATUS    mandatory
                  DESCRIPTION
                             "The software revision.
                              It is mandatory that this only contain
                              printable ASCII characters."
                  ::= { dfSystemParameter 2 }

dfSystemSerialNumber OBJECT-TYPE
                  SYNTAX    INTEGER
                  ACCESS    read-only
                  STATUS    mandatory
                  DESCRIPTION
                             "The serial number."
                  ::= { dfSystemParameter 3 }

dfRegressionStatus OBJECT-TYPE
                  SYNTAX    INTEGER
                  ACCESS    read-only
                  STATUS    mandatory
                  DESCRIPTION
                             "A value of regression status.

                              Bit          Comment
                               0           drive status.
                               1           spare drive status.
                               2           data drive status.
                               3           ENC status.
                               4-5         not used,always 0.
                               6           warning status.
                               7           Other controller status.
                               8           UPS status.
                               9           loop status.
                               10          path status.
                               11          NAS Server status.
                               12          NAS Path status.
                               13          NAS UPS status.
                               14-15       not used,always 0.
                               16          battery status.
                               17          power supply status.
                               18          AC status.
                               19          BK status.
                               20          fan status.
                               21-23       not used,always 0.
                               24          cache memory status.
                               25-31       not used,always 0.

                               When the status is normal,each bit value
                               is 0. When the status is abnormal,each bit 
                               value is 1.
                               "
                  ::= { dfWarningCondition 1 }

dfPreventiveMaintenanceInformation OBJECT-TYPE
                  SYNTAX    INTEGER
                  ACCESS    read-only
                  STATUS    mandatory
                  DESCRIPTION
                             "The Preventive Maintenance Information ."
                  ::= { dfWarningCondition 2 }

dfWarningReserve1 OBJECT-TYPE
                  SYNTAX    INTEGER
                  ACCESS    read-only
                  STATUS    mandatory
                  DESCRIPTION
                             "This is not used."
                  ::= { dfWarningCondition 3 }

dfWarningReserve2 OBJECT-TYPE
                  SYNTAX    INTEGER
                  ACCESS    read-only
                  STATUS    mandatory
                  DESCRIPTION
                             "This is not used."
                  ::= { dfWarningCondition 4 }

dfCommandTable OBJECT-TYPE
                  SYNTAX    SEQUENCE OF DfCommandEntry
                  ACCESS    not-accessible
                  STATUS    mandatory
                  DESCRIPTION
                             "The command execution conditon table."
                  ::= { dfCommandExecutionCondition 1 }

dfCommandEntry OBJECT-TYPE
                  SYNTAX    DfCommandEntry
                  ACCESS    not-accessible
                  STATUS    mandatory
                  DESCRIPTION
                             "The command execution conditon table entry."
                  INDEX     { dfLun }
                  ::= { dfCommandTable 1 }

DfCommandEntry ::=
    SEQUENCE {
        dfLun
            INTEGER,
        dfReadCommandNumber
            INTEGER,
        dfReadHitNumber
            INTEGER,
        dfReadHitRate
            INTEGER,
        dfWriteCommandNumber
            INTEGER,
        dfWriteHitNumber
            INTEGER,
        dfWriteHitRate
            INTEGER
    }

dfLun OBJECT-TYPE
                  SYNTAX    INTEGER
                  ACCESS    read-only
                  STATUS    mandatory
                  DESCRIPTION
                             "The logical unit number."
                  ::= { dfCommandEntry 1 }

dfReadCommandNumber OBJECT-TYPE
                  SYNTAX    INTEGER
                  ACCESS    read-only
                  STATUS    mandatory
                  DESCRIPTION
                             "The numbers of received read commands."
                  ::= { dfCommandEntry 2 }

dfReadHitNumber OBJECT-TYPE
                  SYNTAX    INTEGER
                  ACCESS    read-only
                  STATUS    mandatory
                  DESCRIPTION
                             "The numbers of read hit commands."
                  ::= { dfCommandEntry 3 }

dfReadHitRate OBJECT-TYPE
                  SYNTAX    INTEGER
                  ACCESS    read-only
                  STATUS    mandatory
                  DESCRIPTION
                             "The read hit rate."
                  ::= { dfCommandEntry 4 }

dfWriteCommandNumber OBJECT-TYPE
                  SYNTAX    INTEGER
                  ACCESS    read-only
                  STATUS    mandatory
                  DESCRIPTION
                             "The numbers of received write commands."
                  ::= { dfCommandEntry 5 }

dfWriteHitNumber OBJECT-TYPE
                  SYNTAX    INTEGER
                  ACCESS    read-only
                  STATUS    mandatory
                  DESCRIPTION
                             "The numbers of write hit commands."
                  ::= { dfCommandEntry 6 }

dfWriteHitRate OBJECT-TYPE
                  SYNTAX    INTEGER
                  ACCESS    read-only
                  STATUS    mandatory
                  DESCRIPTION
                             "The write hit rate."
                  ::= { dfCommandEntry 7 }

dfWriteDataRate OBJECT-TYPE
                  SYNTAX    INTEGER
                  ACCESS    read-only
                  STATUS    mandatory
                  DESCRIPTION
                             "The write date rate in the cache memory."
                  ::= { dfCacheLoadCondition 1 }

-- ----------------------------------------------------------------------------
-- LUN Security information

--
-- Security switch
--

dfLUNSSwitch OBJECT-TYPE
                  SYNTAX    SEQUENCE OF DFLUNSSwitchEntry
                  ACCESS    not-accessible
                  STATUS    mandatory
                  DESCRIPTION
                             "LUN security switch."
                  ::= { dfLUNS 1 }

dfLUNSSwitchEntry OBJECT-TYPE
                  SYNTAX    DFLUNSSwitchEntry
                  ACCESS    not-accessible
                  STATUS    mandatory
                  DESCRIPTION
                             "Entry of LUN security switch."
                  INDEX {
                      dfSwitchSerialNumber,
                      dfSwitchPortID
                  }
                  ::= { dfLUNSSwitch 1 }

DFLUNSSwitchEntry ::= 
    SEQUENCE {
        dfSwitchSerialNumber  INTEGER,
        dfSwitchPortID        INTEGER,
        dfSwitchOnOff         INTEGER,
        dfSwitchControlStatus INTEGER
    }

dfSwitchSerialNumber OBJECT-TYPE
                  SYNTAX    INTEGER
                  ACCESS    read-only
                  STATUS    mandatory
                  DESCRIPTION
                             "Serial Number of the DF."
                  ::= { dfLUNSSwitchEntry 1 }

dfSwitchPortID OBJECT-TYPE
                  SYNTAX    INTEGER
                  ACCESS    read-only
                  STATUS    mandatory
                  DESCRIPTION
                             "Port ID of the DF."
                  ::= { dfLUNSSwitchEntry 2 }

dfSwitchOnOff OBJECT-TYPE
                  SYNTAX    INTEGER
                  ACCESS    read-only
                  STATUS    mandatory
                  DESCRIPTION
          "Functional switch.

            Value   Mean
            0   off (LUN Security unused)
            1   on (Use LUN Security)
          "
                  ::= { dfLUNSSwitchEntry 3 }

dfSwitchControlStatus OBJECT-TYPE
                  SYNTAX    INTEGER
                  ACCESS    read-only
                  STATUS    mandatory
                  DESCRIPTION
          "Control flag.

            Value   Mean
            1   Return value.
          "
                  ::= { dfLUNSSwitchEntry 4 }

--
-- WWN information
--

dfLUNSWWN OBJECT-TYPE
                  SYNTAX    SEQUENCE OF DFLUNSWWNEntry
                  ACCESS    not-accessible
                  STATUS    mandatory
                  DESCRIPTION
                             "WWN information."
                  ::= { dfLUNS 2 }

dfLUNSWWNEntry OBJECT-TYPE
                  SYNTAX    DFLUNSWWNEntry
                  ACCESS    not-accessible
                  STATUS    mandatory
                  DESCRIPTION
                             "Entry of WWN information."
                  INDEX {
                      dfWWNSerialNumber,
                      dfWWNPortID,
                      dfWWNControlIndex
                  }
                  ::= { dfLUNSWWN 1 }

DFLUNSWWNEntry ::= 
    SEQUENCE {
        dfWWNSerialNumber  INTEGER,
        dfWWNPortID        INTEGER,
        dfWWNControlIndex  INTEGER,
        dfWWNWWN           OCTET STRING (SIZE(0..8)),
        dfWWNID            INTEGER,
        dfWWNNickname      DisplayString (SIZE(0..8)),
        dfWWNUseNickname   INTEGER,
        dfWWNControlStatus INTEGER
    }

dfWWNSerialNumber OBJECT-TYPE
                  SYNTAX    INTEGER
                  ACCESS    read-only
                  STATUS    mandatory
                  DESCRIPTION
                             "Serial number of the DF."
                  ::= { dfLUNSWWNEntry 1 }

dfWWNPortID OBJECT-TYPE
                  SYNTAX    INTEGER
                  ACCESS    read-only
                  STATUS    mandatory
                  DESCRIPTION
                             "Port ID of the DF."
                  ::= { dfLUNSWWNEntry 2 }

dfWWNControlIndex OBJECT-TYPE
                  SYNTAX    INTEGER
                  ACCESS    read-only
                  STATUS    mandatory
                  DESCRIPTION
                             "Index for WWN control."
                  ::= { dfLUNSWWNEntry 3 }

dfWWNWWN OBJECT-TYPE
                  SYNTAX    OCTET STRING (SIZE(0..8))
                  ACCESS    read-only
                  STATUS    mandatory
                  DESCRIPTION
                             "WWN. (World Wide Name)"
                  ::= { dfLUNSWWNEntry 4 }

dfWWNID OBJECT-TYPE
                  SYNTAX    INTEGER
                  ACCESS    read-only
                  STATUS    mandatory
                  DESCRIPTION
                             "ID of the WWN."
                  ::= { dfLUNSWWNEntry 5 }

dfWWNNickname OBJECT-TYPE
                  SYNTAX    DisplayString (SIZE(0..8))
                  ACCESS    read-only
                  STATUS    deprecated
                  DESCRIPTION
                             "Nickname of the WWN."
                  ::= { dfLUNSWWNEntry 6 }

dfWWNUseNickname OBJECT-TYPE
                  SYNTAX    INTEGER
                  ACCESS    read-only
                  STATUS    mandatory
                  DESCRIPTION
          "Using of nickname.

            Valus   Mean
            0   Nickname Unused.
          "
                  ::= { dfLUNSWWNEntry 7 }

dfWWNControlStatus OBJECT-TYPE
                  SYNTAX    INTEGER
                  ACCESS    read-only
                  STATUS    mandatory
                  DESCRIPTION
          "Control flag.

            Value   Mean
            1   Return value.
          "
                  ::= { dfLUNSWWNEntry 8 }

--
-- WWN group information (not-accessible)
--

dfLUNSWWNGroup OBJECT-TYPE
                  SYNTAX    SEQUENCE OF DFLUNSWWNGroupEntry
                  ACCESS    not-accessible
                  STATUS    mandatory
                  DESCRIPTION
                             "WWN group information."
                  ::= { dfLUNS 3 }

dfLUNSWWNGroupEntry OBJECT-TYPE
                  SYNTAX    DFLUNSWWNGroupEntry
                  ACCESS    not-accessible
                  STATUS    mandatory
                  DESCRIPTION
                             "Entry of WWN group information."
                  INDEX {
                      dfWWNGroupSerialNumber,
                      dfWWNGroupPortID,
                      dfWWNGroupControlIndex
                  }
                  ::= { dfLUNSWWNGroup 1 }

DFLUNSWWNGroupEntry ::= 
    SEQUENCE {
        dfWWNGroupSerialNumber  INTEGER,
        dfWWNGroupPortID        INTEGER,
        dfWWNGroupControlIndex  INTEGER,
        dfWWNGroupID            INTEGER,
        dfWWNGroupNickname      DisplayString (SIZE(0..8)),
        dfWWNGroupedWWNs        OCTET STRING (SIZE(0..2)),
        dfWWNGroupControlStatus INTEGER
    }

dfWWNGroupSerialNumber OBJECT-TYPE
                  SYNTAX    INTEGER
                  ACCESS    not-accessible
                  STATUS    mandatory
                  DESCRIPTION
                             "Serial number of the DF."
                  ::= { dfLUNSWWNGroupEntry 1 }

dfWWNGroupPortID OBJECT-TYPE
                  SYNTAX    INTEGER
                  ACCESS    not-accessible
                  STATUS    mandatory
                  DESCRIPTION
                             "Port ID of the DF."
                  ::= { dfLUNSWWNGroupEntry 2 }

dfWWNGroupControlIndex OBJECT-TYPE
                  SYNTAX    INTEGER
                  ACCESS    not-accessible
                  STATUS    mandatory
                  DESCRIPTION
                             "Index for WWN group control."
                  ::= { dfLUNSWWNGroupEntry 3 }

dfWWNGroupID OBJECT-TYPE
                  SYNTAX    INTEGER
                  ACCESS    not-accessible
                  STATUS    mandatory
                  DESCRIPTION
                             "ID of the WWN."
                  ::= { dfLUNSWWNGroupEntry 4 }

dfWWNGroupNickname OBJECT-TYPE
                  SYNTAX    DisplayString (SIZE(0..8))
                  ACCESS    not-accessible
                  STATUS    mandatory
                  DESCRIPTION
                             "Nickname of the WWN group."
                  ::= { dfLUNSWWNGroupEntry 5 }

dfWWNGroupedWWNs OBJECT-TYPE
                  SYNTAX    OCTET STRING (SIZE(0..2))
                  ACCESS    not-accessible
                  STATUS    mandatory
                  DESCRIPTION
          "Grouped WWNs.

            It is shown whether the bit at the position corresponding 
            to WWNID belongs to the group.

            Value   Mean
            0   Does not belong.
            1   Belongs.
          "
                  ::= { dfLUNSWWNGroupEntry 6 }

dfWWNGroupControlStatus OBJECT-TYPE
                  SYNTAX    INTEGER
                  ACCESS    not-accessible
                  STATUS    mandatory
                  DESCRIPTION
          "Control flag.

            Value   Mean
            1   Return value.
            2   Add request.
            3   Delete request.
            4   Set request. 
          "
                  ::= { dfLUNSWWNGroupEntry 7 }

--
-- LUN information
--

dfLUNSLUN OBJECT-TYPE
                  SYNTAX    SEQUENCE OF DFLUNSLUNEntry
                  ACCESS    not-accessible
                  STATUS    mandatory
                  DESCRIPTION
                             "LUN information."
                  ::= { dfLUNS 4 }

dfLUNSLUNEntry OBJECT-TYPE
                  SYNTAX    DFLUNSLUNEntry
                  ACCESS    not-accessible
                  STATUS    mandatory
                  DESCRIPTION
                             "Entry of LUN information."
                  INDEX {
                      dfLUNSerialNumber,
                      dfLUNPortID,
                      dfLUNLUN
                  }
                  ::= { dfLUNSLUN 1 }

DFLUNSLUNEntry ::= 
    SEQUENCE {
        dfLUNSerialNumber     INTEGER,
        dfLUNPortID           INTEGER,
        dfLUNLUN              INTEGER,
        dfLUNWWNSecurity      OCTET STRING (SIZE(0..16)),
        dfLUNWWNGroupSecurity OCTET STRING (SIZE(0..1)),
        dfLUNControlStatus    INTEGER
    }

dfLUNSerialNumber OBJECT-TYPE
                  SYNTAX    INTEGER
                  ACCESS    read-only
                  STATUS    mandatory
                  DESCRIPTION
                             "Serial number of the DF."
                  ::= { dfLUNSLUNEntry 1 }

dfLUNPortID OBJECT-TYPE
                  SYNTAX    INTEGER
                  ACCESS    read-only
                  STATUS    mandatory
                  DESCRIPTION
                             "Port ID of the DF."
                  ::= { dfLUNSLUNEntry 2 }

dfLUNLUN OBJECT-TYPE
                  SYNTAX    INTEGER
                  ACCESS    read-only
                  STATUS    mandatory
                  DESCRIPTION
                             "LUN of the Port."
                  ::= { dfLUNSLUNEntry 3 }

dfLUNWWNSecurity OBJECT-TYPE
                  SYNTAX    OCTET STRING (SIZE(0..16))
                  ACCESS    read-only
                  STATUS    mandatory
                  DESCRIPTION
          "WWN security setting.

            The bit at the position corresponding to WWNID shows the 
            state of the access permittee.
            
            Value   Mean
            0   Does not accessible.
            1   Accessible.
          "
                  ::= { dfLUNSLUNEntry 4 }

dfLUNWWNGroupSecurity OBJECT-TYPE
                  SYNTAX    OCTET STRING (SIZE(0..1))
                  ACCESS    read-only
                  STATUS    mandatory
                  DESCRIPTION
          "WWN group Security setting.

            The bit at the position corresponding to WWNID group shows 
            the state of the access permittee.
            
            Value   Mean
            0   Does not accessible.
          "
                  ::= { dfLUNSLUNEntry 5 }

dfLUNControlStatus OBJECT-TYPE
                  SYNTAX    INTEGER
                  ACCESS    read-only
                  STATUS    mandatory
                  DESCRIPTION
          "Control flag.

            Value   Mean
            1   Return value.
          "
                  ::= { dfLUNSLUNEntry 6 }

--
-- LUN group information (not-accessible)
--

dfLUNSLUNGroup OBJECT-TYPE
                  SYNTAX    SEQUENCE OF DFLUNSLUNGroupEntry
                  ACCESS    not-accessible
                  STATUS    mandatory
                  DESCRIPTION
                             "LUN group information."
                  ::= { dfLUNS 5 }

dfLUNSLUNGroupEntry OBJECT-TYPE
                  SYNTAX    DFLUNSLUNGroupEntry
                  ACCESS    not-accessible
                  STATUS    mandatory
                  DESCRIPTION
                             "Entry of LUN group information."
                  INDEX {
                      dfLUNGroupSerialNumber,
                      dfLUNGroupPortID,
                      dfLUNGroupControlIndex
                  }
                  ::= { dfLUNSLUNGroup 1 }

DFLUNSLUNGroupEntry ::= 
    SEQUENCE {
        dfLUNGroupSerialNumber     INTEGER,
        dfLUNGroupPortID           INTEGER,
        dfLUNGroupControlIndex     INTEGER,
        dfLUNGroupID               INTEGER,
        dfLUNGroupNickname         DisplayString (SIZE(0..8)),
        dfLUNGroupedLUNs           OCTET STRING (SIZE(0..15)),
        dfLUNGroupWWNSecurity      OCTET STRING (SIZE(0..2)),
        dfLUNGroupWWNGroupSecurity OCTET STRING (SIZE(0..1)),
        dfLUNGroupControlStatus    INTEGER
    }

dfLUNGroupSerialNumber OBJECT-TYPE
                  SYNTAX    INTEGER
                  ACCESS    not-accessible
                  STATUS    mandatory
                  DESCRIPTION
                             "Serial number of the DF."
                  ::= { dfLUNSLUNGroupEntry 1 }

dfLUNGroupPortID OBJECT-TYPE
                  SYNTAX    INTEGER
                  ACCESS    not-accessible
                  STATUS    mandatory
                  DESCRIPTION
                             "Port ID of the DF."
                  ::= { dfLUNSLUNGroupEntry 2 }

dfLUNGroupControlIndex OBJECT-TYPE
                  SYNTAX    INTEGER
                  ACCESS    not-accessible
                  STATUS    mandatory
                  DESCRIPTION
                             "Index for LUN group control."
                  ::= { dfLUNSLUNGroupEntry 3 }

dfLUNGroupID OBJECT-TYPE
                  SYNTAX    INTEGER
                  ACCESS    not-accessible
                  STATUS    mandatory
                  DESCRIPTION
                             "ID of the WWN group."
                  ::= { dfLUNSLUNGroupEntry 4 }

dfLUNGroupNickname OBJECT-TYPE
                  SYNTAX    DisplayString (SIZE(0..8))
                  ACCESS    not-accessible
                  STATUS    deprecated
                  DESCRIPTION
                             "Nickname of the LUN group."
                  ::= { dfLUNSLUNGroupEntry 5 }

dfLUNGroupedLUNs OBJECT-TYPE
                  SYNTAX    OCTET STRING (SIZE(0..15))
                  ACCESS    not-accessible
                  STATUS    mandatory
                  DESCRIPTION
          "Grouped LUNs.

            It is shown whether the bit at the position corresponding 
            to LUN belongs to the group. (0:does not belong 1:belongs)

            Value   Mean
            0   Does not belong.
            1   Belongs.
          "
                  ::= { dfLUNSLUNGroupEntry 6 }

dfLUNGroupWWNSecurity OBJECT-TYPE
                  SYNTAX    OCTET STRING (SIZE(0..2))
                  ACCESS    not-accessible
                  STATUS    mandatory
                  DESCRIPTION
          "WWN Security setting.

            The bit at the position corresponding to WWNID shows the 
            state of the access permittee.
            
            Value   Mean
            0   Does not accessible.
            1   Accessible.
          "
                  ::= { dfLUNSLUNGroupEntry 7 }

dfLUNGroupWWNGroupSecurity OBJECT-TYPE
                  SYNTAX    OCTET STRING (SIZE(0..1))
                  ACCESS    not-accessible
                  STATUS    mandatory
                  DESCRIPTION
          "WWN group Security setting.

            The bit at the position corresponding to WWNID group shows 
            the state of the access permittee.
            
            Value   Mean
            0   Does not accessible.
            1   Accessible.
          "
                  ::= { dfLUNSLUNGroupEntry 8 }

dfLUNGroupControlStatus OBJECT-TYPE
                  SYNTAX    INTEGER
                  ACCESS    not-accessible
                  STATUS    mandatory
                  DESCRIPTION
          "Control flag.

            Value   Mean
            1   Return value.
            2   Add request.
            3   Delete request.
            4   Set request.
          "
                  ::= { dfLUNSLUNGroupEntry 9 }

-- ----------------------------------------------------------------------------
-- Port information

dfPortinf OBJECT-TYPE
                  SYNTAX    SEQUENCE OF DFPortinfEntry
                  ACCESS    not-accessible
                  STATUS    mandatory
                  DESCRIPTION
                             "Port information."
                  ::= { dfPort 1 }

dfPortinfEntry OBJECT-TYPE
                  SYNTAX    DFPortinfEntry
                  ACCESS    not-accessible
                  STATUS    mandatory
                  DESCRIPTION
                             "Entry of port information."
                  INDEX {
                      dfPortSerialNumber,
                      dfPortID
                  }
                  ::= { dfPortinf 1 }

DFPortinfEntry ::=
    SEQUENCE {
        dfPortSerialNumber  INTEGER,
        dfPortID            INTEGER,
        dfPortKind          DisplayString (SIZE (0..8)),
        dfPortHostMode      OCTET STRING (SIZE(0..1)),
        dfPortFibreAddress  INTEGER,
        dfPortFibreTopology INTEGER,
        dfPortControlStatus INTEGER,
        dfPortDisplayName   DisplayString (SIZE (0..8)),
        dfPortWWN           OCTET STRING (SIZE(0..8))
    }

dfPortSerialNumber OBJECT-TYPE
                  SYNTAX    INTEGER
                  ACCESS    read-only
                  STATUS    mandatory
                  DESCRIPTION
                             "Serial Number of the DF."
                  ::= { dfPortinfEntry 1 }

dfPortID OBJECT-TYPE
                  SYNTAX    INTEGER
                  ACCESS    read-only
                  STATUS    mandatory
                  DESCRIPTION
                             "Port ID."
                  ::= { dfPortinfEntry 2 }

dfPortKind OBJECT-TYPE
                  SYNTAX    DisplayString (SIZE(0..8))
                  ACCESS    read-only
                  STATUS    mandatory
                  DESCRIPTION
                             "Kind of port.

                                Value   Mean
                                SCSI    SCSI port.
                                Fibre   Fibre port.
                             "
                  ::= { dfPortinfEntry 3 }

dfPortHostMode OBJECT-TYPE
                  SYNTAX    OCTET STRING (SIZE(0..1))
                  ACCESS    read-only
                  STATUS    mandatory
                  DESCRIPTION
         "Host mode of the port.

            Upper 4 bits. - Each bit has the meaning.
            Bit Mean
            0   Not used. (For reservation. Always 0.)
            1   Not used. (For reservation. Always 0.)
            2   Not used. (For reservation. Always 0.)
            3   Ultra-SCSI mode.

            Lower 4 bits. - Numerical value shown by four bits.
            Value   Mean
            0   Normal setting.
            1   IBM-7135 mode.
            2   NCR mode.
            3   Not usesd. (Reserved)
            4   Sequent mode.
            5   DEC OPEN VMS mode.
            6   UNISYS-NX mode
            7   UNISYS-IX mode.
            8   HP mode.
            9   VxVM-DMP mode.
            10  Not used. (Reserved)
            11  MPE mode.
            other   Not used. (Reserved)

            Note: The following value has a special meaning.
            Value   Mean
            0xFF    Out of the host mode setting object.
         "
                  ::= { dfPortinfEntry 4 }

dfPortFibreAddress OBJECT-TYPE
                  SYNTAX    INTEGER
                  ACCESS    read-only
                  STATUS    mandatory
                  DESCRIPTION
    "Fibre address.

            Value & Mean - describes by the format of Value(Address).

        1:(EF)  17:(CD)  33:(B2)  49:(98)  65:(72)  81:(55)  97:(3A) 113:(25)
        2:(E8)  18:(CC)  34:(B1)  50:(97)  66:(71)  82:(54)  98:(39) 114:(23)
        3:(E4)  19:(CB)  35:(AE)  51:(90)  67:(6E)  83:(53)  99:(36) 115:(1F)
        4:(E2)  20:(CA)  36:(AD)  52:(8F)  68:(6D)  84:(52) 100:(35) 116:(1E)
        5:(E1)  21:(C9)  37:(AC)  53:(88)  69:(6C)  85:(51) 101:(34) 117:(1D)
        6:(E0)  22:(C7)  38:(AB)  54:(84)  70:(6B)  86:(4E) 102:(33) 118:(1B)
        7:(DC)  23:(C6)  39:(AA)  55:(82)  71:(6A)  87:(4D) 103:(32) 119:(18)
        8:(DA)  24:(C5)  40:(A9)  56:(81)  72:(69)  88:(4C) 104:(31) 120:(17)
        9:(D9)  25:(C3)  41:(A7)  57:(80)  73:(67)  89:(4B) 105:(2E) 121:(10)
       10:(D6)  26:(BC)  42:(A6)  58:(7C)  74:(66)  90:(4A) 106:(2D) 122:(0F)
       11:(D5)  27:(BA)  43:(A5)  59:(7A)  75:(65)  91:(49) 107:(2C) 123:(08)
       12:(D4)  28:(B9)  44:(A3)  60:(79)  76:(63)  92:(47) 108:(2B) 124:(04)
       13:(D3)  29:(B6)  45:(9F)  61:(76)  77:(5C)  93:(46) 109:(2A) 125:(02)
       14:(D2)  30:(B5)  46:(9E)  62:(75)  78:(5A)  94:(45) 110:(29) 126:(01)
       15:(D1)  31:(B4)  47:(9D)  63:(74)  79:(59)  95:(43) 111:(27) 
       16:(CE)  32:(B3)  48:(9B)  64:(73)  80:(56)  96:(3C) 112:(26) 

            Note: The following value has a special meaning.
            Value   Mean
            0   Out of the Fibre address setting object.
    "
                  ::= { dfPortinfEntry 5 }

dfPortFibreTopology OBJECT-TYPE
                  SYNTAX    INTEGER
                  ACCESS    read-only
                  STATUS    mandatory
                  DESCRIPTION
         "Toplogy information.

            Value   Mean
            1   Fabric(on)&FCAL
            2   Fabric(off)&FCAL
            3   Fabric(on)&PointToPoint
            4   Fabric(off)&PointToPoint
            5   Not Fibre
         "
                  ::= { dfPortinfEntry 6 }

dfPortControlStatus OBJECT-TYPE
                  SYNTAX    INTEGER
                  ACCESS    read-only
                  STATUS    mandatory
                  DESCRIPTION
         "Control flag.

            Value   Mean
            1   Return value.
         "
                  ::= { dfPortinfEntry 7 }

dfPortDisplayName OBJECT-TYPE
                  SYNTAX    DisplayString (SIZE(0..8))
                  ACCESS    read-only
                  STATUS    mandatory
                  DESCRIPTION
                             "Display name of the port."
                  ::= { dfPortinfEntry 8 }

dfPortWWN OBJECT-TYPE
                  SYNTAX    OCTET STRING (SIZE(0..8))
                  ACCESS    read-only
                  STATUS    mandatory
                  DESCRIPTION
                             "WWN of the port."
                  ::= { dfPortinfEntry 9 }

-- ----------------------------------------------------------------------------

dfCommandInternalTable OBJECT-TYPE
                  SYNTAX    SEQUENCE OF DfCommandInternalEntry
                  ACCESS    not-accessible
                  STATUS    mandatory
                  DESCRIPTION
                      "The internal command execution conditon table."
                  ::= { dfCommandExecutionInternalCondition 1 }

dfCommandInternalEntry OBJECT-TYPE
                  SYNTAX    DfCommandInternalEntry
                  ACCESS    not-accessible
                  STATUS    mandatory
                  DESCRIPTION
                      "The internal command execution conditon table entry."
                  INDEX     { dfInternalLun }
                  ::= { dfCommandInternalTable 1 }

DfCommandInternalEntry ::=
    SEQUENCE {
        dfInternalLun
            INTEGER,
        dfInternalReadCommandNumber
            INTEGER,
        dfInternalReadHitNumber
            INTEGER,
        dfInternalReadHitRate
            INTEGER,
        dfInternalWriteCommandNumber
            INTEGER,
        dfInternalWriteHitNumber
            INTEGER,
        dfInternalWriteHitRate
            INTEGER
    }

dfInternalLun OBJECT-TYPE
                  SYNTAX    INTEGER
                  ACCESS    read-only
                  STATUS    mandatory
                  DESCRIPTION
                  "The internal logical unit number."
                  ::= { dfCommandInternalEntry 1 }

dfInternalReadCommandNumber OBJECT-TYPE
                  SYNTAX    INTEGER
                  ACCESS    read-only
                  STATUS    mandatory
                  DESCRIPTION
                  "The numbers of received read commands to the internal LUN."
                  ::= { dfCommandInternalEntry 2 }

dfInternalReadHitNumber OBJECT-TYPE
                  SYNTAX    INTEGER
                  ACCESS    read-only
                  STATUS    mandatory
                  DESCRIPTION
                  "The numbers of read hit commands to the internal LUN."
                  ::= { dfCommandInternalEntry 3 }

dfInternalReadHitRate OBJECT-TYPE
                  SYNTAX    INTEGER
                  ACCESS    read-only
                  STATUS    mandatory
                  DESCRIPTION
                  "The read hit rate to the internal LUN."
                  ::= { dfCommandInternalEntry 4 }

dfInternalWriteCommandNumber OBJECT-TYPE
                  SYNTAX    INTEGER
                  ACCESS    read-only
                  STATUS    mandatory
                  DESCRIPTION
                  "The numbers of received write commands to the internal LUN."
                  ::= { dfCommandInternalEntry 5 }

dfInternalWriteHitNumber OBJECT-TYPE
                  SYNTAX    INTEGER
                  ACCESS    read-only
                  STATUS    mandatory
                  DESCRIPTION
                  "The numbers of write hit commands to the internal LUN."
                  ::= { dfCommandInternalEntry 6 }

dfInternalWriteHitRate OBJECT-TYPE
                  SYNTAX    INTEGER
                  ACCESS    read-only
                  STATUS    mandatory
                  DESCRIPTION
                  "The write hit rate to the internal LUN."
                  ::= { dfCommandInternalEntry 7 }


-- Traps 

systemDown   TRAP-TYPE
              ENTERPRISE  dfraidLan
              DESCRIPTION
                      "System down occurred."
              ::= 1

driveFailure   TRAP-TYPE
              ENTERPRISE  dfraidLan
              DESCRIPTION
                      "Drive blocking occurred."
              ::= 2

fanFailure   TRAP-TYPE
              ENTERPRISE  dfraidLan
              DESCRIPTION
                      "Fan failure occurred."
              ::= 3 

powerSupplyFailure   TRAP-TYPE
              ENTERPRISE  dfraidLan
              DESCRIPTION
                      "Power supply failure occurred."
              ::= 4 

batteryFailure   TRAP-TYPE
              ENTERPRISE  dfraidLan
              DESCRIPTION
                      "Battery failure occurred."
              ::= 5 

cacheFailure   TRAP-TYPE
              ENTERPRISE  dfraidLan
              DESCRIPTION
                      "Cache memory failure occurred."
              ::= 6 

upsFailure    TRAP-TYPE
              ENTERPRISE  dfraidLan
              DESCRIPTION
                      "UPS failure occurred."
              ::= 7 

inboxFailure  TRAP-TYPE
              ENTERPRISE  dfraidLan
              DESCRIPTION
                      "AC line or inbox failure occurred."
              ::= 8 

backupCircuitFailure   TRAP-TYPE
              ENTERPRISE  dfraidLan
              DESCRIPTION
                      "Cache backup circuit failure occurred."
              ::= 9 

otherControllerFailure TRAP-TYPE
              ENTERPRISE  dfraidLan
              DESCRIPTION
                      "Other controller failure occurred."
              ::= 10 

warning                TRAP-TYPE
              ENTERPRISE  dfraidLan
              DESCRIPTION
                      "Warning occurred."
              ::= 11 

spareDriveFailure      TRAP-TYPE
              ENTERPRISE  dfraidLan
              DESCRIPTION
                      "Spare drive failure occurred."
              ::= 12 

microprogramReplacementExecuted      TRAP-TYPE
              ENTERPRISE  dfraidLan
              DESCRIPTION
                      "Microprogram Replacement Executed."
              ::= 13 

encFailure      TRAP-TYPE
              ENTERPRISE  dfraidLan
              DESCRIPTION
                      "Enclosure controller failure occurred."
              ::= 14 

loopFailure      TRAP-TYPE
              ENTERPRISE  dfraidLan
              DESCRIPTION
                      "Loop failure occurred."
              ::= 15 

pathFailure      TRAP-TYPE
              ENTERPRISE  dfraidLan
              DESCRIPTION
                      "Path failure occurred."
              ::= 16 

-- Trap Code #17-20 is reserved.

drivePreMainte   TRAP-TYPE
              ENTERPRISE  dfraidLan
              DESCRIPTION
                      "The count has exceeded the drive preventive
                       maintenance threshold."
              ::= 21

nasServerFailure      TRAP-TYPE
              ENTERPRISE  dfraidLan
              DESCRIPTION
                      "NAS Server failure occurred."
              ::= 200

nasPathFailure      TRAP-TYPE
              ENTERPRISE  dfraidLan
              DESCRIPTION
                      "NAS Path failure occurred."
              ::= 201

nasUpsFailure      TRAP-TYPE
              ENTERPRISE  dfraidLan
              DESCRIPTION
                      "NAS UPS failure occurred."
              ::= 202

END
