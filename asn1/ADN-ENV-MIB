-- @(\#)A1100NMS mib, 3DJ 50000 AAAA ICS009, R2.9.00.09, Thu Mar  4 15:03:33 EST 1999

--------------------------------------------------------------------------------
--                                                                            --
--  The information in this file is subject to change without notice and      --
--  should not be construed as a commitment by Alcatel Data Networks.         --
--                                                                            --
--               Copyright 1995, 1996 by Alcatel Data Networks,               --
--                        all rights reserved                                 --
--                                                                            --
--  Alcatel Data Networks owns and retains all right, title and interest      --
--  in and to this software.  This software constitutes Alcatel Data          --
--  Networks' proprietary information and intellectual property, and no       --
--  part or parts hereof shall be reproduced, translated, stored in any       --
--  electronic retrieval system or transmitted, in any form or by any means   --
--  (electronic, mechanical, photocopying, recording, or otherwise), without  --
--  the prior permission of Alcatel Data Networks, other than as necessary    --
--  in connection with the management of Alcatel Data Networks products.      --
--                                                                            --
--------------------------------------------------------------------------------

-- automatically generated by mosy R2.1.0.03 (ADN version), do not edit!

ADN-ENV-MIB DEFINITIONS ::= BEGIN


IMPORTS
	OBJECT-TYPE
		FROM RFC-1212
	Counter, IpAddress, Gauge FROM RFC1155-SMI
	adnAtmUniVcCconnectIndex, adnAtmUniVpCconnectIndex, adnLapDLCIIndex,
	adnCongMgmtVCDLCIIndex, adnEquipIndex, adnEquipType, adnFrtVCDLCIIndex,
	adn, adnEnvHss, AdnPercent, AdnFrtVCStates, AdnEnableDisabled, AdnCouplerIndex
		FROM ADN-MIB
	DisplayString FROM SNMPv2-TC
	atmVclVci, atmVclVpi, atmVplVpi
		FROM ATM-MIB
	frPVCEndptDLCIIndex
		FROM FRNETSERV-MIB
	ifIndex, InterfaceIndex
		FROM IF-MIB;

-- created from adnEnvMIB (9901110000Z)

adnEnvMIB OBJECT IDENTIFIER ::= { adn  2 }

adnFranpTrunkEnvMIB OBJECT IDENTIFIER ::= { adnEnvHss  1 }

adnFrtChanSiTable OBJECT-TYPE
    SYNTAX  SEQUENCE OF AdnFrtChanSiEntry
    ACCESS  not-accessible
    STATUS  mandatory
    DESCRIPTION
           "This table is internal for use by FRANP Signalling for 
         the purpose of debugging."
    ::= { adnFranpTrunkEnvMIB  1 }

adnFrtChanSiEntry OBJECT-TYPE
    SYNTAX  AdnFrtChanSiEntry
    ACCESS  not-accessible
    STATUS  mandatory
    DESCRIPTION
           "An entry in the Signalling Trunk Channel Table. There
         will be one entry for each FRANP Signalling Trunk 
         channel configured. This table will also be indexed by
         adnFrtChanSiIndex in order to be able to access
         individual trace entries."
    INDEX   { ifIndex,  adnFrtChanSiIndex }
    ::= { adnFrtChanSiTable  1 }

AdnFrtChanSiEntry ::=
    SEQUENCE {
        adnFrtChanSiIndex
            INTEGER (-2147483648..2147483647),

        adnFrtChanSiResourceAvail
            INTEGER (-2147483648..2147483647),

        adnFrtChanSiBWThreshold
            AdnPercent,

        adnFrtChanSiCcb
            OCTET STRING,

        adnFrtChanSiTraceCntl
            INTEGER,

        adnFrtChanSiTraceSize
            INTEGER,

        adnFrtChanSiTraceArea
            OCTET STRING,

        adnFrtChanSiBsiStat
            OCTET STRING,

        adnFrtChanSiTsiStat
            OCTET STRING,

        adnFrtChanSiBsiCrfa
            OCTET STRING,

        adnFrtChanSiTsiCrfa
            OCTET STRING,

        adnFrtChanSiTsiBwi
            OCTET STRING,

        adnFrtChanSiMinDlyPct
            AdnPercent,

        adnFrtChanSiMinDlyAmt
            INTEGER,

        adnFrtChanSiDlyPersis
            INTEGER
    }

adnFrtChanSiIndex OBJECT-TYPE
    SYNTAX  INTEGER (-2147483648..2147483647)
    ACCESS  read-only
    STATUS  mandatory
    DESCRIPTION
           "This entry represents the current instance or index of
         the table. It is provided in order to be able to dump 
         each instance of each object."
    ::= { adnFrtChanSiEntry  1 }

adnFrtChanSiResourceAvail OBJECT-TYPE
    SYNTAX  INTEGER (-2147483648..2147483647)
    ACCESS  read-write
    STATUS  mandatory
    DESCRIPTION
           "This timer specifies the amount of time to wait for a
         resource available message to be sent to FRANP Path 
         Select SwBB. If the timer expires, then the message 
         is transmitted. This is expressed in SECONDS. The 
         timer may be set by SNMP command."
    DEFVAL  { 60 }
    ::= { adnFrtChanSiEntry  2 }

adnFrtChanSiBWThreshold OBJECT-TYPE
    SYNTAX  AdnPercent
    ACCESS  read-write
    STATUS  mandatory
    DESCRIPTION
           "The threshold value is specified as a percentage of 
         the BAT.  If the available bandwidth drops below 
         this threshold, the resource available message sent
         to FRANP Path Select component.  The value may be 
         set by SNMP command."
    DEFVAL  { 50 }
    ::= { adnFrtChanSiEntry  3 }

adnFrtChanSiCcb OBJECT-TYPE
    SYNTAX  OCTET STRING
    ACCESS  read-only
    STATUS  mandatory
    DESCRIPTION
           "This is the internal BINARY trace area for call 
         control information trace area, maintained by 
         FRANP_SI. It is placed here for maintenance 
         purposes only."
    ::= { adnFrtChanSiEntry  4 }

adnFrtChanSiTraceCntl OBJECT-TYPE
    SYNTAX  INTEGER
    ACCESS  read-write
    STATUS  mandatory
    DESCRIPTION
           "This object provides a mechanism for controlling 
         Franp Signalling ability to enable/disable tracing
         data from its Bus side, Trunk side, and Ism side. 
         The following are the possible values it can hold.
           1 - Trace activity enabled (normally is defaulted on)
           2 - Trace activity disabled"
    DEFVAL  { 1 }
    ::= { adnFrtChanSiEntry  5 }

adnFrtChanSiTraceSize OBJECT-TYPE
    SYNTAX  INTEGER
    ACCESS  read-write
    STATUS  mandatory
    DESCRIPTION
           "This object provides a mechanism for defining the 
         number of entries the Franp Signalling trace area
         can have. Be aware when issuing a set command to
         modify this value, any existing trace data will be 
         lost to make room for the new trace block size."
    DEFVAL  { 64 }
    ::= { adnFrtChanSiEntry  6 }

adnFrtChanSiTraceArea OBJECT-TYPE
    SYNTAX  OCTET STRING
    ACCESS  read-only
    STATUS  mandatory
    DESCRIPTION
           "This is the internal BINARY message trace entry 
         maintained by FRANP_SI for its 3 main interfaces,
         (Bus side, Trunk side, and Ism side). This entry
         is instantiated by AdnFrtChanSiInstance index that 
         comprises the entire trace area table. The FRANP 
         Signalling software is implemented as a Finite 
         State Machine, and all message events received 
         are stored here. It is placed here for maintenance 
         purposes only."
    ::= { adnFrtChanSiEntry  7 }

adnFrtChanSiBsiStat OBJECT-TYPE
    SYNTAX  OCTET STRING
    ACCESS  read-only
    STATUS  mandatory
    DESCRIPTION
           "This is the internal BINARY statistic trace table 
         maintained by FRANP_SI for this Bus Side interface. 
         The Franp Signalling software is implemented as a 
         Finite State Machine, and all statistics collected 
         are stored here. It is placed here for maintenance 
         purposes only."
    ::= { adnFrtChanSiEntry  8 }

adnFrtChanSiTsiStat OBJECT-TYPE
    SYNTAX  OCTET STRING
    ACCESS  read-only
    STATUS  mandatory
    DESCRIPTION
           "This is the internal BINARY statistic trace table 
         maintained by FRANP_SI for this Trunk Side interface. 
         The Franp Signalling software is implemented as a 
         Finite State Machine, and all statistics collected
         are stored here. It is placed here for maintenance 
         purposes only."
    ::= { adnFrtChanSiEntry  9 }

adnFrtChanSiBsiCrfa OBJECT-TYPE
    SYNTAX  OCTET STRING
    ACCESS  read-only
    STATUS  mandatory
    DESCRIPTION
           "This is the internal BINARY call reference active 
         trace maintained by FRANP_SI for this Bus Side 
         interface. It is placed here for maintenance
         purposes only."
    ::= { adnFrtChanSiEntry  10 }

adnFrtChanSiTsiCrfa OBJECT-TYPE
    SYNTAX  OCTET STRING
    ACCESS  read-only
    STATUS  mandatory
    DESCRIPTION
           "This is the internal BINARY call reference active 
         trace maintained by FRANP_SI for this Trunk Side 
         interface. It is placed here for maintenance
         purposes only."
    ::= { adnFrtChanSiEntry  11 }

adnFrtChanSiTsiBwi OBJECT-TYPE
    SYNTAX  OCTET STRING
    ACCESS  read-only
    STATUS  mandatory
    DESCRIPTION
           "This is the internal BINARY Bandwidth Information 
         table maintained by FRANP_SI for this Trunk Side 
         interface. It is placed here for maintenance
         purposes only."
    ::= { adnFrtChanSiEntry  12 }

adnFrtChanSiMinDlyPct OBJECT-TYPE
    SYNTAX  AdnPercent
    ACCESS  read-write
    STATUS  mandatory
    DESCRIPTION
           "This field is used to calculate the minimum delay change
         a periodic delay measurement can consider to be significant.
         Such significant delay changes may result in a new delay
         reported to ROUTES.
	 The minimum delay change is calulated by multiplying this
         field as a percentage times the delay measured immediately
         after a RESTART/RESTART ACK exchange."
    DEFVAL  { 50 }
    ::= { adnFrtChanSiEntry  13 }

adnFrtChanSiMinDlyAmt OBJECT-TYPE
    SYNTAX  INTEGER	-- UNITS milliseconds

    ACCESS  read-write
    STATUS  mandatory
    DESCRIPTION
           "If the minimum delay change calculated using adnFrtChanSiMinDlyPct
         is less than this field, the minimum delay change a periodic
         delay measurement can consider to be significant is set equal
         to this field instead of the calculated value."
    DEFVAL  { 3 }
    ::= { adnFrtChanSiEntry  14 }

adnFrtChanSiDlyPersis OBJECT-TYPE
    SYNTAX  INTEGER
    ACCESS  read-write
    STATUS  mandatory
    DESCRIPTION
           "Before a periodic delay measurement can report a new delay
         value to ROUTES, a specified number of consecutive 
         measurements must be significantly high OR a specified
         number of consecutive measurements must be significantly low.
         This field defines that specified number of consecutive
         measurements."
    DEFVAL  { 3 }
    ::= { adnFrtChanSiEntry  15 }

adnFrtChanSwTable OBJECT-TYPE
    SYNTAX  SEQUENCE OF AdnFrtChanSwEntry
    ACCESS  not-accessible
    STATUS  mandatory
    DESCRIPTION
           "This table contains internal channel level 
         information for FRANP_SW. There is no existing 
         standard MIB for Alcatel internal network  
         protocol."
    ::= { adnFranpTrunkEnvMIB  2 }

adnFrtChanSwEntry OBJECT-TYPE
    SYNTAX  AdnFrtChanSwEntry
    ACCESS  not-accessible
    STATUS  mandatory
    DESCRIPTION
           "An entry in the internal FRANP Switching Channel 
         Table. There will be one entry for each FRANP 
         channel configured"
    INDEX   { ifIndex }
    ::= { adnFrtChanSwTable  1 }

AdnFrtChanSwEntry ::=
    SEQUENCE {
        adnFrtChanSwFRSI
            OCTET STRING,

        adnFrtChanSwIWF
            OCTET STRING,

        adnFrtChanSwFRSIMsgtrace
            OCTET STRING
    }

adnFrtChanSwFRSI OBJECT-TYPE
    SYNTAX  OCTET STRING
    ACCESS  read-only
    STATUS  mandatory
    DESCRIPTION
           "This is the BINARY internal channel structure 
         maintained by FRSI portion of FRANP_SW for this 
         channel.  It is placed here for maintenance 
         purposes only."
    ::= { adnFrtChanSwEntry  3 }

adnFrtChanSwIWF OBJECT-TYPE
    SYNTAX  OCTET STRING
    ACCESS  read-only
    STATUS  mandatory
    DESCRIPTION
           "This is the BINARY internal channel structure 
         maintained by TPX/F IWF portion of FRANP_SW 
         for this channel. It is placed here for 
         maintenance purposes only."
    ::= { adnFrtChanSwEntry  4 }

adnFrtChanSwFRSIMsgtrace OBJECT-TYPE
    SYNTAX  OCTET STRING
    ACCESS  read-only
    STATUS  mandatory
    DESCRIPTION
           "This is the internal BINARY message trace 
         table maintained by FRSI portion of FRANP_SW 
         for this channel.  It is placed here for 
         maintenance purposes only."
    ::= { adnFrtChanSwEntry  5 }

adnFrtVCSiTable OBJECT-TYPE
    SYNTAX  SEQUENCE OF AdnFrtVCSiEntry
    ACCESS  not-accessible
    STATUS  mandatory
    DESCRIPTION
           "This is the PVC table for FRANP trunk protocol."
    ::= { adnFranpTrunkEnvMIB  3 }

adnFrtVCSiEntry OBJECT-TYPE
    SYNTAX  AdnFrtVCSiEntry
    ACCESS  not-accessible
    STATUS  mandatory
    DESCRIPTION
           "PVC table entry"
    INDEX   { ifIndex,  adnFrtVCDLCIIndex }
    ::= { adnFrtVCSiTable  1 }

AdnFrtVCSiEntry ::=
    SEQUENCE {
        adnFrtVCSiBsiCrf
            INTEGER,

        adnFrtVCSiBsiState
            AdnFrtVCStates,

        adnFrtVCSiTsiCrf
            INTEGER,

        adnFrtVCSiTsiState
            AdnFrtVCStates,

        adnFrtVCSiLocalSuid
            INTEGER (-2147483648..2147483647),

        adnFrtVCSiLocalLpx
            INTEGER (-2147483648..2147483647),

        adnFrtVCSiLocalMcmp
            INTEGER (-2147483648..2147483647),

        adnFrtVCSiLocalAppl
            INTEGER (-2147483648..2147483647),

        adnFrtVCSiLocalData
            INTEGER (-2147483648..2147483647),

        adnFrtVCSiLocalFranpSi
            INTEGER (-2147483648..2147483647),

        adnFrtVCSiLocalifIndex
            InterfaceIndex,

        adnFrtVCSiRemoteSuid
            INTEGER (-2147483648..2147483647),

        adnFrtVCSiRemoteLpx
            INTEGER (-2147483648..2147483647),

        adnFrtVCSiRemoteMcmp
            INTEGER (-2147483648..2147483647),

        adnFrtVCSiRemoteAppl
            INTEGER (-2147483648..2147483647),

        adnFrtVCSiRemoteData
            INTEGER (-2147483648..2147483647),

        adnFrtVCSiRemoteFranpSi
            INTEGER (-2147483648..2147483647),

        adnFrtVCSiRemoteifIndex
            InterfaceIndex,

        adnFrtVCSiBsiTimer
            INTEGER (-2147483648..2147483647),

        adnFrtVCSiTsiTimer
            INTEGER (-2147483648..2147483647),

        adnFrtVCSiBsiTimerExpCnt
            Counter,

        adnFrtVCSiTsiTimerExpCnt
            Counter
    }

adnFrtVCSiBsiCrf OBJECT-TYPE
    SYNTAX  INTEGER (-2147483648..2147483647)
    ACCESS  read-only
    STATUS  mandatory
    DESCRIPTION
           "This is the Bus Side Interface call reference associated
         with the VC."
    ::= { adnFrtVCSiEntry  1 }

adnFrtVCSiBsiState OBJECT-TYPE
    SYNTAX  AdnFrtVCStates
    ACCESS  read-write
    STATUS  mandatory
    DESCRIPTION
           "Define here are the state that are implemented and 
         supported for the FRANP Signalling bus Side 
         Interface."
    ::= { adnFrtVCSiEntry  2 }

adnFrtVCSiTsiCrf OBJECT-TYPE
    SYNTAX  INTEGER (-2147483648..2147483647)
    ACCESS  read-only
    STATUS  mandatory
    DESCRIPTION
           "This is the Trunk Side Interface call reference 
         associated with the VC."
    ::= { adnFrtVCSiEntry  3 }

adnFrtVCSiTsiState OBJECT-TYPE
    SYNTAX  AdnFrtVCStates
    ACCESS  read-write
    STATUS  mandatory
    DESCRIPTION
           "Define here are the state that are implemented and 
         supported for the FRANP Signalling Trunk Side 
         Interface."
    ::= { adnFrtVCSiEntry  4 }

adnFrtVCSiLocalSuid OBJECT-TYPE
    SYNTAX  INTEGER (-2147483648..2147483647)
    ACCESS  read-only
    STATUS  mandatory
    DESCRIPTION
           "This is the local Suid associated with the VC."
    ::= { adnFrtVCSiEntry  5 }

adnFrtVCSiLocalLpx OBJECT-TYPE
    SYNTAX  INTEGER (-2147483648..2147483647)
    ACCESS  read-only
    STATUS  mandatory
    DESCRIPTION
           "This is the local LPX associated with the VC."
    ::= { adnFrtVCSiEntry  6 }

adnFrtVCSiLocalMcmp OBJECT-TYPE
    SYNTAX  INTEGER (-2147483648..2147483647)
    ACCESS  read-only
    STATUS  mandatory
    DESCRIPTION
           "This is the local Maximum Congestion Monitoring Period 
         associated with the VC."
    ::= { adnFrtVCSiEntry  7 }

adnFrtVCSiLocalAppl OBJECT-TYPE
    SYNTAX  INTEGER (-2147483648..2147483647)
    ACCESS  read-only
    STATUS  mandatory
    DESCRIPTION
           "This is the local Application reference number associated
         with the VC."
    ::= { adnFrtVCSiEntry  8 }

adnFrtVCSiLocalData OBJECT-TYPE
    SYNTAX  INTEGER (-2147483648..2147483647)
    ACCESS  read-only
    STATUS  mandatory
    DESCRIPTION
           "This is the local Data Handler reference number associated 
         with the VC."
    ::= { adnFrtVCSiEntry  9 }

adnFrtVCSiLocalFranpSi OBJECT-TYPE
    SYNTAX  INTEGER (-2147483648..2147483647)
    ACCESS  read-only
    STATUS  mandatory
    DESCRIPTION
           "This is the local Franp Signalling reference number 
         associated with the VC."
    ::= { adnFrtVCSiEntry  10 }

adnFrtVCSiLocalifIndex OBJECT-TYPE
    SYNTAX  InterfaceIndex
    ACCESS  read-only
    STATUS  mandatory
    DESCRIPTION
           "This indicates the ifindex of the remote Chassis/Slot/
         Port/Channel."
    ::= { adnFrtVCSiEntry  11 }

adnFrtVCSiRemoteSuid OBJECT-TYPE
    SYNTAX  INTEGER (-2147483648..2147483647)
    ACCESS  read-only
    STATUS  mandatory
    DESCRIPTION
           "This is the remote Suid associated with the VC."
    ::= { adnFrtVCSiEntry  12 }

adnFrtVCSiRemoteLpx OBJECT-TYPE
    SYNTAX  INTEGER (-2147483648..2147483647)
    ACCESS  read-only
    STATUS  mandatory
    DESCRIPTION
           "This is the remote Lpx associated with the VC."
    ::= { adnFrtVCSiEntry  13 }

adnFrtVCSiRemoteMcmp OBJECT-TYPE
    SYNTAX  INTEGER (-2147483648..2147483647)
    ACCESS  read-only
    STATUS  mandatory
    DESCRIPTION
           "This is the remote Maximum Congestion Monitoring period 
         associated with the VC."
    ::= { adnFrtVCSiEntry  14 }

adnFrtVCSiRemoteAppl OBJECT-TYPE
    SYNTAX  INTEGER (-2147483648..2147483647)
    ACCESS  read-only
    STATUS  mandatory
    DESCRIPTION
           "This is the remote Application reference number associated 
         with the VC."
    ::= { adnFrtVCSiEntry  15 }

adnFrtVCSiRemoteData OBJECT-TYPE
    SYNTAX  INTEGER (-2147483648..2147483647)
    ACCESS  read-only
    STATUS  mandatory
    DESCRIPTION
           "This is the remote Data Handler reference number associated 
         with the VC."
    ::= { adnFrtVCSiEntry  16 }

adnFrtVCSiRemoteFranpSi OBJECT-TYPE
    SYNTAX  INTEGER (-2147483648..2147483647)
    ACCESS  read-only
    STATUS  mandatory
    DESCRIPTION
           "This is the remote Franp Signalling reference number  
         associated with the VC."
    ::= { adnFrtVCSiEntry  17 }

adnFrtVCSiRemoteifIndex OBJECT-TYPE
    SYNTAX  InterfaceIndex
    ACCESS  read-only
    STATUS  mandatory
    DESCRIPTION
           "This indicates the ifindex of the remote Chassis/Slot/
         Port/Channel."
    ::= { adnFrtVCSiEntry  18 }

adnFrtVCSiBsiTimer OBJECT-TYPE
    SYNTAX  INTEGER (-2147483648..2147483647)
    ACCESS  read-only
    STATUS  mandatory
    DESCRIPTION
           "This is the timer ID that is currently running for this VC."
    ::= { adnFrtVCSiEntry  19 }

adnFrtVCSiTsiTimer OBJECT-TYPE
    SYNTAX  INTEGER (-2147483648..2147483647)
    ACCESS  read-only
    STATUS  mandatory
    DESCRIPTION
           "This is the timer ID that is currently running  for this VC."
    ::= { adnFrtVCSiEntry  20 }

adnFrtVCSiBsiTimerExpCnt OBJECT-TYPE
    SYNTAX  Counter
    ACCESS  read-only
    STATUS  mandatory
    DESCRIPTION
           "This is the number of times this Bus Side Interface timer 
         ID has expired."
    ::= { adnFrtVCSiEntry  21 }

adnFrtVCSiTsiTimerExpCnt OBJECT-TYPE
    SYNTAX  Counter
    ACCESS  read-only
    STATUS  mandatory
    DESCRIPTION
           "This is the number of times this trunk Side Interface timer 
         ID has expired."
    ::= { adnFrtVCSiEntry  22 }

adnFrtVCSwTable OBJECT-TYPE
    SYNTAX  SEQUENCE OF AdnFrtVCSwEntry
    ACCESS  not-accessible
    STATUS  mandatory
    DESCRIPTION
           "This is the internal VC table for FRANP Switching."
    ::= { adnFranpTrunkEnvMIB  4 }

adnFrtVCSwEntry OBJECT-TYPE
    SYNTAX  AdnFrtVCSwEntry
    ACCESS  not-accessible
    STATUS  mandatory
    DESCRIPTION
           "PVC table entry"
    INDEX   { ifIndex,  adnFrtVCDLCIIndex }
    ::= { adnFrtVCSwTable  1 }

AdnFrtVCSwEntry ::=
    SEQUENCE {
        adnFrtVCSwFRSI
            OCTET STRING,

        adnFrtVCSwIWF
            OCTET STRING,

        adnFrtVCSwFRSIMsgtrace
            OCTET STRING
    }

adnFrtVCSwFRSI OBJECT-TYPE
    SYNTAX  OCTET STRING
    ACCESS  read-only
    STATUS  mandatory
    DESCRIPTION
           "This is the BINARY internal VC structure maintained 
         by the FRSI portion of FRANP_SW. It is placed here for 
         maintenance purposes only."
    ::= { adnFrtVCSwEntry  1 }

adnFrtVCSwIWF OBJECT-TYPE
    SYNTAX  OCTET STRING
    ACCESS  read-only
    STATUS  mandatory
    DESCRIPTION
           "This is the BINARY internal VC structure maintained 
         by the TPX/F IWF portion of FRANP_SW. It is placed 
         here for maintenance purposes only."
    ::= { adnFrtVCSwEntry  2 }

adnFrtVCSwFRSIMsgtrace OBJECT-TYPE
    SYNTAX  OCTET STRING
    ACCESS  read-only
    STATUS  mandatory
    DESCRIPTION
           "This is the internal BINARY message trace table 
         maintained by the FRSI portion of FRANP_SW for 
         this VC. It is placed here for maintenance purposes 
         only."
    ::= { adnFrtVCSwEntry  3 }

adnFrtSiTable OBJECT-TYPE
    SYNTAX  SEQUENCE OF AdnFrtSiEntry
    ACCESS  not-accessible
    STATUS  mandatory
    DESCRIPTION
           "This is the FRANP Signalling table. It will exists 
         once per FRANP Signalling instance on each LT."
    ::= { adnFranpTrunkEnvMIB  5 }

adnFrtSiEntry OBJECT-TYPE
    SYNTAX  AdnFrtSiEntry
    ACCESS  not-accessible
    STATUS  mandatory
    DESCRIPTION
           "One instance of the adnFrtSiTable. There will be 
         one instance for each FRANP Signalling on each LT."
    INDEX   { adnCouplerIndex,  adnFrtSiTraceIndex }
    ::= { adnFrtSiTable  1 }

AdnFrtSiEntry ::=
    SEQUENCE {
        adnFrtSiTraceIndex
            INTEGER (-2147483648..2147483647),

        adnFrtSiTraceCntl
            INTEGER,

        adnFrtSiTraceSize
            INTEGER,

        adnFrtSiTraceArea
            OCTET STRING,

        adnFrtSiStat
            OCTET STRING,

        adnFrtSiStatISMTrace
            OCTET STRING
    }

adnFrtSiTraceIndex OBJECT-TYPE
    SYNTAX  INTEGER (-2147483648..2147483647)
    ACCESS  read-only
    STATUS  mandatory
    DESCRIPTION
           "This entry represents the current instance or index. 
         It is provided in order to be able to dump
         each Franp_si trace instance of each object."
    ::= { adnFrtSiEntry  1 }

adnFrtSiTraceCntl OBJECT-TYPE
    SYNTAX  INTEGER
    ACCESS  read-write
    STATUS  mandatory
    DESCRIPTION
           "This object provides a mechanism for controlling
         Franp Signalling ability to enable/disable tracing
         data from its Bus side, Trunk side, and Ism side.
         The following are the possible values it can hold.
           1 - Trace activity enabled 
           2 - Trace activity disabled (default setting)"
    DEFVAL  { 2 }
    ::= { adnFrtSiEntry  2 }

adnFrtSiTraceSize OBJECT-TYPE
    SYNTAX  INTEGER
    ACCESS  read-write
    STATUS  mandatory
    DESCRIPTION
           "This object provides a mechanism for defining the
         number of entries the Franp Signalling trace area
         can have. Be aware when issuing a set command to
         modify this value, any existing trace data will be
         lost to make room for the new trace block size."
    DEFVAL  { 64 }
    ::= { adnFrtSiEntry  3 }

adnFrtSiTraceArea OBJECT-TYPE
    SYNTAX  OCTET STRING
    ACCESS  read-only
    STATUS  mandatory
    DESCRIPTION
           "This is the internal BINARY message trace entry
         maintained by FRANP_SI for its 3 main interfaces,
         (Bus side, Trunk side, and Ism side). This entry
         is instanciated by AdnFrtSiInstance index that
         comprises the entire trace area table. The FRANP
         Signalling software is implemented as a Finite
         State Machine, and all message events received
         are stored here. It is placed here for maintenance
         purposes only."
    ::= { adnFrtSiEntry  4 }

adnFrtSiStat OBJECT-TYPE
    SYNTAX  OCTET STRING
    ACCESS  read-only
    STATUS  mandatory
    DESCRIPTION
           "This is the internal FRANP_SI data structure. This 
         will contain internal error counters and structures. 
         This is the internal table maintained by FRANP_SI."
    ::= { adnFrtSiEntry  5 }

adnFrtSiStatISMTrace OBJECT-TYPE
    SYNTAX  OCTET STRING
    ACCESS  read-only
    STATUS  mandatory
    DESCRIPTION
           "This is the ISM message trace area. All ISM Messages 
         transmitted and received by FRANP_SI are stored here.
         It is placed here for maintenance purposes only."
    ::= { adnFrtSiEntry  6 }

adnFrtSwTable OBJECT-TYPE
    SYNTAX  SEQUENCE OF AdnFrtSwEntry
    ACCESS  not-accessible
    STATUS  mandatory
    DESCRIPTION
           "This is the FRANP_SW table. It will exists once per
         FRANP_SW instance on each LT."
    ::= { adnFranpTrunkEnvMIB  6 }

adnFrtSwEntry OBJECT-TYPE
    SYNTAX  AdnFrtSwEntry
    ACCESS  not-accessible
    STATUS  mandatory
    DESCRIPTION
           "One instance of the adnFrtSwTable. There will be one 
         instance for each FRANP_SW on each LT."
    INDEX   { adnCouplerIndex }
    ::= { adnFrtSwTable  1 }

AdnFrtSwEntry ::=
    SEQUENCE {
        adnFrtSwStatFRSI
            OCTET STRING,

        adnFrtSwStatIWF
            OCTET STRING,

        adnFrtSwStatISMTrace
            OCTET STRING
    }

adnFrtSwStatFRSI OBJECT-TYPE
    SYNTAX  OCTET STRING
    ACCESS  read-only
    STATUS  mandatory
    DESCRIPTION
           "This is the internal FRSI data structure. This will 
         contain internal error counters and structures. This 
         is the internal table maintained by FRSI component of 
         FRANP_SW."
    ::= { adnFrtSwEntry  1 }

adnFrtSwStatIWF OBJECT-TYPE
    SYNTAX  OCTET STRING
    ACCESS  read-only
    STATUS  mandatory
    DESCRIPTION
           "This is the internal IWF data structure. This will 
         contain internal error counters and structures. This 
         is the internal table maintained by IWF component of 
         FRANP_SW."
    ::= { adnFrtSwEntry  2 }

adnFrtSwStatISMTrace OBJECT-TYPE
    SYNTAX  OCTET STRING
    ACCESS  read-only
    STATUS  mandatory
    DESCRIPTION
           "This is the ISM message trace area. All ISM Messages 
         transmitted and received by FRSI component of FRANP_SW 
         are stored here.  It is placed here for maintenance 
         purposes only."
    ::= { adnFrtSwEntry  3 }

adnFrsEnvMIB OBJECT IDENTIFIER ::= { adnEnvHss  2 }

adnFrChanPrivateTable OBJECT-TYPE
    SYNTAX  SEQUENCE OF AdnFrChanPrivateEntry
    ACCESS  not-accessible
    STATUS  mandatory
    DESCRIPTION
           "This table is an extension of the Frame Relay Management
        Signalling Group table and the Frame Relay Logical Port Group
        table from RFC1604."
    ::= { adnFrsEnvMIB  1 }

adnFrChanPrivateEntry OBJECT-TYPE
    SYNTAX  AdnFrChanPrivateEntry
    ACCESS  not-accessible
    STATUS  mandatory
    DESCRIPTION
           "An entry in the Channel Table. There will be one entry for each
        FRS channel configured"
    INDEX   { ifIndex }
    ::= { adnFrChanPrivateTable  1 }

AdnFrChanPrivateEntry ::=
    SEQUENCE {
        adnFrChanPrivateSwitch
            OCTET STRING,

        adnFrChanPrivateSignalling
            OCTET STRING,

        adnFrChanPrivateSwMsgtrace
            OCTET STRING,

        adnFrChanPrivateSiMsgtrace
            OCTET STRING
    }

adnFrChanPrivateSwitch OBJECT-TYPE
    SYNTAX  OCTET STRING
    ACCESS  read-only
    STATUS  mandatory
    DESCRIPTION
           "This is the BINARY internal channel structure maintained by FRS_SW.
        It is placed here for maintenance purposes only."
    ::= { adnFrChanPrivateEntry  1 }

adnFrChanPrivateSignalling OBJECT-TYPE
    SYNTAX  OCTET STRING
    ACCESS  read-only
    STATUS  mandatory
    DESCRIPTION
           "This is the BINARY internal channel structure maintained by FRS_SI.
        It is placed here for maintenance purposes only."
    ::= { adnFrChanPrivateEntry  2 }

adnFrChanPrivateSwMsgtrace OBJECT-TYPE
    SYNTAX  OCTET STRING
    ACCESS  read-only
    STATUS  mandatory
    DESCRIPTION
           "This is the internal BINARY message trace table maintained by
        FRS_SW for this channel. The FRS_SW software is implemented as
        a Finite State Machine, and all events received and their corresponding
        states are stored here.
        It is placed here for maintenance purposes only."
    ::= { adnFrChanPrivateEntry  3 }

adnFrChanPrivateSiMsgtrace OBJECT-TYPE
    SYNTAX  OCTET STRING
    ACCESS  read-only
    STATUS  mandatory
    DESCRIPTION
           "This is the internal BINARY message trace table maintained by
        Channel Management portion of FRS_SI for this VC.
        The Channel Management software is implemented as
        a Finite State Machine, and all events received and their corresponding
        states are stored here.
        It is placed here for maintenance purposes only."
    ::= { adnFrChanPrivateEntry  4 }

adnFrVCPrivateTable OBJECT-TYPE
    SYNTAX  SEQUENCE OF AdnFrVCPrivateEntry
    ACCESS  not-accessible
    STATUS  mandatory
    DESCRIPTION
           "This is the PVC table extensions. The PVC End-Point Table in
        RFC1604 is not sufficient for our HSS network. These fields are
        the extensions to it"
    ::= { adnFrsEnvMIB  2 }

adnFrVCPrivateEntry OBJECT-TYPE
    SYNTAX  AdnFrVCPrivateEntry
    ACCESS  not-accessible
    STATUS  mandatory
    DESCRIPTION
           "PVC table entry"
    INDEX   { ifIndex,  frPVCEndptDLCIIndex }
    ::= { adnFrVCPrivateTable  1 }

AdnFrVCPrivateEntry ::=
    SEQUENCE {
        adnFrVCPrivateSwitch
            OCTET STRING,

        adnFrVCPrivateSignalling
            OCTET STRING,

        adnFrVCPrivateSwMsgtrace
            OCTET STRING,

        adnFrVCPrivateSiMsgtrace
            OCTET STRING
    }

adnFrVCPrivateSwitch OBJECT-TYPE
    SYNTAX  OCTET STRING
    ACCESS  read-only
    STATUS  mandatory
    DESCRIPTION
           "This is the BINARY internal PVC structure maintained by FRS_SW.
        It is placed here for maintenance purposes only."
    ::= { adnFrVCPrivateEntry  1 }

adnFrVCPrivateSignalling OBJECT-TYPE
    SYNTAX  OCTET STRING
    ACCESS  read-only
    STATUS  mandatory
    DESCRIPTION
           "This is the BINARY internal PVC structure maintained by FRS_SI.
        It is placed here for maintenance purposes only."
    ::= { adnFrVCPrivateEntry  2 }

adnFrVCPrivateSwMsgtrace OBJECT-TYPE
    SYNTAX  OCTET STRING
    ACCESS  read-only
    STATUS  mandatory
    DESCRIPTION
           "This is the internal BINARY message trace table maintained by
        FRS_SW for this VC. The FRS_SW software is implemented as
        a Finite State Machine, and all events received and their corresponding
        states are stored here.
        It is placed here for maintenance purposes only."
    ::= { adnFrVCPrivateEntry  3 }

adnFrVCPrivateSiMsgtrace OBJECT-TYPE
    SYNTAX  OCTET STRING
    ACCESS  read-only
    STATUS  mandatory
    DESCRIPTION
           "This is the internal BINARY message trace table maintained by
        PVC handler portion of FRS_SI for this VC.
        The PVC handler software is implemented as
        a Finite State Machine, and all events received and their corresponding
        states are stored here.
        It is placed here for maintenance purposes only."
    ::= { adnFrVCPrivateEntry  4 }

adnFrTable OBJECT-TYPE
    SYNTAX  SEQUENCE OF AdnFrEntry
    ACCESS  not-accessible
    STATUS  mandatory
    DESCRIPTION
           "This is the FRS table. It will exists once per FRS instance
        on each LT."
    ::= { adnFrsEnvMIB  3 }

adnFrEntry OBJECT-TYPE
    SYNTAX  AdnFrEntry
    ACCESS  not-accessible
    STATUS  mandatory
    DESCRIPTION
           "One instance of the adnFRSTable. There will be one instance for
        each FRS on each LT."
    INDEX   { adnCouplerIndex }
    ::= { adnFrTable  1 }

AdnFrEntry ::=
    SEQUENCE {
        adnFrStatSignalling
            OCTET STRING,

        adnFrStatSwitching
            OCTET STRING,

        adnFrStatISMTrace
            OCTET STRING
    }

adnFrStatSignalling OBJECT-TYPE
    SYNTAX  OCTET STRING
    ACCESS  read-only
    STATUS  mandatory
    DESCRIPTION
           "This is the internal FRS data structure. This will contain
        internal error counters and structures. This is the internal table
        maintained by FRS_SI."
    ::= { adnFrEntry  1 }

adnFrStatSwitching OBJECT-TYPE
    SYNTAX  OCTET STRING
    ACCESS  read-only
    STATUS  mandatory
    DESCRIPTION
           "This is the internal FRS data structure. This will contain
        internal error counters and structures. This is the internal table
        maintained by FRS_SW."
    ::= { adnFrEntry  2 }

adnFrStatISMTrace OBJECT-TYPE
    SYNTAX  OCTET STRING
    ACCESS  read-only
    STATUS  mandatory
    DESCRIPTION
           "This is the ISM message trace area. All ISM Messages transmitted
	and received by FRS_SI are stored here."
    ::= { adnFrEntry  3 }

adnLdrEnvMIB OBJECT IDENTIFIER ::= { adnEnvHss  3 }

adnLdrEnvTable OBJECT-TYPE
    SYNTAX  SEQUENCE OF AdnLdrEnvEntry
    ACCESS  not-accessible
    STATUS  mandatory
    DESCRIPTION
           "This is the LDR software building block table. Each LDR on each
	 LT has one. It mainly contains debug information."
    ::= { adnLdrEnvMIB  1 }

adnLdrEnvEntry OBJECT-TYPE
    SYNTAX  AdnLdrEnvEntry
    ACCESS  not-accessible
    STATUS  mandatory
    DESCRIPTION
           "There will be one instance for each LDR on each LT."
    INDEX   { adnCouplerIndex }
    ::= { adnLdrEnvTable  1 }

AdnLdrEnvEntry ::=
    SEQUENCE {
        adnLdrSoftStatus
            OCTET STRING,

        adnLdrISMTrace
            OCTET STRING
    }

adnLdrSoftStatus OBJECT-TYPE
    SYNTAX  OCTET STRING
    ACCESS  read-only
    STATUS  mandatory
    DESCRIPTION
           "This is the internal LDR data structure. It contains 
	 the internal error counters and other information of 
         the LDR Software status. This is the internal table
	 maintained by LDR."
    ::= { adnLdrEnvEntry  1 }

adnLdrISMTrace OBJECT-TYPE
    SYNTAX  OCTET STRING
    ACCESS  read-only
    STATUS  mandatory
    DESCRIPTION
           "This is the ISM message trace area. All ISM Messages transmitted
        and received by FRS_SI are stored here."
    ::= { adnLdrEnvEntry  2 }

adnLdrChanEnvTable OBJECT-TYPE
    SYNTAX  SEQUENCE OF AdnLdrChanEnvEntry
    ACCESS  not-accessible
    STATUS  mandatory
    DESCRIPTION
           "This table contains internal channel structure maintained by LDR.
	 It is used for maintenance purposes only."
    ::= { adnLdrEnvMIB  2 }

adnLdrChanEnvEntry OBJECT-TYPE
    SYNTAX  AdnLdrChanEnvEntry
    ACCESS  not-accessible
    STATUS  mandatory
    DESCRIPTION
           "An entry in the LDR Channel Environment Table. There will 
	   be one entry for each LDR channel configured."
    INDEX   { ifIndex }
    ::= { adnLdrChanEnvTable  1 }

AdnLdrChanEnvEntry ::=
    SEQUENCE {
        adnLdrChanTraceFlag
            AdnEnableDisabled,

        adnLdrChanControlData
            OCTET STRING,

        adnLdrChanCmeMsgTrace
            OCTET STRING,

        adnLdrChanInmpFuncTrace
            OCTET STRING
    }

adnLdrChanTraceFlag OBJECT-TYPE
    SYNTAX  AdnEnableDisabled
    ACCESS  read-write
    STATUS  mandatory
    DESCRIPTION
           "Flag indicating if trace is enabled."
    DEFVAL  { disabled }
    ::= { adnLdrChanEnvEntry  1 }

adnLdrChanControlData OBJECT-TYPE
    SYNTAX  OCTET STRING
    ACCESS  read-only
    STATUS  mandatory
    DESCRIPTION
           "This is the BINARY channel control block data structure 
	    maintained by the LDR. It is placed here for maintenance 
	    purposes only"
    ::= { adnLdrChanEnvEntry  2 }

adnLdrChanCmeMsgTrace OBJECT-TYPE
    SYNTAX  OCTET STRING
    ACCESS  read-only
    STATUS  mandatory
    DESCRIPTION
           "This is the trace area for LDR and CME-SUP interface. The 
            information of messages that sent and received by the LDR 
	    are stored here."
    ::= { adnLdrChanEnvEntry  3 }

adnLdrChanInmpFuncTrace OBJECT-TYPE
    SYNTAX  OCTET STRING
    ACCESS  read-only
    STATUS  mandatory
    DESCRIPTION
           "This is the trace area for LDR and INMP Library interface. 
	    Function call information (LDR functions called by INMP 
	    Library, and functions in INMP Library called by LDR) are 
	    recorded here."
    ::= { adnLdrChanEnvEntry  4 }

adnIsnaEnvMib OBJECT IDENTIFIER ::= { adnEnvHss  4 }

adnIsnaIcIntTable OBJECT-TYPE
    SYNTAX  SEQUENCE OF AdnIsnaIcIntEntry
    ACCESS  not-accessible
    STATUS  mandatory
    DESCRIPTION
           "This is the ISNA Internal Connection diagnostic table definitions.
	It is an extension to the adnIsnaIcTable definitions."
    ::= { adnIsnaEnvMib  1 }

adnIsnaIcIntEntry OBJECT-TYPE
    SYNTAX  AdnIsnaIcIntEntry
    ACCESS  not-accessible
    STATUS  mandatory
    DESCRIPTION
           "Internal ISNA IC level diagnostic table. Uses indeces 
         'adnIsnaIcifIndex and 'adnIsnaIcDlci' defined in 
         'adnIsnaIcTable' table."
    INDEX   { adnIsnaIcIntifIndex,  adnIsnaIcIntDlci }
    ::= { adnIsnaIcIntTable  1 }

AdnIsnaIcIntEntry ::=
    SEQUENCE {
        adnIsnaIcIntifIndex
            INTEGER (-2147483648..2147483647),

        adnIsnaIcIntDlci
            INTEGER (-2147483648..2147483647),

        adnIsnaIcIpOutPkts
            Counter,

        adnIsnaIcIpInPkts
            Counter,

        adnIsnaIcIssOutPkts
            Counter,

        adnIsnaIcIssInPkts
            Counter,

        adnIsnaIcIcmpIntPkts
            Counter,

        adnIsnaIcIcmpExtPkts
            Counter,

        adnIsnaIcIpOutDiscards
            Counter,

        adnIsnaIcIpInDiscards
            Counter,

        adnIsnaIcIcbMsgtrace
            OCTET STRING
    }

adnIsnaIcIntifIndex OBJECT-TYPE
    SYNTAX  INTEGER (-2147483648..2147483647)
    ACCESS  read-only
    STATUS  mandatory
    DESCRIPTION
           "This object defines the 1st half of the Internal Connection defined
      in the 'adnIsnaIcTable' and is one to one mapping to 'adnIsnaIcifIndex'
      object."
    ::= { adnIsnaIcIntEntry  1 }

adnIsnaIcIntDlci OBJECT-TYPE
    SYNTAX  INTEGER (-2147483648..2147483647)
    ACCESS  read-only
    STATUS  mandatory
    DESCRIPTION
           "This object defines the 2nd half of the Internal Connection defined
      in the 'adnIsnaIcTable' and is one to one mapping to 'adnIsnaIcDlci'
      object."
    ::= { adnIsnaIcIntEntry  2 }

adnIsnaIcIpOutPkts OBJECT-TYPE
    SYNTAX  Counter
    ACCESS  read-only
    STATUS  mandatory
    DESCRIPTION
           "The total number of packets transmitted by ISNA to the IP layer
	that are associated with a given Internal Connection"
    ::= { adnIsnaIcIntEntry  3 }

adnIsnaIcIpInPkts OBJECT-TYPE
    SYNTAX  Counter
    ACCESS  read-only
    STATUS  mandatory
    DESCRIPTION
           "The total number of packets received by ISNA from the IP layer
	that are associated with a given Internal Connection"
    ::= { adnIsnaIcIntEntry  4 }

adnIsnaIcIssOutPkts OBJECT-TYPE
    SYNTAX  Counter
    ACCESS  read-only
    STATUS  mandatory
    DESCRIPTION
           "The total number of ISS status packets transmitted by ISNA to ISOM 
	that are associated with a given Internal Connection"
    ::= { adnIsnaIcIntEntry  5 }

adnIsnaIcIssInPkts OBJECT-TYPE
    SYNTAX  Counter
    ACCESS  read-only
    STATUS  mandatory
    DESCRIPTION
           "The total number of ISS status packets received by ISNA from ISOM 
	that are associated with a given Internal Connection"
    ::= { adnIsnaIcIntEntry  6 }

adnIsnaIcIcmpIntPkts OBJECT-TYPE
    SYNTAX  Counter
    ACCESS  read-only
    STATUS  mandatory
    DESCRIPTION
           "The total number of ICMP packets received  by ISNA from the local
	IP layer that are associated with a given Internal Connection"
    ::= { adnIsnaIcIntEntry  7 }

adnIsnaIcIcmpExtPkts OBJECT-TYPE
    SYNTAX  Counter
    ACCESS  read-only
    STATUS  mandatory
    DESCRIPTION
           "The total number of ICMP packets transmitted by ISNA to the local
	IP layer that are associated with a given Internal Connection"
    ::= { adnIsnaIcIntEntry  8 }

adnIsnaIcIpOutDiscards OBJECT-TYPE
    SYNTAX  Counter
    ACCESS  read-only
    STATUS  mandatory
    DESCRIPTION
           "The total number of IP packets destined to IP layer, discarded due to
	internal IP access failures or system resources errors. All packets
	discarded are associated with a given Internal Connection."
    ::= { adnIsnaIcIntEntry  9 }

adnIsnaIcIpInDiscards OBJECT-TYPE
    SYNTAX  Counter
    ACCESS  read-only
    STATUS  mandatory
    DESCRIPTION
           "The total number of IP packets received from IP layer, discarded due
	to internal ICS access failures or system resources errors. All packets
	discarded are associated with a given Internal Connection."
    ::= { adnIsnaIcIntEntry  10 }

adnIsnaIcIcbMsgtrace OBJECT-TYPE
    SYNTAX  OCTET STRING
    ACCESS  read-only
    STATUS  mandatory
    DESCRIPTION
           "This is the internal BINARY message trace table maintained by
	ISNA for this IC/PVC. The ISNA software is implemented as
	a Finite State Machine, and all events received and their corresponding
	states are stored here.
	It is placed here for maintenance purposes only."
    ::= { adnIsnaIcIntEntry  11 }

adnIsnaIpTable OBJECT-TYPE
    SYNTAX  SEQUENCE OF AdnIsnaIpEntry
    ACCESS  not-accessible
    STATUS  mandatory
    DESCRIPTION
           "This is the ISNA IP diagnostic table definitions."
    ::= { adnIsnaEnvMib  2 }

adnIsnaIpEntry OBJECT-TYPE
    SYNTAX  AdnIsnaIpEntry
    ACCESS  not-accessible
    STATUS  mandatory
    DESCRIPTION
           "ISNA IP Trafic counters level diagnostic table. Uses index
        'adnIsnaIpIndex' defined in 'adnIsnaIpTable' table."
    INDEX   { adnIsnaIpIndex }
    ::= { adnIsnaIpTable  1 }

AdnIsnaIpEntry ::=
    SEQUENCE {
        adnIsnaIpIndex
            INTEGER (-2147483648..2147483647),

        adnIsnaIpNumOfLpx
            Counter,

        adnIsnaIpNumOfInterface
            Counter,

        adnIsnaIpNumOfVc
            Counter,

        adnIsnaIpIpOutPkts
            Counter,

        adnIsnaIpIpInPkts
            Counter,

        adnIsnaIpIpDiscards
            Counter,

        adnIsnaIpIpomOutPkts
            Counter,

        adnIsnaIpIpomInPkts
            Counter,

        adnIsnaIpIpomDiscards
            Counter,

        adnIsnaIpRdssOutPkts
            Counter,

        adnIsnaIpRdssInPkts
            Counter,

        adnIsnaIpRdssDiscards
            Counter
    }

adnIsnaIpIndex OBJECT-TYPE
    SYNTAX  INTEGER (-2147483648..2147483647)
    ACCESS  read-only
    STATUS  mandatory
    DESCRIPTION
           "This object is mapped to adnIsnaIpIndex in the
        adnIsnaIpTable."
    ::= { adnIsnaIpEntry  1 }

adnIsnaIpNumOfLpx OBJECT-TYPE
    SYNTAX  Counter
    ACCESS  read-only
    STATUS  mandatory
    DESCRIPTION
           "The total number of LPXs (logical processor index) in 
         IIRT (IP ISNA routing table) table."
    ::= { adnIsnaIpEntry  2 }

adnIsnaIpNumOfInterface OBJECT-TYPE
    SYNTAX  Counter
    ACCESS  read-only
    STATUS  mandatory
    DESCRIPTION
           "The total number of Interfaces in IIRT (IP ISNA routing table) table."
    ::= { adnIsnaIpEntry  3 }

adnIsnaIpNumOfVc OBJECT-TYPE
    SYNTAX  Counter
    ACCESS  read-only
    STATUS  mandatory
    DESCRIPTION
           "The total number of VCs in IIRT (IP ISNA routing table) table."
    ::= { adnIsnaIpEntry  4 }

adnIsnaIpIpOutPkts OBJECT-TYPE
    SYNTAX  Counter
    ACCESS  read-only
    STATUS  mandatory
    DESCRIPTION
           "The total number of packets transmitted by ISNA_IP to the IP layer."
    ::= { adnIsnaIpEntry  5 }

adnIsnaIpIpInPkts OBJECT-TYPE
    SYNTAX  Counter
    ACCESS  read-only
    STATUS  mandatory
    DESCRIPTION
           "The total number of packets received by ISNA_IP from the IP layer."
    ::= { adnIsnaIpEntry  6 }

adnIsnaIpIpDiscards OBJECT-TYPE
    SYNTAX  Counter
    ACCESS  read-only
    STATUS  mandatory
    DESCRIPTION
           "The total number of discarded IP packets coming from IP layer."
    ::= { adnIsnaIpEntry  7 }

adnIsnaIpIpomOutPkts OBJECT-TYPE
    SYNTAX  Counter
    ACCESS  read-only
    STATUS  mandatory
    DESCRIPTION
           "The total number of packets transmitted by ISNA_IP to IPOM sybsystem."
    ::= { adnIsnaIpEntry  9 }

adnIsnaIpIpomInPkts OBJECT-TYPE
    SYNTAX  Counter
    ACCESS  read-only
    STATUS  mandatory
    DESCRIPTION
           "The total number of packets received by ISNA_IP from IPOM subsytem."
    ::= { adnIsnaIpEntry  10 }

adnIsnaIpIpomDiscards OBJECT-TYPE
    SYNTAX  Counter
    ACCESS  read-only
    STATUS  mandatory
    DESCRIPTION
           "The total number of discarded IP packets comming from IPOM subsystem."
    ::= { adnIsnaIpEntry  11 }

adnIsnaIpRdssInPkts OBJECT-TYPE
    SYNTAX  Counter
    ACCESS  read-only
    STATUS  mandatory
    DESCRIPTION
           "The total number of packets received by ISNA_IP from RDSS subsytem."
    ::= { adnIsnaIpEntry  13 }

adnIsnaIpRdssOutPkts OBJECT-TYPE
    SYNTAX  Counter
    ACCESS  read-only
    STATUS  mandatory
    DESCRIPTION
           "The total number of packets transmitted by ISNA_IP to RDSS sybsystem."
    ::= { adnIsnaIpEntry  14 }

adnIsnaIpRdssDiscards OBJECT-TYPE
    SYNTAX  Counter
    ACCESS  read-only
    STATUS  mandatory
    DESCRIPTION
           "The total number of discarded IP packets comming from RDSS subsystem."
    ::= { adnIsnaIpEntry  15 }

adnIsnaIpIirtTable OBJECT-TYPE
    SYNTAX  SEQUENCE OF AdnIsnaIpIirtEntry
    ACCESS  not-accessible
    STATUS  mandatory
    DESCRIPTION
           "This is the ISNA IP IIRT (IP ISNA routing table) tree table definitions."
    ::= { adnIsnaEnvMib  3 }

adnIsnaIpIirtEntry OBJECT-TYPE
    SYNTAX  AdnIsnaIpIirtEntry
    ACCESS  not-accessible
    STATUS  mandatory
    DESCRIPTION
           "ISNA IP IIRT (IP ISNA routing table) tree entry table. Uses index
         'adnIsnaIpIirtIpaddrs' defined in 'adnIsnaIpIirtTable' table."
    INDEX   { adnIsnaIpIirtIpaddrs }
    ::= { adnIsnaIpIirtTable  1 }

AdnIsnaIpIirtEntry ::=
    SEQUENCE {
        adnIsnaIpIirtIpaddrs
            IpAddress,

        adnIsnaIpIirtVcNum
            INTEGER (-2147483648..2147483647),

        adnIsnaIpIirtIfIndex
            INTEGER (-2147483648..2147483647),

        adnIsnaIpIirtLpxNum
            INTEGER (-2147483648..2147483647),

        adnIsnaIpIirtSesid
            INTEGER (-2147483648..2147483647),

        adnIsnaIpIirtVcState
            INTEGER
    }

adnIsnaIpIirtIpaddrs OBJECT-TYPE
    SYNTAX  IpAddress
    ACCESS  read-only
    STATUS  mandatory
    DESCRIPTION
           "The next hop IP address ."
    ::= { adnIsnaIpIirtEntry  1 }

adnIsnaIpIirtVcNum OBJECT-TYPE
    SYNTAX  INTEGER (-2147483648..2147483647)
    ACCESS  read-only
    STATUS  mandatory
    DESCRIPTION
           "The VC number on the local Interface, The NHIPA (next 
         hop IP address) apply to
         the remote interface which the VC is connecting."
    ::= { adnIsnaIpIirtEntry  2 }

adnIsnaIpIirtIfIndex OBJECT-TYPE
    SYNTAX  INTEGER (-2147483648..2147483647)
    ACCESS  read-only
    STATUS  mandatory
    DESCRIPTION
           "The ifindex Interface at the local machine."
    ::= { adnIsnaIpIirtEntry  3 }

adnIsnaIpIirtLpxNum OBJECT-TYPE
    SYNTAX  INTEGER (-2147483648..2147483647)
    ACCESS  read-only
    STATUS  mandatory
    DESCRIPTION
           "The LPX (logical processor index) local which the interface 
         is configured on."
    ::= { adnIsnaIpIirtEntry  5 }

adnIsnaIpIirtSesid OBJECT-TYPE
    SYNTAX  INTEGER (-2147483648..2147483647)
    ACCESS  read-only
    STATUS  mandatory
    DESCRIPTION
           "The session id which IP packet is routed to."
    ::= { adnIsnaIpIirtEntry  6 }

adnIsnaIpIirtVcState OBJECT-TYPE
    SYNTAX  INTEGER {
    up(1),
    down(2)
}
    ACCESS  read-only
    STATUS  mandatory
    DESCRIPTION
           "The status of the VC (up or down) which associate with NHIPA
        (next hop IP address."
    ::= { adnIsnaIpIirtEntry  7 }

adnNodeSupervisionEnvMIB OBJECT IDENTIFIER ::= { adnEnvHss  5 }

adnBoardMiscTable OBJECT-TYPE
    SYNTAX  SEQUENCE OF AdnBoardMiscEntry
    ACCESS  not-accessible
    STATUS  mandatory
    DESCRIPTION
           "This is the board miscellaneous characteristics table."
    ::= { adnNodeSupervisionEnvMIB  1 }

adnBoardMiscEntry OBJECT-TYPE
    SYNTAX  AdnBoardMiscEntry
    ACCESS  not-accessible
    STATUS  mandatory
    DESCRIPTION
           "An entry in the Board Miscellaneous 
	   characteristics Table.
           There is one entry for each Board.
	   The index corresponds to equipment
           type 'card' in the adnEquipTable."
    INDEX   { adnEquipType,  adnEquipIndex }
    ::= { adnBoardMiscTable  1 }

AdnBoardMiscEntry ::=
    SEQUENCE {
        adnBoardMiscISL
            OCTET STRING
    }

adnBoardMiscISL OBJECT-TYPE
    SYNTAX  OCTET STRING
    ACCESS  read-only
    STATUS  mandatory
    DESCRIPTION
           "This object contains the characteristics of the board 
         retrieved through the ISL link. This object
	 is a dump of 256 bytes of the EEPROM of the board,
	 It contains information called 'group 2' information.
	 The signification of each byte is detailed in 
	 the document 8BA00940001ASZZA.
	 When the board is not plugged in, the value of this 
	 object is 00 00 00 00 ( that is, an octet string of 
	 length 4, with each octet having a zero decimal value)."
    ::= { adnBoardMiscEntry  1 }

adnMsupToolBoxEnvMIB OBJECT IDENTIFIER ::= { adnEnvHss  13 }

adnMsupToolBoxSetup OBJECT-TYPE
    SYNTAX  INTEGER {
    default(1),
    temporary(2),
    permanent(3)
}
    ACCESS  read-write
    STATUS  mandatory
    DESCRIPTION
           "This object provides a mechanism for controling the
             whole MSUP tool box setup.
	     - default   : the MSUP tool box configuration parameters
                           are set to the default values.
             - temporary : the MSUP tool box configuration parameters
                           have been personalized, but a CU restart
                           will restore the default values. 
	     - permanent : the MSUP tool box configuration parameters
                           have been personalized and saved in order
                           to retrieve the personalization after
                           CU cold or mild restarts.
	     A set to permanent saves the setup for next restarts.
             A set to temporary keeps the current setup but deletes
             the previous save. 
             A set to default restaures the default setup."
    DEFVAL  { default }
    ::= { adnMsupToolBoxEnvMIB  1 }

AdnMsupCtxType ::=
    INTEGER {
        other(0),
        chassisCtx(1),
        boardCtx(2),
        processorCtx(3),
        aeiPortCtx(4),
        atmCtx(5),
        generalCtx(6),
        nodeConfigCtx(7),
        nodeSystCtx(8),
        sessionCtx(9),
        cuCtx(10)
    }

adnMsupCtxTable OBJECT-TYPE
    SYNTAX  SEQUENCE OF AdnMsupCtxEntry
    ACCESS  not-accessible
    STATUS  mandatory
    DESCRIPTION
           "A set of adnMsupCtxEntry entries."
    ::= { adnMsupToolBoxEnvMIB  2 }

adnMsupCtxEntry OBJECT-TYPE
    SYNTAX  AdnMsupCtxEntry
    ACCESS  not-accessible
    STATUS  mandatory
    DESCRIPTION
           "This object provides a mechanism to dump on
	     the CU craft interface contexts in MSUP memory."
    INDEX   { adnMsupCtxType,  adnMsupCtxIndex }
    ::= { adnMsupCtxTable  1 }

AdnMsupCtxEntry ::=
    SEQUENCE {
        adnMsupCtxType
            AdnMsupCtxType,

        adnMsupCtxIndex
            INTEGER,

        adnMsupCtxAction
            INTEGER
    }

adnMsupCtxType OBJECT-TYPE
    SYNTAX  AdnMsupCtxType
    ACCESS  read-only
    STATUS  mandatory
    DESCRIPTION
           "The types of contexts in MSUP that can be dumped :
        - chassisCtx(1)    : context of a chassis
        - boardCtx(2)      : context of a board         
	- processorCtx(3)  : context of a processor
	- aeiPortCtx(4)    : context of an AEI port
   	- atmCtx(5)        : ATM init context
        - generalCtx(6)    : general MSUP data context
	- nodeConfigCtx(7) : node system configuration context
	- nodeSystCtx(8)   : node system contextual context
	- sessionCtx(9)    : IACS session context
	- cuCtx(10)        : CU management context"
    ::= { adnMsupCtxEntry  1 }

adnMsupCtxIndex OBJECT-TYPE
    SYNTAX  INTEGER
    ACCESS  read-only
    STATUS  mandatory
    DESCRIPTION
           "The index of a context."
    ::= { adnMsupCtxEntry  2 }

adnMsupCtxAction OBJECT-TYPE
    SYNTAX  INTEGER {
    other(0),
    dump(1),
    address(2),
    format(3)
}
    ACCESS  read-write
    STATUS  mandatory
    DESCRIPTION
           "This object provides a mechanism to print on the CU craft
             interface information about a context.
	     - dump     : dumps the content of a context,
             - address  : displays the address of a context,
             - format   : displays the context in a C format."
    ::= { adnMsupCtxEntry  3 }

adnMsupPrintMIB OBJECT IDENTIFIER ::= { adnMsupToolBoxEnvMIB  3 }

adnMsupPrintInterface OBJECT-TYPE
    SYNTAX  INTEGER
    ACCESS  read-write
    STATUS  mandatory
    DESCRIPTION
           "This object is a bitmap that enables to activate the
             printing of MSUP exchanges on the CU craft interface.
               
             bit  
             val  meaning
             ---  -------------------------------------------------------
             1    displays exchanges with SMSUP
             2    displays exchanges with ATMSUP
             4    displays exchanges with APSUP
             8    displays exchanges with CUSUP
            16    displays exchanges with NMGS in fixed format
            32    displays exchanges with FLS
            64    displays exchanges with Debug Manager
           128    displays traps sent to SFAS
           256    displays localization service messages"
    DEFVAL  { 0 }
    ::= { adnMsupPrintMIB  1 }

adnMsupPrintExecution OBJECT-TYPE
    SYNTAX  INTEGER
    ACCESS  read-write
    STATUS  mandatory
    DESCRIPTION
           "This object is a bitmap that enables to activate the
             printing of MSUP exchanges on the CU craft interface.
               
             bit  
             val  meaning
             ---  -------------------------------------------------------
             1    displays execution traces about coupler redundancy
             2    displays execution traces about configuration
	     4    displays execution traces about clock synchronization
             8    displays board automaton traces
            16    displays processor automaton traces
            32    displays execution traces about CU management
            64    displays execution traces about coupler debug 
           128    displays execution traces about timer management"
    DEFVAL  { 0 }
    ::= { adnMsupPrintMIB  2 }

adnMsupPrintCouplerStr OBJECT-TYPE
    SYNTAX  INTEGER {
    no(0),
    yes(1)
}
    ACCESS  read-write
    STATUS  mandatory
    DESCRIPTION
           "This object enable to active the display of STR received
             through SMSUP or APSUP from couplers on the CU craft 
             interface"
    DEFVAL  { no }
    ::= { adnMsupPrintMIB  3 }

adnMsupHssTraceMIB OBJECT IDENTIFIER ::= { adnMsupToolBoxEnvMIB  4 }

adnMsupHssTraceLocalizationService OBJECT-TYPE
    SYNTAX  INTEGER {
    no(0),
    yes(1)
}
    ACCESS  read-write
    STATUS  mandatory
    DESCRIPTION
           "This object indicates wether the MSUP localization
             service writes into the MSUP HSS trace buffer."
    DEFVAL  { yes }
    ::= { adnMsupHssTraceMIB  1 }

adnMsupHssTracePrint OBJECT-TYPE
    SYNTAX  INTEGER {
    no(0),
    yes(1)
}
    ACCESS  read-write
    STATUS  mandatory
    DESCRIPTION
           "This object indicates wether MSUP prints the HSS
             traces on the CU craft interface in real time."
    DEFVAL  { no }
    ::= { adnMsupHssTraceMIB  2 }

adnMsupHssTraceFreeze OBJECT-TYPE
    SYNTAX  INTEGER {
    no(0),
    yes(1)
}
    ACCESS  read-write
    STATUS  mandatory
    DESCRIPTION
           "This object indicates wether the MSUP HSS trace
             is frozen. On any CU restart this object is reset
             to the default value."
    DEFVAL  { no }
    ::= { adnMsupHssTraceMIB  3 }

adnMsupHssTraceFreezeOnAnyStr OBJECT-TYPE
    SYNTAX  INTEGER {
    no(0),
    yes(1)
}
    ACCESS  read-write
    STATUS  mandatory
    DESCRIPTION
           "This object indicates wether the MSUP HSS trace
             is to be frozen on next MSUP STR."
    DEFVAL  { no }
    ::= { adnMsupHssTraceMIB  4 }

adnMsupHssTraceFreezeOnStrNumber OBJECT-TYPE
    SYNTAX  INTEGER
    ACCESS  read-write
    STATUS  mandatory
    DESCRIPTION
           "Number of the STR on which to freeze the MSUP HSS trace.
         0 is an unused STR number."
    DEFVAL  { 0 }
    ::= { adnMsupHssTraceMIB  5 }

adnMsupHssTraceDump OBJECT-TYPE
    SYNTAX  INTEGER {
    yes(1)
}
    ACCESS  read-write
    STATUS  mandatory
    DESCRIPTION
           "This object provides a mechanism to dump on the CU
             craft interface the formated content of the whole
             MSUP HSS trace buffer."
    DEFVAL  { yes }
    ::= { adnMsupHssTraceMIB  6 }

adnMsupHssTraceSize OBJECT-TYPE
    SYNTAX  INTEGER
    ACCESS  read-write
    STATUS  mandatory
    DESCRIPTION
           "The size of the MSUP HSS trace buffer. A modification
             of this object can only be taken into account at the next
             start up."
    DEFVAL  { 1 }
    ::= { adnMsupHssTraceMIB  7 }

adnAtmBoardErrCounterTable OBJECT-TYPE
    SYNTAX  SEQUENCE OF AdnAtmBoardErrCounterEntry
    ACCESS  not-accessible
    STATUS  deprecated
    DESCRIPTION
           "This table is the ATM boards error counter table.
        Each counter corresponds to a defect number
        identified by a bit set in the adnAtmBoardASEStatus
        for ASe board, the adnAtmBoardCIGStatus for CIG
	board and the adnAtmBoardHSCStatus for HSC board.
	These nominators are defined in the 
	adnAtmBoardErCounterTable.
        The counters are classified according to the board
        type. Some are specific to the broadband ATM
        switching element (BBASE) board also called the
        matrix board."
    ::= { adnNodeSupervisionEnvMIB  2 }

adnAtmBoardErrCounterEntry OBJECT-TYPE
    SYNTAX  AdnAtmBoardErrCounterEntry
    ACCESS  not-accessible
    STATUS  deprecated
    DESCRIPTION
           "An entry in the ATM boards error counter table."
    INDEX   { adnEquipType,  adnEquipIndex }
    ::= { adnAtmBoardErrCounterTable  1 }

AdnAtmBoardErrCounterEntry ::=
    SEQUENCE {
        adnAtmBoardErrUFOFCounter
            Counter,

        adnAtmBoardErrUFRFCounter
            Counter,

        adnAtmBoardErrNFOFCounter
            Counter,

        adnAtmBoardErrPHTRAMPCounter
            Counter,

        adnAtmBoardErrNFRFCounter
            Counter,

        adnAtmBoardErrNAVCCounter
            Counter,

        adnAtmBoardErrNAVPCounter
            Counter,

        adnAtmBoardErrRBOFCounter
            Counter,

        adnAtmBoardErrQRP0RAMPCounter
            Counter,

        adnAtmBoardErrQRP0DMACounter
            Counter,

        adnAtmBoardErrQRP0FIFOCounter
            Counter,

        adnAtmBoardErrQRP1RAMPCounter
            Counter,

        adnAtmBoardErrQRP1DMACounter
            Counter,

        adnAtmBoardErrQRP1FIFOCounter
            Counter,

        adnAtmBoardErrQRP2RAMPCounter
            Counter,

        adnAtmBoardErrQRP2DMACounter
            Counter,

        adnAtmBoardErrQRP2FIFOCounter
            Counter,

        adnAtmBoardErrQRP3RAMPCounter
            Counter,

        adnAtmBoardErrQRP3DMACounter
            Counter,

        adnAtmBoardErrQRP3FIFOCounter
            Counter,

        adnAtmBoardErrHMP0LLPCCounter
            Counter,

        adnAtmBoardErrHMP0LHPCCounter
            Counter,

        adnAtmBoardErrHMP0SYNCCounter
            Counter,

        adnAtmBoardErrHMP1LLPCCounter
            Counter,

        adnAtmBoardErrHMP1LHPCCounter
            Counter,

        adnAtmBoardErrHMP1SYNCCounter
            Counter
    }

adnAtmBoardErrUFOFCounter OBJECT-TYPE
    SYNTAX  Counter
    ACCESS  read-only
    STATUS  deprecated
    DESCRIPTION
           "The counter associated with the number of user
        FIFO overflows;
        counter #0 of the ATM core;
        this counter is not relevant for the matrix board."
    ::= { adnAtmBoardErrCounterEntry  1 }

adnAtmBoardErrUFRFCounter OBJECT-TYPE
    SYNTAX  Counter
    ACCESS  read-only
    STATUS  deprecated
    DESCRIPTION
           "The counter associated with the number of user
        FIFO read failures;
        counter #1 of the ATM core;
        this counter is not relevant for the matrix board."
    ::= { adnAtmBoardErrCounterEntry  2 }

adnAtmBoardErrNFOFCounter OBJECT-TYPE
    SYNTAX  Counter
    ACCESS  read-only
    STATUS  deprecated
    DESCRIPTION
           "The counter associated with the number of network
        FIFO overflows;
        counter #2 of the ATM core;
        this counter is not relevant for the matrix board."
    ::= { adnAtmBoardErrCounterEntry  3 }

adnAtmBoardErrPHTRAMPCounter OBJECT-TYPE
    SYNTAX  Counter
    ACCESS  read-only
    STATUS  deprecated
    DESCRIPTION
           "The counter associated with the number of BGPHT
        chip RAM parity errors;
        counter #3 of the ATM core;
        this counter is not relevant for the matrix board."
    ::= { adnAtmBoardErrCounterEntry  4 }

adnAtmBoardErrNFRFCounter OBJECT-TYPE
    SYNTAX  Counter
    ACCESS  read-only
    STATUS  deprecated
    DESCRIPTION
           "The counter associated with the number of network
        FIFO read failures;
        counter #4 of the ATM core;
        this counter is not relevant for the matrix board."
    ::= { adnAtmBoardErrCounterEntry  5 }

adnAtmBoardErrNAVCCounter OBJECT-TYPE
    SYNTAX  Counter
    ACCESS  read-only
    STATUS  deprecated
    DESCRIPTION
           "The counter associated with the number of cells
        received on non active VC;
        counter #5 of the ATM core;
        this counter is not relevant for the matrix board."
    ::= { adnAtmBoardErrCounterEntry  6 }

adnAtmBoardErrNAVPCounter OBJECT-TYPE
    SYNTAX  Counter
    ACCESS  read-only
    STATUS  deprecated
    DESCRIPTION
           "The counter associated with the number of cells
        received on non active VP;
        counter #6 of the ATM core;
        this counter is not relevant for the matrix board."
    ::= { adnAtmBoardErrCounterEntry  7 }

adnAtmBoardErrRBOFCounter OBJECT-TYPE
    SYNTAX  Counter
    ACCESS  read-only
    STATUS  deprecated
    DESCRIPTION
           "The counter associated with the number of
        reception buffer overflows;
        counter #7 of the ATM core;
        this counter is not relevant for the matrix board."
    ::= { adnAtmBoardErrCounterEntry  8 }

adnAtmBoardErrQRP0RAMPCounter OBJECT-TYPE
    SYNTAX  Counter
    ACCESS  read-only
    STATUS  deprecated
    DESCRIPTION
           "The counter associated with the number of QRP 0
        chip RAM parity errors;
        counter #14 of the ATM core;
        this counter is only relevant for the matrix board."
    ::= { adnAtmBoardErrCounterEntry  9 }

adnAtmBoardErrQRP0DMACounter OBJECT-TYPE
    SYNTAX  Counter
    ACCESS  read-only
    STATUS  deprecated
    DESCRIPTION
           "The counter associated with the number of QRP 0
        chip DMA errors;
        counter #15 of the ATM core;
        this counter is only relevant for the matrix board."
    ::= { adnAtmBoardErrCounterEntry  10 }

adnAtmBoardErrQRP0FIFOCounter OBJECT-TYPE
    SYNTAX  Counter
    ACCESS  read-only
    STATUS  deprecated
    DESCRIPTION
           "The counter associated with the number of QRP 0
        chip extraction FIFO overflows;
        counter #16 of the ATM core;
        this counter is only relevant for the matrix board."
    ::= { adnAtmBoardErrCounterEntry  11 }

adnAtmBoardErrQRP1RAMPCounter OBJECT-TYPE
    SYNTAX  Counter
    ACCESS  read-only
    STATUS  deprecated
    DESCRIPTION
           "The counter associated with the number of QRP 1
        chip RAM parity errors; 
        counter #17 of the ATM core;
        this counter is only relevant for the matrix board."
    ::= { adnAtmBoardErrCounterEntry  12 }

adnAtmBoardErrQRP1DMACounter OBJECT-TYPE
    SYNTAX  Counter
    ACCESS  read-only
    STATUS  deprecated
    DESCRIPTION
           "The counter associated with the number of QRP 1
        chip DMA errors;
        counter #18 of the ATM core;
        this counter is only relevant for the matrix board."
    ::= { adnAtmBoardErrCounterEntry  13 }

adnAtmBoardErrQRP1FIFOCounter OBJECT-TYPE
    SYNTAX  Counter
    ACCESS  read-only
    STATUS  deprecated
    DESCRIPTION
           "The counter associated with the number of QRP 1
        chip extraction FIFO overflows;
        counter #19 of the ATM core;
        this counter is only relevant for the matrix board."
    ::= { adnAtmBoardErrCounterEntry  14 }

adnAtmBoardErrQRP2RAMPCounter OBJECT-TYPE
    SYNTAX  Counter
    ACCESS  read-only
    STATUS  deprecated
    DESCRIPTION
           "The counter associated with the number of QRP 2
        chip RAM parity errors; 
        counter #20 of the ATM core;
        this counter is only relevant for the matrix board."
    ::= { adnAtmBoardErrCounterEntry  15 }

adnAtmBoardErrQRP2DMACounter OBJECT-TYPE
    SYNTAX  Counter
    ACCESS  read-only
    STATUS  deprecated
    DESCRIPTION
           "The counter associated with the number of QRP 2
        chip DMA errors;
        counter #21 of the ATM core;
        this counter is only relevant for the matrix board."
    ::= { adnAtmBoardErrCounterEntry  16 }

adnAtmBoardErrQRP2FIFOCounter OBJECT-TYPE
    SYNTAX  Counter
    ACCESS  read-only
    STATUS  deprecated
    DESCRIPTION
           "The counter associated with the number of QRP 2
        chip extraction FIFO overflows;
        counter #22 of the ATM core;
        this counter is only relevant for the matrix board."
    ::= { adnAtmBoardErrCounterEntry  17 }

adnAtmBoardErrQRP3RAMPCounter OBJECT-TYPE
    SYNTAX  Counter
    ACCESS  read-only
    STATUS  deprecated
    DESCRIPTION
           "The counter associated with the number of QRP 3
        chip RAM parity errors;
        counter #23 of the ATM core; 
        this counter is only relevant for the matrix board."
    ::= { adnAtmBoardErrCounterEntry  18 }

adnAtmBoardErrQRP3DMACounter OBJECT-TYPE
    SYNTAX  Counter
    ACCESS  read-only
    STATUS  deprecated
    DESCRIPTION
           "The counter associated with the number of QRP 3
        chip DMA errors;
        counter #24 of the ATM core;
        this counter is only relevant for the matrix board."
    ::= { adnAtmBoardErrCounterEntry  19 }

adnAtmBoardErrQRP3FIFOCounter OBJECT-TYPE
    SYNTAX  Counter
    ACCESS  read-only
    STATUS  deprecated
    DESCRIPTION
           "The counter associated with the number of QRP 3
        chip extraction FIFO overflows;
        counter #25 of the ATM core;
        this counter is only relevant for the matrix board."
    ::= { adnAtmBoardErrCounterEntry  20 }

adnAtmBoardErrHMP0LLPCCounter OBJECT-TYPE
    SYNTAX  Counter
    ACCESS  read-only
    STATUS  deprecated
    DESCRIPTION
           "The counter associated with the number of
        low priority cells lost due to SCD;
        counter #26 of the ATM core;
        this counter is only relevant for the matrix board."
    ::= { adnAtmBoardErrCounterEntry  21 }

adnAtmBoardErrHMP0LHPCCounter OBJECT-TYPE
    SYNTAX  Counter
    ACCESS  read-only
    STATUS  deprecated
    DESCRIPTION
           "The counter associated with the number of
        high priority cells lost due to buffer overflow(FULC);
        counter #27 of the ATM core; 
        this counter is only relevant for the matrix board."
    ::= { adnAtmBoardErrCounterEntry  22 }

adnAtmBoardErrHMP0SYNCCounter OBJECT-TYPE
    SYNTAX  Counter
    ACCESS  read-only
    STATUS  deprecated
    DESCRIPTION
           "The counter associated with the number of fault
        synchronization in the HMP 0 chip;
        counter #28 of the ATM core;
        this counter is only relevant for the matrix board."
    ::= { adnAtmBoardErrCounterEntry  23 }

adnAtmBoardErrHMP1LLPCCounter OBJECT-TYPE
    SYNTAX  Counter
    ACCESS  read-only
    STATUS  deprecated
    DESCRIPTION
           "The counter associated with the number of
        low priority cells lost in the HMP 1 chip;
        counter #29 of the ATM core; 
        this counter is only relevant for the matrix board."
    ::= { adnAtmBoardErrCounterEntry  24 }

adnAtmBoardErrHMP1LHPCCounter OBJECT-TYPE
    SYNTAX  Counter
    ACCESS  read-only
    STATUS  deprecated
    DESCRIPTION
           "The counter associated with the number of
        high priority cells lost in the HMP 1 chip;
        counter #30 of the ATM core;
        this counter is only relevant for the matrix board."
    ::= { adnAtmBoardErrCounterEntry  25 }

adnAtmBoardErrHMP1SYNCCounter OBJECT-TYPE
    SYNTAX  Counter
    ACCESS  read-only
    STATUS  deprecated
    DESCRIPTION
           "The counter associated with the number of fault
        synchronization in the HMP 1 chip; 
        counter #31 of the ATM core;
        this counter is only relevant for the matrix board."
    ::= { adnAtmBoardErrCounterEntry  26 }

adnAtmBoardTrCounterTable OBJECT-TYPE
    SYNTAX  SEQUENCE OF AdnAtmBoardTrCounterEntry
    ACCESS  not-accessible
    STATUS  deprecated
    DESCRIPTION
           "This table is the ATM boards traffic counter
        table.
        The counters are classified according to the board
        type. Some are specific to the broadband ATM
        switching element (BBASE) board also called the
        matrix board."
    ::= { adnNodeSupervisionEnvMIB  3 }

adnAtmBoardTrCounterEntry OBJECT-TYPE
    SYNTAX  AdnAtmBoardTrCounterEntry
    ACCESS  not-accessible
    STATUS  deprecated
    DESCRIPTION
           "An entry in the ATM boards traffic counter table."
    INDEX   { adnEquipType,  adnEquipIndex }
    ::= { adnAtmBoardTrCounterTable  1 }

AdnAtmBoardTrCounterEntry ::=
    SEQUENCE {
        adnAtmBoardTrHMP0MTCounter
            Counter,

        adnAtmBoardTrHMP1MTCounter
            Counter,

        adnAtmBoardTrFPTMICICounter
            Gauge
    }

adnAtmBoardTrHMP0MTCounter OBJECT-TYPE
    SYNTAX  Counter
    ACCESS  read-only
    STATUS  deprecated
    DESCRIPTION
           "The counter associated with the observation 
	threshold 1 crossing of the HMP 0 chip;
        counter #0 of the ATM core;
        this counter is only relevant for the matrix board."
    ::= { adnAtmBoardTrCounterEntry  1 }

adnAtmBoardTrHMP1MTCounter OBJECT-TYPE
    SYNTAX  Counter
    ACCESS  read-only
    STATUS  deprecated
    DESCRIPTION
           "The counter associated with the observation 
	threshold 2 crossing of the HMP 1 chip;
        counter #1 of the ATM core;
        this counter is only relevant for the matrix board."
    ::= { adnAtmBoardTrCounterEntry  2 }

adnAtmBoardTrFPTMICICounter OBJECT-TYPE
    SYNTAX  Gauge
    ACCESS  read-only
    STATUS  deprecated
    DESCRIPTION
           "The counter associated with the number of free
        outgoing point-to-multipoint (PTM) internal channel
        identifiers (ICI);
        counter #2 of the ATM core;
        this counter is only relevant for the matrix board."
    ::= { adnAtmBoardTrCounterEntry  3 }

adnAeiPortErrCounterTable OBJECT-TYPE
    SYNTAX  SEQUENCE OF AdnAeiPortErrCounterEntry
    ACCESS  not-accessible
    STATUS  deprecated
    DESCRIPTION
           "This table is the ATM electrical interface (AEI)
        port error counter table.
        Each counter corresponds to a defect number
      	identified by a bit set in the adnAtmPortASEStatus
        for ASe board, the adnAtmPortCIGStatus for CIG
	board and the adnAtmPortHSCStatus for HSC board.
	These nominators are defined in the 
	adnAtmPortErCounterTable.
        The counters are classified according to the board
        type. Some are specific to the broadband ATM
        switching element (BBASE) board also called the
        matrix board."
    ::= { adnNodeSupervisionEnvMIB  4 }

adnAeiPortErrCounterEntry OBJECT-TYPE
    SYNTAX  AdnAeiPortErrCounterEntry
    ACCESS  not-accessible
    STATUS  deprecated
    DESCRIPTION
           "An entry in the ATM electrical interface (AEI) port
        error counter table."
    INDEX   { adnEquipType,  adnEquipIndex }
    ::= { adnAeiPortErrCounterTable  1 }

AdnAeiPortErrCounterEntry ::=
    SEQUENCE {
        adnAeiPortErrOOSCounter
            Counter,

        adnAeiPortErrLOSCounter
            Counter,

        adnAeiPortErrNFOFCounter
            Counter,

        adnAeiPortErrIEMRAMPCounter
            Counter,

        adnAeiPortErrCECHCounter
            Counter,

        adnAeiPortErrUCECHCounter
            Counter,

        adnAeiPortErrCRCMA1Counter
            Counter,

        adnAeiPortErrCRCSICCounter
            Counter,

        adnAeiPortErrNPECounter
            Counter,

        adnAeiPortErrRTAGCounter
            Counter,

        adnAeiPortErrNMA1Counter
            Counter,

        adnAeiPortErrEMA1Counter
            Counter,

        adnAeiPortErrNSFOFCounter
            Counter,

        adnAeiPortErrNFWFCounter
            Counter,

        adnAeiPortErrSFWFCounter
            Counter,

        adnAeiPortErrNSFRFCounter
            Counter,

        adnAeiPortErrUSFRFCounter
            Counter,

        adnAeiPortErrUFWFCounter
            Counter,

        adnAeiPortErrUSFOFCounter
            Counter,

        adnAeiPortErrNICICounter
            Counter,

        adnAeiPortErrNCRCCounter
            Counter,

        adnAeiPortErrNAALCounter
            Counter,

        adnAeiPortErrUCRCCounter
            Counter,

        adnAeiPortErrUAALCounter
            Counter,

        adnAeiPortErrURCCounter
            Counter
    }

adnAeiPortErrOOSCounter OBJECT-TYPE
    SYNTAX  Counter
    ACCESS  read-only
    STATUS  deprecated
    DESCRIPTION
           "The counter associated with the out of
        synchronization intervals;
        counter #0 of the ATM core."
    ::= { adnAeiPortErrCounterEntry  1 }

adnAeiPortErrLOSCounter OBJECT-TYPE
    SYNTAX  Counter
    ACCESS  read-only
    STATUS  deprecated
    DESCRIPTION
           "The counter associated with the loss of
        synchronization intervals; 
        counter #1 of the ATM core;
        this counter is only relevant for the matrix board."
    ::= { adnAeiPortErrCounterEntry  2 }

adnAeiPortErrNFOFCounter OBJECT-TYPE
    SYNTAX  Counter
    ACCESS  read-only
    STATUS  deprecated
    DESCRIPTION
           "The counter associated with the number of network
        FIFO overflows;
        counter #2 of the ATM core."
    ::= { adnAeiPortErrCounterEntry  3 }

adnAeiPortErrIEMRAMPCounter OBJECT-TYPE
    SYNTAX  Counter
    ACCESS  read-only
    STATUS  deprecated
    DESCRIPTION
           "The counter associated with the number of BGIEM 
        chip RAM parity errors;
        counter #3 of the ATM core; 
        this counter is not relevant for the matrix board."
    ::= { adnAeiPortErrCounterEntry  4 }

adnAeiPortErrCECHCounter OBJECT-TYPE
    SYNTAX  Counter
    ACCESS  read-only
    STATUS  deprecated
    DESCRIPTION
           "The counter associated with the number of
        correctable errors on cells header;
        counter #4 of the ATM core."
    ::= { adnAeiPortErrCounterEntry  5 }

adnAeiPortErrUCECHCounter OBJECT-TYPE
    SYNTAX  Counter
    ACCESS  read-only
    STATUS  deprecated
    DESCRIPTION
           "The counter associated with the number of
        uncorrectable errors on cells header;
        counter #5 of the ATM core."
    ::= { adnAeiPortErrCounterEntry  6 }

adnAeiPortErrCRCMA1Counter OBJECT-TYPE
    SYNTAX  Counter
    ACCESS  read-only
    STATUS  deprecated
    DESCRIPTION
           "The counter associated with the number of CRC
        errors on payload field of maintenance active
        cells of type 1 (MA1);
        counter #6 of the ATM core;
        this counter is not relevant for the matrix board."
    ::= { adnAeiPortErrCounterEntry  7 }

adnAeiPortErrCRCSICCounter OBJECT-TYPE
    SYNTAX  Counter
    ACCESS  read-only
    STATUS  deprecated
    DESCRIPTION
           "The counter associated with the number of CRC
        errors on payload field of self identified cells 
        (SIC);
        counter #7 of the ATM core;
        this counter is not relevant for the matrix board."
    ::= { adnAeiPortErrCounterEntry  8 }

adnAeiPortErrNPECounter OBJECT-TYPE
    SYNTAX  Counter
    ACCESS  read-only
    STATUS  deprecated
    DESCRIPTION
           "The counter associated with the number of parity
        errors on payload field of cells;
        counter #8 of the ATM core."
    ::= { adnAeiPortErrCounterEntry  9 }

adnAeiPortErrRTAGCounter OBJECT-TYPE
    SYNTAX  Counter
    ACCESS  read-only
    STATUS  deprecated
    DESCRIPTION
           "The counter associated with the number of
        unallowed routing tags;
        counter #9 of the ATM core;
        this counter is only relevant for the matrix board."
    ::= { adnAeiPortErrCounterEntry  10 }

adnAeiPortErrNMA1Counter OBJECT-TYPE
    SYNTAX  Counter
    ACCESS  read-only
    STATUS  deprecated
    DESCRIPTION
           "The counter associated with the number of lost
        data maintenance cells;
        counter #12 of the ATM core."
    ::= { adnAeiPortErrCounterEntry  11 }

adnAeiPortErrEMA1Counter OBJECT-TYPE
    SYNTAX  Counter
    ACCESS  read-only
    STATUS  deprecated
    DESCRIPTION
           "The counter associated with the number of data
        maintenance cells received with error;
        counter #14 of the ATM core."
    ::= { adnAeiPortErrCounterEntry  12 }

adnAeiPortErrNSFOFCounter OBJECT-TYPE
    SYNTAX  Counter
    ACCESS  read-only
    STATUS  deprecated
    DESCRIPTION
           "The counter associated with the number of
        network/signalling FIFO overflows;
        counter #17 of the ATM core;
        this counter is not relevant for the matrix board."
    ::= { adnAeiPortErrCounterEntry  13 }

adnAeiPortErrNFWFCounter OBJECT-TYPE
    SYNTAX  Counter
    ACCESS  read-only
    STATUS  deprecated
    DESCRIPTION
           "The counter associated with the number of network
        FIFO write failures;
        counter #18 of the ATM core;
        this counter is not relevant for the matrix board."
    ::= { adnAeiPortErrCounterEntry  14 }

adnAeiPortErrSFWFCounter OBJECT-TYPE
    SYNTAX  Counter
    ACCESS  read-only
    STATUS  deprecated
    DESCRIPTION
           "The counter associated with the number of
        signalling FIFO write failures;
        counter #19 of the ATM core;
        this counter is not relevant for the matrix board."
    ::= { adnAeiPortErrCounterEntry  15 }

adnAeiPortErrNSFRFCounter OBJECT-TYPE
    SYNTAX  Counter
    ACCESS  read-only
    STATUS  deprecated
    DESCRIPTION
           "The counter associated with the number of
        network/signalling FIFO read failures;
        counter #20 of the ATM core;
        this counter is not relevant for the matrix board."
    ::= { adnAeiPortErrCounterEntry  16 }

adnAeiPortErrUSFRFCounter OBJECT-TYPE
    SYNTAX  Counter
    ACCESS  read-only
    STATUS  deprecated
    DESCRIPTION
           "The counter associated with the number of
        user/signalling FIFO read failures;
        counter #22 of the ATM core; 
        this counter is not relevant for the matrix board."
    ::= { adnAeiPortErrCounterEntry  17 }

adnAeiPortErrUFWFCounter OBJECT-TYPE
    SYNTAX  Counter
    ACCESS  read-only
    STATUS  deprecated
    DESCRIPTION
           "The counter associated with the number of user
        FIFO write failures;
        counter #23 of the ATM core;
        this counter is not relevant for the matrix board."
    ::= { adnAeiPortErrCounterEntry  18 }

adnAeiPortErrUSFOFCounter OBJECT-TYPE
    SYNTAX  Counter
    ACCESS  read-only
    STATUS  deprecated
    DESCRIPTION
           "The counter associated with the number of
        user/signalling FIFO overflows;
        counter #24 of the ATM core;
        this counter is not relevant for the matrix board."
    ::= { adnAeiPortErrCounterEntry  19 }

adnAeiPortErrNICICounter OBJECT-TYPE
    SYNTAX  Counter
    ACCESS  read-only
    STATUS  deprecated
    DESCRIPTION
           "The counter associated with the number of cells
        received on non active internal channel identifier
        (ICI);
        counter #25 of the ATM core."
    ::= { adnAeiPortErrCounterEntry  20 }

adnAeiPortErrNCRCCounter OBJECT-TYPE
    SYNTAX  Counter
    ACCESS  read-only
    STATUS  deprecated
    DESCRIPTION
           "The counter associated with the number of CRC
        errors on network side; 
        counter #26 of the ATM core."
    ::= { adnAeiPortErrCounterEntry  21 }

adnAeiPortErrNAALCounter OBJECT-TYPE
    SYNTAX  Counter
    ACCESS  read-only
    STATUS  deprecated
    DESCRIPTION
           "The counter associated with the number of
        ATM adaptation layer (AAL)
        sequence errors on network side;
        counter #27 of the ATM core."
    ::= { adnAeiPortErrCounterEntry  22 }

adnAeiPortErrUCRCCounter OBJECT-TYPE
    SYNTAX  Counter
    ACCESS  read-only
    STATUS  deprecated
    DESCRIPTION
           "The counter associated with the number of CRC
        errors on user side;
        counter #28 of the ATM core;
        this counter is not relevant for the matrix board."
    ::= { adnAeiPortErrCounterEntry  23 }

adnAeiPortErrUAALCounter OBJECT-TYPE
    SYNTAX  Counter
    ACCESS  read-only
    STATUS  deprecated
    DESCRIPTION
           "The counter associated with the number of
        ATM adaptation layer (AAL)
        sequence errors on user side; 
        counter #29 of the ATM core;
        this counter is not relevant for the matrix board."
    ::= { adnAeiPortErrCounterEntry  24 }

adnAeiPortErrURCCounter OBJECT-TYPE
    SYNTAX  Counter
    ACCESS  read-only
    STATUS  deprecated
    DESCRIPTION
           "The counter associated with the number of unrouted
        cells; 
        counter #30 of the ATM core;
        this counter is only relevant for the matrix board."
    ::= { adnAeiPortErrCounterEntry  25 }

adnAeiPortTrCounterTable OBJECT-TYPE
    SYNTAX  SEQUENCE OF AdnAeiPortTrCounterEntry
    ACCESS  not-accessible
    STATUS  deprecated
    DESCRIPTION
           "This table is the ATM electrical interface (AEI) port
        traffic counters table.
        The counters are classified according to the board
        type. Some are specific to the broadband ATM
        switching element (BBASE) board also called the
        matrix board."
    ::= { adnNodeSupervisionEnvMIB  5 }

adnAeiPortTrCounterEntry OBJECT-TYPE
    SYNTAX  AdnAeiPortTrCounterEntry
    ACCESS  not-accessible
    STATUS  deprecated
    DESCRIPTION
           "An entry in the ATM electrical interface (AEI) port
        traffic counters table."
    INDEX   { adnEquipType,  adnEquipIndex }
    ::= { adnAeiPortTrCounterTable  1 }

AdnAeiPortTrCounterEntry ::=
    SEQUENCE {
        adnAeiPortTrPTPSetRqCounter
            Counter,

        adnAeiPortTrPTMSetRqCounter
            Counter,

        adnAeiPortTrPTPSetRjBCounter
            Counter,

        adnAeiPortTrPTMSetRjBCounter
            Counter,

        adnAeiPortTrPTPSetRjCCounter
            Counter,

        adnAeiPortTrPTMSetRjCCounter
            Counter,

        adnAeiPortTrPTPSetTrCounter
            Counter,

        adnAeiPortTrPTMSetTrCounter
            Counter,

        adnAeiPortTrPTPCnxCounter
            Gauge,

        adnAeiPortTrPTMCnxCounter
            Gauge,

        adnAeiPortTrPTPBWICIRqCounter
            Counter,

        adnAeiPortTrPTMBWICIRqCounter
            Counter,

        adnAeiPortTrPTPBWRjCounter
            Counter,

        adnAeiPortTrPTMBWRjCounter
            Counter,

        adnAeiPortTrPTPICIRjCounter
            Counter,

        adnAeiPortTrPTMICIRjCounter
            Counter,

        adnAeiPortTrPeakBWCounter
            Gauge,

        adnAeiPortTrFPTPICICounter
            Gauge,

        adnAeiPortTrMPriorBWCounter
            Gauge,

        adnAeiPortTrInCellsCounter
            Counter,

        adnAeiPortTrOutCellsCounter
            Counter
    }

adnAeiPortTrPTPSetRqCounter OBJECT-TYPE
    SYNTAX  Counter
    ACCESS  read-only
    STATUS  deprecated
    DESCRIPTION
           "The counter associated with the number of 
        point-to-point (PTP) setup requests;
        counter #1 of the ATM core."
    ::= { adnAeiPortTrCounterEntry  1 }

adnAeiPortTrPTMSetRqCounter OBJECT-TYPE
    SYNTAX  Counter
    ACCESS  read-only
    STATUS  deprecated
    DESCRIPTION
           "The counter associated with the number of 
        point-to-multipoint (PTM) setup requests;
        counter #2 of the ATM core."
    ::= { adnAeiPortTrCounterEntry  2 }

adnAeiPortTrPTPSetRjBCounter OBJECT-TYPE
    SYNTAX  Counter
    ACCESS  read-only
    STATUS  deprecated
    DESCRIPTION
           "The counter associated with the number of 
        point-to-point (PTP) 
        setup rejects due to blocking;
        counter #3 of the ATM core;
        this counter is not relevant for the matrix board."
    ::= { adnAeiPortTrCounterEntry  3 }

adnAeiPortTrPTMSetRjBCounter OBJECT-TYPE
    SYNTAX  Counter
    ACCESS  read-only
    STATUS  deprecated
    DESCRIPTION
           "The counter associated with the number of 
        point-to-multipoint (PTM) 
        setup rejects due to blocking; 
        counter #4 of the ATM core;
        this counter is not relevant for the matrix board."
    ::= { adnAeiPortTrCounterEntry  4 }

adnAeiPortTrPTPSetRjCCounter OBJECT-TYPE
    SYNTAX  Counter
    ACCESS  read-only
    STATUS  deprecated
    DESCRIPTION
           "The counter associated with the number of
        point-to-point (PTP)
        setup rejects due to communication;
        counter #5 of the ATM core;
        this counter is not relevant for the matrix board."
    ::= { adnAeiPortTrCounterEntry  5 }

adnAeiPortTrPTMSetRjCCounter OBJECT-TYPE
    SYNTAX  Counter
    ACCESS  read-only
    STATUS  deprecated
    DESCRIPTION
           "The counter associated with the number of
        point-to-multipoint (PTM)
        setup rejects due to communication;
        counter #6 of the ATM core;
        this counter is not relevant for the matrix board."
    ::= { adnAeiPortTrCounterEntry  6 }

adnAeiPortTrPTPSetTrCounter OBJECT-TYPE
    SYNTAX  Counter
    ACCESS  read-only
    STATUS  deprecated
    DESCRIPTION
           "The counter associated with the number of 
        point-to-point (PTP) setup trials;
        counter #7 of the ATM core;  
        this counter is not relevant for the matrix board."
    ::= { adnAeiPortTrCounterEntry  7 }

adnAeiPortTrPTMSetTrCounter OBJECT-TYPE
    SYNTAX  Counter
    ACCESS  read-only
    STATUS  deprecated
    DESCRIPTION
           "The counter associated with the number of 
        point-to-multipoint (PTM) setup trials;
        counter #8 of the ATM core;
        this counter is not relevant for the matrix board."
    ::= { adnAeiPortTrCounterEntry  8 }

adnAeiPortTrPTPCnxCounter OBJECT-TYPE
    SYNTAX  Gauge
    ACCESS  read-only
    STATUS  deprecated
    DESCRIPTION
           "The counter associated with the number of
        point-to-point (PTP) connections in progress;
        counter #13 of the ATM core;
        this counter is not relevant for the matrix board."
    ::= { adnAeiPortTrCounterEntry  9 }

adnAeiPortTrPTMCnxCounter OBJECT-TYPE
    SYNTAX  Gauge
    ACCESS  read-only
    STATUS  deprecated
    DESCRIPTION
           "The counter associated with the number of
        point-to-multipoint (PTM) connections in progress;
        counter #14 of the ATM core;
        this counter is not relevant for the matrix board."
    ::= { adnAeiPortTrCounterEntry  10 }

adnAeiPortTrPTPBWICIRqCounter OBJECT-TYPE
    SYNTAX  Counter
    ACCESS  read-only
    STATUS  deprecated
    DESCRIPTION
           "The counter associated with the number of 
        point-to-point (PTP) bandwith or internal
        channel identifier (BW,ICI) requests;
        counter #4 of the ATM core;
        this counter is only relevant for the matrix board."
    ::= { adnAeiPortTrCounterEntry  11 }

adnAeiPortTrPTMBWICIRqCounter OBJECT-TYPE
    SYNTAX  Counter
    ACCESS  read-only
    STATUS  deprecated
    DESCRIPTION
           "The counter associated with the number of 
        point-to-multipoint (PTM) bandwith or internal
        channel identifier (BW,ICI) requests;
        counter #5 of the ATM core;
        this counter is only relevant for the matrix board."
    ::= { adnAeiPortTrCounterEntry  12 }

adnAeiPortTrPTPBWRjCounter OBJECT-TYPE
    SYNTAX  Counter
    ACCESS  read-only
    STATUS  deprecated
    DESCRIPTION
           "The counter associated with the number of 
        point-to-point (PTP) bandwith (BW) requests failure;
        counter #6 of the ATM core;
        this counter is only relevant for the matrix board."
    ::= { adnAeiPortTrCounterEntry  13 }

adnAeiPortTrPTMBWRjCounter OBJECT-TYPE
    SYNTAX  Counter
    ACCESS  read-only
    STATUS  deprecated
    DESCRIPTION
           "The counter associated with the number of 
        point-to-multipoint (PTM) bandwith (BW) 
        requests failure;
        counter #7 of the ATM core;
        this counter is only relevant for the matrix board."
    ::= { adnAeiPortTrCounterEntry  14 }

adnAeiPortTrPTPICIRjCounter OBJECT-TYPE
    SYNTAX  Counter
    ACCESS  read-only
    STATUS  deprecated
    DESCRIPTION
           "The counter associated with the number of 
        point-to-point (PTP) internal channel identifier
        (ICI) requests failure;
        counter #8 of the ATM core;
        this counter is only relevant for the matrix board."
    ::= { adnAeiPortTrCounterEntry  15 }

adnAeiPortTrPTMICIRjCounter OBJECT-TYPE
    SYNTAX  Counter
    ACCESS  read-only
    STATUS  deprecated
    DESCRIPTION
           "The counter associated with the number of
        point-to-multipoint (PTM) internal channel identifier
        (ICI) requests failure;
        counter #9 of the ATM core;
        this counter is only relevant for the matrix board."
    ::= { adnAeiPortTrCounterEntry  16 }

adnAeiPortTrPeakBWCounter OBJECT-TYPE
    SYNTAX  Gauge
    ACCESS  read-only
    STATUS  deprecated
    DESCRIPTION
           "The counter associated with the reserved peak
        bandwith (BW);
        counter #10 of the ATM core;
        this counter is only relevant for the matrix board."
    ::= { adnAeiPortTrCounterEntry  17 }

adnAeiPortTrFPTPICICounter OBJECT-TYPE
    SYNTAX  Gauge
    ACCESS  read-only
    STATUS  deprecated
    DESCRIPTION
           "The counter associated with the number of free
        point-to-point (PTP) internal channel identifiers
        (ICI);
        counter #12 of the ATM core;
        this counter is only relevant for the matrix board."
    ::= { adnAeiPortTrCounterEntry  18 }

adnAeiPortTrMPriorBWCounter OBJECT-TYPE
    SYNTAX  Gauge
    ACCESS  read-only
    STATUS  deprecated
    DESCRIPTION
           "The counter associated with the reserved mean
        priority bandwith (BW);
        Counter #14 of the ATM core;
        this counter is only relevant for the matrix board."
    ::= { adnAeiPortTrCounterEntry  19 }

adnAeiPortTrInCellsCounter OBJECT-TYPE
    SYNTAX  Counter
    ACCESS  read-only
    STATUS  deprecated
    DESCRIPTION
           "The counter associated with the number of incoming
        cells;
        counter #15 of the ATM core.;
        this counter is only relevant for the matrix board."
    ::= { adnAeiPortTrCounterEntry  20 }

adnAeiPortTrOutCellsCounter OBJECT-TYPE
    SYNTAX  Counter
    ACCESS  read-only
    STATUS  deprecated
    DESCRIPTION
           "The counter associated with the number of outgoing
        cells;
        counter #16 of the ATM core;
        this counter is only relevant for the matrix board."
    ::= { adnAeiPortTrCounterEntry  21 }

adnAtmBoardDefTable OBJECT-TYPE
    SYNTAX  SEQUENCE OF AdnAtmBoardDefEntry
    ACCESS  not-accessible
    STATUS  mandatory
    DESCRIPTION
           "This table is the ATM boards defects table.
        Some defects characteristics are updatable. 
        Matrix board case: all the defects are only
        readable."
    ::= { adnNodeSupervisionEnvMIB  20 }

adnAtmBoardDefEntry OBJECT-TYPE
    SYNTAX  AdnAtmBoardDefEntry
    ACCESS  not-accessible
    STATUS  mandatory
    DESCRIPTION
           "An entry in the ATM boards defects table.  There
        will be one entry for each defect (i.e 
        error/warning) configured.  Notice that according to
        the defect number, default value of each parameter
        of the instance may be different between two
        instances."
    INDEX   { adnAtmBoardDefBoardType,  adnAtmBoardDefNumber }
    ::= { adnAtmBoardDefTable  1 }

AdnAtmBoardDefEntry ::=
    SEQUENCE {
        adnAtmBoardDefBoardType
            INTEGER,

        adnAtmBoardDefNumber
            INTEGER,

        adnAtmBoardDefEventClass
            INTEGER,

        adnAtmBoardDefBegThreshold
            INTEGER,

        adnAtmBoardDefEndThreshold
            INTEGER,

        adnAtmBoardDefBegTimer
            INTEGER,

        adnAtmBoardDefEndTimer
            INTEGER,

        adnAtmBoardDefSignalling
            INTEGER,

        adnAtmBoardDefErrOrWng
            INTEGER,

        adnAtmBoardDefReportEnable
            INTEGER
    }

adnAtmBoardDefBoardType OBJECT-TYPE
    SYNTAX  INTEGER {
    bbase(1),
    hbcig(2),
    bbe3b(3),
    bbt3b(4),
    bbs1b(5),
    bbt1b(6),
    bbe1b(7),
    hbcet(8),
    hbcee(9),
    hbceu(10),
    bbs4b(11),
    bbts1c(12),
    bbtp3c(13)
}
    ACCESS  read-only
    STATUS  mandatory
    DESCRIPTION
           "This is the ATM board type."
    ::= { adnAtmBoardDefEntry  1 }

adnAtmBoardDefNumber OBJECT-TYPE
    SYNTAX  INTEGER
    ACCESS  read-only
    STATUS  mandatory
    DESCRIPTION
           "This indicates the defect number. The description
        of each defect is given via the adnAtmBoardErASEStatus
        for ASE board, the adnAtmBoardErHSCStatus for HSC board,
        the adnAtmBoardErCIGStatus for CIG board. These 
        nominators are defined in the adnAtmBoardErTable.
        There's a one to one mapping between the bit
        position and the defect number."
    ::= { adnAtmBoardDefEntry  2 }

adnAtmBoardDefEventClass OBJECT-TYPE
    SYNTAX  INTEGER {
    event(1),
    status(2),
    statusc(3),
    counter(4)
}
    ACCESS  read-only
    STATUS  mandatory
    DESCRIPTION
           "This indicates the event class from hardware side:

        event: single fault signalled by the hardware or
        another software module to the supervision antenna
        inside the coupler board.  No end is signalled, the
        presence of the fault can't be checked.

        status: the beginning of the fault is signalled to
        the supervision antenna inside the coupler board;  
        the presence of the fault can be checked.

        statusc: the hardware provides no interrupt; this
        status is periodically scanned by the supervision
        antenna inside the coupler board.

        counter: a n bit long hardware counter counts the
        elementary events; an interrupt is generally sent at
        saturation; its value can be read; it is reset to 
        zero when read."
    ::= { adnAtmBoardDefEntry  3 }

adnAtmBoardDefBegThreshold OBJECT-TYPE
    SYNTAX  INTEGER
    ACCESS  read-write
    STATUS  mandatory
    DESCRIPTION
           "This indicates the number of times an error is
        detected within a time period (defined by
        adnAtmBoardDefBegTimer) before an event (beginning
        of error) is generated and an error condition is
        entered."
    ::= { adnAtmBoardDefEntry  4 }

adnAtmBoardDefEndThreshold OBJECT-TYPE
    SYNTAX  INTEGER
    ACCESS  read-write
    STATUS  mandatory
    DESCRIPTION
           "This indicates the maximum number of times a
        condition may be detected within a time period
        (defined by adnAtmBoardDefEndTimer) before an event
        (ending of error) is generated and an error
        condition is cleared."
    ::= { adnAtmBoardDefEntry  5 }

adnAtmBoardDefBegTimer OBJECT-TYPE
    SYNTAX  INTEGER	-- UNITS milliseconds

    ACCESS  read-write
    STATUS  mandatory
    DESCRIPTION
           "This indicates the beginning timer in milliseconds
        during which the first appearance of an error is
        controlled."
    ::= { adnAtmBoardDefEntry  6 }

adnAtmBoardDefEndTimer OBJECT-TYPE
    SYNTAX  INTEGER	-- UNITS milliseconds

    ACCESS  read-write
    STATUS  mandatory
    DESCRIPTION
           "This indicates the end timer in milliseconds 
        during which the disappearance of an error is
        controlled."
    ::= { adnAtmBoardDefEntry  7 }

adnAtmBoardDefSignalling OBJECT-TYPE
    SYNTAX  INTEGER
    ACCESS  read-write
    STATUS  mandatory
    DESCRIPTION
           "This indicates the defect signalling in addition to
        the report towards the control unit (CU). 
        It is coded as a bit map.
        The various bit positions are:

        1        : ERI (error indicator, bit inserted in the
                   active maintenance cells to warn
                   neighbour boards that an error is
                   detected),
	2        : P-FERF or RDI-P (path section far end
                   received failure indication sent to the
                   origin of the defect),
	4        : MS-FERF or RDI-L (multiplexing section
                   far end received failure indication sent
                   to the origin of the defect),
	8        : ATM-AIS (alarm indication signal is
                   sent on a line defect towards the network
                   handler dealing with VP/VC AIS management),
	16       : RAI (remote alarm indication),
	32       : RLED (the status led must be set
                   permanent red)."
    ::= { adnAtmBoardDefEntry  8 }

adnAtmBoardDefErrOrWng OBJECT-TYPE
    SYNTAX  INTEGER {
    warning(1),
    error(2)
}
    ACCESS  read-write
    STATUS  mandatory
    DESCRIPTION
           "This indicates the defect type (i.e error or
        warning); an error is a critical defect which
        modifies the operational state of the object."
    ::= { adnAtmBoardDefEntry  9 }

adnAtmBoardDefReportEnable OBJECT-TYPE
    SYNTAX  INTEGER {
    disable(1),
    enable(2)
}
    ACCESS  read-write
    STATUS  mandatory
    DESCRIPTION
           "This indicates the report control of the defect
        towards the control unit (CU)."
    DEFVAL  { enable }
    ::= { adnAtmBoardDefEntry  10 }

adnAeiPortDefTable OBJECT-TYPE
    SYNTAX  SEQUENCE OF AdnAeiPortDefEntry
    ACCESS  not-accessible
    STATUS  mandatory
    DESCRIPTION
           "This table is the ATM electrical interface (AEI)
        port defects table.
        Some defects characteristics are updatable. 
        Matrix board case: all the defects are only
        readable."
    ::= { adnNodeSupervisionEnvMIB  21 }

adnAeiPortDefEntry OBJECT-TYPE
    SYNTAX  AdnAeiPortDefEntry
    ACCESS  not-accessible
    STATUS  mandatory
    DESCRIPTION
           "An entry in the ATM electrical interface (AEI)
        port defects table.  There will
        be one entry for each defect (i.e error/warning)
        configured.  Notice that according to the defect
        number, default value of each parameter of the
        instance may be different between two instances."
    INDEX   { adnAeiPortDefBoardType,  adnAeiPortDefNumber }
    ::= { adnAeiPortDefTable  1 }

AdnAeiPortDefEntry ::=
    SEQUENCE {
        adnAeiPortDefBoardType
            INTEGER,

        adnAeiPortDefNumber
            INTEGER,

        adnAeiPortDefEventClass
            INTEGER,

        adnAeiPortDefDirection
            INTEGER,

        adnAeiPortDefBegThreshold
            INTEGER,

        adnAeiPortDefEndThreshold
            INTEGER,

        adnAeiPortDefBegTimer
            INTEGER,

        adnAeiPortDefEndTimer
            INTEGER,

        adnAeiPortDefSignalling
            INTEGER,

        adnAeiPortDefErrOrWng
            INTEGER,

        adnAeiPortDefReportEnable
            INTEGER
    }

adnAeiPortDefBoardType OBJECT-TYPE
    SYNTAX  INTEGER {
    bbase(1),
    hbcig(2),
    bbe3b(3),
    bbt3b(4),
    bbs1b(5),
    bbt1b(6),
    bbe1b(7),
    hbcet(8),
    hbcee(9),
    hbceu(10),
    bbs4b(11),
    bbts1c(12),
    bbtp3c(13)
}
    ACCESS  read-only
    STATUS  mandatory
    DESCRIPTION
           "This is the ATM board type."
    ::= { adnAeiPortDefEntry  1 }

adnAeiPortDefNumber OBJECT-TYPE
    SYNTAX  INTEGER
    ACCESS  read-only
    STATUS  mandatory
    DESCRIPTION
           "This indicates the defect number. The description
        of each defect is given via the adnAtmPortErASEStatus
        for ASE board, the adnAtmPortErHSCStatus for HSC board,
        the adnAtmPortErCIGStatus for CIG board. These 
        nominators are defined in the adnAtmPortErTable.
	There's a one to one mappingbetween the bit position
        the defect number."
    ::= { adnAeiPortDefEntry  2 }

adnAeiPortDefEventClass OBJECT-TYPE
    SYNTAX  INTEGER {
    event(1),
    status(2),
    statusc(3),
    counter(4)
}
    ACCESS  read-only
    STATUS  mandatory
    DESCRIPTION
           "This indicates the event class from hardware side:

        event: single fault signalled by the hardware or
        another software module to the supervision antenna
        inside the coupler board.  No end is signalled, the
        presence of the fault can't be checked.

        status: the beginning of the fault is signalled to
        the supervision antenna inside the coupler board;
        the presence of the fault can be checked.

        statusc: the hardware provides no interrupt; this
        status is periodically scanned by the supervision
        antenna inside the coupler board.

        counter: a n bit long hardware counter counts the
        elementary events; an interrupt is generally sent at
        saturation; its value can be read; it is reset to 
        zero when read."
    ::= { adnAeiPortDefEntry  3 }

adnAeiPortDefDirection OBJECT-TYPE
    SYNTAX  INTEGER {
    transmit(1),
    receive(2)
}
    ACCESS  read-only
    STATUS  mandatory
    DESCRIPTION
           "This indicates the direction of the defect when it 
        occurs."
    ::= { adnAeiPortDefEntry  4 }

adnAeiPortDefBegThreshold OBJECT-TYPE
    SYNTAX  INTEGER
    ACCESS  read-write
    STATUS  mandatory
    DESCRIPTION
           "This indicates the number of times an error is
        detected within a time period (defined by
        adnAeiPortDefBegTimer) before an event (beginning of
        error) is generated and an error condition is
        entered."
    ::= { adnAeiPortDefEntry  5 }

adnAeiPortDefEndThreshold OBJECT-TYPE
    SYNTAX  INTEGER
    ACCESS  read-write
    STATUS  mandatory
    DESCRIPTION
           "This indicates the maximum number of times a
        condition may be detected within a time period
        (defined by adnAeiPortDefEndTimer) before an event
        (ending of error) is generated and an error
        condition is cleared."
    ::= { adnAeiPortDefEntry  6 }

adnAeiPortDefBegTimer OBJECT-TYPE
    SYNTAX  INTEGER
    ACCESS  read-write
    STATUS  mandatory
    DESCRIPTION
           "This indicates the beginning timer in milliseconds
        during which the first appearance of an error is
        controlled."
    ::= { adnAeiPortDefEntry  7 }

adnAeiPortDefEndTimer OBJECT-TYPE
    SYNTAX  INTEGER
    ACCESS  read-write
    STATUS  mandatory
    DESCRIPTION
           "This indicates the end timer in milliseconds
        during which the disappearance of an error is 
        controlled."
    ::= { adnAeiPortDefEntry  8 }

adnAeiPortDefSignalling OBJECT-TYPE
    SYNTAX  INTEGER
    ACCESS  read-write
    STATUS  mandatory
    DESCRIPTION
           "This indicates the defect signalling in addition to
        the report towards the control unit (CU).
        It is coded as a bit map.
        The various bit positions are:

        1        : ERI (error indicator, bit inserted in the
                   active maintenance cells to warn
                   neighbour boards that an error is
                   detected),
	2        : P-FERF or RDI-P (path section far end
                   received failure indication sent to the
                   origin of the defect),
	4        : MS-FERF or RDI-L (multiplexing section
                   far end received failure indication sent
                   to the origin of the defect),
	8        : ATM-AIS (alarm indication signal is
                   sent on a line defect towards the network
                   handler dealing with VP/VC AIS management),
	16       : RAI (remote alarm indication),
	32       : RLED (the status led must be set
                   permanent red)."
    ::= { adnAeiPortDefEntry  9 }

adnAeiPortDefErrOrWng OBJECT-TYPE
    SYNTAX  INTEGER {
    warning(1),
    error(2)
}
    ACCESS  read-write
    STATUS  mandatory
    DESCRIPTION
           "This indicates the defect type (i.e error or    
        warning); an error is a critical defect which
        modifies the operational state of the object."
    ::= { adnAeiPortDefEntry  10 }

adnAeiPortDefReportEnable OBJECT-TYPE
    SYNTAX  INTEGER {
    disable(1),
    enable(2)
}
    ACCESS  read-write
    STATUS  mandatory
    DESCRIPTION
           "This indicates the report control of the defect
        towards the control unit (CU)."
    DEFVAL  { enable }
    ::= { adnAeiPortDefEntry  11 }

adnAtmLineDefTable OBJECT-TYPE
    SYNTAX  SEQUENCE OF AdnAtmLineDefEntry
    ACCESS  not-accessible
    STATUS  mandatory
    DESCRIPTION
           "This table is the ATM line defects table."
    ::= { adnNodeSupervisionEnvMIB  22 }

adnAtmLineDefEntry OBJECT-TYPE
    SYNTAX  AdnAtmLineDefEntry
    ACCESS  not-accessible
    STATUS  mandatory
    DESCRIPTION
           "An entry in the ATM line errors/warnings and
        defects table.  There will be one entry for each
        defect (error/warning) configured.  Notice that 
        according to the defect number, default value of
        each parameter of the instance may be different
        between two instances."
    INDEX   { adnAtmLineDefLineType,  adnAtmLineDefNumber }
    ::= { adnAtmLineDefTable  1 }

AdnAtmLineDefEntry ::=
    SEQUENCE {
        adnAtmLineDefLineType
            INTEGER,

        adnAtmLineDefNumber
            INTEGER,

        adnAtmLineDefEventClass
            INTEGER,

        adnAtmLineDefUseInPerfCalcul
            INTEGER,

        adnAtmLineDefPerfType
            INTEGER,

        adnAtmLineDefPerfThreshold
            INTEGER,

        adnAtmLineDefDirection
            INTEGER,

        adnAtmLineDefBegThreshold
            INTEGER,

        adnAtmLineDefEndThreshold
            INTEGER,

        adnAtmLineDefBegTimer
            INTEGER,

        adnAtmLineDefEndTimer
            INTEGER,

        adnAtmLineDefSignalling
            INTEGER,

        adnAtmLineDefErrOrWng
            INTEGER,

        adnAtmLineDefReportEnable
            INTEGER,

        adnAtmLineDefHierarchy
            INTEGER (-2147483648..2147483647),

        adnAtmLineDefPerfLevel
            INTEGER,

        adnAtmLineDefFailureSig
            INTEGER,

        adnAtmLineDefDefectSig
            INTEGER
    }

adnAtmLineDefLineType OBJECT-TYPE
    SYNTAX  INTEGER {
    atmDs3(1),
    atmE3(2),
    atmSonet(3),
    atmSdh(4),
    atmDs1(5),
    atmE1(6),
    cesDs1Unstruct(7),
    cesDs1Struct(8),
    cesE1Unstruct(9),
    cesE1Struct(10),
    cesV35(11),
    cesV36(12),
    cesX21(13)
}
    ACCESS  read-only
    STATUS  mandatory
    DESCRIPTION
           "This is the line type."
    ::= { adnAtmLineDefEntry  1 }

adnAtmLineDefNumber OBJECT-TYPE
    SYNTAX  INTEGER
    ACCESS  read-only
    STATUS  mandatory
    DESCRIPTION
           "This indicates the defect number."
    ::= { adnAtmLineDefEntry  2 }

adnAtmLineDefEventClass OBJECT-TYPE
    SYNTAX  INTEGER {
    event(1),
    status(2),
    statusc(3),
    counter(4)
}
    ACCESS  read-only
    STATUS  mandatory
    DESCRIPTION
           "This indicates the event class from hardware side:

        event: single fault signalled by the hardware or
        another software module to the supervision antenna
        inside the coupler board.  No end is signalled, the
        presence of the fault can't be checked.

        status: the beginning of the fault is signalled to
        the supervision antenna inside the coupler board;
        the presence of the fault can be checked.

        statusc: the hardware provides no interrupt; this
        status is periodically scanned by the supervision
        antenna inside the coupler board.

        counter: a n bit long hardware counter counts the
        elementary events; an interrupt is generally sent at
        saturation; its value can be read; it is reset to 
        zero when read."
    ::= { adnAtmLineDefEntry  3 }

adnAtmLineDefUseInPerfCalcul OBJECT-TYPE
    SYNTAX  INTEGER {
    yes(1),
    no(2)
}
    ACCESS  read-write
    STATUS  mandatory
    DESCRIPTION
           "This indicates if the defect is used or not in
        performance calculation.  If the defect is used for
        the performance calculation (i.e  DefUseInPerfCalcul
        = yes), then the type of this defect (DefPerfType) 
        from performance side can be either:
             
        defect: then, each occurence of the defect
        contributes to the performance calculation,

        counter: then, a counter is used to take into
        account this defect in performance calculation
        when the threshold defined by DefPerfThr is
        reached."
    ::= { adnAtmLineDefEntry  4 }

adnAtmLineDefPerfType OBJECT-TYPE
    SYNTAX  INTEGER {
    counter(1),
    defect(2),
    defectc(3)
}
    ACCESS  read-only
    STATUS  mandatory
    DESCRIPTION
           "This indicates the performance type :
             
        counter: a counter is used to take into
        account this defect in performance calculation
        when the threshold defined by DefPerfThr is
        reached,

        defect: each occurence of the defect
        contributes to the performance calculation,

        defectc: each occurence of the defect
        contributes to the performance calculation,
        with counting of seconds (ANSI only)."
    ::= { adnAtmLineDefEntry  5 }

adnAtmLineDefPerfThreshold OBJECT-TYPE
    SYNTAX  INTEGER
    ACCESS  read-only
    STATUS  mandatory
    DESCRIPTION
           "This indicates the threshold value of the
        performance counter."
    ::= { adnAtmLineDefEntry  6 }

adnAtmLineDefDirection OBJECT-TYPE
    SYNTAX  INTEGER {
    transmit(1),
    receive(2),
    receiveInhib(3)
}
    ACCESS  read-only
    STATUS  mandatory
    DESCRIPTION
           "This indicates the direction of the defect when it
        occurs:
             
        transmit: defect on transmission direction,

        receive: defect on reception direction, without
        inhibition of transmission counters,

        receiveInhib: defect on reception direction,
        with inhibition of transmission counters."
    ::= { adnAtmLineDefEntry  7 }

adnAtmLineDefBegThreshold OBJECT-TYPE
    SYNTAX  INTEGER
    ACCESS  read-write
    STATUS  mandatory
    DESCRIPTION
           "This indicates the number of times an error is
        detected within a time period (defined by
        adnAtmLineDefBegTimer) before an event (beginning of
        error) is generated and an error condition is
        entered."
    ::= { adnAtmLineDefEntry  8 }

adnAtmLineDefEndThreshold OBJECT-TYPE
    SYNTAX  INTEGER
    ACCESS  read-write
    STATUS  mandatory
    DESCRIPTION
           "This indicates the maximum number of times a
        condition may be detected within a time period
        (defined by adnAtmLineDefEndTimer) before an event
        (ending of error) is generated and an error
        condition is cleared."
    ::= { adnAtmLineDefEntry  9 }

adnAtmLineDefBegTimer OBJECT-TYPE
    SYNTAX  INTEGER
    ACCESS  read-write
    STATUS  mandatory
    DESCRIPTION
           "This indicates the beginning timer in milliseconds
        during which the first appearance of an error is
        controlled."
    ::= { adnAtmLineDefEntry  10 }

adnAtmLineDefEndTimer OBJECT-TYPE
    SYNTAX  INTEGER
    ACCESS  read-write
    STATUS  mandatory
    DESCRIPTION
           "This indicates the end timer in milliseconds
        during which the disappearance of an error is 
        controlled."
    ::= { adnAtmLineDefEntry  11 }

adnAtmLineDefSignalling OBJECT-TYPE
    SYNTAX  INTEGER
    ACCESS  read-only
    STATUS  deprecated
    DESCRIPTION
           "This indicates the failure signalling in addition to
        the report towards the control unit (CU).
        It is coded as a bit map.
        The various bit positions are:

        1        : ERI (error indicator, bit inserted in the
                   active maintenance cells to warn
                   neighbour boards that an error is 
                   detected),
	2        : P-FERF or RDI-P (path section far end
                   received failure indication sent to the
                   origin of the defect),
	4        : MS-FERF or RDI-L (multiplexing section
                   far end received failure indication sent
                   to the origin of the defect),
	8        : ATM-AIS (alarm indication signal is
                   sent on a line defect towards the network
                   handler dealing with VP/VC AIS management),
	16       : RAI (remote alarm indication),
	32       : RLED (the status led must be set
                   permanent red)."
    ::= { adnAtmLineDefEntry  12 }

adnAtmLineDefErrOrWng OBJECT-TYPE
    SYNTAX  INTEGER {
    warning(1),
    error(2)
}
    ACCESS  read-write
    STATUS  mandatory
    DESCRIPTION
           "This indicates the defect type (i.e error or
        warning); an error is a critical defect which
        modifies the operational state of the object."
    ::= { adnAtmLineDefEntry  13 }

adnAtmLineDefReportEnable OBJECT-TYPE
    SYNTAX  INTEGER {
    disable(1),
    enable(2)
}
    ACCESS  read-write
    STATUS  mandatory
    DESCRIPTION
           "This indicates the report control of the defect
        towards the control unit (CU)."
    DEFVAL  { enable }
    ::= { adnAtmLineDefEntry  14 }

adnAtmLineDefHierarchy OBJECT-TYPE
    SYNTAX  INTEGER (-2147483648..2147483647)
    ACCESS  read-write
    STATUS  mandatory
    DESCRIPTION
           "This indicates the current Defect hierarchy towards
        the other defects; it is coded as a long integer
        (i.e 32 bits).
        There's one bit per defect:
	- bit #n = 0 : defect n masked (i.e the current
        defect inhibits the #n one if both are present),
	- bit #n = 1 : defect n unmasked."
    ::= { adnAtmLineDefEntry  15 }

adnAtmLineDefPerfLevel OBJECT-TYPE
    SYNTAX  INTEGER {
    line(1),
    path(2)
}
    ACCESS  read-only
    STATUS  mandatory
    DESCRIPTION
           "This indicates the level at which the defect
        is managed:
             
        line: the defect is managed at line level,

        path: the defect is managed at path level."
    ::= { adnAtmLineDefEntry  16 }

adnAtmLineDefFailureSig OBJECT-TYPE
    SYNTAX  INTEGER
    ACCESS  read-write
    STATUS  mandatory
    DESCRIPTION
           "This indicates the failure signalling in addition to
        the report towards the control unit (CU).
        It is coded as a bit map.
        The various bit positions are:

        1        : ERI or RSA (error indicator, bit inserted
                   in theactive maintenance cells to warn
                   neighbour boards that an error is 
                   detected),
	2        : P-FERF or RDI-P or RAI (path section far
                   end received failure indication sent to
                   the origin of the defect),
	4        : MS-FERF or RDI-L (multiplexing section
                   far end received failure indication sent
                   to the origin of the defect),
	8        : ATM-AIS (alarm indication signal is
                   sent on a line defect towards the network
                   handler dealing with VP/VC AIS management),
	32       : RLED (the status led must be set
                   permanent red)."
    ::= { adnAtmLineDefEntry  17 }

adnAtmLineDefDefectSig OBJECT-TYPE
    SYNTAX  INTEGER
    ACCESS  read-write
    STATUS  mandatory
    DESCRIPTION
           "This indicates the defect signalling in addition to
        the report towards the control unit (CU).
        It is coded as a bit map.
        The various bit positions are:

        1        : ERI or RSA (error indicator, bit inserted
                   in theactive maintenance cells to warn
                   neighbour boards that an error is 
                   detected),
	2        : P-FERF or RDI-P or RAI (path section far
                   end received failure indication sent to
                   the origin of the defect),
	4        : MS-FERF or RDI-L (multiplexing section
                   far end received failure indication sent
                   to the origin of the defect),
	8        : ATM-AIS (ATM alarm indication signal is
                   sent on a line defect towards the network
                   handler dealing with VP/VC AIS management),
	32       : RLED (the status led must be set
                   permanent red),
	64       : NB-AIS (not ATM alarm indication signal
                   is sent on a line defect towards the AEI
                   side),
	128      : TCK (trunk conditioning: in circuit
                   emulation, a specified pattern is sent
                   in timeslots, except TS0: a pattern for
                   TS16, another one for other TS)."
    ::= { adnAtmLineDefEntry  18 }

adnAtmLinePerfTable OBJECT-TYPE
    SYNTAX  SEQUENCE OF AdnAtmLinePerfEntry
    ACCESS  not-accessible
    STATUS  mandatory
    DESCRIPTION
           "This table is the ATM line performance parameters
        table."
    ::= { adnNodeSupervisionEnvMIB  23 }

adnAtmLinePerfEntry OBJECT-TYPE
    SYNTAX  AdnAtmLinePerfEntry
    ACCESS  not-accessible
    STATUS  mandatory
    DESCRIPTION
           "An entry in the ATM line performance parameters
        table.  There will be one entry for each line type."
    INDEX   { adnAtmLinePerfLineType }
    ::= { adnAtmLinePerfTable  1 }

AdnAtmLinePerfEntry ::=
    SEQUENCE {
        adnAtmLinePerfLineType
            INTEGER,

        adnAtmLinePerfBlocksPerSec
            INTEGER,

        adnAtmLinePerfLowErrBlockThr
            INTEGER,

        adnAtmLinePerfHighErrBlockThr
            INTEGER,

        adnAtmLinePerfBegUnAvailable
            INTEGER,

        adnAtmLinePerfEndUnAvailable
            INTEGER,

        adnAtmLinePerfConsSeverErrSec
            INTEGER,

        adnAtmLinePerfHighBBE15Thr
            INTEGER,

        adnAtmLinePerfHighES15Thr
            INTEGER,

        adnAtmLinePerfHighSES15Thr
            INTEGER,

        adnAtmLinePerfLowBBE15Thr
            INTEGER,

        adnAtmLinePerfLowES15Thr
            INTEGER,

        adnAtmLinePerfLowSES15Thr
            INTEGER,

        adnAtmLinePerfBBE24Thr
            INTEGER,

        adnAtmLinePerfES24Thr
            INTEGER,

        adnAtmLinePerfSES24Thr
            INTEGER
    }

adnAtmLinePerfLineType OBJECT-TYPE
    SYNTAX  INTEGER {
    atmDs3(1),
    atmE3(2),
    atmSonet(3),
    atmSdh(4),
    atmDs1(5),
    atmE1(6),
    cesDs1(7),
    cesE1(8)
}
    ACCESS  read-only
    STATUS  mandatory
    DESCRIPTION
           "This is the line type."
    ::= { adnAtmLinePerfEntry  1 }

adnAtmLinePerfBlocksPerSec OBJECT-TYPE
    SYNTAX  INTEGER
    ACCESS  read-only
    STATUS  mandatory
    DESCRIPTION
           "This indicates the number of blocks sent and
        received per second."
    ::= { adnAtmLinePerfEntry  2 }

adnAtmLinePerfLowErrBlockThr OBJECT-TYPE
    SYNTAX  INTEGER
    ACCESS  read-write
    STATUS  mandatory
    DESCRIPTION
           "This indicates the low second error block
        threshold; the value range of this threshold is
        1..adnAtmLinePerfHighErrBlockThr."
    ::= { adnAtmLinePerfEntry  3 }

adnAtmLinePerfHighErrBlockThr OBJECT-TYPE
    SYNTAX  INTEGER
    ACCESS  read-write
    STATUS  mandatory
    DESCRIPTION
           "This indicates the high second error block
        threshold; the value range of this threshold is
        1..adnAtmLinePerfBlocksPerSec."
    ::= { adnAtmLinePerfEntry  4 }

adnAtmLinePerfBegUnAvailable OBJECT-TYPE
    SYNTAX  INTEGER
    ACCESS  read-write
    STATUS  mandatory
    DESCRIPTION
           "This indicates the number of consecutive severely
        erroned seconds necessary to declare the beginning
        of an unavailable period."
    ::= { adnAtmLinePerfEntry  5 }

adnAtmLinePerfEndUnAvailable OBJECT-TYPE
    SYNTAX  INTEGER
    ACCESS  read-write
    STATUS  mandatory
    DESCRIPTION
           "This indicates the number of consecutive non
        severely erroned seconds necessary to declare the
        ending of the unavailable period."
    ::= { adnAtmLinePerfEntry  6 }

adnAtmLinePerfConsSeverErrSec OBJECT-TYPE
    SYNTAX  INTEGER
    ACCESS  read-write
    STATUS  mandatory
    DESCRIPTION
           "This indicates the number of consecutive severely
        errored seconds used for the F3 maintenance flow
        calculation."
    ::= { adnAtmLinePerfEntry  7 }

adnAtmLinePerfHighBBE15Thr OBJECT-TYPE
    SYNTAX  INTEGER
    ACCESS  read-write
    STATUS  mandatory
    DESCRIPTION
           "This indicates the high threshold for background
        block error on 1/4 hour period;
        the value range of this threshold is
        0..900*adnAtmLinePerfHighErrBlockThr."
    ::= { adnAtmLinePerfEntry  8 }

adnAtmLinePerfHighES15Thr OBJECT-TYPE
    SYNTAX  INTEGER
    ACCESS  read-write
    STATUS  mandatory
    DESCRIPTION
           "This indicates the high threshold for errored
        second on 1/4 hour period;
        the value range of this threshold is 0..900."
    ::= { adnAtmLinePerfEntry  9 }

adnAtmLinePerfHighSES15Thr OBJECT-TYPE
    SYNTAX  INTEGER
    ACCESS  read-write
    STATUS  mandatory
    DESCRIPTION
           "This indicates the high threshold for severely
        errored second on 1/4 hour period;
        the value range of this threshold is 0..900."
    ::= { adnAtmLinePerfEntry  10 }

adnAtmLinePerfLowBBE15Thr OBJECT-TYPE
    SYNTAX  INTEGER
    ACCESS  read-write
    STATUS  mandatory
    DESCRIPTION
           "This indicates the low threshold for background
        block error on 1/4 hour period;
        the value range of this threshold is
        0..adnAtmLinePerfHighBBE15Thr."
    ::= { adnAtmLinePerfEntry  11 }

adnAtmLinePerfLowES15Thr OBJECT-TYPE
    SYNTAX  INTEGER
    ACCESS  read-write
    STATUS  mandatory
    DESCRIPTION
           "This indicates the low threshold for errored
        second on 1/4 hour period;
        the value range of this threshold is
        0..adnAtmLinePerfHighES15Thr."
    ::= { adnAtmLinePerfEntry  12 }

adnAtmLinePerfLowSES15Thr OBJECT-TYPE
    SYNTAX  INTEGER
    ACCESS  read-write
    STATUS  mandatory
    DESCRIPTION
           "This indicates the low threshold for severely
        errored second on 1/4 hour period;
        the value range of this threshold is
        0..adnAtmLinePerfHighSES15Thr."
    ::= { adnAtmLinePerfEntry  13 }

adnAtmLinePerfBBE24Thr OBJECT-TYPE
    SYNTAX  INTEGER
    ACCESS  read-write
    STATUS  mandatory
    DESCRIPTION
           "This indicates the threshold for background block
        error on 24 hours period;
        the value range of this threshold is
        0..86400*adnAtmLinePerfHighErrBlockThr."
    ::= { adnAtmLinePerfEntry  14 }

adnAtmLinePerfES24Thr OBJECT-TYPE
    SYNTAX  INTEGER
    ACCESS  read-write
    STATUS  mandatory
    DESCRIPTION
           "This indicates the threshold for errored second on
        24 hours period;
        the value range of this threshold is 0..86400."
    ::= { adnAtmLinePerfEntry  15 }

adnAtmLinePerfSES24Thr OBJECT-TYPE
    SYNTAX  INTEGER
    ACCESS  read-write
    STATUS  mandatory
    DESCRIPTION
           "This indicates the threshold for severely errored
        second on 24 hours period;
        the value range of this threshold is 0..86400."
    ::= { adnAtmLinePerfEntry  16 }

adnHscBoardTrMgtEnvTable OBJECT-TYPE
    SYNTAX  SEQUENCE OF AdnHscBoardTrMgtEnvEntry
    ACCESS  not-accessible
    STATUS  mandatory
    DESCRIPTION
           "This table is the HSC Board Traffic Management
        parameters table.
	This is only relevant for HSC boards with
	output buffers"
    ::= { adnNodeSupervisionEnvMIB  24 }

adnHscBoardTrMgtEnvEntry OBJECT-TYPE
    SYNTAX  AdnHscBoardTrMgtEnvEntry
    ACCESS  not-accessible
    STATUS  mandatory
    DESCRIPTION
           "An entry in the ATM Traffic Management parameters
        table."
    INDEX   { adnEquipType,  adnEquipIndex,  adnHscBoardTrMgtEnvOBLineAssig }
    ::= { adnHscBoardTrMgtEnvTable  1 }

AdnHscBoardTrMgtEnvEntry ::=
    SEQUENCE {
        adnHscBoardTrMgtEnvOBLineAssig
            INTEGER,

        adnHscBoardTrMgtEnvMOBEFCIOffTh
            INTEGER,

        adnHscBoardTrMgtEnvLOBEFCIOffTh
            INTEGER
    }

adnHscBoardTrMgtEnvOBLineAssig OBJECT-TYPE
    SYNTAX  INTEGER
    ACCESS  read-only
    STATUS  mandatory
    DESCRIPTION
           "This indicates the line number the output
	buffer is assigned to."
    ::= { adnHscBoardTrMgtEnvEntry  1 }

adnHscBoardTrMgtEnvMOBEFCIOffTh OBJECT-TYPE
    SYNTAX  INTEGER	-- UNITS cells

    ACCESS  read-write
    STATUS  mandatory
    DESCRIPTION
           "This indicates the Explicit Forward Congestion
	Indication (EFCI) activation threshold in medium
	priority output buffer (OB);
	EFCI is generated towards the receiver termination
	point, in order to prevent congestion situation to
	be encountered within the output buffer;
	EFCI tagging is activated as soon as the activation
	threshold is reached; EFCI tagging is stopped as 
	soon as the filling of the OB is below the EFCI
	desactivation threshold;
	the value range of the threshold is 
	0..adnHscBoardTrMgtMOBSize;
        this is not relevant for E1B and T1B boards."
    ::= { adnHscBoardTrMgtEnvEntry  2 }

adnHscBoardTrMgtEnvLOBEFCIOffTh OBJECT-TYPE
    SYNTAX  INTEGER	-- UNITS cells

    ACCESS  read-write
    STATUS  mandatory
    DESCRIPTION
           "This indicates the Explicit Forward Congestion
	Indication (EFCI) desactivation threshold in low
	priority output buffer (OB);
	EFCI is generated towards the receiver termination
	point, in order to prevent congestion situation to
	be encountered within the output buffer;
	EFCI tagging is activated as soon as the activation
	threshold is reached; EFCI tagging is stopped as 
	soon as the filling of the OB is below the EFCI
	desactivation threshold;
	the value range of the threshold is 
	0..adnHscBoardTrMgtLOBSize;
        this is not relevant for E1B and T1B boards."
    ::= { adnHscBoardTrMgtEnvEntry  3 }

adnAseBoardTrMgtEnvTable OBJECT-TYPE
    SYNTAX  SEQUENCE OF AdnAseBoardTrMgtEnvEntry
    ACCESS  not-accessible
    STATUS  mandatory
    DESCRIPTION
           "This table is the BBASE Board Traffic Management 
	environment table;
	the index is the AEI port number of the BBASE;
	this is relevant only for the matrix board with 
	adnEquipSubType equal to adnBbaseb."
    ::= { adnNodeSupervisionEnvMIB  25 }

adnAseBoardTrMgtEnvEntry OBJECT-TYPE
    SYNTAX  AdnAseBoardTrMgtEnvEntry
    ACCESS  not-accessible
    STATUS  mandatory
    DESCRIPTION
           "An entry in the BBASE Board Traffic Management
	environment table."
    INDEX   { adnAseBoardTrMgtEnvAeiPort }
    ::= { adnAseBoardTrMgtEnvTable  1 }

AdnAseBoardTrMgtEnvEntry ::=
    SEQUENCE {
        adnAseBoardTrMgtEnvAeiPort
            INTEGER,

        adnAseBoardTrMgtEnvAeiSpeed
            INTEGER
    }

adnAseBoardTrMgtEnvAeiPort OBJECT-TYPE
    SYNTAX  INTEGER
    ACCESS  read-only
    STATUS  mandatory
    DESCRIPTION
           "This is BBASE AEI port number."
    ::= { adnAseBoardTrMgtEnvEntry  1 }

adnAseBoardTrMgtEnvAeiSpeed OBJECT-TYPE
    SYNTAX  INTEGER {
    speed622(1),
    speed603(2),
    speed593(3),
    speed565(4),
    speed155(5),
    speed150(6),
    speed148(7),
    speed142(8),
    speedLine(9)
}
    ACCESS  read-write
    STATUS  mandatory
    DESCRIPTION
           "This indicates the speed of the AEI port ;
	the allowed values are :
		- speed622  : 622.08 Mb/s
		- speed603  : 603.23 Mb/s
		- speed593  : 593.80 Mb/s
		- speed565  : 565.53 Mb/s
		- speed155  : 155.52 Mb/s
		- speed150  : 150.81 Mb/s
		- speed148  : 148.45 Mb/s
		- speed142  : 142.00 Mb/s
		- speedLine : speed of the outgoing
		physical line ;
	this is relevant only for the matrix board with 
	adnEquipSubType equal to adnBbaseb."
    ::= { adnAseBoardTrMgtEnvEntry  2 }

adnCongMgmtPrivateMIB OBJECT IDENTIFIER ::= { adnEnvHss  6 }

adnCongMgmtLTTable OBJECT-TYPE
    SYNTAX  SEQUENCE OF AdnCongMgmtLTEntry
    ACCESS  not-accessible
    STATUS  mandatory
    DESCRIPTION
           "The Frame Relay LT Information table for Congestion
         Management."
    ::= { adnCongMgmtPrivateMIB  1 }

adnCongMgmtLTEntry OBJECT-TYPE
    SYNTAX  AdnCongMgmtLTEntry
    ACCESS  not-accessible
    STATUS  mandatory
    DESCRIPTION
           "An entry in the Frame Relay LT Information table
           . The line and channel portion of ifIndex is not
	   significant."
    INDEX   { adnCouplerIndex }
    ::= { adnCongMgmtLTTable  1 }

AdnCongMgmtLTEntry ::=
    SEQUENCE {
        adnCongMgmtLTTraceFlag
            AdnEnableDisabled,

        adnCongMgmtFreeBd2CongLevelTable
            OCTET STRING,

        adnCongMgmtProcUtilization
            INTEGER (-2147483648..2147483647)
    }

adnCongMgmtLTTraceFlag OBJECT-TYPE
    SYNTAX  AdnEnableDisabled
    ACCESS  read-write
    STATUS  mandatory
    DESCRIPTION
           " flag indicating if trace per LT is enabled "
    ::= { adnCongMgmtLTEntry  1 }

adnCongMgmtFreeBd2CongLevelTable OBJECT-TYPE
    SYNTAX  OCTET STRING
    ACCESS  read-write
    STATUS  mandatory
    DESCRIPTION
           "This is the BINARY table that determines the congestion level
	 based upon the percentage of free Cryspix Buffer descriptors. 
         It is placed here so that the level could be changed to
	 achieve fine tuning. It is placed here for debugging
	 and maintenance purpose only"
    ::= { adnCongMgmtLTEntry  2 }

adnCongMgmtProcUtilization OBJECT-TYPE
    SYNTAX  INTEGER (-2147483648..2147483647)
    ACCESS  read-only
    STATUS  mandatory
    DESCRIPTION
           "This is the processor utilization value of this LT as calculated by the
         congestion management. it is placed here for maintenance purpose
	 only"
    ::= { adnCongMgmtLTEntry  3 }

adnCongMgmtChanEnvTable OBJECT-TYPE
    SYNTAX  SEQUENCE OF AdnCongMgmtChanEnvEntry
    ACCESS  not-accessible
    STATUS  mandatory
    DESCRIPTION
           "The Frame Relay channel Information table for Congestion
         Management."
    ::= { adnCongMgmtPrivateMIB  2 }

adnCongMgmtChanEnvEntry OBJECT-TYPE
    SYNTAX  AdnCongMgmtChanEnvEntry
    ACCESS  not-accessible
    STATUS  mandatory
    DESCRIPTION
           "An entry in the Frame Relay Channel Information
           table."
    INDEX   { ifIndex }
    ::= { adnCongMgmtChanEnvTable  1 }

AdnCongMgmtChanEnvEntry ::=
    SEQUENCE {
        adnCongMgmtChannel
            OCTET STRING,

        adnCongMgmtChanDiscMsgtrace
            OCTET STRING,

        adnCongMgmtChanAppliMsgTrace
            OCTET STRING,

        adnCongMgmtChanTraceFlag
            AdnEnableDisabled,

        adnCongMgmtChanUtilization
            INTEGER (-2147483648..2147483647),

        adnCongMgmtChanEgressMaxCUF
            INTEGER (-2147483648..2147483647),

        adnCongMgmtChanMinTPSF
            INTEGER (-2147483648..2147483647)
    }

adnCongMgmtChannel OBJECT-TYPE
    SYNTAX  OCTET STRING
    ACCESS  read-only
    STATUS  mandatory
    DESCRIPTION
           "This is the BINARY internal structure per channel maintained by
        congestion management. It contains the contents of the channel 
	control block. It is placed here for maintenance
        purposes only."
    ::= { adnCongMgmtChanEnvEntry  1 }

adnCongMgmtChanDiscMsgtrace OBJECT-TYPE
    SYNTAX  OCTET STRING
    ACCESS  read-only
    STATUS  mandatory
    DESCRIPTION
           "This is the BINARY discard message trace table per channel maintained
	by congestion management. It contents the discard message
	received by this channel from other cards. It is placed here for maintenance
	purposes only."
    ::= { adnCongMgmtChanEnvEntry  2 }

adnCongMgmtChanAppliMsgTrace OBJECT-TYPE
    SYNTAX  OCTET STRING
    ACCESS  read-only
    STATUS  mandatory
    DESCRIPTION
           "This is the BINARY message trace table per channel maintained
        by congestion management. It contents the trace of all the  messages
        received by this channel from the application. It is placed here for maintenance
        purposes only."
    ::= { adnCongMgmtChanEnvEntry  3 }

adnCongMgmtChanTraceFlag OBJECT-TYPE
    SYNTAX  AdnEnableDisabled
    ACCESS  read-write
    STATUS  mandatory
    DESCRIPTION
           " flag indicating if trace per channel is enabled "
    ::= { adnCongMgmtChanEnvEntry  4 }

adnCongMgmtChanUtilization OBJECT-TYPE
    SYNTAX  INTEGER (-2147483648..2147483647)
    ACCESS  read-only
    STATUS  mandatory
    DESCRIPTION
           " Current channel utilization value  in the egress direction"
    ::= { adnCongMgmtChanEnvEntry  5 }

adnCongMgmtChanEgressMaxCUF OBJECT-TYPE
    SYNTAX  INTEGER (-2147483648..2147483647)	-- UNITS Percent

    ACCESS  read-write
    STATUS  mandatory
    DESCRIPTION
           "This is the maximum of the egress channel utilization and the
        processor utilization. This field may be set to zero via SNMP
        command, so that the user may be able to measure or read the
        maximum CUF over a period of time."
    ::= { adnCongMgmtChanEnvEntry  6 }

adnCongMgmtChanMinTPSF OBJECT-TYPE
    SYNTAX  INTEGER (-2147483648..2147483647)
    ACCESS  read-write
    STATUS  mandatory
    DESCRIPTION
           "This is the minimum time in microseconds needed to process
        a subframe. This value is used when calculating processor
        utilization."
    ::= { adnCongMgmtChanEnvEntry  7 }

adnCongMgmtVCEnvTable OBJECT-TYPE
    SYNTAX  SEQUENCE OF AdnCongMgmtVCEnvEntry
    ACCESS  not-accessible
    STATUS  mandatory
    DESCRIPTION
           "This is the VC table for Frame Relay Congestion Management."
    ::= { adnCongMgmtPrivateMIB  3 }

adnCongMgmtVCEnvEntry OBJECT-TYPE
    SYNTAX  AdnCongMgmtVCEnvEntry
    ACCESS  not-accessible
    STATUS  mandatory
    DESCRIPTION
           "VC table entry"
    INDEX   { ifIndex,  adnCongMgmtVCDLCIIndex }
    ::= { adnCongMgmtVCEnvTable  1 }

AdnCongMgmtVCEnvEntry ::=
    SEQUENCE {
        adnCongMgmtVCcb
            OCTET STRING,

        adnCongMgmtVCLineDataTrace
            OCTET STRING,

        adnCongMgmtVCBusDataTrace
            OCTET STRING,

        adnCongMgmtVCTraceEnable
            AdnEnableDisabled,

        adnCongMgmtVCStateMachineTrace
            OCTET STRING
    }

adnCongMgmtVCcb OBJECT-TYPE
    SYNTAX  OCTET STRING
    ACCESS  read-only
    STATUS  mandatory
    DESCRIPTION
           "This is the BINARY internal PVC structure maintained by FRANP_SW.
        It is placed here for maintenance purposes only."
    ::= { adnCongMgmtVCEnvEntry  1 }

adnCongMgmtVCLineDataTrace OBJECT-TYPE
    SYNTAX  OCTET STRING
    ACCESS  read-only
    STATUS  mandatory
    DESCRIPTION
           "This is an internal BINARY message trace table maintained by
         congestion management for this VC. This trace will contain
	 relevant info for each subframe comming from the
	 Line and going to the bus.
	It is placed here for maintenance purposes only."
    ::= { adnCongMgmtVCEnvEntry  2 }

adnCongMgmtVCBusDataTrace OBJECT-TYPE
    SYNTAX  OCTET STRING
    ACCESS  read-only
    STATUS  mandatory
    DESCRIPTION
           "This is an internal BINARY message trace table maintained by
         congestion management for this VC. This trace will contain
         relevant info for each subframe comming from the Bus and
	 going to the Line.
         It is placed here for maintenance purposes only."
    ::= { adnCongMgmtVCEnvEntry  3 }

adnCongMgmtVCTraceEnable OBJECT-TYPE
    SYNTAX  AdnEnableDisabled
    ACCESS  read-write
    STATUS  mandatory
    DESCRIPTION
           " value indicating if trace per VC is enabled"
    ::= { adnCongMgmtVCEnvEntry  4 }

adnCongMgmtVCStateMachineTrace OBJECT-TYPE
    SYNTAX  OCTET STRING
    ACCESS  read-only
    STATUS  mandatory
    DESCRIPTION
           "This is an internal BINARY message trace table maintained by
         congestion management for this VC. This trace will contain
         the state and events of the SIR update state machine
	 and ISM congestion state machine. 
        It is placed here for maintenance purposes only."
    ::= { adnCongMgmtVCEnvEntry  5 }

adnCongMgmtLTTraceTable OBJECT-TYPE
    SYNTAX  SEQUENCE OF AdnCongMgmtLTTraceEntry
    ACCESS  not-accessible
    STATUS  mandatory
    DESCRIPTION
           "The Frame Relay LT Trace table for Congestion
         Management."
    ::= { adnCongMgmtPrivateMIB  4 }

adnCongMgmtLTTraceEntry OBJECT-TYPE
    SYNTAX  AdnCongMgmtLTTraceEntry
    ACCESS  not-accessible
    STATUS  mandatory
    DESCRIPTION
           "An entry in the Franp cm trace table"
    INDEX   { adnCouplerIndex,  adnCongMgmtTraceIndex }
    ::= { adnCongMgmtLTTraceTable  1 }

AdnCongMgmtLTTraceEntry ::=
    SEQUENCE {
        adnCongMgmtLTCQtrace
            OCTET STRING,

        adnCongMgmtTraceIndex
            INTEGER (-2147483648..2147483647)
    }

adnCongMgmtLTCQtrace OBJECT-TYPE
    SYNTAX  OCTET STRING
    ACCESS  read-only
    STATUS  mandatory
    DESCRIPTION
           "This is the trace area for the calendar queue related
         variables. It is placed here for maintenance purpose
         only"
    ::= { adnCongMgmtLTTraceEntry  1 }

adnCongMgmtTraceIndex OBJECT-TYPE
    SYNTAX  INTEGER (-2147483648..2147483647)
    ACCESS  read-write
    STATUS  mandatory
    DESCRIPTION
           "Index indicating the current index of Calendar Queue 
         trace. This is used to display more than 255 bytes of
         trace by means of repeated getnext message from the INMP"
    ::= { adnCongMgmtLTTraceEntry  2 }

adnLapPrivateMIB OBJECT IDENTIFIER ::= { adnEnvHss  7 }

adnLapPrivateTable OBJECT-TYPE
    SYNTAX  SEQUENCE OF AdnLapPrivateEntry
    ACCESS  not-accessible
    STATUS  mandatory
    DESCRIPTION
           "This is the LAP private table.  It will exist once per LAP instance
		on each LT."
    ::= { adnLapPrivateMIB  1 }

adnLapPrivateEntry OBJECT-TYPE
    SYNTAX  AdnLapPrivateEntry
    ACCESS  not-accessible
    STATUS  mandatory
    DESCRIPTION
           "One instance of the adnLapPrivateTable.  There will be one instance
		for each LAP on each LT."
    INDEX   { ifIndex,  adnLapDLCIIndex }
    ::= { adnLapPrivateTable  1 }

AdnLapPrivateEntry ::=
    SEQUENCE {
        adnLapPrivateTraceL1flag
            INTEGER,

        adnLapPrivateTraceL1buffer
            OCTET STRING,

        adnLapPrivateTraceL3flag
            INTEGER,

        adnLapPrivateTraceL3buffer
            OCTET STRING,

        adnLapPrivateTraceNMGSflag
            INTEGER,

        adnLapPrivateTraceNMGSbuffer
            OCTET STRING,

        adnLapFlowRASInfoflag
            INTEGER,

        adnLapFlowRASInfo
            OCTET STRING
    }

adnLapPrivateTraceL1flag OBJECT-TYPE
    SYNTAX  INTEGER {
    disabled(1),
    enabled(2)
}
    ACCESS  read-write
    STATUS  mandatory
    DESCRIPTION
           "This identifies the enable state of the 
		tracing option at the Level 1 interface."
    DEFVAL  { disabled }
    ::= { adnLapPrivateEntry  1 }

adnLapPrivateTraceL1buffer OBJECT-TYPE
    SYNTAX  OCTET STRING
    ACCESS  read-only
    STATUS  mandatory
    DESCRIPTION
           "This is internal Level 1 message trace BINARY buffer"
    ::= { adnLapPrivateEntry  2 }

adnLapPrivateTraceL3flag OBJECT-TYPE
    SYNTAX  INTEGER {
    disabled(1),
    enabled(2)
}
    ACCESS  read-write
    STATUS  mandatory
    DESCRIPTION
           "This identifies the enable state of the 
		tracing option at the Level 3 interface."
    DEFVAL  { disabled }
    ::= { adnLapPrivateEntry  3 }

adnLapPrivateTraceL3buffer OBJECT-TYPE
    SYNTAX  OCTET STRING
    ACCESS  read-only
    STATUS  mandatory
    DESCRIPTION
           "This is internal Level 3 message trace BINARY buffer"
    ::= { adnLapPrivateEntry  4 }

adnLapPrivateTraceNMGSflag OBJECT-TYPE
    SYNTAX  INTEGER {
    disabled(1),
    enabled(2)
}
    ACCESS  read-write
    STATUS  mandatory
    DESCRIPTION
           "This identifies the enable state of the 
		tracing option at the NMGS interface."
    DEFVAL  { disabled }
    ::= { adnLapPrivateEntry  5 }

adnLapPrivateTraceNMGSbuffer OBJECT-TYPE
    SYNTAX  OCTET STRING
    ACCESS  read-only
    STATUS  mandatory
    DESCRIPTION
           "This is internal NMGSmessage trace BINARY buffer"
    ::= { adnLapPrivateEntry  6 }

adnLapFlowRASInfoflag OBJECT-TYPE
    SYNTAX  INTEGER {
    disabled(1),
    enabled(2)
}
    ACCESS  read-write
    STATUS  mandatory
    DESCRIPTION
           "This identifies the enable state of the 
		tracing option for RASinfo."
    DEFVAL  { disabled }
    ::= { adnLapPrivateEntry  7 }

adnLapFlowRASInfo OBJECT-TYPE
    SYNTAX  OCTET STRING
    ACCESS  read-only
    STATUS  mandatory
    DESCRIPTION
           "The statistics, trace information and current states
		debug dump fields to be used for remote debugging 
		information.
		RAS = reliability, accessibility, serviceability"
    ::= { adnLapPrivateEntry  8 }

adnSsupEnvMIB OBJECT IDENTIFIER ::= { adnEnvHss  8 }

adnSsupCUDbgPCBTable OBJECT-TYPE
    SYNTAX  SEQUENCE OF AdnSsupCUDbgPCBEntry
    ACCESS  not-accessible
    STATUS  mandatory
    DESCRIPTION
           "
			SSUPCU maintained SM processor control blocks.
			There is one such block for every secondary
			module (SM) processor that has been created
			(configured).  The SSUPCU will keep current
			status information about the remote processor
			(among many other things) in such a block.
			"
    ::= { adnSsupEnvMIB  1 }

adnSsupCUDbgPCBEntry OBJECT-TYPE
    SYNTAX  AdnSsupCUDbgPCBEntry
    ACCESS  not-accessible
    STATUS  mandatory
    DESCRIPTION
           "
			This is a description of a single entry in the
			SSUPCU Processor control block table.  For
			debugging reason, a hex-dump is considered
			sufficient for now.  Structures defined in
			C-header files will be used to determine the
			values of the appropriate fields.
			
			The table exists only on the CU, and therefore
			uses the CENTRALIZED indexing for SFAS/MSUP
			routing purposes.  The additional index will be
			encoded to 'adnProcessor' type definition allow
			SSUPCU code to determine which instance is
			desired by the user.
			"
    INDEX   { adnEquipIndex }
    ::= { adnSsupCUDbgPCBTable  1 }

AdnSsupCUDbgPCBEntry ::=
    SEQUENCE {
        adnSsupCUDbgPCBData
            OCTET STRING
    }

adnSsupCUDbgPCBData OBJECT-TYPE
    SYNTAX  OCTET STRING
    ACCESS  read-only
    STATUS  mandatory
    DESCRIPTION
           "
			This is the hex-dump that represents the SSUPCU
			processor control block entry.  Each such entry
			contains information about a SM processor on a
			coupler card that is configured.
			"
    ::= { adnSsupCUDbgPCBEntry  4 }

adnSsupOMDbgPCBTable OBJECT-TYPE
    SYNTAX  SEQUENCE OF AdnSsupOMDbgPCBEntry
    ACCESS  not-accessible
    STATUS  mandatory
    DESCRIPTION
           "
			SSUPOM maintained SM processor control blocks.
			There is one such block per OM processor.  Only
			a single instance is maintained in each OM's
			memory, that pertaining to itself.  This block
			contains information needed for the functioning
			of the processor, as well as information
			relating to the LT processors on the card.
			"
    ::= { adnSsupEnvMIB  2 }

adnSsupOMDbgPCBEntry OBJECT-TYPE
    SYNTAX  AdnSsupOMDbgPCBEntry
    ACCESS  not-accessible
    STATUS  mandatory
    DESCRIPTION
           "
			This is a description of a single entry in the
			SSUPOM Processor control block table.  For
			debugging reason, a hex-dump is considered
			sufficient for now.  Structures defined in
			C-header files will be used to determine the
			values of the appropriate fields.

			The 'adnCouplerIndex' is used for SFAS/MSUP
			routing purposes.  This unfortunately only
			contains information of the chassis, slot and
			_line_ number (not processor).  The user has to
			be aware of what line would map to the OM
			processor.

			Currently the line should be encoded as 512.
			Note that this information is likely to change.
			"
    INDEX   { adnCouplerIndex }
    ::= { adnSsupOMDbgPCBTable  1 }

AdnSsupOMDbgPCBEntry ::=
    SEQUENCE {
        adnCouplerIndex
            AdnCouplerIndex,

        adnSsupOMDbgPCBData
            OCTET STRING
    }

adnCouplerIndex OBJECT-TYPE
    SYNTAX  AdnCouplerIndex
    ACCESS  read-only
    STATUS  mandatory
    DESCRIPTION
           "
			The defintion of the 'adnCouplerIndex' object.
			It is used for routing the SNMP command to the
			appropriate processor by SFAS/MSUP sub-systems.
			"
    ::= { adnSsupOMDbgPCBEntry  1 }

adnSsupOMDbgPCBData OBJECT-TYPE
    SYNTAX  OCTET STRING
    ACCESS  read-only
    STATUS  mandatory
    DESCRIPTION
           "
			This is the hex-dump that represents the SSUPOM
			processor control block entry.  Each such entry
			contains information about the OM processor in
			which memory the block resides.
			"
    ::= { adnSsupOMDbgPCBEntry  2 }

adnSsupLTDbgPCBTable OBJECT-TYPE
    SYNTAX  SEQUENCE OF AdnSsupLTDbgPCBEntry
    ACCESS  not-accessible
    STATUS  mandatory
    DESCRIPTION
           "
			SSUPLT maintained SM processor control blocks.
			There is one such block per LT processor.  Only
			one block exists in each LT processor's memory,
			and it contains information needed by that
			processor only.
			"
    ::= { adnSsupEnvMIB  3 }

adnSsupLTDbgPCBEntry OBJECT-TYPE
    SYNTAX  AdnSsupLTDbgPCBEntry
    ACCESS  not-accessible
    STATUS  mandatory
    DESCRIPTION
           "
			This is a description of a single entry in the
			SSUPLT Processor control block table.  For
			debugging reason, a hex-dump is considered
			sufficient for now.  Structures defined in
			C-header files will be used to determine the
			values of the appropriate fields.

			The 'adnCouplerIndex' is used for SFAS/MSUP
			routing purposes.  This unfortunately only
			contains information of the chassis, slot and
			_line_ number (not processor).  The user has to
			be aware of what line would map to the LT
			processor.

			Currently the line should be encoded as 255 for
			the LLT, and 383 for the ULT processor.  Note
			that this information is likely to change.
			"
    INDEX   { adnCouplerIndex }
    ::= { adnSsupLTDbgPCBTable  1 }

AdnSsupLTDbgPCBEntry ::=
    SEQUENCE {
        adnSsupLTDbgPCBData
            OCTET STRING
    }

adnSsupLTDbgPCBData OBJECT-TYPE
    SYNTAX  OCTET STRING
    ACCESS  read-only
    STATUS  mandatory
    DESCRIPTION
           "
			This is the hex-dump that represents the SSUPLT
			processor control block entry.  Each such entry
			contains information about the LT processor in
			which memory the block resides.
			"
    ::= { adnSsupLTDbgPCBEntry  1 }

adnAAFDEnvMIB OBJECT IDENTIFIER ::= { adnEnvHss  10 }

adnAAFDMaintTable OBJECT-TYPE
    SYNTAX  SEQUENCE OF AdnAAFDMaintEntry
    ACCESS  not-accessible
    STATUS  mandatory
    DESCRIPTION
           "This table contains internal AAFD SWBB data
          structure, one entry per AAFD SWBB instance."
    ::= { adnAAFDEnvMIB  1 }

adnAAFDMaintEntry OBJECT-TYPE
    SYNTAX  AdnAAFDMaintEntry
    ACCESS  not-accessible
    STATUS  mandatory
    DESCRIPTION
           "An entry in the adnAAFDMaintTable. There will be
         one entry for each AAFD SWBB instance."
    INDEX   { adnCouplerIndex }
    ::= { adnAAFDMaintTable  1 }

AdnAAFDMaintEntry ::=
    SEQUENCE {
        adnAAFDContxt1
            OCTET STRING,

        adnAAFDContxt2
            OCTET STRING,

        adnAAFDContxt3
            OCTET STRING,

        adnAAFDContxt4
            OCTET STRING,

        adnAAFDContxt5
            OCTET STRING,

        adnAAFDContxt6
            OCTET STRING,

        adnAAFDContxt7
            OCTET STRING
    }

adnAAFDContxt1 OBJECT-TYPE
    SYNTAX  OCTET STRING
    ACCESS  read-only
    STATUS  mandatory
    DESCRIPTION
           "This is the first part of internal AAFD data
          structure containing internal error counters and
          structures."
    ::= { adnAAFDMaintEntry  1 }

adnAAFDContxt2 OBJECT-TYPE
    SYNTAX  OCTET STRING
    ACCESS  read-only
    STATUS  mandatory
    DESCRIPTION
           "This is the second part internal AAFD data
          structure containing internal error counters and
          structures."
    ::= { adnAAFDMaintEntry  2 }

adnAAFDContxt3 OBJECT-TYPE
    SYNTAX  OCTET STRING
    ACCESS  read-only
    STATUS  mandatory
    DESCRIPTION
           "This is the third part internal AAFD data
          structure containing internal error counters and
          structures."
    ::= { adnAAFDMaintEntry  3 }

adnAAFDContxt4 OBJECT-TYPE
    SYNTAX  OCTET STRING
    ACCESS  read-only
    STATUS  mandatory
    DESCRIPTION
           "This is the fourth part of internal AAFD data
          structure containing internal error counters and
          structures."
    ::= { adnAAFDMaintEntry  4 }

adnAAFDContxt5 OBJECT-TYPE
    SYNTAX  OCTET STRING
    ACCESS  read-only
    STATUS  mandatory
    DESCRIPTION
           "This is the fifth part internal AAFD data
          structure containing internal error counters and
          structures."
    ::= { adnAAFDMaintEntry  5 }

adnAAFDContxt6 OBJECT-TYPE
    SYNTAX  OCTET STRING
    ACCESS  read-only
    STATUS  mandatory
    DESCRIPTION
           "This is the sixth part internal AAFD data
          structure containing internal error counters and
          structures."
    ::= { adnAAFDMaintEntry  6 }

adnAAFDContxt7 OBJECT-TYPE
    SYNTAX  OCTET STRING
    ACCESS  read-only
    STATUS  mandatory
    DESCRIPTION
           "This is the seventh part internal AAFD data
          structure containing internal error counters and
          structures."
    ::= { adnAAFDMaintEntry  7 }

adnAAFDVCCMaintTable OBJECT-TYPE
    SYNTAX  SEQUENCE OF AdnAAFDVCCMaintEntry
    ACCESS  not-accessible
    STATUS  mandatory
    DESCRIPTION
           "This table contains internal AAFD SWBB data
         structure, one entry per Frame Relay logical line."
    ::= { adnAAFDEnvMIB  2 }

adnAAFDVCCMaintEntry OBJECT-TYPE
    SYNTAX  AdnAAFDVCCMaintEntry
    ACCESS  not-accessible
    STATUS  mandatory
    DESCRIPTION
           "An entry in the adnAAFDVCCMaintTable. There will
         be one entry for each Frame Relay logical line."
    INDEX   { ifIndex }
    ::= { adnAAFDVCCMaintTable  1 }

AdnAAFDVCCMaintEntry ::=
    SEQUENCE {
        adnAAFDVCCContext1
            OCTET STRING,

        adnAAFDVCCContext2
            OCTET STRING,

        adnAAFDVCCContext3
            OCTET STRING
    }

adnAAFDVCCContext1 OBJECT-TYPE
    SYNTAX  OCTET STRING
    ACCESS  read-only
    STATUS  mandatory
    DESCRIPTION
           "This is the first part of internal data structure containing
          internal errors counters and structures concerning
          this Frame Relay logical line."
    ::= { adnAAFDVCCMaintEntry  1 }

adnAAFDVCCContext2 OBJECT-TYPE
    SYNTAX  OCTET STRING
    ACCESS  read-only
    STATUS  mandatory
    DESCRIPTION
           "This is the second part of internal data structure containing
          internal errors counters and structures concerning
          this Frame Relay logical line."
    ::= { adnAAFDVCCMaintEntry  2 }

adnAAFDVCCContext3 OBJECT-TYPE
    SYNTAX  OCTET STRING
    ACCESS  read-only
    STATUS  mandatory
    DESCRIPTION
           "This is the third part of internal data structure containing
          internal errors counters and structures concerning
          this Frame Relay logical line."
    ::= { adnAAFDVCCMaintEntry  3 }

adnPssMIB OBJECT IDENTIFIER ::= { adnEnvHss  11 }

adnPssBWTable OBJECT-TYPE
    SYNTAX  SEQUENCE OF AdnPssBandWEntry
    ACCESS  not-accessible
    STATUS  mandatory
    DESCRIPTION
           "Entry AdnPssBWEntry "
    ::= { adnPssMIB  1 }

adnPssBWEntry OBJECT-TYPE
    SYNTAX  AdnPssBandWEntry
    ACCESS  not-accessible
    STATUS  mandatory
    DESCRIPTION
           "Each entry (row) in the adnPSSBWTable.  There will be one
         entry per ifindex"
    INDEX   { adnCouplerIndex,  adnpssifindex }
    ::= { adnPssBWTable  1 }

AdnPssBandWEntry ::=
    SEQUENCE {
        adnPssAvailBW
            OCTET STRING,

        adnpssifindex
            INTEGER (-2147483648..2147483647)
    }

adnPssAvailBW OBJECT-TYPE
    SYNTAX  OCTET STRING	-- UNITS Available Band Width

    ACCESS  read-only
    STATUS  mandatory
    DESCRIPTION
           "This is the internal binary available bandwidth information 
	 received by Path Select for a particular ifindex."
    ::= { adnPssBWEntry  1 }

adnpssifindex OBJECT-TYPE
    SYNTAX  INTEGER (-2147483648..2147483647)	-- UNITS If Index

    ACCESS  read-only
    STATUS  mandatory
    DESCRIPTION
           "This is adn pss ifindex."
    ::= { adnPssBWEntry  2 }

adnPssTracehdrTable OBJECT-TYPE
    SYNTAX  SEQUENCE OF AdnPssTraceValEntry
    ACCESS  not-accessible
    STATUS  mandatory
    DESCRIPTION
           "This table contains various trace areas used by Path Select
         for maintenance/diagnostic purpose only."
    ::= { adnPssMIB  2 }

adnPssTracehdrEntry OBJECT-TYPE
    SYNTAX  AdnPssTraceHdrEntry
    ACCESS  not-accessible
    STATUS  mandatory
    DESCRIPTION
           "Each entry (row) in the adnPssTraceTable."
    INDEX   { adnCouplerIndex }
    ::= { adnPssTracehdrTable  1 }

AdnPssTraceHdrEntry ::=
    SEQUENCE {
        adnPssPrintFlag
            INTEGER,

        adnPssFromFrtBuf
            OCTET STRING,

        adnPssToFrtBuf
            OCTET STRING
    }

adnPssPrintFlag OBJECT-TYPE
    SYNTAX  INTEGER {
    noprint(0),
    errorprint(1),
    debugprint(2),
    detailprint(3)
}	-- UNITS Printf control 

    ACCESS  read-write
    STATUS  mandatory
    DESCRIPTION
           " This value is used to set Pss_print_flag to determine
          which printf's are allowed. "
    ::= { adnPssTracehdrEntry  1 }

adnPssFromFrtBuf OBJECT-TYPE
    SYNTAX  OCTET STRING
    ACCESS  read-only
    STATUS  mandatory
    DESCRIPTION
           "This is a binary value"
    ::= { adnPssTracehdrEntry  2 }

adnPssToFrtBuf OBJECT-TYPE
    SYNTAX  OCTET STRING
    ACCESS  read-only
    STATUS  mandatory
    DESCRIPTION
           "The binary buffer value"
    ::= { adnPssTracehdrEntry  3 }

adnPssTraceTable OBJECT-TYPE
    SYNTAX  SEQUENCE OF AdnPssTraceValEntry
    ACCESS  not-accessible
    STATUS  mandatory
    DESCRIPTION
           "This table contains various trace areas used by Path Select
	 for maintenance/diagnostic purpose only."
    ::= { adnPssMIB  3 }

adnPssTraceEntry OBJECT-TYPE
    SYNTAX  AdnPssTraceValEntry
    ACCESS  not-accessible
    STATUS  mandatory
    DESCRIPTION
           "Each entry (row) in the adnPssTraceTable."
    INDEX   { adnCouplerIndex,  adnPssTraceIndex }
    ::= { adnPssTraceTable  1 }

AdnPssTraceValEntry ::=
    SEQUENCE {
        adnPssTraceIndex
            INTEGER,

        adnPssTraceValue
            OCTET STRING
    }

adnPssTraceIndex OBJECT-TYPE
    SYNTAX  INTEGER	-- UNITS Trace index number 

    ACCESS  not-accessible
    STATUS  mandatory
    DESCRIPTION
           "Trace Index Number"
    ::= { adnPssTraceEntry  1 }

adnPssTraceValue OBJECT-TYPE
    SYNTAX  OCTET STRING
    ACCESS  read-only
    STATUS  mandatory
    DESCRIPTION
           "This is the binary. All messages received 
	 from the Franp_si component are stored here"
    ::= { adnPssTraceEntry  2 }

adnRtsagtMIB OBJECT IDENTIFIER ::= { adnEnvHss  12 }

adnRtsagtPrintFlagTable OBJECT-TYPE
    SYNTAX  SEQUENCE OF AdnRtsagtPrintFlagHdrEntry
    ACCESS  not-accessible
    STATUS  mandatory
    DESCRIPTION
           "This table is to turn on and off the print capability Routes 
         Agent for maintenance/diagnostic purpose only."
    ::= { adnRtsagtMIB  1 }

adnRtsagtPrintFlagHdrEntry OBJECT-TYPE
    SYNTAX  AdnRtsagtPrintFlagHdrEntry
    ACCESS  not-accessible
    STATUS  mandatory
    DESCRIPTION
           "Each entry (row) in the adnRtsagtPrintFlagTable."
    INDEX   { adnCouplerIndex }
    ::= { adnRtsagtPrintFlagTable  1 }

AdnRtsagtPrintFlagHdrEntry ::=
    SEQUENCE {
        adnRtsagtPrintFlag
            INTEGER
    }

adnRtsagtPrintFlag OBJECT-TYPE
    SYNTAX  INTEGER {
    noprint(1),
    errorprint(2),
    debugprint(3),
    detailprint(4)
}
    ACCESS  read-write
    STATUS  mandatory
    DESCRIPTION
           " This value is used to set Rtsagt_print_flag to determine
          which printf's are allowed. "
    ::= { adnRtsagtPrintFlagHdrEntry  1 }

adnRtsagtTraceTable OBJECT-TYPE
    SYNTAX  SEQUENCE OF AdnRtsagtTraceEntry
    ACCESS  not-accessible
    STATUS  mandatory
    DESCRIPTION
           "This table contains various trace areas used by Routes Agent
         for maintenance/diagnostic purpose only."
    ::= { adnRtsagtMIB  2 }

adnRtsagtTraceEntry OBJECT-TYPE
    SYNTAX  AdnRtsagtTraceEntry
    ACCESS  not-accessible
    STATUS  mandatory
    DESCRIPTION
           "Each entry (row) in the adnRtsagtTraceTable."
    INDEX   { adnCouplerIndex,  adnRtsagtTraceIndex }
    ::= { adnRtsagtTraceTable  1 }

AdnRtsagtTraceEntry ::=
    SEQUENCE {
        adnRtsagtTraceIndex
            INTEGER,

        adnRtsagtTraceValue
            OCTET STRING
    }

adnRtsagtTraceIndex OBJECT-TYPE
    SYNTAX  INTEGER
    ACCESS  not-accessible
    STATUS  mandatory
    DESCRIPTION
           "Trace Index Number"
    ::= { adnRtsagtTraceEntry  1 }

adnRtsagtTraceValue OBJECT-TYPE
    SYNTAX  OCTET STRING
    ACCESS  read-only
    STATUS  mandatory
    DESCRIPTION
           "This is the binary."
    ::= { adnRtsagtTraceEntry  2 }

adnRtsagtLinkCtrlBlkTable OBJECT-TYPE
    SYNTAX  SEQUENCE OF AdnRtsagtLinkCtrlEntry
    ACCESS  not-accessible
    STATUS  mandatory
    DESCRIPTION
           "This table contains Link Control Block values "
    ::= { adnRtsagtMIB  3 }

adnRtsagtLinkCtrlBlkEntry OBJECT-TYPE
    SYNTAX  AdnRtsagtLinkCtrlEntry
    ACCESS  not-accessible
    STATUS  mandatory
    DESCRIPTION
           " Entry in the adnRtsagtLinkCtrlBlkTable. "
    INDEX   { adnCouplerIndex,  adnRtsagtIfIndex }
    ::= { adnRtsagtLinkCtrlBlkTable  1 }

AdnRtsagtLinkCtrlEntry ::=
    SEQUENCE {
        adnRtsagtIfIndex
            INTEGER (-2147483648..2147483647),

        adnRtsagtLpx
            INTEGER (-2147483648..2147483647),

        adnRtsagtUserNetFlag
            INTEGER,

        adnRtsagtHssTpx
            INTEGER,

        adnRtsagtSigIfState
            INTEGER,

        adnRtsagtL2IfState
            INTEGER,

        adnRtsagtMhIfState
            INTEGER,

        adnRtsagtL3IfState
            INTEGER,

        adnRtsagtLhMainState
            INTEGER,

        adnRtsagtSiCcb
            INTEGER (-2147483648..2147483647),

        adnRtsagtLtLpx
            INTEGER (-2147483648..2147483647),

        adnRtsagtMemLpx
            INTEGER (-2147483648..2147483647),

        adnRtsagtAtmSiIfap
            INTEGER (-2147483648..2147483647),

        adnRtsagtAtmSiSuid
            INTEGER (-2147483648..2147483647),

        adnRtsagtL3MaxPktSize
            INTEGER (-2147483648..2147483647),

        adnRtsagtPeerVersion
            INTEGER (-2147483648..2147483647),

        adnRtsagtHeartBeatTime
            INTEGER (-2147483648..2147483647),

        adnRtsagtLinkDeadTime
            INTEGER (-2147483648..2147483647),

        adnRtsagtSigIfInfo
            OCTET STRING,

        adnRtsagtL2IfInfo
            OCTET STRING,

        adnRtsagtL3IfInfo
            OCTET STRING,

        adnRtsagtMhIfInfo
            OCTET STRING,

        adnRtsagtLhMainInfo
            OCTET STRING,

        adnRtsagtLhTimerInfo
            OCTET STRING,

        adnRtsagtNextLcb
            INTEGER (-2147483648..2147483647),

        adnRtsagtPrevLcb
            INTEGER (-2147483648..2147483647),

        adnRtsagtTimerDurations
            INTEGER,

        adnRtsagtLayer2IdCcb
            INTEGER (-2147483648..2147483647),

        adnRtsagtLayer2RefCcb
            INTEGER (-2147483648..2147483647),

        adnRtsagtChannelType
            INTEGER,

        adnRtsagtLineMetric
            OCTET STRING,

        adnRtsagtLinkDeadFlag
            INTEGER
    }

adnRtsagtIfIndex OBJECT-TYPE
    SYNTAX  INTEGER (-2147483648..2147483647)
    ACCESS  read-only
    STATUS  mandatory
    DESCRIPTION
           " Routes agent link control block ifindex. "
    ::= { adnRtsagtLinkCtrlBlkEntry  1 }

adnRtsagtLpx OBJECT-TYPE
    SYNTAX  INTEGER (-2147483648..2147483647)	-- UNITS Routes agent lpx self 

    ACCESS  read-only
    STATUS  mandatory
    DESCRIPTION
           " Routes agent lpx self "
    ::= { adnRtsagtLinkCtrlBlkEntry  2 }

adnRtsagtUserNetFlag OBJECT-TYPE
    SYNTAX  INTEGER {
    user(1),
    network(2),
    other(3)
}
    ACCESS  read-only
    STATUS  mandatory
    DESCRIPTION
           " Routes Agent 0:user, 1 : network. "
    ::= { adnRtsagtLinkCtrlBlkEntry  3 }

adnRtsagtHssTpx OBJECT-TYPE
    SYNTAX  INTEGER {
    tpx(1),
    hss(2),
    other(3)
}
    ACCESS  read-only
    STATUS  mandatory
    DESCRIPTION
           " Routes agent hss : 1, tpx : 0, other : 2."
    ::= { adnRtsagtLinkCtrlBlkEntry  4 }

adnRtsagtSigIfState OBJECT-TYPE
    SYNTAX  INTEGER {
    rcvdAddSig(1),
    sentChnlRdy(2),
    sigEnabChnl(3),
    sigDisblChnl(4),
    sigBlkdChl(5)
}
    ACCESS  read-only
    STATUS  mandatory
    DESCRIPTION
           " Routes agent Signal channel status received, sent, signal 
	  enabled, sig disabled, sig blocked, no. of sig states. "
    ::= { adnRtsagtLinkCtrlBlkEntry  5 }

adnRtsagtL2IfState OBJECT-TYPE
    SYNTAX  INTEGER {
    l2idlest(1),
    l2waitestb(2),
    l2linkestb(3),
    l2awaitrelst(4),
    l2flowctrlst(5)
}
    ACCESS  read-only
    STATUS  mandatory
    DESCRIPTION
           " Routes agent states for L2 Interface Idle or link released,
	  Waiting for establish, Link Established, Awaiting release conf,
	  L2 flow controlled us, Number of L2 states. "
    ::= { adnRtsagtLinkCtrlBlkEntry  6 }

adnRtsagtMhIfState OBJECT-TYPE
    SYNTAX  INTEGER {
    mhreqsent(1),
    mhlinkstatdown(2),
    mhlinkupreq(3),
    mhlinkup(4),
    mhXoffsent(5),
    mhlclXoffsent(6)
}
    ACCESS  read-only
    STATUS  mandatory
    DESCRIPTION
           " Routes agent MH States, Add request sent to MH, MH link status
	  down, Sent link up request, Link with MH is up, MH has sent
	  XOFF, Local XOFF sent to MH, Number of MH states."
    ::= { adnRtsagtLinkCtrlBlkEntry  7 }

adnRtsagtL3IfState OBJECT-TYPE
    SYNTAX  INTEGER {
    l3notestb(1),
    l3sentestbreq(2),
    l3usrXoffsent(3),
    l3rmtXoffsent(4),
    l3usrblksent(5),
    l3rmtblksent(6),
    l3okxfer(7)
}
    ACCESS  read-only
    STATUS  mandatory
    DESCRIPTION
           " Routes agent state of l3 interface, L3 not yet established,
	  Sent Establish Req, We sent Xoff to Remote, Remote sent Xoff
	  to us, We sent block to Remote, Remote sent block to us,
	  Link up in data xfer, Number of L3 states."
    ::= { adnRtsagtLinkCtrlBlkEntry  8 }

adnRtsagtLhMainState OBJECT-TYPE
    SYNTAX  INTEGER {
    lhproceaddreq(1),
    lhwaitenable(2),
    lhmdlconf(3),
    lhtpxsetup(4),
    lhtpxrelease(5),
    lhl2estb(6),
    lhl3estbl(7),
    lhlinkupfrmmh(8),
    lhwaitreleases(9),
    lhlinkoparational(10),
    lhl3upmhdowm(11),
    lhiacsdown(12)
}
    ACCESS  read-only
    STATUS  mandatory
    DESCRIPTION
           " Routes agent state of Link Handler, Processing Add Request,
	  Waiting for enable, Waiting for MDL confirm, Waiting TPX
	  setup, Waiting TPX release, Waiting L2 establish, Waiting
	  L3 establish, Wait for link up from MH, Wait for releases
	  Link operational, L3 up, MH down on purpose, IACS is down,
	  Number of LH states. "
    ::= { adnRtsagtLinkCtrlBlkEntry  9 }

adnRtsagtSiCcb OBJECT-TYPE
    SYNTAX  INTEGER (-2147483648..2147483647)
    ACCESS  read-only
    STATUS  mandatory
    DESCRIPTION
           " Routes agent Pointer to control Block of signal. "
    ::= { adnRtsagtLinkCtrlBlkEntry  10 }

adnRtsagtLtLpx OBJECT-TYPE
    SYNTAX  INTEGER (-2147483648..2147483647)
    ACCESS  read-only
    STATUS  mandatory
    DESCRIPTION
           " Routes agent lpx of lt. "
    ::= { adnRtsagtLinkCtrlBlkEntry  11 }

adnRtsagtMemLpx OBJECT-TYPE
    SYNTAX  INTEGER (-2147483648..2147483647)	-- UNITS  lpx for lt data xfer memory 

    ACCESS  read-only
    STATUS  mandatory
    DESCRIPTION
           " Routes agent lpx for lt data transfer memory "
    ::= { adnRtsagtLinkCtrlBlkEntry  12 }

adnRtsagtAtmSiIfap OBJECT-TYPE
    SYNTAX  INTEGER (-2147483648..2147483647)	-- UNITS  Signalling IFAP 

    ACCESS  read-only
    STATUS  mandatory
    DESCRIPTION
           " Routes agent Signalling IFAP"
    ::= { adnRtsagtLinkCtrlBlkEntry  13 }

adnRtsagtAtmSiSuid OBJECT-TYPE
    SYNTAX  INTEGER (-2147483648..2147483647)	-- UNITS  Signalling SUID 

    ACCESS  read-only
    STATUS  mandatory
    DESCRIPTION
           " Routes agent SUID "
    ::= { adnRtsagtLinkCtrlBlkEntry  14 }

adnRtsagtL3MaxPktSize OBJECT-TYPE
    SYNTAX  INTEGER (-2147483648..2147483647)
    ACCESS  read-only
    STATUS  mandatory
    DESCRIPTION
           " Routes agent negotiated pkt size with peer "
    ::= { adnRtsagtLinkCtrlBlkEntry  15 }

adnRtsagtPeerVersion OBJECT-TYPE
    SYNTAX  INTEGER
    ACCESS  read-only
    STATUS  mandatory
    DESCRIPTION
           " Routes agent link handler version of peer "
    ::= { adnRtsagtLinkCtrlBlkEntry  16 }

adnRtsagtHeartBeatTime OBJECT-TYPE
    SYNTAX  INTEGER
    ACCESS  read-only
    STATUS  mandatory
    DESCRIPTION
           " Routes agent time period of sending heartbeat "
    ::= { adnRtsagtLinkCtrlBlkEntry  17 }

adnRtsagtLinkDeadTime OBJECT-TYPE
    SYNTAX  INTEGER
    ACCESS  read-only
    STATUS  mandatory
    DESCRIPTION
           " Routes agent if no heartbeat for this time "
    ::= { adnRtsagtLinkCtrlBlkEntry  18 }

adnRtsagtSigIfInfo OBJECT-TYPE
    SYNTAX  OCTET STRING
    ACCESS  read-only
    STATUS  mandatory
    DESCRIPTION
           " Routes agent information relevant to sig_if "
    ::= { adnRtsagtLinkCtrlBlkEntry  19 }

adnRtsagtL2IfInfo OBJECT-TYPE
    SYNTAX  OCTET STRING
    ACCESS  read-only
    STATUS  mandatory
    DESCRIPTION
           " Routes agent information relevant to l2_if "
    ::= { adnRtsagtLinkCtrlBlkEntry  20 }

adnRtsagtL3IfInfo OBJECT-TYPE
    SYNTAX  OCTET STRING
    ACCESS  read-only
    STATUS  mandatory
    DESCRIPTION
           " Routes agent information relevant to l3_if "
    ::= { adnRtsagtLinkCtrlBlkEntry  21 }

adnRtsagtMhIfInfo OBJECT-TYPE
    SYNTAX  OCTET STRING
    ACCESS  read-only
    STATUS  mandatory
    DESCRIPTION
           " Routes agent information relevant to mh_if "
    ::= { adnRtsagtLinkCtrlBlkEntry  22 }

adnRtsagtLhMainInfo OBJECT-TYPE
    SYNTAX  OCTET STRING
    ACCESS  read-only
    STATUS  mandatory
    DESCRIPTION
           " Routes agent information relevant to lh_main "
    ::= { adnRtsagtLinkCtrlBlkEntry  23 }

adnRtsagtLhTimerInfo OBJECT-TYPE
    SYNTAX  OCTET STRING
    ACCESS  read-only
    STATUS  mandatory
    DESCRIPTION
           " Routes agent timer info "
    ::= { adnRtsagtLinkCtrlBlkEntry  24 }

adnRtsagtNextLcb OBJECT-TYPE
    SYNTAX  INTEGER (-2147483648..2147483647)
    ACCESS  read-only
    STATUS  mandatory
    DESCRIPTION
           " Routes agent next LCB in the list "
    ::= { adnRtsagtLinkCtrlBlkEntry  25 }

adnRtsagtPrevLcb OBJECT-TYPE
    SYNTAX  INTEGER (-2147483648..2147483647)
    ACCESS  read-only
    STATUS  mandatory
    DESCRIPTION
           " Routes agent next LCB in the list "
    ::= { adnRtsagtLinkCtrlBlkEntry  26 }

adnRtsagtTimerDurations OBJECT-TYPE
    SYNTAX  OCTET STRING
    ACCESS  read-only
    STATUS  mandatory
    DESCRIPTION
           " Routes agent durations for various timers "
    ::= { adnRtsagtLinkCtrlBlkEntry  27 }

adnRtsagtLayer2IdCcb OBJECT-TYPE
    SYNTAX  INTEGER (-2147483648..2147483647)
    ACCESS  read-only
    STATUS  mandatory
    DESCRIPTION
           " Routes agent set by layer2_id of Add channel "
    ::= { adnRtsagtLinkCtrlBlkEntry  28 }

adnRtsagtLayer2RefCcb OBJECT-TYPE
    SYNTAX  INTEGER (-2147483648..2147483647)
    ACCESS  read-only
    STATUS  mandatory
    DESCRIPTION
           " Routes agent set by l2_ctx.l2_ref of mdl_assign_conf "
    ::= { adnRtsagtLinkCtrlBlkEntry  29 }

adnRtsagtChannelType OBJECT-TYPE
    SYNTAX  INTEGER {
    atmtrunkvpc(1),
    atmtrunkvpandvc(2),
    atmtrunkvc(3),
    atminternodevp(4),
    framerelaytrunk(5)
}
    ACCESS  read-only
    STATUS  mandatory
    DESCRIPTION
           " Routes agent IfIndex type "
    ::= { adnRtsagtLinkCtrlBlkEntry  30 }

adnRtsagtLineMetric OBJECT-TYPE
    SYNTAX  OCTET STRING
    ACCESS  read-only
    STATUS  mandatory
    DESCRIPTION
           " Routes agent trace containing the delay and
          monetary cost metrics per line.  The first and
	  third octet strings are fields which contain a
	  number representing the type of cost (delay(3)
	  and monetary(4)).  The second and fourth octet
	  strings contain the actual cost value for the
	  cost type defined in the field before it. "
    ::= { adnRtsagtLinkCtrlBlkEntry  31 }

adnRtsagtLinkDeadFlag OBJECT-TYPE
    SYNTAX  INTEGER {
    timeroff(0),
    timeron(1)
}
    ACCESS  read-only
    STATUS  mandatory
    DESCRIPTION
           " Routes agent flag representing the status of the
          link dead timer on each line.  A one indicates 
	  the timer is on and a zero indicates the timer
          is off.  The link dead timer is a timer that 
	  starts when a line is set up and expires when
	  there are no messages sent across the line for
	  a period of time.  If the timer expires the link
	  is deemed dead and is reset.  However, the timer
	  is refreshed every time a message is sent across
	  the link. "
    ::= { adnRtsagtLinkCtrlBlkEntry  32 }

adnRtsagtLocalAddrTable OBJECT-TYPE
    SYNTAX  SEQUENCE OF AdnRtsagtLocalAddrEntry
    ACCESS  not-accessible
    STATUS  mandatory
    DESCRIPTION
           " Entry in the adnRtsagtLocalAddrTable "
    ::= { adnRtsagtMIB  4 }

adnRtsagtLocalAddrEntry OBJECT-TYPE
    SYNTAX  AdnRtsagtLocalAddrEntry
    ACCESS  not-accessible
    STATUS  mandatory
    DESCRIPTION
           " Entry in the adnRtsagtLocalAddrTable "
    INDEX   { adnCouplerIndex,  adnRtsagtLocalAddrIndex }
    ::= { adnRtsagtLocalAddrTable  1 }

AdnRtsagtLocalAddrEntry ::=
    SEQUENCE {
        adnRtsagtLocalAddrIndex
            INTEGER (-2147483648..2147483647),

        adnRtsagtLocalAddrBlkHdr
            OCTET STRING,

        adnRtsagtLocalAddrBlkCard
            OCTET STRING
    }

adnRtsagtLocalAddrIndex OBJECT-TYPE
    SYNTAX  INTEGER (-2147483648..2147483647)
    ACCESS  not-accessible
    STATUS  mandatory
    DESCRIPTION
           " Routes agent Address Index. "
    ::= { adnRtsagtLocalAddrEntry  1 }

adnRtsagtLocalAddrBlkHdr OBJECT-TYPE
    SYNTAX  OCTET STRING
    ACCESS  read-only
    STATUS  mandatory
    DESCRIPTION
           " Routes Agent address entry block "
    ::= { adnRtsagtLocalAddrEntry  2 }

adnRtsagtLocalAddrBlkCard OBJECT-TYPE
    SYNTAX  OCTET STRING
    ACCESS  read-only
    STATUS  mandatory
    DESCRIPTION
           " Routes Agent address entry block "
    ::= { adnRtsagtLocalAddrEntry  3 }

adnRtsagtTimerHdrTable OBJECT-TYPE
    SYNTAX  SEQUENCE OF AdnRtsagtTimerHdrEntry
    ACCESS  not-accessible
    STATUS  mandatory
    DESCRIPTION
           " Entry in the adnRtsagtTimerHdrTable "
    ::= { adnRtsagtMIB  5 }

adnRtsagtTimerHdrEntry OBJECT-TYPE
    SYNTAX  AdnRtsagtTimerHdrEntry
    ACCESS  not-accessible
    STATUS  mandatory
    DESCRIPTION
           " Entry in the adnRtsagtTimerHdrTable "
    INDEX   { adnCouplerIndex,  adnRtsagtTimerNext }
    ::= { adnRtsagtTimerHdrTable  1 }

AdnRtsagtTimerHdrEntry ::=
    SEQUENCE {
        adnRtsagtTimerIndex
            INTEGER (-2147483648..2147483647),

        adnRtsagtTimerDuration
            INTEGER (-2147483648..2147483647),

        adnRtsagtTimerPurpose
            INTEGER (-2147483648..2147483647),

        adnRtsagtTimerToBeDeleted
            INTEGER (-2147483648..2147483647),

        adnRtsagtTimerNext
            INTEGER (-2147483648..2147483647),

        adnRtsagtTimerPrevious
            INTEGER (-2147483648..2147483647)
    }

adnRtsagtTimerIndex OBJECT-TYPE
    SYNTAX  INTEGER (-2147483648..2147483647)
    ACCESS  read-only
    STATUS  mandatory
    DESCRIPTION
           " Routes agent Timer Index. "
    ::= { adnRtsagtTimerHdrEntry  1 }

adnRtsagtTimerDuration OBJECT-TYPE
    SYNTAX  INTEGER (-2147483648..2147483647)
    ACCESS  read-only
    STATUS  mandatory
    DESCRIPTION
           " Routes Agent Timer duration "
    ::= { adnRtsagtTimerHdrEntry  2 }

adnRtsagtTimerPurpose OBJECT-TYPE
    SYNTAX  INTEGER {
    addchnlrsp(1),
    mhaddrsp(2),
    mhlinkrsp(3),
    mdlassigncnf(4),
    l2estcnf(5),
    l2rlscnf(6),
    l3estcnf(7),
    l3estretry(8),
    heartbeat(9),
    deadtimer(10),
    numr20timerpurpose(11)
}
    ACCESS  read-only
    STATUS  mandatory
    DESCRIPTION
           " Routes Agent Timer Purpose "
    ::= { adnRtsagtTimerHdrEntry  3 }

adnRtsagtTimerToBeDeleted OBJECT-TYPE
    SYNTAX  INTEGER (-2147483648..2147483647)
    ACCESS  read-only
    STATUS  mandatory
    DESCRIPTION
           " Routes Agent Timer tobedeleted "
    ::= { adnRtsagtTimerHdrEntry  4 }

adnRtsagtTimerNext OBJECT-TYPE
    SYNTAX  INTEGER (-2147483648..2147483647)
    ACCESS  read-only
    STATUS  mandatory
    DESCRIPTION
           " Routes Agent Next timer pointer "
    ::= { adnRtsagtTimerHdrEntry  5 }

adnRtsagtTimerPrevious OBJECT-TYPE
    SYNTAX  INTEGER (-2147483648..2147483647)
    ACCESS  read-only
    STATUS  mandatory
    DESCRIPTION
           " Routes Agent Next timer pointer "
    ::= { adnRtsagtTimerHdrEntry  6 }

adnRtsmgrMIB OBJECT IDENTIFIER ::= { adnEnvHss  15 }

adnRtsmgrTraceTable OBJECT-TYPE
    SYNTAX  SEQUENCE OF AdnRtsmgrTraceEntry
    ACCESS  not-accessible
    STATUS  mandatory
    DESCRIPTION
           "This table is used to get Message handling entries values for Route Manager."
    ::= { adnRtsmgrMIB  1 }

adnRtsmgrTraceEntry OBJECT-TYPE
    SYNTAX  AdnRtsmgrTraceEntry
    ACCESS  not-accessible
    STATUS  mandatory
    DESCRIPTION
           "Each entry (row) in the adnRtsmgrTraceTable."
    INDEX   { adnCouplerIndex,  adnRtsmgrTraceIndex }
    ::= { adnRtsmgrTraceTable  1 }

AdnRtsmgrTraceEntry ::=
    SEQUENCE {
        adnRtsmgrTraceIndex
            INTEGER,

        adnRtsmgrTraceValue
            OCTET STRING
    }

adnRtsmgrTraceIndex OBJECT-TYPE
    SYNTAX  INTEGER
    ACCESS  not-accessible
    STATUS  mandatory
    DESCRIPTION
           "Trace Index Number. "
    ::= { adnRtsmgrTraceEntry  1 }

adnRtsmgrTraceValue OBJECT-TYPE
    SYNTAX  OCTET STRING
    ACCESS  read-only
    STATUS  mandatory
    DESCRIPTION
           "This string displays a string of 36 bytes combination of
         Route Manager trace entry constants, trace entry variables, 
         and time stamp."
    ::= { adnRtsmgrTraceEntry  2 }

adnCvsiHssEnvMIB OBJECT IDENTIFIER ::= { adnEnvHss  14 }

adnCvsiHssTable OBJECT-TYPE
    SYNTAX  SEQUENCE OF AdnCvsiHssEntry
    ACCESS  not-accessible
    STATUS  mandatory
    DESCRIPTION
           "This table is used by CVSI for the purpose of debugging."
    ::= { adnCvsiHssEnvMIB  1 }

adnCvsiHssEntry OBJECT-TYPE
    SYNTAX  AdnCvsiHssEntry
    ACCESS  not-accessible
    STATUS  mandatory
    DESCRIPTION
           "An entry in the CVSI HSS Table."
    INDEX   { adnCvsiHssIndex }
    ::= { adnCvsiHssTable  1 }

AdnCvsiHssEntry ::=
    SEQUENCE {
        adnCvsiHssIndex
            INTEGER (-2147483648..2147483647),

        adnCvsiHssTraceCntl
            INTEGER,

        adnCvsiHssTraceArea
            OCTET STRING,

        adnCvsiHssCounters
            OCTET STRING,

        adnCvsiHssGlobalVars
            OCTET STRING,

        adnCvsiHssPrintCntl
            INTEGER,

        adnCvsiHssVcActive
            INTEGER (-2147483648..2147483647)
    }

adnCvsiHssIndex OBJECT-TYPE
    SYNTAX  INTEGER (-2147483648..2147483647)
    ACCESS  read-only
    STATUS  mandatory
    DESCRIPTION
           "This entry represents the current instance or index of
         the table. It is provided in order to be able to dump 
         each instance of each object."
    ::= { adnCvsiHssEntry  1 }

adnCvsiHssTraceCntl OBJECT-TYPE
    SYNTAX  INTEGER
    ACCESS  read-write
    STATUS  mandatory
    DESCRIPTION
           "This object provides a mechanism for controlling 
         Cvsi's ability to enable/disable tracing of
	 various types of messages.
         The following are the possible values it can hold.
             0 - Trace disabled
             1 - Trace CVSI Library information messages
             2 - Trace CVSI Library Minor error messages
             4 - Trace CVSI Library Major error messages
             8 - Trace CVSI Library detailed messages
            16 - Trace CVSI relay messages
            32 - Trace CVSI Master messages
            64 - Trace ATM Signalling messages
           128 - Trace CLCS messages"
    DEFVAL  { 0 }
    ::= { adnCvsiHssEntry  2 }

adnCvsiHssTraceArea OBJECT-TYPE
    SYNTAX  OCTET STRING
    ACCESS  read-only
    STATUS  mandatory
    DESCRIPTION
           "This is the internal BINARY message trace entry 
         maintained by CVSI."
    ::= { adnCvsiHssEntry  3 }

adnCvsiHssCounters OBJECT-TYPE
    SYNTAX  OCTET STRING
    ACCESS  read-only
    STATUS  mandatory
    DESCRIPTION
           "This is the internal BINARY pointer to
         set of Counters maintained by CVSI."
    ::= { adnCvsiHssEntry  4 }

adnCvsiHssGlobalVars OBJECT-TYPE
    SYNTAX  OCTET STRING
    ACCESS  read-only
    STATUS  mandatory
    DESCRIPTION
           "CVSI global variables."
    ::= { adnCvsiHssEntry  5 }

adnCvsiHssPrintCntl OBJECT-TYPE
    SYNTAX  INTEGER
    ACCESS  read-write
    STATUS  mandatory
    DESCRIPTION
           "This object provides a mechanism for controlling
         Cvsi's ability to print on the CU console various
	 debugging information.
         The following are the possible values for this object.
	     0 - Print disabled
	     1 - Print CVSI Library information messages
	     2 - Print CVSI Library Minor error messages
	     4 - Print CVSI Library Major error messages
	     8 - Print CVSI Library detailed messages
	    16 - Print CVSI relay messages
	    32 - Print CVSI Master messages
	    64 - Print ATM Signalling messages
	   128 - Print CLCS messages"
    DEFVAL  { 0 }
    ::= { adnCvsiHssEntry  6 }

adnCvsiHssVcActive OBJECT-TYPE
    SYNTAX  INTEGER (-2147483648..2147483647)
    ACCESS  read-only
    STATUS  mandatory
    DESCRIPTION
           "Indicates the number of active TDP Virtual
	 Circuits in the current node."
    DEFVAL  { 0 }
    ::= { adnCvsiHssEntry  7 }

adnRdssMIB OBJECT IDENTIFIER ::= { adnEnvHss  100 }

AdnRdssOption ::=
    INTEGER {
        lpxlevel(1),
        interfacelevel(2),
        vclevel(3),
        other(255)
    }

AdnRdssCommandType ::=
    INTEGER {
        add(1),
        delete(2),
        update(3),
        internal(255)
    }

AdnRdssStatus ::=
    INTEGER {
        up(1),
        down(2)
    }

adnRdssRegistrationTable OBJECT-TYPE
    SYNTAX  SEQUENCE OF AdnRdssRegistrationEntry
    ACCESS  not-accessible
    STATUS  mandatory
    DESCRIPTION
           "This table contains an array of records to those subsystems 
         that have established IACS session with Routes Distribution."
    ::= { adnRdssMIB  1 }

adnRdssRegistrationEntry OBJECT-TYPE
    SYNTAX  AdnRdssRegistrationEntry
    ACCESS  not-accessible
    STATUS  mandatory
    DESCRIPTION
           " Entry in the adnRdssRegistrationTable. "
    INDEX   { adnRdssRegLpxIndex }
    ::= { adnRdssRegistrationTable  1 }

AdnRdssRegistrationEntry ::=
    SEQUENCE {
        adnRdssRegLpxIndex
            INTEGER (-2147483648..2147483647),

        adnRdssIcsRef
            INTEGER (-2147483648..2147483647),

        adnRdssSessionId
            INTEGER,

        adnRdssCongestionFlag
            INTEGER,

        adnRdssFatSequenceNum
            INTEGER (-2147483648..2147483647),

        adnRdssGatSequenceNum
            INTEGER (-2147483648..2147483647),

        adnRdssMatSequenceNum
            INTEGER (-2147483648..2147483647),

        adnRdssAckFlags
            INTEGER (-2147483648..2147483647),

        adnRdssNextHopLastSequenceNum
            INTEGER (-2147483648..2147483647),

        adnRdssLatLastSequenceNum
            INTEGER (-2147483648..2147483647),

        adnRdssMatLastSequenceNum
            INTEGER (-2147483648..2147483647),

        adnRdssTransmitMsgBufId
            INTEGER (-2147483648..2147483647),

        adnRdssGatTableTraverseStatus
            INTEGER (-2147483648..2147483647),

        adnRdssGatTableTraverseLpxKey
            INTEGER (-2147483648..2147483647),

        adnRdssTypeOfTableRequested
            INTEGER (-2147483648..2147483647),

        adnRdssGatTableTraverseStartKey
            INTEGER (-2147483648..2147483647),

        adnRdssGatTableTraverseEndKey
            INTEGER (-2147483648..2147483647),

        adnRdssGatMsgQueueStartPointer
            INTEGER (-2147483648..2147483647),

        adnRdssFatEntranceKey
            INTEGER (-2147483648..2147483647)
    }

adnRdssRegLpxIndex OBJECT-TYPE
    SYNTAX  INTEGER (-2147483648..2147483647)
    ACCESS  read-only
    STATUS  mandatory
    DESCRIPTION
           " The LPX of subsystem which is registered to Routes 
          Distribution. "
    ::= { adnRdssRegistrationEntry  1 }

adnRdssIcsRef OBJECT-TYPE
    SYNTAX  INTEGER (-2147483648..2147483647)
    ACCESS  read-only
    STATUS  mandatory
    DESCRIPTION
           " ICS Reference number "
    ::= { adnRdssRegistrationEntry  2 }

adnRdssSessionId OBJECT-TYPE
    SYNTAX  INTEGER {
    ipforwarding(1),
    isna(3),
    gdc(4),
    prta(5),
    sfas(8)
}
    ACCESS  read-only
    STATUS  mandatory
    DESCRIPTION
           " This field identifies which SWBB (IPforwarding, ISNA, GDC,
          SFAS or PRTA) this registration entry is belong to. "
    ::= { adnRdssRegistrationEntry  3 }

adnRdssCongestionFlag OBJECT-TYPE
    SYNTAX  INTEGER {
    notcongested(1),
    congested(2)
}
    ACCESS  read-only
    STATUS  mandatory
    DESCRIPTION
           " This flag indicates whether the IACS session between Routes
          Distribution and the registered subsystem (IPforwarding, ISNA, 
          GDC, SFAS or PRTA) in registration entry is congested or not. "
    ::= { adnRdssRegistrationEntry  4 }

adnRdssFatSequenceNum OBJECT-TYPE
    SYNTAX  INTEGER (-2147483648..2147483647)
    ACCESS  read-only
    STATUS  mandatory
    DESCRIPTION
           " This field identifies the sequence number used to send the 
          last previous FAT message. The sequence number increments 
          sequentially on every new FAT message sent. It will be rolled
          back to zero when reached maximum value. "
    ::= { adnRdssRegistrationEntry  5 }

adnRdssGatSequenceNum OBJECT-TYPE
    SYNTAX  INTEGER (-2147483648..2147483647)
    ACCESS  read-only
    STATUS  mandatory
    DESCRIPTION
           " This field identifies the sequence number used to send the 
          last previous GAT message. The sequence number increments 
          sequentially on every new GAT message sent. It will be rolled
          back to zero when reached maximum value. "
    ::= { adnRdssRegistrationEntry  6 }

adnRdssMatSequenceNum OBJECT-TYPE
    SYNTAX  INTEGER (-2147483648..2147483647)
    ACCESS  read-only
    STATUS  mandatory
    DESCRIPTION
           " This field identifies the sequence number used to send the 
          last previous MAT message. The sequence number increments 
          sequentially on every new MAT message sent. It will be rolled
          back to zero when reached maximum value. "
    ::= { adnRdssRegistrationEntry  7 }

adnRdssAckFlags OBJECT-TYPE
    SYNTAX  INTEGER (-2147483648..2147483647)
    ACCESS  read-only
    STATUS  mandatory
    DESCRIPTION
           " This is bit-map field represents the statuses of acknowledgment
          from a previous transmitted FAT, GAT, or MAT message. Bit 0
          represents FAT acknowledgment, bit 1 represents GAT 
          acknowledgment, and bit 2 represents MAT acknowledgment. If a 
          bit position has value of zero, it indicates the correspond 
          acknowledgment message has not been received. When an 
          acknowledgment message is received, its sequence number is
          compared with the correspond transmitted message's sequence 
          number. If both are match, then the correspond Ack Flag bit will 
          be set. If both are not match, then the received message will
          be ignored. "
    ::= { adnRdssRegistrationEntry  8 }

adnRdssNextHopLastSequenceNum OBJECT-TYPE
    SYNTAX  INTEGER (-2147483648..2147483647)
    ACCESS  read-only
    STATUS  mandatory
    DESCRIPTION
           " This field hold the sequesnce number of the last received valid
          Next-Hop message. It is used for handling duplicate received 
          messages. This field is intialized to 0xff. "
    ::= { adnRdssRegistrationEntry  9 }

adnRdssLatLastSequenceNum OBJECT-TYPE
    SYNTAX  INTEGER (-2147483648..2147483647)
    ACCESS  read-only
    STATUS  mandatory
    DESCRIPTION
           " This field hold the sequesnce number of the last received valid
          LAT message. It is used for handling duplicate received
          messages. This field is intialized to 0xff. "
    ::= { adnRdssRegistrationEntry  10 }

adnRdssMatLastSequenceNum OBJECT-TYPE
    SYNTAX  INTEGER (-2147483648..2147483647)
    ACCESS  read-only
    STATUS  mandatory
    DESCRIPTION
           " This field hold the sequesnce number of the last received valid
          MAT message. It is used for handling duplicate received
          messages. This field is intialized to 0xff. "
    ::= { adnRdssRegistrationEntry  11 }

adnRdssTransmitMsgBufId OBJECT-TYPE
    SYNTAX  INTEGER (-2147483648..2147483647)
    ACCESS  read-only
    STATUS  mandatory
    DESCRIPTION
           " This is the address of the message buffer for sending data."
    ::= { adnRdssRegistrationEntry  12 }

adnRdssGatTableTraverseStatus OBJECT-TYPE
    SYNTAX  INTEGER (-2147483648..2147483647)
    ACCESS  read-only
    STATUS  mandatory
    DESCRIPTION
           " This field is used to indentify whether the traversing is 
          currently on LPX, Ifindex or VC. "
    ::= { adnRdssRegistrationEntry  13 }

adnRdssGatTableTraverseLpxKey OBJECT-TYPE
    SYNTAX  INTEGER (-2147483648..2147483647)
    ACCESS  read-only
    STATUS  mandatory
    DESCRIPTION
           " This field is used to identify the LPX of corresponding interface
          being traverse. "
    ::= { adnRdssRegistrationEntry  14 }

adnRdssTypeOfTableRequested OBJECT-TYPE
    SYNTAX  INTEGER (-2147483648..2147483647)
    ACCESS  read-only
    STATUS  mandatory
    DESCRIPTION
           " This field is bit-map defining what types of tables are to be
          provided to the registering subsystem. Table types include
         FAT, GAT, MAT, and etc. "
    ::= { adnRdssRegistrationEntry  15 }

adnRdssGatTableTraverseStartKey OBJECT-TYPE
    SYNTAX  INTEGER (-2147483648..2147483647)
    ACCESS  read-only
    STATUS  mandatory
    DESCRIPTION
           " This key is used for the purpose of distributing the entries 
          from the GAT table when a SWBB subsystem has just register 
          (just came up) with Routes Distribution.
          The Start Key is the key to the first entry sent on the previous
          message to aid in the scenario when retransmission of the 
          previous message is required. Set Start key to NULL to indicate
          completed table has been sent, or table is empty. Set Start 
          Key to KEY {Root} to start traversal. Set Start Key equal to
          End Key to indicate GAT table traversal is completed. "
    ::= { adnRdssRegistrationEntry  16 }

adnRdssGatTableTraverseEndKey OBJECT-TYPE
    SYNTAX  INTEGER (-2147483648..2147483647)
    ACCESS  read-only
    STATUS  mandatory
    DESCRIPTION
           " This key is used for the purpose of distributing the entries 
          from the GAT table when a SWBB subsystem has just register 
          (just came up) with Routes Distribution.
          The End Key is the key to the last GAT entry sent on the
          previous message, and is used to keep track of where in the 
          GAT table to continue for the next message. "
    ::= { adnRdssRegistrationEntry  17 }

adnRdssGatMsgQueueStartPointer OBJECT-TYPE
    SYNTAX  INTEGER (-2147483648..2147483647)
    ACCESS  read-only
    STATUS  mandatory
    DESCRIPTION
           " The GAT message queue contains linked list of updated entries. 
          This start pointer marks an entry in the lists as beginning entry
          in the lists to be sent or is sending to the correspond IP
          Forwarding subsystem. "
    ::= { adnRdssRegistrationEntry  18 }

adnRdssFatEntranceKey OBJECT-TYPE
    SYNTAX  INTEGER (-2147483648..2147483647)
    ACCESS  read-only
    STATUS  mandatory
    DESCRIPTION
           " The FAT Entrance Key. 
          This field is used to set the starting point to traverse the FAT
          table for this session. "
    ::= { adnRdssRegistrationEntry  19 }

adnRdssForwardingTable OBJECT-TYPE
    SYNTAX  SEQUENCE OF AdnRdssForwardingEntry
    ACCESS  not-accessible
    STATUS  mandatory
    DESCRIPTION
           " The forwarding table contains data information to be forwarded, 
          and status and control information relating to the entry itself 
          for table book keeping purpose. "
    ::= { adnRdssMIB  2 }

adnRdssForwardingEntry OBJECT-TYPE
    SYNTAX  AdnRdssForwardingEntry
    ACCESS  not-accessible
    STATUS  mandatory
    DESCRIPTION
           " Entry in the adnRdssForwardingTable. "
    INDEX   { adnRdssDestIpAddress }
    ::= { adnRdssForwardingTable  1 }

AdnRdssForwardingEntry ::=
    SEQUENCE {
        adnRdssDestIpAddress
            IpAddress,

        adnRdssFatMask
            INTEGER,

        adnRdssFatFlag
            INTEGER,

        adnRdssFatCommand
            AdnRdssCommandType,

        adnRdssFatStatusAckCnt
            INTEGER,

        adnRdssNextHopIpAddr
            IpAddress,

        adnRdssFatLowerFsm
            INTEGER (-2147483648..2147483647),

        adnRdssFatMidFsm
            INTEGER (-2147483648..2147483647),

        adnRdssFatUpperFsm
            INTEGER (-2147483648..2147483647)
    }

adnRdssDestIpAddress OBJECT-TYPE
    SYNTAX  IpAddress
    ACCESS  read-only
    STATUS  mandatory
    DESCRIPTION
           "The IP address of the destination prefix. "
    ::= { adnRdssForwardingEntry  1 }

adnRdssFatMask OBJECT-TYPE
    SYNTAX  INTEGER
    ACCESS  read-only
    STATUS  mandatory
    DESCRIPTION
           " This field represent the valid number of leading bits in the 
          prefix of this address. It is the network IP mask. "
    ::= { adnRdssForwardingEntry  2 }

adnRdssFatFlag OBJECT-TYPE
    SYNTAX  INTEGER {
    unicastentry(1),
    broadcastentry(2),
    multicastentry(3),
    localhostentry(4),
    staticentry(5)
}
    ACCESS  read-only
    STATUS  mandatory
    DESCRIPTION
           " This field represents the type of the destination IP address. "
    ::= { adnRdssForwardingEntry  3 }

adnRdssFatCommand OBJECT-TYPE
    SYNTAX  AdnRdssCommandType
    ACCESS  read-only
    STATUS  mandatory
    DESCRIPTION
           " This is the same as the command field in the entry message
          header. Except when the value od this field is 255, then it 
          is for internal used. "
    ::= { adnRdssForwardingEntry  4 }

adnRdssFatStatusAckCnt OBJECT-TYPE
    SYNTAX  INTEGER
    ACCESS  read-only
    STATUS  mandatory
    DESCRIPTION
           " This field conveys the status information of the entry itself. 
          It has dual functions and divided into two separated fields:
          Entry Status field and ACK count field. "
    ::= { adnRdssForwardingEntry  5 }

adnRdssNextHopIpAddr OBJECT-TYPE
    SYNTAX  IpAddress
    ACCESS  read-only
    STATUS  mandatory
    DESCRIPTION
           " This field represents the IP address of the directly connected
          router or the local IP address. If the adnRdssFatFlag is Local
          Host entry, then this field is Zero. "
    ::= { adnRdssForwardingEntry  6 }

adnRdssFatLowerFsm OBJECT-TYPE
    SYNTAX  INTEGER (-2147483648..2147483647)
    ACCESS  read-only
    STATUS  mandatory
    DESCRIPTION
           " This longword is part of the three longwords which composes of
          forty eight 2-bit fields. Each 2-bits field represents the FSM 
          of this entry to the corresponding IP Forwarding subsystem. 
          The FAT Entry Processing FSM Control Block keeps track of which
          IP Forwarding this entry needed to be forwarding to, and which 
          IP Forwarding this entry has been forwarded to, and which
          IP Forwarding has already acknowledged the reception of this 
          entry. "
    ::= { adnRdssForwardingEntry  7 }

adnRdssFatMidFsm OBJECT-TYPE
    SYNTAX  INTEGER (-2147483648..2147483647)
    ACCESS  read-only
    STATUS  mandatory
    DESCRIPTION
           " This longword is part of the three longwords which composes of
          forty eight 2-bit fields. Each 2-bits field represents the FSM 
          of this entry to the corresponding IP Forwarding subsystem. 
          The FAT Entry Processing FSM Control Block keeps track of which
          IP Forwarding this entry needed to be forwarding to, and which 
          IP Forwarding this entry has been forwarded to, and which
          IP Forwarding has already acknowledged the reception of this 
          entry. "
    ::= { adnRdssForwardingEntry  8 }

adnRdssFatUpperFsm OBJECT-TYPE
    SYNTAX  INTEGER (-2147483648..2147483647)
    ACCESS  read-only
    STATUS  mandatory
    DESCRIPTION
           " This longword is part of the three longwords which composes of
          forty eight 2-bit fields. Each 2-bits field represents the FSM 
          of this entry to the corresponding IP Forwarding subsystem. 
          The FAT Entry Processing FSM Control Block keeps track of which
          IP Forwarding this entry needed to be forwarding to, and which 
          IP Forwarding this entry has been forwarded to, and which
          IP Forwarding has already acknowledged the reception of this 
          entry. "
    ::= { adnRdssForwardingEntry  9 }

adnRdssGatIfindexTable OBJECT-TYPE
    SYNTAX  SEQUENCE OF AdnRdssGatIfindexEntry
    ACCESS  not-accessible
    STATUS  mandatory
    DESCRIPTION
           " This table contains all information associated with
          all the ifindexes, which are configured in the IP
          Forwarding subsystems. "
    ::= { adnRdssMIB  3 }

adnRdssGatIfindexEntry OBJECT-TYPE
    SYNTAX  AdnRdssGatIfindexEntry
    ACCESS  not-accessible
    STATUS  mandatory
    DESCRIPTION
           " Entry in the adnRdssGatIfindexTable. "
    INDEX   { adnRdssGatIfindexLpxIndex,  adnRdssGatIfIndex }
    ::= { adnRdssGatIfindexTable  1 }

AdnRdssGatIfindexEntry ::=
    SEQUENCE {
        adnRdssGatIfindexLpxIndex
            INTEGER (-2147483648..2147483647),

        adnRdssGatIfIndex
            INTEGER (-2147483648..2147483647),

        adnRdssGatIfindexOption
            AdnRdssOption,

        adnRdssGatIfindexCommandType
            AdnRdssCommandType,

        adnRdssGatIfindexStatus
            AdnRdssStatus,

        adnRdssGatIfLiiAddress
            IpAddress,

        adnRdssGatIfMask
            INTEGER,

        adnRdssGatIfServiceType
            INTEGER,

        adnRdssGatIfMtu
            INTEGER,

        adnRdssGatIfPrivateData
            INTEGER,

        adnRdssGatIfBroadcastAddr
            IpAddress,

        adnRdssGatIfCost
            INTEGER (-2147483648..2147483647)
    }

adnRdssGatIfindexLpxIndex OBJECT-TYPE
    SYNTAX  INTEGER (-2147483648..2147483647)
    ACCESS  read-only
    STATUS  mandatory
    DESCRIPTION
           " The LPX of subsystem which is registered to Routes
          Distribution. "
    ::= { adnRdssGatIfindexEntry  1 }

adnRdssGatIfIndex OBJECT-TYPE
    SYNTAX  INTEGER (-2147483648..2147483647)
    ACCESS  read-only
    STATUS  mandatory
    DESCRIPTION
           " This is the unique identifier associated to the logical 
          IP interface. "
    ::= { adnRdssGatIfindexEntry  2 }

adnRdssGatIfindexOption OBJECT-TYPE
    SYNTAX  AdnRdssOption
    ACCESS  read-only
    STATUS  mandatory
    DESCRIPTION
           " Type of LAT message. "
    ::= { adnRdssGatIfindexEntry  3 }

adnRdssGatIfindexCommandType OBJECT-TYPE
    SYNTAX  AdnRdssCommandType
    ACCESS  read-only
    STATUS  mandatory
    DESCRIPTION
           " Type of LAT command. "
    ::= { adnRdssGatIfindexEntry  4 }

adnRdssGatIfindexStatus OBJECT-TYPE
    SYNTAX  AdnRdssStatus
    ACCESS  read-only
    STATUS  mandatory
    DESCRIPTION
           " Status of the ifindex. "
    ::= { adnRdssGatIfindexEntry  5 }

adnRdssGatIfLiiAddress OBJECT-TYPE
    SYNTAX  IpAddress
    ACCESS  read-only
    STATUS  mandatory
    DESCRIPTION
           " This field is the source address associated with the ifindex. "
    ::= { adnRdssGatIfindexEntry  6 }

adnRdssGatIfMask OBJECT-TYPE
    SYNTAX  INTEGER
    ACCESS  read-only
    STATUS  mandatory
    DESCRIPTION
           " This field represents the valid number of leading bits in the
          prefix of the adnRdssGatIfLiiAddress. It is the network IP mask. "
    ::= { adnRdssGatIfindexEntry  7 }

adnRdssGatIfServiceType OBJECT-TYPE
    SYNTAX  INTEGER
    ACCESS  read-only
    STATUS  mandatory
    DESCRIPTION
           " This field defines the type of the data link layer below the 
          <Ifindex, VPI/VCI or DLCI>. Refer to RFC 1512 for the exhaustive
          list of the service types. We currently support only Frame
          Relay and AAL5/ATM. "
    ::= { adnRdssGatIfindexEntry  8 }

adnRdssGatIfMtu OBJECT-TYPE
    SYNTAX  INTEGER
    ACCESS  read-only
    STATUS  mandatory
    DESCRIPTION
           " This field represents the size of the MTU associated with 
          this ifindex. "
    ::= { adnRdssGatIfindexEntry  9 }

adnRdssGatIfPrivateData OBJECT-TYPE
    SYNTAX  INTEGER
    ACCESS  read-only
    STATUS  mandatory
    DESCRIPTION
           " This field is used by IPFW and is passed as it is from RDSS
          to all other IP Forwarding subsystems. "
    ::= { adnRdssGatIfindexEntry  11 }

adnRdssGatIfBroadcastAddr OBJECT-TYPE
    SYNTAX  IpAddress
    ACCESS  read-only
    STATUS  mandatory
    DESCRIPTION
           " This field represents the broadcast IP address associated
          with the Ifindex. "
    ::= { adnRdssGatIfindexEntry  12 }

adnRdssGatIfCost OBJECT-TYPE
    SYNTAX  INTEGER (-2147483648..2147483647)
    ACCESS  read-only
    STATUS  mandatory
    DESCRIPTION
           " This is the interface cost associated with the ifindex. "
    ::= { adnRdssGatIfindexEntry  13 }

adnRdssGatVcTable OBJECT-TYPE
    SYNTAX  SEQUENCE OF AdnRdssGatVcEntry
    ACCESS  not-accessible
    STATUS  mandatory
    DESCRIPTION
           " This table contains all information associated with all the 
          VCs, which are configured in the IP Forwarding subsystems. "
    ::= { adnRdssMIB  4 }

adnRdssGatVcEntry OBJECT-TYPE
    SYNTAX  AdnRdssGatVcEntry
    ACCESS  not-accessible
    STATUS  mandatory
    DESCRIPTION
           " Entry in the adnRdssGatVcTable. "
    INDEX   { adnRdssGatVcNextHopAddr }
    ::= { adnRdssGatVcTable  1 }

AdnRdssGatVcEntry ::=
    SEQUENCE {
        adnRdssGatVcNextHopAddr
            IpAddress,

        adnRdssGatVcLpx
            INTEGER (-2147483648..2147483647),

        adnRdssGatVcIfIndex
            INTEGER (-2147483648..2147483647),

        adnRdssGatVcVpiVciOrDlci
            INTEGER (-2147483648..2147483647),

        adnRdssGatVcOption
            AdnRdssOption,

        adnRdssGatVcCommandType
            AdnRdssCommandType,

        adnRdssGatVcStatus
            AdnRdssStatus,

        adnRdssGatVcServiceType
            INTEGER,

        adnRdssGatVcCost
            INTEGER (-2147483648..2147483647),

        adnRdssGatVcLiiAddress
            IpAddress
    }

adnRdssGatVcNextHopAddr OBJECT-TYPE
    SYNTAX  IpAddress
    ACCESS  read-only
    STATUS  mandatory
    DESCRIPTION
           " This field represents the IP address of the directly connected
          router or the local IP address. "
    ::= { adnRdssGatVcEntry  1 }

adnRdssGatVcLpx OBJECT-TYPE
    SYNTAX  INTEGER (-2147483648..2147483647)
    ACCESS  read-only
    STATUS  mandatory
    DESCRIPTION
           " The LPX of subsystem which is registered to Routes
          Distribution. "
    ::= { adnRdssGatVcEntry  2 }

adnRdssGatVcIfIndex OBJECT-TYPE
    SYNTAX  INTEGER (-2147483648..2147483647)
    ACCESS  read-only
    STATUS  mandatory
    DESCRIPTION
           " This is the unique identifier associated to the VC. "
    ::= { adnRdssGatVcEntry  3 }

adnRdssGatVcVpiVciOrDlci OBJECT-TYPE
    SYNTAX  INTEGER (-2147483648..2147483647)
    ACCESS  read-only
    STATUS  mandatory
    DESCRIPTION
           " This field represents the data link identifier (VPI/VCI for
          AAL5 or DLCI for Frame Relay for the Next-Hop under
          discussion. "
    ::= { adnRdssGatVcEntry  4 }

adnRdssGatVcOption OBJECT-TYPE
    SYNTAX  AdnRdssOption
    ACCESS  read-only
    STATUS  mandatory
    DESCRIPTION
           " Type of LAT message. "
    ::= { adnRdssGatVcEntry  5 }

adnRdssGatVcCommandType OBJECT-TYPE
    SYNTAX  AdnRdssCommandType
    ACCESS  read-only
    STATUS  mandatory
    DESCRIPTION
           " Type of LAT Vc command. "
    ::= { adnRdssGatVcEntry  6 }

adnRdssGatVcStatus OBJECT-TYPE
    SYNTAX  AdnRdssStatus
    ACCESS  read-only
    STATUS  mandatory
    DESCRIPTION
           " Status of Vc. "
    ::= { adnRdssGatVcEntry  7 }

adnRdssGatVcServiceType OBJECT-TYPE
    SYNTAX  INTEGER
    ACCESS  read-only
    STATUS  mandatory
    DESCRIPTION
           " This field defines the type of the data link layer below the
          <Ifindex, VPI/VCI or DLCI>. Refer to RFC 1512 for the exhaustive
          list of the service types. We currently support only Frame
          Relay and AAL5/ATM. "
    ::= { adnRdssGatVcEntry  8 }

adnRdssGatVcCost OBJECT-TYPE
    SYNTAX  INTEGER (-2147483648..2147483647)
    ACCESS  read-only
    STATUS  mandatory
    DESCRIPTION
           " This is the interface cost associated with the ifindex. "
    ::= { adnRdssGatVcEntry  9 }

adnRdssGatVcLiiAddress OBJECT-TYPE
    SYNTAX  IpAddress
    ACCESS  read-only
    STATUS  mandatory
    DESCRIPTION
           " This field is the source address associated with the ifindex. "
    ::= { adnRdssGatVcEntry  10 }

adnRdssTraceTable OBJECT-TYPE
    SYNTAX  SEQUENCE OF AdnRdssTraceEntry
    ACCESS  not-accessible
    STATUS  mandatory
    DESCRIPTION
           "Each entry (row) in the adnRdssTraceTable "
    ::= { adnRdssMIB  5 }

adnRdssTraceEntry OBJECT-TYPE
    SYNTAX  AdnRdssTraceEntry
    ACCESS  not-accessible
    STATUS  mandatory
    DESCRIPTION
           "Each entry (row) in the adnRtsagtTraceTable."
    INDEX   { adnRdssTraceLpxIndex,  adnRdssTraceIndex }
    ::= { adnRdssTraceTable  1 }

AdnRdssTraceEntry ::=
    SEQUENCE {
        adnRdssTraceLpxIndex
            INTEGER (-2147483648..2147483647),

        adnRdssTraceIndex
            INTEGER,

        adnRdssTraceValue
            OCTET STRING
    }

adnRdssTraceLpxIndex OBJECT-TYPE
    SYNTAX  INTEGER (-2147483648..2147483647)
    ACCESS  not-accessible
    STATUS  mandatory
    DESCRIPTION
           "LPX of registered subsystems. "
    ::= { adnRdssTraceEntry  1 }

adnRdssTraceIndex OBJECT-TYPE
    SYNTAX  INTEGER
    ACCESS  not-accessible
    STATUS  mandatory
    DESCRIPTION
           "Trace Index Number"
    ::= { adnRdssTraceEntry  2 }

adnRdssTraceValue OBJECT-TYPE
    SYNTAX  OCTET STRING
    ACCESS  read-only
    STATUS  mandatory
    DESCRIPTION
           "This is the binary."
    ::= { adnRdssTraceEntry  3 }

adnIprtEnvMIB OBJECT IDENTIFIER ::= { adnEnvHss  16 }

adnIpRouteNetstatTable OBJECT-TYPE
    SYNTAX  SEQUENCE OF AdnIpRouteNetstatEntry
    ACCESS  not-accessible
    STATUS  mandatory
    DESCRIPTION
           "This is the IP Routing Environmental Table"
    ::= { adnIprtEnvMIB  1 }

adnIpRouteNetstatEntry OBJECT-TYPE
    SYNTAX  AdnIpRouteNetstatEntry
    ACCESS  not-accessible
    STATUS  mandatory
    DESCRIPTION
           "The IP Route Int Entry provides access to the CU TCP/UDP/IP stack 
     information. It is recommended that the objects of this table be 
     fetched with an SNMP get/getnext/etc. of all instances of the 
     given object without any index postfix."
    INDEX   { adnIpRouteNetstatIndex }
    ::= { adnIpRouteNetstatTable  1 }

AdnIpRouteNetstatEntry ::=
    SEQUENCE {
        adnIpRouteNetstatIndex
            INTEGER (-2147483648..2147483647),

        adnIpRouteNetstatIfconfig
            DisplayString,

        adnIpRouteNetstatRoutes
            DisplayString,

        adnIpRouteNetstatProtStats
            DisplayString,

        adnIpRouteNetstatNetSockets
            DisplayString,

        adnIpRouteNetstatNetConnec
            DisplayString,

        adnIpRouteNetstatNetNum
            DisplayString
    }

adnIpRouteNetstatIndex OBJECT-TYPE
    SYNTAX  INTEGER (-2147483648..2147483647)
    ACCESS  read-only
    STATUS  mandatory
    DESCRIPTION
           "This object defines the Index into this table."
    ::= { adnIpRouteNetstatEntry  1 }

adnIpRouteNetstatIfconfig OBJECT-TYPE
    SYNTAX  DisplayString
    ACCESS  read-only
    STATUS  mandatory
    DESCRIPTION
           "This object defines the ASCII string that includes the CU IP
     Interface description (similar to unix [netstat -i] command)."
    ::= { adnIpRouteNetstatEntry  2 }

adnIpRouteNetstatRoutes OBJECT-TYPE
    SYNTAX  DisplayString
    ACCESS  read-only
    STATUS  mandatory
    DESCRIPTION
           "This object defines the ASCII string that includes the CU IP 
     Forwarding memory cache (similar to unix [netstat -r] command)."
    ::= { adnIpRouteNetstatEntry  3 }

adnIpRouteNetstatProtStats OBJECT-TYPE
    SYNTAX  DisplayString
    ACCESS  read-only
    STATUS  mandatory
    DESCRIPTION
           "This object defines the ASCII string that includes the CU IP/
     TCP/UPD packet count statistics (similar to unix [netstat -s] command)."
    ::= { adnIpRouteNetstatEntry  4 }

adnIpRouteNetstatNetSockets OBJECT-TYPE
    SYNTAX  DisplayString
    ACCESS  read-only
    STATUS  mandatory
    DESCRIPTION
           "This object defines the ASCII string that includes the CU IP 
     network sockets (similar to unix [netstat -a] command)."
    ::= { adnIpRouteNetstatEntry  5 }

adnIpRouteNetstatNetConnec OBJECT-TYPE
    SYNTAX  DisplayString
    ACCESS  read-only
    STATUS  mandatory
    DESCRIPTION
           "This object defines the ASCII string that includes the CU IP 
     network connections (similar to unix [netstat -A] command)."
    ::= { adnIpRouteNetstatEntry  6 }

adnIpRouteNetstatNetNum OBJECT-TYPE
    SYNTAX  DisplayString
    ACCESS  read-only
    STATUS  mandatory
    DESCRIPTION
           "This object defines the ASCII string that includes the CU IP 
     network numbers (similar to unix [netstat -n] command)."
    ::= { adnIpRouteNetstatEntry  7 }

adnIpRouteDiagTable OBJECT-TYPE
    SYNTAX  SEQUENCE OF AdnIpRouteDiagEntry
    ACCESS  not-accessible
    STATUS  mandatory
    DESCRIPTION
           "This is the IP Routing Environmental Table"
    ::= { adnIprtEnvMIB  2 }

adnIpRouteDiagEntry OBJECT-TYPE
    SYNTAX  AdnIpRouteDiagEntry
    ACCESS  not-accessible
    STATUS  mandatory
    DESCRIPTION
           "The IP Route Diag Entry defines IP Routing supplemental objects used
     to diagnose/trouble shoot IP Routing subsystem problems."
    INDEX   { adnIpRouteDiagIndex }
    ::= { adnIpRouteDiagTable  1 }

AdnIpRouteDiagEntry ::=
    SEQUENCE {
        adnIpRouteDiagIndex
            INTEGER (-2147483648..2147483647),

        adnIpRouteDiagPrintFlags
            INTEGER (-2147483648..2147483647)
    }

adnIpRouteDiagIndex OBJECT-TYPE
    SYNTAX  INTEGER (-2147483648..2147483647)
    ACCESS  read-only
    STATUS  mandatory
    DESCRIPTION
           "This object defines the Index into this table."
    ::= { adnIpRouteDiagEntry  1 }

adnIpRouteDiagPrintFlags OBJECT-TYPE
    SYNTAX  INTEGER (-2147483648..2147483647)
    ACCESS  read-write
    STATUS  mandatory
    DESCRIPTION
           "This object defines the print control flags bit mask used to enable 
     printing debugging messages to the CU console screen. Each bit position
     is used to enable printing of processing different level of internal
     IP Routing processing messages:
     --
     The hexidecimal bit positions are defined as follows:
     0x0001  Do not print any diagnostic messages
     0x0002  Print only NHP messages
     0x0004  Print only GAT messages
     0x0008  Print only SNMP messages
     0x0010  Print only CONFIG messages
     0x0020  Print NMGS FSM messages
     0x0040  Print SFAS FSM messages
     0x0080  Print RDSS FSM messages
     0x0100  Print GATED FSM messages
     0x0200  Print all ERROR messages
     0x0400  Print all DEBUG messages 
     0x0800  Print ALL the above message types
     0x1000  Activate GateD with its trace ON 
     --"
    ::= { adnIpRouteDiagEntry  2 }

END
