ChrComHWEquipment-MIB

--FORCE-INCLUDE	<mib.h>
--FORCE-INCLUDE	<snmpdefs.h>
--FORCE-INCLUDE	"mibhand.h"

	DEFINITIONS  ::=  BEGIN

IMPORTS
	OBJECT-TYPE, Counter32			FROM  SNMPv2-SMI
	Integer32, Unsigned32			FROM  SNMPv2-SMI
	chrComHW				FROM  Chromatis-MIB
	DisplayString			FROM  RFC1213-MIB
	CardResetOp				FROM  HwcmTypes-MIB;

-- chrComHWEquipment Table

chrComHWEquipmentTable		OBJECT-TYPE
	SYNTAX		SEQUENCE OF ChrComHWEquipmentEntry
	MAX-ACCESS	not-accessible
	STATUS		current
	DESCRIPTION
	"This table models both the equipment holder (shelves, slots) and the plug in units (cards)"
	::= { chrComHW 2}

chrComHWEquipmentEntry		OBJECT-TYPE
	SYNTAX		ChrComHWEquipmentEntry
	MAX-ACCESS	not-accessible
	STATUS		current
	DESCRIPTION
	""
	INDEX  {  chrComHWEqIndex }

--DEFAULT  get-function-async  MNIL_GetRoutine
--DEFAULT  set-function-async  MNIL_SetRoutine
--DEFAULT  next-function-async MNIL_NextRoutine
--DEFAULT  test-function-async MNIL_TestRoutine
--DEFAULT  cookie "Equipment"
	::= { chrComHWEquipmentTable  1 }

ChrComHWEquipmentEntry  ::=
	SEQUENCE  {
	chrComHWEqIndex			Integer32	(0..65535),
	chrComHWAcceptableCardsFunc	OCTET STRING	(SIZE (4..2048)),
	chrComHWAcceptableMarketingNames DisplayString	(SIZE (4..64)),
	chrComHWExpectedMarketingName	DisplayString	(SIZE (4..64)),
	chrComHWExpectedCardFunc	Unsigned32	(0..4294967295),
	chrComHWActualCardFunc		Unsigned32	(0..4294967295),
	chrComHWActualMarketingName	DisplayString	(SIZE (4..64)),
	chrComHWNMSInfo			OCTET STRING	(SIZE (1..16)),
	chrComHWExternalPortscount	Unsigned32	(0..49),
	chrComHWExternalPortsType	OCTET STRING	(SIZE (0..196)),
	chrComHWAcceptableProtectingPeerList OCTET STRING	(SIZE (0..128)),
	chrComHWProtectingPeer		Unsigned32	(0..4294967295),
	chrComHWModulePartNumber	DisplayString	(SIZE (0..14)),
	chrComHWModuleRevision		DisplayString	(SIZE (0..1)),
	chrComHWSerialNumbrer		DisplayString	(SIZE (0..9)),
	chrComHWCLEI			DisplayString	(SIZE (0..10)),
	chrComHWManufacturingDate	DisplayString	(SIZE (0..10)),
	chrComHWLastTestingDate		DisplayString	(SIZE (0..10)),
	chrComHWTemperature		Integer32	(-40..85),
	chrComHWFirmwareVersion		DisplayString	(SIZE (0..9)),
	chrComHWCardBootVersion		DisplayString	(SIZE (0..9)),
	chrComHWCardSwVersion		DisplayString	(SIZE (0..9)),
	chrComHWMaxATMoverSonetTPs	Unsigned32	(0..4294967295),
	chrComHWSlotAlarmVector		Unsigned32	(0..4294967295),
	chrComHWAlarmSeverProfileIndex	Unsigned32	(0..4294967295),
	chrComHWCardResetOperation	CardResetOp
}

chrComHWEqIndex 	OBJECT-TYPE
	SYNTAX		Integer32	(0..65535)
	MAX-ACCESS 	read-only
	STATUS 		current
	DESCRIPTION
	"Index containing shelf and slot number"
	::= { chrComHWEquipmentEntry  1 }

chrComHWAcceptableCardsFunc 	OBJECT-TYPE
	SYNTAX		OCTET STRING	(SIZE (4..2048))
	MAX-ACCESS 	read-only
	STATUS 		current
	DESCRIPTION
	"The cards that can be inserted to the current slot."
	::= { chrComHWEquipmentEntry  2 }

chrComHWAcceptableMarketingNames 	OBJECT-TYPE
	SYNTAX		DisplayString	(SIZE (4..64))
	MAX-ACCESS 	read-only
	STATUS 		current
	DESCRIPTION
	"The cards that can be inserted to the current slot."
	::= { chrComHWEquipmentEntry  3 }

chrComHWExpectedMarketingName 	OBJECT-TYPE
	SYNTAX		DisplayString	(SIZE (4..64))
	MAX-ACCESS 	read-only
	STATUS 		current
	DESCRIPTION
	"Marketing Name of the card, which is configured to be in the slot. This item is marketing decision."
	::= { chrComHWEquipmentEntry  4 }

chrComHWExpectedCardFunc 	OBJECT-TYPE
	SYNTAX		Unsigned32	(0..4294967295)
	MAX-ACCESS 	read-write
	STATUS 		current
	DESCRIPTION
	"The specific functions the card is expected to provide, which is determined by the expected marketing name."
	::= { chrComHWEquipmentEntry  5 }

chrComHWActualCardFunc 	OBJECT-TYPE
	SYNTAX		Unsigned32	(0..4294967295)
	MAX-ACCESS 	read-only
	STATUS 		current
	DESCRIPTION
	"The specific functions of the card that is inserted in the slot."
	::= { chrComHWEquipmentEntry  6 }

chrComHWActualMarketingName 	OBJECT-TYPE
	SYNTAX		DisplayString	(SIZE (4..64))
	MAX-ACCESS 	read-only
	STATUS 		current
	DESCRIPTION
	"The marketing name of the actual card plugged in the slot."
	::= { chrComHWEquipmentEntry  7 }

chrComHWNMSInfo 	OBJECT-TYPE
	SYNTAX		OCTET STRING	(SIZE (1..16))
	MAX-ACCESS 	read-only
	STATUS 		current
	DESCRIPTION
	"A code representing the module type. "
	::= { chrComHWEquipmentEntry  8 }

chrComHWExternalPortscount 	OBJECT-TYPE
	SYNTAX		Unsigned32	(0..49)
	MAX-ACCESS 	read-only
	STATUS 		current
	DESCRIPTION
	""
	::= { chrComHWEquipmentEntry  9 }

chrComHWExternalPortsType 	OBJECT-TYPE
	SYNTAX		OCTET STRING	(SIZE (0..196))
	MAX-ACCESS 	read-write
	STATUS 		current
	DESCRIPTION
	"For service cards (OCMs and Tribs): An array that specifies per each external port of the card, which is its type. 
For cards other than service cards: N/A
"
	::= { chrComHWEquipmentEntry  10 }

chrComHWAcceptableProtectingPeerList 	OBJECT-TYPE
	SYNTAX		OCTET STRING	(SIZE (0..128))
	MAX-ACCESS 	read-only
	STATUS 		current
	DESCRIPTION
	"List of card IDs (Equipment Index) that might serve as protection peers for the current card.
Null Eq. Index in the list signifies that unprotected option is acceptable for the card.
"
	::= { chrComHWEquipmentEntry  11 }

chrComHWProtectingPeer 	OBJECT-TYPE
	SYNTAX		Unsigned32	(0..4294967295)
	MAX-ACCESS 	read-write
	STATUS 		current
	DESCRIPTION
	"ID of the card (EqIndex) that was selected from the list"
	::= { chrComHWEquipmentEntry  12 }

chrComHWModulePartNumber 	OBJECT-TYPE
	SYNTAX		DisplayString	(SIZE (0..14))
	MAX-ACCESS 	read-only
	STATUS 		current
	DESCRIPTION
	"The Catalog number includes the version and the assembly option of the card."
	::= { chrComHWEquipmentEntry  13 }

chrComHWModuleRevision 	OBJECT-TYPE
	SYNTAX		DisplayString	(SIZE (0..1))
	MAX-ACCESS 	read-only
	STATUS 		current
	DESCRIPTION
	"The revision of the card (mostly the PCB revision)."
	::= { chrComHWEquipmentEntry  14 }

chrComHWSerialNumbrer 	OBJECT-TYPE
	SYNTAX		DisplayString	(SIZE (0..9))
	MAX-ACCESS 	read-only
	STATUS 		current
	DESCRIPTION
	"A unique serial number exists for each combination of Part number, release, assembly type and assembly option."
	::= { chrComHWEquipmentEntry  15 }

chrComHWCLEI 	OBJECT-TYPE
	SYNTAX		DisplayString	(SIZE (0..10))
	MAX-ACCESS 	read-only
	STATUS 		current
	DESCRIPTION
	"The Catalog number includes the version and the assembly option of the card as given by Telecordia (Bellcore)"
	::= { chrComHWEquipmentEntry  16 }

chrComHWManufacturingDate 	OBJECT-TYPE
	SYNTAX		DisplayString	(SIZE (0..10))
	MAX-ACCESS 	read-only
	STATUS 		current
	DESCRIPTION
	"The date the card was assembled."
	::= { chrComHWEquipmentEntry  17 }

chrComHWLastTestingDate 	OBJECT-TYPE
	SYNTAX		DisplayString	(SIZE (0..10))
	MAX-ACCESS 	read-only
	STATUS 		current
	DESCRIPTION
	"The date the card was tested. That might be different than the manufacturing date for cards returning back for testing, upgrading and calibrating."
	::= { chrComHWEquipmentEntry  18 }

chrComHWTemperature 	OBJECT-TYPE
	SYNTAX		Integer32	(-40..85)
	MAX-ACCESS 	read-only
	STATUS 		current
	DESCRIPTION
	"The temperature of the module."
	::= { chrComHWEquipmentEntry  19 }

chrComHWFirmwareVersion 	OBJECT-TYPE
	SYNTAX		DisplayString	(SIZE (0..9))
	MAX-ACCESS 	read-only
	STATUS 		current
	DESCRIPTION
	"The version of the firmware programmed in the EPLD."
	::= { chrComHWEquipmentEntry  20 }

chrComHWCardBootVersion 	OBJECT-TYPE
	SYNTAX		DisplayString	(SIZE (0..9))
	MAX-ACCESS 	read-only
	STATUS 		current
	DESCRIPTION
	"The current boot version."
	::= { chrComHWEquipmentEntry  21 }

chrComHWCardSwVersion 	OBJECT-TYPE
	SYNTAX		DisplayString	(SIZE (0..9))
	MAX-ACCESS 	read-only
	STATUS 		current
	DESCRIPTION
	"The current running card version."
	::= { chrComHWEquipmentEntry  22 }

chrComHWMaxATMoverSonetTPs 	OBJECT-TYPE
	SYNTAX		Unsigned32	(0..4294967295)
	MAX-ACCESS 	read-only
	STATUS 		current
	DESCRIPTION
	"TADM limits the number of paths which might be handled by its Data Engine sub component. Up to 16 paths per TADM."
	::= { chrComHWEquipmentEntry  23 }

chrComHWSlotAlarmVector 	OBJECT-TYPE
	SYNTAX		Unsigned32	(0..4294967295)
	MAX-ACCESS 	read-only
	STATUS 		current
	DESCRIPTION
	""
	::= { chrComHWEquipmentEntry  24 }

chrComHWAlarmSeverProfileIndex 	OBJECT-TYPE
	SYNTAX		Unsigned32	(0..4294967295)
	MAX-ACCESS 	read-write
	STATUS 		current
	DESCRIPTION
	"For release 2.0 the user may select between the default profile and profile #0 (all alarms are not reported)"
	::= { chrComHWEquipmentEntry  25 }

chrComHWCardResetOperation 	OBJECT-TYPE
	SYNTAX		CardResetOp
	MAX-ACCESS 	read-write
	STATUS 		current
	DESCRIPTION
	"Initialize the card and download SW."
	::= { chrComHWEquipmentEntry  26 }


END
