-- ################################################################################

EXTREME-HCLAG-MIB DEFINITIONS ::= BEGIN

        IMPORTS
                MODULE-IDENTITY         FROM SNMPv2-SMI
                OBJECT-TYPE             FROM SNMPv2-SMI
                Unsigned32              FROM SNMPv2-SMI
                TEXTUAL-CONVENTION      FROM SNMPv2-TC
                TruthValue              FROM SNMPv2-TC
                RowStatus               FROM SNMPv2-TC
                DisplayString           FROM RFC1213-MIB
                extremeAgent            FROM EXTREME-BASE-MIB;

    extremeHclag MODULE-IDENTITY
        LAST-UPDATED "1212061000Z"
        ORGANIZATION "Extreme Networks, Inc."
        CONTACT-INFO "www.extremenetworks.com"
        DESCRIPTION "Ethernet Health Check Link-Aggregation"  
        ::= { extremeAgent 38 }

    HclagGroupId
    ::= TEXTUAL-CONVENTION
        STATUS      current
        DESCRIPTION "This represents the Health Check LAG group id."
        SYNTAX      DisplayString (SIZE(1..32))

    HclagMemberPort
    ::= TEXTUAL-CONVENTION
        STATUS      current
        DESCRIPTION "This represents a Health Check LAG's member-port."
        SYNTAX      Unsigned32 (0..4294967295)

    extremeHclagTable OBJECT-TYPE
	SYNTAX SEQUENCE OF ExtremeHclagEntry
	MAX-ACCESS not-accessible
        STATUS current
        DESCRIPTION
                "This table contains HCLAG information about all Health
                 Check LAGs on this device."
	::= { extremeHclag 1 }

    extremeHclagEntry OBJECT-TYPE
        SYNTAX ExtremeHclagEntry
        MAX-ACCESS not-accessible
        STATUS current
        DESCRIPTION
                "An individual entry of this table contains 
                 information related to that Health Check LAG."
        INDEX { extremeHclagGroup,
                extremeHclagMemberPort }
        ::= { extremeHclagTable 1 }

    ExtremeHclagEntry ::= SEQUENCE {
        extremeHclagGroup                HclagGroupId,
        extremeHclagMemberPort           HclagMemberPort,
        extremeHclagAdminState           TruthValue,
	extremeHclagLinkState            TruthValue,
	extremeHclagStatus               TruthValue
    }

    extremeHclagGroup  OBJECT-TYPE
        SYNTAX       HclagGroupId
        MAX-ACCESS   read-only
        STATUS       current
        DESCRIPTION  "This represents the LAG (Link Aggregation Group's) 
                      identifier."
        ::= { extremeHclagEntry 1 }

    extremeHclagMemberPort  OBJECT-TYPE
        SYNTAX       HclagMemberPort
        MAX-ACCESS   read-only
        STATUS       current
        DESCRIPTION
               "This represents a member port within the LAG."
        ::= { extremeHclagEntry 2 }

    extremeHclagAdminState  OBJECT-TYPE
        SYNTAX       TruthValue
        MAX-ACCESS   read-only
        STATUS       current
        DESCRIPTION
               "This represents if the member port has been enabled for
                health checking"
        ::= { extremeHclagEntry 3 }


    extremeHclagLinkState  OBJECT-TYPE
        SYNTAX       TruthValue
        MAX-ACCESS   read-only
        STATUS       current
        DESCRIPTION
               "This represents state of member ports physical link."
        ::= { extremeHclagEntry 4 }

    extremeHclagStatus  OBJECT-TYPE
        SYNTAX       TruthValue
        MAX-ACCESS   read-only
        STATUS       current
        DESCRIPTION
               "This represents if the member port has been added to the
                aggregator or not."
        ::= { extremeHclagEntry 5 }
END
