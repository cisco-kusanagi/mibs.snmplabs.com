Bellcore           Intercarrier SMDS MIB           June 1994


                         Definitions of Managed Objects
                             for Intercarrier SMDS

                                   SNMPv1 MIB
                           bellcore-smdsxaomv1-00.txt
                                   June 1994
                                  Version 1.0

                            Shannon Hansen (editor)
                          Bell Communications Research
                            331 Newman Springs Road
                              Red Bank, NJ  07701

                            shannon@cc.bellcore.com




          1.  Status of this Memo

          This document is a draft private extension to the SNMP MIB.
          Distribution of this memo is unlimited.  Please send
          comments to the editor.

          2.  Abstract

          This memo defines a private extension to the Management
          Information Base (MIB) for use with network management
          protocols in TCP/IP-based internets.  In particular, it
          defines objects that Local Exchange Carriers (LECs) and
          Interexchange Carriers (ICs) can use to manage intercarrier
          SMDS (i.e., when multiple carriers are involved in providing
          SMDS to end-users).

          This memo does not specify a standard for the Internet
          community.














          S. Hansen (editor)                                  [Page 1]





          Bellcore           Intercarrier SMDS MIB           June 1994


          3.  The Network Management Framework

          The Internet-standard Network Management Framework consists
          of three components.  They are:

                RFC 1155 [1] which defines the SMI, the mechanisms used for
                describing and naming objects for the purpose of management.
                RFC 1212 [2] defines a more concise description mechanism,
                which is wholly consistent with the SMI.

                RFC 1156 [3] which defines MIB-I, the core set of managed
                objects for the Internet suite of protocols.  RFC 1213 [4],
                defines MIB-II, an evolution of MIB-I based on
                implementation experience and new operational requirements.

                RFC 1157 [5] which defines the SNMP, the protocol used
                for network access to managed objects.

          The Framework permits new objects to be defined for the purpose
          of experimentation and evaluation.






























          S. Hansen (editor)                                  [Page 2]





          Bellcore           Intercarrier SMDS MIB           June 1994


          4.  Objects

          Managed objects are accessed via a virtual information
          store, termed the Management Information Base or MIB.
          Objects in the MIB are defined using the subset of Abstract
          Syntax Notation One (ASN.1) [6] defined in the SMI.  In
          particular, each object has a name, a syntax, and an
          encoding.  The name is an object identifier, an
          administratively assigned name, which specifies an object
          type.  The object type together with an object instance
          serves to uniquely identify a specific instantiation of the
          object.  For human convenience, we often use a textual
          string, termed the OBJECT DESCRIPTOR, to also refer to the
          object type.

          The syntax of an object type defines the abstract data
          structure corresponding to that object type.  The ASN.1
          language is used for this purpose.  However, the SMI [1]
          purposely restricts the ASN.1 constructs which may be used.
          These restrictions are explicitly made for simplicity.

          The encoding of an object type is simply how that object
          type is represented using the object type's syntax.
          Implicitly tied to the notion of an object type's syntax and
          encoding is how the object type is represented when being
          transmitted on the network.  The SMI specifies the use of
          the basic encoding rules of ASN.1 [7], subject to the
          additional requirements imposed by the SNMP.

          4.1.  Format of Definitions

          Section 6 contains the specification of all object types
          contained in this MIB module.  The object types are defined
          using the conventions defined in the SMI, as amended by the
          extensions specified in RFC1212 [2].















          S. Hansen (editor)                                  [Page 3]





          Bellcore           Intercarrier SMDS MIB           June 1994


          5.  Overview

          This section provides an overview and background
          of how to use this MIB module and other potential MIB modules
          when managing intercarrier SMDS.  Intercarrier SMDS
          refers to two or more carriers involved in providing
          an end-to-end SMDS service [8].

          The following diagram shows the MIB stack that
          could be followed for managing intercarrier SMDS.  This is only
          an example and not meant to be inclusive.

               +----------------------------------------------------------+
               +  MIB  |  Intercarrier SMDS  |  SMDS Subscription |   T   +
               +   II  |---------------------|--------------------|   C   +
               +       |         DS3         |                    |   A   +
               +----------------------------------------------------------+

          SCOPE OF MIB MODULE:

          The intercarrier SMDS MIB module will only manage the SMDS
          portion of the network related to carrier interconnections.
          SMDS Exchange Access Operations Management (XA-OM) and
          Exchange Carrier Operations Management (ECOM) also rely on
          the SMDS Subscription MIB module [9], the DS3 MIB module
          [10], and TCA MIB module [11].

          This MIB module will NOT be implemented on User Equipment.

          The SMDS SNMP MIB module for XA-OM and ECOM is an SNMPv1
          MIB.  It provides read-only information that allows an IC or
          neighboring LEC to obtain performance monitoring, fault, and
          configuration information about: 1) the ICIs that
          interconnect its network with a LEC's network to provide
          intercarrier SMDS and 2) information pertaining to the
          overall management of the end-to-end SMDS service.  By using
          this and other related MIB modules, a carrier's (i.e., IC's
          or neighboring LEC's) NM application can monitor ICIs and
          service aspects of intercarrier SMDS. Internal aspects of
          the network (e.g., switching elements, line cards, and
          network routing tables) are outside the scope of this MIB
          module.  The carrier's NM application will be able to access
          the SNMP proxy-agent within a LEC's SMDS network using SNMP
          over UDP over IP with IP encapsulated in SMDS according to
          RFC1209 [12].  The initial implementation of the MIB module





          S. Hansen (editor)                                  [Page 4]





          Bellcore           Intercarrier SMDS MIB           June 1994


          is based on SNMPv1.  The service capabilities include
          retrieving information and receiving TRAPs.  This MIB module
          will make use of MIB II whenever possible.  Since this MIB
          module will only manage the SMDS portion of the network, the
          scope of this MIB module does not include managed objects
          that: 1) monitor the physical layer, 2) support Threshold
          Crossing Alerts specified for SMDS XA-OM and ECOM, and 3)
          associate an SMDS individual address with a Subscriber-
          Network Interface (SNI).  These objects have already been
          defined in the DS3, TCA, and SMDS Subscription MIB modules.


          5.1.  Apply MIB II to Intercarrier SMDS

          Use the System Group to apply to the SNMP proxy-agent, since
          the proxy-agent may be monitoring many SMDS devices in one
          network.  System Group applies to only one system.  This
          group is not instantiated.

          sysDescr:  ASCII string describing the SNMP proxy-agent.
                     Can be up to 255 characters long. This field is
                     generally used to indicate the network providers
                     identification and type of service offered.

          sysObjectID:  Unique Object Identifier (OID) for
                        the SNMP proxy-agent.

          sysUpTime:  Clock in the SNMP proxy-agent; TimeTicks
                      in 1/100s of a second.  Elapsed type since
                      the proxy-agent came on line.

          sysContact:  Contact for the SNMP proxy-agent.
                       ASCII string of up to 255 characters.

          sysName:  Domain name of the SNMP proxy-agent, for example,
                    acme.com

          sysLocation:  Location of the SNMP proxy-agent.
                        ASCII string of up to 255 characters.

          sysServices:  Services of the managed device.  The value "2"
                        which implies that the SMDS network is providing
                        a subnetwork level service is recommended.

          This memo specifies how the Interfaces General Group





          S. Hansen (editor)                                  [Page 5]





          Bellcore           Intercarrier SMDS MIB           June 1994


          (ifGeneralGroup) defined in MIB II shall be used for the
          management of intercarrier SMDS based interfaces.  This memo
          assumes the interpretation of the ' interfaces' group to be
          in accordance with [13]: "... the 'interfaces' group which
          defines a generic set of managed objects such that any
          network interface can be managed in an interface-independent
          manner through these objects."  Thus, the 'interfaces' group
          allows the following intercarrier SMDS-based interfaces to
          be represented as table entries:

               SMDS interfaces in the SMDS equipment (e.g., switches,
               routers, or networks) -  This information is
               predominantly related to the ICI; however, there are
               several Subscriber-Network Interface (SNI) related
               objects.

          Except for the DS3 MIB module, any counts related to the ICI
          or SNI for SMDS XA-OM and ECOM are specified in this MIB
          module.  To interrelate the ifEntries properly, the
          Interfaces Stack Group defined in [13] shall be supported.

          Carriers should be able to access the
          following objects in the ifGeneralGroup when they
          apply to SNI sublayers:
                  - ifIndex,
                  - ifDescr,
                  - ifType, and
                  - ifOperStatus.

          The manner in which these objects are supported for the SNI
          sublayers  is described in the SMDS Interface Protocol (SIP) MIB
          module [14] and Bellcore Technical Reference
          TR-TSV-001062 [15].

          The following figure illustrates how the ICI has been modeled
          using 2 sublayers:
                              +------------+
                              |    ICIP    |
                              +------------+
                              |     DS3    |
                              +------------+

          The ICIP sublayer consists of ICIP Level 3, Level 2, and
          Physical Layer Convergence Procedure (PLCP).






          S. Hansen (editor)                                  [Page 6]





          Bellcore           Intercarrier SMDS MIB           June 1994


          Some specific interpretations of ifGeneralGroup for intercarrier
          SMDS follow.

           Object                  Use for Each Sublayer of the ICI
           ======                  ================================
           ifIndex                 Each sublayer of the ICI has an ifIndex.

           ifDescr                 ASCII string describing the ICI sublayers.
                                   Can be up to 255 characters long.

           ifType                  The value to be allocated for ICIP sublayer is
                                   "52" (smdsIcip).  The value to be allocated
                                   for the DS3 sublayer of the ICI is "30"
                                   (i.e., DS3).

           ifSpeed                 Peak bandwidth in bits per second available
                                   for use by the ICI sublayer.  The value of
                                   this object is 34 Mbps for the ICIP
                                   sublayer and 45 Mbps for the DS3
                                   sublayer.

           ifPhysAddress           A zero-length string is used for
                                   the ICIP sublayer.  For the DS3 sublayer,
                                   the value of this object is the DS3
                                   circuit identifier.

           ifAdminStatus           Supports read-only access.  The value of this
                                   object for both ICI sublayers is the desired
                                   administrative status of the DS3 sublayer.

           ifOperStatus            The value of this object for both ICI
                                   sublayers is the current operational status
                                   of the DS3 sublayer.

           ifLastChange            The value of this object for both ICI
                                   sublayers is the elapsed time since the last
                                   re-initialization of the DS3
                                   sublayer.

           ifLinkUpDownTrapEnable  This object should be set to enabled
                                   (1) for DS3 sublayer and disabled (2) for
                                   the ICIP sublayer.

           ifConnectorPresent      This object should be set to true (1) for
                                   the DS3 sublayer and false (2) for the ICIP





          S. Hansen (editor)                                  [Page 7]





          Bellcore           Intercarrier SMDS MIB           June 1994


                                   sublayer.

           ifHighSpeed             An estimate of the current bandwidth available
                                   for use by both ICI sublayers (e.g., 34 Mbps
                                   for the ICIP sublayer).

           ifName                  This object should be set to a zero length
                                   string for both ICI sublayers.


          If an object in the ifGeneralGroup is not supported, the
          SNMP proxy agent should return the value "noSuchName"
          following SNMPv1 procedures.


          5.2.  Apply the SMDS Subscription MIB Module to Intercarrier
          SMDS

          SMDS XA-OM and ECOM makes use of one group from the
          SMDS Subscription MIB Module: SMDS Address Table Group.
          Access to this group will enable a carrier to associate an
          SMDS address with an ifIndex [9].  As such, the SMDS Address
          Table Group is mandatory.


          5.3.  Apply the TCA MIB Module to Intercarrier SMDS

          The TCA MIB module should be used for the Threshold Crossing Alerts
          specified for SMDS XA-OM and ECOM [11].  This MIB module
          contains objects associated with TCAs.  By accessing objects in
          this MIB module, carriers can determine when the last threshold
          crossing associated with a given count occurred, the number of
          times a given threshold has been crossed since the agent was
          initialized, and whether a threshold crossing results in a trap
          message.  This MIB module is mandatory.



          5.4.  Apply the DS3 MIB Module to Intercarrier SMDS

          The DS3/E3 MIB (RFC1407) should be used to manage DS3
          sublayer of an SMDS ICI [10].  The ifIndex value from the
          ifGeneralGroup should be used to identify the DS3 sublayer for a
          given ICI.  For an SMDS ICI:
             ifIndex = dsx3LineIndex = dsx3IfIndex.





          S. Hansen (editor)                                  [Page 8]





          Bellcore           Intercarrier SMDS MIB           June 1994


          Mandatory groups for this MIB module are:
             dsx3ConfigTable,
             dsx3CurrentTable, and
             dsx3IntervalTable.

          Note that for the IntervalTable, only eight intervals are supported
          for SMDS XA-OM and ECOM.











































          S. Hansen (editor)                                  [Page 9]





          Bellcore           Intercarrier SMDS MIB           June 1994


          6.  Object Definitions

          Intercarrier-SMDS-MIB DEFINITIONS ::= BEGIN
          IMPORTS
                 enterprises, Gauge
                          FROM RFC1155-SMI
                  DisplayString
                          FROM RFC1213-MIB
                  OBJECT-TYPE
                          FROM RFC-1212;

          --  This MIB module uses the extended OBJECT-TYPE macro as
          --  defined in RFC 1212.

                bellcore              OBJECT IDENTIFIER ::= { enterprises 148 }
                requirements          OBJECT IDENTIFIER ::= { bellcore 1 }
                taTsv001237           OBJECT IDENTIFIER ::= { requirements 4 }
                smdsIomServMIB        OBJECT IDENTIFIER ::= { taTsv001237 1 }
                smdsIomServObjects    OBJECT IDENTIFIER ::= { smdsIomServMIB 1 }

          -- In addition to the imports, two object types have been
          -- defined for this MIB module:
          -- SMDSAddress and CCode.

                SMDSAddress ::= OCTET STRING (SIZE(8))

          -- This object type reflects an SMDS address
          -- associated with an SNI.

                CCode ::= INTEGER (1..9999)

          -- This object type reflects a 4 decimal digit code
          -- associated with an IC or LEC.

















          S. Hansen (editor)                                 [Page 10]





          Bellcore           Intercarrier SMDS MIB           June 1994


          -- The XA-SMDS Subscription Profile Group

          -- Implementation of this group is mandatory for all systems
          -- that perform Intercarrier SMDS.

          -- This group has one table:
          --   Aggregated Access Classes.


          -- Aggregated Access Classes Table

          smdsIomAggAccClTable OBJECT-TYPE
              SYNTAX  SEQUENCE OF SmdsIomAggAccClEntry
              ACCESS  not-accessible
              STATUS  mandatory
              DESCRIPTION
                      "The Aggregated Access Class Table"
              ::= { smdsIomServObjects 1 }

          smdsIomAggAccClEntry OBJECT-TYPE
              SYNTAX  SmdsIomAggAccClEntry
              ACCESS  not-accessible
              STATUS  mandatory
              DESCRIPTION
                      "An entry in the Aggregated Access Class Table"
              INDEX   { smdsIomAggAccClIcIndex }
              ::= { smdsIomAggAccClTable 1 }

          SmdsIomAggAccClEntry ::=
              SEQUENCE {
                  smdsIomAggAccClIcIndex
                     CCode,
                  smdsIomAggAccClValue
                      INTEGER
              }

          smdsIomAggAccClIcIndex OBJECT-TYPE
              SYNTAX  CCode
              ACCESS  read-only
              STATUS  mandatory
              DESCRIPTION
                      "The IC's SMDS CIC"
              ::= { smdsIomAggAccClEntry 1 }







          S. Hansen (editor)                                 [Page 11]





          Bellcore           Intercarrier SMDS MIB           June 1994


          smdsIomAggAccClValue OBJECT-TYPE
              SYNTAX  INTEGER (1..65535)
              ACCESS  read-only
              STATUS  mandatory
              DESCRIPTION
                      "The value of this object reflects the
                      aggregated access classes in Megabits per second
                      of the end-users who have preselected an IC."
              ::= { smdsIomAggAccClEntry 2 }









































          S. Hansen (editor)                                 [Page 12]





          Bellcore           Intercarrier SMDS MIB           June 1994


          -- The Intercarrier SMDS-Related Information Group

          -- Implementation of this group is mandatory for all systems
          -- that perform Intercarrier SMDS.

          -- This group consists of 5 tables:
          --     LEC Network Addresses,
          --     ICI Configuration,
          --     Nested Group Address (NGA),
          --     SNI-Related Current Information, and
          --     SNI-Related Interval Information.


          -- LEC Network Addresses Table
          -- This table lists up to the first six digits following
          -- the country code
          -- of addresses served by the LEC's network.
          -- Note that this table has been designed to support
          -- both North American and European addressing.

          smdsIomLecNetAddrTable OBJECT-TYPE
              SYNTAX  SEQUENCE OF SmdsIomLecNetAddrEntry
              ACCESS  not-accessible
              STATUS  mandatory
              DESCRIPTION
                      "This table lists network addresses, their
                      address types (whether or not the address is an
                      Embodied SAC) and the SMDS addresses of the test
                      SNIs associated with the network addresses."
              ::= { smdsIomServObjects 2 }

          smdsIomLecNetAddrEntry OBJECT-TYPE
              SYNTAX  SmdsIomLecNetAddrEntry
              ACCESS  not-accessible
              STATUS  mandatory
              DESCRIPTION
                      "An entry in the LEC Network Address Table"
              INDEX   { smdsIomLecNetAddrIndex }
              ::= { smdsIomLecNetAddrTable 1 }











          S. Hansen (editor)                                 [Page 13]





          Bellcore           Intercarrier SMDS MIB           June 1994


          SmdsIomLecNetAddrEntry ::=
              SEQUENCE {
                smdsIomLecNetAddrIndex
                      INTEGER,
                smdsIomLecNetAddrDigits
                      INTEGER,
                smdsIomLecNetAddrAddrType
                      INTEGER,
                smdsIomLecNetAddrTestSNI
                      SMDSAddress
                }

          smdsIomLecNetAddrIndex OBJECT-TYPE
              SYNTAX  INTEGER (1..65535)
              ACCESS  read-only
              STATUS  mandatory
              DESCRIPTION
                      "This object is used to index
                      smdsIomLecNetAddrTable."
              ::= { smdsIomLecNetAddrEntry 1 }

          smdsIomLecNetAddrDigits OBJECT-TYPE
              SYNTAX INTEGER (1..999999)
              ACCESS  read-only
              STATUS  mandatory
              DESCRIPTION
                      "The value of this object reflects up to the
                      first six digits following the country code of
                      an SMDS Address served by the LEC's network."
              ::= { smdsIomLecNetAddrEntry 2 }

          smdsIomLecNetAddrAddrType OBJECT-TYPE
              SYNTAX  INTEGER {
                network(1),
                embodiedsac(2)
                }
              ACCESS  read-only
              STATUS  mandatory
              DESCRIPTION
                      "The value of this object indicates the type of
                      address reflected in smdsIomLecNetAddrDigits."
               ::= { smdsIomLecNetAddrEntry 3 }








          S. Hansen (editor)                                 [Page 14]





          Bellcore           Intercarrier SMDS MIB           June 1994


           smdsIomLecNetAddrTestSNI OBJECT-TYPE
              SYNTAX SMDSAddress
              ACCESS  read-only
              STATUS  mandatory
              DESCRIPTION
                      "The value of this object reflects an SMDS
                      Address assigned to the Test SNI that is
                      associated with smdsIomLecNetAddrDigits."
               ::= { smdsIomLecNetAddrEntry 4 }



          -- ICI Configuration Table
          -- This table provides ICI configuration information

          smdsIomIciConfigTable OBJECT-TYPE
              SYNTAX  SEQUENCE OF SmdsIomIciConfigEntry
              ACCESS  not-accessible
              STATUS  mandatory
              DESCRIPTION
                      "This table lists the ICI Transmission Path
                      Identifier, the ICI ifIndex, Location, and
                      MCDUs."
              ::= { smdsIomServObjects 3 }

          smdsIomIciConfigEntry OBJECT-TYPE
              SYNTAX  SmdsIomIciConfigEntry
              ACCESS  not-accessible
              STATUS  mandatory
              DESCRIPTION
                      "An entry in the ICI Configuration Information
                      Table"
              INDEX   { smdsIomIciConfigIciTransPathIdIndex }
              ::= { smdsIomIciConfigTable 1 }

          SmdsIomIciConfigEntry ::=
              SEQUENCE {
                smdsIomIciConfigIciTransPathIdIndex
                      DisplayString,
                smdsIomIciConfigIfIndex
                      INTEGER,
                 smdsIomIciConfigIciLocation
                      DisplayString,
                smdsIomIciConfigIciMcdus
                      INTEGER





          S. Hansen (editor)                                 [Page 15]





          Bellcore           Intercarrier SMDS MIB           June 1994


            }

          smdsIomIciConfigIciTransPathIdIndex OBJECT-TYPE
              SYNTAX DisplayString (SIZE (1..255) )
              ACCESS  read-only
              STATUS  mandatory
              DESCRIPTION
                      "The value of this object reflects an identifier
                      assigned to an ICI as part of the provisioning
                      process."
              ::= { smdsIomIciConfigEntry 1 }

          smdsIomIciConfigIfIndex OBJECT-TYPE
              SYNTAX  INTEGER (1..65535)
              ACCESS  read-only
              STATUS  mandatory
              DESCRIPTION
                      "The value of this object identifies the ifIndex
                      associated with the ICIP sublayer of the ICI."
              ::= { smdsIomIciConfigEntry 2 }

          smdsIomIciConfigIciLocation OBJECT-TYPE
              SYNTAX  DisplayString
              ACCESS  read-only
              STATUS  mandatory
              DESCRIPTION
                      "The value of this object indicates the location
                      of the LEC SS at which the ICI is terminated."
             ::= { smdsIomIciConfigEntry 3 }

           smdsIomIciConfigIciMcdus OBJECT-TYPE
              SYNTAX INTEGER{
                mcdus128(1),
                mcdus511(2)
                }
                ACCESS  read-only
                STATUS  mandatory
              DESCRIPTION
                      "The value of this object reflects the maximum
                      data units in transit concurrently.  For Phase 1
                      Exchange Access SMDS, the two acceptable values
                      are: 128 and 511."
              ::= { smdsIomIciConfigEntry 4 }







          S. Hansen (editor)                                 [Page 16]





          Bellcore           Intercarrier SMDS MIB           June 1994


          -- NGA Table
          -- This table provides all the individual addresses that
          -- are members of a particular Nested Group Address (NGA).

          smdsIomNgaTable OBJECT-TYPE
              SYNTAX  SEQUENCE OF SmdsIomNgaEntry
              ACCESS  not-accessible
              STATUS  mandatory
              DESCRIPTION
                      "This table lists the individual addresses that
                      are members of a particular NGA."
              ::= { smdsIomServObjects 4 }

          smdsIomNgaEntry OBJECT-TYPE
              SYNTAX  SmdsIomNgaEntry
              ACCESS  not-accessible
              STATUS  mandatory
              DESCRIPTION
                      "An entry in the NGA Table"
              INDEX   { smdsIomNgaCountryCodeIndex,
                        smdsIomNgaDestinCodeIndex,
                        smdsIomNgaSubscriberNoIndex,
                        smdsIomNgaMemberCountryCodeIndex,
                        smdsIomNgaMemberDestinCodeIndex,
                        smdsIomNgaMemberSubscriberNoIndex }
              ::= { smdsIomNgaTable 1 }

          SmdsIomNgaEntry ::=
              SEQUENCE {
                smdsIomNgaCountryCodeIndex
                      INTEGER,
                smdsIomNgaDestinCodeIndex
                      INTEGER,
                smdsIomNgaSubscriberNoIndex
                      INTEGER,
                smdsIomNgaMemberCountryCodeIndex
                      INTEGER,
                smdsIomNgaMemberDestinCodeIndex
                      INTEGER,
                smdsIomNgaMemberSubscriberNoIndex
                      INTEGER,
                smdsIomNgaAddress
                      SMDSAddress,
                smdsIomNgaMember
                      SMDSAddress





          S. Hansen (editor)                                 [Page 17]





          Bellcore           Intercarrier SMDS MIB           June 1994


            }

          smdsIomNgaCountryCodeIndex OBJECT-TYPE
              SYNTAX INTEGER (1..999)
              ACCESS  read-only
              STATUS  mandatory
              DESCRIPTION
                      "The value of this object identifies the country
                      code portion of the NGA."
              ::= { smdsIomNgaEntry 1 }

          smdsIomNgaDestinCodeIndex  OBJECT-TYPE
              SYNTAX INTEGER (1..999999999)
              ACCESS  read-only
              STATUS  mandatory
              DESCRIPTION
                      "This object reflects the destination code
                      portion of the NGA.  For North America, the
                      destination code is the first three digits
                      following the country code."
              ::= {  smdsIomNgaEntry 2 }

           smdsIomNgaSubscriberNoIndex OBJECT-TYPE
              SYNTAX INTEGER (1..999999999)
              ACCESS  read-only
              STATUS  mandatory
              DESCRIPTION
                      "This object reflects the subscriber number
                      portion of the NGA. For North America, the
                      subscriber number is the last seven digits of
                      the SMDS address of the NGA."
             ::= { smdsIomNgaEntry 3 }

          smdsIomNgaMemberCountryCodeIndex OBJECT-TYPE
              SYNTAX INTEGER (1..999)
              ACCESS  read-only
              STATUS  mandatory
              DESCRIPTION
                      "The value of this object identifies the country
                      code portion of an individual address that is a
                      member of the NGA."
              ::= { smdsIomNgaEntry 4 }








          S. Hansen (editor)                                 [Page 18]





          Bellcore           Intercarrier SMDS MIB           June 1994


          smdsIomNgaMemberDestinCodeIndex OBJECT-TYPE
              SYNTAX INTEGER (1..999999999)
              ACCESS  read-only
              STATUS  mandatory
              DESCRIPTION
                      "This object reflects the destination code
                      portion of an individual address that is a
                      member of the NGA."
              ::= { smdsIomNgaEntry 5 }

          smdsIomNgaMemberSubscriberNoIndex OBJECT-TYPE
              SYNTAX INTEGER (1..999999999)
              ACCESS  read-only
              STATUS  mandatory
              DESCRIPTION
                      "This object reflects the subscriber number
                      portion of an individual address that is a
                      member of the NGA."
              ::= { smdsIomNgaEntry 6 }

          smdsIomNgaAddress OBJECT-TYPE
              SYNTAX SMDSAddress
              ACCESS  read-only
              STATUS  mandatory
              DESCRIPTION
                      "The value of this object identifies the NGA."
              ::= { smdsIomNgaEntry 7 }

          smdsIomNgaMember OBJECT-TYPE
              SYNTAX SMDSAddress
              ACCESS  read-only
              STATUS  mandatory
              DESCRIPTION
                      "The value of this object identifies an
                      individual address that is a member of the NGA."
              ::= {   smdsIomNgaEntry 8 }














          S. Hansen (editor)                                 [Page 19]





          Bellcore           Intercarrier SMDS MIB           June 1994


          -- SNI-Related Current Information Table
          -- This table provides current SNI-related information such as:
          -- address screening violations, SIP L3_PDU error ratio,
          -- and discards due to service disagreements.

           smdsIomSniCurrentInfoTable OBJECT-TYPE
              SYNTAX  SEQUENCE OF SmdsIomSniCurrentInfoEntry
              ACCESS  not-accessible
              STATUS  mandatory
              DESCRIPTION
                      "This table provides current SNI-related
                      information."
              ::= { smdsIomServObjects 5 }

           smdsIomSniCurrentInfoEntry OBJECT-TYPE
              SYNTAX   SmdsIomSniCurrentInfoEntry
              ACCESS  not-accessible
              STATUS  mandatory
              DESCRIPTION
                      "An entry in the SNI-Related Current Information
                      Table"
              INDEX   {  smdsIomSniCurrentInfoIfIndex }
              ::= {  smdsIomSniCurrentInfoTable 1 }

           SmdsIomSniCurrentInfoEntry ::=
              SEQUENCE {
                smdsIomSniCurrentInfoIfIndex
                      INTEGER,
                smdsIomSniCurrentInfoSourceAddrScreenViolations
                      Gauge,
                smdsIomSniCurrentInfoDestinAddrScreenViolations
                      Gauge,
                smdsIomSniCurrentInfoSipErrorRatio
                       INTEGER,
                smdsIomSniCurrentInfoServDisagreeDiscards
                      Gauge
                }

          smdsIomSniCurrentInfoIfIndex OBJECT-TYPE
              SYNTAX INTEGER (0..65535)
              ACCESS  read-only
              STATUS  mandatory
              DESCRIPTION
                      "The value of this object identifies the ifIndex
                      associated with the appropriate SNI sublayer.





          S. Hansen (editor)                                 [Page 20]





          Bellcore           Intercarrier SMDS MIB           June 1994


                      For more information, refer to TR-TSV-001062."
              ::= { smdsIomSniCurrentInfoEntry 1 }

          smdsIomSniCurrentInfoSourceAddrScreenViolations  OBJECT-TYPE
              SYNTAX Gauge
              ACCESS  read-only
              STATUS  mandatory
              DESCRIPTION
                      "The value of this object reflects the number of
                      SIP L3_PDUs discarded because the source address
                      violated the address screening."
              ::= { smdsIomSniCurrentInfoEntry 2 }

          smdsIomSniCurrentInfoDestinAddrScreenViolations  OBJECT-TYPE
              SYNTAX Gauge
              ACCESS  read-only
              STATUS  mandatory
              DESCRIPTION
                      "The value of this object reflects the number of
                      SIP L3_PDUs discarded because the destination
                      address violated the address screening."
              ::= { smdsIomSniCurrentInfoEntry 3 }

           smdsIomSniCurrentInfoSipErrorRatio  OBJECT-TYPE
              SYNTAX INTEGER (1..65535)
              ACCESS  read-only
              STATUS  mandatory
              DESCRIPTION
                      "The value of this object reflects the result
                      multiplied by a factor of 1000 of the ratio of
                      the number of errored SIP L3_PDUs to the number
                      of total incoming SIP L3_PDUs."
              ::= { smdsIomSniCurrentInfoEntry 4 }

            smdsIomSniCurrentInfoServDisagreeDiscards  OBJECT-TYPE
              SYNTAX Gauge
              ACCESS  read-only
              STATUS  mandatory
              DESCRIPTION
                      " The value of this object reflects the number
                      of SIP L3_PDUs discarded because of service
                      disagreements."
              ::= { smdsIomSniCurrentInfoEntry 5 }







          S. Hansen (editor)                                 [Page 21]





          Bellcore           Intercarrier SMDS MIB           June 1994


          -- SNI-Related Interval Information Table
          -- This table provides SNI-related information for four 15-minute
          -- intervals preceding the current interval.  This table provides
          -- information on the SIP L3_PDU error ratio and
          -- discards due to service disagreements.

           smdsIomSniIntervalInfoTable OBJECT-TYPE
              SYNTAX  SEQUENCE OF SmdsIomSniIntervalInfoEntry
              ACCESS  not-accessible
              STATUS  mandatory
              DESCRIPTION
                      "This table provides SNI-related information
                      from previous intervals."
              ::= { smdsIomServObjects 6 }

           smdsIomSniIntervalInfoEntry OBJECT-TYPE
              SYNTAX   SmdsIomSniIntervalInfoEntry
              ACCESS  not-accessible
              STATUS  mandatory
              DESCRIPTION
                      "An entry in the SNI-Related Interval
                      Information Table"
              INDEX   {  smdsIomSniIntervalInfoIfIndex,
                          smdsIomSniIntervalInfoIntervalIndex }
              ::= {  smdsIomSniIntervalInfoTable 1 }

           SmdsIomSniIntervalInfoEntry ::=
              SEQUENCE {
                smdsIomSniIntervalInfoIfIndex
                      INTEGER,
                smdsIomSniIntervalInfoIntervalIndex
                      INTEGER,
                smdsIomSniIntervalInfoSipErrorRatio
                       INTEGER,
                smdsIomSniIntervalInfoServDisagreeDiscards
                      Gauge
                }

          smdsIomSniIntervalInfoIfIndex OBJECT-TYPE
              SYNTAX INTEGER (0..65535)
              ACCESS  read-only
              STATUS  mandatory
              DESCRIPTION
                      "The value of this object identifies the ifIndex
                      associated with the appropriate SNI sublayer.





          S. Hansen (editor)                                 [Page 22]





          Bellcore           Intercarrier SMDS MIB           June 1994


                      For more information, refer to TR-TSV-001062."
              ::= { smdsIomSniIntervalInfoEntry 1 }

          smdsIomSniIntervalInfoIntervalIndex OBJECT-TYPE
              SYNTAX INTEGER (1..4)
              ACCESS  read-only
              STATUS  mandatory
              DESCRIPTION
                      "The value of this object identifies the
                      interval index associated with the SNI-related
                      information.  An index of '1' is used to
                      indicate the most recent interval and an index
                      '4' is used to indicate the latest interval for
                      which information is maintained."
              ::= { smdsIomSniIntervalInfoEntry 2 }

           smdsIomSniIntervalInfoSipErrorRatio  OBJECT-TYPE
              SYNTAX INTEGER (1..65535)
              ACCESS  read-only
              STATUS  mandatory
              DESCRIPTION
                      "The value of this object reflects the result
                      multiplied by a factor of 1000 of the ratio of
                      the number of errored SIP L3_PDUs to the number
                      of total incoming SIP L3_PDUs."
              ::= { smdsIomSniIntervalInfoEntry 3 }

            smdsIomSniIntervalInfoServDisagreeDiscards  OBJECT-TYPE
              SYNTAX Gauge
              ACCESS  read-only
              STATUS  mandatory
              DESCRIPTION
                      " The value of this object reflects the number
                      of SIP L3_PDUs discarded because of service
                      disagreements."
              ::= { smdsIomSniIntervalInfoEntry 4 }














          S. Hansen (editor)                                 [Page 23]





          Bellcore           Intercarrier SMDS MIB           June 1994


          -- The Inter-Carrier Interface Protocol (ICIP) Level 3 Group


          -- Implementation of this group is mandatory for all systems
          -- that perform intercarrier SMDS.

          -- This group consists of 2 tables:
          --    ICIP Level 3 Current Table, and
          --    ICIP Level 3 Interval Table.
          -- For SMDS XA-OM and ECOM,
          -- counts are collected over 15 minute intervals.

          -- ICIP Level 3 Current Table
          -- This table contains the current interval counts for the
          -- ICIP Level 3 of a given ICI.

          smdsIomIcipL3CurrentTable OBJECT-TYPE
              SYNTAX  SEQUENCE OF SmdsIomIcipL3CurrentEntry
              ACCESS  not-accessible
              STATUS  mandatory
              DESCRIPTION
                      "The ICIP Level 3 Current Table"
              ::= { smdsIomServObjects 7 }

          smdsIomIcipL3CurrentEntry OBJECT-TYPE
              SYNTAX SmdsIomIcipL3CurrentEntry
              ACCESS  not-accessible
              STATUS  mandatory
              DESCRIPTION
                      "An entry in the ICIP Level 3 Current Table"
              INDEX   { smdsIomIcipL3CurrentIfIndex }
              ::= { smdsIomIcipL3CurrentTable 1 }

          SmdsIomIcipL3CurrentEntry ::=
              SEQUENCE {
                smdsIomIcipL3CurrentIfIndex
                      INTEGER,
                smdsIomIcipL3CurrentCSInvalidFieldsDiscards
                      Gauge,
                smdsIomIcipL3CurrentCSIncorrectFieldsDiscards
                      Gauge,
                smdsIomIcipL3CurrentHeaderBEtagDiscards
                      Gauge,
                smdsIomIcipL3CurrentBAsizeDiscards
                      Gauge,





          S. Hansen (editor)                                 [Page 24]





          Bellcore           Intercarrier SMDS MIB           June 1994


                smdsIomIcipL3CurrentLengthFieldDiscards
                      Gauge,
                smdsIomIcipL3CurrentCSSInvalidFieldsDiscards
                      Gauge,
                smdsIomIcipL3CurrentCSSRoutingErrorsDiscards
                      Gauge
              }

            smdsIomIcipL3CurrentIfIndex OBJECT-TYPE
              SYNTAX INTEGER (0..65535)
              ACCESS  read-only
              STATUS  mandatory
              DESCRIPTION
                      "The value of this object identifies the ifIndex
                      associated with the ICIP sublayer of the ICI."
              ::= { smdsIomIcipL3CurrentEntry 1 }

          smdsIomIcipL3CurrentCSInvalidFieldsDiscards  OBJECT-TYPE
              SYNTAX Gauge
              ACCESS  read-only
              STATUS  mandatory
              DESCRIPTION
                      "The value of this object reflects the number of
                      ICIP L3_PDUs discarded because of invalid fields
                      that occurred at the convergence sublayer."
              ::= { smdsIomIcipL3CurrentEntry 2 }

           smdsIomIcipL3CurrentCSIncorrectFieldsDiscards  OBJECT-TYPE
              SYNTAX Gauge
              ACCESS  read-only
              STATUS  mandatory
              DESCRIPTION
                      "The value of this object reflects the number of
                      ICIP L3_PDUs discarded because of incorrect
                      fields that occurred at the convergence
                      sublayer."
              ::= { smdsIomIcipL3CurrentEntry 3 }













          S. Hansen (editor)                                 [Page 25]





          Bellcore           Intercarrier SMDS MIB           June 1994


           smdsIomIcipL3CurrentHeaderBEtagDiscards  OBJECT-TYPE
              SYNTAX Gauge
              ACCESS  read-only
              STATUS  mandatory
              DESCRIPTION
                      "The value of this object reflects the number of
                      ICIP L3_PDUs discarded because of the Header
                      BEtag not equaling the Trailer BEtag."
              ::= { smdsIomIcipL3CurrentEntry 4 }

            smdsIomIcipL3CurrentBAsizeDiscards  OBJECT-TYPE
              SYNTAX Gauge
              ACCESS  read-only
              STATUS  mandatory
              DESCRIPTION
                      " The value of this object reflects the number
                      of ICIP L3_PDUs discarded because of the BAsize
                      not equaling the Length field."
              ::= { smdsIomIcipL3CurrentEntry 5 }

            smdsIomIcipL3CurrentLengthFieldDiscards OBJECT-TYPE
              SYNTAX Gauge
              ACCESS  read-only
              STATUS  mandatory
              DESCRIPTION
                      " The value of this object reflects the number
                      of ICIP L3_PDUs discarded because of the Length
                      field not equaling the number of octets in the
                      portion of the L3_PDU that extends from the
                      Destination Address field up to and including
                      the End-User Data field and Service-Specific
                      Pad."
              ::= { smdsIomIcipL3CurrentEntry  6 }

           smdsIomIcipL3CurrentCSSInvalidFieldsDiscards OBJECT-TYPE
              SYNTAX Gauge
              ACCESS  read-only
              STATUS  mandatory
              DESCRIPTION
                      " The value of this object reflects the number
                      of ICIP L3_PDUs discarded because of invalid
                      fields that occurred at the connectionless
                      service sublayer."
              ::= { smdsIomIcipL3CurrentEntry  7 }






          S. Hansen (editor)                                 [Page 26]





          Bellcore           Intercarrier SMDS MIB           June 1994


           smdsIomIcipL3CurrentCSSRoutingErrorsDiscards OBJECT-TYPE
              SYNTAX Gauge
              ACCESS  read-only
              STATUS  mandatory
              DESCRIPTION
                      " The value of this object reflects the number
                      of ICIP L3_PDUs discarded because of routing
                      errors that occurred at the connectionless
                      service sublayer."
              ::= { smdsIomIcipL3CurrentEntry  8 }


          -- ICIP Level 3 Interval Table
          -- This table contains the performance counts for
          -- the past 8 intervals of ICIP Level 3 of an ICI.
          -- It is possible that less than 8 intervals may be reflected
          -- because the SS or ICI has not been on line for the
          -- entire 2 hours.

          smdsIomIcipL3IntervalTable OBJECT-TYPE
              SYNTAX  SEQUENCE OF SmdsIomIcipL3IntervalEntry
              ACCESS  not-accessible
              STATUS  mandatory
              DESCRIPTION
                      "The ICIP Level 3 Interval Table"
              ::= { smdsIomServObjects 8 }

          smdsIomIcipL3IntervalEntry OBJECT-TYPE
              SYNTAX SmdsIomIcipL3IntervalEntry
              ACCESS  not-accessible
              STATUS  mandatory
              DESCRIPTION
                      "An entry in the ICIP Level 3 Interval Table"
              INDEX   { smdsIomIcipL3IntervalIfIndex,
                        smdsIomIcipL3IntervalIntervalIndex }
              ::= { smdsIomIcipL3IntervalTable 1 }

          SmdsIomIcipL3IntervalEntry ::=
              SEQUENCE {
                smdsIomIcipL3IntervalIfIndex
                      INTEGER,
                smdsIomIcipL3IntervalIntervalIndex
                      INTEGER,
                smdsIomIcipL3IntervalCSInvalidFieldsDiscards
                      Gauge,





          S. Hansen (editor)                                 [Page 27]





          Bellcore           Intercarrier SMDS MIB           June 1994


                smdsIomIcipL3IntervalCSIncorrectFieldsDiscards
                      Gauge,
                smdsIomIcipL3IntervalHeaderBEtagDiscards
                      Gauge,
                smdsIomIcipL3IntervalBAsizeDiscards
                      Gauge,
                smdsIomIcipL3IntervalLengthFieldDiscards
                      Gauge,
                smdsIomIcipL3IntervalCSSInvalidFieldsDiscards
                      Gauge,
                smdsIomIcipL3IntervalCSSRoutingErrorsDiscards
                      Gauge
              }

            smdsIomIcipL3IntervalIfIndex OBJECT-TYPE
              SYNTAX INTEGER (0..65535)
              ACCESS  read-only
              STATUS  mandatory
              DESCRIPTION
                      "The value of this object identifies the ifIndex
                      associated with the ICIP sublayer of the ICI."
              ::= { smdsIomIcipL3IntervalEntry 1 }

            smdsIomIcipL3IntervalIntervalIndex OBJECT-TYPE
              SYNTAX INTEGER (1..8)
              ACCESS  read-only
              STATUS  mandatory
              DESCRIPTION
                      "The value of this object identifies the
                      interval in which the counts occurred.  A value
                      of '1' indicates the most recently completed
                      interval while a value of '8' indicates least
                      recently completed interval."
              ::= { smdsIomIcipL3IntervalEntry 2 }

          smdsIomIcipL3IntervalCSInvalidFieldsDiscards  OBJECT-TYPE
              SYNTAX Gauge
              ACCESS  read-only
              STATUS  mandatory
              DESCRIPTION
                      "The value of this object reflects the number of
                      ICIP L3_PDUs discarded because of invalid fields
                      that occurred at the convergence sublayer."
              ::= { smdsIomIcipL3IntervalEntry 3 }






          S. Hansen (editor)                                 [Page 28]





          Bellcore           Intercarrier SMDS MIB           June 1994


           smdsIomIcipL3IntervalCSIncorrectFieldsDiscards  OBJECT-TYPE
              SYNTAX Gauge
              ACCESS  read-only
              STATUS  mandatory
              DESCRIPTION
                      "The value of this object reflects the number of
                      ICIP L3_PDUs discarded because of incorrect
                      fields that occurred at the convergence
                      sublayer."
              ::= { smdsIomIcipL3IntervalEntry 4 }


           smdsIomIcipL3IntervalHeaderBEtagDiscards  OBJECT-TYPE
              SYNTAX Gauge
              ACCESS  read-only
              STATUS  mandatory
              DESCRIPTION
                      "The value of this object reflects the number of
                      ICIP L3_PDUs discarded because of the Header
                      BEtag not equaling the Trailer BEtag."
              ::= { smdsIomIcipL3IntervalEntry 5 }

            smdsIomIcipL3IntervalBAsizeDiscards  OBJECT-TYPE
              SYNTAX Gauge
              ACCESS  read-only
              STATUS  mandatory
              DESCRIPTION
                      " The value of this object reflects the number
                      of ICIP L3_PDUs discarded because of the BAsize
                      not equaling the Length field."
              ::= { smdsIomIcipL3IntervalEntry  6 }

            smdsIomIcipL3IntervalLengthFieldDiscards OBJECT-TYPE
              SYNTAX Gauge
              ACCESS  read-only
              STATUS  mandatory
              DESCRIPTION
                      " The value of this object reflects the number
                      of ICIP L3_PDUs discarded because of the Length
                      field not equaling the number of octets in the
                      portion of the L3_PDU that extends from the
                      Destination Address field up to and including
                      the End-User Data field and Service-Specific
                      Pad."
              ::= { smdsIomIcipL3IntervalEntry  7 }





          S. Hansen (editor)                                 [Page 29]





          Bellcore           Intercarrier SMDS MIB           June 1994


           smdsIomIcipL3IntervalCSSInvalidFieldsDiscards OBJECT-TYPE
              SYNTAX Gauge
              ACCESS  read-only
              STATUS  mandatory
              DESCRIPTION
                      " The value of this object reflects the number
                      of ICIP L3_PDUs discarded because of invalid
                      fields that occurred at the connectionless
                      service sublayer."
              ::= { smdsIomIcipL3IntervalEntry  8 }

           smdsIomIcipL3IntervalCSSRoutingErrorsDiscards OBJECT-TYPE
              SYNTAX Gauge
              ACCESS  read-only
              STATUS  mandatory
              DESCRIPTION
                      " The value of this object reflects the number
                      of ICIP L3_PDUs discarded because of routing
                      errors that occurred at the connectionless
                      service sublayer."
              ::= { smdsIomIcipL3IntervalEntry  9 }





























          S. Hansen (editor)                                 [Page 30]





          Bellcore           Intercarrier SMDS MIB           June 1994


          -- The Inter-Carrier Interface Protocol (ICIP) Level 2 Group

          -- Implementation of this group is mandatory for all systems
          -- that perform intercarrier SMDS.

          -- This group consists of 2 tables:
          --    ICIP Level 2 Current Table, and
          --    ICIP Level 2 Interval Table.
          -- For SMDS XA-OM and ECOM, counts are
          -- collected over 15 minute intervals.

          -- ICIP Level 2 Current Table
          -- This table contains the current interval performance counts
          -- for the ICIP Level 2 of a given ICI.

          smdsIomIcipL2CurrentTable OBJECT-TYPE
              SYNTAX  SEQUENCE OF SmdsIomIcipL2CurrentEntry
              ACCESS  not-accessible
              STATUS  mandatory
              DESCRIPTION
                      "The ICIP Level 2 Current Count Table"
              ::= { smdsIomServObjects 9 }

          smdsIomIcipL2CurrentEntry OBJECT-TYPE
              SYNTAX SmdsIomIcipL2CurrentEntry
              ACCESS  not-accessible
              STATUS  mandatory
              DESCRIPTION
                      "An entry in the ICIP Level 2 Current Table"
              INDEX   { smdsIomIcipL2CurrentIfIndex }
              ::= { smdsIomIcipL2CurrentTable 1 }

          SmdsIomIcipL2CurrentEntry ::=
              SEQUENCE {
                smdsIomIcipL2CurrentIfIndex
                      INTEGER,
                smdsIomIcipL2CurrentTotalOut
                      Gauge,
                smdsIomIcipL2CurrentCongestionDiscards
                      Gauge,
                smdsIomIcipL2CurrentCellInvalidFieldsDiscards
                      Gauge,
                smdsIomIcipL2CurrentSARInvalidFieldsDiscards
                      Gauge,
                smdsIomIcipL2CurrentSARIncorrectFieldsDiscards





          S. Hansen (editor)                                 [Page 31]





          Bellcore           Intercarrier SMDS MIB           June 1994


                      Gauge,
               smdsIomIcipL2CurrentCRCViolationsDiscards
                      Gauge,
                smdsIomIcipL2CurrentComsEomsDiscards
                      Gauge,
                smdsIomIcipL2CurrentBomsEomsDiscards
                      Gauge,
                smdsIomIcipL2CurrentMRIDiscards
                      Gauge
              }

            smdsIomIcipL2CurrentIfIndex OBJECT-TYPE
              SYNTAX INTEGER (0..65535)
              ACCESS  read-only
              STATUS  mandatory
              DESCRIPTION
                      "The value of this object identifies the ifIndex
                      associated with the ICIP sublayer of the ICI."
              ::= { smdsIomIcipL2CurrentEntry 1 }

           smdsIomIcipL2CurrentTotalOut  OBJECT-TYPE
              SYNTAX Gauge
              ACCESS  read-only
              STATUS  mandatory
              DESCRIPTION
                      "The value of this object reflects the number of
                      ICIP L2_PDUs sent across an ICI."
              ::= { smdsIomIcipL2CurrentEntry 2 }

            smdsIomIcipL2CurrentCongestionDiscards OBJECT-TYPE
              SYNTAX Gauge
              ACCESS  read-only
              STATUS  mandatory
              DESCRIPTION
                      "The value of this object reflects the number of
                      ICIP L2_PDUs discarded because an ICI was in
                      congestion."
              ::= { smdsIomIcipL2CurrentEntry 3 }












          S. Hansen (editor)                                 [Page 32]





          Bellcore           Intercarrier SMDS MIB           June 1994


            smdsIomIcipL2CurrentCellInvalidFieldsDiscards  OBJECT-TYPE
              SYNTAX Gauge
              ACCESS  read-only
              STATUS  mandatory
              DESCRIPTION
                      "The value of this object reflects the number of
                      ICIP L2_PDUs discarded because of invalid fields
                      that occurred at the cell sublayer."
              ::= { smdsIomIcipL2CurrentEntry 4 }

            smdsIomIcipL2CurrentSARInvalidFieldsDiscards  OBJECT-TYPE
              SYNTAX Gauge
              ACCESS  read-only
              STATUS  mandatory
              DESCRIPTION
                      " The value of this object reflects the number
                      of ICIP L2_PDUs discarded because of invalid
                      fields that occurred at the Segmentation and
                      Reassembly (SAR) sublayer."
              ::= { smdsIomIcipL2CurrentEntry  5 }

            smdsIomIcipL2CurrentSARIncorrectFieldsDiscards OBJECT-TYPE
              SYNTAX Gauge
              ACCESS  read-only
              STATUS  mandatory
              DESCRIPTION
                      " The value of this object reflects the number
                      of ICIP L2_PDUs discarded because of incorrect
                      fields that occurred at the SAR sublayer."
              ::= { smdsIomIcipL2CurrentEntry  6 }

             smdsIomIcipL2CurrentCRCViolationsDiscards OBJECT-TYPE
              SYNTAX Gauge
              ACCESS  read-only
              STATUS  mandatory
              DESCRIPTION
                      " The value of this object reflects the number
                      of ICIP L2_PDUs discarded because the payload
                      Cyclic Redundancy Check (CRC) was incorrect."
              ::= { smdsIomIcipL2CurrentEntry  7 }










          S. Hansen (editor)                                 [Page 33]





          Bellcore           Intercarrier SMDS MIB           June 1994


             smdsIomIcipL2CurrentComsEomsDiscards OBJECT-TYPE
              SYNTAX Gauge
              ACCESS  read-only
              STATUS  mandatory
              DESCRIPTION
                      " The value of this object reflects the number
                      of ICIP L2_PDUs discarded because the sequence
                      number of the Continuation of Message (COM) or
                      End of Message (EOM) was not incremented by 1
                      relative to the previous L2_PDU received with
                      the same Message Identifier (MID)."
              ::= {smdsIomIcipL2CurrentEntry  8 }

            smdsIomIcipL2CurrentBomsEomsDiscards OBJECT-TYPE
              SYNTAX Gauge
              ACCESS  read-only
              STATUS  mandatory
              DESCRIPTION
                      " The value of this object reflects the number
                      of ICIP L3_PDUs discarded because the MID of a
                      Beginning of Message (BOM) was currently active
                      or the MID of an EOM was not currently active."
              ::= { smdsIomIcipL2CurrentEntry  9 }

            smdsIomIcipL2CurrentMRIDiscards OBJECT-TYPE
              SYNTAX Gauge
              ACCESS  read-only
              STATUS  mandatory
              DESCRIPTION
                      " The value of this object reflects the number
                      of ICIP L2_PDUs discarded because of MRI
                      Timeout."
              ::= { smdsIomIcipL2CurrentEntry  10 }

















          S. Hansen (editor)                                 [Page 34]





          Bellcore           Intercarrier SMDS MIB           June 1994


          -- ICIP Level 2 Interval Table
          -- This table contains the performance counts for
          -- the past 8 intervals of ICIP Level 2 of an ICI.
          -- It is possible that less than 8 intervals may be reflected because
          -- the SS or ICI has not been on line for the entire 2 hours.

            smdsIomIcipL2IntervalTable OBJECT-TYPE
              SYNTAX  SEQUENCE OF SmdsIomIcipL2IntervalEntry
              ACCESS  not-accessible
              STATUS  mandatory
              DESCRIPTION
                      "The ICIP Level 2 Interval Table"
              ::= { smdsIomServObjects 10 }

            smdsIomIcipL2IntervalEntry OBJECT-TYPE
              SYNTAX SmdsIomIcipL2IntervalEntry
              ACCESS  not-accessible
              STATUS  mandatory
              DESCRIPTION
                      "An entry in the ICIP Level 2 Interval Table"
              INDEX   { smdsIomIcipL2IntervalIfIndex,
                        smdsIomIcipL2IntervalIntervalIndex }
              ::= { smdsIomIcipL2IntervalTable 1 }

            SmdsIomIcipL2IntervalEntry ::=
              SEQUENCE {
                smdsIomIcipL2IntervalIfIndex
                      INTEGER,
                smdsIomIcipL2IntervalIntervalIndex
                      INTEGER,
                smdsIomIcipL2IntervalTotalOut
                      Gauge,
                smdsIomIcipL2IntervalCongestionDiscards
                      Gauge,
                smdsIomIcipL2IntervalCellInvalidFieldsDiscards
                      Gauge,
                smdsIomIcipL2IntervalSARInvalidFieldsDiscards
                      Gauge,
                smdsIomIcipL2IntervalSARIncorrectFieldsDiscards
                      Gauge,
                smdsIomIcipL2IntervalCRCViolationsDiscards
                      Gauge,
                smdsIomIcipL2IntervalComsEomsDiscards
                      Gauge,
                smdsIomIcipL2IntervalBomsEomsDiscards





          S. Hansen (editor)                                 [Page 35]





          Bellcore           Intercarrier SMDS MIB           June 1994


                      Gauge,
                smdsIomIcipL2IntervalMRIDiscards
                      Gauge
              }

            smdsIomIcipL2IntervalIfIndex OBJECT-TYPE
              SYNTAX INTEGER (0..65535)
              ACCESS  read-only
              STATUS  mandatory
              DESCRIPTION
                      "The value of this object identifies the ifIndex
                      associated with the ICIP sublayer of the ICI."
              ::= { smdsIomIcipL2IntervalEntry 1 }

            smdsIomIcipL2IntervalIntervalIndex OBJECT-TYPE
              SYNTAX INTEGER (1..8)
              ACCESS  read-only
              STATUS  mandatory
              DESCRIPTION
                      "The value of this object identifies the
                      interval in which the counts occurred.  A value
                      of '1' indicates the most recently completed
                      interval while a value of '8' indicates least
                      recently completed interval."
              ::= { smdsIomIcipL2IntervalEntry 2 }

            smdsIomIcipL2IntervalTotalOut  OBJECT-TYPE
              SYNTAX Gauge
              ACCESS  read-only
              STATUS  mandatory
              DESCRIPTION
                      "The value of this object reflects the number of
                      ICIP L2_PDUs sent across an ICI."
              ::= { smdsIomIcipL2IntervalEntry 3 }

            smdsIomIcipL2IntervalCongestionDiscards OBJECT-TYPE
              SYNTAX Gauge
              ACCESS  read-only
              STATUS  mandatory
              DESCRIPTION
                      "The value of this object reflects the number of
                      ICIP L2_PDUs discarded because an ICI was in
                      congestion."
              ::= { smdsIomIcipL2IntervalEntry 4 }






          S. Hansen (editor)                                 [Page 36]





          Bellcore           Intercarrier SMDS MIB           June 1994


            smdsIomIcipL2IntervalCellInvalidFieldsDiscards  OBJECT-TYPE
              SYNTAX Gauge
              ACCESS  read-only
              STATUS  mandatory
              DESCRIPTION
                      "The value of this object reflects the number of
                      ICIP L2_PDUs discarded because of invalid fields
                      that occurred at the cell sublayer."
              ::= { smdsIomIcipL2IntervalEntry 5 }

            smdsIomIcipL2IntervalSARInvalidFieldsDiscards  OBJECT-TYPE
              SYNTAX Gauge
              ACCESS  read-only
              STATUS  mandatory
              DESCRIPTION
                      " The value of this object reflects the number
                      of ICIP L2_PDUs discarded because of invalid
                      fields that occurred at the Segmentation and
                      Reassembly (SAR) sublayer."
              ::= { smdsIomIcipL2IntervalEntry  6 }

            smdsIomIcipL2IntervalSARIncorrectFieldsDiscards OBJECT-TYPE
              SYNTAX Gauge
              ACCESS  read-only
              STATUS  mandatory
              DESCRIPTION
                      " The value of this object reflects the number
                      of ICIP L2_PDUs discarded because of incorrect
                      fields that occurred at the SAR sublayer."
              ::= { smdsIomIcipL2IntervalEntry  7 }

            smdsIomIcipL2IntervalCRCViolationsDiscards OBJECT-TYPE
              SYNTAX Gauge
              ACCESS  read-only
              STATUS  mandatory
              DESCRIPTION
                      " The value of this object reflects the number
                      of ICIP L2_PDUs discarded because the payload
                      Cyclic Redundancy Check (CRC) was incorrect."
              ::= { smdsIomIcipL2IntervalEntry  8 }










          S. Hansen (editor)                                 [Page 37]





          Bellcore           Intercarrier SMDS MIB           June 1994


             smdsIomIcipL2IntervalComsEomsDiscards OBJECT-TYPE
              SYNTAX Gauge
              ACCESS  read-only
              STATUS  mandatory
              DESCRIPTION
                      " The value of this object reflects the number
                      of ICIP L2_PDUs discarded because the sequence
                      number of the Continuation of Message (COM) or
                      End of Message (EOM) was not incremented by 1
                      relative to the previous L2_PDU received with
                      the same Message Identifier (MID)."
              ::= { smdsIomIcipL2IntervalEntry  9 }

            smdsIomIcipL2IntervalBomsEomsDiscards OBJECT-TYPE
              SYNTAX Gauge
              ACCESS  read-only
              STATUS  mandatory
              DESCRIPTION
                      " The value of this object reflects the number
                      of ICIP L3_PDUs discarded because the MID of a
                      Beginning of Message (BOM) was currently active
                      or the MID of an EOM was not currently active."
              ::= { smdsIomIcipL2IntervalEntry  10 }

            smdsIomIcipL2IntervalMRIDiscards OBJECT-TYPE
              SYNTAX Gauge
              ACCESS  read-only
              STATUS  mandatory
              DESCRIPTION
                      " The value of this object reflects the number
                      of ICIP L2_PDUs discarded because of MRI
                      Timeout."
              ::= { smdsIomIcipL2IntervalEntry  11 }

















          S. Hansen (editor)                                 [Page 38]





          Bellcore           Intercarrier SMDS MIB           June 1994


          -- The Inter-Carrier Interface Protocol (ICIP) Physical Layer
          -- Convergence Procedure (PLCP) Group

          -- Implementation of this group is mandatory for all systems
          -- that perform intercarrier SMDS.

          -- This group consists of 2 tables:
          --    ICIP PLCP Current Table, and
          --    ICIP PLCP Interval Table.
          -- For SMDS XA-OM and ECOM, counts are collected over 15
          -- minute intervals.

          -- ICIP PLCP Current Table
          -- This table contains the current performance counts for the
          -- ICIP PLCP of a given ICI.

          smdsIomIcipPlcpCurrentTable OBJECT-TYPE
              SYNTAX  SEQUENCE OF SmdsIomIcipPlcpCurrentEntry
              ACCESS  not-accessible
              STATUS  mandatory
              DESCRIPTION
                      "The ICIP PLCP Current Table"
              ::= { smdsIomServObjects 11 }

          smdsIomIcipPlcpCurrentEntry OBJECT-TYPE
              SYNTAX SmdsIomIcipPlcpCurrentEntry
              ACCESS  not-accessible
              STATUS  mandatory
              DESCRIPTION
                      "An entry in the ICIP Level 2 Current Table"
              INDEX   { smdsIomIcipPlcpCurrentIfIndex }
              ::= { smdsIomIcipPlcpCurrentTable 1 }

          SmdsIomIcipPlcpCurrentEntry ::=
              SEQUENCE {
                smdsIomIcipPlcpCurrentIfIndex
                      INTEGER,
                smdsIomIcipPlcpCurrentSEFS
                      Gauge,
                smdsIomIcipPlcpCurrentAlarmState
                     INTEGER,
                smdsIomIcipPlcpCurrentUnavailSeconds
                      Gauge
              }






          S. Hansen (editor)                                 [Page 39]





          Bellcore           Intercarrier SMDS MIB           June 1994


            smdsIomIcipPlcpCurrentIfIndex OBJECT-TYPE
              SYNTAX INTEGER (0..65535)
              ACCESS  read-only
              STATUS  mandatory
              DESCRIPTION
                      "The value of this object identifies the ifIndex
                      associated with the ICIP sublayer of the ICI."
              ::= { smdsIomIcipPlcpCurrentEntry 1 }

          smdsIomIcipPlcpCurrentSEFS  OBJECT-TYPE
              SYNTAX Gauge
              ACCESS  read-only
              STATUS  mandatory
              DESCRIPTION
                      "The value of this object reflects the number of
                      one-second intervals containing one or more
                      Severely Errored Framing (SEF) events."
              ::= { smdsIomIcipPlcpCurrentEntry 2 }

          smdsIomIcipPlcpCurrentAlarmState OBJECT-TYPE
              SYNTAX INTEGER {
                noAlarm (1),
                receivedFarEndAlarm (2),
                incomingLOF (3)
              }
              ACCESS  read-only
              STATUS  mandatory
              DESCRIPTION
                      "The value of this object reflects the alarm
                      state of the ICIP PLCP. The value noAlarm means
                      that there are no alarms present.  The value
                      receivedFarEndAlarm means that the DS3 PLCP
                      received an incoming Yellow Signal.  The value
                      incomingLOF means that the DS3 PLCP has declared
                      a Loss of Frame (LOF) failure condition."
              ::= { smdsIomIcipPlcpCurrentEntry 3 }














          S. Hansen (editor)                                 [Page 40]





          Bellcore           Intercarrier SMDS MIB           June 1994


            smdsIomIcipPlcpCurrentUnavailSeconds  OBJECT-TYPE
              SYNTAX Gauge
              ACCESS  read-only
              STATUS  mandatory
              DESCRIPTION
                      "The value of this object reflects the number of
                      seconds during which the PLCP is considered
                      unavailable."
              ::= {smdsIomIcipPlcpCurrentEntry 4 }



          -- ICIP PLCP Interval Table
          -- This table contains the performance counts for
          -- the past 8 intervals of ICIP PLCP of an ICI.
          -- It is possible that less than 8 intervals may be reflected
          -- because the SS or ICI has not been on line
          -- for the entire 2 hours.

            smdsIomIcipPlcpIntervalTable OBJECT-TYPE
              SYNTAX  SEQUENCE OF SmdsIomIcipPlcpIntervalEntry
              ACCESS  not-accessible
              STATUS  mandatory
              DESCRIPTION
                      "The ICIP PLCP Interval Table"
              ::= { smdsIomServObjects 12 }

            smdsIomIcipPlcpIntervalEntry OBJECT-TYPE
              SYNTAX SmdsIomIcipPlcpIntervalEntry
              ACCESS  not-accessible
              STATUS  mandatory
              DESCRIPTION
                      "An entry in the ICIP PLCP Interval Table"
              INDEX   { smdsIomIcipPlcpIntervalIfIndex,
                        smdsIomIcipPlcpIntervalIntervalIndex }
              ::= { smdsIomIcipPlcpIntervalTable 1 }

            SmdsIomIcipPlcpIntervalEntry ::=
              SEQUENCE {
                smdsIomIcipPlcpIntervalIfIndex
                      INTEGER,
                smdsIomIcipPlcpIntervalIntervalIndex
                      INTEGER,
                smdsIomIcipPlcpIntervalSEFS
                      Gauge,





          S. Hansen (editor)                                 [Page 41]





          Bellcore           Intercarrier SMDS MIB           June 1994


                smdsIomIcipPlcpIntervalUnavailSeconds
                      Gauge
                }

            smdsIomIcipPlcpIntervalIfIndex OBJECT-TYPE
              SYNTAX INTEGER (0..65535)
              ACCESS  read-only
              STATUS  mandatory
              DESCRIPTION
                      "The value of this object identifies the ifIndex
                      associated with the ICIP sublayer of the ICI."
              ::= { smdsIomIcipPlcpIntervalEntry 1 }

            smdsIomIcipPlcpIntervalIntervalIndex OBJECT-TYPE
              SYNTAX INTEGER (1..8)
              ACCESS  read-only
              STATUS  mandatory
              DESCRIPTION
                      "The value of this object identifies the
                      interval in which the counts occurred.  A value
                      of '1' indicates the most recently completed
                      interval while a value of '8' indicates least
                      recently completed interval."
              ::= { smdsIomIcipPlcpIntervalEntry 2 }

            smdsIomIcipPlcpIntervalSEFS  OBJECT-TYPE
              SYNTAX Gauge
              ACCESS  read-only
              STATUS  mandatory
              DESCRIPTION
                      "The value of this object reflects the number of
                      one-second intervals containing one or more
                      Severely Errored Framing (SEF) events."
              ::= { smdsIomIcipPlcpIntervalEntry 3 }

            smdsIomIcipPlcpIntervalUnavailSeconds OBJECT-TYPE
              SYNTAX Gauge
              ACCESS  read-only
              STATUS  mandatory
              DESCRIPTION
                      "The value of this object reflects the number of
                      seconds during which the PLCP is considered
                      unavailable."
              ::= { smdsIomIcipPlcpIntervalEntry 4 }
          END





          S. Hansen (editor)                                 [Page 42]





          Bellcore           Intercarrier SMDS MIB           June 1994


          7.  Acknowledgments

          This document was produced by the SIG Intercarrier Working
          Group.

          8.  References

             [1] M. Rose and K. McCloghrie, "Structure and Identification of
                 Management Information for TCP/IP-based internets", RFC
                 1155, Performance Systems International, Hughes LAN
                 Systems, May 1990.

             [2] M. Rose, and K. McCloghrie, Editors, "Concise MIB
                 Definitions", RFC 1212, Performance Systems International,
                 Hughes LAN Systems, March 1991.

             [3] K. McCloghrie and M. Rose, "Management Information Base
                 for Network Management of TCP/IP-based internets", RFC
                 1156, Hughes LAN Systems, Performance Systems
                 International, May 1990.

             [4] K. McCloghrie and M. Rose, Editors, "Management
                 Information Base for Network Management of TCP/IP-based
                 internets", RFC 1213, Performance Systems International,
                 March 1991.

             [5] J. Case, M. Fedor, M. Schoffstall, and J. Davin, "Simple
                 Network Management Protocol", RFC 1157, SNMP Research,
                 Performance Systems International, Performance Systems
                 International, MIT Laboratory for Computer Science, May
                 1990.

             [6] Information processing systems - Open Systems
                 Interconnection - Specification of Abstract Syntax Notation
                 One (ASN.1), International Organization for Standardization,
                 International Standard 8824, December 1987.

             [7] Information processing systems - Open Systems
                 Interconnection - Specification of Basic Encoding Rules
                 for Abstract Notation One (ASN.1), International Organization
                 for Standardization, International Standard 8825,
                 December 1987.

             [8] GR-1237-CORE, "SMDS Generic Requirements for Initial
                 Operations Management Capabilities in Support of





          S. Hansen (editor)                                 [Page 43]





          Bellcore           Intercarrier SMDS MIB           June 1994


                 Exchange Access and Intercompany Serving Arrangements",
                 Bellcore, Issue 1, June 1994.

             [9] T. A. Cox and K. Tesink, "Definitions of Managed Objects
                 for SMDS Subscription", Bellcore Enterprise-specific MIB
                 (posted on venera.isi.edu), Network Information Center (NIC),
                 SRI International, Menlo Park, CA, August 1992.

             [10] T. A. Cox and K. Tesink, "Definitions of Managed Objects
                  for the DS3 and E3 Interface Type", RFC 1407, Network
                  Information Center (NIC), SRI International, Menlo Park,
                  CA, January 1993.

             [11] T. A. Brown and K. Tesink, "Definitions of Managed Objects for
                  ThresholdCrossing Alerts", Bellcore Enterprise-specific MIB
                  (posted on venera.isi.edu as bellcore-tcav2-01.txt, SNMPv2
                  MIB, and bellcore-tcav1-00.mib, SNMPv1 MIB), Version
                  1.1, June 1994.

             [12] D. Piscitello, and J. Lawrence, "A Standard for Transmitting
                  IP Datagrams over SMDS Service", RFC 1209, Network
                  Information Center (NIC), SRI International, Menlo Park,
                  CA, March 1991.

             [13] K. McCloghrie and F. Kastenholz, "Evolution of Interfaces
                  Group of MIB-II", RFC 1573, January 1994.

             [14] T. Cox, and K. Tesink, "Definitions of Managed Objects for
                  the SIP Interface Type", RFC 1304, Network Information
                  Center (NIC), SRI International, Menlo Park, CA,
                  February 1992.

             [15] TR-TSV-001062, "Generic Requirements for Phase 1
                  SMDS Customer Network Management Service", Bellcore,
                  Issue 1, March 1993 and Revision 1, December 1993.



          9.  Security Considerations

          Security issues are not discussed in this memo.









          S. Hansen (editor)                                 [Page 44]





          Bellcore           Intercarrier SMDS MIB           June 1994


          10.  Author's Address

             Shannon Hansen
             Bellcore
             331 Newman Springs Road
             Room 1C322
             Red Bank, NJ  07701

             Phone: (908) 758-5288

             E-mail:shannon@cc.bellcore.com







































          S. Hansen (editor)                                 [Page 45]





          Bellcore           Intercarrier SMDS MIB           June 1994


          Table of Contents


          1 Status of this Memo .................................    1
          2 Abstract ............................................    1
          3 The Network Management Framework ....................    2
          4 Objects .............................................    3
          4.1 Format of Definitions .............................    3
          5 Overview ............................................    4
          5.1 Apply MIB II to Intercarrier SMDS .................    5
          5.2 Apply the SMDS Subscription MIB Module to Inter-
               carrier SMDS .....................................    8
          5.3 Apply the TCA MIB Module to Intercarrier SMDS .....    8
          5.4 Apply the DS3 MIB Module to Intercarrier SMDS .....    8
          6 Object Definitions ..................................   10
          6.1 The XA-SMDS Subscription Profile Group ............   11
          6.1.1 Aggregated Access Classes .......................   11
          6.2 The Intercarrier SMDS-Related Information  Group
               ..................................................   13
          6.2.1 LEC Network Addresses ...........................   13
          6.2.2 ICI Configuration Table .........................   15
          6.2.3 Nested Group Address (NGA) Table ................   17
          6.2.4 SNI-Related Current Information Table ...........   20
          6.2.5 SNI-Related Interval Information Table ..........   22
          6.3 Inter-Carrier Interface Protocol Level  3  Group
               ..................................................   24
          6.3.1  Inter-Carrier  Interface  Protocol  Level   3
               Current Table ....................................   24
          6.3.2 Inter-Carrier Interface Protocol Level  3  In-
               terval Table .....................................   27
          6.4 Inter-Carrier Interface Protocol Level  2  Group
               ..................................................   31
          6.4.1  Inter-Carrier  Interface  Protocol  Level   2
               Current Table ....................................   31
          6.4.2 Inter-Carrier Interface Protocol Level  2  In-
               terval Table .....................................   35
          6.5 Inter-Carrier Interface Protocol PLCP Group .......   39
          6.5.1 Inter-Carrier Interface Protocol PLCP  Current
               Table ............................................   39
          6.5.2 Inter-Carrier Interface Protocol PLCP Interval
               Table ............................................   41
          7 Acknowledgments .....................................   43
          8 References ..........................................   43
          9 Security Considerations .............................   44
          10 Author's Address ...................................   45





          S. Hansen (editor)                                 [Page 46]





          Bellcore           Intercarrier SMDS MIB           June 1994




















































          S. Hansen (editor)                                 [Page 47]
