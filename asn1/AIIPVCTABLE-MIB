AIIPVCTABLE-MIB DEFINITIONS ::= BEGIN

IMPORTS
		MODULE-IDENTITY, OBJECT-TYPE, enterprises
					FROM SNMPv2-SMI
		TEXTUAL-CONVENTION, RowStatus
					FROM SNMPv2-TC
		MODULE-COMPLIANCE, OBJECT-GROUP
					FROM SNMPv2-CONF;


		UnsignedShort   ::= INTEGER (0..65535)
		PositiveInteger ::= INTEGER (0..2147483647)
		IfIndexType     ::= INTEGER (1..2147483647)

		aii			OBJECT IDENTIFIER ::= { enterprises 539 }
		aiSLC2	    OBJECT IDENTIFIER ::= { aii 16 }

aiPVC	MODULE-IDENTITY
		LAST-UPDATED "9909141400Z"
		ORGANIZATION "Applied Innovation Inc."
		CONTACT-INFO
                     "        Engineering MIB Administrator

                      Postal: Applied Innovation Inc.
                              5800 Innovation Drive
                              Dublin, Ohio 43016-3271

                              Tel: 614-798-2000
                              Fax: 614-798-1770
                              E-mail: snmp@aiinet.com"
		DESCRIPTION
				"The MIB module for the PVC Table"
	::= { aiSLC2 1 }

   IANAifType ::= TEXTUAL-CONVENTION
       STATUS       current
       DESCRIPTION
               "This data type is used as the syntax of the ifType
               object in the (updated) definition of MIB-II's
               ifTable.

               The definition of this textual convention with the
               addition of newly assigned values is published
               periodically by the IANA, in either the Assigned
               Numbers RFC, or some derivative of it specific to
               Internet Network Management number assignments.  (The
               latest arrangements can be obtained by contacting the
               IANA.)

               Requests for new values should be made to IANA via
               email (iana@isi.edu).

               The relationship between the assignment of ifType
               values and of OIDs to particular media-specific MIBs
               is solely the purview of IANA and is subject to change
               without notice.  Quite often, a media-specific MIB's
               OID-subtree assignment within MIB-II's 'transmission'
               subtree will be the same as its ifType value.
               However, in some circumstances this will not be the
               case, and implementors must not pre-assume any
               specific relationship between ifType values and
               transmission subtree OIDs."
       SYNTAX  INTEGER {
                   other(1),          -- none of the following
                   regular1822(2),
                   hdh1822(3),
                   ddnX25(4),
                   rfc877x25(5),
                   ethernetCsmacd(6),
                   iso88023Csmacd(7),
                   iso88024TokenBus(8),
                   iso88025TokenRing(9),
                   iso88026Man(10),
                   starLan(11),
                   proteon10Mbit(12),
                   proteon80Mbit(13),
                   hyperchannel(14),
                   fddi(15),
                   lapb(16),
                   sdlc(17),
                   ds1(18),           -- DS1/E1 (RFC 1406)
                   e1(19),            -- obsolete
                   basicISDN(20),
                   primaryISDN(21),
                   propPointToPointSerial(22), -- proprietary serial
                   ppp(23),
                   softwareLoopback(24),
                   eon(25),            -- CLNP over IP (RFC 1070)
                   ethernet3Mbit(26),
                   nsip(27),           -- XNS over IP
                   slip(28),           -- generic SLIP
                   ultra(29),          -- ULTRA technologies
                   ds3(30),            -- T-3
                   sip(31),            -- SMDS
                   frameRelay(32),    -- DTE only
                   rs232(33),
                   para(34),           -- parallel-port
                   arcnet(35),         -- arcnet
                   arcnetPlus(36),     -- arcnet plus
                   atm(37),            -- ATM cells
                   miox25(38),
                   sonet(39),          -- SONET or SDH
                   x25ple(40),
                   iso88022llc(41),
                   localTalk(42),
                   smdsDxi(43),
                   frameRelayService(44),  -- Frame relay DCE
                   v35(45),
                   hssi(46),
                   hippi(47),
                   modem(48),          -- Generic modem
                   aal5(49),           -- AAL5 over ATM
                   sonetPath(50),
                   sonetVT(51),
                   smdsIcip(52),       -- SMDS InterCarrier Interface
                   propVirtual(53),    -- proprietary virtual/internal
                   propMultiplexor(54) -- proprietary multiplexing
               }

aiPVCTable OBJECT-TYPE
		SYNTAX  SEQUENCE OF AIPVCEntry
		MAX-ACCESS  not-accessible
		STATUS  current
		DESCRIPTION

"
Entries define permanent virtual circuits (PVCs) in the system.  Each
entry contains enough information to create one PVC on one network
interface.

Each entry may also contain the information required to create another
circuit in the system, of any kind.  This other circuit we will call a
companion circuit, since eventually it is going to be connected to the
PVC defined in the same entry.  This connection information does not
need to be present, but may be, to allow for a rapid association
between a PVC and its companion circuit.
"
		
	::= { aiPVC 1 }

aiPVCEntry OBJECT-TYPE
		SYNTAX  AIPVCEntry
		MAX-ACCESS  not-accessible
		STATUS  current
		DESCRIPTION
			"Entries of aiPVCTable."
		INDEX { aiPVCIfType, aiPVCIfIndex, aiPVCCircuit }
	::= { aiPVCTable 1 }

AIPVCEntry ::= SEQUENCE {
		aiPVCStatus
				RowStatus,
		aiPVCIfType
				IANAifType,
		aiPVCIfIndex
				IfIndexType,
		aiPVCCircuit
				PositiveInteger,
		aiPVCCallTimer
				UnsignedShort,
		aiPVCInactivityTimer
				UnsignedShort
		}

aiPVCStatus OBJECT-TYPE
		SYNTAX  RowStatus
		MAX-ACCESS  read-create
		STATUS  current

		DESCRIPTION
"
The status of this PVC entry. See RFC 1443 for details of usage.
"

	::= { aiPVCEntry 1 }

aiPVCIfType OBJECT-TYPE
		SYNTAX		IANAifType
		MAX-ACCESS	read-write
		STATUS		current

		DESCRIPTION
"
The type of subnetwork on which this PVC is to be created.
Examples are frameRelay(32), and x25ple(40).
"
	::= { aiPVCEntry 2 }

aiPVCIfIndex OBJECT-TYPE
		SYNTAX		IfIndexType
		MAX-ACCESS	read-write
		STATUS		current

		DESCRIPTION
"
The index into the interfaces group of MIB-II, which defines the
particular subnetwork on which this PVC will be created.  This index
corresponds to what AII calls a link.
"
	::= { aiPVCEntry 3 }

aiPVCCircuit OBJECT-TYPE
		SYNTAX		PositiveInteger
		MAX-ACCESS	read-write
		STATUS		current

		DESCRIPTION
"
The individual circuit number on the subnetwork (defined by
aiPVCIfIndex), to which the PVC defined by this entry is mapped.

In X.25, this number maps directly to a Logical Channel Number.

In Frame Relay, this number maps directly to a DLCI.

In other words, this object, and aiPVCIfIndex, tell the SLC where
a PVC is located.
"
	::= { aiPVCEntry 4 }

aiPVCCallTimer OBJECT-TYPE
		SYNTAX		UnsignedShort
		MAX-ACCESS	read-write
		STATUS		current

		DESCRIPTION
"
The time, in seconds, between successive attempts to create a
composite circuit comprising the PVC defined in this entry, and its
companion circuit.

When a PVC is created, if its aiPVCCallTimer is greater than zero,
then the PVC will attempt to connect to a remote host (as specified
elsewhere).  If the connection attempt times out before completion,
then the PVC will try again after aiPVCCallTimer seconds.
"

	::= { aiPVCEntry 5 }

aiPVCInactivityTimer OBJECT-TYPE
		SYNTAX		UnsignedShort
		MAX-ACCESS	read-write
		STATUS		current

		DESCRIPTION
"
The time, in seconds, of inactivity on a composite circuit before
a PVC will tear down the composite circuit.

Once a composite circuit has been created, comprising a PVC and its
companion circuit, then if the PVC's aiPVCInactivityTimer is greater
than zero, and if no data passes through the composite circuit in
either direction for aiPVCInactivityTimer seconds, then the PVC
will close the composite circuit.
"

	::= { aiPVCEntry 6 }

-- conformance information

aiPVCConformance OBJECT IDENTIFIER ::= { aiPVC 2 }

aiPVCGroups      OBJECT IDENTIFIER ::= { aiPVCConformance 1 }
aiPVCCompliances OBJECT IDENTIFIER ::= { aiPVCConformance 2 }


-- compliance statements

aiPVCCompliance MODULE-COMPLIANCE
		STATUS  current

		DESCRIPTION
	   "The compliance statement for SNMPv2 entities
		which have AII PVC tables."

		MODULE  -- this module
				MANDATORY-GROUPS { aiPVCGroup }
	::= { aiPVCCompliances 1 }


-- units of conformance

aiPVCGroup    OBJECT-GROUP
		OBJECTS {
				aiPVCStatus,
				aiPVCIfIndex,
				aiPVCIfType,
				aiPVCCircuit,
				aiPVCCallTimer,
				aiPVCInactivityTimer
		}
		STATUS  current

		DESCRIPTION
	   "A collection of objects providing information
		applicable to all AII cal parameter name tables."

	::= { aiPVCGroups 1 }

END
