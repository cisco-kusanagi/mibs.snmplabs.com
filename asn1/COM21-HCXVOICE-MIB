--  Copyright 1996, Com21 Inc.  All Rights Reserved.
--
 
COM21-HCXVOICE-MIB DEFINITIONS ::= BEGIN
  IMPORTS
        MODULE-IDENTITY, OBJECT-TYPE, NOTIFICATION-TYPE, Integer32,
        IpAddress, Gauge32, TimeTicks
            FROM SNMPv2-SMI
        DisplayString, MacAddress
            FROM SNMPv2-TC
        com21, com21Hcx
            FROM COM21-HCX-MIB
        hcxAlmSeverity, hcxEventLogTime
            FROM COM21-HCXALM-MIB;
 
 
        com21HcxVoice MODULE-IDENTITY
                LAST-UPDATED "9701080000Z"
                ORGANIZATION "Com21, Inc."
                CONTACT-INFO
                "       Network Management
                                Postal: Paul Gordon
                                Com21, Inc.
                                750 Tasman Drive
                                Milpitas, California 95035
                                USA
                                Tel: +1 408 953 9100
                                Fax: +1 408 953 9299
                                E-mail: pgordon@com21.com"
 
                DESCRIPTION
                        "This is the Com21 ComController Oc3
                         MIB module. COM21 Part# 005-0025-00"
                ::= { com21Hcx 100 }
 
 
 

        com21HcxVoiceGroup         	  OBJECT IDENTIFIER ::= {com21Hcx 101}
--	com21HcxVpnGroup		  OBJECT IDENTIFIER ::= {com21Hcx 102}	
	com21HcxVpnRxGroup		  OBJECT IDENTIFIER ::= {com21Hcx 102}	
	com21HcxVpnRxStatsGroup		  OBJECT IDENTIFIER ::= {com21Hcx 103}	
        com21HcxStuVoiceChannelGroup      OBJECT IDENTIFIER ::= {com21Hcx 104}
        com21HcxStuVoiceCallStatsGroup    OBJECT IDENTIFIER ::= {com21Hcx 105}

        PrimServiceState ::= INTEGER { is(1), oos(2) }
        Com21RowStatus   ::= INTEGER { active(1),
                                       create(2),
                                       destroy(3),
                                       deactive(4) }



        -- -- -- -- -- -- -- -- -- -- -- -- -- -- -- -- -- -- -- -- -- -- -- --
        -- -- -- -- -- -- -- -- -- -- -- -- -- -- -- -- -- -- -- -- -- -- -- --
        --
        -- com21HcxVoiceGroup
        --
	-- defines the system wide parameters for Voice connections over
	-- the HCX system
        --
        -- -- -- -- -- -- -- -- -- -- -- -- -- -- -- -- -- -- -- -- -- -- -- --
        -- -- -- -- -- -- -- -- -- -- -- -- -- -- -- -- -- -- -- -- -- -- -- --

        hcxConfiguredVoiceChannels OBJECT-TYPE
                SYNTAX Integer32
                MAX-ACCESS read-only
                STATUS current
                DESCRIPTION "
                        Defines the number of Voice Channels currently
                        configured on the system."
                ::= { com21HcxVoiceGroup 1 }

       hcxActiveVoiceChannels OBJECT-TYPE
                SYNTAX Integer32
                MAX-ACCESS read-only
                STATUS current
                DESCRIPTION "
                        Defines the number of Voice Channels that are
                        currently active on the system."
                ::= { com21HcxVoiceGroup 2 }

	hcxVoiceChannelMode	OBJECT-TYPE
		SYNTAX	INTEGER { aLaw (1), muLaw (2) }
                MAX-ACCESS read-write
                STATUS current
                DESCRIPTION "
			Defines the type of compression scheme to be
			used for voice.
			Default is aLaw."
                ::= { com21HcxVoiceGroup 3 }

	hcxVoiceOAMEnable    OBJECT-TYPE
                SYNTAX  INTEGER { disable (1), enable (2) }
                MAX-ACCESS read-write
                STATUS current
                DESCRIPTION "
			Defines whether OAM cells should be transmitted
			on voice VCC's when voice calls are idle.
			default: disable"
                ::= { com21HcxVoiceGroup 4 }

        hcxVoiceFEndEchoCancEnable   OBJECT-TYPE
                SYNTAX  INTEGER { disable (1), enable (2) }
                MAX-ACCESS read-write
                STATUS current
                DESCRIPTION "
			Defines whether Far End Echo Cancellation
			should be enabled or not.
			Default: disable"
                ::= { com21HcxVoiceGroup 5 }

        hcxVoiceRTTDelay    OBJECT-TYPE
                SYNTAX  Integer32 
                MAX-ACCESS read-write
                STATUS current
                DESCRIPTION "
			Defines the Round Trip Transit Delay in
			milliseconds. This should be configured
			if 'hcxVoiceFEndEchoCancEnable' is enabled.
                        Default: 0"
                ::= { com21HcxVoiceGroup 6 }


        -- -- -- -- -- -- -- -- -- -- -- -- -- -- -- -- -- -- -- -- -- -- -- --
        -- -- -- -- -- -- -- -- -- -- -- -- -- -- -- -- -- -- -- -- -- -- -- --
        --
        -- com21HcxVpnGroup
        --
        -- This group defines the Max Number of Simultaneous Voice Calls 
	-- Per Virtual Private Network (VPN) 
        --
        -- -- -- -- -- -- -- -- -- -- -- -- -- -- -- -- -- -- -- -- -- -- -- --
        -- -- -- -- -- -- -- -- -- -- -- -- -- -- -- -- -- -- -- -- -- -- -- --
 
--        com21HcxVpnTable OBJECT-TYPE
--                SYNTAX SEQUENCE OF HcxVpnEntry
--                MAX-ACCESS not-accessible
--                STATUS current
--                DESCRIPTION "."
--                ::= { com21HcxVpnGroup 1 }
-- 
--        com21HcxVpnEntry OBJECT-TYPE
--                SYNTAX HcxVpnEntry
--                MAX-ACCESS not-accessible
--                STATUS current
--                DESCRIPTION "."
--                INDEX { hcxVpnNum }
--                ::= { com21HcxVpnTable 1 }
--
--        HcxVpnEntry ::= SEQUENCE {
--                hcxVpnNum      		Integer32,
--		hcxVpnRowStatus		Com21RowStatus,
--                hcxVpnMaxActiveCalls    Integer32 }
--
--        hcxVpnNum OBJECT-TYPE
--                SYNTAX Integer32 
--                MAX-ACCESS read-only
--                STATUS current
--                DESCRIPTION "
--			Defines the Vpn Number. Used as Index."
--                ::= { com21HcxVpnEntry 1 }
--
--        hcxVpnRowStatus OBJECT-TYPE
--                SYNTAX Com21RowStatus
--                MAX-ACCESS read-create
--                STATUS current
--                DESCRIPTION "
--			lets the user Create a Vpn Instance.
--			Deactive is not allowed."
--                ::= { com21HcxVpnEntry 2 }
--
-- 
--        hcxVpnMaxActiveCalls OBJECT-TYPE
--                SYNTAX Integer32
--                MAX-ACCESS read-write
--                STATUS current
--               DESCRIPTION "
--			Defines the maximum number of voice calls
--			that should be allowed for this VPN."
--                ::= { com21HcxVpnEntry 3 }


        -- -- -- -- -- -- -- -- -- -- -- -- -- -- -- -- -- -- -- -- -- -- -- --
        -- -- -- -- -- -- -- -- -- -- -- -- -- -- -- -- -- -- -- -- -- -- -- --
        --
        -- com21HcxVpnRxGroup
        --
	-- This group defines the Max Number of Simultaneous Voice Calls
	-- that should be supported for a given VPN per RX Group
        --
        -- -- -- -- -- -- -- -- -- -- -- -- -- -- -- -- -- -- -- -- -- -- -- --
        -- -- -- -- -- -- -- -- -- -- -- -- -- -- -- -- -- -- -- -- -- -- -- --

        com21HcxVpnRxTable OBJECT-TYPE
                SYNTAX SEQUENCE OF HcxVpnRxEntry
                MAX-ACCESS not-accessible
                STATUS current
                DESCRIPTION "."
                ::= { com21HcxVpnRxGroup 1 }


        com21HcxVpnRxEntry OBJECT-TYPE
                SYNTAX HcxVpnRxEntry
                MAX-ACCESS not-accessible
                STATUS current
                DESCRIPTION "."
                INDEX { hcxVpnRxNum, hcxVpnRxEntryId }
                ::= { com21HcxVpnRxTable 1 }
 
        HcxVpnRxEntry ::= SEQUENCE {
                hcxVpnRxNum                 Integer32,
                hcxVpnRxEntryId             Integer32,
                hcxVpnRxRowStatus           Com21RowStatus,
                hcxVpnRxMaxActiveCalls      Integer32 }
 
        hcxVpnRxNum OBJECT-TYPE
                SYNTAX Integer32 
                MAX-ACCESS read-only
                STATUS current
                DESCRIPTION "
                        Defines the Vpn Number. Used as Index."
                ::= { com21HcxVpnRxEntry 1 }

        hcxVpnRxEntryId OBJECT-TYPE
                SYNTAX Integer32 
                MAX-ACCESS read-only
                STATUS current
                DESCRIPTION "
                        Defines the Rx Group Id. Used as Index."
                ::= { com21HcxVpnRxEntry 2 }

        hcxVpnRxRowStatus OBJECT-TYPE
                SYNTAX Com21RowStatus
                MAX-ACCESS read-create
                STATUS current
                DESCRIPTION "
			Used to create an Instance of Rx Group Id
			for a given VPN. Deactive is not allowed."
                ::= { com21HcxVpnRxEntry 3 }

        hcxVpnRxMaxActiveCalls OBJECT-TYPE
                SYNTAX Integer32
                MAX-ACCESS read-write
                STATUS current
                DESCRIPTION "
                        Defines the maximum number of voice calls
                        that should be allowed for this VPN on this
			Rx Group ."
                ::= { com21HcxVpnRxEntry 4 }




        -- -- -- -- -- -- -- -- -- -- -- -- -- -- -- -- -- -- -- -- -- -- -- --
        -- -- -- -- -- -- -- -- -- -- -- -- -- -- -- -- -- -- -- -- -- -- -- --
        --
        -- com21HcxVpnRxStatsGroup
        --
	-- This group displays the Voice Call Statistics collected on
	-- a Per Rx Group Per VPN 
        --
        -- -- -- -- -- -- -- -- -- -- -- -- -- -- -- -- -- -- -- -- -- -- -- --
        -- -- -- -- -- -- -- -- -- -- -- -- -- -- -- -- -- -- -- -- -- -- -- --
 
        com21HcxVpnRxStatsTable OBJECT-TYPE
                SYNTAX SEQUENCE OF HcxVpnRxStatsEntry
                MAX-ACCESS not-accessible
                STATUS current
                DESCRIPTION "."
                ::= { com21HcxVpnRxStatsGroup 1 }
 
 
        com21HcxVpnRxStatsEntry OBJECT-TYPE
                SYNTAX HcxVpnRxStatsEntry
                MAX-ACCESS not-accessible
                STATUS current
                DESCRIPTION "."
                INDEX { hcxVpnRxStatsNum, hcxVpnRxStatsEntryId }
                ::= { com21HcxVpnRxStatsTable 1 }
 
        HcxVpnRxStatsEntry ::= SEQUENCE {
                hcxVpnRxStatsNum                 Integer32,
                hcxVpnRxStatsEntryId             Integer32,
		hcxVpnRxStatsCurrCallsAllwd	 Integer32,
		hcxVpnRxStatsCurrCallsBlkd	 Integer32,
		hcxVpnRxStatsPrevCallsAllwd	 Integer32,
		hcxVpnRxStatsPrevCallsBlkd	 Integer32,
		hcxVpnRxStatsClear	         INTEGER }


        hcxVpnRxStatsNum   OBJECT-TYPE
                SYNTAX  Integer32 
                MAX-ACCESS  read-only
                STATUS  current
                DESCRIPTION "
			Defines the VPN value for which the stats are 
			collected. Used as Index."
                ::= { com21HcxVpnRxStatsEntry 1 }

        hcxVpnRxStatsEntryId   OBJECT-TYPE
                SYNTAX  Integer32 
                MAX-ACCESS  read-only
                STATUS  current
                DESCRIPTION "
                        Defines the Rx Group Number for which the stats are 
                        collected. Used as Index."
                ::= { com21HcxVpnRxStatsEntry 2 }

        hcxVpnRxStatsCurrCallsAllwd   OBJECT-TYPE
                SYNTAX  Integer32
                MAX-ACCESS  read-only
                STATUS  current
                DESCRIPTION "
			Defines the number of calls allowed in the
			given 15-min period for a ComPort on this
			Rx Group and on this VPN."
                ::= { com21HcxVpnRxStatsEntry 3 }

        hcxVpnRxStatsCurrCallsBlkd   OBJECT-TYPE
                SYNTAX  Integer32
                MAX-ACCESS  read-only
                STATUS  current
                DESCRIPTION "
                        Defines the number of calls blocked in the
                        given 15-min period for a ComPort on this 
                        Rx Group and on this VPN."
                ::= { com21HcxVpnRxStatsEntry 4 }

        hcxVpnRxStatsPrevCallsAllwd   OBJECT-TYPE
                SYNTAX  Integer32
                MAX-ACCESS  read-only
                STATUS  current
                DESCRIPTION "
                        Defines the number of calls allowed in the
                        previous 15-min period for a ComPort on this 
                        Rx Group and on this VPN."
                ::= { com21HcxVpnRxStatsEntry 5 }


        hcxVpnRxStatsPrevCallsBlkd   OBJECT-TYPE
                SYNTAX  Integer32
                MAX-ACCESS  read-only
                STATUS  current
                DESCRIPTION "
                        Defines the number of calls blocked in the
                        previous 15-min period for a ComPort on this 
                        Rx Group and on this VPN."
                ::= { com21HcxVpnRxStatsEntry 6 }

        hcxVpnRxStatsClear   OBJECT-TYPE
                SYNTAX  INTEGER { nil(1), clear(2) }
                MAX-ACCESS  read-write
                STATUS  current
                DESCRIPTION "
			This attribute is used to clear all call	
			statistics counters in this group.
                        This operation
                        is only possible if the hcxStatsControl attribute
                        is set to wrapCurr."
                ::= { com21HcxVpnRxStatsEntry 7 }





        -- -- -- -- -- -- -- -- -- -- -- -- -- -- -- -- -- -- -- -- -- -- -- --
        -- -- -- -- -- -- -- -- -- -- -- -- -- -- -- -- -- -- -- -- -- -- -- --
        --
        -- com21HcxStuVoiceChannelGroup
        --
        -- This group defines the Voice Channels on each Comport device
        --
        -- -- -- -- -- -- -- -- -- -- -- -- -- -- -- -- -- -- -- -- -- -- -- --
        -- -- -- -- -- -- -- -- -- -- -- -- -- -- -- -- -- -- -- -- -- -- -- --

        com21HcxStuVoiceChannelTable OBJECT-TYPE
                SYNTAX SEQUENCE OF HcxStuVoiceChannelEntry
                MAX-ACCESS not-accessible
                STATUS current
                DESCRIPTION "."
                ::= { com21HcxStuVoiceChannelGroup 1 }
 
        com21HcxStuVoiceChannelEntry OBJECT-TYPE
                SYNTAX HcxStuVoiceChannelEntry
                MAX-ACCESS not-accessible
                STATUS current
                DESCRIPTION "."
                INDEX { hcxStuVoiceChannelMacAddr , hcxStuVoiceChannelNum  }
                ::= { com21HcxStuVoiceChannelTable 1 }
 
        HcxStuVoiceChannelEntry ::= SEQUENCE {
                hcxStuVoiceChannelMacAddr      MacAddress,
                hcxStuVoiceChannelNum          INTEGER,
                hcxStuVoiceChannelVpi          INTEGER,
                hcxStuVoiceChannelVci          INTEGER,
                hcxStuVoiceChannelPriStatus    Com21RowStatus,
                hcxStuVoiceChannelState        INTEGER,
		hcxStuVoiceChannelExtLpBk      INTEGER}

        hcxStuVoiceChannelMacAddr OBJECT-TYPE
                SYNTAX MacAddress
                MAX-ACCESS read-only
                STATUS current
                DESCRIPTION "
                        Contains IEEE 802 medium access control address
                        of the ComPort device."
                ::= { com21HcxStuVoiceChannelEntry 1 }
 
        hcxStuVoiceChannelNum OBJECT-TYPE
                SYNTAX INTEGER (1..2)
                MAX-ACCESS read-only
                STATUS current
                DESCRIPTION "
                        Defines the voice channel on the Comport device used
                        for Voice."
                ::= { com21HcxStuVoiceChannelEntry 2 }
 
        hcxStuVoiceChannelVpi OBJECT-TYPE
                SYNTAX INTEGER (1..64)
                MAX-ACCESS read-write
                STATUS current
                DESCRIPTION "
                        Defines the VPI to use to connect the Comport's
                        voice channel to the external device on the
                        OC3 wan port. The 'hcxStuVoiceChannelVpi', 
			'hcxStuVoiceChannelVci'
                        combination should form a unique VCC for each
                        entry in 'com21HcxStuVoiceChannelTable'.
                        Default is 0"
                ::= { com21HcxStuVoiceChannelEntry 3 }
 
        hcxStuVoiceChannelVci OBJECT-TYPE
                SYNTAX INTEGER (1..255)
                MAX-ACCESS read-write
                STATUS current
                DESCRIPTION "
                        Defines the VCI to use to connect the Comport's
                        voice channel to the external device on the
                        OC3 wan port. The 'hcxStuVoiceChannelVpi', 
			'hcxStuVoiceChannelVci'
                        combination should form a unique VCC for each
                        entry in 'com21HcxStuVoiceChannelTable'.
                        Default is 0"
                ::= { com21HcxStuVoiceChannelEntry 4 }
 
        hcxStuVoiceChannelPriStatus OBJECT-TYPE
                SYNTAX Com21RowStatus
                MAX-ACCESS read-create
                STATUS current
                DESCRIPTION "
                        Used to control Create, Activate/Deactivate,
			or Destroy a row. Activation/Deactivation of the 
			row is not allowed if all writeable attributes do 
			not have valid values. "
                ::= { com21HcxStuVoiceChannelEntry 5 }
 
 
        hcxStuVoiceChannelState OBJECT-TYPE
                SYNTAX INTEGER { voiceChanIdle (1), voiceChanActive (2) }
                MAX-ACCESS read-only
                STATUS current
                DESCRIPTION "
                        Defines the current state of the port.
			voicePortActive indicates that the call is in progress "
                ::= { com21HcxStuVoiceChannelEntry 6 }

        hcxStuVoiceChannelExtLpBk OBJECT-TYPE
                SYNTAX INTEGER { disable (1), enable (2) }
                MAX-ACCESS read-write
                STATUS current
                DESCRIPTION "
			If this attribute is enabled, the Oc3 
			Port will loopback all cells received
			on this VCC. The attribute cannot
			be enabled if voiceChannel is active,
			and if this attribute is enabled,
			voiceChannel will not be allowed to
			go active.
			default: disable."
                ::= { com21HcxStuVoiceChannelEntry 7 }




        -- -- -- -- -- -- -- -- -- -- -- -- -- -- -- -- -- -- -- -- -- -- -- --
        -- -- -- -- -- -- -- -- -- -- -- -- -- -- -- -- -- -- -- -- -- -- -- --
        --
        -- com21HcxStuVoiceCallStatsGroup
        --
        -- This group defines the Voice Call Stats
        --
        -- -- -- -- -- -- -- -- -- -- -- -- -- -- -- -- -- -- -- -- -- -- -- --
        -- -- -- -- -- -- -- -- -- -- -- -- -- -- -- -- -- -- -- -- -- -- -- --
 
        com21HcxStuVoiceCallStatsTable OBJECT-TYPE
                SYNTAX SEQUENCE OF HcxStuVoiceCallStatsEntry
                MAX-ACCESS not-accessible
                STATUS current
                DESCRIPTION "."
                ::= { com21HcxStuVoiceCallStatsGroup 1 }
 
        com21HcxStuVoiceCallStatsEntry OBJECT-TYPE
                SYNTAX HcxStuVoiceCallStatsEntry
                MAX-ACCESS not-accessible
                STATUS current
                DESCRIPTION "."
                INDEX { hcxStuVoiceCallStatsMacAddr , hcxStuVoiceCallStatsNum  }
                ::= { com21HcxStuVoiceCallStatsTable 1 }
 
        HcxStuVoiceCallStatsEntry ::= SEQUENCE {
                hcxStuVoiceCallStatsMacAddr      	MacAddress,
                hcxStuVoiceCallStatsNum          	INTEGER,
		hcxStuVoiceCallCurrInCallsAllwd		Gauge32,
		hcxStuVoiceCallCurrOutCallsAllwd 	Gauge32,
		hcxStuVoiceCallCurrInCallsBlkd		Gauge32,
		hcxStuVoiceCallCurrOutCallsBlkd	 	Gauge32,
		hcxStuVoiceCallPrevInCallsAllwd		Gauge32,
		hcxStuVoiceCallPrevOutCallsAllwd 	Gauge32,
		hcxStuVoiceCallPrevInCallsBlkd		Gauge32,
		hcxStuVoiceCallPrevOutCallsBlkd	 	Gauge32,
		hcxStuVoiceCallStatsClear	 	INTEGER }

        hcxStuVoiceCallStatsMacAddr   OBJECT-TYPE
                SYNTAX  MacAddress 
                MAX-ACCESS  read-only
                STATUS  current
                DESCRIPTION "
                        Contains IEEE 802 medium access control address
                        of the ComPort device."
                ::= { com21HcxStuVoiceCallStatsEntry 1 }

        hcxStuVoiceCallStatsNum   OBJECT-TYPE
                SYNTAX  INTEGER (1..2) 
                MAX-ACCESS  read-only
                STATUS  current
                DESCRIPTION "
                       Defines the voice channel on the Comport device used
                       for Voice."
                ::= { com21HcxStuVoiceCallStatsEntry 2 }

        hcxStuVoiceCallCurrInCallsAllwd   OBJECT-TYPE
                SYNTAX  Gauge32
                MAX-ACCESS  read-only
                STATUS  current
                DESCRIPTION "
			Defines the number of Incoming calls allowed in the 
			given 15-min time period. Incoming calls are calls
			being placed to this voice channel."
                ::= { com21HcxStuVoiceCallStatsEntry 3 }

        hcxStuVoiceCallCurrOutCallsAllwd   OBJECT-TYPE
                SYNTAX  Gauge32
                MAX-ACCESS  read-only
                STATUS  current
                DESCRIPTION "
                        Defines the number of Outgoing calls allowed in the
                        given 15-min time period. Outgoing calls are calls
                        being placed by this voice channel."
                ::= { com21HcxStuVoiceCallStatsEntry 4 }

        hcxStuVoiceCallCurrInCallsBlkd   OBJECT-TYPE
                SYNTAX  Gauge32
                MAX-ACCESS  read-only
                STATUS  current
                DESCRIPTION "
                        Defines the number of Incoming calls blocked in the 
                        given 15-min time period. Incoming calls are calls
                        being placed to this voice channel."
                ::= { com21HcxStuVoiceCallStatsEntry 5 }

        hcxStuVoiceCallCurrOutCallsBlkd   OBJECT-TYPE
                SYNTAX  Gauge32
                MAX-ACCESS  read-only
                STATUS  current
                DESCRIPTION "
                        Defines the number of Outgoing calls blocked in the 
                        given 15-min time period. Outgoing calls are calls
                        being placed by this voice channel."
                ::= { com21HcxStuVoiceCallStatsEntry 6 }


        hcxStuVoiceCallPrevInCallsAllwd   OBJECT-TYPE
                SYNTAX  Gauge32
                MAX-ACCESS  read-only
                STATUS  current
                DESCRIPTION "
                        Defines the number of Incoming calls allowed in the 
                        previous 15-min time period. Incoming calls are calls
                        being placed to this voice channel."
                ::= { com21HcxStuVoiceCallStatsEntry 7 }
 
        hcxStuVoiceCallPrevOutCallsAllwd   OBJECT-TYPE
                SYNTAX  Gauge32
                MAX-ACCESS  read-only
                STATUS  current
                DESCRIPTION "
                        Defines the number of Outgoing calls blocked in the
                        previous 15-min time period. Outgoing calls are calls
                        being placed by this voice channel."
                ::= { com21HcxStuVoiceCallStatsEntry 8 }

        hcxStuVoiceCallPrevInCallsBlkd   OBJECT-TYPE
                SYNTAX  Gauge32
                MAX-ACCESS  read-only
                STATUS  current
                DESCRIPTION "
                        Defines the number of Incoming calls blocked in the 
                        previous 15-min time period. Incoming calls are calls
                        being placed to this voice channel."
                ::= { com21HcxStuVoiceCallStatsEntry 9 }
 
        hcxStuVoiceCallPrevOutCallsBlkd   OBJECT-TYPE
                SYNTAX  Gauge32
                MAX-ACCESS  read-only
                STATUS  current
                DESCRIPTION "
                        Defines the number of Outgoing calls blocked in the 
                        previous 15-min time period. Outgoing calls are calls
                        being placed by this voice channel."
                ::= { com21HcxStuVoiceCallStatsEntry 10 }


        hcxStuVoiceCallStatsClear   OBJECT-TYPE
                SYNTAX  INTEGER { nil(1), clear(2) }
                MAX-ACCESS  read-write
                STATUS  current
                DESCRIPTION "
			This attribute is used to clear all the voice 
			channel statistics counters in this group. 
			This operation
                        is only possible if the hcxStatsControl attribute
                        is set to wrapCurr."
                ::= { com21HcxStuVoiceCallStatsEntry 11 }

END
