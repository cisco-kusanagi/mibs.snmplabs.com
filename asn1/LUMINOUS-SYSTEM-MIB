LUMINOUS-SYSTEM-MIB DEFINITIONS ::= BEGIN
    IMPORTS
            TimeTicks, enterprises,
            MODULE-IDENTITY, OBJECT-TYPE, NOTIFICATION-TYPE,
            ObjectName, Integer32, Counter32       
                                    FROM SNMPv2-SMI
            DisplayString FROM RFC1213-MIB
				RowStatus, DateAndTime
                                    FROM SNMPv2-TC
            LumSlotNum, LumAdminStatus, LumOperStatus,
            LumName, LumDescr, LumPortNum, LumSimpleIndex,
            LumAlarmSeverity, LumCardBaseType, LumVersionString,
            LumResetCmd, LumSignalState
                                    FROM LUMINOUS-TC-MIB;

  -- IANA-registered  Luminous Network Enterprise Number of 4614

    luminous OBJECT IDENTIFIER ::= { enterprises 4614}


  -- leaving tree-space for the future products:

    lumADM   OBJECT IDENTIFIER ::= { luminous 1}


  --  This MIB module defines various system configurations.

 
    lumSystemMIB         MODULE-IDENTITY      
        LAST-UPDATED "0007250000Z"
        ORGANIZATION "Luminous Networks"
        CONTACT-INFO "  Luminous Technical Support

                        Postal: Luminous Networks,
                                14060 Bubb Road,
                                Cupertino, CA 95014

                        Tel: +1 408 342 6400
                        Fax: +1 408 863 1100
                        E-mail: support@luminousnetworks.com"
        DESCRIPTION  "The Luminous System MIB contains     
                    information related to the  
                    Luminous system configurations and monitoring." 

        REVISION     "0106270000Z"
        DESCRIPTION "Added new LumAlarmSeverity TC and reformatted."

        REVISION     "0105240000Z"
        DESCRIPTION "Added lumDownLoadImageType values:
                                
                        wdmBand1(24),
                        wdmBand2(25),
                        wdmBand3(26),
                        wdmBand4(27),
                        ds3cc12(28),
                        ds3cc12IO(29),
                        t3cc12(30),
                        e3cc12(31)"

        REVISION      "0010160000Z"
        DESCRIPTION  "Added ring primary and secorndary los."
        ::= { lumADM    4}


--
-- Object Hierachy
--

    lumSoftwareDownload OBJECT IDENTIFIER ::= { lumSystemMIB 1}


    lumSystemReset      OBJECT IDENTIFIER ::= { lumSystemMIB 2}


    lumAlarms           OBJECT IDENTIFIER ::= { lumSystemMIB 3}

    lumAlarmType        OBJECT IDENTIFIER ::= { lumAlarms 1 }
  
    lumAlarmSource      OBJECT IDENTIFIER ::= { lumAlarms 2 } 

    lumAlarmLog         OBJECT IDENTIFIER ::= { lumAlarms 4 }
     
    lumAlarmSummary     OBJECT IDENTIFIER ::= { lumAlarms 5 }
         
    lumAlarmTraps       OBJECT IDENTIFIER ::= { lumAlarms 10 }
    lumAlarmV2Traps     OBJECT IDENTIFIER ::= { lumAlarms 0}

--  System software download


    lumDownLoadImageType  OBJECT-TYPE
        SYNTAX   LumCardBaseType
        MAX-ACCESS  read-write
        STATUS   current
        DESCRIPTION  "The type of image to be downloaded."
        DEFVAL  { 1 }
        ::= { lumSoftwareDownload 1 }

    lumDownLoadHost OBJECT-TYPE
        SYNTAX   DisplayString (SIZE (0..16))
        MAX-ACCESS  read-write
        STATUS   current
        DESCRIPTION  "The IP address or name of the image downloading host."  
        ::= { lumSoftwareDownload 2 }

    lumDownLoadUsrName  OBJECT-TYPE
        SYNTAX   DisplayString (SIZE (0..16))
        MAX-ACCESS  read-write
        STATUS   current
        DESCRIPTION  "The user logging name for accessing the image
                       downloading host."
        ::= { lumSoftwareDownload 3 }

    lumDownLoadPasswd  OBJECT-TYPE
        SYNTAX   DisplayString (SIZE (0..16))
        MAX-ACCESS  read-write
        STATUS   current
        DESCRIPTION  "The password associated with the lumDownLoadUsrName
                        when accessing the image downloading host."
        ::= {lumSoftwareDownload 4 }

    lumDownLoadFilePath  OBJECT-TYPE
        SYNTAX   DisplayString (SIZE (0..64))
        MAX-ACCESS read-write
        STATUS  current
        DESCRIPTION  "The image file name and its directory path
                       on the downloading host."
        ::= { lumSoftwareDownload 5 }

    lumDownLoadVersion  OBJECT-TYPE
        SYNTAX    LumVersionString
        MAX-ACCESS read-write
        STATUS  current
        DESCRIPTION  "The version number of the image file to be 
                       downloaded."
        ::= { lumSoftwareDownload 6 }

    lumDownLoadSlot  OBJECT-TYPE
        SYNTAX   LumSlotNum
        MAX-ACCESS read-write
        STATUS  current
        DESCRIPTION  "The slot number to which the image will be 
                       downloaded to.  When the slot number is 0, all 
                       the applicable cards are to be downloaded 
                       with the image."
        ::= { lumSoftwareDownload 7 } 

    lumDownLoadTimeOut OBJECT-TYPE
        SYNTAX    Integer32
        UNITS      "minutes"
        MAX-ACCESS read-write
        STATUS  current
        DESCRIPTION "The length of time, in minutes, that agent
                        allows the download process to continue."
        DEFVAL {10}
        ::= { lumSoftwareDownload 8}

    lumDownLoadCmd OBJECT-TYPE
        SYNTAX    INTEGER {
              none(1),
              download(2)
            }
        MAX-ACCESS read-write
        STATUS  current
        DESCRIPTION "Set object to download(2) to active the image 
                        download process.  The image downloading related
                        objects should have been properly configuered.
                        The download command will be rejected if the
                        the lumDownLoadStatus has a value of 
                        download-in-progress(2)." 
        ::= { lumSoftwareDownload 9}        

    lumDownLoadStatus OBJECT-TYPE
        SYNTAX    INTEGER {
                    none(1),
                    download-in-progress(2),
                    download-succeeded(3),
                    download-failed(4)
                 }
        MAX-ACCESS read-only
        STATUS     current
        DESCRIPTION "The status of a previously issued software download
                     command." 
        DEFVAL {1}
        ::= { lumSoftwareDownload 10}

    lumDownLoadAbort OBJECT-TYPE
        SYNTAX    INTEGER {
                     none(1),
                     abort(2)
            }
        MAX-ACCESS read-write
        STATUS     current
        DESCRIPTION "Abort the software download process."
        DEFVAL {1}
        ::= { lumSoftwareDownload 11}


-- System and line card Resets

    lumSystemResetCardTable OBJECT-TYPE
        SYNTAX  SEQUENCE OF LumSystemResetCardEntry
        MAX-ACCESS not-accessible
        STATUS  deprecated
        DESCRIPTION "The Luminous line card reset table."
        ::= { lumSystemReset 1   }
       
    lumSystemResetCardEntry OBJECT-TYPE
        SYNTAX  LumSystemResetCardEntry
        MAX-ACCESS not-accessible
        STATUS  deprecated
        DESCRIPTION "An lumSystemResetCardEntry contains a line
                     card to be reset."

        INDEX { lumSystemResetCardIndex }
        ::= { lumSystemResetCardTable 1   }

    LumSystemResetCardEntry ::=
            SEQUENCE {
                       lumSystemResetCardIndex      LumSlotNum,
                       lumSystemResetCardCmd        LumResetCmd
                     }

    lumSystemResetCardIndex   OBJECT-TYPE
        SYNTAX     LumSlotNum
        MAX-ACCESS read-only
        STATUS     deprecated
        DESCRIPTION  "The line card number."
        ::= { lumSystemResetCardEntry 1 }
 
    lumSystemResetCardCmd OBJECT-TYPE
        SYNTAX     LumResetCmd
        MAX-ACCESS read-write
        STATUS     deprecated
        DESCRIPTION  "Reset a line card. This will always return
                    none on read."
        ::= { lumSystemResetCardEntry 2 }
 
    lumSystemResetShelfCmd OBJECT-TYPE
        SYNTAX    LumResetCmd
        MAX-ACCESS read-write
        STATUS     deprecated
        DESCRIPTION "Reset the Luminous shelf.  This will always return
                    none on read."
        ::= { lumSystemReset 2}
 

-- Alarm types used for sending alarm traps.
-- These objects are not to be access directly.
     
    lumProvisionAlarmType OBJECT-TYPE
        SYNTAX  INTEGER{
                        provCardFailedNoBackup(1),
                        provCardFailedWithBackup(2) 
                        }
        MAX-ACCESS not-accessible
        STATUS  current
        DESCRIPTION  "The provision Alarms."
        ::=  {lumAlarmType 1 }
 
    lumAlarmCardAlarmType OBJECT-TYPE
        SYNTAX  INTEGER{
                        input0(1),
                        input1(2),
                        input2(3),
                        input3(4),
                        input4(5),
                        input5(6),
                        input6(7),
                        input7(8),
                        alarmCardFailedNoBackup(9),
                        alarmCardFailedWithBackup(10),
                        card-lost(11)
                        }
        MAX-ACCESS not-accessible
        STATUS  current
        DESCRIPTION  "The Alarm card Alarms."
        ::=  {lumAlarmType 2 }

    lumSysconAlarmType OBJECT-TYPE
        SYNTAX  INTEGER{
                        cmmlf(1),           -- Card com failure 
                        redundancy-lost(2) -- syscon redundancy lost
                        }
        MAX-ACCESS not-accessible
        STATUS  current
        DESCRIPTION  "The Syscon card Alarms."
        ::=  {lumAlarmType 3 }

    lumT1AlarmType OBJECT-TYPE
        SYNTAX  INTEGER{
                        bpv(1),         -- Bipolar violation
                        lof(2),         -- Loss of frame
                        los(3),         -- Loss of signal
                        ais(4),         -- Alarm indication status 
                        rai(5),         -- Remote alarm indication
                        ovrfl(6),       -- Packetizing buffer overflow
                        sf-ber(7),      -- Error failure
                        sf-es(8),       -- Exceeded errored seconds threshold
                        sf-ses(9),      -- Exceeded severely errored 
                                        -- seconds threshold  
                        tcfl(10)        -- I/O transmission card failure 
                        }
        MAX-ACCESS not-accessible
        STATUS  current
        DESCRIPTION  "The T1 card Alarms."
        ::=  {lumAlarmType 4 }

    lumTEN100AlarmType OBJECT-TYPE
        SYNTAX  INTEGER{
                        an-fail(1),     -- Auto negotiation failure
                        los(2),         -- Loss of signal
                        symer(3),       -- Rx 4B/5B coding errors
                        rxer(4),        -- Mac receive errors
                        frlex(5),       -- Frame too long
                        aler(6),        -- Alignment errors
                        fcserr(7)       -- Frame check sequence error
                        }
        MAX-ACCESS not-accessible
        STATUS  current
        DESCRIPTION  "The 10/100 card Alarms."
        ::=  {lumAlarmType 5 }

    lumSonetAlarmType OBJECT-TYPE
        SYNTAX  INTEGER{
                        laser-loop(1),
                        laser-bias(2),
                        laser-pwr(3),
                        loss-of-sync(4),
                        los-s(5),
                        lof-s(6),
                        ais-l(7),
                        rfi-l(8),
                        sf-ber(9),
                        sd-ber(10),
                        ais-p(11),
                        rfi-p(12),
                        lop-p(13),
                        uneq-p(14),
                        plm-p(15),
                        aps-k1(16),
                        aps-k2(17),
                        aps-mode(18),
                        aps-far-end(19),
                        aps-success(20),
                        aps-failed(21)
                        }
        MAX-ACCESS not-accessible
        STATUS  current
        DESCRIPTION  "The Sonet card Alarms."
        ::=  {lumAlarmType 6 }

    lumRingCardAlarmType OBJECT-TYPE
        SYNTAX  INTEGER{
                        los(1),             -- Loss of signal
                        losynch(2),         -- Loss of ring link synchronization
                        sf-ber(3),          -- Ring BER failure threshold exceeded
                        sd-ber(4),          -- 
                        pri-los(5),         -- Lost primary source for ring sync
                        sec-los(6),         -- Lost secondary source for ring sync 
                        io-west-lost(7),    -- Ring west IO card lost
                        io-east-lost(8),    -- Ring east IO card lost
                        io-card-lost(9),    -- Ring IO card lost 
                        switch-fabric-lost(10),
                        switch-fabric-redundancy-lost(11)
                        }
        MAX-ACCESS not-accessible
        STATUS  current
        DESCRIPTION  "The Ring card Alarms."
        ::=  {lumAlarmType 7 }

    lumUtilityAlarmType OBJECT-TYPE
        SYNTAX  INTEGER{
                        vltg(1),            -- On-board volt out of range
                        hitmp(2),           -- High on-board temp
                        pwra(3),            -- Power A-48V feed down
                        pwrb(4),            -- Power B-48V feed down
                        card-lost(5)        -- Utility card lost
                        }
        MAX-ACCESS not-accessible
        STATUS  current
        DESCRIPTION  "The Utility card Alarms."
        ::=  {lumAlarmType 8 }

    lumEquipmentAlarmType OBJECT-TYPE
        SYNTAX  INTEGER{
                        fncrt(1),               -- Critical fault on fan tray
                        fnmjr(2),               -- Major fault on fan tray
                        boot(3),                -- Boot failure
                        hwfl(4),                -- Hardware failure
                        hitmp(5),               -- High on-board temp
                        vltg(6),                -- On-board vold out of range
                        trans-mea(7),           -- Transition line card mismatch
                        sgeo(8),                -- Supporting entity is in OOS
                        ueq(9),                 -- Hardware or software is missing
                        mea(10),                -- Mismatched of equipment attributes
                        prov-io-card-lost(11),  -- A provisioned IO card is lost
                        io-card-lost(12),       -- An IO card is lost  
                        prov-io-card-mismatched(13), -- Mismatched IO card in provisioning  
                        io-card-mismatched(14)  -- Mismatched IO card found
                        }
        MAX-ACCESS not-accessible
        STATUS  current
        DESCRIPTION  "The Equipment Alarms."
        ::=  {lumAlarmType 9 }
     
    lumDataFlowAlarmType OBJECT-TYPE
        SYNTAX  INTEGER{
                        sf-dfc(1),          -- Exceeded discarded packets limit
                        sf-ifc(2),          -- Exceeded invalid packet header limit
                        sf-bfc(3)           -- Exceeded invalid packets limit
                        }
        MAX-ACCESS not-accessible
        STATUS  current
        DESCRIPTION  "The Data Flow Alarms."
        ::=  {lumAlarmType 10 }

    lumDataBaseAlarmType OBJECT-TYPE
        SYNTAX  INTEGER{
                        saveFailed(1),      -- Failed to save the data base
                        restoreFailed(2)    -- Failed to retore the data base
                        }
        MAX-ACCESS not-accessible
        STATUS  current
        DESCRIPTION  "The Data Base Alarms."
        ::=  {lumAlarmType 11 }

    lumPPPAlarmType OBJECT-TYPE
        SYNTAX  INTEGER{
                        linkDown(1)         -- PPP Link down
                       }
        MAX-ACCESS not-accessible
        STATUS   current
        DESCRIPTION  "The PPP Alarms."
        ::=  {lumAlarmType 12 }
       
 -- Alarm sources are used for sending alarm traps.
 -- These objects are not to be access directly.

    lumAlarmSlotId    OBJECT-TYPE
        SYNTAX  LumSlotNum
        MAX-ACCESS  not-accessible
        STATUS  current
        DESCRIPTION  "The card's slot number. Starts with 1 for the both 
                        front plane and for the back plane."
        ::= { lumAlarmSource 1 }              

    lumAlarmPortId    OBJECT-TYPE
        SYNTAX  LumPortNum
        MAX-ACCESS  not-accessible
        STATUS  current
        DESCRIPTION  "The card's port number."
        ::= { lumAlarmSource 2 }

 -- Alarm status is used for sending alarm traps.
 -- These objects are not to be access directly.

    lumAlarmStatus    OBJECT-TYPE
        SYNTAX  INTEGER {
                        alarmClear(1),      -- The previously occured alarm has been cleared
                        alarmSet (2),       -- An alarm has occured
                        alarmMasked(3)      -- The alarm is to be masked (don't report)
                        }
        MAX-ACCESS  not-accessible
        STATUS     current
        DESCRIPTION  "The status of the alarm."
        ::= { lumAlarms 3 }

--
-- Alarm Status Summary
-- 
    lumAlarmSummaryGroup    OBJECT IDENTIFIER ::= { lumAlarmSummary 1 }

--
-- lumAlarmSummaryGroup
--

    lumAlarmSummaryState    OBJECT-TYPE
        SYNTAX      LumAlarmSeverity
        MAX-ACCESS  read-only
        STATUS      current
        DESCRIPTION  "This reflect the highest severity of any active alarm."
        ::= { lumAlarmSummaryGroup 1 }

    lumAlarmSummaryCriticalStatus   OBJECT-TYPE
        SYNTAX      LumSignalState
        MAX-ACCESS  read-only
        STATUS      current
        DESCRIPTION  "This is active if one or more critical alarms are active."
        ::= { lumAlarmSummaryGroup 2 }

    lumAlarmSummaryMajorStatus  OBJECT-TYPE
        SYNTAX      LumSignalState
        MAX-ACCESS  read-only
        STATUS      current
        DESCRIPTION  "This is active if one or more major alarms are active."
        ::= { lumAlarmSummaryGroup 3 }

    lumAlarmSummaryMinorStatus  OBJECT-TYPE
        SYNTAX      LumSignalState
        MAX-ACCESS  read-only
        STATUS      current
        DESCRIPTION  "This is active if one or more minor alarms are active."
        ::= { lumAlarmSummaryGroup 4 }

--
--  Alarm logs
--

    lumAlarmActiveTable OBJECT-TYPE
        SYNTAX  SEQUENCE OF LumAlarmActiveEntry
        MAX-ACCESS not-accessible
        STATUS  current
        DESCRIPTION "The Luminous active alarms table which
                    contains all the currently active alarms."
        ::= { lumAlarmLog 1   }

    lumAlarmActiveEntry OBJECT-TYPE
        SYNTAX  LumAlarmActiveEntry
        MAX-ACCESS not-accessible
        STATUS  current
        DESCRIPTION "An lumAlarmActive Entry contains the 
                    information for an active alarm."
        INDEX { lumAlarmActiveIndex }
        ::= { lumAlarmActiveTable 1   }

    LumAlarmActiveEntry ::=
       SEQUENCE {
                 lumAlarmActiveIndex         Integer32,
                 lumAlarmActiveType          INTEGER,
                 lumAlarmActiveValue         Integer32,
                 lumAlarmActiveStatus        INTEGER, 
                 lumAlarmActiveTimeStamp     TimeTicks,
                 lumAlarmActiveSlotId        LumSlotNum,
                 lumAlarmActivePortId        LumPortNum 
                }

    lumAlarmActiveIndex   OBJECT-TYPE
        SYNTAX    Integer32
        MAX-ACCESS read-only
        STATUS    current
        DESCRIPTION "This is the index to the actvie alarm log."
        ::= { lumAlarmActiveEntry 1 } 
     
    lumAlarmActiveType  OBJECT-TYPE
        SYNTAX  INTEGER {
                        provision (1),
                        alarmCard (2),
                        syscon (3),
                        t1 (4),
                        tEN100 (5),
                        sonet (6),
                        ringCard (7),
                        utility (8),
                        equipment (9),
                        dataFlow (10), 
                        dataBase (11)
                        }    
        MAX-ACCESS read-only
        STATUS    current
        DESCRIPTION "The alarm type which corresponds to one
                    of the types defined under lumAlarmType."    
        ::= { lumAlarmActiveEntry 2 } 

    lumAlarmActiveValue  OBJECT-TYPE
        SYNTAX    Integer32
        MAX-ACCESS read-only
        STATUS    current
        DESCRIPTION "The specific alarm.  The meaning of the 
                     value of this object can be found by 
                     looking up the enums defined uner lumAlarmType."
        ::= { lumAlarmActiveEntry 3 }

    lumAlarmActiveStatus    OBJECT-TYPE
        SYNTAX  INTEGER { 
                        alarmClear(1),      -- A removed alarm
                        alarmSet (2),       -- An existing alarm
                        alarmMasked(3)      -- A masked alarm
                        }
        MAX-ACCESS read-only
        STATUS    current
        DESCRIPTION "The active alarm status."
        ::= { lumAlarmActiveEntry  4 }

    lumAlarmActiveTimeStamp   OBJECT-TYPE
        SYNTAX   DateAndTime
        MAX-ACCESS read-only
        STATUS    current
        DESCRIPTION "The alarm time stamp."
        ::= { lumAlarmActiveEntry  5 }

    lumAlarmActiveSlotId     OBJECT-TYPE
        SYNTAX    LumSlotNum
        MAX-ACCESS read-only 
        STATUS    current
        DESCRIPTION "The card's slot number. Slot number 0
                        is used for alarms that do not associate
                        with a particular slot."
        ::= { lumAlarmActiveEntry 6 }

    lumAlarmActivePortId     OBJECT-TYPE
        SYNTAX    LumPortNum
        MAX-ACCESS read-only 
        STATUS    current
        DESCRIPTION "The card's port number.  Port number 0
                        is used for alarms that do not associate
                        with a particular port."
        ::= { lumAlarmActiveEntry 7 }

-- Alarm history table

    lumAlarmHistoryTable OBJECT-TYPE
        SYNTAX  SEQUENCE OF LumAlarmHistoryEntry
        MAX-ACCESS not-accessible
        STATUS  current
        DESCRIPTION "The Luminous alarms history table which
                    contains all the occured alarms.  
                    The actual retrieveable alarm entries
                    depends on system memory utilization"
        ::= { lumAlarmLog 2   }

    lumAlarmHistoryEntry OBJECT-TYPE
        SYNTAX  LumAlarmHistoryEntry
        MAX-ACCESS not-accessible
        STATUS  current
        DESCRIPTION "An lumAlarmHistoryEntry contains the
                    information for an occured alarm."
        INDEX { lumAlarmHistoryIndex }
        ::= { lumAlarmHistoryTable 1    }

    LumAlarmHistoryEntry ::= 
        SEQUENCE {
                lumAlarmHistoryIndex        Integer32,
                lumAlarmHistoryData         DisplayString
                }

    lumAlarmHistoryIndex    OBJECT-TYPE
        SYNTAX     Integer32
        MAX-ACCESS read-only
        STATUS     current
        DESCRIPTION  "This is the index to the alarm history table."
        ::= { lumAlarmHistoryEntry 1 }

    lumAlarmHistoryData   OBJECT-TYPE
        SYNTAX    DisplayString   (SIZE(0..255))
        MAX-ACCESS read-only
        STATUS     current
        DESCRIPTION  "The text message of the alarm."
        ::= { lumAlarmHistoryEntry 2 }

--
-- Alarm Traps
--
    lumAlarmSummaryChangeTrap  NOTIFICATION-TYPE
         OBJECTS { lumAlarmSummaryState,
                   lumAlarmSummaryCriticalStatus,
                   lumAlarmSummaryMajorStatus,
                   lumAlarmSummaryMinorStatus
                 }
        STATUS  current
        DESCRIPTION
                 "This notification is issued when the  Alarm Summary
                 information changes."
          ::= { lumAlarmV2Traps 1 }

 
END
