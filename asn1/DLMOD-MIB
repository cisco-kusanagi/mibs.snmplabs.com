DLMOD-MIB DEFINITIONS ::= BEGIN

IMPORTS
	Integer32 FROM SNMPv2-SMI
	OBJECT-TYPE
		FROM RFC-1212
	ucdavis
		FROM UCD-SNMP-MIB
	DisplayString
		FROM SNMPv2-TC;

dlmod OBJECT IDENTIFIER ::= { ucdavis 14 }

dlmodNextIndex OBJECT-TYPE 
	SYNTAX		Integer32
	MAX-ACCESS	read-only
	STATUS		current
	DESCRIPTION
		"The index number of next appropiate
		unassigned entry in dlmodTable"
	::= { dlmod 1 }

dlmodTable OBJECT-TYPE 
	SYNTAX		SEQUENCE OF DlmodEntry
	MAX-ACCESS	not-accessible
	STATUS		current
	DESCRIPTION
		"A list of dlmodEntry"
	::= { dlmod 2 }

dlmodEntry OBJECT-TYPE
	SYNTAX		DlmodEntry
	MAX-ACCESS	not-accessible
	STATUS		current
	DESCRIPTION
		"A list parameters of dynamic module"
	INDEX		{ dlmodIndex }
	::= { dlmodTable 1 }

DlmodEntry ::= SEQUENCE {
	dlmodIndex	INTEGER,
	dlmodName	DisplayString,
	dlmodPath	DisplayString,
	dlmodError	DisplayString,
	dlmodStatus	INTEGER
}

dlmodIndex OBJECT-TYPE
	SYNTAX		INTEGER (1..65535)
	MAX-ACCESS	read-only
	STATUS		current
	DESCRIPTION
		"An index that uniqely indenties an entry in dlmodTable"
	::= { dlmodEntry 1 }

dlmodName OBJECT-TYPE
	SYNTAX		DisplayString (SIZE (0..255))
	MAX-ACCESS	read-write
	STATUS		current
	DESCRIPTION
		"The module name"
	::= { dlmodEntry 2 }

dlmodPath OBJECT-TYPE
	SYNTAX		DisplayString (SIZE (0..255))
	MAX-ACCESS	read-write
	STATUS		current
	DESCRIPTION
		"The path of the module executable file"
	::= { dlmodEntry 3 } 

dlmodError OBJECT-TYPE
	SYNTAX		DisplayString (SIZE (0..255))
	MAX-ACCESS	read-only
	STATUS		current
	DESCRIPTION
		"The last error from dlmod_load_module"
	::= { dlmodEntry 4 }

dlmodStatus OBJECT-TYPE
	SYNTAX		INTEGER {
		loaded(1),
		unloaded(2),
		error(3),
		load(4),
		unload(5),
		create(6),
		delete(7)
	}
	MAX-ACCESS	read-write
	STATUS		current
	DESCRIPTION
		"Module status"
	::= { dlmodEntry 5 }
END
