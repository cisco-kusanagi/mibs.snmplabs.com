--******************************************************************
--*
--*         Copyright (c) 1993, 1999 by 3Com Corporation
--*                    All Rights Reserved
--*
--*    $Revision:   7.0  $
--*    $Date:   Jul 15 1999 11:54:24  $
--*
--*    3COM IPGW MIB
--*
--******************************************************************


IPGW-MIB DEFINITIONS ::= BEGIN

IMPORTS
   enterprises,
   experimental,
   IpAddress,
   TimeTicks,
   Gauge,
   Counter
      FROM RFC1155-SMI
   DisplayString
      FROM RFC1213-MIB
   OBJECT-TYPE
      FROM RFC-1212;


usr OBJECT IDENTIFIER ::= { enterprises 429 }

nas OBJECT IDENTIFIER ::= { usr 1 }

ipgw OBJECT IDENTIFIER ::= { nas 13 }

-- The IP Gateway Card Configuration Group.

ipgwCfg OBJECT IDENTIFIER ::= { ipgw 1 }

ipgwCfgTable OBJECT-TYPE
SYNTAX SEQUENCE OF IpgwCfgEntry
ACCESS not-accessible
STATUS mandatory
DESCRIPTION
"The IP Gateway Card Configuration Table contains an entry 
for each of the manageable IP Gateway Card in the chassis.  
It contains objects that reflect the current configuration 
of parameters that affect the operation of all the entities 
that reside on the given card."
::= { ipgwCfg 1 }

ipgwCfgEntry OBJECT-TYPE
SYNTAX IpgwCfgEntry
ACCESS not-accessible
STATUS mandatory
DESCRIPTION
"There is one IP Gateway Card Configuration table entry per 
IP Gateway Card in the chassis."
INDEX { ipgwCfgIndex }
::= { ipgwCfgTable 1 }

IpgwCfgEntry ::=
SEQUENCE {
ipgwCfgIndex
    INTEGER,
ipgwCfgLocalIpAdrs
    IpAddress,
ipgwCfgGatewayIpAdrs
    IpAddress,
ipgwCfgTrapDest
    INTEGER,
ipgwCfgGatewayNetMask
    IpAddress,
ipgwCfgEthnetFraming
    INTEGER,
ipgwCfgEthIfaceName
    DisplayString,
ipgwCfgDefMgmtStationIp
    IpAddress,
ipgwCfgDefCommStr
    DisplayString
}

ipgwCfgIndex OBJECT-TYPE
SYNTAX INTEGER
ACCESS read-only
STATUS mandatory
DESCRIPTION
"A unique value for each IP Gateway Card in the chassis.  
The value of ipgwCfgIndex matches the value of the index 
for the corresponding IP Gateway Card entity in the entity 
table of the chassis MIB."
::= { ipgwCfgEntry 1 }

ipgwCfgLocalIpAdrs OBJECT-TYPE
SYNTAX IpAddress
ACCESS read-write
STATUS mandatory
DESCRIPTION
"Specifies the local IP address used by the IP Gateway Card 
for management related access."
::= { ipgwCfgEntry 2 }

ipgwCfgGatewayIpAdrs OBJECT-TYPE
SYNTAX IpAddress
ACCESS read-write
STATUS mandatory
DESCRIPTION
"Specifies the IP address of the gateway for the IP Gateway 
card."
::= { ipgwCfgEntry 3 }

ipgwCfgTrapDest OBJECT-TYPE
SYNTAX INTEGER{
  nmc(1),
  local(2),
  both(3)
}
ACCESS read-write
STATUS mandatory
DESCRIPTION
"Specifies whether the IP Gateway Card sends SNMP traps to 
the NMC or only to its locally configured management 
stations. Default=local."
::= { ipgwCfgEntry 4 }

ipgwCfgGatewayNetMask OBJECT-TYPE
SYNTAX IpAddress
ACCESS read-write
STATUS mandatory
DESCRIPTION
"Specifies the subnet mask for the IP Gateway Card."
::= { ipgwCfgEntry 5 }

ipgwCfgEthnetFraming OBJECT-TYPE
SYNTAX INTEGER{
  snap(1),
  dix(2)
}
ACCESS read-write
STATUS mandatory
DESCRIPTION
"Specifies the type of ethernet framing used by the IP 
Gateway Card."
::= { ipgwCfgEntry 6 }

ipgwCfgEthIfaceName OBJECT-TYPE
SYNTAX DisplayString (SIZE(0..32))
ACCESS read-write
STATUS mandatory
DESCRIPTION
"Specifies the name of the ethernet interface that is to be 
used by the IP Gateway Card."
::= { ipgwCfgEntry 7 }

ipgwCfgDefMgmtStationIp OBJECT-TYPE
SYNTAX IpAddress
ACCESS read-write
STATUS mandatory
DESCRIPTION
"IP address of a management station allowed to manage the IP 
Gateway Card. Used with the community string for management 
security. Default =0.0.0.0."
::= { ipgwCfgEntry 8 }

ipgwCfgDefCommStr OBJECT-TYPE
SYNTAX DisplayString (SIZE(0..32))
ACCESS read-write
STATUS mandatory
DESCRIPTION
"Specifies the default SNMP community string to be used by a 
management station in communicating with the IP Gateway 
Card. Used with the default management station IP address 
for management security access."
::= { ipgwCfgEntry 9 }

-- The IP Gateway Card Command Group.

ipgwCmd OBJECT IDENTIFIER ::= { ipgw 3 }

ipgwCmdTable OBJECT-TYPE
SYNTAX SEQUENCE OF IpgwCmdEntry
ACCESS not-accessible
STATUS mandatory
DESCRIPTION
"The IP Card Command table contains an entry for each of the 
manageable IP Gateway Card in the chassis.  It provides a 
means through which to take specific actions on one or more 
IP Gateway cards in the NAS chassis."
::= { ipgwCmd 1 }

ipgwCmdEntry OBJECT-TYPE
SYNTAX IpgwCmdEntry
ACCESS not-accessible
STATUS mandatory
DESCRIPTION
"There is one IP Gateway Card Command entry per IP Gateway 
Card in the chassis."
INDEX { ipgwCmdIndex }
::= { ipgwCmdTable 1 }

IpgwCmdEntry ::=
SEQUENCE {
ipgwCmdIndex
    INTEGER,
ipgwCmdMgtStationId
    OCTET STRING,
ipgwCmdReqId
    INTEGER,
ipgwCmdFunction
    INTEGER,
ipgwCmdForce
    INTEGER,
ipgwCmdParam
    OCTET STRING,
ipgwCmdResult
    INTEGER,
ipgwCmdCode
    INTEGER
}

ipgwCmdIndex OBJECT-TYPE
SYNTAX INTEGER
ACCESS read-only
STATUS mandatory
DESCRIPTION
"A unique value for each IP Gateway Card in the chassis.  
The value of this object matches the value of the index of 
the correspond1ing IP Gateway Card's entry in the entity 
table of the chassis MIB."
::= { ipgwCmdEntry 1 }

ipgwCmdMgtStationId OBJECT-TYPE
SYNTAX OCTET STRING (SIZE(0..8))
ACCESS read-write
STATUS mandatory
DESCRIPTION
"This object is a generic read-write variable that a 
Management Station (MS) can use to guarantee that the 
results from a given command are the results of a command 
issued by that specific MS.  Each MS must SET a unique 
value to this object when doing commands and GET the value 
of this object together with ipgwCmdReqId and ipgwCmdResult 
to detect interference from other MSs."
::= { ipgwCmdEntry 2 }

ipgwCmdReqId OBJECT-TYPE
SYNTAX INTEGER
ACCESS read-only
STATUS mandatory
DESCRIPTION
"This object contains the value of the request-id field in 
the SNMP PDU which invoked the current or most recent 
command or test on this IP Gateway Card.  If the request-id 
is unknown or undefined, this object contains the value 
zero."
::= { ipgwCmdEntry 3 }

ipgwCmdFunction OBJECT-TYPE
SYNTAX INTEGER{
  noCommand(1),
  saveToNVRAM(2),
  restoreFromNVRAM(3),
  restoreFromDefault(4),
  nonDisruptSelfTest(5),
  disruptSelfTest(6),
  softwareReset(7),
  lanLoopBack(8),
  bulkfileUpload(9),
  bulkfileDownload(10)
}
ACCESS read-write
STATUS mandatory
DESCRIPTION
"This object contains a value which describes the command 
which is being invoked."
::= { ipgwCmdEntry 4 }

ipgwCmdForce OBJECT-TYPE
SYNTAX INTEGER{
  force(1),
  noForce(2)
}
ACCESS read-write
STATUS mandatory
DESCRIPTION
"In some cases, the IP Gateway Card may be in a state such 
that certain commands could adversely affect connections.  
In such cases, a command request with this object not 
present or set to noForce will result in a warning.  If the 
operator elects to ignore such warnings, this object can be 
set to force in a subsequent issue of the command to cause 
the command to be carried out regardless of its potentially 
hazzardous effects."
::= { ipgwCmdEntry 5 }

ipgwCmdParam OBJECT-TYPE
SYNTAX OCTET STRING
ACCESS read-write
STATUS mandatory
DESCRIPTION
"This object contains parameters that are specific to the 
particular command being issued.  In some cases, there will 
be no aditional parameters required."
::= { ipgwCmdEntry 6 }

ipgwCmdResult OBJECT-TYPE
SYNTAX INTEGER{
  none(1),
  success(2),
  inProgress(3),
  notSupported(4),
  unAbleToRun(5),
  aborted(6),
  failed(7)
}
ACCESS read-only
STATUS mandatory
DESCRIPTION
"This object contains the result of the most recently 
requested command or test, or the value none(1) if no 
commands have been requested since the last reset."
::= { ipgwCmdEntry 7 }

ipgwCmdCode OBJECT-TYPE
SYNTAX INTEGER{
  noError(1),
  unable(2),
  unrecognizedCommand(6),
  slotEmpty(8),
  noResponse(12),
  unsupportedCommand(20),
  deviceDisabled(22),
  testFailed(25),
  userInterfaceActive(58),
  pendingSoftwareDownload(73)
}
ACCESS read-only
STATUS mandatory
DESCRIPTION
"The value of this object upon command completion indicates 
a further description of what went wrong if the command was 
unsuccessful.  In the case of tests, a bit mapped result of 
each of the sub-tests performed can be found in the status 
table."
::= { ipgwCmdEntry 8 }

-- The IP Gateway Card Trap Enable Group

ipgwTrap OBJECT IDENTIFIER ::= { ipgw 4 }

ipgwTrapEnaTable OBJECT-TYPE
SYNTAX SEQUENCE OF IpgwTrapEnaEntry
ACCESS not-accessible
STATUS mandatory
DESCRIPTION
"Table containing objects to enable traps on the IP Gateway 
Cards in the chassis."
::= { ipgwTrap 1 }

ipgwTrapEnaEntry OBJECT-TYPE
SYNTAX IpgwTrapEnaEntry
ACCESS not-accessible
STATUS mandatory
DESCRIPTION
"There is one entry for each IP Gateway Card in the 
chassis."
INDEX { ipgwTrapEnaIndex }
::= { ipgwTrapEnaTable 1 }

IpgwTrapEnaEntry ::=
SEQUENCE {
ipgwTrapEnaIndex
    INTEGER,
ipgwTrapEnaUiReset
    INTEGER
}

ipgwTrapEnaIndex OBJECT-TYPE
SYNTAX INTEGER
ACCESS read-only
STATUS mandatory
DESCRIPTION
"A unique index identifying the IP Gateway Card to which the 
trap enable objects pertain."
::= { ipgwTrapEnaEntry 1 }

ipgwTrapEnaUiReset OBJECT-TYPE
SYNTAX INTEGER{
  enable(1),
  disable(2)
}
ACCESS read-write
STATUS mandatory
DESCRIPTION
"Enables reporting of traps for card reset requests 
initiated from the Gateway NAC user interface."
::= { ipgwTrapEnaEntry 2 }

END
