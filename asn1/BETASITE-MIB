BETASITE-MIB DEFINITIONS ::= BEGIN
	IMPORTS
          OBJECT-TYPE, MODULE-IDENTITY, NOTIFICATION-TYPE,
          OBJECT-IDENTITY, Integer32
               	FROM SNMPv2-SMI
          common
                FROM USR-DEFINITIONS-MIB;
    usrBetaSite MODULE-IDENTITY
         LAST-UPDATED "200204161530Z"
         ORGANIZATION "CommWorks Corporation, a 3Com Company"
         CONTACT-INFO "Customer Support"
         DESCRIPTION
                 "The commWorks enterprise defined MIB objects
                  Beta Site specific objects."
--       REVISION        "200204161530Z"
--       DESCRIPTION "Converted to SNMPv2"
         ::= { common 76 }
   -- textual conventions
   -- 
   -- textual conventions are like pre-processor macro in 'C'
   --        (i.e. #define statements)
   -- Use them to define your own 'datatypes'
   -- Begin managed object definitions here...
    usrBetaObjs  OBJECT IDENTIFIER ::= { usrBetaSite 1 }
    usrBetaTraps OBJECT IDENTIFIER ::= { usrBetaSite 2 }
    usrChassisActiveCalls  OBJECT-TYPE
         SYNTAX  Integer32
         MAX-ACCESS  read-only
         STATUS  current
         DESCRIPTION
             "The number of active calls on the chassis at that moment."
         ::= { usrBetaObjs 1 }
    usrChassisTotalPorts  OBJECT-TYPE
         SYNTAX  Integer32
         MAX-ACCESS  read-only
         STATUS  current
         DESCRIPTION
             "The number of ports in the chassis."
         ::= { usrBetaObjs 2 }
    usrChassisPortUtilization  OBJECT-TYPE
         SYNTAX  Integer32
         MAX-ACCESS  read-only
         STATUS  current
         DESCRIPTION
             "The percent utilization of the modem ports in the chassis."
         ::= { usrBetaObjs 3 }
    usrChassisCallsInLast24Hrs  OBJECT-TYPE
         SYNTAX  Integer32
         MAX-ACCESS  read-only
         STATUS  current
         DESCRIPTION
             "The number of calls answered by the Hiper in last 24 hours."
         ::= { usrBetaObjs 4 }
    usrRouterMemoryUtilization  OBJECT-TYPE
         SYNTAX  Integer32
         MAX-ACCESS  read-only
         STATUS  current
         DESCRIPTION
             "The memory utilization of the system."
         ::= { usrBetaObjs 5 }
    usrRouterUptime  OBJECT-TYPE
         SYNTAX  OCTET STRING (SIZE(0..400)) 
         MAX-ACCESS  read-only
         STATUS  current
         DESCRIPTION
             "The router uptime."
         ::= { usrBetaObjs 6 }
    usrRouterCodeVersion  OBJECT-TYPE
         SYNTAX  OCTET STRING (SIZE(0..400)) 
         MAX-ACCESS  read-only
         STATUS  current
         DESCRIPTION
             "The code version of Hiper Access Router Card."
         ::= { usrBetaObjs 7 }
    usrRouterEthInterfaceIngressPkts  OBJECT-TYPE
         SYNTAX  Integer32
         MAX-ACCESS  read-only
         STATUS  current
         DESCRIPTION
             "The aggregate number of incoming packets on all ethernet interfaces."
         ::= { usrBetaObjs 8 }
    usrRouterEthInterfaceEgressPkts  OBJECT-TYPE
         SYNTAX  Integer32
         MAX-ACCESS  read-only
         STATUS  current
         DESCRIPTION
             "The aggregate number of outgoing packets on all ethernet interfaces."
         ::= { usrBetaObjs 9 }
    usrBetaTrapsV2  OBJECT-IDENTITY
        STATUS      current
        DESCRIPTION 
            " The events for the Beta Site MIB. "
        ::= { usrBetaTraps 0 }
    usrBetaInfoTrap NOTIFICATION-TYPE
        OBJECTS {
    		usrChassisActiveCalls, 
    		usrChassisTotalPorts, 
    		usrChassisPortUtilization, 
    		usrChassisCallsInLast24Hrs,
    		usrRouterMemoryUtilization, 
    		usrRouterUptime,
    		usrRouterCodeVersion,
    		usrRouterEthInterfaceIngressPkts,
    		usrRouterEthInterfaceEgressPkts
        }
        STATUS current
        DESCRIPTION     
            "This trap is generated periodically from the Beta sites
             and passed on to the 3Com Trap server so that performance
             of beta code can be monitored closely."
        --#TYPE     "Betasite Information"
        --#SUMMARY  "Betasite Statistics:- Active Calls %d; TotalPorts %d; PortUtilization %d;\nCallsInLast24Hors %d; MemoryUtilization %d; Uptime %d; CodeVersion %d;\n IngressPackets %d; Egress Packets %d"
        --#ARGUMENTS { 0 1 2 3 4 5 6 7 8 }
        --#SEVERITY INFORMATIONAL
        --#STATE    NONOPERATIONAL
        --#PROBABLECAUSE ""
        ::= { usrBetaTrapsV2 1 }
    usrHealthTrapState  OBJECT-TYPE
         SYNTAX  INTEGER {
		enabled(1), 
		disabled(2) 
		}
         MAX-ACCESS  read-write
         STATUS  current
         DESCRIPTION
             "Whether the Health Trap is enabled or disabled."
	 DEFVAL { disabled }
	 --CONFIGURABLE
         ::= { usrBetaObjs 10 }
    usrHealthTrapInterval  OBJECT-TYPE
         SYNTAX  Integer32 (1..1440)
         MAX-ACCESS  read-write
         STATUS  current
         DESCRIPTION
             "The frequency in minutes the Health Trap is sent out."
	 DEFVAL { 60 }
	 --CONFIGURABLE
         ::= { usrBetaObjs 11 }
END         -- End USRBETA-MIB definitions
