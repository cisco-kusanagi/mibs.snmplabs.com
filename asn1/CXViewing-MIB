-- Memotec Enterprise CX PRODUCT MIB
-- March1994
-- Revision 1.0
-- C. Rocray and C. Poirier 

CXViewing-MIB DEFINITIONS ::= BEGIN

IMPORTS
  OBJECT-TYPE	
    FROM RFC-1212
 IpAddress
    FROM RFC1155-SMI
 cxViewing
    FROM CXProduct-SMI;

cxViewTable OBJECT-TYPE
	SYNTAX SEQUENCE OF CxViewEntry
	ACCESS not-accessible
	STATUS mandatory
	DESCRIPTION
"The View table."
	::= { cxViewing 1 }

cxViewEntry OBJECT-TYPE
	SYNTAX CxViewEntry
	ACCESS not-accessible
	STATUS mandatory
	DESCRIPTION
"Information of views between managers and sub-systems "
	INDEX { cxViewConsoleAddress }
	::= { cxViewTable 1 }

CxViewEntry ::= SEQUENCE {
	cxViewConsoleAddress 
		IpAddress,
	cxViewCurrent	
		INTEGER
	}

cxViewConsoleAddress OBJECT-TYPE
	SYNTAX IpAddress
	ACCESS read-only
	STATUS mandatory
	DESCRIPTION
"The address of a console. 0 is reserved for a local console "
	::= { cxViewEntry 1 }

cxViewCurrent OBJECT-TYPE
	SYNTAX INTEGER (0..16)
	ACCESS write-only
	STATUS mandatory
	DESCRIPTION
"The slot number where a sub-system sits. 0 is reserved for the sub-system 
where the master NME sites. Only the manager whose address matches the 
above address can set (or change) the value"
	::= { cxViewEntry 2 }

cxViewNMEStatus OBJECT-TYPE
	SYNTAX  INTEGER (0..16)
	ACCESS  read-write
	STATUS  mandatory
	DESCRIPTION
"Indicates if the CPU card try to get the control of management and act as 
a chassis server. The election mechanism needs that."
	::= { cxViewing 2 }

cxViewNMEMode OBJECT-TYPE
	SYNTAX  INTEGER {
			slave	(1),
			master	(2)
			}

	ACCESS  read-only
	STATUS  mandatory
	DESCRIPTION
"Indicates if the CPU card got the control of chassis management and act 
as a chassis server."
	::= { cxViewing 3 }

END
