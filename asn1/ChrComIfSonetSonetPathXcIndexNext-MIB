ChrComIfSonetSonetPathXcIndexNext-MIB

--FORCE-INCLUDE	<mib.h>
--FORCE-INCLUDE	<snmpdefs.h>
--FORCE-INCLUDE	"mibhand.h"

	DEFINITIONS  ::=  BEGIN

IMPORTS
	OBJECT-TYPE, Counter32			FROM  SNMPv2-SMI
	Integer32, Unsigned32			FROM  SNMPv2-SMI
	chrComIfSonet				FROM  Chromatis-MIB;

-- chrComIfSonetSonetPathXcIndexNext Table

chrComIfSonetSonetPathXcIndexNextTable		OBJECT-TYPE
    SYNTAX         INTEGER (0..2147483647)
    MAX-ACCESS     read-only
	STATUS		current
	DESCRIPTION
	"SonetPathXcIndexNext"
--DEFAULT  get-function-async  MNIL_atmVcCrossConnectIndexNext_GetRoutine
--DEFAULT  set-function-async  MNIL_atmVcCrossConnectIndexNext_SetRoutine
--DEFAULT  next-function-async MNIL_atmVcCrossConnectIndexNext_NextRoutine
--DEFAULT  test-function-async MNIL_atmVcCrossConnectIndexNext_TestRoutine
--DEFAULT  cookie "SonetPathXcIndexNext"
	::= { chrComIfSonet 8}




END
