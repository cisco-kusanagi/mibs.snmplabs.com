TERAWAVE-ces-MIB DEFINITIONS ::= BEGIN
        -- Created by sml2mib compiler 
        IMPORTS

 enterprises,  OBJECT-TYPE,  Counter,  Gauge,  TimeTicks
        FROM RFC1155-SMI
	Gauge32, Counter32 FROM SNMPv2-SMI;

atmForum OBJECT IDENTIFIER ::=  { enterprises 353 }

atmForumNetworkManagment OBJECT IDENTIFIER ::=  { atmForum 5 }

atmfCESmib OBJECT IDENTIFIER ::=  { atmForumNetworkManagment 2 }

atmfCES OBJECT IDENTIFIER ::=  { atmfCESmib 2 }

atmfCESObjects OBJECT IDENTIFIER ::=  { atmfCES 1 }

     -- atmfCESConTable

atmfCESConTable OBJECT-TYPE
     SYNTAX SEQUENCE OF AtmfCESConTableEntryType
     ACCESS not-accessible
     STATUS mandatory
     DESCRIPTION
          " table atmfCESConTable"
     ::= { atmfCESObjects 1 }

atmfCESConTableEntry OBJECT-TYPE
          SYNTAX AtmfCESConTableEntryType
          ACCESS not-accessible
          STATUS mandatory
          DESCRIPTION
               " table entry atmfCESConTableEntry "
          INDEX {                   atmfCESCbrIndex }
     ::= { atmfCESConTable 1 }

AtmfCESConTableEntryType ::= SEQUENCE {
          atmfCESCbrIndex   
             INTEGER,
          atmfCESAtmIndex   
             INTEGER,
          atmfCESAtmVpi   
             INTEGER (0..4095),
          atmfCESAtmVci   
             INTEGER (0..65535),
          atmfCESCbrService   
             INTEGER,
          atmfCESCbrClockMode   
             INTEGER,
          atmfCESCas   
             INTEGER,
          atmfCESPartialFill   
             INTEGER (0..47),
          atmfCESBufMaxSize   
             INTEGER (1..510),
          atmfCESCdvtRxT   
             INTEGER (1..65535),
          atmfCESCellLossIntegrationPeriod   
             INTEGER (1000..65535),
          atmfCESConnType   
             INTEGER,
          atmfCESLocalAddr   
             OCTET STRING,
          atmfCESAdminStatus   
             INTEGER,
          atmfCESOperStatus   
             INTEGER,
          atmCESConfRowStatus   
             INTEGER
}

atmfCESCbrIndex OBJECT-TYPE
          SYNTAX INTEGER
          ACCESS read-only
          STATUS mandatory
          DESCRIPTION
               ""
          ::= { atmfCESConTableEntry 1 }

atmfCESAtmIndex OBJECT-TYPE
          SYNTAX INTEGER
          ACCESS read-write
          STATUS mandatory
          DESCRIPTION
               ""
          ::= { atmfCESConTableEntry 2 }

atmfCESAtmVpi OBJECT-TYPE
          SYNTAX INTEGER (0..4095)
          ACCESS read-write
          STATUS mandatory
          DESCRIPTION
               ""
          ::= { atmfCESConTableEntry 3 }

atmfCESAtmVci OBJECT-TYPE
          SYNTAX INTEGER (0..65535)
          ACCESS read-write
          STATUS mandatory
          DESCRIPTION
               ""
          ::= { atmfCESConTableEntry 4 }

atmfCESCbrService OBJECT-TYPE
          SYNTAX INTEGER
                  {
                  unstructured(1),
                  structured(2)
                  }
          ACCESS read-write
          STATUS mandatory
          DESCRIPTION
               ""
          ::= { atmfCESConTableEntry 5 }

atmfCESCbrClockMode OBJECT-TYPE
          SYNTAX INTEGER
                  {
                  synchronous(1),
                  srts(2),
                  adaptive(3),
                  looped(4)
                  }
          ACCESS read-write
          STATUS mandatory
          DESCRIPTION
               ""
          ::= { atmfCESConTableEntry 6 }

atmfCESCas OBJECT-TYPE
          SYNTAX INTEGER
                  {
                  basic(1),
                  e1Cas(2),
                  ds1SfCas(3),
                  ds1EsfCas(4),
                  j2Cas(5)
                  }
          ACCESS read-write
          STATUS mandatory
          DESCRIPTION
               ""
          ::= { atmfCESConTableEntry 7 }

atmfCESPartialFill OBJECT-TYPE
          SYNTAX INTEGER (0..47)
          ACCESS read-write
          STATUS mandatory
          DESCRIPTION
               ""
          ::= { atmfCESConTableEntry 8 }

atmfCESBufMaxSize OBJECT-TYPE
          SYNTAX INTEGER (1..510)
          ACCESS read-write
          STATUS mandatory
          DESCRIPTION
               ""
          ::= { atmfCESConTableEntry 9 }

atmfCESCdvtRxT OBJECT-TYPE
          SYNTAX INTEGER (1..65535)
          ACCESS read-write
          STATUS mandatory
          DESCRIPTION
               ""
          ::= { atmfCESConTableEntry 10 }

atmfCESCellLossIntegrationPeriod OBJECT-TYPE
          SYNTAX INTEGER (1000..65535)
          ACCESS read-write
          STATUS mandatory
          DESCRIPTION
               ""
          ::= { atmfCESConTableEntry 11 }

atmfCESConnType OBJECT-TYPE
          SYNTAX INTEGER
                  {
                  other(1),
                  pvc(2),
                  activeSvc(3),
                  passiveSvc(4)
                  }
          ACCESS read-write
          STATUS mandatory
          DESCRIPTION
               ""
          ::= { atmfCESConTableEntry 12 }

atmfCESLocalAddr OBJECT-TYPE
          SYNTAX OCTET STRING
          ACCESS read-write
          STATUS mandatory
          DESCRIPTION
               ""
          ::= { atmfCESConTableEntry 13 }

atmfCESAdminStatus OBJECT-TYPE
          SYNTAX INTEGER
                  {
                  up(1),
                  down(2)
                  }
          ACCESS read-write
          STATUS mandatory
          DESCRIPTION
               ""
          ::= { atmfCESConTableEntry 14 }

atmfCESOperStatus OBJECT-TYPE
          SYNTAX INTEGER
                  {
                  up(1),
                  down(2),
                  unknown(3)
                  }
          ACCESS read-only
          STATUS mandatory
          DESCRIPTION
               ""
          ::= { atmfCESConTableEntry 15 }

atmCESConfRowStatus OBJECT-TYPE
          SYNTAX INTEGER
                  {
                  active(1),
                  notInService(2),
                  notReady(3),
                  createAndGo(4),
                  createAndWait(5),
                  destroy(6)
                  }
          ACCESS read-write
          STATUS mandatory
          DESCRIPTION
               ""
          ::= { atmfCESConTableEntry 16 }

     -- atmfCESMappingTable

atmfCESMappingTable OBJECT-TYPE
     SYNTAX SEQUENCE OF AtmfCESMappingTableEntryType
     ACCESS not-accessible
     STATUS mandatory
     DESCRIPTION
          " table atmfCESMappingTable"
     ::= { atmfCESObjects 2 }

atmfCESMappingTableEntry OBJECT-TYPE
          SYNTAX AtmfCESMappingTableEntryType
          ACCESS not-accessible
          STATUS mandatory
          DESCRIPTION
               " table entry atmfCESMappingTableEntry "
          INDEX {                   atmfCESAtmIndex,                  atmfCESAtmVpi,                  atmfCESAtmVci }
     ::= { atmfCESMappingTable 1 }

AtmfCESMappingTableEntryType ::= SEQUENCE {
          atmfCESMappingCbrIndex   
             INTEGER
}

atmfCESMappingCbrIndex OBJECT-TYPE
          SYNTAX INTEGER
          ACCESS read-only
          STATUS mandatory
          DESCRIPTION
               ""
          ::= { atmfCESMappingTableEntry 1 }

     -- atmfCESStatsTable

atmfCESStatsTable OBJECT-TYPE
     SYNTAX SEQUENCE OF AtmfCESStatsTableEntryType
     ACCESS not-accessible
     STATUS mandatory
     DESCRIPTION
          " table atmfCESStatsTable"
     ::= { atmfCESObjects 3 }

atmfCESStatsTableEntry OBJECT-TYPE
          SYNTAX AtmfCESStatsTableEntryType
          ACCESS not-accessible
          STATUS mandatory
          DESCRIPTION
               " table entry atmfCESStatsTableEntry "
          INDEX {                   atmfCESCbrIndex }
     ::= { atmfCESStatsTable 1 }

AtmfCESStatsTableEntryType ::= SEQUENCE {
          atmfCESReassCells   
             Counter32,
          atmfCESHdrErrors   
             Counter32,
          atmfCESPointerReframes   
             Counter32,
          atmfCESPointerParityErrors   
             Counter32,
          atmfCESAal1SeqErrors   
             Counter32,
          atmfCESLostCells   
             Counter32,
          atmfCESMisinsertedCells   
             Counter32,
          atmfCESBufUnderflows   
             Counter32,
          atmfCESBufOverflows   
             Counter32,
          atmfCESCellLossStatus   
             INTEGER
}

atmfCESReassCells OBJECT-TYPE
          SYNTAX Counter32
          ACCESS read-only
          STATUS mandatory
          DESCRIPTION
               ""
          ::= { atmfCESStatsTableEntry 1 }

atmfCESHdrErrors OBJECT-TYPE
          SYNTAX Counter32
          ACCESS read-only
          STATUS mandatory
          DESCRIPTION
               ""
          ::= { atmfCESStatsTableEntry 2 }

atmfCESPointerReframes OBJECT-TYPE
          SYNTAX Counter32
          ACCESS read-only
          STATUS mandatory
          DESCRIPTION
               ""
          ::= { atmfCESStatsTableEntry 3 }

atmfCESPointerParityErrors OBJECT-TYPE
          SYNTAX Counter32
          ACCESS read-only
          STATUS mandatory
          DESCRIPTION
               ""
          ::= { atmfCESStatsTableEntry 4 }

atmfCESAal1SeqErrors OBJECT-TYPE
          SYNTAX Counter32
          ACCESS read-only
          STATUS mandatory
          DESCRIPTION
               ""
          ::= { atmfCESStatsTableEntry 5 }

atmfCESLostCells OBJECT-TYPE
          SYNTAX Counter32
          ACCESS read-only
          STATUS mandatory
          DESCRIPTION
               ""
          ::= { atmfCESStatsTableEntry 6 }

atmfCESMisinsertedCells OBJECT-TYPE
          SYNTAX Counter32
          ACCESS read-only
          STATUS mandatory
          DESCRIPTION
               ""
          ::= { atmfCESStatsTableEntry 7 }

atmfCESBufUnderflows OBJECT-TYPE
          SYNTAX Counter32
          ACCESS read-only
          STATUS mandatory
          DESCRIPTION
               ""
          ::= { atmfCESStatsTableEntry 8 }

atmfCESBufOverflows OBJECT-TYPE
          SYNTAX Counter32
          ACCESS read-only
          STATUS mandatory
          DESCRIPTION
               ""
          ::= { atmfCESStatsTableEntry 9 }

atmfCESCellLossStatus OBJECT-TYPE
          SYNTAX INTEGER
                  {
                  noloss(1),
                  loss(2)
                  }
          ACCESS read-only
          STATUS mandatory
          DESCRIPTION
               ""
          ::= { atmfCESStatsTableEntry 10 }

     -- atmfCESActiveSvcTable

atmfCESActiveSvcTable OBJECT-TYPE
     SYNTAX SEQUENCE OF AtmfCESActiveSvcTableEntryType
     ACCESS not-accessible
     STATUS mandatory
     DESCRIPTION
          " table atmfCESActiveSvcTable"
     ::= { atmfCESObjects 4 }

atmfCESActiveSvcTableEntry OBJECT-TYPE
          SYNTAX AtmfCESActiveSvcTableEntryType
          ACCESS not-accessible
          STATUS mandatory
          DESCRIPTION
               " table entry atmfCESActiveSvcTableEntry "
          INDEX {                   atmfCESCbrIndex }
     ::= { atmfCESActiveSvcTable 1 }

AtmfCESActiveSvcTableEntryType ::= SEQUENCE {
          atmfCESRemoteAddr   
             OCTET STRING,
          atmfCESFirstRetryInterval   
             INTEGER (1..3600),
          atmfCESRetryTimer   
             INTEGER (0..86400),
          atmfCESRetryLimit   
             INTEGER (0..65535),
          atmfCESRetryFailures   
             Gauge32,
          atmfCESActiveSvcRestart   
             INTEGER,
          atmfCESActiveSvcOperStatus   
             INTEGER,
          atmfCESLastReleaseCause   
             INTEGER (1..127),
          atmfCESLastReleaseDiagnostics   
             OCTET STRING
}

atmfCESRemoteAddr OBJECT-TYPE
          SYNTAX OCTET STRING
          ACCESS read-write
          STATUS mandatory
          DESCRIPTION
               ""
          ::= { atmfCESActiveSvcTableEntry 1 }

atmfCESFirstRetryInterval OBJECT-TYPE
          SYNTAX INTEGER (1..3600)
          ACCESS read-write
          STATUS mandatory
          DESCRIPTION
               ""
          ::= { atmfCESActiveSvcTableEntry 2 }

atmfCESRetryTimer OBJECT-TYPE
          SYNTAX INTEGER (0..86400)
          ACCESS read-only
          STATUS mandatory
          DESCRIPTION
               ""
          ::= { atmfCESActiveSvcTableEntry 3 }

atmfCESRetryLimit OBJECT-TYPE
          SYNTAX INTEGER (0..65535)
          ACCESS read-write
          STATUS mandatory
          DESCRIPTION
               ""
          ::= { atmfCESActiveSvcTableEntry 4 }

atmfCESRetryFailures OBJECT-TYPE
          SYNTAX Gauge32
          ACCESS read-only
          STATUS mandatory
          DESCRIPTION
               ""
          ::= { atmfCESActiveSvcTableEntry 5 }

atmfCESActiveSvcRestart OBJECT-TYPE
          SYNTAX INTEGER
                  {
                  restart(1),
                  noop(2)
                  }
          ACCESS read-write
          STATUS mandatory
          DESCRIPTION
               ""
          ::= { atmfCESActiveSvcTableEntry 6 }

atmfCESActiveSvcOperStatus OBJECT-TYPE
          SYNTAX INTEGER
          ACCESS read-only
          STATUS mandatory
          DESCRIPTION
               ""
          ::= { atmfCESActiveSvcTableEntry 7 }

atmfCESLastReleaseCause OBJECT-TYPE
          SYNTAX INTEGER (1..127)
          ACCESS read-only
          STATUS mandatory
          DESCRIPTION
               ""
          ::= { atmfCESActiveSvcTableEntry 8 }

atmfCESLastReleaseDiagnostics OBJECT-TYPE
          SYNTAX OCTET STRING
          ACCESS read-only
          STATUS mandatory
          DESCRIPTION
               ""
          ::= { atmfCESActiveSvcTableEntry 9 }

END
