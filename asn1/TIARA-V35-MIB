-- *****************************************************************
-- tiaranet-v35.mib:  Tiara Networks V35 MIB
--
-- April,1st 1998, Shyla
--
-- Copyright (c) 1998-2000 by Tiara Networks, Inc.
-- All rights reserved.
--
-- *****************************************************************

TIARA-V35-MIB DEFINITIONS ::= BEGIN

IMPORTS
     MODULE-IDENTITY, OBJECT-TYPE,
        Integer32,Counter32       FROM SNMPv2-SMI
--     TruthValue                 FROM SNMPv2-TC
     TRAP-TYPE                    FROM RFC-1215
     tiaraInterfaces              FROM TIARA-NETWORKS-SMI;

tiaraV35Mib MODULE-IDENTITY
    LAST-UPDATED "0008180000Z"
    ORGANIZATION "Tiara Networks Inc."
    CONTACT-INFO
                	     "Tiara Networks
                        Customer Support

                        525 Race Street, Suite 100,
                        San Jose, CA 95126
                        USA

                   	Tel: +1 408-216-4700
                   	Fax: +1 408-216-4701

                		Email: support@tiaranetworks.com"

    DESCRIPTION
            "MIB definitions for Tiara V35 module."
    REVISION "0008180000Z"
    DESCRIPTION
            "Initial revision."
    ::= { tiaraInterfaces 3 }

v35Traps OBJECT IDENTIFIER ::= {tiaraV35Mib 3}
v35TrapVariables OBJECT IDENTIFIER ::= {v35Traps 1}

-- v35ConfigTable definitions.

v35ConfigTable    	OBJECT-TYPE
    SYNTAX        	SEQUENCE OF V35ConfigTableEntry
    MAX-ACCESS    	not-accessible
    STATUS        	current
    DESCRIPTION   	"Tiara Networks V35 interface-related
                   	configurable parameters are listed in 
				this table."
    ::= {tiaraV35Mib 1}

v35ConfigTableEntry 	OBJECT-TYPE
    SYNTAX        	V35ConfigTableEntry
    MAX-ACCESS    	not-accessible
    STATUS        	current
    DESCRIPTION   	"V35 table entry."
    INDEX 			{v35IfIndex}
    ::= {v35ConfigTable 1}

V35ConfigTableEntry ::= SEQUENCE {
    v35IfIndex            INTEGER,
    v35ConfigClockRate    Integer32 (1000000 .. 8000000),
    v35ConfigClockSource  INTEGER,
    v35ConfigMode         INTEGER,
    v35ConfigCRC          INTEGER,
    v35ConfigDataMode     INTEGER,
    v35ConfigFlowControl  INTEGER
    }


v35IfIndex         	OBJECT-TYPE
    SYNTAX         	INTEGER
    MAX-ACCESS     	not-accessible
    STATUS         	current 
    DESCRIPTION    	"An integer value that is an index in the 
				entries of the ifTable (MIB-II) with a 
				V.35 interface type."
                   
    ::= {v35ConfigTableEntry 1}
    

v35ConfigClockRate 	OBJECT-TYPE
    SYNTAX         	Integer32(1000000 .. 8000000)
    MAX-ACCESS     	read-write
    STATUS         	current
    DESCRIPTION    	"Configures the clock rate for V35."
    DEFVAL 			{8000000}
    ::= {v35ConfigTableEntry 2}   

v35ConfigClockSource 	OBJECT-TYPE
    SYNTAX         	INTEGER
                  	{ internal(1),
                     	  line (2)
                   	}
    MAX-ACCESS     	read-write 
    STATUS         	current 
    DESCRIPTION    	"Configures the clock source for V35. 
				It can be either internal or line."

    DEFVAL 			{line}
    ::= {v35ConfigTableEntry 3}

v35ConfigMode 		OBJECT-TYPE   
    SYNTAX         	INTEGER
                   	{ dce(1),
                     	  dte(2)
                   	}
    MAX-ACCESS     	read-write
    STATUS         	current
    DESCRIPTION    	"Configures the mode for V35 to be either 
				dce or dte."

    DEFVAL 			{dte}
    ::= {v35ConfigTableEntry 4}

v35ConfigCRC 		OBJECT-TYPE   
    SYNTAX         	INTEGER
                   	{ crc16(1),
                     	  crc32(2)
                   	}
    MAX-ACCESS     	read-write
    STATUS         	current
    DESCRIPTION    	"Configures the cyclic redundancy check 
				for V35 to be either 16 or 32 bits."

    DEFVAL 			{crc32}
    ::= {v35ConfigTableEntry 5}

v35ConfigDataMode 	OBJECT-TYPE
    SYNTAX         	INTEGER
                   	{
                        	normal(1),
                        	inverted(2)
                   	}
    MAX-ACCESS     	read-write
    STATUS         	current
    DESCRIPTION    	"Configures the data for V.35 to be either
				normal or inverted."
    DEFVAL 			{normal}
    ::= {v35ConfigTableEntry 6}

v35ConfigFlowControl 	OBJECT-TYPE
    SYNTAX         	INTEGER
                   	{
                        	off(1),
                        	on(2)
                   	}
    MAX-ACCESS     	read-write
    STATUS         	current
    DESCRIPTION    	"Configures the hardware flow control for
				V.35 to be either on or off."
    DEFVAL 			{off}
    ::= {v35ConfigTableEntry 7}

   
-- v35StatsTable definition

v35StatsTable     	OBJECT-TYPE
    SYNTAX        	SEQUENCE OF V35StatsTableEntry
    MAX-ACCESS    	not-accessible
    STATUS        	current
    DESCRIPTION   	"Tiara Networks V35 interface-related
                   	status variables are listed in this table."
    ::= {tiaraV35Mib 2}

v35StatsTableEntry 	OBJECT-TYPE
    SYNTAX        	V35StatsTableEntry
    MAX-ACCESS    	not-accessible
    STATUS        	current
    DESCRIPTION   	"V35 statistics table entry."
    INDEX 			{v35IfIndex}
    ::= {v35StatsTable 1}

V35StatsTableEntry ::= SEQUENCE {
    v35StatsAlarmStatus    BITS,
    v35StatsFramesIn       Counter32,
    v35StatsFramesOut      Counter32,
    v35StatsOctetsIn       Counter32,
    v35StatsOctetsOut      Counter32,
    v35StatsCRCErrors      Counter32
    }

v35StatsAlarmStatus 	OBJECT-TYPE
    SYNTAX         	BITS
                    	{
                        v35-no-alarms(0),
                        v35-alarms-DTR(1),
                        v35-alarms-DSR(2),
                        v35-alarms-ST(3),
                        v35-alarms-CTS(4),
                        v35-alarms-RTS(5)
                    	}
    MAX-ACCESS     	read-only
    STATUS         	current
    DESCRIPTION    	"Specifies the status of the V35 alarm. If
				the bit is set, it indicates that the alarm
                    	state is on. Alarm bits are mode dependent;
                    	they are interpreted as follows:
                    
				v35-alarms-DTR  - DTR not received from DTE 
							(V.35 is DCE)
                    	v35-alarms-DSR  - DSR not received from DCE 
							(V.35 is DTE)
                    	v35-alarms-ST   - V.35 adaptor driving ST   
							(V.35 is DCE)
                    	v35-alarms-CTS  - CTS not received from DCE 
							(V.35 is DTE)
                    	v35-alarms-RTS  - RTS not received from DTE 
							(V.35 is DCE)
                    	"

    ::= {v35StatsTableEntry 1}

v35StatsFramesIn 		OBJECT-TYPE
    SYNTAX         	Counter32
    MAX-ACCESS     	read-only
    STATUS         	current
    DESCRIPTION    	"Specifies the number of incoming frames."

    ::= {v35StatsTableEntry 2}


v35StatsFramesOut 	OBJECT-TYPE
    SYNTAX         	Counter32
    MAX-ACCESS     	read-only
    STATUS         	current
    DESCRIPTION    	"Specifies the number of outgoing frames."

    ::= {v35StatsTableEntry 3}

v35StatsOctetsIn 		OBJECT-TYPE
    SYNTAX         	Counter32
    MAX-ACCESS     	read-only
    STATUS         	current
    DESCRIPTION    	"Specifies the number of incoming octets."

    ::= {v35StatsTableEntry 4}

v35StatsOctetsOut 	OBJECT-TYPE
    SYNTAX         	Counter32
    MAX-ACCESS     	read-only
    STATUS         	current
    DESCRIPTION    	"Specifies the number of outgoing octets."

    ::= {v35StatsTableEntry 5}

v35StatsCRCErrors 	OBJECT-TYPE
    SYNTAX         	Counter32
    MAX-ACCESS     	read-only
    STATUS         	current
    DESCRIPTION    	"Specifies the number of CRC errors that have 
				been identified so far."

    ::= {v35StatsTableEntry 6}

-- V35 alarm trap variable definitions.

v35SlotNumber  		OBJECT-TYPE
    SYNTAX          	INTEGER
    MAX-ACCESS      	not-accessible
    STATUS          	current
    DESCRIPTION     	"This V35 trap variable specifies the 
                     	slot number of the V35 interface."
    ::= {v35TrapVariables 1}
 
v35AlarmType  		OBJECT-TYPE
    SYNTAX         	INTEGER
                   	{
                     	v35-alarm-DTR (1),
                     	v35-alarm-DSR (2),
                     	v35-alarm-ST (3),
                     	v35-alarm-CTS (4),
                     	v35-alarm-RTS (5)
                   	}
    MAX-ACCESS     	not-accessible
    STATUS         	current
    DESCRIPTION    	"This V35 alarm type specifies the 
                    	type of the alarm trap generated by the agent 
                    	for the V35 interface. Alarm bits are mode 
				dependent; they are interpreted as follows:
                    	
				v35-alarms-DTR  - DTR not received from DTE 
							(V.35 is DCE)
                    	v35-alarms-DSR  - DSR not received from DCE 
							(V.35 is DTE)
                    	v35-alarms-ST   - V.35 adaptor driving ST   
							(V.35 is DCE)
                    	v35-alarms-CTS  - CTS not received from DCE 
							(V.35 is DTE)
                    	v35-alarms-RTS - RTS not received from DTE 
							(V.35 is DCE)
                    	"
    ::= {v35TrapVariables 2}

v35AlarmOnTrap  		TRAP-TYPE
    ENTERPRISE       	v35Traps
    VARIABLES       	{
                      	  v35IfIndex,
                       	  v35AlarmType
                     	}
    DESCRIPTION      	"V35 alarm traps for the Alarm On state."
             --#TYPE "V35 Alarm On state"
             --#SUMMARY "V35 Alarm On trap sent from Interface index: %s with the Alarm type: %s"
             --#ARGUMENTS {0,1}
             --#SEVERITY MAJOR       
   
    ::= 1 

v35AlarmOffTrap  		TRAP-TYPE
    ENTERPRISE       	v35Traps
    VARIABLES        	{
                       	  v35IfIndex,
                       	  v35AlarmType
                     	}
    DESCRIPTION      	"V35 alarm traps for the Alarm Off state."
             --#TYPE "V35 Alarm Off state"
             --#SUMMARY "V35 Alarm Off trap sent from Interface index: %s with the Alarm type: %s"
             --#ARGUMENTS {0,1}
             --#SEVERITY NORMAL   
    ::= 2 


END
