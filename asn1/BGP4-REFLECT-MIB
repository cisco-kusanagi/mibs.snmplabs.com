-- extracted from draft-richardson-bgp4-reflect-mib-00.txt
-- at Sat Feb 24 06:04:17 2001

    BGP4-REFLECT-MIB DEFINITIONS ::= BEGIN


        IMPORTS
            MODULE-IDENTITY, OBJECT-TYPE, NOTIFICATION-TYPE,
            IpAddress, mib-2
                FROM SNMPv2-SMI
            MODULE-COMPLIANCE, OBJECT-GROUP, NOTIFICATION-GROUP
                FROM SNMPv2-CONF
	    TruthValue
		FROM SNMPv2-TC
	    bgp
		FROM BGP-MIB;

        bgpReflect MODULE-IDENTITY
            LAST-UPDATED "200102230000Z"
            ORGANIZATION "IETF IDR Working Group"
            CONTACT-INFO "E-mail:  idr@merit.net

			  Mathew Richardson (Author)
			  E-mail: mrr@nexthop.com
			  Shane Wright (Author)
			  E-mail: swright@nexthop.com
                          517 W. William Street
                          Ann Arbor, MI 48103-4943
                          Tel: +1 734 973-2200
                          Fax: +1 734 615-3241

                          Susan Hares  (Editor)
                          517 W. William Street
                          Ann Arbor, MI 48103-4943
                          Tel: +1 734 973-2200
                          Fax: +1 734 615-3241
                          E-mail: skh@nexthop.com"

            REVISION    "200102230000Z"
            DESCRIPTION
                    "Extension of the MIB module for BGP-4 to include
		     information about attributes and characteristics defined
		     in BGP Route Reflection."
	    REFERENCE
		    "RFC 2796 - BGP Route Reflection"
            ::= { bgp 11 }


	bgpClusterId OBJECT-TYPE
	    SYNTAX	IpAddress
	    MAX-ACCESS	read-only
	    STATUS	current
	    DESCRIPTION
		    "The configured Cluster-ID of the local router. A value
		     of 0.0.0.0 indicates the absence of this value."
	    REFERENCE
		    "RFC 2796 - BGP Route Reflection"
	    ::= { bgpReflect 1 }


        bgpPeerReflectTable OBJECT-TYPE
            SYNTAX     SEQUENCE OF BgpPeerReflectEntry
            MAX-ACCESS not-accessible
            STATUS     current
            DESCRIPTION
		    "BGP Peer Reflect Table.  This table maintains information
		     about whether each peer is a Route Reflector."
	    REFERENCE
		    "RFC 2796 - BGP Route Reflection"
            ::= { bgpReflect 2 }


        bgpPeerReflectEntry OBJECT-TYPE
            SYNTAX     BgpPeerReflectEntry
            MAX-ACCESS not-accessible
            STATUS     current
            DESCRIPTION
		    "Peer related information pertaining to Route Reflection."
	    REFERENCE
		    "RFC 2796 - BGP Route Reflection"
            AUGMENTS	{ bgpPeerEntry }
            ::= { bgpPeerReflectTable 1 }


        BgpPeerReflectEntry ::= SEQUENCE {
		bgpPeerIsReflectorClient
			TruthValue
                }

	bgpPeerIsReflectorClient OBJECT-TYPE
	    SYNTAX	INTEGER {
				nonClient(0),
				client(1),
				meshedClient(2)
			}
	    MAX-ACCESS	read-only
	    STATUS	current
	    DESCRIPTION
		    "This value indicates whether the given peer is a reflector
		     client of this router, or not.  A value of nonClient
		     indicates that this peer is not a reflector client.  A
		     value of client indicates that this peer is a reflector
		     client that is not fully meshed with other reflector
		     clients.  A value of meshedClient indicates that the
		     peer is a reflector client and is fully meshed with all
		     other reflector clients."
	    REFERENCE
		    "RFC 2796 - BGP Route Reflection"
	    ::= { bgpPeerReflectEntry 1 }

        bgp4ReflectTable OBJECT-TYPE
            SYNTAX     SEQUENCE OF Bgp4ReflectEntry
            MAX-ACCESS not-accessible
            STATUS     current
            DESCRIPTION
		    "BGP Reflect Table.  This table contains the route
		     reflection specific path attributes received with a
		     given route."
	    REFERENCE
		    "RFC 2796 - BGP Route Reflection"
            ::= { bgpReflect 3 }


        bgp4ReflectEntry OBJECT-TYPE
            SYNTAX     Bgp4ReflectEntry
            MAX-ACCESS not-accessible
            STATUS     current
            DESCRIPTION
		    "Information about the route reflection specific path
		     attributes received with a given route."
	    AUGMENTS	{ bgp4PathAttrTable }
	    ::= { bgp4ReflectTable 1 }


        Bgp4ReflectEntry ::= SEQUENCE {
	    bgp4PathAttrOriginatorId
		 IpAddress,
	    bgp4PathAttrClusterList
		 OCTET STRING,
        }


	bgp4PathAttrOriginatorId OBJECT-TYPE
	    SYNTAX	IpAddress
	    MAX-ACCESS	read-only
	    STATUS	current
	    DESCRIPTION
		    "The Originator-ID identifying the router that initially
		     advertised this destination to a Route Reflector.  A
		     value of 0.0.0.0 indicates the absence of this attribute.
		     This attribute is defined in [RFC2796]."
	    ::= { bgp4ReflectEntry 1 }

	bgp4PathAttrClusterList OBJECT-TYPE
	    SYNTAX	OCTET STRING (SIZE(0..4096))
	    MAX-ACCESS	read-only
	    STATUS	current
	    DESCRIPTION
		    "A sequence of four octet long values representing the
		     reflection path that the route has passed.  Each four
		     octet long value represents the ID of a cluster that
		     the route has traversed.  A length of zero (0) indicates
		     the absence of this attribute.  This attribute is defined
		     in [RFC2796]."
	    ::= { bgp4ReflectEntry 2 }

    END

-- 
-- 
--    Copyright (C) The Internet Society (1999).  All Rights Reserved.
-- 
-- 
--    This document and translations of it may be copied and furnished to
--    others, and derivative works that comment on or otherwise explain it
--    or assist in its implementation may be prepared, copied, published
--    and distributed, in whole or in part, without restriction of any
--    kind, provided that the above copyright notice and this paragraph are
--    included on all such copies and derivative works.  However, this
--    document itself may not be modified in any way, such as by removing
--    the copyright notice or references to the Internet Society or other
--    Internet organizations, except as needed for the purpose of
--    developing Internet standards in which case the procedures for
--    copyrights defined in the Internet Standards process must be
--    followed, or as required to translate it into languages other than
--    English.
-- 
-- 
--    The limited permissions granted above are perpetual and will not be
--    revoked by the Internet Society or its successors or assigns.
-- 
-- 
--    This document and the information contained herein is provided on an
--    "AS IS" basis and THE INTERNET SOCIETY AND THE INTERNET ENGINEERING
--    TASK FORCE DISCLAIMS ALL WARRANTIES, EXPRESS OR IMPLIED, INCLUDING
--    BUT NOT LIMITED TO ANY WARRANTY THAT THE USE OF THE INFORMATION
--    HEREIN WILL NOT INFRINGE ANY RIGHTS OR ANY IMPLIED WARRANTIES OF
--    MERCHANTABILITY OR FITNESS FOR A PARTICULAR PURPOSE.
-- 
-- Expires August 2001
