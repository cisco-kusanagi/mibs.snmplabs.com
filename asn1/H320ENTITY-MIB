-- H.320 Entity MIB
--
-- This defines the MIB in support of the ITU-T H.320 protocols.
-- This MIB is a collection of common objects which can be used in a H.320 terminal,
-- a H.320 MCU and a H.320/H.323 gateway.  Objects are grouped as tables.
-- a H.320 terminal will have only one row of the table.  A H.320 MCU and a 
-- a H.320/H.323 gateway may have multiple entries in the table.
-- 

H320ENTITY-MIB DEFINITIONS ::= BEGIN
      IMPORTS
            MODULE-IDENTITY, OBJECT-TYPE, Counter32, Gauge32,
            Integer32
                  FROM SNMPv2-SMI
            DisplayString
                  FROM SNMPv2-TC
            MODULE-COMPLIANCE, OBJECT-GROUP
                  FROM SNMPv2-CONF
            mmH320Root,   MmTerminalLineRateCapability,
            MmTerminalVideoCapability, MmTerminalAudioCapability,      
            MmTerminalDataCapability
                  FROM  MULTI-MEDIA-MIB-TC;


      h320Entity MODULE-IDENTITY
            LAST-UPDATED "9812181400Z" -- December 18, 1998
            ORGANIZATION "ITU-T"
            CONTACT-INFO
                  " ITU-T SG-16 "
            DESCRIPTION
                  "This MIB module supports the common functions of the 
                  ITU-T H.320 terminal, MCU and H.320/H.323 gateway"
            REVISION "9812181400Z" -- Decem6280ber 18, 1998
            DESCRIPTION
                  " The H320 entity mib"
            ::= {mmH320Root 1} 

      h320Capability     OBJECT IDENTIFIER ::= { h320Entity 1  }
      h320CallStatus     OBJECT IDENTIFIER ::= { h320Entity 2  }
      h320H221Stats      OBJECT IDENTIFIER ::= { h320Entity 3  }

      -- H320 entity capability
      --

      h320CapsTable OBJECT-TYPE
            SYNTAX  SEQUENCE OF H320CapsEntry
            MAX-ACCESS  not-accessible
            STATUS  current
            DESCRIPTION
                  "A list of capability entries.  Objects are grouped as a 
                  table so that one can use this table in the H.320 terminal, 
                  the H.320 MCU, and the H.320/H.323 gateway.  
                  The total number of capability entries is
                  equal to the number of H.320 entities in a system.
                  For instance, there will be one row of capability
                  in the table of the H.320 terminal.  The number of rows 
                  will be equal to the number of H320 entities in the MCU
                  and the H320/H323 gateway. 
                  These entries describe the general capability of a system.  
                  Within a particular call, the behavior of the system is
                  further constrained by the characteristics of the call itself. 
                  For example, h320CapsEntityMaxVideoRate describes 
                  the maximum video rate a system can handle (perhaps 
                  due to processing constraints).  A particular call's transfer 
                  rate may limit video to a lower rate "
      ::= { h320Capability 1 }

      h320CapsEntry  OBJECT-TYPE
            SYNTAX  H320CapsEntry
            MAX-ACCESS  not-accessible
            STATUS  current
            DESCRIPTION
                  "A capability  row."
            INDEX   { terminalIndex }
      ::= { h320CapsTable 1 }

      H320CapsEntry ::=
            SEQUENCE {
                  terminalIndex
                            INTEGER,
                  h320CapsEntityLineRate
                        MmTerminalLineRateCapability,
                  h320CapsEntityVideoFormats      
                        MmTerminalVideoCapability,
                  h320CapsEntityMaxVideoRate
                        Integer32,      
                  h320CapsEntityAudioTypes
                        MmTerminalAudioCapability,      
                  h320CapsEntityDataCaps
                        MmTerminalDataCapability,
                  h320CapsEntityEncryp
                        Integer32,
                  h320CapsEntryRDC
                        Integer32
            }

       terminalIndex OBJECT-TYPE
            SYNTAX  INTEGER (1..2147483647)
            MAX-ACCESS  not-accessible
            STATUS  current
            DESCRIPTION
                  "A unique value for each video conference entity.
                   The value ranges between 1 and the number of H.320 entities 
                   in a system.  For instance, the table in the H.320 terminal 
                   has one row and the H.323/H.320 gateway or the H.320 MCU may 
                   have multiple rows of the H.320 capability. "
      ::= { h320CapsEntry 1 }

      h320CapsEntityLineRate OBJECT-TYPE
            SYNTAX MmTerminalLineRateCapability
            MAX-ACCESS read-only
            STATUS current
            DESCRIPTION
                  "This object represents the line rate capabilities of 
                  the H.320 entity.  Supported line rates are indicated by 
                  an octet string marked with 1s."
      ::= { h320CapsEntry 2 }

      h320CapsEntityVideoFormats OBJECT-TYPE
            SYNTAX MmTerminalVideoCapability
            MAX-ACCESS read-only
            STATUS current
            DESCRIPTION
                  "This object represents the video capabilities of the
                  H.320 entity. This includes the various video algorithms 
                  that it supports."
      ::= { h320CapsEntry 3 }

      h320CapsEntityMaxVideoRate OBJECT-TYPE
            SYNTAX  Integer32 
            MAX-ACCESS  read-only
            STATUS  current
            DESCRIPTION
                  "The maximum bit rate in kbit/s that the video channel can do."
      ::= { h320CapsEntry 4 }

      h320CapsEntityAudioTypes OBJECT-TYPE
            SYNTAX MmTerminalAudioCapability
            MAX-ACCESS read-only
            STATUS current
            DESCRIPTION
                  "This object represents the audio capabilities of the
                  H320 entity. This includes the various audio algorithms 
                  that it supports."
      ::= { h320CapsEntry 5 }

      h320CapsEntityDataCaps OBJECT-TYPE
            SYNTAX MmTerminalDataCapability 
            MAX-ACCESS read-only
            STATUS current
            DESCRIPTION
                  "This object represents the data capability of the
                  entity. "           
      ::= { h320CapsEntry 6 }

      h320CapsEntityEncryp OBJECT-TYPE
            SYNTAX Integer32
            MAX-ACCESS read-only
            STATUS current
            DESCRIPTION
                  "This object represents the encryption capability of the
                  entity.                          
  
                        Capability             Bit #
                        other                    0   
                        H.233/H.234              1   
  
                  Bits are numbered starting with the most
                  significant bit of the first byte being bit 0, the
                  least significant bit of the first byte being bit
                  7, the most significant bit of the second byte
                  being bit 8, and so on.  A one bit encodes that
                  the capability is supported, a zero bit encodes that
                  the capability is not supported."
      ::= { h320CapsEntry 7 }

      h320CapsEntryRDC OBJECT-TYPE
            SYNTAX Integer32
            MAX-ACCESS read-only
            STATUS current
            DESCRIPTION
                  "This object represents the Remote Device Control
                  capability of the entity. 

                  Capability          Bit #
                  Other                  0   
                  H.281                  1   -- Far-end Camera Control
                      
                  Bits are numbered starting with the most
                  significant bit of the first byte being bit 0, the
                  least significant bit of the first byte being bit
                  7, the most significant bit of the second byte
                  being bit 8, and so on.  A one bit encodes that
                  the capability is supported, a zero bit encodes that
                  the capability is not supported." 
      ::= { h320CapsEntry 8 }

      -- Call status group
      -- This group provides the information about the status of
      -- the calls in progress

      h320CallStatusTable OBJECT-TYPE
              SYNTAX  SEQUENCE OF H320CallStatusEntry
              MAX-ACCESS  not-accessible
              STATUS  current
              DESCRIPTION
                  "A list of call status entries.  Objects are grouped as a 
                   table so that one can use this table in the H.320 
                   terminal, the H.320 MCU, and the H.320/H.323 gateway.  
                   The total number of call status entries is equal to the 
                   number of H.320 entities in a system. For instance, there 
                   will be one row of call status in the table of the H.320 
                   terminal.  The number of rows will be equal to the number 
                   of H320 entities in the MCU and the H320/H323 gateway"
      ::= { h320CallStatus 1 }

      h320CallStatusEntry  OBJECT-TYPE
              SYNTAX  H320CallStatusEntry
              MAX-ACCESS  not-accessible
              STATUS  current
              DESCRIPTION
                    "A call status  row."
              AUGMENTS { h320CapsEntry }
      ::= { h320CallStatusTable 1 }

      H320CallStatusEntry ::=
            SEQUENCE {
                  h320CallCurrentCallStatus
                        INTEGER,
                  h320CallSiteName
                        DisplayString,
                  h320CallLineRate
                        MmTerminalLineRateCapability,
                  h320CallVideoInFormat
                        MmTerminalVideoCapability,
                  h320CallVideoOutFormat
                        MmTerminalVideoCapability,
                  h320CallAudioInFormat
                        MmTerminalAudioCapability,
                  h320CallAudioOutFormat
                        MmTerminalAudioCapability,
                  h320CallData
                        MmTerminalDataCapability,
                  h320CallEncryp
                        INTEGER,
                  h320CallRDC 
                        INTEGER,
                  h221CallStatusHangUpDirection 
                        INTEGER,
                  h221CallStatusQ850Cause
                        INTEGER 
            }

      h320CallCurrentCallStatus OBJECT-TYPE
            SYNTAX  INTEGER {
                  idle(1),
                  connecting(2),
                  connected(3),
                  disconnecting(4),
                  disconnected(5)
                  }
            MAX-ACCESS  read-only
            STATUS  current
            DESCRIPTION
                  "The current call status. An idle(1) means there were
                   no calls placed since the system is up. Once calls
                   were established and disconnected, the system remains
                   in the disconnected(5) state. A connected(2)
                   means the call is established and reached its
                   intended mode of operation "
      ::= { h320CallStatusEntry 1 }

      h320CallSiteName OBJECT-TYPE
            SYNTAX  DisplayString (SIZE (0..255))
            MAX-ACCESS  read-only
            STATUS  current
            DESCRIPTION
                  "The address to which this call is made. "
      ::= { h320CallStatusEntry 2 }

      h320CallLineRate OBJECT-TYPE
            SYNTAX MmTerminalLineRateCapability
            MAX-ACCESS  read-only
            STATUS  current
            DESCRIPTION
                  "This object represents the line rate being used 
                  in the current call in progress."
      ::= { h320CallStatusEntry 3 }

      h320CallVideoInFormat OBJECT-TYPE
            SYNTAX MmTerminalVideoCapability
            MAX-ACCESS read-only
            STATUS current
            DESCRIPTION
                  "This object represents the video decoding format being
                  used in the current call in progress."
      ::= { h320CallStatusEntry 4 }

      h320CallVideoOutFormat OBJECT-TYPE
            SYNTAX MmTerminalVideoCapability
            MAX-ACCESS read-only
            STATUS current
            DESCRIPTION
                  "This object represents the video encoding format being
                  used in the current call in progress."
      ::= { h320CallStatusEntry 5 }

      h320CallAudioInFormat OBJECT-TYPE
            SYNTAX MmTerminalAudioCapability
            MAX-ACCESS read-only
            STATUS current
            DESCRIPTION
                  "This object represents the audio decoding format
                  being used in the current call in progress."
      ::= { h320CallStatusEntry 6 }

      h320CallAudioOutFormat OBJECT-TYPE
            SYNTAX MmTerminalAudioCapability  
            MAX-ACCESS read-only
            STATUS current
            DESCRIPTION
                  "This object represents the audio encoding format
                  being used in the current call in progress."
      ::= { h320CallStatusEntry 7 }

      h320CallData OBJECT-TYPE
            SYNTAX MmTerminalDataCapability      
            MAX-ACCESS read-only
            STATUS current
            DESCRIPTION
                  "This object represents the type of data communication
                  protocol used in the call."              
      ::= { h320CallStatusEntry 8 }

      h320CallEncryp OBJECT-TYPE
            SYNTAX INTEGER {
                  other (1),
                  h233(2)      
                  }
            MAX-ACCESS read-only
            STATUS current
            DESCRIPTION
                  "This object indicates the type of encryption
                  protocol used in the call. 
                  1 indicates other type of encryption.
                  2 indicates the encryption based on H.233."
      ::= { h320CallStatusEntry 9 }

      h320CallRDC OBJECT-TYPE
            SYNTAX INTEGER {
                  other(1),
                  h281FECC(2)
                  }
            MAX-ACCESS read-only
            STATUS current
            DESCRIPTION
                  "This object indicates the type of remote device
                  control.
                  1 indicates other type of device is used.
                  2 indicates the FECC is used. "
      ::= { h320CallStatusEntry 10 }

      h221CallStatusHangUpDirection OBJECT-TYPE
            SYNTAX INTEGER {
                            nearEndUser (1),
                            nearEndSystem (2),
                            farEnd (3)
                             } 
            MAX-ACCESS read-only
            STATUS current
            DESCRIPTION
                    "Identifies who initiated hanging up the last call: 
                     the near end user; the near end videoconferencing
                     system (perhaps due to errors such as loss of framing);
                     or the far end/ network.  If a call is currently active,
                     this refers to the previous call."
      ::= { h320CallStatusEntry 11 }

      h221CallStatusQ850Cause OBJECT-TYPE
             SYNTAX INTEGER (1..2147483647)
             MAX-ACCESS read-only
             STATUS current
             DESCRIPTION
                    "The Q.850 cause code received from the network when the
                     last call hung-up.  If the near end hung up the call, 
                     this field should be set to zero. If a call is currently
                     active, this refers to the previous call."
     ::= { h320CallStatusEntry 12 }

      --
      -- H.221 statistics
      --

      h221ChannelStatsTable OBJECT-TYPE
              SYNTAX  SEQUENCE OF H221ChannelStatsEntry
              MAX-ACCESS  not-accessible
              STATUS  current
              DESCRIPTION
                    "A list of statistics entries.  Objects are grouped as a 
                    table so that one can use this table in the H.320 terminal, 
                    the H.320 MCU, and the H.320/H.323 gateway.  
                    The total number of statistics entries is
                    equal to the number of H.320 entities in a system.
                    For instance, there will be one row of statistics
                    in the table of the H.320 terminal.  The number of rows 
                    will be equal to the number of H320 entities in the MCU
                    and the H320/H323 gateway"
      ::= { h320H221Stats 1 }

      h221ChannelStatsEntry  OBJECT-TYPE
              SYNTAX  H221ChannelStatsEntry
              MAX-ACCESS  not-accessible
              STATUS  current
              DESCRIPTION
                    "A h221 statistics row."
              AUGMENTS { h320CapsEntry }
      ::= { h221ChannelStatsTable 1 }

      H221ChannelStatsEntry ::=
            SEQUENCE {
              numberofConnections 
                        INTEGER,
              h221StatsInVideoFrames 
                        Counter32, 
              h221StatsInVideoFramesCorrectableErrs 
                        Counter32, 
              h221StatsInVideoFramesUncorrectableErrs 
                        Counter32, 
              h221StatsOutVCU 
                        Counter32 
                  }

      numberofConnections OBJECT-TYPE
            SYNTAX  INTEGER (1..2147483647)
            MAX-ACCESS  read-only
            STATUS  current
            DESCRIPTION
                  "The number of connections in each channel
                  in a call.  For instance 2x64 has two connections "
      ::= { h221ChannelStatsEntry 1 }

      h221StatsInVideoFrames OBJECT-TYPE
             SYNTAX Counter32 
             MAX-ACCESS read-only
             STATUS current
             DESCRIPTION
                    "The total number of video BCH frames received"
      ::= { h221ChannelStatsEntry 2 }

      h221StatsInVideoFramesCorrectableErrs OBJECT-TYPE
             SYNTAX Counter32 
             MAX-ACCESS read-only
             STATUS current
             DESCRIPTION
                    "The number of video BCH frames received with 
                    correctable errors"
      ::= { h221ChannelStatsEntry 3 }

      h221StatsInVideoFramesUncorrectableErrs OBJECT-TYPE
             SYNTAX Counter32 
             MAX-ACCESS read-only
             STATUS current
             DESCRIPTION
                    "The number of video BCH frames received with 
                     uncorrectable errors"
      ::= { h221ChannelStatsEntry 4 }

      h221StatsOutVCU OBJECT-TYPE
             SYNTAX Counter32 
             MAX-ACCESS read-only
             STATUS current
             DESCRIPTION
                    "The number of VCUs transmitted"
      ::= { h221ChannelStatsEntry 5 }

      h221ConnectionStatsTable OBJECT-TYPE
              SYNTAX  SEQUENCE OF H221ConnectionStatsEntry
              MAX-ACCESS  not-accessible
              STATUS  current
              DESCRIPTION
                    "A list of statistics entries for each port. There are 
                     two connections if the call is 2x64. These statistics 
                     get re-initialized at the start of each call and are
                     retained after the end of the call.  Thus, one can query
                     these items after the end of call and prior to the start
                     of a new call to get the overall statistics of the old 
                     call."
      ::= { h320H221Stats 2 }

      h221ConnectionStatsEntry  OBJECT-TYPE
              SYNTAX  H221ConnectionStatsEntry
              MAX-ACCESS  not-accessible
              STATUS  current
              DESCRIPTION
                    "A h221 statistics row."
              INDEX { terminalIndex, connectionIndex }
      ::= { h221ConnectionStatsTable 1 }

      H221ConnectionStatsEntry ::=
            SEQUENCE {
                  connectionIndex
                        INTEGER,
                  h221StatsInFrames
                        Counter32,
                  h221StatsOutFrames
                        Counter32,
                  h221StatsInFrameErrs 
                        Counter32,
                  h221StatsFrameAlignmentErrs 
                        Counter32,
                  h221StatsMultiFrameAlignmentErrs
                        Counter32, 
                  h221StatsErrorPerformance
                         Gauge32,
                  h221StatsBASErrs
                        Counter32,
                  h221StatsCRC4Err 
                        Counter32, 
                  h221StatsInEBit 
                        Counter32, 
                  h221StatsInopportuneBAS 
                        Counter32 
                  }

      connectionIndex OBJECT-TYPE
            SYNTAX  INTEGER (1..2147483647)
            MAX-ACCESS  not-accessible
            STATUS  current
            DESCRIPTION
                  "A unique value for each entry. The value ranges 
                   between 1 and the number of connections indicated 
                   in numberofConnections."
      ::= { h221ConnectionStatsEntry 1 }

      h221StatsInFrames OBJECT-TYPE
             SYNTAX Counter32
             MAX-ACCESS read-only
             STATUS current
             DESCRIPTION
                   "The number of H.221 frames received"
      ::= { h221ConnectionStatsEntry 2 }

      h221StatsOutFrames OBJECT-TYPE
             SYNTAX Counter32
             MAX-ACCESS read-only
             STATUS current
             DESCRIPTION
                    "The number of H.221 frames sent"
      ::= { h221ConnectionStatsEntry 3 }

      h221StatsInFrameErrs OBJECT-TYPE
             SYNTAX Counter32
             MAX-ACCESS read-only
             STATUS current
             DESCRIPTION
                    "The number of error frames received"
      ::= { h221ConnectionStatsEntry 4 }

      h221StatsFrameAlignmentErrs OBJECT-TYPE
             SYNTAX  Counter32
             MAX-ACCESS read-only
             STATUS current
             DESCRIPTION
                    "The number of times frame alignment is lost, i.e.
                     three consecutive frame alignment words were
                     received with an error after the establishment
                     of frame alignment. "
      ::= { h221ConnectionStatsEntry 5 }

      h221StatsMultiFrameAlignmentErrs OBJECT-TYPE
             SYNTAX Counter32
             MAX-ACCESS read-only
             STATUS current
             DESCRIPTION
                   "The number of times multi-frame alignment is lost, i.e.
                     three consecutive multi-frame alignment words were
                     received with an error after the establishment
                     of frame alignment. 
                     "
      ::= { h221ConnectionStatsEntry 6 }

      h221StatsErrorPerformance OBJECT-TYPE
             SYNTAX Gauge32 (0..50)
             MAX-ACCESS read-only
             STATUS current
             DESCRIPTION
                    "The quality of the 64 kbp/s connection can be monitored 
                    by counting the number of  CRC blocks in error (E-bit = 1) 
                    within a period of one second (50 blocks). The following
                    indicates the mapping between the number of CRC blocks 
                    in error and the equivalent line error rate. 
                    Percentage of CRC blocks in error          Error rate
                    70% CRC blocks in error                     10E-4
                    12% CRC blocks in error                     10E-5
                    1.2% CRC blocks in error                    10E-6
                    0.12% CRC blocks in error                   10E-7
                    0.012% CRC blocks in error                  10E-8"
      ::= { h221ConnectionStatsEntry 7 }

      h221StatsBASErrs OBJECT-TYPE
             SYNTAX Counter32 
             MAX-ACCESS read-only
             STATUS current
             DESCRIPTION
                    "The number of BAS codes received with ECC errors
                     "
      ::= { h221ConnectionStatsEntry 8 }

      h221StatsCRC4Err OBJECT-TYPE
             SYNTAX Counter32 
             MAX-ACCESS read-only
             STATUS current
             DESCRIPTION
                    "The number of frames received with CRC4 errors "
      ::= { h221ConnectionStatsEntry 9 }

      h221StatsInEBit OBJECT-TYPE
             SYNTAX Counter32 
             MAX-ACCESS read-only
             STATUS current
             DESCRIPTION
                    "The number of frames received with the E bit set"
      ::= { h221ConnectionStatsEntry 10 }

      h221StatsInopportuneBAS OBJECT-TYPE
             SYNTAX Counter32 
             MAX-ACCESS read-only
             STATUS current
             DESCRIPTION
                    "The number of BAS codes received at inappropriate 
                     times (e.g. commands received in the middle of 
                     capabilities exchange)."
      ::= { h221ConnectionStatsEntry 11 }

      -- CONFORMANCE
      --

      h320EntityMIBConfs       OBJECT IDENTIFIER ::= { h320Entity 4 }
      h320EntityMIBGroups      OBJECT IDENTIFIER ::= { h320EntityMIBConfs 1 }
      h320EntityMIBCompl       OBJECT IDENTIFIER ::= { h320EntityMIBConfs 2 }      

      --
      -- Groups for conformance
      --

      h320CapsGroups      OBJECT-GROUP
            OBJECTS {
                  h320CapsEntityLineRate,
                  h320CapsEntityVideoFormats,      
                  h320CapsEntityMaxVideoRate,
                  h320CapsEntityAudioTypes,
                  h320CapsEntityDataCaps,
                  h320CapsEntityEncryp,
                  h320CapsEntryRDC,
                  h221CallStatusHangUpDirection, 
                  h221CallStatusQ850Cause            }
            STATUS current
            DESCRIPTION
                  "A collection of objects providing capabilities of 
                  the entity"
      ::= {h320EntityMIBGroups 1}

      h320CallStatusGroup OBJECT-GROUP
            OBJECTS {
                  h320CallCurrentCallStatus,
                  h320CallSiteName,
                  h320CallLineRate, 
                  h320CallVideoInFormat, 
                  h320CallVideoOutFormat, 
                  h320CallAudioInFormat, 
                  h320CallAudioOutFormat, 
                  h320CallData, 
                  h320CallEncryp,
                  h320CallRDC 
            }
            STATUS current
            DESCRIPTION
                  "A collection of objects providing the ability to 
                  invoke terminal functions"
      ::= { h320EntityMIBGroups 2}

      h320H221StatsGroup      OBJECT-GROUP
            OBJECTS {
                  numberofConnections,
                  h221StatsInFrames,
                  h221StatsOutFrames, 
                  h221StatsInFrameErrs, 
                  h221StatsFrameAlignmentErrs, 
                  h221StatsMultiFrameAlignmentErrs, 
                  h221StatsErrorPerformance, 
                  h221StatsBASErrs,
                  h221StatsInVideoFrames, 
                  h221StatsInVideoFramesCorrectableErrs, 
                  h221StatsInVideoFramesUncorrectableErrs, 
                  h221StatsOutVCU, 
                  h221StatsCRC4Err, 
                  h221StatsInEBit, 
                  h221StatsInopportuneBAS             }
            STATUS current
            DESCRIPTION
                  "A collection of objects providing the ability to invoke 
                  terminal functions"
      ::= { h320EntityMIBGroups 3}

      h221StatsCompliance      MODULE-COMPLIANCE
            STATUS      current
            DESCRIPTION      
                  "The set of objects required for compliance"
      -- Unconditionally mandatory groups
            MODULE
            MANDATORY-GROUPS       { h320CapsGroups, h320CallStatusGroup,
                           h320H221StatsGroup }
            
      ::= { h320EntityMIBCompl 1 }

END
