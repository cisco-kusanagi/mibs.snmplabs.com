USR-ATM-1577-PVC-MIB DEFINITIONS ::= BEGIN
               IMPORTS
                  OBJECT-TYPE
                      FROM SNMPv2-SMI
                  DisplayString
                      FROM RFC1213-MIB
		  RowStatus
	              FROM SNMPv2-TC
                  IfIndex
		      FROM ATM-MIB
	          usrAtm1577Pvc
	              FROM USR-DEFINITIONS-MIB
                  ;    
               --  The ATM 1577 PVCs for cli commands
               usrAtm1577PvcTable OBJECT-TYPE
                    SYNTAX  SEQUENCE OF UsrAtm1577PvcEntry
                    MAX-ACCESS  not-accessible
                    STATUS  current
                    DESCRIPTION
                     "This usrAtm1577PvcTable keeps PVC name
                      and corresponding index values for the
                      VCL table row. It also contains mib objects
   		      that may be used in retrieving values for
 	              display of 1577 PVCs."
                    ::= { usrAtm1577Pvc 1 }
               usrAtm1577PvcEntry OBJECT-TYPE
                    SYNTAX  UsrAtm1577PvcEntry
                    MAX-ACCESS  not-accessible
                    STATUS  current
                    DESCRIPTION "This is the name of the RFC1577 PVC."
                    INDEX { usrAtm1577PvcName}
                    ::= { usrAtm1577PvcTable 1 }
               UsrAtm1577PvcEntry ::= SEQUENCE {
                    usrAtm1577PvcName	        DisplayString,
                    usrAtm1577PvcIfIndex        IfIndex,
                    usrAtm1577PvcVpi		INTEGER,
		    usrAtm1577PvcVci		INTEGER,
		    usrAtm1577PvcNetworkName    DisplayString,
		    usrAtm1577PvcPort           INTEGER,
		    usrAtm1577PvcPcr            INTEGER,
	 	    usrAtm1577PvcRowStatus      RowStatus
               }
               usrAtm1577PvcName OBJECT-TYPE
                    SYNTAX  DisplayString
                    MAX-ACCESS  not-accessible
                    STATUS  current
                    DESCRIPTION "ATM 1577 PVC name used as an index"
                    ::= { usrAtm1577PvcEntry 1 }
               usrAtm1577PvcIfIndex OBJECT-TYPE
                    SYNTAX  IfIndex
                    MAX-ACCESS  read-create
                    STATUS  current
                    DESCRIPTION  "IfIndex of the ATMNET interface for this entry"
		    --CONFIGURABLE
                    ::= { usrAtm1577PvcEntry 2 }
               usrAtm1577PvcVpi OBJECT-TYPE
                    SYNTAX  INTEGER (0..4095)
                    MAX-ACCESS  read-create
                    STATUS  current
                    DESCRIPTION  "VPI value of this ATM 1577 PVC "
                    --CONFIGURABLE
                    ::= { usrAtm1577PvcEntry 3 }
               usrAtm1577PvcVci OBJECT-TYPE
                    SYNTAX  INTEGER (0..65535)
                    MAX-ACCESS  read-create
                    STATUS  current
                    DESCRIPTION  "VCI value of this ATM 1577 PVC "
                    --CONFIGURABLE
                    ::= { usrAtm1577PvcEntry 4 }
               usrAtm1577PvcPort OBJECT-TYPE
		    SYNTAX INTEGER(1..2)
                    MAX-ACCESS  read-only
                    STATUS      current
                    DESCRIPTION
                    "The port number for the RFC1577 PVC."
                    ::= { usrAtm1577PvcEntry 5 }
               usrAtm1577PvcPcr OBJECT-TYPE
                    SYNTAX INTEGER(1000..100000)
                    MAX-ACCESS  read-only
                    STATUS      current
                    DESCRIPTION
                    "The peak cell rate configured for this PVC."
                    ::= { usrAtm1577PvcEntry 6 }
               usrAtm1577PvcNetworkName OBJECT-TYPE
                    SYNTAX DisplayString (SIZE(0..32))
                    MAX-ACCESS  read-only
                    STATUS      current
                    DESCRIPTION
                    "A string containing the name of the network of this RFC1577 PVC."
                    ::= { usrAtm1577PvcEntry 7 }
               usrAtm1577PvcRowStatus OBJECT-TYPE
                    SYNTAX  RowStatus
                    MAX-ACCESS  read-only
                    STATUS  current
                    DESCRIPTION  "1577 PVC VCL row status"
                    ::= { usrAtm1577PvcEntry 8 }
               END -- End of USR-ATM-1577-PVC-MIB DEFINITIONS
