--******************************************************************
--*
--*         Copyright (c) 1993, 1999 by 3Com Corporation
--*                    All Rights Reserved
--*
--*    $Revision:   7.0  $
--*    $Date:   Jul 15 1999 15:21:52  $
--*
--*    3COM TRAX MIB
--*
--******************************************************************


TRAX-MIB DEFINITIONS ::= BEGIN

IMPORTS
   enterprises,
   experimental,
   IpAddress,
   TimeTicks,
   Gauge,
   Counter
      FROM RFC1155-SMI
   DisplayString
      FROM RFC1213-MIB
   OBJECT-TYPE
      FROM RFC-1212;


usr OBJECT IDENTIFIER ::= { enterprises 429 }

nas OBJECT IDENTIFIER ::= { usr 1 }

trax OBJECT IDENTIFIER ::= { nas 31 }

-- The TRAX Card Identification Group.

traxId OBJECT IDENTIFIER ::= { trax 1 }

traxIdTable OBJECT-TYPE
SYNTAX SEQUENCE OF TraxIdEntry
ACCESS not-accessible
STATUS mandatory
DESCRIPTION
"A table that contains information that identifies the 
hardware and software that make up the specified Hiper TRAX 
card."
::= { traxId 1 }

traxIdEntry OBJECT-TYPE
SYNTAX TraxIdEntry
ACCESS not-accessible
STATUS mandatory
DESCRIPTION
"There is one entry in this table for every Hiper TRAX card 
in the chassis."
INDEX { traxIdIndex }
::= { traxIdTable 1 }

TraxIdEntry ::=
SEQUENCE {
traxIdIndex
    INTEGER,
traxIdHardwareSerNum
    DisplayString,
traxIdHardwareRev
    DisplayString,
traxIdSoftwareRev
    DisplayString,
traxIdCpuType
    INTEGER,
traxIdRamInstalled
    INTEGER,
traxIdFlashInstalled
    INTEGER,
traxIdSelfTestResult
    INTEGER,
traxIdMgmtConnect
    INTEGER
}

traxIdIndex OBJECT-TYPE
SYNTAX INTEGER
ACCESS read-only
STATUS mandatory
DESCRIPTION
"An index that uniquely identifies the Hiper TRAX card for 
which this row in the table pertains.  The value of this 
index matches the value of the index for the corresponding 
entity in the entity table of the chassis MIB."
::= { traxIdEntry 1 }

traxIdHardwareSerNum OBJECT-TYPE
SYNTAX DisplayString
ACCESS read-only
STATUS mandatory
DESCRIPTION
"The Hiper TRAX card's hardware serial number as stored in 
EEPROM."
::= { traxIdEntry 2 }

traxIdHardwareRev OBJECT-TYPE
SYNTAX DisplayString
ACCESS read-only
STATUS mandatory
DESCRIPTION
"The hardware revision of the specified Hiper TRAX card as 
stored in its EEPROM."
::= { traxIdEntry 3 }

traxIdSoftwareRev OBJECT-TYPE
SYNTAX DisplayString
ACCESS read-only
STATUS mandatory
DESCRIPTION
"The revision of the software being executed in the 
specified Hiper TRAX card."
::= { traxIdEntry 4 }

traxIdCpuType OBJECT-TYPE
SYNTAX INTEGER{
  i80386(1),
  i80486(2),
  powerPC603(3)
}
ACCESS read-only
STATUS mandatory
DESCRIPTION
"Defines the type of CPU present on the Hiper TRAX NAC."
::= { traxIdEntry 5 }

traxIdRamInstalled OBJECT-TYPE
SYNTAX INTEGER
ACCESS read-only
STATUS mandatory
DESCRIPTION
"Specifies the amount of DRAM installed on the Hiper TRAX 
Gateway NAC in Kbytes."
::= { traxIdEntry 6 }

traxIdFlashInstalled OBJECT-TYPE
SYNTAX INTEGER
ACCESS read-only
STATUS mandatory
DESCRIPTION
"Specifies the amount of Flash Rom installed on the Hiper 
TRAX NAC in Kbytes."
::= { traxIdEntry 7 }

traxIdSelfTestResult OBJECT-TYPE
SYNTAX INTEGER
ACCESS read-only
STATUS mandatory
DESCRIPTION
"Displays the results of the most resent self test performed 
by the Hiper TRAX NAC.  If all tests have passed a value of 
0 is returned."
::= { traxIdEntry 9 }

traxIdMgmtConnect OBJECT-TYPE
SYNTAX INTEGER{
  inactive(1),
  active(2)
}
ACCESS read-only
STATUS mandatory
DESCRIPTION
"Indicates the current status of Hiper TRAX Card user 
interface."
::= { traxIdEntry 10 }

-- The TRAX Card Command Group.

traxCmd OBJECT IDENTIFIER ::= { trax 2 }

traxCmdTable OBJECT-TYPE
SYNTAX SEQUENCE OF TraxCmdEntry
ACCESS not-accessible
STATUS mandatory
DESCRIPTION
"The Hiper TRAX Card Command table contains an entry for 
each of the manageable Hiper TRAX Cards in the chassis.  It 
provides a means through which to take specific actions on 
one or more Hiper TRAX cards in the NAS chassis."
::= { traxCmd 1 }

traxCmdEntry OBJECT-TYPE
SYNTAX TraxCmdEntry
ACCESS not-accessible
STATUS mandatory
DESCRIPTION
"There is one Hiper TRAX Card Command entry per Hiper TRAX 
Card in the chassis."
INDEX { traxCmdIndex }
::= { traxCmdTable 1 }

TraxCmdEntry ::=
SEQUENCE {
traxCmdIndex
    INTEGER,
traxCmdMgtStationId
    OCTET STRING,
traxCmdReqId
    INTEGER,
traxCmdFunction
    INTEGER,
traxCmdForce
    INTEGER,
traxCmdParam
    OCTET STRING,
traxCmdResult
    INTEGER,
traxCmdCode
    INTEGER
}

traxCmdIndex OBJECT-TYPE
SYNTAX INTEGER
ACCESS read-only
STATUS mandatory
DESCRIPTION
"A unique value for each Hiper TRAX Card in the chassis.  
The value of this object matches the value of the index of 
the corresponding Hiper TRAX Card's entry in the entity 
table of the chassis MIB."
::= { traxCmdEntry 1 }

traxCmdMgtStationId OBJECT-TYPE
SYNTAX OCTET STRING (SIZE(0..8))
ACCESS read-write
STATUS mandatory
DESCRIPTION
"This object is a generic read-write variable that a 
Management Station (MS) can use to guarantee that the 
results from a given command are the results of a command 
issued by that specific MS.  Each MS must SET a unique 
value to this object"
::= { traxCmdEntry 2 }

traxCmdReqId OBJECT-TYPE
SYNTAX INTEGER
ACCESS read-only
STATUS mandatory
DESCRIPTION
"This object contains the value of the request-id field in 
the SNMP PDU which invoked the current or most recent 
command or test on this X.25 Card.  If the request-id is 
unknown or undefined, this object contains the value zero."
::= { traxCmdEntry 3 }

traxCmdFunction OBJECT-TYPE
SYNTAX INTEGER{
  noCommand(1),
  saveToNVRAM(2),
  restoreFromNVRAM(3),
  restoreFromDefault(4),
  nonDisruptSelfTest(5),
  disruptSelfTest(6),
  softwareReset(7),
  downloadCfgFile(8),
  uploadCfgFile(9),
  resetStsCounters(10)
}
ACCESS read-write
STATUS mandatory
DESCRIPTION
"This object contains a value which describes the command 
which is being invoked."
::= { traxCmdEntry 4 }

traxCmdForce OBJECT-TYPE
SYNTAX INTEGER
ACCESS read-write
STATUS mandatory
DESCRIPTION
"In some cases, the Hiper TRAX Card may be in a state such 
that certain commands could adversely affect connections.  
In such cases, a command request with this object not 
present or set to noForce will result in a warning"
::= { traxCmdEntry 5 }

traxCmdParam OBJECT-TYPE
SYNTAX OCTET STRING
ACCESS read-write
STATUS mandatory
DESCRIPTION
"This object contains parameters that are specific to the 
particular command being issued.  In some cases, there will 
be no aditional parameters required."
::= { traxCmdEntry 6 }

traxCmdResult OBJECT-TYPE
SYNTAX INTEGER{
  none(1),
  success(2),
  inProgress(3),
  notSupported(4),
  unAbleToRun(5),
  aborted(6),
  failed(7)
}
ACCESS read-only
STATUS mandatory
DESCRIPTION
"This object contains the result of the most recently 
requested command or test, or the value none(1) if no 
commands have been requested since the last reset."
::= { traxCmdEntry 7 }

traxCmdCode OBJECT-TYPE
SYNTAX INTEGER{
  noError(1),
  unable(2),
  unrecognizedCommand(6),
  slotEmpty(8),
  noResponse(12),
  unsupportedCommand(20),
  deviceDisabled(22),
  fileTooBig(46),
  userInterfaceActive(58),
  badFlashRomID(61),
  badFlashVoltage(62),
  flashEraseError(63),
  eraseSequenceError(64),
  eraseExecutionError(65),
  receiveBufferOverflow(66),
  badProgramVoltage(68),
  programmingDataError(69),
  programCodeError(70),
  invalidCodeError(71),
  romCrcBad(72),
  pendingSoftwareDownload(73),
  ramCrcBad(74),
  invalidRomId(75),
  cardIdMismatch(84),
  cardIdUnknown(85),
  tftpTimeout(86),
  flashEraseTimeout(87),
  invalidFileHeader(88),
  bulkTransferInProcess(93)
}
ACCESS read-only
STATUS mandatory
DESCRIPTION
"The value of this object is noError(1) if the command was 
successful, and indicates a further description of what 
went wrong if it was unsuccessful."
::= { traxCmdEntry 8 }

-- The TRAX Card Configuration Group.

traxCfg OBJECT IDENTIFIER ::= { trax 3 }

traxCfgTable OBJECT-TYPE
SYNTAX SEQUENCE OF TraxCfgEntry
ACCESS not-accessible
STATUS mandatory
DESCRIPTION
"A table of configurable parameters specific to the Hiper 
TRAX NAC."
::= { traxCfg 1 }

traxCfgEntry OBJECT-TYPE
SYNTAX TraxCfgEntry
ACCESS not-accessible
STATUS mandatory
DESCRIPTION
""
INDEX { traxCfgIndex }
::= { traxCfgTable 1 }

TraxCfgEntry ::=
SEQUENCE {
traxCfgIndex
    INTEGER,
traxCfgCardIPAddress
    IpAddress,
traxCfgIPMask
    IpAddress,
traxCfgGatewayIpAddr
    IpAddress,
traxCfgHostIPAddr
    IpAddress,
traxCfgX25Addr
    DisplayString,
traxCfgNicTrapDestination
    IpAddress,
traxCfgReadMemAddr
    INTEGER,
traxCfgReadMemData
    OCTET STRING,
traxCfgReadMemLength
    INTEGER,
traxCfgWriteMemAddr
    INTEGER,
traxCfgWriteMemLen
    INTEGER,
traxCfgWriteMemData
    OCTET STRING,
traxFailureReason
    INTEGER,
traxDNIFailureReason
    OCTET STRING,
traxCfgX25AddrPort1
    DisplayString
}

traxCfgIndex OBJECT-TYPE
SYNTAX INTEGER
ACCESS read-only
STATUS mandatory
DESCRIPTION
"A unique value for each Hiper TRAX NAC installed in the 
chassis.  The value of this index is identical to the index 
in the USR chassis MIB associates with the Hiper TRAX Card 
entity."
::= { traxCfgEntry 1 }

traxCfgCardIPAddress OBJECT-TYPE
SYNTAX IpAddress
ACCESS read-write
STATUS mandatory
DESCRIPTION
"Specifies the local IP address used for the Hiper TRAX Card 
Mgmt"
::= { traxCfgEntry 2 }

traxCfgIPMask OBJECT-TYPE
SYNTAX IpAddress
ACCESS read-write
STATUS mandatory
DESCRIPTION
"Specifies the subnet mask for the Hiper TRAX Card"
::= { traxCfgEntry 3 }

traxCfgGatewayIpAddr OBJECT-TYPE
SYNTAX IpAddress
ACCESS read-write
STATUS mandatory
DESCRIPTION
"Specifies Hiper TRAX gateway IP Address"
::= { traxCfgEntry 4 }

traxCfgHostIPAddr OBJECT-TYPE
SYNTAX IpAddress
ACCESS read-write
STATUS mandatory
DESCRIPTION
"Specifies Hiper TRAX Cards LAN HOST IP Address"
::= { traxCfgEntry 5 }

traxCfgX25Addr OBJECT-TYPE
SYNTAX DisplayString (SIZE(0..15))
ACCESS read-write
STATUS mandatory
DESCRIPTION
"Specifies Hiper TRAX network address port 0 for card."
::= { traxCfgEntry 6 }

traxCfgNicTrapDestination OBJECT-TYPE
SYNTAX IpAddress
ACCESS read-write
STATUS mandatory
DESCRIPTION
"Specifies alternative trap destination for the NIC IP Port"
::= { traxCfgEntry 7 }

traxCfgReadMemAddr OBJECT-TYPE
SYNTAX INTEGER
ACCESS read-write
STATUS mandatory
DESCRIPTION
"Memory Address for retrieving data"
::= { traxCfgEntry 8 }

traxCfgReadMemData OBJECT-TYPE
SYNTAX OCTET STRING (SIZE(0..32))
ACCESS read-write
STATUS mandatory
DESCRIPTION
""
::= { traxCfgEntry 9 }

traxCfgReadMemLength OBJECT-TYPE
SYNTAX INTEGER
ACCESS read-write
STATUS mandatory
DESCRIPTION
"Specifies number of byte of the ReadMemoryAddr to Read"
::= { traxCfgEntry 10 }

traxCfgWriteMemAddr OBJECT-TYPE
SYNTAX INTEGER
ACCESS read-write
STATUS mandatory
DESCRIPTION
"Memory address for setting data"
::= { traxCfgEntry 11 }

traxCfgWriteMemLen OBJECT-TYPE
SYNTAX INTEGER
ACCESS read-write
STATUS mandatory
DESCRIPTION
"Specifies the number of bytes of the WriteMemoryData string 
to write"
::= { traxCfgEntry 12 }

traxCfgWriteMemData OBJECT-TYPE
SYNTAX OCTET STRING (SIZE(0..32))
ACCESS read-write
STATUS mandatory
DESCRIPTION
"Specifies the data to be written to processor memory"
::= { traxCfgEntry 13 }

traxFailureReason OBJECT-TYPE
SYNTAX INTEGER
ACCESS not-accessible
STATUS mandatory
DESCRIPTION
"Specifies the Failure Reason for the TRAX Traps."
::= { traxCfgEntry 14 }

traxDNIFailureReason OBJECT-TYPE
SYNTAX OCTET STRING (SIZE(0..20))
ACCESS not-accessible
STATUS mandatory
DESCRIPTION
"Specifies the Failure Reason for the TRAX Traps."
::= { traxCfgEntry 15 }

traxCfgX25AddrPort1 OBJECT-TYPE
SYNTAX DisplayString (SIZE(0..15))
ACCESS read-write
STATUS mandatory
DESCRIPTION
"Specifies Hiper TRAX network address port 1 for card"
::= { traxCfgEntry 16 }

-- The TRAX Trap Enable Group.

traxTrapEna OBJECT IDENTIFIER ::= { trax 4 }

traxTrapEnaTable OBJECT-TYPE
SYNTAX SEQUENCE OF TraxTrapEnaEntry
ACCESS not-accessible
STATUS mandatory
DESCRIPTION
"Table containing objects to enable traps on the Hiper TRAX 
Cards in the chassis."
::= { traxTrapEna 1 }

traxTrapEnaEntry OBJECT-TYPE
SYNTAX TraxTrapEnaEntry
ACCESS not-accessible
STATUS mandatory
DESCRIPTION
"There is one entry for each Hiper TRAX Card in the chassis"
INDEX { traxTrapEnaIndex }
::= { traxTrapEnaTable 1 }

TraxTrapEnaEntry ::=
SEQUENCE {
traxTrapEnaIndex
    INTEGER,
traxTrapEnaNicMissing
    INTEGER,
traxTrapEnaX25FrameLevelUp
    INTEGER,
traxTrapEnaX25FrameLevelDown
    INTEGER,
traxTrapEnaX25PacketLevelUp
    INTEGER,
traxTrapEnaX25PacketLevelDn
    INTEGER,
traxTrapEnaX25LostCalls
    INTEGER,
traxTrapEnaX25LinkUp
    INTEGER,
traxTrapEnaX25LinkDn
    INTEGER,
traxTrapEnaDnisLookUp
    INTEGER,
traxTrapEnaSvcSetUp
    INTEGER,
traxTrapEnaSvcAlarm
    INTEGER,
traxTrapDupTrans
    INTEGER
}

traxTrapEnaIndex OBJECT-TYPE
SYNTAX INTEGER
ACCESS read-only
STATUS mandatory
DESCRIPTION
"A unique index identifying the Hiper TRAX Card to which the 
trap enable objects pertain."
::= { traxTrapEnaEntry 1 }

traxTrapEnaNicMissing OBJECT-TYPE
SYNTAX INTEGER{
  enable(1),
  disable(2)
}
ACCESS read-write
STATUS mandatory
DESCRIPTION
"Enables reporting of NIC missing event"
::= { traxTrapEnaEntry 2 }

traxTrapEnaX25FrameLevelUp OBJECT-TYPE
SYNTAX INTEGER{
  enable(1),
  disable(2)
}
ACCESS read-write
STATUS mandatory
DESCRIPTION
"Enables reporting of Hiper TRAX Frame Level Up Event"
::= { traxTrapEnaEntry 3 }

traxTrapEnaX25FrameLevelDown OBJECT-TYPE
SYNTAX INTEGER{
  enable(1),
  disable(2)
}
ACCESS read-write
STATUS mandatory
DESCRIPTION
"Enable reporting of Hiper TRAX Frame Level Down Event"
::= { traxTrapEnaEntry 4 }

traxTrapEnaX25PacketLevelUp OBJECT-TYPE
SYNTAX INTEGER{
  enable(1),
  disable(2)
}
ACCESS read-write
STATUS mandatory
DESCRIPTION
"Enables Hiper TRAX packet level up event"
::= { traxTrapEnaEntry 5 }

traxTrapEnaX25PacketLevelDn OBJECT-TYPE
SYNTAX INTEGER{
  enable(1),
  disable(2)
}
ACCESS read-write
STATUS mandatory
DESCRIPTION
"Enable Hiper TRAX Packet Level Down Event"
::= { traxTrapEnaEntry 6 }

traxTrapEnaX25LostCalls OBJECT-TYPE
SYNTAX INTEGER{
  enable(1),
  disable(2)
}
ACCESS read-write
STATUS mandatory
DESCRIPTION
"Enables Hiper TRAX Lost Calls Event"
::= { traxTrapEnaEntry 7 }

traxTrapEnaX25LinkUp OBJECT-TYPE
SYNTAX INTEGER{
  enable(1),
  disable(2)
}
ACCESS read-write
STATUS mandatory
DESCRIPTION
"Enables Hiper TRAX link Up Event"
::= { traxTrapEnaEntry 8 }

traxTrapEnaX25LinkDn OBJECT-TYPE
SYNTAX INTEGER{
  enable(1),
  disable(2)
}
ACCESS read-write
STATUS mandatory
DESCRIPTION
"Enables Hiper TRAX Link Down Event"
::= { traxTrapEnaEntry 9 }

traxTrapEnaDnisLookUp OBJECT-TYPE
SYNTAX INTEGER{
  enable(1),
  disable(2)
}
ACCESS read-write
STATUS mandatory
DESCRIPTION
"Enables Hiper TRAX DNI Look Up event"
::= { traxTrapEnaEntry 10 }

traxTrapEnaSvcSetUp OBJECT-TYPE
SYNTAX INTEGER{
  enable(1),
  disable(2)
}
ACCESS read-write
STATUS mandatory
DESCRIPTION
"Enables Hiper TRAX SVC  setup failed Event"
::= { traxTrapEnaEntry 11 }

traxTrapEnaSvcAlarm OBJECT-TYPE
SYNTAX INTEGER{
  enable(1),
  disable(2)
}
ACCESS read-write
STATUS mandatory
DESCRIPTION
"Enables Hiper TRAX SVC alarm event"
::= { traxTrapEnaEntry 12 }

traxTrapDupTrans OBJECT-TYPE
SYNTAX INTEGER{
  enable(1),
  disable(2)
}
ACCESS read-write
STATUS mandatory
DESCRIPTION
"Enables Hiper TRAX duplicate transaction event"
::= { traxTrapEnaEntry 13 }

--The TRAX Card Visa Statistics.

traxVisaSts OBJECT IDENTIFIER ::= { trax 5 }

traxVisaStsTable OBJECT-TYPE
SYNTAX SEQUENCE OF TraxVisaStsEntry
ACCESS not-accessible
STATUS mandatory
DESCRIPTION
""
::= { traxVisaSts 1 }

traxVisaStsEntry OBJECT-TYPE
SYNTAX TraxVisaStsEntry
ACCESS not-accessible
STATUS mandatory
DESCRIPTION
"Entries of Hiper TRAX  VISA  Statistics"
INDEX { traxVisaStsIndex }
::= { traxVisaStsTable 1 }

TraxVisaStsEntry ::=
SEQUENCE {
traxVisaStsIndex
    INTEGER,
traxVisaCallCount
    Counter,
traxVisaTransactionCount
    Counter,
traxVisaRetransCount
    Counter,
traxVisaDuplicateTransCount
    Counter,
traxVisaDiscNormal
    Counter,
traxVisaDiscPosRequest
    Counter,
traxVisaDiscHostRequest
    Counter,
traxVisaDiscMaxEnqs
    Counter,
traxVisaDiscMaxRetranToPos
    Counter,
traxVisaDiscMaxRetranToHost
    Counter,
traxVisaDiscMaxBadFrames
    Counter,
traxVisaDiscPosWriteTimeouts
    Counter,
traxVisaDiscHostWriteTimeouts
    Counter,
traxVisaDiscSynDelayTooLong
    Counter,
traxVisaDiscBadCurrentState
    Counter,
traxVisaDiscUnexpectedEvent
    Counter,
traxVisaDiscNdcLogonFailures
    Counter,
traxVisaDiscPosRcvTimeouts
    Counter,
traxVisaDiscPosFrameTooBig
    Counter,
traxVisaDiscHostFrameTooBig
    Counter,
traxVisaDiscHostRespTimeouts
    Counter,
traxVisaDiscNumBadMsg
    Counter,
traxVisaDiscNumSystem
    Counter
}

traxVisaStsIndex OBJECT-TYPE
SYNTAX INTEGER
ACCESS read-only
STATUS mandatory
DESCRIPTION
"Index into Hiper TRAX Visa Table"
::= { traxVisaStsEntry 1 }

traxVisaCallCount OBJECT-TYPE
SYNTAX Counter
ACCESS read-only
STATUS mandatory
DESCRIPTION
"Number of calls in which VISA protocol was initiated"
::= { traxVisaStsEntry 2 }

traxVisaTransactionCount OBJECT-TYPE
SYNTAX Counter
ACCESS read-only
STATUS mandatory
DESCRIPTION
"Number of processed VISA transactions"
::= { traxVisaStsEntry 3 }

traxVisaRetransCount OBJECT-TYPE
SYNTAX Counter
ACCESS read-only
STATUS mandatory
DESCRIPTION
"Number of VISA retransmits to POS"
::= { traxVisaStsEntry 4 }

traxVisaDuplicateTransCount OBJECT-TYPE
SYNTAX Counter
ACCESS read-only
STATUS mandatory
DESCRIPTION
"Number of duplicate Visa Transactions Detected"
::= { traxVisaStsEntry 5 }

traxVisaDiscNormal OBJECT-TYPE
SYNTAX Counter
ACCESS read-only
STATUS mandatory
DESCRIPTION
"Number of Visa Calls that terminated normally"
::= { traxVisaStsEntry 6 }

traxVisaDiscPosRequest OBJECT-TYPE
SYNTAX Counter
ACCESS read-only
STATUS mandatory
DESCRIPTION
"Number of Visa Calls that disconnected at POS request"
::= { traxVisaStsEntry 7 }

traxVisaDiscHostRequest OBJECT-TYPE
SYNTAX Counter
ACCESS read-only
STATUS mandatory
DESCRIPTION
"Number of Visa Calls that disconnected at Host's request"
::= { traxVisaStsEntry 8 }

traxVisaDiscMaxEnqs OBJECT-TYPE
SYNTAX Counter
ACCESS read-only
STATUS mandatory
DESCRIPTION
"Number of VISA Calls disconnected due to exceeding maximum 
ENQ limit"
::= { traxVisaStsEntry 9 }

traxVisaDiscMaxRetranToPos OBJECT-TYPE
SYNTAX Counter
ACCESS read-only
STATUS mandatory
DESCRIPTION
"Number of VISA calls disconnected due to excedding maximum 
retransmissions to POS"
::= { traxVisaStsEntry 10 }

traxVisaDiscMaxRetranToHost OBJECT-TYPE
SYNTAX Counter
ACCESS read-only
STATUS mandatory
DESCRIPTION
"Number of VISA calls disconnected due to excedding maximum 
retransmissions to HOST"
::= { traxVisaStsEntry 11 }

traxVisaDiscMaxBadFrames OBJECT-TYPE
SYNTAX Counter
ACCESS read-only
STATUS mandatory
DESCRIPTION
"Number of VISA calls disconnected due to excedding maximum 
number of bad frames"
::= { traxVisaStsEntry 12 }

traxVisaDiscPosWriteTimeouts OBJECT-TYPE
SYNTAX Counter
ACCESS read-only
STATUS mandatory
DESCRIPTION
"Number of VISA calls disconnected due to excedding POS 
write timeout"
::= { traxVisaStsEntry 13 }

traxVisaDiscHostWriteTimeouts OBJECT-TYPE
SYNTAX Counter
ACCESS read-only
STATUS mandatory
DESCRIPTION
"Number of VISA calls disconnected due to excedding host 
write timeout"
::= { traxVisaStsEntry 14 }

traxVisaDiscSynDelayTooLong OBJECT-TYPE
SYNTAX Counter
ACCESS read-only
STATUS mandatory
DESCRIPTION
"Number of VISA calls disconnected due to excedding SYN 
delay limit"
::= { traxVisaStsEntry 15 }

traxVisaDiscBadCurrentState OBJECT-TYPE
SYNTAX Counter
ACCESS read-only
STATUS mandatory
DESCRIPTION
"Number of VISA calls disconnected due to Transaction 
process in wrong state"
::= { traxVisaStsEntry 16 }

traxVisaDiscUnexpectedEvent OBJECT-TYPE
SYNTAX Counter
ACCESS read-only
STATUS mandatory
DESCRIPTION
"Number of VISA calls disconnected due to occurence of an 
unexpected event in VISA protocol processing"
::= { traxVisaStsEntry 17 }

traxVisaDiscNdcLogonFailures OBJECT-TYPE
SYNTAX Counter
ACCESS read-only
STATUS mandatory
DESCRIPTION
"Number of calls disconnected due to too NDC Logon Failures"
::= { traxVisaStsEntry 18 }

traxVisaDiscPosRcvTimeouts OBJECT-TYPE
SYNTAX Counter
ACCESS read-only
STATUS mandatory
DESCRIPTION
"Number of calls disconnected due to POS exceeding timeout"
::= { traxVisaStsEntry 19 }

traxVisaDiscPosFrameTooBig OBJECT-TYPE
SYNTAX Counter
ACCESS read-only
STATUS mandatory
DESCRIPTION
"Number of calls disconnected due to too large frame from 
the POS"
::= { traxVisaStsEntry 20 }

traxVisaDiscHostFrameTooBig OBJECT-TYPE
SYNTAX Counter
ACCESS read-only
STATUS mandatory
DESCRIPTION
"Number of calls disconnected due to too large frame from 
Host"
::= { traxVisaStsEntry 21 }

traxVisaDiscHostRespTimeouts OBJECT-TYPE
SYNTAX Counter
ACCESS read-only
STATUS mandatory
DESCRIPTION
"Number of calls disconnected due to timeout on response 
from the host"
::= { traxVisaStsEntry 22 }

traxVisaDiscNumBadMsg OBJECT-TYPE
SYNTAX Counter
ACCESS read-only
STATUS mandatory
DESCRIPTION
"Number of calls disconnected due to bad message"
::= { traxVisaStsEntry 23 }

traxVisaDiscNumSystem OBJECT-TYPE
SYNTAX Counter
ACCESS read-only
STATUS mandatory
DESCRIPTION
""
::= { traxVisaStsEntry 24 }

--The TRAX CARD Synchronous transaction Statistics Group.

traxSyncSts OBJECT IDENTIFIER ::= { trax 6 }

traxSyncStsTable OBJECT-TYPE
SYNTAX SEQUENCE OF TraxSyncStsEntry
ACCESS not-accessible
STATUS mandatory
DESCRIPTION
"Hiper TRAX Synchronus  Transaction Statistics Group"
::= { traxSyncSts 1 }

traxSyncStsEntry OBJECT-TYPE
SYNTAX TraxSyncStsEntry
ACCESS not-accessible
STATUS mandatory
DESCRIPTION
""
INDEX { traxSyncStsIndex }
::= { traxSyncStsTable 1 }

TraxSyncStsEntry ::=
SEQUENCE {
traxSyncStsIndex
    INTEGER,
traxSyncCallCount
    Counter,
traxSyncTransactionCount
    Counter,
traxSyncDiscNormal
    Counter,
traxSyncDiscMaxRetrans
    Counter,
traxSyncDiscMaxSnrms
    Counter,
traxSyncDiscHostFrameTooBig
    Counter,
traxSyncDiscPosFrameTooSmall
    Counter,
traxSyncDiscPosFrameTooBig
    Counter,
traxSyncDiscHostFlowOffTimeOuts
    Counter,
traxSyncDiscPosFlowoffTimeOuts
    Counter,
traxSyncDiscInactivityTimeouts
    Counter,
traxSyncDiscNoBuffers
    Counter,
traxSyncDiscInvalidEvent
    Counter,
traxSyncDiscInvalidState
    Counter
}

traxSyncStsIndex OBJECT-TYPE
SYNTAX INTEGER
ACCESS read-only
STATUS mandatory
DESCRIPTION
"Index for Hiper TRAX Synchronus Transaction Statistics 
Table"
::= { traxSyncStsEntry 1 }

traxSyncCallCount OBJECT-TYPE
SYNTAX Counter
ACCESS read-only
STATUS mandatory
DESCRIPTION
"Number of Calls for which synchronous transaction was 
initiated"
::= { traxSyncStsEntry 2 }

traxSyncTransactionCount OBJECT-TYPE
SYNTAX Counter
ACCESS read-only
STATUS mandatory
DESCRIPTION
"Number of processed synchronous transaction"
::= { traxSyncStsEntry 3 }

traxSyncDiscNormal OBJECT-TYPE
SYNTAX Counter
ACCESS read-only
STATUS mandatory
DESCRIPTION
"Number of processed synchronous calls disconnected 
normally"
::= { traxSyncStsEntry 4 }

traxSyncDiscMaxRetrans OBJECT-TYPE
SYNTAX Counter
ACCESS read-only
STATUS mandatory
DESCRIPTION
"Number of synchronous call disconnected due to excedding 
the max number of retransmissions without acknowledgments"
::= { traxSyncStsEntry 5 }

traxSyncDiscMaxSnrms OBJECT-TYPE
SYNTAX Counter
ACCESS read-only
STATUS mandatory
DESCRIPTION
"Number of synchronous call disconnected because link could 
not be initiated within SNRM limit"
::= { traxSyncStsEntry 6 }

traxSyncDiscHostFrameTooBig OBJECT-TYPE
SYNTAX Counter
ACCESS read-only
STATUS mandatory
DESCRIPTION
"Number of processed synchronous calls disconnected beacause 
too large an iframe was received from the host"
::= { traxSyncStsEntry 7 }

traxSyncDiscPosFrameTooSmall OBJECT-TYPE
SYNTAX Counter
ACCESS read-only
STATUS mandatory
DESCRIPTION
"Number of processed synchronous calls disconnected beacause 
too small an iframe was received from the host"
::= { traxSyncStsEntry 8 }

traxSyncDiscPosFrameTooBig OBJECT-TYPE
SYNTAX Counter
ACCESS read-only
STATUS mandatory
DESCRIPTION
"Number of processed synchronous calls disconnected beacause 
too large an iframe was received from the POS"
::= { traxSyncStsEntry 9 }

traxSyncDiscHostFlowOffTimeOuts OBJECT-TYPE
SYNTAX Counter
ACCESS read-only
STATUS mandatory
DESCRIPTION
"Number of processed synchronous calls disconnected because 
host has flowed off for too long"
::= { traxSyncStsEntry 10 }

traxSyncDiscPosFlowoffTimeOuts OBJECT-TYPE
SYNTAX Counter
ACCESS read-only
STATUS mandatory
DESCRIPTION
"Number of processed synchronous calls disconnected because 
POS has flowed off for too long"
::= { traxSyncStsEntry 11 }

traxSyncDiscInactivityTimeouts OBJECT-TYPE
SYNTAX Counter
ACCESS read-only
STATUS mandatory
DESCRIPTION
"Number of processed synchronous calls disconnected because 
there has been no inframe activity for too long"
::= { traxSyncStsEntry 12 }

traxSyncDiscNoBuffers OBJECT-TYPE
SYNTAX Counter
ACCESS read-only
STATUS mandatory
DESCRIPTION
"Number of processed synchronous calls disconnected because 
of internal buffer allocation problems"
::= { traxSyncStsEntry 13 }

traxSyncDiscInvalidEvent OBJECT-TYPE
SYNTAX Counter
ACCESS read-only
STATUS mandatory
DESCRIPTION
"Number of Synchronous calls disconnected due to occurrence 
of an unexpected event in the synchronous protocol 
processing"
::= { traxSyncStsEntry 14 }

traxSyncDiscInvalidState OBJECT-TYPE
SYNTAX Counter
ACCESS read-only
STATUS mandatory
DESCRIPTION
"Number of Synchronous calls disconnected"
::= { traxSyncStsEntry 15 }

--The TRAX Card X25W Sts.

traxX25wSts OBJECT IDENTIFIER ::= { trax 7 }

traxx25wanStats OBJECT IDENTIFIER ::= { traxX25wSts 1 }

traxx25wanStatsTable OBJECT-TYPE
SYNTAX SEQUENCE OF Traxx25wanStatsEntry
ACCESS not-accessible
STATUS mandatory
DESCRIPTION
"The x25wanStatsTable is composed of counters which allow 
the operator to view activity which can indicate the health 
of the WAN connection."
::= { traxx25wanStats 1 }

traxx25wanStatsEntry OBJECT-TYPE
SYNTAX Traxx25wanStatsEntry
ACCESS not-accessible
STATUS mandatory
DESCRIPTION
"There is one X.25 WAN status entry for each x.25 subnet 
installed in the NAS chassis."
INDEX { traxx25wanStatsIndex }
::= { traxx25wanStatsTable 1 }

Traxx25wanStatsEntry ::=
SEQUENCE {
traxx25wanStatsIndex
    INTEGER,
traxx25wanStatsGoodFramesTxs
    Counter,
traxx25wanStatsGoodFramesRxs
    Counter,
traxx25wanStatsTxUnderruns
    Counter,
traxx25wanStatsRxOverruns
    Counter,
traxx25wanStatsRxCrcErrs
    Counter,
traxx25wanStatsRxFrameNoBufs
    Counter,
traxx25wanStatsUnrecoveredRxs
    Counter,
traxx25wanStatsRxOverflows
    Counter,
traxx25wanStatsRxAborts
    Counter,
traxx25wanStatsRxTooLongs
    Counter,
traxx25wanStatsTxTooShorts
    Counter,
traxx25wanStatsRxTooShorts
    Counter,
traxx25wanStatsTxBadPackets
    Counter,
traxx25wanStatsTxRingQFulls
    Counter,
traxx25wanStatsDSR
    INTEGER,
traxx25wanStatsCTS
    INTEGER,
traxx25wanStatsDCD
    INTEGER
}

traxx25wanStatsIndex OBJECT-TYPE
SYNTAX INTEGER
ACCESS read-only
STATUS mandatory
DESCRIPTION
"A unique value for each X25 WAN port in the NAS chassis.  
The value of this index matches is the entity index 
associated with this X25 subnet found in the USR Chassis 
MIB."
::= { traxx25wanStatsEntry 1 }

traxx25wanStatsGoodFramesTxs OBJECT-TYPE
SYNTAX Counter
ACCESS read-only
STATUS mandatory
DESCRIPTION
"A count of the number of good frames transmitted since this 
entity was initialized."
::= { traxx25wanStatsEntry 2 }

traxx25wanStatsGoodFramesRxs OBJECT-TYPE
SYNTAX Counter
ACCESS read-only
STATUS mandatory
DESCRIPTION
"A count of the good frames received since this entity was 
intitalized."
::= { traxx25wanStatsEntry 3 }

traxx25wanStatsTxUnderruns OBJECT-TYPE
SYNTAX Counter
ACCESS read-only
STATUS mandatory
DESCRIPTION
"A count of the number of transmit underruns that have been 
seen by this entity since initialization."
::= { traxx25wanStatsEntry 4 }

traxx25wanStatsRxOverruns OBJECT-TYPE
SYNTAX Counter
ACCESS read-only
STATUS mandatory
DESCRIPTION
"The number of receiver overruns detected by this entity 
since intitialization."
::= { traxx25wanStatsEntry 5 }

traxx25wanStatsRxCrcErrs OBJECT-TYPE
SYNTAX Counter
ACCESS read-only
STATUS mandatory
DESCRIPTION
"The number of received crc errors since this entity was 
intitialized."
::= { traxx25wanStatsEntry 6 }

traxx25wanStatsRxFrameNoBufs OBJECT-TYPE
SYNTAX Counter
ACCESS read-only
STATUS mandatory
DESCRIPTION
"The number of times this entity has recieved data without a 
buffer to place it into."
::= { traxx25wanStatsEntry 7 }

traxx25wanStatsUnrecoveredRxs OBJECT-TYPE
SYNTAX Counter
ACCESS read-only
STATUS mandatory
DESCRIPTION
"The number of overrun frames that the entity was unable to 
recover."
::= { traxx25wanStatsEntry 8 }

traxx25wanStatsRxOverflows OBJECT-TYPE
SYNTAX Counter
ACCESS read-only
STATUS mandatory
DESCRIPTION
"The number of receive buffer overflows seen by this entity 
since initialization."
::= { traxx25wanStatsEntry 9 }

traxx25wanStatsRxAborts OBJECT-TYPE
SYNTAX Counter
ACCESS read-only
STATUS mandatory
DESCRIPTION
"The number of recieve frame aborts seen by this entity 
since initialization."
::= { traxx25wanStatsEntry 10 }

traxx25wanStatsRxTooLongs OBJECT-TYPE
SYNTAX Counter
ACCESS read-only
STATUS mandatory
DESCRIPTION
"The number of frames recieved that exceeded the defined 
maximum receive frame size."
::= { traxx25wanStatsEntry 11 }

traxx25wanStatsTxTooShorts OBJECT-TYPE
SYNTAX Counter
ACCESS read-only
STATUS mandatory
DESCRIPTION
"The number of times that the upper protocol layers 
attempted to transmit too small a frame."
::= { traxx25wanStatsEntry 12 }

traxx25wanStatsRxTooShorts OBJECT-TYPE
SYNTAX Counter
ACCESS read-only
STATUS mandatory
DESCRIPTION
"A count of the number of frames received that were smaller 
than the minimum frame size."

::= { traxx25wanStatsEntry 13 }

traxx25wanStatsTxBadPackets OBJECT-TYPE
SYNTAX Counter
ACCESS read-only
STATUS mandatory
DESCRIPTION
"The number of bad packets that the WAN interface received 
for transmission from the upper layers of the X.25 protocol 
stack."
::= { traxx25wanStatsEntry 14 }

traxx25wanStatsTxRingQFulls OBJECT-TYPE
SYNTAX Counter
ACCESS read-only
STATUS mandatory
DESCRIPTION
"A count of the number of times the circular buffer used for 
transmission was full when a transmission was attempted by 
the upper layers of the X.25 protocol stack."
::= { traxx25wanStatsEntry 15 }

traxx25wanStatsDSR OBJECT-TYPE
SYNTAX INTEGER{
  off(1),
  on(2)
}
ACCESS read-only
STATUS mandatory
DESCRIPTION
"X.25 WAN interface DSR signal status."
::= { traxx25wanStatsEntry 17 }

traxx25wanStatsCTS OBJECT-TYPE
SYNTAX INTEGER{
  off(1),
  on(2)
}
ACCESS read-only
STATUS mandatory
DESCRIPTION
"X.25 WAN interface CTS signal status."
::= { traxx25wanStatsEntry 18 }

traxx25wanStatsDCD OBJECT-TYPE
SYNTAX INTEGER{
  off(1),
  on(2)
}
ACCESS read-only
STATUS mandatory
DESCRIPTION
"X.25 WAN interface DCD signal status."
::= { traxx25wanStatsEntry 19 }

--The TRAX Card UX25 Sts.

traxUX25Sts OBJECT IDENTIFIER ::= { trax 8 }

traxUx25StatTable OBJECT-TYPE
SYNTAX SEQUENCE OF TraxUx25StatEntry
ACCESS not-accessible
STATUS mandatory
DESCRIPTION
"Defines Object that Report Operational sts for an Hiper 
TRAX interface"
::= { traxUX25Sts 1 }

traxUx25StatEntry OBJECT-TYPE
SYNTAX TraxUx25StatEntry
ACCESS not-accessible
STATUS mandatory
DESCRIPTION
"Entries of ux25StatTable."
INDEX { traxUx25StatIndex }
::= { traxUx25StatTable 1 }

TraxUx25StatEntry ::=
SEQUENCE {
traxUx25StatIndex
    INTEGER,
traxUx25StatCallsRcvd
    INTEGER,
traxUx25StatCallsSent
    INTEGER,
traxUx25StatCallsRcvdEstab
    INTEGER,
traxUx25StatCallsSentEstab
    INTEGER,
traxUx25StatDataPktsRcvd
    INTEGER,
traxUx25StatDataPktsSent
    INTEGER,
traxUx25StatRestartsRcvd
    INTEGER,
traxUx25StatRestartsSent
    INTEGER,
traxUx25StatRcvrNotRdyRcvd
    INTEGER,
traxUx25StatRcvrNotRdySent
    INTEGER,
traxUx25StatRcvrRdyRcvd
    INTEGER,
traxUx25StatRcvrRdySent
    INTEGER,
traxUx25StatResetsRcvd
    INTEGER,
traxUx25StatResetsSent
    INTEGER,
traxUx25StatDiagPktsRcvd
    INTEGER,
traxUx25StatDiagPktsSent
    INTEGER,
traxUx25StatIntrptPktsRcvd
    INTEGER,
traxUx25StatIntrptPktsSent
    INTEGER,
traxUx25StatRejPktsRcvd
    INTEGER,
traxUx25StatRejPktsSent
    INTEGER,
traxUx25StatClrPktRcvd
    INTEGER,
traxUx25StatClrPktSent
    INTEGER,
traxUx25StatPVCsInDatTrnsfrState
    INTEGER,
traxUx25StatSVCsInDatTrnsfrState
    INTEGER
}

traxUx25StatIndex OBJECT-TYPE
SYNTAX INTEGER
ACCESS read-only
STATUS mandatory
DESCRIPTION
"A unique value for each Hiper TRAX subnetwork entity in the 
chassis.  The value of this object matches the value of the 
index of the corresponding Hiper TRAX subnetwork entity 
entry in the entity table of the chassis MIB."
::= { traxUx25StatEntry 1 }

traxUx25StatCallsRcvd OBJECT-TYPE
SYNTAX INTEGER
ACCESS read-only
STATUS mandatory
DESCRIPTION
"Number of incoming calls."
::= { traxUx25StatEntry 2 }

traxUx25StatCallsSent OBJECT-TYPE
SYNTAX INTEGER
ACCESS read-only
STATUS mandatory
DESCRIPTION
"Number of outgoing calls."
::= { traxUx25StatEntry 3 }

traxUx25StatCallsRcvdEstab OBJECT-TYPE
SYNTAX INTEGER
ACCESS read-only
STATUS mandatory
DESCRIPTION
"Number of incoming calls established."
::= { traxUx25StatEntry 4 }

traxUx25StatCallsSentEstab OBJECT-TYPE
SYNTAX INTEGER
ACCESS read-only
STATUS mandatory
DESCRIPTION
"Number of outgoing calls established."
::= { traxUx25StatEntry 5 }

traxUx25StatDataPktsRcvd OBJECT-TYPE
SYNTAX INTEGER
ACCESS read-only
STATUS mandatory
DESCRIPTION
"Number of data packets received."
::= { traxUx25StatEntry 6 }

traxUx25StatDataPktsSent OBJECT-TYPE
SYNTAX INTEGER
ACCESS read-only
STATUS mandatory
DESCRIPTION
"Number of data packets sent."
::= { traxUx25StatEntry 7 }

traxUx25StatRestartsRcvd OBJECT-TYPE
SYNTAX INTEGER
ACCESS read-only
STATUS mandatory
DESCRIPTION
"Number of restarts received."
::= { traxUx25StatEntry 8 }

traxUx25StatRestartsSent OBJECT-TYPE
SYNTAX INTEGER
ACCESS read-only
STATUS mandatory
DESCRIPTION
"Number of restarts sent."
::= { traxUx25StatEntry 9 }

traxUx25StatRcvrNotRdyRcvd OBJECT-TYPE
SYNTAX INTEGER
ACCESS read-only
STATUS mandatory
DESCRIPTION
"Number of receiver not ready received."
::= { traxUx25StatEntry 10 }

traxUx25StatRcvrNotRdySent OBJECT-TYPE
SYNTAX INTEGER
ACCESS read-only
STATUS mandatory
DESCRIPTION
"Number of receiver not ready sent."
::= { traxUx25StatEntry 11 }

traxUx25StatRcvrRdyRcvd OBJECT-TYPE
SYNTAX INTEGER
ACCESS read-only
STATUS mandatory
DESCRIPTION
"Number of receiver ready received."
::= { traxUx25StatEntry 12 }

traxUx25StatRcvrRdySent OBJECT-TYPE
SYNTAX INTEGER
ACCESS read-only
STATUS mandatory
DESCRIPTION
"Number of receiver ready sent."
::= { traxUx25StatEntry 13 }

traxUx25StatResetsRcvd OBJECT-TYPE
SYNTAX INTEGER
ACCESS read-only
STATUS mandatory
DESCRIPTION
"Number of resets received."
::= { traxUx25StatEntry 14 }

traxUx25StatResetsSent OBJECT-TYPE
SYNTAX INTEGER
ACCESS read-only
STATUS mandatory
DESCRIPTION
"Number of resets sent."
::= { traxUx25StatEntry 15 }

traxUx25StatDiagPktsRcvd OBJECT-TYPE
SYNTAX INTEGER
ACCESS read-only
STATUS mandatory
DESCRIPTION
"Number of diagnostic packets received."
::= { traxUx25StatEntry 16 }

traxUx25StatDiagPktsSent OBJECT-TYPE
SYNTAX INTEGER
ACCESS read-only
STATUS mandatory
DESCRIPTION
"Number of diagnostic packets sent."
::= { traxUx25StatEntry 17 }

traxUx25StatIntrptPktsRcvd OBJECT-TYPE
SYNTAX INTEGER
ACCESS read-only
STATUS mandatory
DESCRIPTION
"Number of interrupt packets received."
::= { traxUx25StatEntry 18 }

traxUx25StatIntrptPktsSent OBJECT-TYPE
SYNTAX INTEGER
ACCESS read-only
STATUS mandatory
DESCRIPTION
"Number of interrupt packets sent."
::= { traxUx25StatEntry 19 }

traxUx25StatRejPktsRcvd OBJECT-TYPE
SYNTAX INTEGER
ACCESS read-only
STATUS mandatory
DESCRIPTION
"Number of rejects packets received"
::= { traxUx25StatEntry 20 }

traxUx25StatRejPktsSent OBJECT-TYPE
SYNTAX INTEGER
ACCESS read-only
STATUS mandatory
DESCRIPTION
"Number of rejects packets sent"
::= { traxUx25StatEntry 21 }

traxUx25StatClrPktRcvd OBJECT-TYPE
SYNTAX INTEGER
ACCESS read-only
STATUS mandatory
DESCRIPTION
"Number of clear packets received"
::= { traxUx25StatEntry 22 }

traxUx25StatClrPktSent OBJECT-TYPE
SYNTAX INTEGER
ACCESS read-only
STATUS mandatory
DESCRIPTION
"Number of clear packets sent"
::= { traxUx25StatEntry 23 }

traxUx25StatPVCsInDatTrnsfrState OBJECT-TYPE
SYNTAX INTEGER
ACCESS read-only
STATUS mandatory
DESCRIPTION
"Number of PVCs in Data Transfer State."
::= { traxUx25StatEntry 24 }

traxUx25StatSVCsInDatTrnsfrState OBJECT-TYPE
SYNTAX INTEGER
ACCESS read-only
STATUS mandatory
DESCRIPTION
"Number of SVCs in Data Transfer State."
::= { traxUx25StatEntry 25 }

--The TRAX CARD ULPB Sts.

traxULPBSts OBJECT IDENTIFIER ::= { trax 9 }

traxulpbStatTable OBJECT-TYPE
SYNTAX SEQUENCE OF TraxulpbStatEntry
ACCESS not-accessible
STATUS mandatory
DESCRIPTION
""
::= { traxULPBSts 1 }

traxulpbStatEntry OBJECT-TYPE
SYNTAX TraxulpbStatEntry
ACCESS not-accessible
STATUS mandatory
DESCRIPTION
"Entries of ulpbStatTrable."
INDEX { traxulpbStatIndex }
::= { traxulpbStatTable 1 }

TraxulpbStatEntry ::=
SEQUENCE {
traxulpbStatIndex
    INTEGER,
traxulpbStatRRRcvd
    INTEGER,
traxulpbStatRRTrnsmt
    INTEGER,
traxulpbStatRNRCmdsRcvd
    INTEGER,
traxulpbStatRNRCmdsTrnsmt
    INTEGER,
traxulpbStatREJCmdsRcvd
    INTEGER,
traxulpbStatREJCmdsTrnsmt
    INTEGER,
traxulpbStatREJRspsRcvd
    INTEGER,
traxulpbStatREJRspsTrnsmt
    INTEGER,
traxulpbStatSABMCmdsRcvd
    INTEGER,
traxulpbStatSABMCmdsTrnsmt
    INTEGER,
traxulpbStatSABMECmdsRcvd
    INTEGER,
traxulpbStatSABMECmdsTransmit
    INTEGER,
traxulpbStatDISCCmdsRcvd
    INTEGER,
traxulpbStatDISCCmdsTrnsmt
    INTEGER,
traxulpbStatDMRspsRcvd
    INTEGER,
traxulpbStatDMRspsTrnsmt
    INTEGER,
traxulpbStatUARspsRcvd
    INTEGER,
traxulpbStatUARspsTrnsmt
    INTEGER,
traxulpbStatFRMRRspsRcvd
    INTEGER,
traxulpbStatFRMRRspsTrnsmt
    INTEGER,
traxulpbStatIFrameCmdsRcvd
    INTEGER,
traxulpbStatIFrameCmdsTrnsmt
    INTEGER
}

traxulpbStatIndex OBJECT-TYPE
SYNTAX INTEGER
ACCESS read-only
STATUS mandatory
DESCRIPTION
"A unique value for each  Hiper TRAX entity running LAPB in 
the chassis.  The value of this object matches the value of 
the index of the corresponding X.25 subnetwork entity 
running LAPB entry in the entity table of the chassis MIB."
::= { traxulpbStatEntry 1 }

traxulpbStatRRRcvd OBJECT-TYPE
SYNTAX INTEGER
ACCESS read-only
STATUS mandatory
DESCRIPTION
"Number of RR commands received."
::= { traxulpbStatEntry 2 }

traxulpbStatRRTrnsmt OBJECT-TYPE
SYNTAX INTEGER
ACCESS read-only
STATUS mandatory
DESCRIPTION
"Number of RR commands transmitted."
::= { traxulpbStatEntry 3 }

traxulpbStatRNRCmdsRcvd OBJECT-TYPE
SYNTAX INTEGER
ACCESS read-only
STATUS mandatory
DESCRIPTION
"Number of RNR commands received."
::= { traxulpbStatEntry 4 }

traxulpbStatRNRCmdsTrnsmt OBJECT-TYPE
SYNTAX INTEGER
ACCESS read-only
STATUS mandatory
DESCRIPTION
"Number of RNR commands transmitted."
::= { traxulpbStatEntry 5 }

traxulpbStatREJCmdsRcvd OBJECT-TYPE
SYNTAX INTEGER
ACCESS read-only
STATUS mandatory
DESCRIPTION
"Number of REJ commands received."
::= { traxulpbStatEntry 6 }

traxulpbStatREJCmdsTrnsmt OBJECT-TYPE
SYNTAX INTEGER
ACCESS read-only
STATUS mandatory
DESCRIPTION
"Number of REJ commands transmitted."
::= { traxulpbStatEntry 7 }

traxulpbStatREJRspsRcvd OBJECT-TYPE
SYNTAX INTEGER
ACCESS read-only
STATUS mandatory
DESCRIPTION
"Number of REJ responses received."
::= { traxulpbStatEntry 8 }

traxulpbStatREJRspsTrnsmt OBJECT-TYPE
SYNTAX INTEGER
ACCESS read-only
STATUS mandatory
DESCRIPTION
"Number of REJ responses transmitted."
::= { traxulpbStatEntry 9 }

traxulpbStatSABMCmdsRcvd OBJECT-TYPE
SYNTAX INTEGER
ACCESS read-only
STATUS mandatory
DESCRIPTION
"Number of SABM commands received."
::= { traxulpbStatEntry 10 }

traxulpbStatSABMCmdsTrnsmt OBJECT-TYPE
SYNTAX INTEGER
ACCESS read-only
STATUS mandatory
DESCRIPTION
"Number of SABM commands transmitted."
::= { traxulpbStatEntry 11 }

traxulpbStatSABMECmdsRcvd OBJECT-TYPE
SYNTAX INTEGER
ACCESS read-only
STATUS mandatory
DESCRIPTION
"Number of SABME commands received."
::= { traxulpbStatEntry 12 }

traxulpbStatSABMECmdsTransmit OBJECT-TYPE
SYNTAX INTEGER
ACCESS read-only
STATUS mandatory
DESCRIPTION
"Number of SABME commands transmitted."
::= { traxulpbStatEntry 13 }

traxulpbStatDISCCmdsRcvd OBJECT-TYPE
SYNTAX INTEGER
ACCESS read-only
STATUS mandatory
DESCRIPTION
"Number of DISC commands received."
::= { traxulpbStatEntry 14 }

traxulpbStatDISCCmdsTrnsmt OBJECT-TYPE
SYNTAX INTEGER
ACCESS read-only
STATUS mandatory
DESCRIPTION
"Number of DISC commands transmitted."
::= { traxulpbStatEntry 15 }

traxulpbStatDMRspsRcvd OBJECT-TYPE
SYNTAX INTEGER
ACCESS read-only
STATUS mandatory
DESCRIPTION
"Number of DM response received."
::= { traxulpbStatEntry 16 }

traxulpbStatDMRspsTrnsmt OBJECT-TYPE
SYNTAX INTEGER
ACCESS read-only
STATUS mandatory
DESCRIPTION
"Number of DM response transmitted."
::= { traxulpbStatEntry 17 }

traxulpbStatUARspsRcvd OBJECT-TYPE
SYNTAX INTEGER
ACCESS read-only
STATUS mandatory
DESCRIPTION
"Number of UA response received."
::= { traxulpbStatEntry 18 }

traxulpbStatUARspsTrnsmt OBJECT-TYPE
SYNTAX INTEGER
ACCESS read-only
STATUS mandatory
DESCRIPTION
"Number of UA response transmitted."
::= { traxulpbStatEntry 19 }

traxulpbStatFRMRRspsRcvd OBJECT-TYPE
SYNTAX INTEGER
ACCESS read-only
STATUS mandatory
DESCRIPTION
"Number of FRMR response received."
::= { traxulpbStatEntry 20 }

traxulpbStatFRMRRspsTrnsmt OBJECT-TYPE
SYNTAX INTEGER
ACCESS read-only
STATUS mandatory
DESCRIPTION
"Number of FRMR response transmitted."
::= { traxulpbStatEntry 21 }

traxulpbStatIFrameCmdsRcvd OBJECT-TYPE
SYNTAX INTEGER
ACCESS read-only
STATUS mandatory
DESCRIPTION
"Number of IFRMR CMD Recvd."
::= { traxulpbStatEntry 22 }

traxulpbStatIFrameCmdsTrnsmt OBJECT-TYPE
SYNTAX INTEGER
ACCESS read-only
STATUS mandatory
DESCRIPTION
"Number of IFRMR CMD Trsmit."
::= { traxulpbStatEntry 23 }

END
