CXIoHardware-MIB DEFINITIONS ::= BEGIN

--#CURRENT_VERSION 1

IMPORTS
	OBJECT-TYPE     FROM RFC-1212
	TRAP-TYPE               FROM RFC-1215

--  Proprietary Imports
	cxIoHardware, Alias     FROM CXProduct-SMI;



cxIoCardAdmTable        OBJECT-TYPE
	SYNTAX  SEQUENCE OF CxIoCardAdmEntry
	ACCESS  not-accessible
	STATUS  mandatory
	DESCRIPTION
"Administrative table used to configure the required I/O card hardware."
	::= { cxIoHardware 1 }

	cxIoCardAdmEntry        OBJECT-TYPE
		SYNTAX  CxIoCardAdmEntry
		ACCESS  not-accessible
		STATUS  mandatory
		DESCRIPTION
"The parameters required to fully specify the I/O card."
		INDEX { cxIoCardAdmIndex }
		::= { cxIoCardAdmTable  1 }

	CxIoCardAdmEntry ::=
		SEQUENCE {
			cxIoCardAdmIndex
				INTEGER,
			cxIoCardAdmRowStatus
				INTEGER,
			cxIoCardAdmAlias
				Alias,
			cxIoCardAdmPhysSlot
				INTEGER,
			cxIoCardAdmType
				INTEGER,
			cxIoCardAdmState
				INTEGER
			}


	cxIoCardAdmIndex        OBJECT-TYPE
		SYNTAX  INTEGER
		ACCESS  read-only
		STATUS  mandatory
		DESCRIPTION
"Index used for table management only. No other MIB object refers to this 
index."
		::= { cxIoCardAdmEntry 1 }

	cxIoCardAdmRowStatus    OBJECT-TYPE
		SYNTAX  INTEGER {
					invalid (1),
					valid   (2),
					disabled  (3)
				}
		ACCESS  read-write
		STATUS  mandatory
		DESCRIPTION
"Indicates whether a particular I/O card is configured within the MIB.

Options:
invalid (1): Deletes an I/O card entry (row) from the MIB table.

valid (2): Creates an I/O card entry (row) in the MIB table.

disabled (3): No I/O card entries being created or deleted.

Default Value: disabled (3)

Configuration Changed: operative"
		DEFVAL     { disabled }
		::= { cxIoCardAdmEntry 2 }


	cxIoCardAdmAlias        OBJECT-TYPE
		SYNTAX  Alias   
		ACCESS  read-write
		STATUS  mandatory
		DESCRIPTION
"Identifies an alias or alternative name for this card. This alias is 
recorded in the port administrative table to link it to the correct I/O card.

Range of Values: 0 to 35 alphanumeric characters beginning with a 
non-numeric character

Default Value: none

Configuration Changed: administrative"
		::= { cxIoCardAdmEntry 3 }


	cxIoCardAdmPhysSlot     OBJECT-TYPE
		SYNTAX  INTEGER
		ACCESS  read-write
		STATUS  mandatory
		DESCRIPTION
"Identifies the CX1000 I/O slot being configured.

Range of Values: 1 - 16

Default Value: none

Configuration Changed: administrative"
		::= { cxIoCardAdmEntry 4 }

	cxIoCardAdmType OBJECT-TYPE
		SYNTAX  INTEGER {       
					iuscFourPortCard (1),
					lanCard (2),
               vceCmpCard (3),
               tokenRingCard (4),
               ethernetCard (5),
               isdnCard (6),
               digitalVceCmpCard (7),
               highSpeedFr4LIDCard (8),
               octalV34ModemCard (9)
				}       
		ACCESS  read-write
		STATUS  mandatory
		DESCRIPTION
"Identifies the type of card that occupies or will occupy this slot.

Options:
iuscFourPortCard (1): a proprietary I/O card

lanCard (2): a LAN adapter such as an Ethernet or Token-Ring card

vceCmpCard (3): a voice Compression Card

tokenRingCard (4): a Token-Ring I/O card for TL600

ethernetCard (5): an Ethernet I/O card for EL600

isdnCard (6): a T1/E1 ISDN I/O card

digitalVceCmpCard (7): a Digital Voice Compression Card ( 15 channels )

highSpeedFr4LIDCard (8): a high speed frame relay 4-LID I/O card

octalV34ModemCard (9): an octal V.34 modem I/O card

Default Value: none

Related Objects:
cxIoCardAdmState
cxIoCardAdmPhysSlot

Configuration Changed: administrative"
		::= { cxIoCardAdmEntry 5 }


	cxIoCardAdmState        OBJECT-TYPE
		SYNTAX  INTEGER {
					invalid (1),
					valid   (2)
				}
		ACCESS  read-only
		STATUS  mandatory
		DESCRIPTION
"Indicates whether the card type configured using the cxIoCardAdmType 
object matches the card inserted in the slot.

Options:
invalid (1): The configured card type does not match the card inserted in 
the slot. You must adjust one or the other.

valid (2): The configured card typed matches the card inserted in the slot.

Related Objects:
cxIoCardAdmPhysSlot
cxIoCardAdmType"
		DEFVAL  { valid  }
		::= { cxIoCardAdmEntry 6 }


cxIoPortAdmTable        OBJECT-TYPE
	SYNTAX  SEQUENCE OF CxIoPortAdmEntry
	ACCESS  not-accessible
	STATUS  mandatory
	DESCRIPTION
"Administrative table used to configure the required I/O port hardware."
	::= { cxIoHardware 2 }

	cxIoPortAdmEntry        OBJECT-TYPE
		SYNTAX  CxIoPortAdmEntry
		ACCESS  not-accessible
		STATUS  mandatory
		DESCRIPTION
"The parameters required to fully specify the I/O port."
		INDEX { cxIoPortAdmIndex }
		::= { cxIoPortAdmTable 1 }

	CxIoPortAdmEntry ::=
		SEQUENCE {
			cxIoPortAdmIndex
				INTEGER,
			cxIoPortAdmRowStatus
				INTEGER,
			cxIoPortAdmAlias
				Alias,
			cxIoPortAdmCardAlias
				Alias,
			cxIoPortAdmCardLocalIndex
				INTEGER
			}

	
cxIoPortAdmIndex        OBJECT-TYPE
		SYNTAX  INTEGER
		ACCESS  read-only
		STATUS  mandatory
		DESCRIPTION
"Index used for table management only. No other MIB object refers to this 
index."
		::= { cxIoPortAdmEntry 1 }

	cxIoPortAdmRowStatus    OBJECT-TYPE
		SYNTAX  INTEGER {
					invalid (1),
					valid   (2),
					disabled (3)
				}
		ACCESS  read-write
		STATUS  mandatory
		DESCRIPTION
"Indicates whether a particular I/O port is configured within the MIB.

Options:
invalid (1): Deletes an I/O port entry (row) from the MIB table.

valid (2): Creates an I/O port entry (row) in the MIB table.

disabled (3): No I/O port entries (rows) created or deleted.

Default Value: disabled (3)

Configuration Changed: operative"
		DEFVAL  { disabled }
		::= { cxIoPortAdmEntry 2 }


	cxIoPortAdmAlias        OBJECT-TYPE
		SYNTAX  Alias   
		ACCESS  read-write
		STATUS  mandatory
		DESCRIPTION
"Specifies an alias or alternative name for this hardware port. This alias 
is used by the related driver SAP to link it to the correct I/O hardware 
port.

Range of Values: 0 to 35 alphanumeric characters beginning with a 
non-numeric character

Default Value: none

Configuration Changed: administrative"
		::= { cxIoPortAdmEntry 3 }


	cxIoPortAdmCardAlias OBJECT-TYPE
		SYNTAX  Alias   
		ACCESS  read-write
		STATUS  mandatory
		DESCRIPTION
"Specifies the alias of the I/O card containing this port.

Range of Values: 0 to 35 alphanumeric characters beginning with a 
non-numeric character

Default Value: none

Related Objects:
cxIoCardAdmAlias

Configuration Changed: administrative"
		::= { cxIoPortAdmEntry 4 }


	cxIoPortAdmCardLocalIndex OBJECT-TYPE
		SYNTAX  INTEGER
		ACCESS  read-write
		STATUS  mandatory
		DESCRIPTION
"Defines this port's position on the I/O card. This information is 
presented as an index.

Note: To move to a different port on an I/O card, you need only change 
this value.

Range of Values: Dependent on I/O card type

Configuration Changed: administrative"
		::= { cxIoPortAdmEntry 5 }


cxIoCardOperTable       OBJECT-TYPE
	SYNTAX  SEQUENCE OF CxIoCardOperEntry
	ACCESS  not-accessible
	STATUS  mandatory
	DESCRIPTION
"Table describing what the software detects at each I/O slot on this CPU 
card"
	::= { cxIoHardware 3 }


	cxIoCardOperEntry       OBJECT-TYPE
		SYNTAX  CxIoCardOperEntry
		ACCESS  not-accessible
		STATUS  mandatory
		DESCRIPTION
"Contains all parameters describing the detected I/O cards. The rows in 
this table are always defined since they cannot be created or deleted. The 
number of rows represents the maximum number of I/O cards a CPU card can 
support. For the current CX1000 chassis, eight I/O slots are available. 

The cxIoCardOperState object determines whether the I/O slot is occupied 
by an I/O card. The table index corresponds to the physical slot number of 
the chassis. From the current I/O-to-CPU slot relation defined, the first 
index in this table is equal to the CPU card slot number. The last index 
in this table is the CPU card slot number plus 7.

Entries for which no corresponding slot number exists in the chassis are 
not defined. For example, on a CPU card using slot 14, the I/O card index 
ranges from 14 to 21; however, the entries related to slot numbers 18 to 
21 will not be used since no such slots exist."
		INDEX { cxIoCardOperPhysSlot }
		::= { cxIoCardOperTable 1 }


	CxIoCardOperEntry ::=
		SEQUENCE {
			cxIoCardOperPhysSlot
				INTEGER,
			cxIoCardOperState
				INTEGER,
			cxIoCardOperType
				INTEGER,
			cxIoCardOperRevision
				INTEGER,
			cxIoCardOperAssemblyAndEco
				INTEGER,
			cxIoCardOperSpecialEco
				INTEGER
			}

	cxIoCardOperPhysSlot    OBJECT-TYPE
		SYNTAX  INTEGER
		ACCESS  read-only
		STATUS  mandatory
		DESCRIPTION
"Identifies the CX1000 I/O slot being described."
		::= { cxIoCardOperEntry 1 }

	cxIoCardOperState       OBJECT-TYPE
		SYNTAX  INTEGER {
					invalid (1),
					valid   (2)
				}
		ACCESS  read-only
		STATUS  mandatory
		DESCRIPTION
"Indicates whether the particular I/O card is physically present."
		::= { cxIoCardOperEntry 2 }

	cxIoCardOperType        OBJECT-TYPE
		SYNTAX  INTEGER {
					iuscFourPortCard (1),
					lanCard (2),
               vceCmpCard (3),
               tokenRingCard (4),
               ethernetCard (5),
               isdnCard (6),
               digitalVceCmpCard (7),
               highSpeedFr4LIDCard (8),
               octalV34ModemCard (9), 
               other ( 255 )
				}
		ACCESS  read-only
		STATUS  mandatory
		DESCRIPTION
"Identifies the type of card occupying this slot. This information is 
detected by the CX1000.

Options:
iuscFourPortCard (1): a proprietary I/O card

lanCard (2): a LAN adapter such as an Ethernet or Token-Ring card for CL600

vceCmpCard (3): a voice Compression Card

tokenRingCard (4): a Token-Ring I/O card for TL600

ethernetCard (5): an Ethernet I/O card for EL600

isdnCard (6): a T1/E1 ISDN I/O card

digitalVceCmpCard (7): a Digital Voice Compression Card ( 15 channels )

highSpeedFr4LIDCard (8): a high speed frame relay 4-LID I/O card

octalV34ModemCard (9): an octal V.34 modem I/O card

other (255):  none of the above.

"
		::= { cxIoCardOperEntry 3 }

	cxIoCardOperRevision OBJECT-TYPE
		SYNTAX  INTEGER
		ACCESS  read-only
		STATUS  mandatory
		DESCRIPTION
"The revision number read from the I/O card ID register."
		::= { cxIoCardOperEntry 4 }


	cxIoCardOperAssemblyAndEco OBJECT-TYPE
		SYNTAX  INTEGER
		ACCESS  read-only
		STATUS  mandatory
		DESCRIPTION
"The assembly and ECO numbers read from the I/O card assembly and ECO 
registers."
		::= { cxIoCardOperEntry 5 }

	cxIoCardOperSpecialEco OBJECT-TYPE
		SYNTAX  INTEGER
		ACCESS  read-only
		STATUS  mandatory
		DESCRIPTION
"The special ECO number read from the I/O card special ECO register."
		::= { cxIoCardOperEntry 6 }


cxIoHwCardTypeTrapReport         OBJECT-TYPE
	SYNTAX  INTEGER {
				disabled (1),
				enabled  (2)
			}
	ACCESS  read-write
	STATUS  mandatory
	DESCRIPTION
"Indicates whether a mismatch between the value of the cxIoCardAdmType 
object (the configured card type) and the physical card inserted in the 
slot should generate a cxIoHwCardTypeTrap.

Options:
disabled (1): No action taken when a mismatch is detected.

enabled (2): Generates a 'cxIoHwCardTypeTrap' when a mismatch is detected.

Default Value: disabled (1)

Related Objects:
cxIoHwCardTypeTrap
cxIoCardAdmType
cxIoCardOperType

Configuration Changed: administrative"
	DEFVAL { disabled }
	::= { cxIoHardware 4 }

cxIHMibLevel OBJECT-TYPE
	SYNTAX	INTEGER
	ACCESS	read-only
	STATUS	mandatory
	DESCRIPTION
"Used to determine current MIB module release supported
by the agent. Object is in decimal."
	DEFVAL { 0 }
	--#STARTING_VERSION 1
	::= {  cxIoHardware 5 }


-- I/O Hardware related traps

cxIoHwCardTypeTrap      TRAP-TYPE
	ENTERPRISE      cxIoHardware
	VARIABLES       {       cxIoCardOperPhysSlot,
				cxIoCardOperState,
				cxIoCardOperType
				}
	DESCRIPTION
"Indicates that a mismatch exists between the configured card type and 
card type detected in the slot by the software. A trap is also produced if 
the slot is empty.

Related Objects:
cxIoCardOperPhysSlot
cxIoCardOperState,
cxIoCardOperType"
	::= 1


END
