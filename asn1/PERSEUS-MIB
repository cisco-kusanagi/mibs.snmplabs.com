-- --------------------------------------------------------------------
-- ************ THE STARTING POINT FOR ALL MIB DEFINITIONS ************
-- --------------------------------------------------------------------

 PERSEUS-MIB DEFINITIONS ::= BEGIN	 

          IMPORTS
                   Counter
                     FROM RFC1155-SMI
                   OBJECT-TYPE
		      			FROM RFC-1212
		  			 		DisplayString
		      			FROM RFC1213-MIB
						   linkSwitch1000-mib
							FROM A3Com-products-MIB;


			 a3Com         OBJECT IDENTIFIER ::= { enterprises 43 }
          linkSwitch1000-mib OBJECT IDENTIFIER ::= { a3Com 18 }

--------------------------------------------------------------------------------
-- Stack Group 
--------------------------------------------------------------------------------
linkSwitchStackGroup		OBJECT IDENTIFIER ::= {linkSwitch1000-mib 1}

lsStackFwdingAction OBJECT-TYPE
	SYNTAX	INTEGER  {
		notApplicable (1),
		fwdToDlink (2),
		fwdToAll (3)
	}
	ACCESS	read-write
	STATUS	mandatory
	DESCRIPTION		
		"This  object  specifies what action a Perseus unit takes when
		it  receives  a  packet with an unknown destination address. A
		unit   can  forward  the  packet  to  the  downlink  (if  any)
		associated  with the source port, or it can forward the packet
		to all its ports."
	::= {linkSwitchStackGroup 1}

lsStackFwdingMode OBJECT-TYPE
	SYNTAX	INTEGER  {
		fastForward(1),
		fragmentFree(2),
		storeAndForward(3)
	}
	ACCESS	read-write
	STATUS	mandatory
	DESCRIPTION	
		"This  object  controls  whether  cut-thru  is  enabled on the
		stack.  Enabling  cut-thru  can  help  to  minimise  the delay
		experienced  by  packets  before  they  are forwarded to their
		destination.  Setting  cut-thru  to 'fastForward' causes frame
		forwarding to begin as soon as 32 bytes of the frame have been
		received. Setting it to 'fragmentFree' causes frame forwarding
		to begin when 64 bytes have been received. This is slower, but
		eliminates  the risk of forwarding an illegally short frame to
		the destination port, however a valid length frame might still
		be  forwarded  even though  it  had a CRC error.  Setting this
		object  to 'storeAndForward' disables cut-thru completely, and
		frames  will not be forwarded until they have been received in
		their  entirety.

		Cut-thru  cannot  operate if the destination port is currently
		involved  in  'cut-thru'  from  another port. In this case the
		device will process the frame in store and forward mode."
	::= {linkSwitchStackGroup 2}

-- -----------------------------------------------------------------------------
--	Configuration Group 
--------------------------------------------------------------------------------
linkSwitchConfigGroup		OBJECT IDENTIFIER ::= {linkSwitch1000-mib 2}
-- -----------------------------------------------------------------------------
--	Configuration Port Table
--
--	This table provides details on the configuration of a port on a
--      Perseus unit.
--------------------------------------------------------------------------------
lsConfigPortTable OBJECT-TYPE
	SYNTAX	SEQUENCE OF LsConfigPortEntry
	ACCESS	not-accessible
	STATUS	mandatory
	DESCRIPTION	
		"Table  providing  configuration information about a port on a
		Perseus unit."
	::= {linkSwitchConfigGroup 1}

lsConfigPortEntry OBJECT-TYPE
	SYNTAX	LsConfigPortEntry
	ACCESS	not-accessible
	STATUS	mandatory
	DESCRIPTION	"Configuration options for a single port."
	INDEX	{lsConPortUnitId,lsConPortId}
	::= {lsConfigPortTable 1}

LsConfigPortEntry ::= SEQUENCE {
		lsConPortUnitId			INTEGER,
		lsConPortId			INTEGER,
		lsConPortWorkGroupId		INTEGER,
		lsConPortIfIndex		INTEGER,
		lsConPortMode			INTEGER,
		lsConPortIFM			INTEGER,
		lsConPortDiscardOnTx		INTEGER
		}

lsConPortUnitId OBJECT-TYPE
	SYNTAX	INTEGER 
	ACCESS	read-only
	STATUS	mandatory
	DESCRIPTION
		"This  attribute  uniquely  identifies a unit on a stack (or a
		card  within  a  chassis)  for which this table entry contains
		configuration information."
	::= {lsConfigPortEntry 1}

lsConPortId OBJECT-TYPE
	SYNTAX	INTEGER (1..32)
	ACCESS	read-only
	STATUS	mandatory
	DESCRIPTION	
		"This  parameter  specifies  the second part of the index into
		this  table.  Having selected a unit/card, it is now necessary
		to identify the port on the unit/card."
	::= {lsConfigPortEntry 2}

lsConPortWorkGroupId OBJECT-TYPE
	SYNTAX	INTEGER (1..16)
	ACCESS	read-write
	STATUS	mandatory
	DESCRIPTION
		"This  attribute  uniquely  identifies  the workgroup of which
		this  port  is  a member. The attribute is used as an index in
		the  WorkGroup table to locate this port's workgroup entry. If
		this  port  is  the downlink port for more than one workgroup,
		this  attribute  is  set  to  0.  The  WorkGroup table must be
		queried for the workgroups of which it is a member."
	::= {lsConfigPortEntry 3}

lsConPortIfIndex OBJECT-TYPE
	SYNTAX	INTEGER 
	ACCESS	read-only
	STATUS	mandatory
	DESCRIPTION	
		"This  attribute specifies the index into the ifTable, for the
		interface corresponding to this port."
	::= {lsConfigPortEntry 4}

lsConPortMode OBJECT-TYPE
	SYNTAX	INTEGER  {
		notApplicable (1),
		halfDuplex (2),
		fullDuplex (3)
	}
	ACCESS	read-write
	STATUS	mandatory
	DESCRIPTION
		"This  attribute  specifies  the mode of the TP link between a
		port   and   its  endstation.  If  the  attribute  is  set  to
		'fullDuplex',  frames  are  sent  and  received simultaneously
		without generating collisions on the segment. If the attribute
		is set to 'halfDuplex', the normal rules of ethernet apply.
		Not all ports can support full duplex mode.  An attempt to set
		such a port to fullDuplex(3) will be rejected."
	::= {lsConfigPortEntry 5}

lsConPortIFM OBJECT-TYPE
	SYNTAX	INTEGER  {
		notApplicable (1),
		off (2),
		maxJams6 (3),
		maxJams7 (4),
		maxJams8 (5),
		maxJams9 (6),
		maxJams10 (7),
		maxJams11 (8),
		maxJams12 (9),
		maxJams13 (10)
	}
	ACCESS	read-write
	STATUS	mandatory
	DESCRIPTION	
		"This  object controls the Intelligent Flow Management for the
		port.  It  specifies  what  action a port takes whenever it is
		unable  to  receive a packet because its buffers are full.  If
		the  it  is  set  to  off(1), the packet is dropped and no jam
		signal  is transmitted.  If the attribute is set to any of the
		values  maxJams6(2)  to maxJams13(10), a jam signal is applied
		to  the  segment attached to this port in order to backoff the
		transmitting station.  This will be repeated a maximum of 6 to
		13  times depending on the setting.  If the port is then still
		unable  to  receive  the  packet  it is  dropped.  Intelligent
		Flow   Management  should  be  disabled  on  ports  which  are
		connected to repeated segments."
	::= {lsConfigPortEntry 6}

lsConPortDiscardOnTx OBJECT-TYPE
	SYNTAX	INTEGER {
		notApplicable (1),
		off (2),
		on (3)
	}
	ACCESS	read-write
	STATUS	mandatory
	DESCRIPTION	
		"This attribute indicates if the 'Discard-on-transmit' feature
		is  enabled  for  frames originating at this port and going to
		any  one  of  the  other  ports  on  a  Perseus  unit. If this
		attribute  is  set  to  on(3),  the unit will  discard  frames
		destined  for any other port on a Perseus unit, if that port's
		Tx  FIFO  is full. If this attribute is set to off(2), a frame
		will not be forwarded to another port until the Tx FIFO has
		space available for the frame."
	::= {lsConfigPortEntry 7}

-- -----------------------------------------------------------------------------
--	WorkGroup Table
--
--	This table provides details on the workgroups which have been setup
--	on a Perseus unit.
--------------------------------------------------------------------------------
lsWorkGroupTable OBJECT-TYPE
	SYNTAX	SEQUENCE OF LsWorkGroupEntry
	ACCESS	not-accessible
	STATUS	mandatory
	DESCRIPTION	
		"This  table  provides  configuration  information  about  the
		workgroups  on  a Perseus unit. A workgroup is a collection of
		ports which may freely communicate with each other; they exist
		in  the  same  broadcast  domain.  Any port in a workgroup has
		restricted  access  to  ports in other workgroups; Packets can
		only  be transferred between ports in different workgroups via
		a router."
	::= {linkSwitchConfigGroup 2}

lsWorkGroupEntry OBJECT-TYPE
	SYNTAX	LsWorkGroupEntry
	ACCESS	not-accessible
	STATUS	mandatory
	DESCRIPTION	
		"Configuration  information  about a particular workgroup on a
		Perseus unit."
	INDEX	{lsWorkGroupIndex}
	::= {lsWorkGroupTable 1}

LsWorkGroupEntry ::= SEQUENCE {
		lsWorkGroupIndex		INTEGER,
		lsWorkGroupName			DisplayString,
		lsWorkGroupDLUnitId		INTEGER,
		lsWorkGroupDLPortId		INTEGER,
		lsWorkGroupRowStatus		INTEGER,
		lsWorkGroupDBaction		INTEGER
		}

lsWorkGroupIndex OBJECT-TYPE
	SYNTAX	INTEGER (1..16)
	ACCESS	read-only
	STATUS	mandatory
	DESCRIPTION	
		"This attribute uniquely identifies one of the workgroups on a
		unit.  This  attribute  is  also  used  as  an  index into the
		WorkGroup table."
	::= {lsWorkGroupEntry 1}

lsWorkGroupName OBJECT-TYPE
	SYNTAX	DisplayString (SIZE(0..32))
	ACCESS	read-write
	STATUS	mandatory
	DESCRIPTION	
		"This   attribute  specifies  a  text  string  which  uniquely
		identifies the  workgroup.  It may be set only if the value of
		lsWorkGroupRowStatus is notInService(2) or notReady(3), or the
		workgroup  does  not already exist. In this case, provided the
		workgroup  index  is  in  the  range  1  to  16  inclusive the
		workgroup  will  be  created  with lsWorkGroupRowStatus set to
		notReady(3)."
	::= {lsWorkGroupEntry 2}

lsWorkGroupDLUnitId OBJECT-TYPE
	SYNTAX	INTEGER 
	ACCESS	read-write
	STATUS	mandatory
	DESCRIPTION
		"This  attribute  specifies  the identity of the unit on which
		this  workgroup's downlink resides.  It may be set only if the
		value    of   lsWorkGroupRowStatus   is   notInService(2)   or
		notReady(3),  or the workgroup does not already exist. In this
		case,  provided  the  workgroup  index is in the range 1 to 16
		inclusive    the    workgroup    will    be    created    with
		lsWorkGroupRowStatus set to notReady(3).
		If  this  object  and  lsWorkGroupDLPortId are both zero,  the
		workgroup does not have a downlink."
	::= {lsWorkGroupEntry 3}

lsWorkGroupDLPortId OBJECT-TYPE
	SYNTAX	INTEGER 
	ACCESS	read-write
	STATUS	mandatory
	DESCRIPTION	
		"This   attribute   identifies  the  downlink  port  for  this
		workgroup.   It   may   be   set   only   if   the   value  of
		lsWorkGroupRowStatus is notInService(2) or notReady(3), or the
		workgroup  does  not already exist. In this case, provided the
		workgroup  index  is  in  the  range  1  to  16  inclusive the
		workgroup  will  be  created  with lsWorkGroupRowStatus set to
		notReady(3).
		If  lsWorkGroupDLUnitId  and  this  object are both zero,  the
		workgroup does not have a downlink."
	::= {lsWorkGroupEntry 4}

lsWorkGroupRowStatus OBJECT-TYPE
	SYNTAX	INTEGER  {
		active (1),
		notInService (2),
		notReady (3),
		createAndGo (4),
		createAndWait (5),
		destroy (6)
	}
	ACCESS	read-write
	STATUS	mandatory
	DESCRIPTION
		"The  WorkGroup  table  contains a row for each workgroup that
		exists on a unit up to a maximum of 16.  Ports can be assigned
		to  active  workgroups.  A  new  workgroup  can  be created by
		writing  either  createAndGo(4)  or  createAndWait(5)  to this
		object  for  an  instance  which  does not already exist. (The
		workgroup  may  also  be  created by setting the downlink unit
		and/or port). Provided the index value is in the range 1 to 16
		inclusive,  a  new workgroup will be created with that number,
		and  default  values  of downlink unit and port. If the row is
		created  by  writing  createAndGo(5),  the  status  of the new
		workgroup  becomes active(1) immediately, otherwise it becomes
		notReady(3),  and  subsequent reads of this object will return
		that value.

		Only   if   the  status  of  the  row  is  notInService(2)  or
		notReady(3)  will  sets  of  the  downlink  unit  or  port  be
		successful.  Changes  will  not take effect until active(1) is
		next written to the rowStatus. Thus, to amend the downlink for
		a  workgroup  the  network manager must first set rowStatus to
		notInService(2), set the new values for the downlink, then set
		rowStatus  back  to active(1). This will fail if the specified
		port is not assigned to the workgroup.

		A  workgroup  may  be  deleted  by  setting  its row status to
		destroy(6).  This  will  be  rejected if the workgroup has any
		ports   assigned  to  it  and  its  rowStatus  is  other  than
		notReady(3)."
	::= {lsWorkGroupEntry 5}

lsWorkGroupDBaction OBJECT-TYPE
	SYNTAX	INTEGER  {
		noAction (1),
		freezeAddrs (2)
	}
	ACCESS	read-write
	STATUS	mandatory
	DESCRIPTION	
		"This  object  allows  a  user to carry out operations on this
		workgroup's   address   list   in   the  forwarding  database.
		freezeAddrs(2) makes all addresses in the workgroup permanent.
		The value noAction(1) is always returned in response to a get."
	::= {lsWorkGroupEntry 6}

-- -----------------------------------------------------------------------------
--	Monitor Group 
--------------------------------------------------------------------------------
linkSwitchMonitorGroup		OBJECT IDENTIFIER ::= {linkSwitch1000-mib 3}
-- -----------------------------------------------------------------------------
--	Monitor WorkGroup Table 
--
--  This  group  provides  monitoring  information  about  a  Perseus hub on a
--  workgroup level.
--------------------------------------------------------------------------------
lsMonitorWGTable OBJECT-TYPE
	SYNTAX	SEQUENCE OF LsMonWgEntry
	ACCESS	not-accessible
	STATUS	mandatory
	DESCRIPTION	
		"This  table  provides  monitoring  information on a workgroup
		which has been setup on a Perseus hub."
	::= {linkSwitchMonitorGroup 1}

lsMonitorWGTableEntry OBJECT-TYPE
	SYNTAX	LsMonWgEntry
	ACCESS	not-accessible
	STATUS	mandatory
	DESCRIPTION	"Monitoring information for a single workgroup."
	INDEX	{lsMonWgIndex}
	::= {lsMonitorWGTable 1}

LsMonWgEntry ::= SEQUENCE {
		lsMonWgIndex			INTEGER,
		lsMonWgTxFrames			Counter,
		lsMonWgTxOctets			Counter,
		lsMonWgTxErrors			Counter,
		lsMonWgRxCongestion		Counter,
		lsMonWgTxCongestion		Counter,
		lsMonWgFilteredFrms		Counter,
		lsMonWgForwardedFrms		Counter,
		lsMonWgTxUnderruns		Counter,
		lsMonWgRxDribble		Counter,
		lsMonWgCutThrus			Counter,
		lsMonWgJamCount			Counter,
		lsMonWgClearCounters		INTEGER
		}

lsMonWgIndex OBJECT-TYPE
	SYNTAX	INTEGER (1..16)
	ACCESS	read-only
	STATUS	mandatory
	DESCRIPTION	
		"A  stack/chassis  may  contain  more than one workgroup. This
		parameter  uniquely  identifies  the  workgroup  which  is the
		target of the request."
	::= {lsMonitorWGTableEntry 1}

lsMonWgTxFrames OBJECT-TYPE
	SYNTAX	Counter
	ACCESS	read-only
	STATUS	mandatory
	DESCRIPTION	
		"This  parameter  specifies  the  number  of frames (including
		error   frames)  which  were  transmitted  by  ports  in  this
		workgroup."
	::= {lsMonitorWGTableEntry 2}

lsMonWgTxOctets OBJECT-TYPE
	SYNTAX	Counter
	ACCESS	read-only
	STATUS	mandatory
	DESCRIPTION
		"This  parameter  specifies  the  number  of octets (including
		octets  in  error  frames)  which were transmitted by ports in
		this workgroup."
	::= {lsMonitorWGTableEntry 3}

lsMonWgTxErrors OBJECT-TYPE
	SYNTAX	Counter
	ACCESS	read-only
	STATUS	mandatory
	DESCRIPTION	
		"This  parameter  specifies  the  number of error frames which
		were transmitted by ports in this workgroup."
	::= {lsMonitorWGTableEntry 4}

lsMonWgRxCongestion OBJECT-TYPE
	SYNTAX	Counter
	ACCESS	read-only
	STATUS	mandatory
	DESCRIPTION	
		"This  parameter  specifies  the  number  of frames which were
		dropped  due  to  congestion  (lack of buffer resource) on the
		receive side of ports in this workgroup."
	::= {lsMonitorWGTableEntry 5}

lsMonWgTxCongestion OBJECT-TYPE
	SYNTAX	Counter
	ACCESS	read-only
	STATUS	mandatory
	DESCRIPTION	
		"This  parameter  specifies  the  number  of frames which were
		dropped  due  to  congestion  (lack of buffer resource) on the
		transmit side of ports in this workgroup."
	::= {lsMonitorWGTableEntry 6}

lsMonWgFilteredFrms OBJECT-TYPE
	SYNTAX	Counter
	ACCESS	read-only
	STATUS	mandatory
	DESCRIPTION	
		"The  total  number  of  frames  within  a workgroup that were
		filtered  because  the  destination  station  was  on the same
		segment (port) as the source station."
	::= {lsMonitorWGTableEntry 7}

lsMonWgForwardedFrms OBJECT-TYPE
	SYNTAX	Counter
	ACCESS	read-only
	STATUS	mandatory
	DESCRIPTION	
		"The  total  number of frames that were forwarded successfully
		by ports in this workgroup to their destinations."
	::= {lsMonitorWGTableEntry 8}

lsMonWgTxUnderruns OBJECT-TYPE
	SYNTAX	Counter
	ACCESS	read-only
	STATUS	mandatory
	DESCRIPTION	
		"The  total  number  of frames within this workgroup that were
		transmitted  with  a  bad  CRC  because  the MMAC did not have
		enough data to continue transmission."
	::= {lsMonitorWGTableEntry 9}

lsMonWgRxDribble OBJECT-TYPE
	SYNTAX	Counter
	ACCESS	read-only
	STATUS	mandatory
	DESCRIPTION	
		"The  total  number  of  frames that were received by ports in
		this  workgroup  which  has  dribble  bits  at  the end of the
		frames"
	::= {lsMonitorWGTableEntry 10}

lsMonWgCutThrus OBJECT-TYPE
	SYNTAX	Counter
	ACCESS	read-only
	STATUS	mandatory
	DESCRIPTION
		"The  total  number  of  frames  that  were forwarded to their
		destinstion  in  'cut-thru'  mode  by ports in this workgroup.
		When  a  port  is  operating  in  'cut-thru'  mode,  it starts
		forwarding  the  frame to its destination before the frame has
		been fully received."
	::= {lsMonitorWGTableEntry 11}

lsMonWgJamCount OBJECT-TYPE
	SYNTAX	Counter
	ACCESS	read-only
	STATUS	mandatory
	DESCRIPTION	
		"The  total  number  of  attempts  made  to  jam frames due to
		insufficient   resources   at   the   receive  ports  in  this
		workgroup."
	::= {lsMonitorWGTableEntry 12}

lsMonWgClearCounters OBJECT-TYPE
	SYNTAX	INTEGER  {
		noChangeCounters (1),
		clearCounters (2)
	}
	ACCESS	read-write
	STATUS	mandatory
	DESCRIPTION
		"This  attribute is used to clear all counters on all ports in
		a workgroup."
	::= {lsMonitorWGTableEntry 13}

-- -----------------------------------------------------------------------------
--	Monitor Port Table
--
--  This  table  provides  monitoring information about a port on a Perseus
--  unit.
--------------------------------------------------------------------------------
lsMonitorPortTable OBJECT-TYPE
	SYNTAX	SEQUENCE OF LsMonPortEntry
	ACCESS	not-accessible
	STATUS	mandatory
	DESCRIPTION	
		"This  table provides monitoring information about a port on a
		Perseus   unit.   This  information  is  in  addition  to  the
		statistical  information  already provided by the 'mrmMonPort'
		table.  Note: The 'mrmMonPort' table has objects which provide
		the  value  of  RxFrames,  RxOctets  and  RxErrors on a port."
	::= {linkSwitchMonitorGroup 2}

lsMonitorPortTableEntry OBJECT-TYPE
	SYNTAX	LsMonPortEntry
	ACCESS	not-accessible
	STATUS	mandatory
	DESCRIPTION	"Monitor options for a single port."
	INDEX	{lsMonPortWgIndex,lsMonPortUnitId,lsMonPortId}
	::= {lsMonitorPortTable 1}

LsMonPortEntry ::= SEQUENCE {
		lsMonPortWgIndex		INTEGER,
		lsMonPortUnitId			INTEGER,
		lsMonPortId			INTEGER,
		lsMonPortReceivedFrms		Counter,
		lsMonPortTransmittedFrms	Counter,
		lsMonPortFilteredFrms		Counter,
		lsMonPortForwardedFrms		Counter,
		lsMonPortFragmentFrms		Counter,
		lsMonPortRxCongestion		Counter,
		lsMonPortTxCongestion		Counter,
		lsMonPortTxUnderruns		Counter,
		lsMonPortRxDribble		Counter,
		lsMonPortCutThrus		Counter,
		lsMonPortRxJamCount		Counter,
		lsMonPortPercentFwd		INTEGER,
		lsMonPortBcastBndwth		INTEGER,
		lsMonPortClearCounters		INTEGER
		}

lsMonPortWgIndex OBJECT-TYPE
	SYNTAX	INTEGER (1..16)
	ACCESS	read-only
	STATUS	mandatory
	DESCRIPTION	
		"A  stack/chassis  may  contain  more than one workgroup. This
		parameter  uniquely  identifies  the  workgroup  which  is the
		target of the request."
	::= {lsMonitorPortTableEntry 1}

lsMonPortUnitId OBJECT-TYPE
	SYNTAX	INTEGER 
	ACCESS	read-only
	STATUS	mandatory
	DESCRIPTION	
		"A  stack/chassis  may  contain  more than one unit/card. This
		parameter  uniquely  identifies  the  unit/card  which  is the
		target of a request."
	::= {lsMonitorPortTableEntry 2}

lsMonPortId OBJECT-TYPE
	SYNTAX	INTEGER (1..32)
	ACCESS	read-only
	STATUS	mandatory
	DESCRIPTION	
		"A  unit/card  contains  many  ports.  This parameter uniquely
		identifies the port which is the target of a request."
	::= {lsMonitorPortTableEntry 3}

lsMonPortReceivedFrms OBJECT-TYPE
	SYNTAX	Counter
	ACCESS	read-only
	STATUS	mandatory
	DESCRIPTION	
		"The  total  number  of  good and bad frames that were received
		at this port."
	::= {lsMonitorPortTableEntry 4}

lsMonPortTransmittedFrms OBJECT-TYPE
	SYNTAX	Counter
	ACCESS	read-only
	STATUS	mandatory
	DESCRIPTION	
		"The  total  number  of  good and bad frames that were transmitted
		from this port."
	::= {lsMonitorPortTableEntry 5}

lsMonPortFilteredFrms OBJECT-TYPE
	SYNTAX	Counter
	ACCESS	read-only
	STATUS	mandatory
	DESCRIPTION	
		"The  total  number  of  frames that were filtered because the
		destination  station  was  on  the  same segment (port) as the
		source station."
	::= {lsMonitorPortTableEntry 6}

lsMonPortForwardedFrms OBJECT-TYPE
	SYNTAX	Counter
	ACCESS	read-only
	STATUS	mandatory
	DESCRIPTION	
		"The  total  number of frames which were received by this port
		and forwarded to their destinations."
	::= {lsMonitorPortTableEntry 7}

lsMonPortFragmentFrms OBJECT-TYPE
	SYNTAX	Counter
	ACCESS	read-only
	STATUS	mandatory
	DESCRIPTION	
		"The  total  number of frames less than 64 octets and with a bad
		CRC that were received at/transmitted from this port."
	::= {lsMonitorPortTableEntry 8}

lsMonPortRxCongestion OBJECT-TYPE
	SYNTAX	Counter
	ACCESS	read-only
	STATUS	mandatory
	DESCRIPTION	
		"This  parameter  specifies  the  number  of frames which were
		dropped  due  to  congestion  (lack of buffer resource) on the
		receive side of this port."
	::= {lsMonitorPortTableEntry 9}

lsMonPortTxCongestion OBJECT-TYPE
	SYNTAX	Counter
	ACCESS	read-only
	STATUS	mandatory
	DESCRIPTION	
		"This  parameter  specifies  the  number  of frames which were
		dropped  due  to  congestion  (lack of buffer resource) on the
		transmit side of this port."
	::= {lsMonitorPortTableEntry 10}

lsMonPortTxUnderruns OBJECT-TYPE
	SYNTAX	Counter
	ACCESS	read-only
	STATUS	mandatory
	DESCRIPTION	
		"The  total number of frames that were transmitted with an bad
		CRC  because  the  MMAC  did  not have enough data to continue
		transmission."
	::= {lsMonitorPortTableEntry 11}

lsMonPortRxDribble OBJECT-TYPE
	SYNTAX	Counter
	ACCESS	read-only
	STATUS	mandatory
	DESCRIPTION	
		"The  number  of  frames  that were received on this port with
		dribble bits at the end of the frame."
	::= {lsMonitorPortTableEntry 12}

lsMonPortCutThrus OBJECT-TYPE
	SYNTAX	Counter
	ACCESS	read-only
	STATUS	mandatory
	DESCRIPTION	
		"The  total  number  of  frames  that  were forwarded to their
		destination in 'cut-through' mode. When a port is operating in
		'cut-through'  mode,  it  starts  forwarding  the frame to its
		destination before the frame has been fully received."
	::= {lsMonitorPortTableEntry 13}

lsMonPortRxJamCount OBJECT-TYPE
	SYNTAX	Counter
	ACCESS	read-only
	STATUS	mandatory
	DESCRIPTION	
		"The  total  number  of  attempts  made  to jam packets due to
		insufficient resources at the receive port."
	::= {lsMonitorPortTableEntry 14}

lsMonPortPercentFwd OBJECT-TYPE
	SYNTAX	INTEGER 
	ACCESS	read-only
	STATUS	mandatory
	DESCRIPTION	
		"This is a high level 'Smart' MIB object. This object provides
		a  running  average  of  the proportion of the received frames
		that  are  forwarded.  This value is calculated locally on the
		agent  and  so  does  not require processor bandwidth from the
		management   station  or  occupy  valuable  network  bandwidth
		communicating   with   that   station.  By  default  an  agent
		supporting   this   parameter   will   exhibit  the  following
		characteristics :-

		   (1)  The parameter will be recalculated at approx 60 second
		   	intervals.
		   (2)  Every  calculation  period,  the  device will read the
		   	value of dot1dTpPortInFrames and dot1dTpPortInDiscards.
		   (3)  The calculation will be performed on the most recent 4
		   	samples as follows:
	      4
	      sum (dot1dTpPortInDiscards(i) / dot1dTpPortInFrames(i)) * 1000/4
	      i=1
			which  gives  the  'percentage*10'  filtered, and then
			subtracting this from 1000 to give the 'percentage*10'
			forwarded.
	
		Note: dot1dTpPortInDiscards(i) is dot1dTpPortInDiscards(i) -
						  dot1dTpPortInDiscards(i-1).
		      dot1dTpPortInFrames(i) is dot1dTpPortInFrames(i) -
		      				dot1dTpPortInFrames(i-1).
		The  value  is  expressed  as  a  percentage * 10.  A  default
		threshold  exists  on  this  average  so  that if a calculated
		average  exceeds  85%,  a  trap will be sent to the management
		station.  Further  traps  will  not  be sent until the average
		drops to below 50%.

		A  particular  device  may  provide  the means of changing the
		number   of  samples,  the  averaging  period,  threshold  and
		threshold action if it so wishes."
	::= {lsMonitorPortTableEntry 15}

lsMonPortBcastBndwth OBJECT-TYPE
	SYNTAX	INTEGER 
	ACCESS	read-only
	STATUS	mandatory
	DESCRIPTION	
		"This is a high level 'Smart' MIB object. This object provides
		a  running  average  of  the Broadcast frame bandwidth in use.
		This  value is calculated locally on the agent and so does not
		require  processor  bandwidth  from  the management station or
		occupy  valuable  network  bandwidth  communicating  with that
		station.  By  default  an agent supporting this parameter will
		exhibit the following characteristics:
		
		(1) The  parameter  will  be  recalculated at approx 20 second
		    intervals
	
		(2) Every calculation period the device will read the value of
		    mrmMonPortBroadcastFrames

		(3) The  calculation  will  be  performed on the most recent 4
		    samples as follows:
		
		     4
		    Sum(sample(i)/(time(i) * K)) * 1000/4
		    i=1
		
		Sample(i) is mrmMonPortBroadcastFrames(i) -
			     mrmMonPortBroadcastFrames(i-1)
		time(i)	  is the time between sample(i-1) and sample(i)
		K         is the max frames per unit time  (i.e. the available
			  bandwidth)

		The value is expressed as a percentage * 10.
		
		A  default  threshold  exists  on  this  average  so that if a
		calculated  average  exceeds  20%  a  trap will be sent to the
		management  station.  Further traps will not be sent until the
		average drops to below 10%.
		
		A particular device may provide a means of changing the number
		of  samples,  the  averaging  period,  threshold and threshold
		action if it so wishes."
	::= {lsMonitorPortTableEntry 16}

lsMonPortClearCounters OBJECT-TYPE
	SYNTAX	INTEGER  {
		noChangeCounters (1),
		clearCounters (2)
	}
	ACCESS	read-write
	STATUS	mandatory
	DESCRIPTION	"This  attribute  is  used  to clear all counters on a
			port."
	::= {lsMonitorPortTableEntry 17}

-- -----------------------------------------------------------------------------
--	Database Group 
--------------------------------------------------------------------------------
linkSwitchDatabaseGroup         OBJECT IDENTIFIER ::= {linkSwitch1000-mib 4}

lsDatabaseSize OBJECT-TYPE
	SYNTAX	INTEGER 
	ACCESS	read-only
	STATUS	mandatory
	DESCRIPTION
		"This parameter indicates the number of permanent and
		non-permanent entries currently held in the database on a
		linkSwitch1000 hub."
	::= {linkSwitchDatabaseGroup 1}

lsPermDatabaseSize OBJECT-TYPE
	SYNTAX	INTEGER 
	ACCESS	read-only
	STATUS	mandatory
	DESCRIPTION
		"This parameter indicates the number of permanent addresses
		currently held in the database on a linkSwitch1000."
	::= {linkSwitchDatabaseGroup 2}

-- -----------------------------------------------------------------------------
--	Port Table
--
--  This  group  provides  a view of the database on a linkSwitch1000 unit in
--  ascending port number order.
--------------------------------------------------------------------------------
lsDbPortTable OBJECT-TYPE
	SYNTAX	SEQUENCE OF LsDbPortEntry
	ACCESS	not-accessible
	STATUS	mandatory
	DESCRIPTION	"Port View Table"
	::= {linkSwitchDatabaseGroup 3}

lsDbPortEntry OBJECT-TYPE
	SYNTAX	LsDbPortEntry
	ACCESS	not-accessible
	STATUS	mandatory
	DESCRIPTION	"Port View Table entry"
	INDEX	{lsDbPortUnitId, lsDbPortPortId, lsDbPortIndex}
	::= {lsDbPortTable 1}

LsDbPortEntry ::= SEQUENCE {
		lsDbPortUnitId		INTEGER,
		lsDbPortPortId		INTEGER,
		lsDbPortIndex		INTEGER,
		lsDbPortAddress		OCTET STRING,
		lsDbPortAddrStatus	INTEGER
		}

lsDbPortUnitId OBJECT-TYPE
	SYNTAX	INTEGER 
	ACCESS	read-only
	STATUS	mandatory
	DESCRIPTION
		"A linkSwitch stack may contain up to 4 units. This parameter
		uniquely identifies the unit on which the address was learnt."
	::= {lsDbPortEntry 1}

lsDbPortPortId OBJECT-TYPE
	SYNTAX	INTEGER 
	ACCESS	read-only
	STATUS	mandatory
	DESCRIPTION
		"A linkSwitch1000 unit can contain up to 26 ports. This
		parameter uniquely the port on which the address was learnt."
	::= {lsDbPortEntry 2}

lsDbPortIndex OBJECT-TYPE
	SYNTAX	INTEGER 
	ACCESS	read-only
	STATUS	mandatory
	DESCRIPTION
		"Multiple addresses can be learnt on a single port. This
		parameter uniquely identifies one address on a port."
	::= {lsDbPortEntry 3}

lsDbPortAddress OBJECT-TYPE
	SYNTAX	OCTET STRING  (SIZE(6))
	ACCESS	read-write
	STATUS	mandatory
	DESCRIPTION
		"The physical address of the station which has been learnt on
		a port on a linkSwitch1000 stack."
	::= {lsDbPortEntry 4}

lsDbPortAddrStatus OBJECT-TYPE
	SYNTAX	INTEGER  {
		nonPermanent (1),
		permanent (2),
		delete (3)
	}
	ACCESS	read-write
	STATUS	mandatory
	DESCRIPTION
		"This attribute indicates if the address will age out of the
		database on a linkSwitch1000 unit when it is not the subject of
		lookup requests (nonPermanent) OR if it remains in the database
		until the user deletes it (permanent). The user can remove this
		address from the database by setting this attribute to
		delete(3)."
	::= {lsDbPortEntry 5}

-- -----------------------------------------------------------------------------
--	Smart MIB Object Group 
--------------------------------------------------------------------------------
linkSwitchSmartGroup           OBJECT IDENTIFIER ::= {linkSwitch1000-mib 5}

lsSmartBcastBndwdth OBJECT-TYPE
	SYNTAX	INTEGER 
	ACCESS	read-only
	STATUS	mandatory
	DESCRIPTION
		"This is a smart MIB object which is used internally by the
		agent to provide a running average of the broadcast bandwidth
		in use. It should not be accessed by a management station and
		is used by the logic which calculates its associated object
		'lsMonPortBcastBndwdth'."
	::= {linkSwitchSmartGroup 2}

lsSmartPercentFwd OBJECT-TYPE
	SYNTAX	INTEGER 
	ACCESS	read-only
	STATUS	mandatory
	DESCRIPTION
		"This is a smart MIB object which is used internally by the
		agent to provide a running average of the percentage of
		incoming frames which are forwarded. It should not be accessed
		by a management station and is used by the logic which
		calculates the value of its associated object
		'mrmMonPortPercentFwd'."
	::= {linkSwitchSmartGroup 1}

END
