--******************************************************************
--*
--*         Copyright (c) 1993, 1999 by 3Com Corporation
--*                    All Rights Reserved
--*
--*    $Revision:   7.0  $
--*    $Date:   Jul 15 1999 15:22:30  $
--*
--*    3COM HDR2 MIB
--*
--******************************************************************


HDR2-MIB DEFINITIONS ::= BEGIN

IMPORTS
   enterprises
      FROM RFC1155-SMI
   DisplayString
      FROM RFC1213-MIB
   OBJECT-TYPE
      FROM RFC-1212;


usr OBJECT IDENTIFIER ::= { enterprises 429 }

common OBJECT IDENTIFIER ::= { usr 4 }

hdr2 OBJECT IDENTIFIER ::= { common 48 }

-- The E1-R2 CAS for the Hiper DSP Configuration Group

hdr2Cfg OBJECT IDENTIFIER ::= { hdr2 1 }

hdr2CfgTable OBJECT-TYPE
SYNTAX SEQUENCE OF Hdr2CfgEntry
ACCESS not-accessible
STATUS mandatory
DESCRIPTION
"A table containing the configuration parameters for the 
Hiper E1/R2 Card."
::= { hdr2Cfg 1 }

hdr2CfgEntry OBJECT-TYPE
SYNTAX Hdr2CfgEntry
ACCESS not-accessible
STATUS mandatory
DESCRIPTION
"Configuration parameters for the E1/R2 module. "
INDEX { hdr2CfgIndex }
::= { hdr2CfgTable 1 }

Hdr2CfgEntry ::=
SEQUENCE {
hdr2CfgIndex
    INTEGER,
hdr2CfgRegSigType
    INTEGER,
hdr2CfgAnumIden
    INTEGER,
hdr2CfgForcedRel
    INTEGER,
hdr2CfgLastBDigTout
    INTEGER,
hdr2CfgAddrComplete
    INTEGER,
hdr2CfgEndBparty
    INTEGER,
hdr2CfgAlawMulaw
    INTEGER,
hdr2CfgLineSigType
    INTEGER,
hdr2CfgProjID
    INTEGER,
hdr2CfgSeizeAck
    INTEGER,
hdr2CfgAnumBnum
    INTEGER,
hdr2CfgSubBusy
    INTEGER,
hdr2CfgSndCallingPtyCatgy
    INTEGER,
hdr2CfgLineDirection
    INTEGER,
hdr2CfgPersistentOverride
    INTEGER,
hdr2CfgWrongNumber
    INTEGER,
hdr2CfgIncomingCpc
    INTEGER,
hdr2CfgRegSigStatus
    INTEGER,
hdr2CfgUnusedAbcd
    INTEGER,
hdr2CfgBlkToBlk
    INTEGER,
hdr2CfgDelayLos
    INTEGER,
hdr2CfgInGlare
    INTEGER,
hdr2CfgClrCall
    INTEGER,
hdr2CfgANumQry
    INTEGER,
hdr2CfgANumNAv
    INTEGER,
hdr2CfgANumReq
    INTEGER,
hdr2CfgClrFwd
    INTEGER,
hdr2CfgRelGuard
    INTEGER,
hdr2CfgPIClrBck
    INTEGER,
hdr2CfgDelayAns
    INTEGER,
hdr2CfgBNumLen
    INTEGER,
hdr2CfgActBTout
    INTEGER,
hdr2CfgInSubFree
    INTEGER,
hdr2CfgBNumNFnd
    INTEGER,
hdr2CfgSndBNumN
    INTEGER,
hdr2CfgSndBNumN1
    INTEGER,
hdr2CfgSndBNumN2
    INTEGER,
hdr2CfgSndBNumN3
    INTEGER,
hdr2CfgSndFBNum
    INTEGER,
hdr2CfgDumANum
    DisplayString,
hdr2CfgEndANum
    INTEGER,
hdr2CfgOutCatAnalog
    INTEGER,
hdr2CfgOutCatDigital
    INTEGER,
hdr2CfgOutCatTest
    INTEGER,
hdr2CfgOutCatMaintenance
    INTEGER
}

hdr2CfgIndex OBJECT-TYPE
SYNTAX INTEGER
ACCESS read-only
STATUS mandatory
DESCRIPTION
"The index which uniquely identifies the Hiper E1/R2 CARD to 
which this entry is applicable.  "
::= { hdr2CfgEntry 1 }

hdr2CfgRegSigType OBJECT-TYPE
SYNTAX INTEGER{
  r2MFC(1),
  r2MFSC(2)
}
ACCESS read-write
STATUS mandatory
DESCRIPTION
"This object Defines the type of Register Signaling used for 
Bit Oriented Signaling."
DEFVAL { r2MFC }
::= { hdr2CfgEntry 2 }

hdr2CfgAnumIden OBJECT-TYPE
SYNTAX INTEGER{
  disable(1),
  enable(2)
}
ACCESS read-write
STATUS mandatory
DESCRIPTION
"This parameter enables or disables the collection of 
calling party ( A party or ANI) phone numbers when used 
with R2MFC signaling type."
DEFVAL { disable }
::= { hdr2CfgEntry 3 }

hdr2CfgForcedRel OBJECT-TYPE
SYNTAX INTEGER{
  disable(1),
  enable(2)
}
ACCESS read-write
STATUS mandatory
DESCRIPTION
"In E1/ R2 ,Forced Release Line signal will be sent only in 
case of this parameter is enabled. This signal is 
optional."

DEFVAL { disable }
::= { hdr2CfgEntry 4 }

hdr2CfgLastBDigTout OBJECT-TYPE
SYNTAX INTEGER (100..10000)
ACCESS read-write
STATUS mandatory
DESCRIPTION
"This parameter decides, after how many milliseconds of 
silence during the B digit reception, the B party number is 
assumed as completed. "
DEFVAL { 2000 }
::= { hdr2CfgEntry 5 }

hdr2CfgAddrComplete OBJECT-TYPE
SYNTAX INTEGER{
  a3(1),
  a5(2),
  a6(3)
}
ACCESS read-write
STATUS mandatory
DESCRIPTION
"On reception of this signal it is assumed that the required 
number of B party digits are received. It can hold the 
values ranging from A1 to A15. It depends on country 
specification. "

DEFVAL { a3 }
::= { hdr2CfgEntry 6 }

hdr2CfgEndBparty OBJECT-TYPE
SYNTAX INTEGER{
  disable(1),
  enable(2)
}
ACCESS read-write
STATUS mandatory
DESCRIPTION
"This indicates whether I15 is will be received as an 
indication for End of  B party number or not. If enabled, 
at the end of B party number , this I15 signal is received 
informing that B party number is completed. "

DEFVAL { enable }
::= { hdr2CfgEntry 7 }

hdr2CfgAlawMulaw OBJECT-TYPE
SYNTAX INTEGER{
  aLAW(1),
  mULAW(2),
  auto(3)
}
ACCESS read-write
STATUS mandatory
DESCRIPTION
"This object is configuration to apply A Law(E1)  or 
MuLaw(T1) Companding. "
DEFVAL { auto }
::= { hdr2CfgEntry 8 }

hdr2CfgLineSigType OBJECT-TYPE
SYNTAX INTEGER{
  r2DIG(1),
  p7DIG(2),
  r2EandM(3)
}
ACCESS read-write
STATUS mandatory
DESCRIPTION
"This object defines the type of Line Signaling for Bit 
Oriented Signaling. "
DEFVAL { r2DIG }
::= { hdr2CfgEntry 9 }

hdr2CfgProjID OBJECT-TYPE
SYNTAX INTEGER{
  iTU-T(1),
  argentina(2),
  australia(3),
  brazil(4),
  chile(5),
  china(6),
  colombia(7),
  india(8),
  korea(9),
  malaysia(10),
  mexico(11),
  newZealand(12),
  philippines(13),
  sweden(14),
  venezuela(15)
}
ACCESS read-write
STATUS mandatory
DESCRIPTION
"Depending on this parameter, country dependent or project 
dependent parameters are updated. Each and every parameter 
has a set of variables to be initialized. "


DEFVAL { iTU-T }
::= { hdr2CfgEntry 10 }

hdr2CfgSeizeAck OBJECT-TYPE
SYNTAX INTEGER{
  disable(1),
  enable(2)
}
ACCESS read-write
STATUS mandatory
DESCRIPTION
"It defines whether seize acknowledge signal is used or not  
for Bit Oriented Signaling. "
DEFVAL { enable }
::= { hdr2CfgEntry 11 }

hdr2CfgAnumBnum OBJECT-TYPE
SYNTAX INTEGER (1..36)
ACCESS read-write
STATUS mandatory
DESCRIPTION
"During Bit oriented Register Signaling , after number of B 
party ( called party or DNIS) digits have been received, 
the A party (calling or ANI) digits are requested , 
provided A party (ANI) request is enabled. Otherwise this 
parameter is ignored. "
DEFVAL { 1 }
::= { hdr2CfgEntry 12 }

hdr2CfgSubBusy OBJECT-TYPE
SYNTAX INTEGER{
  b2(1),
  b3(2)
}
ACCESS read-write
STATUS mandatory
DESCRIPTION
"This object is used in case of subscirber busy. "
DEFVAL { b3 }
::= { hdr2CfgEntry 13 }

hdr2CfgSndCallingPtyCatgy OBJECT-TYPE
SYNTAX INTEGER{
  a5(1),
  a6(2)
}
ACCESS read-write
STATUS mandatory
DESCRIPTION
"This register Signal requests the calling ( A PARTY's ) 
category. "
DEFVAL { a5 }
::= { hdr2CfgEntry 14 }

hdr2CfgLineDirection OBJECT-TYPE
SYNTAX INTEGER{
  incoming(1),
  outgoing(2),
  both(3)
}
ACCESS read-write
STATUS mandatory
DESCRIPTION
"This object sets the direction of the channels on the span 
line. " 
DEFVAL { incoming }
::= { hdr2CfgEntry 15 }

hdr2CfgPersistentOverride OBJECT-TYPE
SYNTAX INTEGER (0..255)
ACCESS read-write
STATUS mandatory
DESCRIPTION
"This object allows the recieved line signal persistence 
(debounce time). " 
DEFVAL { 0 }
::= { hdr2CfgEntry 16 }

hdr2CfgWrongNumber OBJECT-TYPE
SYNTAX INTEGER{
  b5(1),
  b7(2)
}
ACCESS read-write
STATUS mandatory
DESCRIPTION
"This object is the backward register signal used to 
indicate that an invalid number has been dialed. "
DEFVAL { b5 }
::= { hdr2CfgEntry 17 }

hdr2CfgIncomingCpc OBJECT-TYPE
SYNTAX INTEGER{
  analog(1),
  digital(2),
  maintanace(3),
  test(4)
}
ACCESS read-write
STATUS mandatory
DESCRIPTION
"This object determines the default calling party category 
to be assumed when none is supplied for an incoming call. "
DEFVAL { analog }
::= { hdr2CfgEntry 18 }

hdr2CfgRegSigStatus OBJECT-TYPE
SYNTAX INTEGER{
  disable(1),
  enable(2)
}
ACCESS read-write
STATUS mandatory
DESCRIPTION
"This object determines whether or not register signalling 
is used for incoming and outgoing calls for R2."
DEFVAL { enable }
::= { hdr2CfgEntry 19 }

hdr2CfgUnusedAbcd OBJECT-TYPE
SYNTAX INTEGER (0..15)
ACCESS read-write
STATUS mandatory
DESCRIPTION
"This object determines the bit pattern transmitted for 
whichever of the ABCD bits are not used for the selected 
line signalling scheme. This means CD for R2 Digital and 
P7, and BCD for R2 E&M."
DEFVAL { 5 }
::= { hdr2CfgEntry 20 }

hdr2CfgBlkToBlk OBJECT-TYPE
SYNTAX INTEGER{
  disable(1),
  enable(2)
}
ACCESS read-write
STATUS mandatory
DESCRIPTION
"This object determines whether or not a blocking signals 
received in the idle state is automatically responded to 
with a transmitted block signals."
DEFVAL { disable }
::= { hdr2CfgEntry 21 }

hdr2CfgDelayLos OBJECT-TYPE
SYNTAX INTEGER (0..10000)
ACCESS read-write
STATUS mandatory
DESCRIPTION
"This object determines the required duration of the LOS 
state before active calls are dropped and the signalling is 
reinitialised. Restoration of signal during this period 
allows calls to continue."
DEFVAL { 6000 }
::= { hdr2CfgEntry 22 }

hdr2CfgInGlare OBJECT-TYPE
SYNTAX INTEGER{
  disable(1),
  enable(2)
}
ACCESS read-write
STATUS mandatory
DESCRIPTION
"This object determines whether the incoming call is 
accepted and the outgoing call is dropped in a glare 
condition, or both calls are dropped as currently 
implemented."
DEFVAL { disable }
::= { hdr2CfgEntry 23 }

hdr2CfgClrCall OBJECT-TYPE
SYNTAX INTEGER{
  disable(1),
  enable(2)
}
ACCESS read-write
STATUS mandatory
DESCRIPTION
"This object determines whether an active call is cleared 
when an unexpected line signal is received, or the line 
signal is ignored as currently implemented."
DEFVAL { enable }
::= { hdr2CfgEntry 24 }

hdr2CfgANumQry OBJECT-TYPE
SYNTAX INTEGER{
  disable(1),
  enable(2)
}
ACCESS read-write
STATUS mandatory
DESCRIPTION
"This object determines whether or not an extra MFC cycle is 
used before to the A-number to indicate whether an A-number 
is available,using III-1 for yes and III-0 for no."
DEFVAL { disable }
::= { hdr2CfgEntry 25 }

hdr2CfgANumNAv OBJECT-TYPE
SYNTAX INTEGER{
  disable(1),
  enable(2)
}
ACCESS read-write
STATUS mandatory
DESCRIPTION
"THis object interpret I-12 as A-number not available."
DEFVAL { disable }
::= { hdr2CfgEntry 26 }

hdr2CfgANumReq OBJECT-TYPE
SYNTAX INTEGER{
  c1(1),
  c5(2),
  c6(3),
  c9(4)
}
ACCESS read-write
STATUS mandatory
DESCRIPTION
"this object backward register signal used to request 
transmission of the next A-number digit Frequently this is 
the same as the signal used to request transmission of the 
call category and A-number ."
DEFVAL { c5 }
::= { hdr2CfgEntry 27 }

hdr2CfgClrFwd OBJECT-TYPE
SYNTAX INTEGER{
  disable(1),
  enable(2)
}
ACCESS read-write
STATUS mandatory
DESCRIPTION
"This object repeatd size/clear-forward sequence is sent to 
startup to try to provoke a response from attached 
equipment."
DEFVAL { disable }
::= { hdr2CfgEntry 28 }

hdr2CfgRelGuard OBJECT-TYPE
SYNTAX INTEGER (0..2000)
ACCESS read-write
STATUS mandatory
DESCRIPTION
"This object is duration for which Release Guard signal is 
sent."
DEFVAL { 400 }
::= { hdr2CfgEntry 29 }

hdr2CfgPIClrBck OBJECT-TYPE
SYNTAX INTEGER{
  disable(1),
  enable(2)
}
ACCESS read-write
STATUS mandatory
DESCRIPTION
"This object determines whether or not a repeated 
release/Seize-ack sequence is sent while attempting to 
clear anincoming call."
DEFVAL { enable }
::= { hdr2CfgEntry 30 }

hdr2CfgDelayAns OBJECT-TYPE
SYNTAX INTEGER (100..2000)
ACCESS read-write
STATUS mandatory
DESCRIPTION
"this object determines the delay between the end of 
addressing and transmission of the answer signal."
DEFVAL { 100 }
::= { hdr2CfgEntry 31 }

hdr2CfgBNumLen OBJECT-TYPE
SYNTAX INTEGER (1..36)
ACCESS read-write
STATUS mandatory
DESCRIPTION
"this object determines the number of B-number digits to 
accept beore sending the 'address complete'signal, provided 
the 'end of B_number'signal is not received first."
DEFVAL { 4 }
::= { hdr2CfgEntry 32 }

hdr2CfgActBTout OBJECT-TYPE
SYNTAX INTEGER{
  b-number(1),
  error(2)
}
ACCESS read-write
STATUS mandatory
DESCRIPTION
"this object determines action to be taken on last B-digit 
timeout."
DEFVAL { b-number }
::= { hdr2CfgEntry 33 }

hdr2CfgInSubFree OBJECT-TYPE
SYNTAX INTEGER{
  b1(1),
  b5(2),
  b6(3)
}
ACCESS read-write
STATUS mandatory
DESCRIPTION
"this object backward register signal used to indicate 
acceptance of an incoming call."
DEFVAL { b6 }
::= { hdr2CfgEntry 34 }

hdr2CfgBNumNFnd OBJECT-TYPE
SYNTAX INTEGER{
  acceptAllCalls(1),
  rejectAllCalls(2),
  acceptAllCallsAsDigital(3),
  acceptAllCallsAnalog(4)
}
ACCESS read-write
STATUS mandatory
DESCRIPTION
"this object determines the action on B-Number not found in 
teh DNIS handling table."
DEFVAL { acceptAllCalls }
::= { hdr2CfgEntry 35 }

hdr2CfgSndBNumN OBJECT-TYPE
SYNTAX INTEGER{
  a9(1),
  a10(2)
}
ACCESS read-write
STATUS mandatory
DESCRIPTION
"this object backward signal requesting retransmission of 
curent B-number digit for outgoing calls."
DEFVAL { a9 }
::= { hdr2CfgEntry 36 }

hdr2CfgSndBNumN1 OBJECT-TYPE
SYNTAX INTEGER{
  a2(1),
  a8(2),
  a9(3),
  a10(4)
}
ACCESS read-write
STATUS mandatory
DESCRIPTION
"this object backward signal requesting transmission of 
B-number digit N-1 for outgoing calls."
DEFVAL { a2 }
::= { hdr2CfgEntry 37 }

hdr2CfgSndBNumN2 OBJECT-TYPE
SYNTAX INTEGER{
  a7(1),
  a9(2)
}
ACCESS read-write
STATUS mandatory
DESCRIPTION
"this object backward signal requesting transimission of 
B-number digit N-2 for outgoing calls."
DEFVAL { a7 }
::= { hdr2CfgEntry 38 }

hdr2CfgSndBNumN3 OBJECT-TYPE
SYNTAX INTEGER{
  a8(1),
  a10(2)
}
ACCESS read-write
STATUS mandatory
DESCRIPTION
"this object backward signal requesting transimission of 
B-number digit N-3 for outgoing calls."
DEFVAL { a8 }
::= { hdr2CfgEntry 39 }

hdr2CfgSndFBNum OBJECT-TYPE
SYNTAX INTEGER{
  a2(1),
  a9(2),
  a10(3)
}
ACCESS read-write
STATUS mandatory
DESCRIPTION
"this object determines whether or not the I-15 'end of 
B-number' signal is used for outgoing calls."
DEFVAL { a10 }
::= { hdr2CfgEntry 40 }

hdr2CfgDumANum OBJECT-TYPE
SYNTAX DisplayString (SIZE(1..36))
ACCESS read-write
STATUS mandatory
DESCRIPTION
"this object default A-number for outgoing calls in case 
none is supplied during call initiation."
DEFVAL { "1234" }
::= { hdr2CfgEntry 41 }

hdr2CfgEndANum OBJECT-TYPE
SYNTAX INTEGER{
  iii-12(1),
  iii-15(2)
}
ACCESS read-write
STATUS mandatory
DESCRIPTION
"This object forward register signal used to indicate that 
no more a_number digits are avaible.default=iii-15."
DEFVAL { iii-15 }
::= { hdr2CfgEntry 42 }

hdr2CfgOutCatAnalog OBJECT-TYPE
SYNTAX INTEGER{
  ii-1(1),
  ii-2(2),
  ii-3(3),
  ii-4(4),
  ii-5(5),
  ii-6(6),
  ii-7(7),
  ii-8(8),
  ii-9(9),
  ii-10(10),
  ii-11(11),
  ii-12(12),
  ii-13(13),
  ii-14(14),
  ii-15(15)
}
ACCESS read-write
STATUS mandatory
DESCRIPTION
"This object forward signals used to indicate the call 
category for outgoing calls."
DEFVAL { ii-1 }
::= { hdr2CfgEntry 43 }

hdr2CfgOutCatDigital OBJECT-TYPE
SYNTAX INTEGER{
  ii-1(1),
  ii-2(2),
  ii-3(3),
  ii-4(4),
  ii-5(5),
  ii-6(6),
  ii-7(7),
  ii-8(8),
  ii-9(9),
  ii-10(10),
  ii-11(11),
  ii-12(12),
  ii-13(13),
  ii-14(14),
  ii-15(15)
}
ACCESS read-write
STATUS mandatory
DESCRIPTION
""
DEFVAL { ii-6 }
::= { hdr2CfgEntry 44 }

hdr2CfgOutCatTest OBJECT-TYPE
SYNTAX INTEGER{
  ii-1(1),
  ii-2(2),
  ii-3(3),
  ii-4(4),
  ii-5(5),
  ii-6(6),
  ii-7(7),
  ii-8(8),
  ii-9(9),
  ii-10(10),
  ii-11(11),
  ii-12(12),
  ii-13(13),
  ii-14(14),
  ii-15(15)
}
ACCESS read-write
STATUS mandatory
DESCRIPTION
""
DEFVAL { ii-13 }
::= { hdr2CfgEntry 45 }

hdr2CfgOutCatMaintenance OBJECT-TYPE
SYNTAX INTEGER{
  ii-1(1),
  ii-2(2),
  ii-3(3),
  ii-4(4),
  ii-5(5),
  ii-6(6),
  ii-7(7),
  ii-8(8),
  ii-9(9),
  ii-10(10),
  ii-11(11),
  ii-12(12),
  ii-13(13),
  ii-14(14),
  ii-15(15)
}
ACCESS read-write
STATUS mandatory
DESCRIPTION
""
DEFVAL { ii-3 }
::= { hdr2CfgEntry 46 }

hdr2InCatMap OBJECT IDENTIFIER ::= { hdr2 2 }

hdr2InCatMapTable OBJECT-TYPE
SYNTAX SEQUENCE OF Hdr2InCatMapEntry
ACCESS not-accessible
STATUS mandatory
DESCRIPTION
"A table containing in cat map configurations for the Hiper 
E1/R2 Module."
::= { hdr2InCatMap 1 }

hdr2InCatMapEntry OBJECT-TYPE
SYNTAX Hdr2InCatMapEntry
ACCESS not-accessible
STATUS mandatory
DESCRIPTION
"Configuration parameters for the E1/R2 module."
INDEX { hdr2InCatMapIndex, hdr2InCatMapSigNum }
::= { hdr2InCatMapTable 1 }

Hdr2InCatMapEntry ::=
SEQUENCE {
hdr2InCatMapIndex
    INTEGER,
hdr2InCatMapSigNum
    INTEGER,
hdr2InCatMapCallType
    INTEGER
}

hdr2InCatMapIndex OBJECT-TYPE
SYNTAX INTEGER
ACCESS read-only
STATUS mandatory
DESCRIPTION
"The index which uniquely identifies the Hiper E1/R2 Module 
to which this entry is applicable. "
::= { hdr2InCatMapEntry 1 }

hdr2InCatMapSigNum OBJECT-TYPE
SYNTAX INTEGER (1..15)
ACCESS read-only
STATUS mandatory
DESCRIPTION
"This object is the index for one of 15 possible forward 
call category signals for imcoming calls."
::= { hdr2InCatMapEntry 2 }

hdr2InCatMapCallType OBJECT-TYPE
SYNTAX INTEGER{
  analog(1),
  digital(2),
  test(3),
  maintenance(4)
}
ACCESS read-write
STATUS mandatory
DESCRIPTION
"This object determines the meaning of forward call category 
for incoming calls."
DEFVAL { analog }
::= { hdr2InCatMapEntry 3 }

hdr2Pte OBJECT IDENTIFIER ::= { hdr2 3 }

hdr2PteTable OBJECT-TYPE
SYNTAX SEQUENCE OF Hdr2PteEntry
ACCESS not-accessible
STATUS mandatory
DESCRIPTION
"A table containing the Positron Trap Enable configurations 
for the Hiper E1/R2 Module."
::= { hdr2Pte 1 }

hdr2PteEntry OBJECT-TYPE
SYNTAX Hdr2PteEntry
ACCESS not-accessible
STATUS mandatory
DESCRIPTION
"Trap Enable Configuration parameters for the E1/R2 module. 
"
INDEX { hdr2PteIndex }
::= { hdr2PteTable 1 }

Hdr2PteEntry ::=
SEQUENCE {
hdr2PteIndex
    INTEGER,
hdr2PteMultiFrame
    INTEGER,
hdr2PteMultiFrameClr
    INTEGER,
hdr2PteRemMultiFrame
    INTEGER,
hdr2PteRemMultiFrameClr
    INTEGER
}

hdr2PteIndex OBJECT-TYPE
SYNTAX INTEGER
ACCESS read-only
STATUS mandatory
DESCRIPTION
"The index which uniquely identifies the Hiper E1/R2 Module 
to which this entry is applicable. "
::= { hdr2PteEntry 1 }

hdr2PteMultiFrame OBJECT-TYPE
SYNTAX INTEGER{
  disableAll(1),
  enableTrapOnly(2),
  enableSysLogOnly(3),
  enableAll(4)
}
ACCESS read-write
STATUS mandatory
DESCRIPTION
"Enable the generation of an SNMP trap upon detection of a 
Multi-Frame Alignment condition on the specified DS1. "
DEFVAL { enableAll }
::= { hdr2PteEntry 2 }

hdr2PteMultiFrameClr OBJECT-TYPE
SYNTAX INTEGER{
  disableAll(1),
  enableTrapOnly(2),
  enableSysLogOnly(3),
  enableAll(4)
}
ACCESS read-write
STATUS mandatory
DESCRIPTION
"Enable the generation of an SNMP trap upon detection of 
clearing a Multi-Frame Alignment condition on the specified 
DS1. "
DEFVAL { enableAll }
::= { hdr2PteEntry 3 }

hdr2PteRemMultiFrame OBJECT-TYPE
SYNTAX INTEGER{
  disableAll(1),
  enableTrapOnly(2),
  enableSysLogOnly(3),
  enableAll(4)
}
ACCESS read-write
STATUS mandatory
DESCRIPTION
"Enable the generation of an SNMP trap upon detection of a 
Remote Multi-Frame Alignment condition on the specified 
DS1. "
DEFVAL { enableAll }
::= { hdr2PteEntry 4 }

hdr2PteRemMultiFrameClr OBJECT-TYPE
SYNTAX INTEGER{
  disableAll(1),
  enableTrapOnly(2),
  enableSysLogOnly(3),
  enableAll(4)
}
ACCESS read-write
STATUS mandatory
DESCRIPTION
"Enable the generation of an SNMP trap upon detection of 
clearing a Remote Multi-Frame Alignment condition on the 
specified DS1. "
DEFVAL { enableAll }
::= { hdr2PteEntry 5 }

-- The E1-R2 CAS for the Hiper DSP Trap Enable Group

hdr2Te OBJECT IDENTIFIER ::= { hdr2 4 }

hdr2TeTable OBJECT-TYPE
SYNTAX SEQUENCE OF Hdr2TeEntry
ACCESS not-accessible
STATUS mandatory
DESCRIPTION
"A table containing the Trap Enable configurations for the 
Hiper E1/R2 Module."
::= { hdr2Te 1 }

hdr2TeEntry OBJECT-TYPE
SYNTAX Hdr2TeEntry
ACCESS not-accessible
STATUS mandatory
DESCRIPTION
"Trap Enable Configuration parameters for the E1/R2 module. 
"
INDEX { hdr2TeIndex }
::= { hdr2TeTable 1 }

Hdr2TeEntry ::=
SEQUENCE {
hdr2TeIndex
    INTEGER,
hdr2TeMultiFrame
    INTEGER,
hdr2TeMultiFrameClr
    INTEGER,
hdr2TeRemMultiFrame
    INTEGER,
hdr2TeRemMultiFrameClr
    INTEGER
}

hdr2TeIndex OBJECT-TYPE
SYNTAX INTEGER
ACCESS read-only
STATUS mandatory
DESCRIPTION
"The index which uniquely identifies the Hiper E1/R2 CARD to 
which this entry is applicable. "
::= { hdr2TeEntry 1 }

hdr2TeMultiFrame OBJECT-TYPE
SYNTAX INTEGER{
  enableTrap(1),
  disableAll(2),
  enableLog(3),
  enableAll(4)
}
ACCESS read-write
STATUS mandatory
DESCRIPTION
"Enable the generation of an SNMP trap upon detection of a 
Multi-Frame Alignment condition on the specified DS1. "
::= { hdr2TeEntry 2 }

hdr2TeMultiFrameClr OBJECT-TYPE
SYNTAX INTEGER{
  enableTrap(1),
  disableAll(2),
  enableLog(3),
  enableAll(4)
}
ACCESS read-write
STATUS mandatory
DESCRIPTION
"Enable the generation of an SNMP trap upon detection of 
clearing a Multi-Frame Alignment condition on the specified 
DS1. "
::= { hdr2TeEntry 3 }

hdr2TeRemMultiFrame OBJECT-TYPE
SYNTAX INTEGER{
  enableTrap(1),
  disableAll(2),
  enableLog(3),
  enableAll(4)
}
ACCESS read-write
STATUS mandatory
DESCRIPTION
"Enable the generation of an SNMP trap upon detection of a 
Remote Multi-Frame Alignment condition on the specified 
DS1. "
::= { hdr2TeEntry 4 }

hdr2TeRemMultiFrameClr OBJECT-TYPE
SYNTAX INTEGER{
  enableTrap(1),
  disableAll(2),
  enableLog(3),
  enableAll(4)
}
ACCESS read-write
STATUS mandatory
DESCRIPTION
"Enable the generation of an SNMP trap upon detection of 
clearing a Remote Multi-Frame Alignment condition on the 
specified DS1. "
::= { hdr2TeEntry 5 }

END
