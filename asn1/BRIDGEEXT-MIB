-- $Id: bridgeExt.mib,v 1.4 1999/04/15 18:23:13 tfinn Exp $
   BRIDGEEXT-MIB


   --FORCE-INCLUDE <mib.h>
   --FORCE-INCLUDE <snmpdefs.h>
   --FORCE-INCLUDE <snmpstat.h>
   --FORCE-INCLUDE "mibproto.h"


   DEFINITIONS ::= BEGIN

   IMPORTS
   bridgeExt
       FROM APENT-MIB
   OBJECT-TYPE
       FROM RFC-1212;

          Timeout ::= INTEGER -- a STP timer in units of seconds

          -- groups in the BridgeExt MIB

          apBridge     OBJECT IDENTIFIER ::= { bridgeExt 1 }

          apBridgeMaxAge OBJECT-TYPE
              SYNTAX  Timeout (6..40)
              ACCESS  read-write
              STATUS  mandatory
              DESCRIPTION
                      "The value that all bridges use for MaxAge when
                      this bridge is acting as the root.  Note that
                      802.1D-1990 specifies that the range for this
                      parameter is related to the value of
                      dot1dStpBridgeHelloTime."
              REFERENCE
                      "IEEE 802.1D-1990: Section 4.5.3.8"
              ::= { apBridge 1 }

          apBridgeHelloTime OBJECT-TYPE
              SYNTAX  Timeout (1..10)
              ACCESS  read-write
              STATUS  mandatory
              DESCRIPTION
                      "The value that all bridges use for HelloTime when
                      this bridge is acting as the root."
              REFERENCE
                      "IEEE 802.1D-1990: Section 4.5.3.9"
              ::= { apBridge 2 }

          apBridgeForwardDelay OBJECT-TYPE
              SYNTAX  Timeout (4..30)
              ACCESS  read-write
              STATUS  mandatory
              DESCRIPTION
                      "The value that all bridges use for ForwardDelay
                      when this bridge is acting as the root.  Note that
                      802.1D-1990 specifies that the range for this
                      parameter is related to the value of
                      dot1dStpBridgeMaxAge."
              REFERENCE
                      "IEEE 802.1D-1990: Section 4.5.3.10"
              ::= { apBridge 3 }


          -- The extended Bridge Port Table

          apBridgePortTable OBJECT-TYPE
              SYNTAX  SEQUENCE OF ApBridgePortEntry
              ACCESS  not-accessible
              STATUS  mandatory
              DESCRIPTION
                      "A table that contains generic information about
                      every port that is associated with this bridge."
              ::= { apBridge 4 }

          apBridgePortEntry OBJECT-TYPE
              SYNTAX  ApBridgePortEntry
              ACCESS  not-accessible
              STATUS  mandatory
              DESCRIPTION
                      "A list of information for each port of the
                      bridge."
              REFERENCE
                      "IEEE 802.1D-1990: Section 6.4.2, 6.6.1"
              INDEX  { apBridgePort }
			  --DEFAULT apjam-group apBridgeExtInst, apBridgePort
			  --DEFAULT apjam-popup-def apBridgeExtInst, Properties, local
              ::= { apBridgePortTable 1 }


          ApBridgePortEntry ::=
              SEQUENCE {
                  apBridgePort
                      INTEGER,
                  apBridgePortVlan
                      INTEGER
              }

          apBridgePort OBJECT-TYPE
              SYNTAX  INTEGER
              ACCESS  read-only
              STATUS  mandatory
              DESCRIPTION
                      "The port number of the port for which this entry
                      contains bridge management information."
			  --DEFAULT ap-display-name	Index
			  --DEFAULT apjam-popup-ref apBridgeExtInst, Properties
              ::= { apBridgePortEntry 1 }

          apBridgePortVlan OBJECT-TYPE
              SYNTAX  INTEGER (1..4095)
              ACCESS  read-write
              STATUS  mandatory
              DESCRIPTION
                      "The virtual local area network number (VLAN)
                      to associate with this port."
			  --DEFAULT ap-display-name	Vlan
			  --DEFAULT apjam-popup-ref apBridgeExtInst, Properties
              ::= { apBridgePortEntry 2 }

          apBridgeSpanningTreeState OBJECT-TYPE
              SYNTAX  INTEGER {
                          enabled(1),
                          disabled(2)
                          }
              ACCESS  read-write
              STATUS  mandatory
              DESCRIPTION
                      "This allows spanning-tree to be enabled/disabled
                      on the unit."
              ::= { apBridge 5 }

          END
