CACHEFLOW-MIB DEFINITIONS ::= BEGIN

IMPORTS
	MODULE-IDENTITY, OBJECT-TYPE, Integer32, Counter32 FROM SNMPv2-SMI
	DisplayString			FROM SNMPv2-TC
	enterprises 			FROM RFC1155-SMI;

-- CacheFlow's private MIBs

cacheFlow MODULE-IDENTITY
	LAST-UPDATED "9910181700"
	ORGANIZATION "CacheFlow Inc."
	CONTACT-INFO
		"support@CacheFlow.com
		http://www.CacheFlow.com"
	DESCRIPTION
		"The MIB module for CacheFlow"

	::= { enterprises 3417 }

-- cacheFlow	OBJECT IDENTIFIER ::= { enterprises 3417 }
products		OBJECT IDENTIFIER ::= { cacheFlow 1 }
cacheFlowMgmt	OBJECT IDENTIFIER ::= { cacheFlow 2 }
cache			OBJECT IDENTIFIER ::= { products 1 }
cacheFlow1000	OBJECT IDENTIFIER ::= { cache 1 }
cacheFlow100	OBJECT IDENTIFIER ::= { cache 2 }
cacheFlow500	OBJECT IDENTIFIER ::= { cache 3 }
cacheFlow2000	OBJECT IDENTIFIER ::= { cache 4 }
cacheFlow5000	OBJECT IDENTIFIER ::= { cache 5 }
cacheFlow500A	OBJECT IDENTIFIER ::= { cache 6 }
cacheFlow3000	OBJECT IDENTIFIER ::= { cache 7 }
cacheFlow5x5	OBJECT IDENTIFIER ::= { cache 8 }
cacheFlow110	OBJECT IDENTIFIER ::= { cache 9 }
cacheFlow600	OBJECT IDENTIFIER ::= { cache 10 }
cacheFlow6000	OBJECT IDENTIFIER ::= { cache 11 }
cacheFlow610	OBJECT IDENTIFIER ::= { cache 12 }
cacheFlow6x5	OBJECT IDENTIFIER ::= { cache 13 }
cacheFlow3000s	OBJECT IDENTIFIER ::= { cache 14 }
cacheFlow5000s	OBJECT IDENTIFIER ::= { cache 15 }
cacheFlow7x5	OBJECT IDENTIFIER ::= { cache 16 }
cacheFlow710	OBJECT IDENTIFIER ::= { cache 17 }
cacheFlow7000	OBJECT IDENTIFIER ::= { cache 18 }
cacheFlow611	OBJECT IDENTIFIER ::= { cache 19 }
cacheFlow800	OBJECT IDENTIFIER ::= { cache 20 }

END
