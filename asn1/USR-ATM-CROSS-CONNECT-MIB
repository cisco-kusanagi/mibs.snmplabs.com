USR-ATM-CROSS-CONNECT-MIB DEFINITIONS ::= BEGIN
               IMPORTS
                  OBJECT-TYPE, MODULE-IDENTITY,
                  Integer32
                      FROM SNMPv2-SMI
                  RowStatus
                      FROM SNMPv2-TC
                  DisplayString
                      FROM RFC1213-MIB
                  IfIndex
		      FROM ATM-MIB
                  common
		      FROM USR-DEFINITIONS-MIB;
    usrAtmCrossConnect  MODULE-IDENTITY
                        LAST-UPDATED "200204061356Z"
                        ORGANIZATION "CommWorks Corporation, a 3Com Company"
                        CONTACT-INFO "Customer Support"
                        DESCRIPTION
                                "The commWorks enterprise defined MIB objects
                                 for VC Cross Connect."
--                      REVISION  "200204061356Z"
--                      DESCRIPTION " Added MODULE-IDENTITY and corrected
--                                    SNMPv2 syntax."
                        ::= { common 50 }
               --  The ATM VC Cross Connect for cli commands
               usrAtmVcCrossConnectTable OBJECT-TYPE
                    SYNTAX  SEQUENCE OF UsrAtmVcCrossConnectEntry
                    MAX-ACCESS  not-accessible
                    STATUS  current
                    DESCRIPTION
                     "This usrAtmVcCrossConnectTable keeps cross connect name
                      and corresponding cross connect index
                      pcr is used to obtain traffic descriptor Index."
                    ::= { usrAtmCrossConnect 1 }
               usrAtmVcCrossConnectEntry OBJECT-TYPE
                    SYNTAX  UsrAtmVcCrossConnectEntry
                    MAX-ACCESS  not-accessible
                    STATUS  current
                    DESCRIPTION " "
                    INDEX { usrAtmVcCrossConnectName}
                    ::= { usrAtmVcCrossConnectTable 1 }
               UsrAtmVcCrossConnectEntry ::= SEQUENCE {
                    usrAtmVcCrossConnectName           DisplayString,
                    usrAtmVcCrossConnectIndex          Integer32,
                    usrAtmVcCrossConnectLowIfIndex     IfIndex,
                    usrAtmVcCrossConnectLowVpi         Integer32,
                    usrAtmVcCrossConnectLowVci         Integer32,
                    usrAtmVcCrossConnectHighIfIndex    IfIndex,
                    usrAtmVcCrossConnectHighVpi        Integer32,
                    usrAtmVcCrossConnectHighVci        Integer32,
                    usrAtmVcCrossConnectLowPort        Integer32,
                    usrAtmVcCrossConnectHighPort       Integer32,
                    usrAtmVcCrossConnectPcr            Integer32,
                    usrAtmVcCrossConnectRowStatus      RowStatus
               }
               usrAtmVcCrossConnectName OBJECT-TYPE
                    SYNTAX  DisplayString
                    MAX-ACCESS  not-accessible
                    STATUS  current
                    DESCRIPTION "VC Cross connect name used as index"
                    --CONFIGURABLE
                    ::= { usrAtmVcCrossConnectEntry 1 }
               usrAtmVcCrossConnectIndex OBJECT-TYPE
                    SYNTAX  Integer32
                    MAX-ACCESS  read-create
                    STATUS  current
                    DESCRIPTION  "cross connect index for the entry  "
                    --CONFIGURABLE
                    ::= { usrAtmVcCrossConnectEntry 2 }
               usrAtmVcCrossConnectLowIfIndex OBJECT-TYPE
                    SYNTAX  IfIndex
                    MAX-ACCESS  read-create
                    STATUS  current
                    DESCRIPTION  "ifindex of the vc with low val "
                    --CONFIGURABLE
                    ::= { usrAtmVcCrossConnectEntry 3 }
               usrAtmVcCrossConnectLowVpi OBJECT-TYPE
                    SYNTAX  Integer32
                    MAX-ACCESS  read-create
                    STATUS  current
                    DESCRIPTION  "vpi value of the vc with low ifindex"
                    --CONFIGURABLE
                    ::= { usrAtmVcCrossConnectEntry 4 }
               usrAtmVcCrossConnectLowVci OBJECT-TYPE
                    SYNTAX  Integer32
                    MAX-ACCESS  read-create
                    STATUS  current
                    DESCRIPTION  "vci of the vc with low ifindex val"
                    --CONFIGURABLE
                    ::= { usrAtmVcCrossConnectEntry 5 }
               usrAtmVcCrossConnectHighIfIndex OBJECT-TYPE
                    SYNTAX  IfIndex
                    MAX-ACCESS  read-create
                    STATUS  current
                    DESCRIPTION  "vc associated with high ifindex param"
                    --CONFIGURABLE
                    ::= { usrAtmVcCrossConnectEntry 6 }
               usrAtmVcCrossConnectHighVpi OBJECT-TYPE
                    SYNTAX  Integer32
                    MAX-ACCESS  read-create
                    STATUS  current
                    DESCRIPTION  "vpi of the vc with high ifindex param"
                    --CONFIGURABLE
                    ::= { usrAtmVcCrossConnectEntry 7 }
               usrAtmVcCrossConnectHighVci OBJECT-TYPE
                    SYNTAX  Integer32
                    MAX-ACCESS  read-create
                    STATUS  current
                    DESCRIPTION  "vci of the vc eith high ifindex val"
                    --CONFIGURABLE
                    ::= { usrAtmVcCrossConnectEntry 8 }
               usrAtmVcCrossConnectLowPort OBJECT-TYPE
                    SYNTAX  Integer32
                    MAX-ACCESS  read-create
                    STATUS  current
                    DESCRIPTION  "low end port number"
                    ::= { usrAtmVcCrossConnectEntry 9 }
               usrAtmVcCrossConnectHighPort OBJECT-TYPE
                    SYNTAX  Integer32
                    MAX-ACCESS  read-create
                    STATUS  current
                    DESCRIPTION  "high end port number"
                    ::= { usrAtmVcCrossConnectEntry 10 }
               usrAtmVcCrossConnectPcr OBJECT-TYPE
                    SYNTAX  Integer32
                    MAX-ACCESS  read-create
                    STATUS  current
                    DESCRIPTION  "peak cell rate -as traffic descr index created"
                    ::= { usrAtmVcCrossConnectEntry 11 }
               usrAtmVcCrossConnectRowStatus OBJECT-TYPE
                    SYNTAX  RowStatus
                    MAX-ACCESS   read-only
                    STATUS  current
                    DESCRIPTION  "cross connect row status"
                    ::= { usrAtmVcCrossConnectEntry 12 }
               END -- End of USR-ATM-CROSS-CONNECT-MIB DEFINITIONS
-- ************************************************************************
--
--	usr_dsx3.mib - A MIB file for the Netserver gateway card
--                    Dsx3 MIB
--
-- Author:         Jay D. Miller
--
