BAS-CARD-INFO-MIB DEFINITIONS ::= BEGIN

IMPORTS
	MODULE-IDENTITY, OBJECT-TYPE,
        IpAddress,
	Integer32						FROM SNMPv2-SMI
	RowStatus						FROM SNMPv2-TC
	basCardInfo, BasChassisId,
	BasSlotId, BasInterfaceId,
	BasLogicalPortId, BasCardClass	FROM BAS-MIB;


basCardInfoMib MODULE-IDENTITY
	LAST-UPDATED "9810081200Z"
	ORGANIZATION "Broadband Access Systems"
	CONTACT-INFO
		" Tech Support
		  Broadband Access Systems
		  201 Forest Street
		  Marlboro, MA  01752
		  U.S.A.
		  
		  508-485-8200
		  support@basystems.com"
	DESCRIPTION
		"This MIB module defines the configuration MIB objects
		 for a Broadband Access System Chassis cards."
	::= { basCardInfo 1 }


basCardObjects	OBJECT IDENTIFIER ::= { basCardInfoMib 1 }

--
-- ----------------------------------------------------------------------
--
-- Bas Mgr Configuration Object
--
-- ----------------------------------------------------------------------
--

basCardInfoTable OBJECT-TYPE
	SYNTAX		SEQUENCE OF BasCardInfoEntry
	MAX-ACCESS	not-accessible
	STATUS		current
	DESCRIPTION
		"Info about this slot."
	::= { basCardObjects 1 }

basCardInfoEntry OBJECT-TYPE
	SYNTAX		BasCardInfoEntry
	MAX-ACCESS	not-accessible
	STATUS		current
	DESCRIPTION
		"Chassis and slot information."
	INDEX		{ 
					basCardInfoChassis,
					basCardInfoSlot,
					basCardInfoIf,
					basCardInfoLPort
				}
	::= { basCardInfoTable 1 }

BasCardInfoEntry ::= SEQUENCE {
		basCardInfoChassis					BasChassisId,
		basCardInfoSlot						BasSlotId,
		basCardInfoIf						BasInterfaceId,
		basCardInfoLPort					BasLogicalPortId,
		basCardInfoChassisNumber				Integer32,
		basCardInfoClass					BasCardClass,
                basAgentConfigSave					INTEGER,
		basAgentConfigSaveStatus				INTEGER,
                basBcmIpAddress						IpAddress,
		basCardReset						INTEGER,	
		basAgentSharedKey					OCTET STRING,
		basAgentUdpPort						INTEGER,
		basAgentTcpPort                                       INTEGER,
		basCardInfoAdminStatus					INTEGER,
		basCardResetState					INTEGER,
		basCardWatchdogTimer					INTEGER	
	}

basCardInfoChassis OBJECT-TYPE
	SYNTAX		BasChassisId
	MAX-ACCESS	not-accessible
	STATUS		current
	DESCRIPTION
		"The BAS Chassis ID of this card."
	::= { basCardInfoEntry 1 }

basCardInfoSlot OBJECT-TYPE
	SYNTAX		BasSlotId
	MAX-ACCESS	not-accessible
	STATUS		current
	DESCRIPTION
		"The BAS Slot ID of this card."
	::= { basCardInfoEntry 2 }

basCardInfoIf OBJECT-TYPE
	SYNTAX		BasInterfaceId
	MAX-ACCESS	not-accessible
	STATUS		current
	DESCRIPTION
		"The BAS interface ID of this card."
	::= { basCardInfoEntry 3 }

basCardInfoLPort OBJECT-TYPE
	SYNTAX		BasLogicalPortId
	MAX-ACCESS	not-accessible
	STATUS		current
	DESCRIPTION
		"The BAS logical port ID of this card."
	::= { basCardInfoEntry 4 }

basCardInfoChassisNumber OBJECT-TYPE
    SYNTAX		Integer32
    MAX-ACCESS	read-only
    STATUS		current
    DESCRIPTION
		"The BAS Chassis serial number of this card."
    ::= { basCardInfoEntry 5 }

basCardInfoClass OBJECT-TYPE
    SYNTAX		BasCardClass
    MAX-ACCESS	read-only
    STATUS		current
    DESCRIPTION
		"The BAS card class of this card."
    ::= { basCardInfoEntry 6 }

basAgentConfigSave OBJECT-TYPE
    SYNTAX		INTEGER {
                        normal(1),
                        save(2),
                        saving(3)
			}
    MAX-ACCESS	        read-write
    STATUS		current
    DESCRIPTION
		"The BAS save configuration Object"
    ::= { basCardInfoEntry 7 }

basAgentConfigSaveStatus OBJECT-TYPE
    SYNTAX		INTEGER {
                        none(1),
                        passed(2),
                        failed(3)
			}	
    MAX-ACCESS	read-only
    STATUS		current
    DESCRIPTION
		"The BAS save configuration status Object"
    ::= { basCardInfoEntry 8}

basBcmIpAddress OBJECT-TYPE
    SYNTAX		IpAddress
    MAX-ACCESS	        read-write
    STATUS		current
    DESCRIPTION
		"The BCM IP Address Object"
    ::= { basCardInfoEntry 9 }

basCardReset OBJECT-TYPE
    SYNTAX		INTEGER {
                        normal(1),
                        reset(2)
			}
    MAX-ACCESS	        read-write
    STATUS		current
    DESCRIPTION
		"The BAS Card Reset Object. In order to set this object to reset(2),
                 the object basCardResetState must first be set to unlocked(2)."
    ::= { basCardInfoEntry 10 }


basAgentSharedKey OBJECT-TYPE
    SYNTAX		OCTET STRING (SIZE (0..256))
    MAX-ACCESS	        read-write
    STATUS		current
    DESCRIPTION
		"The Agent Shared Key Object"
    ::= { basCardInfoEntry 11 }


basAgentUdpPort OBJECT-TYPE
    SYNTAX		INTEGER(0..65535)
    MAX-ACCESS	        read-write
    STATUS		current
    DESCRIPTION
		"The BAS Agent SNMP UDP Port Object"
    ::= { basCardInfoEntry 12 }


basAgentTcpPort OBJECT-TYPE
    SYNTAX		INTEGER(0..65535)
    MAX-ACCESS	        read-write
    STATUS		current
    DESCRIPTION
		"The BAS Agentx Tcp Port Object"
    ::= { basCardInfoEntry 13 }

 basCardInfoAdminStatus OBJECT-TYPE
      SYNTAX  INTEGER {
                         up(1),       
 --Card ready
                         down(2),
                         testing(3),
--Card in some test mode
			 loading(4),
			 loaded(5),
			 registering(6),
			 registered(7),
			 agentxstarting(8),
			 agentxstarted(9)
--Card in init mode
                       }
      MAX-ACCESS  read-only
      STATUS  current
      DESCRIPTION
                  "The desired state of the card.  The
                   testing(3) state indicates that the card is
                   under test, the IFs are not operational."
         ::= { basCardInfoEntry 14 }

basCardResetState OBJECT-TYPE
    SYNTAX		INTEGER {
                        locked(1),
                        unlocked(2)
			}
    MAX-ACCESS	        read-write
    STATUS		current
    DESCRIPTION
		"The state of the basCardReset object. If this object
                is set to locked(1), then the card cannot be reset without
                first setting this object to unlocked(2)."
    ::= { basCardInfoEntry 15 }

basCardWatchdogTimer OBJECT-TYPE
    SYNTAX		INTEGER {
                        enable(1),
                        disable(2),
                        notSupported(3)
			}
    MAX-ACCESS	        read-write
    STATUS		current
    DESCRIPTION
		"This object may be set to enable(1) to enable the watchdog
                timer or to disable(2) to disable the watchdog timer. Setting
                this object to notSupported(3) has no affect. A notSupported(3)
                value returned means the watchdog timer is not supported by
                the hardware."
    ::= { basCardInfoEntry 16 }

basCardRSTable OBJECT-TYPE
	SYNTAX		SEQUENCE OF BasCardRSEntry
	MAX-ACCESS	not-accessible
	STATUS		current
	DESCRIPTION
		"A table specifying a list of Route Servers for this card."
	::= { basCardObjects 2 }

basCardRSEntry OBJECT-TYPE
	SYNTAX      BasCardRSEntry
	MAX-ACCESS  not-accessible
	STATUS      current
	DESCRIPTION
		"Card specific Route Server information entry."
	INDEX		{ basCardChassis,
				  basCardSlot,
				  basCardIf,
				  basCardLPort,
				  basCardRSChassis,
				  basCardRSSlot,
				  basCardRSIf,
				  basCardRSLPort
				}
	::= { basCardRSTable 1 }

BasCardRSEntry ::= SEQUENCE {
		basCardChassis		BasChassisId,
		basCardSlot			BasSlotId,
		basCardIf			BasInterfaceId,
		basCardLPort		BasLogicalPortId,
		basCardRSChassis	BasChassisId,
		basCardRSSlot		BasSlotId,
		basCardRSIf			BasInterfaceId,
		basCardRSLPort		BasLogicalPortId,
		basCardRSStatus		RowStatus
	}

basCardChassis OBJECT-TYPE
	SYNTAX		BasChassisId
	MAX-ACCESS	not-accessible
	STATUS		current
	DESCRIPTION
		"The BAS Chassis ID of this card."
	::= { basCardRSEntry 1 }

basCardSlot OBJECT-TYPE
	SYNTAX		BasSlotId
	MAX-ACCESS	not-accessible
	STATUS		current
	DESCRIPTION
		"The BAS Slot ID of this card."
	::= { basCardRSEntry 2 }

basCardIf OBJECT-TYPE
	SYNTAX		BasInterfaceId
	MAX-ACCESS	not-accessible
	STATUS		current
	DESCRIPTION
		"The BAS interface ID of this card."
	::= { basCardRSEntry 3 }

basCardLPort OBJECT-TYPE
	SYNTAX		BasLogicalPortId
	MAX-ACCESS	not-accessible
	STATUS		current
	DESCRIPTION
		"The BAS logical port ID of this card."
	::= { basCardRSEntry 4 }

basCardRSChassis OBJECT-TYPE
	SYNTAX		BasChassisId
	MAX-ACCESS	read-create
	STATUS		current
	DESCRIPTION
		"The BAS Chassis ID of a Route Server known by this card."
	::= { basCardRSEntry 5 }

basCardRSSlot OBJECT-TYPE
	SYNTAX		BasSlotId
	MAX-ACCESS	read-create
	STATUS		current
	DESCRIPTION
		"The BAS Slot ID of a Route Server known by this card."
	::= { basCardRSEntry 6 }

basCardRSIf OBJECT-TYPE
	SYNTAX		BasInterfaceId
	MAX-ACCESS	read-create
	STATUS		current
	DESCRIPTION
		"The BAS interface ID of a Route Server known by this card."
	::= { basCardRSEntry 7 }

basCardRSLPort OBJECT-TYPE
	SYNTAX		BasLogicalPortId
	MAX-ACCESS	read-create
	STATUS		current
	DESCRIPTION
		"The BAS logical port ID of a Route Server known by this card."
	::= { basCardRSEntry 8 }

basCardRSStatus OBJECT-TYPE
	SYNTAX		RowStatus
	MAX-ACCESS	read-create
	STATUS		current
	DESCRIPTION
		"The row status object used to create and delete a 
		 conceptual row according to RowStatus conventions."
	::= { basCardRSEntry 9 }

--
-- ----------------------------------------------------------------------
--
-- End
--
-- ----------------------------------------------------------------------
--

END
