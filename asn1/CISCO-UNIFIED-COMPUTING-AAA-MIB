-- *********************************************************************
-- CISCO-UNIFIED-COMPUTING-AAA-MIB.my
-- 
-- MIB representation of the Cisco Unified Computing System
-- AAA management information model package
-- 
-- Created January 2016 by Charles Bullis
-- 
-- Copyright (c) 2005-2016 Cisco Systems, Inc. All rights reserved.
-- 
-- *********************************************************************

CISCO-UNIFIED-COMPUTING-AAA-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoUnifiedComputingMIBObjects,
    CucsManagedObjectId,
    CucsManagedObjectDn
        FROM CISCO-UNIFIED-COMPUTING-MIB
    CucsAaaAccess,
    CucsAaaAccountStatus,
    CucsAaaAuthRealmFsmCurrentFsm,
    CucsAaaAuthRealmFsmStageName,
    CucsAaaCimcSessionType,
    CucsAaaClear,
    CucsAaaConfigState,
    CucsAaaDomainAuthRealm,
    CucsAaaEpAccess,
    CucsAaaEpFsmCurrentFsm,
    CucsAaaEpFsmStageName,
    CucsAaaEpFsmTaskItem,
    CucsAaaExtMgmtAccess,
    CucsAaaIpmiOverLan,
    CucsAaaLdapEpFsmCurrentFsm,
    CucsAaaLdapEpFsmStageName,
    CucsAaaLdapGroupRuleAuthorization,
    CucsAaaLdapGroupRuleTraversal,
    CucsAaaLdapVendor,
    CucsAaaNoRolePolicy,
    CucsAaaPwdPolicy,
    CucsAaaRadiusEpFsmCurrentFsm,
    CucsAaaRadiusEpFsmStageName,
    CucsAaaRadiusService,
    CucsAaaRealm,
    CucsAaaRealmFsmCurrentFsm,
    CucsAaaRealmFsmStageName,
    CucsAaaRealmFsmTaskItem,
    CucsAaaSession,
    CucsAaaSessionState,
    CucsAaaSshStr,
    CucsAaaTacacsPlusEpFsmCurrentFsm,
    CucsAaaTacacsPlusEpFsmStageName,
    CucsAaaUserEpFsmCurrentFsm,
    CucsAaaUserEpFsmStageName,
    CucsAaaUserEpFsmTaskItem,
    CucsAaaUserInterface,
    CucsConditionActionIndicator,
    CucsConditionCause,
    CucsConditionCode,
    CucsConditionRemoteInvRslt,
    CucsConditionSeverity,
    CucsFsmCompletion,
    CucsFsmFlags,
    CucsFsmFsmStageStatus,
    CucsNetworkSwitchId,
    CucsPolicyPolicyOwner
        FROM CISCO-UNIFIED-COMPUTING-TC-MIB;

cucsAaaObjects MODULE-IDENTITY
    LAST-UPDATED    "201601180000Z"
    ORGANIZATION    "Cisco Systems Inc."
    CONTACT-INFO
        "Cisco Systems
        Customer Service
        
        Postal: 170 W Tasman Drive
        San Jose, CA  95134
        USA
        
        Tel: +1 800 553 -NETS
        
        E-mail: cs-san@cisco.com, cs-lan-switch-snmp@cisco.com"
    DESCRIPTION
        "MIB representation of the Cisco Unified Computing System
        AAA management information model package"
    ::= { ciscoUnifiedComputingMIBObjects 2 }

cucsAaaAuthRealmTable OBJECT-TYPE
    SYNTAX           SEQUENCE OF CucsAaaAuthRealmEntry
    MAX-ACCESS       not-accessible
    STATUS           current
    DESCRIPTION
        "Cisco UCS aaa:AuthRealm managed object table"
    ::= { cucsAaaObjects 1 }

cucsAaaAuthRealmEntry OBJECT-TYPE
    SYNTAX           CucsAaaAuthRealmEntry
    MAX-ACCESS       not-accessible
    STATUS           current
    DESCRIPTION
        "Entry for the cucsAaaAuthRealmTable table."
    INDEX { cucsAaaAuthRealmInstanceId }
    ::= { cucsAaaAuthRealmTable 1 }

CucsAaaAuthRealmEntry ::= SEQUENCE {
    cucsAaaAuthRealmInstanceId                                       CucsManagedObjectId,
    cucsAaaAuthRealmDn                                               CucsManagedObjectDn,
    cucsAaaAuthRealmRn                                               SnmpAdminString,
    cucsAaaAuthRealmConLogin                                         CucsAaaRealm,
    cucsAaaAuthRealmDefLogin                                         CucsAaaRealm,
    cucsAaaAuthRealmDefRolePolicy                                    CucsAaaNoRolePolicy,
    cucsAaaAuthRealmDescr                                            SnmpAdminString,
    cucsAaaAuthRealmFsmDescr                                         SnmpAdminString,
    cucsAaaAuthRealmFsmPrev                                          SnmpAdminString,
    cucsAaaAuthRealmFsmProgr                                         Gauge32,
    cucsAaaAuthRealmFsmRmtInvErrCode                                 Gauge32,
    cucsAaaAuthRealmFsmRmtInvErrDescr                                SnmpAdminString,
    cucsAaaAuthRealmFsmRmtInvRslt                                    CucsConditionRemoteInvRslt,
    cucsAaaAuthRealmFsmStageDescr                                    SnmpAdminString,
    cucsAaaAuthRealmFsmStamp                                         DateAndTime,
    cucsAaaAuthRealmFsmStatus                                        SnmpAdminString,
    cucsAaaAuthRealmFsmTry                                           Gauge32,
    cucsAaaAuthRealmIntId                                            SnmpAdminString,
    cucsAaaAuthRealmName                                             SnmpAdminString,
    cucsAaaAuthRealmPolicyLevel                                      Gauge32,
    cucsAaaAuthRealmPolicyOwner                                      CucsPolicyPolicyOwner
}

cucsAaaAuthRealmInstanceId OBJECT-TYPE
    SYNTAX       CucsManagedObjectId
    MAX-ACCESS   not-accessible
    STATUS       current
    DESCRIPTION
        "Instance identifier of the managed object."
    ::= { cucsAaaAuthRealmEntry 1 }

cucsAaaAuthRealmDn OBJECT-TYPE
    SYNTAX       CucsManagedObjectDn
    MAX-ACCESS   read-only
    STATUS       current
    DESCRIPTION
        "Cisco UCS aaa:AuthRealm:dn managed object property"
    ::= { cucsAaaAuthRealmEntry 2 }

cucsAaaAuthRealmRn OBJECT-TYPE
    SYNTAX       SnmpAdminString
    MAX-ACCESS   read-only
    STATUS       current
    DESCRIPTION
        "Cisco UCS aaa:AuthRealm:rn managed object property"
    ::= { cucsAaaAuthRealmEntry 3 }

cucsAaaAuthRealmConLogin OBJECT-TYPE
    SYNTAX       CucsAaaRealm
    MAX-ACCESS   read-only
    STATUS       current
    DESCRIPTION
        "Cisco UCS aaa:AuthRealm:conLogin managed object property"
    ::= { cucsAaaAuthRealmEntry 4 }

cucsAaaAuthRealmDefLogin OBJECT-TYPE
    SYNTAX       CucsAaaRealm
    MAX-ACCESS   read-only
    STATUS       current
    DESCRIPTION
        "Cisco UCS aaa:AuthRealm:defLogin managed object property"
    ::= { cucsAaaAuthRealmEntry 5 }

cucsAaaAuthRealmDefRolePolicy OBJECT-TYPE
    SYNTAX       CucsAaaNoRolePolicy
    MAX-ACCESS   read-only
    STATUS       current
    DESCRIPTION
        "Cisco UCS aaa:AuthRealm:defRolePolicy managed object property"
    ::= { cucsAaaAuthRealmEntry 6 }

cucsAaaAuthRealmDescr OBJECT-TYPE
    SYNTAX       SnmpAdminString
    MAX-ACCESS   read-only
    STATUS       current
    DESCRIPTION
        "Cisco UCS aaa:AuthRealm:descr managed object property"
    ::= { cucsAaaAuthRealmEntry 7 }

cucsAaaAuthRealmFsmDescr OBJECT-TYPE
    SYNTAX       SnmpAdminString
    MAX-ACCESS   read-only
    STATUS       current
    DESCRIPTION
        "Cisco UCS aaa:AuthRealm:fsmDescr managed object property"
    ::= { cucsAaaAuthRealmEntry 8 }

cucsAaaAuthRealmFsmPrev OBJECT-TYPE
    SYNTAX       SnmpAdminString
    MAX-ACCESS   read-only
    STATUS       current
    DESCRIPTION
        "Cisco UCS aaa:AuthRealm:fsmPrev managed object property"
    ::= { cucsAaaAuthRealmEntry 9 }

cucsAaaAuthRealmFsmProgr OBJECT-TYPE
    SYNTAX       Gauge32
    MAX-ACCESS   read-only
    STATUS       current
    DESCRIPTION
        "Cisco UCS aaa:AuthRealm:fsmProgr managed object property"
    ::= { cucsAaaAuthRealmEntry 10 }

cucsAaaAuthRealmFsmRmtInvErrCode OBJECT-TYPE
    SYNTAX       Gauge32
    MAX-ACCESS   read-only
    STATUS       current
    DESCRIPTION
        "Cisco UCS aaa:AuthRealm:fsmRmtInvErrCode managed object property"
    ::= { cucsAaaAuthRealmEntry 11 }

cucsAaaAuthRealmFsmRmtInvErrDescr OBJECT-TYPE
    SYNTAX       SnmpAdminString
    MAX-ACCESS   read-only
    STATUS       current
    DESCRIPTION
        "Cisco UCS aaa:AuthRealm:fsmRmtInvErrDescr managed
        object property"
    ::= { cucsAaaAuthRealmEntry 12 }

cucsAaaAuthRealmFsmRmtInvRslt OBJECT-TYPE
    SYNTAX       CucsConditionRemoteInvRslt
    MAX-ACCESS   read-only
    STATUS       current
    DESCRIPTION
        "Cisco UCS aaa:AuthRealm:fsmRmtInvRslt managed object property"
    ::= { cucsAaaAuthRealmEntry 13 }

cucsAaaAuthRealmFsmStageDescr OBJECT-TYPE
    SYNTAX       SnmpAdminString
    MAX-ACCESS   read-only
    STATUS       current
    DESCRIPTION
        "Cisco UCS aaa:AuthRealm:fsmStageDescr managed object property"
    ::= { cucsAaaAuthRealmEntry 14 }

cucsAaaAuthRealmFsmStamp OBJECT-TYPE
    SYNTAX       DateAndTime
    MAX-ACCESS   read-only
    STATUS       current
    DESCRIPTION
        "Cisco UCS aaa:AuthRealm:fsmStamp managed object property"
    ::= { cucsAaaAuthRealmEntry 15 }

cucsAaaAuthRealmFsmStatus OBJECT-TYPE
    SYNTAX       SnmpAdminString
    MAX-ACCESS   read-only
    STATUS       current
    DESCRIPTION
        "Cisco UCS aaa:AuthRealm:fsmStatus managed object property"
    ::= { cucsAaaAuthRealmEntry 16 }

cucsAaaAuthRealmFsmTry OBJECT-TYPE
    SYNTAX       Gauge32
    MAX-ACCESS   read-only
    STATUS       current
    DESCRIPTION
        "Cisco UCS aaa:AuthRealm:fsmTry managed object property"
    ::= { cucsAaaAuthRealmEntry 17 }

cucsAaaAuthRealmIntId OBJECT-TYPE
    SYNTAX       SnmpAdminString
    MAX-ACCESS   read-only
    STATUS       current
    DESCRIPTION
        "Cisco UCS aaa:AuthRealm:intId managed object property"
    ::= { cucsAaaAuthRealmEntry 18 }

cucsAaaAuthRealmName OBJECT-TYPE
    SYNTAX       SnmpAdminString
    MAX-ACCESS   read-only
    STATUS       current
    DESCRIPTION
        "Cisco UCS aaa:AuthRealm:name managed object property"
    ::= { cucsAaaAuthRealmEntry 19 }

cucsAaaAuthRealmPolicyLevel OBJECT-TYPE
    SYNTAX       Gauge32
    MAX-ACCESS   read-only
    STATUS       current
    DESCRIPTION
        "Cisco UCS aaa:AuthRealm:policyLevel managed object property"
    ::= { cucsAaaAuthRealmEntry 20 }

cucsAaaAuthRealmPolicyOwner OBJECT-TYPE
    SYNTAX       CucsPolicyPolicyOwner
    MAX-ACCESS   read-only
    STATUS       current
    DESCRIPTION
        "Cisco UCS aaa:AuthRealm:policyOwner managed object property"
    ::= { cucsAaaAuthRealmEntry 21 }

cucsAaaAuthRealmFsmTable OBJECT-TYPE
    SYNTAX           SEQUENCE OF CucsAaaAuthRealmFsmEntry
    MAX-ACCESS       not-accessible
    STATUS           current
    DESCRIPTION
        "Cisco UCS aaa:AuthRealmFsm managed object table"
    ::= { cucsAaaObjects 41 }

cucsAaaAuthRealmFsmEntry OBJECT-TYPE
    SYNTAX           CucsAaaAuthRealmFsmEntry
    MAX-ACCESS       not-accessible
    STATUS           current
    DESCRIPTION
        "Entry for the cucsAaaAuthRealmFsmTable table."
    INDEX { cucsAaaAuthRealmFsmInstanceId }
    ::= { cucsAaaAuthRealmFsmTable 1 }

CucsAaaAuthRealmFsmEntry ::= SEQUENCE {
    cucsAaaAuthRealmFsmInstanceId                                    CucsManagedObjectId,
    cucsAaaAuthRealmFsmDn                                            CucsManagedObjectDn,
    cucsAaaAuthRealmFsmRn                                            SnmpAdminString,
    cucsAaaAuthRealmFsmCompletionTime                                DateAndTime,
    cucsAaaAuthRealmFsmCurrentFsm                                    CucsAaaAuthRealmFsmCurrentFsm,
    cucsAaaAuthRealmFsmDescrData                                     SnmpAdminString,
    cucsAaaAuthRealmFsmFsmStatus                                     CucsFsmFsmStageStatus,
    cucsAaaAuthRealmFsmProgress                                      Gauge32,
    cucsAaaAuthRealmFsmRmtErrCode                                    Gauge32,
    cucsAaaAuthRealmFsmRmtErrDescr                                   SnmpAdminString,
    cucsAaaAuthRealmFsmRmtRslt                                       CucsConditionRemoteInvRslt
}

cucsAaaAuthRealmFsmInstanceId OBJECT-TYPE
    SYNTAX       CucsManagedObjectId
    MAX-ACCESS   not-accessible
    STATUS       current
    DESCRIPTION
        "Instance identifier of the managed object."
    ::= { cucsAaaAuthRealmFsmEntry 1 }

cucsAaaAuthRealmFsmDn OBJECT-TYPE
    SYNTAX       CucsManagedObjectDn
    MAX-ACCESS   read-only
    STATUS       current
    DESCRIPTION
        "Cisco UCS aaa:AuthRealmFsm:dn managed object property"
    ::= { cucsAaaAuthRealmFsmEntry 2 }

cucsAaaAuthRealmFsmRn OBJECT-TYPE
    SYNTAX       SnmpAdminString
    MAX-ACCESS   read-only
    STATUS       current
    DESCRIPTION
        "Cisco UCS aaa:AuthRealmFsm:rn managed object property"
    ::= { cucsAaaAuthRealmFsmEntry 3 }

cucsAaaAuthRealmFsmCompletionTime OBJECT-TYPE
    SYNTAX       DateAndTime
    MAX-ACCESS   read-only
    STATUS       current
    DESCRIPTION
        "Cisco UCS aaa:AuthRealmFsm:completionTime managed
        object property"
    ::= { cucsAaaAuthRealmFsmEntry 4 }

cucsAaaAuthRealmFsmCurrentFsm OBJECT-TYPE
    SYNTAX       CucsAaaAuthRealmFsmCurrentFsm
    MAX-ACCESS   read-only
    STATUS       current
    DESCRIPTION
        "Cisco UCS aaa:AuthRealmFsm:currentFsm managed object property"
    ::= { cucsAaaAuthRealmFsmEntry 5 }

cucsAaaAuthRealmFsmDescrData OBJECT-TYPE
    SYNTAX       SnmpAdminString
    MAX-ACCESS   read-only
    STATUS       current
    DESCRIPTION
        "Cisco UCS aaa:AuthRealmFsm:descr managed object property"
    ::= { cucsAaaAuthRealmFsmEntry 6 }

cucsAaaAuthRealmFsmFsmStatus OBJECT-TYPE
    SYNTAX       CucsFsmFsmStageStatus
    MAX-ACCESS   read-only
    STATUS       current
    DESCRIPTION
        "Cisco UCS aaa:AuthRealmFsm:fsmStatus managed object property"
    ::= { cucsAaaAuthRealmFsmEntry 7 }

cucsAaaAuthRealmFsmProgress OBJECT-TYPE
    SYNTAX       Gauge32
    MAX-ACCESS   read-only
    STATUS       current
    DESCRIPTION
        "Cisco UCS aaa:AuthRealmFsm:progress managed object property"
    ::= { cucsAaaAuthRealmFsmEntry 8 }

cucsAaaAuthRealmFsmRmtErrCode OBJECT-TYPE
    SYNTAX       Gauge32
    MAX-ACCESS   read-only
    STATUS       current
    DESCRIPTION
        "Cisco UCS aaa:AuthRealmFsm:rmtErrCode managed object property"
    ::= { cucsAaaAuthRealmFsmEntry 9 }

cucsAaaAuthRealmFsmRmtErrDescr OBJECT-TYPE
    SYNTAX       SnmpAdminString
    MAX-ACCESS   read-only
    STATUS       current
    DESCRIPTION
        "Cisco UCS aaa:AuthRealmFsm:rmtErrDescr managed object property"
    ::= { cucsAaaAuthRealmFsmEntry 10 }

cucsAaaAuthRealmFsmRmtRslt OBJECT-TYPE
    SYNTAX       CucsConditionRemoteInvRslt
    MAX-ACCESS   read-only
    STATUS       current
    DESCRIPTION
        "Cisco UCS aaa:AuthRealmFsm:rmtRslt managed object property"
    ::= { cucsAaaAuthRealmFsmEntry 11 }

cucsAaaAuthRealmFsmStageTable OBJECT-TYPE
    SYNTAX           SEQUENCE OF CucsAaaAuthRealmFsmStageEntry
    MAX-ACCESS       not-accessible
    STATUS           current
    DESCRIPTION
        "Cisco UCS aaa:AuthRealmFsmStage managed object table"
    ::= { cucsAaaObjects 42 }

cucsAaaAuthRealmFsmStageEntry OBJECT-TYPE
    SYNTAX           CucsAaaAuthRealmFsmStageEntry
    MAX-ACCESS       not-accessible
    STATUS           current
    DESCRIPTION
        "Entry for the cucsAaaAuthRealmFsmStageTable table."
    INDEX { cucsAaaAuthRealmFsmStageInstanceId }
    ::= { cucsAaaAuthRealmFsmStageTable 1 }

CucsAaaAuthRealmFsmStageEntry ::= SEQUENCE {
    cucsAaaAuthRealmFsmStageInstanceId                               CucsManagedObjectId,
    cucsAaaAuthRealmFsmStageDn                                       CucsManagedObjectDn,
    cucsAaaAuthRealmFsmStageRn                                       SnmpAdminString,
    cucsAaaAuthRealmFsmStageDescrData                                SnmpAdminString,
    cucsAaaAuthRealmFsmStageLastUpdateTime                           DateAndTime,
    cucsAaaAuthRealmFsmStageName                                     CucsAaaAuthRealmFsmStageName,
    cucsAaaAuthRealmFsmStageOrder                                    Gauge32,
    cucsAaaAuthRealmFsmStageRetry                                    Gauge32,
    cucsAaaAuthRealmFsmStageStageStatus                              CucsFsmFsmStageStatus
}

cucsAaaAuthRealmFsmStageInstanceId OBJECT-TYPE
    SYNTAX       CucsManagedObjectId
    MAX-ACCESS   not-accessible
    STATUS       current
    DESCRIPTION
        "Instance identifier of the managed object."
    ::= { cucsAaaAuthRealmFsmStageEntry 1 }

cucsAaaAuthRealmFsmStageDn OBJECT-TYPE
    SYNTAX       CucsManagedObjectDn
    MAX-ACCESS   read-only
    STATUS       current
    DESCRIPTION
        "Cisco UCS aaa:AuthRealmFsmStage:dn managed object property"
    ::= { cucsAaaAuthRealmFsmStageEntry 2 }

cucsAaaAuthRealmFsmStageRn OBJECT-TYPE
    SYNTAX       SnmpAdminString
    MAX-ACCESS   read-only
    STATUS       current
    DESCRIPTION
        "Cisco UCS aaa:AuthRealmFsmStage:rn managed object property"
    ::= { cucsAaaAuthRealmFsmStageEntry 3 }

cucsAaaAuthRealmFsmStageDescrData OBJECT-TYPE
    SYNTAX       SnmpAdminString
    MAX-ACCESS   read-only
    STATUS       current
    DESCRIPTION
        "Cisco UCS aaa:AuthRealmFsmStage:descr managed object property"
    ::= { cucsAaaAuthRealmFsmStageEntry 4 }

cucsAaaAuthRealmFsmStageLastUpdateTime OBJECT-TYPE
    SYNTAX       DateAndTime
    MAX-ACCESS   read-only
    STATUS       current
    DESCRIPTION
        "Cisco UCS aaa:AuthRealmFsmStage:lastUpdateTime
        managed object property"
    ::= { cucsAaaAuthRealmFsmStageEntry 5 }

cucsAaaAuthRealmFsmStageName OBJECT-TYPE
    SYNTAX       CucsAaaAuthRealmFsmStageName
    MAX-ACCESS   read-only
    STATUS       current
    DESCRIPTION
        "Cisco UCS aaa:AuthRealmFsmStage:name managed object property"
    ::= { cucsAaaAuthRealmFsmStageEntry 6 }

cucsAaaAuthRealmFsmStageOrder OBJECT-TYPE
    SYNTAX       Gauge32
    MAX-ACCESS   read-only
    STATUS       current
    DESCRIPTION
        "Cisco UCS aaa:AuthRealmFsmStage:order managed object property"
    ::= { cucsAaaAuthRealmFsmStageEntry 7 }

cucsAaaAuthRealmFsmStageRetry OBJECT-TYPE
    SYNTAX       Gauge32
    MAX-ACCESS   read-only
    STATUS       current
    DESCRIPTION
        "Cisco UCS aaa:AuthRealmFsmStage:retry managed object property"
    ::= { cucsAaaAuthRealmFsmStageEntry 8 }

cucsAaaAuthRealmFsmStageStageStatus OBJECT-TYPE
    SYNTAX       CucsFsmFsmStageStatus
    MAX-ACCESS   read-only
    STATUS       current
    DESCRIPTION
        "Cisco UCS aaa:AuthRealmFsmStage:stageStatus managed
        object property"
    ::= { cucsAaaAuthRealmFsmStageEntry 9 }

cucsAaaCimcSessionTable OBJECT-TYPE
    SYNTAX           SEQUENCE OF CucsAaaCimcSessionEntry
    MAX-ACCESS       not-accessible
    STATUS           current
    DESCRIPTION
        "Cisco UCS aaa:CimcSession managed object table"
    ::= { cucsAaaObjects 55 }

cucsAaaCimcSessionEntry OBJECT-TYPE
    SYNTAX           CucsAaaCimcSessionEntry
    MAX-ACCESS       not-accessible
    STATUS           current
    DESCRIPTION
        "Entry for the cucsAaaCimcSessionTable table."
    INDEX { cucsAaaCimcSessionInstanceId }
    ::= { cucsAaaCimcSessionTable 1 }

CucsAaaCimcSessionEntry ::= SEQUENCE {
    cucsAaaCimcSessionInstanceId                                     CucsManagedObjectId,
    cucsAaaCimcSessionDn                                             CucsManagedObjectDn,
    cucsAaaCimcSessionRn                                             SnmpAdminString,
    cucsAaaCimcSessionAdminState                                     CucsAaaSessionState,
    cucsAaaCimcSessionId                                             SnmpAdminString,
    cucsAaaCimcSessionIntDel                                         TruthValue,
    cucsAaaCimcSessionIsDelete                                       CucsAaaClear,
    cucsAaaCimcSessionLastUpdatedTime                                DateAndTime,
    cucsAaaCimcSessionLoginTime                                      DateAndTime,
    cucsAaaCimcSessionLsDn                                           SnmpAdminString,
    cucsAaaCimcSessionPid                                            Gauge32,
    cucsAaaCimcSessionPnDn                                           SnmpAdminString,
    cucsAaaCimcSessionPriv                                           SnmpAdminString,
    cucsAaaCimcSessionSourceAddr                                     SnmpAdminString,
    cucsAaaCimcSessionType                                           CucsAaaCimcSessionType,
    cucsAaaCimcSessionUser                                           SnmpAdminString,
    cucsAaaCimcSessionCimcAddr                                       SnmpAdminString
}

cucsAaaCimcSessionInstanceId OBJECT-TYPE
    SYNTAX       CucsManagedObjectId
    MAX-ACCESS   not-accessible
    STATUS       current
    DESCRIPTION
        "Instance identifier of the managed object."
    ::= { cucsAaaCimcSessionEntry 1 }

cucsAaaCimcSessionDn OBJECT-TYPE
    SYNTAX       CucsManagedObjectDn
    MAX-ACCESS   read-only
    STATUS       current
    DESCRIPTION
        "Cisco UCS aaa:CimcSession:dn managed object property"
    ::= { cucsAaaCimcSessionEntry 2 }

cucsAaaCimcSessionRn OBJECT-TYPE
    SYNTAX       SnmpAdminString
    MAX-ACCESS   read-only
    STATUS       current
    DESCRIPTION
        "Cisco UCS aaa:CimcSession:rn managed object property"
    ::= { cucsAaaCimcSessionEntry 3 }

cucsAaaCimcSessionAdminState OBJECT-TYPE
    SYNTAX       CucsAaaSessionState
    MAX-ACCESS   read-only
    STATUS       current
    DESCRIPTION
        "Cisco UCS aaa:CimcSession:adminState managed object property"
    ::= { cucsAaaCimcSessionEntry 4 }

cucsAaaCimcSessionId OBJECT-TYPE
    SYNTAX       SnmpAdminString
    MAX-ACCESS   read-only
    STATUS       current
    DESCRIPTION
        "Cisco UCS aaa:CimcSession:id managed object property"
    ::= { cucsAaaCimcSessionEntry 5 }

cucsAaaCimcSessionIntDel OBJECT-TYPE
    SYNTAX       TruthValue
    MAX-ACCESS   read-only
    STATUS       current
    DESCRIPTION
        "Cisco UCS aaa:CimcSession:intDel managed object property"
    ::= { cucsAaaCimcSessionEntry 6 }

cucsAaaCimcSessionIsDelete OBJECT-TYPE
    SYNTAX       CucsAaaClear
    MAX-ACCESS   read-only
    STATUS       current
    DESCRIPTION
        "Cisco UCS aaa:CimcSession:isDelete managed object property"
    ::= { cucsAaaCimcSessionEntry 7 }

cucsAaaCimcSessionLastUpdatedTime OBJECT-TYPE
    SYNTAX       DateAndTime
    MAX-ACCESS   read-only
    STATUS       current
    DESCRIPTION
        "Cisco UCS aaa:CimcSession:lastUpdatedTime managed
        object property"
    ::= { cucsAaaCimcSessionEntry 8 }

cucsAaaCimcSessionLoginTime OBJECT-TYPE
    SYNTAX       DateAndTime
    MAX-ACCESS   read-only
    STATUS       current
    DESCRIPTION
        "Cisco UCS aaa:CimcSession:loginTime managed object property"
    ::= { cucsAaaCimcSessionEntry 9 }

cucsAaaCimcSessionLsDn OBJECT-TYPE
    SYNTAX       SnmpAdminString
    MAX-ACCESS   read-only
    STATUS       current
    DESCRIPTION
        "Cisco UCS aaa:CimcSession:lsDn managed object property"
    ::= { cucsAaaCimcSessionEntry 10 }

cucsAaaCimcSessionPid OBJECT-TYPE
    SYNTAX       Gauge32
    MAX-ACCESS   read-only
    STATUS       current
    DESCRIPTION
        "Cisco UCS aaa:CimcSession:pid managed object property"
    ::= { cucsAaaCimcSessionEntry 11 }

cucsAaaCimcSessionPnDn OBJECT-TYPE
    SYNTAX       SnmpAdminString
    MAX-ACCESS   read-only
    STATUS       current
    DESCRIPTION
        "Cisco UCS aaa:CimcSession:pnDn managed object property"
    ::= { cucsAaaCimcSessionEntry 12 }

cucsAaaCimcSessionPriv OBJECT-TYPE
    SYNTAX       SnmpAdminString
    MAX-ACCESS   read-only
    STATUS       current
    DESCRIPTION
        "Cisco UCS aaa:CimcSession:priv managed object property"
    ::= { cucsAaaCimcSessionEntry 13 }

cucsAaaCimcSessionSourceAddr OBJECT-TYPE
    SYNTAX       SnmpAdminString
    MAX-ACCESS   read-only
    STATUS       current
    DESCRIPTION
        "Cisco UCS aaa:CimcSession:sourceAddr managed object property"
    ::= { cucsAaaCimcSessionEntry 14 }

cucsAaaCimcSessionType OBJECT-TYPE
    SYNTAX       CucsAaaCimcSessionType
    MAX-ACCESS   read-only
    STATUS       current
    DESCRIPTION
        "Cisco UCS aaa:CimcSession:type managed object property"
    ::= { cucsAaaCimcSessionEntry 15 }

cucsAaaCimcSessionUser OBJECT-TYPE
    SYNTAX       SnmpAdminString
    MAX-ACCESS   read-only
    STATUS       current
    DESCRIPTION
        "Cisco UCS aaa:CimcSession:user managed object property"
    ::= { cucsAaaCimcSessionEntry 16 }

cucsAaaCimcSessionCimcAddr OBJECT-TYPE
    SYNTAX       SnmpAdminString
    MAX-ACCESS   read-only
    STATUS       current
    DESCRIPTION
        "Cisco UCS aaa:CimcSession:cimcAddr managed object property"
    ::= { cucsAaaCimcSessionEntry 17 }

cucsAaaConsoleAuthTable OBJECT-TYPE
    SYNTAX           SEQUENCE OF CucsAaaConsoleAuthEntry
    MAX-ACCESS       not-accessible
    STATUS           current
    DESCRIPTION
        "Cisco UCS aaa:ConsoleAuth managed object table"
    ::= { cucsAaaObjects 2 }

cucsAaaConsoleAuthEntry OBJECT-TYPE
    SYNTAX           CucsAaaConsoleAuthEntry
    MAX-ACCESS       not-accessible
    STATUS           current
    DESCRIPTION
        "Entry for the cucsAaaConsoleAuthTable table."
    INDEX { cucsAaaConsoleAuthInstanceId }
    ::= { cucsAaaConsoleAuthTable 1 }

CucsAaaConsoleAuthEntry ::= SEQUENCE {
    cucsAaaConsoleAuthInstanceId                                     CucsManagedObjectId,
    cucsAaaConsoleAuthDn                                             CucsManagedObjectDn,
    cucsAaaConsoleAuthRn                                             SnmpAdminString,
    cucsAaaConsoleAuthDescr                                          SnmpAdminString,
    cucsAaaConsoleAuthName                                           SnmpAdminString,
    cucsAaaConsoleAuthProviderGroup                                  SnmpAdminString,
    cucsAaaConsoleAuthRealm                                          CucsAaaRealm,
    cucsAaaConsoleAuthOperProviderGroup                              SnmpAdminString,
    cucsAaaConsoleAuthOperRealm                                      CucsAaaRealm,
    cucsAaaConsoleAuthUse2Factor                                     TruthValue
}

cucsAaaConsoleAuthInstanceId OBJECT-TYPE
    SYNTAX       CucsManagedObjectId
    MAX-ACCESS   not-accessible
    STATUS       current
    DESCRIPTION
        "Instance identifier of the managed object."
    ::= { cucsAaaConsoleAuthEntry 1 }

cucsAaaConsoleAuthDn OBJECT-TYPE
    SYNTAX       CucsManagedObjectDn
    MAX-ACCESS   read-only
    STATUS       current
    DESCRIPTION
        "Cisco UCS aaa:ConsoleAuth:dn managed object property"
    ::= { cucsAaaConsoleAuthEntry 2 }

cucsAaaConsoleAuthRn OBJECT-TYPE
    SYNTAX       SnmpAdminString
    MAX-ACCESS   read-only
    STATUS       current
    DESCRIPTION
        "Cisco UCS aaa:ConsoleAuth:rn managed object property"
    ::= { cucsAaaConsoleAuthEntry 3 }

cucsAaaConsoleAuthDescr OBJECT-TYPE
    SYNTAX       SnmpAdminString
    MAX-ACCESS   read-only
    STATUS       current
    DESCRIPTION
        "Cisco UCS aaa:ConsoleAuth:descr managed object property"
    ::= { cucsAaaConsoleAuthEntry 4 }

cucsAaaConsoleAuthName OBJECT-TYPE
    SYNTAX       SnmpAdminString
    MAX-ACCESS   read-only
    STATUS       current
    DESCRIPTION
        "Cisco UCS aaa:ConsoleAuth:name managed object property"
    ::= { cucsAaaConsoleAuthEntry 6 }

cucsAaaConsoleAuthProviderGroup OBJECT-TYPE
    SYNTAX       SnmpAdminString
    MAX-ACCESS   read-only
    STATUS       current
    DESCRIPTION
        "Cisco UCS aaa:ConsoleAuth:providerGroup managed object property"
    ::= { cucsAaaConsoleAuthEntry 7 }

cucsAaaConsoleAuthRealm OBJECT-TYPE
    SYNTAX       CucsAaaRealm
    MAX-ACCESS   read-only
    STATUS       current
    DESCRIPTION
        "Cisco UCS aaa:ConsoleAuth:realm managed object property"
    ::= { cucsAaaConsoleAuthEntry 8 }

cucsAaaConsoleAuthOperProviderGroup OBJECT-TYPE
    SYNTAX       SnmpAdminString
    MAX-ACCESS   read-only
    STATUS       current
    DESCRIPTION
        "Cisco UCS aaa:ConsoleAuth:operProviderGroup managed
        object property"
    ::= { cucsAaaConsoleAuthEntry 9 }

cucsAaaConsoleAuthOperRealm OBJECT-TYPE
    SYNTAX       CucsAaaRealm
    MAX-ACCESS   read-only
    STATUS       current
    DESCRIPTION
        "Cisco UCS aaa:ConsoleAuth:operRealm managed object property"
    ::= { cucsAaaConsoleAuthEntry 10 }

cucsAaaConsoleAuthUse2Factor OBJECT-TYPE
    SYNTAX       TruthValue
    MAX-ACCESS   read-only
    STATUS       current
    DESCRIPTION
        "Cisco UCS aaa:ConsoleAuth:use2Factor managed object property"
    ::= { cucsAaaConsoleAuthEntry 11 }

cucsAaaDefaultAuthTable OBJECT-TYPE
    SYNTAX           SEQUENCE OF CucsAaaDefaultAuthEntry
    MAX-ACCESS       not-accessible
    STATUS           current
    DESCRIPTION
        "Cisco UCS aaa:DefaultAuth managed object table"
    ::= { cucsAaaObjects 3 }

cucsAaaDefaultAuthEntry OBJECT-TYPE
    SYNTAX           CucsAaaDefaultAuthEntry
    MAX-ACCESS       not-accessible
    STATUS           current
    DESCRIPTION
        "Entry for the cucsAaaDefaultAuthTable table."
    INDEX { cucsAaaDefaultAuthInstanceId }
    ::= { cucsAaaDefaultAuthTable 1 }

CucsAaaDefaultAuthEntry ::= SEQUENCE {
    cucsAaaDefaultAuthInstanceId                                     CucsManagedObjectId,
    cucsAaaDefaultAuthDn                                             CucsManagedObjectDn,
    cucsAaaDefaultAuthRn                                             SnmpAdminString,
    cucsAaaDefaultAuthDescr                                          SnmpAdminString,
    cucsAaaDefaultAuthName                                           SnmpAdminString,
    cucsAaaDefaultAuthProviderGroup                                  SnmpAdminString,
    cucsAaaDefaultAuthRealm                                          CucsAaaRealm,
    cucsAaaDefaultAuthRefreshPeriod                                  Gauge32,
    cucsAaaDefaultAuthSessionTimeout                                 Gauge32,
    cucsAaaDefaultAuthOperProviderGroup                              SnmpAdminString,
    cucsAaaDefaultAuthOperRealm                                      CucsAaaRealm,
    cucsAaaDefaultAuthUse2Factor                                     TruthValue,
    cucsAaaDefaultAuthConfigState                                    CucsAaaConfigState,
    cucsAaaDefaultAuthConfigStatusMessage                            SnmpAdminString
}

cucsAaaDefaultAuthInstanceId OBJECT-TYPE
    SYNTAX       CucsManagedObjectId
    MAX-ACCESS   not-accessible
    STATUS       current
    DESCRIPTION
        "Instance identifier of the managed object."
    ::= { cucsAaaDefaultAuthEntry 1 }

cucsAaaDefaultAuthDn OBJECT-TYPE
    SYNTAX       CucsManagedObjectDn
    MAX-ACCESS   read-only
    STATUS       current
    DESCRIPTION
        "Cisco UCS aaa:DefaultAuth:dn managed object property"
    ::= { cucsAaaDefaultAuthEntry 2 }

cucsAaaDefaultAuthRn OBJECT-TYPE
    SYNTAX       SnmpAdminString
    MAX-ACCESS   read-only
    STATUS       current
    DESCRIPTION
        "Cisco UCS aaa:DefaultAuth:rn managed object property"
    ::= { cucsAaaDefaultAuthEntry 3 }

cucsAaaDefaultAuthDescr OBJECT-TYPE
    SYNTAX       SnmpAdminString
    MAX-ACCESS   read-only
    STATUS       current
    DESCRIPTION
        "Cisco UCS aaa:DefaultAuth:descr managed object property"
    ::= { cucsAaaDefaultAuthEntry 4 }

cucsAaaDefaultAuthName OBJECT-TYPE
    SYNTAX       SnmpAdminString
    MAX-ACCESS   read-only
    STATUS       current
    DESCRIPTION
        "Cisco UCS aaa:DefaultAuth:name managed object property"
    ::= { cucsAaaDefaultAuthEntry 6 }

cucsAaaDefaultAuthProviderGroup OBJECT-TYPE
    SYNTAX       SnmpAdminString
    MAX-ACCESS   read-only
    STATUS       current
    DESCRIPTION
        "Cisco UCS aaa:DefaultAuth:providerGroup managed object property"
    ::= { cucsAaaDefaultAuthEntry 7 }

cucsAaaDefaultAuthRealm OBJECT-TYPE
    SYNTAX       CucsAaaRealm
    MAX-ACCESS   read-only
    STATUS       current
    DESCRIPTION
        "Cisco UCS aaa:DefaultAuth:realm managed object property"
    ::= { cucsAaaDefaultAuthEntry 8 }

cucsAaaDefaultAuthRefreshPeriod OBJECT-TYPE
    SYNTAX       Gauge32
    MAX-ACCESS   read-only
    STATUS       current
    DESCRIPTION
        "Cisco UCS aaa:DefaultAuth:refreshPeriod managed object property"
    ::= { cucsAaaDefaultAuthEntry 9 }

cucsAaaDefaultAuthSessionTimeout OBJECT-TYPE
    SYNTAX       Gauge32
    MAX-ACCESS   read-only
    STATUS       current
    DESCRIPTION
        "Cisco UCS aaa:DefaultAuth:sessionTimeout managed object property"
    ::= { cucsAaaDefaultAuthEntry 10 }

cucsAaaDefaultAuthOperProviderGroup OBJECT-TYPE
    SYNTAX       SnmpAdminString
    MAX-ACCESS   read-only
    STATUS       current
    DESCRIPTION
        "Cisco UCS aaa:DefaultAuth:operProviderGroup managed
        object property"
    ::= { cucsAaaDefaultAuthEntry 11 }

cucsAaaDefaultAuthOperRealm OBJECT-TYPE
    SYNTAX       CucsAaaRealm
    MAX-ACCESS   read-only
    STATUS       current
    DESCRIPTION
        "Cisco UCS aaa:DefaultAuth:operRealm managed object property"
    ::= { cucsAaaDefaultAuthEntry 12 }

cucsAaaDefaultAuthUse2Factor OBJECT-TYPE
    SYNTAX       TruthValue
    MAX-ACCESS   read-only
    STATUS       current
    DESCRIPTION
        "Cisco UCS aaa:DefaultAuth:use2Factor managed object property"
    ::= { cucsAaaDefaultAuthEntry 13 }

cucsAaaDefaultAuthConfigState OBJECT-TYPE
    SYNTAX       CucsAaaConfigState
    MAX-ACCESS   read-only
    STATUS       current
    DESCRIPTION
        "Cisco UCS aaa:DefaultAuth:configState managed object property"
    ::= { cucsAaaDefaultAuthEntry 14 }

cucsAaaDefaultAuthConfigStatusMessage OBJECT-TYPE
    SYNTAX       SnmpAdminString
    MAX-ACCESS   read-only
    STATUS       current
    DESCRIPTION
        "Cisco UCS aaa:DefaultAuth:configStatusMessage
        managed object property"
    ::= { cucsAaaDefaultAuthEntry 15 }

cucsAaaDomainTable OBJECT-TYPE
    SYNTAX           SEQUENCE OF CucsAaaDomainEntry
    MAX-ACCESS       not-accessible
    STATUS           current
    DESCRIPTION
        "Cisco UCS aaa:Domain managed object table"
    ::= { cucsAaaObjects 4 }

cucsAaaDomainEntry OBJECT-TYPE
    SYNTAX           CucsAaaDomainEntry
    MAX-ACCESS       not-accessible
    STATUS           current
    DESCRIPTION
        "Entry for the cucsAaaDomainTable table."
    INDEX { cucsAaaDomainInstanceId }
    ::= { cucsAaaDomainTable 1 }

CucsAaaDomainEntry ::= SEQUENCE {
    cucsAaaDomainInstanceId                                          CucsManagedObjectId,
    cucsAaaDomainDn                                                  CucsManagedObjectDn,
    cucsAaaDomainRn                                                  SnmpAdminString,
    cucsAaaDomainDescr                                               SnmpAdminString,
    cucsAaaDomainName                                                SnmpAdminString,
    cucsAaaDomainRefreshPeriod                                       Gauge32,
    cucsAaaDomainSessionTimeout                                      Gauge32,
    cucsAaaDomainConfigState                                         CucsAaaConfigState,
    cucsAaaDomainConfigStatusMessage                                 SnmpAdminString
}

cucsAaaDomainInstanceId OBJECT-TYPE
    SYNTAX       CucsManagedObjectId
    MAX-ACCESS   not-accessible
    STATUS       current
    DESCRIPTION
        "Instance identifier of the managed object."
    ::= { cucsAaaDomainEntry 1 }

cucsAaaDomainDn OBJECT-TYPE
    SYNTAX       CucsManagedObjectDn
    MAX-ACCESS   read-only
    STATUS       current
    DESCRIPTION
        "Cisco UCS aaa:Domain:dn managed object property"
    ::= { cucsAaaDomainEntry 2 }

cucsAaaDomainRn OBJECT-TYPE
    SYNTAX       SnmpAdminString
    MAX-ACCESS   read-only
    STATUS       current
    DESCRIPTION
        "Cisco UCS aaa:Domain:rn managed object property"
    ::= { cucsAaaDomainEntry 3 }

cucsAaaDomainDescr OBJECT-TYPE
    SYNTAX       SnmpAdminString
    MAX-ACCESS   read-only
    STATUS       current
    DESCRIPTION
        "Cisco UCS aaa:Domain:descr managed object property"
    ::= { cucsAaaDomainEntry 4 }

cucsAaaDomainName OBJECT-TYPE
    SYNTAX       SnmpAdminString
    MAX-ACCESS   read-only
    STATUS       current
    DESCRIPTION
        "Cisco UCS aaa:Domain:name managed object property"
    ::= { cucsAaaDomainEntry 6 }

cucsAaaDomainRefreshPeriod OBJECT-TYPE
    SYNTAX       Gauge32
    MAX-ACCESS   read-only
    STATUS       current
    DESCRIPTION
        "Cisco UCS aaa:Domain:refreshPeriod managed object property"
    ::= { cucsAaaDomainEntry 7 }

cucsAaaDomainSessionTimeout OBJECT-TYPE
    SYNTAX       Gauge32
    MAX-ACCESS   read-only
    STATUS       current
    DESCRIPTION
        "Cisco UCS aaa:Domain:sessionTimeout managed object property"
    ::= { cucsAaaDomainEntry 8 }

cucsAaaDomainConfigState OBJECT-TYPE
    SYNTAX       CucsAaaConfigState
    MAX-ACCESS   read-only
    STATUS       current
    DESCRIPTION
        "Cisco UCS aaa:Domain:configState managed object property"
    ::= { cucsAaaDomainEntry 9 }

cucsAaaDomainConfigStatusMessage OBJECT-TYPE
    SYNTAX       SnmpAdminString
    MAX-ACCESS   read-only
    STATUS       current
    DESCRIPTION
        "Cisco UCS aaa:Domain:configStatusMessage managed object property"
    ::= { cucsAaaDomainEntry 10 }

cucsAaaDomainAuthTable OBJECT-TYPE
    SYNTAX           SEQUENCE OF CucsAaaDomainAuthEntry
    MAX-ACCESS       not-accessible
    STATUS           current
    DESCRIPTION
        "Cisco UCS aaa:DomainAuth managed object table"
    ::= { cucsAaaObjects 5 }

cucsAaaDomainAuthEntry OBJECT-TYPE
    SYNTAX           CucsAaaDomainAuthEntry
    MAX-ACCESS       not-accessible
    STATUS           current
    DESCRIPTION
        "Entry for the cucsAaaDomainAuthTable table."
    INDEX { cucsAaaDomainAuthInstanceId }
    ::= { cucsAaaDomainAuthTable 1 }

CucsAaaDomainAuthEntry ::= SEQUENCE {
    cucsAaaDomainAuthInstanceId                                      CucsManagedObjectId,
    cucsAaaDomainAuthDn                                              CucsManagedObjectDn,
    cucsAaaDomainAuthRn                                              SnmpAdminString,
    cucsAaaDomainAuthDescr                                           SnmpAdminString,
    cucsAaaDomainAuthName                                            SnmpAdminString,
    cucsAaaDomainAuthProviderGroup                                   SnmpAdminString,
    cucsAaaDomainAuthRealm                                           CucsAaaDomainAuthRealm,
    cucsAaaDomainAuthOperProviderGroup                               SnmpAdminString,
    cucsAaaDomainAuthOperRealm                                       CucsAaaRealm,
    cucsAaaDomainAuthUse2Factor                                      TruthValue
}

cucsAaaDomainAuthInstanceId OBJECT-TYPE
    SYNTAX       CucsManagedObjectId
    MAX-ACCESS   not-accessible
    STATUS       current
    DESCRIPTION
        "Instance identifier of the managed object."
    ::= { cucsAaaDomainAuthEntry 1 }

cucsAaaDomainAuthDn OBJECT-TYPE
    SYNTAX       CucsManagedObjectDn
    MAX-ACCESS   read-only
    STATUS       current
    DESCRIPTION
        "Cisco UCS aaa:DomainAuth:dn managed object property"
    ::= { cucsAaaDomainAuthEntry 2 }

cucsAaaDomainAuthRn OBJECT-TYPE
    SYNTAX       SnmpAdminString
    MAX-ACCESS   read-only
    STATUS       current
    DESCRIPTION
        "Cisco UCS aaa:DomainAuth:rn managed object property"
    ::= { cucsAaaDomainAuthEntry 3 }

cucsAaaDomainAuthDescr OBJECT-TYPE
    SYNTAX       SnmpAdminString
    MAX-ACCESS   read-only
    STATUS       current
    DESCRIPTION
        "Cisco UCS aaa:DomainAuth:descr managed object property"
    ::= { cucsAaaDomainAuthEntry 4 }

cucsAaaDomainAuthName OBJECT-TYPE
    SYNTAX       SnmpAdminString
    MAX-ACCESS   read-only
    STATUS       current
    DESCRIPTION
        "Cisco UCS aaa:DomainAuth:name managed object property"
    ::= { cucsAaaDomainAuthEntry 6 }

cucsAaaDomainAuthProviderGroup OBJECT-TYPE
    SYNTAX       SnmpAdminString
    MAX-ACCESS   read-only
    STATUS       current
    DESCRIPTION
        "Cisco UCS aaa:DomainAuth:providerGroup managed object property"
    ::= { cucsAaaDomainAuthEntry 7 }

cucsAaaDomainAuthRealm OBJECT-TYPE
    SYNTAX       CucsAaaDomainAuthRealm
    MAX-ACCESS   read-only
    STATUS       current
    DESCRIPTION
        "Cisco UCS aaa:DomainAuth:realm managed object property"
    ::= { cucsAaaDomainAuthEntry 8 }

cucsAaaDomainAuthOperProviderGroup OBJECT-TYPE
    SYNTAX       SnmpAdminString
    MAX-ACCESS   read-only
    STATUS       current
    DESCRIPTION
        "Cisco UCS aaa:DomainAuth:operProviderGroup managed
        object property"
    ::= { cucsAaaDomainAuthEntry 9 }

cucsAaaDomainAuthOperRealm OBJECT-TYPE
    SYNTAX       CucsAaaRealm
    MAX-ACCESS   read-only
    STATUS       current
    DESCRIPTION
        "Cisco UCS aaa:DomainAuth:operRealm managed object property"
    ::= { cucsAaaDomainAuthEntry 10 }

cucsAaaDomainAuthUse2Factor OBJECT-TYPE
    SYNTAX       TruthValue
    MAX-ACCESS   read-only
    STATUS       current
    DESCRIPTION
        "Cisco UCS aaa:DomainAuth:use2Factor managed object property"
    ::= { cucsAaaDomainAuthEntry 11 }

cucsAaaEpAuthProfileTable OBJECT-TYPE
    SYNTAX           SEQUENCE OF CucsAaaEpAuthProfileEntry
    MAX-ACCESS       not-accessible
    STATUS           current
    DESCRIPTION
        "Cisco UCS aaa:EpAuthProfile managed object table"
    ::= { cucsAaaObjects 6 }

cucsAaaEpAuthProfileEntry OBJECT-TYPE
    SYNTAX           CucsAaaEpAuthProfileEntry
    MAX-ACCESS       not-accessible
    STATUS           current
    DESCRIPTION
        "Entry for the cucsAaaEpAuthProfileTable table."
    INDEX { cucsAaaEpAuthProfileInstanceId }
    ::= { cucsAaaEpAuthProfileTable 1 }

CucsAaaEpAuthProfileEntry ::= SEQUENCE {
    cucsAaaEpAuthProfileInstanceId                                   CucsManagedObjectId,
    cucsAaaEpAuthProfileDn                                           CucsManagedObjectDn,
    cucsAaaEpAuthProfileRn                                           SnmpAdminString,
    cucsAaaEpAuthProfileDescr                                        SnmpAdminString,
    cucsAaaEpAuthProfileIntId                                        SnmpAdminString,
    cucsAaaEpAuthProfileName                                         SnmpAdminString,
    cucsAaaEpAuthProfilePolicyLevel                                  Gauge32,
    cucsAaaEpAuthProfilePolicyOwner                                  CucsPolicyPolicyOwner,
    cucsAaaEpAuthProfileIpmiOverLan                                  CucsAaaIpmiOverLan
}

cucsAaaEpAuthProfileInstanceId OBJECT-TYPE
    SYNTAX       CucsManagedObjectId
    MAX-ACCESS   not-accessible
    STATUS       current
    DESCRIPTION
        "Instance identifier of the managed object."
    ::= { cucsAaaEpAuthProfileEntry 1 }

cucsAaaEpAuthProfileDn OBJECT-TYPE
    SYNTAX       CucsManagedObjectDn
    MAX-ACCESS   read-only
    STATUS       current
    DESCRIPTION
        "Cisco UCS aaa:EpAuthProfile:dn managed object property"
    ::= { cucsAaaEpAuthProfileEntry 2 }

cucsAaaEpAuthProfileRn OBJECT-TYPE
    SYNTAX       SnmpAdminString
    MAX-ACCESS   read-only
    STATUS       current
    DESCRIPTION
        "Cisco UCS aaa:EpAuthProfile:rn managed object property"
    ::= { cucsAaaEpAuthProfileEntry 3 }

cucsAaaEpAuthProfileDescr OBJECT-TYPE
    SYNTAX       SnmpAdminString
    MAX-ACCESS   read-only
    STATUS       current
    DESCRIPTION
        "Cisco UCS aaa:EpAuthProfile:descr managed object property"
    ::= { cucsAaaEpAuthProfileEntry 4 }

cucsAaaEpAuthProfileIntId OBJECT-TYPE
    SYNTAX       SnmpAdminString
    MAX-ACCESS   read-only
    STATUS       current
    DESCRIPTION
        "Cisco UCS aaa:EpAuthProfile:intId managed object property"
    ::= { cucsAaaEpAuthProfileEntry 5 }

cucsAaaEpAuthProfileName OBJECT-TYPE
    SYNTAX       SnmpAdminString
    MAX-ACCESS   read-only
    STATUS       current
    DESCRIPTION
        "Cisco UCS aaa:EpAuthProfile:name managed object property"
    ::= { cucsAaaEpAuthProfileEntry 6 }

cucsAaaEpAuthProfilePolicyLevel OBJECT-TYPE
    SYNTAX       Gauge32
    MAX-ACCESS   read-only
    STATUS       current
    DESCRIPTION
        "Cisco UCS aaa:EpAuthProfile:policyLevel managed object property"
    ::= { cucsAaaEpAuthProfileEntry 7 }

cucsAaaEpAuthProfilePolicyOwner OBJECT-TYPE
    SYNTAX       CucsPolicyPolicyOwner
    MAX-ACCESS   read-only
    STATUS       current
    DESCRIPTION
        "Cisco UCS aaa:EpAuthProfile:policyOwner managed object property"
    ::= { cucsAaaEpAuthProfileEntry 8 }

cucsAaaEpAuthProfileIpmiOverLan OBJECT-TYPE
    SYNTAX       CucsAaaIpmiOverLan
    MAX-ACCESS   read-only
    STATUS       current
    DESCRIPTION
        "Cisco UCS aaa:EpAuthProfile:ipmiOverLan managed object property"
    ::= { cucsAaaEpAuthProfileEntry 9 }

cucsAaaEpFsmTable OBJECT-TYPE
    SYNTAX           SEQUENCE OF CucsAaaEpFsmEntry
    MAX-ACCESS       not-accessible
    STATUS           current
    DESCRIPTION
        "Cisco UCS aaa:EpFsm managed object table"
    ::= { cucsAaaObjects 43 }

cucsAaaEpFsmEntry OBJECT-TYPE
    SYNTAX           CucsAaaEpFsmEntry
    MAX-ACCESS       not-accessible
    STATUS           current
    DESCRIPTION
        "Entry for the cucsAaaEpFsmTable table."
    INDEX { cucsAaaEpFsmInstanceId }
    ::= { cucsAaaEpFsmTable 1 }

CucsAaaEpFsmEntry ::= SEQUENCE {
    cucsAaaEpFsmInstanceId                                           CucsManagedObjectId,
    cucsAaaEpFsmDn                                                   CucsManagedObjectDn,
    cucsAaaEpFsmRn                                                   SnmpAdminString,
    cucsAaaEpFsmCompletionTime                                       DateAndTime,
    cucsAaaEpFsmCurrentFsm                                           CucsAaaEpFsmCurrentFsm,
    cucsAaaEpFsmDescr                                                SnmpAdminString,
    cucsAaaEpFsmFsmStatus                                            CucsFsmFsmStageStatus,
    cucsAaaEpFsmProgress                                             Gauge32,
    cucsAaaEpFsmRmtErrCode                                           Gauge32,
    cucsAaaEpFsmRmtErrDescr                                          SnmpAdminString,
    cucsAaaEpFsmRmtRslt                                              CucsConditionRemoteInvRslt
}

cucsAaaEpFsmInstanceId OBJECT-TYPE
    SYNTAX       CucsManagedObjectId
    MAX-ACCESS   not-accessible
    STATUS       current
    DESCRIPTION
        "Instance identifier of the managed object."
    ::= { cucsAaaEpFsmEntry 1 }

cucsAaaEpFsmDn OBJECT-TYPE
    SYNTAX       CucsManagedObjectDn
    MAX-ACCESS   read-only
    STATUS       current
    DESCRIPTION
        "Cisco UCS aaa:EpFsm:dn managed object property"
    ::= { cucsAaaEpFsmEntry 2 }

cucsAaaEpFsmRn OBJECT-TYPE
    SYNTAX       SnmpAdminString
    MAX-ACCESS   read-only
    STATUS       current
    DESCRIPTION
        "Cisco UCS aaa:EpFsm:rn managed object property"
    ::= { cucsAaaEpFsmEntry 3 }

cucsAaaEpFsmCompletionTime OBJECT-TYPE
    SYNTAX       DateAndTime
    MAX-ACCESS   read-only
    STATUS       current
    DESCRIPTION
        "Cisco UCS aaa:EpFsm:completionTime managed object property"
    ::= { cucsAaaEpFsmEntry 4 }

cucsAaaEpFsmCurrentFsm OBJECT-TYPE
    SYNTAX       CucsAaaEpFsmCurrentFsm
    MAX-ACCESS   read-only
    STATUS       current
    DESCRIPTION
        "Cisco UCS aaa:EpFsm:currentFsm managed object property"
    ::= { cucsAaaEpFsmEntry 5 }

cucsAaaEpFsmDescr OBJECT-TYPE
    SYNTAX       SnmpAdminString
    MAX-ACCESS   read-only
    STATUS       current
    DESCRIPTION
        "Cisco UCS aaa:EpFsm:descr managed object property"
    ::= { cucsAaaEpFsmEntry 6 }

cucsAaaEpFsmFsmStatus OBJECT-TYPE
    SYNTAX       CucsFsmFsmStageStatus
    MAX-ACCESS   read-only
    STATUS       current
    DESCRIPTION
        "Cisco UCS aaa:EpFsm:fsmStatus managed object property"
    ::= { cucsAaaEpFsmEntry 7 }

cucsAaaEpFsmProgress OBJECT-TYPE
    SYNTAX       Gauge32
    MAX-ACCESS   read-only
    STATUS       current
    DESCRIPTION
        "Cisco UCS aaa:EpFsm:progress managed object property"
    ::= { cucsAaaEpFsmEntry 8 }

cucsAaaEpFsmRmtErrCode OBJECT-TYPE
    SYNTAX       Gauge32
    MAX-ACCESS   read-only
    STATUS       current
    DESCRIPTION
        "Cisco UCS aaa:EpFsm:rmtErrCode managed object property"
    ::= { cucsAaaEpFsmEntry 9 }

cucsAaaEpFsmRmtErrDescr OBJECT-TYPE
    SYNTAX       SnmpAdminString
    MAX-ACCESS   read-only
    STATUS       current
    DESCRIPTION
        "Cisco UCS aaa:EpFsm:rmtErrDescr managed object property"
    ::= { cucsAaaEpFsmEntry 10 }

cucsAaaEpFsmRmtRslt OBJECT-TYPE
    SYNTAX       CucsConditionRemoteInvRslt
    MAX-ACCESS   read-only
    STATUS       current
    DESCRIPTION
        "Cisco UCS aaa:EpFsm:rmtRslt managed object property"
    ::= { cucsAaaEpFsmEntry 11 }

cucsAaaEpFsmStageTable OBJECT-TYPE
    SYNTAX           SEQUENCE OF CucsAaaEpFsmStageEntry
    MAX-ACCESS       not-accessible
    STATUS           current
    DESCRIPTION
        "Cisco UCS aaa:EpFsmStage managed object table"
    ::= { cucsAaaObjects 44 }

cucsAaaEpFsmStageEntry OBJECT-TYPE
    SYNTAX           CucsAaaEpFsmStageEntry
    MAX-ACCESS       not-accessible
    STATUS           current
    DESCRIPTION
        "Entry for the cucsAaaEpFsmStageTable table."
    INDEX { cucsAaaEpFsmStageInstanceId }
    ::= { cucsAaaEpFsmStageTable 1 }

CucsAaaEpFsmStageEntry ::= SEQUENCE {
    cucsAaaEpFsmStageInstanceId                                      CucsManagedObjectId,
    cucsAaaEpFsmStageDn                                              CucsManagedObjectDn,
    cucsAaaEpFsmStageRn                                              SnmpAdminString,
    cucsAaaEpFsmStageDescr                                           SnmpAdminString,
    cucsAaaEpFsmStageLastUpdateTime                                  DateAndTime,
    cucsAaaEpFsmStageName                                            CucsAaaEpFsmStageName,
    cucsAaaEpFsmStageOrder                                           Gauge32,
    cucsAaaEpFsmStageRetry                                           Gauge32,
    cucsAaaEpFsmStageStageStatus                                     CucsFsmFsmStageStatus
}

cucsAaaEpFsmStageInstanceId OBJECT-TYPE
    SYNTAX       CucsManagedObjectId
    MAX-ACCESS   not-accessible
    STATUS       current
    DESCRIPTION
        "Instance identifier of the managed object."
    ::= { cucsAaaEpFsmStageEntry 1 }

cucsAaaEpFsmStageDn OBJECT-TYPE
    SYNTAX       CucsManagedObjectDn
    MAX-ACCESS   read-only
    STATUS       current
    DESCRIPTION
        "Cisco UCS aaa:EpFsmStage:dn managed object property"
    ::= { cucsAaaEpFsmStageEntry 2 }

cucsAaaEpFsmStageRn OBJECT-TYPE
    SYNTAX       SnmpAdminString
    MAX-ACCESS   read-only
    STATUS       current
    DESCRIPTION
        "Cisco UCS aaa:EpFsmStage:rn managed object property"
    ::= { cucsAaaEpFsmStageEntry 3 }

cucsAaaEpFsmStageDescr OBJECT-TYPE
    SYNTAX       SnmpAdminString
    MAX-ACCESS   read-only
    STATUS       current
    DESCRIPTION
        "Cisco UCS aaa:EpFsmStage:descr managed object property"
    ::= { cucsAaaEpFsmStageEntry 4 }

cucsAaaEpFsmStageLastUpdateTime OBJECT-TYPE
    SYNTAX       DateAndTime
    MAX-ACCESS   read-only
    STATUS       current
    DESCRIPTION
        "Cisco UCS aaa:EpFsmStage:lastUpdateTime managed object property"
    ::= { cucsAaaEpFsmStageEntry 5 }

cucsAaaEpFsmStageName OBJECT-TYPE
    SYNTAX       CucsAaaEpFsmStageName
    MAX-ACCESS   read-only
    STATUS       current
    DESCRIPTION
        "Cisco UCS aaa:EpFsmStage:name managed object property"
    ::= { cucsAaaEpFsmStageEntry 6 }

cucsAaaEpFsmStageOrder OBJECT-TYPE
    SYNTAX       Gauge32
    MAX-ACCESS   read-only
    STATUS       current
    DESCRIPTION
        "Cisco UCS aaa:EpFsmStage:order managed object property"
    ::= { cucsAaaEpFsmStageEntry 7 }

cucsAaaEpFsmStageRetry OBJECT-TYPE
    SYNTAX       Gauge32
    MAX-ACCESS   read-only
    STATUS       current
    DESCRIPTION
        "Cisco UCS aaa:EpFsmStage:retry managed object property"
    ::= { cucsAaaEpFsmStageEntry 8 }

cucsAaaEpFsmStageStageStatus OBJECT-TYPE
    SYNTAX       CucsFsmFsmStageStatus
    MAX-ACCESS   read-only
    STATUS       current
    DESCRIPTION
        "Cisco UCS aaa:EpFsmStage:stageStatus managed object property"
    ::= { cucsAaaEpFsmStageEntry 9 }

cucsAaaEpFsmTaskTable OBJECT-TYPE
    SYNTAX           SEQUENCE OF CucsAaaEpFsmTaskEntry
    MAX-ACCESS       not-accessible
    STATUS           current
    DESCRIPTION
        "Cisco UCS aaa:EpFsmTask managed object table"
    ::= { cucsAaaObjects 7 }

cucsAaaEpFsmTaskEntry OBJECT-TYPE
    SYNTAX           CucsAaaEpFsmTaskEntry
    MAX-ACCESS       not-accessible
    STATUS           current
    DESCRIPTION
        "Entry for the cucsAaaEpFsmTaskTable table."
    INDEX { cucsAaaEpFsmTaskInstanceId }
    ::= { cucsAaaEpFsmTaskTable 1 }

CucsAaaEpFsmTaskEntry ::= SEQUENCE {
    cucsAaaEpFsmTaskInstanceId                                       CucsManagedObjectId,
    cucsAaaEpFsmTaskDn                                               CucsManagedObjectDn,
    cucsAaaEpFsmTaskRn                                               SnmpAdminString,
    cucsAaaEpFsmTaskCompletion                                       CucsFsmCompletion,
    cucsAaaEpFsmTaskFlags                                            CucsFsmFlags,
    cucsAaaEpFsmTaskItem                                             CucsAaaEpFsmTaskItem,
    cucsAaaEpFsmTaskSeqId                                            Gauge32
}

cucsAaaEpFsmTaskInstanceId OBJECT-TYPE
    SYNTAX       CucsManagedObjectId
    MAX-ACCESS   not-accessible
    STATUS       current
    DESCRIPTION
        "Instance identifier of the managed object."
    ::= { cucsAaaEpFsmTaskEntry 1 }

cucsAaaEpFsmTaskDn OBJECT-TYPE
    SYNTAX       CucsManagedObjectDn
    MAX-ACCESS   read-only
    STATUS       current
    DESCRIPTION
        "Cisco UCS aaa:EpFsmTask:dn managed object property"
    ::= { cucsAaaEpFsmTaskEntry 2 }

cucsAaaEpFsmTaskRn OBJECT-TYPE
    SYNTAX       SnmpAdminString
    MAX-ACCESS   read-only
    STATUS       current
    DESCRIPTION
        "Cisco UCS aaa:EpFsmTask:rn managed object property"
    ::= { cucsAaaEpFsmTaskEntry 3 }

cucsAaaEpFsmTaskCompletion OBJECT-TYPE
    SYNTAX       CucsFsmCompletion
    MAX-ACCESS   read-only
    STATUS       current
    DESCRIPTION
        "Cisco UCS aaa:EpFsmTask:completion managed object property"
    ::= { cucsAaaEpFsmTaskEntry 4 }

cucsAaaEpFsmTaskFlags OBJECT-TYPE
    SYNTAX       CucsFsmFlags
    MAX-ACCESS   read-only
    STATUS       current
    DESCRIPTION
        "Cisco UCS aaa:EpFsmTask:flags managed object property"
    ::= { cucsAaaEpFsmTaskEntry 5 }

cucsAaaEpFsmTaskItem OBJECT-TYPE
    SYNTAX       CucsAaaEpFsmTaskItem
    MAX-ACCESS   read-only
    STATUS       current
    DESCRIPTION
        "Cisco UCS aaa:EpFsmTask:item managed object property"
    ::= { cucsAaaEpFsmTaskEntry 6 }

cucsAaaEpFsmTaskSeqId OBJECT-TYPE
    SYNTAX       Gauge32
    MAX-ACCESS   read-only
    STATUS       current
    DESCRIPTION
        "Cisco UCS aaa:EpFsmTask:seqId managed object property"
    ::= { cucsAaaEpFsmTaskEntry 7 }

cucsAaaEpLoginTable OBJECT-TYPE
    SYNTAX           SEQUENCE OF CucsAaaEpLoginEntry
    MAX-ACCESS       not-accessible
    STATUS           current
    DESCRIPTION
        "Cisco UCS aaa:EpLogin managed object table"
    ::= { cucsAaaObjects 8 }

cucsAaaEpLoginEntry OBJECT-TYPE
    SYNTAX           CucsAaaEpLoginEntry
    MAX-ACCESS       not-accessible
    STATUS           current
    DESCRIPTION
        "Entry for the cucsAaaEpLoginTable table."
    INDEX { cucsAaaEpLoginInstanceId }
    ::= { cucsAaaEpLoginTable 1 }

CucsAaaEpLoginEntry ::= SEQUENCE {
    cucsAaaEpLoginInstanceId                                         CucsManagedObjectId,
    cucsAaaEpLoginDn                                                 CucsManagedObjectDn,
    cucsAaaEpLoginRn                                                 SnmpAdminString,
    cucsAaaEpLoginDescr                                              SnmpAdminString,
    cucsAaaEpLoginId                                                 SnmpAdminString,
    cucsAaaEpLoginIntId                                              SnmpAdminString,
    cucsAaaEpLoginLocalHost                                          SnmpAdminString,
    cucsAaaEpLoginName                                               SnmpAdminString,
    cucsAaaEpLoginRemoteHost                                         SnmpAdminString,
    cucsAaaEpLoginSession                                            CucsAaaSession,
    cucsAaaEpLoginSwitchId                                           CucsNetworkSwitchId,
    cucsAaaEpLoginPolicyLevel                                        Gauge32,
    cucsAaaEpLoginPolicyOwner                                        CucsPolicyPolicyOwner
}

cucsAaaEpLoginInstanceId OBJECT-TYPE
    SYNTAX       CucsManagedObjectId
    MAX-ACCESS   not-accessible
    STATUS       current
    DESCRIPTION
        "Instance identifier of the managed object."
    ::= { cucsAaaEpLoginEntry 1 }

cucsAaaEpLoginDn OBJECT-TYPE
    SYNTAX       CucsManagedObjectDn
    MAX-ACCESS   read-only
    STATUS       current
    DESCRIPTION
        "Cisco UCS aaa:EpLogin:dn managed object property"
    ::= { cucsAaaEpLoginEntry 2 }

cucsAaaEpLoginRn OBJECT-TYPE
    SYNTAX       SnmpAdminString
    MAX-ACCESS   read-only
    STATUS       current
    DESCRIPTION
        "Cisco UCS aaa:EpLogin:rn managed object property"
    ::= { cucsAaaEpLoginEntry 3 }

cucsAaaEpLoginDescr OBJECT-TYPE
    SYNTAX       SnmpAdminString
    MAX-ACCESS   read-only
    STATUS       current
    DESCRIPTION
        "Cisco UCS aaa:EpLogin:descr managed object property"
    ::= { cucsAaaEpLoginEntry 4 }

cucsAaaEpLoginId OBJECT-TYPE
    SYNTAX       SnmpAdminString
    MAX-ACCESS   read-only
    STATUS       current
    DESCRIPTION
        "Cisco UCS aaa:EpLogin:id managed object property"
    ::= { cucsAaaEpLoginEntry 5 }

cucsAaaEpLoginIntId OBJECT-TYPE
    SYNTAX       SnmpAdminString
    MAX-ACCESS   read-only
    STATUS       current
    DESCRIPTION
        "Cisco UCS aaa:EpLogin:intId managed object property"
    ::= { cucsAaaEpLoginEntry 6 }

cucsAaaEpLoginLocalHost OBJECT-TYPE
    SYNTAX       SnmpAdminString
    MAX-ACCESS   read-only
    STATUS       current
    DESCRIPTION
        "Cisco UCS aaa:EpLogin:localHost managed object property"
    ::= { cucsAaaEpLoginEntry 7 }

cucsAaaEpLoginName OBJECT-TYPE
    SYNTAX       SnmpAdminString
    MAX-ACCESS   read-only
    STATUS       current
    DESCRIPTION
        "Cisco UCS aaa:EpLogin:name managed object property"
    ::= { cucsAaaEpLoginEntry 8 }

cucsAaaEpLoginRemoteHost OBJECT-TYPE
    SYNTAX       SnmpAdminString
    MAX-ACCESS   read-only
    STATUS       current
    DESCRIPTION
        "Cisco UCS aaa:EpLogin:remoteHost managed object property"
    ::= { cucsAaaEpLoginEntry 9 }

cucsAaaEpLoginSession OBJECT-TYPE
    SYNTAX       CucsAaaSession
    MAX-ACCESS   read-only
    STATUS       current
    DESCRIPTION
        "Cisco UCS aaa:EpLogin:session managed object property"
    ::= { cucsAaaEpLoginEntry 10 }

cucsAaaEpLoginSwitchId OBJECT-TYPE
    SYNTAX       CucsNetworkSwitchId
    MAX-ACCESS   read-only
    STATUS       current
    DESCRIPTION
        "Cisco UCS aaa:EpLogin:switchId managed object property"
    ::= { cucsAaaEpLoginEntry 11 }

cucsAaaEpLoginPolicyLevel OBJECT-TYPE
    SYNTAX       Gauge32
    MAX-ACCESS   read-only
    STATUS       current
    DESCRIPTION
        "Cisco UCS aaa:EpLogin:policyLevel managed object property"
    ::= { cucsAaaEpLoginEntry 12 }

cucsAaaEpLoginPolicyOwner OBJECT-TYPE
    SYNTAX       CucsPolicyPolicyOwner
    MAX-ACCESS   read-only
    STATUS       current
    DESCRIPTION
        "Cisco UCS aaa:EpLogin:policyOwner managed object property"
    ::= { cucsAaaEpLoginEntry 13 }

cucsAaaEpUserTable OBJECT-TYPE
    SYNTAX           SEQUENCE OF CucsAaaEpUserEntry
    MAX-ACCESS       not-accessible
    STATUS           current
    DESCRIPTION
        "Cisco UCS aaa:EpUser managed object table"
    ::= { cucsAaaObjects 9 }

cucsAaaEpUserEntry OBJECT-TYPE
    SYNTAX           CucsAaaEpUserEntry
    MAX-ACCESS       not-accessible
    STATUS           current
    DESCRIPTION
        "Entry for the cucsAaaEpUserTable table."
    INDEX { cucsAaaEpUserInstanceId }
    ::= { cucsAaaEpUserTable 1 }

CucsAaaEpUserEntry ::= SEQUENCE {
    cucsAaaEpUserInstanceId                                          CucsManagedObjectId,
    cucsAaaEpUserDn                                                  CucsManagedObjectDn,
    cucsAaaEpUserRn                                                  SnmpAdminString,
    cucsAaaEpUserDescr                                               SnmpAdminString,
    cucsAaaEpUserName                                                SnmpAdminString,
    cucsAaaEpUserPriv                                                CucsAaaEpAccess,
    cucsAaaEpUserPwd                                                 SnmpAdminString,
    cucsAaaEpUserPwdSet                                              TruthValue,
    cucsAaaEpUserConfigState                                         CucsAaaConfigState,
    cucsAaaEpUserConfigStatusMessage                                 SnmpAdminString,
    cucsAaaEpUserIsPwdEnc                                            TruthValue
}

cucsAaaEpUserInstanceId OBJECT-TYPE
    SYNTAX       CucsManagedObjectId
    MAX-ACCESS   not-accessible
    STATUS       current
    DESCRIPTION
        "Instance identifier of the managed object."
    ::= { cucsAaaEpUserEntry 1 }

cucsAaaEpUserDn OBJECT-TYPE
    SYNTAX       CucsManagedObjectDn
    MAX-ACCESS   read-only
    STATUS       current
    DESCRIPTION
        "Cisco UCS aaa:EpUser:dn managed object property"
    ::= { cucsAaaEpUserEntry 2 }

cucsAaaEpUserRn OBJECT-TYPE
    SYNTAX       SnmpAdminString
    MAX-ACCESS   read-only
    STATUS       current
    DESCRIPTION
        "Cisco UCS aaa:EpUser:rn managed object property"
    ::= { cucsAaaEpUserEntry 3 }

cucsAaaEpUserDescr OBJECT-TYPE
    SYNTAX       SnmpAdminString
    MAX-ACCESS   read-only
    STATUS       current
    DESCRIPTION
        "Cisco UCS aaa:EpUser:descr managed object property"
    ::= { cucsAaaEpUserEntry 4 }

cucsAaaEpUserName OBJECT-TYPE
    SYNTAX       SnmpAdminString
    MAX-ACCESS   read-only
    STATUS       current
    DESCRIPTION
        "Cisco UCS aaa:EpUser:name managed object property"
    ::= { cucsAaaEpUserEntry 6 }

cucsAaaEpUserPriv OBJECT-TYPE
    SYNTAX       CucsAaaEpAccess
    MAX-ACCESS   read-only
    STATUS       current
    DESCRIPTION
        "Cisco UCS aaa:EpUser:priv managed object property"
    ::= { cucsAaaEpUserEntry 7 }

cucsAaaEpUserPwd OBJECT-TYPE
    SYNTAX       SnmpAdminString
    MAX-ACCESS   read-only
    STATUS       current
    DESCRIPTION
        "Cisco UCS aaa:EpUser:pwd managed object property"
    ::= { cucsAaaEpUserEntry 8 }

cucsAaaEpUserPwdSet OBJECT-TYPE
    SYNTAX       TruthValue
    MAX-ACCESS   read-only
    STATUS       current
    DESCRIPTION
        "Cisco UCS aaa:EpUser:pwdSet managed object property"
    ::= { cucsAaaEpUserEntry 9 }

cucsAaaEpUserConfigState OBJECT-TYPE
    SYNTAX       CucsAaaConfigState
    MAX-ACCESS   read-only
    STATUS       current
    DESCRIPTION
        "Cisco UCS aaa:EpUser:configState managed object property"
    ::= { cucsAaaEpUserEntry 10 }

cucsAaaEpUserConfigStatusMessage OBJECT-TYPE
    SYNTAX       SnmpAdminString
    MAX-ACCESS   read-only
    STATUS       current
    DESCRIPTION
        "Cisco UCS aaa:EpUser:configStatusMessage managed object property"
    ::= { cucsAaaEpUserEntry 11 }

cucsAaaEpUserIsPwdEnc OBJECT-TYPE
    SYNTAX       TruthValue
    MAX-ACCESS   read-only
    STATUS       current
    DESCRIPTION
        "Cisco UCS aaa:EpUser:isPwdEnc managed object property"
    ::= { cucsAaaEpUserEntry 14 }

cucsAaaExtMgmtCutThruTknTable OBJECT-TYPE
    SYNTAX           SEQUENCE OF CucsAaaExtMgmtCutThruTknEntry
    MAX-ACCESS       not-accessible
    STATUS           current
    DESCRIPTION
        "Cisco UCS aaa:ExtMgmtCutThruTkn managed object table"
    ::= { cucsAaaObjects 10 }

cucsAaaExtMgmtCutThruTknEntry OBJECT-TYPE
    SYNTAX           CucsAaaExtMgmtCutThruTknEntry
    MAX-ACCESS       not-accessible
    STATUS           current
    DESCRIPTION
        "Entry for the cucsAaaExtMgmtCutThruTknTable table."
    INDEX { cucsAaaExtMgmtCutThruTknInstanceId }
    ::= { cucsAaaExtMgmtCutThruTknTable 1 }

CucsAaaExtMgmtCutThruTknEntry ::= SEQUENCE {
    cucsAaaExtMgmtCutThruTknInstanceId                               CucsManagedObjectId,
    cucsAaaExtMgmtCutThruTknDn                                       CucsManagedObjectDn,
    cucsAaaExtMgmtCutThruTknRn                                       SnmpAdminString,
    cucsAaaExtMgmtCutThruTknAuthUser                                 SnmpAdminString,
    cucsAaaExtMgmtCutThruTknDescr                                    SnmpAdminString,
    cucsAaaExtMgmtCutThruTknIntId                                    SnmpAdminString,
    cucsAaaExtMgmtCutThruTknLocales                                  SnmpAdminString,
    cucsAaaExtMgmtCutThruTknName                                     SnmpAdminString,
    cucsAaaExtMgmtCutThruTknPnDn                                     SnmpAdminString,
    cucsAaaExtMgmtCutThruTknPriv                                     CucsAaaAccess,
    cucsAaaExtMgmtCutThruTknRemote                                   TruthValue,
    cucsAaaExtMgmtCutThruTknToken                                    SnmpAdminString,
    cucsAaaExtMgmtCutThruTknType                                     CucsAaaExtMgmtAccess,
    cucsAaaExtMgmtCutThruTknUser                                     SnmpAdminString,
    cucsAaaExtMgmtCutThruTknCreationTime                             DateAndTime,
    cucsAaaExtMgmtCutThruTknAuthDomain                               SnmpAdminString,
    cucsAaaExtMgmtCutThruTknPolicyLevel                              Gauge32,
    cucsAaaExtMgmtCutThruTknPolicyOwner                              CucsPolicyPolicyOwner
}

cucsAaaExtMgmtCutThruTknInstanceId OBJECT-TYPE
    SYNTAX       CucsManagedObjectId
    MAX-ACCESS   not-accessible
    STATUS       current
    DESCRIPTION
        "Instance identifier of the managed object."
    ::= { cucsAaaExtMgmtCutThruTknEntry 1 }

cucsAaaExtMgmtCutThruTknDn OBJECT-TYPE
    SYNTAX       CucsManagedObjectDn
    MAX-ACCESS   read-only
    STATUS       current
    DESCRIPTION
        "Cisco UCS aaa:ExtMgmtCutThruTkn:dn managed object property"
    ::= { cucsAaaExtMgmtCutThruTknEntry 2 }

cucsAaaExtMgmtCutThruTknRn OBJECT-TYPE
    SYNTAX       SnmpAdminString
    MAX-ACCESS   read-only
    STATUS       current
    DESCRIPTION
        "Cisco UCS aaa:ExtMgmtCutThruTkn:rn managed object property"
    ::= { cucsAaaExtMgmtCutThruTknEntry 3 }

cucsAaaExtMgmtCutThruTknAuthUser OBJECT-TYPE
    SYNTAX       SnmpAdminString
    MAX-ACCESS   read-only
    STATUS       current
    DESCRIPTION
        "Cisco UCS aaa:ExtMgmtCutThruTkn:authUser managed object property"
    ::= { cucsAaaExtMgmtCutThruTknEntry 4 }

cucsAaaExtMgmtCutThruTknDescr OBJECT-TYPE
    SYNTAX       SnmpAdminString
    MAX-ACCESS   read-only
    STATUS       current
    DESCRIPTION
        "Cisco UCS aaa:ExtMgmtCutThruTkn:descr managed object property"
    ::= { cucsAaaExtMgmtCutThruTknEntry 5 }

cucsAaaExtMgmtCutThruTknIntId OBJECT-TYPE
    SYNTAX       SnmpAdminString
    MAX-ACCESS   read-only
    STATUS       current
    DESCRIPTION
        "Cisco UCS aaa:ExtMgmtCutThruTkn:intId managed object property"
    ::= { cucsAaaExtMgmtCutThruTknEntry 6 }

cucsAaaExtMgmtCutThruTknLocales OBJECT-TYPE
    SYNTAX       SnmpAdminString
    MAX-ACCESS   read-only
    STATUS       current
    DESCRIPTION
        "Cisco UCS aaa:ExtMgmtCutThruTkn:locales managed object property"
    ::= { cucsAaaExtMgmtCutThruTknEntry 7 }

cucsAaaExtMgmtCutThruTknName OBJECT-TYPE
    SYNTAX       SnmpAdminString
    MAX-ACCESS   read-only
    STATUS       current
    DESCRIPTION
        "Cisco UCS aaa:ExtMgmtCutThruTkn:name managed object property"
    ::= { cucsAaaExtMgmtCutThruTknEntry 8 }

cucsAaaExtMgmtCutThruTknPnDn OBJECT-TYPE
    SYNTAX       SnmpAdminString
    MAX-ACCESS   read-only
    STATUS       current
    DESCRIPTION
        "Cisco UCS aaa:ExtMgmtCutThruTkn:pnDn managed object property"
    ::= { cucsAaaExtMgmtCutThruTknEntry 9 }

cucsAaaExtMgmtCutThruTknPriv OBJECT-TYPE
    SYNTAX       CucsAaaAccess
    MAX-ACCESS   read-only
    STATUS       current
    DESCRIPTION
        "Cisco UCS aaa:ExtMgmtCutThruTkn:priv managed object property"
    ::= { cucsAaaExtMgmtCutThruTknEntry 10 }

cucsAaaExtMgmtCutThruTknRemote OBJECT-TYPE
    SYNTAX       TruthValue
    MAX-ACCESS   read-only
    STATUS       current
    DESCRIPTION
        "Cisco UCS aaa:ExtMgmtCutThruTkn:remote managed object property"
    ::= { cucsAaaExtMgmtCutThruTknEntry 11 }

cucsAaaExtMgmtCutThruTknToken OBJECT-TYPE
    SYNTAX       SnmpAdminString
    MAX-ACCESS   read-only
    STATUS       current
    DESCRIPTION
        "Cisco UCS aaa:ExtMgmtCutThruTkn:token managed object property"
    ::= { cucsAaaExtMgmtCutThruTknEntry 12 }

cucsAaaExtMgmtCutThruTknType OBJECT-TYPE
    SYNTAX       CucsAaaExtMgmtAccess
    MAX-ACCESS   read-only
    STATUS       current
    DESCRIPTION
        "Cisco UCS aaa:ExtMgmtCutThruTkn:type managed object property"
    ::= { cucsAaaExtMgmtCutThruTknEntry 13 }

cucsAaaExtMgmtCutThruTknUser OBJECT-TYPE
    SYNTAX       SnmpAdminString
    MAX-ACCESS   read-only
    STATUS       current
    DESCRIPTION
        "Cisco UCS aaa:ExtMgmtCutThruTkn:user managed object property"
    ::= { cucsAaaExtMgmtCutThruTknEntry 14 }

cucsAaaExtMgmtCutThruTknCreationTime OBJECT-TYPE
    SYNTAX       DateAndTime
    MAX-ACCESS   read-only
    STATUS       current
    DESCRIPTION
        "Cisco UCS aaa:ExtMgmtCutThruTkn:creationTime managed
        object property"
    ::= { cucsAaaExtMgmtCutThruTknEntry 15 }

cucsAaaExtMgmtCutThruTknAuthDomain OBJECT-TYPE
    SYNTAX       SnmpAdminString
    MAX-ACCESS   read-only
    STATUS       current
    DESCRIPTION
        "Cisco UCS aaa:ExtMgmtCutThruTkn:authDomain managed
        object property"
    ::= { cucsAaaExtMgmtCutThruTknEntry 16 }

cucsAaaExtMgmtCutThruTknPolicyLevel OBJECT-TYPE
    SYNTAX       Gauge32
    MAX-ACCESS   read-only
    STATUS       current
    DESCRIPTION
        "Cisco UCS aaa:ExtMgmtCutThruTkn:policyLevel managed
        object property"
    ::= { cucsAaaExtMgmtCutThruTknEntry 17 }

cucsAaaExtMgmtCutThruTknPolicyOwner OBJECT-TYPE
    SYNTAX       CucsPolicyPolicyOwner
    MAX-ACCESS   read-only
    STATUS       current
    DESCRIPTION
        "Cisco UCS aaa:ExtMgmtCutThruTkn:policyOwner managed
        object property"
    ::= { cucsAaaExtMgmtCutThruTknEntry 18 }

cucsAaaLdapEpTable OBJECT-TYPE
    SYNTAX           SEQUENCE OF CucsAaaLdapEpEntry
    MAX-ACCESS       not-accessible
    STATUS           current
    DESCRIPTION
        "Cisco UCS aaa:LdapEp managed object table"
    ::= { cucsAaaObjects 11 }

cucsAaaLdapEpEntry OBJECT-TYPE
    SYNTAX           CucsAaaLdapEpEntry
    MAX-ACCESS       not-accessible
    STATUS           current
    DESCRIPTION
        "Entry for the cucsAaaLdapEpTable table."
    INDEX { cucsAaaLdapEpInstanceId }
    ::= { cucsAaaLdapEpTable 1 }

CucsAaaLdapEpEntry ::= SEQUENCE {
    cucsAaaLdapEpInstanceId                                          CucsManagedObjectId,
    cucsAaaLdapEpDn                                                  CucsManagedObjectDn,
    cucsAaaLdapEpRn                                                  SnmpAdminString,
    cucsAaaLdapEpAttribute                                           SnmpAdminString,
    cucsAaaLdapEpBasedn                                              SnmpAdminString,
    cucsAaaLdapEpDescr                                               SnmpAdminString,
    cucsAaaLdapEpFilter                                              SnmpAdminString,
    cucsAaaLdapEpFsmDescr                                            SnmpAdminString,
    cucsAaaLdapEpFsmPrev                                             SnmpAdminString,
    cucsAaaLdapEpFsmProgr                                            Gauge32,
    cucsAaaLdapEpFsmRmtInvErrCode                                    Gauge32,
    cucsAaaLdapEpFsmRmtInvErrDescr                                   SnmpAdminString,
    cucsAaaLdapEpFsmRmtInvRslt                                       CucsConditionRemoteInvRslt,
    cucsAaaLdapEpFsmStageDescr                                       SnmpAdminString,
    cucsAaaLdapEpFsmStamp                                            DateAndTime,
    cucsAaaLdapEpFsmStatus                                           SnmpAdminString,
    cucsAaaLdapEpFsmTry                                              Gauge32,
    cucsAaaLdapEpIntId                                               SnmpAdminString,
    cucsAaaLdapEpName                                                SnmpAdminString,
    cucsAaaLdapEpRetries                                             Gauge32,
    cucsAaaLdapEpTimeout                                             Gauge32,
    cucsAaaLdapEpPolicyLevel                                         Gauge32,
    cucsAaaLdapEpPolicyOwner                                         CucsPolicyPolicyOwner
}

cucsAaaLdapEpInstanceId OBJECT-TYPE
    SYNTAX       CucsManagedObjectId
    MAX-ACCESS   not-accessible
    STATUS       current
    DESCRIPTION
        "Instance identifier of the managed object."
    ::= { cucsAaaLdapEpEntry 1 }

cucsAaaLdapEpDn OBJECT-TYPE
    SYNTAX       CucsManagedObjectDn
    MAX-ACCESS   read-only
    STATUS       current
    DESCRIPTION
        "Cisco UCS aaa:LdapEp:dn managed object property"
    ::= { cucsAaaLdapEpEntry 2 }

cucsAaaLdapEpRn OBJECT-TYPE
    SYNTAX       SnmpAdminString
    MAX-ACCESS   read-only
    STATUS       current
    DESCRIPTION
        "Cisco UCS aaa:LdapEp:rn managed object property"
    ::= { cucsAaaLdapEpEntry 3 }

cucsAaaLdapEpAttribute OBJECT-TYPE
    SYNTAX       SnmpAdminString
    MAX-ACCESS   read-only
    STATUS       current
    DESCRIPTION
        "Cisco UCS aaa:LdapEp:attribute managed object property"
    ::= { cucsAaaLdapEpEntry 4 }

cucsAaaLdapEpBasedn OBJECT-TYPE
    SYNTAX       SnmpAdminString
    MAX-ACCESS   read-only
    STATUS       current
    DESCRIPTION
        "Cisco UCS aaa:LdapEp:basedn managed object property"
    ::= { cucsAaaLdapEpEntry 5 }

cucsAaaLdapEpDescr OBJECT-TYPE
    SYNTAX       SnmpAdminString
    MAX-ACCESS   read-only
    STATUS       current
    DESCRIPTION
        "Cisco UCS aaa:LdapEp:descr managed object property"
    ::= { cucsAaaLdapEpEntry 6 }

cucsAaaLdapEpFilter OBJECT-TYPE
    SYNTAX       SnmpAdminString
    MAX-ACCESS   read-only
    STATUS       current
    DESCRIPTION
        "Cisco UCS aaa:LdapEp:filter managed object property"
    ::= { cucsAaaLdapEpEntry 7 }

cucsAaaLdapEpFsmDescr OBJECT-TYPE
    SYNTAX       SnmpAdminString
    MAX-ACCESS   read-only
    STATUS       current
    DESCRIPTION
        "Cisco UCS aaa:LdapEp:fsmDescr managed object property"
    ::= { cucsAaaLdapEpEntry 8 }

cucsAaaLdapEpFsmPrev OBJECT-TYPE
    SYNTAX       SnmpAdminString
    MAX-ACCESS   read-only
    STATUS       current
    DESCRIPTION
        "Cisco UCS aaa:LdapEp:fsmPrev managed object property"
    ::= { cucsAaaLdapEpEntry 9 }

cucsAaaLdapEpFsmProgr OBJECT-TYPE
    SYNTAX       Gauge32
    MAX-ACCESS   read-only
    STATUS       current
    DESCRIPTION
        "Cisco UCS aaa:LdapEp:fsmProgr managed object property"
    ::= { cucsAaaLdapEpEntry 10 }

cucsAaaLdapEpFsmRmtInvErrCode OBJECT-TYPE
    SYNTAX       Gauge32
    MAX-ACCESS   read-only
    STATUS       current
    DESCRIPTION
        "Cisco UCS aaa:LdapEp:fsmRmtInvErrCode managed object property"
    ::= { cucsAaaLdapEpEntry 11 }

cucsAaaLdapEpFsmRmtInvErrDescr OBJECT-TYPE
    SYNTAX       SnmpAdminString
    MAX-ACCESS   read-only
    STATUS       current
    DESCRIPTION
        "Cisco UCS aaa:LdapEp:fsmRmtInvErrDescr managed object property"
    ::= { cucsAaaLdapEpEntry 12 }

cucsAaaLdapEpFsmRmtInvRslt OBJECT-TYPE
    SYNTAX       CucsConditionRemoteInvRslt
    MAX-ACCESS   read-only
    STATUS       current
    DESCRIPTION
        "Cisco UCS aaa:LdapEp:fsmRmtInvRslt managed object property"
    ::= { cucsAaaLdapEpEntry 13 }

cucsAaaLdapEpFsmStageDescr OBJECT-TYPE
    SYNTAX       SnmpAdminString
    MAX-ACCESS   read-only
    STATUS       current
    DESCRIPTION
        "Cisco UCS aaa:LdapEp:fsmStageDescr managed object property"
    ::= { cucsAaaLdapEpEntry 14 }

cucsAaaLdapEpFsmStamp OBJECT-TYPE
    SYNTAX       DateAndTime
    MAX-ACCESS   read-only
    STATUS       current
    DESCRIPTION
        "Cisco UCS aaa:LdapEp:fsmStamp managed object property"
    ::= { cucsAaaLdapEpEntry 15 }

cucsAaaLdapEpFsmStatus OBJECT-TYPE
    SYNTAX       SnmpAdminString
    MAX-ACCESS   read-only
    STATUS       current
    DESCRIPTION
        "Cisco UCS aaa:LdapEp:fsmStatus managed object property"
    ::= { cucsAaaLdapEpEntry 16 }

cucsAaaLdapEpFsmTry OBJECT-TYPE
    SYNTAX       Gauge32
    MAX-ACCESS   read-only
    STATUS       current
    DESCRIPTION
        "Cisco UCS aaa:LdapEp:fsmTry managed object property"
    ::= { cucsAaaLdapEpEntry 17 }

cucsAaaLdapEpIntId OBJECT-TYPE
    SYNTAX       SnmpAdminString
    MAX-ACCESS   read-only
    STATUS       current
    DESCRIPTION
        "Cisco UCS aaa:LdapEp:intId managed object property"
    ::= { cucsAaaLdapEpEntry 18 }

cucsAaaLdapEpName OBJECT-TYPE
    SYNTAX       SnmpAdminString
    MAX-ACCESS   read-only
    STATUS       current
    DESCRIPTION
        "Cisco UCS aaa:LdapEp:name managed object property"
    ::= { cucsAaaLdapEpEntry 19 }

cucsAaaLdapEpRetries OBJECT-TYPE
    SYNTAX       Gauge32
    MAX-ACCESS   read-only
    STATUS       current
    DESCRIPTION
        "Cisco UCS aaa:LdapEp:retries managed object property"
    ::= { cucsAaaLdapEpEntry 20 }

cucsAaaLdapEpTimeout OBJECT-TYPE
    SYNTAX       Gauge32
    MAX-ACCESS   read-only
    STATUS       current
    DESCRIPTION
        "Cisco UCS aaa:LdapEp:timeout managed object property"
    ::= { cucsAaaLdapEpEntry 21 }

cucsAaaLdapEpPolicyLevel OBJECT-TYPE
    SYNTAX       Gauge32
    MAX-ACCESS   read-only
    STATUS       current
    DESCRIPTION
        "Cisco UCS aaa:LdapEp:policyLevel managed object property"
    ::= { cucsAaaLdapEpEntry 22 }

cucsAaaLdapEpPolicyOwner OBJECT-TYPE
    SYNTAX       CucsPolicyPolicyOwner
    MAX-ACCESS   read-only
    STATUS       current
    DESCRIPTION
        "Cisco UCS aaa:LdapEp:policyOwner managed object property"
    ::= { cucsAaaLdapEpEntry 23 }

cucsAaaLdapEpFsmTable OBJECT-TYPE
    SYNTAX           SEQUENCE OF CucsAaaLdapEpFsmEntry
    MAX-ACCESS       not-accessible
    STATUS           current
    DESCRIPTION
        "Cisco UCS aaa:LdapEpFsm managed object table"
    ::= { cucsAaaObjects 45 }

cucsAaaLdapEpFsmEntry OBJECT-TYPE
    SYNTAX           CucsAaaLdapEpFsmEntry
    MAX-ACCESS       not-accessible
    STATUS           current
    DESCRIPTION
        "Entry for the cucsAaaLdapEpFsmTable table."
    INDEX { cucsAaaLdapEpFsmInstanceId }
    ::= { cucsAaaLdapEpFsmTable 1 }

CucsAaaLdapEpFsmEntry ::= SEQUENCE {
    cucsAaaLdapEpFsmInstanceId                                       CucsManagedObjectId,
    cucsAaaLdapEpFsmDn                                               CucsManagedObjectDn,
    cucsAaaLdapEpFsmRn                                               SnmpAdminString,
    cucsAaaLdapEpFsmCompletionTime                                   DateAndTime,
    cucsAaaLdapEpFsmCurrentFsm                                       CucsAaaLdapEpFsmCurrentFsm,
    cucsAaaLdapEpFsmDescrData                                        SnmpAdminString,
    cucsAaaLdapEpFsmFsmStatus                                        CucsFsmFsmStageStatus,
    cucsAaaLdapEpFsmProgress                                         Gauge32,
    cucsAaaLdapEpFsmRmtErrCode                                       Gauge32,
    cucsAaaLdapEpFsmRmtErrDescr                                      SnmpAdminString,
    cucsAaaLdapEpFsmRmtRslt                                          CucsConditionRemoteInvRslt
}

cucsAaaLdapEpFsmInstanceId OBJECT-TYPE
    SYNTAX       CucsManagedObjectId
    MAX-ACCESS   not-accessible
    STATUS       current
    DESCRIPTION
        "Instance identifier of the managed object."
    ::= { cucsAaaLdapEpFsmEntry 1 }

cucsAaaLdapEpFsmDn OBJECT-TYPE
    SYNTAX       CucsManagedObjectDn
    MAX-ACCESS   read-only
    STATUS       current
    DESCRIPTION
        "Cisco UCS aaa:LdapEpFsm:dn managed object property"
    ::= { cucsAaaLdapEpFsmEntry 2 }

cucsAaaLdapEpFsmRn OBJECT-TYPE
    SYNTAX       SnmpAdminString
    MAX-ACCESS   read-only
    STATUS       current
    DESCRIPTION
        "Cisco UCS aaa:LdapEpFsm:rn managed object property"
    ::= { cucsAaaLdapEpFsmEntry 3 }

cucsAaaLdapEpFsmCompletionTime OBJECT-TYPE
    SYNTAX       DateAndTime
    MAX-ACCESS   read-only
    STATUS       current
    DESCRIPTION
        "Cisco UCS aaa:LdapEpFsm:completionTime managed object property"
    ::= { cucsAaaLdapEpFsmEntry 4 }

cucsAaaLdapEpFsmCurrentFsm OBJECT-TYPE
    SYNTAX       CucsAaaLdapEpFsmCurrentFsm
    MAX-ACCESS   read-only
    STATUS       current
    DESCRIPTION
        "Cisco UCS aaa:LdapEpFsm:currentFsm managed object property"
    ::= { cucsAaaLdapEpFsmEntry 5 }

cucsAaaLdapEpFsmDescrData OBJECT-TYPE
    SYNTAX       SnmpAdminString
    MAX-ACCESS   read-only
    STATUS       current
    DESCRIPTION
        "Cisco UCS aaa:LdapEpFsm:descr managed object property"
    ::= { cucsAaaLdapEpFsmEntry 6 }

cucsAaaLdapEpFsmFsmStatus OBJECT-TYPE
    SYNTAX       CucsFsmFsmStageStatus
    MAX-ACCESS   read-only
    STATUS       current
    DESCRIPTION
        "Cisco UCS aaa:LdapEpFsm:fsmStatus managed object property"
    ::= { cucsAaaLdapEpFsmEntry 7 }

cucsAaaLdapEpFsmProgress OBJECT-TYPE
    SYNTAX       Gauge32
    MAX-ACCESS   read-only
    STATUS       current
    DESCRIPTION
        "Cisco UCS aaa:LdapEpFsm:progress managed object property"
    ::= { cucsAaaLdapEpFsmEntry 8 }

cucsAaaLdapEpFsmRmtErrCode OBJECT-TYPE
    SYNTAX       Gauge32
    MAX-ACCESS   read-only
    STATUS       current
    DESCRIPTION
        "Cisco UCS aaa:LdapEpFsm:rmtErrCode managed object property"
    ::= { cucsAaaLdapEpFsmEntry 9 }

cucsAaaLdapEpFsmRmtErrDescr OBJECT-TYPE
    SYNTAX       SnmpAdminString
    MAX-ACCESS   read-only
    STATUS       current
    DESCRIPTION
        "Cisco UCS aaa:LdapEpFsm:rmtErrDescr managed object property"
    ::= { cucsAaaLdapEpFsmEntry 10 }

cucsAaaLdapEpFsmRmtRslt OBJECT-TYPE
    SYNTAX       CucsConditionRemoteInvRslt
    MAX-ACCESS   read-only
    STATUS       current
    DESCRIPTION
        "Cisco UCS aaa:LdapEpFsm:rmtRslt managed object property"
    ::= { cucsAaaLdapEpFsmEntry 11 }

cucsAaaLdapEpFsmStageTable OBJECT-TYPE
    SYNTAX           SEQUENCE OF CucsAaaLdapEpFsmStageEntry
    MAX-ACCESS       not-accessible
    STATUS           current
    DESCRIPTION
        "Cisco UCS aaa:LdapEpFsmStage managed object table"
    ::= { cucsAaaObjects 46 }

cucsAaaLdapEpFsmStageEntry OBJECT-TYPE
    SYNTAX           CucsAaaLdapEpFsmStageEntry
    MAX-ACCESS       not-accessible
    STATUS           current
    DESCRIPTION
        "Entry for the cucsAaaLdapEpFsmStageTable table."
    INDEX { cucsAaaLdapEpFsmStageInstanceId }
    ::= { cucsAaaLdapEpFsmStageTable 1 }

CucsAaaLdapEpFsmStageEntry ::= SEQUENCE {
    cucsAaaLdapEpFsmStageInstanceId                                  CucsManagedObjectId,
    cucsAaaLdapEpFsmStageDn                                          CucsManagedObjectDn,
    cucsAaaLdapEpFsmStageRn                                          SnmpAdminString,
    cucsAaaLdapEpFsmStageDescrData                                   SnmpAdminString,
    cucsAaaLdapEpFsmStageLastUpdateTime                              DateAndTime,
    cucsAaaLdapEpFsmStageName                                        CucsAaaLdapEpFsmStageName,
    cucsAaaLdapEpFsmStageOrder                                       Gauge32,
    cucsAaaLdapEpFsmStageRetry                                       Gauge32,
    cucsAaaLdapEpFsmStageStageStatus                                 CucsFsmFsmStageStatus
}

cucsAaaLdapEpFsmStageInstanceId OBJECT-TYPE
    SYNTAX       CucsManagedObjectId
    MAX-ACCESS   not-accessible
    STATUS       current
    DESCRIPTION
        "Instance identifier of the managed object."
    ::= { cucsAaaLdapEpFsmStageEntry 1 }

cucsAaaLdapEpFsmStageDn OBJECT-TYPE
    SYNTAX       CucsManagedObjectDn
    MAX-ACCESS   read-only
    STATUS       current
    DESCRIPTION
        "Cisco UCS aaa:LdapEpFsmStage:dn managed object property"
    ::= { cucsAaaLdapEpFsmStageEntry 2 }

cucsAaaLdapEpFsmStageRn OBJECT-TYPE
    SYNTAX       SnmpAdminString
    MAX-ACCESS   read-only
    STATUS       current
    DESCRIPTION
        "Cisco UCS aaa:LdapEpFsmStage:rn managed object property"
    ::= { cucsAaaLdapEpFsmStageEntry 3 }

cucsAaaLdapEpFsmStageDescrData OBJECT-TYPE
    SYNTAX       SnmpAdminString
    MAX-ACCESS   read-only
    STATUS       current
    DESCRIPTION
        "Cisco UCS aaa:LdapEpFsmStage:descr managed object property"
    ::= { cucsAaaLdapEpFsmStageEntry 4 }

cucsAaaLdapEpFsmStageLastUpdateTime OBJECT-TYPE
    SYNTAX       DateAndTime
    MAX-ACCESS   read-only
    STATUS       current
    DESCRIPTION
        "Cisco UCS aaa:LdapEpFsmStage:lastUpdateTime managed
        object property"
    ::= { cucsAaaLdapEpFsmStageEntry 5 }

cucsAaaLdapEpFsmStageName OBJECT-TYPE
    SYNTAX       CucsAaaLdapEpFsmStageName
    MAX-ACCESS   read-only
    STATUS       current
    DESCRIPTION
        "Cisco UCS aaa:LdapEpFsmStage:name managed object property"
    ::= { cucsAaaLdapEpFsmStageEntry 6 }

cucsAaaLdapEpFsmStageOrder OBJECT-TYPE
    SYNTAX       Gauge32
    MAX-ACCESS   read-only
    STATUS       current
    DESCRIPTION
        "Cisco UCS aaa:LdapEpFsmStage:order managed object property"
    ::= { cucsAaaLdapEpFsmStageEntry 7 }

cucsAaaLdapEpFsmStageRetry OBJECT-TYPE
    SYNTAX       Gauge32
    MAX-ACCESS   read-only
    STATUS       current
    DESCRIPTION
        "Cisco UCS aaa:LdapEpFsmStage:retry managed object property"
    ::= { cucsAaaLdapEpFsmStageEntry 8 }

cucsAaaLdapEpFsmStageStageStatus OBJECT-TYPE
    SYNTAX       CucsFsmFsmStageStatus
    MAX-ACCESS   read-only
    STATUS       current
    DESCRIPTION
        "Cisco UCS aaa:LdapEpFsmStage:stageStatus managed object property"
    ::= { cucsAaaLdapEpFsmStageEntry 9 }

cucsAaaLdapGroupTable OBJECT-TYPE
    SYNTAX           SEQUENCE OF CucsAaaLdapGroupEntry
    MAX-ACCESS       not-accessible
    STATUS           current
    DESCRIPTION
        "Cisco UCS aaa:LdapGroup managed object table"
    ::= { cucsAaaObjects 12 }

cucsAaaLdapGroupEntry OBJECT-TYPE
    SYNTAX           CucsAaaLdapGroupEntry
    MAX-ACCESS       not-accessible
    STATUS           current
    DESCRIPTION
        "Entry for the cucsAaaLdapGroupTable table."
    INDEX { cucsAaaLdapGroupInstanceId }
    ::= { cucsAaaLdapGroupTable 1 }

CucsAaaLdapGroupEntry ::= SEQUENCE {
    cucsAaaLdapGroupInstanceId                                       CucsManagedObjectId,
    cucsAaaLdapGroupDn                                               CucsManagedObjectDn,
    cucsAaaLdapGroupRn                                               SnmpAdminString,
    cucsAaaLdapGroupDescr                                            SnmpAdminString,
    cucsAaaLdapGroupName                                             SnmpAdminString
}

cucsAaaLdapGroupInstanceId OBJECT-TYPE
    SYNTAX       CucsManagedObjectId
    MAX-ACCESS   not-accessible
    STATUS       current
    DESCRIPTION
        "Instance identifier of the managed object."
    ::= { cucsAaaLdapGroupEntry 1 }

cucsAaaLdapGroupDn OBJECT-TYPE
    SYNTAX       CucsManagedObjectDn
    MAX-ACCESS   read-only
    STATUS       current
    DESCRIPTION
        "Cisco UCS aaa:LdapGroup:dn managed object property"
    ::= { cucsAaaLdapGroupEntry 2 }

cucsAaaLdapGroupRn OBJECT-TYPE
    SYNTAX       SnmpAdminString
    MAX-ACCESS   read-only
    STATUS       current
    DESCRIPTION
        "Cisco UCS aaa:LdapGroup:rn managed object property"
    ::= { cucsAaaLdapGroupEntry 3 }

cucsAaaLdapGroupDescr OBJECT-TYPE
    SYNTAX       SnmpAdminString
    MAX-ACCESS   read-only
    STATUS       current
    DESCRIPTION
        "Cisco UCS aaa:LdapGroup:descr managed object property"
    ::= { cucsAaaLdapGroupEntry 4 }

cucsAaaLdapGroupName OBJECT-TYPE
    SYNTAX       SnmpAdminString
    MAX-ACCESS   read-only
    STATUS       current
    DESCRIPTION
        "Cisco UCS aaa:LdapGroup:name managed object property"
    ::= { cucsAaaLdapGroupEntry 6 }

cucsAaaLdapGroupRuleTable OBJECT-TYPE
    SYNTAX           SEQUENCE OF CucsAaaLdapGroupRuleEntry
    MAX-ACCESS       not-accessible
    STATUS           current
    DESCRIPTION
        "Cisco UCS aaa:LdapGroupRule managed object table"
    ::= { cucsAaaObjects 13 }

cucsAaaLdapGroupRuleEntry OBJECT-TYPE
    SYNTAX           CucsAaaLdapGroupRuleEntry
    MAX-ACCESS       not-accessible
    STATUS           current
    DESCRIPTION
        "Entry for the cucsAaaLdapGroupRuleTable table."
    INDEX { cucsAaaLdapGroupRuleInstanceId }
    ::= { cucsAaaLdapGroupRuleTable 1 }

CucsAaaLdapGroupRuleEntry ::= SEQUENCE {
    cucsAaaLdapGroupRuleInstanceId                                   CucsManagedObjectId,
    cucsAaaLdapGroupRuleDn                                           CucsManagedObjectDn,
    cucsAaaLdapGroupRuleRn                                           SnmpAdminString,
    cucsAaaLdapGroupRuleAuthorization                                CucsAaaLdapGroupRuleAuthorization,
    cucsAaaLdapGroupRuleDescr                                        SnmpAdminString,
    cucsAaaLdapGroupRuleName                                         SnmpAdminString,
    cucsAaaLdapGroupRuleTargetAttr                                   SnmpAdminString,
    cucsAaaLdapGroupRuleTraversal                                    CucsAaaLdapGroupRuleTraversal,
    cucsAaaLdapGroupRuleUsePrimaryGroup                              TruthValue
}

cucsAaaLdapGroupRuleInstanceId OBJECT-TYPE
    SYNTAX       CucsManagedObjectId
    MAX-ACCESS   not-accessible
    STATUS       current
    DESCRIPTION
        "Instance identifier of the managed object."
    ::= { cucsAaaLdapGroupRuleEntry 1 }

cucsAaaLdapGroupRuleDn OBJECT-TYPE
    SYNTAX       CucsManagedObjectDn
    MAX-ACCESS   read-only
    STATUS       current
    DESCRIPTION
        "Cisco UCS aaa:LdapGroupRule:dn managed object property"
    ::= { cucsAaaLdapGroupRuleEntry 2 }

cucsAaaLdapGroupRuleRn OBJECT-TYPE
    SYNTAX       SnmpAdminString
    MAX-ACCESS   read-only
    STATUS       current
    DESCRIPTION
        "Cisco UCS aaa:LdapGroupRule:rn managed object property"
    ::= { cucsAaaLdapGroupRuleEntry 3 }

cucsAaaLdapGroupRuleAuthorization OBJECT-TYPE
    SYNTAX       CucsAaaLdapGroupRuleAuthorization
    MAX-ACCESS   read-only
    STATUS       current
    DESCRIPTION
        "Cisco UCS aaa:LdapGroupRule:authorization managed
        object property"
    ::= { cucsAaaLdapGroupRuleEntry 4 }

cucsAaaLdapGroupRuleDescr OBJECT-TYPE
    SYNTAX       SnmpAdminString
    MAX-ACCESS   read-only
    STATUS       current
    DESCRIPTION
        "Cisco UCS aaa:LdapGroupRule:descr managed object property"
    ::= { cucsAaaLdapGroupRuleEntry 5 }

cucsAaaLdapGroupRuleName OBJECT-TYPE
    SYNTAX       SnmpAdminString
    MAX-ACCESS   read-only
    STATUS       current
    DESCRIPTION
        "Cisco UCS aaa:LdapGroupRule:name managed object property"
    ::= { cucsAaaLdapGroupRuleEntry 7 }

cucsAaaLdapGroupRuleTargetAttr OBJECT-TYPE
    SYNTAX       SnmpAdminString
    MAX-ACCESS   read-only
    STATUS       current
    DESCRIPTION
        "Cisco UCS aaa:LdapGroupRule:targetAttr managed object property"
    ::= { cucsAaaLdapGroupRuleEntry 8 }

cucsAaaLdapGroupRuleTraversal OBJECT-TYPE
    SYNTAX       CucsAaaLdapGroupRuleTraversal
    MAX-ACCESS   read-only
    STATUS       current
    DESCRIPTION
        "Cisco UCS aaa:LdapGroupRule:traversal managed object property"
    ::= { cucsAaaLdapGroupRuleEntry 9 }

cucsAaaLdapGroupRuleUsePrimaryGroup OBJECT-TYPE
    SYNTAX       TruthValue
    MAX-ACCESS   read-only
    STATUS       current
    DESCRIPTION
        "Cisco UCS aaa:LdapGroupRule:usePrimaryGroup managed
        object property"
    ::= { cucsAaaLdapGroupRuleEntry 10 }

cucsAaaLdapProviderTable OBJECT-TYPE
    SYNTAX           SEQUENCE OF CucsAaaLdapProviderEntry
    MAX-ACCESS       not-accessible
    STATUS           current
    DESCRIPTION
        "Cisco UCS aaa:LdapProvider managed object table"
    ::= { cucsAaaObjects 14 }

cucsAaaLdapProviderEntry OBJECT-TYPE
    SYNTAX           CucsAaaLdapProviderEntry
    MAX-ACCESS       not-accessible
    STATUS           current
    DESCRIPTION
        "Entry for the cucsAaaLdapProviderTable table."
    INDEX { cucsAaaLdapProviderInstanceId }
    ::= { cucsAaaLdapProviderTable 1 }

CucsAaaLdapProviderEntry ::= SEQUENCE {
    cucsAaaLdapProviderInstanceId                                    CucsManagedObjectId,
    cucsAaaLdapProviderDn                                            CucsManagedObjectDn,
    cucsAaaLdapProviderRn                                            SnmpAdminString,
    cucsAaaLdapProviderAttribute                                     SnmpAdminString,
    cucsAaaLdapProviderBasedn                                        SnmpAdminString,
    cucsAaaLdapProviderDescr                                         SnmpAdminString,
    cucsAaaLdapProviderEnableSSL                                     TruthValue,
    cucsAaaLdapProviderEncKey                                        SnmpAdminString,
    cucsAaaLdapProviderFilter                                        SnmpAdminString,
    cucsAaaLdapProviderKey                                           SnmpAdminString,
    cucsAaaLdapProviderKeySet                                        TruthValue,
    cucsAaaLdapProviderName                                          SnmpAdminString,
    cucsAaaLdapProviderOrder                                         Gauge32,
    cucsAaaLdapProviderPort                                          Gauge32,
    cucsAaaLdapProviderRetries                                       Gauge32,
    cucsAaaLdapProviderRootdn                                        SnmpAdminString,
    cucsAaaLdapProviderTimeout                                       Gauge32,
    cucsAaaLdapProviderVendor                                        CucsAaaLdapVendor
}

cucsAaaLdapProviderInstanceId OBJECT-TYPE
    SYNTAX       CucsManagedObjectId
    MAX-ACCESS   not-accessible
    STATUS       current
    DESCRIPTION
        "Instance identifier of the managed object."
    ::= { cucsAaaLdapProviderEntry 1 }

cucsAaaLdapProviderDn OBJECT-TYPE
    SYNTAX       CucsManagedObjectDn
    MAX-ACCESS   read-only
    STATUS       current
    DESCRIPTION
        "Cisco UCS aaa:LdapProvider:dn managed object property"
    ::= { cucsAaaLdapProviderEntry 2 }

cucsAaaLdapProviderRn OBJECT-TYPE
    SYNTAX       SnmpAdminString
    MAX-ACCESS   read-only
    STATUS       current
    DESCRIPTION
        "Cisco UCS aaa:LdapProvider:rn managed object property"
    ::= { cucsAaaLdapProviderEntry 3 }

cucsAaaLdapProviderAttribute OBJECT-TYPE
    SYNTAX       SnmpAdminString
    MAX-ACCESS   read-only
    STATUS       current
    DESCRIPTION
        "Cisco UCS aaa:LdapProvider:attribute managed object property"
    ::= { cucsAaaLdapProviderEntry 4 }

cucsAaaLdapProviderBasedn OBJECT-TYPE
    SYNTAX       SnmpAdminString
    MAX-ACCESS   read-only
    STATUS       current
    DESCRIPTION
        "Cisco UCS aaa:LdapProvider:basedn managed object property"
    ::= { cucsAaaLdapProviderEntry 5 }

cucsAaaLdapProviderDescr OBJECT-TYPE
    SYNTAX       SnmpAdminString
    MAX-ACCESS   read-only
    STATUS       current
    DESCRIPTION
        "Cisco UCS aaa:LdapProvider:descr managed object property"
    ::= { cucsAaaLdapProviderEntry 6 }

cucsAaaLdapProviderEnableSSL OBJECT-TYPE
    SYNTAX       TruthValue
    MAX-ACCESS   read-only
    STATUS       current
    DESCRIPTION
        "Cisco UCS aaa:LdapProvider:enableSSL managed object property"
    ::= { cucsAaaLdapProviderEntry 7 }

cucsAaaLdapProviderEncKey OBJECT-TYPE
    SYNTAX       SnmpAdminString
    MAX-ACCESS   read-only
    STATUS       current
    DESCRIPTION
        "Cisco UCS aaa:LdapProvider:encKey managed object property"
    ::= { cucsAaaLdapProviderEntry 8 }

cucsAaaLdapProviderFilter OBJECT-TYPE
    SYNTAX       SnmpAdminString
    MAX-ACCESS   read-only
    STATUS       current
    DESCRIPTION
        "Cisco UCS aaa:LdapProvider:filter managed object property"
    ::= { cucsAaaLdapProviderEntry 9 }

cucsAaaLdapProviderKey OBJECT-TYPE
    SYNTAX       SnmpAdminString
    MAX-ACCESS   read-only
    STATUS       current
    DESCRIPTION
        "Cisco UCS aaa:LdapProvider:key managed object property"
    ::= { cucsAaaLdapProviderEntry 11 }

cucsAaaLdapProviderKeySet OBJECT-TYPE
    SYNTAX       TruthValue
    MAX-ACCESS   read-only
    STATUS       current
    DESCRIPTION
        "Cisco UCS aaa:LdapProvider:keySet managed object property"
    ::= { cucsAaaLdapProviderEntry 12 }

cucsAaaLdapProviderName OBJECT-TYPE
    SYNTAX       SnmpAdminString
    MAX-ACCESS   read-only
    STATUS       current
    DESCRIPTION
        "Cisco UCS aaa:LdapProvider:name managed object property"
    ::= { cucsAaaLdapProviderEntry 13 }

cucsAaaLdapProviderOrder OBJECT-TYPE
    SYNTAX       Gauge32
    MAX-ACCESS   read-only
    STATUS       current
    DESCRIPTION
        "Cisco UCS aaa:LdapProvider:order managed object property"
    ::= { cucsAaaLdapProviderEntry 14 }

cucsAaaLdapProviderPort OBJECT-TYPE
    SYNTAX       Gauge32
    MAX-ACCESS   read-only
    STATUS       current
    DESCRIPTION
        "Cisco UCS aaa:LdapProvider:port managed object property"
    ::= { cucsAaaLdapProviderEntry 15 }

cucsAaaLdapProviderRetries OBJECT-TYPE
    SYNTAX       Gauge32
    MAX-ACCESS   read-only
    STATUS       current
    DESCRIPTION
        "Cisco UCS aaa:LdapProvider:retries managed object property"
    ::= { cucsAaaLdapProviderEntry 16 }

cucsAaaLdapProviderRootdn OBJECT-TYPE
    SYNTAX       SnmpAdminString
    MAX-ACCESS   read-only
    STATUS       current
    DESCRIPTION
        "Cisco UCS aaa:LdapProvider:rootdn managed object property"
    ::= { cucsAaaLdapProviderEntry 17 }

cucsAaaLdapProviderTimeout OBJECT-TYPE
    SYNTAX       Gauge32
    MAX-ACCESS   read-only
    STATUS       current
    DESCRIPTION
        "Cisco UCS aaa:LdapProvider:timeout managed object property"
    ::= { cucsAaaLdapProviderEntry 18 }

cucsAaaLdapProviderVendor OBJECT-TYPE
    SYNTAX       CucsAaaLdapVendor
    MAX-ACCESS   read-only
    STATUS       current
    DESCRIPTION
        "Cisco UCS aaa:LdapProvider:vendor managed object property"
    ::= { cucsAaaLdapProviderEntry 19 }

cucsAaaLocaleTable OBJECT-TYPE
    SYNTAX           SEQUENCE OF CucsAaaLocaleEntry
    MAX-ACCESS       not-accessible
    STATUS           current
    DESCRIPTION
        "Cisco UCS aaa:Locale managed object table"
    ::= { cucsAaaObjects 15 }

cucsAaaLocaleEntry OBJECT-TYPE
    SYNTAX           CucsAaaLocaleEntry
    MAX-ACCESS       not-accessible
    STATUS           current
    DESCRIPTION
        "Entry for the cucsAaaLocaleTable table."
    INDEX { cucsAaaLocaleInstanceId }
    ::= { cucsAaaLocaleTable 1 }

CucsAaaLocaleEntry ::= SEQUENCE {
    cucsAaaLocaleInstanceId                                          CucsManagedObjectId,
    cucsAaaLocaleDn                                                  CucsManagedObjectDn,
    cucsAaaLocaleRn                                                  SnmpAdminString,
    cucsAaaLocaleDescr                                               SnmpAdminString,
    cucsAaaLocaleIntId                                               SnmpAdminString,
    cucsAaaLocaleName                                                SnmpAdminString,
    cucsAaaLocaleConfigState                                         CucsAaaConfigState,
    cucsAaaLocaleConfigStatusMessage                                 SnmpAdminString,
    cucsAaaLocalePolicyLevel                                         Gauge32,
    cucsAaaLocalePolicyOwner                                         CucsPolicyPolicyOwner
}

cucsAaaLocaleInstanceId OBJECT-TYPE
    SYNTAX       CucsManagedObjectId
    MAX-ACCESS   not-accessible
    STATUS       current
    DESCRIPTION
        "Instance identifier of the managed object."
    ::= { cucsAaaLocaleEntry 1 }

cucsAaaLocaleDn OBJECT-TYPE
    SYNTAX       CucsManagedObjectDn
    MAX-ACCESS   read-only
    STATUS       current
    DESCRIPTION
        "Cisco UCS aaa:Locale:dn managed object property"
    ::= { cucsAaaLocaleEntry 2 }

cucsAaaLocaleRn OBJECT-TYPE
    SYNTAX       SnmpAdminString
    MAX-ACCESS   read-only
    STATUS       current
    DESCRIPTION
        "Cisco UCS aaa:Locale:rn managed object property"
    ::= { cucsAaaLocaleEntry 3 }

cucsAaaLocaleDescr OBJECT-TYPE
    SYNTAX       SnmpAdminString
    MAX-ACCESS   read-only
    STATUS       current
    DESCRIPTION
        "Cisco UCS aaa:Locale:descr managed object property"
    ::= { cucsAaaLocaleEntry 4 }

cucsAaaLocaleIntId OBJECT-TYPE
    SYNTAX       SnmpAdminString
    MAX-ACCESS   read-only
    STATUS       current
    DESCRIPTION
        "Cisco UCS aaa:Locale:intId managed object property"
    ::= { cucsAaaLocaleEntry 5 }

cucsAaaLocaleName OBJECT-TYPE
    SYNTAX       SnmpAdminString
    MAX-ACCESS   read-only
    STATUS       current
    DESCRIPTION
        "Cisco UCS aaa:Locale:name managed object property"
    ::= { cucsAaaLocaleEntry 6 }

cucsAaaLocaleConfigState OBJECT-TYPE
    SYNTAX       CucsAaaConfigState
    MAX-ACCESS   read-only
    STATUS       current
    DESCRIPTION
        "Cisco UCS aaa:Locale:configState managed object property"
    ::= { cucsAaaLocaleEntry 7 }

cucsAaaLocaleConfigStatusMessage OBJECT-TYPE
    SYNTAX       SnmpAdminString
    MAX-ACCESS   read-only
    STATUS       current
    DESCRIPTION
        "Cisco UCS aaa:Locale:configStatusMessage managed object property"
    ::= { cucsAaaLocaleEntry 8 }

cucsAaaLocalePolicyLevel OBJECT-TYPE
    SYNTAX       Gauge32
    MAX-ACCESS   read-only
    STATUS       current
    DESCRIPTION
        "Cisco UCS aaa:Locale:policyLevel managed object property"
    ::= { cucsAaaLocaleEntry 9 }

cucsAaaLocalePolicyOwner OBJECT-TYPE
    SYNTAX       CucsPolicyPolicyOwner
    MAX-ACCESS   read-only
    STATUS       current
    DESCRIPTION
        "Cisco UCS aaa:Locale:policyOwner managed object property"
    ::= { cucsAaaLocaleEntry 10 }

cucsAaaLogTable OBJECT-TYPE
    SYNTAX           SEQUENCE OF CucsAaaLogEntry
    MAX-ACCESS       not-accessible
    STATUS           current
    DESCRIPTION
        "Cisco UCS aaa:Log managed object table"
    ::= { cucsAaaObjects 16 }

cucsAaaLogEntry OBJECT-TYPE
    SYNTAX           CucsAaaLogEntry
    MAX-ACCESS       not-accessible
    STATUS           current
    DESCRIPTION
        "Entry for the cucsAaaLogTable table."
    INDEX { cucsAaaLogInstanceId }
    ::= { cucsAaaLogTable 1 }

CucsAaaLogEntry ::= SEQUENCE {
    cucsAaaLogInstanceId                                             CucsManagedObjectId,
    cucsAaaLogDn                                                     CucsManagedObjectDn,
    cucsAaaLogRn                                                     SnmpAdminString,
    cucsAaaLogMaxSize                                                Gauge32,
    cucsAaaLogPurgeWindow                                            Gauge32,
    cucsAaaLogSize                                                   Gauge32
}

cucsAaaLogInstanceId OBJECT-TYPE
    SYNTAX       CucsManagedObjectId
    MAX-ACCESS   not-accessible
    STATUS       current
    DESCRIPTION
        "Instance identifier of the managed object."
    ::= { cucsAaaLogEntry 1 }

cucsAaaLogDn OBJECT-TYPE
    SYNTAX       CucsManagedObjectDn
    MAX-ACCESS   read-only
    STATUS       current
    DESCRIPTION
        "Cisco UCS aaa:Log:dn managed object property"
    ::= { cucsAaaLogEntry 2 }

cucsAaaLogRn OBJECT-TYPE
    SYNTAX       SnmpAdminString
    MAX-ACCESS   read-only
    STATUS       current
    DESCRIPTION
        "Cisco UCS aaa:Log:rn managed object property"
    ::= { cucsAaaLogEntry 3 }

cucsAaaLogMaxSize OBJECT-TYPE
    SYNTAX       Gauge32
    MAX-ACCESS   read-only
    STATUS       current
    DESCRIPTION
        "Cisco UCS aaa:Log:maxSize managed object property"
    ::= { cucsAaaLogEntry 4 }

cucsAaaLogPurgeWindow OBJECT-TYPE
    SYNTAX       Gauge32
    MAX-ACCESS   read-only
    STATUS       current
    DESCRIPTION
        "Cisco UCS aaa:Log:purgeWindow managed object property"
    ::= { cucsAaaLogEntry 5 }

cucsAaaLogSize OBJECT-TYPE
    SYNTAX       Gauge32
    MAX-ACCESS   read-only
    STATUS       current
    DESCRIPTION
        "Cisco UCS aaa:Log:size managed object property"
    ::= { cucsAaaLogEntry 6 }

cucsAaaModLRTable OBJECT-TYPE
    SYNTAX           SEQUENCE OF CucsAaaModLREntry
    MAX-ACCESS       not-accessible
    STATUS           current
    DESCRIPTION
        "Cisco UCS aaa:ModLR managed object table"
    ::= { cucsAaaObjects 17 }

cucsAaaModLREntry OBJECT-TYPE
    SYNTAX           CucsAaaModLREntry
    MAX-ACCESS       not-accessible
    STATUS           current
    DESCRIPTION
        "Entry for the cucsAaaModLRTable table."
    INDEX { cucsAaaModLRInstanceId }
    ::= { cucsAaaModLRTable 1 }

CucsAaaModLREntry ::= SEQUENCE {
    cucsAaaModLRInstanceId                                           CucsManagedObjectId,
    cucsAaaModLRDn                                                   CucsManagedObjectDn,
    cucsAaaModLRRn                                                   SnmpAdminString,
    cucsAaaModLRAffected                                             SnmpAdminString,
    cucsAaaModLRCause                                                CucsConditionCause,
    cucsAaaModLRChangeSet                                            SnmpAdminString,
    cucsAaaModLRCode                                                 CucsConditionCode,
    cucsAaaModLRCreated                                              DateAndTime,
    cucsAaaModLRDescr                                                SnmpAdminString,
    cucsAaaModLRId                                                   Gauge32,
    cucsAaaModLRInd                                                  CucsConditionActionIndicator,
    cucsAaaModLRSeverity                                             CucsConditionSeverity,
    cucsAaaModLRTrig                                                 Gauge32,
    cucsAaaModLRTxId                                                 Unsigned64,
    cucsAaaModLRUser                                                 SnmpAdminString,
    cucsAaaModLRSessionId                                            SnmpAdminString
}

cucsAaaModLRInstanceId OBJECT-TYPE
    SYNTAX       CucsManagedObjectId
    MAX-ACCESS   not-accessible
    STATUS       current
    DESCRIPTION
        "Instance identifier of the managed object."
    ::= { cucsAaaModLREntry 1 }

cucsAaaModLRDn OBJECT-TYPE
    SYNTAX       CucsManagedObjectDn
    MAX-ACCESS   read-only
    STATUS       current
    DESCRIPTION
        "Cisco UCS aaa:ModLR:dn managed object property"
    ::= { cucsAaaModLREntry 2 }

cucsAaaModLRRn OBJECT-TYPE
    SYNTAX       SnmpAdminString
    MAX-ACCESS   read-only
    STATUS       current
    DESCRIPTION
        "Cisco UCS aaa:ModLR:rn managed object property"
    ::= { cucsAaaModLREntry 3 }

cucsAaaModLRAffected OBJECT-TYPE
    SYNTAX       SnmpAdminString
    MAX-ACCESS   read-only
    STATUS       current
    DESCRIPTION
        "Cisco UCS aaa:ModLR:affected managed object property"
    ::= { cucsAaaModLREntry 4 }

cucsAaaModLRCause OBJECT-TYPE
    SYNTAX       CucsConditionCause
    MAX-ACCESS   read-only
    STATUS       current
    DESCRIPTION
        "Cisco UCS aaa:ModLR:cause managed object property"
    ::= { cucsAaaModLREntry 5 }

cucsAaaModLRChangeSet OBJECT-TYPE
    SYNTAX       SnmpAdminString
    MAX-ACCESS   read-only
    STATUS       current
    DESCRIPTION
        "Cisco UCS aaa:ModLR:changeSet managed object property"
    ::= { cucsAaaModLREntry 6 }

cucsAaaModLRCode OBJECT-TYPE
    SYNTAX       CucsConditionCode
    MAX-ACCESS   read-only
    STATUS       current
    DESCRIPTION
        "Cisco UCS aaa:ModLR:code managed object property"
    ::= { cucsAaaModLREntry 7 }

cucsAaaModLRCreated OBJECT-TYPE
    SYNTAX       DateAndTime
    MAX-ACCESS   read-only
    STATUS       current
    DESCRIPTION
        "Cisco UCS aaa:ModLR:created managed object property"
    ::= { cucsAaaModLREntry 8 }

cucsAaaModLRDescr OBJECT-TYPE
    SYNTAX       SnmpAdminString
    MAX-ACCESS   read-only
    STATUS       current
    DESCRIPTION
        "Cisco UCS aaa:ModLR:descr managed object property"
    ::= { cucsAaaModLREntry 9 }

cucsAaaModLRId OBJECT-TYPE
    SYNTAX       Gauge32
    MAX-ACCESS   read-only
    STATUS       current
    DESCRIPTION
        "Cisco UCS aaa:ModLR:id managed object property"
    ::= { cucsAaaModLREntry 10 }

cucsAaaModLRInd OBJECT-TYPE
    SYNTAX       CucsConditionActionIndicator
    MAX-ACCESS   read-only
    STATUS       current
    DESCRIPTION
        "Cisco UCS aaa:ModLR:ind managed object property"
    ::= { cucsAaaModLREntry 11 }

cucsAaaModLRSeverity OBJECT-TYPE
    SYNTAX       CucsConditionSeverity
    MAX-ACCESS   read-only
    STATUS       current
    DESCRIPTION
        "Cisco UCS aaa:ModLR:severity managed object property"
    ::= { cucsAaaModLREntry 12 }

cucsAaaModLRTrig OBJECT-TYPE
    SYNTAX       Gauge32
    MAX-ACCESS   read-only
    STATUS       current
    DESCRIPTION
        "Cisco UCS aaa:ModLR:trig managed object property"
    ::= { cucsAaaModLREntry 13 }

cucsAaaModLRTxId OBJECT-TYPE
    SYNTAX       Unsigned64
    MAX-ACCESS   read-only
    STATUS       current
    DESCRIPTION
        "Cisco UCS aaa:ModLR:txId managed object property"
    ::= { cucsAaaModLREntry 14 }

cucsAaaModLRUser OBJECT-TYPE
    SYNTAX       SnmpAdminString
    MAX-ACCESS   read-only
    STATUS       current
    DESCRIPTION
        "Cisco UCS aaa:ModLR:user managed object property"
    ::= { cucsAaaModLREntry 15 }

cucsAaaModLRSessionId OBJECT-TYPE
    SYNTAX       SnmpAdminString
    MAX-ACCESS   read-only
    STATUS       current
    DESCRIPTION
        "Cisco UCS aaa:ModLR:sessionId managed object property"
    ::= { cucsAaaModLREntry 16 }

cucsAaaOrgTable OBJECT-TYPE
    SYNTAX           SEQUENCE OF CucsAaaOrgEntry
    MAX-ACCESS       not-accessible
    STATUS           current
    DESCRIPTION
        "Cisco UCS aaa:Org managed object table"
    ::= { cucsAaaObjects 18 }

cucsAaaOrgEntry OBJECT-TYPE
    SYNTAX           CucsAaaOrgEntry
    MAX-ACCESS       not-accessible
    STATUS           current
    DESCRIPTION
        "Entry for the cucsAaaOrgTable table."
    INDEX { cucsAaaOrgInstanceId }
    ::= { cucsAaaOrgTable 1 }

CucsAaaOrgEntry ::= SEQUENCE {
    cucsAaaOrgInstanceId                                             CucsManagedObjectId,
    cucsAaaOrgDn                                                     CucsManagedObjectDn,
    cucsAaaOrgRn                                                     SnmpAdminString,
    cucsAaaOrgDescr                                                  SnmpAdminString,
    cucsAaaOrgName                                                   SnmpAdminString,
    cucsAaaOrgOrgDn                                                  SnmpAdminString,
    cucsAaaOrgConfigState                                            CucsAaaConfigState,
    cucsAaaOrgConfigStatusMessage                                    SnmpAdminString
}

cucsAaaOrgInstanceId OBJECT-TYPE
    SYNTAX       CucsManagedObjectId
    MAX-ACCESS   not-accessible
    STATUS       current
    DESCRIPTION
        "Instance identifier of the managed object."
    ::= { cucsAaaOrgEntry 1 }

cucsAaaOrgDn OBJECT-TYPE
    SYNTAX       CucsManagedObjectDn
    MAX-ACCESS   read-only
    STATUS       current
    DESCRIPTION
        "Cisco UCS aaa:Org:dn managed object property"
    ::= { cucsAaaOrgEntry 2 }

cucsAaaOrgRn OBJECT-TYPE
    SYNTAX       SnmpAdminString
    MAX-ACCESS   read-only
    STATUS       current
    DESCRIPTION
        "Cisco UCS aaa:Org:rn managed object property"
    ::= { cucsAaaOrgEntry 3 }

cucsAaaOrgDescr OBJECT-TYPE
    SYNTAX       SnmpAdminString
    MAX-ACCESS   read-only
    STATUS       current
    DESCRIPTION
        "Cisco UCS aaa:Org:descr managed object property"
    ::= { cucsAaaOrgEntry 4 }

cucsAaaOrgName OBJECT-TYPE
    SYNTAX       SnmpAdminString
    MAX-ACCESS   read-only
    STATUS       current
    DESCRIPTION
        "Cisco UCS aaa:Org:name managed object property"
    ::= { cucsAaaOrgEntry 6 }

cucsAaaOrgOrgDn OBJECT-TYPE
    SYNTAX       SnmpAdminString
    MAX-ACCESS   read-only
    STATUS       current
    DESCRIPTION
        "Cisco UCS aaa:Org:orgDn managed object property"
    ::= { cucsAaaOrgEntry 7 }

cucsAaaOrgConfigState OBJECT-TYPE
    SYNTAX       CucsAaaConfigState
    MAX-ACCESS   read-only
    STATUS       current
    DESCRIPTION
        "Cisco UCS aaa:Org:configState managed object property"
    ::= { cucsAaaOrgEntry 8 }

cucsAaaOrgConfigStatusMessage OBJECT-TYPE
    SYNTAX       SnmpAdminString
    MAX-ACCESS   read-only
    STATUS       current
    DESCRIPTION
        "Cisco UCS aaa:Org:configStatusMessage managed object property"
    ::= { cucsAaaOrgEntry 9 }

cucsAaaPreLoginBannerTable OBJECT-TYPE
    SYNTAX           SEQUENCE OF CucsAaaPreLoginBannerEntry
    MAX-ACCESS       not-accessible
    STATUS           current
    DESCRIPTION
        "Cisco UCS aaa:PreLoginBanner managed object table"
    ::= { cucsAaaObjects 38 }

cucsAaaPreLoginBannerEntry OBJECT-TYPE
    SYNTAX           CucsAaaPreLoginBannerEntry
    MAX-ACCESS       not-accessible
    STATUS           current
    DESCRIPTION
        "Entry for the cucsAaaPreLoginBannerTable table."
    INDEX { cucsAaaPreLoginBannerInstanceId }
    ::= { cucsAaaPreLoginBannerTable 1 }

CucsAaaPreLoginBannerEntry ::= SEQUENCE {
    cucsAaaPreLoginBannerInstanceId                                  CucsManagedObjectId,
    cucsAaaPreLoginBannerDn                                          CucsManagedObjectDn,
    cucsAaaPreLoginBannerRn                                          SnmpAdminString,
    cucsAaaPreLoginBannerDescr                                       SnmpAdminString,
    cucsAaaPreLoginBannerIntId                                       SnmpAdminString,
    cucsAaaPreLoginBannerMessage                                     SnmpAdminString,
    cucsAaaPreLoginBannerName                                        SnmpAdminString,
    cucsAaaPreLoginBannerPolicyLevel                                 Gauge32,
    cucsAaaPreLoginBannerPolicyOwner                                 CucsPolicyPolicyOwner
}

cucsAaaPreLoginBannerInstanceId OBJECT-TYPE
    SYNTAX       CucsManagedObjectId
    MAX-ACCESS   not-accessible
    STATUS       current
    DESCRIPTION
        "Instance identifier of the managed object."
    ::= { cucsAaaPreLoginBannerEntry 1 }

cucsAaaPreLoginBannerDn OBJECT-TYPE
    SYNTAX       CucsManagedObjectDn
    MAX-ACCESS   read-only
    STATUS       current
    DESCRIPTION
        "Cisco UCS aaa:PreLoginBanner:dn managed object property"
    ::= { cucsAaaPreLoginBannerEntry 2 }

cucsAaaPreLoginBannerRn OBJECT-TYPE
    SYNTAX       SnmpAdminString
    MAX-ACCESS   read-only
    STATUS       current
    DESCRIPTION
        "Cisco UCS aaa:PreLoginBanner:rn managed object property"
    ::= { cucsAaaPreLoginBannerEntry 3 }

cucsAaaPreLoginBannerDescr OBJECT-TYPE
    SYNTAX       SnmpAdminString
    MAX-ACCESS   read-only
    STATUS       current
    DESCRIPTION
        "Cisco UCS aaa:PreLoginBanner:descr managed object property"
    ::= { cucsAaaPreLoginBannerEntry 4 }

cucsAaaPreLoginBannerIntId OBJECT-TYPE
    SYNTAX       SnmpAdminString
    MAX-ACCESS   read-only
    STATUS       current
    DESCRIPTION
        "Cisco UCS aaa:PreLoginBanner:intId managed object property"
    ::= { cucsAaaPreLoginBannerEntry 5 }

cucsAaaPreLoginBannerMessage OBJECT-TYPE
    SYNTAX       SnmpAdminString
    MAX-ACCESS   read-only
    STATUS       current
    DESCRIPTION
        "Cisco UCS aaa:PreLoginBanner:message managed object property"
    ::= { cucsAaaPreLoginBannerEntry 6 }

cucsAaaPreLoginBannerName OBJECT-TYPE
    SYNTAX       SnmpAdminString
    MAX-ACCESS   read-only
    STATUS       current
    DESCRIPTION
        "Cisco UCS aaa:PreLoginBanner:name managed object property"
    ::= { cucsAaaPreLoginBannerEntry 7 }

cucsAaaPreLoginBannerPolicyLevel OBJECT-TYPE
    SYNTAX       Gauge32
    MAX-ACCESS   read-only
    STATUS       current
    DESCRIPTION
        "Cisco UCS aaa:PreLoginBanner:policyLevel managed object property"
    ::= { cucsAaaPreLoginBannerEntry 8 }

cucsAaaPreLoginBannerPolicyOwner OBJECT-TYPE
    SYNTAX       CucsPolicyPolicyOwner
    MAX-ACCESS   read-only
    STATUS       current
    DESCRIPTION
        "Cisco UCS aaa:PreLoginBanner:policyOwner managed object property"
    ::= { cucsAaaPreLoginBannerEntry 9 }

cucsAaaProviderGroupTable OBJECT-TYPE
    SYNTAX           SEQUENCE OF CucsAaaProviderGroupEntry
    MAX-ACCESS       not-accessible
    STATUS           current
    DESCRIPTION
        "Cisco UCS aaa:ProviderGroup managed object table"
    ::= { cucsAaaObjects 19 }

cucsAaaProviderGroupEntry OBJECT-TYPE
    SYNTAX           CucsAaaProviderGroupEntry
    MAX-ACCESS       not-accessible
    STATUS           current
    DESCRIPTION
        "Entry for the cucsAaaProviderGroupTable table."
    INDEX { cucsAaaProviderGroupInstanceId }
    ::= { cucsAaaProviderGroupTable 1 }

CucsAaaProviderGroupEntry ::= SEQUENCE {
    cucsAaaProviderGroupInstanceId                                   CucsManagedObjectId,
    cucsAaaProviderGroupDn                                           CucsManagedObjectDn,
    cucsAaaProviderGroupRn                                           SnmpAdminString,
    cucsAaaProviderGroupDescr                                        SnmpAdminString,
    cucsAaaProviderGroupName                                         SnmpAdminString,
    cucsAaaProviderGroupConfigState                                  CucsAaaConfigState,
    cucsAaaProviderGroupSize                                         Gauge32
}

cucsAaaProviderGroupInstanceId OBJECT-TYPE
    SYNTAX       CucsManagedObjectId
    MAX-ACCESS   not-accessible
    STATUS       current
    DESCRIPTION
        "Instance identifier of the managed object."
    ::= { cucsAaaProviderGroupEntry 1 }

cucsAaaProviderGroupDn OBJECT-TYPE
    SYNTAX       CucsManagedObjectDn
    MAX-ACCESS   read-only
    STATUS       current
    DESCRIPTION
        "Cisco UCS aaa:ProviderGroup:dn managed object property"
    ::= { cucsAaaProviderGroupEntry 2 }

cucsAaaProviderGroupRn OBJECT-TYPE
    SYNTAX       SnmpAdminString
    MAX-ACCESS   read-only
    STATUS       current
    DESCRIPTION
        "Cisco UCS aaa:ProviderGroup:rn managed object property"
    ::= { cucsAaaProviderGroupEntry 3 }

cucsAaaProviderGroupDescr OBJECT-TYPE
    SYNTAX       SnmpAdminString
    MAX-ACCESS   read-only
    STATUS       current
    DESCRIPTION
        "Cisco UCS aaa:ProviderGroup:descr managed object property"
    ::= { cucsAaaProviderGroupEntry 4 }

cucsAaaProviderGroupName OBJECT-TYPE
    SYNTAX       SnmpAdminString
    MAX-ACCESS   read-only
    STATUS       current
    DESCRIPTION
        "Cisco UCS aaa:ProviderGroup:name managed object property"
    ::= { cucsAaaProviderGroupEntry 6 }

cucsAaaProviderGroupConfigState OBJECT-TYPE
    SYNTAX       CucsAaaConfigState
    MAX-ACCESS   read-only
    STATUS       current
    DESCRIPTION
        "Cisco UCS aaa:ProviderGroup:configState managed object property"
    ::= { cucsAaaProviderGroupEntry 7 }

cucsAaaProviderGroupSize OBJECT-TYPE
    SYNTAX       Gauge32
    MAX-ACCESS   read-only
    STATUS       current
    DESCRIPTION
        "Cisco UCS aaa:ProviderGroup:size managed object property"
    ::= { cucsAaaProviderGroupEntry 8 }

cucsAaaProviderRefTable OBJECT-TYPE
    SYNTAX           SEQUENCE OF CucsAaaProviderRefEntry
    MAX-ACCESS       not-accessible
    STATUS           current
    DESCRIPTION
        "Cisco UCS aaa:ProviderRef managed object table"
    ::= { cucsAaaObjects 20 }

cucsAaaProviderRefEntry OBJECT-TYPE
    SYNTAX           CucsAaaProviderRefEntry
    MAX-ACCESS       not-accessible
    STATUS           current
    DESCRIPTION
        "Entry for the cucsAaaProviderRefTable table."
    INDEX { cucsAaaProviderRefInstanceId }
    ::= { cucsAaaProviderRefTable 1 }

CucsAaaProviderRefEntry ::= SEQUENCE {
    cucsAaaProviderRefInstanceId                                     CucsManagedObjectId,
    cucsAaaProviderRefDn                                             CucsManagedObjectDn,
    cucsAaaProviderRefRn                                             SnmpAdminString,
    cucsAaaProviderRefDescr                                          SnmpAdminString,
    cucsAaaProviderRefName                                           SnmpAdminString,
    cucsAaaProviderRefOrder                                          Gauge32
}

cucsAaaProviderRefInstanceId OBJECT-TYPE
    SYNTAX       CucsManagedObjectId
    MAX-ACCESS   not-accessible
    STATUS       current
    DESCRIPTION
        "Instance identifier of the managed object."
    ::= { cucsAaaProviderRefEntry 1 }

cucsAaaProviderRefDn OBJECT-TYPE
    SYNTAX       CucsManagedObjectDn
    MAX-ACCESS   read-only
    STATUS       current
    DESCRIPTION
        "Cisco UCS aaa:ProviderRef:dn managed object property"
    ::= { cucsAaaProviderRefEntry 2 }

cucsAaaProviderRefRn OBJECT-TYPE
    SYNTAX       SnmpAdminString
    MAX-ACCESS   read-only
    STATUS       current
    DESCRIPTION
        "Cisco UCS aaa:ProviderRef:rn managed object property"
    ::= { cucsAaaProviderRefEntry 3 }

cucsAaaProviderRefDescr OBJECT-TYPE
    SYNTAX       SnmpAdminString
    MAX-ACCESS   read-only
    STATUS       current
    DESCRIPTION
        "Cisco UCS aaa:ProviderRef:descr managed object property"
    ::= { cucsAaaProviderRefEntry 4 }

cucsAaaProviderRefName OBJECT-TYPE
    SYNTAX       SnmpAdminString
    MAX-ACCESS   read-only
    STATUS       current
    DESCRIPTION
        "Cisco UCS aaa:ProviderRef:name managed object property"
    ::= { cucsAaaProviderRefEntry 6 }

cucsAaaProviderRefOrder OBJECT-TYPE
    SYNTAX       Gauge32
    MAX-ACCESS   read-only
    STATUS       current
    DESCRIPTION
        "Cisco UCS aaa:ProviderRef:order managed object property"
    ::= { cucsAaaProviderRefEntry 7 }

cucsAaaPwdProfileTable OBJECT-TYPE
    SYNTAX           SEQUENCE OF CucsAaaPwdProfileEntry
    MAX-ACCESS       not-accessible
    STATUS           current
    DESCRIPTION
        "Cisco UCS aaa:PwdProfile managed object table"
    ::= { cucsAaaObjects 39 }

cucsAaaPwdProfileEntry OBJECT-TYPE
    SYNTAX           CucsAaaPwdProfileEntry
    MAX-ACCESS       not-accessible
    STATUS           current
    DESCRIPTION
        "Entry for the cucsAaaPwdProfileTable table."
    INDEX { cucsAaaPwdProfileInstanceId }
    ::= { cucsAaaPwdProfileTable 1 }

CucsAaaPwdProfileEntry ::= SEQUENCE {
    cucsAaaPwdProfileInstanceId                                      CucsManagedObjectId,
    cucsAaaPwdProfileDn                                              CucsManagedObjectDn,
    cucsAaaPwdProfileRn                                              SnmpAdminString,
    cucsAaaPwdProfileChangeCount                                     Gauge32,
    cucsAaaPwdProfileChangeDuringInterval                            CucsAaaPwdPolicy,
    cucsAaaPwdProfileChangeInterval                                  Gauge32,
    cucsAaaPwdProfileDescr                                           SnmpAdminString,
    cucsAaaPwdProfileExpirationWarnTime                              Gauge32,
    cucsAaaPwdProfileHistoryCount                                    Gauge32,
    cucsAaaPwdProfileIntId                                           SnmpAdminString,
    cucsAaaPwdProfileName                                            SnmpAdminString,
    cucsAaaPwdProfileNoChangeInterval                                Gauge32,
    cucsAaaPwdProfilePolicyLevel                                     Gauge32,
    cucsAaaPwdProfilePolicyOwner                                     CucsPolicyPolicyOwner,
    cucsAaaPwdProfileMinPassphraseLen                                Gauge32
}

cucsAaaPwdProfileInstanceId OBJECT-TYPE
    SYNTAX       CucsManagedObjectId
    MAX-ACCESS   not-accessible
    STATUS       current
    DESCRIPTION
        "Instance identifier of the managed object."
    ::= { cucsAaaPwdProfileEntry 1 }

cucsAaaPwdProfileDn OBJECT-TYPE
    SYNTAX       CucsManagedObjectDn
    MAX-ACCESS   read-only
    STATUS       current
    DESCRIPTION
        "Cisco UCS aaa:PwdProfile:dn managed object property"
    ::= { cucsAaaPwdProfileEntry 2 }

cucsAaaPwdProfileRn OBJECT-TYPE
    SYNTAX       SnmpAdminString
    MAX-ACCESS   read-only
    STATUS       current
    DESCRIPTION
        "Cisco UCS aaa:PwdProfile:rn managed object property"
    ::= { cucsAaaPwdProfileEntry 3 }

cucsAaaPwdProfileChangeCount OBJECT-TYPE
    SYNTAX       Gauge32
    MAX-ACCESS   read-only
    STATUS       current
    DESCRIPTION
        "Cisco UCS aaa:PwdProfile:changeCount managed object property"
    ::= { cucsAaaPwdProfileEntry 4 }

cucsAaaPwdProfileChangeDuringInterval OBJECT-TYPE
    SYNTAX       CucsAaaPwdPolicy
    MAX-ACCESS   read-only
    STATUS       current
    DESCRIPTION
        "Cisco UCS aaa:PwdProfile:changeDuringInterval
        managed object property"
    ::= { cucsAaaPwdProfileEntry 5 }

cucsAaaPwdProfileChangeInterval OBJECT-TYPE
    SYNTAX       Gauge32
    MAX-ACCESS   read-only
    STATUS       current
    DESCRIPTION
        "Cisco UCS aaa:PwdProfile:changeInterval managed object property"
    ::= { cucsAaaPwdProfileEntry 6 }

cucsAaaPwdProfileDescr OBJECT-TYPE
    SYNTAX       SnmpAdminString
    MAX-ACCESS   read-only
    STATUS       current
    DESCRIPTION
        "Cisco UCS aaa:PwdProfile:descr managed object property"
    ::= { cucsAaaPwdProfileEntry 7 }

cucsAaaPwdProfileExpirationWarnTime OBJECT-TYPE
    SYNTAX       Gauge32
    MAX-ACCESS   read-only
    STATUS       current
    DESCRIPTION
        "Cisco UCS aaa:PwdProfile:expirationWarnTime managed
        object property"
    ::= { cucsAaaPwdProfileEntry 8 }

cucsAaaPwdProfileHistoryCount OBJECT-TYPE
    SYNTAX       Gauge32
    MAX-ACCESS   read-only
    STATUS       current
    DESCRIPTION
        "Cisco UCS aaa:PwdProfile:historyCount managed object property"
    ::= { cucsAaaPwdProfileEntry 9 }

cucsAaaPwdProfileIntId OBJECT-TYPE
    SYNTAX       SnmpAdminString
    MAX-ACCESS   read-only
    STATUS       current
    DESCRIPTION
        "Cisco UCS aaa:PwdProfile:intId managed object property"
    ::= { cucsAaaPwdProfileEntry 10 }

cucsAaaPwdProfileName OBJECT-TYPE
    SYNTAX       SnmpAdminString
    MAX-ACCESS   read-only
    STATUS       current
    DESCRIPTION
        "Cisco UCS aaa:PwdProfile:name managed object property"
    ::= { cucsAaaPwdProfileEntry 11 }

cucsAaaPwdProfileNoChangeInterval OBJECT-TYPE
    SYNTAX       Gauge32
    MAX-ACCESS   read-only
    STATUS       current
    DESCRIPTION
        "Cisco UCS aaa:PwdProfile:noChangeInterval managed
        object property"
    ::= { cucsAaaPwdProfileEntry 12 }

cucsAaaPwdProfilePolicyLevel OBJECT-TYPE
    SYNTAX       Gauge32
    MAX-ACCESS   read-only
    STATUS       current
    DESCRIPTION
        "Cisco UCS aaa:PwdProfile:policyLevel managed object property"
    ::= { cucsAaaPwdProfileEntry 13 }

cucsAaaPwdProfilePolicyOwner OBJECT-TYPE
    SYNTAX       CucsPolicyPolicyOwner
    MAX-ACCESS   read-only
    STATUS       current
    DESCRIPTION
        "Cisco UCS aaa:PwdProfile:policyOwner managed object property"
    ::= { cucsAaaPwdProfileEntry 14 }

cucsAaaPwdProfileMinPassphraseLen OBJECT-TYPE
    SYNTAX       Gauge32
    MAX-ACCESS   read-only
    STATUS       current
    DESCRIPTION
        "Cisco UCS aaa:PwdProfile:minPassphraseLen managed
        object property"
    ::= { cucsAaaPwdProfileEntry 16 }

cucsAaaRadiusEpTable OBJECT-TYPE
    SYNTAX           SEQUENCE OF CucsAaaRadiusEpEntry
    MAX-ACCESS       not-accessible
    STATUS           current
    DESCRIPTION
        "Cisco UCS aaa:RadiusEp managed object table"
    ::= { cucsAaaObjects 21 }

cucsAaaRadiusEpEntry OBJECT-TYPE
    SYNTAX           CucsAaaRadiusEpEntry
    MAX-ACCESS       not-accessible
    STATUS           current
    DESCRIPTION
        "Entry for the cucsAaaRadiusEpTable table."
    INDEX { cucsAaaRadiusEpInstanceId }
    ::= { cucsAaaRadiusEpTable 1 }

CucsAaaRadiusEpEntry ::= SEQUENCE {
    cucsAaaRadiusEpInstanceId                                        CucsManagedObjectId,
    cucsAaaRadiusEpDn                                                CucsManagedObjectDn,
    cucsAaaRadiusEpRn                                                SnmpAdminString,
    cucsAaaRadiusEpDescr                                             SnmpAdminString,
    cucsAaaRadiusEpFsmDescr                                          SnmpAdminString,
    cucsAaaRadiusEpFsmPrev                                           SnmpAdminString,
    cucsAaaRadiusEpFsmProgr                                          Gauge32,
    cucsAaaRadiusEpFsmRmtInvErrCode                                  Gauge32,
    cucsAaaRadiusEpFsmRmtInvErrDescr                                 SnmpAdminString,
    cucsAaaRadiusEpFsmRmtInvRslt                                     CucsConditionRemoteInvRslt,
    cucsAaaRadiusEpFsmStageDescr                                     SnmpAdminString,
    cucsAaaRadiusEpFsmStamp                                          DateAndTime,
    cucsAaaRadiusEpFsmStatus                                         SnmpAdminString,
    cucsAaaRadiusEpFsmTry                                            Gauge32,
    cucsAaaRadiusEpIntId                                             SnmpAdminString,
    cucsAaaRadiusEpName                                              SnmpAdminString,
    cucsAaaRadiusEpRetries                                           Gauge32,
    cucsAaaRadiusEpTimeout                                           Gauge32,
    cucsAaaRadiusEpPolicyLevel                                       Gauge32,
    cucsAaaRadiusEpPolicyOwner                                       CucsPolicyPolicyOwner
}

cucsAaaRadiusEpInstanceId OBJECT-TYPE
    SYNTAX       CucsManagedObjectId
    MAX-ACCESS   not-accessible
    STATUS       current
    DESCRIPTION
        "Instance identifier of the managed object."
    ::= { cucsAaaRadiusEpEntry 1 }

cucsAaaRadiusEpDn OBJECT-TYPE
    SYNTAX       CucsManagedObjectDn
    MAX-ACCESS   read-only
    STATUS       current
    DESCRIPTION
        "Cisco UCS aaa:RadiusEp:dn managed object property"
    ::= { cucsAaaRadiusEpEntry 2 }

cucsAaaRadiusEpRn OBJECT-TYPE
    SYNTAX       SnmpAdminString
    MAX-ACCESS   read-only
    STATUS       current
    DESCRIPTION
        "Cisco UCS aaa:RadiusEp:rn managed object property"
    ::= { cucsAaaRadiusEpEntry 3 }

cucsAaaRadiusEpDescr OBJECT-TYPE
    SYNTAX       SnmpAdminString
    MAX-ACCESS   read-only
    STATUS       current
    DESCRIPTION
        "Cisco UCS aaa:RadiusEp:descr managed object property"
    ::= { cucsAaaRadiusEpEntry 4 }

cucsAaaRadiusEpFsmDescr OBJECT-TYPE
    SYNTAX       SnmpAdminString
    MAX-ACCESS   read-only
    STATUS       current
    DESCRIPTION
        "Cisco UCS aaa:RadiusEp:fsmDescr managed object property"
    ::= { cucsAaaRadiusEpEntry 5 }

cucsAaaRadiusEpFsmPrev OBJECT-TYPE
    SYNTAX       SnmpAdminString
    MAX-ACCESS   read-only
    STATUS       current
    DESCRIPTION
        "Cisco UCS aaa:RadiusEp:fsmPrev managed object property"
    ::= { cucsAaaRadiusEpEntry 6 }

cucsAaaRadiusEpFsmProgr OBJECT-TYPE
    SYNTAX       Gauge32
    MAX-ACCESS   read-only
    STATUS       current
    DESCRIPTION
        "Cisco UCS aaa:RadiusEp:fsmProgr managed object property"
    ::= { cucsAaaRadiusEpEntry 7 }

cucsAaaRadiusEpFsmRmtInvErrCode OBJECT-TYPE
    SYNTAX       Gauge32
    MAX-ACCESS   read-only
    STATUS       current
    DESCRIPTION
        "Cisco UCS aaa:RadiusEp:fsmRmtInvErrCode managed object property"
    ::= { cucsAaaRadiusEpEntry 8 }

cucsAaaRadiusEpFsmRmtInvErrDescr OBJECT-TYPE
    SYNTAX       SnmpAdminString
    MAX-ACCESS   read-only
    STATUS       current
    DESCRIPTION
        "Cisco UCS aaa:RadiusEp:fsmRmtInvErrDescr managed object property"
    ::= { cucsAaaRadiusEpEntry 9 }

cucsAaaRadiusEpFsmRmtInvRslt OBJECT-TYPE
    SYNTAX       CucsConditionRemoteInvRslt
    MAX-ACCESS   read-only
    STATUS       current
    DESCRIPTION
        "Cisco UCS aaa:RadiusEp:fsmRmtInvRslt managed object property"
    ::= { cucsAaaRadiusEpEntry 10 }

cucsAaaRadiusEpFsmStageDescr OBJECT-TYPE
    SYNTAX       SnmpAdminString
    MAX-ACCESS   read-only
    STATUS       current
    DESCRIPTION
        "Cisco UCS aaa:RadiusEp:fsmStageDescr managed object property"
    ::= { cucsAaaRadiusEpEntry 11 }

cucsAaaRadiusEpFsmStamp OBJECT-TYPE
    SYNTAX       DateAndTime
    MAX-ACCESS   read-only
    STATUS       current
    DESCRIPTION
        "Cisco UCS aaa:RadiusEp:fsmStamp managed object property"
    ::= { cucsAaaRadiusEpEntry 12 }

cucsAaaRadiusEpFsmStatus OBJECT-TYPE
    SYNTAX       SnmpAdminString
    MAX-ACCESS   read-only
    STATUS       current
    DESCRIPTION
        "Cisco UCS aaa:RadiusEp:fsmStatus managed object property"
    ::= { cucsAaaRadiusEpEntry 13 }

cucsAaaRadiusEpFsmTry OBJECT-TYPE
    SYNTAX       Gauge32
    MAX-ACCESS   read-only
    STATUS       current
    DESCRIPTION
        "Cisco UCS aaa:RadiusEp:fsmTry managed object property"
    ::= { cucsAaaRadiusEpEntry 14 }

cucsAaaRadiusEpIntId OBJECT-TYPE
    SYNTAX       SnmpAdminString
    MAX-ACCESS   read-only
    STATUS       current
    DESCRIPTION
        "Cisco UCS aaa:RadiusEp:intId managed object property"
    ::= { cucsAaaRadiusEpEntry 15 }

cucsAaaRadiusEpName OBJECT-TYPE
    SYNTAX       SnmpAdminString
    MAX-ACCESS   read-only
    STATUS       current
    DESCRIPTION
        "Cisco UCS aaa:RadiusEp:name managed object property"
    ::= { cucsAaaRadiusEpEntry 16 }

cucsAaaRadiusEpRetries OBJECT-TYPE
    SYNTAX       Gauge32
    MAX-ACCESS   read-only
    STATUS       current
    DESCRIPTION
        "Cisco UCS aaa:RadiusEp:retries managed object property"
    ::= { cucsAaaRadiusEpEntry 17 }

cucsAaaRadiusEpTimeout OBJECT-TYPE
    SYNTAX       Gauge32
    MAX-ACCESS   read-only
    STATUS       current
    DESCRIPTION
        "Cisco UCS aaa:RadiusEp:timeout managed object property"
    ::= { cucsAaaRadiusEpEntry 18 }

cucsAaaRadiusEpPolicyLevel OBJECT-TYPE
    SYNTAX       Gauge32
    MAX-ACCESS   read-only
    STATUS       current
    DESCRIPTION
        "Cisco UCS aaa:RadiusEp:policyLevel managed object property"
    ::= { cucsAaaRadiusEpEntry 19 }

cucsAaaRadiusEpPolicyOwner OBJECT-TYPE
    SYNTAX       CucsPolicyPolicyOwner
    MAX-ACCESS   read-only
    STATUS       current
    DESCRIPTION
        "Cisco UCS aaa:RadiusEp:policyOwner managed object property"
    ::= { cucsAaaRadiusEpEntry 20 }

cucsAaaRadiusEpFsmTable OBJECT-TYPE
    SYNTAX           SEQUENCE OF CucsAaaRadiusEpFsmEntry
    MAX-ACCESS       not-accessible
    STATUS           current
    DESCRIPTION
        "Cisco UCS aaa:RadiusEpFsm managed object table"
    ::= { cucsAaaObjects 47 }

cucsAaaRadiusEpFsmEntry OBJECT-TYPE
    SYNTAX           CucsAaaRadiusEpFsmEntry
    MAX-ACCESS       not-accessible
    STATUS           current
    DESCRIPTION
        "Entry for the cucsAaaRadiusEpFsmTable table."
    INDEX { cucsAaaRadiusEpFsmInstanceId }
    ::= { cucsAaaRadiusEpFsmTable 1 }

CucsAaaRadiusEpFsmEntry ::= SEQUENCE {
    cucsAaaRadiusEpFsmInstanceId                                     CucsManagedObjectId,
    cucsAaaRadiusEpFsmDn                                             CucsManagedObjectDn,
    cucsAaaRadiusEpFsmRn                                             SnmpAdminString,
    cucsAaaRadiusEpFsmCompletionTime                                 DateAndTime,
    cucsAaaRadiusEpFsmCurrentFsm                                     CucsAaaRadiusEpFsmCurrentFsm,
    cucsAaaRadiusEpFsmDescrData                                      SnmpAdminString,
    cucsAaaRadiusEpFsmFsmStatus                                      CucsFsmFsmStageStatus,
    cucsAaaRadiusEpFsmProgress                                       Gauge32,
    cucsAaaRadiusEpFsmRmtErrCode                                     Gauge32,
    cucsAaaRadiusEpFsmRmtErrDescr                                    SnmpAdminString,
    cucsAaaRadiusEpFsmRmtRslt                                        CucsConditionRemoteInvRslt
}

cucsAaaRadiusEpFsmInstanceId OBJECT-TYPE
    SYNTAX       CucsManagedObjectId
    MAX-ACCESS   not-accessible
    STATUS       current
    DESCRIPTION
        "Instance identifier of the managed object."
    ::= { cucsAaaRadiusEpFsmEntry 1 }

cucsAaaRadiusEpFsmDn OBJECT-TYPE
    SYNTAX       CucsManagedObjectDn
    MAX-ACCESS   read-only
    STATUS       current
    DESCRIPTION
        "Cisco UCS aaa:RadiusEpFsm:dn managed object property"
    ::= { cucsAaaRadiusEpFsmEntry 2 }

cucsAaaRadiusEpFsmRn OBJECT-TYPE
    SYNTAX       SnmpAdminString
    MAX-ACCESS   read-only
    STATUS       current
    DESCRIPTION
        "Cisco UCS aaa:RadiusEpFsm:rn managed object property"
    ::= { cucsAaaRadiusEpFsmEntry 3 }

cucsAaaRadiusEpFsmCompletionTime OBJECT-TYPE
    SYNTAX       DateAndTime
    MAX-ACCESS   read-only
    STATUS       current
    DESCRIPTION
        "Cisco UCS aaa:RadiusEpFsm:completionTime managed object property"
    ::= { cucsAaaRadiusEpFsmEntry 4 }

cucsAaaRadiusEpFsmCurrentFsm OBJECT-TYPE
    SYNTAX       CucsAaaRadiusEpFsmCurrentFsm
    MAX-ACCESS   read-only
    STATUS       current
    DESCRIPTION
        "Cisco UCS aaa:RadiusEpFsm:currentFsm managed object property"
    ::= { cucsAaaRadiusEpFsmEntry 5 }

cucsAaaRadiusEpFsmDescrData OBJECT-TYPE
    SYNTAX       SnmpAdminString
    MAX-ACCESS   read-only
    STATUS       current
    DESCRIPTION
        "Cisco UCS aaa:RadiusEpFsm:descr managed object property"
    ::= { cucsAaaRadiusEpFsmEntry 6 }

cucsAaaRadiusEpFsmFsmStatus OBJECT-TYPE
    SYNTAX       CucsFsmFsmStageStatus
    MAX-ACCESS   read-only
    STATUS       current
    DESCRIPTION
        "Cisco UCS aaa:RadiusEpFsm:fsmStatus managed object property"
    ::= { cucsAaaRadiusEpFsmEntry 7 }

cucsAaaRadiusEpFsmProgress OBJECT-TYPE
    SYNTAX       Gauge32
    MAX-ACCESS   read-only
    STATUS       current
    DESCRIPTION
        "Cisco UCS aaa:RadiusEpFsm:progress managed object property"
    ::= { cucsAaaRadiusEpFsmEntry 8 }

cucsAaaRadiusEpFsmRmtErrCode OBJECT-TYPE
    SYNTAX       Gauge32
    MAX-ACCESS   read-only
    STATUS       current
    DESCRIPTION
        "Cisco UCS aaa:RadiusEpFsm:rmtErrCode managed object property"
    ::= { cucsAaaRadiusEpFsmEntry 9 }

cucsAaaRadiusEpFsmRmtErrDescr OBJECT-TYPE
    SYNTAX       SnmpAdminString
    MAX-ACCESS   read-only
    STATUS       current
    DESCRIPTION
        "Cisco UCS aaa:RadiusEpFsm:rmtErrDescr managed object property"
    ::= { cucsAaaRadiusEpFsmEntry 10 }

cucsAaaRadiusEpFsmRmtRslt OBJECT-TYPE
    SYNTAX       CucsConditionRemoteInvRslt
    MAX-ACCESS   read-only
    STATUS       current
    DESCRIPTION
        "Cisco UCS aaa:RadiusEpFsm:rmtRslt managed object property"
    ::= { cucsAaaRadiusEpFsmEntry 11 }

cucsAaaRadiusEpFsmStageTable OBJECT-TYPE
    SYNTAX           SEQUENCE OF CucsAaaRadiusEpFsmStageEntry
    MAX-ACCESS       not-accessible
    STATUS           current
    DESCRIPTION
        "Cisco UCS aaa:RadiusEpFsmStage managed object table"
    ::= { cucsAaaObjects 48 }

cucsAaaRadiusEpFsmStageEntry OBJECT-TYPE
    SYNTAX           CucsAaaRadiusEpFsmStageEntry
    MAX-ACCESS       not-accessible
    STATUS           current
    DESCRIPTION
        "Entry for the cucsAaaRadiusEpFsmStageTable table."
    INDEX { cucsAaaRadiusEpFsmStageInstanceId }
    ::= { cucsAaaRadiusEpFsmStageTable 1 }

CucsAaaRadiusEpFsmStageEntry ::= SEQUENCE {
    cucsAaaRadiusEpFsmStageInstanceId                                CucsManagedObjectId,
    cucsAaaRadiusEpFsmStageDn                                        CucsManagedObjectDn,
    cucsAaaRadiusEpFsmStageRn                                        SnmpAdminString,
    cucsAaaRadiusEpFsmStageDescrData                                 SnmpAdminString,
    cucsAaaRadiusEpFsmStageLastUpdateTime                            DateAndTime,
    cucsAaaRadiusEpFsmStageName                                      CucsAaaRadiusEpFsmStageName,
    cucsAaaRadiusEpFsmStageOrder                                     Gauge32,
    cucsAaaRadiusEpFsmStageRetry                                     Gauge32,
    cucsAaaRadiusEpFsmStageStageStatus                               CucsFsmFsmStageStatus
}

cucsAaaRadiusEpFsmStageInstanceId OBJECT-TYPE
    SYNTAX       CucsManagedObjectId
    MAX-ACCESS   not-accessible
    STATUS       current
    DESCRIPTION
        "Instance identifier of the managed object."
    ::= { cucsAaaRadiusEpFsmStageEntry 1 }

cucsAaaRadiusEpFsmStageDn OBJECT-TYPE
    SYNTAX       CucsManagedObjectDn
    MAX-ACCESS   read-only
    STATUS       current
    DESCRIPTION
        "Cisco UCS aaa:RadiusEpFsmStage:dn managed object property"
    ::= { cucsAaaRadiusEpFsmStageEntry 2 }

cucsAaaRadiusEpFsmStageRn OBJECT-TYPE
    SYNTAX       SnmpAdminString
    MAX-ACCESS   read-only
    STATUS       current
    DESCRIPTION
        "Cisco UCS aaa:RadiusEpFsmStage:rn managed object property"
    ::= { cucsAaaRadiusEpFsmStageEntry 3 }

cucsAaaRadiusEpFsmStageDescrData OBJECT-TYPE
    SYNTAX       SnmpAdminString
    MAX-ACCESS   read-only
    STATUS       current
    DESCRIPTION
        "Cisco UCS aaa:RadiusEpFsmStage:descr managed object property"
    ::= { cucsAaaRadiusEpFsmStageEntry 4 }

cucsAaaRadiusEpFsmStageLastUpdateTime OBJECT-TYPE
    SYNTAX       DateAndTime
    MAX-ACCESS   read-only
    STATUS       current
    DESCRIPTION
        "Cisco UCS aaa:RadiusEpFsmStage:lastUpdateTime
        managed object property"
    ::= { cucsAaaRadiusEpFsmStageEntry 5 }

cucsAaaRadiusEpFsmStageName OBJECT-TYPE
    SYNTAX       CucsAaaRadiusEpFsmStageName
    MAX-ACCESS   read-only
    STATUS       current
    DESCRIPTION
        "Cisco UCS aaa:RadiusEpFsmStage:name managed object property"
    ::= { cucsAaaRadiusEpFsmStageEntry 6 }

cucsAaaRadiusEpFsmStageOrder OBJECT-TYPE
    SYNTAX       Gauge32
    MAX-ACCESS   read-only
    STATUS       current
    DESCRIPTION
        "Cisco UCS aaa:RadiusEpFsmStage:order managed object property"
    ::= { cucsAaaRadiusEpFsmStageEntry 7 }

cucsAaaRadiusEpFsmStageRetry OBJECT-TYPE
    SYNTAX       Gauge32
    MAX-ACCESS   read-only
    STATUS       current
    DESCRIPTION
        "Cisco UCS aaa:RadiusEpFsmStage:retry managed object property"
    ::= { cucsAaaRadiusEpFsmStageEntry 8 }

cucsAaaRadiusEpFsmStageStageStatus OBJECT-TYPE
    SYNTAX       CucsFsmFsmStageStatus
    MAX-ACCESS   read-only
    STATUS       current
    DESCRIPTION
        "Cisco UCS aaa:RadiusEpFsmStage:stageStatus managed
        object property"
    ::= { cucsAaaRadiusEpFsmStageEntry 9 }

cucsAaaRadiusProviderTable OBJECT-TYPE
    SYNTAX           SEQUENCE OF CucsAaaRadiusProviderEntry
    MAX-ACCESS       not-accessible
    STATUS           current
    DESCRIPTION
        "Cisco UCS aaa:RadiusProvider managed object table"
    ::= { cucsAaaObjects 22 }

cucsAaaRadiusProviderEntry OBJECT-TYPE
    SYNTAX           CucsAaaRadiusProviderEntry
    MAX-ACCESS       not-accessible
    STATUS           current
    DESCRIPTION
        "Entry for the cucsAaaRadiusProviderTable table."
    INDEX { cucsAaaRadiusProviderInstanceId }
    ::= { cucsAaaRadiusProviderTable 1 }

CucsAaaRadiusProviderEntry ::= SEQUENCE {
    cucsAaaRadiusProviderInstanceId                                  CucsManagedObjectId,
    cucsAaaRadiusProviderDn                                          CucsManagedObjectDn,
    cucsAaaRadiusProviderRn                                          SnmpAdminString,
    cucsAaaRadiusProviderAuthPort                                    Gauge32,
    cucsAaaRadiusProviderDescr                                       SnmpAdminString,
    cucsAaaRadiusProviderEncKey                                      SnmpAdminString,
    cucsAaaRadiusProviderKey                                         SnmpAdminString,
    cucsAaaRadiusProviderKeySet                                      TruthValue,
    cucsAaaRadiusProviderName                                        SnmpAdminString,
    cucsAaaRadiusProviderOrder                                       Gauge32,
    cucsAaaRadiusProviderRetries                                     Gauge32,
    cucsAaaRadiusProviderService                                     CucsAaaRadiusService,
    cucsAaaRadiusProviderTimeout                                     Gauge32
}

cucsAaaRadiusProviderInstanceId OBJECT-TYPE
    SYNTAX       CucsManagedObjectId
    MAX-ACCESS   not-accessible
    STATUS       current
    DESCRIPTION
        "Instance identifier of the managed object."
    ::= { cucsAaaRadiusProviderEntry 1 }

cucsAaaRadiusProviderDn OBJECT-TYPE
    SYNTAX       CucsManagedObjectDn
    MAX-ACCESS   read-only
    STATUS       current
    DESCRIPTION
        "Cisco UCS aaa:RadiusProvider:dn managed object property"
    ::= { cucsAaaRadiusProviderEntry 2 }

cucsAaaRadiusProviderRn OBJECT-TYPE
    SYNTAX       SnmpAdminString
    MAX-ACCESS   read-only
    STATUS       current
    DESCRIPTION
        "Cisco UCS aaa:RadiusProvider:rn managed object property"
    ::= { cucsAaaRadiusProviderEntry 3 }

cucsAaaRadiusProviderAuthPort OBJECT-TYPE
    SYNTAX       Gauge32
    MAX-ACCESS   read-only
    STATUS       current
    DESCRIPTION
        "Cisco UCS aaa:RadiusProvider:authPort managed object property"
    ::= { cucsAaaRadiusProviderEntry 4 }

cucsAaaRadiusProviderDescr OBJECT-TYPE
    SYNTAX       SnmpAdminString
    MAX-ACCESS   read-only
    STATUS       current
    DESCRIPTION
        "Cisco UCS aaa:RadiusProvider:descr managed object property"
    ::= { cucsAaaRadiusProviderEntry 5 }

cucsAaaRadiusProviderEncKey OBJECT-TYPE
    SYNTAX       SnmpAdminString
    MAX-ACCESS   read-only
    STATUS       current
    DESCRIPTION
        "Cisco UCS aaa:RadiusProvider:encKey managed object property"
    ::= { cucsAaaRadiusProviderEntry 6 }

cucsAaaRadiusProviderKey OBJECT-TYPE
    SYNTAX       SnmpAdminString
    MAX-ACCESS   read-only
    STATUS       current
    DESCRIPTION
        "Cisco UCS aaa:RadiusProvider:key managed object property"
    ::= { cucsAaaRadiusProviderEntry 8 }

cucsAaaRadiusProviderKeySet OBJECT-TYPE
    SYNTAX       TruthValue
    MAX-ACCESS   read-only
    STATUS       current
    DESCRIPTION
        "Cisco UCS aaa:RadiusProvider:keySet managed object property"
    ::= { cucsAaaRadiusProviderEntry 9 }

cucsAaaRadiusProviderName OBJECT-TYPE
    SYNTAX       SnmpAdminString
    MAX-ACCESS   read-only
    STATUS       current
    DESCRIPTION
        "Cisco UCS aaa:RadiusProvider:name managed object property"
    ::= { cucsAaaRadiusProviderEntry 10 }

cucsAaaRadiusProviderOrder OBJECT-TYPE
    SYNTAX       Gauge32
    MAX-ACCESS   read-only
    STATUS       current
    DESCRIPTION
        "Cisco UCS aaa:RadiusProvider:order managed object property"
    ::= { cucsAaaRadiusProviderEntry 11 }

cucsAaaRadiusProviderRetries OBJECT-TYPE
    SYNTAX       Gauge32
    MAX-ACCESS   read-only
    STATUS       current
    DESCRIPTION
        "Cisco UCS aaa:RadiusProvider:retries managed object property"
    ::= { cucsAaaRadiusProviderEntry 12 }

cucsAaaRadiusProviderService OBJECT-TYPE
    SYNTAX       CucsAaaRadiusService
    MAX-ACCESS   read-only
    STATUS       current
    DESCRIPTION
        "Cisco UCS aaa:RadiusProvider:service managed object property"
    ::= { cucsAaaRadiusProviderEntry 13 }

cucsAaaRadiusProviderTimeout OBJECT-TYPE
    SYNTAX       Gauge32
    MAX-ACCESS   read-only
    STATUS       current
    DESCRIPTION
        "Cisco UCS aaa:RadiusProvider:timeout managed object property"
    ::= { cucsAaaRadiusProviderEntry 14 }

cucsAaaRealmFsmTable OBJECT-TYPE
    SYNTAX           SEQUENCE OF CucsAaaRealmFsmEntry
    MAX-ACCESS       not-accessible
    STATUS           current
    DESCRIPTION
        "Cisco UCS aaa:RealmFsm managed object table"
    ::= { cucsAaaObjects 49 }

cucsAaaRealmFsmEntry OBJECT-TYPE
    SYNTAX           CucsAaaRealmFsmEntry
    MAX-ACCESS       not-accessible
    STATUS           current
    DESCRIPTION
        "Entry for the cucsAaaRealmFsmTable table."
    INDEX { cucsAaaRealmFsmInstanceId }
    ::= { cucsAaaRealmFsmTable 1 }

CucsAaaRealmFsmEntry ::= SEQUENCE {
    cucsAaaRealmFsmInstanceId                                        CucsManagedObjectId,
    cucsAaaRealmFsmDn                                                CucsManagedObjectDn,
    cucsAaaRealmFsmRn                                                SnmpAdminString,
    cucsAaaRealmFsmCompletionTime                                    DateAndTime,
    cucsAaaRealmFsmCurrentFsm                                        CucsAaaRealmFsmCurrentFsm,
    cucsAaaRealmFsmDescr                                             SnmpAdminString,
    cucsAaaRealmFsmFsmStatus                                         CucsFsmFsmStageStatus,
    cucsAaaRealmFsmProgress                                          Gauge32,
    cucsAaaRealmFsmRmtErrCode                                        Gauge32,
    cucsAaaRealmFsmRmtErrDescr                                       SnmpAdminString,
    cucsAaaRealmFsmRmtRslt                                           CucsConditionRemoteInvRslt
}

cucsAaaRealmFsmInstanceId OBJECT-TYPE
    SYNTAX       CucsManagedObjectId
    MAX-ACCESS   not-accessible
    STATUS       current
    DESCRIPTION
        "Instance identifier of the managed object."
    ::= { cucsAaaRealmFsmEntry 1 }

cucsAaaRealmFsmDn OBJECT-TYPE
    SYNTAX       CucsManagedObjectDn
    MAX-ACCESS   read-only
    STATUS       current
    DESCRIPTION
        "Cisco UCS aaa:RealmFsm:dn managed object property"
    ::= { cucsAaaRealmFsmEntry 2 }

cucsAaaRealmFsmRn OBJECT-TYPE
    SYNTAX       SnmpAdminString
    MAX-ACCESS   read-only
    STATUS       current
    DESCRIPTION
        "Cisco UCS aaa:RealmFsm:rn managed object property"
    ::= { cucsAaaRealmFsmEntry 3 }

cucsAaaRealmFsmCompletionTime OBJECT-TYPE
    SYNTAX       DateAndTime
    MAX-ACCESS   read-only
    STATUS       current
    DESCRIPTION
        "Cisco UCS aaa:RealmFsm:completionTime managed object property"
    ::= { cucsAaaRealmFsmEntry 4 }

cucsAaaRealmFsmCurrentFsm OBJECT-TYPE
    SYNTAX       CucsAaaRealmFsmCurrentFsm
    MAX-ACCESS   read-only
    STATUS       current
    DESCRIPTION
        "Cisco UCS aaa:RealmFsm:currentFsm managed object property"
    ::= { cucsAaaRealmFsmEntry 5 }

cucsAaaRealmFsmDescr OBJECT-TYPE
    SYNTAX       SnmpAdminString
    MAX-ACCESS   read-only
    STATUS       current
    DESCRIPTION
        "Cisco UCS aaa:RealmFsm:descr managed object property"
    ::= { cucsAaaRealmFsmEntry 6 }

cucsAaaRealmFsmFsmStatus OBJECT-TYPE
    SYNTAX       CucsFsmFsmStageStatus
    MAX-ACCESS   read-only
    STATUS       current
    DESCRIPTION
        "Cisco UCS aaa:RealmFsm:fsmStatus managed object property"
    ::= { cucsAaaRealmFsmEntry 7 }

cucsAaaRealmFsmProgress OBJECT-TYPE
    SYNTAX       Gauge32
    MAX-ACCESS   read-only
    STATUS       current
    DESCRIPTION
        "Cisco UCS aaa:RealmFsm:progress managed object property"
    ::= { cucsAaaRealmFsmEntry 8 }

cucsAaaRealmFsmRmtErrCode OBJECT-TYPE
    SYNTAX       Gauge32
    MAX-ACCESS   read-only
    STATUS       current
    DESCRIPTION
        "Cisco UCS aaa:RealmFsm:rmtErrCode managed object property"
    ::= { cucsAaaRealmFsmEntry 9 }

cucsAaaRealmFsmRmtErrDescr OBJECT-TYPE
    SYNTAX       SnmpAdminString
    MAX-ACCESS   read-only
    STATUS       current
    DESCRIPTION
        "Cisco UCS aaa:RealmFsm:rmtErrDescr managed object property"
    ::= { cucsAaaRealmFsmEntry 10 }

cucsAaaRealmFsmRmtRslt OBJECT-TYPE
    SYNTAX       CucsConditionRemoteInvRslt
    MAX-ACCESS   read-only
    STATUS       current
    DESCRIPTION
        "Cisco UCS aaa:RealmFsm:rmtRslt managed object property"
    ::= { cucsAaaRealmFsmEntry 11 }

cucsAaaRealmFsmStageTable OBJECT-TYPE
    SYNTAX           SEQUENCE OF CucsAaaRealmFsmStageEntry
    MAX-ACCESS       not-accessible
    STATUS           current
    DESCRIPTION
        "Cisco UCS aaa:RealmFsmStage managed object table"
    ::= { cucsAaaObjects 50 }

cucsAaaRealmFsmStageEntry OBJECT-TYPE
    SYNTAX           CucsAaaRealmFsmStageEntry
    MAX-ACCESS       not-accessible
    STATUS           current
    DESCRIPTION
        "Entry for the cucsAaaRealmFsmStageTable table."
    INDEX { cucsAaaRealmFsmStageInstanceId }
    ::= { cucsAaaRealmFsmStageTable 1 }

CucsAaaRealmFsmStageEntry ::= SEQUENCE {
    cucsAaaRealmFsmStageInstanceId                                   CucsManagedObjectId,
    cucsAaaRealmFsmStageDn                                           CucsManagedObjectDn,
    cucsAaaRealmFsmStageRn                                           SnmpAdminString,
    cucsAaaRealmFsmStageDescr                                        SnmpAdminString,
    cucsAaaRealmFsmStageLastUpdateTime                               DateAndTime,
    cucsAaaRealmFsmStageName                                         CucsAaaRealmFsmStageName,
    cucsAaaRealmFsmStageOrder                                        Gauge32,
    cucsAaaRealmFsmStageRetry                                        Gauge32,
    cucsAaaRealmFsmStageStageStatus                                  CucsFsmFsmStageStatus
}

cucsAaaRealmFsmStageInstanceId OBJECT-TYPE
    SYNTAX       CucsManagedObjectId
    MAX-ACCESS   not-accessible
    STATUS       current
    DESCRIPTION
        "Instance identifier of the managed object."
    ::= { cucsAaaRealmFsmStageEntry 1 }

cucsAaaRealmFsmStageDn OBJECT-TYPE
    SYNTAX       CucsManagedObjectDn
    MAX-ACCESS   read-only
    STATUS       current
    DESCRIPTION
        "Cisco UCS aaa:RealmFsmStage:dn managed object property"
    ::= { cucsAaaRealmFsmStageEntry 2 }

cucsAaaRealmFsmStageRn OBJECT-TYPE
    SYNTAX       SnmpAdminString
    MAX-ACCESS   read-only
    STATUS       current
    DESCRIPTION
        "Cisco UCS aaa:RealmFsmStage:rn managed object property"
    ::= { cucsAaaRealmFsmStageEntry 3 }

cucsAaaRealmFsmStageDescr OBJECT-TYPE
    SYNTAX       SnmpAdminString
    MAX-ACCESS   read-only
    STATUS       current
    DESCRIPTION
        "Cisco UCS aaa:RealmFsmStage:descr managed object property"
    ::= { cucsAaaRealmFsmStageEntry 4 }

cucsAaaRealmFsmStageLastUpdateTime OBJECT-TYPE
    SYNTAX       DateAndTime
    MAX-ACCESS   read-only
    STATUS       current
    DESCRIPTION
        "Cisco UCS aaa:RealmFsmStage:lastUpdateTime managed
        object property"
    ::= { cucsAaaRealmFsmStageEntry 5 }

cucsAaaRealmFsmStageName OBJECT-TYPE
    SYNTAX       CucsAaaRealmFsmStageName
    MAX-ACCESS   read-only
    STATUS       current
    DESCRIPTION
        "Cisco UCS aaa:RealmFsmStage:name managed object property"
    ::= { cucsAaaRealmFsmStageEntry 6 }

cucsAaaRealmFsmStageOrder OBJECT-TYPE
    SYNTAX       Gauge32
    MAX-ACCESS   read-only
    STATUS       current
    DESCRIPTION
        "Cisco UCS aaa:RealmFsmStage:order managed object property"
    ::= { cucsAaaRealmFsmStageEntry 7 }

cucsAaaRealmFsmStageRetry OBJECT-TYPE
    SYNTAX       Gauge32
    MAX-ACCESS   read-only
    STATUS       current
    DESCRIPTION
        "Cisco UCS aaa:RealmFsmStage:retry managed object property"
    ::= { cucsAaaRealmFsmStageEntry 8 }

cucsAaaRealmFsmStageStageStatus OBJECT-TYPE
    SYNTAX       CucsFsmFsmStageStatus
    MAX-ACCESS   read-only
    STATUS       current
    DESCRIPTION
        "Cisco UCS aaa:RealmFsmStage:stageStatus managed object property"
    ::= { cucsAaaRealmFsmStageEntry 9 }

cucsAaaRealmFsmTaskTable OBJECT-TYPE
    SYNTAX           SEQUENCE OF CucsAaaRealmFsmTaskEntry
    MAX-ACCESS       not-accessible
    STATUS           current
    DESCRIPTION
        "Cisco UCS aaa:RealmFsmTask managed object table"
    ::= { cucsAaaObjects 23 }

cucsAaaRealmFsmTaskEntry OBJECT-TYPE
    SYNTAX           CucsAaaRealmFsmTaskEntry
    MAX-ACCESS       not-accessible
    STATUS           current
    DESCRIPTION
        "Entry for the cucsAaaRealmFsmTaskTable table."
    INDEX { cucsAaaRealmFsmTaskInstanceId }
    ::= { cucsAaaRealmFsmTaskTable 1 }

CucsAaaRealmFsmTaskEntry ::= SEQUENCE {
    cucsAaaRealmFsmTaskInstanceId                                    CucsManagedObjectId,
    cucsAaaRealmFsmTaskDn                                            CucsManagedObjectDn,
    cucsAaaRealmFsmTaskRn                                            SnmpAdminString,
    cucsAaaRealmFsmTaskCompletion                                    CucsFsmCompletion,
    cucsAaaRealmFsmTaskFlags                                         CucsFsmFlags,
    cucsAaaRealmFsmTaskItem                                          CucsAaaRealmFsmTaskItem,
    cucsAaaRealmFsmTaskSeqId                                         Gauge32
}

cucsAaaRealmFsmTaskInstanceId OBJECT-TYPE
    SYNTAX       CucsManagedObjectId
    MAX-ACCESS   not-accessible
    STATUS       current
    DESCRIPTION
        "Instance identifier of the managed object."
    ::= { cucsAaaRealmFsmTaskEntry 1 }

cucsAaaRealmFsmTaskDn OBJECT-TYPE
    SYNTAX       CucsManagedObjectDn
    MAX-ACCESS   read-only
    STATUS       current
    DESCRIPTION
        "Cisco UCS aaa:RealmFsmTask:dn managed object property"
    ::= { cucsAaaRealmFsmTaskEntry 2 }

cucsAaaRealmFsmTaskRn OBJECT-TYPE
    SYNTAX       SnmpAdminString
    MAX-ACCESS   read-only
    STATUS       current
    DESCRIPTION
        "Cisco UCS aaa:RealmFsmTask:rn managed object property"
    ::= { cucsAaaRealmFsmTaskEntry 3 }

cucsAaaRealmFsmTaskCompletion OBJECT-TYPE
    SYNTAX       CucsFsmCompletion
    MAX-ACCESS   read-only
    STATUS       current
    DESCRIPTION
        "Cisco UCS aaa:RealmFsmTask:completion managed object property"
    ::= { cucsAaaRealmFsmTaskEntry 4 }

cucsAaaRealmFsmTaskFlags OBJECT-TYPE
    SYNTAX       CucsFsmFlags
    MAX-ACCESS   read-only
    STATUS       current
    DESCRIPTION
        "Cisco UCS aaa:RealmFsmTask:flags managed object property"
    ::= { cucsAaaRealmFsmTaskEntry 5 }

cucsAaaRealmFsmTaskItem OBJECT-TYPE
    SYNTAX       CucsAaaRealmFsmTaskItem
    MAX-ACCESS   read-only
    STATUS       current
    DESCRIPTION
        "Cisco UCS aaa:RealmFsmTask:item managed object property"
    ::= { cucsAaaRealmFsmTaskEntry 6 }

cucsAaaRealmFsmTaskSeqId OBJECT-TYPE
    SYNTAX       Gauge32
    MAX-ACCESS   read-only
    STATUS       current
    DESCRIPTION
        "Cisco UCS aaa:RealmFsmTask:seqId managed object property"
    ::= { cucsAaaRealmFsmTaskEntry 7 }

cucsAaaRemoteUserTable OBJECT-TYPE
    SYNTAX           SEQUENCE OF CucsAaaRemoteUserEntry
    MAX-ACCESS       not-accessible
    STATUS           current
    DESCRIPTION
        "Cisco UCS aaa:RemoteUser managed object table"
    ::= { cucsAaaObjects 24 }

cucsAaaRemoteUserEntry OBJECT-TYPE
    SYNTAX           CucsAaaRemoteUserEntry
    MAX-ACCESS       not-accessible
    STATUS           current
    DESCRIPTION
        "Entry for the cucsAaaRemoteUserTable table."
    INDEX { cucsAaaRemoteUserInstanceId }
    ::= { cucsAaaRemoteUserTable 1 }

CucsAaaRemoteUserEntry ::= SEQUENCE {
    cucsAaaRemoteUserInstanceId                                      CucsManagedObjectId,
    cucsAaaRemoteUserDn                                              CucsManagedObjectDn,
    cucsAaaRemoteUserRn                                              SnmpAdminString,
    cucsAaaRemoteUserDescr                                           SnmpAdminString,
    cucsAaaRemoteUserName                                            SnmpAdminString,
    cucsAaaRemoteUserPwd                                             SnmpAdminString,
    cucsAaaRemoteUserPwdSet                                          TruthValue,
    cucsAaaRemoteUserConfigState                                     CucsAaaConfigState,
    cucsAaaRemoteUserConfigStatusMessage                             SnmpAdminString
}

cucsAaaRemoteUserInstanceId OBJECT-TYPE
    SYNTAX       CucsManagedObjectId
    MAX-ACCESS   not-accessible
    STATUS       current
    DESCRIPTION
        "Instance identifier of the managed object."
    ::= { cucsAaaRemoteUserEntry 1 }

cucsAaaRemoteUserDn OBJECT-TYPE
    SYNTAX       CucsManagedObjectDn
    MAX-ACCESS   read-only
    STATUS       current
    DESCRIPTION
        "Cisco UCS aaa:RemoteUser:dn managed object property"
    ::= { cucsAaaRemoteUserEntry 2 }

cucsAaaRemoteUserRn OBJECT-TYPE
    SYNTAX       SnmpAdminString
    MAX-ACCESS   read-only
    STATUS       current
    DESCRIPTION
        "Cisco UCS aaa:RemoteUser:rn managed object property"
    ::= { cucsAaaRemoteUserEntry 3 }

cucsAaaRemoteUserDescr OBJECT-TYPE
    SYNTAX       SnmpAdminString
    MAX-ACCESS   read-only
    STATUS       current
    DESCRIPTION
        "Cisco UCS aaa:RemoteUser:descr managed object property"
    ::= { cucsAaaRemoteUserEntry 4 }

cucsAaaRemoteUserName OBJECT-TYPE
    SYNTAX       SnmpAdminString
    MAX-ACCESS   read-only
    STATUS       current
    DESCRIPTION
        "Cisco UCS aaa:RemoteUser:name managed object property"
    ::= { cucsAaaRemoteUserEntry 6 }

cucsAaaRemoteUserPwd OBJECT-TYPE
    SYNTAX       SnmpAdminString
    MAX-ACCESS   read-only
    STATUS       current
    DESCRIPTION
        "Cisco UCS aaa:RemoteUser:pwd managed object property"
    ::= { cucsAaaRemoteUserEntry 7 }

cucsAaaRemoteUserPwdSet OBJECT-TYPE
    SYNTAX       TruthValue
    MAX-ACCESS   read-only
    STATUS       current
    DESCRIPTION
        "Cisco UCS aaa:RemoteUser:pwdSet managed object property"
    ::= { cucsAaaRemoteUserEntry 8 }

cucsAaaRemoteUserConfigState OBJECT-TYPE
    SYNTAX       CucsAaaConfigState
    MAX-ACCESS   read-only
    STATUS       current
    DESCRIPTION
        "Cisco UCS aaa:RemoteUser:configState managed object property"
    ::= { cucsAaaRemoteUserEntry 9 }

cucsAaaRemoteUserConfigStatusMessage OBJECT-TYPE
    SYNTAX       SnmpAdminString
    MAX-ACCESS   read-only
    STATUS       current
    DESCRIPTION
        "Cisco UCS aaa:RemoteUser:configStatusMessage managed
        object property"
    ::= { cucsAaaRemoteUserEntry 10 }

cucsAaaRoleTable OBJECT-TYPE
    SYNTAX           SEQUENCE OF CucsAaaRoleEntry
    MAX-ACCESS       not-accessible
    STATUS           current
    DESCRIPTION
        "Cisco UCS aaa:Role managed object table"
    ::= { cucsAaaObjects 25 }

cucsAaaRoleEntry OBJECT-TYPE
    SYNTAX           CucsAaaRoleEntry
    MAX-ACCESS       not-accessible
    STATUS           current
    DESCRIPTION
        "Entry for the cucsAaaRoleTable table."
    INDEX { cucsAaaRoleInstanceId }
    ::= { cucsAaaRoleTable 1 }

CucsAaaRoleEntry ::= SEQUENCE {
    cucsAaaRoleInstanceId                                            CucsManagedObjectId,
    cucsAaaRoleDn                                                    CucsManagedObjectDn,
    cucsAaaRoleRn                                                    SnmpAdminString,
    cucsAaaRoleDescr                                                 SnmpAdminString,
    cucsAaaRoleIntId                                                 SnmpAdminString,
    cucsAaaRoleName                                                  SnmpAdminString,
    cucsAaaRolePriv                                                  CucsAaaAccess,
    cucsAaaRoleConfigState                                           CucsAaaConfigState,
    cucsAaaRoleConfigStatusMessage                                   SnmpAdminString,
    cucsAaaRolePolicyLevel                                           Gauge32,
    cucsAaaRolePolicyOwner                                           CucsPolicyPolicyOwner
}

cucsAaaRoleInstanceId OBJECT-TYPE
    SYNTAX       CucsManagedObjectId
    MAX-ACCESS   not-accessible
    STATUS       current
    DESCRIPTION
        "Instance identifier of the managed object."
    ::= { cucsAaaRoleEntry 1 }

cucsAaaRoleDn OBJECT-TYPE
    SYNTAX       CucsManagedObjectDn
    MAX-ACCESS   read-only
    STATUS       current
    DESCRIPTION
        "Cisco UCS aaa:Role:dn managed object property"
    ::= { cucsAaaRoleEntry 2 }

cucsAaaRoleRn OBJECT-TYPE
    SYNTAX       SnmpAdminString
    MAX-ACCESS   read-only
    STATUS       current
    DESCRIPTION
        "Cisco UCS aaa:Role:rn managed object property"
    ::= { cucsAaaRoleEntry 3 }

cucsAaaRoleDescr OBJECT-TYPE
    SYNTAX       SnmpAdminString
    MAX-ACCESS   read-only
    STATUS       current
    DESCRIPTION
        "Cisco UCS aaa:Role:descr managed object property"
    ::= { cucsAaaRoleEntry 4 }

cucsAaaRoleIntId OBJECT-TYPE
    SYNTAX       SnmpAdminString
    MAX-ACCESS   read-only
    STATUS       current
    DESCRIPTION
        "Cisco UCS aaa:Role:intId managed object property"
    ::= { cucsAaaRoleEntry 5 }

cucsAaaRoleName OBJECT-TYPE
    SYNTAX       SnmpAdminString
    MAX-ACCESS   read-only
    STATUS       current
    DESCRIPTION
        "Cisco UCS aaa:Role:name managed object property"
    ::= { cucsAaaRoleEntry 6 }

cucsAaaRolePriv OBJECT-TYPE
    SYNTAX       CucsAaaAccess
    MAX-ACCESS   read-only
    STATUS       current
    DESCRIPTION
        "Cisco UCS aaa:Role:priv managed object property"
    ::= { cucsAaaRoleEntry 7 }

cucsAaaRoleConfigState OBJECT-TYPE
    SYNTAX       CucsAaaConfigState
    MAX-ACCESS   read-only
    STATUS       current
    DESCRIPTION
        "Cisco UCS aaa:Role:configState managed object property"
    ::= { cucsAaaRoleEntry 8 }

cucsAaaRoleConfigStatusMessage OBJECT-TYPE
    SYNTAX       SnmpAdminString
    MAX-ACCESS   read-only
    STATUS       current
    DESCRIPTION
        "Cisco UCS aaa:Role:configStatusMessage managed object property"
    ::= { cucsAaaRoleEntry 9 }

cucsAaaRolePolicyLevel OBJECT-TYPE
    SYNTAX       Gauge32
    MAX-ACCESS   read-only
    STATUS       current
    DESCRIPTION
        "Cisco UCS aaa:Role:policyLevel managed object property"
    ::= { cucsAaaRoleEntry 10 }

cucsAaaRolePolicyOwner OBJECT-TYPE
    SYNTAX       CucsPolicyPolicyOwner
    MAX-ACCESS   read-only
    STATUS       current
    DESCRIPTION
        "Cisco UCS aaa:Role:policyOwner managed object property"
    ::= { cucsAaaRoleEntry 11 }

cucsAaaSessionTable OBJECT-TYPE
    SYNTAX           SEQUENCE OF CucsAaaSessionEntry
    MAX-ACCESS       not-accessible
    STATUS           current
    DESCRIPTION
        "Cisco UCS aaa:Session managed object table"
    ::= { cucsAaaObjects 26 }

cucsAaaSessionEntry OBJECT-TYPE
    SYNTAX           CucsAaaSessionEntry
    MAX-ACCESS       not-accessible
    STATUS           current
    DESCRIPTION
        "Entry for the cucsAaaSessionTable table."
    INDEX { cucsAaaSessionInstanceId }
    ::= { cucsAaaSessionTable 1 }

CucsAaaSessionEntry ::= SEQUENCE {
    cucsAaaSessionInstanceId                                         CucsManagedObjectId,
    cucsAaaSessionDn                                                 CucsManagedObjectDn,
    cucsAaaSessionRn                                                 SnmpAdminString,
    cucsAaaSessionHost                                               SnmpAdminString,
    cucsAaaSessionId                                                 SnmpAdminString,
    cucsAaaSessionIntDel                                             TruthValue,
    cucsAaaSessionLoginTime                                          DateAndTime,
    cucsAaaSessionPid                                                Gauge32,
    cucsAaaSessionSwitchId                                           CucsNetworkSwitchId,
    cucsAaaSessionTerm                                               SnmpAdminString,
    cucsAaaSessionUi                                                 CucsAaaUserInterface,
    cucsAaaSessionUser                                               SnmpAdminString,
    cucsAaaSessionRefreshPeriod                                      Gauge32,
    cucsAaaSessionSessionTimeout                                     Gauge32
}

cucsAaaSessionInstanceId OBJECT-TYPE
    SYNTAX       CucsManagedObjectId
    MAX-ACCESS   not-accessible
    STATUS       current
    DESCRIPTION
        "Instance identifier of the managed object."
    ::= { cucsAaaSessionEntry 1 }

cucsAaaSessionDn OBJECT-TYPE
    SYNTAX       CucsManagedObjectDn
    MAX-ACCESS   read-only
    STATUS       current
    DESCRIPTION
        "Cisco UCS aaa:Session:dn managed object property"
    ::= { cucsAaaSessionEntry 2 }

cucsAaaSessionRn OBJECT-TYPE
    SYNTAX       SnmpAdminString
    MAX-ACCESS   read-only
    STATUS       current
    DESCRIPTION
        "Cisco UCS aaa:Session:rn managed object property"
    ::= { cucsAaaSessionEntry 3 }

cucsAaaSessionHost OBJECT-TYPE
    SYNTAX       SnmpAdminString
    MAX-ACCESS   read-only
    STATUS       current
    DESCRIPTION
        "Cisco UCS aaa:Session:host managed object property"
    ::= { cucsAaaSessionEntry 4 }

cucsAaaSessionId OBJECT-TYPE
    SYNTAX       SnmpAdminString
    MAX-ACCESS   read-only
    STATUS       current
    DESCRIPTION
        "Cisco UCS aaa:Session:id managed object property"
    ::= { cucsAaaSessionEntry 5 }

cucsAaaSessionIntDel OBJECT-TYPE
    SYNTAX       TruthValue
    MAX-ACCESS   read-only
    STATUS       current
    DESCRIPTION
        "Cisco UCS aaa:Session:intDel managed object property"
    ::= { cucsAaaSessionEntry 6 }

cucsAaaSessionLoginTime OBJECT-TYPE
    SYNTAX       DateAndTime
    MAX-ACCESS   read-only
    STATUS       current
    DESCRIPTION
        "Cisco UCS aaa:Session:loginTime managed object property"
    ::= { cucsAaaSessionEntry 7 }

cucsAaaSessionPid OBJECT-TYPE
    SYNTAX       Gauge32
    MAX-ACCESS   read-only
    STATUS       current
    DESCRIPTION
        "Cisco UCS aaa:Session:pid managed object property"
    ::= { cucsAaaSessionEntry 8 }

cucsAaaSessionSwitchId OBJECT-TYPE
    SYNTAX       CucsNetworkSwitchId
    MAX-ACCESS   read-only
    STATUS       current
    DESCRIPTION
        "Cisco UCS aaa:Session:switchId managed object property"
    ::= { cucsAaaSessionEntry 9 }

cucsAaaSessionTerm OBJECT-TYPE
    SYNTAX       SnmpAdminString
    MAX-ACCESS   read-only
    STATUS       current
    DESCRIPTION
        "Cisco UCS aaa:Session:term managed object property"
    ::= { cucsAaaSessionEntry 10 }

cucsAaaSessionUi OBJECT-TYPE
    SYNTAX       CucsAaaUserInterface
    MAX-ACCESS   read-only
    STATUS       current
    DESCRIPTION
        "Cisco UCS aaa:Session:ui managed object property"
    ::= { cucsAaaSessionEntry 11 }

cucsAaaSessionUser OBJECT-TYPE
    SYNTAX       SnmpAdminString
    MAX-ACCESS   read-only
    STATUS       current
    DESCRIPTION
        "Cisco UCS aaa:Session:user managed object property"
    ::= { cucsAaaSessionEntry 12 }

cucsAaaSessionRefreshPeriod OBJECT-TYPE
    SYNTAX       Gauge32
    MAX-ACCESS   read-only
    STATUS       current
    DESCRIPTION
        "Cisco UCS aaa:Session:refreshPeriod managed object property"
    ::= { cucsAaaSessionEntry 13 }

cucsAaaSessionSessionTimeout OBJECT-TYPE
    SYNTAX       Gauge32
    MAX-ACCESS   read-only
    STATUS       current
    DESCRIPTION
        "Cisco UCS aaa:Session:sessionTimeout managed object property"
    ::= { cucsAaaSessionEntry 14 }

cucsAaaSessionInfoTable OBJECT-TYPE
    SYNTAX           SEQUENCE OF CucsAaaSessionInfoEntry
    MAX-ACCESS       not-accessible
    STATUS           current
    DESCRIPTION
        "Cisco UCS aaa:SessionInfo managed object table"
    ::= { cucsAaaObjects 56 }

cucsAaaSessionInfoEntry OBJECT-TYPE
    SYNTAX           CucsAaaSessionInfoEntry
    MAX-ACCESS       not-accessible
    STATUS           current
    DESCRIPTION
        "Entry for the cucsAaaSessionInfoTable table."
    INDEX { cucsAaaSessionInfoInstanceId }
    ::= { cucsAaaSessionInfoTable 1 }

CucsAaaSessionInfoEntry ::= SEQUENCE {
    cucsAaaSessionInfoInstanceId                                     CucsManagedObjectId,
    cucsAaaSessionInfoDn                                             CucsManagedObjectDn,
    cucsAaaSessionInfoRn                                             SnmpAdminString,
    cucsAaaSessionInfoAddress                                        SnmpAdminString,
    cucsAaaSessionInfoDestIp                                         SnmpAdminString,
    cucsAaaSessionInfoEtime                                          DateAndTime,
    cucsAaaSessionInfoId                                             SnmpAdminString,
    cucsAaaSessionInfoPriv                                           SnmpAdminString,
    cucsAaaSessionInfoType                                           CucsAaaCimcSessionType,
    cucsAaaSessionInfoUser                                           SnmpAdminString,
    cucsAaaSessionInfoUserType                                       CucsAaaSession
}

cucsAaaSessionInfoInstanceId OBJECT-TYPE
    SYNTAX       CucsManagedObjectId
    MAX-ACCESS   not-accessible
    STATUS       current
    DESCRIPTION
        "Instance identifier of the managed object."
    ::= { cucsAaaSessionInfoEntry 1 }

cucsAaaSessionInfoDn OBJECT-TYPE
    SYNTAX       CucsManagedObjectDn
    MAX-ACCESS   read-only
    STATUS       current
    DESCRIPTION
        "Cisco UCS aaa:SessionInfo:dn managed object property"
    ::= { cucsAaaSessionInfoEntry 2 }

cucsAaaSessionInfoRn OBJECT-TYPE
    SYNTAX       SnmpAdminString
    MAX-ACCESS   read-only
    STATUS       current
    DESCRIPTION
        "Cisco UCS aaa:SessionInfo:rn managed object property"
    ::= { cucsAaaSessionInfoEntry 3 }

cucsAaaSessionInfoAddress OBJECT-TYPE
    SYNTAX       SnmpAdminString
    MAX-ACCESS   read-only
    STATUS       current
    DESCRIPTION
        "Cisco UCS aaa:SessionInfo:address managed object property"
    ::= { cucsAaaSessionInfoEntry 4 }

cucsAaaSessionInfoDestIp OBJECT-TYPE
    SYNTAX       SnmpAdminString
    MAX-ACCESS   read-only
    STATUS       current
    DESCRIPTION
        "Cisco UCS aaa:SessionInfo:destIp managed object property"
    ::= { cucsAaaSessionInfoEntry 5 }

cucsAaaSessionInfoEtime OBJECT-TYPE
    SYNTAX       DateAndTime
    MAX-ACCESS   read-only
    STATUS       current
    DESCRIPTION
        "Cisco UCS aaa:SessionInfo:etime managed object property"
    ::= { cucsAaaSessionInfoEntry 6 }

cucsAaaSessionInfoId OBJECT-TYPE
    SYNTAX       SnmpAdminString
    MAX-ACCESS   read-only
    STATUS       current
    DESCRIPTION
        "Cisco UCS aaa:SessionInfo:id managed object property"
    ::= { cucsAaaSessionInfoEntry 7 }

cucsAaaSessionInfoPriv OBJECT-TYPE
    SYNTAX       SnmpAdminString
    MAX-ACCESS   read-only
    STATUS       current
    DESCRIPTION
        "Cisco UCS aaa:SessionInfo:priv managed object property"
    ::= { cucsAaaSessionInfoEntry 8 }

cucsAaaSessionInfoType OBJECT-TYPE
    SYNTAX       CucsAaaCimcSessionType
    MAX-ACCESS   read-only
    STATUS       current
    DESCRIPTION
        "Cisco UCS aaa:SessionInfo:type managed object property"
    ::= { cucsAaaSessionInfoEntry 9 }

cucsAaaSessionInfoUser OBJECT-TYPE
    SYNTAX       SnmpAdminString
    MAX-ACCESS   read-only
    STATUS       current
    DESCRIPTION
        "Cisco UCS aaa:SessionInfo:user managed object property"
    ::= { cucsAaaSessionInfoEntry 10 }

cucsAaaSessionInfoUserType OBJECT-TYPE
    SYNTAX       CucsAaaSession
    MAX-ACCESS   read-only
    STATUS       current
    DESCRIPTION
        "Cisco UCS aaa:SessionInfo:userType managed object property"
    ::= { cucsAaaSessionInfoEntry 11 }

cucsAaaSessionInfoTableTable OBJECT-TYPE
    SYNTAX           SEQUENCE OF CucsAaaSessionInfoTableEntry
    MAX-ACCESS       not-accessible
    STATUS           current
    DESCRIPTION
        "Cisco UCS aaa:SessionInfoTable managed object table"
    ::= { cucsAaaObjects 57 }

cucsAaaSessionInfoTableEntry OBJECT-TYPE
    SYNTAX           CucsAaaSessionInfoTableEntry
    MAX-ACCESS       not-accessible
    STATUS           current
    DESCRIPTION
        "Entry for the cucsAaaSessionInfoTableTable table."
    INDEX { cucsAaaSessionInfoTableInstanceId }
    ::= { cucsAaaSessionInfoTableTable 1 }

CucsAaaSessionInfoTableEntry ::= SEQUENCE {
    cucsAaaSessionInfoTableInstanceId                                CucsManagedObjectId,
    cucsAaaSessionInfoTableDn                                        CucsManagedObjectDn,
    cucsAaaSessionInfoTableRn                                        SnmpAdminString
}

cucsAaaSessionInfoTableInstanceId OBJECT-TYPE
    SYNTAX       CucsManagedObjectId
    MAX-ACCESS   not-accessible
    STATUS       current
    DESCRIPTION
        "Instance identifier of the managed object."
    ::= { cucsAaaSessionInfoTableEntry 1 }

cucsAaaSessionInfoTableDn OBJECT-TYPE
    SYNTAX       CucsManagedObjectDn
    MAX-ACCESS   read-only
    STATUS       current
    DESCRIPTION
        "Cisco UCS aaa:SessionInfoTable:dn managed object property"
    ::= { cucsAaaSessionInfoTableEntry 2 }

cucsAaaSessionInfoTableRn OBJECT-TYPE
    SYNTAX       SnmpAdminString
    MAX-ACCESS   read-only
    STATUS       current
    DESCRIPTION
        "Cisco UCS aaa:SessionInfoTable:rn managed object property"
    ::= { cucsAaaSessionInfoTableEntry 3 }

cucsAaaSessionLRTable OBJECT-TYPE
    SYNTAX           SEQUENCE OF CucsAaaSessionLREntry
    MAX-ACCESS       not-accessible
    STATUS           current
    DESCRIPTION
        "Cisco UCS aaa:SessionLR managed object table"
    ::= { cucsAaaObjects 27 }

cucsAaaSessionLREntry OBJECT-TYPE
    SYNTAX           CucsAaaSessionLREntry
    MAX-ACCESS       not-accessible
    STATUS           current
    DESCRIPTION
        "Entry for the cucsAaaSessionLRTable table."
    INDEX { cucsAaaSessionLRInstanceId }
    ::= { cucsAaaSessionLRTable 1 }

CucsAaaSessionLREntry ::= SEQUENCE {
    cucsAaaSessionLRInstanceId                                       CucsManagedObjectId,
    cucsAaaSessionLRDn                                               CucsManagedObjectDn,
    cucsAaaSessionLRRn                                               SnmpAdminString,
    cucsAaaSessionLRAffected                                         SnmpAdminString,
    cucsAaaSessionLRCause                                            CucsConditionCause,
    cucsAaaSessionLRChangeSet                                        SnmpAdminString,
    cucsAaaSessionLRCode                                             CucsConditionCode,
    cucsAaaSessionLRCreated                                          DateAndTime,
    cucsAaaSessionLRDescr                                            SnmpAdminString,
    cucsAaaSessionLRId                                               Gauge32,
    cucsAaaSessionLRInd                                              CucsConditionActionIndicator,
    cucsAaaSessionLRSeverity                                         CucsConditionSeverity,
    cucsAaaSessionLRTrig                                             Gauge32,
    cucsAaaSessionLRTxId                                             Unsigned64,
    cucsAaaSessionLRUser                                             SnmpAdminString,
    cucsAaaSessionLRSessionId                                        SnmpAdminString
}

cucsAaaSessionLRInstanceId OBJECT-TYPE
    SYNTAX       CucsManagedObjectId
    MAX-ACCESS   not-accessible
    STATUS       current
    DESCRIPTION
        "Instance identifier of the managed object."
    ::= { cucsAaaSessionLREntry 1 }

cucsAaaSessionLRDn OBJECT-TYPE
    SYNTAX       CucsManagedObjectDn
    MAX-ACCESS   read-only
    STATUS       current
    DESCRIPTION
        "Cisco UCS aaa:SessionLR:dn managed object property"
    ::= { cucsAaaSessionLREntry 2 }

cucsAaaSessionLRRn OBJECT-TYPE
    SYNTAX       SnmpAdminString
    MAX-ACCESS   read-only
    STATUS       current
    DESCRIPTION
        "Cisco UCS aaa:SessionLR:rn managed object property"
    ::= { cucsAaaSessionLREntry 3 }

cucsAaaSessionLRAffected OBJECT-TYPE
    SYNTAX       SnmpAdminString
    MAX-ACCESS   read-only
    STATUS       current
    DESCRIPTION
        "Cisco UCS aaa:SessionLR:affected managed object property"
    ::= { cucsAaaSessionLREntry 4 }

cucsAaaSessionLRCause OBJECT-TYPE
    SYNTAX       CucsConditionCause
    MAX-ACCESS   read-only
    STATUS       current
    DESCRIPTION
        "Cisco UCS aaa:SessionLR:cause managed object property"
    ::= { cucsAaaSessionLREntry 5 }

cucsAaaSessionLRChangeSet OBJECT-TYPE
    SYNTAX       SnmpAdminString
    MAX-ACCESS   read-only
    STATUS       current
    DESCRIPTION
        "Cisco UCS aaa:SessionLR:changeSet managed object property"
    ::= { cucsAaaSessionLREntry 6 }

cucsAaaSessionLRCode OBJECT-TYPE
    SYNTAX       CucsConditionCode
    MAX-ACCESS   read-only
    STATUS       current
    DESCRIPTION
        "Cisco UCS aaa:SessionLR:code managed object property"
    ::= { cucsAaaSessionLREntry 7 }

cucsAaaSessionLRCreated OBJECT-TYPE
    SYNTAX       DateAndTime
    MAX-ACCESS   read-only
    STATUS       current
    DESCRIPTION
        "Cisco UCS aaa:SessionLR:created managed object property"
    ::= { cucsAaaSessionLREntry 8 }

cucsAaaSessionLRDescr OBJECT-TYPE
    SYNTAX       SnmpAdminString
    MAX-ACCESS   read-only
    STATUS       current
    DESCRIPTION
        "Cisco UCS aaa:SessionLR:descr managed object property"
    ::= { cucsAaaSessionLREntry 9 }

cucsAaaSessionLRId OBJECT-TYPE
    SYNTAX       Gauge32
    MAX-ACCESS   read-only
    STATUS       current
    DESCRIPTION
        "Cisco UCS aaa:SessionLR:id managed object property"
    ::= { cucsAaaSessionLREntry 10 }

cucsAaaSessionLRInd OBJECT-TYPE
    SYNTAX       CucsConditionActionIndicator
    MAX-ACCESS   read-only
    STATUS       current
    DESCRIPTION
        "Cisco UCS aaa:SessionLR:ind managed object property"
    ::= { cucsAaaSessionLREntry 11 }

cucsAaaSessionLRSeverity OBJECT-TYPE
    SYNTAX       CucsConditionSeverity
    MAX-ACCESS   read-only
    STATUS       current
    DESCRIPTION
        "Cisco UCS aaa:SessionLR:severity managed object property"
    ::= { cucsAaaSessionLREntry 12 }

cucsAaaSessionLRTrig OBJECT-TYPE
    SYNTAX       Gauge32
    MAX-ACCESS   read-only
    STATUS       current
    DESCRIPTION
        "Cisco UCS aaa:SessionLR:trig managed object property"
    ::= { cucsAaaSessionLREntry 13 }

cucsAaaSessionLRTxId OBJECT-TYPE
    SYNTAX       Unsigned64
    MAX-ACCESS   read-only
    STATUS       current
    DESCRIPTION
        "Cisco UCS aaa:SessionLR:txId managed object property"
    ::= { cucsAaaSessionLREntry 14 }

cucsAaaSessionLRUser OBJECT-TYPE
    SYNTAX       SnmpAdminString
    MAX-ACCESS   read-only
    STATUS       current
    DESCRIPTION
        "Cisco UCS aaa:SessionLR:user managed object property"
    ::= { cucsAaaSessionLREntry 15 }

cucsAaaSessionLRSessionId OBJECT-TYPE
    SYNTAX       SnmpAdminString
    MAX-ACCESS   read-only
    STATUS       current
    DESCRIPTION
        "Cisco UCS aaa:SessionLR:sessionId managed object property"
    ::= { cucsAaaSessionLREntry 16 }

cucsAaaShellLoginTable OBJECT-TYPE
    SYNTAX           SEQUENCE OF CucsAaaShellLoginEntry
    MAX-ACCESS       not-accessible
    STATUS           current
    DESCRIPTION
        "Cisco UCS aaa:ShellLogin managed object table"
    ::= { cucsAaaObjects 28 }

cucsAaaShellLoginEntry OBJECT-TYPE
    SYNTAX           CucsAaaShellLoginEntry
    MAX-ACCESS       not-accessible
    STATUS           current
    DESCRIPTION
        "Entry for the cucsAaaShellLoginTable table."
    INDEX { cucsAaaShellLoginInstanceId }
    ::= { cucsAaaShellLoginTable 1 }

CucsAaaShellLoginEntry ::= SEQUENCE {
    cucsAaaShellLoginInstanceId                                      CucsManagedObjectId,
    cucsAaaShellLoginDn                                              CucsManagedObjectDn,
    cucsAaaShellLoginRn                                              SnmpAdminString,
    cucsAaaShellLoginDescr                                           SnmpAdminString,
    cucsAaaShellLoginId                                              SnmpAdminString,
    cucsAaaShellLoginIntId                                           SnmpAdminString,
    cucsAaaShellLoginLocalHost                                       SnmpAdminString,
    cucsAaaShellLoginName                                            SnmpAdminString,
    cucsAaaShellLoginRemoteHost                                      SnmpAdminString,
    cucsAaaShellLoginSession                                         CucsAaaSession,
    cucsAaaShellLoginSwitchId                                        CucsNetworkSwitchId,
    cucsAaaShellLoginPolicyLevel                                     Gauge32,
    cucsAaaShellLoginPolicyOwner                                     CucsPolicyPolicyOwner
}

cucsAaaShellLoginInstanceId OBJECT-TYPE
    SYNTAX       CucsManagedObjectId
    MAX-ACCESS   not-accessible
    STATUS       current
    DESCRIPTION
        "Instance identifier of the managed object."
    ::= { cucsAaaShellLoginEntry 1 }

cucsAaaShellLoginDn OBJECT-TYPE
    SYNTAX       CucsManagedObjectDn
    MAX-ACCESS   read-only
    STATUS       current
    DESCRIPTION
        "Cisco UCS aaa:ShellLogin:dn managed object property"
    ::= { cucsAaaShellLoginEntry 2 }

cucsAaaShellLoginRn OBJECT-TYPE
    SYNTAX       SnmpAdminString
    MAX-ACCESS   read-only
    STATUS       current
    DESCRIPTION
        "Cisco UCS aaa:ShellLogin:rn managed object property"
    ::= { cucsAaaShellLoginEntry 3 }

cucsAaaShellLoginDescr OBJECT-TYPE
    SYNTAX       SnmpAdminString
    MAX-ACCESS   read-only
    STATUS       current
    DESCRIPTION
        "Cisco UCS aaa:ShellLogin:descr managed object property"
    ::= { cucsAaaShellLoginEntry 4 }

cucsAaaShellLoginId OBJECT-TYPE
    SYNTAX       SnmpAdminString
    MAX-ACCESS   read-only
    STATUS       current
    DESCRIPTION
        "Cisco UCS aaa:ShellLogin:id managed object property"
    ::= { cucsAaaShellLoginEntry 5 }

cucsAaaShellLoginIntId OBJECT-TYPE
    SYNTAX       SnmpAdminString
    MAX-ACCESS   read-only
    STATUS       current
    DESCRIPTION
        "Cisco UCS aaa:ShellLogin:intId managed object property"
    ::= { cucsAaaShellLoginEntry 6 }

cucsAaaShellLoginLocalHost OBJECT-TYPE
    SYNTAX       SnmpAdminString
    MAX-ACCESS   read-only
    STATUS       current
    DESCRIPTION
        "Cisco UCS aaa:ShellLogin:localHost managed object property"
    ::= { cucsAaaShellLoginEntry 7 }

cucsAaaShellLoginName OBJECT-TYPE
    SYNTAX       SnmpAdminString
    MAX-ACCESS   read-only
    STATUS       current
    DESCRIPTION
        "Cisco UCS aaa:ShellLogin:name managed object property"
    ::= { cucsAaaShellLoginEntry 8 }

cucsAaaShellLoginRemoteHost OBJECT-TYPE
    SYNTAX       SnmpAdminString
    MAX-ACCESS   read-only
    STATUS       current
    DESCRIPTION
        "Cisco UCS aaa:ShellLogin:remoteHost managed object property"
    ::= { cucsAaaShellLoginEntry 9 }

cucsAaaShellLoginSession OBJECT-TYPE
    SYNTAX       CucsAaaSession
    MAX-ACCESS   read-only
    STATUS       current
    DESCRIPTION
        "Cisco UCS aaa:ShellLogin:session managed object property"
    ::= { cucsAaaShellLoginEntry 10 }

cucsAaaShellLoginSwitchId OBJECT-TYPE
    SYNTAX       CucsNetworkSwitchId
    MAX-ACCESS   read-only
    STATUS       current
    DESCRIPTION
        "Cisco UCS aaa:ShellLogin:switchId managed object property"
    ::= { cucsAaaShellLoginEntry 11 }

cucsAaaShellLoginPolicyLevel OBJECT-TYPE
    SYNTAX       Gauge32
    MAX-ACCESS   read-only
    STATUS       current
    DESCRIPTION
        "Cisco UCS aaa:ShellLogin:policyLevel managed object property"
    ::= { cucsAaaShellLoginEntry 12 }

cucsAaaShellLoginPolicyOwner OBJECT-TYPE
    SYNTAX       CucsPolicyPolicyOwner
    MAX-ACCESS   read-only
    STATUS       current
    DESCRIPTION
        "Cisco UCS aaa:ShellLogin:policyOwner managed object property"
    ::= { cucsAaaShellLoginEntry 13 }

cucsAaaSshAuthTable OBJECT-TYPE
    SYNTAX           SEQUENCE OF CucsAaaSshAuthEntry
    MAX-ACCESS       not-accessible
    STATUS           current
    DESCRIPTION
        "Cisco UCS aaa:SshAuth managed object table"
    ::= { cucsAaaObjects 29 }

cucsAaaSshAuthEntry OBJECT-TYPE
    SYNTAX           CucsAaaSshAuthEntry
    MAX-ACCESS       not-accessible
    STATUS           current
    DESCRIPTION
        "Entry for the cucsAaaSshAuthTable table."
    INDEX { cucsAaaSshAuthInstanceId }
    ::= { cucsAaaSshAuthTable 1 }

CucsAaaSshAuthEntry ::= SEQUENCE {
    cucsAaaSshAuthInstanceId                                         CucsManagedObjectId,
    cucsAaaSshAuthDn                                                 CucsManagedObjectDn,
    cucsAaaSshAuthRn                                                 SnmpAdminString,
    cucsAaaSshAuthData                                               SnmpAdminString,
    cucsAaaSshAuthOldStrType                                         CucsAaaSshStr,
    cucsAaaSshAuthStrType                                            CucsAaaSshStr
}

cucsAaaSshAuthInstanceId OBJECT-TYPE
    SYNTAX       CucsManagedObjectId
    MAX-ACCESS   not-accessible
    STATUS       current
    DESCRIPTION
        "Instance identifier of the managed object."
    ::= { cucsAaaSshAuthEntry 1 }

cucsAaaSshAuthDn OBJECT-TYPE
    SYNTAX       CucsManagedObjectDn
    MAX-ACCESS   read-only
    STATUS       current
    DESCRIPTION
        "Cisco UCS aaa:SshAuth:dn managed object property"
    ::= { cucsAaaSshAuthEntry 2 }

cucsAaaSshAuthRn OBJECT-TYPE
    SYNTAX       SnmpAdminString
    MAX-ACCESS   read-only
    STATUS       current
    DESCRIPTION
        "Cisco UCS aaa:SshAuth:rn managed object property"
    ::= { cucsAaaSshAuthEntry 3 }

cucsAaaSshAuthData OBJECT-TYPE
    SYNTAX       SnmpAdminString
    MAX-ACCESS   read-only
    STATUS       current
    DESCRIPTION
        "Cisco UCS aaa:SshAuth:data managed object property"
    ::= { cucsAaaSshAuthEntry 4 }

cucsAaaSshAuthOldStrType OBJECT-TYPE
    SYNTAX       CucsAaaSshStr
    MAX-ACCESS   read-only
    STATUS       current
    DESCRIPTION
        "Cisco UCS aaa:SshAuth:oldStrType managed object property"
    ::= { cucsAaaSshAuthEntry 5 }

cucsAaaSshAuthStrType OBJECT-TYPE
    SYNTAX       CucsAaaSshStr
    MAX-ACCESS   read-only
    STATUS       current
    DESCRIPTION
        "Cisco UCS aaa:SshAuth:strType managed object property"
    ::= { cucsAaaSshAuthEntry 6 }

cucsAaaTacacsPlusEpTable OBJECT-TYPE
    SYNTAX           SEQUENCE OF CucsAaaTacacsPlusEpEntry
    MAX-ACCESS       not-accessible
    STATUS           current
    DESCRIPTION
        "Cisco UCS aaa:TacacsPlusEp managed object table"
    ::= { cucsAaaObjects 30 }

cucsAaaTacacsPlusEpEntry OBJECT-TYPE
    SYNTAX           CucsAaaTacacsPlusEpEntry
    MAX-ACCESS       not-accessible
    STATUS           current
    DESCRIPTION
        "Entry for the cucsAaaTacacsPlusEpTable table."
    INDEX { cucsAaaTacacsPlusEpInstanceId }
    ::= { cucsAaaTacacsPlusEpTable 1 }

CucsAaaTacacsPlusEpEntry ::= SEQUENCE {
    cucsAaaTacacsPlusEpInstanceId                                    CucsManagedObjectId,
    cucsAaaTacacsPlusEpDn                                            CucsManagedObjectDn,
    cucsAaaTacacsPlusEpRn                                            SnmpAdminString,
    cucsAaaTacacsPlusEpDescr                                         SnmpAdminString,
    cucsAaaTacacsPlusEpFsmDescr                                      SnmpAdminString,
    cucsAaaTacacsPlusEpFsmPrev                                       SnmpAdminString,
    cucsAaaTacacsPlusEpFsmProgr                                      Gauge32,
    cucsAaaTacacsPlusEpFsmRmtInvErrCode                              Gauge32,
    cucsAaaTacacsPlusEpFsmRmtInvErrDescr                             SnmpAdminString,
    cucsAaaTacacsPlusEpFsmRmtInvRslt                                 CucsConditionRemoteInvRslt,
    cucsAaaTacacsPlusEpFsmStageDescr                                 SnmpAdminString,
    cucsAaaTacacsPlusEpFsmStamp                                      DateAndTime,
    cucsAaaTacacsPlusEpFsmStatus                                     SnmpAdminString,
    cucsAaaTacacsPlusEpFsmTry                                        Gauge32,
    cucsAaaTacacsPlusEpIntId                                         SnmpAdminString,
    cucsAaaTacacsPlusEpName                                          SnmpAdminString,
    cucsAaaTacacsPlusEpRetries                                       Gauge32,
    cucsAaaTacacsPlusEpTimeout                                       Gauge32,
    cucsAaaTacacsPlusEpPolicyLevel                                   Gauge32,
    cucsAaaTacacsPlusEpPolicyOwner                                   CucsPolicyPolicyOwner
}

cucsAaaTacacsPlusEpInstanceId OBJECT-TYPE
    SYNTAX       CucsManagedObjectId
    MAX-ACCESS   not-accessible
    STATUS       current
    DESCRIPTION
        "Instance identifier of the managed object."
    ::= { cucsAaaTacacsPlusEpEntry 1 }

cucsAaaTacacsPlusEpDn OBJECT-TYPE
    SYNTAX       CucsManagedObjectDn
    MAX-ACCESS   read-only
    STATUS       current
    DESCRIPTION
        "Cisco UCS aaa:TacacsPlusEp:dn managed object property"
    ::= { cucsAaaTacacsPlusEpEntry 2 }

cucsAaaTacacsPlusEpRn OBJECT-TYPE
    SYNTAX       SnmpAdminString
    MAX-ACCESS   read-only
    STATUS       current
    DESCRIPTION
        "Cisco UCS aaa:TacacsPlusEp:rn managed object property"
    ::= { cucsAaaTacacsPlusEpEntry 3 }

cucsAaaTacacsPlusEpDescr OBJECT-TYPE
    SYNTAX       SnmpAdminString
    MAX-ACCESS   read-only
    STATUS       current
    DESCRIPTION
        "Cisco UCS aaa:TacacsPlusEp:descr managed object property"
    ::= { cucsAaaTacacsPlusEpEntry 4 }

cucsAaaTacacsPlusEpFsmDescr OBJECT-TYPE
    SYNTAX       SnmpAdminString
    MAX-ACCESS   read-only
    STATUS       current
    DESCRIPTION
        "Cisco UCS aaa:TacacsPlusEp:fsmDescr managed object property"
    ::= { cucsAaaTacacsPlusEpEntry 5 }

cucsAaaTacacsPlusEpFsmPrev OBJECT-TYPE
    SYNTAX       SnmpAdminString
    MAX-ACCESS   read-only
    STATUS       current
    DESCRIPTION
        "Cisco UCS aaa:TacacsPlusEp:fsmPrev managed object property"
    ::= { cucsAaaTacacsPlusEpEntry 6 }

cucsAaaTacacsPlusEpFsmProgr OBJECT-TYPE
    SYNTAX       Gauge32
    MAX-ACCESS   read-only
    STATUS       current
    DESCRIPTION
        "Cisco UCS aaa:TacacsPlusEp:fsmProgr managed object property"
    ::= { cucsAaaTacacsPlusEpEntry 7 }

cucsAaaTacacsPlusEpFsmRmtInvErrCode OBJECT-TYPE
    SYNTAX       Gauge32
    MAX-ACCESS   read-only
    STATUS       current
    DESCRIPTION
        "Cisco UCS aaa:TacacsPlusEp:fsmRmtInvErrCode managed
        object property"
    ::= { cucsAaaTacacsPlusEpEntry 8 }

cucsAaaTacacsPlusEpFsmRmtInvErrDescr OBJECT-TYPE
    SYNTAX       SnmpAdminString
    MAX-ACCESS   read-only
    STATUS       current
    DESCRIPTION
        "Cisco UCS aaa:TacacsPlusEp:fsmRmtInvErrDescr managed
        object property"
    ::= { cucsAaaTacacsPlusEpEntry 9 }

cucsAaaTacacsPlusEpFsmRmtInvRslt OBJECT-TYPE
    SYNTAX       CucsConditionRemoteInvRslt
    MAX-ACCESS   read-only
    STATUS       current
    DESCRIPTION
        "Cisco UCS aaa:TacacsPlusEp:fsmRmtInvRslt managed object property"
    ::= { cucsAaaTacacsPlusEpEntry 10 }

cucsAaaTacacsPlusEpFsmStageDescr OBJECT-TYPE
    SYNTAX       SnmpAdminString
    MAX-ACCESS   read-only
    STATUS       current
    DESCRIPTION
        "Cisco UCS aaa:TacacsPlusEp:fsmStageDescr managed object property"
    ::= { cucsAaaTacacsPlusEpEntry 11 }

cucsAaaTacacsPlusEpFsmStamp OBJECT-TYPE
    SYNTAX       DateAndTime
    MAX-ACCESS   read-only
    STATUS       current
    DESCRIPTION
        "Cisco UCS aaa:TacacsPlusEp:fsmStamp managed object property"
    ::= { cucsAaaTacacsPlusEpEntry 12 }

cucsAaaTacacsPlusEpFsmStatus OBJECT-TYPE
    SYNTAX       SnmpAdminString
    MAX-ACCESS   read-only
    STATUS       current
    DESCRIPTION
        "Cisco UCS aaa:TacacsPlusEp:fsmStatus managed object property"
    ::= { cucsAaaTacacsPlusEpEntry 13 }

cucsAaaTacacsPlusEpFsmTry OBJECT-TYPE
    SYNTAX       Gauge32
    MAX-ACCESS   read-only
    STATUS       current
    DESCRIPTION
        "Cisco UCS aaa:TacacsPlusEp:fsmTry managed object property"
    ::= { cucsAaaTacacsPlusEpEntry 14 }

cucsAaaTacacsPlusEpIntId OBJECT-TYPE
    SYNTAX       SnmpAdminString
    MAX-ACCESS   read-only
    STATUS       current
    DESCRIPTION
        "Cisco UCS aaa:TacacsPlusEp:intId managed object property"
    ::= { cucsAaaTacacsPlusEpEntry 15 }

cucsAaaTacacsPlusEpName OBJECT-TYPE
    SYNTAX       SnmpAdminString
    MAX-ACCESS   read-only
    STATUS       current
    DESCRIPTION
        "Cisco UCS aaa:TacacsPlusEp:name managed object property"
    ::= { cucsAaaTacacsPlusEpEntry 16 }

cucsAaaTacacsPlusEpRetries OBJECT-TYPE
    SYNTAX       Gauge32
    MAX-ACCESS   read-only
    STATUS       current
    DESCRIPTION
        "Cisco UCS aaa:TacacsPlusEp:retries managed object property"
    ::= { cucsAaaTacacsPlusEpEntry 17 }

cucsAaaTacacsPlusEpTimeout OBJECT-TYPE
    SYNTAX       Gauge32
    MAX-ACCESS   read-only
    STATUS       current
    DESCRIPTION
        "Cisco UCS aaa:TacacsPlusEp:timeout managed object property"
    ::= { cucsAaaTacacsPlusEpEntry 18 }

cucsAaaTacacsPlusEpPolicyLevel OBJECT-TYPE
    SYNTAX       Gauge32
    MAX-ACCESS   read-only
    STATUS       current
    DESCRIPTION
        "Cisco UCS aaa:TacacsPlusEp:policyLevel managed object property"
    ::= { cucsAaaTacacsPlusEpEntry 19 }

cucsAaaTacacsPlusEpPolicyOwner OBJECT-TYPE
    SYNTAX       CucsPolicyPolicyOwner
    MAX-ACCESS   read-only
    STATUS       current
    DESCRIPTION
        "Cisco UCS aaa:TacacsPlusEp:policyOwner managed object property"
    ::= { cucsAaaTacacsPlusEpEntry 20 }

cucsAaaTacacsPlusEpFsmTable OBJECT-TYPE
    SYNTAX           SEQUENCE OF CucsAaaTacacsPlusEpFsmEntry
    MAX-ACCESS       not-accessible
    STATUS           current
    DESCRIPTION
        "Cisco UCS aaa:TacacsPlusEpFsm managed object table"
    ::= { cucsAaaObjects 51 }

cucsAaaTacacsPlusEpFsmEntry OBJECT-TYPE
    SYNTAX           CucsAaaTacacsPlusEpFsmEntry
    MAX-ACCESS       not-accessible
    STATUS           current
    DESCRIPTION
        "Entry for the cucsAaaTacacsPlusEpFsmTable table."
    INDEX { cucsAaaTacacsPlusEpFsmInstanceId }
    ::= { cucsAaaTacacsPlusEpFsmTable 1 }

CucsAaaTacacsPlusEpFsmEntry ::= SEQUENCE {
    cucsAaaTacacsPlusEpFsmInstanceId                                 CucsManagedObjectId,
    cucsAaaTacacsPlusEpFsmDn                                         CucsManagedObjectDn,
    cucsAaaTacacsPlusEpFsmRn                                         SnmpAdminString,
    cucsAaaTacacsPlusEpFsmCompletionTime                             DateAndTime,
    cucsAaaTacacsPlusEpFsmCurrentFsm                                 CucsAaaTacacsPlusEpFsmCurrentFsm,
    cucsAaaTacacsPlusEpFsmDescrData                                  SnmpAdminString,
    cucsAaaTacacsPlusEpFsmFsmStatus                                  CucsFsmFsmStageStatus,
    cucsAaaTacacsPlusEpFsmProgress                                   Gauge32,
    cucsAaaTacacsPlusEpFsmRmtErrCode                                 Gauge32,
    cucsAaaTacacsPlusEpFsmRmtErrDescr                                SnmpAdminString,
    cucsAaaTacacsPlusEpFsmRmtRslt                                    CucsConditionRemoteInvRslt
}

cucsAaaTacacsPlusEpFsmInstanceId OBJECT-TYPE
    SYNTAX       CucsManagedObjectId
    MAX-ACCESS   not-accessible
    STATUS       current
    DESCRIPTION
        "Instance identifier of the managed object."
    ::= { cucsAaaTacacsPlusEpFsmEntry 1 }

cucsAaaTacacsPlusEpFsmDn OBJECT-TYPE
    SYNTAX       CucsManagedObjectDn
    MAX-ACCESS   read-only
    STATUS       current
    DESCRIPTION
        "Cisco UCS aaa:TacacsPlusEpFsm:dn managed object property"
    ::= { cucsAaaTacacsPlusEpFsmEntry 2 }

cucsAaaTacacsPlusEpFsmRn OBJECT-TYPE
    SYNTAX       SnmpAdminString
    MAX-ACCESS   read-only
    STATUS       current
    DESCRIPTION
        "Cisco UCS aaa:TacacsPlusEpFsm:rn managed object property"
    ::= { cucsAaaTacacsPlusEpFsmEntry 3 }

cucsAaaTacacsPlusEpFsmCompletionTime OBJECT-TYPE
    SYNTAX       DateAndTime
    MAX-ACCESS   read-only
    STATUS       current
    DESCRIPTION
        "Cisco UCS aaa:TacacsPlusEpFsm:completionTime managed
        object property"
    ::= { cucsAaaTacacsPlusEpFsmEntry 4 }

cucsAaaTacacsPlusEpFsmCurrentFsm OBJECT-TYPE
    SYNTAX       CucsAaaTacacsPlusEpFsmCurrentFsm
    MAX-ACCESS   read-only
    STATUS       current
    DESCRIPTION
        "Cisco UCS aaa:TacacsPlusEpFsm:currentFsm managed object property"
    ::= { cucsAaaTacacsPlusEpFsmEntry 5 }

cucsAaaTacacsPlusEpFsmDescrData OBJECT-TYPE
    SYNTAX       SnmpAdminString
    MAX-ACCESS   read-only
    STATUS       current
    DESCRIPTION
        "Cisco UCS aaa:TacacsPlusEpFsm:descr managed object property"
    ::= { cucsAaaTacacsPlusEpFsmEntry 6 }

cucsAaaTacacsPlusEpFsmFsmStatus OBJECT-TYPE
    SYNTAX       CucsFsmFsmStageStatus
    MAX-ACCESS   read-only
    STATUS       current
    DESCRIPTION
        "Cisco UCS aaa:TacacsPlusEpFsm:fsmStatus managed object property"
    ::= { cucsAaaTacacsPlusEpFsmEntry 7 }

cucsAaaTacacsPlusEpFsmProgress OBJECT-TYPE
    SYNTAX       Gauge32
    MAX-ACCESS   read-only
    STATUS       current
    DESCRIPTION
        "Cisco UCS aaa:TacacsPlusEpFsm:progress managed object property"
    ::= { cucsAaaTacacsPlusEpFsmEntry 8 }

cucsAaaTacacsPlusEpFsmRmtErrCode OBJECT-TYPE
    SYNTAX       Gauge32
    MAX-ACCESS   read-only
    STATUS       current
    DESCRIPTION
        "Cisco UCS aaa:TacacsPlusEpFsm:rmtErrCode managed object property"
    ::= { cucsAaaTacacsPlusEpFsmEntry 9 }

cucsAaaTacacsPlusEpFsmRmtErrDescr OBJECT-TYPE
    SYNTAX       SnmpAdminString
    MAX-ACCESS   read-only
    STATUS       current
    DESCRIPTION
        "Cisco UCS aaa:TacacsPlusEpFsm:rmtErrDescr managed
        object property"
    ::= { cucsAaaTacacsPlusEpFsmEntry 10 }

cucsAaaTacacsPlusEpFsmRmtRslt OBJECT-TYPE
    SYNTAX       CucsConditionRemoteInvRslt
    MAX-ACCESS   read-only
    STATUS       current
    DESCRIPTION
        "Cisco UCS aaa:TacacsPlusEpFsm:rmtRslt managed object property"
    ::= { cucsAaaTacacsPlusEpFsmEntry 11 }

cucsAaaTacacsPlusEpFsmStageTable OBJECT-TYPE
    SYNTAX           SEQUENCE OF CucsAaaTacacsPlusEpFsmStageEntry
    MAX-ACCESS       not-accessible
    STATUS           current
    DESCRIPTION
        "Cisco UCS aaa:TacacsPlusEpFsmStage managed object table"
    ::= { cucsAaaObjects 52 }

cucsAaaTacacsPlusEpFsmStageEntry OBJECT-TYPE
    SYNTAX           CucsAaaTacacsPlusEpFsmStageEntry
    MAX-ACCESS       not-accessible
    STATUS           current
    DESCRIPTION
        "Entry for the cucsAaaTacacsPlusEpFsmStageTable table."
    INDEX { cucsAaaTacacsPlusEpFsmStageInstanceId }
    ::= { cucsAaaTacacsPlusEpFsmStageTable 1 }

CucsAaaTacacsPlusEpFsmStageEntry ::= SEQUENCE {
    cucsAaaTacacsPlusEpFsmStageInstanceId                            CucsManagedObjectId,
    cucsAaaTacacsPlusEpFsmStageDn                                    CucsManagedObjectDn,
    cucsAaaTacacsPlusEpFsmStageRn                                    SnmpAdminString,
    cucsAaaTacacsPlusEpFsmStageDescrData                             SnmpAdminString,
    cucsAaaTacacsPlusEpFsmStageLastUpdateTime                        DateAndTime,
    cucsAaaTacacsPlusEpFsmStageName                                  CucsAaaTacacsPlusEpFsmStageName,
    cucsAaaTacacsPlusEpFsmStageOrder                                 Gauge32,
    cucsAaaTacacsPlusEpFsmStageRetry                                 Gauge32,
    cucsAaaTacacsPlusEpFsmStageStageStatus                           CucsFsmFsmStageStatus
}

cucsAaaTacacsPlusEpFsmStageInstanceId OBJECT-TYPE
    SYNTAX       CucsManagedObjectId
    MAX-ACCESS   not-accessible
    STATUS       current
    DESCRIPTION
        "Instance identifier of the managed object."
    ::= { cucsAaaTacacsPlusEpFsmStageEntry 1 }

cucsAaaTacacsPlusEpFsmStageDn OBJECT-TYPE
    SYNTAX       CucsManagedObjectDn
    MAX-ACCESS   read-only
    STATUS       current
    DESCRIPTION
        "Cisco UCS aaa:TacacsPlusEpFsmStage:dn managed object property"
    ::= { cucsAaaTacacsPlusEpFsmStageEntry 2 }

cucsAaaTacacsPlusEpFsmStageRn OBJECT-TYPE
    SYNTAX       SnmpAdminString
    MAX-ACCESS   read-only
    STATUS       current
    DESCRIPTION
        "Cisco UCS aaa:TacacsPlusEpFsmStage:rn managed object property"
    ::= { cucsAaaTacacsPlusEpFsmStageEntry 3 }

cucsAaaTacacsPlusEpFsmStageDescrData OBJECT-TYPE
    SYNTAX       SnmpAdminString
    MAX-ACCESS   read-only
    STATUS       current
    DESCRIPTION
        "Cisco UCS aaa:TacacsPlusEpFsmStage:descr managed object property"
    ::= { cucsAaaTacacsPlusEpFsmStageEntry 4 }

cucsAaaTacacsPlusEpFsmStageLastUpdateTime OBJECT-TYPE
    SYNTAX       DateAndTime
    MAX-ACCESS   read-only
    STATUS       current
    DESCRIPTION
        "Cisco UCS aaa:TacacsPlusEpFsmStage:lastUpdateTime
        managed object property"
    ::= { cucsAaaTacacsPlusEpFsmStageEntry 5 }

cucsAaaTacacsPlusEpFsmStageName OBJECT-TYPE
    SYNTAX       CucsAaaTacacsPlusEpFsmStageName
    MAX-ACCESS   read-only
    STATUS       current
    DESCRIPTION
        "Cisco UCS aaa:TacacsPlusEpFsmStage:name managed object property"
    ::= { cucsAaaTacacsPlusEpFsmStageEntry 6 }

cucsAaaTacacsPlusEpFsmStageOrder OBJECT-TYPE
    SYNTAX       Gauge32
    MAX-ACCESS   read-only
    STATUS       current
    DESCRIPTION
        "Cisco UCS aaa:TacacsPlusEpFsmStage:order managed object property"
    ::= { cucsAaaTacacsPlusEpFsmStageEntry 7 }

cucsAaaTacacsPlusEpFsmStageRetry OBJECT-TYPE
    SYNTAX       Gauge32
    MAX-ACCESS   read-only
    STATUS       current
    DESCRIPTION
        "Cisco UCS aaa:TacacsPlusEpFsmStage:retry managed object property"
    ::= { cucsAaaTacacsPlusEpFsmStageEntry 8 }

cucsAaaTacacsPlusEpFsmStageStageStatus OBJECT-TYPE
    SYNTAX       CucsFsmFsmStageStatus
    MAX-ACCESS   read-only
    STATUS       current
    DESCRIPTION
        "Cisco UCS aaa:TacacsPlusEpFsmStage:stageStatus
        managed object property"
    ::= { cucsAaaTacacsPlusEpFsmStageEntry 9 }

cucsAaaTacacsPlusProviderTable OBJECT-TYPE
    SYNTAX           SEQUENCE OF CucsAaaTacacsPlusProviderEntry
    MAX-ACCESS       not-accessible
    STATUS           current
    DESCRIPTION
        "Cisco UCS aaa:TacacsPlusProvider managed object table"
    ::= { cucsAaaObjects 31 }

cucsAaaTacacsPlusProviderEntry OBJECT-TYPE
    SYNTAX           CucsAaaTacacsPlusProviderEntry
    MAX-ACCESS       not-accessible
    STATUS           current
    DESCRIPTION
        "Entry for the cucsAaaTacacsPlusProviderTable table."
    INDEX { cucsAaaTacacsPlusProviderInstanceId }
    ::= { cucsAaaTacacsPlusProviderTable 1 }

CucsAaaTacacsPlusProviderEntry ::= SEQUENCE {
    cucsAaaTacacsPlusProviderInstanceId                              CucsManagedObjectId,
    cucsAaaTacacsPlusProviderDn                                      CucsManagedObjectDn,
    cucsAaaTacacsPlusProviderRn                                      SnmpAdminString,
    cucsAaaTacacsPlusProviderDescr                                   SnmpAdminString,
    cucsAaaTacacsPlusProviderEncKey                                  SnmpAdminString,
    cucsAaaTacacsPlusProviderKey                                     SnmpAdminString,
    cucsAaaTacacsPlusProviderKeySet                                  TruthValue,
    cucsAaaTacacsPlusProviderName                                    SnmpAdminString,
    cucsAaaTacacsPlusProviderOrder                                   Gauge32,
    cucsAaaTacacsPlusProviderPort                                    Gauge32,
    cucsAaaTacacsPlusProviderRetries                                 Gauge32,
    cucsAaaTacacsPlusProviderTimeout                                 Gauge32
}

cucsAaaTacacsPlusProviderInstanceId OBJECT-TYPE
    SYNTAX       CucsManagedObjectId
    MAX-ACCESS   not-accessible
    STATUS       current
    DESCRIPTION
        "Instance identifier of the managed object."
    ::= { cucsAaaTacacsPlusProviderEntry 1 }

cucsAaaTacacsPlusProviderDn OBJECT-TYPE
    SYNTAX       CucsManagedObjectDn
    MAX-ACCESS   read-only
    STATUS       current
    DESCRIPTION
        "Cisco UCS aaa:TacacsPlusProvider:dn managed object property"
    ::= { cucsAaaTacacsPlusProviderEntry 2 }

cucsAaaTacacsPlusProviderRn OBJECT-TYPE
    SYNTAX       SnmpAdminString
    MAX-ACCESS   read-only
    STATUS       current
    DESCRIPTION
        "Cisco UCS aaa:TacacsPlusProvider:rn managed object property"
    ::= { cucsAaaTacacsPlusProviderEntry 3 }

cucsAaaTacacsPlusProviderDescr OBJECT-TYPE
    SYNTAX       SnmpAdminString
    MAX-ACCESS   read-only
    STATUS       current
    DESCRIPTION
        "Cisco UCS aaa:TacacsPlusProvider:descr managed object property"
    ::= { cucsAaaTacacsPlusProviderEntry 4 }

cucsAaaTacacsPlusProviderEncKey OBJECT-TYPE
    SYNTAX       SnmpAdminString
    MAX-ACCESS   read-only
    STATUS       current
    DESCRIPTION
        "Cisco UCS aaa:TacacsPlusProvider:encKey managed object property"
    ::= { cucsAaaTacacsPlusProviderEntry 5 }

cucsAaaTacacsPlusProviderKey OBJECT-TYPE
    SYNTAX       SnmpAdminString
    MAX-ACCESS   read-only
    STATUS       current
    DESCRIPTION
        "Cisco UCS aaa:TacacsPlusProvider:key managed object property"
    ::= { cucsAaaTacacsPlusProviderEntry 7 }

cucsAaaTacacsPlusProviderKeySet OBJECT-TYPE
    SYNTAX       TruthValue
    MAX-ACCESS   read-only
    STATUS       current
    DESCRIPTION
        "Cisco UCS aaa:TacacsPlusProvider:keySet managed object property"
    ::= { cucsAaaTacacsPlusProviderEntry 8 }

cucsAaaTacacsPlusProviderName OBJECT-TYPE
    SYNTAX       SnmpAdminString
    MAX-ACCESS   read-only
    STATUS       current
    DESCRIPTION
        "Cisco UCS aaa:TacacsPlusProvider:name managed object property"
    ::= { cucsAaaTacacsPlusProviderEntry 9 }

cucsAaaTacacsPlusProviderOrder OBJECT-TYPE
    SYNTAX       Gauge32
    MAX-ACCESS   read-only
    STATUS       current
    DESCRIPTION
        "Cisco UCS aaa:TacacsPlusProvider:order managed object property"
    ::= { cucsAaaTacacsPlusProviderEntry 10 }

cucsAaaTacacsPlusProviderPort OBJECT-TYPE
    SYNTAX       Gauge32
    MAX-ACCESS   read-only
    STATUS       current
    DESCRIPTION
        "Cisco UCS aaa:TacacsPlusProvider:port managed object property"
    ::= { cucsAaaTacacsPlusProviderEntry 11 }

cucsAaaTacacsPlusProviderRetries OBJECT-TYPE
    SYNTAX       Gauge32
    MAX-ACCESS   read-only
    STATUS       current
    DESCRIPTION
        "Cisco UCS aaa:TacacsPlusProvider:retries managed object property"
    ::= { cucsAaaTacacsPlusProviderEntry 12 }

cucsAaaTacacsPlusProviderTimeout OBJECT-TYPE
    SYNTAX       Gauge32
    MAX-ACCESS   read-only
    STATUS       current
    DESCRIPTION
        "Cisco UCS aaa:TacacsPlusProvider:timeout managed object property"
    ::= { cucsAaaTacacsPlusProviderEntry 13 }

cucsAaaUserTable OBJECT-TYPE
    SYNTAX           SEQUENCE OF CucsAaaUserEntry
    MAX-ACCESS       not-accessible
    STATUS           current
    DESCRIPTION
        "Cisco UCS aaa:User managed object table"
    ::= { cucsAaaObjects 32 }

cucsAaaUserEntry OBJECT-TYPE
    SYNTAX           CucsAaaUserEntry
    MAX-ACCESS       not-accessible
    STATUS           current
    DESCRIPTION
        "Entry for the cucsAaaUserTable table."
    INDEX { cucsAaaUserInstanceId }
    ::= { cucsAaaUserTable 1 }

CucsAaaUserEntry ::= SEQUENCE {
    cucsAaaUserInstanceId                                            CucsManagedObjectId,
    cucsAaaUserDn                                                    CucsManagedObjectDn,
    cucsAaaUserRn                                                    SnmpAdminString,
    cucsAaaUserDescr                                                 SnmpAdminString,
    cucsAaaUserEmail                                                 SnmpAdminString,
    cucsAaaUserEncPwd                                                SnmpAdminString,
    cucsAaaUserExpiration                                            DateAndTime,
    cucsAaaUserExpires                                               TruthValue,
    cucsAaaUserFirstName                                             SnmpAdminString,
    cucsAaaUserLastName                                              SnmpAdminString,
    cucsAaaUserName                                                  SnmpAdminString,
    cucsAaaUserPhone                                                 SnmpAdminString,
    cucsAaaUserPriv                                                  CucsAaaAccess,
    cucsAaaUserPwd                                                   SnmpAdminString,
    cucsAaaUserPwdSet                                                TruthValue,
    cucsAaaUserAccountStatus                                         CucsAaaAccountStatus,
    cucsAaaUserClearPwdHistory                                       CucsAaaClear,
    cucsAaaUserPwdLifeTime                                           Gauge32,
    cucsAaaUserConfigState                                           CucsAaaConfigState,
    cucsAaaUserConfigStatusMessage                                   SnmpAdminString,
    cucsAaaUserEncPwdSet                                             TruthValue
}

cucsAaaUserInstanceId OBJECT-TYPE
    SYNTAX       CucsManagedObjectId
    MAX-ACCESS   not-accessible
    STATUS       current
    DESCRIPTION
        "Instance identifier of the managed object."
    ::= { cucsAaaUserEntry 1 }

cucsAaaUserDn OBJECT-TYPE
    SYNTAX       CucsManagedObjectDn
    MAX-ACCESS   read-only
    STATUS       current
    DESCRIPTION
        "Cisco UCS aaa:User:dn managed object property"
    ::= { cucsAaaUserEntry 2 }

cucsAaaUserRn OBJECT-TYPE
    SYNTAX       SnmpAdminString
    MAX-ACCESS   read-only
    STATUS       current
    DESCRIPTION
        "Cisco UCS aaa:User:rn managed object property"
    ::= { cucsAaaUserEntry 3 }

cucsAaaUserDescr OBJECT-TYPE
    SYNTAX       SnmpAdminString
    MAX-ACCESS   read-only
    STATUS       current
    DESCRIPTION
        "Cisco UCS aaa:User:descr managed object property"
    ::= { cucsAaaUserEntry 4 }

cucsAaaUserEmail OBJECT-TYPE
    SYNTAX       SnmpAdminString
    MAX-ACCESS   read-only
    STATUS       current
    DESCRIPTION
        "Cisco UCS aaa:User:email managed object property"
    ::= { cucsAaaUserEntry 5 }

cucsAaaUserEncPwd OBJECT-TYPE
    SYNTAX       SnmpAdminString
    MAX-ACCESS   read-only
    STATUS       current
    DESCRIPTION
        "Cisco UCS aaa:User:encPwd managed object property"
    ::= { cucsAaaUserEntry 6 }

cucsAaaUserExpiration OBJECT-TYPE
    SYNTAX       DateAndTime
    MAX-ACCESS   read-only
    STATUS       current
    DESCRIPTION
        "Cisco UCS aaa:User:expiration managed object property"
    ::= { cucsAaaUserEntry 7 }

cucsAaaUserExpires OBJECT-TYPE
    SYNTAX       TruthValue
    MAX-ACCESS   read-only
    STATUS       current
    DESCRIPTION
        "Cisco UCS aaa:User:expires managed object property"
    ::= { cucsAaaUserEntry 8 }

cucsAaaUserFirstName OBJECT-TYPE
    SYNTAX       SnmpAdminString
    MAX-ACCESS   read-only
    STATUS       current
    DESCRIPTION
        "Cisco UCS aaa:User:firstName managed object property"
    ::= { cucsAaaUserEntry 9 }

cucsAaaUserLastName OBJECT-TYPE
    SYNTAX       SnmpAdminString
    MAX-ACCESS   read-only
    STATUS       current
    DESCRIPTION
        "Cisco UCS aaa:User:lastName managed object property"
    ::= { cucsAaaUserEntry 11 }

cucsAaaUserName OBJECT-TYPE
    SYNTAX       SnmpAdminString
    MAX-ACCESS   read-only
    STATUS       current
    DESCRIPTION
        "Cisco UCS aaa:User:name managed object property"
    ::= { cucsAaaUserEntry 12 }

cucsAaaUserPhone OBJECT-TYPE
    SYNTAX       SnmpAdminString
    MAX-ACCESS   read-only
    STATUS       current
    DESCRIPTION
        "Cisco UCS aaa:User:phone managed object property"
    ::= { cucsAaaUserEntry 13 }

cucsAaaUserPriv OBJECT-TYPE
    SYNTAX       CucsAaaAccess
    MAX-ACCESS   read-only
    STATUS       current
    DESCRIPTION
        "Cisco UCS aaa:User:priv managed object property"
    ::= { cucsAaaUserEntry 14 }

cucsAaaUserPwd OBJECT-TYPE
    SYNTAX       SnmpAdminString
    MAX-ACCESS   read-only
    STATUS       current
    DESCRIPTION
        "Cisco UCS aaa:User:pwd managed object property"
    ::= { cucsAaaUserEntry 15 }

cucsAaaUserPwdSet OBJECT-TYPE
    SYNTAX       TruthValue
    MAX-ACCESS   read-only
    STATUS       current
    DESCRIPTION
        "Cisco UCS aaa:User:pwdSet managed object property"
    ::= { cucsAaaUserEntry 16 }

cucsAaaUserAccountStatus OBJECT-TYPE
    SYNTAX       CucsAaaAccountStatus
    MAX-ACCESS   read-only
    STATUS       current
    DESCRIPTION
        "Cisco UCS aaa:User:accountStatus managed object property"
    ::= { cucsAaaUserEntry 17 }

cucsAaaUserClearPwdHistory OBJECT-TYPE
    SYNTAX       CucsAaaClear
    MAX-ACCESS   read-only
    STATUS       current
    DESCRIPTION
        "Cisco UCS aaa:User:clearPwdHistory managed object property"
    ::= { cucsAaaUserEntry 18 }

cucsAaaUserPwdLifeTime OBJECT-TYPE
    SYNTAX       Gauge32
    MAX-ACCESS   read-only
    STATUS       current
    DESCRIPTION
        "Cisco UCS aaa:User:pwdLifeTime managed object property"
    ::= { cucsAaaUserEntry 19 }

cucsAaaUserConfigState OBJECT-TYPE
    SYNTAX       CucsAaaConfigState
    MAX-ACCESS   read-only
    STATUS       current
    DESCRIPTION
        "Cisco UCS aaa:User:configState managed object property"
    ::= { cucsAaaUserEntry 20 }

cucsAaaUserConfigStatusMessage OBJECT-TYPE
    SYNTAX       SnmpAdminString
    MAX-ACCESS   read-only
    STATUS       current
    DESCRIPTION
        "Cisco UCS aaa:User:configStatusMessage managed object property"
    ::= { cucsAaaUserEntry 21 }

cucsAaaUserEncPwdSet OBJECT-TYPE
    SYNTAX       TruthValue
    MAX-ACCESS   read-only
    STATUS       current
    DESCRIPTION
        "Cisco UCS aaa:User:encPwdSet managed object property"
    ::= { cucsAaaUserEntry 22 }

cucsAaaUserDataTable OBJECT-TYPE
    SYNTAX           SEQUENCE OF CucsAaaUserDataEntry
    MAX-ACCESS       not-accessible
    STATUS           current
    DESCRIPTION
        "Cisco UCS aaa:UserData managed object table"
    ::= { cucsAaaObjects 40 }

cucsAaaUserDataEntry OBJECT-TYPE
    SYNTAX           CucsAaaUserDataEntry
    MAX-ACCESS       not-accessible
    STATUS           current
    DESCRIPTION
        "Entry for the cucsAaaUserDataTable table."
    INDEX { cucsAaaUserDataInstanceId }
    ::= { cucsAaaUserDataTable 1 }

CucsAaaUserDataEntry ::= SEQUENCE {
    cucsAaaUserDataInstanceId                                        CucsManagedObjectId,
    cucsAaaUserDataDn                                                CucsManagedObjectDn,
    cucsAaaUserDataRn                                                SnmpAdminString,
    cucsAaaUserDataDescr                                             SnmpAdminString,
    cucsAaaUserDataIntId                                             SnmpAdminString,
    cucsAaaUserDataName                                              SnmpAdminString,
    cucsAaaUserDataPwdChangeCount                                    Gauge32,
    cucsAaaUserDataPwdChangeIntervalBegin                            DateAndTime,
    cucsAaaUserDataPwdChangedDate                                    DateAndTime,
    cucsAaaUserDataPwdHistory                                        SnmpAdminString,
    cucsAaaUserDataPolicyLevel                                       Gauge32,
    cucsAaaUserDataPolicyOwner                                       CucsPolicyPolicyOwner
}

cucsAaaUserDataInstanceId OBJECT-TYPE
    SYNTAX       CucsManagedObjectId
    MAX-ACCESS   not-accessible
    STATUS       current
    DESCRIPTION
        "Instance identifier of the managed object."
    ::= { cucsAaaUserDataEntry 1 }

cucsAaaUserDataDn OBJECT-TYPE
    SYNTAX       CucsManagedObjectDn
    MAX-ACCESS   read-only
    STATUS       current
    DESCRIPTION
        "Cisco UCS aaa:UserData:dn managed object property"
    ::= { cucsAaaUserDataEntry 2 }

cucsAaaUserDataRn OBJECT-TYPE
    SYNTAX       SnmpAdminString
    MAX-ACCESS   read-only
    STATUS       current
    DESCRIPTION
        "Cisco UCS aaa:UserData:rn managed object property"
    ::= { cucsAaaUserDataEntry 3 }

cucsAaaUserDataDescr OBJECT-TYPE
    SYNTAX       SnmpAdminString
    MAX-ACCESS   read-only
    STATUS       current
    DESCRIPTION
        "Cisco UCS aaa:UserData:descr managed object property"
    ::= { cucsAaaUserDataEntry 4 }

cucsAaaUserDataIntId OBJECT-TYPE
    SYNTAX       SnmpAdminString
    MAX-ACCESS   read-only
    STATUS       current
    DESCRIPTION
        "Cisco UCS aaa:UserData:intId managed object property"
    ::= { cucsAaaUserDataEntry 5 }

cucsAaaUserDataName OBJECT-TYPE
    SYNTAX       SnmpAdminString
    MAX-ACCESS   read-only
    STATUS       current
    DESCRIPTION
        "Cisco UCS aaa:UserData:name managed object property"
    ::= { cucsAaaUserDataEntry 6 }

cucsAaaUserDataPwdChangeCount OBJECT-TYPE
    SYNTAX       Gauge32
    MAX-ACCESS   read-only
    STATUS       current
    DESCRIPTION
        "Cisco UCS aaa:UserData:pwdChangeCount managed object property"
    ::= { cucsAaaUserDataEntry 7 }

cucsAaaUserDataPwdChangeIntervalBegin OBJECT-TYPE
    SYNTAX       DateAndTime
    MAX-ACCESS   read-only
    STATUS       current
    DESCRIPTION
        "Cisco UCS aaa:UserData:pwdChangeIntervalBegin
        managed object property"
    ::= { cucsAaaUserDataEntry 8 }

cucsAaaUserDataPwdChangedDate OBJECT-TYPE
    SYNTAX       DateAndTime
    MAX-ACCESS   read-only
    STATUS       current
    DESCRIPTION
        "Cisco UCS aaa:UserData:pwdChangedDate managed object property"
    ::= { cucsAaaUserDataEntry 9 }

cucsAaaUserDataPwdHistory OBJECT-TYPE
    SYNTAX       SnmpAdminString
    MAX-ACCESS   read-only
    STATUS       current
    DESCRIPTION
        "Cisco UCS aaa:UserData:pwdHistory managed object property"
    ::= { cucsAaaUserDataEntry 10 }

cucsAaaUserDataPolicyLevel OBJECT-TYPE
    SYNTAX       Gauge32
    MAX-ACCESS   read-only
    STATUS       current
    DESCRIPTION
        "Cisco UCS aaa:UserData:policyLevel managed object property"
    ::= { cucsAaaUserDataEntry 11 }

cucsAaaUserDataPolicyOwner OBJECT-TYPE
    SYNTAX       CucsPolicyPolicyOwner
    MAX-ACCESS   read-only
    STATUS       current
    DESCRIPTION
        "Cisco UCS aaa:UserData:policyOwner managed object property"
    ::= { cucsAaaUserDataEntry 12 }

cucsAaaUserEpTable OBJECT-TYPE
    SYNTAX           SEQUENCE OF CucsAaaUserEpEntry
    MAX-ACCESS       not-accessible
    STATUS           current
    DESCRIPTION
        "Cisco UCS aaa:UserEp managed object table"
    ::= { cucsAaaObjects 33 }

cucsAaaUserEpEntry OBJECT-TYPE
    SYNTAX           CucsAaaUserEpEntry
    MAX-ACCESS       not-accessible
    STATUS           current
    DESCRIPTION
        "Entry for the cucsAaaUserEpTable table."
    INDEX { cucsAaaUserEpInstanceId }
    ::= { cucsAaaUserEpTable 1 }

CucsAaaUserEpEntry ::= SEQUENCE {
    cucsAaaUserEpInstanceId                                          CucsManagedObjectId,
    cucsAaaUserEpDn                                                  CucsManagedObjectDn,
    cucsAaaUserEpRn                                                  SnmpAdminString,
    cucsAaaUserEpDescr                                               SnmpAdminString,
    cucsAaaUserEpFsmDescr                                            SnmpAdminString,
    cucsAaaUserEpFsmPrev                                             SnmpAdminString,
    cucsAaaUserEpFsmProgr                                            Gauge32,
    cucsAaaUserEpFsmRmtInvErrCode                                    Gauge32,
    cucsAaaUserEpFsmRmtInvErrDescr                                   SnmpAdminString,
    cucsAaaUserEpFsmRmtInvRslt                                       CucsConditionRemoteInvRslt,
    cucsAaaUserEpFsmStageDescr                                       SnmpAdminString,
    cucsAaaUserEpFsmStamp                                            DateAndTime,
    cucsAaaUserEpFsmStatus                                           SnmpAdminString,
    cucsAaaUserEpFsmTry                                              Gauge32,
    cucsAaaUserEpIntId                                               SnmpAdminString,
    cucsAaaUserEpName                                                SnmpAdminString,
    cucsAaaUserEpPwdStrengthCheck                                    TruthValue,
    cucsAaaUserEpPolicyLevel                                         Gauge32,
    cucsAaaUserEpPolicyOwner                                         CucsPolicyPolicyOwner
}

cucsAaaUserEpInstanceId OBJECT-TYPE
    SYNTAX       CucsManagedObjectId
    MAX-ACCESS   not-accessible
    STATUS       current
    DESCRIPTION
        "Instance identifier of the managed object."
    ::= { cucsAaaUserEpEntry 1 }

cucsAaaUserEpDn OBJECT-TYPE
    SYNTAX       CucsManagedObjectDn
    MAX-ACCESS   read-only
    STATUS       current
    DESCRIPTION
        "Cisco UCS aaa:UserEp:dn managed object property"
    ::= { cucsAaaUserEpEntry 2 }

cucsAaaUserEpRn OBJECT-TYPE
    SYNTAX       SnmpAdminString
    MAX-ACCESS   read-only
    STATUS       current
    DESCRIPTION
        "Cisco UCS aaa:UserEp:rn managed object property"
    ::= { cucsAaaUserEpEntry 3 }

cucsAaaUserEpDescr OBJECT-TYPE
    SYNTAX       SnmpAdminString
    MAX-ACCESS   read-only
    STATUS       current
    DESCRIPTION
        "Cisco UCS aaa:UserEp:descr managed object property"
    ::= { cucsAaaUserEpEntry 4 }

cucsAaaUserEpFsmDescr OBJECT-TYPE
    SYNTAX       SnmpAdminString
    MAX-ACCESS   read-only
    STATUS       current
    DESCRIPTION
        "Cisco UCS aaa:UserEp:fsmDescr managed object property"
    ::= { cucsAaaUserEpEntry 5 }

cucsAaaUserEpFsmPrev OBJECT-TYPE
    SYNTAX       SnmpAdminString
    MAX-ACCESS   read-only
    STATUS       current
    DESCRIPTION
        "Cisco UCS aaa:UserEp:fsmPrev managed object property"
    ::= { cucsAaaUserEpEntry 6 }

cucsAaaUserEpFsmProgr OBJECT-TYPE
    SYNTAX       Gauge32
    MAX-ACCESS   read-only
    STATUS       current
    DESCRIPTION
        "Cisco UCS aaa:UserEp:fsmProgr managed object property"
    ::= { cucsAaaUserEpEntry 7 }

cucsAaaUserEpFsmRmtInvErrCode OBJECT-TYPE
    SYNTAX       Gauge32
    MAX-ACCESS   read-only
    STATUS       current
    DESCRIPTION
        "Cisco UCS aaa:UserEp:fsmRmtInvErrCode managed object property"
    ::= { cucsAaaUserEpEntry 8 }

cucsAaaUserEpFsmRmtInvErrDescr OBJECT-TYPE
    SYNTAX       SnmpAdminString
    MAX-ACCESS   read-only
    STATUS       current
    DESCRIPTION
        "Cisco UCS aaa:UserEp:fsmRmtInvErrDescr managed object property"
    ::= { cucsAaaUserEpEntry 9 }

cucsAaaUserEpFsmRmtInvRslt OBJECT-TYPE
    SYNTAX       CucsConditionRemoteInvRslt
    MAX-ACCESS   read-only
    STATUS       current
    DESCRIPTION
        "Cisco UCS aaa:UserEp:fsmRmtInvRslt managed object property"
    ::= { cucsAaaUserEpEntry 10 }

cucsAaaUserEpFsmStageDescr OBJECT-TYPE
    SYNTAX       SnmpAdminString
    MAX-ACCESS   read-only
    STATUS       current
    DESCRIPTION
        "Cisco UCS aaa:UserEp:fsmStageDescr managed object property"
    ::= { cucsAaaUserEpEntry 11 }

cucsAaaUserEpFsmStamp OBJECT-TYPE
    SYNTAX       DateAndTime
    MAX-ACCESS   read-only
    STATUS       current
    DESCRIPTION
        "Cisco UCS aaa:UserEp:fsmStamp managed object property"
    ::= { cucsAaaUserEpEntry 12 }

cucsAaaUserEpFsmStatus OBJECT-TYPE
    SYNTAX       SnmpAdminString
    MAX-ACCESS   read-only
    STATUS       current
    DESCRIPTION
        "Cisco UCS aaa:UserEp:fsmStatus managed object property"
    ::= { cucsAaaUserEpEntry 13 }

cucsAaaUserEpFsmTry OBJECT-TYPE
    SYNTAX       Gauge32
    MAX-ACCESS   read-only
    STATUS       current
    DESCRIPTION
        "Cisco UCS aaa:UserEp:fsmTry managed object property"
    ::= { cucsAaaUserEpEntry 14 }

cucsAaaUserEpIntId OBJECT-TYPE
    SYNTAX       SnmpAdminString
    MAX-ACCESS   read-only
    STATUS       current
    DESCRIPTION
        "Cisco UCS aaa:UserEp:intId managed object property"
    ::= { cucsAaaUserEpEntry 15 }

cucsAaaUserEpName OBJECT-TYPE
    SYNTAX       SnmpAdminString
    MAX-ACCESS   read-only
    STATUS       current
    DESCRIPTION
        "Cisco UCS aaa:UserEp:name managed object property"
    ::= { cucsAaaUserEpEntry 16 }

cucsAaaUserEpPwdStrengthCheck OBJECT-TYPE
    SYNTAX       TruthValue
    MAX-ACCESS   read-only
    STATUS       current
    DESCRIPTION
        "Cisco UCS aaa:UserEp:pwdStrengthCheck managed object property"
    ::= { cucsAaaUserEpEntry 17 }

cucsAaaUserEpPolicyLevel OBJECT-TYPE
    SYNTAX       Gauge32
    MAX-ACCESS   read-only
    STATUS       current
    DESCRIPTION
        "Cisco UCS aaa:UserEp:policyLevel managed object property"
    ::= { cucsAaaUserEpEntry 19 }

cucsAaaUserEpPolicyOwner OBJECT-TYPE
    SYNTAX       CucsPolicyPolicyOwner
    MAX-ACCESS   read-only
    STATUS       current
    DESCRIPTION
        "Cisco UCS aaa:UserEp:policyOwner managed object property"
    ::= { cucsAaaUserEpEntry 20 }

cucsAaaUserEpFsmTable OBJECT-TYPE
    SYNTAX           SEQUENCE OF CucsAaaUserEpFsmEntry
    MAX-ACCESS       not-accessible
    STATUS           current
    DESCRIPTION
        "Cisco UCS aaa:UserEpFsm managed object table"
    ::= { cucsAaaObjects 53 }

cucsAaaUserEpFsmEntry OBJECT-TYPE
    SYNTAX           CucsAaaUserEpFsmEntry
    MAX-ACCESS       not-accessible
    STATUS           current
    DESCRIPTION
        "Entry for the cucsAaaUserEpFsmTable table."
    INDEX { cucsAaaUserEpFsmInstanceId }
    ::= { cucsAaaUserEpFsmTable 1 }

CucsAaaUserEpFsmEntry ::= SEQUENCE {
    cucsAaaUserEpFsmInstanceId                                       CucsManagedObjectId,
    cucsAaaUserEpFsmDn                                               CucsManagedObjectDn,
    cucsAaaUserEpFsmRn                                               SnmpAdminString,
    cucsAaaUserEpFsmCompletionTime                                   DateAndTime,
    cucsAaaUserEpFsmCurrentFsm                                       CucsAaaUserEpFsmCurrentFsm,
    cucsAaaUserEpFsmDescrData                                        SnmpAdminString,
    cucsAaaUserEpFsmFsmStatus                                        CucsFsmFsmStageStatus,
    cucsAaaUserEpFsmProgress                                         Gauge32,
    cucsAaaUserEpFsmRmtErrCode                                       Gauge32,
    cucsAaaUserEpFsmRmtErrDescr                                      SnmpAdminString,
    cucsAaaUserEpFsmRmtRslt                                          CucsConditionRemoteInvRslt
}

cucsAaaUserEpFsmInstanceId OBJECT-TYPE
    SYNTAX       CucsManagedObjectId
    MAX-ACCESS   not-accessible
    STATUS       current
    DESCRIPTION
        "Instance identifier of the managed object."
    ::= { cucsAaaUserEpFsmEntry 1 }

cucsAaaUserEpFsmDn OBJECT-TYPE
    SYNTAX       CucsManagedObjectDn
    MAX-ACCESS   read-only
    STATUS       current
    DESCRIPTION
        "Cisco UCS aaa:UserEpFsm:dn managed object property"
    ::= { cucsAaaUserEpFsmEntry 2 }

cucsAaaUserEpFsmRn OBJECT-TYPE
    SYNTAX       SnmpAdminString
    MAX-ACCESS   read-only
    STATUS       current
    DESCRIPTION
        "Cisco UCS aaa:UserEpFsm:rn managed object property"
    ::= { cucsAaaUserEpFsmEntry 3 }

cucsAaaUserEpFsmCompletionTime OBJECT-TYPE
    SYNTAX       DateAndTime
    MAX-ACCESS   read-only
    STATUS       current
    DESCRIPTION
        "Cisco UCS aaa:UserEpFsm:completionTime managed object property"
    ::= { cucsAaaUserEpFsmEntry 4 }

cucsAaaUserEpFsmCurrentFsm OBJECT-TYPE
    SYNTAX       CucsAaaUserEpFsmCurrentFsm
    MAX-ACCESS   read-only
    STATUS       current
    DESCRIPTION
        "Cisco UCS aaa:UserEpFsm:currentFsm managed object property"
    ::= { cucsAaaUserEpFsmEntry 5 }

cucsAaaUserEpFsmDescrData OBJECT-TYPE
    SYNTAX       SnmpAdminString
    MAX-ACCESS   read-only
    STATUS       current
    DESCRIPTION
        "Cisco UCS aaa:UserEpFsm:descr managed object property"
    ::= { cucsAaaUserEpFsmEntry 6 }

cucsAaaUserEpFsmFsmStatus OBJECT-TYPE
    SYNTAX       CucsFsmFsmStageStatus
    MAX-ACCESS   read-only
    STATUS       current
    DESCRIPTION
        "Cisco UCS aaa:UserEpFsm:fsmStatus managed object property"
    ::= { cucsAaaUserEpFsmEntry 7 }

cucsAaaUserEpFsmProgress OBJECT-TYPE
    SYNTAX       Gauge32
    MAX-ACCESS   read-only
    STATUS       current
    DESCRIPTION
        "Cisco UCS aaa:UserEpFsm:progress managed object property"
    ::= { cucsAaaUserEpFsmEntry 8 }

cucsAaaUserEpFsmRmtErrCode OBJECT-TYPE
    SYNTAX       Gauge32
    MAX-ACCESS   read-only
    STATUS       current
    DESCRIPTION
        "Cisco UCS aaa:UserEpFsm:rmtErrCode managed object property"
    ::= { cucsAaaUserEpFsmEntry 9 }

cucsAaaUserEpFsmRmtErrDescr OBJECT-TYPE
    SYNTAX       SnmpAdminString
    MAX-ACCESS   read-only
    STATUS       current
    DESCRIPTION
        "Cisco UCS aaa:UserEpFsm:rmtErrDescr managed object property"
    ::= { cucsAaaUserEpFsmEntry 10 }

cucsAaaUserEpFsmRmtRslt OBJECT-TYPE
    SYNTAX       CucsConditionRemoteInvRslt
    MAX-ACCESS   read-only
    STATUS       current
    DESCRIPTION
        "Cisco UCS aaa:UserEpFsm:rmtRslt managed object property"
    ::= { cucsAaaUserEpFsmEntry 11 }

cucsAaaUserEpFsmStageTable OBJECT-TYPE
    SYNTAX           SEQUENCE OF CucsAaaUserEpFsmStageEntry
    MAX-ACCESS       not-accessible
    STATUS           current
    DESCRIPTION
        "Cisco UCS aaa:UserEpFsmStage managed object table"
    ::= { cucsAaaObjects 54 }

cucsAaaUserEpFsmStageEntry OBJECT-TYPE
    SYNTAX           CucsAaaUserEpFsmStageEntry
    MAX-ACCESS       not-accessible
    STATUS           current
    DESCRIPTION
        "Entry for the cucsAaaUserEpFsmStageTable table."
    INDEX { cucsAaaUserEpFsmStageInstanceId }
    ::= { cucsAaaUserEpFsmStageTable 1 }

CucsAaaUserEpFsmStageEntry ::= SEQUENCE {
    cucsAaaUserEpFsmStageInstanceId                                  CucsManagedObjectId,
    cucsAaaUserEpFsmStageDn                                          CucsManagedObjectDn,
    cucsAaaUserEpFsmStageRn                                          SnmpAdminString,
    cucsAaaUserEpFsmStageDescrData                                   SnmpAdminString,
    cucsAaaUserEpFsmStageLastUpdateTime                              DateAndTime,
    cucsAaaUserEpFsmStageName                                        CucsAaaUserEpFsmStageName,
    cucsAaaUserEpFsmStageOrder                                       Gauge32,
    cucsAaaUserEpFsmStageRetry                                       Gauge32,
    cucsAaaUserEpFsmStageStageStatus                                 CucsFsmFsmStageStatus
}

cucsAaaUserEpFsmStageInstanceId OBJECT-TYPE
    SYNTAX       CucsManagedObjectId
    MAX-ACCESS   not-accessible
    STATUS       current
    DESCRIPTION
        "Instance identifier of the managed object."
    ::= { cucsAaaUserEpFsmStageEntry 1 }

cucsAaaUserEpFsmStageDn OBJECT-TYPE
    SYNTAX       CucsManagedObjectDn
    MAX-ACCESS   read-only
    STATUS       current
    DESCRIPTION
        "Cisco UCS aaa:UserEpFsmStage:dn managed object property"
    ::= { cucsAaaUserEpFsmStageEntry 2 }

cucsAaaUserEpFsmStageRn OBJECT-TYPE
    SYNTAX       SnmpAdminString
    MAX-ACCESS   read-only
    STATUS       current
    DESCRIPTION
        "Cisco UCS aaa:UserEpFsmStage:rn managed object property"
    ::= { cucsAaaUserEpFsmStageEntry 3 }

cucsAaaUserEpFsmStageDescrData OBJECT-TYPE
    SYNTAX       SnmpAdminString
    MAX-ACCESS   read-only
    STATUS       current
    DESCRIPTION
        "Cisco UCS aaa:UserEpFsmStage:descr managed object property"
    ::= { cucsAaaUserEpFsmStageEntry 4 }

cucsAaaUserEpFsmStageLastUpdateTime OBJECT-TYPE
    SYNTAX       DateAndTime
    MAX-ACCESS   read-only
    STATUS       current
    DESCRIPTION
        "Cisco UCS aaa:UserEpFsmStage:lastUpdateTime managed
        object property"
    ::= { cucsAaaUserEpFsmStageEntry 5 }

cucsAaaUserEpFsmStageName OBJECT-TYPE
    SYNTAX       CucsAaaUserEpFsmStageName
    MAX-ACCESS   read-only
    STATUS       current
    DESCRIPTION
        "Cisco UCS aaa:UserEpFsmStage:name managed object property"
    ::= { cucsAaaUserEpFsmStageEntry 6 }

cucsAaaUserEpFsmStageOrder OBJECT-TYPE
    SYNTAX       Gauge32
    MAX-ACCESS   read-only
    STATUS       current
    DESCRIPTION
        "Cisco UCS aaa:UserEpFsmStage:order managed object property"
    ::= { cucsAaaUserEpFsmStageEntry 7 }

cucsAaaUserEpFsmStageRetry OBJECT-TYPE
    SYNTAX       Gauge32
    MAX-ACCESS   read-only
    STATUS       current
    DESCRIPTION
        "Cisco UCS aaa:UserEpFsmStage:retry managed object property"
    ::= { cucsAaaUserEpFsmStageEntry 8 }

cucsAaaUserEpFsmStageStageStatus OBJECT-TYPE
    SYNTAX       CucsFsmFsmStageStatus
    MAX-ACCESS   read-only
    STATUS       current
    DESCRIPTION
        "Cisco UCS aaa:UserEpFsmStage:stageStatus managed object property"
    ::= { cucsAaaUserEpFsmStageEntry 9 }

cucsAaaUserEpFsmTaskTable OBJECT-TYPE
    SYNTAX           SEQUENCE OF CucsAaaUserEpFsmTaskEntry
    MAX-ACCESS       not-accessible
    STATUS           current
    DESCRIPTION
        "Cisco UCS aaa:UserEpFsmTask managed object table"
    ::= { cucsAaaObjects 34 }

cucsAaaUserEpFsmTaskEntry OBJECT-TYPE
    SYNTAX           CucsAaaUserEpFsmTaskEntry
    MAX-ACCESS       not-accessible
    STATUS           current
    DESCRIPTION
        "Entry for the cucsAaaUserEpFsmTaskTable table."
    INDEX { cucsAaaUserEpFsmTaskInstanceId }
    ::= { cucsAaaUserEpFsmTaskTable 1 }

CucsAaaUserEpFsmTaskEntry ::= SEQUENCE {
    cucsAaaUserEpFsmTaskInstanceId                                   CucsManagedObjectId,
    cucsAaaUserEpFsmTaskDn                                           CucsManagedObjectDn,
    cucsAaaUserEpFsmTaskRn                                           SnmpAdminString,
    cucsAaaUserEpFsmTaskCompletion                                   CucsFsmCompletion,
    cucsAaaUserEpFsmTaskFlags                                        CucsFsmFlags,
    cucsAaaUserEpFsmTaskItem                                         CucsAaaUserEpFsmTaskItem,
    cucsAaaUserEpFsmTaskSeqId                                        Gauge32
}

cucsAaaUserEpFsmTaskInstanceId OBJECT-TYPE
    SYNTAX       CucsManagedObjectId
    MAX-ACCESS   not-accessible
    STATUS       current
    DESCRIPTION
        "Instance identifier of the managed object."
    ::= { cucsAaaUserEpFsmTaskEntry 1 }

cucsAaaUserEpFsmTaskDn OBJECT-TYPE
    SYNTAX       CucsManagedObjectDn
    MAX-ACCESS   read-only
    STATUS       current
    DESCRIPTION
        "Cisco UCS aaa:UserEpFsmTask:dn managed object property"
    ::= { cucsAaaUserEpFsmTaskEntry 2 }

cucsAaaUserEpFsmTaskRn OBJECT-TYPE
    SYNTAX       SnmpAdminString
    MAX-ACCESS   read-only
    STATUS       current
    DESCRIPTION
        "Cisco UCS aaa:UserEpFsmTask:rn managed object property"
    ::= { cucsAaaUserEpFsmTaskEntry 3 }

cucsAaaUserEpFsmTaskCompletion OBJECT-TYPE
    SYNTAX       CucsFsmCompletion
    MAX-ACCESS   read-only
    STATUS       current
    DESCRIPTION
        "Cisco UCS aaa:UserEpFsmTask:completion managed object property"
    ::= { cucsAaaUserEpFsmTaskEntry 4 }

cucsAaaUserEpFsmTaskFlags OBJECT-TYPE
    SYNTAX       CucsFsmFlags
    MAX-ACCESS   read-only
    STATUS       current
    DESCRIPTION
        "Cisco UCS aaa:UserEpFsmTask:flags managed object property"
    ::= { cucsAaaUserEpFsmTaskEntry 5 }

cucsAaaUserEpFsmTaskItem OBJECT-TYPE
    SYNTAX       CucsAaaUserEpFsmTaskItem
    MAX-ACCESS   read-only
    STATUS       current
    DESCRIPTION
        "Cisco UCS aaa:UserEpFsmTask:item managed object property"
    ::= { cucsAaaUserEpFsmTaskEntry 6 }

cucsAaaUserEpFsmTaskSeqId OBJECT-TYPE
    SYNTAX       Gauge32
    MAX-ACCESS   read-only
    STATUS       current
    DESCRIPTION
        "Cisco UCS aaa:UserEpFsmTask:seqId managed object property"
    ::= { cucsAaaUserEpFsmTaskEntry 7 }

cucsAaaUserLocaleTable OBJECT-TYPE
    SYNTAX           SEQUENCE OF CucsAaaUserLocaleEntry
    MAX-ACCESS       not-accessible
    STATUS           current
    DESCRIPTION
        "Cisco UCS aaa:UserLocale managed object table"
    ::= { cucsAaaObjects 35 }

cucsAaaUserLocaleEntry OBJECT-TYPE
    SYNTAX           CucsAaaUserLocaleEntry
    MAX-ACCESS       not-accessible
    STATUS           current
    DESCRIPTION
        "Entry for the cucsAaaUserLocaleTable table."
    INDEX { cucsAaaUserLocaleInstanceId }
    ::= { cucsAaaUserLocaleTable 1 }

CucsAaaUserLocaleEntry ::= SEQUENCE {
    cucsAaaUserLocaleInstanceId                                      CucsManagedObjectId,
    cucsAaaUserLocaleDn                                              CucsManagedObjectDn,
    cucsAaaUserLocaleRn                                              SnmpAdminString,
    cucsAaaUserLocaleDescr                                           SnmpAdminString,
    cucsAaaUserLocaleName                                            SnmpAdminString,
    cucsAaaUserLocaleConfigState                                     CucsAaaConfigState,
    cucsAaaUserLocaleConfigStatusMessage                             SnmpAdminString
}

cucsAaaUserLocaleInstanceId OBJECT-TYPE
    SYNTAX       CucsManagedObjectId
    MAX-ACCESS   not-accessible
    STATUS       current
    DESCRIPTION
        "Instance identifier of the managed object."
    ::= { cucsAaaUserLocaleEntry 1 }

cucsAaaUserLocaleDn OBJECT-TYPE
    SYNTAX       CucsManagedObjectDn
    MAX-ACCESS   read-only
    STATUS       current
    DESCRIPTION
        "Cisco UCS aaa:UserLocale:dn managed object property"
    ::= { cucsAaaUserLocaleEntry 2 }

cucsAaaUserLocaleRn OBJECT-TYPE
    SYNTAX       SnmpAdminString
    MAX-ACCESS   read-only
    STATUS       current
    DESCRIPTION
        "Cisco UCS aaa:UserLocale:rn managed object property"
    ::= { cucsAaaUserLocaleEntry 3 }

cucsAaaUserLocaleDescr OBJECT-TYPE
    SYNTAX       SnmpAdminString
    MAX-ACCESS   read-only
    STATUS       current
    DESCRIPTION
        "Cisco UCS aaa:UserLocale:descr managed object property"
    ::= { cucsAaaUserLocaleEntry 4 }

cucsAaaUserLocaleName OBJECT-TYPE
    SYNTAX       SnmpAdminString
    MAX-ACCESS   read-only
    STATUS       current
    DESCRIPTION
        "Cisco UCS aaa:UserLocale:name managed object property"
    ::= { cucsAaaUserLocaleEntry 6 }

cucsAaaUserLocaleConfigState OBJECT-TYPE
    SYNTAX       CucsAaaConfigState
    MAX-ACCESS   read-only
    STATUS       current
    DESCRIPTION
        "Cisco UCS aaa:UserLocale:configState managed object property"
    ::= { cucsAaaUserLocaleEntry 7 }

cucsAaaUserLocaleConfigStatusMessage OBJECT-TYPE
    SYNTAX       SnmpAdminString
    MAX-ACCESS   read-only
    STATUS       current
    DESCRIPTION
        "Cisco UCS aaa:UserLocale:configStatusMessage managed
        object property"
    ::= { cucsAaaUserLocaleEntry 8 }

cucsAaaUserRoleTable OBJECT-TYPE
    SYNTAX           SEQUENCE OF CucsAaaUserRoleEntry
    MAX-ACCESS       not-accessible
    STATUS           current
    DESCRIPTION
        "Cisco UCS aaa:UserRole managed object table"
    ::= { cucsAaaObjects 36 }

cucsAaaUserRoleEntry OBJECT-TYPE
    SYNTAX           CucsAaaUserRoleEntry
    MAX-ACCESS       not-accessible
    STATUS           current
    DESCRIPTION
        "Entry for the cucsAaaUserRoleTable table."
    INDEX { cucsAaaUserRoleInstanceId }
    ::= { cucsAaaUserRoleTable 1 }

CucsAaaUserRoleEntry ::= SEQUENCE {
    cucsAaaUserRoleInstanceId                                        CucsManagedObjectId,
    cucsAaaUserRoleDn                                                CucsManagedObjectDn,
    cucsAaaUserRoleRn                                                SnmpAdminString,
    cucsAaaUserRoleDescr                                             SnmpAdminString,
    cucsAaaUserRoleName                                              SnmpAdminString,
    cucsAaaUserRoleConfigState                                       CucsAaaConfigState,
    cucsAaaUserRoleConfigStatusMessage                               SnmpAdminString
}

cucsAaaUserRoleInstanceId OBJECT-TYPE
    SYNTAX       CucsManagedObjectId
    MAX-ACCESS   not-accessible
    STATUS       current
    DESCRIPTION
        "Instance identifier of the managed object."
    ::= { cucsAaaUserRoleEntry 1 }

cucsAaaUserRoleDn OBJECT-TYPE
    SYNTAX       CucsManagedObjectDn
    MAX-ACCESS   read-only
    STATUS       current
    DESCRIPTION
        "Cisco UCS aaa:UserRole:dn managed object property"
    ::= { cucsAaaUserRoleEntry 2 }

cucsAaaUserRoleRn OBJECT-TYPE
    SYNTAX       SnmpAdminString
    MAX-ACCESS   read-only
    STATUS       current
    DESCRIPTION
        "Cisco UCS aaa:UserRole:rn managed object property"
    ::= { cucsAaaUserRoleEntry 3 }

cucsAaaUserRoleDescr OBJECT-TYPE
    SYNTAX       SnmpAdminString
    MAX-ACCESS   read-only
    STATUS       current
    DESCRIPTION
        "Cisco UCS aaa:UserRole:descr managed object property"
    ::= { cucsAaaUserRoleEntry 4 }

cucsAaaUserRoleName OBJECT-TYPE
    SYNTAX       SnmpAdminString
    MAX-ACCESS   read-only
    STATUS       current
    DESCRIPTION
        "Cisco UCS aaa:UserRole:name managed object property"
    ::= { cucsAaaUserRoleEntry 6 }

cucsAaaUserRoleConfigState OBJECT-TYPE
    SYNTAX       CucsAaaConfigState
    MAX-ACCESS   read-only
    STATUS       current
    DESCRIPTION
        "Cisco UCS aaa:UserRole:configState managed object property"
    ::= { cucsAaaUserRoleEntry 7 }

cucsAaaUserRoleConfigStatusMessage OBJECT-TYPE
    SYNTAX       SnmpAdminString
    MAX-ACCESS   read-only
    STATUS       current
    DESCRIPTION
        "Cisco UCS aaa:UserRole:configStatusMessage managed
        object property"
    ::= { cucsAaaUserRoleEntry 8 }

cucsAaaWebLoginTable OBJECT-TYPE
    SYNTAX           SEQUENCE OF CucsAaaWebLoginEntry
    MAX-ACCESS       not-accessible
    STATUS           current
    DESCRIPTION
        "Cisco UCS aaa:WebLogin managed object table"
    ::= { cucsAaaObjects 37 }

cucsAaaWebLoginEntry OBJECT-TYPE
    SYNTAX           CucsAaaWebLoginEntry
    MAX-ACCESS       not-accessible
    STATUS           current
    DESCRIPTION
        "Entry for the cucsAaaWebLoginTable table."
    INDEX { cucsAaaWebLoginInstanceId }
    ::= { cucsAaaWebLoginTable 1 }

CucsAaaWebLoginEntry ::= SEQUENCE {
    cucsAaaWebLoginInstanceId                                        CucsManagedObjectId,
    cucsAaaWebLoginDn                                                CucsManagedObjectDn,
    cucsAaaWebLoginRn                                                SnmpAdminString,
    cucsAaaWebLoginDescr                                             SnmpAdminString,
    cucsAaaWebLoginId                                                SnmpAdminString,
    cucsAaaWebLoginIntId                                             SnmpAdminString,
    cucsAaaWebLoginLocalHost                                         SnmpAdminString,
    cucsAaaWebLoginName                                              SnmpAdminString,
    cucsAaaWebLoginRemoteHost                                        SnmpAdminString,
    cucsAaaWebLoginSession                                           CucsAaaSession,
    cucsAaaWebLoginSwitchId                                          CucsNetworkSwitchId,
    cucsAaaWebLoginPolicyLevel                                       Gauge32,
    cucsAaaWebLoginPolicyOwner                                       CucsPolicyPolicyOwner
}

cucsAaaWebLoginInstanceId OBJECT-TYPE
    SYNTAX       CucsManagedObjectId
    MAX-ACCESS   not-accessible
    STATUS       current
    DESCRIPTION
        "Instance identifier of the managed object."
    ::= { cucsAaaWebLoginEntry 1 }

cucsAaaWebLoginDn OBJECT-TYPE
    SYNTAX       CucsManagedObjectDn
    MAX-ACCESS   read-only
    STATUS       current
    DESCRIPTION
        "Cisco UCS aaa:WebLogin:dn managed object property"
    ::= { cucsAaaWebLoginEntry 2 }

cucsAaaWebLoginRn OBJECT-TYPE
    SYNTAX       SnmpAdminString
    MAX-ACCESS   read-only
    STATUS       current
    DESCRIPTION
        "Cisco UCS aaa:WebLogin:rn managed object property"
    ::= { cucsAaaWebLoginEntry 3 }

cucsAaaWebLoginDescr OBJECT-TYPE
    SYNTAX       SnmpAdminString
    MAX-ACCESS   read-only
    STATUS       current
    DESCRIPTION
        "Cisco UCS aaa:WebLogin:descr managed object property"
    ::= { cucsAaaWebLoginEntry 4 }

cucsAaaWebLoginId OBJECT-TYPE
    SYNTAX       SnmpAdminString
    MAX-ACCESS   read-only
    STATUS       current
    DESCRIPTION
        "Cisco UCS aaa:WebLogin:id managed object property"
    ::= { cucsAaaWebLoginEntry 5 }

cucsAaaWebLoginIntId OBJECT-TYPE
    SYNTAX       SnmpAdminString
    MAX-ACCESS   read-only
    STATUS       current
    DESCRIPTION
        "Cisco UCS aaa:WebLogin:intId managed object property"
    ::= { cucsAaaWebLoginEntry 6 }

cucsAaaWebLoginLocalHost OBJECT-TYPE
    SYNTAX       SnmpAdminString
    MAX-ACCESS   read-only
    STATUS       current
    DESCRIPTION
        "Cisco UCS aaa:WebLogin:localHost managed object property"
    ::= { cucsAaaWebLoginEntry 7 }

cucsAaaWebLoginName OBJECT-TYPE
    SYNTAX       SnmpAdminString
    MAX-ACCESS   read-only
    STATUS       current
    DESCRIPTION
        "Cisco UCS aaa:WebLogin:name managed object property"
    ::= { cucsAaaWebLoginEntry 8 }

cucsAaaWebLoginRemoteHost OBJECT-TYPE
    SYNTAX       SnmpAdminString
    MAX-ACCESS   read-only
    STATUS       current
    DESCRIPTION
        "Cisco UCS aaa:WebLogin:remoteHost managed object property"
    ::= { cucsAaaWebLoginEntry 9 }

cucsAaaWebLoginSession OBJECT-TYPE
    SYNTAX       CucsAaaSession
    MAX-ACCESS   read-only
    STATUS       current
    DESCRIPTION
        "Cisco UCS aaa:WebLogin:session managed object property"
    ::= { cucsAaaWebLoginEntry 10 }

cucsAaaWebLoginSwitchId OBJECT-TYPE
    SYNTAX       CucsNetworkSwitchId
    MAX-ACCESS   read-only
    STATUS       current
    DESCRIPTION
        "Cisco UCS aaa:WebLogin:switchId managed object property"
    ::= { cucsAaaWebLoginEntry 11 }

cucsAaaWebLoginPolicyLevel OBJECT-TYPE
    SYNTAX       Gauge32
    MAX-ACCESS   read-only
    STATUS       current
    DESCRIPTION
        "Cisco UCS aaa:WebLogin:policyLevel managed object property"
    ::= { cucsAaaWebLoginEntry 12 }

cucsAaaWebLoginPolicyOwner OBJECT-TYPE
    SYNTAX       CucsPolicyPolicyOwner
    MAX-ACCESS   read-only
    STATUS       current
    DESCRIPTION
        "Cisco UCS aaa:WebLogin:policyOwner managed object property"
    ::= { cucsAaaWebLoginEntry 13 }

END
