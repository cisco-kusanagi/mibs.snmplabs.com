--			Ascend mibdadslnet MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBDADSLNET-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibdadslNetworkProfile  OBJECT IDENTIFIER ::= { configuration 7}

	-- The mibdadslNetworkProfile table
	--
	-- This table contains parameters for the mibdadslNetworkProfile profile
	--

    mibdadslNetworkProfileTable	OBJECT-TYPE
	SYNTAX		SEQUENCE OF MibdadslNetworkProfileEntry
	ACCESS		not-accessible
	STATUS		mandatory
	DESCRIPTION	"A list of mibdadslNetworkProfile profile entries."
	::= { mibdadslNetworkProfile 1 }

    mibdadslNetworkProfileEntry	OBJECT-TYPE
	SYNTAX		MibdadslNetworkProfileEntry
	ACCESS		not-accessible
	STATUS		mandatory
	DESCRIPTION	"A mibdadslNetworkProfile entry containing objects that
			 maps to the parameters of mibdadslNetworkProfile profile."
	INDEX		{ dadslNetworkProfile-Shelf-o, dadslNetworkProfile-Slot-o, dadslNetworkProfile-Item-o }
	::= { mibdadslNetworkProfileTable 1 }

    MibdadslNetworkProfileEntry ::=
	SEQUENCE {
	    dadslNetworkProfile-Shelf-o
		INTEGER,
	    dadslNetworkProfile-Slot-o
		INTEGER,
	    dadslNetworkProfile-Item-o
		INTEGER,
	    dadslNetworkProfile-Name
		DisplayString,
	    dadslNetworkProfile-PhysicalAddress-Shelf
		INTEGER,
	    dadslNetworkProfile-PhysicalAddress-Slot
		INTEGER,
	    dadslNetworkProfile-PhysicalAddress-ItemNumber
		INTEGER,
	    dadslNetworkProfile-Enabled
		INTEGER,
	    dadslNetworkProfile-ProfileNumber
		INTEGER,
	    dadslNetworkProfile-LineConfig-TrunkGroup
		INTEGER,
	    dadslNetworkProfile-LineConfig-NailedGroup
		INTEGER,
	    dadslNetworkProfile-LineConfig-RoutePort-SlotNumber-SlotNumber
		INTEGER,
	    dadslNetworkProfile-LineConfig-RoutePort-SlotNumber-ShelfNumber
		INTEGER,
	    dadslNetworkProfile-LineConfig-RoutePort-RelativePortNumber-RelativePortNumber
		INTEGER,
	    dadslNetworkProfile-LineConfig-Activation
		INTEGER,
	    dadslNetworkProfile-LineConfig-DataRateMode
		INTEGER,
	    dadslNetworkProfile-LineConfig-MaxUpStreamRate
		INTEGER,
	    dadslNetworkProfile-LineConfig-MaxDownStreamRate
		INTEGER,
	    dadslNetworkProfile-LineConfig-UpStreamMargin
		INTEGER,
	    dadslNetworkProfile-LineConfig-DownStreamMargin
		INTEGER,
	    dadslNetworkProfile-LineConfig-UpStreamInterleave
		INTEGER,
	    dadslNetworkProfile-LineConfig-DownStreamInterleave
		INTEGER,
	    dadslNetworkProfile-LineConfig-TxPowerLevel
		INTEGER,
	    dadslNetworkProfile-LineConfig-TxPowerAutoState
		INTEGER,
	    dadslNetworkProfile-LineConfig-MaintainLanUp
		INTEGER,
	    dadslNetworkProfile-Action-o
		INTEGER
	}

    dadslNetworkProfile-Shelf-o	OBJECT-TYPE
	SYNTAX	INTEGER
	ACCESS	read-only
	STATUS	mandatory
	DESCRIPTION	""
	::= { mibdadslNetworkProfileEntry 1 }

    dadslNetworkProfile-Slot-o	OBJECT-TYPE
	SYNTAX	INTEGER
	ACCESS	read-only
	STATUS	mandatory
	DESCRIPTION	""
	::= { mibdadslNetworkProfileEntry 2 }

    dadslNetworkProfile-Item-o	OBJECT-TYPE
	SYNTAX	INTEGER
	ACCESS	read-only
	STATUS	mandatory
	DESCRIPTION	""
	::= { mibdadslNetworkProfileEntry 3 }

    dadslNetworkProfile-Name	OBJECT-TYPE
	SYNTAX	DisplayString
	ACCESS	read-write
	STATUS	mandatory
	DESCRIPTION	"For future use. The current design does not use the name field but instead references Dmt adsl lines by the physical address; we may in the future support referencing Dmt adsl lines by name as well as by address. The name consists of a null terminated ascii string supplied by the user; it defaults to the ascii form of the Dmt adsl line physical address."
	::= { mibdadslNetworkProfileEntry 4 }

    dadslNetworkProfile-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibdadslNetworkProfileEntry 5 }

    dadslNetworkProfile-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibdadslNetworkProfileEntry 6 }

    dadslNetworkProfile-PhysicalAddress-ItemNumber	OBJECT-TYPE
	SYNTAX	INTEGER
	ACCESS	read-write
	STATUS	mandatory
	DESCRIPTION	"A number that specifies an addressable entity within the context of shelf and slot."
	::= { mibdadslNetworkProfileEntry 7 }

    dadslNetworkProfile-Enabled	OBJECT-TYPE
	SYNTAX	INTEGER {
		    no (1),
		    yes (2)
		}
	ACCESS	read-write
	STATUS	mandatory
	DESCRIPTION	"TRUE if the line is enabled, otherwise FALSE."
	::= { mibdadslNetworkProfileEntry 8 }

    dadslNetworkProfile-ProfileNumber	OBJECT-TYPE
	SYNTAX	INTEGER
	ACCESS	read-write
	STATUS	mandatory
	DESCRIPTION	"For potential backwards compatibility. The current design consists of one line profile numbered 0."
	::= { mibdadslNetworkProfileEntry 9 }

    dadslNetworkProfile-LineConfig-TrunkGroup	OBJECT-TYPE
	SYNTAX	INTEGER
	ACCESS	read-write
	STATUS	mandatory
	DESCRIPTION	"The trunk group to which this line is assigned. 0 means this line is not part of a trunk group."
	::= { mibdadslNetworkProfileEntry 10 }

    dadslNetworkProfile-LineConfig-NailedGroup	OBJECT-TYPE
	SYNTAX	INTEGER
	ACCESS	read-write
	STATUS	mandatory
	DESCRIPTION	"A number that identifies the set of lines that makes up a nailed group. 0 means this line is not part of a nailed group."
	::= { mibdadslNetworkProfileEntry 11 }

    dadslNetworkProfile-LineConfig-RoutePort-SlotNumber-SlotNumber	OBJECT-TYPE
	SYNTAX	INTEGER
	ACCESS	read-write
	STATUS	mandatory
	DESCRIPTION	""
	::= { mibdadslNetworkProfileEntry 12 }

    dadslNetworkProfile-LineConfig-RoutePort-SlotNumber-ShelfNumber	OBJECT-TYPE
	SYNTAX	INTEGER
	ACCESS	read-write
	STATUS	mandatory
	DESCRIPTION	"TNT is a multi shelf system. To minimise the changes required to existing code the shelf number is added to this structure as it will almost always be needed when a slot number is needed."
	::= { mibdadslNetworkProfileEntry 13 }

    dadslNetworkProfile-LineConfig-RoutePort-RelativePortNumber-RelativePortNumber	OBJECT-TYPE
	SYNTAX	INTEGER
	ACCESS	read-write
	STATUS	mandatory
	DESCRIPTION	""
	::= { mibdadslNetworkProfileEntry 14 }

    dadslNetworkProfile-LineConfig-Activation	OBJECT-TYPE
	SYNTAX	INTEGER {
		    static (1),
		    dsrActive (2),
		    dcdDsrActive (3)
		}
	ACCESS	read-write
	STATUS	mandatory
	DESCRIPTION	"Line activation mode."
	::= { mibdadslNetworkProfileEntry 15 }

    dadslNetworkProfile-LineConfig-DataRateMode	OBJECT-TYPE
	SYNTAX	INTEGER {
		    autobaud (2),
		    singlebaud (3)
		}
	ACCESS	read-write
	STATUS	mandatory
	DESCRIPTION	"The data rate mode define the mode for modem training."
	::= { mibdadslNetworkProfileEntry 19 }

    dadslNetworkProfile-LineConfig-MaxUpStreamRate	OBJECT-TYPE
	SYNTAX	INTEGER {
		    upstrmMegMax (151),
		    n-1088000 (152),
		    n-928000 (153),
		    n-896000 (154),
		    n-800000 (155),
		    n-768000 (156),
		    n-640000 (157),
		    n-512000 (158),
		    n-384000 (159),
		    n-256000 (160),
		    n-128000 (161)
		}
	ACCESS	read-write
	STATUS	mandatory
	DESCRIPTION	"The up stream max rate defines the maximum rate from the cpe to the coe."
	::= { mibdadslNetworkProfileEntry 20 }

    dadslNetworkProfile-LineConfig-MaxDownStreamRate	OBJECT-TYPE
	SYNTAX	INTEGER {
		    dwnstrmMegMax (101),
		    n-9504000 (102),
		    n-8960000 (103),
		    n-8000000 (104),
		    n-7168000 (105),
		    n-6272000 (106),
		    n-5120000 (107),
		    n-4480000 (108),
		    n-3200000 (109),
		    n-2688000 (110),
		    n-2560000 (111),
		    n-2240000 (112),
		    n-1920000 (113),
		    n-1600000 (114),
		    n-1280000 (115),
		    n-960000 (116),
		    n-768000 (117),
		    n-640000 (118),
		    n-512000 (119),
		    n-384000 (120),
		    n-256000 (121),
		    n-128000 (122)
		}
	ACCESS	read-write
	STATUS	mandatory
	DESCRIPTION	"The down stream max rate defines the maximum rate from the coe to the cpe."
	::= { mibdadslNetworkProfileEntry 21 }

    dadslNetworkProfile-LineConfig-UpStreamMargin	OBJECT-TYPE
	SYNTAX	INTEGER
	ACCESS	read-write
	STATUS	mandatory
	DESCRIPTION	"The up stream margin requirement in dB."
	::= { mibdadslNetworkProfileEntry 22 }

    dadslNetworkProfile-LineConfig-DownStreamMargin	OBJECT-TYPE
	SYNTAX	INTEGER
	ACCESS	read-write
	STATUS	mandatory
	DESCRIPTION	"The down stream margin requirement in dB."
	::= { mibdadslNetworkProfileEntry 23 }

    dadslNetworkProfile-LineConfig-UpStreamInterleave	OBJECT-TYPE
	SYNTAX	INTEGER {
		    dmt0 (1),
		    dmt2 (3),
		    dmt4 (5),
		    dmt8 (9),
		    dmt16 (17),
		    dmt32 (33),
		    dmt64 (65)
		}
	ACCESS	read-write
	STATUS	mandatory
	DESCRIPTION	"The up stream interleaver depth in bytes."
	::= { mibdadslNetworkProfileEntry 24 }

    dadslNetworkProfile-LineConfig-DownStreamInterleave	OBJECT-TYPE
	SYNTAX	INTEGER {
		    dmt0 (1),
		    dmt2 (3),
		    dmt4 (5),
		    dmt8 (9),
		    dmt16 (17),
		    dmt32 (33),
		    dmt64 (65)
		}
	ACCESS	read-write
	STATUS	mandatory
	DESCRIPTION	"The down stream interleaver depth in bytes."
	::= { mibdadslNetworkProfileEntry 25 }

    dadslNetworkProfile-LineConfig-TxPowerLevel	OBJECT-TYPE
	SYNTAX	INTEGER
	ACCESS	read-write
	STATUS	mandatory
	DESCRIPTION	"The downstream transmitter power level in percents."
	::= { mibdadslNetworkProfileEntry 26 }

    dadslNetworkProfile-LineConfig-TxPowerAutoState	OBJECT-TYPE
	SYNTAX	INTEGER {
		    disabled (1),
		    adjusting (2),
		    tracking (3),
		    locked (4)
		}
	ACCESS	read-write
	STATUS	mandatory
	DESCRIPTION	"The downstream transmitter auto power level managment state. Only settable to ADJUSTING or DISABLED!"
	::= { mibdadslNetworkProfileEntry 27 }

    dadslNetworkProfile-LineConfig-MaintainLanUp	OBJECT-TYPE
	SYNTAX	INTEGER {
		    no (1),
		    yes (2)
		}
	ACCESS	read-write
	STATUS	mandatory
	DESCRIPTION	"If TRUE the LAN Session will not be brought down while the DMT modem retrains, unless there is no remote detected for over 20 sec or failed to retrain in 2 minutes. Cannot be disabled while modem is in the process of retraining. If using frame relay with LMI this parameter will be automatically forced to NO."
	::= { mibdadslNetworkProfileEntry 28 }

    dadslNetworkProfile-Action-o	OBJECT-TYPE
	SYNTAX	INTEGER {
		    noAction (1),
		    createProfile (2),
		    deleteProfile (3)
		}
	ACCESS	read-write
	STATUS	mandatory
	DESCRIPTION	""
	::= { mibdadslNetworkProfileEntry 29 }

END
