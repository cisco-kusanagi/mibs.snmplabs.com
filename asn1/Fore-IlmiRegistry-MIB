-- 
-- Copyright 1999 by Fore Systems, Inc. 
-- Converted to SMIv2 rfc 2578,2579,2580 - STD 58
--

Fore-IlmiRegistry-MIB DEFINITIONS ::= BEGIN


IMPORTS
        OBJECT-TYPE,
        MODULE-IDENTITY                 FROM SNMPv2-SMI
	RowStatus                       FROM SNMPv2-TC
	ilmiRegistry,
	AtmAddress			FROM Fore-Common-MIB;

ilmiRegistryModule MODULE-IDENTITY
          LAST-UPDATED         "9911050000Z"
          ORGANIZATION         "FORE"
          CONTACT-INFO         
               "      Postal:   FORE Systems Inc.
                                 1000 FORE Drive
                                 Warrendale, PA 15086-7502
                       Tel:      +1 724 742 6900
                       Email:    nm_mibs@fore.com
                       Web:      http://www.fore.com"
          DESCRIPTION "Fore ILMI Registry Module."
        ::= { ilmiRegistry 2 }

--              Object Identifier definitions
-- The following values are defined for use as possible values
-- of the atmfSrvcRegServiceID object.

-- LAN Emulation Configuration Server (LECS)
-- atmfSrvcRegLecs ::= { atmfSrvcRegTypes 1 }
-- When atmfSrvcRegServiceID has a value of atmfSrvcRegLecs,
-- the value of atmfSrvcRegParm1 is ignored.

-- ATM Name Server (ANS)
-- atmfSrvcRegAns         OBJECT IDENTIFIER ::= { atmfSrvcRegTypes 2 }
-- When atmfSrvcRegServiceID has a value of atmfSrvcRegAns,
-- the value of atmfSrvcRegParm1 is ignored.


--          The Service Registry Table
--
-- The Service Registry Table is implemented by the network-side IME

adminIlmiRegTable OBJECT-TYPE
        SYNTAX  SEQUENCE OF AdminIlmiRegEntry
        MAX-ACCESS  not-accessible
        STATUS  current
        DESCRIPTION
                "The table implemented by the IME on the network side of
                the ATM UNI port contains all of the services that are
                available to the user-side IME indexed by service
                identifier."
        ::= { ilmiRegistry 1 }

adminIlmiRegEntry OBJECT-TYPE
        SYNTAX  AdminIlmiRegEntry
        MAX-ACCESS  not-accessible
        STATUS  current
        DESCRIPTION
                "Information about a single service provider that is 
                available to the user-side IME."
        INDEX   { adminIlmiRegPort, adminIlmiRegServiceID, 
                  adminIlmiRegAddressIndex }
        ::= { adminIlmiRegTable 1 }

AdminIlmiRegEntry ::=
        SEQUENCE {
                adminIlmiRegPort
                        INTEGER,
                adminIlmiRegServiceID
                        OBJECT IDENTIFIER,
                adminIlmiRegATMAddress
                        AtmAddress,
                adminIlmiRegAddressIndex
                        INTEGER,
                adminIlmiRegParm1
                        OCTET STRING,
		adminIlmiRegRowStatus
			RowStatus
        }

adminIlmiRegPort OBJECT-TYPE
        SYNTAX  INTEGER (0..2147483647)
        MAX-ACCESS  not-accessible
        STATUS  current
        DESCRIPTION
                "The value of 0 which has the special meaning of
                identifying the ATM Interface over which this message
                was received."
       ::= { adminIlmiRegEntry 1 }

adminIlmiRegServiceID OBJECT-TYPE
        SYNTAX  OBJECT IDENTIFIER
        MAX-ACCESS  not-accessible
        STATUS  current
        DESCRIPTION
                "This is the service identifier which uniquely identifies
                the type of service at the address provided in the table."
        ::= { adminIlmiRegEntry 2 }

adminIlmiRegATMAddress OBJECT-TYPE
        SYNTAX  AtmAddress
        MAX-ACCESS  read-create
        STATUS  current
        DESCRIPTION
                "This is the full address of the service.  The user-side
                IME may use this address to establish a connection
                with the service."
        ::= { adminIlmiRegEntry 3 }

adminIlmiRegAddressIndex OBJECT-TYPE
        SYNTAX INTEGER (1..2147483647)
        MAX-ACCESS  not-accessible
        STATUS  current
        DESCRIPTION
                "An arbitrary integer to differentiate multiple rows
                containing different ATM addresses for the same service
                on the same port."
        ::= { adminIlmiRegEntry 4 }

adminIlmiRegParm1 OBJECT-TYPE
        SYNTAX  OCTET STRING (SIZE (1..255))
        MAX-ACCESS  read-only
        STATUS  current
        DESCRIPTION
                "An octet string whose size and meaning is determined
                by the value of adminIlmiRegServiceID."
        ::= { adminIlmiRegEntry 5 }

adminIlmiRegRowStatus OBJECT-TYPE
	SYNTAX RowStatus
	MAX-ACCESS read-create
	STATUS current
	DESCRIPTION 
	" " 
	::= {adminIlmiRegEntry 6 }
END
