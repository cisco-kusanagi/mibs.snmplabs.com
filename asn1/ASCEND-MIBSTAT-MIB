--			Ascend mibstat MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBSTAT-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibsdslLineStatus  OBJECT IDENTIFIER ::= { configuration 180}
    mibatmIfStatus  OBJECT IDENTIFIER ::= { configuration 185}
    mibds3AtmLineStatus  OBJECT IDENTIFIER ::= { configuration 182}
    mibbRINetworkInterfaceState  OBJECT IDENTIFIER ::= { configuration 28}
    mibdmtAlDslLineStatus  OBJECT IDENTIFIER ::= { configuration 181}
    mibe3AtmLineStatus  OBJECT IDENTIFIER ::= { configuration 184}
    miboc3AtmLineStatus  OBJECT IDENTIFIER ::= { configuration 183}

	-- The mibsdslLineStatus table
	--
	-- This table contains parameters for the mibsdslLineStatus profile
	--

    mibsdslLineStatusTable	OBJECT-TYPE
	SYNTAX		SEQUENCE OF MibsdslLineStatusEntry
	ACCESS		not-accessible
	STATUS		mandatory
	DESCRIPTION	"A list of mibsdslLineStatus profile entries."
	::= { mibsdslLineStatus 1 }

    mibsdslLineStatusEntry	OBJECT-TYPE
	SYNTAX		MibsdslLineStatusEntry
	ACCESS		not-accessible
	STATUS		mandatory
	DESCRIPTION	"A mibsdslLineStatus entry containing objects that
			 maps to the parameters of mibsdslLineStatus profile."
	INDEX		{ sdslLineStatus-Shelf-o, sdslLineStatus-Slot-o, sdslLineStatus-Item-o }
	::= { mibsdslLineStatusTable 1 }

    MibsdslLineStatusEntry ::=
	SEQUENCE {
	    sdslLineStatus-Shelf-o
		INTEGER,
	    sdslLineStatus-Slot-o
		INTEGER,
	    sdslLineStatus-Item-o
		INTEGER,
	    sdslLineStatus-PhysicalAddress-Shelf
		INTEGER,
	    sdslLineStatus-PhysicalAddress-Slot
		INTEGER,
	    sdslLineStatus-PhysicalAddress-ItemNumber
		INTEGER,
	    sdslLineStatus-LineState
		INTEGER,
	    sdslLineStatus-SparePhysicalAddress-Shelf
		INTEGER,
	    sdslLineStatus-SparePhysicalAddress-Slot
		INTEGER,
	    sdslLineStatus-SparePhysicalAddress-ItemNumber
		INTEGER,
	    sdslLineStatus-SparingState
		INTEGER,
	    sdslLineStatus-SparingChangeReason
		INTEGER,
	    sdslLineStatus-SparingChangeTime
		INTEGER,
	    sdslLineStatus-SparingChangeCounter
		INTEGER,
	    sdslLineStatus-VpiVciRange
		INTEGER,
	    sdslLineStatus-VpSwitchingVpi
		INTEGER,
	    sdslLineStatus-ErrorCount
		INTEGER,
	    sdslLineStatus-PhysicalStatus-IfGroupIndex
		INTEGER,
	    sdslLineStatus-PhysicalStatus-UnitType
		INTEGER,
	    sdslLineStatus-PhysicalStatus-DevLineState
		INTEGER,
	    sdslLineStatus-PhysicalStatus-UpStreamRate
		INTEGER,
	    sdslLineStatus-PhysicalStatus-DownStreamRate
		INTEGER,
	    sdslLineStatus-PhysicalStatus-MajorFirmwareVer
		INTEGER,
	    sdslLineStatus-PhysicalStatus-MinorFirmwareVer
		INTEGER,
	    sdslLineStatus-PhysicalStatus-HardwareVer
		INTEGER,
	    sdslLineStatus-PhysicalStatistic-LineUpTimer-Days
		INTEGER,
	    sdslLineStatus-PhysicalStatistic-LineUpTimer-Hours
		INTEGER,
	    sdslLineStatus-PhysicalStatistic-LineUpTimer-Minutes
		INTEGER,
	    sdslLineStatus-PhysicalStatistic-RxSignalPresent
		INTEGER,
	    sdslLineStatus-PhysicalStatistic-LineQuality
		INTEGER,
	    sdslLineStatus-PhysicalStatistic-UpDwnCntr
		INTEGER,
	    sdslLineStatus-PhysicalStatistic-SelfTest
		INTEGER,
	    sdslLineStatus-PhysicalStatistic-FarEndDbAttenuation
		INTEGER,
	    sdslLineStatus-PhysicalStatistic-FirmwareStartupStage
		INTEGER,
	    sdslLineStatus-PhysicalStatistic-HdlcRxCrcErrorCnt
		INTEGER,
	    sdslLineStatus-Action-o
		INTEGER
	}

    sdslLineStatus-Shelf-o	OBJECT-TYPE
	SYNTAX	INTEGER
	ACCESS	read-only
	STATUS	mandatory
	DESCRIPTION	""
	::= { mibsdslLineStatusEntry 1 }

    sdslLineStatus-Slot-o	OBJECT-TYPE
	SYNTAX	INTEGER
	ACCESS	read-only
	STATUS	mandatory
	DESCRIPTION	""
	::= { mibsdslLineStatusEntry 2 }

    sdslLineStatus-Item-o	OBJECT-TYPE
	SYNTAX	INTEGER
	ACCESS	read-only
	STATUS	mandatory
	DESCRIPTION	""
	::= { mibsdslLineStatusEntry 3 }

    sdslLineStatus-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibsdslLineStatusEntry 4 }

    sdslLineStatus-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibsdslLineStatusEntry 5 }

    sdslLineStatus-PhysicalAddress-ItemNumber	OBJECT-TYPE
	SYNTAX	INTEGER
	ACCESS	read-write
	STATUS	mandatory
	DESCRIPTION	"A number that specifies an addressable entity within the context of shelf and slot."
	::= { mibsdslLineStatusEntry 6 }

    sdslLineStatus-LineState	OBJECT-TYPE
	SYNTAX	INTEGER {
		    doesNotExist (1),
		    disabled (2),
		    active (3)
		}
	ACCESS	read-write
	STATUS	mandatory
	DESCRIPTION	"The overall state of the line."
	::= { mibsdslLineStatusEntry 7 }

    sdslLineStatus-SparePhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibsdslLineStatusEntry 8 }

    sdslLineStatus-SparePhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibsdslLineStatusEntry 9 }

    sdslLineStatus-SparePhysicalAddress-ItemNumber	OBJECT-TYPE
	SYNTAX	INTEGER
	ACCESS	read-write
	STATUS	mandatory
	DESCRIPTION	"A number that specifies an addressable entity within the context of shelf and slot."
	::= { mibsdslLineStatusEntry 10 }

    sdslLineStatus-SparingState	OBJECT-TYPE
	SYNTAX	INTEGER {
		    sparingNone (1),
		    primaryActive (2),
		    primaryInactive (3),
		    secondaryActive (4),
		    secondaryInactive (5)
		}
	ACCESS	read-only
	STATUS	mandatory
	DESCRIPTION	"The sparing state of the line."
	::= { mibsdslLineStatusEntry 11 }

    sdslLineStatus-SparingChangeReason	OBJECT-TYPE
	SYNTAX	INTEGER {
		    unknown (1),
		    manual (2),
		    automatic (3),
		    test (4)
		}
	ACCESS	read-only
	STATUS	mandatory
	DESCRIPTION	"The reason for the last sparing state change."
	::= { mibsdslLineStatusEntry 12 }

    sdslLineStatus-SparingChangeTime	OBJECT-TYPE
	SYNTAX	INTEGER
	ACCESS	read-only
	STATUS	mandatory
	DESCRIPTION	"The time of the last sparing state change."
	::= { mibsdslLineStatusEntry 13 }

    sdslLineStatus-SparingChangeCounter	OBJECT-TYPE
	SYNTAX	INTEGER
	ACCESS	read-only
	STATUS	mandatory
	DESCRIPTION	"The number of sparing state changes."
	::= { mibsdslLineStatusEntry 14 }

    sdslLineStatus-VpiVciRange	OBJECT-TYPE
	SYNTAX	INTEGER {
		    vpi01Vci321023 (6),
		    vpi03Vci32511 (1),
		    vpi07Vci32255 (2),
		    vpi015Vci32127 (3),
		    vpi031Vci3263 (4),
		    notApplicable (5)
		}
	ACCESS	read-only
	STATUS	mandatory
	DESCRIPTION	"The valid range of vpi and vci for the circuits established for the line. This range can change only after LIM reboot."
	::= { mibsdslLineStatusEntry 15 }

    sdslLineStatus-VpSwitchingVpi	OBJECT-TYPE
	SYNTAX	INTEGER
	ACCESS	read-only
	STATUS	mandatory
	DESCRIPTION	"VPI to be used for the VP switching. Rest of the VPIs will be used for the VC switching."
	::= { mibsdslLineStatusEntry 16 }

    sdslLineStatus-ErrorCount	OBJECT-TYPE
	SYNTAX	INTEGER
	ACCESS	read-write
	STATUS	mandatory
	DESCRIPTION	"The number of errors experienced by the line."
	::= { mibsdslLineStatusEntry 17 }

    sdslLineStatus-PhysicalStatus-IfGroupIndex	OBJECT-TYPE
	SYNTAX	INTEGER
	ACCESS	read-only
	STATUS	mandatory
	DESCRIPTION	"Interface groups index assigned to this physical port."
	::= { mibsdslLineStatusEntry 18 }

    sdslLineStatus-PhysicalStatus-UnitType	OBJECT-TYPE
	SYNTAX	INTEGER {
		    coe (1),
		    cpe (2)
		}
	ACCESS	read-only
	STATUS	mandatory
	DESCRIPTION	"Unit types defines if the node is operating Central Office or Customer Premise equipment software."
	::= { mibsdslLineStatusEntry 19 }

    sdslLineStatus-PhysicalStatus-DevLineState	OBJECT-TYPE
	SYNTAX	INTEGER {
		    config (1),
		    deactivate (2),
		    inactive (3),
		    activating (4),
		    activeRx (5),
		    portUp (6),
		    portupPendingDeactivate (7),
		    deactivateLost (8),
		    hardwareTest (9),
		    outOfService (10),
		    tipRingDetect (11),
		    foreverBert (12),
		    tipWait1 (13),
		    tipHunt (14),
		    tipWait2 (15),
		    alteraTipHunt (19),
		    cellDelination (16),
		    deactivateWait (17),
		    preact (20),
		    preactWait (21)
		}
	ACCESS	read-only
	STATUS	mandatory
	DESCRIPTION	"Displays the current interface state. config -- interface being configured. deactivate -- interface is imposing deactivation. deactivate-lost -- interface is waiting for the LOS Timer to expire. inactive -- interface is starting up. activating -- interface is waiting for remote to start up. active-rx -- interface is waiting for remote side to start 4 level transmission. port-up -- interface is connected to remote node and data can be transfered. portup-pending-deactive -- interface experienced an LOS or noise margin error."
	::= { mibsdslLineStatusEntry 20 }

    sdslLineStatus-PhysicalStatus-UpStreamRate	OBJECT-TYPE
	SYNTAX	INTEGER
	ACCESS	read-only
	STATUS	mandatory
	DESCRIPTION	"Current upstream interface rate."
	::= { mibsdslLineStatusEntry 21 }

    sdslLineStatus-PhysicalStatus-DownStreamRate	OBJECT-TYPE
	SYNTAX	INTEGER
	ACCESS	read-only
	STATUS	mandatory
	DESCRIPTION	"Current down stream interface rate."
	::= { mibsdslLineStatusEntry 22 }

    sdslLineStatus-PhysicalStatus-MajorFirmwareVer	OBJECT-TYPE
	SYNTAX	INTEGER
	ACCESS	read-only
	STATUS	mandatory
	DESCRIPTION	"Firmware major version ID."
	::= { mibsdslLineStatusEntry 23 }

    sdslLineStatus-PhysicalStatus-MinorFirmwareVer	OBJECT-TYPE
	SYNTAX	INTEGER
	ACCESS	read-only
	STATUS	mandatory
	DESCRIPTION	"Firmwares minor version ID."
	::= { mibsdslLineStatusEntry 24 }

    sdslLineStatus-PhysicalStatus-HardwareVer	OBJECT-TYPE
	SYNTAX	INTEGER
	ACCESS	read-only
	STATUS	mandatory
	DESCRIPTION	"Hardware chip version."
	::= { mibsdslLineStatusEntry 25 }

    sdslLineStatus-PhysicalStatistic-LineUpTimer-Days	OBJECT-TYPE
	SYNTAX	INTEGER
	ACCESS	read-only
	STATUS	mandatory
	DESCRIPTION	"Number of days that the DSL line has been up."
	::= { mibsdslLineStatusEntry 26 }

    sdslLineStatus-PhysicalStatistic-LineUpTimer-Hours	OBJECT-TYPE
	SYNTAX	INTEGER
	ACCESS	read-only
	STATUS	mandatory
	DESCRIPTION	"Number of hours that the DSL line has been up."
	::= { mibsdslLineStatusEntry 27 }

    sdslLineStatus-PhysicalStatistic-LineUpTimer-Minutes	OBJECT-TYPE
	SYNTAX	INTEGER
	ACCESS	read-only
	STATUS	mandatory
	DESCRIPTION	"Number of minutes that the DSL line has been up."
	::= { mibsdslLineStatusEntry 28 }

    sdslLineStatus-PhysicalStatistic-RxSignalPresent	OBJECT-TYPE
	SYNTAX	INTEGER {
		    yes (3),
		    no (2)
		}
	ACCESS	read-only
	STATUS	mandatory
	DESCRIPTION	"State if the receive signal is present or not."
	::= { mibsdslLineStatusEntry 29 }

    sdslLineStatus-PhysicalStatistic-LineQuality	OBJECT-TYPE
	SYNTAX	INTEGER
	ACCESS	read-only
	STATUS	mandatory
	DESCRIPTION	"While the port is in the up state, this parameter displays the line quality."
	::= { mibsdslLineStatusEntry 30 }

    sdslLineStatus-PhysicalStatistic-UpDwnCntr	OBJECT-TYPE
	SYNTAX	INTEGER
	ACCESS	read-only
	STATUS	mandatory
	DESCRIPTION	"Interface Up Down counter value displays the number of times the interface trasitions from a down to up state."
	::= { mibsdslLineStatusEntry 31 }

    sdslLineStatus-PhysicalStatistic-SelfTest	OBJECT-TYPE
	SYNTAX	INTEGER {
		    passed (1),
		    selfTestFailed (2),
		    localLoopBackFailed (3)
		}
	ACCESS	read-only
	STATUS	mandatory
	DESCRIPTION	"Hardware/firmware self test results."
	::= { mibsdslLineStatusEntry 32 }

    sdslLineStatus-PhysicalStatistic-FarEndDbAttenuation	OBJECT-TYPE
	SYNTAX	INTEGER
	ACCESS	read-only
	STATUS	mandatory
	DESCRIPTION	"Receive signal attenuation."
	::= { mibsdslLineStatusEntry 33 }

    sdslLineStatus-PhysicalStatistic-FirmwareStartupStage	OBJECT-TYPE
	SYNTAX	INTEGER {
		    idle (1),
		    activateSystem (2),
		    dcCancellation (3),
		    initStartup (4),
		    adaptEcStage1 (5),
		    adaptEcStage2 (6),
		    adaptEcStage3 (7),
		    adaptEcAfterAagc1 (8),
		    adaptEcAfterAagc2 (9),
		    adaptEcAfterAagc3 (10),
		    adaptEcAfterAagc4 (11),
		    adaptEc1 (12),
		    adaptEc2 (13),
		    adaptEc3 (14),
		    waitForSignal (15),
		    adaptAagc1 (16),
		    adaptAagc2 (17),
		    adaptAagc3 (18),
		    waitForRemotePhaseLock (19),
		    remotePhaseLock (20),
		    startOpenEye (21),
		    openEye1 (22),
		    openEye2 (23),
		    openEye3 (24),
		    openEye4 (25),
		    openEye5 (26),
		    openEye6 (27),
		    openEye7 (28),
		    openEyeAtOptimalPhase1 (29),
		    openEyeAtOptimalPhase2 (30),
		    openEyeAtOptimalPhase3 (31),
		    openEyeAtOptimalPhase4 (32),
		    openEyeAtOptimalPhase5 (33),
		    openEyeAtOptimalPhase6 (34),
		    openEyeAtOptimalPhase7 (35),
		    openEyeAtOptimalPhase8 (36),
		    openEyeAtOptimalPhase9 (37),
		    openEyeAtOptimalPhase10 (38),
		    openEyeAtOptimalPhase11 (39),
		    openEyeAtOptimalPhase12 (40),
		    openEyeAtOptimalPhase13 (41),
		    phaseAdaptEc1 (42),
		    phaseAdaptEc2 (43),
		    phaseAdaptEc3 (44),
		    phaseAdaptEc4 (45),
		    acquireFreq1 (46),
		    acquireFreq2 (47),
		    acquireFreq3 (48),
		    acquireFreq4 (49),
		    acquireFreq5 (50),
		    phaseLocked (51),
		    optimalPhase (52),
		    tx2Level (53),
		    adaptDagcAfterAagc (54),
		    adaptEq1 (55),
		    adaptEq2 (56),
		    adaptEq3 (57),
		    waitFor1Min (58),
		    transmit4Level (59),
		    waitFor4Level (60),
		    adaptModules1 (61),
		    adaptModules2 (62),
		    setNormalConditions (63),
		    normalOperation (64),
		    deactivateMode (65)
		}
	ACCESS	read-only
	STATUS	mandatory
	DESCRIPTION	"Current firmware state."
	::= { mibsdslLineStatusEntry 34 }

    sdslLineStatus-PhysicalStatistic-HdlcRxCrcErrorCnt	OBJECT-TYPE
	SYNTAX	INTEGER
	ACCESS	read-only
	STATUS	mandatory
	DESCRIPTION	"While the port is in the up state, this parameter displays the number of HDLC CRC errors associated with this channel. If there are too many errors, then this channel lost communications with the remote node and is restarted."
	::= { mibsdslLineStatusEntry 35 }

    sdslLineStatus-Action-o	OBJECT-TYPE
	SYNTAX	INTEGER {
		    noAction (1),
		    createProfile (2),
		    deleteProfile (3)
		}
	ACCESS	read-write
	STATUS	mandatory
	DESCRIPTION	""
	::= { mibsdslLineStatusEntry 36 }


	-- The mibatmIfStatus table
	--
	-- This table contains parameters for the mibatmIfStatus profile
	--

    mibatmIfStatusTable	OBJECT-TYPE
	SYNTAX		SEQUENCE OF MibatmIfStatusEntry
	ACCESS		not-accessible
	STATUS		mandatory
	DESCRIPTION	"A list of mibatmIfStatus profile entries."
	::= { mibatmIfStatus 1 }

    mibatmIfStatusEntry	OBJECT-TYPE
	SYNTAX		MibatmIfStatusEntry
	ACCESS		not-accessible
	STATUS		mandatory
	DESCRIPTION	"A mibatmIfStatus entry containing objects that
			 maps to the parameters of mibatmIfStatus profile."
	INDEX		{ atmIfStatus-Shelf-o, atmIfStatus-Slot-o, atmIfStatus-Item-o, atmIfStatus-LogicalItem-o }
	::= { mibatmIfStatusTable 1 }

    MibatmIfStatusEntry ::=
	SEQUENCE {
	    atmIfStatus-Shelf-o
		INTEGER,
	    atmIfStatus-Slot-o
		INTEGER,
	    atmIfStatus-Item-o
		INTEGER,
	    atmIfStatus-LogicalItem-o
		INTEGER,
	    atmIfStatus-Address-PhysicalAddress-Shelf
		INTEGER,
	    atmIfStatus-Address-PhysicalAddress-Slot
		INTEGER,
	    atmIfStatus-Address-PhysicalAddress-ItemNumber
		INTEGER,
	    atmIfStatus-Address-LogicalItem
		INTEGER,
	    atmIfStatus-IfNumber
		INTEGER,
	    atmIfStatus-NailedGroup
		INTEGER,
	    atmIfStatus-PortState
		INTEGER,
	    atmIfStatus-SignallingState
		INTEGER,
	    atmIfStatus-PnniLinkState
		INTEGER,
	    atmIfStatus-Action-o
		INTEGER
	}

    atmIfStatus-Shelf-o	OBJECT-TYPE
	SYNTAX	INTEGER
	ACCESS	read-only
	STATUS	mandatory
	DESCRIPTION	""
	::= { mibatmIfStatusEntry 1 }

    atmIfStatus-Slot-o	OBJECT-TYPE
	SYNTAX	INTEGER
	ACCESS	read-only
	STATUS	mandatory
	DESCRIPTION	""
	::= { mibatmIfStatusEntry 2 }

    atmIfStatus-Item-o	OBJECT-TYPE
	SYNTAX	INTEGER
	ACCESS	read-only
	STATUS	mandatory
	DESCRIPTION	""
	::= { mibatmIfStatusEntry 3 }

    atmIfStatus-LogicalItem-o	OBJECT-TYPE
	SYNTAX	INTEGER
	ACCESS	read-only
	STATUS	mandatory
	DESCRIPTION	""
	::= { mibatmIfStatusEntry 4 }

    atmIfStatus-Address-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibatmIfStatusEntry 5 }

    atmIfStatus-Address-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibatmIfStatusEntry 6 }

    atmIfStatus-Address-PhysicalAddress-ItemNumber	OBJECT-TYPE
	SYNTAX	INTEGER
	ACCESS	read-write
	STATUS	mandatory
	DESCRIPTION	"A number that specifies an addressable entity within the context of shelf and slot."
	::= { mibatmIfStatusEntry 7 }

    atmIfStatus-Address-LogicalItem	OBJECT-TYPE
	SYNTAX	INTEGER
	ACCESS	read-write
	STATUS	mandatory
	DESCRIPTION	"A number that specifies an addressable logical entity within the context of a physical address."
	::= { mibatmIfStatusEntry 8 }

    atmIfStatus-IfNumber	OBJECT-TYPE
	SYNTAX	INTEGER
	ACCESS	read-only
	STATUS	mandatory
	DESCRIPTION	"The ATM Interface Number"
	::= { mibatmIfStatusEntry 9 }

    atmIfStatus-NailedGroup	OBJECT-TYPE
	SYNTAX	INTEGER
	ACCESS	read-only
	STATUS	mandatory
	DESCRIPTION	"The nailed group number for the physical interface."
	::= { mibatmIfStatusEntry 10 }

    atmIfStatus-PortState	OBJECT-TYPE
	SYNTAX	INTEGER {
		    notConfigured (1),
		    up (2),
		    down (3)
		}
	ACCESS	read-only
	STATUS	mandatory
	DESCRIPTION	"The ATM port state."
	::= { mibatmIfStatusEntry 11 }

    atmIfStatus-SignallingState	OBJECT-TYPE
	SYNTAX	INTEGER {
		    notConfigured (1),
		    up (2),
		    down (3)
		}
	ACCESS	read-only
	STATUS	mandatory
	DESCRIPTION	"The signalling state of the port."
	::= { mibatmIfStatusEntry 12 }

    atmIfStatus-PnniLinkState	OBJECT-TYPE
	SYNTAX	INTEGER {
		    notConfigured (1),
		    up (2),
		    down (3)
		}
	ACCESS	read-only
	STATUS	mandatory
	DESCRIPTION	"The PNNI link state of the port."
	::= { mibatmIfStatusEntry 13 }

    atmIfStatus-Action-o	OBJECT-TYPE
	SYNTAX	INTEGER {
		    noAction (1),
		    createProfile (2),
		    deleteProfile (3)
		}
	ACCESS	read-write
	STATUS	mandatory
	DESCRIPTION	""
	::= { mibatmIfStatusEntry 14 }


	-- The mibds3AtmLineStatus table
	--
	-- This table contains parameters for the mibds3AtmLineStatus profile
	--

    mibds3AtmLineStatusTable	OBJECT-TYPE
	SYNTAX		SEQUENCE OF Mibds3AtmLineStatusEntry
	ACCESS		not-accessible
	STATUS		mandatory
	DESCRIPTION	"A list of mibds3AtmLineStatus profile entries."
	::= { mibds3AtmLineStatus 1 }

    mibds3AtmLineStatusEntry	OBJECT-TYPE
	SYNTAX		Mibds3AtmLineStatusEntry
	ACCESS		not-accessible
	STATUS		mandatory
	DESCRIPTION	"A mibds3AtmLineStatus entry containing objects that
			 maps to the parameters of mibds3AtmLineStatus profile."
	INDEX		{ ds3AtmLineStatus-Shelf-o, ds3AtmLineStatus-Slot-o, ds3AtmLineStatus-Item-o }
	::= { mibds3AtmLineStatusTable 1 }

    Mibds3AtmLineStatusEntry ::=
	SEQUENCE {
	    ds3AtmLineStatus-Shelf-o
		INTEGER,
	    ds3AtmLineStatus-Slot-o
		INTEGER,
	    ds3AtmLineStatus-Item-o
		INTEGER,
	    ds3AtmLineStatus-PhysicalAddress-Shelf
		INTEGER,
	    ds3AtmLineStatus-PhysicalAddress-Slot
		INTEGER,
	    ds3AtmLineStatus-PhysicalAddress-ItemNumber
		INTEGER,
	    ds3AtmLineStatus-LineState
		INTEGER,
	    ds3AtmLineStatus-SparePhysicalAddress-Shelf
		INTEGER,
	    ds3AtmLineStatus-SparePhysicalAddress-Slot
		INTEGER,
	    ds3AtmLineStatus-SparePhysicalAddress-ItemNumber
		INTEGER,
	    ds3AtmLineStatus-SparingState
		INTEGER,
	    ds3AtmLineStatus-SparingChangeReason
		INTEGER,
	    ds3AtmLineStatus-SparingChangeTime
		INTEGER,
	    ds3AtmLineStatus-SparingChangeCounter
		INTEGER,
	    ds3AtmLineStatus-VpiVciRange
		INTEGER,
	    ds3AtmLineStatus-VcSwitchingVpi
		DisplayString,
	    ds3AtmLineStatus-FBitErrorCount
		INTEGER,
	    ds3AtmLineStatus-PBitErrorCount
		INTEGER,
	    ds3AtmLineStatus-CpBitErrorCount
		INTEGER,
	    ds3AtmLineStatus-FebErrorCount
		INTEGER,
	    ds3AtmLineStatus-BpvErrorCount
		INTEGER,
	    ds3AtmLineStatus-LossOfSignal
		INTEGER,
	    ds3AtmLineStatus-LossOfFrame
		INTEGER,
	    ds3AtmLineStatus-YellowReceive
		INTEGER,
	    ds3AtmLineStatus-AisReceive
		INTEGER,
	    ds3AtmLineStatus-Action-o
		INTEGER
	}

    ds3AtmLineStatus-Shelf-o	OBJECT-TYPE
	SYNTAX	INTEGER
	ACCESS	read-only
	STATUS	mandatory
	DESCRIPTION	""
	::= { mibds3AtmLineStatusEntry 1 }

    ds3AtmLineStatus-Slot-o	OBJECT-TYPE
	SYNTAX	INTEGER
	ACCESS	read-only
	STATUS	mandatory
	DESCRIPTION	""
	::= { mibds3AtmLineStatusEntry 2 }

    ds3AtmLineStatus-Item-o	OBJECT-TYPE
	SYNTAX	INTEGER
	ACCESS	read-only
	STATUS	mandatory
	DESCRIPTION	""
	::= { mibds3AtmLineStatusEntry 3 }

    ds3AtmLineStatus-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibds3AtmLineStatusEntry 4 }

    ds3AtmLineStatus-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibds3AtmLineStatusEntry 5 }

    ds3AtmLineStatus-PhysicalAddress-ItemNumber	OBJECT-TYPE
	SYNTAX	INTEGER
	ACCESS	read-write
	STATUS	mandatory
	DESCRIPTION	"A number that specifies an addressable entity within the context of shelf and slot."
	::= { mibds3AtmLineStatusEntry 6 }

    ds3AtmLineStatus-LineState	OBJECT-TYPE
	SYNTAX	INTEGER {
		    doesNotExist (1),
		    disabled (2),
		    lossOfSignal (3),
		    lossOfFrame (4),
		    yellowReceive (5),
		    aisReceive (6),
		    active (7)
		}
	ACCESS	read-only
	STATUS	mandatory
	DESCRIPTION	"The overall state of the line."
	::= { mibds3AtmLineStatusEntry 7 }

    ds3AtmLineStatus-SparePhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibds3AtmLineStatusEntry 8 }

    ds3AtmLineStatus-SparePhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibds3AtmLineStatusEntry 9 }

    ds3AtmLineStatus-SparePhysicalAddress-ItemNumber	OBJECT-TYPE
	SYNTAX	INTEGER
	ACCESS	read-write
	STATUS	mandatory
	DESCRIPTION	"A number that specifies an addressable entity within the context of shelf and slot."
	::= { mibds3AtmLineStatusEntry 10 }

    ds3AtmLineStatus-SparingState	OBJECT-TYPE
	SYNTAX	INTEGER {
		    sparingNone (1),
		    primaryActive (2),
		    primaryInactive (3),
		    secondaryActive (4),
		    secondaryInactive (5)
		}
	ACCESS	read-only
	STATUS	mandatory
	DESCRIPTION	"The sparing state of the line."
	::= { mibds3AtmLineStatusEntry 11 }

    ds3AtmLineStatus-SparingChangeReason	OBJECT-TYPE
	SYNTAX	INTEGER {
		    unknown (1),
		    manual (2),
		    automatic (3),
		    test (4)
		}
	ACCESS	read-only
	STATUS	mandatory
	DESCRIPTION	"The reason for the last sparing state change."
	::= { mibds3AtmLineStatusEntry 12 }

    ds3AtmLineStatus-SparingChangeTime	OBJECT-TYPE
	SYNTAX	INTEGER
	ACCESS	read-only
	STATUS	mandatory
	DESCRIPTION	"The time of the last sparing state change."
	::= { mibds3AtmLineStatusEntry 13 }

    ds3AtmLineStatus-SparingChangeCounter	OBJECT-TYPE
	SYNTAX	INTEGER
	ACCESS	read-only
	STATUS	mandatory
	DESCRIPTION	"The number of sparing state changes."
	::= { mibds3AtmLineStatusEntry 14 }

    ds3AtmLineStatus-VpiVciRange	OBJECT-TYPE
	SYNTAX	INTEGER {
		    n-01-3232767 (1),
		    n-03-3216383 (2),
		    n-07-328191 (3),
		    n-015-324095 (4),
		    n-031-322047 (5),
		    n-063-321023 (6),
		    n-0127-32511 (7),
		    n-0255-32255 (8),
		    vpi0255Vci32255 (9),
		    vpi0255Vci32511 (10),
		    vpi0255Vci321023 (11),
		    vpi0255Vci322047 (12),
		    vpi0255Vci324095 (13),
		    vpi0255Vci328191 (14),
		    vpi0255Vci3216383 (15)
		}
	ACCESS	read-only
	STATUS	mandatory
	DESCRIPTION	"Current valid range of VPI/VCI. This range can change only after system reboot. The valid range of VCI is same for all VC switching VPIs. VP switching VPIs don't have restriction over VCI range."
	::= { mibds3AtmLineStatusEntry 15 }

    ds3AtmLineStatus-VcSwitchingVpi	OBJECT-TYPE
	SYNTAX	DisplayString
	ACCESS	read-only
	STATUS	mandatory
	DESCRIPTION	"A list of VPIs used for the VC switching (VCC). Rest of the VPIs are used for VP switching."
	::= { mibds3AtmLineStatusEntry 16 }

    ds3AtmLineStatus-FBitErrorCount	OBJECT-TYPE
	SYNTAX	INTEGER
	ACCESS	read-only
	STATUS	mandatory
	DESCRIPTION	"The number of F-bit or M-bit errors experienced by the line."
	::= { mibds3AtmLineStatusEntry 17 }

    ds3AtmLineStatus-PBitErrorCount	OBJECT-TYPE
	SYNTAX	INTEGER
	ACCESS	read-only
	STATUS	mandatory
	DESCRIPTION	"The number of P-bit errors experienced by the line."
	::= { mibds3AtmLineStatusEntry 18 }

    ds3AtmLineStatus-CpBitErrorCount	OBJECT-TYPE
	SYNTAX	INTEGER
	ACCESS	read-only
	STATUS	mandatory
	DESCRIPTION	"The number of C-bit parity errors experienced by the line."
	::= { mibds3AtmLineStatusEntry 19 }

    ds3AtmLineStatus-FebErrorCount	OBJECT-TYPE
	SYNTAX	INTEGER
	ACCESS	read-only
	STATUS	mandatory
	DESCRIPTION	"The number of far-end block errors experienced by the line."
	::= { mibds3AtmLineStatusEntry 20 }

    ds3AtmLineStatus-BpvErrorCount	OBJECT-TYPE
	SYNTAX	INTEGER
	ACCESS	read-only
	STATUS	mandatory
	DESCRIPTION	"The number of bipolar violation errors experienced by the line."
	::= { mibds3AtmLineStatusEntry 21 }

    ds3AtmLineStatus-LossOfSignal	OBJECT-TYPE
	SYNTAX	INTEGER {
		    false (1),
		    true (2)
		}
	ACCESS	read-only
	STATUS	mandatory
	DESCRIPTION	"Indicates a loss of signal on the line."
	::= { mibds3AtmLineStatusEntry 22 }

    ds3AtmLineStatus-LossOfFrame	OBJECT-TYPE
	SYNTAX	INTEGER {
		    false (1),
		    true (2)
		}
	ACCESS	read-only
	STATUS	mandatory
	DESCRIPTION	"Indicates a loss of frame on the line (a.k.a. Red Alarm)."
	::= { mibds3AtmLineStatusEntry 23 }

    ds3AtmLineStatus-YellowReceive	OBJECT-TYPE
	SYNTAX	INTEGER {
		    false (1),
		    true (2)
		}
	ACCESS	read-only
	STATUS	mandatory
	DESCRIPTION	"Indicates receiving far end loss of frame (a.k.a. Yellow Alarm)."
	::= { mibds3AtmLineStatusEntry 24 }

    ds3AtmLineStatus-AisReceive	OBJECT-TYPE
	SYNTAX	INTEGER {
		    false (1),
		    true (2)
		}
	ACCESS	read-only
	STATUS	mandatory
	DESCRIPTION	"Indicates far end is sending Alarm Indication Signal."
	::= { mibds3AtmLineStatusEntry 25 }

    ds3AtmLineStatus-Action-o	OBJECT-TYPE
	SYNTAX	INTEGER {
		    noAction (1),
		    createProfile (2),
		    deleteProfile (3)
		}
	ACCESS	read-write
	STATUS	mandatory
	DESCRIPTION	""
	::= { mibds3AtmLineStatusEntry 26 }


	-- The mibbRINetworkInterfaceState table
	--
	-- This table contains parameters for the mibbRINetworkInterfaceState profile
	--

    mibbRINetworkInterfaceStateTable	OBJECT-TYPE
	SYNTAX		SEQUENCE OF MibbRINetworkInterfaceStateEntry
	ACCESS		not-accessible
	STATUS		mandatory
	DESCRIPTION	"A list of mibbRINetworkInterfaceState profile entries."
	::= { mibbRINetworkInterfaceState 1 }

    mibbRINetworkInterfaceStateEntry	OBJECT-TYPE
	SYNTAX		MibbRINetworkInterfaceStateEntry
	ACCESS		not-accessible
	STATUS		mandatory
	DESCRIPTION	"A mibbRINetworkInterfaceState entry containing objects that
			 maps to the parameters of mibbRINetworkInterfaceState profile."
	INDEX		{ bRINetworkInterfaceState-Shelf-o, bRINetworkInterfaceState-Slot-o, bRINetworkInterfaceState-Item-o }
	::= { mibbRINetworkInterfaceStateTable 1 }

    MibbRINetworkInterfaceStateEntry ::=
	SEQUENCE {
	    bRINetworkInterfaceState-Shelf-o
		INTEGER,
	    bRINetworkInterfaceState-Slot-o
		INTEGER,
	    bRINetworkInterfaceState-Item-o
		INTEGER,
	    bRINetworkInterfaceState-PhysicalAddress-Shelf
		INTEGER,
	    bRINetworkInterfaceState-PhysicalAddress-Slot
		INTEGER,
	    bRINetworkInterfaceState-PhysicalAddress-ItemNumber
		INTEGER,
	    bRINetworkInterfaceState-LineState
		INTEGER,
	    bRINetworkInterfaceState-SparePhysicalAddress-Shelf
		INTEGER,
	    bRINetworkInterfaceState-SparePhysicalAddress-Slot
		INTEGER,
	    bRINetworkInterfaceState-SparePhysicalAddress-ItemNumber
		INTEGER,
	    bRINetworkInterfaceState-SparingState
		INTEGER,
	    bRINetworkInterfaceState-SparingChangeReason
		INTEGER,
	    bRINetworkInterfaceState-SparingChangeTime
		INTEGER,
	    bRINetworkInterfaceState-SparingChangeCounter
		INTEGER,
	    bRINetworkInterfaceState-PhysicalStatus-IfGroupIndex
		INTEGER,
	    bRINetworkInterfaceState-PhysicalStatistic-LineUpTimer-Days
		INTEGER,
	    bRINetworkInterfaceState-PhysicalStatistic-LineUpTimer-Hours
		INTEGER,
	    bRINetworkInterfaceState-PhysicalStatistic-LineUpTimer-Minutes
		INTEGER,
	    bRINetworkInterfaceState-PhysicalStatistic-UpDwnCntr
		INTEGER,
	    bRINetworkInterfaceState-Action-o
		INTEGER
	}

    bRINetworkInterfaceState-Shelf-o	OBJECT-TYPE
	SYNTAX	INTEGER
	ACCESS	read-only
	STATUS	mandatory
	DESCRIPTION	""
	::= { mibbRINetworkInterfaceStateEntry 1 }

    bRINetworkInterfaceState-Slot-o	OBJECT-TYPE
	SYNTAX	INTEGER
	ACCESS	read-only
	STATUS	mandatory
	DESCRIPTION	""
	::= { mibbRINetworkInterfaceStateEntry 2 }

    bRINetworkInterfaceState-Item-o	OBJECT-TYPE
	SYNTAX	INTEGER
	ACCESS	read-only
	STATUS	mandatory
	DESCRIPTION	""
	::= { mibbRINetworkInterfaceStateEntry 3 }

    bRINetworkInterfaceState-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibbRINetworkInterfaceStateEntry 4 }

    bRINetworkInterfaceState-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibbRINetworkInterfaceStateEntry 5 }

    bRINetworkInterfaceState-PhysicalAddress-ItemNumber	OBJECT-TYPE
	SYNTAX	INTEGER
	ACCESS	read-write
	STATUS	mandatory
	DESCRIPTION	"A number that specifies an addressable entity within the context of shelf and slot."
	::= { mibbRINetworkInterfaceStateEntry 6 }

    bRINetworkInterfaceState-LineState	OBJECT-TYPE
	SYNTAX	INTEGER {
		    doesNotExist (1),
		    disabled (2),
		    noPhysical (3),
		    noLogical (4),
		    noMgmt (5),
		    pointToPoint (6),
		    multipoint1 (7),
		    multipoint2 (8)
		}
	ACCESS	read-write
	STATUS	mandatory
	DESCRIPTION	"The overall state of the line."
	::= { mibbRINetworkInterfaceStateEntry 7 }

    bRINetworkInterfaceState-SparePhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibbRINetworkInterfaceStateEntry 9 }

    bRINetworkInterfaceState-SparePhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibbRINetworkInterfaceStateEntry 10 }

    bRINetworkInterfaceState-SparePhysicalAddress-ItemNumber	OBJECT-TYPE
	SYNTAX	INTEGER
	ACCESS	read-write
	STATUS	mandatory
	DESCRIPTION	"A number that specifies an addressable entity within the context of shelf and slot."
	::= { mibbRINetworkInterfaceStateEntry 11 }

    bRINetworkInterfaceState-SparingState	OBJECT-TYPE
	SYNTAX	INTEGER {
		    sparingNone (1),
		    primaryActive (2),
		    primaryInactive (3),
		    secondaryActive (4),
		    secondaryInactive (5)
		}
	ACCESS	read-only
	STATUS	mandatory
	DESCRIPTION	"The sparing state of the line."
	::= { mibbRINetworkInterfaceStateEntry 12 }

    bRINetworkInterfaceState-SparingChangeReason	OBJECT-TYPE
	SYNTAX	INTEGER {
		    unknown (1),
		    manual (2),
		    automatic (3),
		    test (4)
		}
	ACCESS	read-only
	STATUS	mandatory
	DESCRIPTION	"The reason for the last sparing state change."
	::= { mibbRINetworkInterfaceStateEntry 13 }

    bRINetworkInterfaceState-SparingChangeTime	OBJECT-TYPE
	SYNTAX	INTEGER
	ACCESS	read-only
	STATUS	mandatory
	DESCRIPTION	"The time of the last sparing state change."
	::= { mibbRINetworkInterfaceStateEntry 14 }

    bRINetworkInterfaceState-SparingChangeCounter	OBJECT-TYPE
	SYNTAX	INTEGER
	ACCESS	read-only
	STATUS	mandatory
	DESCRIPTION	"The number of sparing state changes."
	::= { mibbRINetworkInterfaceStateEntry 15 }

    bRINetworkInterfaceState-PhysicalStatus-IfGroupIndex	OBJECT-TYPE
	SYNTAX	INTEGER
	ACCESS	read-only
	STATUS	mandatory
	DESCRIPTION	"Interface groups index assigned to this physical port."
	::= { mibbRINetworkInterfaceStateEntry 16 }

    bRINetworkInterfaceState-PhysicalStatistic-LineUpTimer-Days	OBJECT-TYPE
	SYNTAX	INTEGER
	ACCESS	read-only
	STATUS	mandatory
	DESCRIPTION	"Number of days that the DSL line has been up."
	::= { mibbRINetworkInterfaceStateEntry 17 }

    bRINetworkInterfaceState-PhysicalStatistic-LineUpTimer-Hours	OBJECT-TYPE
	SYNTAX	INTEGER
	ACCESS	read-only
	STATUS	mandatory
	DESCRIPTION	"Number of hours that the DSL line has been up."
	::= { mibbRINetworkInterfaceStateEntry 18 }

    bRINetworkInterfaceState-PhysicalStatistic-LineUpTimer-Minutes	OBJECT-TYPE
	SYNTAX	INTEGER
	ACCESS	read-only
	STATUS	mandatory
	DESCRIPTION	"Number of minutes that the DSL line has been up."
	::= { mibbRINetworkInterfaceStateEntry 19 }

    bRINetworkInterfaceState-PhysicalStatistic-UpDwnCntr	OBJECT-TYPE
	SYNTAX	INTEGER
	ACCESS	read-only
	STATUS	mandatory
	DESCRIPTION	"Interface Up Down counter value displays the number of times the interface trasitions from a down to up state."
	::= { mibbRINetworkInterfaceStateEntry 20 }

    bRINetworkInterfaceState-Action-o	OBJECT-TYPE
	SYNTAX	INTEGER {
		    noAction (1),
		    createProfile (2),
		    deleteProfile (3)
		}
	ACCESS	read-write
	STATUS	mandatory
	DESCRIPTION	""
	::= { mibbRINetworkInterfaceStateEntry 8 }


	-- The mibbRINetworkInterfaceState__physical_statistic__error_count table
	--
	-- This table contains parameters for the mibbRINetworkInterfaceState__physical_statistic__error_count profile
	--

    mibbRINetworkInterfaceState-PhysicalStatistic-ErrorCountTable	OBJECT-TYPE
	SYNTAX		SEQUENCE OF MibbRINetworkInterfaceState-PhysicalStatistic-ErrorCountEntry
	ACCESS		not-accessible
	STATUS		mandatory
	DESCRIPTION	"A list of mibbRINetworkInterfaceState__physical_statistic__error_count profile entries."
	::= { mibbRINetworkInterfaceState 4 }

    mibbRINetworkInterfaceState-PhysicalStatistic-ErrorCountEntry	OBJECT-TYPE
	SYNTAX		MibbRINetworkInterfaceState-PhysicalStatistic-ErrorCountEntry
	ACCESS		not-accessible
	STATUS		mandatory
	DESCRIPTION	"A mibbRINetworkInterfaceState__physical_statistic__error_count entry containing objects that
			 maps to the parameters of mibbRINetworkInterfaceState__physical_statistic__error_count profile."
	INDEX		{ bRINetworkInterfaceState-PhysicalStatistic-ErrorCount-Shelf-o, bRINetworkInterfaceState-PhysicalStatistic-ErrorCount-Slot-o, bRINetworkInterfaceState-PhysicalStatistic-ErrorCount-Item-o, bRINetworkInterfaceState-PhysicalStatistic-ErrorCount-Index-o }
	::= { mibbRINetworkInterfaceState-PhysicalStatistic-ErrorCountTable 1 }

    MibbRINetworkInterfaceState-PhysicalStatistic-ErrorCountEntry ::=
	SEQUENCE {
	    bRINetworkInterfaceState-PhysicalStatistic-ErrorCount-Shelf-o
		INTEGER,
	    bRINetworkInterfaceState-PhysicalStatistic-ErrorCount-Slot-o
		INTEGER,
	    bRINetworkInterfaceState-PhysicalStatistic-ErrorCount-Item-o
		INTEGER,
	    bRINetworkInterfaceState-PhysicalStatistic-ErrorCount-Index-o
		INTEGER,
	    bRINetworkInterfaceState-PhysicalStatistic-ErrorCount
		INTEGER
	}

    bRINetworkInterfaceState-PhysicalStatistic-ErrorCount-Shelf-o	OBJECT-TYPE
	SYNTAX	INTEGER
	ACCESS	read-only
	STATUS	mandatory
	DESCRIPTION	""
	::= { mibbRINetworkInterfaceState-PhysicalStatistic-ErrorCountEntry 1 }

    bRINetworkInterfaceState-PhysicalStatistic-ErrorCount-Slot-o	OBJECT-TYPE
	SYNTAX	INTEGER
	ACCESS	read-only
	STATUS	mandatory
	DESCRIPTION	""
	::= { mibbRINetworkInterfaceState-PhysicalStatistic-ErrorCountEntry 2 }

    bRINetworkInterfaceState-PhysicalStatistic-ErrorCount-Item-o	OBJECT-TYPE
	SYNTAX	INTEGER
	ACCESS	read-only
	STATUS	mandatory
	DESCRIPTION	""
	::= { mibbRINetworkInterfaceState-PhysicalStatistic-ErrorCountEntry 3 }

    bRINetworkInterfaceState-PhysicalStatistic-ErrorCount-Index-o	OBJECT-TYPE
	SYNTAX	INTEGER
	ACCESS	read-only
	STATUS	mandatory
	DESCRIPTION	""
	::= { mibbRINetworkInterfaceState-PhysicalStatistic-ErrorCountEntry 4 }

    bRINetworkInterfaceState-PhysicalStatistic-ErrorCount	OBJECT-TYPE
	SYNTAX	INTEGER
	ACCESS	read-write
	STATUS	mandatory
	DESCRIPTION	"The number of errors experienced by each channel."
	::= { mibbRINetworkInterfaceState-PhysicalStatistic-ErrorCountEntry 5 }


	-- The mibbRINetworkInterfaceState__error_count table
	--
	-- This table contains parameters for the mibbRINetworkInterfaceState__error_count profile
	--

    mibbRINetworkInterfaceState-ErrorCountTable	OBJECT-TYPE
	SYNTAX		SEQUENCE OF MibbRINetworkInterfaceState-ErrorCountEntry
	ACCESS		not-accessible
	STATUS		mandatory
	DESCRIPTION	"A list of mibbRINetworkInterfaceState__error_count profile entries."
	::= { mibbRINetworkInterfaceState 2 }

    mibbRINetworkInterfaceState-ErrorCountEntry	OBJECT-TYPE
	SYNTAX		MibbRINetworkInterfaceState-ErrorCountEntry
	ACCESS		not-accessible
	STATUS		mandatory
	DESCRIPTION	"A mibbRINetworkInterfaceState__error_count entry containing objects that
			 maps to the parameters of mibbRINetworkInterfaceState__error_count profile."
	INDEX		{ bRINetworkInterfaceState-ErrorCount-Shelf-o, bRINetworkInterfaceState-ErrorCount-Slot-o, bRINetworkInterfaceState-ErrorCount-Item-o, bRINetworkInterfaceState-ErrorCount-Index-o }
	::= { mibbRINetworkInterfaceState-ErrorCountTable 1 }

    MibbRINetworkInterfaceState-ErrorCountEntry ::=
	SEQUENCE {
	    bRINetworkInterfaceState-ErrorCount-Shelf-o
		INTEGER,
	    bRINetworkInterfaceState-ErrorCount-Slot-o
		INTEGER,
	    bRINetworkInterfaceState-ErrorCount-Item-o
		INTEGER,
	    bRINetworkInterfaceState-ErrorCount-Index-o
		INTEGER,
	    bRINetworkInterfaceState-ErrorCount
		INTEGER
	}

    bRINetworkInterfaceState-ErrorCount-Shelf-o	OBJECT-TYPE
	SYNTAX	INTEGER
	ACCESS	read-only
	STATUS	mandatory
	DESCRIPTION	""
	::= { mibbRINetworkInterfaceState-ErrorCountEntry 1 }

    bRINetworkInterfaceState-ErrorCount-Slot-o	OBJECT-TYPE
	SYNTAX	INTEGER
	ACCESS	read-only
	STATUS	mandatory
	DESCRIPTION	""
	::= { mibbRINetworkInterfaceState-ErrorCountEntry 2 }

    bRINetworkInterfaceState-ErrorCount-Item-o	OBJECT-TYPE
	SYNTAX	INTEGER
	ACCESS	read-only
	STATUS	mandatory
	DESCRIPTION	""
	::= { mibbRINetworkInterfaceState-ErrorCountEntry 3 }

    bRINetworkInterfaceState-ErrorCount-Index-o	OBJECT-TYPE
	SYNTAX	INTEGER
	ACCESS	read-only
	STATUS	mandatory
	DESCRIPTION	""
	::= { mibbRINetworkInterfaceState-ErrorCountEntry 4 }

    bRINetworkInterfaceState-ErrorCount	OBJECT-TYPE
	SYNTAX	INTEGER
	ACCESS	read-write
	STATUS	mandatory
	DESCRIPTION	"The number of errors experienced by each channel."
	::= { mibbRINetworkInterfaceState-ErrorCountEntry 5 }


	-- The mibbRINetworkInterfaceState__channel_state table
	--
	-- This table contains parameters for the mibbRINetworkInterfaceState__channel_state profile
	--

    mibbRINetworkInterfaceState-ChannelStateTable	OBJECT-TYPE
	SYNTAX		SEQUENCE OF MibbRINetworkInterfaceState-ChannelStateEntry
	ACCESS		not-accessible
	STATUS		mandatory
	DESCRIPTION	"A list of mibbRINetworkInterfaceState__channel_state profile entries."
	::= { mibbRINetworkInterfaceState 3 }

    mibbRINetworkInterfaceState-ChannelStateEntry	OBJECT-TYPE
	SYNTAX		MibbRINetworkInterfaceState-ChannelStateEntry
	ACCESS		not-accessible
	STATUS		mandatory
	DESCRIPTION	"A mibbRINetworkInterfaceState__channel_state entry containing objects that
			 maps to the parameters of mibbRINetworkInterfaceState__channel_state profile."
	INDEX		{ bRINetworkInterfaceState-ChannelState-Shelf-o, bRINetworkInterfaceState-ChannelState-Slot-o, bRINetworkInterfaceState-ChannelState-Item-o, bRINetworkInterfaceState-ChannelState-Index-o }
	::= { mibbRINetworkInterfaceState-ChannelStateTable 1 }

    MibbRINetworkInterfaceState-ChannelStateEntry ::=
	SEQUENCE {
	    bRINetworkInterfaceState-ChannelState-Shelf-o
		INTEGER,
	    bRINetworkInterfaceState-ChannelState-Slot-o
		INTEGER,
	    bRINetworkInterfaceState-ChannelState-Item-o
		INTEGER,
	    bRINetworkInterfaceState-ChannelState-Index-o
		INTEGER,
	    bRINetworkInterfaceState-ChannelState
		INTEGER
	}

    bRINetworkInterfaceState-ChannelState-Shelf-o	OBJECT-TYPE
	SYNTAX	INTEGER
	ACCESS	read-only
	STATUS	mandatory
	DESCRIPTION	""
	::= { mibbRINetworkInterfaceState-ChannelStateEntry 1 }

    bRINetworkInterfaceState-ChannelState-Slot-o	OBJECT-TYPE
	SYNTAX	INTEGER
	ACCESS	read-only
	STATUS	mandatory
	DESCRIPTION	""
	::= { mibbRINetworkInterfaceState-ChannelStateEntry 2 }

    bRINetworkInterfaceState-ChannelState-Item-o	OBJECT-TYPE
	SYNTAX	INTEGER
	ACCESS	read-only
	STATUS	mandatory
	DESCRIPTION	""
	::= { mibbRINetworkInterfaceState-ChannelStateEntry 3 }

    bRINetworkInterfaceState-ChannelState-Index-o	OBJECT-TYPE
	SYNTAX	INTEGER
	ACCESS	read-only
	STATUS	mandatory
	DESCRIPTION	""
	::= { mibbRINetworkInterfaceState-ChannelStateEntry 4 }

    bRINetworkInterfaceState-ChannelState	OBJECT-TYPE
	SYNTAX	INTEGER {
		    unavailable (1),
		    unused (2),
		    outOfService (3),
		    nailedUp (4),
		    held (5),
		    offHook (6),
		    idle (7),
		    clearPending (8),
		    dialing (9),
		    ringing (10),
		    connected (11),
		    signaling (12),
		    cutThrough (13),
		    currentD (14),
		    backupD (15),
		    maintainence (16),
		    spcUp (17),
		    disabled (18)
		}
	ACCESS	read-write
	STATUS	mandatory
	DESCRIPTION	"The state of each individual channel."
	::= { mibbRINetworkInterfaceState-ChannelStateEntry 5 }


	-- The mibdmtAlDslLineStatus table
	--
	-- This table contains parameters for the mibdmtAlDslLineStatus profile
	--

    mibdmtAlDslLineStatusTable	OBJECT-TYPE
	SYNTAX		SEQUENCE OF MibdmtAlDslLineStatusEntry
	ACCESS		not-accessible
	STATUS		mandatory
	DESCRIPTION	"A list of mibdmtAlDslLineStatus profile entries."
	::= { mibdmtAlDslLineStatus 1 }

    mibdmtAlDslLineStatusEntry	OBJECT-TYPE
	SYNTAX		MibdmtAlDslLineStatusEntry
	ACCESS		not-accessible
	STATUS		mandatory
	DESCRIPTION	"A mibdmtAlDslLineStatus entry containing objects that
			 maps to the parameters of mibdmtAlDslLineStatus profile."
	INDEX		{ dmtAlDslLineStatus-Shelf-o, dmtAlDslLineStatus-Slot-o, dmtAlDslLineStatus-Item-o }
	::= { mibdmtAlDslLineStatusTable 1 }

    MibdmtAlDslLineStatusEntry ::=
	SEQUENCE {
	    dmtAlDslLineStatus-Shelf-o
		INTEGER,
	    dmtAlDslLineStatus-Slot-o
		INTEGER,
	    dmtAlDslLineStatus-Item-o
		INTEGER,
	    dmtAlDslLineStatus-PhysicalAddress-Shelf
		INTEGER,
	    dmtAlDslLineStatus-PhysicalAddress-Slot
		INTEGER,
	    dmtAlDslLineStatus-PhysicalAddress-ItemNumber
		INTEGER,
	    dmtAlDslLineStatus-LineState
		INTEGER,
	    dmtAlDslLineStatus-SparePhysicalAddress-Shelf
		INTEGER,
	    dmtAlDslLineStatus-SparePhysicalAddress-Slot
		INTEGER,
	    dmtAlDslLineStatus-SparePhysicalAddress-ItemNumber
		INTEGER,
	    dmtAlDslLineStatus-SparingState
		INTEGER,
	    dmtAlDslLineStatus-SparingChangeReason
		INTEGER,
	    dmtAlDslLineStatus-SparingChangeTime
		INTEGER,
	    dmtAlDslLineStatus-SparingChangeCounter
		INTEGER,
	    dmtAlDslLineStatus-VpiVciRange
		INTEGER,
	    dmtAlDslLineStatus-VpSwitchingVpi
		INTEGER,
	    dmtAlDslLineStatus-PhysicalStatus-IfGroupIndex
		INTEGER,
	    dmtAlDslLineStatus-PhysicalStatus-UnitType
		INTEGER,
	    dmtAlDslLineStatus-PhysicalStatus-DevLineState
		INTEGER,
	    dmtAlDslLineStatus-PhysicalStatus-UpStreamRateFast
		INTEGER,
	    dmtAlDslLineStatus-PhysicalStatus-DownStreamRateFast
		INTEGER,
	    dmtAlDslLineStatus-PhysicalStatus-UpStreamRateInterleaved
		INTEGER,
	    dmtAlDslLineStatus-PhysicalStatus-DownStreamRateInterleaved
		INTEGER,
	    dmtAlDslLineStatus-PhysicalStatus-UpStreamLatency
		INTEGER,
	    dmtAlDslLineStatus-PhysicalStatus-DownStreamLatency
		INTEGER,
	    dmtAlDslLineStatus-PhysicalStatus-FirmwareVer
		DisplayString,
	    dmtAlDslLineStatus-PhysicalStatus-AnsiAdslVer
		INTEGER,
	    dmtAlDslLineStatus-PhysicalStatus-InitialAdslVer
		INTEGER,
	    dmtAlDslLineStatus-PhysicalStatus-HardwareVer
		INTEGER,
	    dmtAlDslLineStatus-PhysicalStatus-ModemHwState
		INTEGER,
	    dmtAlDslLineStatus-PhysicalStatus-AccumBitErr
		INTEGER,
	    dmtAlDslLineStatus-PhysicalStatus-NumSecValid
		INTEGER,
	    dmtAlDslLineStatus-PhysicalStatus-NumSecInvalid
		INTEGER,
	    dmtAlDslLineStatus-PhysicalStatus-OperationalMode
		INTEGER,
	    dmtAlDslLineStatus-PhysicalStatistic-LineUpTimer-Days
		INTEGER,
	    dmtAlDslLineStatus-PhysicalStatistic-LineUpTimer-Hours
		INTEGER,
	    dmtAlDslLineStatus-PhysicalStatistic-LineUpTimer-Minutes
		INTEGER,
	    dmtAlDslLineStatus-PhysicalStatistic-RxSignalPresent
		INTEGER,
	    dmtAlDslLineStatus-PhysicalStatistic-UpDwnCntr
		INTEGER,
	    dmtAlDslLineStatus-PhysicalStatistic-SelfTest
		INTEGER,
	    dmtAlDslLineStatus-PhysicalStatistic-NoiseMarginDown
		INTEGER,
	    dmtAlDslLineStatus-PhysicalStatistic-AttenuationDown
		INTEGER,
	    dmtAlDslLineStatus-PhysicalStatistic-OutputPowerDown
		INTEGER,
	    dmtAlDslLineStatus-PhysicalStatistic-NoiseMarginUp
		INTEGER,
	    dmtAlDslLineStatus-PhysicalStatistic-AttenuationUp
		INTEGER,
	    dmtAlDslLineStatus-PhysicalStatistic-OutputPowerUp
		INTEGER,
	    dmtAlDslLineStatus-PhysicalStatistic-NearEndFec
		INTEGER,
	    dmtAlDslLineStatus-PhysicalStatistic-NearEndCrc
		INTEGER,
	    dmtAlDslLineStatus-PhysicalStatistic-NearEndHec
		INTEGER,
	    dmtAlDslLineStatus-PhysicalStatistic-FarEndFec
		INTEGER,
	    dmtAlDslLineStatus-PhysicalStatistic-FarEndCrc
		INTEGER,
	    dmtAlDslLineStatus-PhysicalStatistic-FarEndHec
		INTEGER,
	    dmtAlDslLineStatus-PhysicalStatistic-ReceivedRsBlocks
		INTEGER,
	    dmtAlDslLineStatus-PhysicalStatistic-TransmittedRsBlocks
		INTEGER,
	    dmtAlDslLineStatus-PhysicalStatistic-IncomingCells
		INTEGER,
	    dmtAlDslLineStatus-PhysicalStatistic-OutgoingCells
		INTEGER,
	    dmtAlDslLineStatus-Action-o
		INTEGER
	}

    dmtAlDslLineStatus-Shelf-o	OBJECT-TYPE
	SYNTAX	INTEGER
	ACCESS	read-only
	STATUS	mandatory
	DESCRIPTION	""
	::= { mibdmtAlDslLineStatusEntry 1 }

    dmtAlDslLineStatus-Slot-o	OBJECT-TYPE
	SYNTAX	INTEGER
	ACCESS	read-only
	STATUS	mandatory
	DESCRIPTION	""
	::= { mibdmtAlDslLineStatusEntry 2 }

    dmtAlDslLineStatus-Item-o	OBJECT-TYPE
	SYNTAX	INTEGER
	ACCESS	read-only
	STATUS	mandatory
	DESCRIPTION	""
	::= { mibdmtAlDslLineStatusEntry 3 }

    dmtAlDslLineStatus-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibdmtAlDslLineStatusEntry 4 }

    dmtAlDslLineStatus-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibdmtAlDslLineStatusEntry 5 }

    dmtAlDslLineStatus-PhysicalAddress-ItemNumber	OBJECT-TYPE
	SYNTAX	INTEGER
	ACCESS	read-write
	STATUS	mandatory
	DESCRIPTION	"A number that specifies an addressable entity within the context of shelf and slot."
	::= { mibdmtAlDslLineStatusEntry 6 }

    dmtAlDslLineStatus-LineState	OBJECT-TYPE
	SYNTAX	INTEGER {
		    doesNotExist (1),
		    disabled (2),
		    active (3)
		}
	ACCESS	read-only
	STATUS	mandatory
	DESCRIPTION	"The overall state of the line."
	::= { mibdmtAlDslLineStatusEntry 7 }

    dmtAlDslLineStatus-SparePhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibdmtAlDslLineStatusEntry 8 }

    dmtAlDslLineStatus-SparePhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibdmtAlDslLineStatusEntry 9 }

    dmtAlDslLineStatus-SparePhysicalAddress-ItemNumber	OBJECT-TYPE
	SYNTAX	INTEGER
	ACCESS	read-write
	STATUS	mandatory
	DESCRIPTION	"A number that specifies an addressable entity within the context of shelf and slot."
	::= { mibdmtAlDslLineStatusEntry 10 }

    dmtAlDslLineStatus-SparingState	OBJECT-TYPE
	SYNTAX	INTEGER {
		    sparingNone (1),
		    primaryActive (2),
		    primaryInactive (3),
		    secondaryActive (4),
		    secondaryInactive (5)
		}
	ACCESS	read-only
	STATUS	mandatory
	DESCRIPTION	"The sparing state of the line."
	::= { mibdmtAlDslLineStatusEntry 11 }

    dmtAlDslLineStatus-SparingChangeReason	OBJECT-TYPE
	SYNTAX	INTEGER {
		    unknown (1),
		    manual (2),
		    automatic (3),
		    test (4)
		}
	ACCESS	read-only
	STATUS	mandatory
	DESCRIPTION	"The reason for the last sparing state change."
	::= { mibdmtAlDslLineStatusEntry 12 }

    dmtAlDslLineStatus-SparingChangeTime	OBJECT-TYPE
	SYNTAX	INTEGER
	ACCESS	read-only
	STATUS	mandatory
	DESCRIPTION	"The time of the last sparing state change."
	::= { mibdmtAlDslLineStatusEntry 13 }

    dmtAlDslLineStatus-SparingChangeCounter	OBJECT-TYPE
	SYNTAX	INTEGER
	ACCESS	read-only
	STATUS	mandatory
	DESCRIPTION	"The number of sparing state changes."
	::= { mibdmtAlDslLineStatusEntry 14 }

    dmtAlDslLineStatus-VpiVciRange	OBJECT-TYPE
	SYNTAX	INTEGER {
		    vpi01Vci321023 (6),
		    vpi03Vci32511 (1),
		    vpi07Vci32255 (2),
		    vpi015Vci32127 (3),
		    vpi031Vci3263 (4),
		    notApplicable (5)
		}
	ACCESS	read-only
	STATUS	mandatory
	DESCRIPTION	"The valid range of vpi and vci for the circuits established for the line. This range can change only after LIM reboot."
	::= { mibdmtAlDslLineStatusEntry 15 }

    dmtAlDslLineStatus-VpSwitchingVpi	OBJECT-TYPE
	SYNTAX	INTEGER
	ACCESS	read-only
	STATUS	mandatory
	DESCRIPTION	"VPI to be used for the VP switching. Rest of the VPIs will be used for the VC switching."
	::= { mibdmtAlDslLineStatusEntry 16 }

    dmtAlDslLineStatus-PhysicalStatus-IfGroupIndex	OBJECT-TYPE
	SYNTAX	INTEGER
	ACCESS	read-only
	STATUS	mandatory
	DESCRIPTION	"Interface groups index assigned to this physical port."
	::= { mibdmtAlDslLineStatusEntry 17 }

    dmtAlDslLineStatus-PhysicalStatus-UnitType	OBJECT-TYPE
	SYNTAX	INTEGER {
		    coe (1),
		    cpe (2)
		}
	ACCESS	read-only
	STATUS	mandatory
	DESCRIPTION	"Unit types defines if the node is operating Central Office or Customer Premise equipment software."
	::= { mibdmtAlDslLineStatusEntry 18 }

    dmtAlDslLineStatus-PhysicalStatus-DevLineState	OBJECT-TYPE
	SYNTAX	INTEGER {
		    down (1),
		    activation (9),
		    training (17),
		    portUp (33),
		    failed (256),
		    loopback (106),
		    test (122),
		    download (138),
		    fastRetrain (154),
		    dummy (86)
		}
	ACCESS	read-only
	STATUS	mandatory
	DESCRIPTION	"Display of current interface state."
	::= { mibdmtAlDslLineStatusEntry 19 }

    dmtAlDslLineStatus-PhysicalStatus-UpStreamRateFast	OBJECT-TYPE
	SYNTAX	INTEGER
	ACCESS	read-only
	STATUS	mandatory
	DESCRIPTION	"Operational fast up stream rate in Bps."
	::= { mibdmtAlDslLineStatusEntry 20 }

    dmtAlDslLineStatus-PhysicalStatus-DownStreamRateFast	OBJECT-TYPE
	SYNTAX	INTEGER
	ACCESS	read-only
	STATUS	mandatory
	DESCRIPTION	"Operational fast down stream rate in Bps."
	::= { mibdmtAlDslLineStatusEntry 21 }

    dmtAlDslLineStatus-PhysicalStatus-UpStreamRateInterleaved	OBJECT-TYPE
	SYNTAX	INTEGER
	ACCESS	read-only
	STATUS	mandatory
	DESCRIPTION	"Operational interleaved up stream rate in Bps."
	::= { mibdmtAlDslLineStatusEntry 22 }

    dmtAlDslLineStatus-PhysicalStatus-DownStreamRateInterleaved	OBJECT-TYPE
	SYNTAX	INTEGER
	ACCESS	read-only
	STATUS	mandatory
	DESCRIPTION	"Operational interleaved down stream rate in Bps."
	::= { mibdmtAlDslLineStatusEntry 23 }

    dmtAlDslLineStatus-PhysicalStatus-UpStreamLatency	OBJECT-TYPE
	SYNTAX	INTEGER {
		    none (1),
		    fast (2),
		    interleave (3),
		    both (4)
		}
	ACCESS	read-only
	STATUS	mandatory
	DESCRIPTION	"Operational up stream latency."
	::= { mibdmtAlDslLineStatusEntry 24 }

    dmtAlDslLineStatus-PhysicalStatus-DownStreamLatency	OBJECT-TYPE
	SYNTAX	INTEGER {
		    none (1),
		    fast (2),
		    interleave (3),
		    both (4)
		}
	ACCESS	read-only
	STATUS	mandatory
	DESCRIPTION	"Operational down stream latency."
	::= { mibdmtAlDslLineStatusEntry 25 }

    dmtAlDslLineStatus-PhysicalStatus-FirmwareVer	OBJECT-TYPE
	SYNTAX	DisplayString
	ACCESS	read-only
	STATUS	mandatory
	DESCRIPTION	"The showtime firmware version."
	::= { mibdmtAlDslLineStatusEntry 26 }

    dmtAlDslLineStatus-PhysicalStatus-AnsiAdslVer	OBJECT-TYPE
	SYNTAX	INTEGER
	ACCESS	read-only
	STATUS	mandatory
	DESCRIPTION	"Standard issue number, indicates the modem's standard compliance mode."
	::= { mibdmtAlDslLineStatusEntry 27 }

    dmtAlDslLineStatus-PhysicalStatus-InitialAdslVer	OBJECT-TYPE
	SYNTAX	INTEGER
	ACCESS	read-only
	STATUS	mandatory
	DESCRIPTION	"Initialzation version number. Implementation version"
	::= { mibdmtAlDslLineStatusEntry 28 }

    dmtAlDslLineStatus-PhysicalStatus-HardwareVer	OBJECT-TYPE
	SYNTAX	INTEGER
	ACCESS	read-only
	STATUS	mandatory
	DESCRIPTION	"Hardware platform version."
	::= { mibdmtAlDslLineStatusEntry 29 }

    dmtAlDslLineStatus-PhysicalStatus-ModemHwState	OBJECT-TYPE
	SYNTAX	INTEGER {
		    down (1),
		    initOk (129),
		    badSdram (130),
		    badCache (131),
		    badCacheSdram (132)
		}
	ACCESS	read-only
	STATUS	mandatory
	DESCRIPTION	"Display of modem components' state."
	::= { mibdmtAlDslLineStatusEntry 30 }

    dmtAlDslLineStatus-PhysicalStatus-AccumBitErr	OBJECT-TYPE
	SYNTAX	INTEGER
	ACCESS	read-only
	STATUS	mandatory
	DESCRIPTION	"Accumulated number of bit errors."
	::= { mibdmtAlDslLineStatusEntry 31 }

    dmtAlDslLineStatus-PhysicalStatus-NumSecValid	OBJECT-TYPE
	SYNTAX	INTEGER
	ACCESS	read-only
	STATUS	mandatory
	DESCRIPTION	"Number of valid seconds."
	::= { mibdmtAlDslLineStatusEntry 32 }

    dmtAlDslLineStatus-PhysicalStatus-NumSecInvalid	OBJECT-TYPE
	SYNTAX	INTEGER
	ACCESS	read-only
	STATUS	mandatory
	DESCRIPTION	"Number of invalid seconds."
	::= { mibdmtAlDslLineStatusEntry 33 }

    dmtAlDslLineStatus-PhysicalStatus-OperationalMode	OBJECT-TYPE
	SYNTAX	INTEGER {
		    ansiDmt (2),
		    gDmt (3),
		    gLite (9),
		    unknown (256),
		    ansiAlcatel141 (257),
		    ansiAdi (258),
		    ansiAlcatelPost141 (259),
		    uawg (260),
		    annexB (261),
		    annexCGliteFbm (262),
		    annexCGdmtFbm (263),
		    annexCGliteDbm (264),
		    annexCGdmtDbm (265),
		    annexBEtsi (266)
		}
	ACCESS	read-only
	STATUS	mandatory
	DESCRIPTION	"Modem's operational mode."
	::= { mibdmtAlDslLineStatusEntry 34 }

    dmtAlDslLineStatus-PhysicalStatistic-LineUpTimer-Days	OBJECT-TYPE
	SYNTAX	INTEGER
	ACCESS	read-only
	STATUS	mandatory
	DESCRIPTION	"Number of days that the DSL line has been up."
	::= { mibdmtAlDslLineStatusEntry 35 }

    dmtAlDslLineStatus-PhysicalStatistic-LineUpTimer-Hours	OBJECT-TYPE
	SYNTAX	INTEGER
	ACCESS	read-only
	STATUS	mandatory
	DESCRIPTION	"Number of hours that the DSL line has been up."
	::= { mibdmtAlDslLineStatusEntry 36 }

    dmtAlDslLineStatus-PhysicalStatistic-LineUpTimer-Minutes	OBJECT-TYPE
	SYNTAX	INTEGER
	ACCESS	read-only
	STATUS	mandatory
	DESCRIPTION	"Number of minutes that the DSL line has been up."
	::= { mibdmtAlDslLineStatusEntry 37 }

    dmtAlDslLineStatus-PhysicalStatistic-RxSignalPresent	OBJECT-TYPE
	SYNTAX	INTEGER {
		    yes (3),
		    no (2)
		}
	ACCESS	read-only
	STATUS	mandatory
	DESCRIPTION	"State if the receive signal is present or not."
	::= { mibdmtAlDslLineStatusEntry 38 }

    dmtAlDslLineStatus-PhysicalStatistic-UpDwnCntr	OBJECT-TYPE
	SYNTAX	INTEGER
	ACCESS	read-only
	STATUS	mandatory
	DESCRIPTION	"Interface Up Down counter value displays the number of times the interface trasitions from a down to up state."
	::= { mibdmtAlDslLineStatusEntry 39 }

    dmtAlDslLineStatus-PhysicalStatistic-SelfTest	OBJECT-TYPE
	SYNTAX	INTEGER {
		    notDone (1),
		    failed (2),
		    passed (3)
		}
	ACCESS	read-only
	STATUS	mandatory
	DESCRIPTION	"Hardware/firmware self test results."
	::= { mibdmtAlDslLineStatusEntry 40 }

    dmtAlDslLineStatus-PhysicalStatistic-NoiseMarginDown	OBJECT-TYPE
	SYNTAX	INTEGER
	ACCESS	read-only
	STATUS	mandatory
	DESCRIPTION	"The downstream noise margin in dB."
	::= { mibdmtAlDslLineStatusEntry 41 }

    dmtAlDslLineStatus-PhysicalStatistic-AttenuationDown	OBJECT-TYPE
	SYNTAX	INTEGER
	ACCESS	read-only
	STATUS	mandatory
	DESCRIPTION	"The downstream attenuation in dB."
	::= { mibdmtAlDslLineStatusEntry 42 }

    dmtAlDslLineStatus-PhysicalStatistic-OutputPowerDown	OBJECT-TYPE
	SYNTAX	INTEGER
	ACCESS	read-only
	STATUS	mandatory
	DESCRIPTION	"The total output power downstream in dBm."
	::= { mibdmtAlDslLineStatusEntry 43 }

    dmtAlDslLineStatus-PhysicalStatistic-NoiseMarginUp	OBJECT-TYPE
	SYNTAX	INTEGER
	ACCESS	read-only
	STATUS	mandatory
	DESCRIPTION	"The upstream noise margin in dB."
	::= { mibdmtAlDslLineStatusEntry 44 }

    dmtAlDslLineStatus-PhysicalStatistic-AttenuationUp	OBJECT-TYPE
	SYNTAX	INTEGER
	ACCESS	read-only
	STATUS	mandatory
	DESCRIPTION	"The upstream attenuation in dB."
	::= { mibdmtAlDslLineStatusEntry 45 }

    dmtAlDslLineStatus-PhysicalStatistic-OutputPowerUp	OBJECT-TYPE
	SYNTAX	INTEGER
	ACCESS	read-only
	STATUS	mandatory
	DESCRIPTION	"The total output power upstream in dBm."
	::= { mibdmtAlDslLineStatusEntry 46 }

    dmtAlDslLineStatus-PhysicalStatistic-NearEndFec	OBJECT-TYPE
	SYNTAX	INTEGER
	ACCESS	read-only
	STATUS	mandatory
	DESCRIPTION	"How many frames had Reed Solomon error correction for the data."
	::= { mibdmtAlDslLineStatusEntry 47 }

    dmtAlDslLineStatus-PhysicalStatistic-NearEndCrc	OBJECT-TYPE
	SYNTAX	INTEGER
	ACCESS	read-only
	STATUS	mandatory
	DESCRIPTION	"Received CRC-8 code is different for data in superframe than the one calculated."
	::= { mibdmtAlDslLineStatusEntry 48 }

    dmtAlDslLineStatus-PhysicalStatistic-NearEndHec	OBJECT-TYPE
	SYNTAX	INTEGER
	ACCESS	read-only
	STATUS	mandatory
	DESCRIPTION	"HEC error in received cell."
	::= { mibdmtAlDslLineStatusEntry 49 }

    dmtAlDslLineStatus-PhysicalStatistic-FarEndFec	OBJECT-TYPE
	SYNTAX	INTEGER
	ACCESS	read-only
	STATUS	mandatory
	DESCRIPTION	"How many frames had Reed Solomon error correction for the data."
	::= { mibdmtAlDslLineStatusEntry 50 }

    dmtAlDslLineStatus-PhysicalStatistic-FarEndCrc	OBJECT-TYPE
	SYNTAX	INTEGER
	ACCESS	read-only
	STATUS	mandatory
	DESCRIPTION	"Received CRC-8 code is different for data in superframe than the one calculated."
	::= { mibdmtAlDslLineStatusEntry 51 }

    dmtAlDslLineStatus-PhysicalStatistic-FarEndHec	OBJECT-TYPE
	SYNTAX	INTEGER
	ACCESS	read-only
	STATUS	mandatory
	DESCRIPTION	"HEC error in received cell."
	::= { mibdmtAlDslLineStatusEntry 52 }

    dmtAlDslLineStatus-PhysicalStatistic-ReceivedRsBlocks	OBJECT-TYPE
	SYNTAX	INTEGER
	ACCESS	read-only
	STATUS	mandatory
	DESCRIPTION	"How many Reed Solomon blocks received."
	::= { mibdmtAlDslLineStatusEntry 53 }

    dmtAlDslLineStatus-PhysicalStatistic-TransmittedRsBlocks	OBJECT-TYPE
	SYNTAX	INTEGER
	ACCESS	read-only
	STATUS	mandatory
	DESCRIPTION	"How many Reed Solomon blocks transmitted."
	::= { mibdmtAlDslLineStatusEntry 54 }

    dmtAlDslLineStatus-PhysicalStatistic-IncomingCells	OBJECT-TYPE
	SYNTAX	INTEGER
	ACCESS	read-only
	STATUS	mandatory
	DESCRIPTION	"How many cells received."
	::= { mibdmtAlDslLineStatusEntry 55 }

    dmtAlDslLineStatus-PhysicalStatistic-OutgoingCells	OBJECT-TYPE
	SYNTAX	INTEGER
	ACCESS	read-only
	STATUS	mandatory
	DESCRIPTION	"How many cells transmitted."
	::= { mibdmtAlDslLineStatusEntry 56 }

    dmtAlDslLineStatus-Action-o	OBJECT-TYPE
	SYNTAX	INTEGER {
		    noAction (1),
		    createProfile (2),
		    deleteProfile (3)
		}
	ACCESS	read-write
	STATUS	mandatory
	DESCRIPTION	""
	::= { mibdmtAlDslLineStatusEntry 57 }


	-- The mibe3AtmLineStatus table
	--
	-- This table contains parameters for the mibe3AtmLineStatus profile
	--

    mibe3AtmLineStatusTable	OBJECT-TYPE
	SYNTAX		SEQUENCE OF Mibe3AtmLineStatusEntry
	ACCESS		not-accessible
	STATUS		mandatory
	DESCRIPTION	"A list of mibe3AtmLineStatus profile entries."
	::= { mibe3AtmLineStatus 1 }

    mibe3AtmLineStatusEntry	OBJECT-TYPE
	SYNTAX		Mibe3AtmLineStatusEntry
	ACCESS		not-accessible
	STATUS		mandatory
	DESCRIPTION	"A mibe3AtmLineStatus entry containing objects that
			 maps to the parameters of mibe3AtmLineStatus profile."
	INDEX		{ e3AtmLineStatus-Shelf-o, e3AtmLineStatus-Slot-o, e3AtmLineStatus-Item-o }
	::= { mibe3AtmLineStatusTable 1 }

    Mibe3AtmLineStatusEntry ::=
	SEQUENCE {
	    e3AtmLineStatus-Shelf-o
		INTEGER,
	    e3AtmLineStatus-Slot-o
		INTEGER,
	    e3AtmLineStatus-Item-o
		INTEGER,
	    e3AtmLineStatus-PhysicalAddress-Shelf
		INTEGER,
	    e3AtmLineStatus-PhysicalAddress-Slot
		INTEGER,
	    e3AtmLineStatus-PhysicalAddress-ItemNumber
		INTEGER,
	    e3AtmLineStatus-LineState
		INTEGER,
	    e3AtmLineStatus-SparePhysicalAddress-Shelf
		INTEGER,
	    e3AtmLineStatus-SparePhysicalAddress-Slot
		INTEGER,
	    e3AtmLineStatus-SparePhysicalAddress-ItemNumber
		INTEGER,
	    e3AtmLineStatus-SparingState
		INTEGER,
	    e3AtmLineStatus-SparingChangeReason
		INTEGER,
	    e3AtmLineStatus-SparingChangeTime
		INTEGER,
	    e3AtmLineStatus-SparingChangeCounter
		INTEGER,
	    e3AtmLineStatus-VpiVciRange
		INTEGER,
	    e3AtmLineStatus-VcSwitchingVpi
		DisplayString,
	    e3AtmLineStatus-FBitErrorCount
		INTEGER,
	    e3AtmLineStatus-PBitErrorCount
		INTEGER,
	    e3AtmLineStatus-CpBitErrorCount
		INTEGER,
	    e3AtmLineStatus-FebErrorCount
		INTEGER,
	    e3AtmLineStatus-BpvErrorCount
		INTEGER,
	    e3AtmLineStatus-LossOfSignal
		INTEGER,
	    e3AtmLineStatus-LossOfFrame
		INTEGER,
	    e3AtmLineStatus-YellowReceive
		INTEGER,
	    e3AtmLineStatus-AisReceive
		INTEGER,
	    e3AtmLineStatus-Action-o
		INTEGER
	}

    e3AtmLineStatus-Shelf-o	OBJECT-TYPE
	SYNTAX	INTEGER
	ACCESS	read-only
	STATUS	mandatory
	DESCRIPTION	""
	::= { mibe3AtmLineStatusEntry 1 }

    e3AtmLineStatus-Slot-o	OBJECT-TYPE
	SYNTAX	INTEGER
	ACCESS	read-only
	STATUS	mandatory
	DESCRIPTION	""
	::= { mibe3AtmLineStatusEntry 2 }

    e3AtmLineStatus-Item-o	OBJECT-TYPE
	SYNTAX	INTEGER
	ACCESS	read-only
	STATUS	mandatory
	DESCRIPTION	""
	::= { mibe3AtmLineStatusEntry 3 }

    e3AtmLineStatus-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibe3AtmLineStatusEntry 4 }

    e3AtmLineStatus-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibe3AtmLineStatusEntry 5 }

    e3AtmLineStatus-PhysicalAddress-ItemNumber	OBJECT-TYPE
	SYNTAX	INTEGER
	ACCESS	read-write
	STATUS	mandatory
	DESCRIPTION	"A number that specifies an addressable entity within the context of shelf and slot."
	::= { mibe3AtmLineStatusEntry 6 }

    e3AtmLineStatus-LineState	OBJECT-TYPE
	SYNTAX	INTEGER {
		    doesNotExist (1),
		    disabled (2),
		    lossOfSignal (3),
		    lossOfFrame (4),
		    yellowReceive (5),
		    aisReceive (6),
		    active (7)
		}
	ACCESS	read-write
	STATUS	mandatory
	DESCRIPTION	"The overall state of the line."
	::= { mibe3AtmLineStatusEntry 7 }

    e3AtmLineStatus-SparePhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibe3AtmLineStatusEntry 8 }

    e3AtmLineStatus-SparePhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibe3AtmLineStatusEntry 9 }

    e3AtmLineStatus-SparePhysicalAddress-ItemNumber	OBJECT-TYPE
	SYNTAX	INTEGER
	ACCESS	read-write
	STATUS	mandatory
	DESCRIPTION	"A number that specifies an addressable entity within the context of shelf and slot."
	::= { mibe3AtmLineStatusEntry 10 }

    e3AtmLineStatus-SparingState	OBJECT-TYPE
	SYNTAX	INTEGER {
		    sparingNone (1),
		    primaryActive (2),
		    primaryInactive (3),
		    secondaryActive (4),
		    secondaryInactive (5)
		}
	ACCESS	read-only
	STATUS	mandatory
	DESCRIPTION	"The sparing state of the line."
	::= { mibe3AtmLineStatusEntry 11 }

    e3AtmLineStatus-SparingChangeReason	OBJECT-TYPE
	SYNTAX	INTEGER {
		    unknown (1),
		    manual (2),
		    automatic (3),
		    test (4)
		}
	ACCESS	read-only
	STATUS	mandatory
	DESCRIPTION	"The reason for the last sparing state change."
	::= { mibe3AtmLineStatusEntry 12 }

    e3AtmLineStatus-SparingChangeTime	OBJECT-TYPE
	SYNTAX	INTEGER
	ACCESS	read-only
	STATUS	mandatory
	DESCRIPTION	"The time of the last sparing state change."
	::= { mibe3AtmLineStatusEntry 13 }

    e3AtmLineStatus-SparingChangeCounter	OBJECT-TYPE
	SYNTAX	INTEGER
	ACCESS	read-only
	STATUS	mandatory
	DESCRIPTION	"The number of sparing state changes."
	::= { mibe3AtmLineStatusEntry 14 }

    e3AtmLineStatus-VpiVciRange	OBJECT-TYPE
	SYNTAX	INTEGER {
		    n-01-3232767 (1),
		    n-03-3216383 (2),
		    n-07-328191 (3),
		    n-015-324095 (4),
		    n-031-322047 (5),
		    n-063-321023 (6),
		    n-0127-32511 (7),
		    n-0255-32255 (8),
		    vpi0255Vci32255 (9),
		    vpi0255Vci32511 (10),
		    vpi0255Vci321023 (11),
		    vpi0255Vci322047 (12),
		    vpi0255Vci324095 (13),
		    vpi0255Vci328191 (14),
		    vpi0255Vci3216383 (15)
		}
	ACCESS	read-only
	STATUS	mandatory
	DESCRIPTION	"Current valid range of VPI/VCI. This range can change only after system reboot. The valid range of VCI is same for all VC switching VPIs. VP switching VPIs don't have restriction over VCI range."
	::= { mibe3AtmLineStatusEntry 15 }

    e3AtmLineStatus-VcSwitchingVpi	OBJECT-TYPE
	SYNTAX	DisplayString
	ACCESS	read-only
	STATUS	mandatory
	DESCRIPTION	"A list of VPIs used for the VC switching (VCC). Rest of the VPIs are used for VP switching."
	::= { mibe3AtmLineStatusEntry 16 }

    e3AtmLineStatus-FBitErrorCount	OBJECT-TYPE
	SYNTAX	INTEGER
	ACCESS	read-write
	STATUS	mandatory
	DESCRIPTION	"The number of F-bit or M-bit errors experienced by the line."
	::= { mibe3AtmLineStatusEntry 17 }

    e3AtmLineStatus-PBitErrorCount	OBJECT-TYPE
	SYNTAX	INTEGER
	ACCESS	read-write
	STATUS	mandatory
	DESCRIPTION	"The number of P-bit errors experienced by the line."
	::= { mibe3AtmLineStatusEntry 18 }

    e3AtmLineStatus-CpBitErrorCount	OBJECT-TYPE
	SYNTAX	INTEGER
	ACCESS	read-write
	STATUS	mandatory
	DESCRIPTION	"The number of C-bit parity errors experienced by the line."
	::= { mibe3AtmLineStatusEntry 19 }

    e3AtmLineStatus-FebErrorCount	OBJECT-TYPE
	SYNTAX	INTEGER
	ACCESS	read-write
	STATUS	mandatory
	DESCRIPTION	"The number of far-end block errors experienced by the line."
	::= { mibe3AtmLineStatusEntry 20 }

    e3AtmLineStatus-BpvErrorCount	OBJECT-TYPE
	SYNTAX	INTEGER
	ACCESS	read-write
	STATUS	mandatory
	DESCRIPTION	"The number of bipolar violation errors experienced by the line."
	::= { mibe3AtmLineStatusEntry 21 }

    e3AtmLineStatus-LossOfSignal	OBJECT-TYPE
	SYNTAX	INTEGER {
		    false (1),
		    true (2)
		}
	ACCESS	read-write
	STATUS	mandatory
	DESCRIPTION	"Indicates a loss of signal on the line."
	::= { mibe3AtmLineStatusEntry 22 }

    e3AtmLineStatus-LossOfFrame	OBJECT-TYPE
	SYNTAX	INTEGER {
		    false (1),
		    true (2)
		}
	ACCESS	read-write
	STATUS	mandatory
	DESCRIPTION	"Indicates a loss of frame on the line (a.k.a. Red Alarm)."
	::= { mibe3AtmLineStatusEntry 23 }

    e3AtmLineStatus-YellowReceive	OBJECT-TYPE
	SYNTAX	INTEGER {
		    false (1),
		    true (2)
		}
	ACCESS	read-write
	STATUS	mandatory
	DESCRIPTION	"Indicates receiving far end loss of frame (a.k.a. Yellow Alarm)."
	::= { mibe3AtmLineStatusEntry 24 }

    e3AtmLineStatus-AisReceive	OBJECT-TYPE
	SYNTAX	INTEGER {
		    false (1),
		    true (2)
		}
	ACCESS	read-write
	STATUS	mandatory
	DESCRIPTION	"Indicates far end is sending Alarm Indication Signal."
	::= { mibe3AtmLineStatusEntry 25 }

    e3AtmLineStatus-Action-o	OBJECT-TYPE
	SYNTAX	INTEGER {
		    noAction (1),
		    createProfile (2),
		    deleteProfile (3)
		}
	ACCESS	read-write
	STATUS	mandatory
	DESCRIPTION	""
	::= { mibe3AtmLineStatusEntry 26 }


	-- The miboc3AtmLineStatus table
	--
	-- This table contains parameters for the miboc3AtmLineStatus profile
	--

    miboc3AtmLineStatusTable	OBJECT-TYPE
	SYNTAX		SEQUENCE OF Miboc3AtmLineStatusEntry
	ACCESS		not-accessible
	STATUS		mandatory
	DESCRIPTION	"A list of miboc3AtmLineStatus profile entries."
	::= { miboc3AtmLineStatus 1 }

    miboc3AtmLineStatusEntry	OBJECT-TYPE
	SYNTAX		Miboc3AtmLineStatusEntry
	ACCESS		not-accessible
	STATUS		mandatory
	DESCRIPTION	"A miboc3AtmLineStatus entry containing objects that
			 maps to the parameters of miboc3AtmLineStatus profile."
	INDEX		{ oc3AtmLineStatus-Shelf-o, oc3AtmLineStatus-Slot-o, oc3AtmLineStatus-Item-o }
	::= { miboc3AtmLineStatusTable 1 }

    Miboc3AtmLineStatusEntry ::=
	SEQUENCE {
	    oc3AtmLineStatus-Shelf-o
		INTEGER,
	    oc3AtmLineStatus-Slot-o
		INTEGER,
	    oc3AtmLineStatus-Item-o
		INTEGER,
	    oc3AtmLineStatus-PhysicalAddress-Shelf
		INTEGER,
	    oc3AtmLineStatus-PhysicalAddress-Slot
		INTEGER,
	    oc3AtmLineStatus-PhysicalAddress-ItemNumber
		INTEGER,
	    oc3AtmLineStatus-LineState
		INTEGER,
	    oc3AtmLineStatus-SparePhysicalAddress-Shelf
		INTEGER,
	    oc3AtmLineStatus-SparePhysicalAddress-Slot
		INTEGER,
	    oc3AtmLineStatus-SparePhysicalAddress-ItemNumber
		INTEGER,
	    oc3AtmLineStatus-SparingState
		INTEGER,
	    oc3AtmLineStatus-SparingChangeReason
		INTEGER,
	    oc3AtmLineStatus-SparingChangeTime
		INTEGER,
	    oc3AtmLineStatus-SparingChangeCounter
		INTEGER,
	    oc3AtmLineStatus-VpiVciRange
		INTEGER,
	    oc3AtmLineStatus-VcSwitchingVpi
		DisplayString,
	    oc3AtmLineStatus-ApsConfigName
		DisplayString,
	    oc3AtmLineStatus-ApsChannelStatus
		INTEGER,
	    oc3AtmLineStatus-ApsChannelSdCondition
		INTEGER,
	    oc3AtmLineStatus-ApsChannelSfCondition
		INTEGER,
	    oc3AtmLineStatus-ApsChannelLowDirection
		INTEGER,
	    oc3AtmLineStatus-ApsChannelRecvSdCount
		INTEGER,
	    oc3AtmLineStatus-ApsChannelRecvSfCount
		INTEGER,
	    oc3AtmLineStatus-ApsChannelRecvAisCount
		INTEGER,
	    oc3AtmLineStatus-ApsChannelRecvRdiCount
		INTEGER,
	    oc3AtmLineStatus-LossOfSignal
		INTEGER,
	    oc3AtmLineStatus-LossOfFrame
		INTEGER,
	    oc3AtmLineStatus-OutOfFrame
		INTEGER,
	    oc3AtmLineStatus-SectionState
		INTEGER,
	    oc3AtmLineStatus-PathState
		INTEGER,
	    oc3AtmLineStatus-AisReceive
		INTEGER,
	    oc3AtmLineStatus-YellowReceive
		INTEGER,
	    oc3AtmLineStatus-OutOfCellDelineation
		INTEGER,
	    oc3AtmLineStatus-LossOfCellDelineation
		INTEGER,
	    oc3AtmLineStatus-ApsReceive
		INTEGER,
	    oc3AtmLineStatus-RsopBipErrorCount
		INTEGER,
	    oc3AtmLineStatus-RlopBipErrorCount
		INTEGER,
	    oc3AtmLineStatus-RlopFebeErrorCount
		INTEGER,
	    oc3AtmLineStatus-RpopBipErrorCount
		INTEGER,
	    oc3AtmLineStatus-RpopFebeErrorCount
		INTEGER,
	    oc3AtmLineStatus-RacpChcsErrorCount
		INTEGER,
	    oc3AtmLineStatus-RacpUchcsErrorCount
		INTEGER,
	    oc3AtmLineStatus-RacpRxCellCount
		INTEGER,
	    oc3AtmLineStatus-TacpTxCellCount
		INTEGER,
	    oc3AtmLineStatus-FrequencyJustificationCount
		INTEGER,
	    oc3AtmLineStatus-oHECCellDropCounter
		INTEGER,
	    oc3AtmLineStatus-oFIFOOverflowCounter
		INTEGER,
	    oc3AtmLineStatus-IdleCellCounter
		INTEGER,
	    oc3AtmLineStatus-ValidCellCounter
		INTEGER,
	    oc3AtmLineStatus-PerformanceMonitoring-SonetSectionErroredSeconds
		INTEGER,
	    oc3AtmLineStatus-PerformanceMonitoring-SonetSectionSeverelyErroredSeconds
		INTEGER,
	    oc3AtmLineStatus-PerformanceMonitoring-SonetSectionSeverelyErroredFramingSeconds
		INTEGER,
	    oc3AtmLineStatus-PerformanceMonitoring-SonetSectionCodingViolations
		INTEGER,
	    oc3AtmLineStatus-PerformanceMonitoring-SonetLineErroredSeconds
		INTEGER,
	    oc3AtmLineStatus-PerformanceMonitoring-SonetLineSeverelyErroredSeconds
		INTEGER,
	    oc3AtmLineStatus-PerformanceMonitoring-SonetLineCodingViolations
		INTEGER,
	    oc3AtmLineStatus-PerformanceMonitoring-SonetLineUnavailableSeconds
		INTEGER,
	    oc3AtmLineStatus-PerformanceMonitoring-SonetFarEndLineErroredSeconds
		INTEGER,
	    oc3AtmLineStatus-PerformanceMonitoring-SonetFarEndLineSeverelyErroredSeconds
		INTEGER,
	    oc3AtmLineStatus-PerformanceMonitoring-SonetFarEndLineCodingViolations
		INTEGER,
	    oc3AtmLineStatus-PerformanceMonitoring-SonetFarEndLineUnavailableSeconds
		INTEGER,
	    oc3AtmLineStatus-PerformanceMonitoring-SonetPathErroredSeconds
		INTEGER,
	    oc3AtmLineStatus-PerformanceMonitoring-SonetPathSeverelyErroredSeconds
		INTEGER,
	    oc3AtmLineStatus-PerformanceMonitoring-SonetPathCodingViolations
		INTEGER,
	    oc3AtmLineStatus-PerformanceMonitoring-SonetPathUnavailableSeconds
		INTEGER,
	    oc3AtmLineStatus-PerformanceMonitoring-SonetFarEndPathErroredSeconds
		INTEGER,
	    oc3AtmLineStatus-PerformanceMonitoring-SonetFarEndPathSeverelyErroredSeconds
		INTEGER,
	    oc3AtmLineStatus-PerformanceMonitoring-SonetFarEndPathCodingViolations
		INTEGER,
	    oc3AtmLineStatus-PerformanceMonitoring-SonetFarEndPathUnavailableSeconds
		INTEGER,
	    oc3AtmLineStatus-Action-o
		INTEGER
	}

    oc3AtmLineStatus-Shelf-o	OBJECT-TYPE
	SYNTAX	INTEGER
	ACCESS	read-only
	STATUS	mandatory
	DESCRIPTION	""
	::= { miboc3AtmLineStatusEntry 1 }

    oc3AtmLineStatus-Slot-o	OBJECT-TYPE
	SYNTAX	INTEGER
	ACCESS	read-only
	STATUS	mandatory
	DESCRIPTION	""
	::= { miboc3AtmLineStatusEntry 2 }

    oc3AtmLineStatus-Item-o	OBJECT-TYPE
	SYNTAX	INTEGER
	ACCESS	read-only
	STATUS	mandatory
	DESCRIPTION	""
	::= { miboc3AtmLineStatusEntry 3 }

    oc3AtmLineStatus-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { miboc3AtmLineStatusEntry 4 }

    oc3AtmLineStatus-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { miboc3AtmLineStatusEntry 5 }

    oc3AtmLineStatus-PhysicalAddress-ItemNumber	OBJECT-TYPE
	SYNTAX	INTEGER
	ACCESS	read-write
	STATUS	mandatory
	DESCRIPTION	"A number that specifies an addressable entity within the context of shelf and slot."
	::= { miboc3AtmLineStatusEntry 6 }

    oc3AtmLineStatus-LineState	OBJECT-TYPE
	SYNTAX	INTEGER {
		    doesNotExist (1),
		    disabled (2),
		    lossOfSignal (3),
		    lossOfFrame (4),
		    yellowReceive (5),
		    aisReceive (6),
		    active (7)
		}
	ACCESS	read-only
	STATUS	mandatory
	DESCRIPTION	"The overall state of the line."
	::= { miboc3AtmLineStatusEntry 7 }

    oc3AtmLineStatus-SparePhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { miboc3AtmLineStatusEntry 8 }

    oc3AtmLineStatus-SparePhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { miboc3AtmLineStatusEntry 9 }

    oc3AtmLineStatus-SparePhysicalAddress-ItemNumber	OBJECT-TYPE
	SYNTAX	INTEGER
	ACCESS	read-write
	STATUS	mandatory
	DESCRIPTION	"A number that specifies an addressable entity within the context of shelf and slot."
	::= { miboc3AtmLineStatusEntry 10 }

    oc3AtmLineStatus-SparingState	OBJECT-TYPE
	SYNTAX	INTEGER {
		    sparingNone (1),
		    primaryActive (2),
		    primaryInactive (3),
		    secondaryActive (4),
		    secondaryInactive (5)
		}
	ACCESS	read-only
	STATUS	mandatory
	DESCRIPTION	"The sparing state of the line."
	::= { miboc3AtmLineStatusEntry 11 }

    oc3AtmLineStatus-SparingChangeReason	OBJECT-TYPE
	SYNTAX	INTEGER {
		    unknown (1),
		    manual (2),
		    automatic (3),
		    test (4)
		}
	ACCESS	read-only
	STATUS	mandatory
	DESCRIPTION	"The reason for the last sparing state change."
	::= { miboc3AtmLineStatusEntry 12 }

    oc3AtmLineStatus-SparingChangeTime	OBJECT-TYPE
	SYNTAX	INTEGER
	ACCESS	read-only
	STATUS	mandatory
	DESCRIPTION	"The time of the last sparing state change."
	::= { miboc3AtmLineStatusEntry 13 }

    oc3AtmLineStatus-SparingChangeCounter	OBJECT-TYPE
	SYNTAX	INTEGER
	ACCESS	read-only
	STATUS	mandatory
	DESCRIPTION	"The number of sparing state changes."
	::= { miboc3AtmLineStatusEntry 14 }

    oc3AtmLineStatus-VpiVciRange	OBJECT-TYPE
	SYNTAX	INTEGER {
		    n-01-3232767 (1),
		    n-03-3216383 (2),
		    n-07-328191 (3),
		    n-015-324095 (4),
		    n-031-322047 (5),
		    n-063-321023 (6),
		    n-0127-32511 (7),
		    n-0255-32255 (8),
		    vpi0255Vci32255 (9),
		    vpi0255Vci32511 (10),
		    vpi0255Vci321023 (11),
		    vpi0255Vci322047 (12),
		    vpi0255Vci324095 (13),
		    vpi0255Vci328191 (14),
		    vpi0255Vci3216383 (15)
		}
	ACCESS	read-only
	STATUS	mandatory
	DESCRIPTION	"Current valid range of VPI/VCI. This range can change only after system reboot. The valid range of VCI is same for all VC switching VPIs. VP switching VPIs don't have restriction over VCI range."
	::= { miboc3AtmLineStatusEntry 15 }

    oc3AtmLineStatus-VcSwitchingVpi	OBJECT-TYPE
	SYNTAX	DisplayString
	ACCESS	read-only
	STATUS	mandatory
	DESCRIPTION	"A list of VPIs used for the VC switching (VCC). Rest of the VPIs are used for VP switching."
	::= { miboc3AtmLineStatusEntry 16 }

    oc3AtmLineStatus-ApsConfigName	OBJECT-TYPE
	SYNTAX	DisplayString
	ACCESS	read-write
	STATUS	mandatory
	DESCRIPTION	"APS Config Profile name, specifies APS configuration profile that defines a protection group for this channel."
	::= { miboc3AtmLineStatusEntry 17 }

    oc3AtmLineStatus-ApsChannelStatus	OBJECT-TYPE
	SYNTAX	INTEGER {
		    unknown (1),
		    onProtection (2),
		    onWorking (3),
		    lockedOutWorking (4)
		}
	ACCESS	read-write
	STATUS	mandatory
	DESCRIPTION	"Indicates the current status of the channel (port)."
	::= { miboc3AtmLineStatusEntry 18 }

    oc3AtmLineStatus-ApsChannelSdCondition	OBJECT-TYPE
	SYNTAX	INTEGER {
		    false (1),
		    true (2)
		}
	ACCESS	read-only
	STATUS	mandatory
	DESCRIPTION	"Indicates Signal Degrade condition."
	::= { miboc3AtmLineStatusEntry 19 }

    oc3AtmLineStatus-ApsChannelSfCondition	OBJECT-TYPE
	SYNTAX	INTEGER {
		    false (1),
		    true (2)
		}
	ACCESS	read-only
	STATUS	mandatory
	DESCRIPTION	"Indicates Signal Failure condition."
	::= { miboc3AtmLineStatusEntry 20 }

    oc3AtmLineStatus-ApsChannelLowDirection	OBJECT-TYPE
	SYNTAX	INTEGER {
		    lowNone (1),
		    lowRecv (2),
		    lowSend (3),
		    lowBoth (4)
		}
	ACCESS	read-only
	STATUS	mandatory
	DESCRIPTION	"LOW direction."
	::= { miboc3AtmLineStatusEntry 21 }

    oc3AtmLineStatus-ApsChannelRecvSdCount	OBJECT-TYPE
	SYNTAX	INTEGER
	ACCESS	read-write
	STATUS	mandatory
	DESCRIPTION	"Counts the number of signal degrade conditions (line bit error rate that exceeded the configured threshold) received over the K1K2 APS channel received from the far-end."
	::= { miboc3AtmLineStatusEntry 22 }

    oc3AtmLineStatus-ApsChannelRecvSfCount	OBJECT-TYPE
	SYNTAX	INTEGER
	ACCESS	read-write
	STATUS	mandatory
	DESCRIPTION	"Counts the number of signal failure conditions (loss of signal, loss of frame, AIS-L or BER exceeding the configured threshold)."
	::= { miboc3AtmLineStatusEntry 23 }

    oc3AtmLineStatus-ApsChannelRecvAisCount	OBJECT-TYPE
	SYNTAX	INTEGER
	ACCESS	read-write
	STATUS	mandatory
	DESCRIPTION	"Counts the number of AIS-L received."
	::= { miboc3AtmLineStatusEntry 24 }

    oc3AtmLineStatus-ApsChannelRecvRdiCount	OBJECT-TYPE
	SYNTAX	INTEGER
	ACCESS	read-write
	STATUS	mandatory
	DESCRIPTION	"Counts the number of RDI-L received."
	::= { miboc3AtmLineStatusEntry 25 }

    oc3AtmLineStatus-LossOfSignal	OBJECT-TYPE
	SYNTAX	INTEGER {
		    false (1),
		    true (2)
		}
	ACCESS	read-only
	STATUS	mandatory
	DESCRIPTION	"Indicates a loss of signal on the line."
	::= { miboc3AtmLineStatusEntry 26 }

    oc3AtmLineStatus-LossOfFrame	OBJECT-TYPE
	SYNTAX	INTEGER {
		    false (1),
		    true (2)
		}
	ACCESS	read-only
	STATUS	mandatory
	DESCRIPTION	"Indicates a loss of frame on the line (a.k.a. Red Alarm)."
	::= { miboc3AtmLineStatusEntry 27 }

    oc3AtmLineStatus-OutOfFrame	OBJECT-TYPE
	SYNTAX	INTEGER {
		    false (1),
		    true (2)
		}
	ACCESS	read-only
	STATUS	mandatory
	DESCRIPTION	"Indicates near end out of frame."
	::= { miboc3AtmLineStatusEntry 28 }

    oc3AtmLineStatus-SectionState	OBJECT-TYPE
	SYNTAX	INTEGER {
		    sonetDisabled (1),
		    sonetSectionActiveNoDefect (2),
		    sonetSectionLossOfSignal (3),
		    sonetSectionLossOfFrame (4)
		}
	ACCESS	read-only
	STATUS	mandatory
	DESCRIPTION	"The state of the Sonet Section"
	::= { miboc3AtmLineStatusEntry 29 }

    oc3AtmLineStatus-PathState	OBJECT-TYPE
	SYNTAX	INTEGER {
		    sonetDisabled (1),
		    sonetPathActiveNoDefect (2),
		    sonetPathLossOfPointer (3),
		    sonetPathAlarmIndicationSignal (4),
		    sonetPathRdi (5),
		    sonetPathUnquipped (6),
		    sonetPathSignalLabelMismatch (7)
		}
	ACCESS	read-only
	STATUS	mandatory
	DESCRIPTION	"The state of the Sonet Path"
	::= { miboc3AtmLineStatusEntry 30 }

    oc3AtmLineStatus-AisReceive	OBJECT-TYPE
	SYNTAX	INTEGER {
		    false (1),
		    true (2)
		}
	ACCESS	read-only
	STATUS	mandatory
	DESCRIPTION	"Indicates far end is sending Alarm Indication Signal."
	::= { miboc3AtmLineStatusEntry 31 }

    oc3AtmLineStatus-YellowReceive	OBJECT-TYPE
	SYNTAX	INTEGER {
		    false (1),
		    true (2)
		}
	ACCESS	read-only
	STATUS	mandatory
	DESCRIPTION	"Indicates receiving far end loss of frame (a.k.a. Yellow Alarm)."
	::= { miboc3AtmLineStatusEntry 32 }

    oc3AtmLineStatus-OutOfCellDelineation	OBJECT-TYPE
	SYNTAX	INTEGER {
		    false (1),
		    true (2)
		}
	ACCESS	read-only
	STATUS	mandatory
	DESCRIPTION	"Indicates out of cell delineation - HEC check failed."
	::= { miboc3AtmLineStatusEntry 33 }

    oc3AtmLineStatus-LossOfCellDelineation	OBJECT-TYPE
	SYNTAX	INTEGER {
		    false (1),
		    true (2)
		}
	ACCESS	read-only
	STATUS	mandatory
	DESCRIPTION	"Indicates loss of cell delineation."
	::= { miboc3AtmLineStatusEntry 34 }

    oc3AtmLineStatus-ApsReceive	OBJECT-TYPE
	SYNTAX	INTEGER {
		    false (1),
		    true (2)
		}
	ACCESS	read-only
	STATUS	mandatory
	DESCRIPTION	"APS activated ????. <placeholder .. for further study>"
	::= { miboc3AtmLineStatusEntry 35 }

    oc3AtmLineStatus-RsopBipErrorCount	OBJECT-TYPE
	SYNTAX	INTEGER
	ACCESS	read-only
	STATUS	mandatory
	DESCRIPTION	"The number RSOP BIP errors experienced by the line."
	::= { miboc3AtmLineStatusEntry 36 }

    oc3AtmLineStatus-RlopBipErrorCount	OBJECT-TYPE
	SYNTAX	INTEGER
	ACCESS	read-only
	STATUS	mandatory
	DESCRIPTION	"The number of RLOP BIP errors experienced by the line."
	::= { miboc3AtmLineStatusEntry 37 }

    oc3AtmLineStatus-RlopFebeErrorCount	OBJECT-TYPE
	SYNTAX	INTEGER
	ACCESS	read-only
	STATUS	mandatory
	DESCRIPTION	"The number of RLOP FEBE errors experienced by the line."
	::= { miboc3AtmLineStatusEntry 38 }

    oc3AtmLineStatus-RpopBipErrorCount	OBJECT-TYPE
	SYNTAX	INTEGER
	ACCESS	read-only
	STATUS	mandatory
	DESCRIPTION	"The number of RPOP BIE errors experienced by the line."
	::= { miboc3AtmLineStatusEntry 39 }

    oc3AtmLineStatus-RpopFebeErrorCount	OBJECT-TYPE
	SYNTAX	INTEGER
	ACCESS	read-only
	STATUS	mandatory
	DESCRIPTION	"The number of RPOP FEBE errors experienced by the line."
	::= { miboc3AtmLineStatusEntry 40 }

    oc3AtmLineStatus-RacpChcsErrorCount	OBJECT-TYPE
	SYNTAX	INTEGER
	ACCESS	read-only
	STATUS	mandatory
	DESCRIPTION	"The number of RACP CHCS errors experienced by the line."
	::= { miboc3AtmLineStatusEntry 41 }

    oc3AtmLineStatus-RacpUchcsErrorCount	OBJECT-TYPE
	SYNTAX	INTEGER
	ACCESS	read-only
	STATUS	mandatory
	DESCRIPTION	"The number of RACP UCHCS errors experienced by the line."
	::= { miboc3AtmLineStatusEntry 42 }

    oc3AtmLineStatus-RacpRxCellCount	OBJECT-TYPE
	SYNTAX	INTEGER
	ACCESS	read-only
	STATUS	mandatory
	DESCRIPTION	"The number of RACP RX cells received by the line."
	::= { miboc3AtmLineStatusEntry 43 }

    oc3AtmLineStatus-TacpTxCellCount	OBJECT-TYPE
	SYNTAX	INTEGER
	ACCESS	read-only
	STATUS	mandatory
	DESCRIPTION	"The number of TACP Tx cells transmittted by the line."
	::= { miboc3AtmLineStatusEntry 44 }

    oc3AtmLineStatus-FrequencyJustificationCount	OBJECT-TYPE
	SYNTAX	INTEGER
	ACCESS	read-only
	STATUS	mandatory
	DESCRIPTION	"The number of frequency justification operations."
	::= { miboc3AtmLineStatusEntry 45 }

    oc3AtmLineStatus-oHECCellDropCounter	OBJECT-TYPE
	SYNTAX	INTEGER
	ACCESS	read-only
	STATUS	mandatory
	DESCRIPTION	"The number of cells dropped by HEC processing."
	::= { miboc3AtmLineStatusEntry 46 }

    oc3AtmLineStatus-oFIFOOverflowCounter	OBJECT-TYPE
	SYNTAX	INTEGER
	ACCESS	read-only
	STATUS	mandatory
	DESCRIPTION	"The number of cells dropped due to FIFO overflow."
	::= { miboc3AtmLineStatusEntry 47 }

    oc3AtmLineStatus-IdleCellCounter	OBJECT-TYPE
	SYNTAX	INTEGER
	ACCESS	read-only
	STATUS	mandatory
	DESCRIPTION	"The total number of received idle cells."
	::= { miboc3AtmLineStatusEntry 48 }

    oc3AtmLineStatus-ValidCellCounter	OBJECT-TYPE
	SYNTAX	INTEGER
	ACCESS	read-only
	STATUS	mandatory
	DESCRIPTION	"The total number of valid cells received."
	::= { miboc3AtmLineStatusEntry 49 }

    oc3AtmLineStatus-PerformanceMonitoring-SonetSectionErroredSeconds	OBJECT-TYPE
	SYNTAX	INTEGER
	ACCESS	read-only
	STATUS	mandatory
	DESCRIPTION	"The number of errored seconds encountered by a Sonet section."
	::= { miboc3AtmLineStatusEntry 50 }

    oc3AtmLineStatus-PerformanceMonitoring-SonetSectionSeverelyErroredSeconds	OBJECT-TYPE
	SYNTAX	INTEGER
	ACCESS	read-only
	STATUS	mandatory
	DESCRIPTION	"The number of severely errored seconds encountered by a Sonet section."
	::= { miboc3AtmLineStatusEntry 51 }

    oc3AtmLineStatus-PerformanceMonitoring-SonetSectionSeverelyErroredFramingSeconds	OBJECT-TYPE
	SYNTAX	INTEGER
	ACCESS	read-only
	STATUS	mandatory
	DESCRIPTION	"The number of severely errored framing seconds encountered by a Sonet section."
	::= { miboc3AtmLineStatusEntry 52 }

    oc3AtmLineStatus-PerformanceMonitoring-SonetSectionCodingViolations	OBJECT-TYPE
	SYNTAX	INTEGER
	ACCESS	read-only
	STATUS	mandatory
	DESCRIPTION	"The number of coding violations encountered by a Sonet section."
	::= { miboc3AtmLineStatusEntry 53 }

    oc3AtmLineStatus-PerformanceMonitoring-SonetLineErroredSeconds	OBJECT-TYPE
	SYNTAX	INTEGER
	ACCESS	read-only
	STATUS	mandatory
	DESCRIPTION	"The number of errored seconds encountered by a Sonet line."
	::= { miboc3AtmLineStatusEntry 54 }

    oc3AtmLineStatus-PerformanceMonitoring-SonetLineSeverelyErroredSeconds	OBJECT-TYPE
	SYNTAX	INTEGER
	ACCESS	read-only
	STATUS	mandatory
	DESCRIPTION	"The number of severely errored seconds encountered by a Sonet line."
	::= { miboc3AtmLineStatusEntry 55 }

    oc3AtmLineStatus-PerformanceMonitoring-SonetLineCodingViolations	OBJECT-TYPE
	SYNTAX	INTEGER
	ACCESS	read-only
	STATUS	mandatory
	DESCRIPTION	"The number of coding violations encountered by a Sonet line."
	::= { miboc3AtmLineStatusEntry 56 }

    oc3AtmLineStatus-PerformanceMonitoring-SonetLineUnavailableSeconds	OBJECT-TYPE
	SYNTAX	INTEGER
	ACCESS	read-only
	STATUS	mandatory
	DESCRIPTION	"The number of unavailable seconds encountered by a Sonet line."
	::= { miboc3AtmLineStatusEntry 57 }

    oc3AtmLineStatus-PerformanceMonitoring-SonetFarEndLineErroredSeconds	OBJECT-TYPE
	SYNTAX	INTEGER
	ACCESS	read-only
	STATUS	mandatory
	DESCRIPTION	"The number of far end errored seconds encountered by a Sonet line."
	::= { miboc3AtmLineStatusEntry 58 }

    oc3AtmLineStatus-PerformanceMonitoring-SonetFarEndLineSeverelyErroredSeconds	OBJECT-TYPE
	SYNTAX	INTEGER
	ACCESS	read-only
	STATUS	mandatory
	DESCRIPTION	"The number of far end severely errored seconds encountered by a Sonet line."
	::= { miboc3AtmLineStatusEntry 59 }

    oc3AtmLineStatus-PerformanceMonitoring-SonetFarEndLineCodingViolations	OBJECT-TYPE
	SYNTAX	INTEGER
	ACCESS	read-only
	STATUS	mandatory
	DESCRIPTION	"The number of far end coding violations encountered by a Sonet line."
	::= { miboc3AtmLineStatusEntry 60 }

    oc3AtmLineStatus-PerformanceMonitoring-SonetFarEndLineUnavailableSeconds	OBJECT-TYPE
	SYNTAX	INTEGER
	ACCESS	read-only
	STATUS	mandatory
	DESCRIPTION	"The number of far end unavailable seconds encountered by a Sonet line."
	::= { miboc3AtmLineStatusEntry 61 }

    oc3AtmLineStatus-PerformanceMonitoring-SonetPathErroredSeconds	OBJECT-TYPE
	SYNTAX	INTEGER
	ACCESS	read-only
	STATUS	mandatory
	DESCRIPTION	"The number of errored seconds encountered by a Sonet path."
	::= { miboc3AtmLineStatusEntry 62 }

    oc3AtmLineStatus-PerformanceMonitoring-SonetPathSeverelyErroredSeconds	OBJECT-TYPE
	SYNTAX	INTEGER
	ACCESS	read-only
	STATUS	mandatory
	DESCRIPTION	"The number of severely errored seconds encountered by a Sonet path."
	::= { miboc3AtmLineStatusEntry 63 }

    oc3AtmLineStatus-PerformanceMonitoring-SonetPathCodingViolations	OBJECT-TYPE
	SYNTAX	INTEGER
	ACCESS	read-only
	STATUS	mandatory
	DESCRIPTION	"The number of coding violations encountered by a Sonet path."
	::= { miboc3AtmLineStatusEntry 64 }

    oc3AtmLineStatus-PerformanceMonitoring-SonetPathUnavailableSeconds	OBJECT-TYPE
	SYNTAX	INTEGER
	ACCESS	read-only
	STATUS	mandatory
	DESCRIPTION	"The number of unavailable seconds encountered by a Sonet path."
	::= { miboc3AtmLineStatusEntry 65 }

    oc3AtmLineStatus-PerformanceMonitoring-SonetFarEndPathErroredSeconds	OBJECT-TYPE
	SYNTAX	INTEGER
	ACCESS	read-only
	STATUS	mandatory
	DESCRIPTION	"The number of far end errored seconds encountered by a Sonet path."
	::= { miboc3AtmLineStatusEntry 66 }

    oc3AtmLineStatus-PerformanceMonitoring-SonetFarEndPathSeverelyErroredSeconds	OBJECT-TYPE
	SYNTAX	INTEGER
	ACCESS	read-only
	STATUS	mandatory
	DESCRIPTION	"The number of far end severely errored seconds encountered by a Sonet path."
	::= { miboc3AtmLineStatusEntry 67 }

    oc3AtmLineStatus-PerformanceMonitoring-SonetFarEndPathCodingViolations	OBJECT-TYPE
	SYNTAX	INTEGER
	ACCESS	read-only
	STATUS	mandatory
	DESCRIPTION	"The number of far end coding violations encountered by a Sonet path."
	::= { miboc3AtmLineStatusEntry 68 }

    oc3AtmLineStatus-PerformanceMonitoring-SonetFarEndPathUnavailableSeconds	OBJECT-TYPE
	SYNTAX	INTEGER
	ACCESS	read-only
	STATUS	mandatory
	DESCRIPTION	"The number of far end unavailable seconds encountered by a Sonet path."
	::= { miboc3AtmLineStatusEntry 69 }

    oc3AtmLineStatus-Action-o	OBJECT-TYPE
	SYNTAX	INTEGER {
		    noAction (1),
		    createProfile (2),
		    deleteProfile (3)
		}
	ACCESS	read-write
	STATUS	mandatory
	DESCRIPTION	""
	::= { miboc3AtmLineStatusEntry 70 }


	-- The miboc3AtmLineStatus__interval_performance_monitoring table
	--
	-- This table contains parameters for the miboc3AtmLineStatus__interval_performance_monitoring profile
	--

    miboc3AtmLineStatus-IntervalPerformanceMonitoringTable	OBJECT-TYPE
	SYNTAX		SEQUENCE OF Miboc3AtmLineStatus-IntervalPerformanceMonitoringEntry
	ACCESS		not-accessible
	STATUS		mandatory
	DESCRIPTION	"A list of miboc3AtmLineStatus__interval_performance_monitoring profile entries."
	::= { miboc3AtmLineStatus 2 }

    miboc3AtmLineStatus-IntervalPerformanceMonitoringEntry	OBJECT-TYPE
	SYNTAX		Miboc3AtmLineStatus-IntervalPerformanceMonitoringEntry
	ACCESS		not-accessible
	STATUS		mandatory
	DESCRIPTION	"A miboc3AtmLineStatus__interval_performance_monitoring entry containing objects that
			 maps to the parameters of miboc3AtmLineStatus__interval_performance_monitoring profile."
	INDEX		{ oc3AtmLineStatus-IntervalPerformanceMonitoring-Shelf-o, oc3AtmLineStatus-IntervalPerformanceMonitoring-Slot-o, oc3AtmLineStatus-IntervalPerformanceMonitoring-Item-o, oc3AtmLineStatus-IntervalPerformanceMonitoring-Index-o }
	::= { miboc3AtmLineStatus-IntervalPerformanceMonitoringTable 1 }

    Miboc3AtmLineStatus-IntervalPerformanceMonitoringEntry ::=
	SEQUENCE {
	    oc3AtmLineStatus-IntervalPerformanceMonitoring-Shelf-o
		INTEGER,
	    oc3AtmLineStatus-IntervalPerformanceMonitoring-Slot-o
		INTEGER,
	    oc3AtmLineStatus-IntervalPerformanceMonitoring-Item-o
		INTEGER,
	    oc3AtmLineStatus-IntervalPerformanceMonitoring-Index-o
		INTEGER,
	    oc3AtmLineStatus-IntervalPerformanceMonitoring-SonetSectionErroredSeconds
		INTEGER,
	    oc3AtmLineStatus-IntervalPerformanceMonitoring-SonetSectionSeverelyErroredSeconds
		INTEGER,
	    oc3AtmLineStatus-IntervalPerformanceMonitoring-SonetSectionSeverelyErroredFramingSeconds
		INTEGER,
	    oc3AtmLineStatus-IntervalPerformanceMonitoring-SonetSectionCodingViolations
		INTEGER,
	    oc3AtmLineStatus-IntervalPerformanceMonitoring-SonetLineErroredSeconds
		INTEGER,
	    oc3AtmLineStatus-IntervalPerformanceMonitoring-SonetLineSeverelyErroredSeconds
		INTEGER,
	    oc3AtmLineStatus-IntervalPerformanceMonitoring-SonetLineCodingViolations
		INTEGER,
	    oc3AtmLineStatus-IntervalPerformanceMonitoring-SonetLineUnavailableSeconds
		INTEGER,
	    oc3AtmLineStatus-IntervalPerformanceMonitoring-SonetFarEndLineErroredSeconds
		INTEGER,
	    oc3AtmLineStatus-IntervalPerformanceMonitoring-SonetFarEndLineSeverelyErroredSeconds
		INTEGER,
	    oc3AtmLineStatus-IntervalPerformanceMonitoring-SonetFarEndLineCodingViolations
		INTEGER,
	    oc3AtmLineStatus-IntervalPerformanceMonitoring-SonetFarEndLineUnavailableSeconds
		INTEGER,
	    oc3AtmLineStatus-IntervalPerformanceMonitoring-SonetPathErroredSeconds
		INTEGER,
	    oc3AtmLineStatus-IntervalPerformanceMonitoring-SonetPathSeverelyErroredSeconds
		INTEGER,
	    oc3AtmLineStatus-IntervalPerformanceMonitoring-SonetPathCodingViolations
		INTEGER,
	    oc3AtmLineStatus-IntervalPerformanceMonitoring-SonetPathUnavailableSeconds
		INTEGER,
	    oc3AtmLineStatus-IntervalPerformanceMonitoring-SonetFarEndPathErroredSeconds
		INTEGER,
	    oc3AtmLineStatus-IntervalPerformanceMonitoring-SonetFarEndPathSeverelyErroredSeconds
		INTEGER,
	    oc3AtmLineStatus-IntervalPerformanceMonitoring-SonetFarEndPathCodingViolations
		INTEGER,
	    oc3AtmLineStatus-IntervalPerformanceMonitoring-SonetFarEndPathUnavailableSeconds
		INTEGER
	}

    oc3AtmLineStatus-IntervalPerformanceMonitoring-Shelf-o	OBJECT-TYPE
	SYNTAX	INTEGER
	ACCESS	read-only
	STATUS	mandatory
	DESCRIPTION	""
	::= { miboc3AtmLineStatus-IntervalPerformanceMonitoringEntry 1 }

    oc3AtmLineStatus-IntervalPerformanceMonitoring-Slot-o	OBJECT-TYPE
	SYNTAX	INTEGER
	ACCESS	read-only
	STATUS	mandatory
	DESCRIPTION	""
	::= { miboc3AtmLineStatus-IntervalPerformanceMonitoringEntry 2 }

    oc3AtmLineStatus-IntervalPerformanceMonitoring-Item-o	OBJECT-TYPE
	SYNTAX	INTEGER
	ACCESS	read-only
	STATUS	mandatory
	DESCRIPTION	""
	::= { miboc3AtmLineStatus-IntervalPerformanceMonitoringEntry 3 }

    oc3AtmLineStatus-IntervalPerformanceMonitoring-Index-o	OBJECT-TYPE
	SYNTAX	INTEGER
	ACCESS	read-only
	STATUS	mandatory
	DESCRIPTION	""
	::= { miboc3AtmLineStatus-IntervalPerformanceMonitoringEntry 4 }

    oc3AtmLineStatus-IntervalPerformanceMonitoring-SonetSectionErroredSeconds	OBJECT-TYPE
	SYNTAX	INTEGER
	ACCESS	read-only
	STATUS	mandatory
	DESCRIPTION	"The number of errored seconds encountered by a Sonet section."
	::= { miboc3AtmLineStatus-IntervalPerformanceMonitoringEntry 5 }

    oc3AtmLineStatus-IntervalPerformanceMonitoring-SonetSectionSeverelyErroredSeconds	OBJECT-TYPE
	SYNTAX	INTEGER
	ACCESS	read-only
	STATUS	mandatory
	DESCRIPTION	"The number of severely errored seconds encountered by a Sonet section."
	::= { miboc3AtmLineStatus-IntervalPerformanceMonitoringEntry 6 }

    oc3AtmLineStatus-IntervalPerformanceMonitoring-SonetSectionSeverelyErroredFramingSeconds	OBJECT-TYPE
	SYNTAX	INTEGER
	ACCESS	read-only
	STATUS	mandatory
	DESCRIPTION	"The number of severely errored framing seconds encountered by a Sonet section."
	::= { miboc3AtmLineStatus-IntervalPerformanceMonitoringEntry 7 }

    oc3AtmLineStatus-IntervalPerformanceMonitoring-SonetSectionCodingViolations	OBJECT-TYPE
	SYNTAX	INTEGER
	ACCESS	read-only
	STATUS	mandatory
	DESCRIPTION	"The number of coding violations encountered by a Sonet section."
	::= { miboc3AtmLineStatus-IntervalPerformanceMonitoringEntry 8 }

    oc3AtmLineStatus-IntervalPerformanceMonitoring-SonetLineErroredSeconds	OBJECT-TYPE
	SYNTAX	INTEGER
	ACCESS	read-only
	STATUS	mandatory
	DESCRIPTION	"The number of errored seconds encountered by a Sonet line."
	::= { miboc3AtmLineStatus-IntervalPerformanceMonitoringEntry 9 }

    oc3AtmLineStatus-IntervalPerformanceMonitoring-SonetLineSeverelyErroredSeconds	OBJECT-TYPE
	SYNTAX	INTEGER
	ACCESS	read-only
	STATUS	mandatory
	DESCRIPTION	"The number of severely errored seconds encountered by a Sonet line."
	::= { miboc3AtmLineStatus-IntervalPerformanceMonitoringEntry 10 }

    oc3AtmLineStatus-IntervalPerformanceMonitoring-SonetLineCodingViolations	OBJECT-TYPE
	SYNTAX	INTEGER
	ACCESS	read-only
	STATUS	mandatory
	DESCRIPTION	"The number of coding violations encountered by a Sonet line."
	::= { miboc3AtmLineStatus-IntervalPerformanceMonitoringEntry 11 }

    oc3AtmLineStatus-IntervalPerformanceMonitoring-SonetLineUnavailableSeconds	OBJECT-TYPE
	SYNTAX	INTEGER
	ACCESS	read-only
	STATUS	mandatory
	DESCRIPTION	"The number of unavailable seconds encountered by a Sonet line."
	::= { miboc3AtmLineStatus-IntervalPerformanceMonitoringEntry 12 }

    oc3AtmLineStatus-IntervalPerformanceMonitoring-SonetFarEndLineErroredSeconds	OBJECT-TYPE
	SYNTAX	INTEGER
	ACCESS	read-only
	STATUS	mandatory
	DESCRIPTION	"The number of far end errored seconds encountered by a Sonet line."
	::= { miboc3AtmLineStatus-IntervalPerformanceMonitoringEntry 13 }

    oc3AtmLineStatus-IntervalPerformanceMonitoring-SonetFarEndLineSeverelyErroredSeconds	OBJECT-TYPE
	SYNTAX	INTEGER
	ACCESS	read-only
	STATUS	mandatory
	DESCRIPTION	"The number of far end severely errored seconds encountered by a Sonet line."
	::= { miboc3AtmLineStatus-IntervalPerformanceMonitoringEntry 14 }

    oc3AtmLineStatus-IntervalPerformanceMonitoring-SonetFarEndLineCodingViolations	OBJECT-TYPE
	SYNTAX	INTEGER
	ACCESS	read-only
	STATUS	mandatory
	DESCRIPTION	"The number of far end coding violations encountered by a Sonet line."
	::= { miboc3AtmLineStatus-IntervalPerformanceMonitoringEntry 15 }

    oc3AtmLineStatus-IntervalPerformanceMonitoring-SonetFarEndLineUnavailableSeconds	OBJECT-TYPE
	SYNTAX	INTEGER
	ACCESS	read-only
	STATUS	mandatory
	DESCRIPTION	"The number of far end unavailable seconds encountered by a Sonet line."
	::= { miboc3AtmLineStatus-IntervalPerformanceMonitoringEntry 16 }

    oc3AtmLineStatus-IntervalPerformanceMonitoring-SonetPathErroredSeconds	OBJECT-TYPE
	SYNTAX	INTEGER
	ACCESS	read-only
	STATUS	mandatory
	DESCRIPTION	"The number of errored seconds encountered by a Sonet path."
	::= { miboc3AtmLineStatus-IntervalPerformanceMonitoringEntry 17 }

    oc3AtmLineStatus-IntervalPerformanceMonitoring-SonetPathSeverelyErroredSeconds	OBJECT-TYPE
	SYNTAX	INTEGER
	ACCESS	read-only
	STATUS	mandatory
	DESCRIPTION	"The number of severely errored seconds encountered by a Sonet path."
	::= { miboc3AtmLineStatus-IntervalPerformanceMonitoringEntry 18 }

    oc3AtmLineStatus-IntervalPerformanceMonitoring-SonetPathCodingViolations	OBJECT-TYPE
	SYNTAX	INTEGER
	ACCESS	read-only
	STATUS	mandatory
	DESCRIPTION	"The number of coding violations encountered by a Sonet path."
	::= { miboc3AtmLineStatus-IntervalPerformanceMonitoringEntry 19 }

    oc3AtmLineStatus-IntervalPerformanceMonitoring-SonetPathUnavailableSeconds	OBJECT-TYPE
	SYNTAX	INTEGER
	ACCESS	read-only
	STATUS	mandatory
	DESCRIPTION	"The number of unavailable seconds encountered by a Sonet path."
	::= { miboc3AtmLineStatus-IntervalPerformanceMonitoringEntry 20 }

    oc3AtmLineStatus-IntervalPerformanceMonitoring-SonetFarEndPathErroredSeconds	OBJECT-TYPE
	SYNTAX	INTEGER
	ACCESS	read-only
	STATUS	mandatory
	DESCRIPTION	"The number of far end errored seconds encountered by a Sonet path."
	::= { miboc3AtmLineStatus-IntervalPerformanceMonitoringEntry 21 }

    oc3AtmLineStatus-IntervalPerformanceMonitoring-SonetFarEndPathSeverelyErroredSeconds	OBJECT-TYPE
	SYNTAX	INTEGER
	ACCESS	read-only
	STATUS	mandatory
	DESCRIPTION	"The number of far end severely errored seconds encountered by a Sonet path."
	::= { miboc3AtmLineStatus-IntervalPerformanceMonitoringEntry 22 }

    oc3AtmLineStatus-IntervalPerformanceMonitoring-SonetFarEndPathCodingViolations	OBJECT-TYPE
	SYNTAX	INTEGER
	ACCESS	read-only
	STATUS	mandatory
	DESCRIPTION	"The number of far end coding violations encountered by a Sonet path."
	::= { miboc3AtmLineStatus-IntervalPerformanceMonitoringEntry 23 }

    oc3AtmLineStatus-IntervalPerformanceMonitoring-SonetFarEndPathUnavailableSeconds	OBJECT-TYPE
	SYNTAX	INTEGER
	ACCESS	read-only
	STATUS	mandatory
	DESCRIPTION	"The number of far end unavailable seconds encountered by a Sonet path."
	::= { miboc3AtmLineStatus-IntervalPerformanceMonitoringEntry 24 }

END
