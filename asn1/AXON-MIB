-- ======================================================================
--
--  3Com Corporation
--  80 Central Street
--  Boxborough, MA 01719
--  (978) 264-1400
--
--  Change History:
--
----------------------------------------------------------------------------------------
--
--  10/07/98 - tmeiczin	moved location
--  09/24/98 - tmeiczin Added to 3com Mibs
--                      renamed from fddiRmon.mib
--
----------------------------------------------------------------------------------------

-- ======================================================================

AXON-MIB DEFINITIONS ::= BEGIN
--

              IMPORTS
                  TimeTicks,
                  Counter                FROM RFC1155-SMI
                  OBJECT-TYPE            FROM RFC-1212
              ;

            org           OBJECT IDENTIFIER ::= { iso 3 }
            dod           OBJECT IDENTIFIER ::= { org 6 }
            internet      OBJECT IDENTIFIER ::= { dod 1 }
            directory     OBJECT IDENTIFIER ::= { internet 1 }
            mgmt          OBJECT IDENTIFIER ::= { internet 2 }
            experimental  OBJECT IDENTIFIER ::= { internet 3 }
            private       OBJECT IDENTIFIER ::= { internet 4 }
            enterprises   OBJECT IDENTIFIER ::= { private 1 }

            mib-2         OBJECT IDENTIFIER ::= { mgmt 1 }

--  Axon's nodes in the enterprises MIB
    axon         OBJECT IDENTIFIER ::= { enterprises 370 }

    clone        OBJECT IDENTIFIER ::= { axon 1 }

    product      OBJECT IDENTIFIER ::= { axon 2 }
    common       OBJECT IDENTIFIER ::= { product 1 }
    
    application  OBJECT IDENTIFIER ::= { axon 3 }

--  Axon FDDI specifics
    axFddi      OBJECT IDENTIFIER ::= { axon 4 }

          axFddiStatistics        OBJECT IDENTIFIER ::= { axFddi 1 }
          axFddiHistory           OBJECT IDENTIFIER ::= { axFddi 2 }

          -- The Statistics Group
          --
          -- The statistics group is based etherStats.
          --
          -- (The packet size distribution counters incorparate sizes from
          -- the tokenRingPStats with those found in etherStats.)
          --
          -- The statistics group contains statistics measured by the
          -- probe for each monitored interface on this device.  These
          -- statistics take the form of free running counters that
          -- start from zero when a valid entry is created.
          --
          -- This group contains has statistics defined only for
          -- FDDI interfaces.  Each fddiStatsEntry contains
          -- statistics for one FDDI interface.  The probe must
          -- create one fddiStats entry for each monitored FDDI
          -- interface on the device.

          fddiStatsTable OBJECT-TYPE
              SYNTAX SEQUENCE OF FddiStatsEntry
              ACCESS not-accessible
              STATUS mandatory
			  DESCRIPTION
					"A list of promiscuous FDDI statistics entries"
              ::= { axFddiStatistics 1 }

          fddiStatsEntry OBJECT-TYPE
              SYNTAX FddiStatsEntry
              ACCESS not-accessible
              STATUS mandatory
			  DESCRIPTION
                      "A collection of promiscuous statistics kept for
                       packets on a particular FDDI interface."
              INDEX { fddiStatsIndex }
              ::= { fddiStatsTable 1 }

          -- As an example, an instance of the
          -- fddiStatsOctets object
          -- might be named fddiStatsOctets.1

          FddiStatsEntry ::= SEQUENCE {
              fddiStatsIndex                    INTEGER (1..65535),
              fddiStatsDataSource               OBJECT IDENTIFIER,
              fddiStatsDropEvents               Counter,
              fddiStatsOctets                   Counter,
              fddiStatsPkts                     Counter,
              fddiStatsBroadcastPkts            Counter,
              fddiStatsMulticastPkts            Counter,
              fddiStatsErrors                   Counter,
              fddiStatsPkts22Octets             Counter,
              fddiStatsPkts23to63Octets         Counter,
              fddiStatsPkts64to127Octets        Counter,
              fddiStatsPkts128to255Octets       Counter,
              fddiStatsPkts256to511Octets       Counter,
              fddiStatsPkts512to1023Octets      Counter,
              fddiStatsPkts1024to2047Octets     Counter,
              fddiStatsPkts2048to4095Octets     Counter,
              fddiStatsPkts4096to4500Octets     Counter,
              fddiStatsTNEG                     Counter,
              fddiStatsTokens                   Counter,
              fddiStatsSMTs                     Counter,
              fddiStatsClaims                   Counter,
              fddiStatsDirBeacons               Counter,
              fddiStatsBeacons                  Counter,
              fddiStatsBeaconAddr               OCTET STRING,
              fddiStatsDirBeaconAddr            OCTET STRING,
              fddiStatsClaimAddr                OCTET STRING,
              fddiStatsRingState                INTEGER,
              fddiStatsOwner                    OCTET STRING,
              fddiStatsStatus                   INTEGER,
              fddiStatsOtherPkts                Counter,
              fddiStatsOtherOctets              Counter
          }

          fddiStatsIndex OBJECT-TYPE
              SYNTAX INTEGER (1..65535)
              ACCESS read-only
              STATUS mandatory
              DESCRIPTION
                  "The value of this object uniquely identifies this
                   fddiStats entry."
              ::= { fddiStatsEntry 1 }

          fddiStatsDataSource OBJECT-TYPE
              SYNTAX OBJECT IDENTIFIER
              ACCESS read-write
              STATUS mandatory
              DESCRIPTION
                  "This object identifies the source of the data
                   that this fddiStats entry is configured to
                   analyze.  This source can be any FDDI
                   interface on this device.  In order to identify a
                   particular interface, this object shall identify
                   the instance of the ifIndex object, defined in
                   RFC 1213 and RFC 1573 [4,6], for the desired
                   interface.  For example, if an entry were to
                   receive data from interface #1, this object would
                   be set to ifIndex.1.

                   The statistics in this group reflect all
                   packets on the local network segment attached to
                   the identified interface.

                   This object may not be modified if the associated
                   fddiStatsStatus object is equal to
                   valid(1)."
              ::= { fddiStatsEntry 2 }

          fddiStatsDropEvents OBJECT-TYPE
              SYNTAX Counter
              ACCESS read-only
              STATUS mandatory
              DESCRIPTION
                  "The total number of events in which packets were
                   dropped by the probe due to lack of resources.
                   Note that this number is not necessarily the
                   number of packets dropped; it is just the number
                   of times this condition has been detected."
              ::= { fddiStatsEntry 3 }

          fddiStatsOctets OBJECT-TYPE
              SYNTAX Counter
              ACCESS read-only
              STATUS mandatory
              DESCRIPTION
                  "The total number of octets of LLC data
                   (including those in bad packets) received on the
                   network (excluding framing bits but including
                   FCS octets)."
              ::= { fddiStatsEntry 4 }

          fddiStatsPkts OBJECT-TYPE
              SYNTAX Counter
              ACCESS read-only
              STATUS mandatory
              DESCRIPTION
                  "The total number of LLC packets (including bad
                   packets, broadcast packets, and multicast packets)
                   received."
              ::= { fddiStatsEntry 5 }

          fddiStatsBroadcastPkts OBJECT-TYPE
              SYNTAX Counter
              ACCESS read-only
              STATUS mandatory
              DESCRIPTION
                  "The total number of packets received
                   that were directed to the broadcast address
                   (0xFFFFFFFFFFFF).  Note that this
                   does not include multicast packets."
              ::= { fddiStatsEntry 6 }

          fddiStatsMulticastPkts OBJECT-TYPE
              SYNTAX Counter
              ACCESS read-only
              STATUS mandatory
              DESCRIPTION
                  "The total number of packets received
                   that were directed to a local or global multicast
                   or functional address.  Note that this number does
                   not include packets directed to the broadcast
                   address."
              ::= { fddiStatsEntry 7 }

          fddiStatsErrors OBJECT-TYPE
              SYNTAX Counter
              ACCESS read-only
              STATUS mandatory
              DESCRIPTION
                  "The total number of packets received that had
                   either a bad Frame Check Sequence (FCS) or a
                   invalid data length. A packet with a invalid data
                   length is one that is too short (length less than
                   21 octets / 42 symbols) or had an odd number of
                   symbols."
              ::= { fddiStatsEntry 8 }

          fddiStatsPkts22Octets OBJECT-TYPE
              SYNTAX Counter
              ACCESS read-only
              STATUS mandatory
              DESCRIPTION
                  "The total number of good packets received
                   that were 22 octets, or less, in length
                   (excluding framing bits but including FCS octets)."
              ::= { fddiStatsEntry 9 }

          fddiStatsPkts23to63Octets OBJECT-TYPE
              SYNTAX Counter
              ACCESS read-only
              STATUS mandatory
              DESCRIPTION
                  "The total number of good packets received that
                   were between 23 and 63 octets in length inclusive
                   (excluding framing bits but including FCS octets)."
              ::= { fddiStatsEntry 10 }

          fddiStatsPkts64to127Octets OBJECT-TYPE
              SYNTAX Counter
              ACCESS read-only
              STATUS mandatory
              DESCRIPTION
                  "The total number of good packets received that
                   were between 64 and 127 octets in length inclusive
                   (excluding framing bits but including FCS octets)."
              ::= { fddiStatsEntry 11 }

          fddiStatsPkts128to255Octets OBJECT-TYPE
              SYNTAX Counter
              ACCESS read-only
              STATUS mandatory
              DESCRIPTION
                  "The total number of good packets received that
                   were between 128 and 255 octets in length inclusive
                   (excluding framing bits but including FCS octets)."
              ::= { fddiStatsEntry 12 }

          fddiStatsPkts256to511Octets OBJECT-TYPE
              SYNTAX Counter
              ACCESS read-only
              STATUS mandatory
              DESCRIPTION
                  "The total number of good packets received that
                   were between 256 and 511 octets in length inclusive
                   (excluding framing bits but including FCS octets)."
              ::= { fddiStatsEntry 13 }

          fddiStatsPkts512to1023Octets OBJECT-TYPE
              SYNTAX Counter
              ACCESS read-only
              STATUS mandatory
              DESCRIPTION
                  "The total number of good packets received that
                   were between 512 and 1023 octets in length inclusive
                   (excluding framing bits but including FCS octets)."
              ::= { fddiStatsEntry 14 }


          fddiStatsPkts1024to2047Octets OBJECT-TYPE
              SYNTAX Counter
              ACCESS read-only
              STATUS mandatory
              DESCRIPTION
                  "The total number of good packets received that
                   were between 1024 and 2047 octets in length inclusive
                   (excluding framing bits but including FCS octets)."
              ::= { fddiStatsEntry 15 }

          fddiStatsPkts2048to4095Octets     OBJECT-TYPE
              SYNTAX Counter
              ACCESS read-only
              STATUS mandatory
              DESCRIPTION
                  "The total number of good packets received that
                   were between 2048 and 4095 octets in length inclusive
                   (excluding framing bits but including FCS octets)."
              ::= { fddiStatsEntry 16 }

          fddiStatsPkts4096to4500Octets     OBJECT-TYPE
              SYNTAX Counter
              ACCESS read-only
              STATUS mandatory
              DESCRIPTION
                  "The total number of good packets received that
                   were between 4096 and 4500 octets in length inclusive
                   (excluding framing bits but including FCS octets)."
              ::= { fddiStatsEntry 17 }

          fddiStatsTNEG OBJECT-TYPE
              SYNTAX Counter
              ACCESS read-only
              STATUS mandatory
              DESCRIPTION
                  "The Negotiated Token Rotation Time, TNeg, in
                   nano-seconds"
              ::= { fddiStatsEntry 18 }

          fddiStatsTokens OBJECT-TYPE
              SYNTAX Counter
              ACCESS read-only
              STATUS mandatory
              DESCRIPTION
                  "The number of valid tokens received"
              ::= { fddiStatsEntry 19 }

          fddiStatsSMTs OBJECT-TYPE
              SYNTAX Counter
              ACCESS read-only
              STATUS mandatory
              DESCRIPTION
                  "The number of SMT frames received"
              ::= { fddiStatsEntry 20 }

          fddiStatsClaims OBJECT-TYPE
              SYNTAX Counter
              ACCESS read-only
              STATUS mandatory
              DESCRIPTION
                  "The number of Claim frames received"
              ::= { fddiStatsEntry 21 }

          fddiStatsDirBeacons OBJECT-TYPE
              SYNTAX Counter
              ACCESS read-only
              STATUS mandatory
              DESCRIPTION
                  "The number of Directed Beacon frames
                   received.  Directed Beacon frames have an FC field
                   of 0xC2, a Destination Address of
                   non-canonical: 80:01:43:00:80:00,
                   canonical: 01:80:C2:00:01:00,
                   a Source Address of this station, and a info field
                   of 0x01 (Beacon Type) + pad field (0x000000)."
              ::= { fddiStatsEntry 22 }

          fddiStatsBeacons OBJECT-TYPE
              SYNTAX Counter
              ACCESS read-only
              STATUS mandatory
              DESCRIPTION
                  "The number of MAC Beacon frames
                   received.  MAC Beacon frames have an FC field
                   of 0xC2, a Destination Address of the null address
                   a Source Address of this station, and a info field
                   of 0x00 (Beacon Type) + pad field (0x000000)."
              ::= { fddiStatsEntry 23 }

          fddiStatsBeaconAddr OBJECT-TYPE
              SYNTAX OCTET STRING
              ACCESS read-only
              STATUS mandatory
              DESCRIPTION
                  "The MAC address of the last station to send a Beacon
                   Frame"
              ::= { fddiStatsEntry 24 }

          fddiStatsDirBeaconAddr OBJECT-TYPE
              SYNTAX OCTET STRING
              ACCESS read-only
              STATUS mandatory
              DESCRIPTION
                  "The MAC address of the last station to send a
                   Directed Beacon Frame"
              ::= { fddiStatsEntry 25 }

          fddiStatsClaimAddr OBJECT-TYPE
              SYNTAX OCTET STRING
              ACCESS read-only
              STATUS mandatory
              DESCRIPTION
                  "The MAC address of the last station to send a Claim
                   Frame"
              ::= { fddiStatsEntry 26 }

          fddiStatsRingState OBJECT-TYPE
              SYNTAX INTEGER 
              ACCESS read-only
              STATUS mandatory
              DESCRIPTION
                  "The current detected state of the ring.
                    1 Operational
                    2 Non Operational Claim
                    3 Non Operational Beacon
                    4 Non Operational Dir. Beacon"
              ::= { fddiStatsEntry 27 }

          fddiStatsOwner OBJECT-TYPE
              SYNTAX OCTET STRING 
              ACCESS read-write
              STATUS mandatory
			  DESCRIPTION
                  "The entity that configured this entry and is
                  therefore using the resources assigned to it."
              ::= { fddiStatsEntry 28 }

          fddiStatsStatus OBJECT-TYPE
              SYNTAX INTEGER
              ACCESS read-write
              STATUS mandatory
			  DESCRIPTION
                  "The status of this fddiStats entry."

              ::= { fddiStatsEntry 29 }

		  fddiStatsOtherPkts OBJECT-TYPE
			  SYNTAX Counter
			  ACCESS read-only
			  STATUS mandatory
		      DESCRIPTION
                  "The total number of other packets (including bad
                   packets, broadcast packets, and multicast packets)
                   received.  Other packets which are packets which
                   are not LLC, SMT or recognized MAC beacon packets."
			  ::= { fddiStatsEntry 30 }

		  fddiStatsOtherOctets OBJECT-TYPE
			  SYNTAX Counter
			  ACCESS read-only
			  STATUS mandatory
		      DESCRIPTION
                  "The total number of other octets (including those
                   in bad packets) received on the network
                   (excluding framing bits but including FCS
                   octets).  Other octets are those from packets which
                   are packets which are not LLC, SMT or recognized
                   MAC beacon packets."
			  ::= { fddiStatsEntry 31 }


          -- The History Group

          -- The History group is based on etherHistory.
          -- It uses the existing historyControlTable table.
          --
          -- The history group records periodic statistical samples from
          -- a network and stores them for later retrieval.  The
          -- historyControl table stores configuration entries that each
          -- define an interface, polling period, and other parameters.
          -- Once samples are taken, their data is stored in an entry
          -- in a media-specific table.  Each such entry defines one
          -- sample, and is associated with the historyControlEntry that
          -- caused the sample to be taken.  
          --
          -- If the probe keeps track of the time of day, it should
          -- start the first sample of the history at a time such that
          -- when the next hour of the day begins, a sample is
          -- started at that instant.  This tends to make more
          -- user-friendly reports, and enables comparison of reports
          -- from different probes that have relatively accurate time
          -- of day.
          --
          -- The monitor is encouraged to add two history control entries
          -- per monitored interface upon initialization that describe
          -- a short term and a long term polling period.  Suggested
          -- parameters are 30 seconds for the short term polling
          -- period and 30 minutes for the long term period.

          -- Fddi History table

          -- Implementation of the FDDI History group is optional.
          --
          -- The FDDI History group records periodic
          -- statistical samples from a network and stores them
          -- for later retrieval.  Once samples are taken, their
          -- data is stored in an entry in a media-specific
          -- table.  Each such entry defines one sample, and is
          -- associated with the historyControlEntry that caused
          -- the sample to be taken.  This group defines the
          -- fddiHistoryTable, for FDDI networks.
          --

          fddiHistoryTable OBJECT-TYPE
              SYNTAX SEQUENCE OF FddiHistoryEntry
              ACCESS not-accessible
              STATUS mandatory
			  DESCRIPTION
                  "A list of FDDI history entries."
              ::= { axFddiHistory 5 }

          fddiHistoryEntry OBJECT-TYPE
              SYNTAX FddiHistoryEntry
              ACCESS not-accessible
              STATUS mandatory
			  DESCRIPTION
                  "An historical sample of FDDI statistics on a
                  particular FDDI interface.  This sample is
                  associated with the historyControlEntry which set up
                  the parameters for a regular collection of these
                  samples.  As an example, an instance of the
                  fddiHistoryPkts object might be named
                  fddiHistoryPkts.2.89"
              INDEX { fddiHistoryIndex , fddiHistorySampleIndex }
              ::= { fddiHistoryTable 1 }

          FddiHistoryEntry ::= SEQUENCE {
              fddiHistoryIndex                    INTEGER (1..65535),
              fddiHistorySampleIndex              INTEGER (1..2147483647),
              fddiHistoryIntervalStart            TimeTicks,
              fddiHistoryDropEvents               Counter,
              fddiHistoryOctets                   Counter,
              fddiHistoryPkts                     Counter,
              fddiHistoryBroadcastPkts            Counter,
              fddiHistoryMulticastPkts            Counter,
              fddiHistoryErrors                   Counter,
              fddiHistoryPkts22Octets             Counter,
              fddiHistoryPkts23to63Octets         Counter,
              fddiHistoryPkts64to127Octets        Counter,
              fddiHistoryPkts128to255Octets       Counter,
              fddiHistoryPkts256to511Octets       Counter,
              fddiHistoryPkts512to1023Octets      Counter,
              fddiHistoryPkts1024to2047Octets     Counter,
              fddiHistoryPkts2048to4095Octets     Counter,
              fddiHistoryPkts4096to4500Octets     Counter,
              fddiHistoryUtilization              INTEGER (0..10000),
              fddiHistoryTNEG                     Counter,
			  fddiHistoryMeanTRT				  Counter,
			  fddiHistorySMTs				      Counter,
			  fddiHistoryClaims                   Counter,
			  fddiHistoryDirBeacons			      Counter,
			  fddiHistoryBeacons				  Counter,
              fddiHistoryRingStateChanges         Counter
          }

          fddiHistoryIndex OBJECT-TYPE
              SYNTAX INTEGER (1..65535)
              ACCESS read-only
              STATUS mandatory
			  DESCRIPTION
                  "The history of which this entry is a part.  The
                  history identified by a particular value of this
                  index is the same history as identified
                  by the same value of historyControlIndex."
              ::= { fddiHistoryEntry 1 }

          fddiHistorySampleIndex OBJECT-TYPE
              SYNTAX INTEGER
              ACCESS read-only
              STATUS mandatory
			  DESCRIPTION
                  "An index that uniquely identifies the particular
                  sample this entry represents among all samples
                  associated with the same historyControlEntry.
                  This index starts at 1 and increases by one
                  as each new sample is taken."
              ::= { fddiHistoryEntry 2 }

          fddiHistoryIntervalStart OBJECT-TYPE
              SYNTAX TimeTicks
              ACCESS read-only
              STATUS mandatory
			  DESCRIPTION
                  "The value of sysUpTime at the start of the interval
                  over which this sample was measured.  If the probe
                  keeps track of the time of day, it should start
                  the first sample of the history at a time such that
                  when the next hour of the day begins, a sample is
                  started at that instant.  Note that following this
                  rule may require the probe to delay collecting the
                  first sample of the history, as each sample must be
                  of the same interval.  Also note that the sample which
                  is currently being collected is not accessible in this
                  table until the end of its interval."
              ::= { fddiHistoryEntry 3 }

          fddiHistoryDropEvents OBJECT-TYPE
              SYNTAX Counter
              ACCESS read-only
              STATUS mandatory
			  DESCRIPTION
                  "The total number of events in which packets
                  were dropped by the probe due to lack of resources
                  during this sampling interval.  Note that this number
                  is not necessarily the number of packets dropped, it
                  is just the number of times this condition has been
                  detected."
              ::= { fddiHistoryEntry 4 }

          fddiHistoryOctets OBJECT-TYPE
              SYNTAX Counter
              ACCESS read-only
              STATUS mandatory
			  DESCRIPTION
                  "The total number of octets of LLC data
                   (including those in bad packets) received on the
                   network (excluding framing bits but including
                   FCS octets) during this sampling interval."
              ::= { fddiHistoryEntry 5 }

          fddiHistoryPkts OBJECT-TYPE
              SYNTAX Counter
              ACCESS read-only
              STATUS mandatory
			  DESCRIPTION
                  "The total number of LLC packets (including bad
                   packets, broadcast packets, and multicast packets)
                   received during this sampling interval."
              ::= { fddiHistoryEntry 6 }

          fddiHistoryBroadcastPkts OBJECT-TYPE
              SYNTAX Counter
              ACCESS read-only
              STATUS mandatory
			  DESCRIPTION
                  "The total number of packets received
                   that were directed to the broadcast address
                   (0xFFFFFFFFFFFF) during this sampling
                   interval.  Note that this does not include
                   multicast packets."
              ::= { fddiHistoryEntry 7 }

          fddiHistoryMulticastPkts OBJECT-TYPE
              SYNTAX Counter
              ACCESS read-only
              STATUS mandatory
			  DESCRIPTION
                  "The total number of packets received
                   that were directed to a local or global multicast
                   or functional address during this sampling
                   interval.  Note that this number does not
                   include packets directed to the broadcast address."
              ::= { fddiHistoryEntry 8 }

          fddiHistoryErrors OBJECT-TYPE
              SYNTAX Counter
              ACCESS read-only
              STATUS mandatory
			  DESCRIPTION
                  "The total number of packets received that had
                   either a bad Frame Check Sequence (FCS) or a
                   invalid data length during this sampling
                   interval. A packet with a invalid data
                   length is one that is too short (length less than
                   21 octets / 42 symbols) or had an odd number of
                   symbols."
              ::= { fddiHistoryEntry 9 }

          fddiHistoryPkts22Octets OBJECT-TYPE
              SYNTAX Counter
              ACCESS read-only
              STATUS mandatory
			  DESCRIPTION
                  "The total number of good packets received
                   that were 22 octets, or less, in length
                   (excluding framing bits but including FCS octets)
                   during this sampling interval."
              ::= { fddiHistoryEntry 10 }

          fddiHistoryPkts23to63Octets OBJECT-TYPE
              SYNTAX Counter
              ACCESS read-only
              STATUS mandatory
			  DESCRIPTION
                  "The total number of good packets received that
                   were between 23 and 63 octets in length inclusive
                   (excluding framing bits but including FCS octets)
                   during this sampling interval."

              ::= { fddiHistoryEntry 11 }

          fddiHistoryPkts64to127Octets OBJECT-TYPE
              SYNTAX Counter
              ACCESS read-only
              STATUS mandatory
			  DESCRIPTION
                  "The total number of good packets received that
                   were between 64 and 127 octets in length inclusive
                   (excluding framing bits but including FCS octets)
                   during this sampling interval."

              ::= { fddiHistoryEntry 12 }

          fddiHistoryPkts128to255Octets OBJECT-TYPE
              SYNTAX Counter
              ACCESS read-only
              STATUS mandatory
			  DESCRIPTION
                  "The total number of good packets received that
                   were between 128 and 255 octets in length inclusive
                   (excluding framing bits but including FCS octets)
                   during this sampling interval."

              ::= { fddiHistoryEntry 13 }

          fddiHistoryPkts256to511Octets OBJECT-TYPE
              SYNTAX Counter
              ACCESS read-only
              STATUS mandatory
			  DESCRIPTION
                  "The total number of good packets received that
                   were between 256 and 511 octets in length inclusive
                   (excluding framing bits but including FCS octets)
                   during this sampling interval."

              ::= { fddiHistoryEntry 14 }

          fddiHistoryPkts512to1023Octets OBJECT-TYPE
              SYNTAX Counter
              ACCESS read-only
              STATUS mandatory
			  DESCRIPTION
                  "The total number of good packets received that
                   were between 512 and 1023 octets in length inclusive
                   (excluding framing bits but including FCS octets)
                   during this sampling interval."

              ::= { fddiHistoryEntry 15 }


          fddiHistoryPkts1024to2047Octets OBJECT-TYPE
              SYNTAX Counter
              ACCESS read-only
              STATUS mandatory
			  DESCRIPTION
                  "The total number of good packets received that
                   were between 1024 and 2047 octets in length inclusive
                   (excluding framing bits but including FCS octets)
                   during this sampling interval."

              ::= { fddiHistoryEntry 16 }
 
          fddiHistoryPkts2048to4095Octets     OBJECT-TYPE
              SYNTAX Counter
              ACCESS read-only
              STATUS mandatory
			  DESCRIPTION
                  "The total number of good packets received that
                   were between 2048 and 4095 octets in length inclusive
                   (excluding framing bits but including FCS octets)
                   during this sampling interval."

              ::= { fddiHistoryEntry 17 }

          fddiHistoryPkts4096to4500Octets     OBJECT-TYPE
              SYNTAX Counter
              ACCESS read-only
              STATUS mandatory
			  DESCRIPTION
                  "The total number of good packets received that
                   were between 4096 and 4500 octets in length inclusive
                   (excluding framing bits but including FCS octets)
                   during this sampling interval."

              ::= { fddiHistoryEntry 18 }

          fddiHistoryUtilization OBJECT-TYPE
              SYNTAX INTEGER (0..10000)
              ACCESS read-only
              STATUS mandatory
			  DESCRIPTION
                  "The best estimate of the mean physical layer
                   network utilization on this interface during this
                   sampling interval, in hundredths of a
                   percent.  This is calculated as:

                   utilize = ((bits/s used) * 10000) / (MAX bits/s)
                           = ((bits/ms used) * 10000000) / 100000000
                           = (bits/ms used) / 10
                           = (((pkts * 5) + octets) * 8) / (interval * 10)"
              ::= { fddiHistoryEntry 19 }

          fddiHistoryTNEG OBJECT-TYPE
              SYNTAX Counter
              ACCESS read-only
              STATUS mandatory
              DESCRIPTION
                  "The Negotiated Token Rotation Time, TNeg, in
                   nano-seconds at the end of the sample interval."

              ::= { fddiHistoryEntry 20 }

          fddiHistoryMeanTRT OBJECT-TYPE
              SYNTAX Counter
              ACCESS read-only
              STATUS mandatory
              DESCRIPTION
                  "The Mean token rotation time. This calculated
                   as the tokens received during the sample interval
                   divided by the sample interval."

              ::= { fddiHistoryEntry 21 }

          fddiHistorySMTs OBJECT-TYPE
              SYNTAX Counter
              ACCESS read-only
              STATUS mandatory
              DESCRIPTION
                  "The number of SMT frames received during the
                   sample interval."
              ::= { fddiHistoryEntry 22 }

          fddiHistoryClaims OBJECT-TYPE
              SYNTAX Counter
              ACCESS read-only
              STATUS mandatory
              DESCRIPTION
                  "The number of Claim frames received during the
                   sample interval."
              ::= { fddiHistoryEntry 23 }

          fddiHistoryDirBeacons OBJECT-TYPE
              SYNTAX Counter
              ACCESS read-only
              STATUS mandatory
              DESCRIPTION
                  "The number of Directed Beacon frames
                   received during the sample
                   interval.  Directed Beacon frames have an FC field
                   of 0xC2, a Destination Address of
                   non-canonical: 80:01:43:00:80:00,
                   canonical: 01:80:C2:00:01:00,
                   a Source Address of this station, and a info field
                   of 0x01 (Beacon Type) + pad field (0x000000)."
              ::= { fddiHistoryEntry 24 }

          fddiHistoryBeacons OBJECT-TYPE
              SYNTAX Counter
              ACCESS read-only
              STATUS mandatory
              DESCRIPTION
                  "The number of MAC Beacon frames
                   received during the sample
                   interval.  MAC Beacon frames have an FC field
                   of 0xC2, a Destination Address of the null address
                   a Source Address of this station, and a info field
                   of 0x00 (Beacon Type) + pad field (0x000000)."
              ::= { fddiHistoryEntry 25 }

          fddiHistoryRingStateChanges OBJECT-TYPE
              SYNTAX Counter 
              ACCESS read-only
              STATUS mandatory
              DESCRIPTION
                     "Count of changes of the state of the ring
                      during the sample interval."
              ::= { fddiHistoryEntry 26 }

END
