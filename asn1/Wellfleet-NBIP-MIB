Wellfleet-NBIP-MIB DEFINITIONS ::= BEGIN

-- Created by mdl2asn version 3.1
-- Creation date: Wed Aug 30 16:45:32 EDT 1995


    IMPORTS

      IpAddress, Counter
        FROM RFC1155-SMI
      OBJECT-TYPE
        FROM RFC-1212
      wfNetBIOSIpGroup
        FROM Wellfleet-COMMON-MIB;


    wfNetbiosIp	OBJECT IDENTIFIER ::= { wfNetBIOSIpGroup 1 }

    wfNetbiosIpDelete OBJECT-TYPE
        SYNTAX	INTEGER {
    		    created(1),
    		    deleted(2)
    		}
        ACCESS	read-write
        STATUS	mandatory
        DESCRIPTION
                "Create/Delete parameter. Default is created.
                Users perform an SNMP SET operation on this
                object in order to create/delete the NetBIOS
                over IP support."
        DEFVAL	{ created }
        ::= { wfNetbiosIp 1 }

    wfNetbiosIpDisable OBJECT-TYPE
        SYNTAX	INTEGER {
    		    enabled(1),
    		    disabled(2)
    		}
        ACCESS	read-write
        STATUS	mandatory
        DESCRIPTION
                "Enable/Disable parameter. Default is enabled.
                Users perform an SNMP SET operation on this
                object in order to enable/disable the NetBIOS
                over IP support."
        DEFVAL	{ enabled }
        ::= { wfNetbiosIp 2 }

    wfNetbiosIpState OBJECT-TYPE
        SYNTAX	INTEGER {
    		    up(1),
    		    down(2),
    		    init(3),
    		    notpres(4)
    		}
        ACCESS	read-only
        STATUS	mandatory
        DESCRIPTION
                "The current state of the entire NetBIOS over IP."
        DEFVAL	{ notpres }
        ::= { wfNetbiosIp 3 }

    wfNetbiosIpNameCacheDisable OBJECT-TYPE
        SYNTAX	INTEGER {
    		    enabled(1),
    		    disabled(2)
    		}
        ACCESS	read-write
        STATUS	mandatory
        DESCRIPTION
                "Enable/Disable parameter for the NetBIOS name cache."
        DEFVAL	{ disabled }
        ::= { wfNetbiosIp 4 }

    wfNetbiosIp15CharacterDisable OBJECT-TYPE
        SYNTAX	INTEGER {
    		    enabled(1),
    		    disabled(2)
    		}
        ACCESS	read-write
        STATUS	mandatory
        DESCRIPTION
                "Enable/Disable parameter for 15-character NetBIOS name caching."
        DEFVAL	{ disabled }
        ::= { wfNetbiosIp 5 }

    wfNetbiosIpNameCacheMibDisable OBJECT-TYPE
        SYNTAX	INTEGER {
    		    enabled(1),
    		    disabled(2)
    		}
        ACCESS	read-write
        STATUS	mandatory
        DESCRIPTION
                "Enable/Disable creation of MIB instances for each cached name."
        DEFVAL	{ enabled }
        ::= { wfNetbiosIp 6 }

    wfNetbiosIpNameCacheMaximumEntries OBJECT-TYPE
        SYNTAX	INTEGER
        ACCESS	read-write
        STATUS	mandatory
        DESCRIPTION
                "The maximum number of entries allowed in the NetBIOS name cache."
        DEFVAL	{ 100 }
        ::= { wfNetbiosIp 7 }

    wfNetbiosIpNameCacheCurrentEntries OBJECT-TYPE
        SYNTAX	INTEGER
        ACCESS	read-only
        STATUS	mandatory
        DESCRIPTION
                "The number of entries currently in the NetBIOS name cache."
        ::= { wfNetbiosIp 8 }

    wfNetbiosIpNameCacheAgeTime OBJECT-TYPE
        SYNTAX	INTEGER(60..604800)
        ACCESS	read-write
        STATUS	mandatory
        DESCRIPTION
                "The age in seconds when inactive NetBIOS names will be aged out of the
                cache."
        DEFVAL	{ 300 }
        ::= { wfNetbiosIp 9 }

    wfNetbiosIpNameCacheHashEntries OBJECT-TYPE
        SYNTAX	INTEGER
        ACCESS	read-write
        STATUS	mandatory
        DESCRIPTION
                "The number of entries in the NetBIOS name cache hash table."
        DEFVAL	{ 253 }
        ::= { wfNetbiosIp 10 }

    wfNetbiosIpNameCacheHits OBJECT-TYPE
        SYNTAX	Counter
        ACCESS	read-only
        STATUS	mandatory
        DESCRIPTION
                "The number of times the NetBIOS name cache has been used."
        ::= { wfNetbiosIp 11 }

    wfNetbiosIpNameCacheMisses OBJECT-TYPE
        SYNTAX	Counter
        ACCESS	read-only
        STATUS	mandatory
        DESCRIPTION
                "The number of failed lookups on the NetBIOS name cache."
        ::= { wfNetbiosIp 12 }

    wfNetbiosIpRebroadcastTTL OBJECT-TYPE
        SYNTAX	INTEGER(1..255)
        ACCESS	read-write
        STATUS	mandatory
        DESCRIPTION
                "The default time-to-live value in seconds to use in rebroadcasted packets."
        DEFVAL	{ 5 }
        ::= { wfNetbiosIp 13 }

    wfNetbiosIpRebroadcastRecordRoute OBJECT-TYPE
        SYNTAX	INTEGER {
    		    enabled(1),
    		    disabled(2)
    		}
        ACCESS	read-write
        STATUS	mandatory
        DESCRIPTION
                "Enable/Disable insertion of Record Route option in rebroadcasted packets."
        DEFVAL	{ disabled }
        ::= { wfNetbiosIp 14 }

    wfNetbiosIpInterfaceTable OBJECT-TYPE
        SYNTAX	SEQUENCE OF WfNetbiosIpInterfaceEntry
        ACCESS	not-accessible
        STATUS	mandatory
        DESCRIPTION
                "A table that contains information about every interface that is
                configured to run/not run NetBIOS over IP.
                inst_id[1] = wfNetbiosIpInterfaceIndex"
        ::= { wfNetBIOSIpGroup 2 }

    wfNetbiosIpInterfaceEntry OBJECT-TYPE
        SYNTAX	WfNetbiosIpInterfaceEntry
        ACCESS	not-accessible
        STATUS	mandatory
        DESCRIPTION
                "An entry in the NetBIOS interface table."
        INDEX	{ wfNetbiosIpInterfaceIndex }
        ::= { wfNetbiosIpInterfaceTable 1 }

    WfNetbiosIpInterfaceEntry ::= SEQUENCE {
    	    wfNetbiosIpInterfaceDelete
    		INTEGER,
    	    wfNetbiosIpInterfaceDisable
    		INTEGER,
    	    wfNetbiosIpInterfaceState
    		INTEGER,
    	    wfNetbiosIpInterfaceIndex
    		IpAddress,
    	    wfNetbiosIpInterfaceReceivedFrames
    		Counter,
    	    wfNetbiosIpInterfaceReceivedBadFrames
    		Counter,
    	    wfNetbiosIpInterfaceTransmittedFrames
    		Counter,
    	    wfNetbiosIpInterfaceNameCacheDisable
    		INTEGER,
    	    wfNetbiosIpInterfaceInBroadcastDisable
    		INTEGER,
    	    wfNetbiosIpInterfaceOutBroadcastDisable
    		INTEGER,
    	    wfNetbiosIpInterfaceRebroadcastAddr
    		IpAddress
        }

    wfNetbiosIpInterfaceDelete OBJECT-TYPE
        SYNTAX	INTEGER {
    		    created(1),
    		    deleted(2)
    		}
        ACCESS	read-write
        STATUS	mandatory
        DESCRIPTION
                "Create/Delete parameter. Default is created.
                Users perform an SNMP SET operation on this
                object in order to create/delete an interface."
        DEFVAL	{ created }
        ::= { wfNetbiosIpInterfaceEntry 1 }

    wfNetbiosIpInterfaceDisable OBJECT-TYPE
        SYNTAX	INTEGER {
    		    enabled(1),
    		    disabled(2)
    		}
        ACCESS	read-write
        STATUS	mandatory
        DESCRIPTION
                "Enable/Disable parameter. Default is enabled.
                Users perform an SNMP SET operation on this
                object in order to enable/disable an interface."
        DEFVAL	{ enabled }
        ::= { wfNetbiosIpInterfaceEntry 2 }

    wfNetbiosIpInterfaceState OBJECT-TYPE
        SYNTAX	INTEGER {
    		    up(1),
    		    down(2),
    		    init(3),
    		    notpres(4)
    		}
        ACCESS	read-only
        STATUS	mandatory
        DESCRIPTION
                "The current state of NetBIOS over IP on this interface."
        DEFVAL	{ notpres }
        ::= { wfNetbiosIpInterfaceEntry 3 }

    wfNetbiosIpInterfaceIndex OBJECT-TYPE
        SYNTAX	IpAddress
        ACCESS	read-only
        STATUS	mandatory
        DESCRIPTION
                "The IP address of this interface."
        ::= { wfNetbiosIpInterfaceEntry 4 }

    wfNetbiosIpInterfaceReceivedFrames OBJECT-TYPE
        SYNTAX	Counter
        ACCESS	read-only
        STATUS	mandatory
        DESCRIPTION
                "The number of frames that have been received by
                this interface from its circuit."
        ::= { wfNetbiosIpInterfaceEntry 5 }

    wfNetbiosIpInterfaceReceivedBadFrames OBJECT-TYPE
        SYNTAX	Counter
        ACCESS	read-only
        STATUS	mandatory
        DESCRIPTION
                "The number of invalid frames that have been received by
                this interface from its circuit."
        ::= { wfNetbiosIpInterfaceEntry 6 }

    wfNetbiosIpInterfaceTransmittedFrames OBJECT-TYPE
        SYNTAX	Counter
        ACCESS	read-only
        STATUS	mandatory
        DESCRIPTION
                "The number of frames that have been transmitted
                by this interface."
        ::= { wfNetbiosIpInterfaceEntry 7 }

    wfNetbiosIpInterfaceNameCacheDisable OBJECT-TYPE
        SYNTAX	INTEGER {
    		    enabled(1),
    		    disabled(2)
    		}
        ACCESS	read-write
        STATUS	mandatory
        DESCRIPTION
                "Enable/Disable parameter for NetBIOS name caching."
        DEFVAL	{ enabled }
        ::= { wfNetbiosIpInterfaceEntry 8 }

    wfNetbiosIpInterfaceInBroadcastDisable OBJECT-TYPE
        SYNTAX	INTEGER {
    		    enabled(1),
    		    disabled(2)
    		}
        ACCESS	read-write
        STATUS	mandatory
        DESCRIPTION
                "Enable/Disable parameter for the input of NetBIOS broadcasts."
        DEFVAL	{ enabled }
        ::= { wfNetbiosIpInterfaceEntry 9 }

    wfNetbiosIpInterfaceOutBroadcastDisable OBJECT-TYPE
        SYNTAX	INTEGER {
    		    enabled(1),
    		    disabled(2)
    		}
        ACCESS	read-write
        STATUS	mandatory
        DESCRIPTION
                "Enable/Disable parameter for the output of NetBIOS broadcasts."
        DEFVAL	{ enabled }
        ::= { wfNetbiosIpInterfaceEntry 10 }

    wfNetbiosIpInterfaceRebroadcastAddr OBJECT-TYPE
        SYNTAX	IpAddress
        ACCESS	read-write
        STATUS	mandatory
        DESCRIPTION
                "The IP broadcast address to use for rebroadcasted packets out this
                interface."
        ::= { wfNetbiosIpInterfaceEntry 11 }

    wfNetbiosIpNameTable OBJECT-TYPE
        SYNTAX	SEQUENCE OF WfNetbiosIpNameEntry
        ACCESS	not-accessible
        STATUS	mandatory
        DESCRIPTION
                "The NetBIOS name cache table."
        ::= { wfNetBIOSIpGroup 3 }

    wfNetbiosIpNameEntry OBJECT-TYPE
        SYNTAX	WfNetbiosIpNameEntry
        ACCESS	not-accessible
        STATUS	mandatory
        DESCRIPTION
                "An entry in the NetBIOS name cache table."
        INDEX	{ wfNetbiosIpName,
    		  wfNetbiosIpAddress,
    		  wfNetbiosIpIdNumber }
        ::= { wfNetbiosIpNameTable 1 }

    WfNetbiosIpNameEntry ::= SEQUENCE {
    	    wfNetbiosIpName
    		OCTET STRING,
    	    wfNetbiosIpScopeId
    		OCTET STRING,
    	    wfNetbiosIpAddress
    		IpAddress,
    	    wfNetbiosIpStatic
    		INTEGER,
    	    wfNetbiosIpCacheHits
    		Counter,
    	    wfNetbiosIpIdNumber
    		INTEGER
        }

    wfNetbiosIpName OBJECT-TYPE
        SYNTAX	OCTET STRING (SIZE (16))
        ACCESS	read-only
        STATUS	mandatory
        DESCRIPTION
                "The NetBIOS name of this station. It is a maximum of 16 characters."
        ::= { wfNetbiosIpNameEntry 1 }

    wfNetbiosIpScopeId OBJECT-TYPE
        SYNTAX	OCTET STRING
        ACCESS	read-only
        STATUS	mandatory
        DESCRIPTION
                "The NetBIOS scope id of this station."
        ::= { wfNetbiosIpNameEntry 2 }

    wfNetbiosIpAddress OBJECT-TYPE
        SYNTAX	IpAddress
        ACCESS	read-only
        STATUS	mandatory
        DESCRIPTION
                "The IP address of the NetBIOS station."
        ::= { wfNetbiosIpNameEntry 3 }

    wfNetbiosIpStatic OBJECT-TYPE
        SYNTAX	INTEGER {
    		    static(1),
    		    learned(2)
    		}
        ACCESS	read-only
        STATUS	mandatory
        DESCRIPTION
                "Indicates whether this entry is a static or learned entry."
        ::= { wfNetbiosIpNameEntry 4 }

    wfNetbiosIpCacheHits OBJECT-TYPE
        SYNTAX	Counter
        ACCESS	read-only
        STATUS	mandatory
        DESCRIPTION
                "The number of Name Query Responses that have been converted by this station."
        ::= { wfNetbiosIpNameEntry 5 }

    wfNetbiosIpIdNumber OBJECT-TYPE
        SYNTAX	INTEGER
        ACCESS	read-only
        STATUS	mandatory
        DESCRIPTION
                "Uniqueness ID for the MIB entry."
        ::= { wfNetbiosIpNameEntry 6 }

    wfNetbiosIpStaticTable OBJECT-TYPE
        SYNTAX	SEQUENCE OF WfNetbiosIpStaticEntry
        ACCESS	not-accessible
        STATUS	mandatory
        DESCRIPTION
                "The NetBIOS static server/client entry table."
        ::= { wfNetBIOSIpGroup 4 }

    wfNetbiosIpStaticEntry OBJECT-TYPE
        SYNTAX	WfNetbiosIpStaticEntry
        ACCESS	not-accessible
        STATUS	mandatory
        DESCRIPTION
                "An entry in the NetBIOS static entry table."
        INDEX	{ wfNetbiosIpStaticName,
    		  wfNetbiosIpStaticIpAddress,
    		  wfNetbiosIpStaticIdNumber }
        ::= { wfNetbiosIpStaticTable 1 }

    WfNetbiosIpStaticEntry ::= SEQUENCE {
    	    wfNetbiosIpStaticDelete
    		INTEGER,
    	    wfNetbiosIpStaticDisable
    		INTEGER,
    	    wfNetbiosIpStaticState
    		INTEGER,
    	    wfNetbiosIpStaticName
    		OCTET STRING,
    	    wfNetbiosIpStaticScopeId
    		OCTET STRING,
    	    wfNetbiosIpStaticIpAddress
    		IpAddress,
    	    wfNetbiosIpStaticIdNumber
    		INTEGER
        }

    wfNetbiosIpStaticDelete OBJECT-TYPE
        SYNTAX	INTEGER {
    		    created(1),
    		    deleted(2)
    		}
        ACCESS	read-write
        STATUS	mandatory
        DESCRIPTION
                "Create/Delete parameter for the NetBIOS static entry."
        DEFVAL	{ created }
        ::= { wfNetbiosIpStaticEntry 1 }

    wfNetbiosIpStaticDisable OBJECT-TYPE
        SYNTAX	INTEGER {
    		    enabled(1),
    		    disabled(2)
    		}
        ACCESS	read-write
        STATUS	mandatory
        DESCRIPTION
                "Enable/Disable parameter for the NetBIOS static entry."
        DEFVAL	{ enabled }
        ::= { wfNetbiosIpStaticEntry 2 }

    wfNetbiosIpStaticState OBJECT-TYPE
        SYNTAX	INTEGER {
    		    valid(1),
    		    invalid(2)
    		}
        ACCESS	read-only
        STATUS	mandatory
        DESCRIPTION
                "The state of this NetBIOS static entry."
        DEFVAL	{ invalid }
        ::= { wfNetbiosIpStaticEntry 3 }

    wfNetbiosIpStaticName OBJECT-TYPE
        SYNTAX	OCTET STRING (SIZE (16))
        ACCESS	read-only
        STATUS	mandatory
        DESCRIPTION
                "The NetBIOS name of the station. It is a maximum of 16 characters.
                Names that are shorter are padded with ASCII spaces - 0x20."
        ::= { wfNetbiosIpStaticEntry 4 }

    wfNetbiosIpStaticScopeId OBJECT-TYPE
        SYNTAX	OCTET STRING
        ACCESS	read-write
        STATUS	mandatory
        DESCRIPTION
                "The NetBIOS scope id of the station. Once set, this should not be changed."
        ::= { wfNetbiosIpStaticEntry 5 }

    wfNetbiosIpStaticIpAddress OBJECT-TYPE
        SYNTAX	IpAddress
        ACCESS	read-only
        STATUS	mandatory
        DESCRIPTION
                "The IP address of the NetBIOS station."
        ::= { wfNetbiosIpStaticEntry 6 }

    wfNetbiosIpStaticIdNumber OBJECT-TYPE
        SYNTAX	INTEGER
        ACCESS	read-only
        STATUS	mandatory
        DESCRIPTION
                "Uniqueness ID for the MIB entry."
        ::= { wfNetbiosIpStaticEntry 7 }

    END  -- Wellfleet-NBIP-MIB
