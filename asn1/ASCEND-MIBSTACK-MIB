--			Ascend mibstack MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBSTACK-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibstackingProfile  OBJECT IDENTIFIER ::= { configuration 122}

	-- The mibstackingProfile table
	--
	-- This table contains parameters for the mibstackingProfile profile
	--

    mibstackingProfileTable	OBJECT-TYPE
	SYNTAX		SEQUENCE OF MibstackingProfileEntry
	ACCESS		not-accessible
	STATUS		mandatory
	DESCRIPTION	"A list of mibstackingProfile profile entries."
	::= { mibstackingProfile 1 }

    mibstackingProfileEntry	OBJECT-TYPE
	SYNTAX		MibstackingProfileEntry
	ACCESS		not-accessible
	STATUS		mandatory
	DESCRIPTION	"A mibstackingProfile entry containing objects that
			 maps to the parameters of mibstackingProfile profile."
	INDEX		{ stackingProfile-Index-o }
	::= { mibstackingProfileTable 1 }

    MibstackingProfileEntry ::=
	SEQUENCE {
	    stackingProfile-Index-o
		INTEGER,
	    stackingProfile-Enabled
		INTEGER,
	    stackingProfile-Name
		DisplayString,
	    stackingProfile-UdpPort
		INTEGER,
	    stackingProfile-MulticastAddress
		IpAddress,
	    stackingProfile-MulticastInterfaceIpAddress
		IpAddress,
	    stackingProfile-DataIpAddress
		IpAddress,
	    stackingProfile-Action-o
		INTEGER
	}

    stackingProfile-Index-o	OBJECT-TYPE
	SYNTAX	INTEGER
	ACCESS	read-only
	STATUS	mandatory
	DESCRIPTION	""
	::= { mibstackingProfileEntry 1 }

    stackingProfile-Enabled	OBJECT-TYPE
	SYNTAX	INTEGER {
		    no (1),
		    yes (2)
		}
	ACCESS	read-write
	STATUS	mandatory
	DESCRIPTION	"Defines whether or not stacking is enabled."
	::= { mibstackingProfileEntry 2 }

    stackingProfile-Name	OBJECT-TYPE
	SYNTAX	DisplayString
	ACCESS	read-write
	STATUS	mandatory
	DESCRIPTION	"The name of the stack this machine is a member of."
	::= { mibstackingProfileEntry 3 }

    stackingProfile-UdpPort	OBJECT-TYPE
	SYNTAX	INTEGER
	ACCESS	read-write
	STATUS	mandatory
	DESCRIPTION	"UDP port number to be used for receiving stacking control messages."
	::= { mibstackingProfileEntry 4 }

    stackingProfile-MulticastAddress	OBJECT-TYPE
	SYNTAX	IpAddress
	ACCESS	read-write
	STATUS	mandatory
	DESCRIPTION	"Multicast address for stacking."
	::= { mibstackingProfileEntry 5 }

    stackingProfile-MulticastInterfaceIpAddress	OBJECT-TYPE
	SYNTAX	IpAddress
	ACCESS	read-write
	STATUS	mandatory
	DESCRIPTION	"IP Address of ethernet interface to be used for sending stacking multicast messages. If set to 0.0.0.0 the shelf ethernet interface is used."
	::= { mibstackingProfileEntry 6 }

    stackingProfile-DataIpAddress	OBJECT-TYPE
	SYNTAX	IpAddress
	ACCESS	read-write
	STATUS	mandatory
	DESCRIPTION	"IP address of interface to be used for receiving stacking data from peers. If set to 0.0.0.0 the system IP address will be used."
	::= { mibstackingProfileEntry 7 }

    stackingProfile-Action-o	OBJECT-TYPE
	SYNTAX	INTEGER {
		    noAction (1),
		    createProfile (2),
		    deleteProfile (3)
		}
	ACCESS	read-write
	STATUS	mandatory
	DESCRIPTION	""
	::= { mibstackingProfileEntry 8 }

END
