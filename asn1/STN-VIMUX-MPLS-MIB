-- *****************************************************************
--
-- stn-vimux-mpls.mib:  
--      Spring Tide Networks Network VIMUX Interface for MPLS
--                     (VIMUX MPLS) MIB File
--
--
--      Copyright (c) 2000 by Spring Tide Networks, Inc.
--                      ALL RIGHTS RESERVED       
--
-- *****************************************************************

-- MIB Object definitions for Spring Tide VIMUX MPLS

STN-VIMUX-MPLS-MIB DEFINITIONS ::= BEGIN

    IMPORTS
        MODULE-IDENTITY,
        OBJECT-TYPE, 
        Gauge32,
        Integer32,
		IpAddress
                FROM SNMPv2-SMI

        DisplayString
                FROM SNMPv2-TC

        InterfaceIndex
                FROM IF-MIB

        stnRouterVimuxMpls
                FROM STN-ROUTER-MIB;


    stnVimuxMpls MODULE-IDENTITY
        LAST-UPDATED    "0004060000Z"
        ORGANIZATION    "Spring Tide Networks"
        CONTACT-INFO
                "
                Spring Tide Networks, Inc.
                Customer Service

                Postal: 3 Clock Tower Place
                        Suite 200
                        Maynard, MA 01754 USA
                Tel:    +1 978 298 2000
                Email:  custserv@springtidenet.com
                "
        DESCRIPTION     "This MIB module describes managed objects of
                         Spring Tide Networks VIMUX MPLS Interface."
        ::= { stnRouterVimuxMpls 1 }


--
-- Top Level STN VIMUX MPLS MIB Objects
--

    stnVimuxMplsObjects       OBJECT IDENTIFIER ::= {stnVimuxMpls 1}
    
--
-- STN VIMUX MPLS Layer 2 Table  
--   One entry for each VIMUX MPLS defined in the system.
--
    stnVimuxMplsL2Table OBJECT-TYPE
        SYNTAX		SEQUENCE OF StnVimuxMplsL2Entry
        MAX-ACCESS	not-accessible
        STATUS		current
        DESCRIPTION	"A list of VIMUX MPLS L2 entries."
        ::= { stnVimuxMplsObjects 1 }
 
    stnVimuxMplsL2Entry OBJECT-TYPE
        SYNTAX          StnVimuxMplsL2Entry
        MAX-ACCESS      not-accessible
        STATUS          current
        DESCRIPTION     "Entry contains information about a particular VIMUX MPLS L2."
        INDEX           { stnVimuxMplsL2IfIndex }
        ::= { stnVimuxMplsL2Table 1 }
 
    StnVimuxMplsL2Entry ::= SEQUENCE {
        stnVimuxMplsL2IfIndex                     InterfaceIndex,
        stnVimuxMplsL2ViId                        Integer32,
        stnVimuxMplsL2Name                        DisplayString,
        stnVimuxMplsL2State                       INTEGER,              
        stnVimuxMplsL2RegisteredLowerLinks        Gauge32,
        stnVimuxMplsL2ActiveLowerLinks            Gauge32,
        stnVimuxMplsL2InvalidInLabelPackets       Integer32,
        stnVimuxMplsL2InvalidOutLabelPackets      Integer32
    }

    stnVimuxMplsL2IfIndex OBJECT-TYPE
        SYNTAX          InterfaceIndex
        MAX-ACCESS      read-only
        STATUS          current
        DESCRIPTION     "The ifIndex of the VIMUX MPLS Layer 2 Interface."
        ::= { stnVimuxMplsL2Entry 1 }

    stnVimuxMplsL2ViId OBJECT-TYPE
        SYNTAX          Integer32
        MAX-ACCESS      read-only
        STATUS          current
        DESCRIPTION     "The instance of the configuration record 
                         corresponding to this VIMUX MPLS."
        ::= { stnVimuxMplsL2Entry 2 }

    stnVimuxMplsL2Name OBJECT-TYPE
        SYNTAX          DisplayString (SIZE (1..32))
        MAX-ACCESS      read-only
        STATUS          current
        DESCRIPTION     "The name configured for this VIMUX MPLS."
        ::= { stnVimuxMplsL2Entry 3 }

    stnVimuxMplsL2State OBJECT-TYPE
        SYNTAX          INTEGER {
                          up(1),       -- ready to pass packets
                          down(2),
                          testing(3)   -- in some test mode
                        }
        MAX-ACCESS      read-only
        STATUS          current
        DESCRIPTION     "The current operational state of the VIMUX MPLS."
        ::= { stnVimuxMplsL2Entry 4 }

    stnVimuxMplsL2RegisteredLowerLinks OBJECT-TYPE
        SYNTAX          Gauge32
        MAX-ACCESS      read-only
        STATUS          current
        DESCRIPTION     "The current number of VCLinks registered with the VIMUX MPLS."
        ::= { stnVimuxMplsL2Entry 5 }

    stnVimuxMplsL2ActiveLowerLinks OBJECT-TYPE
        SYNTAX          Gauge32
        MAX-ACCESS      read-only
        STATUS          current
        DESCRIPTION     "The current number of VCLinks actively carrying 
			            traffic for this VIMUX MPLS."
        ::= { stnVimuxMplsL2Entry 6 }

    stnVimuxMplsL2InvalidInLabelPackets OBJECT-TYPE
        SYNTAX          Integer32
        MAX-ACCESS      read-only
        STATUS          current
        DESCRIPTION     "The number of packets dropped because of invalid incoming labels."
        ::= { stnVimuxMplsL2Entry 7 }

    stnVimuxMplsL2InvalidOutLabelPackets OBJECT-TYPE
        SYNTAX          Integer32
        MAX-ACCESS      read-only
        STATUS          current
        DESCRIPTION     "The number of packets dropped because of invalid outgoing labels."
        ::= { stnVimuxMplsL2Entry 8 }


--
-- STN VIMUX MPLS Link Table  
--   One entry for each lower VcLink per VIMUX MPLS L2
--

    stnVimuxMplsLinkTable OBJECT-TYPE
        SYNTAX		SEQUENCE OF StnVimuxMplsLinkEntry
        MAX-ACCESS	not-accessible
        STATUS		current
        DESCRIPTION	"A list of the links configured for a VIMUX MPLS."
        ::= { stnVimuxMplsObjects 2 }
 
    stnVimuxMplsLinkEntry OBJECT-TYPE
        SYNTAX          StnVimuxMplsLinkEntry
        MAX-ACCESS      not-accessible
        STATUS          current
        DESCRIPTION     "Entry contains information about a particular VIMUX MPLS L2."
        INDEX           { stnVimuxMplsLinkVimuxMplsIfIndex, stnVimuxMplsLinkIfIndex }
        ::= { stnVimuxMplsLinkTable 1 }
 
    StnVimuxMplsLinkEntry ::= SEQUENCE {
        stnVimuxMplsLinkVimuxMplsIfIndex            InterfaceIndex,
        stnVimuxMplsLinkIfIndex                 InterfaceIndex,
        stnVimuxMplsLinkPhysIfIndex             InterfaceIndex,
        stnVimuxMplsLinkVpi                     Integer32,
        stnVimuxMplsLinkVci                     Integer32
    }
    
    stnVimuxMplsLinkVimuxMplsIfIndex OBJECT-TYPE
        SYNTAX          InterfaceIndex
        MAX-ACCESS      read-only
        STATUS          current
        DESCRIPTION     "The IfIndex of the VIMUX MPLS for which this VcLink is 
			             configured."
        ::= { stnVimuxMplsLinkEntry 1 }

    stnVimuxMplsLinkIfIndex OBJECT-TYPE
        SYNTAX          InterfaceIndex
        MAX-ACCESS      read-only
        STATUS          current
        DESCRIPTION     "The IfIndex of this VcLink."
        ::= { stnVimuxMplsLinkEntry 2 }

    stnVimuxMplsLinkPhysIfIndex OBJECT-TYPE
        SYNTAX          InterfaceIndex
        MAX-ACCESS      read-only
        STATUS          current
        DESCRIPTION     "The physical interface index represents the port and line card
                         used by this link. It is calculated based on the slot and 
                         port of the module."
        ::= { stnVimuxMplsLinkEntry 3 }

    stnVimuxMplsLinkVpi OBJECT-TYPE     
        SYNTAX          Integer32 
        MAX-ACCESS      read-only
        STATUS          current
        DESCRIPTION     "The VPI value of the PVC represented by this link."
        ::= { stnVimuxMplsLinkEntry 4 }

    stnVimuxMplsLinkVci OBJECT-TYPE     
        SYNTAX          Integer32 
        MAX-ACCESS      read-only
        STATUS          current
        DESCRIPTION     "The VCI value of the PVC represented by this link." 
        ::= { stnVimuxMplsLinkEntry 5 }


--
-- STN VIMUX MPLS Incoming Label Table  
--   One entry for each incoming label defined for the VIMUX MPLS.
--

    stnVimuxMplsIncomingLabelTable OBJECT-TYPE
        SYNTAX		SEQUENCE OF StnVimuxMplsIncomingLabel
        MAX-ACCESS	not-accessible
        STATUS		current
        DESCRIPTION	"A list of the incoming labels defined for this VIMUX MPLS."
        ::= { stnVimuxMplsObjects 3 }
 
    stnVimuxMplsIncomingLabel OBJECT-TYPE
        SYNTAX          StnVimuxMplsIncomingLabel
        MAX-ACCESS      not-accessible
        STATUS          current
        DESCRIPTION     "Entry contains information about a particular incoming 
			            label defined for this VIMUX MPLS."
        INDEX           { stnVimuxMplsIncomingLabelValue } 
        ::= { stnVimuxMplsIncomingLabelTable 1 }
 
    StnVimuxMplsIncomingLabel ::= SEQUENCE {
    	stnVimuxMplsIncomingLabelIfIndex            InterfaceIndex, 
        stnVimuxMplsIncomingLabelValue              Integer32,
        stnVimuxMplsIncomingLabelAction             INTEGER,
        stnVimuxMplsIncomingLabelToPush1            Integer32,
        stnVimuxMplsIncomingLabelToPush2            Integer32,
        stnVimuxMplsIncomingLabelToPush3            Integer32,
        stnVimuxMplsIncomingLabelToPush4            Integer32,
        stnVimuxMplsIncomingLabelNextVimuxMplsIfIndex   InterfaceIndex,
        stnVimuxMplsIncomingLabelTtl                Integer32,
        stnVimuxMplsIncomingLabelReceivedPackets    Integer32,
        stnVimuxMplsIncomingLabelDroppedPackets     Integer32
    }

    stnVimuxMplsIncomingLabelIfIndex OBJECT-TYPE
        SYNTAX          InterfaceIndex
        MAX-ACCESS      read-only
        STATUS          current
        DESCRIPTION     "The IfIndex of the VIMUX MPLS which 
			 owns the incoming label."
        ::= { stnVimuxMplsIncomingLabel 1 }

    stnVimuxMplsIncomingLabelValue OBJECT-TYPE
        SYNTAX          Integer32
        MAX-ACCESS      read-only
        STATUS          current
        DESCRIPTION     "The value of the incoming label."
        ::= { stnVimuxMplsIncomingLabel 2 }

    stnVimuxMplsIncomingLabelAction OBJECT-TYPE
        SYNTAX          INTEGER {
                            pop(1),
                            replace(2)
                        }
        MAX-ACCESS      read-only
        STATUS          current
        DESCRIPTION     "The action to perform on this incoming label."
        ::= { stnVimuxMplsIncomingLabel 3 }

    stnVimuxMplsIncomingLabelToPush1 OBJECT-TYPE
        SYNTAX          Integer32
        MAX-ACCESS      read-only
        STATUS          current
        DESCRIPTION     "The value of the last label pushed."
        ::= { stnVimuxMplsIncomingLabel 4 }

    stnVimuxMplsIncomingLabelToPush2 OBJECT-TYPE
        SYNTAX          Integer32
        MAX-ACCESS      read-only
        STATUS          current
        DESCRIPTION     "The value of the second-to-last label pushed."
        ::= { stnVimuxMplsIncomingLabel 5 }

    stnVimuxMplsIncomingLabelToPush3 OBJECT-TYPE
        SYNTAX          Integer32
        MAX-ACCESS      read-only
        STATUS          current
        DESCRIPTION     "The value of the third-to-last label pushed."
        ::= { stnVimuxMplsIncomingLabel 6 }

    stnVimuxMplsIncomingLabelToPush4 OBJECT-TYPE
        SYNTAX          Integer32
        MAX-ACCESS      read-only
        STATUS          current
        DESCRIPTION     "The value of the fourth-to-last label pushed."
        ::= { stnVimuxMplsIncomingLabel 7 }

    stnVimuxMplsIncomingLabelNextVimuxMplsIfIndex OBJECT-TYPE
        SYNTAX          InterfaceIndex
        MAX-ACCESS      read-only
        STATUS          current
        DESCRIPTION     "The IfIndex of the VIMUX MPLS to pass the packets to."
        ::= { stnVimuxMplsIncomingLabel 8 }

    stnVimuxMplsIncomingLabelTtl OBJECT-TYPE
        SYNTAX          Integer32
        MAX-ACCESS      read-only
        STATUS          current
        DESCRIPTION     "The TTL value of this label."
        ::= { stnVimuxMplsIncomingLabel 9 }

    stnVimuxMplsIncomingLabelReceivedPackets OBJECT-TYPE
        SYNTAX          Integer32
        MAX-ACCESS      read-only
        STATUS          current
        DESCRIPTION     "The number of packets received with this label."
        ::= { stnVimuxMplsIncomingLabel 10 }

    stnVimuxMplsIncomingLabelDroppedPackets OBJECT-TYPE
        SYNTAX          Integer32
        MAX-ACCESS      read-only
        STATUS          current
        DESCRIPTION     "The number of packets dropped with this label."
        ::= { stnVimuxMplsIncomingLabel 11 }


--
-- STN VIMUX MPLS Outgoing Label Table  
--   One entry for each outgoing label defined for the VIMUX MPLS.
--

    stnVimuxMplsOutgoingLabelTable OBJECT-TYPE
        SYNTAX		SEQUENCE OF StnVimuxMplsOutgoingLabel
        MAX-ACCESS	not-accessible
        STATUS		current
        DESCRIPTION	"A list of the outgoing labels defined for this VIMUX MPLS."
        ::= { stnVimuxMplsObjects 4 }
 
    stnVimuxMplsOutgoingLabel OBJECT-TYPE
        SYNTAX          StnVimuxMplsOutgoingLabel
        MAX-ACCESS      not-accessible
        STATUS          current
        DESCRIPTION     "Entry contains information about a particular outgoing 
			            label defined for this VIMUX MPLS."
        INDEX           { stnVimuxMplsOutgoingLabelValue } 
        ::= { stnVimuxMplsOutgoingLabelTable 1 }
 
    StnVimuxMplsOutgoingLabel ::= SEQUENCE {
    	stnVimuxMplsOutgoingLabelIfIndex            InterfaceIndex, 
        stnVimuxMplsOutgoingLabelValue              Integer32,
        stnVimuxMplsOutgoingLabelOutgoingIfIndex    InterfaceIndex,
        stnVimuxMplsOutgoingLabelNexthop            IpAddress,
        stnVimuxMplsOutgoingLabelSentPackets        Integer32,
        stnVimuxMplsOutgoingLabelDroppedPackets     Integer32
    }

    stnVimuxMplsOutgoingLabelIfIndex OBJECT-TYPE
        SYNTAX          InterfaceIndex
        MAX-ACCESS      read-only
        STATUS          current
        DESCRIPTION     "The IfIndex of the VIMUX MPLS which 
			 owns the outgoing label."
        ::= { stnVimuxMplsOutgoingLabel 1 }

    stnVimuxMplsOutgoingLabelValue OBJECT-TYPE
        SYNTAX          Integer32
        MAX-ACCESS      read-only
        STATUS          current
        DESCRIPTION     "The value of the outgoing label."
        ::= { stnVimuxMplsOutgoingLabel 2 }

    stnVimuxMplsOutgoingLabelOutgoingIfIndex OBJECT-TYPE
        SYNTAX          InterfaceIndex
        MAX-ACCESS      read-only
        STATUS          current
        DESCRIPTION     "The IfIndex of the L2 interface to pass the packets to."
        ::= { stnVimuxMplsOutgoingLabel 3 }

    stnVimuxMplsOutgoingLabelNexthop OBJECT-TYPE
        SYNTAX          IpAddress
        MAX-ACCESS      read-only
        STATUS          current
        DESCRIPTION     "The next hop IP address packets will be sent to, if Ethernet I/F."
        ::= { stnVimuxMplsOutgoingLabel 4 }

    stnVimuxMplsOutgoingLabelSentPackets OBJECT-TYPE
        SYNTAX          Integer32
        MAX-ACCESS      read-only
        STATUS          current
        DESCRIPTION     "The number of packets sent with this label."
        ::= { stnVimuxMplsOutgoingLabel 5 }

    stnVimuxMplsOutgoingLabelDroppedPackets OBJECT-TYPE
        SYNTAX          Integer32
        MAX-ACCESS      read-only
        STATUS          current
        DESCRIPTION     "The number of packets dropped with this label."
        ::= { stnVimuxMplsOutgoingLabel 6 }


END
