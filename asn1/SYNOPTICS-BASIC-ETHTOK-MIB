----------
X-Sun-Data-Type: text
X-Sun-Data-Description: text
X-Sun-Data-Name: text
X-Sun-Content-Lines: 10

Iana,
Could you please post this new version of the Synoptics MIB on
on venera?  We know that the MIB file currently on vernera is
woefully out-of-date.  The MIB file was sent as an attachment.
If you have any problems or questions please send me e-mail
or give me a call.
Thank You.
Greg Foster
gfoster@synoptics.com
(408) 764-1642
----------
X-Sun-Data-Type: default
X-Sun-Data-Description: default
X-Sun-Data-Name: synoptics.mib
X-Sun-Content-Lines: 6156

-- SynOptics Basic Ethernet & Token Ring 2K & 3K MIB
-- Revision 09/18/94.

-- Copyright 1991-94 SynOptics Communications, Inc.
-- All rights reserved.
-- This SynOptics SNMP Management Information Base Specification
-- (Specification) embodies SynOptics' confidential and
-- proprietary intellectual property. SynOptics retains all
-- title and ownership in the Specification, including any
-- revisions.

-- This Specification is supplied "AS IS," and SynOptics makes
-- no warranty, either express or implied, as to the use,
-- operation, condition, or performance of the Specification.
--
-- This MIB is based on the 331x/331xA v5.2, 351x/271x v3.5,
-- and 281x v5.1.1 basic agents, and was constructed from the
-- Common MIB v4.6.1, Token Ring MIB v4.2.2, Ethernet MIB v4.5.1,
-- Synoptic's IEEE802.3 MIB v1.1.0, and IPX MIB v1.1.0.  The
-- objects contained in the MIB are generally a subset of
-- the advanced agents.

SYNOPTICS-BASIC-ETHTOK-MIB DEFINITIONS ::= BEGIN

IMPORTS
        enterprises,
        IpAddress, Counter, Gauge, TimeTicks
                FROM RFC1155-SMI
        OBJECT-TYPE
                FROM RFC-1212
        TRAP-TYPE
                FROM RFC-1215;

DisplayString ::=
            OCTET STRING

PhysAddress ::=
            OCTET STRING

SnpxBackplaneType ::=
            INTEGER {
            other(1),
            eth(2),
            ethTok(3),
            ethFddi(4),
            ethTokFddi(5),
            ethTokRed(6),
            ethTokFddiRed(7),
            tok(8)
            }

SnpxChassisType ::=
            INTEGER {
            other(1),
            m3000(2),
            m3030(3),
            m2310(4),
            m2810(5),
            m2912(6),
            m2914(7),
            m271x(8),
            m2813(9),
            m2814(10),
            m2915(11),
            m5000(12),
            m2813SA(13),
            m2814SA(14),
            m810M(15),
            m1032x(16),
            m5005(17),
            mAlcatelEthConc(18),
            m2715SA(20),
            m2486(21)
            }

S3ModuleType ::=
            INTEGER {
            empty(1),
            other(2),
            m3302(3),
            m3304-ST(4),
            m3305(5),
            m3308(6),
            m3313(7),
            m3313M(8),
            m3314-ST(9),
            m3314M-ST(10),
            m3323(11),
            m3324-ST(12),
            m3502(13),
            m3532(14),
            m3552(15),
            m3301(16),
            m3307(17),
            m3356(18),
            m3512(19),
            m3514(20),
            m3505(21),
            m3554(22),
            m3534(23),
            m3383(24),
            m3384(25),
            m331x(26),
            m351x(27),
            m3502-A(28),
            m3902(29),
            m3904(30),
            m3910S(31),
            m3386(32),
            m3394(33),
            m3395(34),
            m3323S(35),
            m3324S-ST(36),
            m3307A(37),
            m3308A(38),
            m3505A(39),
            m3513(40),
            m3333(41),
            m3334-ST(42),
            m3040(43),
            m3100R(44),
            notUsed45(45),
            notUsed46(46),
            m2810-hm(47),
            m2810-nmm(48),
            m3313S(49),
            m3314S(50),
            m3368(51),
            m3512S(52),
            m3513S(53),
            m3514S(54),
            m3522(55),
            m2912(56),
            m2914(57),
            notUsed58(58),
            m3301-75(59),
            m3301-93(60),
            m271x-nmm(61),
            m2705-hm(62),
            m2715-hm(63),
            m2813-nmm(64),
            m2814-nmm(65),
            m2813-hm(66),
            m2814-hm(67),
            m2803-hm(68),
            m2804-hm(69),
            m3395A(70),
            m3040S(71),
            m3502B(72),
            m3505B(73),
            m2715-F-hm(74),
            m2712-hm(75),
            m2712-F-hm(76),
            m2702-hm(77),
            m2702-C-hm(78),
            m2705-F-hm(79),
            m2702-F-hm(80),
            m2705-C-hm(81),
            m3902A(82),
            m2912A(83),
            m3313A(84),
            m3314A(85),
            m3307HD(86),
            m3328(87),
            m3904-2SM(88),
            m3910S-SM(89),
            m3800(90),
            m3910S-SD(91),
            m3904-4SM(92),
            m2915(93),
            m3910SA(94),
            m3910SA-SM(95),
            m3905(96),
            m2715B-hm(97),
            m2705B-hm(98),
            m2715B-F-hm(99),
            m2712B-hm(100),
            m2712B-F-hm(101),
            m2702B-C-hm(102),
            m3304A(103),
            m3486(104),
            m3308B(105),
            m2813SA-nmm(106),
            m2814SA-nmm(107),
            m3517SA(108),
            m810M(109),
            m3313SA(110),
            m3314SA(111),
            m3522A(112),
            m3504-ST(113),
            m3513SA(114),
            mAlcatel-Eth-nmm(115),
            mAlcatel-Eth-hm1(116),
            mAlcatel-Eth-hm(117),
            m2486-nmm(118),
            m2486-hm(119),
            m3174(120),
            m271xSA-nmm(121),
            m3299C(122),
            m3299U(123),
            m3299F(124)
            }

S3PsType ::=
            INTEGER {
            other(1),
            low(2),
            medium(3),
            high(4),
            redundantCapable(5),
            empty(6)
            }

IpxAddress ::=
            OCTET STRING (SIZE(10))

synoptics               OBJECT IDENTIFIER ::= { enterprises 45 }

products                OBJECT IDENTIFIER ::= { synoptics 1 }

s3SnmpAgent             OBJECT IDENTIFIER ::= { products 2 }

s3AgentSw               OBJECT IDENTIFIER ::= { s3SnmpAgent 1 }

s3AgentNetProtocol      OBJECT IDENTIFIER ::= { s3SnmpAgent 2 }

s3AgentIpProtocol       OBJECT IDENTIFIER ::= { s3AgentNetProtocol 1 }

s3AgentIpxProtocol      OBJECT IDENTIFIER ::= { s3AgentNetProtocol 2 }

s3AgentHw               OBJECT IDENTIFIER ::= { s3SnmpAgent 4 }

s3AgentLocImage         OBJECT IDENTIFIER ::= { s3SnmpAgent 6 }

series3000              OBJECT IDENTIFIER ::= { products 3 }

s3000Chassis            OBJECT IDENTIFIER ::= { series3000 1 }

s3000RedundantPs        OBJECT IDENTIFIER ::= { s3000Chassis 10 }

s3000Ethernet           OBJECT IDENTIFIER ::= { series3000 2 }

s3000EnetConcentrator   OBJECT IDENTIFIER ::= { s3000Ethernet 1 }

s3000EnetBoard          OBJECT IDENTIFIER ::= { s3000Ethernet 2 }

s3000EnetLocBridge      OBJECT IDENTIFIER ::= { s3000EnetBoard 2 }

s3000EnetRemBridge      OBJECT IDENTIFIER ::= { s3000EnetBoard 3 }

s3000EnetRouter         OBJECT IDENTIFIER ::= { s3000EnetBoard 4 }

s3000EnetPort           OBJECT IDENTIFIER ::= { s3000Ethernet 3 }

s3000EnetPlusStatistics OBJECT IDENTIFIER ::= { s3000Ethernet 10 }

s3000EnetPlusConc       OBJECT IDENTIFIER ::= { s3000EnetPlusStatistics 3 }

s3000TokenRing          OBJECT IDENTIFIER ::= { series3000 3 }

s3000TrBoard            OBJECT IDENTIFIER ::= { s3000TokenRing 2 }

s3000TrPort             OBJECT IDENTIFIER ::= { s3000TokenRing 3 }

s3000TrNmm              OBJECT IDENTIFIER ::= { s3000TokenRing 4 }

s3000TrNode             OBJECT IDENTIFIER ::= { s3000TokenRing 5 }

s3000TrRing             OBJECT IDENTIFIER ::= { s3000TokenRing 7 }

s3TrRingStats           OBJECT IDENTIFIER ::= { s3000TrRing 1 }

temporary               OBJECT IDENTIFIER ::= { synoptics 2 }

ieee8023                OBJECT IDENTIFIER ::= { temporary 1 }

registration            OBJECT IDENTIFIER ::= { synoptics 3 }

s3reg-3000              OBJECT IDENTIFIER ::= { registration 2 }

s3reg-3000-enetNMM      OBJECT IDENTIFIER ::= { s3reg-3000 1 }

s3reg-3000-trNMM        OBJECT IDENTIFIER ::= { s3reg-3000 2 }

s3reg-3030              OBJECT IDENTIFIER ::= { registration 3 }

s3reg-3030-enetNMM      OBJECT IDENTIFIER ::= { s3reg-3030 1 }

s3reg-3030-trNMM        OBJECT IDENTIFIER ::= { s3reg-3030 2 }

s3reg-2715              OBJECT IDENTIFIER ::= { registration 9 }

s3reg-2715-trNMM        OBJECT IDENTIFIER ::= { s3reg-2715 1 }

s3reg-281X              OBJECT IDENTIFIER ::= { registration 12 }

s3reg-281X-enetNMM      OBJECT IDENTIFIER ::= { s3reg-281X 1 }

s3AgentType OBJECT-TYPE
    SYNTAX  INTEGER {
            other(1),
            m3313(2),
            m3313M(3),
            m3314-ST(4),
            m3314M-ST(5),
            m2310(6),
            m3512(7),
            m3514(8),
            m332x(9),
            m3356(10),
            m332xS(11),
            m3910S(12),
            m3395(13),
            m3394(14),
            m3513(15),
            m331xS(16),
            m291x(17),
            m271x(18),
            m281x(19),
            m331xA(20),
            m3522(21),
            m2722(22),
            m281xSA(23),
            m810M(24),
            m351xSA(25),
            m331xSA(26),
            m271xSA(27),
            m2486(28)
            }
    ACCESS  read-only
    STATUS  mandatory
    DESCRIPTION
                "The 3000 series agent's Module type."
    ::= { s3AgentSw 1 }

s3AgentFwVer OBJECT-TYPE
    SYNTAX  INTEGER
    ACCESS  read-only
    STATUS  mandatory
    DESCRIPTION
                "The agent's module firmware version
                0=Rev A,1=Rev B,etc."
    ::= { s3AgentSw 2 }

s3AgentSwMajorVer OBJECT-TYPE
    SYNTAX  INTEGER
    ACCESS  read-only
    STATUS  mandatory
    DESCRIPTION
                "The agent major software version number.
                (version is specified as major.minor.maint or 3.0.1).
                Object is in decimal."
    ::= { s3AgentSw 3 }

s3AgentSwMinorVer OBJECT-TYPE
    SYNTAX  INTEGER
    ACCESS  read-only
    STATUS  mandatory
    DESCRIPTION
                "The agent minor software version number
                (version is specified as major.minor.maint or 3.0.1).
                Object is in decimal."
    ::= { s3AgentSw 4 }

s3AgentBootProtocol OBJECT-TYPE
    SYNTAX  INTEGER {
            other(1),
            bootp-tftp(2),
            tftp-only(3),
            ieee802-1e(4),
            proprietary(5),
            dll-download(6)
            }
    ACCESS  read-only
    STATUS  mandatory
    DESCRIPTION
                "Boot protocol used to load the module with its software.
                On Agents with the Local Load option the value return by
                this object is valid only if the MIB object
                s3LocImageLoadMode is remoteBoot(2) or localAsBackup(4)."
    ::= { s3AgentSw 5 }

s3AgentBootFile OBJECT-TYPE
    SYNTAX  DisplayString (SIZE(0..64))
    ACCESS  read-write
    STATUS  mandatory
    DESCRIPTION
                "The name of the boot file that is sent to the file
                server during boot time.  The actual boot protocol
                used to retrieve the file is determined by 
                s3AgentBootProtocol.

                This parameter will not take effect until written 
                into EEPROM (s3AgentWriteEeprom) and a reset
                (s3AgentReset) is issued. This parameter is used
                only if the s3AgentBootMode is set to use EEPROM."
    ::= { s3AgentSw 6 }

s3AgentAuthTrap OBJECT-TYPE
    SYNTAX  INTEGER {
            disable(1),
            enable(2)
            }
    ACCESS  read-write
    STATUS  deprecated
    DESCRIPTION
                "Enable or disable the use of authentication error
                trap generation.

                This parameter will take effect only after a restart
                (s3AgentRestart) is issued.  This parameter will not
                survive a reset (s3AgentReset) unless the specific
                NMM configuration file is updated to reflect the
                change.

                This object is now deprecated.  Managers should use
                the snmpEnableAuthenTraps object in MIB-II instead.
                This object is aliased to snmpEnableAuthenTraps.
                Changing either variable will change the other
                accordingly."
    ::= { s3AgentSw 7 }

s3AgentLocation OBJECT-TYPE
    SYNTAX  DisplayString (SIZE(0..64))
    ACCESS  read-write
    STATUS  deprecated
    DESCRIPTION
                "This is a informational string that could be used
                to show the physical location (i.e. area) of the
                NMM or concentrator.

                This parameter will take effect only after a restart
                (s3AgentRestart) is issued.  This parameter will not
                survive a reset (s3AgentReset) unless the specific
                NMM configuration file is updated to reflect the
                change.

                This object is now deprecated.  Managers should use
                the sysLocation object in MIB-II instead."
    ::= { s3AgentSw 8 }

s3AgentMibLevel OBJECT-TYPE
    SYNTAX  INTEGER
    ACCESS  read-only
    STATUS  mandatory
    DESCRIPTION
                "Used to determine current MIB release supported
                by agent.  The encoding of this object is of the
                following form: xyy, where x is the major version
                number and yy is the minor version number.  Thus,
                version 3.0 would be represented as 300,  version
                3.01 would be 301 and 3.1 would be 310.  Object is
                in decimal.  Values that correspond to each agent
                type and version are specified in the other
                SynOptics documentation."
    ::= { s3AgentSw 9 }

s3AgentFeatureLevel OBJECT-TYPE
    SYNTAX  INTEGER
    ACCESS  read-only
    STATUS  deprecated
    DESCRIPTION
                "Used to determine feature level of the agent.
                The encoding of this object is of the following
                form: xyy, where x is the major version 
                number and yy is the minor version number.  Thus,
                feature level version 1.0 would be represented as
                100, version 1.01 would be 101 and 1.1 would be 110.
                Object is in decimal. The current values are the
                following:
                  100 - 331x V3.x
                        - Basic Agent
                  100 - 351x
                        - Basic Agent
                  100 - 271x V3.x
                        - Basic Agent
                  101 - 281x V5.0 
                        - Basic Agent
                        - Dual Stack
                  102 - 331x V4.2.0
                        - Basic Agent
                        - Non Segmentable Chassis
                        - Ethernet Common board table
                        - Ethernet Command port table
                        - redundant power supply group
                  103 - 331xA V4.2.0
                        - Basic Agent
                        - Segmentable chassis
                        - Ethernet Common board table
                        - Ethernet Common port table
                        - redundant power supply group
                        - Ethernet plus statistics,
                  104 - 331xA V4.2.0
                        - Basic Agent
                        - Non-Segmentable chassis
                        - Ethernet Common board table
                        - Ethernet Common port table
                        - redundant power supply group
                        - Ethernet plus statistics,
                  109 - 331x V4.2.0
                        - Basic Agent
                        - Segmentable Chassis
                        - Ethernet Common board table
                        - Ethernet Common port table
                        - redundant power supply group
                  112 - 281x V5.1.0
                        - Basic Agent
                        - Dual Stack
                        - Network to MAC address mapping
                  113 - 331x V5.1.0
                        - Basic Agent
                        - Segmentable chassis
                        - Full Truffle Support
                        - Dual Stack
                        - Network to MAC address mapping
                  114 - 331x V5.1.0
                        - Basic Agent
                        - Non-Segmentable chassis
                        - Full Truffle Support
                        - Dual Stack
                        - Network to MAC address mapping
                  115 - 331xA V5.1.0
                        - Basic Agent
                        - Segmentable chassis
                        - Dual Stack
                        - Full Truffle Support
                        - Network to MAC address mapping
                  116 - 331xA V5.1.0
                        - Basic Agent
                        - Non-Segmentable chassis
                        - Dual Stack
                        - Full Truffle Support
                        - Network to MAC address mapping
                  200 - 331x V4.0 & V4.0.1
                        - Advanced Agent
                  200 - 271x V4.x
                        - Advanced Agent
                  200 - 351x V4.x
                        - Advanced Agent
                  200 - all FDDI Agents
                  201 - 331x V4.1.0, V4.1.1
                        - Advanced Agent
                        - redundant power supply group
                  202 - 331xS V4.1.0, V4.1.1
                        - Advanced Agent
                        - redundant power supply  group
                        - DS/SD traffic tables,
                        - Ethernet plus statistics,
                        - frame type distribution table
                        - frame length distribution table
                  203 - 281x V4.2.0
                        - Advanced Agent
                        - Dual Stack
                  204 - 331x V4.2.0
                        - Advanced Agent
                        - Non-Segmentable chassis
                        - Ethernet Common board table
                        - Ethernet Common port table
                        - redundant power supply group
                  205 - 331xS V4.2.0
                        - Advanced Agent
                        - Segmentable chassis
                        - Ethernet Common board table
                        - Ethernet Common port table
                        - redundant power supply  group
                        - DS/SD traffic tables,
                        - Ethernet plus statistics,
                        - frame type distribution table
                        - frame length distribution table
                  206 - 331xS V4.2.0
                        - Advanced Agent
                        - Non-Segmentable chassis
                        - Ethernet Common board table
                        - Ethernet Common port table
                        - redundant power supply  group
                        - DS/SD traffic tables,
                        - Ethernet plus statistics,
                        - frame type distribution table
                        - frame length distribution table
                  207 - 331xA V4.2.0
                        - Advanced agent
                        - Segmentable chassis
                        - Ethernet Common board table
                        - Ethernet Common port table
                        - redundant power supply  group
                        - Ethernet plus statistics,
                  208 - 331xA V4.2.0
                        - Advanced agent
                        - Non-Segmentable chassis
                        - Ethernet Common board table
                        - Ethernet Common port table
                        - redundant power supply  group
                        - Ethernet plus statistics,
                  209 - 331x V4.2.0
                        - Advanced agent
                        - Segmentable chassis
                        - Ethernet Common board table
                        - Ethernet Command port table
                        - redundant power supply group
                  212 - 331x V5.1.0
                        - Advanced Agent
                        - Dual Stack
                        - Network to MAC address mapping
                        - RMON Ether Stats, History, Alarm, Event Groups
                  213 - 281x V5.1.0
                        - Advanced Agent
                        - Segmentable chassis
                        - Full Truffle Support
                        - Dual Stack
                        - Network to MAC address mapping
                        - RMON Ether Stats, History, Alarm, Event Groups
                  214 - 331x V5.1.0
                        - Advanced Agent
                        - Non-Segmentable chassis
                        - Full Truffle Support
                        - Dual Stack
                        - Network to MAC address mapping
                        - RMON Ether Stats, History, Alarm, Event Groups
                  215 - 331xA V5.1.0
                        - Advanced Agent
                        - Segmentable chassis
                        - RMON Ether Stats, History, Alarm, Event Groups
                        - Dual Stack
                        - Full Truffle Support
                        - Network to MAC address mapping
                  216 - 331xA V5.1.0
                        - Advanced Agent
                        - Non-Segmentable chassis
                        - Full Truffle Support
                        - Dual Stack
                        - Network to MAC address mapping
                        - RMON Ether Stats, History, Alarm, Event Groups
                  217 - 331xS V5.1.0
                        - Advanced Agent
                        - Segmentable chassis
                        - Full Truffle Support
                        - Dual Stack
                        - Network to MAC address mapping
                        - RMON Ether Stats, History, Alarm, Event Groups
                        - Bulk table retrieval for traffic matrix
                  218 - 331xS V5.1.0
                        - Advanced Agent
                        - Non-Segmentable chassis
                        - Full Truffle Support
                        - Dual Stack
                        - Network to MAC address mapping
                        - RMON Ether Stats, History, Alarm, Event Groups
                        - Bulk table retrieval for traffic matrix"
    ::= { s3AgentSw 10 }

s3AgentMySlotId OBJECT-TYPE
    SYNTAX  INTEGER
    ACCESS  read-only
    STATUS  mandatory
    DESCRIPTION
                "Slot where this agent currently resides.  If
                hardware is unable to determine then a 0 should
                be returned."
    ::= { s3AgentSw 11 }

s3AgentUnAuthIp OBJECT-TYPE
    SYNTAX  IpAddress
    ACCESS  read-only
    STATUS  mandatory
    DESCRIPTION
                "This object contains the IP address of the last
                station that tried to access this agent with an
                invalid community string.  This object is used
                as a VarBind in an Authentication Trap PDU.  A get
                request will return the last value used, and will
                return the null address 0.0.0.0 if no 
                authentication traps have been sent."
    ::= { s3AgentSw 12 }

s3AgentUnAuthComm OBJECT-TYPE
    SYNTAX  OCTET STRING (SIZE(0..20))
    ACCESS  read-only
    STATUS  mandatory
    DESCRIPTION
                "This object contains the community string of the
                last unauthenticated attempt to access this agent.
                This object is used as a VarBind in an Authentication
                Trap PDU.  A get request will return the last value
                used, and will return the null string (length 0) if
                no authentication traps have been sent."
    ::= { s3AgentSw 13 }

s3AgentSwLicenseCode OBJECT-TYPE
    SYNTAX  DisplayString (SIZE(8))
    ACCESS  read-only
    STATUS  mandatory
    DESCRIPTION
                "The software license code assigned to this agent.
                This code is required for initializing the agent.
                The code consists of exactly eight printable
                characters."
    ::= { s3AgentSw 14 }

s3AgentPerformance OBJECT-TYPE
    SYNTAX  Counter
    ACCESS  read-only
    STATUS  mandatory
    DESCRIPTION
                "This counts the CPU idle time of the agent
                in units of 10 microseconds."
    ::= { s3AgentSw 15 }

s3AgentSwMaintVer OBJECT-TYPE
    SYNTAX  INTEGER
    ACCESS  read-only
    STATUS  mandatory
    DESCRIPTION
                "The agent software maintenance version number
                (version is specified as major.minor.maint or 3.0.1).
                Object is in decimal."
    ::= { s3AgentSw 16 }

s3AgentConfigLoadMode OBJECT-TYPE
    SYNTAX  INTEGER {
            other(1),
            remoteConfig(2),
            localConfig(3),
            localAsBackup(4)
            }
    ACCESS  read-only
    STATUS  mandatory
    DESCRIPTION
                "This indicates whether the agent should get
                configuration data from the network, use the local
                configuration data, or try the network first and then
                fall back to local configuration if the network load
                fails.  This object applies only to agents with boot
                prom support for agent configuration load options.

                This parameter will not take effect until written into
                EEPROM (s3AgentWriteEeprom) and a reset (s3AgentReset)
                is issued.

                ***ACCESS VARIATION - changed access from read-write"
    ::= { s3AgentSw 17 }

s3AgentConfigActualSource OBJECT-TYPE
    SYNTAX  INTEGER {
            other(1),
            remoteConfig(2),
            localConfig(3)
            }
    ACCESS  read-only
    STATUS  mandatory
    DESCRIPTION
                "This indicates whether the agent loaded configuration
                data from the network or used the local configuration
                data."
    ::= { s3AgentSw 18 }

s3AgentMgmtProtoMode OBJECT-TYPE
    SYNTAX  INTEGER {
            other(1),
            ip(2),
            ipx(3),
            ipAndIpx(4)
            }
    ACCESS  read-write
    STATUS  mandatory
    DESCRIPTION
                "This indicates from which network transports over
                which the agent will accept SNMP requests.  This object
                only applies to agents with IP and IPX dual stack support.

                This parameter will not take effect until written into
                EEPROM (s3AgentWriteEeprom) and a reset (s3AgentReset)
                or a restart (s3AgentRestart) is issued."
    ::= { s3AgentSw 19 }

s3AgentActualMgmtProtocol OBJECT-TYPE
    SYNTAX  INTEGER {
            other(1),
            ip(2),
            ipx(3),
            ipAndIpx(4)
            }
    ACCESS  read-only
    STATUS  mandatory
    DESCRIPTION
                "This indicates which network transports over which
                the agent will currently accept SNMP requests."
    ::= { s3AgentSw 20 }

s3AgentIpAddr OBJECT-TYPE
    SYNTAX  IpAddress
    ACCESS  read-write
    STATUS  mandatory
    DESCRIPTION
                "The Agent's administrative IP address. The
                current operational IP address can be obtained
                by the ipAdEntAddr entry in the ipAddrTable.

                This parameter will take effect only after a
                restart (s3AgentRestart) is issued. This parameter
                will not survive a reset (s3AgentReset) unless it
                is written into EEPROM (s3AgentWriteEeprom). This
                parameter is used only if the s3AgentBootMode is
                set to use EEPROM."
    ::= { s3AgentIpProtocol 1 }

s3AgentNetMask OBJECT-TYPE
    SYNTAX  IpAddress
    ACCESS  read-write
    STATUS  mandatory
    DESCRIPTION
                "The Agent's administrative subnet mask. The
                current operational subnet mask can be obtained
                by the ipAdEntNetMask entry in the ipAddrTable.

                This parameter will take effect only after a
                restart (s3AgentRestart) is issued. This parameter
                will not survive a reset (s3AgentReset) unless it 
                is written into EEPROM (s3AgentWriteEeprom). This
                parameter is used only if the agentBootMode is set
                to use EEPROM.

                NOTE:  The Model 331x (3313, 3313M, 3314-ST,
                3314M-ST) Ethernet NMM agents do not store this
                parameter in EEPROM, so for these agents the subnet
                mask configuration must be downloaded in the
                configuration file."
    ::= { s3AgentIpProtocol 2 }

s3AgentDefaultGateway OBJECT-TYPE
    SYNTAX  IpAddress
    ACCESS  read-write
    STATUS  mandatory
    DESCRIPTION
                "The Agent's administrative default gateway IP
                address. The current operational default gateway's
                IP address can be obtained from the ipRoutingTable.

                This parameter will take effect only after a
                restart (s3AgentRestart) is issued.  This parameter
                will not survive a reset (s3AgentReset) unless it 
                is written into EEPROM (s3AgentWriteEeprom).  This
                parameter is used only if the agentBootMode is set
                to use EEPROM."
    ::= { s3AgentIpProtocol 3 }

s3AgentBootServerAddr OBJECT-TYPE
    SYNTAX  IpAddress
    ACCESS  read-write
    STATUS  mandatory
    DESCRIPTION
                "The IP address to which the requests for boot files
                are sent. The protocol used to retrieve the boot
                files is determined by object s3AgentBootProtocol.

                This parameter will not take effect until until
                written into EEPROM (s3AgentWriteEeprom) and a
                reset (s3AgentReset) is issued. This parameter is
                used only if the s3AgentBootMode is set to use EEPROM."
    ::= { s3AgentIpProtocol 4 }

s3AgentSecDefaultGateway OBJECT-TYPE
    SYNTAX  IpAddress
    ACCESS  read-write
    STATUS  mandatory
    DESCRIPTION
                "The agent's administrative secondary default
                gateway IP address. This default gateway's IP
                address will be used when the primary default
                gateway (s3AgentDefaultGateway) is determined
                unreachable.

                This parameter will not survive a reset (s3AgentReset)
                unless it is written into EEPROM (s3AgentWriteEeprom)."
    ::= { s3AgentIpProtocol 5 }

s3AgentPingDefaultRtrSwitch OBJECT-TYPE
    SYNTAX  INTEGER {
            other(1),
            on(2),
            off(3)
            }
    ACCESS  read-write
    STATUS  mandatory
    DESCRIPTION
                "Controls whether the agent will periodically send
                out the icmp echos (pings) to the default router(s).
                The values are:
                  other(1)...unknown or other
                  on(2)......agent will periodically send out pings
                               to the default router(s).
                  off(3).....agent won't send out the pings to the
                               default router(s)."
    ::= { s3AgentIpProtocol 6 }

s3AgentPingDefaultRtrTime OBJECT-TYPE
    SYNTAX  TimeTicks
    ACCESS  read-write
    STATUS  mandatory
    DESCRIPTION
                "The time interval that the agent uses to send
                out the pings periodically to the default router(s)
                to check if the router(s) are still reachable."
    ::= { s3AgentIpProtocol 7 }

s3AgentBootRouter OBJECT-TYPE
    SYNTAX  IpAddress
    ACCESS  read-write
    STATUS  mandatory
    DESCRIPTION
                "The default route IP address used at boot
                time to download the NMM's agent configuration
                and image files from the TFTP server.

                This parameter will not survive a reset
                (s3AgentReset) unless it is written into EEPROM
                (s3AgentWriteEeprom)."
    ::= { s3AgentIpProtocol 8 }

s3AgentIpxAddr OBJECT-TYPE
    SYNTAX  IpxAddress
    ACCESS  read-only
    STATUS  mandatory
    DESCRIPTION
                "The current IPX address used by this agent."
    ::= { s3AgentIpxProtocol 1 }

s3AgentUnAuthIpx OBJECT-TYPE
    SYNTAX  IpxAddress
    ACCESS  read-only
    STATUS  mandatory
    DESCRIPTION
                "This object contains the IPX address of the last
                station that tried to access this agent with an
                invalid community string. This object is used as
                a VarBind in an authentication trap PDU.  A GET
                request will return the last value used, and will
                return an address of zeros if no IPX
                authentication trap has been sent."
    ::= { s3AgentIpxProtocol 3 }

s3AgentTrapReceiverTable OBJECT-TYPE
    SYNTAX  SEQUENCE OF S3AgentTrapReceiverEntry
    ACCESS  not-accessible
    STATUS  mandatory
    DESCRIPTION
                "Table containing list of NMS's that are to receive
                traps generated by this NMM."
    ::= { s3SnmpAgent 3 }

s3AgentTrapReceiverEntry OBJECT-TYPE
    SYNTAX  S3AgentTrapReceiverEntry
    ACCESS  not-accessible
    STATUS  mandatory
    DESCRIPTION
                "A destination address and community string to a
                particular trap server, along with a trap filter
                and entry aging capability."
    INDEX   { s3AgentTrapRcvrNetAddress }
    ::= { s3AgentTrapReceiverTable 1 }

S3AgentTrapReceiverEntry ::= SEQUENCE {
    s3AgentTrapRcvrStatus
        INTEGER,
    s3AgentTrapRcvrNetAddress
        OCTET STRING,
    s3AgentTrapRcvrComm
        OCTET STRING,
    s3AgentTrapRcvrAgeTime
        TimeTicks
    }

s3AgentTrapRcvrStatus OBJECT-TYPE
    SYNTAX  INTEGER {
            other(1),
            valid(2),
            invalid(3)
            }
    ACCESS  read-write
    STATUS  mandatory
    DESCRIPTION
                "Setting this object to the value invalid(3) has
                the effect of invalidating the corresponding entry
                in the s3AgentTrapReceiverTable.  That is, it 
                effectively disassociates the address identified
                with the entry by removing the entry from the table.
                On a read the value of valid(2) should be returned
                if the entry contains a valid record, or invalid(3)
                should be returned if the entry contains an invalid
                record."
    ::= { s3AgentTrapReceiverEntry 1 }

s3AgentTrapRcvrNetAddress OBJECT-TYPE
    SYNTAX  OCTET STRING (SIZE(4))
    ACCESS  read-write
    STATUS  mandatory
    DESCRIPTION
                "IP address for trap server that is to receive
                the trap."
    ::= { s3AgentTrapReceiverEntry 2 }

s3AgentTrapRcvrComm OBJECT-TYPE
    SYNTAX  OCTET STRING (SIZE(0..20))
    ACCESS  read-write
    STATUS  mandatory
    DESCRIPTION
                "Community string used for traps sent to this
                trap receiver."
    ::= { s3AgentTrapReceiverEntry 3 }

s3AgentTrapRcvrAgeTime OBJECT-TYPE
    SYNTAX  TimeTicks
    ACCESS  read-write
    STATUS  mandatory
    DESCRIPTION
                "This is the time interval used to age entries out
                of the trap receiver table.  The default value if
                not specified will be 0, or infinite, never to be
                aged out."
    ::= { s3AgentTrapReceiverEntry 4 }

s3AgentStatus OBJECT-TYPE
    SYNTAX  INTEGER {
            offline(1),
            online(2)
            }
    ACCESS  read-write
    STATUS  mandatory
    DESCRIPTION
                "This indicates whether the NMM is online(2) and
                operating, or offline(1) (ie: not connected to the
                concentrator backplane).

                ***ACCESS VARIATION - changed access from read-only"
    ::= { s3AgentHw 1 }

s3AgentMdaHwVer OBJECT-TYPE
    SYNTAX  INTEGER
    ACCESS  read-only
    STATUS  mandatory
    DESCRIPTION
                "The network management module's MDA hardware
                version number  (0=Rev. A, 1=Rev. B, etc.)."
    ::= { s3AgentHw 2 }

s3AgentMode OBJECT-TYPE
    SYNTAX  INTEGER {
            primary(1),
            secondary(2),
            other(3)
            }
    ACCESS  read-only
    STATUS  mandatory
    DESCRIPTION
                "This indicates whether the NMM is operating in
                primary(1) or secondary(2) mode.

                ***ACCESS VARIATION - changed access from read-write"
    ::= { s3AgentHw 3 }

s3AgentReset OBJECT-TYPE
    SYNTAX  INTEGER {
            noReset(1),
            reset(2)
            }
    ACCESS  read-write
    STATUS  mandatory
    DESCRIPTION
                "Network management module reset status.  Writing
                a reset(2) to this object will reset the NMM and
                perform a download and restart."
    ::= { s3AgentHw 4 }

s3AgentRestart OBJECT-TYPE
    SYNTAX  INTEGER {
            noRestart(1),
            restart(2)
            }
    ACCESS  read-write
    STATUS  mandatory
    DESCRIPTION
                "Network management module restart status.
                Writing a restart(2) to this object will restart
                the NMM.  This initializes all the counters,
                re-reads the EEPROM data structure and starts
                executing from the beginning of the code."
    ::= { s3AgentHw 5 }

s3AgentBootMode OBJECT-TYPE
    SYNTAX  INTEGER {
            eeprom(1),
            net(2),
            otherCase(3)
            }
    ACCESS  read-write
    STATUS  mandatory
    DESCRIPTION
                "The method for obtaining boot parameter information.
                The possible values are:
                  eeprom(1)......get boot info from eeprom
                  net(2).........get boot info from remote server
                  otherCase(3)...not eeprom or net

                This parameter will not take effect until written
                into EEPROM (s3AgentWriteEeprom) and a reset
                (s3AgentReset) is issued.

                Note: In previous versions of this MIB the name
                      associated with the value '2' was 'other',
                      which implied the same meaning as it does
                      now.  Thus to prevent confusion, the name
                      for value '3' was chosen to be 'otherCase'."
    ::= { s3AgentHw 6 }

s3AgentWriteEeprom OBJECT-TYPE
    SYNTAX  INTEGER {
            noWriteEeprom(1),
            writeEeprom(2)
            }
    ACCESS  read-write
    STATUS  mandatory
    DESCRIPTION
                "Network management module EEPROM write status.
                Writing a (2) to this object will write the contents
                of current EEPROM data structure in the EEPROM."
    ::= { s3AgentHw 7 }

s3AgentBaudRate OBJECT-TYPE
    SYNTAX  Gauge
    ACCESS  read-write
    STATUS  mandatory
    DESCRIPTION
                "Specifies the baud rate in bits per second of
                either the internal modem or the RS-232 port.

                This parameter will take effect only after a
                restart (s3AgentRestart) is issued.  This parameter
                will not survive a reset (s3AgentReset) unless
                the specific NMM configuration file is updated
                to reflect the change."
    ::= { s3AgentHw 8 }

s3AgentInitString OBJECT-TYPE
    SYNTAX  OCTET STRING (SIZE(0..64))
    ACCESS  read-write
    STATUS  mandatory
    DESCRIPTION
                "This is the initialization string used to establish
                the out-of-band connection. (i.e. could contain the
                string ATDT,415-960-1100 for an internal or external
                modem). This is used as a hint for the network manager
                since this string is not used by the agent to initiate
                a connection to a management station.

                This parameter will take effect only after a restart
                (s3AgentRestart) is issued.  This parameter will not
                survive a reset (s3AgentReset) unless the specific
                NMM configuration file is updated to reflect
                the change."
    ::= { s3AgentHw 9 }

s3AgentEepromSize OBJECT-TYPE
    SYNTAX  INTEGER
    ACCESS  read-only
    STATUS  mandatory
    DESCRIPTION
                "The size of the EEPROM of the agent in units of bytes."
    ::= { s3AgentHw 10 }

s3AgentEpromSize OBJECT-TYPE
    SYNTAX  INTEGER
    ACCESS  read-only
    STATUS  mandatory
    DESCRIPTION
                "The size of the EPROM of the agent in units of bytes."
    ::= { s3AgentHw 11 }

s3AgentDramSize OBJECT-TYPE
    SYNTAX  INTEGER
    ACCESS  read-only
    STATUS  mandatory
    DESCRIPTION
                "The size of the DRAM of the agent in units of bytes."
    ::= { s3AgentHw 12 }

s3AgentHexDisplay OBJECT-TYPE
    SYNTAX  DisplayString (SIZE(0..4))
    ACCESS  read-only
    STATUS  mandatory
    DESCRIPTION
                "The current 4 ASCII character display of the agent.

                Agents with no hex display hardware should return a
                zero length string."
    ::= { s3AgentHw 13 }

s3AgentFlashStatus OBJECT-TYPE
    SYNTAX  INTEGER {
            other(1),
            ok(2),
            fail(3)
            }
    ACCESS  read-only
    STATUS  mandatory
    DESCRIPTION
                "This indicates the operational status of the flash
                device of the agent.  A fail(3) indicates that either
                the flash device configuration on board is not valid
                or the flash EEPROMs on the board have failed."
    ::= { s3AgentHw 14 }

s3LocImageValid OBJECT-TYPE
    SYNTAX  INTEGER {
            other(1),
            localImageValid(2),
            localImageInvalid(3)
            }
    ACCESS  read-only
    STATUS  mandatory
    DESCRIPTION
                "This indicates whether the agent has a valid local
                code image on board.  An EPROM checksum failure would
                cause the agent to return localImageInvalid(3)."
    ::= { s3AgentLocImage 1 }

s3LocImageMajorVersion OBJECT-TYPE
    SYNTAX  INTEGER
    ACCESS  read-only
    STATUS  mandatory
    DESCRIPTION
                "The major software version number of the
                locally-stored image.  This object applies only to
                agents with valid local image.  Other agents 
                should return zero."
    ::= { s3AgentLocImage 2 }

s3LocImageMinorVersion OBJECT-TYPE
    SYNTAX  INTEGER
    ACCESS  read-only
    STATUS  mandatory
    DESCRIPTION
                "The minor software version number of the
                locally-stored image.  This object applies only
                to agents with valid local image.  Other agents
                should return zero."
    ::= { s3AgentLocImage 3 }

s3LocImageLoadMode OBJECT-TYPE
    SYNTAX  INTEGER {
            other(1),
            remoteBoot(2),
            localBoot(3),
            localAsBackup(4),
            remoteNoUpdate(5),
            remoteNewUpdate(6),
            localAutoUpdate(7)
            }
    ACCESS  read-write
    STATUS  mandatory
    DESCRIPTION
                "This indicates whether the agent should get code
                from the network, use a local image, or try the
                network first and then fall back to local image if 
                the network boot fails. The localBoot(3) and
                localAsBackup(4) values apply only to agents with
                local load option. Note: on agents that have
                no local storage, either remoteBoot(2), or
                remoteNoUpdate(5) may be specified, however
                the value remoteBoot(2) is prefered due to
                backwards compatibility "
    ::= { s3AgentLocImage 4 }

s3LocImageActualSource OBJECT-TYPE
    SYNTAX  INTEGER {
            other(1),
            remoteImage(2),
            localImage(3)
            }
    ACCESS  read-only
    STATUS  mandatory
    DESCRIPTION
                "This indicates whether the agent loaded code from
                the network or used a local image.  When the the
                ImageLoadMode is localAsBackup, this variable
                indicates whether the network load was successful."
    ::= { s3AgentLocImage 5 }

s3LocImageMaintVersion OBJECT-TYPE
    SYNTAX  INTEGER
    ACCESS  read-only
    STATUS  mandatory
    DESCRIPTION
                "The maintenance software version number of the
                locally-stored image.  This object applies only
                to agents with valid local image.  Other agents
                should return zero."
    ::= { s3AgentLocImage 6 }

s3AgentIpxTrapReceiverTable OBJECT-TYPE
    SYNTAX  SEQUENCE OF S3AgentIpxTrapReceiverEntry
    ACCESS  not-accessible
    STATUS  mandatory
    DESCRIPTION
                "Table containing list of NMS's that are to receive
                traps generated by this NMM sent over IPX."
    ::= { s3SnmpAgent 7 }

s3AgentIpxTrapReceiverEntry OBJECT-TYPE
    SYNTAX  S3AgentIpxTrapReceiverEntry
    ACCESS  not-accessible
    STATUS  mandatory
    INDEX   { s3AgentIpxTrapRcvrNetAddress }
    ::= { s3AgentIpxTrapReceiverTable 1 }

S3AgentIpxTrapReceiverEntry ::= SEQUENCE {
    s3AgentIpxTrapRcvrStatus
        INTEGER,
    s3AgentIpxTrapRcvrNetAddress
        IpxAddress,
    s3AgentIpxTrapRcvrComm
        OCTET STRING,
    s3AgentIpxTrapRcvrAgeTime
        TimeTicks
    }

s3AgentIpxTrapRcvrStatus OBJECT-TYPE
    SYNTAX  INTEGER {
            other(1),
            valid(2),
            invalid(3)
            }
    ACCESS  read-write
    STATUS  mandatory
    DESCRIPTION
                "Action/status for the row. The values that can
                be written are:
                  valid(2).....create row
                  invalid(3)...delete row

                The values that can be read are:
                  other(1).....some unknown case
                  valid(2).....row is valid
                  invalid(3)...row is invalid

                Setting this object to the value invalid(3) has the
                effect of invalidating the corresponding entry in
                the s3AgentIpxTrapReceiverTable.  That is, it
                effectively disassociates the address identified
                with the entry by removing the entry from the table
                On a read the value of valid(2) should be returned
                if the entry contains a valid record, or invalid(3)
                should be returned if the entry contains an invalid
                record."
    ::= { s3AgentIpxTrapReceiverEntry 1 }

s3AgentIpxTrapRcvrNetAddress OBJECT-TYPE
    SYNTAX  IpxAddress
    ACCESS  read-write
    STATUS  mandatory
    DESCRIPTION
                "IPX address for trap server that is to receive the
                trap.  The value may only be written when the row
                is created."
    ::= { s3AgentIpxTrapReceiverEntry 2 }

s3AgentIpxTrapRcvrComm OBJECT-TYPE
    SYNTAX  OCTET STRING (SIZE(0..20))
    ACCESS  read-write
    STATUS  mandatory
    DESCRIPTION
                "Community string used for traps sent to this
                trap receiver."
    ::= { s3AgentIpxTrapReceiverEntry 3 }

s3AgentIpxTrapRcvrAgeTime OBJECT-TYPE
    SYNTAX  TimeTicks
    ACCESS  read-write
    STATUS  mandatory
    DESCRIPTION
                "This is the time interval used to age entries out of
                the trap receiver table.  The default value if not
                specified will be 0, or infinite, never to be 
                aged out."
    ::= { s3AgentIpxTrapReceiverEntry 4 }

s3ChassisType OBJECT-TYPE
    SYNTAX  SnpxChassisType
    ACCESS  read-only
    STATUS  mandatory
    DESCRIPTION
                "The chassis type."
    ::= { s3000Chassis 1 }

s3ChassisBkplType OBJECT-TYPE
    SYNTAX  SnpxBackplaneType
    ACCESS  read-only
    STATUS  mandatory
    DESCRIPTION
                "The chassis backplane type."
    ::= { s3000Chassis 2 }

s3ChassisBkplRev OBJECT-TYPE
    SYNTAX  INTEGER
    ACCESS  read-only
    STATUS  mandatory
    DESCRIPTION
                "The chassis backplane revision."
    ::= { s3000Chassis 3 }

s3ChassisPsType OBJECT-TYPE
    SYNTAX  S3PsType
    ACCESS  read-only
    STATUS  mandatory
    DESCRIPTION
                "The chassis power supply type.  This value is
                valid only when the backplane type is not
                other(1).  If the chassis has a redundant backplane,
                the agent returns redundantCapable(5), even if only
                one power supply is installed.  The objects
                s3RedPsPrimaryConfig and s3RedPsSecondaryConfig
                should be consulted to determine the installed
                power supply type(s) with redundant backplanes."
    ::= { s3000Chassis 4 }

s3ChassisPsStatus OBJECT-TYPE
    SYNTAX  INTEGER {
            ok(1),
            primaryFail(2),
            secondaryFail(3),
            bothFail(4)
            }
    ACCESS  read-only
    STATUS  mandatory
    DESCRIPTION
                "The chassis power supply status."
    ::= { s3000Chassis 5 }

s3ChassisFanStatus OBJECT-TYPE
    SYNTAX  INTEGER {
            ok(1),
            fail(2),
            other(3)
            }
    ACCESS  read-only
    STATUS  mandatory
    DESCRIPTION
                "The status of the chassis cooling fan."
    ::= { s3000Chassis 6 }

s3SlotConfigTable OBJECT-TYPE
    SYNTAX  SEQUENCE OF S3SlotConfigEntry
    ACCESS  not-accessible
    STATUS  mandatory
    DESCRIPTION
                "The chassis slot configuration table."
    ::= { s3000Chassis 7 }

s3SlotConfigEntry OBJECT-TYPE
    SYNTAX  S3SlotConfigEntry
    ACCESS  not-accessible
    STATUS  mandatory
    DESCRIPTION
                "What type of module is in each slot of the chassis."
    INDEX   { s3SlotNumber }
    ::= { s3SlotConfigTable 1 }

S3SlotConfigEntry ::= SEQUENCE {
    s3SlotNumber
        INTEGER,
    s3SlotModuleId
        INTEGER,
    s3SlotModuleType
        S3ModuleType,
    s3SlotModuleDescr
        DisplayString,
    s3SlotModuleLed
        OCTET STRING,
    s3SlotModuleMdaId
        INTEGER
    }

s3SlotNumber OBJECT-TYPE
    SYNTAX  INTEGER
    ACCESS  read-only
    STATUS  mandatory
    DESCRIPTION
                "The 3000 Chassis slot number. Valid entries are 1-12."
    ::= { s3SlotConfigEntry 1 }

s3SlotModuleId OBJECT-TYPE
    SYNTAX  INTEGER
    ACCESS  read-only
    STATUS  mandatory
    DESCRIPTION
                "ID for the module.  Values are specified in
                SynOptics technical documents."
    ::= { s3SlotConfigEntry 2 }

s3SlotModuleType OBJECT-TYPE
    SYNTAX  S3ModuleType
    ACCESS  read-only
    STATUS  deprecated
    DESCRIPTION
                "The type of module this entry represents.
                Values are specified in SynOptics technical documents."
    ::= { s3SlotConfigEntry 3 }

s3SlotModuleDescr OBJECT-TYPE
    SYNTAX  DisplayString (SIZE(0..128))
    ACCESS  read-only
    STATUS  mandatory
    DESCRIPTION
                "Module description.  Values are specified in
                SynOptics technical documents."
    ::= { s3SlotConfigEntry 4 }

s3SlotModuleLed OBJECT-TYPE
    SYNTAX  OCTET STRING (SIZE(8))
    ACCESS  read-only
    STATUS  mandatory
    DESCRIPTION
                "Status of the module LEDs.  Format is specified in
                SynOptics technical documents.  NOTE: the 291x FDDI
                workgroup concentrators actually return a string
                with size of 10."
    ::= { s3SlotConfigEntry 5 }

s3SlotModuleMdaId OBJECT-TYPE
    SYNTAX  INTEGER
    ACCESS  read-only
    STATUS  mandatory
    DESCRIPTION
                "ID of the medium-dependent part of the board.
                The value is board dependent. Values are specified
                in SynOptics technical documents."
    ::= { s3SlotConfigEntry 6 }

s3CommonBoardTable OBJECT-TYPE
    SYNTAX  SEQUENCE OF S3CommonBoardEntry
    ACCESS  not-accessible
    STATUS  mandatory
    DESCRIPTION
                "A table containing information about the boards
                currently plugged into the 3000 Chassis.  This
                board table contains an entry for each non-empty
                slot in the s3SlotConfigTable, EXCEPT for those
                slots containing Retiming Modules.

                All of the information in this board table is
                retrievable using the NMI commands that are common
                to all boards integrated into the SynOptics
                Series 3000 Concentrators."
    ::= { s3000Chassis 8 }

s3CommonBoardEntry OBJECT-TYPE
    SYNTAX  S3CommonBoardEntry
    ACCESS  not-accessible
    STATUS  mandatory
    DESCRIPTION
                "A table entry containing information about a
                single Board currently plugged into the 3000
                Chassis. These values can be retrieved using the
                common board NMI commands."
    INDEX   { s3CommonBoardIndex }
    ::= { s3CommonBoardTable 1 }

S3CommonBoardEntry ::= SEQUENCE {
    s3CommonBoardIndex
        INTEGER,
    s3CommonBoardId
        INTEGER,
    s3CommonBoardHwVer
        INTEGER,
    s3CommonBoardStatus
        INTEGER,
    s3CommonBoardReset
        INTEGER,
    s3CommonBoardPartStatus
        INTEGER,
    s3CommonBoardNmCntlStatus
        INTEGER,
    s3CommonBoardPsStatus
        INTEGER,
    s3CommonBoardPartTime
        TimeTicks
    }

s3CommonBoardIndex OBJECT-TYPE
    SYNTAX  INTEGER
    ACCESS  read-only
    STATUS  mandatory
    DESCRIPTION
                "A unique value for each board. Its value ranges
                between 1 and 12. The value for each board must
                remain constant at least from one re-initialization
                of the entity's network management system to the
                next re-initialization."
    ::= { s3CommonBoardEntry 1 }

s3CommonBoardId OBJECT-TYPE
    SYNTAX  INTEGER {
            m331x(1),
            m3302(2),
            m332x(3),
            m3304ST(4),
            m3305(5),
            m333x(6),
            m3307(7),
            m3308(8),
            m3301(9),
            m3904(10),
            m3902(11),
            m3910S(12),
            m331xS(14),
            m3100R(15),
            m3502(16),
            m3502A(17),
            m353x(18),
            m3040(19),
            m3505(20),
            m3505A(21),
            m355x(22),
            m3040S(23),
            m351x(24),
            m332xS(25),
            m338x(26),
            m3328(27),
            m3395(28),
            m3394(29),
            m3522(30),
            m3395A(31),
            m3800(32),
            m3368(36),
            m3308A(38),
            m2810nmm(39),
            m2810hm(40),
            m3301ohms75(41),
            m3301ohms93(42),
            m2912(43),
            m2914(44),
            m3502B(45),
            m3505B(46),
            m3307HD(47),
            m2702Fhm(48),
            m2712Fhm(49),
            m2712hm(50),
            m2702hm(51),
            m2813nmm(52),
            m2813hm(53),
            m2814hm(54),
            m2803hm(55),
            m3356(56),
            m2814nmm(57),
            m2804hm(58),
            m2702Chm(59),
            m2715Fhm(60),
            m2705Fhm(61),
            m2705Chm(62),
            m3902A(63),
            m2912A(64),
            m271xnmm(65),
            m2715hm(66),
            m3910SSD(67),
            m3313A(68),
            m3314A(69),
            m3304A(70),
            m3910SA(71),
            m2705hm(72),
            m3905(73),
            m2915(74),
            m2715Bhm(75),
            m2705Bhm(76),
            m2715BFhm(77),
            m2712Bhm(78),
            m2712BFhm(79),
            m2702BChm(80),
            m3486(82),
            m810m(88),
            m3517SA(101),
            m3308B(102),
            m2813SAnmm(103),
            m2814SAnmm(104),
            m3313SA(105),
            m3314SA(106),
            m3174(107),
            m3522A(108),
            m3513SA(109),
            m271xSAnmm(110),
            m3299C(116),
            m3299U(117),
            m3299F(119),
            mAlcatelEthConcnmm(250),
            mAlcatelEthConchm(251)
            }
    ACCESS  read-only
    STATUS  mandatory
    DESCRIPTION
                "This is the ID of the board, which is 'hard-coded' in the
                board, and identifies the board's basic functionality.
                Some boards have the capability to change aspects of
                their functionality, such as media type, interface types,
                or power supply wattages, by plugging in different daughter
                cards.  Other boards may identify the type of cable plugged
                into them.  The boards that have these capabilities use 
                different values for the object s3SlotModuleMda to identify
                the changable portion of the functionality currently used.
                Boards that do not support these capabilities typically set
                the object s3SlotModuleMda to 255 or zero.  The combination
                of the value of this object and the s3SlotModuleMda object
                are then mapped by software to determine the type of
                module (i.e., s3SlotModuleType).

                Notes:  1.)  The object s3SlotModuleType is marked
                             as deprecated.
                        2.)  Agents do not implement a complete mapping of
                             s3CommonBoardId and s3SlotModuleMda to
                             s3SlotModuleType.  The mapping that is performed
                             pertains to the media type of the agent.

                The possible values for this object are:
                  m331x(1)...................331x Ethernet NMM
                  m3302(2)...................3302 Ethernet STP Host
                  m332x(3)...................332x Ethernet Local Bridge
                  m3304ST(4).................3304 Ethernet FOIRL-ST Host
                  m3305(5)...................3305 Ethernet UTP Host
                  m333x(6)...................333x Ethernet Repeater/Retiming
                  m3307(7)...................3307 Ethernet 50 Pin UTP Host
                  m3308(8)...................3308 10BaseT UTP Host
                  m3301(9)...................3301 10Base2 Thin Net Host
                  m3904(10)..................3904 FDDI Multimode Fiber Host
                  m3902(11)..................3902 FDDI STP Host
                  m3910S(12).................3910S FDDI NMM
                  m331xS(14).................331xS Ethernet NMM
                  m3100R(15).................3100R Power Supply Summing
                  m3502(16)..................3502 Token Ring Passive STP Host
                  m3502A(17).................3502A Token Ring Passive STP/UTP Host
                  m353x(18)..................353x Token Ring RI/RO Repeater
                  m3040(19)..................3040 Network Control Engine (NCE)
                  m3505(20)..................3505 Token Ring Active UTP Host
                  m3505A(21).................3505A Token Ring Active UTP Host
                  m355x(22)..................355x Token Ring FOIRL RI/RO Repeater
                  m3040S(23).................3040S Network Control Engine
                  m351x(24)..................351x Token Ring NMM
                  m332xS(25).................332xS Ethernet High Speed Local Bridge
                  m338x(26)..................338x Ethernet Remote Router
                  m3328(27)..................3328 Ethernet Switching Engine (ESE)
                  m3395(28)..................3395 Terminal Server
                  m3394(29)..................3394 LattisTalk Router/Repeater
                  m3522(30)..................3522 Token Ring Local Bridge
                  m3395A(31).................3395A Terminal Server
                  m3800(32)..................3800 Multimedia Router
                  m3368(36)..................3368 Ethernet LattisSecure Host
                  m3308A(38).................3308A 10BaseT Host
                  m2810nmm(39)...............2810 Ethernet NMM
                  m2810hm(40)................2810 Ethernet Host
                  m3301ohms75(41)............3301-75 Ethernet Thin Net Host (75-ohm)
                  m3301ohms93(42)............3301-93 Ethernet Thin Net Host (93-ohm)
                  m2912(43)..................2912 FDDI STP Concentrator
                  m2914(44)..................2914 FDDI Fiber Concentrator
                  m3502B(45).................3502B Token Ring Passive STP/UTP Host
                  m3505B(46).................3505B Token Ring Active STP/UTP Host
                  m3307HD(47)................3307HD Ethernet 100 Pin UTP Host
                  m2702Fhm(48)...............2702F Token Ring Passive Host
                  m2712Fhm(49)...............2712F Token Ring Passive Host
                  m2712hm(50)................2712 Token Ring Passive Host
                  m2702hm(51)................2702 Token Ring Passive Host
                  m2813nmm(52)...............2813 Ethernet NMM
                  m2813hm(53)................2813 Ethernet Host
                  m2814hm(54)................2814 Ethernet Host
                  m2803hm(55)................2803 Ethernet Host
                  m3356(56)..................3356 Ethernet Remote Bridge
                  m2814nmm(57)...............2814 Ethernet NMM
                  m2804hm(58)................2804 Ethernet Host
                  m2702Chm(59)...............2702C Token Ring Passive Host
                  m2715Fhm(60)...............2715F Token Ring Active Host
                  m2705Fhm(61)...............2705F Token Ring Active Host
                  m2705Chm(62)...............2705C Token Ring Active Host
                  m3902A(63).................3902A FDDI STP Host
                  m2912A(64).................2912A FDDI STP Concentrator
                  m271xnmm(65)...............271x Token Ring NMM
                  m2715hm(66)................2715 Token Ring Active Host
                  m3910SSD(67)...............3910S-SD FDDI NMM
                  m3313A(68).................3313A Ethernet NMM
                  m3314A(69).................3314A Ethernet NMM
                  m3304A(70).................3304A Ethernet 10BaseF Host
                  m3910SA(71)................3910SA FDDI NMM
                  m2705hm(72)................2705 Token Ring Active Host
                  m3905(73)..................3905 FDDI UTP Host
                  m2915(74)..................2915 FDDI UTP Concentrator
                  m2715Bhm(75)...............2715B Token Ring Active Host
                  m2705Bhm(76)...............2505B Token Ring Active Host
                  m2715BFhm(77)..............2715B-F Token Ring Active Host
                  m2712Bhm(78)...............2712B Token Ring Passive Host
                  m2712BFhm(79)..............2712B-F Token Ring Passive Host
                  m2702BChm(80)..............2702B-C Token Ring Passive Host
                  m3486(82)..................3486 LattisEngine/486
                  m810m(88)..................810M Ethernet Concentrator
                  m3517SA(101)...............3517SA Token Ring NMM
                  m3308B(102)................3308B 10BaseT Host
                  m2813SAnmm(103)............2813SA Ethernet NMM
                  m2814SAnmm(104)............2814SA Ethernet NMM
                  m3313SA(105)...............3313SA Ethernet NMM
                  m3314SA(106)...............3314SA Ethernet NMM
                  m3174(107).................3174 Workstation Controller
                  m3522A(108)................3522A Token Ring Local Bridge
                  m3513SA(109)...............3513SA Token Ring NMM
                  m271xSAnmm(110)............271xSA Token Ring NMM
                  m3299C(116)................3299-C Terminal Multiplexor Adapter
                  m3299U(117)................3299-U TTP Terminal Multiplexor Adapter
                  m3299F(119)................3299-F Fiber Optic Terminal Adapter
                  mAlcatelEthConcnmm(250)....Alcatel Ethernet NMM
                  mAlcatelEthConchm(251).....Alcatel Ethernet Host"
    ::= { s3CommonBoardEntry 2 }

s3CommonBoardHwVer OBJECT-TYPE
    SYNTAX  INTEGER
    ACCESS  read-only
    STATUS  mandatory
    DESCRIPTION
                "The hardware revision of the board.
                  0=Rev. A, 1=Rev. B, etc."
    ::= { s3CommonBoardEntry 3 }

s3CommonBoardStatus OBJECT-TYPE
    SYNTAX  INTEGER {
            ok(1),
            fail(2)
            }
    ACCESS  read-only
    STATUS  mandatory
    DESCRIPTION
                "This indicates the operational status of the board."
    ::= { s3CommonBoardEntry 4 }

s3CommonBoardReset OBJECT-TYPE
    SYNTAX  INTEGER {
            noReset(1),
            reset(2)
            }
    ACCESS  read-write
    STATUS  mandatory
    DESCRIPTION
                "This indicates the reset state of the board.
                Writing with the value reset (2) will reset
                the board."
    ::= { s3CommonBoardEntry 5 }

s3CommonBoardPartStatus OBJECT-TYPE
    SYNTAX  INTEGER {
            enabled(1),
            partition(2),
            timedPartition(3)
            }
    ACCESS  read-write
    STATUS  mandatory
    DESCRIPTION
                "Tells whether the board is partitioned or enabled.
                Writing with the value partition(2) will partition
                the board indefinitely and writing with the value
                enabled(1) will enable the board.

                If a timed partition is desired, then this object
                must be written with timedPartition(3) and in the
                same PDU a partition duration must be supplied in
                s3CommonBoardPartTime. Timed partitions will not
                survive across a reset. In this case the port will
                go to the partition(2) state.

                Boards cannot be partitioned in the 2810 concentrator
                and other workgroup concentrators. These agents will
                implement this object as read-only."
    ::= { s3CommonBoardEntry 6 }

s3CommonBoardNmCntlStatus OBJECT-TYPE
    SYNTAX  INTEGER {
            notNmControl(1),
            nmControl(2)
            }
    ACCESS  read-only
    STATUS  mandatory
    DESCRIPTION
                "Tells whether the board is under network management
                control.  The value nmControl(2) indicates that the
                board or one or more ports are being controlled by
                network management.  This means that the board
                or one or more ports are partitioned via a network
                manager."
    ::= { s3CommonBoardEntry 7 }

s3CommonBoardPsStatus OBJECT-TYPE
    SYNTAX  INTEGER {
            ok(1),
            fail(2)
            }
    ACCESS  read-only
    STATUS  mandatory
    DESCRIPTION
                "This indicates the operational status of the board
                power supply.  A fail(2) indicates that one of the
                power supplies on the board has failed."
    ::= { s3CommonBoardEntry 8 }

s3CommonBoardPartTime OBJECT-TYPE
    SYNTAX  TimeTicks
    ACCESS  read-write
    STATUS  mandatory
    DESCRIPTION
                "When partitioning the board for a specified time, 
                s3CommonBoardPartStatus must be set with
                timedPartition(3) and this object must be supplied
                with the duration value. If a PDU sets 
                s3CommonBoardPartStatus and not this object, the
                board will not be partitioned.  This value is
                decremented while the board is partitioned
                until the value reaches zero at which time the
                board is enabled."
    ::= { s3CommonBoardEntry 9 }

s3SlotConfigOctetString OBJECT-TYPE
    SYNTAX  OCTET STRING (SIZE(12..144))
    ACCESS  read-only
    STATUS  mandatory
    DESCRIPTION
                "Packed octet string for the slot configuration table.
                Format is specified in SynOptics technical documents.
                NOTE: the 291x FDDI workgroup concentrators actually
                return a string with size a multiple of 14."
    ::= { s3000Chassis 9 }

s3RedPsPlus5vCurrent OBJECT-TYPE
    SYNTAX  Gauge
    ACCESS  read-only
    STATUS  mandatory
    DESCRIPTION
                "This gauge is measured in amperes."
    ::= { s3000RedundantPs 1 }

s3RedPsPlus12vCurrent OBJECT-TYPE
    SYNTAX  Gauge
    ACCESS  read-only
    STATUS  mandatory
    DESCRIPTION
                "This gauge is measured in amperes."
    ::= { s3000RedundantPs 2 }

s3RedPsAmbientTempStatus OBJECT-TYPE
    SYNTAX  INTEGER {
            other(1),
            normalTemperature(2),
            aboveNormalTemp(3)
            }
    ACCESS  read-only
    STATUS  mandatory
    DESCRIPTION
                "This status indicates whether the ambient
                temperature is  normal, i.e., below 40 degree C."
    ::= { s3000RedundantPs 3 }

s3RedPsAmbientTemperature OBJECT-TYPE
    SYNTAX  Gauge
    ACCESS  read-only
    STATUS  mandatory
    DESCRIPTION
                "This gauge is measured in Celsius."
    ::= { s3000RedundantPs 4 }

s3RedPsPrimaryConfig OBJECT-TYPE
    SYNTAX  S3PsType
    ACCESS  read-only
    STATUS  mandatory
    DESCRIPTION
                "This indicates the primary power supply type
                (PS 1).  Note that value redundantCapable(5)
                should not be returned for this object."
    ::= { s3000RedundantPs 5 }

s3RedPsSecondaryConfig OBJECT-TYPE
    SYNTAX  S3PsType
    ACCESS  read-only
    STATUS  mandatory
    DESCRIPTION
                "This indicates the secondary power supply type
                (PS 2).  Note that value redundantCapable(5)
                should not be returned for this object."
    ::= { s3000RedundantPs 6 }

s3RedPsDiodeStatus OBJECT-TYPE
    SYNTAX  INTEGER {
            other(1),
            bothOk(2),
            primaryFail(3),
            secondaryFail(4),
            bothFail(5)
            }
    ACCESS  read-only
    STATUS  mandatory
    DESCRIPTION
                "This gives the status of the summing diode on the
                3100R associated with the indicated power supply."
    ::= { s3000RedundantPs 7 }

s3RedPsPowerAlarm OBJECT-TYPE
    SYNTAX  INTEGER {
            other(1),
            bothOk(2),
            primaryFail(3),
            secondaryFail(4),
            bothFail(5)
            }
    ACCESS  read-only
    STATUS  mandatory
    DESCRIPTION
                "This tells whether the indicated power supply is
                sensing voltage on the backplane."
    ::= { s3000RedundantPs 8 }

s3ChassisBkPlEthChanDiv OBJECT-TYPE
    SYNTAX  INTEGER
    ACCESS  read-only
    STATUS  mandatory
    DESCRIPTION
                "A value that describes the divisions of the
                segmentable ethernet channel.  For those devices
                that do not implement a backplane with this feature,
                they still need to implement this object and return
                a value (i.e., zero) to indicate that no divisions
                are enabled.

                The value is a sum (i.e., integer bit string).
                This value initially takes the value of zero,
                then for each division that is enabled on the channel,
                2 raised to a power is added to the sum.  The powers
                are according to the following table:

                  Division between    Power
                    Slots 4 and 5     0
                    Slots 6 and 7     1
                    Slots 8 and 9     2

                For example, a channel with no divisions enabled
                (i.e., not segmented) would have a value of 0.
                A channel with divisions between slots 6 and 7,
                and slots 8 and 9 enabled (i.e., having three
                segments) would have a value of 6 (2**1 + 2**2)."
    ::= { s3000Chassis 11 }

s3ChassisEnetChannelAType OBJECT-TYPE
    SYNTAX  INTEGER {
            other(1),
            aSegmentable(2),
            aNotSegmentable(3)
            }
    ACCESS  read-only
    STATUS  mandatory
    DESCRIPTION
                "The agent will return aSegmentable(2) for the 3000N,
                3000NT, 3000S, 3000SR, and any other backplanes in
                which Ethernet channel A can be divided into multiple
                segments.  The value aNotSegmentable(3) indicates
                that the Ethernet backplane channel A cannot be
                segmented.

                For Token Ring or FDDI workgroup concentrators, or
                other devices in which there is no Ethernet channel,
                the agent will return other(1)."
    ::= { s3000Chassis 12 }

s3EnetConcRetimingStatus OBJECT-TYPE
    SYNTAX  INTEGER {
            off(1),
            on(2)
            }
    ACCESS  read-write
    STATUS  mandatory
    DESCRIPTION
                "Does this concentrator have retiming turned on.
                Writing a 1 will turn off retiming and writing a
                2 will turn on retiming.  This will change the
                active state of retiming but will change the value
                in EEPROM only when agentWriteEeprom is set.The
                factory default of this state is on.

                Retiming cannot be disabled in the 2810 concentrator.
                The 2810 agent will implement this object as read-only."
    ::= { s3000EnetConcentrator 1 }

s3EnetConcFrmsRxOk OBJECT-TYPE
    SYNTAX  Counter
    ACCESS  read-only
    STATUS  mandatory
    DESCRIPTION
                "This contains a count of frames that are successfully
                received by the concentrator.  This does not include
                frames received with a frame-too-long, runt, FCS, or
                alignment errors.

                This counter includes broadcast and multicast frames
                that are received."
    ::= { s3000EnetConcentrator 2 }

s3EnetConcOctetsRxOk OBJECT-TYPE
    SYNTAX  Counter
    ACCESS  read-only
    STATUS  mandatory
    DESCRIPTION
                "Contains a count of data and padding octets in frames
                that are successfully received by the concentrator.
                This does not include frames received with a
                frame-too-long, runt, FCS, or alignment errors.

                This counter includes octets in broadcast and multicast
                frames that are received.

                This counter does not include the octets in the
                CRC field. The octets in the address and length/type
                fields are counted."
    ::= { s3000EnetConcentrator 3 }

s3EnetConcMcastFrmsRxOk OBJECT-TYPE
    SYNTAX  Counter
    ACCESS  read-only
    STATUS  mandatory
    DESCRIPTION
                "This contains a count of frames that are successfully
                received by the concentrator and are directed to an
                active non-broadcast group address.  This does not
                include frames received with a frame-too-long, runt,
                FCS, or alignment errors.

                Only frames that are for a multicast address that
                this interface is receiving are counted.  Broadcast
                packets are not included."
    ::= { s3000EnetConcentrator 4 }

s3EnetConcBcastFrmsRxOk OBJECT-TYPE
    SYNTAX  Counter
    ACCESS  read-only
    STATUS  mandatory
    DESCRIPTION
                "This contains a count of frames that are successfully
                received by the concentrator and are directed to the
                broadcast group address.  This does not include frames
                received with a frame-too-long, runt, FCS, or
                alignment errors.

                Multicast packets are not included."
    ::= { s3000EnetConcentrator 5 }

s3EnetConcColls OBJECT-TYPE
    SYNTAX  Counter
    ACCESS  read-only
    STATUS  mandatory
    DESCRIPTION
                "This contains a count of the collisions at the
                concentrator level.  For NMM+ this is a true counter.
                For other NMMs this is a summation of all the port
                level collision 'flags' for all ports."
    ::= { s3000EnetConcentrator 6 }

s3EnetConcTooLongErrors OBJECT-TYPE
    SYNTAX  Counter
    ACCESS  read-only
    STATUS  mandatory
    DESCRIPTION
                "This contains a count of frames that are received by
                the concentrator and exceed the maximum permitted
                frame size.  This counter is incremented when the
                frameTooLong error is detected."
    ::= { s3000EnetConcentrator 7 }

s3EnetConcRuntErrors OBJECT-TYPE
    SYNTAX  Counter
    ACCESS  read-only
    STATUS  mandatory
    DESCRIPTION
                "This contains a count of frames received by the
                concentrator that are less than the minimum permitted
                frame size and have a good FCS."
    ::= { s3000EnetConcentrator 8 }

s3EnetConcFragErrors OBJECT-TYPE
    SYNTAX  Counter
    ACCESS  read-only
    STATUS  mandatory
    DESCRIPTION
                "This contains a count of frames received by the
                concentrator that are less than the minimum permitted
                frame size and have a bad FCS or alignment error."
    ::= { s3000EnetConcentrator 9 }

s3EnetConcAlignErrors OBJECT-TYPE
    SYNTAX  Counter
    ACCESS  read-only
    STATUS  mandatory
    DESCRIPTION
                "This contains a count of frames received by the
                concentrator that are not an integral number of
                octets in length and do not pass the FCS check.
                This counter is incremented when the alignment
                Error status is detected."
    ::= { s3000EnetConcentrator 10 }

s3EnetConcFcsErrors OBJECT-TYPE
    SYNTAX  Counter
    ACCESS  read-only
    STATUS  mandatory
    DESCRIPTION
                "This contains a count of frames received by the
                concentrator that are an integral number of octets
                in length that do not pass the FCS check.  This
                counter is incremented when the frame Check Error
                status is detected."
    ::= { s3000EnetConcentrator 11 }

s3EnetConcLateCollErrors OBJECT-TYPE
    SYNTAX  Counter
    ACCESS  read-only
    STATUS  mandatory
    DESCRIPTION
                "This contains a total concentrator count of the
                late collisions. For NMM+ this is a true counter.
                For other NMMs this is a summation of all the port
                level late collision 'flags' for all ports."
    ::= { s3000EnetConcentrator 12 }

s3EnetConcSecureStatus OBJECT-TYPE
    SYNTAX  INTEGER {
            other(1),
            concSecureOn(2),
            portCheckOn(3),
            slotCheckOn(4),
            concSecureOff(5)
            }
    ACCESS  read-write
    STATUS  mandatory
    DESCRIPTION
                "This s3EnetConcSecureStatus object indicates whether
                the security features (both allowed nodes and
                LattisSecure) for the concentrator are active or
                inactive.  If security is active, this object also
                indicates whether the allowed nodes feature is
                controlled at the concentrator, board, or port level.
                LattisSecure features are always controlled at the
                port level.  (See the Authorized Nodes tables for
                more information about how the allowed nodes and
                LattisSecure receive security features are
                configured.)

                If this object is set to concSecureOn(2), then the
                allowed nodes feature is controlled at the
                concentrator level and activated for every
                non-LattisSecure Ethernet port in the concentrator.
                If an authorized node violation occurs on any port,
                the action specified in s3EnetConcAuthAction is taken.

                If this object is set to portCheckOn(3), then allowed
                nodes is controlled at the port level by the
                s3EnetPortSecureStatus object for that port.  The
                port's s3EnetPortAuthAction determines the action
                taken when authorized nodes violations occur on that
                port.

                If this object is set to slotCheckOn(4), then allowed
                nodes is controlled at the board level by the
                s3EnetBoardSecureStatus object for that board.
                The board's s3EnetBoardAuthAction determines the
                action taken when authorized nodes violations
                occur on that board's ports.

                If this object is set to concentratorOff(5), then
                all security features, including LattisSecure, are
                deactivated for the entire concentrator.

                No matter what the status of this object, the board
                and port level SecureStatus and AuthAction are not
                lost even if they are not currently being used.  Thus,
                the user can change a port's status even if this object
                is slotCheckOn(4).  If this object is then changed to
                portCheckOn(3), then the change will take effect.

                The agent must support download of this object in the
                CFG file.

                In release 4.0, this object was called
                s3EnetConcAuthStatus."
    ::= { s3000EnetConcentrator 13 }

s3EnetConcAuthAction OBJECT-TYPE
    SYNTAX  INTEGER {
            other(1),
            noAction(2),
            sendTrap(3),
            partition(4),
            sendTrapPartition(5)
            }
    ACCESS  read-write
    STATUS  mandatory
    DESCRIPTION
                "If s3EnetConcSecureStatus is concSecureOn(2) and a
                violation occurs, then the action specified by this
                object will take place.  On a partition, only the
                port that the violation occurs on will be partitioned.

                This object does not apply to LattisSecure ports.

                The agent must support download of this object in
                the CFG file."
    ::= { s3000EnetConcentrator 14 }

s3EnetConcSecurityLock OBJECT-TYPE
    SYNTAX  INTEGER {
            other(1),
            locked(2),
            notLocked(3)
            }
    ACCESS  read-only
    STATUS  mandatory
    DESCRIPTION
                "If s3EnetConcSecurityLock is locked(2), the agent will
                refuse all requests to modify the 'security configuration'
                (defined below) by returning a BadValue return value.
                If s3EnetConcSecurityLock is notLocked(3), requests to
                modify security configuration will be handled in the
                usual manner.  SetRequests for objects not included
                in the security configuration are not affected by the
                state of this object.

                Objects that are part of the security configuration
                are s3EnetConcAuthStatus, s3EnetConcAuthAction,
                s3EnetBoardAuthStatus, s3EnetBoardAuthAction,
                s3EnetPortAuthStatus, s3EnetPortAuthAction,
                s3EnetPortAddrLearnMode, s3EnetPortTxSecurity,
                and all of the objects in the s3EnetAuthNodesTable."
    ::= { s3000EnetConcentrator 15 }

s3EnetConcEnetChan OBJECT-TYPE
    SYNTAX  INTEGER {
            other(1),
            enetA(2),
            enetB(3)
            }
    ACCESS  read-only
    STATUS  mandatory
    DESCRIPTION
                "Identifies the channel to which this NMM is
                currently monitoring."
    ::= { s3000EnetConcentrator 16 }

s3EnetBoardTable OBJECT-TYPE
    SYNTAX  SEQUENCE OF S3EnetBoardEntry
    ACCESS  not-accessible
    STATUS  mandatory
    DESCRIPTION
                "A table of board-related objects.  The number of
                entries is given by the number of Ethernet host
                module and network management module boards that
                are contained in same backplane Ethernet segment
                as the reporting NMM."
    ::= { s3000EnetBoard 1 }

s3EnetBoardEntry OBJECT-TYPE
    SYNTAX  S3EnetBoardEntry
    ACCESS  not-accessible
    STATUS  mandatory
    DESCRIPTION
                "A table containing objects about Ethernet boards
                which are currently plugged into the 3000 chassis."
    INDEX   { s3EnetBoardIndex }
    ::= { s3EnetBoardTable 1 }

S3EnetBoardEntry ::= SEQUENCE {
    s3EnetBoardIndex
        INTEGER,
    s3EnetBoardFrmsRxOk
        Counter,
    s3EnetBoardOctetsRxOk
        Counter,
    s3EnetBoardMcastFrmsRxOk
        Counter,
    s3EnetBoardBcastFrmsRxOk
        Counter,
    s3EnetBoardColls
        Counter,
    s3EnetBoardTooLongErrors
        Counter,
    s3EnetBoardRuntErrors
        Counter,
    s3EnetBoardAlignErrors
        Counter,
    s3EnetBoardFcsErrors
        Counter,
    s3EnetBoardLateCollErrors
        Counter,
    s3EnetBoardAuthStatus
        INTEGER,
    s3EnetBoardAuthAction
        INTEGER,
    s3EnetBoardUpStamp
        TimeTicks
    }

s3EnetBoardIndex OBJECT-TYPE
    SYNTAX  INTEGER
    ACCESS  read-only
    STATUS  mandatory
    DESCRIPTION
                "A unique value for each board.  Its value ranges
                between 1 and 12.  The value for each board must
                remain constant at least from one re-initialization
                of the entity's network management system to the next
                re-initialization."
    ::= { s3EnetBoardEntry 1 }

s3EnetBoardFrmsRxOk OBJECT-TYPE
    SYNTAX  Counter
    ACCESS  read-only
    STATUS  mandatory
    DESCRIPTION
                "This contains a count of frames that are successfully
                received by the board.  This does not include frames
                received with a frame-too-long, runt, FCS, or alignment
                errors.

                This counter includes broadcast and multicast frames
                that are received."
    ::= { s3EnetBoardEntry 9 }

s3EnetBoardOctetsRxOk OBJECT-TYPE
    SYNTAX  Counter
    ACCESS  read-only
    STATUS  mandatory
    DESCRIPTION
                "Contains a count of data and padding octets in frames
                that are successfully received by the board.  This does
                not include frames received with a frame-too-long, runt,
                FCS, or alignment errors.

                This counter includes octets in broadcast and multicast
                frames that are received.

                This counter does not include the octets in the
                CRC field. The octets in the address and length/type
                fields are counted."
    ::= { s3EnetBoardEntry 10 }

s3EnetBoardMcastFrmsRxOk OBJECT-TYPE
    SYNTAX  Counter
    ACCESS  read-only
    STATUS  mandatory
    DESCRIPTION
                "This contains a count of frames that are successfully
                received by the board and are directed to an active
                non-broadcast group address.  This does not include
                frames received with a frame-too-long, runt, FCS, or
                alignment errors.

                Only frames that are for a multicast address that
                this interface is receiving are counted. Broadcast
                packets are not included."
    ::= { s3EnetBoardEntry 11 }

s3EnetBoardBcastFrmsRxOk OBJECT-TYPE
    SYNTAX  Counter
    ACCESS  read-only
    STATUS  mandatory
    DESCRIPTION
                "This contains a count of frames that are successfully
                received by the board and are directed to the broadcast
                group address.  This does not include frames received
                with a frame-too-long, runt, FCS, or alignment errors.
                Multicast packets are not included."
    ::= { s3EnetBoardEntry 12 }

s3EnetBoardColls OBJECT-TYPE
    SYNTAX  Counter
    ACCESS  read-only
    STATUS  mandatory
    DESCRIPTION
                "This contains a board level count of collisions.
                For NMM+ this is a true counter.  For other NMMs
                this is a summation of all the port level collision
                'flags' for this board."
    ::= { s3EnetBoardEntry 13 }

s3EnetBoardTooLongErrors OBJECT-TYPE
    SYNTAX  Counter
    ACCESS  read-only
    STATUS  mandatory
    DESCRIPTION
                "This contains a count of frames that are received by
                the board and exceed the maximum permitted frame size.
                This counter is incremented when the frameTooLong
                error is detected."
    ::= { s3EnetBoardEntry 14 }

s3EnetBoardRuntErrors OBJECT-TYPE
    SYNTAX  Counter
    ACCESS  read-only
    STATUS  mandatory
    DESCRIPTION
                "This contains a count of frames received by the board
                that are less than the minimum permitted frame size and
                have a good FCS."
    ::= { s3EnetBoardEntry 15 }

s3EnetBoardAlignErrors OBJECT-TYPE
    SYNTAX  Counter
    ACCESS  read-only
    STATUS  mandatory
    DESCRIPTION
                "This contains a count of frames received by the board
                that are not an integral number of octets in length and
                do not pass the FCS check.  This counter is incremented
                when the alignmentError status is detected."
    ::= { s3EnetBoardEntry 16 }

s3EnetBoardFcsErrors OBJECT-TYPE
    SYNTAX  Counter
    ACCESS  read-only
    STATUS  mandatory
    DESCRIPTION
                "This contains a count of frames received by the board
                that are an integral number of octets in length that
                do not pass the FCS check.  This counter is incremented
                when the frameCheckError status is detected."
    ::= { s3EnetBoardEntry 17 }

s3EnetBoardLateCollErrors OBJECT-TYPE
    SYNTAX  Counter
    ACCESS  read-only
    STATUS  mandatory
    DESCRIPTION
                "This contains a count of the board level late collisions.
                For NMM+ this is a true counter.  For other NMMs this is a
                summation of all the port level late collision 'flags' for
                this board."
    ::= { s3EnetBoardEntry 18 }

s3EnetBoardAuthStatus OBJECT-TYPE
    SYNTAX  INTEGER {
            other(1),
            on(2),
            off(3)
            }
    ACCESS  read-write
    STATUS  mandatory
    DESCRIPTION
                "This object is only used if s3EnetConcSecureStatus is
                set to slotCheckOn(4).  In this case, turning this object
                on(2) means that any node that is heard on this board
                which is not allowed on this board (i.e., not in AuthNode
                table with the slotIndex equal to this board or 0 for all
                boards) will cause the action specified in
                s3EnetBoardAuthAction to take place.

                If s3EnetConcSecureStatus is set to slotCheckOn(4) but
                this object is set to off(3), then the authorized nodes
                feature for this board is deactivated.

                If s3EnetConcSecureStatus is not set to slotCheckOn(4),
                then this object will not be used but will maintain
                its settings unless explicitly changed.

                This object does not affect the configuration or
                functioning of security features on LattisSecure
                Host Modules."
    ::= { s3EnetBoardEntry 19 }

s3EnetBoardAuthAction OBJECT-TYPE
    SYNTAX  INTEGER {
            other(1),
            noAction(2),
            sendTrap(3),
            partition(4),
            sendTrapPartition(5)
            }
    ACCESS  read-write
    STATUS  mandatory
    DESCRIPTION
                "If s3EnetConcSecureStatus is slotCheckOn(4) and
                s3EnetBoardAuthStatus is on(2) and an authorized nodes
                violation occurs on the board, then the action specified
                by this object will take place.  On a partition, only the
                port that the violation occurs on will be partitioned.

                This object does not apply to LattisSecure ports."
    ::= { s3EnetBoardEntry 20 }

s3EnetBoardUpStamp OBJECT-TYPE
    SYNTAX  TimeTicks
    ACCESS  read-only
    STATUS  mandatory
    DESCRIPTION
                "The time ( in hundredths of a second) that the board
                was first seen as a member of this NMM's segment."
    ::= { s3EnetBoardEntry 21 }

s3EnetLocBridgeSlotTable OBJECT-TYPE
    SYNTAX  SEQUENCE OF S3EnetLocBridgeEntry
    ACCESS  not-accessible
    STATUS  mandatory
    DESCRIPTION
                "A table of Local Bridge Board entries.  The number of
                entries is determined by  the Concentrator Slot
                Configuration Table.  Only those entries that are
                Ethernet local bridges will have entries in this list."
    ::= { s3000EnetLocBridge 1 }

s3EnetLocBridgeEntry OBJECT-TYPE
    SYNTAX  S3EnetLocBridgeEntry
    ACCESS  not-accessible
    STATUS  mandatory
    DESCRIPTION
                "A table containing objects about Boards which are
                local bridges that are currently plugged into the
                3000 chassis."
    INDEX   { s3EnetLocBridgeIndex }
    ::= { s3EnetLocBridgeSlotTable 1 }

S3EnetLocBridgeEntry ::= SEQUENCE {
    s3EnetLocBridgeIndex
        INTEGER,
    s3EnetLocBridgeDescr
        DisplayString,
    s3EnetLocBridgePortCount
        INTEGER,
    s3EnetLocBridgeDiagSts
        OCTET STRING,
    s3EnetLocBridgeBootSts
        INTEGER,
    s3EnetLocBridgeStandbySts
        INTEGER
    }

s3EnetLocBridgeIndex OBJECT-TYPE
    SYNTAX  INTEGER
    ACCESS  read-only
    STATUS  mandatory
    DESCRIPTION
                "A unique value for each board.  Its value ranges between
                1 and 12.  The value for each board must remain constant
                at least from one re-initialization of the entity's
                network management system to the next re-initialization."
    ::= { s3EnetLocBridgeEntry 1 }

s3EnetLocBridgeDescr OBJECT-TYPE
    SYNTAX  DisplayString (SIZE(0..128))
    ACCESS  read-only
    STATUS  mandatory
    DESCRIPTION
                "Description of the local bridge board."
    ::= { s3EnetLocBridgeEntry 2 }

s3EnetLocBridgePortCount OBJECT-TYPE
    SYNTAX  INTEGER
    ACCESS  read-only
    STATUS  mandatory
    DESCRIPTION
                "Number of ports that are on the local bridge board."
    ::= { s3EnetLocBridgeEntry 3 }

s3EnetLocBridgeDiagSts OBJECT-TYPE
    SYNTAX  OCTET STRING (SIZE(4))
    ACCESS  read-only
    STATUS  mandatory
    DESCRIPTION
                "Latest Diagnostic LED Status that has been recorded."
    ::= { s3EnetLocBridgeEntry 4 }

s3EnetLocBridgeBootSts OBJECT-TYPE
    SYNTAX  INTEGER {
            other(1),
            reqstToBoot(2),
            notReqstToBoot(3)
            }
    ACCESS  read-only
    STATUS  mandatory
    DESCRIPTION
                "The current status of the board as it relates
                to rebooting."
    ::= { s3EnetLocBridgeEntry 5 }

s3EnetLocBridgeStandbySts OBJECT-TYPE
    SYNTAX  INTEGER {
            other(1),
            standby(2),
            notStandby(3)
            }
    ACCESS  read-only
    STATUS  mandatory
    DESCRIPTION
                "This status says whether the local bridge is active
                or in standby mode."
    ::= { s3EnetLocBridgeEntry 6 }

s3EnetLocBridgePortTable OBJECT-TYPE
    SYNTAX  SEQUENCE OF S3EnetLocBridgePortEntry
    ACCESS  not-accessible
    STATUS  mandatory
    DESCRIPTION
                "A table of Port entries that are part of a local
                bridge.  The number of entries is determined by knowing
                the number of local bridge boards that are installed
                by looking at s3ChassisSlotConfigTable and by knowing
                how many ports are on a local bridge board by looking at
                s3EnetLocBridgePortCount."
    ::= { s3000EnetLocBridge 2 }

s3EnetLocBridgePortEntry OBJECT-TYPE
    SYNTAX  S3EnetLocBridgePortEntry
    ACCESS  not-accessible
    STATUS  mandatory
    DESCRIPTION
                "A table containing objects about the ports of the
                local bridges that are currently plugged into the
                3000 chassis."
    INDEX   { s3EnetLocBridgePortSlotIndex,
              s3EnetLocBridgePortIndex }
    ::= { s3EnetLocBridgePortTable 1 }

S3EnetLocBridgePortEntry ::= SEQUENCE {
    s3EnetLocBridgePortSlotIndex
        INTEGER,
    s3EnetLocBridgePortIndex
        INTEGER,
    s3EnetLocBridgePortMdaId
        INTEGER,
    s3EnetLocBridgePortIf
        INTEGER,
    s3EnetLocBridgePortDescr
        DisplayString,
    s3EnetLocBridgePortOpSts
        INTEGER
    }

s3EnetLocBridgePortSlotIndex OBJECT-TYPE
    SYNTAX  INTEGER
    ACCESS  read-only
    STATUS  mandatory
    DESCRIPTION
                "A unique value for each board.  Its value ranges
                between 1 and 12.  The value for each board must
                remain constant at least from one re-initialization
                of the entity's network management system to the
                next re-initialization."
    ::= { s3EnetLocBridgePortEntry 1 }

s3EnetLocBridgePortIndex OBJECT-TYPE
    SYNTAX  INTEGER
    ACCESS  read-only
    STATUS  mandatory
    DESCRIPTION
                "A unique value for each port.  Its value ranges
                between 1 and 12.  The value for each port must
                remain constant at least from one re-initialization
                of the entity's network management system to the
                next re-initialization."
    ::= { s3EnetLocBridgePortEntry 2 }

s3EnetLocBridgePortMdaId OBJECT-TYPE
    SYNTAX  INTEGER
    ACCESS  read-only
    STATUS  mandatory
    DESCRIPTION
                "Medium dependent ID for the port. See s3SlotModuleMdaId
                in the SynOptics Common MIB."
    ::= { s3EnetLocBridgePortEntry 3 }

s3EnetLocBridgePortIf OBJECT-TYPE
    SYNTAX  INTEGER {
            other(1),
            etherEther(2),
            etherTokenRing(3)
            }
    ACCESS  read-only
    STATUS  mandatory
    DESCRIPTION
                "Bridge interface types."
    ::= { s3EnetLocBridgePortEntry 4 }

s3EnetLocBridgePortDescr OBJECT-TYPE
    SYNTAX  DisplayString (SIZE(0..128))
    ACCESS  read-only
    STATUS  mandatory
    DESCRIPTION
                "A text description of the port."
    ::= { s3EnetLocBridgePortEntry 5 }

s3EnetLocBridgePortOpSts OBJECT-TYPE
    SYNTAX  INTEGER {
            other(1),
            standby(2),
            notStandby(3)
            }
    ACCESS  read-only
    STATUS  mandatory
    DESCRIPTION
                "Operating status of the port."
    ::= { s3EnetLocBridgePortEntry 6 }

s3EnetRemBridgeSlotTable OBJECT-TYPE
    SYNTAX  SEQUENCE OF S3EnetRemBridgeEntry
    ACCESS  not-accessible
    STATUS  mandatory
    DESCRIPTION
                "A table of Remote Bridge Board entries.  The number
                of entries is determined by the Concentrator Slot
                Configuration Table.  Only those entries that are
                Ethernet remote bridges will have entries in this list."
    ::= { s3000EnetRemBridge 1 }

s3EnetRemBridgeEntry OBJECT-TYPE
    SYNTAX  S3EnetRemBridgeEntry
    ACCESS  not-accessible
    STATUS  mandatory
    DESCRIPTION
                "A table containing objects about Boards which are
                remote bridges that are currently plugged into the
                3000 chassis."
    INDEX   { s3EnetRemBridgeIndex }
    ::= { s3EnetRemBridgeSlotTable 1 }

S3EnetRemBridgeEntry ::= SEQUENCE {
    s3EnetRemBridgeIndex
        INTEGER,
    s3EnetRemBridgeDescr
        DisplayString,
    s3EnetRemBridgePortCount
        INTEGER,
    s3EnetRemBridgeDiagSts
        OCTET STRING,
    s3EnetRemBridgeBootSts
        INTEGER,
    s3EnetRemBridgeStandbySts
        INTEGER
    }

s3EnetRemBridgeIndex OBJECT-TYPE
    SYNTAX  INTEGER
    ACCESS  read-only
    STATUS  mandatory
    DESCRIPTION
                "A unique value for each board.  Its value ranges
                between 1 and 12.  The value for each board must
                remain constant at least from one re-initialization
                of the entity's network management system to the
                next re-initialization."
    ::= { s3EnetRemBridgeEntry 1 }

s3EnetRemBridgeDescr OBJECT-TYPE
    SYNTAX  DisplayString (SIZE(0..128))
    ACCESS  read-only
    STATUS  mandatory
    DESCRIPTION
                "Description of the board."
    ::= { s3EnetRemBridgeEntry 2 }

s3EnetRemBridgePortCount OBJECT-TYPE
    SYNTAX  INTEGER
    ACCESS  read-only
    STATUS  mandatory
    DESCRIPTION
                "Number of ports that are on the board."
    ::= { s3EnetRemBridgeEntry 3 }

s3EnetRemBridgeDiagSts OBJECT-TYPE
    SYNTAX  OCTET STRING (SIZE(4))
    ACCESS  read-only
    STATUS  mandatory
    DESCRIPTION
                "Latest Diagnostic LED Status that has been recorded."
    ::= { s3EnetRemBridgeEntry 4 }

s3EnetRemBridgeBootSts OBJECT-TYPE
    SYNTAX  INTEGER {
            other(1),
            reqstToBoot(2),
            notReqstToBoot(3)
            }
    ACCESS  read-only
    STATUS  mandatory
    DESCRIPTION
                "The current status of the board as it relates to rebooting."
    ::= { s3EnetRemBridgeEntry 5 }

s3EnetRemBridgeStandbySts OBJECT-TYPE
    SYNTAX  INTEGER {
            other(1),
            standby(2),
            notStandby(3)
            }
    ACCESS  read-only
    STATUS  mandatory
    DESCRIPTION
                "This status says whether the remote bridge is active
                or in standby mode."
    ::= { s3EnetRemBridgeEntry 6 }

s3EnetRemBridgePortTable OBJECT-TYPE
    SYNTAX  SEQUENCE OF S3EnetRemBridgePortEntry
    ACCESS  not-accessible
    STATUS  mandatory
    DESCRIPTION
                "A table of Port entries that are part of a remote
                bridge.  The number of entries is determined by
                knowing the number of remote bridge boards that are
                installed by looking at s3ChassisSlotConfigTable and
                by knowing how many ports are on a remote bridge
                board by looking at s3EnetRemBridgePortCount."
    ::= { s3000EnetRemBridge 2 }

s3EnetRemBridgePortEntry OBJECT-TYPE
    SYNTAX  S3EnetRemBridgePortEntry
    ACCESS  not-accessible
    STATUS  mandatory
    DESCRIPTION
                "A table containing objects about the ports of the
                remote bridges that are currently plugged into the
                3000 chassis."
    INDEX   { s3EnetRemBridgePortSlotIndex,
              s3EnetRemBridgePortIndex }
    ::= { s3EnetRemBridgePortTable 1 }

S3EnetRemBridgePortEntry ::= SEQUENCE {
    s3EnetRemBridgePortSlotIndex
        INTEGER,
    s3EnetRemBridgePortIndex
        INTEGER,
    s3EnetRemBridgePortMdaId
        INTEGER,
    s3EnetRemBridgePortDescr
        DisplayString,
    s3EnetRemBridgePortOpSts
        INTEGER,
    s3EnetRemBridgePortRdySnd
        INTEGER,
    s3EnetRemBridgePortClrSnd
        INTEGER,
    s3EnetRemBridgePortCarDt
        INTEGER
    }

s3EnetRemBridgePortSlotIndex OBJECT-TYPE
    SYNTAX  INTEGER
    ACCESS  read-only
    STATUS  mandatory
    DESCRIPTION
                "A unique value for each board.  Its value ranges
                between 1 and 12.  The value for each board must
                remain constant at least from one re-initialization
                of the entity's network management system to the
                next re-initialization."
    ::= { s3EnetRemBridgePortEntry 1 }

s3EnetRemBridgePortIndex OBJECT-TYPE
    SYNTAX  INTEGER
    ACCESS  read-only
    STATUS  mandatory
    DESCRIPTION
                "A unique value for each port.  Its value ranges
                between 1 and 12.  The value for each port must
                remain constant at least from one re-initialization
                of the entity's network management system to the next
                re-initialization."
    ::= { s3EnetRemBridgePortEntry 2 }

s3EnetRemBridgePortMdaId OBJECT-TYPE
    SYNTAX  INTEGER {
            other(1),
            ethernet(2),
            x21Barrier(3),
            x21Unbarrier(4),
            rs232(5),
            rs449(6),
            v35(7),
            g703(8),
            t1(9)
            }
    ACCESS  read-only
    STATUS  mandatory
    DESCRIPTION
                "Medium dependent ID for the port."
    ::= { s3EnetRemBridgePortEntry 3 }

s3EnetRemBridgePortDescr OBJECT-TYPE
    SYNTAX  DisplayString (SIZE(0..128))
    ACCESS  read-only
    STATUS  mandatory
    DESCRIPTION
                "A text description of the port."
    ::= { s3EnetRemBridgePortEntry 4 }

s3EnetRemBridgePortOpSts OBJECT-TYPE
    SYNTAX  INTEGER {
            other(1),
            standby(2),
            operational(3),
            noLink(4)
            }
    ACCESS  read-only
    STATUS  mandatory
    DESCRIPTION
                "Operating status of the port."
    ::= { s3EnetRemBridgePortEntry 5 }

s3EnetRemBridgePortRdySnd OBJECT-TYPE
    SYNTAX  INTEGER {
            other(1),
            rdySnd(2),
            notRdySnd(3)
            }
    ACCESS  read-only
    STATUS  mandatory
    DESCRIPTION
                "Ready to send status of the port."
    ::= { s3EnetRemBridgePortEntry 6 }

s3EnetRemBridgePortClrSnd OBJECT-TYPE
    SYNTAX  INTEGER {
            other(1),
            clrSnd(2),
            notClrSnd(3)
            }
    ACCESS  read-only
    STATUS  mandatory
    DESCRIPTION
                "Clear to send status of the port."
    ::= { s3EnetRemBridgePortEntry 7 }

s3EnetRemBridgePortCarDt OBJECT-TYPE
    SYNTAX  INTEGER {
            other(1),
            carDt(2),
            noCarDt(3)
            }
    ACCESS  read-only
    STATUS  mandatory
    DESCRIPTION
                "Carrier detect status of the port."
    ::= { s3EnetRemBridgePortEntry 8 }

s3EnetRouterSlotTable OBJECT-TYPE
    SYNTAX  SEQUENCE OF S3EnetRouterEntry
    ACCESS  not-accessible
    STATUS  mandatory
    DESCRIPTION
                "A table of Router Board entries.  The number of
                entries is determined by  the Concentrator Slot
                Configuration Table.  Only those entries that
                are Ethernet routers will have entries in this list."
    ::= { s3000EnetRouter 1 }

s3EnetRouterEntry OBJECT-TYPE
    SYNTAX  S3EnetRouterEntry
    ACCESS  not-accessible
    STATUS  mandatory
    DESCRIPTION
                "A table containing objects about Boards which
                are routers that are currently plugged into the
                3000 chassis."
    INDEX   { s3EnetRouterIndex }
    ::= { s3EnetRouterSlotTable 1 }

S3EnetRouterEntry ::= SEQUENCE {
    s3EnetRouterIndex
        INTEGER,
    s3EnetRouterDescr
        DisplayString,
    s3EnetRouterDiagSts
        OCTET STRING,
    s3EnetRouterStandbySts
        INTEGER
    }

s3EnetRouterIndex OBJECT-TYPE
    SYNTAX  INTEGER
    ACCESS  read-only
    STATUS  mandatory
    DESCRIPTION
                "A unique value for each board.  Its value ranges
                between 1 and 12.  The value for each board must
                remain constant at least from one re-initialization
                of the entity's network management system to the
                next re-initialization."
    ::= { s3EnetRouterEntry 1 }

s3EnetRouterDescr OBJECT-TYPE
    SYNTAX  DisplayString (SIZE(0..128))
    ACCESS  read-only
    STATUS  mandatory
    DESCRIPTION
                "Description of the router board."
    ::= { s3EnetRouterEntry 2 }

s3EnetRouterDiagSts OBJECT-TYPE
    SYNTAX  OCTET STRING (SIZE(4))
    ACCESS  read-only
    STATUS  mandatory
    DESCRIPTION
                "Latest Diagnostic LED Status that has been recorded."
    ::= { s3EnetRouterEntry 3 }

s3EnetRouterStandbySts OBJECT-TYPE
    SYNTAX  INTEGER {
            other(1),
            standby(2),
            notStandby(3)
            }
    ACCESS  read-only
    STATUS  mandatory
    DESCRIPTION
                "This status says whether the router is active or in
                standby mode."
    ::= { s3EnetRouterEntry 4 }

s3EnetCommonBoardTable OBJECT-TYPE
    SYNTAX  SEQUENCE OF S3EnetCommonBoardEntry
    ACCESS  not-accessible
    STATUS  mandatory
    DESCRIPTION
                "Information maintained for each Ethernet board.  The
                information can be retrieved for any Ethernet board,
                even if the board is not on the same backplane Ethernet
                segment as this NMM.

                The instance is the slot number of the concentrator
                that the board occupies."
    ::= { s3000EnetBoard 5 }

s3EnetCommonBoardEntry OBJECT-TYPE
    SYNTAX  S3EnetCommonBoardEntry
    ACCESS  not-accessible
    STATUS  mandatory
    DESCRIPTION
                "There is one entry per Ethernet board in this table."
    INDEX   { s3EnetCommonBoardIndex }
    ::= { s3EnetCommonBoardTable 1 }

S3EnetCommonBoardEntry ::= SEQUENCE {
    s3EnetCommonBoardIndex
        INTEGER,
    s3EnetCommonBoardEnetAB
        INTEGER,
    s3EnetCommonBoardChanSwitch
        INTEGER,
    s3EnetCommonBoardRedund
        INTEGER
    }

s3EnetCommonBoardIndex OBJECT-TYPE
    SYNTAX  INTEGER
    ACCESS  read-only
    STATUS  mandatory
    DESCRIPTION
                "A unique value for each board.  Its value ranges
                between 1 and 12. The value for each board must
                remain constant at least from one re-initialization
                of the entity's network management system to the
                next re-initialization."
    ::= { s3EnetCommonBoardEntry 1 }

s3EnetCommonBoardEnetAB OBJECT-TYPE
    SYNTAX  INTEGER {
            other(1),
            enetA(2),
            enetB(3),
            enetAandEnetB(4)
            }
    ACCESS  read-write
    STATUS  mandatory
    DESCRIPTION
                "The channel to which the board is connected.  The
                primary use of this object is for providing realtime
                switching of boards between channel A and channel B.
                It is also returned in the enetChannelChange trap, in
                which case it indicates a board is switched from one
                channel to the other.  The write capability of this
                object can only apply to those modules with channel
                switching function.  Any attempt to write this object
                for a non-switchable board, the agent will return
                badValue."
    ::= { s3EnetCommonBoardEntry 2 }

s3EnetCommonBoardChanSwitch OBJECT-TYPE
    SYNTAX  INTEGER {
            other(1),
            switchCapable(2),
            notSwitchCapable(3)
            }
    ACCESS  read-only
    STATUS  mandatory
    DESCRIPTION
                "The agent will return switchCapable(2) for any
                Ethernet host board which can be switched between
                Ethernet channels.  The value notSwitchCapable(3)
                indicates that the Ethernet board can not be switched
                to another channel."
    ::= { s3EnetCommonBoardEntry 3 }

s3EnetCommonBoardRedund OBJECT-TYPE
    SYNTAX  INTEGER {
            other(1),
            redundCapable(2),
            notRedundCapable(3)
            }
    ACCESS  read-only
    STATUS  mandatory
    DESCRIPTION
                "The agent will return redundCapable(2) for any Ethernet
                host board which can provide hardware and/or software
                controlled redundancy on the port level.  The value
                notRedundCapable(3) indicates that the Ethernet board
                can not support port redundancy."
    ::= { s3EnetCommonBoardEntry 4 }

s3EnetPortTable OBJECT-TYPE
    SYNTAX  SEQUENCE OF S3EnetPortEntry
    ACCESS  not-accessible
    STATUS  mandatory
    DESCRIPTION
                "A list of port entries.  The number of entries is
                given by learning the type of board from the
                information in the s3ChassisSlotConfigTable."
    ::= { s3000EnetPort 1 }

s3EnetPortEntry OBJECT-TYPE
    SYNTAX  S3EnetPortEntry
    ACCESS  not-accessible
    STATUS  mandatory
    DESCRIPTION
                "A table containing objects about the Ports of
                each board plugged into the 3000 chassis which
                are on the same backplane Ethernet segment as
                the reporting NMM."
    INDEX   { s3EnetPortBoardIndex,
              s3EnetPortIndex }
    ::= { s3EnetPortTable 1 }

S3EnetPortEntry ::= SEQUENCE {
    s3EnetPortBoardIndex
        INTEGER,
    s3EnetPortIndex
        INTEGER,
    s3EnetPortLinkStatus
        INTEGER,
    s3EnetPortPartStatus
        INTEGER,
    s3EnetPortJabberStatus
        INTEGER,
    s3EnetPortFrmsRxOk
        Counter,
    s3EnetPortOctetsRxOk
        Counter,
    s3EnetPortMcastFrmsRxOk
        Counter,
    s3EnetPortBcastFrmsRxOk
        Counter,
    s3EnetPortColls
        Counter,
    s3EnetPortTooLongErrors
        Counter,
    s3EnetPortRuntErrors
        Counter,
    s3EnetPortAlignErrors
        Counter,
    s3EnetPortFcsErrors
        Counter,
    s3EnetPortLateCollErrors
        Counter,
    s3EnetPortAuthStatus
        INTEGER,
    s3EnetPortAuthAction
        INTEGER,
    s3EnetPortPartTime
        TimeTicks,
    s3EnetPortType
        INTEGER,
    s3EnetPortInterconStatus
        INTEGER,
    s3EnetPortAddrCollect
        INTEGER,
    s3EnetPortAddrLearnMode
        INTEGER,
    s3EnetPortTxSecurity
        INTEGER
    }

s3EnetPortBoardIndex OBJECT-TYPE
    SYNTAX  INTEGER
    ACCESS  read-only
    STATUS  mandatory
    DESCRIPTION
                "A unique value for each board.  Its value ranges
                between 1 and 12.  The value for each board must
                remain constant at least from one reinitialization
                of the entity's network management system to the
                next reinitialization."
    ::= { s3EnetPortEntry 1 }

s3EnetPortIndex OBJECT-TYPE
    SYNTAX  INTEGER
    ACCESS  read-only
    STATUS  mandatory
    DESCRIPTION
                "A unique value for each port.  Its value is dependent
                on the board type.  The value for each port must
                remain constant at least from one re-initialization
                of the entity's network management system to the
                next re-initialization."
    ::= { s3EnetPortEntry 2 }

s3EnetPortLinkStatus OBJECT-TYPE
    SYNTAX  INTEGER {
            off(1),
            on(2),
            other(3)
            }
    ACCESS  read-only
    STATUS  deprecated
    DESCRIPTION
                "Tells whether the port is receiving link status."
    ::= { s3EnetPortEntry 3 }

s3EnetPortPartStatus OBJECT-TYPE
    SYNTAX  INTEGER {
            enabled(1),
            partition(2),
            autoPartition(3),
            timedPartition(4),
            latSecPartition(5)
            }
    ACCESS  read-write
    STATUS  deprecated
    DESCRIPTION
                "This indicates the operational status of the Port.
                Writing a partition(2) will partition the port
                indefinitely and enabled(1) will enable the port.

                If a timed partition is desired, then writing
                timedPartition(4) to this object at the same time
                that a time value is supplied in s3EnetPortPartTime
                is required. Timed partitions will not survive across
                a reset. In this case the port will go to the
                partition(2) state.

                The value latSecPartition(5) is returned when the port
                has been automatically partitioned by the LattisSecure
                Host Module because of a security violation.  The value
                autoPartition(3) is returned when the port has been
                automatically partitioned by the repeater using the
                802.3 repeater auto-partition function.

                The agent will not allow this object to be set to
                autoPartition(3) or latSecPartition(5) using an
                SNMP request."
    ::= { s3EnetPortEntry 4 }

s3EnetPortJabberStatus OBJECT-TYPE
    SYNTAX  INTEGER {
            ok(1),
            jabbering(2)
            }
    ACCESS  read-only
    STATUS  mandatory
    DESCRIPTION
                "Tells whether the DTE connected to the Port is
                jabbering or not."
    ::= { s3EnetPortEntry 5 }

s3EnetPortFrmsRxOk OBJECT-TYPE
    SYNTAX  Counter
    ACCESS  read-only
    STATUS  mandatory
    DESCRIPTION
                "This contains a count of frames that are successfully
                received by the port.  This does not include frames
                received with a frame-too-long, runt, FCS, or alignment
                errors.  This counter includes broadcast and multicast
                frames that are received."
    ::= { s3EnetPortEntry 6 }

s3EnetPortOctetsRxOk OBJECT-TYPE
    SYNTAX  Counter
    ACCESS  read-only
    STATUS  mandatory
    DESCRIPTION
                "Contains a count of data and padding octets in frames
                that are successfully received by the port.  This does
                not include frames received with a frame-too-long, runt,
                FCS, or alignment errors.

                This counter includes octets in broadcast and multicast
                frames that are received.

                This counter does not include the octets in the
                CRC field. The octets in the address and length/type
                fields are counted."
    ::= { s3EnetPortEntry 7 }

s3EnetPortMcastFrmsRxOk OBJECT-TYPE
    SYNTAX  Counter
    ACCESS  read-only
    STATUS  mandatory
    DESCRIPTION
                "This contains a count of frames that are successfully
                received by the port and are directed to an active
                non-broadcast group address.  This does not include
                frames received with a frame-too-long, runt, FCS, or
                alignment errors.

                Only frames that are for a multicast address that this
                interface is receiving are counted. Broadcast packets
                are not included."
    ::= { s3EnetPortEntry 8 }

s3EnetPortBcastFrmsRxOk OBJECT-TYPE
    SYNTAX  Counter
    ACCESS  read-only
    STATUS  mandatory
    DESCRIPTION
                "This contains a count of frames that are successfully
                received by the port and are directed to the broadcast
                group address.  This does not include frames received
                with a frame-too-long, runt, FCS, or alignment errors.

                Multicast packets are not included."
    ::= { s3EnetPortEntry 9 }

s3EnetPortColls OBJECT-TYPE
    SYNTAX  Counter
    ACCESS  read-only
    STATUS  mandatory
    DESCRIPTION
                "This contains a count of collisions. For NMM+ this is a
                true counter.  For other NMMs this is a count of the
                collision flags."
    ::= { s3EnetPortEntry 10 }

s3EnetPortTooLongErrors OBJECT-TYPE
    SYNTAX  Counter
    ACCESS  read-only
    STATUS  mandatory
    DESCRIPTION
                "This contains a count of frames that are received by
                the port and exceed the maximum permitted frame size.
                This counter is incremented when the frameTooLong
                error is detected."
    ::= { s3EnetPortEntry 11 }

s3EnetPortRuntErrors OBJECT-TYPE
    SYNTAX  Counter
    ACCESS  read-only
    STATUS  mandatory
    DESCRIPTION
                "This contains a count of frames received by the port
                that are less than the minimum permitted frame size and
                have a good FCS."
    ::= { s3EnetPortEntry 12 }

s3EnetPortAlignErrors OBJECT-TYPE
    SYNTAX  Counter
    ACCESS  read-only
    STATUS  mandatory
    DESCRIPTION
                "This contains a count of frames received by the port
                that are not an integral number of octets in length and
                do not pass the FCS check.  This counter is incremented
                when the alignmentError status is detected."
    ::= { s3EnetPortEntry 13 }

s3EnetPortFcsErrors OBJECT-TYPE
    SYNTAX  Counter
    ACCESS  read-only
    STATUS  mandatory
    DESCRIPTION
                "This contains a count of frames received the port
                that are an integral number of octets in length that
                do not pass the FCS check.  This counter is incremented
                when the frameCheckError status is detected."
    ::= { s3EnetPortEntry 14 }

s3EnetPortLateCollErrors OBJECT-TYPE
    SYNTAX  Counter
    ACCESS  read-only
    STATUS  mandatory
    DESCRIPTION
                "This contains a count of late collisions. For NMM+
                this is a true counter.  For other NMMs this is a count
                of the late collision flags."
    ::= { s3EnetPortEntry 15 }

s3EnetPortAuthStatus OBJECT-TYPE
    SYNTAX  INTEGER {
            other(1),
            on(2),
            off(3)
            }
    ACCESS  read-write
    STATUS  mandatory
    DESCRIPTION
                "This object is only used if s3EnetConcSecureStatus
                is set to portCheckOn(3) or if the port is on a
                LattisSecure Host Module.

                In this case, turning this object on(2) means that
                any node that heard on this port which is not allowed
                on this port will cause the action specified in
                s3EnetPortAuthAction to take place.

                This object does not affect the LattisSecure transmit
                security feature for the port.  It is incompatible with
                LattisSecure continuous learning mode.  If the value of
                s3EnetPortAddrLearnMode for a LattisSecure port is
                continuousLearn(3), turning this object to on(2) for
                that port will not have any affect.

                If s3EnetConcSecureStatus is set to portCheckOn(3) but
                this object is set to off(3), then all authorized nodes
                or LattisSecure receive security features for this port
                are deactivated.

                If s3EnetConcSecureStatus is not set to portCheckOn(3),
                then this object will not be used for allowed nodes,
                but will be used for LattisSecure."
    ::= { s3EnetPortEntry 16 }

s3EnetPortAuthAction OBJECT-TYPE
    SYNTAX  INTEGER {
            other(1),
            noAction(2),
            sendTrap(3),
            partition(4),
            sendTrapPartition(5)
            }
    ACCESS  read-write
    STATUS  mandatory
    DESCRIPTION
                "If s3EnetConcSecureStatus is portCheckOn(3) or this
                port is on a LattisSecure Host Module, and
                s3EnetPortAuthStatus is on(2) and an authorized nodes
                violation occurs on this port, then the action specified
                by this object will take place on this port.

                If the port is a LattisSecure port, the authorized
                nodes security will be implemented by the LattisSecure
                Host Module."
    ::= { s3EnetPortEntry 17 }

s3EnetPortPartTime OBJECT-TYPE
    SYNTAX  TimeTicks
    ACCESS  read-write
    STATUS  deprecated
    DESCRIPTION
                "When partitioning the port for a specified time,
                s3EnetPortPartStatus must be set with timedpartition(4)
                and this object must be supplied with the duration
                value.  If a PDU sets s3EnetPortPartStatus and not
                this object, the port will not be partitioned."
    ::= { s3EnetPortEntry 18 }

s3EnetPortType OBJECT-TYPE
    SYNTAX  INTEGER {
            other(1),
            tenBaseT(2),
            tenBaseTMdi(3),
            aui(4),
            bnc(5),
            foirl(6),
            tenBaseFL(7),
            switch(8),
            switchMdi(9),
            tenBaseFLRedund(10)
            }
    ACCESS  read-only
    STATUS  deprecated
    DESCRIPTION
                "The media connection type for this port.

                Note that this object was called s3EnetPortMDIXSwitch
                in the Ethernet 3.3 and 4.0 MIBs."
    ::= { s3EnetPortEntry 19 }

s3EnetPortInterconStatus OBJECT-TYPE
    SYNTAX  INTEGER {
            other(1),
            interconnect(2)
            }
    ACCESS  read-only
    STATUS  mandatory
    DESCRIPTION
                "This object tells whether the port is connected to a
                host or to an interconnect (defined to be another NMM
                that is sending hello messages).

                The NMM agent will assign this object the value other(1)
                on initialization.  If it sees hello messages coming in
                on the port, it will change the InterconStatus to be
                interconnect(2)."
    ::= { s3EnetPortEntry 20 }

s3EnetPortAddrCollect OBJECT-TYPE
    SYNTAX  INTEGER {
            default(1),
            neverCollect(2),
            alwaysCollect(3)
            }
    ACCESS  read-write
    STATUS  mandatory
    DESCRIPTION
                "This object tells whether the NMM should collect
                node address information from this port for the Find
                Nodes, Show Nodes, and Traffic Matrix (NMM+ only)
                tables.

                By default, the node addresses are collected only
                from ports that are not identified as interconnect
                ports.  In addition, allowed nodes checking is
                done only on ports that are not interconnect ports.
                This object provides a means of overriding the default
                for collection and checking of node addresses.

                Setting this variable to default(1) tells the NMM to
                collect and check addresses if and only the port has
                not been identified as an interconnect port.

                To disable node address collection and checking on a
                port, set this object to neverCollect(2).

                To collect and check node addresses for an interconnect
                port, set this object to alwaysCollect(3).

                This object and its default setting has no affect
                on LattisSecure receive or transmit security features.

                To restore the 'natural' value for the port, set this
                object to default(1)."
    ::= { s3EnetPortEntry 21 }

s3EnetPortAddrLearnMode OBJECT-TYPE
    SYNTAX  INTEGER {
            other(1),
            noAutoLearn(2),
            continuousLearn(3),
            oneShotLearn(4)
            }
    ACCESS  read-write
    STATUS  mandatory
    DESCRIPTION
                "This object indicates whether the port should
                automatically learn the port address by reading the
                source address on the incoming packets.  This object
                applies only to ports on a LattisSecure Host Module.
                For other ports, the agent  returns the value other.

                A Get will return the current learning mode of the port.

                Setting to noAutoLearn(2) can be used to turn off
                continuousLearn (3) or oneShotLearn(4).

                The value of this object is in effect regardless of the
                value of s3EnetConcSecureStatus or s3EnetPortAuthStatus.

                Continuous learning is not compatible with LattisSecure
                receive security, thus s3EnetPortAddrLearnMode should not
                be set to continuousLearn(3) when s3EnetPortAuthStatus
                is on(2).  If this combination is set, the receive
                security will not function.

                If this object is set to oneShotLearn(4), the agent will
                store the address (when it is learned) into the allowed
                nodes tables.  This can cause the current address to be
                written over.

                Because continuous learning is not compatible with
                receive security, addresses learned while the port
                is in continuous learning mode will not be stored in
                the allowed nodes tables.

                Attempts to set the value to other(1) on a LattisSecure
                port will be rejected by the agent.  Likewise, attempts
                to set the value to noAutoLearn(2), continuousLearn(3),
                or oneShotLearn(4) on a non-LattisSecure port will be
                rejected."
    ::= { s3EnetPortEntry 22 }

s3EnetPortTxSecurity OBJECT-TYPE
    SYNTAX  INTEGER {
            other(1),
            on(2),
            off(3)
            }
    ACCESS  read-write
    STATUS  mandatory
    DESCRIPTION
                "This value of this object is meaningful only when
                s3EnetConcSecureStatus is not set to concSecureOff(5)
                (i.e., if security features are activated on the
                concentrator).

                This object applies only to ports on LattisSecure Host
                Modules.  For other ports, the agent will return other(1)
                in response to a get request.

                The value off(3) indicates that LattisSecure transmit
                security is disabled on this LattisSecure port.  The
                value on(2) indicates that LattisSecure transmit security
                is enabled on this LattisSecure port.

                Attempts to set the value to other(1) on a LattisSecure
                port will be rejected by the agent.  Likewise, attempts
                to set the value to on(2) or off(3) on a non-LattisSecure
                port will be rejected."
    ::= { s3EnetPortEntry 23 }

s3EnetCommonPortTable OBJECT-TYPE
    SYNTAX  SEQUENCE OF S3EnetCommonPortEntry
    ACCESS  not-accessible
    STATUS  mandatory
    DESCRIPTION
                "This table provides a list of port entries.  The
                number of entries is given for any Ethernet board
                in the concentrator, even if the board is not on the
                same Ethernet segment as this NMM."
    ::= { s3000EnetPort 2 }

s3EnetCommonPortEntry OBJECT-TYPE
    SYNTAX  S3EnetCommonPortEntry
    ACCESS  not-accessible
    STATUS  mandatory
    DESCRIPTION
                "A table containing objects about the ports of each
                Ethernet board plugged into the 3000-series chassis."
    INDEX   { s3EnetCommonPortBoardIndex,
              s3EnetCommonPortIndex }
    ::= { s3EnetCommonPortTable 1 }

S3EnetCommonPortEntry ::= SEQUENCE {
    s3EnetCommonPortBoardIndex
        INTEGER,
    s3EnetCommonPortIndex
        INTEGER,
    s3EnetCommonPortLinkStatus
        INTEGER,
    s3EnetCommonPortPartStatus
        INTEGER,
    s3EnetCommonPortType
        INTEGER,
    s3EnetCommonPortPartTime
        TimeTicks
    }

s3EnetCommonPortBoardIndex OBJECT-TYPE
    SYNTAX  INTEGER
    ACCESS  read-only
    STATUS  mandatory
    DESCRIPTION
                "A unique value for each board.  Its value ranges
                between 1 and 12.  The value for each board must
                remain constant at least from one re-initialization
                of the entity's network management system to the
                next re-initialization."
    ::= { s3EnetCommonPortEntry 1 }

s3EnetCommonPortIndex OBJECT-TYPE
    SYNTAX  INTEGER
    ACCESS  read-only
    STATUS  mandatory
    DESCRIPTION
                "A unique value for each port.  Its value is dependent
                on the board type."
    ::= { s3EnetCommonPortEntry 2 }

s3EnetCommonPortLinkStatus OBJECT-TYPE
    SYNTAX  INTEGER {
            off(1),
            on(2),
            other(3)
            }
    ACCESS  read-only
    STATUS  mandatory
    DESCRIPTION
                "Tells whether the port is receiving link status."
    ::= { s3EnetCommonPortEntry 3 }

s3EnetCommonPortPartStatus OBJECT-TYPE
    SYNTAX  INTEGER {
            enabled(1),
            partition(2),
            autoPartition(3),
            timedPartition(4),
            latSecPartition(5)
            }
    ACCESS  read-write
    STATUS  mandatory
    DESCRIPTION
                "This indicates the operational status of the Port.
                Writing a partition(2) will partition the port
                indefinitely and enabled(1) will enable the port.

                If a timed partition is desired, then writing
                timedPartition(4) to this object at the same time
                that a time value is supplied in s3EnetCommonPortPartTime
                is required.  Timed partitions will not survive across
                a reset.  In this case the port will go to the
                partition(2) state.

                The value latSecPartition(5) is returned when the port
                has been automatically partitioned by the LattisSecure
                Host Module because of a security violation.  The value
                autoPartition(3) is returned when the port has been
                automatically partitioned by the repeater using the
                802.3 repeater auto-partition function.

                The agent will not allow this object to be set to
                autoPartition(3) or latSecPartition(5) using an SNMP
                request.

                Note that the value timedPartition(4)  is returned only
                when the board is timed partitioned by this NMM."
    ::= { s3EnetCommonPortEntry 4 }

s3EnetCommonPortType OBJECT-TYPE
    SYNTAX  INTEGER {
            other(1),
            tenBaseT(2),
            tenBaseTMdi(3),
            aui(4),
            bnc(5),
            foirl(6),
            tenBaseFL(7),
            switch(8),
            switchMdi(9),
            tenBaseFLRedund(10)
            }
    ACCESS  read-only
    STATUS  mandatory
    DESCRIPTION
                "The media connnection type for this port.

                Note that this object was called s3EnetPortMDIXSwitch
                in the Ethernet 3.3 and 4.0 MIBs."
    ::= { s3EnetCommonPortEntry 5 }

s3EnetCommonPortPartTime OBJECT-TYPE
    SYNTAX  TimeTicks
    ACCESS  read-write
    STATUS  mandatory
    DESCRIPTION
                "When partitioning the port for a specified time,
                s3EnetCommonPortPartStatus must be set with
                timedPartition(4) and this object must be supplied
                with the duration value.  If a PDU sets
                s3EnetCommonPortPartStatus and not this object,
                the port will not be partitioned."
    ::= { s3EnetCommonPortEntry 6 }

s3EnetRedPortTable OBJECT-TYPE
    SYNTAX  SEQUENCE OF S3EnetRedPortEntry
    ACCESS  not-accessible
    STATUS  mandatory
    DESCRIPTION
                "A table of ports for each 10BASE-FL board with
                redundancy capability.  The number of boards is
                determined by checking s3EnetCommonBoardRedund having
                a value of redundCapable(2) for each board in table
                s3EnetCommonBoardTable."
    ::= { s3000EnetPort 3 }

s3EnetRedPortEntry OBJECT-TYPE
    SYNTAX  S3EnetRedPortEntry
    ACCESS  not-accessible
    STATUS  mandatory
    DESCRIPTION
                "An entry in the table of ports on boards with
                redundancy capability."
    INDEX   { s3EnetRedPortBoardIndex,
              s3EnetRedPortIndex }
    ::= { s3EnetRedPortTable 1 }

S3EnetRedPortEntry ::= SEQUENCE {
    s3EnetRedPortBoardIndex
        INTEGER,
    s3EnetRedPortIndex
        INTEGER,
    s3EnetRedPortRedundMode
        INTEGER,
    s3EnetRedPortOperStatus
        INTEGER,
    s3EnetRedPortRemoteOperStatus
        INTEGER,
    s3EnetRedPortCompanionSlotNo
        INTEGER,
    s3EnetRedPortCompanionPortNo
        INTEGER
    }

s3EnetRedPortBoardIndex OBJECT-TYPE
    SYNTAX  INTEGER
    ACCESS  read-only
    STATUS  mandatory
    DESCRIPTION
                "The index of the slot containing the board.  The value
                for each board must remain constant at least from one
                re-initialization of the entity's network management
                system to the next re-initialization."
    ::= { s3EnetRedPortEntry 1 }

s3EnetRedPortIndex OBJECT-TYPE
    SYNTAX  INTEGER
    ACCESS  read-only
    STATUS  mandatory
    DESCRIPTION
                "The index of the port on the module."
    ::= { s3EnetRedPortEntry 2 }

s3EnetRedPortRedundMode OBJECT-TYPE
    SYNTAX  INTEGER {
            standAlone(1),
            hwActive(2),
            hwStandby(3)
            }
    ACCESS  read-only
    STATUS  mandatory
    DESCRIPTION
                "This object indicates the port's redundancy mode. A value
                of standAlone(1) indicates that the port is not set for
                hardware redundancy. A value of hwActive(2) indicates that
                the port is the active one of a hardware redundant pair.
                A value of hwStandby(3) indicates that the port is the
                standby one of a hardware redundant pair"
    ::= { s3EnetRedPortEntry 3 }

s3EnetRedPortOperStatus OBJECT-TYPE
    SYNTAX  INTEGER {
            other(1),
            ok(2),
            localFault(3),
            remoteFault(4)
            }
    ACCESS  read-only
    STATUS  mandatory
    DESCRIPTION
                "This object indicates port's redundancy status.  This
                value is valid only when the redundant mode is not
                standAlone(1).  The values are:
                  other(1).........none of the following
                  ok(2)............no fault
                  localFault(3)....the port had a Local Fault condition
                  remoteFault(4)...the port is receiving Remote Fault signal

                Either a localFault(3) or remoteFault(4) condition should
                cause a redundant port pair to switchover."
    ::= { s3EnetRedPortEntry 4 }

s3EnetRedPortRemoteOperStatus OBJECT-TYPE
    SYNTAX  INTEGER {
            snpxFLRemFltCpblPortUp(1),
            snpxFLFBRemFltCpblPortUp(2),
            tenBaseFLPortUp(3),
            tenBaseFBPortUp(4),
            snpxRemFltCpblPortFault(5),
            tenBaseFBPortFault(6),
            unknown(7)
            }
    ACCESS  read-only
    STATUS  mandatory
    DESCRIPTION
                "This object reflects the real time status of the
                received data from the remote port.

                A value of snpxFLRemFltCpblPortUp(1) indicates that
                the remote port is capable of 10BASE-FL signaling, as
                well as SynOptics proprietary remote fault signaling.
                A remote fault on such a port is indicated by
                snpxRemFltCpblPortFault(5).

                A value of snpxFLFBRemFltCpblPortUp(2) indicates that
                the remote port is capable of 10BASE-FL, 10BASE-FB and
                SynOptics proprietary remote fault signaling.  A remote
                fault on such a port is indicated by
                snpxRemFltCpblPortFault(5).

                A value of tenBaseFLPortUp(3) indicates that the remote
                port uses regular idle 10BASE-FL signaling, and is
                incapable of remote fault signaling.

                A value of tenBaseFBPortUp(4) indicates that the remote
                port uses 10BASE-FB synchronous signaling.  A remote
                fault on such a port is indicated by
                tenBaseFBPortFault(6).

                A value of unknown(7) indicates that the remote signal
                received is none of the above."
    ::= { s3EnetRedPortEntry 5 }

s3EnetRedPortCompanionSlotNo OBJECT-TYPE
    SYNTAX  INTEGER
    ACCESS  read-only
    STATUS  mandatory
    DESCRIPTION
                "The slot number of the other port which is in the
                redundant pair.  In the case of a standalone port,
                a value of 0 will be returned."
    ::= { s3EnetRedPortEntry 6 }

s3EnetRedPortCompanionPortNo OBJECT-TYPE
    SYNTAX  INTEGER
    ACCESS  read-only
    STATUS  mandatory
    DESCRIPTION
                "The port number of the other port which is in the
                redundant pair.  In the case of a standalone port,
                a value of 0 will be returned."
    ::= { s3EnetRedPortEntry 7 }

s3EnetPlusPortTable OBJECT-TYPE
    SYNTAX  SEQUENCE OF S3EnetPlusPortEntry
    ACCESS  not-accessible
    STATUS  mandatory
    DESCRIPTION
                "This table provides a list of entries, each entry
                providing information related to frame MAC level
                error conditions per port. This table is conceptually
                an extension to the s3EnetPortTable and is
                only implemented by the 3313S and 3314S NMMs."
    ::= { s3000EnetPlusStatistics 1 }

s3EnetPlusPortEntry OBJECT-TYPE
    SYNTAX  S3EnetPlusPortEntry
    ACCESS  not-accessible
    STATUS  mandatory
    DESCRIPTION
                "An entry in the Plus Port table."
    INDEX   { s3EnetPlusPortBoardIndex,
              s3EnetPlusPortIndex }
    ::= { s3EnetPlusPortTable 1 }

S3EnetPlusPortEntry ::= SEQUENCE {
    s3EnetPlusPortBoardIndex
        INTEGER,
    s3EnetPlusPortIndex
        INTEGER,
    s3EnetPortFragments
        Counter,
    s3EnetPortShortEvents
        Counter,
    s3EnetPortAutoPartitions
        Counter,
    s3EnetPortRateMismatches
        Counter,
    s3EnetPortJabbers
        Counter,
    s3EnetPortLastSrcAddr
        PhysAddress,
    s3EnetPortSrcAddrChanges
        Counter
    }

s3EnetPlusPortBoardIndex OBJECT-TYPE
    SYNTAX  INTEGER
    ACCESS  read-only
    STATUS  mandatory
    DESCRIPTION
                "A unique value for each board.  Its value ranges between
                1 and 12.  (This is the slot number.)"
    ::= { s3EnetPlusPortEntry 1 }

s3EnetPlusPortIndex OBJECT-TYPE
    SYNTAX  INTEGER
    ACCESS  read-only
    STATUS  mandatory
    DESCRIPTION
                "A unique value for each port.  Its value typically ranges
                between 1 and 12."
    ::= { s3EnetPlusPortEntry 2 }

s3EnetPortFragments OBJECT-TYPE
    SYNTAX  Counter
    ACCESS  read-only
    STATUS  mandatory
    DESCRIPTION
                "This contains a count of fragments received by the
                board between 80-512 bits (64 bytes), inclusively,
                with invalid FCS or alignment errors.  (These
                commonly represent collision fragments, and are
                not errors.  Collision fragments were called
                FragErrors in the rev 3.x MIB, and were counted
                only on a per-board basis.)"
    ::= { s3EnetPlusPortEntry 3 }

s3EnetPortShortEvents OBJECT-TYPE
    SYNTAX  Counter
    ACCESS  read-only
    STATUS  mandatory
    DESCRIPTION
                "This contains a count of fragments received by the
                port shorter than 80 bits."
    ::= { s3EnetPlusPortEntry 4 }

s3EnetPortAutoPartitions OBJECT-TYPE
    SYNTAX  Counter
    ACCESS  read-only
    STATUS  mandatory
    DESCRIPTION
                "This contains a count of times the ports on the board
                have autopartitioned due to excessive collisions (more
                than 32 consecutive collisions).  This count is an
                approximation and may be less than the total count."
    ::= { s3EnetPlusPortEntry 5 }

s3EnetPortRateMismatches OBJECT-TYPE
    SYNTAX  Counter
    ACCESS  read-only
    STATUS  mandatory
    DESCRIPTION
                "This contains a count of the occurrences of out of
                spec bit rates.  This indicates the number of times
                FIFO buffer over-runs or underruns due to transmission
                rate errors."
    ::= { s3EnetPlusPortEntry 6 }

s3EnetPortJabbers OBJECT-TYPE
    SYNTAX  Counter
    ACCESS  read-only
    STATUS  mandatory
    DESCRIPTION
                "This contains a count of the times that MAU jabber
                lockup protection (MJLP) was invoked because transmission
                of data from this port exceeded 5 msec in duration.
                This information can be useful in identifying faulty
                stations."
    ::= { s3EnetPlusPortEntry 7 }

s3EnetPortLastSrcAddr OBJECT-TYPE
    SYNTAX  PhysAddress (SIZE(6))
    ACCESS  read-only
    STATUS  mandatory
    DESCRIPTION
                "This is the source address of the last packet
                received through this port."
    ::= { s3EnetPlusPortEntry 8 }

s3EnetPortSrcAddrChanges OBJECT-TYPE
    SYNTAX  Counter
    ACCESS  read-only
    STATUS  mandatory
    DESCRIPTION
                "This is the number of times that the
                s3EnetPortLastSrcAddr object for this has changed."
    ::= { s3EnetPlusPortEntry 9 }

s3EnetPlusBoardTable OBJECT-TYPE
    SYNTAX  SEQUENCE OF S3EnetPlusBoardEntry
    ACCESS  not-accessible
    STATUS  mandatory
    DESCRIPTION
                "This table provides a list of entries, each entry
                providing information related to frame MAC level
                error conditions per board.  This table is conceptually
                an extension to the s3EnetboardTable and is
                only implemented by the 3313S and 3314S NMMs."
    ::= { s3000EnetPlusStatistics 2 }

s3EnetPlusBoardEntry OBJECT-TYPE
    SYNTAX  S3EnetPlusBoardEntry
    ACCESS  not-accessible
    STATUS  mandatory
    DESCRIPTION
                "An entry in the Plus Board table."
    INDEX   { s3EnetPlusBoardIndex }
    ::= { s3EnetPlusBoardTable 1 }

S3EnetPlusBoardEntry ::= SEQUENCE {
    s3EnetPlusBoardIndex
        INTEGER,
    s3EnetBoardFragments
        Counter,
    s3EnetBoardShortEvents
        Counter,
    s3EnetBoardAutoPartitions
        Counter,
    s3EnetBoardRateMismatches
        Counter,
    s3EnetBoardJabbers
        Counter
    }

s3EnetPlusBoardIndex OBJECT-TYPE
    SYNTAX  INTEGER
    ACCESS  read-only
    STATUS  mandatory
    DESCRIPTION
                "The board number part of an index."
    ::= { s3EnetPlusBoardEntry 1 }

s3EnetBoardFragments OBJECT-TYPE
    SYNTAX  Counter
    ACCESS  read-only
    STATUS  mandatory
    DESCRIPTION
                "This contains a count of fragments received by the
                board between 80-512 bits (64 bytes), inclusively,
                with invalid FCS or alignment errors.  (These
                commonly represent collision fragments, and are
                not errors.  Collision fragments were called
                FragErrors in the rev 3.x MIB, and were counted
                only on a per-concentrator basis.)"
    ::= { s3EnetPlusBoardEntry 2 }

s3EnetBoardShortEvents OBJECT-TYPE
    SYNTAX  Counter
    ACCESS  read-only
    STATUS  mandatory
    DESCRIPTION
                "This contains a count of fragments received by
                the board shorter than 80 bits."
    ::= { s3EnetPlusBoardEntry 3 }

s3EnetBoardAutoPartitions OBJECT-TYPE
    SYNTAX  Counter
    ACCESS  read-only
    STATUS  mandatory
    DESCRIPTION
                "This contains a count of times the ports on this
                board have been autopartitioned due to excessive
                collisions (more than 32 consecutive collisions).
                This count is an approximation and may be less than
                the total count."
    ::= { s3EnetPlusBoardEntry 4 }

s3EnetBoardRateMismatches OBJECT-TYPE
    SYNTAX  Counter
    ACCESS  read-only
    STATUS  mandatory
    DESCRIPTION
                "This contains a count of the occurrences of out of
                spec bit rates.  This indicates the number of times
                FIFO buffer over-runs or underruns due to
                transmission rate errors."
    ::= { s3EnetPlusBoardEntry 5 }

s3EnetBoardJabbers OBJECT-TYPE
    SYNTAX  Counter
    ACCESS  read-only
    STATUS  mandatory
    DESCRIPTION
                "This contains a count of the times that MAU jabber
                lockup protection (MJLP) was invoked because
                transmission of data from a port on this board
                exceeded 5 msec in duration.  This information can
                be useful in identifying faulty stations."
    ::= { s3EnetPlusBoardEntry 6 }

s3EnetConcShortEvents OBJECT-TYPE
    SYNTAX  Counter
    ACCESS  read-only
    STATUS  mandatory
    DESCRIPTION
                "This contains a count of fragments received by
                the concentrator shorter than 80 bits."
    ::= { s3000EnetPlusConc 1 }

s3EnetConcAutoPartitions OBJECT-TYPE
    SYNTAX  Counter
    ACCESS  read-only
    STATUS  mandatory
    DESCRIPTION
                "This contains a count of times the ports on this
                concentrator have been autopartitioned due to
                excessive collisions (more than 32 consecutive
                collisions).  This count is based on a one-bit
                counter (flag) per port in the host modules, and
                will not always represent the total count."
    ::= { s3000EnetPlusConc 2 }

s3EnetConcRateMismatches OBJECT-TYPE
    SYNTAX  Counter
    ACCESS  read-only
    STATUS  mandatory
    DESCRIPTION
                "This contains a count of the occurrences of out
                of spec bit rates.  This indicates the number of
                times FIFO buffer over-runs or underruns due to
                transmission rate errors."
    ::= { s3000EnetPlusConc 3 }

s3EnetConcJabbers OBJECT-TYPE
    SYNTAX  Counter
    ACCESS  read-only
    STATUS  mandatory
    DESCRIPTION
                "This contains a count of the times that MAU jabber
                lockup protection (MJLP) was invoked because
                transmission of data from a port on this
                concentrator exceeded 5 msec in duration.
                This information can be useful in identifying
                faulty stations."
    ::= { s3000EnetPlusConc 4 }

s3EnetConcCollBackoffErrors OBJECT-TYPE
    SYNTAX  Counter
    ACCESS  read-only
    STATUS  mandatory
    DESCRIPTION
                "This contains a total concentrator count of the
                collision events that occur during the normal
                collision window (i.e., the collisions is not
                a late collision) and do not have a runt error."
    ::= { s3000EnetPlusConc 5 }

s3TrCommonBoardTable OBJECT-TYPE
    SYNTAX  SEQUENCE OF S3TrCommonBoardEntry
    ACCESS  not-accessible
    STATUS  mandatory
    DESCRIPTION
                "Information maintained for each token ring board.
                The information can be retrieved for any token
                ring board, even if the board is not on the 
                same backplane ring as this NMM.

                The instance is the slot number of the concentrator
                that the board occupies."
    ::= { s3000TrBoard 2 }

s3TrCommonBoardEntry OBJECT-TYPE
    SYNTAX  S3TrCommonBoardEntry
    ACCESS  not-accessible
    STATUS  mandatory
    DESCRIPTION
                "There is one entry per board in this table."
    INDEX   { s3TrCommonBoardIndex }
    ::= { s3TrCommonBoardTable 1 }

S3TrCommonBoardEntry ::= SEQUENCE {
    s3TrCommonBoardIndex
        INTEGER,
    s3TrCommonBoardRing1or2
        INTEGER,
    s3TrCommonBoardRingSpeed
        INTEGER
    }

s3TrCommonBoardIndex OBJECT-TYPE
    SYNTAX  INTEGER
    ACCESS  read-only
    STATUS  mandatory
    DESCRIPTION
                "A unique value for each board.  Its value ranges
                between 1 and 12.  The value for each board must
                remain constant at least from one re-initialization
                of the entity's network management system to the
                next re-initialization.

                If a board is inserted or reinserted in a concentrator
                then the NMM has to be reinitialized."
    ::= { s3TrCommonBoardEntry 1 }

s3TrCommonBoardRing1or2 OBJECT-TYPE
    SYNTAX  INTEGER {
            other(1),
            ring1(2),
            ring2(3)
            }
    ACCESS  read-only
    STATUS  mandatory
    DESCRIPTION
                "Determines which ring the board is currently using
                on the concentrator backplane."
    ::= { s3TrCommonBoardEntry 2 }

s3TrCommonBoardRingSpeed OBJECT-TYPE
    SYNTAX  INTEGER {
            other(1),
            speed1M(2),
            speed4M(3),
            speed16M(4)
            }
    ACCESS  read-only
    STATUS  mandatory
    DESCRIPTION
                "Token Ring speed of the ring that this board is
                connected to."
    ::= { s3TrCommonBoardEntry 3 }

s3TrPortTable OBJECT-TYPE
    SYNTAX  SEQUENCE OF S3TrPortEntry
    ACCESS  not-accessible
    STATUS  mandatory
    DESCRIPTION
                "A table containing information about each port
                of a LattisNet concentrator.  The number of entries
                is given by knowing the number of occupied slots
                in s3ChassisSlotConfigTable whose s3SlotModuleType
                is of a token ring type and is on the same backplane
                ring as the agent NMM."
    ::= { s3000TrPort 1 }

s3TrPortEntry OBJECT-TYPE
    SYNTAX  S3TrPortEntry
    ACCESS  not-accessible
    STATUS  mandatory
    DESCRIPTION
                "A port entry containing objects at the port level
                for a particular port."
    INDEX   { s3TrPortBoardIndex,
              s3TrPortIndex }
    ::= { s3TrPortTable 1 }

S3TrPortEntry ::= SEQUENCE {
    s3TrPortBoardIndex
        INTEGER,
    s3TrPortIndex
        INTEGER,
    s3TrPortWrap
        INTEGER,
    s3TrPortTestLatch
        INTEGER,
    s3TrPortRelayStatus
        INTEGER,
    s3TrPortPhantomStatus
        INTEGER,
    s3TrPortPhantomChangeFlag
        INTEGER,
    s3TrPortChgSyn2IBM
        INTEGER,
    s3TrPortStrap
        INTEGER
    }

s3TrPortBoardIndex OBJECT-TYPE
    SYNTAX  INTEGER
    ACCESS  read-only
    STATUS  mandatory
    DESCRIPTION
                "A unique value for each board.  Its value ranges
                between 1 and 12.  The value for each board must
                remain constant at least from one re-initialization
                of the entity's network management system to the
                next re-initialization.

                If a board is inserted or reinserted in a concentrator
                then the NMM has to be reinitialized."
    ::= { s3TrPortEntry 1 }

s3TrPortIndex OBJECT-TYPE
    SYNTAX  INTEGER
    ACCESS  read-only
    STATUS  mandatory
    DESCRIPTION
                "A unique value for each port.  Its value ranges
                between 1 and 12.  The value for each port must
                remain constant at least from one re-initialization
                of the entity's network management system to the
                next re-initialization.  If the board is an NMM
                board it will only have 2 ports, with Port 1 being
                for Ring In and Port 2 being for Ring Out."
    ::= { s3TrPortEntry 2 }

s3TrPortWrap OBJECT-TYPE
    SYNTAX  INTEGER {
            other(1),
            wrap(2),
            connect(3),
            timedWrap(4),
            beaconWrap(5),
            wrongSpeedWrap(6),
            permBeaconWrap(7),
            securityViolationWrap(8)
            }
    ACCESS  read-write
    STATUS  mandatory
    DESCRIPTION
                "Status of the port. Setting wrap(2) disconnects
                the port from the ring and setting this object to
                connect(3) connects the port to the ring.  If a
                timed wrap is desired, then writing timedWrap(4)
                to this object at the same time that a time value
                is supplied in s3TrPortPartTime is required.
                Timed wraps will not survive across a reset.  In
                this case the port will go to the wrap(2) state.
                BeaconWrap(5) indicates that the port is temporary
                wrapped by the agent due to the station of the
                port which was beaconing. The wrapped port will
                be unwrapped by the agent when the station is
                deinserted from the ring.  WrongSpeedWrap(6)
                indicates that the port is wrapped by the host
                module. This is due to the wrong speed of a new
                station which was inserted to the ring.
                PermBeaconWrap(7) indicates that the port is
                wrapped by the agent permanently. This is caused
                by the beaconing station of the port attempting
                to deinsert/insert to the ring for more than
                2 times within 1 minute. The wrapped port will
                not be unwrapped by the agent. SecurityViolationWrap(8)
                indicates that the port is wrapped by the agent due to
                the station not being allowed to insert in the port.
                The values beaconWrap(5), wrongSpeedWap(6),
                permanentBeaconwrap(7) and securityViolationWrap(8)
                can not be written.

                Note: The securityViolationWrap feature is implemented
                      only in version 4.3 and subsequent agents."
    ::= { s3TrPortEntry 3 }

s3TrPortTestLatch OBJECT-TYPE
    SYNTAX  INTEGER {
            other(1),
            on(2),
            off(3)
            }
    ACCESS  read-write
    STATUS  mandatory
    DESCRIPTION
                "Status of the test latch which is used to set
                the channel decoder used to monitor the health
                of the communication path between the NMM and
                the module channel."
    ::= { s3TrPortEntry 4 }

s3TrPortRelayStatus OBJECT-TYPE
    SYNTAX  INTEGER {
            other(1),
            on(2),
            off(3)
            }
    ACCESS  read-only
    STATUS  mandatory
    DESCRIPTION
                "Status of the channel's present relay mode.
                On(2) means the channel is in the ring and off(3)
                means the channel is bypassed."
    ::= { s3TrPortEntry 5 }

s3TrPortPhantomStatus OBJECT-TYPE
    SYNTAX  INTEGER {
            other(1),
            on(2),
            off(3)
            }
    ACCESS  read-only
    STATUS  mandatory
    DESCRIPTION
                "Status of the ring access request signal."
    ::= { s3TrPortEntry 6 }

s3TrPortPhantomChangeFlag OBJECT-TYPE
    SYNTAX  INTEGER {
            other(1),
            noChange(2),
            change(3)
            }
    ACCESS  read-only
    STATUS  mandatory
    DESCRIPTION
                "Change(3) indicates that port phantom has been
                changed from OFF to ON.  After inquiry by NMS, it
                will be cleared to noChange(2).  Port phantom
                changing from ON to OFF has no impact on this object."
    ::= { s3TrPortEntry 7 }

s3TrPortChgSyn2IBM OBJECT-TYPE
    SYNTAX  INTEGER {
            notSupported(1),
            synoptics(2),
            ibm(3)
            }
    ACCESS  read-write
    STATUS  mandatory
    DESCRIPTION
                "If the port is on a ring in/ring out module this
                object changes the strap state depending on the
                jumper setting retrieved as s3TrPortStrap.  If the
                strap is set for SynOptics phantom option, this
                object can be changed to ibm(3).  If the strap is
                set for non-SynOptics option, this object can not
                be changed.

                Non ring in/ring out modules or fiber
                ring in/ring out modules must take on the value
                of notSupported(1)."
    ::= { s3TrPortEntry 8 }

s3TrPortStrap OBJECT-TYPE
    SYNTAX  INTEGER {
            notSupported(1),
            synoptics(2),
            ibm(3)
            }
    ACCESS  read-only
    STATUS  mandatory
    DESCRIPTION
                "If the port is on a ring in/ring out module this
                object signifies whether the hardware jumper is in
                synoptics(2) mode or ibm(3) mode.  This information
                is retrieved using a  NMI command.

                For ports on fiber ring in/ring out modules, and those
                ports not on ring in/ring out modules, the agent
                always returns notSupported(1)."
    ::= { s3TrPortEntry 9 }

s3TrNmmFnNum OBJECT-TYPE
    SYNTAX  INTEGER
    ACCESS  read-write
    STATUS  mandatory
    DESCRIPTION
                "Defines the flat network number that this NMM
                is part of."
    ::= { s3000TrNmm 1 }

s3TrNmmRingNum OBJECT-TYPE
    SYNTAX  INTEGER
    ACCESS  read-write
    STATUS  mandatory
    DESCRIPTION
                "Defines the segment number that this NMM
                is connected to.

                ***ACCESS VARIATION - changed access from read-only"
    ::= { s3000TrNmm 2 }

s3TrNmmSlotNum OBJECT-TYPE
    SYNTAX  INTEGER
    ACCESS  read-only
    STATUS  deprecated
    DESCRIPTION
                "Defines the slot number that this NMM is
                connected to.  New NMS implementations should
                use the object s3AgentMySlotId defined in the
                common MIB.  This object will be deleted from
                a future version of the Token Ring MIB."
    ::= { s3000TrNmm 3 }

s3TrNmmFpuIdRev OBJECT-TYPE
    SYNTAX  INTEGER
    ACCESS  read-only
    STATUS  mandatory
    DESCRIPTION
                "The revision of the Front-end Frame Processing
                unit.  0=Rev. A, 1=Rev. B, etc."
    ::= { s3000TrNmm 4 }

s3TrNmmFpuStatus OBJECT-TYPE
    SYNTAX  INTEGER {
            notPresent(1),
            notOperational(2),
            operational(3)
            }
    ACCESS  read-only
    STATUS  mandatory
    DESCRIPTION
                "The status of the Front-end Frame Processing Unit."
    ::= { s3000TrNmm 5 }

s3TrNmmDramSize OBJECT-TYPE
    SYNTAX  INTEGER {
            other(1),
            k512(2),
            oneMeg(3),
            twoMeg(4),
            threeMeg(5),
            fourMeg(6),
            fiveMeg(7),
            sixMeg(8),
            sevenMeg(9),
            eightMeg(10),
            nineMeg(11),
            tenMeg(12),
            elevenMeg(13),
            twelveMeg(14),
            thirteenMeg(15),
            fourteenMeg(16),
            fifteenMeg(17),
            sixteenMeg(18)
            }
    ACCESS  read-only
    STATUS  mandatory
    DESCRIPTION
                "The highest address of the DRAM in the NMM memory map.
                The possible values are:
                  other(1).........Unknown size
                  k512(2)..........512K memory
                  oneMeg(3)........1M memory
                         .
                         .
                         .
                  sixteenMeg(18)...16M memory"
    ::= { s3000TrNmm 6 }

s3TrNmmEepromSize OBJECT-TYPE
    SYNTAX  INTEGER {
            other(1),
            size2kBytes(2),
            size8kBytes(3),
            size16kBytes(4)
            }
    ACCESS  read-only
    STATUS  mandatory
    DESCRIPTION
                "The size of the EEPROM in the NMM memory map.
                The possible values are:
                  other(1)..........Unknown size
                  size2kBytes(4)....2K by 8
                  size8kBytes(4)....8K by 8
                  size16kBytes(4)...16K by 8"
    ::= { s3000TrNmm 7 }

s3TrNmmGrpAddrFrmsRxOk OBJECT-TYPE
    SYNTAX  Counter
    ACCESS  read-only
    STATUS  mandatory
    DESCRIPTION
                "Number of Group Address frames received without
                error by this NMM.

                Note:  The NMM counts only Group Address frames
                that are addressed to its own Group Address(es)."
    ::= { s3000TrNmm 8 }

s3TrNmmRing1or2 OBJECT-TYPE
    SYNTAX  INTEGER {
            other(1),
            ring1(2),
            ring2(3)
            }
    ACCESS  read-only
    STATUS  mandatory
    DESCRIPTION
                "Determines which ring the NMM is currently using
                on the concentrator backplane."
    ::= { s3000TrNmm 9 }

s3TrNmmRingSpeed OBJECT-TYPE
    SYNTAX  INTEGER {
            other(1),
            speed1M(2),
            speed4M(3),
            speed16M(4)
            }
    ACCESS  read-only
    STATUS  mandatory
    DESCRIPTION
                "Token Ring speed."
    ::= { s3000TrNmm 10 }

s3TrNmmHexDisplay OBJECT-TYPE
    SYNTAX  DisplayString (SIZE(4))
    ACCESS  read-only
    STATUS  mandatory
    DESCRIPTION
                "4 octet hex display string that is displayed
                on the NMM control panel."
    ::= { s3000TrNmm 11 }

s3TrNmmEpromSize OBJECT-TYPE
    SYNTAX  INTEGER {
            other(1),
            k2kby8(2),
            k8kby8(3),
            k16kby8(4),
            k32kby8(5),
            k64kby8(6),
            k128kby8(7),
            k256kby8(8)
            }
    ACCESS  read-only
    STATUS  mandatory
    DESCRIPTION
                "The size of the EPROM in the NMM memory map."
    ::= { s3000TrNmm 12 }

s3TrNodeTable OBJECT-TYPE
    SYNTAX  SEQUENCE OF S3TrNodeEntry
    ACCESS  not-accessible
    STATUS  mandatory
    DESCRIPTION
                "Table containing station specific information."
    ::= { s3000TrNode 1 }

s3TrNodeEntry OBJECT-TYPE
    SYNTAX  S3TrNodeEntry
    ACCESS  not-accessible
    STATUS  mandatory
    DESCRIPTION
                "Entry in the table containing counters and
                profiling information for each node detected on
                the local token ring."
    INDEX   { s3TrNodeEntMacAddress }
    ::= { s3TrNodeTable 1 }

S3TrNodeEntry ::= SEQUENCE {
    s3TrNodeEntMacAddress
        PhysAddress,
    s3TrNodeEntStatus
        INTEGER,
    s3TrNodeEntNodeStatus
        OCTET STRING,
    s3TrNodeLineErrs
        Counter,
    s3TrNodeBurstErrs
        Counter,
    s3TrNodeAriFciErrs
        Counter,
    s3TrNodeLostFrames
        Counter,
    s3TrNodeRcvCongestErrs
        Counter,
    s3TrNodeFrmCopyErrs
        Counter,
    s3TrNodeTokenErrs
        Counter,
    s3TrNodeInternalErrs
        Counter,
    s3TrNodeAbortTransErrs
        Counter,
    s3TrNodeFrequencyErrs
        Counter,
    s3TrNodeEntProductId
        OCTET STRING,
    s3TrNodeEntUna
        OCTET STRING,
    s3TrNodeEntNodeVersion
        OCTET STRING,
    s3TrNodeEntPhysDrop
        OCTET STRING,
    s3TrNodeEntFuncAddr
        OCTET STRING,
    s3TrNodeEntAuthFuncClass
        OCTET STRING,
    s3TrNodeEntAuthAccPriority
        OCTET STRING,
    s3TrNodeEntGrpAddr
        OCTET STRING,
    s3TrNodeEntStationId
        OCTET STRING,
    s3TrNodeEntBeaconType
        INTEGER,
    s3TrNodeBeaconCnt
        Counter,
    s3TrNodeLastBeaconTime
        TimeTicks,
    s3TrNodeLastInsertTime
        TimeTicks,
    s3TrNodeFirstInsertTime
        TimeTicks,
    s3TrNodeLastDeinsertTime
        TimeTicks,
    s3TrNodeRemoveStation
        INTEGER
    }

s3TrNodeEntMacAddress OBJECT-TYPE
    SYNTAX  PhysAddress (SIZE(6))
    ACCESS  read-only
    STATUS  mandatory
    DESCRIPTION
                "MAC address of node that this entry in the
                table is for."
    ::= { s3TrNodeEntry 1 }

s3TrNodeEntStatus OBJECT-TYPE
    SYNTAX  INTEGER {
            beaconing(1),
            notBeaconing(2)
            }
    ACCESS  read-only
    STATUS  mandatory
    DESCRIPTION
                "Tells whether the station is currently
                beaconing or not."
    ::= { s3TrNodeEntry 4 }

s3TrNodeEntNodeStatus OBJECT-TYPE
    SYNTAX  OCTET STRING (SIZE(6))
    ACCESS  read-only
    STATUS  mandatory
    DESCRIPTION
                "Node status as defined in 802.5 specification
                (section 3.3.2.18)."
    ::= { s3TrNodeEntry 5 }

s3TrNodeLineErrs OBJECT-TYPE
    SYNTAX  Counter
    ACCESS  read-only
    STATUS  mandatory
    DESCRIPTION
                "Number of line errors.  Section 3.8.1 of
                IEEE 802.5 specification."
    ::= { s3TrNodeEntry 6 }

s3TrNodeBurstErrs OBJECT-TYPE
    SYNTAX  Counter
    ACCESS  read-only
    STATUS  mandatory
    DESCRIPTION
                "Number of burst errors.  Section 3.8.3 of
                IEEE 802.5 specification."
    ::= { s3TrNodeEntry 7 }

s3TrNodeAriFciErrs OBJECT-TYPE
    SYNTAX  Counter
    ACCESS  read-only
    STATUS  mandatory
    DESCRIPTION
                "Number of ARI FCI errors.  See AC errors,
                Section 3.8.4 of IEEE 802.5 specification."
    ::= { s3TrNodeEntry 8 }

s3TrNodeLostFrames OBJECT-TYPE
    SYNTAX  Counter
    ACCESS  read-only
    STATUS  mandatory
    DESCRIPTION
                "Number of frames lost.  Section 3.8.6 of
                IEEE 802.5 specification."
    ::= { s3TrNodeEntry 9 }

s3TrNodeRcvCongestErrs OBJECT-TYPE
    SYNTAX  Counter
    ACCESS  read-only
    STATUS  mandatory
    DESCRIPTION
                "Number of receive congestion errors.
                Section 3.8.7 of IEEE 802.5 specification."
    ::= { s3TrNodeEntry 10 }

s3TrNodeFrmCopyErrs OBJECT-TYPE
    SYNTAX  Counter
    ACCESS  read-only
    STATUS  mandatory
    DESCRIPTION
                "Number of frame copy errors.  Section 3.8.8
                of IEEE 802.5 specification."
    ::= { s3TrNodeEntry 11 }

s3TrNodeTokenErrs OBJECT-TYPE
    SYNTAX  Counter
    ACCESS  read-only
    STATUS  mandatory
    DESCRIPTION
                "Number of token errors.  Section 3.8.10
                of IEEE 802.5 specification."
    ::= { s3TrNodeEntry 12 }

s3TrNodeInternalErrs OBJECT-TYPE
    SYNTAX  Counter
    ACCESS  read-only
    STATUS  mandatory
    DESCRIPTION
                "Number of internal errors.  Section 3.8.2
                of IEEE 802.5 specification."
    ::= { s3TrNodeEntry 13 }

s3TrNodeAbortTransErrs OBJECT-TYPE
    SYNTAX  Counter
    ACCESS  read-only
    STATUS  mandatory
    DESCRIPTION
                "Number of abort delimiter transmitted errors.
                Section 3.8.5 of IEEE 802.5 specification."
    ::= { s3TrNodeEntry 14 }

s3TrNodeFrequencyErrs OBJECT-TYPE
    SYNTAX  Counter
    ACCESS  read-only
    STATUS  mandatory
    DESCRIPTION
                "Number of frequency errors.  Section 3.8.9
                of IEEE 802.5 specification."
    ::= { s3TrNodeEntry 15 }

s3TrNodeEntProductId OBJECT-TYPE
    SYNTAX  OCTET STRING (SIZE(18))
    ACCESS  read-only
    STATUS  mandatory
    DESCRIPTION
                "A brief string describing the product specified
                by the vendor.  Section 3.3.2.14 of IEEE 802.5
                specification.

                The characters in the string are represented in
                EBCDIC for IBM products, in ASCII for others."
    ::= { s3TrNodeEntry 16 }

s3TrNodeEntUna OBJECT-TYPE
    SYNTAX  OCTET STRING (SIZE(6))
    ACCESS  read-only
    STATUS  mandatory
    DESCRIPTION
                "The Upstream Neighbor Address.  Section 3.3.2.15
                of IEEE 802.5 specification."
    ::= { s3TrNodeEntry 17 }

s3TrNodeEntNodeVersion OBJECT-TYPE
    SYNTAX  OCTET STRING (SIZE(10))
    ACCESS  read-only
    STATUS  mandatory
    DESCRIPTION
                "String that represents the version of the station
                software.  Section 3.3.2.17 of IEEE 802.5 specification.

                The characters in the string are represented in
                EBCDIC for IBM products, in ASCII for others."
    ::= { s3TrNodeEntry 18 }

s3TrNodeEntPhysDrop OBJECT-TYPE
    SYNTAX  OCTET STRING (SIZE(4))
    ACCESS  read-only
    STATUS  mandatory
    DESCRIPTION
                "This reports the physical location of this node on the
                ring.  Section 3.3.2.13 of IEEE 802.5 specification."
    ::= { s3TrNodeEntry 19 }

s3TrNodeEntFuncAddr OBJECT-TYPE
    SYNTAX  OCTET STRING (SIZE(6))
    ACCESS  read-only
    STATUS  mandatory
    DESCRIPTION
                "Specifies the functional addresses used by this
                station.  Section 3.3.2.8 of IEEE 802.5 specification."
    ::= { s3TrNodeEntry 20 }

s3TrNodeEntAuthFuncClass OBJECT-TYPE
    SYNTAX  OCTET STRING (SIZE(2))
    ACCESS  read-only
    STATUS  mandatory
    DESCRIPTION
                "This specifies the functional classes that are
                allowed to be active in the station.  Section 3.3.2.3
                of IEEE 802.5 specification."
    ::= { s3TrNodeEntry 21 }

s3TrNodeEntAuthAccPriority OBJECT-TYPE
    SYNTAX  OCTET STRING (SIZE(2))
    ACCESS  read-only
    STATUS  mandatory
    DESCRIPTION
                "The maximum priority this station is allowed to use.
                Section 3.3.2.2 of IEEE 802.5 specification."
    ::= { s3TrNodeEntry 22 }

s3TrNodeEntGrpAddr OBJECT-TYPE
    SYNTAX  OCTET STRING (SIZE(6))
    ACCESS  read-only
    STATUS  mandatory
    DESCRIPTION
                "This contains the group address of this station.
                Section 3.3.2.9 of IEEE 802.5 specification."
    ::= { s3TrNodeEntry 23 }

s3TrNodeEntStationId OBJECT-TYPE
    SYNTAX  OCTET STRING (SIZE(6))
    ACCESS  read-only
    STATUS  mandatory
    DESCRIPTION
                "This string is used to uniquely identify the station.
                It may be equal to the station's MAC address.
                Section 3.3.2.21 of IEEE 802.5 specification."
    ::= { s3TrNodeEntry 24 }

s3TrNodeEntBeaconType OBJECT-TYPE
    SYNTAX  INTEGER {
            reconfiguration(1),
            signalLoss(2),
            bitStreaming(3),
            contentionStreaming(4)
            }
    ACCESS  read-only
    STATUS  mandatory
    DESCRIPTION
                "This specifies the type of beacon frame seen.
                Section 3.3.2.4 of IEEE 802.5 specification."
    ::= { s3TrNodeEntry 25 }

s3TrNodeBeaconCnt OBJECT-TYPE
    SYNTAX  Counter
    ACCESS  read-only
    STATUS  mandatory
    DESCRIPTION
                "Number of beacon frames that have been sent by
                this station."
    ::= { s3TrNodeEntry 26 }

s3TrNodeLastBeaconTime OBJECT-TYPE
    SYNTAX  TimeTicks
    ACCESS  read-only
    STATUS  mandatory
    DESCRIPTION
                "The time of the last beacon frame sent by
                this station."
    ::= { s3TrNodeEntry 27 }

s3TrNodeLastInsertTime OBJECT-TYPE
    SYNTAX  TimeTicks
    ACCESS  read-only
    STATUS  mandatory
    DESCRIPTION
                "The time of the last ring insertion by this
                station.  Time is relative from the system uptime."
    ::= { s3TrNodeEntry 28 }

s3TrNodeFirstInsertTime OBJECT-TYPE
    SYNTAX  TimeTicks
    ACCESS  read-only
    STATUS  mandatory
    DESCRIPTION
                "The time of the first ring insertion by this
                station.  Time is relative from the system uptime."
    ::= { s3TrNodeEntry 29 }

s3TrNodeLastDeinsertTime OBJECT-TYPE
    SYNTAX  TimeTicks
    ACCESS  read-only
    STATUS  mandatory
    DESCRIPTION
                "The time of the last ring deinsertion by this
                station.  Time is relative from the system uptime."
    ::= { s3TrNodeEntry 30 }

s3TrNodeRemoveStation OBJECT-TYPE
    SYNTAX  INTEGER {
            other(1),
            remove(2)
            }
    ACCESS  read-write
    STATUS  mandatory
    DESCRIPTION
                "Removes the MAC address associated with this entry
                from the ring by sending a REMOVE MAC frame if this
                object is written to with remove(2)."
    ::= { s3TrNodeEntry 31 }

s3TrRingStatus OBJECT-TYPE
    SYNTAX  INTEGER {
            beaconing(1),
            notbeaconing(2)
            }
    ACCESS  read-only
    STATUS  mandatory
    DESCRIPTION
                "The status of the ring."
    ::= { s3TrRingStats 1 }

s3TrRingFrmsRxOk OBJECT-TYPE
    SYNTAX  Counter
    ACCESS  read-only
    STATUS  mandatory
    DESCRIPTION
                "Number of frames received successfully by the NMM."
    ::= { s3TrRingStats 2 }

s3TrRingOctetsRxOk OBJECT-TYPE
    SYNTAX  Counter
    ACCESS  read-only
    STATUS  mandatory
    DESCRIPTION
                "Number of octets received successfully by the NMM."
    ::= { s3TrRingStats 3 }

s3TrRingBcastFrmsRxOk OBJECT-TYPE
    SYNTAX  Counter
    ACCESS  read-only
    STATUS  mandatory
    DESCRIPTION
                "Number of broadcast frames received successfully
                by the NMM."
    ::= { s3TrRingStats 4 }

s3TrRingLineErrs OBJECT-TYPE
    SYNTAX  Counter
    ACCESS  read-only
    STATUS  mandatory
    DESCRIPTION
                "Number of line errors.  Section 3.8.1 of
                IEEE 802.5 specification."
    ::= { s3TrRingStats 5 }

s3TrRingBurstErrs OBJECT-TYPE
    SYNTAX  Counter
    ACCESS  read-only
    STATUS  mandatory
    DESCRIPTION
                "Number of burst errors.  Section 3.8.3 of
                IEEE 802.5 specification."
    ::= { s3TrRingStats 6 }

s3TrRingAriFciErrs OBJECT-TYPE
    SYNTAX  Counter
    ACCESS  read-only
    STATUS  mandatory
    DESCRIPTION
                "Number of ARI FCI errors.  See AC errors,
                Section 3.8.4 of IEEE 802.5 specification."
    ::= { s3TrRingStats 7 }

s3TrRingLostFrames OBJECT-TYPE
    SYNTAX  Counter
    ACCESS  read-only
    STATUS  mandatory
    DESCRIPTION
                "Number of frames lost.  Section 3.8.6 of
                IEEE 802.5 specification."
    ::= { s3TrRingStats 8 }

s3TrRingRcvCongestErrs OBJECT-TYPE
    SYNTAX  Counter
    ACCESS  read-only
    STATUS  mandatory
    DESCRIPTION
                "Number of receive congestion errors.  Section
                3.8.7 of IEEE 802.5 specification."
    ::= { s3TrRingStats 9 }

s3TrRingFrmCopyErrs OBJECT-TYPE
    SYNTAX  Counter
    ACCESS  read-only
    STATUS  mandatory
    DESCRIPTION
                "Number of frame copy errors.  Section 3.8.8 of
                IEEE 802.5 specification."
    ::= { s3TrRingStats 10 }

s3TrRingTokenErrs OBJECT-TYPE
    SYNTAX  Counter
    ACCESS  read-only
    STATUS  mandatory
    DESCRIPTION
                "Number of token errors.  Section 3.8.10 of
                IEEE 802.5 specification."
    ::= { s3TrRingStats 11 }

s3TrRingInternalErrs OBJECT-TYPE
    SYNTAX  Counter
    ACCESS  read-only
    STATUS  mandatory
    DESCRIPTION
                "Number of internal errors.  Section 3.8.2 of
                IEEE 802.5 specification."
    ::= { s3TrRingStats 12 }

s3TrRingAbortTransErrs OBJECT-TYPE
    SYNTAX  Counter
    ACCESS  read-only
    STATUS  mandatory
    DESCRIPTION
                "Number of abort delimiter transmitted errors.
                Section 3.8.5 of IEEE 802.5 specification."
    ::= { s3TrRingStats 13 }

s3TrRingFrequencyErrs OBJECT-TYPE
    SYNTAX  Counter
    ACCESS  read-only
    STATUS  mandatory
    DESCRIPTION
                "Number of frequency errors.  Section 3.8.9 of
                IEEE 802.5 specification."
    ::= { s3TrRingStats 14 }

s3TrRingBeaconCnt OBJECT-TYPE
    SYNTAX  Counter
    ACCESS  read-only
    STATUS  mandatory
    DESCRIPTION
                "Number of beacon frames that have been seen."
    ::= { s3TrRingStats 15 }

s3TrRingBeaconType OBJECT-TYPE
    SYNTAX  INTEGER {
            reconfiguration(1),
            signalLoss(2),
            bitStreaming(3),
            contentionStreaming(4)
            }
    ACCESS  read-only
    STATUS  mandatory
    DESCRIPTION
                "This specifies the type of beacon frame seen.
                Section 3.3.2.4 of IEEE 802.5 Specification."
    ::= { s3TrRingStats 16 }

s3TrRingLastBeaconTime OBJECT-TYPE
    SYNTAX  TimeTicks
    ACCESS  read-only
    STATUS  mandatory
    DESCRIPTION
                "The time of the last beacon frame sent on the ring.
                Time is relative from the system uptime."
    ::= { s3TrRingStats 17 }

s3TrRingBeaconStation OBJECT-TYPE
    SYNTAX  OCTET STRING (SIZE(6))
    ACCESS  read-only
    STATUS  mandatory
    DESCRIPTION
                "The MAC address of station last beaconing."
    ::= { s3TrRingStats 18 }

ieee8023IfTable OBJECT-TYPE
    SYNTAX  SEQUENCE OF Ieee8023IfEntry
    ACCESS  not-accessible
    STATUS  mandatory
    DESCRIPTION
                "Statistics for a list of interface entries. There is
                one entry per IEEE 802.3 like 'interface.'"
    ::= { ieee8023 1 }

ieee8023IfEntry OBJECT-TYPE
    SYNTAX  Ieee8023IfEntry
    ACCESS  not-accessible
    STATUS  mandatory
    INDEX   { ieee8023IfIndex }
    ::= { ieee8023IfTable 1 }

Ieee8023IfEntry ::= SEQUENCE {
    ieee8023IfIndex
        INTEGER,
    ieee8023FrmsTxOk
        Counter,
    ieee8023SingleCollFrms
        Counter,
    ieee8023MultipleCollFrms
        Counter,
    ieee8023OctetsTxOk
        Counter,
    ieee8023DefTx
        Counter,
    ieee8023McastFrmsTxOk
        Counter,
    ieee8023BcastFrmsTxOk
        Counter,
    ieee8023LateColls
        Counter,
    ieee8023ExcessColls
        Counter,
    ieee8023IntlMacTxError
        Counter,
    ieee8023CsErrors
        Counter,
    ieee8023ExcessDef
        Counter,
    ieee8023FrmsRxOk
        Counter,
    ieee8023OctetsRxOk
        Counter,
    ieee8023McastFrmsRxOk
        Counter,
    ieee8023BcastFrmsRxOk
        Counter,
    ieee8023TooLongErrors
        Counter,
    ieee8023AlignErrors
        Counter,
    ieee8023FcsErrors
        Counter,
    ieee8023IrLengthErrors
        Counter,
    ieee8023OorLengthFields
        Counter,
    ieee8023IntlMacRxErrors
        Counter,
    ieee8023InitMac
        INTEGER,
    ieee8023PromRxStatus
        INTEGER,
    ieee8023MacSubLayerStatus
        INTEGER,
    ieee8023TxStatus
        INTEGER,
    ieee8023McastRxStatus
        INTEGER,
    ieee8023MacAddress
        PhysAddress,
    ieee8023SqeTestErrors
        Counter
    }

ieee8023IfIndex OBJECT-TYPE
    SYNTAX  INTEGER
    ACCESS  read-only
    STATUS  mandatory
    DESCRIPTION
                "Index of the interface.  The interface identified by a
                particular value of this index is the same interface as
                identified by the same value of ifIndex."
    ::= { ieee8023IfEntry 1 }

ieee8023FrmsTxOk OBJECT-TYPE
    SYNTAX  Counter
    ACCESS  read-only
    STATUS  mandatory
    DESCRIPTION
                "The number of frames that are successfully transmitted.

                This counter is incremented when a frame is successfully
                transmitted, even if one of the collision counters
                (following two objects) is also counted. In other words,
                this count includes transmissions that succeeded after
                some number of collisions.

                This count includes multicast and broadcast frames."
    ::= { ieee8023IfEntry 2 }

ieee8023SingleCollFrms OBJECT-TYPE
    SYNTAX  Counter
    ACCESS  read-only
    STATUS  mandatory
    DESCRIPTION
                "The number of frames that are involved in a single
                collision, and are subsequently transmitted successfully.

                If this counter is incremented, then the ieee8023FrmsTxOK
                count will also be incremented AND ieee8023MultipleCollFrms
                will NOT be incremented."
    ::= { ieee8023IfEntry 3 }

ieee8023MultipleCollFrms OBJECT-TYPE
    SYNTAX  Counter
    ACCESS  read-only
    STATUS  mandatory
    DESCRIPTION
                "The number of frames that are involved in more than one
                collision and are subsequently transmitted successfully.

                If this counter is incremented, then the ieee8023FrmsTxOK
                count will also be incremented AND ieee8023SingleCollFrms
                will NOT be incremented."
    ::= { ieee8023IfEntry 4 }

ieee8023OctetsTxOk OBJECT-TYPE
    SYNTAX  Counter
    ACCESS  read-only
    STATUS  mandatory
    DESCRIPTION
                "The amount of data AND PADDING octets of frames that are
                successfully transmitted.

                This counter includes octets in broadcast and multicast
                frames that are transmitted.

                This count does not include the address fields, length/type
                field, and CRC field of the frame. According to Ethernet
                terminology, it is purely the data field (IP header, etc.)."
    ::= { ieee8023IfEntry 5 }

ieee8023DefTx OBJECT-TYPE
    SYNTAX  Counter
    ACCESS  read-only
    STATUS  mandatory
    DESCRIPTION
                "The number of frames whose transmission was delayed on its
                first attempt because the medium was busy. Frames involved
                in collisions are NOT included in this count."
    ::= { ieee8023IfEntry 6 }

ieee8023McastFrmsTxOk OBJECT-TYPE
    SYNTAX  Counter
    ACCESS  read-only
    STATUS  mandatory
    DESCRIPTION
                "The number of frames successfully transmitted to a
                multicast address. This counter does not include frames
                sent to the broadcast address."
    ::= { ieee8023IfEntry 7 }

ieee8023BcastFrmsTxOk OBJECT-TYPE
    SYNTAX  Counter
    ACCESS  read-only
    STATUS  mandatory
    DESCRIPTION
                "The number of frames successfully transmitted to the
                broadcast address. This counter does not include frames
                sent to a multicast address."
    ::= { ieee8023IfEntry 8 }

ieee8023LateColls OBJECT-TYPE
    SYNTAX  Counter
    ACCESS  read-only
    STATUS  mandatory
    DESCRIPTION
                "The number of times that a collision has been detected
                later than 512 bit times into the transmission of a packet.
                512 bit times is 51.2 micro secs. This type of collision
                is counted twice-both as a late collision and as a regular,
                ordinary collision."
    ::= { ieee8023IfEntry 9 }

ieee8023ExcessColls OBJECT-TYPE
    SYNTAX  Counter
    ACCESS  read-only
    STATUS  mandatory
    DESCRIPTION
                "The number of frames that are not transmitted because of
                excessive collisions."
    ::= { ieee8023IfEntry 10 }

ieee8023IntlMacTxError OBJECT-TYPE
    SYNTAX  Counter
    ACCESS  read-only
    STATUS  mandatory
    DESCRIPTION
                "The number of frames that would otherwise be transmitted by
                the station, but could not be sent because of an internal MAC
                sublayer transmit error. If this counter is incremented, then
                none of the other counters in this section are incremented.
                The exact meaning and mechanism for incrementing this counter
                is implementation dependent.

                In short, this is the count of errors for which there are no
                specific counters."
    ::= { ieee8023IfEntry 11 }

ieee8023CsErrors OBJECT-TYPE
    SYNTAX  Counter
    ACCESS  read-only
    STATUS  mandatory
    DESCRIPTION
                "The number of times that carrier sense was lost or never
                appeared when attempting to transmit a packet. This counter
                is incremented ONCE per transmission attempt, even if
                Carrier Sense fluctuates."
    ::= { ieee8023IfEntry 12 }

ieee8023ExcessDef OBJECT-TYPE
    SYNTAX  Counter
    ACCESS  read-only
    STATUS  mandatory
    DESCRIPTION
                "The number of frames that deferred for an excessive period
                of time."
    ::= { ieee8023IfEntry 13 }

ieee8023FrmsRxOk OBJECT-TYPE
    SYNTAX  Counter
    ACCESS  read-only
    STATUS  mandatory
    DESCRIPTION
                "The number of frames that are successfully received. This
                counter does not include frames received with frame-too-long,
                FCS, length, or alignment errors, or frames lost because of
                internal MAC sublayer error.

                This counter includes broadcast and multicast frames that
                are received."
    ::= { ieee8023IfEntry 14 }

ieee8023OctetsRxOk OBJECT-TYPE
    SYNTAX  Counter
    ACCESS  read-only
    STATUS  mandatory
    DESCRIPTION
                "The number entry of data and padding octets in frames that
                are successfully received. This counter does not include
                frames received with frame-too-long, FCS, length, or
                alignment errors, or frames lost because of internal MAC
                sublayer error.

                This counter includes octets in broadcast and multicast
                frames that are received.

                This counter does not include the octets in the address,
                length/type, and CRC fields."
    ::= { ieee8023IfEntry 15 }

ieee8023McastFrmsRxOk OBJECT-TYPE
    SYNTAX  Counter
    ACCESS  read-only
    STATUS  mandatory
    DESCRIPTION
                "The number of frames that are successfully received and are
                directed to an active non-broadcast group address. This
                counter does not include frames received with frame-too-long,
                FCS, length, or alignment errors, or frames lost because of
                internal MAC sublayer error.

                Only frames for a multicast address that this interface is
                receiving are counted. Broadcast packets are not included."
    ::= { ieee8023IfEntry 16 }

ieee8023BcastFrmsRxOk OBJECT-TYPE
    SYNTAX  Counter
    ACCESS  read-only
    STATUS  mandatory
    DESCRIPTION
                "The number of frames that are successfully received and are
                directed to the broadcast group address. This counter does
                not include frames received with frame-too-long, FCS, length,
                or alignment errors, or frames lost because of internal MAC
                sublayer error.

                Multicast packets are not included."
    ::= { ieee8023IfEntry 17 }

ieee8023TooLongErrors OBJECT-TYPE
    SYNTAX  Counter
    ACCESS  read-only
    STATUS  mandatory
    DESCRIPTION
                "The number of frames that are received and exceed the
                maximum permitted frame size. This counter is incremented
                when the frameTooLong error is returned."
    ::= { ieee8023IfEntry 18 }

ieee8023AlignErrors OBJECT-TYPE
    SYNTAX  Counter
    ACCESS  read-only
    STATUS  mandatory
    DESCRIPTION
                "The number of frames that are not an integral number of
                octets in length and do not pass the FCS check. This counter
                is incremented when the alignmentError status is returned
                to the LLC."
    ::= { ieee8023IfEntry 19 }

ieee8023FcsErrors OBJECT-TYPE
    SYNTAX  Counter
    ACCESS  read-only
    STATUS  mandatory
    DESCRIPTION
                "The number of frames that are an integral number of octets
                in length and do not pass the FCS check. This counter is
                incremented when the frameCheckError status is returned to
                the LLC."
    ::= { ieee8023IfEntry 20 }

ieee8023IrLengthErrors OBJECT-TYPE
    SYNTAX  Counter
    ACCESS  read-only
    STATUS  mandatory
    DESCRIPTION
                "The number of frames with a length field value between the
                minimum unpadded LLC data size and the maximum allowed LLC
                data size inclusive, and which do not match the number of LLC
                data octets received. The counter also contains frames with a
                length field value less than the minimum unpadded LLC data
                size."
    ::= { ieee8023IfEntry 21 }

ieee8023OorLengthFields OBJECT-TYPE
    SYNTAX  Counter
    ACCESS  read-only
    STATUS  mandatory
    DESCRIPTION
                "The number of frames with a length field value greater than
                the maximum allowed LLC data size.

                If true 802.3 is followed for layer management, then this
                counter will be incremented for every IP or ARP frame
                received that uses the Ethernet encapsulation method. Both
                IP and ARP use type field values that will cause this counter
                to be incremented, showing a high error rate."
    ::= { ieee8023IfEntry 22 }

ieee8023IntlMacRxErrors OBJECT-TYPE
    SYNTAX  Counter
    ACCESS  read-only
    STATUS  mandatory
    DESCRIPTION
                "The number of frames that would otherwise be received by the
                station, but could not be accepted because of an internal MAC
                sublayer receive error. If this counter is incremented, then
                none of the other counters in this section are incremented.
                The exact meaning and mechanism for incrementing this counter
                is implementation dependent.

                This is the count of other errors."
    ::= { ieee8023IfEntry 23 }

ieee8023InitMac OBJECT-TYPE
    SYNTAX  INTEGER {
            initialize(1),
            uninitialize(2)
            }
    ACCESS  read-write
    STATUS  mandatory
    DESCRIPTION
                "Reinitializes the MAC and PLS (physical layer signaling).
                All MIB counters are set to 0. The states of the status
                variables (described below) are as follows:

                - The receive and transmit Layer Management state variables
                  (receiveEnabled and transmitEnabled) are set to enable
                  reception and transmission of frames.

                - The promiscuous receive function is disabled.

                - Multicast reception is disabled."
    ::= { ieee8023IfEntry 24 }

ieee8023PromRxStatus OBJECT-TYPE
    SYNTAX  INTEGER {
            enabled(1),
            disabled(2)
            }
    ACCESS  read-write
    STATUS  mandatory
    DESCRIPTION
                "This variable combines the enable ieee8023PromRx, disable
                ieee8023PromRx, and read ieee8023PromStatus MAC actions.

                Setting this variable to enabled causes the interface to
                accept frames regardless of their destination address.

                When enabled, all received frames increment all counters as
                though those frames were directed to this station.

                Frames can be promiscuously received only if the
                ieee8023MacSubLayerStatus variable is also set to enabled(1)."
    ::= { ieee8023IfEntry 25 }

ieee8023MacSubLayerStatus OBJECT-TYPE
    SYNTAX  INTEGER {
            enabled(1),
            disabled(2)
            }
    ACCESS  read-write
    STATUS  mandatory
    DESCRIPTION
                "This variable causes the MAC sublayer to enter the normal
                operational state at idle. The PLS is reset by this
                operation. It is accomplished by setting receiveEnabled
                and transmitEnabled to true.

                Setting this variable to enabled(1) enables the MAC sublayer
                to both receive and transmit frames. Setting this variable to
                enabled(1) will also set the ieee8023TransmitStatus variable
                to enabled(1). Similarly, setting this variable to disabled(2)
                will also set ieee8023TransmitStatus to disabled(2).

                Modifying this variable does not change the state of any other
                variables.

                If the variable is set to disabled(2), then any current
                transmission/reception is completed before the
                transmission/reception process is disabled.

                The value returned when this variable is read is the logical
                and of the receiveEnabled and transmitEnabled MAC internal
                state variables. If both are in the enabled state, then
                enabled(1) is returned; otherwise disabled(2) is returned."
    ::= { ieee8023IfEntry 26 }

ieee8023TxStatus OBJECT-TYPE
    SYNTAX  INTEGER {
            enabled(1),
            disabled(2)
            }
    ACCESS  read-write
    STATUS  mandatory
    DESCRIPTION
                "This variable enables the MAC sublayer to be explicitly
                enabled/disabled for transmitting frames.

                If a frame is being transmitted when this variable is set to
                disabled(2), that transmission is completed.

                Note that ieee8023MACSubLayerStatus has an effect on this
                variable."
    ::= { ieee8023IfEntry 27 }

ieee8023McastRxStatus OBJECT-TYPE
    SYNTAX  INTEGER {
            enabled(1),
            disabled(2)
            }
    ACCESS  read-write
    STATUS  mandatory
    DESCRIPTION
                "Enables/disables reception of multicast frames. To actually
                receive multicasts, both this variable AND
                ieee8023MacSubLayerStatus must be set to enabled."
    ::= { ieee8023IfEntry 28 }

ieee8023MacAddress OBJECT-TYPE
    SYNTAX  PhysAddress (SIZE(6))
    ACCESS  read-write
    STATUS  mandatory
    DESCRIPTION
                "This object contains the MAC station address (i.e., the
                Ethernet address)."
    ::= { ieee8023IfEntry 29 }

ieee8023SqeTestErrors OBJECT-TYPE
    SYNTAX  Counter
    ACCESS  read-only
    STATUS  mandatory
    DESCRIPTION
                "The number of times that the SQE TEST ERROR status was
                received."
    ::= { ieee8023IfEntry 30 }

ieee8023CollTable OBJECT-TYPE
    SYNTAX  SEQUENCE OF Ieee8023CollEntry
    ACCESS  not-accessible
    STATUS  mandatory
    DESCRIPTION
                "A table containing information on collision activity."
    ::= { ieee8023 2 }

ieee8023CollEntry OBJECT-TYPE
    SYNTAX  Ieee8023CollEntry
    ACCESS  not-accessible
    STATUS  mandatory
    INDEX   { ieee8023CollRetrans,
              ieee8023CollIndex }
    ::= { ieee8023CollTable 1 }

Ieee8023CollEntry ::= SEQUENCE {
    ieee8023CollRetrans
        INTEGER,
    ieee8023CollIndex
        INTEGER,
    ieee8023Collisions
        Counter
    }

ieee8023CollRetrans OBJECT-TYPE
    SYNTAX  INTEGER
    ACCESS  read-only
    STATUS  mandatory
    DESCRIPTION
                "The entry corresponding to the number of attempts made
                before a frame was successfully transmitted. The range is
                from 1 to 15."
    ::= { ieee8023CollEntry 1 }

ieee8023CollIndex OBJECT-TYPE
    SYNTAX  INTEGER
    ACCESS  read-only
    STATUS  mandatory
    DESCRIPTION
                "The index value that uniquely identifies the interface to
                which this entry is applicable. The interface identified by
                a particular value of this index is the same interface as
                identified by the same value of ifIndex."
    ::= { ieee8023CollEntry 2 }

ieee8023Collisions OBJECT-TYPE
    SYNTAX  Counter
    ACCESS  read-only
    STATUS  mandatory
    DESCRIPTION
                "The number of frames that were retransmitted a specific
                number of times."
    ::= { ieee8023CollEntry 3 }

ieee8023GroupTable OBJECT-TYPE
    SYNTAX  SEQUENCE OF Ieee8023GroupEntry
    ACCESS  not-accessible
    STATUS  mandatory
    DESCRIPTION
                "A table containing information on group addresses. There
                are five entries in the table."
    ::= { ieee8023 3 }

ieee8023GroupEntry OBJECT-TYPE
    SYNTAX  Ieee8023GroupEntry
    ACCESS  not-accessible
    STATUS  mandatory
    INDEX   { ieee8023GroupIndex,
              ieee8023GroupAddress }
    ::= { ieee8023GroupTable 1 }

Ieee8023GroupEntry ::= SEQUENCE {
    ieee8023GroupIndex
        INTEGER,
    ieee8023GroupAddress
        PhysAddress,
    ieee8023GroupType
        INTEGER
    }

ieee8023GroupIndex OBJECT-TYPE
    SYNTAX  INTEGER
    ACCESS  read-only
    STATUS  mandatory
    DESCRIPTION
                "The index value that uniquely identifies the interface to
                which this entry is applicable. The interface identified by
                a particular value of this index is the same interface as
                identified by the same value of ifIndex."
    ::= { ieee8023GroupEntry 1 }

ieee8023GroupAddress OBJECT-TYPE
    SYNTAX  PhysAddress (SIZE(6))
    ACCESS  read-write
    STATUS  mandatory
    DESCRIPTION
                "A group address to which this Ethernet-like interface
                responds.

                ***ACCESS VARIATION - changed access from read-only"
    ::= { ieee8023GroupEntry 2 }

ieee8023GroupType OBJECT-TYPE
    SYNTAX  INTEGER {
            other(1),
            invalid(2),
            flatnet(3),
            segmentnet(4)
            }
    ACCESS  read-write
    STATUS  mandatory
    DESCRIPTION
                "Type of group address.

                Setting this object to the value invalid(2) invalidates the
                corresponding entry in the ieee8023GroupTable. That is, it
                effectively disassociates the interface identified with said
                entry from the group address identified with said entry.
                Whether the agent removes an invalidated entry from the table
                is an implementation-specific matter. Accordingly, management
                stations must be prepared to receive tabular information from
                agents that corresponds to entries not currently in use.
                Proper interpretation of such entries requires examination of
                the relevant ieee8023GroupType object.

                A value of flatnet(3) indicates a multicast address for
                Synoptics autotopology flat net hello messages. A value of
                segmentnet(4) indicates a multicast address for Synoptics
                autotopology segment net hello messages."
    ::= { ieee8023GroupEntry 3 }

chassisPowerSupplyFailure TRAP-TYPE
    ENTERPRISE  synoptics
    VARIABLES   { s3ChassisPsStatus }
    DESCRIPTION
                "Concentrator power supply failure."
    ::= 0

chassisFanFailure TRAP-TYPE
    ENTERPRISE  synoptics
    VARIABLES   { s3ChassisFanStatus }
    DESCRIPTION
                "Concentrator fan failure."
    ::= 1

portAutoPartition TRAP-TYPE
    ENTERPRISE  synoptics
    VARIABLES   { s3EnetPortPartStatus,
                  s3EnetPortJabberStatus }
    DESCRIPTION
                "Port auto partitions (wraps)."
    ::= 4

portDTEJabbering TRAP-TYPE
    ENTERPRISE  synoptics
    VARIABLES   { s3EnetPortJabberStatus }
    DESCRIPTION
                "Ethernet DTE jabbering detected."
    ::= 5

localBridgeDiagnostic TRAP-TYPE
    ENTERPRISE  synoptics
    VARIABLES   { s3EnetLocBridgeDiagSts }
    DESCRIPTION
                "NMM detects bridge failure."
    ::= 8

remoteBridgePortOperationChanged TRAP-TYPE
    ENTERPRISE  synoptics
    VARIABLES   { s3EnetRemBridgePortOpSts }
    DESCRIPTION
                "Bridge changes from standby <-> operation."
    ::= 9

remoteBridgeDiagnostic TRAP-TYPE
    ENTERPRISE  synoptics
    VARIABLES   { s3EnetRemBridgeDiagSts }
    DESCRIPTION
                "NMM detects remote bridge failure."
    ::= 10

boardLEDFailure TRAP-TYPE
    ENTERPRISE  synoptics
    VARIABLES   { s3CommonBoardStatus }
    DESCRIPTION
                "Board is on but LED is off."
    ::= 11

boardPowerSupplyFailure TRAP-TYPE
    ENTERPRISE  synoptics
    VARIABLES   { s3CommonBoardPsStatus }
    DESCRIPTION
                "Board power supply failure."
    ::= 27

localBridgeOperationChanged TRAP-TYPE
    ENTERPRISE  synoptics
    VARIABLES   { s3EnetLocBridgeStandbySts }
    DESCRIPTION
                "Bridge changes from standby <-> operation."
    ::= 30

remoteBridgeOperationChanged TRAP-TYPE
    ENTERPRISE  synoptics
    VARIABLES   { s3EnetRemBridgeStandbySts }
    DESCRIPTION
                "Bridge changes from standby <-> operation."
    ::= 31

routerOperationChanged TRAP-TYPE
    ENTERPRISE  synoptics
    VARIABLES   { s3EnetRouterStandbySts }
    DESCRIPTION
                "Router changes from standby <-> operation."
    ::= 33

routerDiagnostic TRAP-TYPE
    ENTERPRISE  synoptics
    VARIABLES   { s3EnetRouterDiagSts }
    DESCRIPTION
                "NMM detects router failure."
    ::= 34

keyManagementFailure TRAP-TYPE
    ENTERPRISE  synoptics
    VARIABLES   { s3AgentMibLevel,
                  s3AgentFeatureLevel }
    DESCRIPTION
                "NMM detects that its key doesn't match the 
                configuration."
    ::= 35

nmmSaturationA TRAP-TYPE
    ENTERPRISE  synoptics
    DESCRIPTION
                "NMM is dropping packets due to overload."
    ::= 44

lattisSecureInitRequired TRAP-TYPE
    ENTERPRISE  synoptics
    VARIABLES   { s3SlotModuleType }
    DESCRIPTION
                "This trap is sent by a 331xS Ethernet NMM+ when a
                LattisSecure Host Module needs initialization.  The
                location of the module is indicated by the instance
                identifier part of the returned variable, and the value
                of the variable tells the board identity."
    ::= 46

redPsPlus5vCurrentExceed TRAP-TYPE
    ENTERPRISE  synoptics
    VARIABLES   { s3RedPsPrimaryConfig,
                  s3RedPsSecondaryConfig,
                  s3RedPsPlus5vCurrent }
    DESCRIPTION
                "This trap is sent when the current level on the +5 V
                supply exceeds the maximum recommended level: 1) 30 amps
                if at least one of the power supplies is a 3001. 2) 50
                amps if both power supplies are 3002. Note: The agent
                reads the current level only when it restarts.Changes in
                the current level that occur while the agent is running
                will not be noticed.  Thus, this trap can only be
                generated at the end of the restart sequence."
    ::= 47

redPsPlus12vCurrentExceed TRAP-TYPE
    ENTERPRISE  synoptics
    VARIABLES   { s3RedPsPrimaryConfig,
                  s3RedPsSecondaryConfig,
                  s3RedPsPlus12vCurrent }
    DESCRIPTION
                "This trap is sent when the current level on the +12 V
                supply exceeds the maximum recommended level of 15 amps
                for any set of power supplies.  Note: The agent reads
                the current level only when it restarts.  Changes in the
                current level that occur while the agent is running will
                not be noticed.  Thus, this trap can only be generated
                at the end of the restart sequence."
    ::= 48

redPsAmbientTempStatChg TRAP-TYPE
    ENTERPRISE  synoptics
    VARIABLES   { s3RedPsAmbientTempStatus,
                  s3RedPsAmbientTemperature }
    DESCRIPTION
                "This trap is sent whenever there is a change (in either
                direction) in the psAmbientTempStatus variable."
    ::= 49

redPsSummingDiodeFailure TRAP-TYPE
    ENTERPRISE  synoptics
    VARIABLES   { s3RedPsDiodeStatus }
    DESCRIPTION
                "This trap is sent whenever the reported status of
                either 3100R summing diode changes from 'Ok' to 'Fail'."
    ::= 50

boardSwap TRAP-TYPE
    ENTERPRISE  synoptics
    VARIABLES   { s3SlotModuleId,
                  s3SlotModuleType,
                  s3SlotModuleMdaId }
    DESCRIPTION
                "This trap is sent whenever a board is inserted or
                removed.  The values returned are those before the
                action was taken.  Thus, the value of s3SlotModuleType
                will be empty(1) when a board is inserted.  The instance
                value for the variables is the slot number of the board.
                On receiving the trap, a manager should use a get
                request to find the current values of these variables."
    ::= 51

enetChannelChange TRAP-TYPE
    ENTERPRISE  synoptics
    VARIABLES   { s3EnetCommonBoardEnetAB }
    DESCRIPTION
                "This trap is sent whenever a board is switched
                from one channel to the other.  The value returned
                is the one before the action was taken. Thus, the
                value of s3EnetCommonBoardEnetAB will specify
                channel that the board was attached to before
                the channel was changed.  The instance value
                from s3EnetCommonBoardEnetAB identifies the
                board that was affected."
    ::= 53

flashUpdateFailure TRAP-TYPE
    ENTERPRISE  synoptics
    VARIABLES   { s3AgentFlashStatus }
    DESCRIPTION
                "This trap is sent whenever the agent failed
                to update the local image due to flash device
                failure."
    ::= 54

redundPortSwitchover TRAP-TYPE
    ENTERPRISE  synoptics
    VARIABLES   { s3EnetRedPortRedundMode,
                  s3EnetRedPortOperStatus,
                  s3EnetRedPortCompanionSlotNo,
                  s3EnetRedPortCompanionPortNo }
    DESCRIPTION
                "This trap is sent whenever NMM detects a redundant port
                pair switchover.  The values returned are those after
                the action was taken.  The instance values (slot.port)
                for the variables is for the port from which the
                switchover occurred."
    ::= 58

redundBadRemCfgDetected TRAP-TYPE
    ENTERPRISE  synoptics
    VARIABLES   { s3EnetRedPortRemoteOperStatus,
                  s3EnetRedPortRedundMode }
    DESCRIPTION
                "This trap is sent periodically when the NMM detects
                a s3EnetRedPortRemoteOperStatus of flidl(3) on a port
                set for hardware redundancy. The trap is also sent
                when the port's s3EnetRedPortRemoteOperStatus is
                unknown(7) and the companion port has a good link.
                The instance values (slot.port) for the variables
                is for the receiving port."
    ::= 59


END
