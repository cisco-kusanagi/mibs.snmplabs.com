WS-INFRA-DIAG-MIB DEFINITIONS ::= BEGIN
 
		IMPORTS
			OBJECT-GROUP, MODULE-COMPLIANCE			
				FROM SNMPv2-CONF			
			Integer32, Unsigned32, OBJECT-TYPE, MODULE-IDENTITY			
				FROM SNMPv2-SMI			
			DisplayString			
				FROM SNMPv2-TC			
			wsInfraDiag			
				FROM WS-INFRA-SMI-MIB;

		-- 1.3.6.1.4.1.388.14.1.6.1
		wsInfraDiagMib MODULE-IDENTITY 
			LAST-UPDATED "200601051631Z"		-- January 05, 2006 at 16:31 GMT
			ORGANIZATION 
				"Symbol Technologies"
			CONTACT-INFO 
				"Symbol Technologies, Inc.
				Customer Service
				Postal:
				One Symbol Plaza
				Holtsville, NY 11742-1300
				USA
				Tel: +1. 631.738.6213
				E-mail: support@symbol.com
				Web: http://www.symbol.com/support"
			DESCRIPTION 
				"Description."
			REVISION "200606061031Z"		-- June 06, 2006 at 10:31 GMT
			DESCRIPTION 
				"02a02"
			REVISION "200604051330Z"		-- April 05, 2006 at 13:30 GMT
			DESCRIPTION 
				"02a01"
			REVISION "200601051755Z"		-- January 05, 2006 at 17:55 GMT
			DESCRIPTION 
				"01a04"
			REVISION "200512011630Z"		-- December 01, 2005 at 16:30 GMT
			DESCRIPTION 
				"01a03"
			REVISION "200505191537Z"		-- May 19, 2005 at 15:37 GMT
			DESCRIPTION 
				"01a02"
			REVISION "200505181654Z"		-- May 18, 2005 at 16:54 GMT
			DESCRIPTION 
				"01a01"
			::= { wsInfraDiag 1 }

		-- 1.3.6.1.4.1.388.14.1.6.1.1
		wsInfraDiagTempControl OBJECT IDENTIFIER ::= { wsInfraDiagMib 1 }

		-- 1.3.6.1.4.1.388.14.1.6.1.1.1
		wsInfraDiagTempCurrentTemp OBJECT-TYPE
			SYNTAX INTEGER (0..450 | 1000)
			UNITS "0.1C"
			MAX-ACCESS read-only
			STATUS obsolete
			DESCRIPTION
				"current temperature of the temperature sensor, 
				if there is no temp sensor, it will return 1000.
				"
			::= { wsInfraDiagTempControl 1 }

		-- 1.3.6.1.4.1.388.14.1.6.1.1.2
		wsInfraDiagTempHighTemp OBJECT-TYPE
			SYNTAX INTEGER (0..450 | 1000..1001)
			UNITS "0.1C"
			MAX-ACCESS read-write
			STATUS obsolete
			DESCRIPTION
				"high temperature of the temperature sensor, 
				if there is no temp sensor, it will return 1000
				The user could only set the temp from 0 to 450."
			::= { wsInfraDiagTempControl 2 }

		-- 1.3.6.1.4.1.388.14.1.6.1.1.3
		wsInfraDiagTempHighTempHysteresis OBJECT-TYPE
			SYNTAX INTEGER (0..100)
			UNITS "0.1C"
			MAX-ACCESS read-write
			STATUS obsolete
			DESCRIPTION
				"high temperature hysteresis of the temperature sensor.
				If there is no temp sensor, it will return 0.
				the user could only set the high temperature hysteresis
				1-100."
			::= { wsInfraDiagTempControl 3 }

		-- 1.3.6.1.4.1.388.14.1.6.1.2
		wsInfraDiagFanControl OBJECT IDENTIFIER ::= { wsInfraDiagMib 2 }

		-- 1.3.6.1.4.1.388.14.1.6.1.2.1
		wsInfraDiagSysFanSpeed OBJECT-TYPE
			SYNTAX INTEGER (0..10000)
			UNITS "1 rpm"
			MAX-ACCESS read-only
			STATUS obsolete
			DESCRIPTION
				"system fan speed"
			::= { wsInfraDiagFanControl 1 }

		-- 1.3.6.1.4.1.388.14.1.6.1.2.2
		wsDiagProcFanSpeed OBJECT-TYPE
			SYNTAX INTEGER (0..10000)
			UNITS "1 rpm"
			MAX-ACCESS read-only
			STATUS obsolete
			DESCRIPTION
				"processor fan speed"
			::= { wsInfraDiagFanControl 2 }

		-- 1.3.6.1.4.1.388.14.1.6.1.3
		wsInfraHwBuildInfo OBJECT IDENTIFIER ::= { wsInfraDiagMib 3 }

		-- 1.3.6.1.4.1.388.14.1.6.1.3.1
		wsInfraHwTotalNum OBJECT-TYPE
			SYNTAX INTEGER (1..128)
			MAX-ACCESS read-only
			STATUS obsolete
			DESCRIPTION
				"total hardware number in the system"
			::= { wsInfraHwBuildInfo 1 }

		-- 1.3.6.1.4.1.388.14.1.6.1.3.2
		wsInfraHwBuildInfoTable OBJECT-TYPE
			SYNTAX SEQUENCE OF WsInfraHwBuildInfoEntry
			MAX-ACCESS not-accessible
			STATUS current
			DESCRIPTION
				"Shows the system hardware configuration"
			::= { wsInfraHwBuildInfo 2 }

		-- 1.3.6.1.4.1.388.14.1.6.1.3.2.1
		wsInfraHwBuildInfoEntry OBJECT-TYPE
			SYNTAX WsInfraHwBuildInfoEntry
			MAX-ACCESS not-accessible
			STATUS current
			DESCRIPTION
				"Description."
			INDEX { wsInfraHwBuildInfoModuleIndex }
			::= { wsInfraHwBuildInfoTable 1 }

		WsInfraHwBuildInfoEntry ::=
			SEQUENCE { 
				wsInfraHwBuildInfoModuleIndex
					INTEGER,
				wsInfraHwBuildInfoModuleName
					DisplayString,
				wsInfraHwBuildInfoVersion
					DisplayString,
				wsInfraHwBuildInfoManufacturer
					DisplayString,
				wsInfraHwBuildInfoDesc
					DisplayString
			 }

		-- 1.3.6.1.4.1.388.14.1.6.1.3.2.1.1
		wsInfraHwBuildInfoModuleIndex OBJECT-TYPE
			SYNTAX INTEGER (1..32)
			MAX-ACCESS not-accessible
			STATUS current
			DESCRIPTION
				"hardware module index"
			::= { wsInfraHwBuildInfoEntry 1 }

		-- 1.3.6.1.4.1.388.14.1.6.1.3.2.1.2
		wsInfraHwBuildInfoModuleName OBJECT-TYPE
			SYNTAX DisplayString
			MAX-ACCESS read-only
			STATUS current
			DESCRIPTION
				"Name of the hardware module"
			::= { wsInfraHwBuildInfoEntry 2 }

		-- 1.3.6.1.4.1.388.14.1.6.1.3.2.1.3
		wsInfraHwBuildInfoVersion OBJECT-TYPE
			SYNTAX DisplayString
			MAX-ACCESS read-only
			STATUS current
			DESCRIPTION
				"Version of the hardware module"
			::= { wsInfraHwBuildInfoEntry 3 }

		-- 1.3.6.1.4.1.388.14.1.6.1.3.2.1.4
		wsInfraHwBuildInfoManufacturer OBJECT-TYPE
			SYNTAX DisplayString
			MAX-ACCESS read-only
			STATUS current
			DESCRIPTION
				"Name of the hardware component manufacturer"
			::= { wsInfraHwBuildInfoEntry 4 }

		-- 1.3.6.1.4.1.388.14.1.6.1.3.2.1.5
		wsInfraHwBuildInfoDesc OBJECT-TYPE
			SYNTAX DisplayString
			MAX-ACCESS read-only
			STATUS current
			DESCRIPTION
				"Description of the device/hardware component"
			::= { wsInfraHwBuildInfoEntry 5 }

		-- 1.3.6.1.4.1.388.14.1.6.1.4
		wsInfraResStats OBJECT IDENTIFIER ::= { wsInfraDiagMib 4 }

		-- 1.3.6.1.4.1.388.14.1.6.1.4.1
		wsInfraResCpuLoad1 OBJECT-TYPE
			SYNTAX INTEGER (0..1000)
			UNITS "%"
			MAX-ACCESS read-only
			STATUS current
			DESCRIPTION
				"% of CPU load averaged over 1 min. Precision is to the degree of 0.1 %"
			::= { wsInfraResStats 1 }

		-- 1.3.6.1.4.1.388.14.1.6.1.4.2
		wsInfraResCpuLoad5 OBJECT-TYPE
			SYNTAX INTEGER (0..1000)
			UNITS "%"
			MAX-ACCESS read-only
			STATUS current
			DESCRIPTION
				"% of CPU load averaged over 5 mins. Precision is to the degree of 0.1 %"
			::= { wsInfraResStats 2 }

		-- 1.3.6.1.4.1.388.14.1.6.1.4.3
		wsInfraResCpuLoad15 OBJECT-TYPE
			SYNTAX INTEGER (0..1000)
			UNITS "%"
			MAX-ACCESS read-only
			STATUS current
			DESCRIPTION
				"% of CPU load averaged over 15 mins. Precision is to the degree of 0.1 %"
			::= { wsInfraResStats 3 }

		-- 1.3.6.1.4.1.388.14.1.6.1.4.4
		wsInfraFreeMemory OBJECT-TYPE
			SYNTAX Unsigned32
			UNITS "KB"
			MAX-ACCESS read-only
			STATUS obsolete
			DESCRIPTION
				"Amount of free memory available in the system in KB"
			::= { wsInfraResStats 4 }

		-- 1.3.6.1.4.1.388.14.1.6.1.4.5
		wsInfraRootFSFree OBJECT-TYPE
			SYNTAX Unsigned32
			UNITS "KB"
			MAX-ACCESS read-only
			STATUS obsolete
			DESCRIPTION
				"Amount of free space available on root file system in KB"
			::= { wsInfraResStats 5 }

		-- 1.3.6.1.4.1.388.14.1.6.1.4.6
		wsInfraRootFSInodesFree OBJECT-TYPE
			SYNTAX Unsigned32
			MAX-ACCESS read-only
			STATUS obsolete
			DESCRIPTION
				"free Inodes available on root file system"
			::= { wsInfraResStats 6 }

		-- 1.3.6.1.4.1.388.14.1.6.1.4.7
		wsInfraRamFSFree OBJECT-TYPE
			SYNTAX Unsigned32
			UNITS "KB"
			MAX-ACCESS read-only
			STATUS obsolete
			DESCRIPTION
				"Free space available on RAM file system"
			::= { wsInfraResStats 7 }

		-- 1.3.6.1.4.1.388.14.1.6.1.4.8
		wsInfraRamFSInodesFree OBJECT-TYPE
			SYNTAX Unsigned32
			MAX-ACCESS read-only
			STATUS obsolete
			DESCRIPTION
				"free Inodes available on RAM file system"
			::= { wsInfraResStats 8 }

		-- 1.3.6.1.4.1.388.14.1.6.1.4.9
		wsInfraFreeFileDesc OBJECT-TYPE
			SYNTAX Unsigned32
			MAX-ACCESS read-only
			STATUS obsolete
			DESCRIPTION
				"Number of free file descriptor"
			::= { wsInfraResStats 9 }

		-- 1.3.6.1.4.1.388.14.1.6.1.4.10
		wsInfraUsedKernBuff32 OBJECT-TYPE
			SYNTAX Unsigned32
			MAX-ACCESS read-only
			STATUS current
			DESCRIPTION
				"Number of 32 byte kernel buffers used"
			::= { wsInfraResStats 10 }

		-- 1.3.6.1.4.1.388.14.1.6.1.4.11
		wsInfraUsedKernBuff64 OBJECT-TYPE
			SYNTAX Unsigned32
			MAX-ACCESS read-only
			STATUS current
			DESCRIPTION
				"Number of 64 byte kernel buffers used"
			::= { wsInfraResStats 11 }

		-- 1.3.6.1.4.1.388.14.1.6.1.4.12
		wsInfraUsedKernBuff128 OBJECT-TYPE
			SYNTAX Unsigned32
			MAX-ACCESS read-only
			STATUS current
			DESCRIPTION
				"Number of 128 byte kernel buffers used"
			::= { wsInfraResStats 12 }

		-- 1.3.6.1.4.1.388.14.1.6.1.4.13
		wsInfraUsedKernBuff256 OBJECT-TYPE
			SYNTAX Unsigned32
			MAX-ACCESS read-only
			STATUS current
			DESCRIPTION
				"Number of 256 byte kernel buffers used"
			::= { wsInfraResStats 13 }

		-- 1.3.6.1.4.1.388.14.1.6.1.4.14
		wsInfraUsedKernBuff512 OBJECT-TYPE
			SYNTAX Unsigned32
			MAX-ACCESS read-only
			STATUS current
			DESCRIPTION
				"Number of 512 byte kernel buffers used"
			::= { wsInfraResStats 14 }

		-- 1.3.6.1.4.1.388.14.1.6.1.4.15
		wsInfraUsedKernBuff1024 OBJECT-TYPE
			SYNTAX Unsigned32
			MAX-ACCESS read-only
			STATUS current
			DESCRIPTION
				"Number of 1024 byte kernel buffers used"
			::= { wsInfraResStats 15 }

		-- 1.3.6.1.4.1.388.14.1.6.1.4.16
		wsInfraUsedKernBuff2048 OBJECT-TYPE
			SYNTAX Unsigned32
			MAX-ACCESS read-write
			STATUS current
			DESCRIPTION
				"Number of 2048 byte kernel buffers used"
			::= { wsInfraResStats 16 }

		-- 1.3.6.1.4.1.388.14.1.6.1.4.17
		wsInfraUsedKernBuff4096 OBJECT-TYPE
			SYNTAX Unsigned32
			MAX-ACCESS read-only
			STATUS current
			DESCRIPTION
				"Number of 4096 byte kernel buffers used"
			::= { wsInfraResStats 17 }

		-- 1.3.6.1.4.1.388.14.1.6.1.4.18
		wsInfraUsedKernBuff8192 OBJECT-TYPE
			SYNTAX Unsigned32
			MAX-ACCESS read-only
			STATUS current
			DESCRIPTION
				"Number of 8192 byte kernel buffers used"
			::= { wsInfraResStats 18 }

		-- 1.3.6.1.4.1.388.14.1.6.1.4.19
		wsInfraUsedKernBuff16384 OBJECT-TYPE
			SYNTAX Unsigned32
			MAX-ACCESS read-only
			STATUS current
			DESCRIPTION
				"Number of 16384 byte kernel buffers used"
			::= { wsInfraResStats 19 }

		-- 1.3.6.1.4.1.388.14.1.6.1.4.20
		wsInfraUsedKernBuff32768 OBJECT-TYPE
			SYNTAX Unsigned32
			MAX-ACCESS read-only
			STATUS current
			DESCRIPTION
				"Number of 32768 byte kernel buffers used"
			::= { wsInfraResStats 20 }

		-- 1.3.6.1.4.1.388.14.1.6.1.4.21
		wsInfraUsedKernBuff65536 OBJECT-TYPE
			SYNTAX Unsigned32
			MAX-ACCESS read-only
			STATUS current
			DESCRIPTION
				"Number of 65536 byte kernel buffers used"
			::= { wsInfraResStats 21 }

		-- 1.3.6.1.4.1.388.14.1.6.1.4.22
		wsInfraUsedKernBuff131072 OBJECT-TYPE
			SYNTAX Unsigned32
			MAX-ACCESS read-only
			STATUS current
			DESCRIPTION
				"Number of 131072 byte kernel buffers used"
			::= { wsInfraResStats 22 }

		-- 1.3.6.1.4.1.388.14.1.6.1.4.23
		wsInfraResCpuLoad1MinLimit OBJECT-TYPE
			SYNTAX INTEGER (0..1000)
			UNITS "%"
			MAX-ACCESS read-write
			STATUS current
			DESCRIPTION
				"Limit on CPU load averaged over 1 minute"
			::= { wsInfraResStats 23 }

		-- 1.3.6.1.4.1.388.14.1.6.1.4.24
		wsInfraResCpuLoad5MinLimit OBJECT-TYPE
			SYNTAX Integer32 (0..1000)
			UNITS "0.1%"
			MAX-ACCESS read-write
			STATUS current
			DESCRIPTION
				"Limit on CPU load averaged over 5 minutes"
			::= { wsInfraResStats 24 }

		-- 1.3.6.1.4.1.388.14.1.6.1.4.25
		wsInfraResCpuLoad15MinLimit OBJECT-TYPE
			SYNTAX Integer32 (0..1000)
			UNITS "0.1%"
			MAX-ACCESS read-write
			STATUS current
			DESCRIPTION
				"Limit on CPU load averaged over 15 minutes"
			::= { wsInfraResStats 25 }

		-- 1.3.6.1.4.1.388.14.1.6.1.4.26
		wsInfraUsedKernBuff32Limit OBJECT-TYPE
			SYNTAX INTEGER (0..65535)
			MAX-ACCESS read-write
			STATUS current
			DESCRIPTION
				"32 byte buffer usage warning limit"
			::= { wsInfraResStats 26 }

		-- 1.3.6.1.4.1.388.14.1.6.1.4.27
		wsInfraUsedKernBuff64Limit OBJECT-TYPE
			SYNTAX INTEGER (0..65535)
			MAX-ACCESS read-write
			STATUS current
			DESCRIPTION
				"64 byte buffer usage warning limit"
			::= { wsInfraResStats 27 }

		-- 1.3.6.1.4.1.388.14.1.6.1.4.28
		wsInfraUsedKernBuff128Limit OBJECT-TYPE
			SYNTAX INTEGER (0..65535)
			MAX-ACCESS read-write
			STATUS current
			DESCRIPTION
				"128 byte buffer usage warning limit"
			::= { wsInfraResStats 28 }

		-- 1.3.6.1.4.1.388.14.1.6.1.4.29
		wsInfraUsedKernBuff256Limit OBJECT-TYPE
			SYNTAX INTEGER (0..65535)
			MAX-ACCESS read-write
			STATUS current
			DESCRIPTION
				"256 byte buffer usage warning limit"
			::= { wsInfraResStats 29 }

		-- 1.3.6.1.4.1.388.14.1.6.1.4.30
		wsInfraUsedKernBuff512Limit OBJECT-TYPE
			SYNTAX INTEGER (0..65535)
			MAX-ACCESS read-write
			STATUS current
			DESCRIPTION
				"512 byte buffer usage warning limit"
			::= { wsInfraResStats 30 }

		-- 1.3.6.1.4.1.388.14.1.6.1.4.31
		wsInfraUsedKernBuff1024Limit OBJECT-TYPE
			SYNTAX INTEGER (0..65535)
			MAX-ACCESS read-write
			STATUS current
			DESCRIPTION
				"1024 byte buffer usage warning limit"
			::= { wsInfraResStats 31 }

		-- 1.3.6.1.4.1.388.14.1.6.1.4.32
		wsInfraUsedKernBuff2048Limit OBJECT-TYPE
			SYNTAX INTEGER (0..65535)
			MAX-ACCESS read-only
			STATUS current
			DESCRIPTION
				"2048 byte buffer usage warning limit"
			::= { wsInfraResStats 32 }

		-- 1.3.6.1.4.1.388.14.1.6.1.4.33
		wsInfraUsedKernBuff4096Limit OBJECT-TYPE
			SYNTAX INTEGER (0..65535)
			MAX-ACCESS read-write
			STATUS current
			DESCRIPTION
				"4096 byte buffer usage warning limit"
			::= { wsInfraResStats 33 }

		-- 1.3.6.1.4.1.388.14.1.6.1.4.34
		wsInfraUsedKernBuff8192Limit OBJECT-TYPE
			SYNTAX INTEGER (0..65535)
			MAX-ACCESS read-write
			STATUS current
			DESCRIPTION
				"8192 byte buffer usage warning limit"
			::= { wsInfraResStats 34 }

		-- 1.3.6.1.4.1.388.14.1.6.1.4.35
		wsInfraUsedKernBuff16384Limit OBJECT-TYPE
			SYNTAX INTEGER (0..65535)
			MAX-ACCESS read-write
			STATUS current
			DESCRIPTION
				"16384 byte buffer usage warning limit"
			::= { wsInfraResStats 35 }

		-- 1.3.6.1.4.1.388.14.1.6.1.4.36
		wsInfraUsedKernBuff32768Limit OBJECT-TYPE
			SYNTAX INTEGER (0..65535)
			MAX-ACCESS read-write
			STATUS current
			DESCRIPTION
				"32768 byte buffer usage warning limit"
			::= { wsInfraResStats 36 }

		-- 1.3.6.1.4.1.388.14.1.6.1.4.37
		wsInfraUsedKernBuff65536Limit OBJECT-TYPE
			SYNTAX INTEGER (0..65535)
			MAX-ACCESS read-write
			STATUS current
			DESCRIPTION
				"65536 byte buffer usage warning limit"
			::= { wsInfraResStats 37 }

		-- 1.3.6.1.4.1.388.14.1.6.1.4.38
		wsInfraUsedKernBuff131072Limit OBJECT-TYPE
			SYNTAX INTEGER (0..65535)
			MAX-ACCESS read-write
			STATUS current
			DESCRIPTION
				"131072 byte buffer usage warning limit"
			::= { wsInfraResStats 38 }

		-- 1.3.6.1.4.1.388.14.1.6.1.6
		wsInfraDiagControl OBJECT-TYPE
			SYNTAX INTEGER
				{
				enable(1),
				disable(2)
				}
			MAX-ACCESS read-write
			STATUS current
			DESCRIPTION
				"Used to enable/disable in service diagnostics"
			::= { wsInfraDiagMib 6 }

		-- 1.3.6.1.4.1.388.14.1.6.1.7
		wsInfraDiagPeriod OBJECT-TYPE
			SYNTAX INTEGER (100..30000)
			UNITS "millisecond"
			MAX-ACCESS read-write
			STATUS current
			DESCRIPTION
				"Period of in service diagnostics in ms"
			::= { wsInfraDiagMib 7 }

		-- 1.3.6.1.4.1.388.14.1.6.1.8
		wsInfraDiagFanNum OBJECT-TYPE
			SYNTAX INTEGER (0..8)
			MAX-ACCESS read-only
			STATUS current
			DESCRIPTION
				"Total number of fans in the system"
			::= { wsInfraDiagMib 8 }

		-- 1.3.6.1.4.1.388.14.1.6.1.9
		wsInfraDiagTempSensorNum OBJECT-TYPE
			SYNTAX INTEGER (0..8)
			MAX-ACCESS read-only
			STATUS current
			DESCRIPTION
				"Total number of temperature sensors in the system"
			::= { wsInfraDiagMib 9 }

		-- 1.3.6.1.4.1.388.14.1.6.1.10
		wsInfraDiagPlatform OBJECT-TYPE
			SYNTAX DisplayString
			MAX-ACCESS read-only
			STATUS current
			DESCRIPTION
				"Name of the hardware platform of the switch"
			::= { wsInfraDiagMib 10 }

		-- 1.3.6.1.4.1.388.14.1.6.1.11
		wsInfraDiagMonitoredFSTable OBJECT-TYPE
			SYNTAX SEQUENCE OF WsInfraDiagMonitoredFSEntry
			MAX-ACCESS not-accessible
			STATUS current
			DESCRIPTION
				"Table of monitored file systems like flash, etc and var."
			::= { wsInfraDiagMib 11 }

		-- 1.3.6.1.4.1.388.14.1.6.1.11.1
		wsInfraDiagMonitoredFSEntry OBJECT-TYPE
			SYNTAX WsInfraDiagMonitoredFSEntry
			MAX-ACCESS not-accessible
			STATUS current
			DESCRIPTION
				"Description."
			INDEX { wsInfraDiagMonitoredFSTableIndex }
			::= { wsInfraDiagMonitoredFSTable 1 }

		WsInfraDiagMonitoredFSEntry ::=
			SEQUENCE { 
				wsInfraDiagMonitoredFSTableIndex
					Unsigned32,
				wsInfraDiagMonitoredFSName
					DisplayString,
				wsInfraDiagMonitoredFSFreeSpace
					Unsigned32,
				wsInfraDiagMonitoredFSFreeSpacePercent
					Integer32,
				wsInfraDiagMonitoredFSFreeSpaceLimit
					INTEGER,
				wsInfraDiagMonitoredFSSize
					Integer32,
				wsInfraDiagMonitoredFSUsed
					Integer32,
				wsInfraDiagMonitoredFSINodesFree
					Integer32,
				wsInfraDiagMonitoredFSINodesLimit
					INTEGER
			 }

		-- 1.3.6.1.4.1.388.14.1.6.1.11.1.1
		wsInfraDiagMonitoredFSTableIndex OBJECT-TYPE
			SYNTAX Unsigned32 (1..3)
			MAX-ACCESS not-accessible
			STATUS current
			DESCRIPTION
				"Simple Index."
			::= { wsInfraDiagMonitoredFSEntry 1 }

		-- 1.3.6.1.4.1.388.14.1.6.1.11.1.2
		wsInfraDiagMonitoredFSName OBJECT-TYPE
			SYNTAX DisplayString
			MAX-ACCESS read-only
			STATUS current
			DESCRIPTION
				"Name of the monitored File System."
			::= { wsInfraDiagMonitoredFSEntry 2 }

		-- 1.3.6.1.4.1.388.14.1.6.1.11.1.3
		wsInfraDiagMonitoredFSFreeSpace OBJECT-TYPE
			SYNTAX Unsigned32
			UNITS "KB"
			MAX-ACCESS read-only
			STATUS current
			DESCRIPTION
				"Free space currently available in monitored File System."
			::= { wsInfraDiagMonitoredFSEntry 3 }

		-- 1.3.6.1.4.1.388.14.1.6.1.11.1.4
		wsInfraDiagMonitoredFSFreeSpacePercent OBJECT-TYPE
			SYNTAX Integer32
			UNITS "0.1%"
			MAX-ACCESS read-only
			STATUS current
			DESCRIPTION
				"Description."
			::= { wsInfraDiagMonitoredFSEntry 4 }

		-- 1.3.6.1.4.1.388.14.1.6.1.11.1.5
		wsInfraDiagMonitoredFSFreeSpaceLimit OBJECT-TYPE
			SYNTAX INTEGER (0..1000)
			UNITS "0.1%"
			MAX-ACCESS read-write
			STATUS current
			DESCRIPTION
				"Threshold value for free space available in the monitored 
				File System. If the free space available falls below this 
				value, a notification should get sent out."
			::= { wsInfraDiagMonitoredFSEntry 5 }

		-- 1.3.6.1.4.1.388.14.1.6.1.11.1.6
		wsInfraDiagMonitoredFSSize OBJECT-TYPE
			SYNTAX Integer32
			MAX-ACCESS read-only
			STATUS current
			DESCRIPTION
				"Size of monitored File System."
			::= { wsInfraDiagMonitoredFSEntry 6 }

		-- 1.3.6.1.4.1.388.14.1.6.1.11.1.7
		wsInfraDiagMonitoredFSUsed OBJECT-TYPE
			SYNTAX Integer32
			MAX-ACCESS read-only
			STATUS current
			DESCRIPTION
				"Amount of monitored File System space used."
			::= { wsInfraDiagMonitoredFSEntry 7 }

		-- 1.3.6.1.4.1.388.14.1.6.1.11.1.8
		wsInfraDiagMonitoredFSINodesFree OBJECT-TYPE
			SYNTAX Integer32
			MAX-ACCESS read-only
			STATUS current
			DESCRIPTION
				"Number of free INodes in monitored File System."
			::= { wsInfraDiagMonitoredFSEntry 8 }

		-- 1.3.6.1.4.1.388.14.1.6.1.11.1.9
		wsInfraDiagMonitoredFSINodesLimit OBJECT-TYPE
			SYNTAX INTEGER (0..100)
			UNITS "0.1%"
			MAX-ACCESS read-write
			STATUS current
			DESCRIPTION
				"Limit of INodes in monitored File System in %. Precision is to the degree of 0.1%."
			DEFVAL { 10 }
			::= { wsInfraDiagMonitoredFSEntry 9 }

		-- 1.3.6.1.4.1.388.14.1.6.1.12
		wsInfraDiagTempTable OBJECT-TYPE
			SYNTAX SEQUENCE OF WsInfraDiagTempEntry
			MAX-ACCESS not-accessible
			STATUS current
			DESCRIPTION
				"Description."
			::= { wsInfraDiagMib 12 }

		-- 1.3.6.1.4.1.388.14.1.6.1.12.1
		wsInfraDiagTempEntry OBJECT-TYPE
			SYNTAX WsInfraDiagTempEntry
			MAX-ACCESS not-accessible
			STATUS current
			DESCRIPTION
				"Description."
			INDEX { wsInfraDiagTempIndex }
			::= { wsInfraDiagTempTable 1 }

		WsInfraDiagTempEntry ::=
			SEQUENCE { 
				wsInfraDiagTempIndex
					INTEGER,
				wsInfraDiagTempSensorName
					DisplayString,
				wsInfraDiagTempCurrTemp
					Integer32,
				wsInfraDiagTempMaxTemp
					INTEGER,
				wsInfraDiagTempOverTemp
					INTEGER
			 }

		-- 1.3.6.1.4.1.388.14.1.6.1.12.1.1
		wsInfraDiagTempIndex OBJECT-TYPE
			SYNTAX INTEGER (1..8)
			MAX-ACCESS accessible-for-notify
			STATUS current
			DESCRIPTION
				"Simple Index."
			::= { wsInfraDiagTempEntry 1 }

		-- 1.3.6.1.4.1.388.14.1.6.1.12.1.2
		wsInfraDiagTempSensorName OBJECT-TYPE
			SYNTAX DisplayString
			MAX-ACCESS read-only
			STATUS current
			DESCRIPTION
				"Name of temperature sensor. Gives an indication of the location of the sensor on the system."
			::= { wsInfraDiagTempEntry 2 }

		-- 1.3.6.1.4.1.388.14.1.6.1.12.1.3
		wsInfraDiagTempCurrTemp OBJECT-TYPE
			SYNTAX Integer32
			UNITS "0.1C"
			MAX-ACCESS read-only
			STATUS current
			DESCRIPTION
				"Current temperature measured by the sensor."
			::= { wsInfraDiagTempEntry 3 }

		-- 1.3.6.1.4.1.388.14.1.6.1.12.1.4
		wsInfraDiagTempMaxTemp OBJECT-TYPE
			SYNTAX INTEGER (0..2500)
			UNITS "0.1C"
			MAX-ACCESS read-write
			STATUS current
			DESCRIPTION
				"Upper limit of temperature measured by the sensor. Send out a notification if this is reached."
			::= { wsInfraDiagTempEntry 4 }

		-- 1.3.6.1.4.1.388.14.1.6.1.12.1.5
		wsInfraDiagTempOverTemp OBJECT-TYPE
			SYNTAX INTEGER (0..2500)
			UNITS "0.1C"
			MAX-ACCESS read-write
			STATUS current
			DESCRIPTION
				"Over limit of temperature measured by the sensor. Send out a notification if temp gets above this value."
			::= { wsInfraDiagTempEntry 5 }

		-- 1.3.6.1.4.1.388.14.1.6.1.13
		wsInfraDiagFanTable OBJECT-TYPE
			SYNTAX SEQUENCE OF WsInfraDiagFanEntry
			MAX-ACCESS not-accessible
			STATUS current
			DESCRIPTION
				"Description."
			::= { wsInfraDiagMib 13 }

		-- 1.3.6.1.4.1.388.14.1.6.1.13.1
		wsInfraDiagFanEntry OBJECT-TYPE
			SYNTAX WsInfraDiagFanEntry
			MAX-ACCESS not-accessible
			STATUS current
			DESCRIPTION
				"Description."
			INDEX { wsInfraDiagFanIndex }
			::= { wsInfraDiagFanTable 1 }

		WsInfraDiagFanEntry ::=
			SEQUENCE { 
				wsInfraDiagFanIndex
					INTEGER,
				wsInfraDiagFanName
					DisplayString,
				wsInfraDiagFanSpeed
					INTEGER,
				wsInfraDiagFanLowSpeedLimit
					INTEGER
			 }

		-- 1.3.6.1.4.1.388.14.1.6.1.13.1.1
		wsInfraDiagFanIndex OBJECT-TYPE
			SYNTAX INTEGER (1..6)
			MAX-ACCESS accessible-for-notify
			STATUS current
			DESCRIPTION
				"Simple Index."
			::= { wsInfraDiagFanEntry 1 }

		-- 1.3.6.1.4.1.388.14.1.6.1.13.1.2
		wsInfraDiagFanName OBJECT-TYPE
			SYNTAX DisplayString
			MAX-ACCESS read-only
			STATUS current
			DESCRIPTION
				"Name of fan. Gives an indication of the location of the fan on the system."
			::= { wsInfraDiagFanEntry 2 }

		-- 1.3.6.1.4.1.388.14.1.6.1.13.1.3
		wsInfraDiagFanSpeed OBJECT-TYPE
			SYNTAX INTEGER (1..15000)
			UNITS "1 rpm"
			MAX-ACCESS read-only
			STATUS current
			DESCRIPTION
				"Speed of fan in rpm"
			::= { wsInfraDiagFanEntry 3 }

		-- 1.3.6.1.4.1.388.14.1.6.1.13.1.4
		wsInfraDiagFanLowSpeedLimit OBJECT-TYPE
			SYNTAX INTEGER (1000..15000)
			UNITS "1 rpm"
			MAX-ACCESS read-write
			STATUS current
			DESCRIPTION
				"Low speed limit of fan. Send out a notification if speed gets to, or below this value."
			::= { wsInfraDiagFanEntry 4 }

		-- 1.3.6.1.4.1.388.14.1.6.1.14
		wsInfraDiagProcTable OBJECT-TYPE
			SYNTAX SEQUENCE OF WsInfraDiagProcEntry
			MAX-ACCESS not-accessible
			STATUS current
			DESCRIPTION
				"Table of top 10 processes."
			::= { wsInfraDiagMib 14 }

		-- 1.3.6.1.4.1.388.14.1.6.1.14.1
		wsInfraDiagProcEntry OBJECT-TYPE
			SYNTAX WsInfraDiagProcEntry
			MAX-ACCESS not-accessible
			STATUS current
			DESCRIPTION
				"Description."
			INDEX { wsInfraDiagProcIndex }
			::= { wsInfraDiagProcTable 1 }

		WsInfraDiagProcEntry ::=
			SEQUENCE { 
				wsInfraDiagProcIndex
					INTEGER,
				wsInfraDiagProcName
					DisplayString,
				wsInfraDiagProcPercentCPU
					INTEGER,
				wsInfraDiagProcPercentMem
					INTEGER
			 }

		-- 1.3.6.1.4.1.388.14.1.6.1.14.1.1
		wsInfraDiagProcIndex OBJECT-TYPE
			SYNTAX INTEGER (1..10)
			MAX-ACCESS accessible-for-notify
			STATUS current
			DESCRIPTION
				"Simple index"
			::= { wsInfraDiagProcEntry 1 }

		-- 1.3.6.1.4.1.388.14.1.6.1.14.1.2
		wsInfraDiagProcName OBJECT-TYPE
			SYNTAX DisplayString
			MAX-ACCESS read-only
			STATUS current
			DESCRIPTION
				"Name of proc "
			::= { wsInfraDiagProcEntry 2 }

		-- 1.3.6.1.4.1.388.14.1.6.1.14.1.3
		wsInfraDiagProcPercentCPU OBJECT-TYPE
			SYNTAX INTEGER (0..1000)
			UNITS "0.1%"
			MAX-ACCESS read-only
			STATUS current
			DESCRIPTION
				"% of CPU used by proc."
			::= { wsInfraDiagProcEntry 3 }

		-- 1.3.6.1.4.1.388.14.1.6.1.14.1.4
		wsInfraDiagProcPercentMem OBJECT-TYPE
			SYNTAX INTEGER (0..1000)
			UNITS "0.1%"
			MAX-ACCESS read-only
			STATUS current
			DESCRIPTION
				"% of memory used by proc."
			::= { wsInfraDiagProcEntry 4 }

		-- 1.3.6.1.4.1.388.14.1.6.1.15
		wsInfraDiagRamStats OBJECT IDENTIFIER ::= { wsInfraDiagMib 15 }

		-- 1.3.6.1.4.1.388.14.1.6.1.15.1
		wsInfraDiagRamStatsTotal OBJECT-TYPE
			SYNTAX Integer32
			MAX-ACCESS read-only
			STATUS current
			DESCRIPTION
				"Total RAM available in the system"
			::= { wsInfraDiagRamStats 1 }

		-- 1.3.6.1.4.1.388.14.1.6.1.15.2
		wsInfraDiagRamStatsUsed OBJECT-TYPE
			SYNTAX Integer32
			MAX-ACCESS read-only
			STATUS current
			DESCRIPTION
				"Total RAM used in the system"
			::= { wsInfraDiagRamStats 2 }

		-- 1.3.6.1.4.1.388.14.1.6.1.15.3
		wsInfraDiagRamStatsFree OBJECT-TYPE
			SYNTAX Integer32
			MAX-ACCESS read-only
			STATUS current
			DESCRIPTION
				"Total RAM not used in the system"
			::= { wsInfraDiagRamStats 3 }

		-- 1.3.6.1.4.1.388.14.1.6.1.15.4
		wsInfraDiagRamStatsPercentFree OBJECT-TYPE
			SYNTAX INTEGER (0..1000)
			UNITS "0.1%"
			MAX-ACCESS read-only
			STATUS current
			DESCRIPTION
				"% of free RAM in system"
			::= { wsInfraDiagRamStats 4 }

		-- 1.3.6.1.4.1.388.14.1.6.1.15.5
		wsInfraDiagRamStatsPercentFreeLimit OBJECT-TYPE
			SYNTAX INTEGER (0..250)
			UNITS "0.1 %"
			MAX-ACCESS read-write
			STATUS current
			DESCRIPTION
				"Limit of free RAM in system in %."
			::= { wsInfraDiagRamStats 5 }

		-- 1.3.6.1.4.1.388.14.1.6.1.17
		wsInfraDiagPktBuffStats OBJECT IDENTIFIER ::= { wsInfraDiagMib 17 }

		-- 1.3.6.1.4.1.388.14.1.6.1.17.1
		wsInfraDiagPktBuffAlloc OBJECT-TYPE
			SYNTAX Integer32
			MAX-ACCESS read-only
			STATUS current
			DESCRIPTION
				"Amount of allocated packet buffer in system."
			::= { wsInfraDiagPktBuffStats 1 }

		-- 1.3.6.1.4.1.388.14.1.6.1.17.2
		wsInfraDiagPktBuffUsed OBJECT-TYPE
			SYNTAX Integer32
			MAX-ACCESS read-only
			STATUS current
			DESCRIPTION
				"Amount of used packet buffer in system."
			::= { wsInfraDiagPktBuffStats 2 }

		-- 1.3.6.1.4.1.388.14.1.6.1.17.3
		wsInfraDiagPktBuffMax OBJECT-TYPE
			SYNTAX INTEGER (0..65535)
			UNITS "KB"
			MAX-ACCESS read-write
			STATUS current
			DESCRIPTION
				"Limit on maximum of allocated packet buffer in system."
			::= { wsInfraDiagPktBuffStats 3 }

		-- 1.3.6.1.4.1.388.14.1.6.1.18
		wsInfraDiagIpRouteCacheStats OBJECT IDENTIFIER ::= { wsInfraDiagMib 18 }

		-- 1.3.6.1.4.1.388.14.1.6.1.18.1
		wsInfraDiagIpRouteCacheAlloc OBJECT-TYPE
			SYNTAX Integer32
			MAX-ACCESS read-only
			STATUS current
			DESCRIPTION
				"Amount of allocated IP route cache in system."
			::= { wsInfraDiagIpRouteCacheStats 1 }

		-- 1.3.6.1.4.1.388.14.1.6.1.18.2
		wsInfraDiagIpRouteCacheUsed OBJECT-TYPE
			SYNTAX Integer32
			MAX-ACCESS read-only
			STATUS current
			DESCRIPTION
				"Amount of used IP route cache in system."
			::= { wsInfraDiagIpRouteCacheStats 2 }

		-- 1.3.6.1.4.1.388.14.1.6.1.18.3
		wsInfraDiagIpRouteCacheMax OBJECT-TYPE
			SYNTAX INTEGER (0..65535)
			MAX-ACCESS read-write
			STATUS current
			DESCRIPTION
				"Max limit of allocated IP route cache in system."
			::= { wsInfraDiagIpRouteCacheStats 3 }

		-- 1.3.6.1.4.1.388.14.1.6.1.19
		wsInfraDiagFileDescStats OBJECT IDENTIFIER ::= { wsInfraDiagMib 19 }

		-- 1.3.6.1.4.1.388.14.1.6.1.19.1
		wsInfraDiagFileDescInUse OBJECT-TYPE
			SYNTAX Integer32
			MAX-ACCESS read-only
			STATUS current
			DESCRIPTION
				"Number of file descriptors in use."
			::= { wsInfraDiagFileDescStats 1 }

		-- 1.3.6.1.4.1.388.14.1.6.1.19.2
		wsInfraDiagFileDescHWM OBJECT-TYPE
			SYNTAX Integer32
			MAX-ACCESS read-only
			STATUS current
			DESCRIPTION
				"Description."
			::= { wsInfraDiagFileDescStats 2 }

		-- 1.3.6.1.4.1.388.14.1.6.1.19.3
		wsInfraDiagFileDescLimit OBJECT-TYPE
			SYNTAX INTEGER (0..32767)
			MAX-ACCESS read-write
			STATUS current
			DESCRIPTION
				"Limit of file descriptors."
			DEFVAL { ''b }
			::= { wsInfraDiagFileDescStats 3 }

		-- 1.3.6.1.4.1.388.14.1.6.1.20
		wsInfraDiagProcNum OBJECT-TYPE
			SYNTAX Integer32
			MAX-ACCESS read-only
			STATUS current
			DESCRIPTION
				"Number of procs currently running in the system"
			::= { wsInfraDiagMib 20 }

		-- 1.3.6.1.4.1.388.14.1.6.1.21
		wsInfraDiagProcMemLimit OBJECT-TYPE
			SYNTAX INTEGER (0..1000)
			UNITS "%"
			MAX-ACCESS read-write
			STATUS current
			DESCRIPTION
				"Memory limit on processes running in the system."
			::= { wsInfraDiagMib 21 }

		-- 1.3.6.1.4.1.388.14.1.6.1.100
		wsInfraDiagMIBConformance OBJECT IDENTIFIER ::= { wsInfraDiagMib 100 }

		-- 1.3.6.1.4.1.388.14.1.6.1.100.1
		wsInfraDiagMIBCompliances OBJECT IDENTIFIER ::= { wsInfraDiagMIBConformance 1 }

		-- 1.3.6.1.4.1.388.14.1.6.1.100.1.1
		wsInfraDiagMIBCompliance MODULE-COMPLIANCE
			STATUS current
			DESCRIPTION 
				"diag MIB compliance"
			MODULE -- this module
				MANDATORY-GROUPS { wsInfraMIBDiagGroup }
			::= { wsInfraDiagMIBCompliances 1 }

		-- 1.3.6.1.4.1.388.14.1.6.1.100.2
		wsInfraDiagMIBGroups OBJECT IDENTIFIER ::= { wsInfraDiagMIBConformance 2 }

		-- 1.3.6.1.4.1.388.14.1.6.1.100.2.1
		wsInfraMIBDiagGroup OBJECT-GROUP
			OBJECTS { wsInfraHwBuildInfoModuleName, wsInfraHwBuildInfoVersion, wsInfraHwBuildInfoManufacturer, wsInfraHwBuildInfoDesc, wsInfraResCpuLoad1, 
				wsInfraResCpuLoad5, wsInfraResCpuLoad15, wsInfraUsedKernBuff32, wsInfraUsedKernBuff64, wsInfraUsedKernBuff128, 
				wsInfraUsedKernBuff256, wsInfraUsedKernBuff512, wsInfraUsedKernBuff1024, wsInfraUsedKernBuff2048, wsInfraUsedKernBuff4096, 
				wsInfraUsedKernBuff8192, wsInfraUsedKernBuff16384, wsInfraUsedKernBuff32768, wsInfraUsedKernBuff65536, wsInfraUsedKernBuff131072, 
				wsInfraDiagControl, wsInfraDiagPeriod, wsInfraDiagFanNum, wsInfraDiagTempSensorNum, wsInfraDiagPlatform, 
				wsInfraDiagMonitoredFSFreeSpaceLimit, wsInfraResCpuLoad1MinLimit, wsInfraUsedKernBuff32Limit, wsInfraUsedKernBuff64Limit, wsInfraUsedKernBuff128Limit, 
				wsInfraUsedKernBuff256Limit, wsInfraUsedKernBuff512Limit, wsInfraUsedKernBuff1024Limit, wsInfraUsedKernBuff2048Limit, wsInfraUsedKernBuff4096Limit, 
				wsInfraUsedKernBuff8192Limit, wsInfraUsedKernBuff16384Limit, wsInfraUsedKernBuff32768Limit, wsInfraUsedKernBuff65536Limit, wsInfraUsedKernBuff131072Limit, 
				wsInfraDiagMonitoredFSSize, wsInfraDiagMonitoredFSUsed, wsInfraDiagMonitoredFSINodesFree, wsInfraDiagMonitoredFSINodesLimit, wsInfraDiagTempIndex, 
				wsInfraDiagTempSensorName, wsInfraDiagTempCurrTemp, wsInfraDiagTempMaxTemp, wsInfraDiagTempOverTemp, wsInfraDiagFanIndex, 
				wsInfraDiagFanName, wsInfraDiagFanSpeed, wsInfraDiagFanLowSpeedLimit, wsInfraDiagProcIndex, wsInfraDiagProcName, 
				wsInfraDiagProcPercentCPU, wsInfraDiagProcPercentMem, wsInfraDiagPktBuffAlloc, wsInfraDiagPktBuffUsed, wsInfraDiagPktBuffMax, 
				wsInfraDiagIpRouteCacheAlloc, wsInfraDiagIpRouteCacheUsed, wsInfraDiagIpRouteCacheMax, wsInfraDiagFileDescInUse, wsInfraDiagFileDescHWM, 
				wsInfraDiagFileDescLimit, wsInfraDiagProcNum, wsInfraDiagProcMemLimit, wsInfraDiagRamStatsTotal, wsInfraDiagRamStatsUsed, 
				wsInfraDiagRamStatsFree, wsInfraDiagRamStatsPercentFree, wsInfraDiagRamStatsPercentFreeLimit, wsInfraResCpuLoad15MinLimit, wsInfraResCpuLoad5MinLimit, 
				wsInfraDiagMonitoredFSFreeSpacePercent, wsInfraDiagMonitoredFSFreeSpace, wsInfraDiagMonitoredFSName }
			STATUS current
			DESCRIPTION 
				"diag MIB group"
			::= { wsInfraDiagMIBGroups 1 }

		-- 1.3.6.1.4.1.388.14.1.6.1.100.2.2
		wsInfraMIBDiagObsoleteGroup OBJECT-GROUP
			OBJECTS { wsInfraDiagTempCurrentTemp, wsInfraDiagTempHighTemp, wsInfraDiagTempHighTempHysteresis, wsInfraDiagSysFanSpeed, wsDiagProcFanSpeed, 
				wsInfraFreeMemory, wsInfraRootFSFree, wsInfraRootFSInodesFree, wsInfraRamFSFree, wsInfraRamFSInodesFree, 
				wsInfraFreeFileDesc, wsInfraHwTotalNum }
			STATUS obsolete
			DESCRIPTION 
				"Description."
			::= { wsInfraDiagMIBGroups 2 }
	END
