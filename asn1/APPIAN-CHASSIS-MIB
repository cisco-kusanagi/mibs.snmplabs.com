--
--      Title:  Appian Chassis MIB
--
--      Dated:  11/4/99
--      Author: D. Theriault
--
--      Description:
--
--      This MIB file contains the definitions and support for the Appian
--      Optical Services Access Platform(s).
-- 
--      The Appian chassis MIB supports attributes which are chassis specific.
--
--
APPIAN-CHASSIS-MIB DEFINITIONS ::= BEGIN
    IMPORTS
        acOsap, AcAdminStatus, AcOpStatus,
        AcNodeId, AcMibVersion, AcRingId,
        AcNodeArchitecture                          FROM APPIAN-SMI-MIB 
            
        MODULE-IDENTITY, OBJECT-TYPE, 
        IpAddress, TimeTicks, NOTIFICATION-TYPE     FROM SNMPv2-SMI

        DateAndTime, DisplayString, TruthValue,
        TEXTUAL-CONVENTION                          FROM SNMPv2-TC;


acChassis       MODULE-IDENTITY
    LAST-UPDATED    "0004200000Z"
    ORGANIZATION    "Appian Communications, Inc."
    CONTACT-INFO    "Douglas Theriault"
    
    DESCRIPTION     "Appian OSAP Chassis MIB which defines the current hardware
                    configuration and state information."
                    
    REVISION        "0004200000Z"

    DESCRIPTION     "Engineering draft version, not for release."

    ::= { acOsap 1 }

    AcFanStatus    ::= TEXTUAL-CONVENTION
    STATUS         current
    DESCRIPTION
        "The FAN status."
    SYNTAX  INTEGER {
                    unknown (0),
                    fast (1),
                                medium (2),
                                slow (3),
                                failed (4)
            }


acGlobals  OBJECT IDENTIFIER ::= { acChassis 1 }

acNodeId OBJECT-TYPE
    SYNTAX  AcNodeId
    MAX-ACCESS  read-write
    STATUS  current
    DESCRIPTION
    "A unique node identifier assigned by the EMS to uniquely identify a
    node within an Appian ring. This must be set before setting other MIB
    objects that used NodeId as part of the index."
    
    ::= { acGlobals 1 }

--
-- Chassis Table
--
acChassisTable  OBJECT-TYPE
    SYNTAX  SEQUENCE OF AcChassisEntry
    MAX-ACCESS  not-accessible
    STATUS  current
    DESCRIPTION
    "A table of configuration and statistics parameters for an Appian
    Communications chassis's within an Appian ring."
    
    ::= { acChassis 2 }
    
acChassisEntry  OBJECT-TYPE
    SYNTAX  AcChassisEntry
    MAX-ACCESS  not-accessible
    STATUS  current
    DESCRIPTION
    "A single node's chassis parameters.  The index to this record is
    AcNodeId which is a unique identifier assigned by the EMS system."
    
    INDEX { acChassisNodeId }
    
    ::= { acChassisTable 1 }
    
    AcChassisEntry ::=
        SEQUENCE {
            acChassisNodeId                     AcNodeId,
            acChassisAdminStatus                AcAdminStatus,
            acChassisOpStatus                   AcOpStatus,
            acChassisCfgType                    INTEGER,
            acChassisModelNumber                INTEGER,
            acChassisSerialNumber               DisplayString,
            acChassisProductionDate             DisplayString,
            acChassisRevision                   INTEGER,
            acChassisTemperature                INTEGER,
            acChassisFanSpeed                   AcFanStatus,
            acChassisFan1Status                 AcFanStatus,
            acChassisFan2Status                 AcFanStatus,
            acChassisFan3Status                 AcFanStatus,
            acChassisFan4Status                 AcFanStatus,
            acChassisFan5Status                 AcFanStatus,
            acChassisFan6Status                 AcFanStatus,
            acChassisPowerAStatus               AcOpStatus,
            acChassisPowerBStatus               AcOpStatus,
            acChassisContact                    DisplayString,
            acChassisName                       DisplayString,
            acChassisLocation                   DisplayString,
            acChassisDescription                DisplayString,
            acChassisMaxSlots                   INTEGER,
            acChassisSysUpTime                  TimeTicks,
            acChassisCurrentTime                DateAndTime,
            acChassisMaxSerialPorts             INTEGER,
            acChassisRingId                     AcRingId,
            acChassisRingName                   DisplayString,
            acChassisMibVersion                 AcMibVersion,
            acChassisNodeArchitecture           AcNodeArchitecture,
            acChassisNodePoll                   OCTET STRING,
            acChassisModulePoll                 OCTET STRING,
            acChassisPortPoll                   OCTET STRING,
            acChassisReset                      TruthValue,
	    acChassisTdmAccessRedundancyMode    INTEGER
        }
        
--
-- Chassis Record
--
acChassisNodeId OBJECT-TYPE
    SYNTAX  AcNodeId
    MAX-ACCESS  accessible-for-notify
    STATUS  current
    DESCRIPTION
    "A unique node identifier assigned by the EMS to uniquely identify a
    node within an Appian ring."
    
    ::= { acChassisEntry 1 }
    
acChassisAdminStatus    OBJECT-TYPE
    SYNTAX  AcAdminStatus
    MAX-ACCESS      read-write
    STATUS          current
    DESCRIPTION
    "This field is used by the administrator to ensure only one
    client can configure the chassis record at a time.  The field
    is set to locked when a client is performing administrative
    operations and available when it is free."
    
    DEFVAL { activate }

    ::= { acChassisEntry 2 }

acChassisOpStatus  OBJECT-TYPE
    SYNTAX      AcOpStatus
    MAX-ACCESS  read-only
    STATUS      current
    DESCRIPTION
    "The state field is used to identify the current operational state of
    the chassis."

    ::= { acChassisEntry 3 }

acChassisCfgType    OBJECT-TYPE
    SYNTAX  INTEGER {
                unknown(0),
                osap-1600(1),
                osap-4800(2),
                osap-10G(3)
            }
    MAX-ACCESS  read-write
    STATUS      current
    DESCRIPTION
    "This field describes the type of physical chassis as defined by the
    AppianVista EMS. The model number is a simple enumeration type for 
    an Appian Communications chassis."

    DEFVAL { unknown }

    ::= { acChassisEntry 4 }
    
acChassisModelNumber    OBJECT-TYPE
    SYNTAX  INTEGER {
                unknown(0),
                osap-1600(1),
                osap-4800(2),
                osap-10G(3)
            }
    MAX-ACCESS  read-only
    STATUS      current
    DESCRIPTION
    "This field defines the type of physical chassis.  The model number
    is a simple enumeration type for an Appian Communications chassis."

    ::= { acChassisEntry 5 }

acChassisSerialNumber   OBJECT-TYPE
    SYNTAX  DisplayString (SIZE (0..32))
    MAX-ACCESS  read-only
    STATUS      current
    DESCRIPTION
    "Display string containing the serial number which is read from the 
    chassis backplane prom."

    ::= { acChassisEntry 6 }

acChassisProductionDate OBJECT-TYPE
    SYNTAX  DisplayString (SIZE (0..5))
    MAX-ACCESS  read-only
    STATUS      current
    DESCRIPTION
    "The date code when this chassis was manufactured.  This field 
    is read-only and set by manufacturing in the I2C prom. The format used
    is YYWW; with YY = year and WW = week."

    ::= { acChassisEntry 7 }

acChassisRevision   OBJECT-TYPE
    SYNTAX  INTEGER (0..255)
    MAX-ACCESS      read-only
    STATUS          current
    DESCRIPTION
    "The revision of the chassis expressed as an integer monotonically 
    increasing from 0 to 255."

    ::= { acChassisEntry 8 }

acChassisTemperature    OBJECT-TYPE
    SYNTAX  INTEGER {
                unknown(0),
                normal(1),
                tooCold(2),
                tooHot(3)
            }
    MAX-ACCESS  read-only
    STATUS      current
    DESCRIPTION
    "The current temperature state for the chassis as reported by the fan
    and temperature controller card. If the temperature is too hot, it is
    possible that the input filter is blocked, which is reported in the
    acChassisFanStatus attribute."

    ::= { acChassisEntry 9 }

acChassisFanSpeed  OBJECT-TYPE
    SYNTAX  AcFanStatus
    MAX-ACCESS  read-write
    STATUS      current
    DESCRIPTION
    "The desired fan speed."
    ::= { acChassisEntry 10 }

acChassisFan1Status  OBJECT-TYPE
    SYNTAX  AcFanStatus
    MAX-ACCESS  read-only
    STATUS      current
    DESCRIPTION
    "FAN 1 status."
    ::= { acChassisEntry 11 }

acChassisFan2Status  OBJECT-TYPE
    SYNTAX  AcFanStatus
    MAX-ACCESS  read-only
    STATUS      current
    DESCRIPTION
    "FAN 2 status."
    ::= { acChassisEntry 12 }

acChassisFan3Status  OBJECT-TYPE
    SYNTAX  AcFanStatus
    MAX-ACCESS  read-only
    STATUS      current
    DESCRIPTION
    "FAN 3 status."
    ::= { acChassisEntry 13 }

acChassisFan4Status  OBJECT-TYPE
    SYNTAX  AcFanStatus
    MAX-ACCESS  read-only
    STATUS      current
    DESCRIPTION
    "FAN 4 status."
    ::= { acChassisEntry 14 }

acChassisFan5Status  OBJECT-TYPE
    SYNTAX  AcFanStatus
    MAX-ACCESS  read-only
    STATUS      current
    DESCRIPTION
    "FAN 5 status."
    ::= { acChassisEntry 15 }

acChassisFan6Status  OBJECT-TYPE
    SYNTAX  AcFanStatus
    MAX-ACCESS  read-only
    STATUS      current
    DESCRIPTION
    "FAN 6 status."
    ::= { acChassisEntry 16 }

acChassisPowerAStatus    OBJECT-TYPE
    SYNTAX  AcOpStatus
    MAX-ACCESS  read-only
    STATUS      current
    DESCRIPTION
    "The current state of the power supply subsystem."
    ::= { acChassisEntry 17 }

acChassisPowerBStatus    OBJECT-TYPE
    SYNTAX  AcOpStatus
    MAX-ACCESS  read-only
    STATUS      current
    DESCRIPTION
    "The current state of the power supply subsystem."
    ::= { acChassisEntry 18 }

acChassisContact    OBJECT-TYPE
    SYNTAX  DisplayString (SIZE (0..255))
    MAX-ACCESS  read-write
    STATUS      current
    DESCRIPTION
    "The identification and contact information of the person responsible
    for this managed node. This field is mapped to the MIB-II sysContact
    field."
    DEFVAL { "" }

    ::= { acChassisEntry 19 }

acChassisName   OBJECT-TYPE
    SYNTAX  DisplayString (SIZE (0..255))
    MAX-ACCESS  read-write
    STATUS      current
    DESCRIPTION
    "An administratively assigned name for this managed node. This field is
    mapped to MIB-II sysName field."
    DEFVAL { "" }

    ::= { acChassisEntry 20 }

acChassisLocation   OBJECT-TYPE
    SYNTAX  DisplayString (SIZE (0..255))
    MAX-ACCESS  read-write
    STATUS      current
    DESCRIPTION
    "The physical location of this node. The field is mapped to the MIB-II
    sysLocation field."
    DEFVAL { "" }

    ::= { acChassisEntry 21 }

acChassisDescription    OBJECT-TYPE
    SYNTAX  DisplayString (SIZE (0..255))
    MAX-ACCESS  read-only
    STATUS      current
    DESCRIPTION
    "A description of the node indicating the type of Appian Communications 
    equipment. This field is mapped to the MIB-II sysDescr attribute."

    ::= { acChassisEntry 22 }

acChassisMaxSlots   OBJECT-TYPE
    SYNTAX  INTEGER (1..16)
    MAX-ACCESS  read-only
    STATUS      current
    DESCRIPTION
    "The maximum number of slots within this chassis."

    ::= { acChassisEntry 23 }

acChassisSysUpTime  OBJECT-TYPE
    SYNTAX  TimeTicks
    MAX-ACCESS  read-only
    STATUS      current
    DESCRIPTION
    "The time in hundredths of a second since the network management
    portion of the system was last reinitialized. The acChassisSysUpTime
    field is mapped to the MIB-II sysUptime field. Note: The value of 
    acChassisSysUpTime will not be reset when an Active to Standby failover
    occurs on the Switch Control Processor(s). The acChassisSysUpTime 
    value will only be reset when the whole system has been reset."

    ::= { acChassisEntry 24 }

acChassisCurrentTime    OBJECT-TYPE
    SYNTAX  DateAndTime
    MAX-ACCESS  read-write
    STATUS      current
    DESCRIPTION
    "A string containing the current time and date as read from 
    the active Switch Control Processor (SCP) NovRam. The
    format is defined by DateAndTime syntax."

    DEFVAL { "" }

    ::= { acChassisEntry 25 }

acChassisMaxSerialPorts  OBJECT-TYPE
    SYNTAX  INTEGER (1..2)
    MAX-ACCESS  read-only
    STATUS  current
    DESCRIPTION
    "Identifies the total number of serial interface ports on the OSAP chassis."

    ::= { acChassisEntry 26 }


acChassisRingId  OBJECT-TYPE
    SYNTAX  AcRingId 
    MAX-ACCESS  read-write
    STATUS  current
    DESCRIPTION
    "A unique Ring Identification number which is assigned by the EMS system to
    uniquely identify the Appian Ring supported by this node."

    ::= { acChassisEntry 27 }


acChassisRingName  OBJECT-TYPE
    SYNTAX  DisplayString (SIZE(0..64))
    MAX-ACCESS  read-write
    STATUS  current
    DESCRIPTION
    "A user defined string assigned to the Ring Id which uniquely identifies the
    Appian Ring supported by this node."

    ::= { acChassisEntry 28 }
    
acChassisMibVersion  OBJECT-TYPE
    SYNTAX  AcMibVersion
    MAX-ACCESS  read-only
    STATUS  current
    DESCRIPTION
    "A ASCII string which identifies the Appian MIB version which is 
    currently supported by the active switch control processor."

    ::= { acChassisEntry 29 }

acChassisNodeArchitecture  OBJECT-TYPE
    SYNTAX  AcNodeArchitecture
    MAX-ACCESS  read-write
    STATUS  current
    DESCRIPTION
    "Node architecture."

    ::= { acChassisEntry 30 }

acChassisNodePoll  OBJECT-TYPE
    SYNTAX      OCTET STRING
    MAX-ACCESS  read-only
    STATUS  current
    DESCRIPTION
    "This object returns a concise summary of the system state. It contains
        information on the system operational status, mib revision, fan status,
        power supply status, and other status information.

        The value is in compacted binary format:

        Element             Size Value              Description
        -----------------------------------------------------------------------
        poll version         1   0x01               Node poll version
        operational status   1   acChassisOpStatus  overall system status
        mib version          4   
        software version     4   
        chassis temperature  1   actual temperature? maybe it should be in module?
        fan status, each fan status is encoded as:
          0xA1   - FAN status IE
      0x01   - FAN #1
          0x01   - operational
        power supply status, with each power supply status encoded as:
          0xA2   - power status IE
          0x02   - power supply #2
          0x01   - operational
        "
    ::= { acChassisEntry 31 }

acChassisModulePoll  OBJECT-TYPE
    SYNTAX      OCTET STRING
    MAX-ACCESS  read-only
    STATUS  current
    DESCRIPTION
    "This object returns a concise summary of the module cards in the system.
        For each module card present, it includes card slot, card configured type
        and actual type, card operational status, redundancy status, and possibly
        LED information.

        slot            -  1 byte representing the physical slot number.
        number          -  1 byte representing the module number.
        configured type -  1 byte value from AcModuleType.
        actual type     -  1 byte value from AcModuleType.
        operStatus      -  1 byte representing an AcOpStatus.
        redundancy      -  1 byte to indicate it's active or standby
        number of LEDs  -  1 byte, indicates how many LED status follows
          LED states    -  1 byte for each LED to represent: 
                          green, red, yellow, off.
                                                  with high bit on as ing.
    "
    ::= { acChassisEntry 32 }

acChassisPortPoll  OBJECT-TYPE
    SYNTAX      OCTET STRING
    MAX-ACCESS  read-only
    STATUS  current
    DESCRIPTION
    "This object returns a concise summary of the module cards in the system.
        For each module card present, it includes card slot, card configured type
        and actual type, card operational status, redundancy status, possibly
        LED information, and port information.

        slot            -  1 byte representing the physical slot number.
        configured type -  1 byte value from AcModuleType.
        actual type     -  1 byte value from AcModuleType.
        operStatus      -  1 byte representing an AcOpStatus.
        media slot      -  1 byte, valid only 
        number of LEDs  -  1 byte, indicates how many LED status follows
          LED states    -  1 byte for each LED to represent: 
                          green, red, yellow, off.
                                                  with high bit on as ing.
    number of ports -  1 byte, indicates how many physical ports on the card
      port info     -  for each port, it includes operStatus and service
                       status.

    Take a system with the following configuration as an example:

           slot 1 - a single port OC3
           slot 2 - a single port OC3
           slot 3 - a switching control card
           slot 5 - an ethernet media card
           slot 6 - an ethernet media card, currently backing up slot 5
           slot 11 - an 8-port ethernet PHY card driven by slot 5
           slot 12 - an 8-port ethernet PHY card driven by slot 5.

        The poll would resemble this:

        0x01  - the first poll version
        0xA3  - this indicates a card information element
      0x01 - card slot 1
      0x13 - configured card type: oc3-sr-1
          0x13 - actual card type: oc3-sr-1
          0x01 - card operational status: operational
          ox00 - media slot, not applicable
          0x00 - # of LEDs, 0 means no LED information included
          0x01 - # of ports
            0x01 - port status: up
                0x00 - no services on this port
        0xA3  - this indicates a card information element
      0x02 - card slot 2
      0x13 - configured card type: oc3-sr-1
          0x13 - actual card type: oc3-sr-1
          0x01 - card operational status: operational
          ox00 - media slot, not applicable
          0x00 - # of LEDs, 0 means no LED information included
          0x01 - # of ports
            0x01 - port status: up
                0x00 - no services on this port
        0xA3  - this indicates a card information element
      0x03 - card slot 3
      0x03 - configured card type: sw-1
          0x03 - actual card type: sw-1
          0x01 - card operational status: operational
          ox00 - media slot, not applicable
          0x00 - # of LEDs, 0 means no LED information included
          0x00 - # of ports
        0xA3  - this indicates a card information element
      0x05 - card slot 5
      0x04 - configured card type: 16-port fast ethernet
          0x04 - actual card type: 16-port fast ethernet
          0x01 - card operational status: operational
          ox00 - media slot, not applicable
          0x00 - # of LEDs, 0 means no LED information included
          0x00 - # of ports - defer port status to PHY cards?
        0xA3  - this indicates a card information element
      0x0B - card slot 11
      0x05 - configured card type: fe8-tx-io (8-port phy card)
          0x05 - actual card type: fe8-tx-io (8-port phy card)
          0x01 - card operational status: operational
          ox05 - media slot: currently driven by media card in slot 5
          0x00 - # of LEDs, 0 means no LED information included
          0x08 - info for 8 ports follows
        0x01 0x??  - port 1, up and service status? 
        0x02 0x??  - port 2, down and service status?
        ...
             1 byte can be used to represent 4 service status, with 2
                         bits each?
        0xA3  - this indicates a card information element
      0x0C - card slot 11
      0x05 - configured card type: fe8-tx-io (8-port phy card)
          0x05 - actual card type: fe8-tx-io (8-port phy card)
          0x01 - card operational status: operational
          ox05 - media slot: currently driven by media card in slot 5
          0x00 - # of LEDs, 0 means no LED information included
          0x08 - info for 8 ports follows
        0x01 0x??  - port 1, up and service status? 
        0x02 0x??  - port 2, down and service status?
        ...
             1 byte can be used to represent 4 service status, with 2
                         bits each?
    "
    ::= { acChassisEntry 33 }

acChassisReset  OBJECT-TYPE
    SYNTAX      TruthValue
    MAX-ACCESS  read-write
    STATUS      current
    DESCRIPTION
		"Setting this object to true causes the entire system to reset."
	::= { acChassisEntry 34 }
    
acChassisTdmAccessRedundancyMode  OBJECT-TYPE
    SYNTAX  INTEGER {
               n-to-one(0),
               one-to-one(1)
               }
    MAX-ACCESS  read-write
    STATUS  current
    DESCRIPTION
    "This value describes how backup TDM Access cards are used
     to provide redundancy for active TDM Access cards in the 
     system.  

       n-to-one:   One backup card will provide redundancy for
                   all other similar type TDM Access cards.

       one-to-one: Each backup card will be assigned to provide
                   redundancy for at most one TDM Access card."

    DEFVAL { n-to-one }

    ::= { acChassisEntry 35 }

--
-- Chassis Related Traps
--
acChassisTraps  OBJECT IDENTIFIER ::= { acChassis 0 }

acChassisCfgMismatchTrap  NOTIFICATION-TYPE
    OBJECTS  { 
        acChassisCurrentTime, acChassisRingId, 
        acChassisNodeId, 
        acChassisModelNumber, 
        acChassisCfgType 
    }
    STATUS  current
    DESCRIPTION
    "The user configured chassis model does not match the actual chassis
    model generated by this trap."
    
    ::= { acChassisTraps 1 }
    
acChassisTemperatureTrap  NOTIFICATION-TYPE
    OBJECTS  { 
        acChassisCurrentTime, acChassisRingId, 
        acChassisNodeId,
        acChassisTemperature
    }
    STATUS  current
    DESCRIPTION
    "The temperature for this chassis has exceeded or fallen below the normal 
    operational range."
    
    ::= { acChassisTraps 2 }
    
acChassisFanFailureTrap  NOTIFICATION-TYPE
    OBJECTS  { 
        acChassisCurrentTime, acChassisRingId, 
        acChassisNodeId,
        acChassisFan1Status,
        acChassisFan2Status,
        acChassisFan3Status,
        acChassisFan4Status,
        acChassisFan5Status,
        acChassisFan6Status
    }
    STATUS  current
    DESCRIPTION
    "The fan shelf subsystem is reporting a failure of one or more fans."
    
    ::= { acChassisTraps 3 }
    
acChassisTemperatureClearTrap  NOTIFICATION-TYPE
    OBJECTS  { 
        acChassisCurrentTime, acChassisRingId, 
        acChassisNodeId,
        acChassisTemperature
    }
    STATUS  current
    DESCRIPTION
    "The temperature for this chassis has returned back to the normal 
    operational range."
    
    ::= { acChassisTraps 4 }

acChassisFanFailureClearTrap  NOTIFICATION-TYPE
    OBJECTS  { 
        acChassisCurrentTime, acChassisRingId, 
        acChassisNodeId,
        acChassisFan1Status,
        acChassisFan2Status,
        acChassisFan3Status,
        acChassisFan4Status,
        acChassisFan5Status,
        acChassisFan6Status
    }
    STATUS  current
    DESCRIPTION
    "The fan shelf subsystem that reported a failure of one or more fans
     has returned back to normal."
    
    ::= { acChassisTraps 5 }

--
-- Management Access Table
--
acMgmtAccessTable  OBJECT-TYPE
    SYNTAX  SEQUENCE OF AcMgmtAccessEntry
    MAX-ACCESS  not-accessible
    STATUS  current
    DESCRIPTION
    "This table contains the configuration parameters which define the 
    method used for management of the OSAP via a remote EMS such as the
    AppianVista platform.  The table contains the IP Address, gateway and
    subnet for in-band and OOB access to the OSAP."
    
    ::= { acChassis 3 }
    
acMgmtAccessEntry OBJECT-TYPE
    SYNTAX  AcMgmtAccessEntry
    MAX-ACCESS  not-accessible
    STATUS  current
    DESCRIPTION
    "A configuration record defining a single nodes in-band and oob access
    methods and interfaces. This entry must be created by the EMS or CLI
    and is not by default automatically instantiated."
    
    INDEX { acMgmtAccessNodeId, acMgmtAccessIndex }
    
    ::= { acMgmtAccessTable 1 }
    
    AcMgmtAccessEntry ::= 
        SEQUENCE {
            acMgmtAccessNodeId                      AcNodeId,
            acMgmtAccessIndex                       INTEGER,
            acMgmtAccessInterfaceType               INTEGER,
            acMgmtAccessAdminStatus                 AcAdminStatus,
            acMgmtAccessOpStatus                    AcOpStatus,
            acMgmtAccessIpAddress                   IpAddress,
            acMgmtAccessIpSubnet                    IpAddress,
            acMgmtAccessTrunk                       INTEGER,
            acMgmtAccessFrDlci                      INTEGER
        }
        
acMgmtAccessNodeId  OBJECT-TYPE
    SYNTAX  AcNodeId
    MAX-ACCESS  accessible-for-notify
    STATUS  current
    DESCRIPTION
    "A unique node identifier assigned by the EMS to uniquely identify a
    node within an Appian ring."

    ::= { acMgmtAccessEntry 1 }

acMgmtAccessIndex  OBJECT-TYPE
    SYNTAX  INTEGER
    MAX-ACCESS  accessible-for-notify
    STATUS  current
    DESCRIPTION
    "Unique identifier of management access interface in this node."

    ::= { acMgmtAccessEntry 2 }

acMgmtAccessInterfaceType  OBJECT-TYPE
    SYNTAX  INTEGER {
                unknown(0),
                ethernet(1),
                appian-dcc(2),
                oob-ppp (3),    -- PPP over console/modem
                frame-relay(4), -- frame relay circuit
                ppp(5),         -- in-band management over a PPP trunk
                sonet-1-dbg(6),  -- OC3 OOB Enet, in house only !
                sonet-2-dbg(7)   -- OC3 OOB Enet, in house only !                
            }
    MAX-ACCESS  read-create
    STATUS  current
    DESCRIPTION
    "This attribute defines what type of management access port is being 
    configured.  The Ethernet(1) interface refers to the OOB Ethernet port
    on the switch controller and is used for both master and slave switch
    controllers, only one of which is active at a time.  Frame-Relay(4) and
    PPP(5) refer to In-Band access interface.  Appian-DCC(2) is used as an 
    extended LAN and needs to be configured for each node within an Appian
    SONET Ring."

    ::= { acMgmtAccessEntry 3 }

acMgmtAccessAdminStatus  OBJECT-TYPE
    SYNTAX  AcAdminStatus
    MAX-ACCESS  read-create
    STATUS  current
    DESCRIPTION
    "This field is used by the administrator to ensure only one client can 
    perform configuration operations on the chassis record at a time.  The 
    field is set to locked when a client is performing administrative
    operations and available when it is free.  The field is also used to 
    enable or disable a specific management access port.  Setting the value
    to inactivate(1) will cause the interface to be disabled.  Setting the 
    state to activate(2) will enable the management interface."
    
    ::= { acMgmtAccessEntry 4 }
        
acMgmtAccessOpStatus  OBJECT-TYPE
    SYNTAX  AcOpStatus
    MAX-ACCESS  read-only
    STATUS  current
    DESCRIPTION
    "This attribute is used to determine the current state of the management
    access agent.  Refer to the appian-smi.mib for defintion details of the
    AcOpStatus attribute."
    
    ::= { acMgmtAccessEntry 5 }
    
acMgmtAccessIpAddress  OBJECT-TYPE
    SYNTAX  IpAddress
    MAX-ACCESS  read-create
    STATUS  current
    DESCRIPTION
    "The IP Address in dotted notation which is used by the AppianVista EMS
    system or for telnet, tftp, rlogin or ftp access to the network element.
    This IP address may be bound to a frame-relay trunk/dlci or could be 
    bound to a TLS trunk running PPP."
    
    ::= { acMgmtAccessEntry 6 }

acMgmtAccessIpSubnet  OBJECT-TYPE
    SYNTAX  IpAddress
    MAX-ACCESS  read-create
    STATUS      current
    DESCRIPTION
    "The IP Subnet address in dotted notation used for the primary in-band
    access interface.  If no value is entered, the management agent will 
    assume the natural mask."
    
    DEFVAL { 0 }

    ::= { acMgmtAccessEntry 7 }

acMgmtAccessTrunk  OBJECT-TYPE
    SYNTAX  INTEGER
    MAX-ACCESS  read-create
    STATUS      current
    DESCRIPTION
    "If the access type is either frame relay or PPP, this object has the
        trunk number of the trunk being used for inband management. If the 
        access type is not frame relay nor PPP, this object has value of 0
        and is not applicable."

    ::= { acMgmtAccessEntry 8 }
    
acMgmtAccessFrDlci  OBJECT-TYPE
    SYNTAX  INTEGER (16..1022)
    MAX-ACCESS  read-create
    STATUS      current
    DESCRIPTION
    "The Frame-Relay DLCI number used for in-band management access to the
    network element when the access interface uses a frame-relay trunk."

    ::= { acMgmtAccessEntry 9 }


END
