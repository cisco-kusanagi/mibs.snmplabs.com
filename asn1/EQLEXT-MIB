EQLEXT-MIB 

   --FORCE-INCLUDE <mib.h>
   --FORCE-INCLUDE <snmpdefs.h>
   --FORCE-INCLUDE <snmpstat.h>
   --FORCE-INCLUDE "mibproto.h"
 
	DEFINITIONS ::= BEGIN

	IMPORTS
		MODULE-IDENTITY, OBJECT-TYPE
			FROM SNMPv2-SMI
		DisplayString, RowStatus
			FROM SNMPv2-TC
		eqlExt
			FROM APENT-MIB;

--EQLEXT MIB

    apEqlExtMib MODULE-IDENTITY
	   LAST-UPDATED "9710092000Z" -- Thu October 9 20:00:00 EST 1997
	   ORGANIZATION "ArrowPoint Communications Inc."
	   CONTACT-INFO
	   "                      
	   Postal:               ArrowPoint Communications Inc.
				                 50 Nagog Park
				                 Acton, Massachusetts 01720
	   Tel:                   +1 978-206-3000  option 1
	   E-Mail:                support@arrowpoint.com"
       DESCRIPTION
	  "The MIB module used to describe the ArrowPoint Communications
	  (E)xtension (Q)ualification (L)ists"
      ::= { eqlExt 1}


apEqlTable OBJECT-TYPE
	SYNTAX          SEQUENCE OF APEqlEntry
	MAX-ACCESS      not-accessible
	STATUS          current
	DESCRIPTION
		"A list of extension qualifier lists"
	::= { eqlExt 2 }

apEqlEntry OBJECT-TYPE
	SYNTAX          APEqlEntry
	MAX-ACCESS      not-accessible
	STATUS          current
	DESCRIPTION
		"A group of information uniquely identifying an EQL.  One entry 
         exists for each EQL"
	INDEX   { apEqlName }
	::= { apEqlTable 1 }

APEqlEntry ::= SEQUENCE {
		apEqlName                    DisplayString,
      apEqlDescription             DisplayString,
		apEqlStatus                  RowStatus
}

apEqlName OBJECT-TYPE
	SYNTAX          DisplayString (SIZE(1..31))
	MAX-ACCESS      read-create
	STATUS          current
	DESCRIPTION     
			"The name of the EQL"
	::= {apEqlEntry 1}

apEqlDescription OBJECT-TYPE
	SYNTAX          DisplayString (SIZE(0..64))
	MAX-ACCESS      read-create
	STATUS          current
	DESCRIPTION     
			"An EQL description"
	::= {apEqlEntry 2}

apEqlStatus OBJECT-TYPE
	SYNTAX          RowStatus
	MAX-ACCESS      read-create
	STATUS          current
	DESCRIPTION      
		"Status entry for this row "
	::= {apEqlEntry 3}


apEqlExtTable OBJECT-TYPE
	SYNTAX          SEQUENCE OF APEqlExtEntry
	MAX-ACCESS      not-accessible
	STATUS          current
	DESCRIPTION
		"A list of extensions associated with an EQL"
	::= { eqlExt 3 }

apEqlExtEntry OBJECT-TYPE
	SYNTAX          APEqlExtEntry
	MAX-ACCESS      not-accessible
	STATUS          current
	DESCRIPTION
		"Information uniquely identifying an extension within an EQL"
	INDEX   { apEqlName,apEqlExtName }
	::= { apEqlExtTable 1 }

APEqlExtEntry ::= SEQUENCE {
		apEqlExtName                    DisplayString,
		apEqlExtDescription             DisplayString,
		apEqlExtStatus                  RowStatus
}

apEqlExtName OBJECT-TYPE
	SYNTAX          DisplayString (SIZE(1..7))
	MAX-ACCESS      read-create
	STATUS          current
	DESCRIPTION     
			"The extension"
	::= {apEqlExtEntry 1}

apEqlExtDescription OBJECT-TYPE
	SYNTAX          DisplayString (SIZE(1..64))
	MAX-ACCESS      read-create
	STATUS          current
	DESCRIPTION     
			"A description of this extension"
	::= {apEqlExtEntry 2}

apEqlExtStatus OBJECT-TYPE
	SYNTAX          RowStatus
	MAX-ACCESS      read-create
	STATUS          current
	DESCRIPTION      
		"Status entry for this row "
	::= {apEqlExtEntry 3}

END
