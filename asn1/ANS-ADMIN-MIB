--*********************************************************************
-- Copyright: Ericsson Telecom AB 2000
-- Doc no: 112/190 55-CAA 134 74 Uen
--
-- NAME ANS-ADMIN-MIB.mib
--
-- REVISION HISTORY
--
-- The revision history is found in clearcase.
-- Use the 'ct lshistory' command to view it, or
-- use the program '/vobs/tools/bin/cc_mp' program to print
-- the file with the revision information.
-- 
-- PA1  01-03-22        teigaba First version. 
-- PA2  01-10-15        teigaba Changed branch. 


ANS-ADMIN-MIB DEFINITIONS ::= BEGIN
IMPORTS
        OBJECT-TYPE, IpAddress
                FROM SNMPv2-SMI
	DisplayString
		FROM RFC1213-MIB
	RowPointer, RowStatus, mlpmpR115
		FROM ANS-COMMON-MIB;

adminServices          OBJECT IDENTIFIER ::= {mlpmpR115 6}
ansLicense             OBJECT IDENTIFIER ::= {adminServices 1}

-- *****************************************************************************
-- 
--			License Table
--
-- *****************************************************************************

ansLicenseTable OBJECT-TYPE 
	SYNTAX	SEQUENCE OF AnsLicenseEntry
	ACCESS	not-accessible
	STATUS	mandatory
	DESCRIPTION
		"License Table"
	::= { ansLicense 1 }

ansLicenseEntry OBJECT-TYPE
	SYNTAX	AnsLicenseEntry
	ACCESS	not-accessible
	STATUS	mandatory
	DESCRIPTION
		"This entity represents a license interface."
	INDEX {ansLicenseId}
	::= { ansLicenseTable 1 }

AnsLicenseEntry ::= SEQUENCE {
	ansLicenseId			INTEGER,
	ansLicenseName			DisplayString,
	ansLicenseCapacity		INTEGER,
	ansLicenseCurrentCapacity	INTEGER,
	ansLicenseExpirationDate	DisplayString,
	ansLicenseInstall		DisplayString
}

ansLicenseId OBJECT-TYPE
	SYNTAX	INTEGER
	ACCESS	read-only -- key
	STATUS	mandatory
	DESCRIPTION
		"Id"
	::= { ansLicenseEntry 1 }

ansLicenseName OBJECT-TYPE
	SYNTAX	DisplayString
	ACCESS	read-only
	STATUS	mandatory
	DESCRIPTION
		"Name"
	::= { ansLicenseEntry 2 }

ansLicenseCapacity OBJECT-TYPE
	SYNTAX	INTEGER
	ACCESS	read-only
	STATUS	mandatory
	DESCRIPTION
		"License Capacity (-1) for undefined"
	::= { ansLicenseEntry 3 }

ansLicenseCurrentCapacity OBJECT-TYPE
	SYNTAX	INTEGER
	ACCESS	read-only 
	STATUS	mandatory
	DESCRIPTION
		"Current Capacity (-1) for undefined"
	::= { ansLicenseEntry 4 }

ansLicenseExpirationDate OBJECT-TYPE
	SYNTAX	DisplayString
	ACCESS	read-only
	STATUS	mandatory
	DESCRIPTION
		"Expiration Date yymmdd"
	::= { ansLicenseEntry 5 }

ansLicenseInstall OBJECT-TYPE
	SYNTAX	DisplayString
	ACCESS	read-write
	STATUS	mandatory
	DESCRIPTION
		"License String"
	::= { ansLicenseEntry 6 }

END
