--	$Id: VRU_Networkv2.mib,v 1.4 1998/09/30 21:14:23 john Exp $
--
--	Copyright (c) 1994 by
--	Periphonics Corporation
--	4000 Veterans Memorial Hwy
--	Bohemia, NY 11716
--	
--	This software is furnished under a license and may be used and
--	copied only in accordance with the terms of such license and with
--	the inclusion of the above copyright notice. This software or any
--	other copies thereof, may not be provided or otherwise made
--	available to anyone other than the licensee. Title to and ownership
--	of this software remains with the Periphonics Corporation.
--	
--	The information in this document is subject to change without
--	notice and should not be construed as a commitment by Periphonics.
--	
--	Periphonics assumes no responsibility for the use or reliability of
--	its software on equipment that is not supplied by Periphonics.
--	
--	File Name:	VRU_Networkv2.mib
--	
--	Description:	Periphonics SNMP MIB for Voice Response Unit (VRU)
--			Network subtree.  See MODULE-IDENTITY for revision
--			history.
--	

PERIPHONICS-VRU-NETWORK-MIB DEFINITIONS ::= BEGIN

IMPORTS
	periphonics 
		FROM PERIPHONICS-MIB

	MODULE-IDENTITY, OBJECT-TYPE, NOTIFICATION-TYPE, IpAddress
		FROM SNMPv2-SMI
	
	TruthValue, DisplayString, DateAndTime
		FROM SNMPv2-TC

	MODULE-COMPLIANCE, OBJECT-GROUP, NOTIFICATION-GROUP
		FROM SNMPv2-CONF

	;

vruNetwork MODULE-IDENTITY
	LAST-UPDATED "9808050000Z"
	ORGANIZATION "Periphonics Corporation"
	CONTACT-INFO
		""
	DESCRIPTION
		"SNMP MIB module for a VRU Network."
	
	REVISION	"9808050000Z"
	DESCRIPTION	"Changed notifyAlarmByComponent, componentEventsGroup,
			 componentNotificationsGroup, and
			 vruNetworkMIBComplianceByComponent status to
			 deprecated.

			 Added notifyAlarmByComponentEx,
			 alrmLogComponentIpAddress, componentEventsGroup2,
			 componentNotificationsGroup2, and
			 vruNetworkMIBComplianceByComponent2.
			 "

	REVISION	"9801050000Z"
	DESCRIPTION	"The component model has changed.  The component id must
			 be unique for all components of the same type.  We no
			 longer need to use IP (componentIpAddress) as the
			 index into ComponentTable.  alrmLogComponentIpAddress
			 has been deleted and removed from
			 notifyAlarmByComponent.
			"

	REVISION	"9707290000Z"
	DESCRIPTION	"Removed VAS support (vasTable and notifyVasStateChg).
			 Added support for components.

			 Change alrmLogVruId, notifyVruStateChg, notifyAlarm,
			 vruEventsGroup and vruNotificationsGroup status to
			 deprecated.

			 Added alrmLogComponentId, alrmLogComponentIpAddress,
			 alrmLogComponentType, notifyAlarmByComp, 
			 componentEventsGroup,
			 vruNetworkMIBComplianceByComponent,
			 and componentNotificationsGroup,
			"

	REVISION	"9705060000Z"
	DESCRIPTION	"Mod description of appStatsValue."

	REVISION	"9704080000Z"
	DESCRIPTION	"Mod alrmLogMax description to be more clearer.
			 Mod description of lineState.
			"

	REVISION	"9703260000Z"
	DESCRIPTION	"Fix alrmLogSeverity description."

	REVISION	"9702240000Z"
	DESCRIPTION	"Added vasTable and notifyVasStateChg."

	REVISION	"9701180000Z"
	DESCRIPTION	"Mods so SMICng does not complain.
				remove unused imports from IMPORTS section
				make MODULE-IDENTITY first entry.
				remove - from enum constants since this is
					only valid in SMIv1.
				add enterprises, IpAddress to imports.
				add size restriction to DisplayStrings used
					as implied index.  Index item cant have
					size of zero.
				mod evtObjectId and evChange MAX-ACCESS to
					accessible-for-notify.
				add OBJECT-GROUP, NOTIFICATION-GROUP,
					MODULE-COMPLIANCE.
			"

	REVISION	"9701150000Z"
	DESCRIPTION	"Added notifyTopologyChg trap."

	REVISION	"9612170000Z"
	DESCRIPTION	"Added appStats table.
			 Added spanEnabled.
			"


	REVISION	"9612040000Z"
	DESCRIPTION	"Added vruLineCnt, vruSpanCnt, vruHostCnt and
			 hostLuCnt.
			"

	REVISION	"9607010000Z"
	DESCRIPTION	"Creation."

	::= { periphonics 1 }

--
-- Conformance Information
--

vruNetworkMIBConformance OBJECT IDENTIFIER ::= { vruNetwork 1 }

vruNetworkMIBCompliances OBJECT IDENTIFIER ::= { vruNetworkMIBConformance 1}
vruNetworkMIBGroups	 OBJECT IDENTIFIER ::= { vruNetworkMIBConformance 2}

--
-- Compliance Statements
--

vruNetworkMIBCompliance MODULE-COMPLIANCE
	STATUS  deprecated
	DESCRIPTION
		"The compliance statement for SNMPv2 entities
		which implement the VRU-NETWORK MIB."

	MODULE  -- this module
		MANDATORY-GROUPS { vruNotificationsGroup, vruEventsGroup,
				vruGroup, lineGroup, applicationGroup,
				hostGroup }
	::= { vruNetworkMIBCompliances 1 }

vruNetworkMIBComplianceByComponent MODULE-COMPLIANCE
	STATUS  deprecated
	DESCRIPTION
		"The compliance statement for SNMPv2 entities which implement 
		the VRU-NETWORK MIB."

	MODULE  -- this module
		MANDATORY-GROUPS { vruGroup, lineGroup, applicationGroup,
				hostGroup, componentGroup,
				componentNotificationsGroup,
				componentEventsGroup }
	::= { vruNetworkMIBCompliances 2 }

vruNetworkMIBComplianceByComponent2 MODULE-COMPLIANCE
	STATUS  current
	DESCRIPTION
		"The compliance statement for SNMPv2 entities which implement 
		the VRU-NETWORK MIB."

	MODULE  -- this module
		MANDATORY-GROUPS { vruGroup, lineGroup, applicationGroup,
				hostGroup, componentGroup,
				componentNotificationsGroup2,
				componentEventsGroup2 }
	::= { vruNetworkMIBCompliances 3 }

--
-- units of conformance
--

vruNotificationsGroup NOTIFICATION-GROUP
	NOTIFICATIONS { notifyAlarm, notifyVruStateChg, notifyLineAppStateChg,
			notifySpanStateChg, notifyHostStateChg,
			notifyLuStateChg, notifyTopologyChg }
	STATUS		deprecated
	DESCRIPTION
		"A collection of notifications related to an Voice Response
		Unit(VRU)."
	::= { vruNetworkMIBGroups 1 }

vruEventsGroup OBJECT-GROUP
	OBJECTS		{ evObjectId, evChange,
			alrmLogMax, alrmLogNumber, alrmLogSeverity, alrmLogCode,
			alrmLogVruId, alrmLogLineId, alrmLogHostId,
			alrmLogProcName, alrmLogMessage, alrmLogTime }
	STATUS		deprecated
	DESCRIPTION
		"A collection of objects related to a VRU."
	::= { vruNetworkMIBGroups 2 }

vruGroup OBJECT-GROUP
	OBJECTS		{ vruIpAddress, vruDescr, vruLineCnt, vruSpanCnt,
			vruHostCnt, vruAdminState, vruState, vruStateLastChange
			}
	STATUS		current
	DESCRIPTION
		"A collection of objects related to a VRU."
	::= { vruNetworkMIBGroups 3 }

lineGroup OBJECT-GROUP
        OBJECTS         { lineType, lineProtocol, lineState, lineAppName,
			lineAppOverlay, lineAppAdminState, lineAppState,
			lineAppStateLastChange, lineAppCfgLastChange,
			spanLineIdStart, spanLineNumber, spanEnabled,
			spanState, spanStateLastChange }
        STATUS          current
        DESCRIPTION
                "A collection of objects related to a line on a VRU."
        ::= { vruNetworkMIBGroups 4 }

applicationGroup OBJECT-GROUP
        OBJECTS         { appDescr, appOptions, appLineCnt,
			appStatsValue, appStatsLastChange }
        STATUS          current
        DESCRIPTION
                "A collection of objects related to a VRU application."
        ::= { vruNetworkMIBGroups 5 }

hostGroup OBJECT-GROUP
        OBJECTS         { hostDescr, hostLuCnt, hostProtocol, hostMedia, 
			hostAdminState, hostState, hostStateLastChange,
			luDescr, luPoolName, luState, luStateLastChange }
        STATUS          current
        DESCRIPTION
                "A collection of objects related to a VRU host." 
        ::= { vruNetworkMIBGroups 6 }

componentGroup OBJECT-GROUP
        OBJECTS         { componentTypeName, componentIpAddress, componentState,
			componentStateLastChange }
        STATUS          current
        DESCRIPTION
                "A collection of objects related to components." 
        ::= { vruNetworkMIBGroups 7 }

componentNotificationsGroup NOTIFICATION-GROUP
	NOTIFICATIONS { notifyLineAppStateChg, notifySpanStateChg,
			notifyHostStateChg, notifyLuStateChg, notifyTopologyChg,
			notifyComponentStateChg, notifyAlarmByComponent }
	STATUS		deprecated
	DESCRIPTION
		"A collection of notifications related to the VPS/is network."
	::= { vruNetworkMIBGroups 8 }

componentEventsGroup OBJECT-GROUP
	OBJECTS		{ evObjectId, evChange,
			alrmLogMax, alrmLogNumber, alrmLogSeverity, alrmLogCode,
			alrmLogLineId, alrmLogHostId, alrmLogProcName,
			alrmLogMessage, alrmLogTime, alrmLogComponentType,
			alrmLogComponentId }
	STATUS		deprecated
	DESCRIPTION
		"A collection of objects related to a VRU."
	::= { vruNetworkMIBGroups 9 }

componentNotificationsGroup2 NOTIFICATION-GROUP
	NOTIFICATIONS { notifyLineAppStateChg, notifySpanStateChg,
			notifyHostStateChg, notifyLuStateChg, notifyTopologyChg,
			notifyComponentStateChg, notifyAlarmByComponentEx }
	STATUS		current
	DESCRIPTION
		"A collection of notifications related to the VPS/is network."
	::= { vruNetworkMIBGroups 10 }

componentEventsGroup2 OBJECT-GROUP
	OBJECTS		{ evObjectId, evChange,
			alrmLogMax, alrmLogNumber, alrmLogSeverity, alrmLogCode,
			alrmLogLineId, alrmLogHostId, alrmLogProcName,
			alrmLogMessage, alrmLogTime, alrmLogComponentType,
			alrmLogComponentId, alrmLogComponentIpAddress }
	STATUS		current
	DESCRIPTION
		"A collection of objects related to a VRU."
	::= { vruNetworkMIBGroups 11 }

--
-- VRU Events Subtree 
--

vruEvents	OBJECT IDENTIFIER ::= { vruNetwork 2 } 

--
-- VRU Events Variables Subtree
--
-- Defines variables that may be included within an VRU Network trap.  These
-- object ID's cannot be retrieved from the SNMP Agent.  Defining them here
-- serves as documentation for the contents of NMS traps.
---

vruEventVars OBJECT IDENTIFIER ::= { vruEvents 1 }

evObjectId OBJECT-TYPE
	SYNTAX		OBJECT IDENTIFIER
	MAX-ACCESS	accessible-for-notify
	STATUS		current
	DESCRIPTION
		"Object identifier associated with the source of the trap.  This
		object can not be retrieved from the SNMP agent."
	::= { vruEventVars 1 }

evChange OBJECT-TYPE
	SYNTAX		INTEGER {
		other(1),
		add(2),
		del(3),
		mod(4)
	}
	MAX-ACCESS	accessible-for-notify
	STATUS		current
	DESCRIPTION
		"Describes the type of change which just occurred.  This object
		can not be retrieved from the SNMP agent."
	::= { vruEventVars 2 }

--
-- Events Group Notifications Subtree
--
-- Defines traps that are sent to Network Management Stations.
--

vruNotifications OBJECT IDENTIFIER ::= { vruEvents 2 }

notifyAlarm NOTIFICATION-TYPE
	OBJECTS		{ alrmLogSeverity, alrmLogCode, alrmLogVruId,
			alrmLogLineId, alrmLogHostId, alrmLogProcName,
			alrmLogMessage, alrmLogTime }
	STATUS		deprecated
	DESCRIPTION
		"When a exceptional condition occurs the VRU system will
		generate an alarm.  This trap forwards these alarms to the
		Network Management Station.
	
		**NOTE: this trap is deprecated and replaced by
		notifyAlarmByComponent trap"
	::= { vruNotifications 1 }

notifyVruStateChg NOTIFICATION-TYPE
	OBJECTS		{ vruState }
	STATUS		deprecated
	DESCRIPTION
		"This trap is forwarded to the Network Management Station when
		the VRU changes its state.

		**NOTE: this trap is deprecated and replaced by the
		notifyComponentStateChg trap."
	::= { vruNotifications 2 }

notifyLineAppStateChg NOTIFICATION-TYPE
	OBJECTS		{ lineAppState, lineAppName, lineAppOverlay }
	STATUS		current
	DESCRIPTION
		"This trap is forwarded to the Network Management Station when
		a application attached to a VRU line changes its state."
	::= { vruNotifications 3 }

notifySpanStateChg NOTIFICATION-TYPE
	OBJECTS		{ spanState }
	STATUS		current
	DESCRIPTION
		"This trap is forwarded to the Network Management Station
		when a VRU span changes its state."
	::= { vruNotifications 4 }

notifyHostStateChg NOTIFICATION-TYPE
	OBJECTS		{ hostState }
	STATUS		current
	DESCRIPTION
		"This trap is forwarded to the Network Management Station
		when a VRU host changes its state."
	::= { vruNotifications 5 }

notifyLuStateChg NOTIFICATION-TYPE
	OBJECTS		{ luState }
	STATUS		current
	DESCRIPTION
		"This trap is forwarded to the Network Management Station
		when a VRU host lu changes its state."
	::= { vruNotifications 6 }

notifyTopologyChg NOTIFICATION-TYPE
        OBJECTS         { evObjectId, evChange }
        STATUS          current
        DESCRIPTION
                "This trap is forwarded to the Network Management Station
                when a VRU Network object topology status has changed."
        ::= { vruNotifications 7 }

notifyComponentStateChg NOTIFICATION-TYPE
	OBJECTS		{ componentState }
	STATUS		current
	DESCRIPTION
		"This trap is forwarded to the Network Management Station 
		when a VRU Network component changes its state."
	::= { vruNotifications 8 }

notifyAlarmByComponent NOTIFICATION-TYPE
	OBJECTS		{ alrmLogComponentType, alrmLogComponentId,
			  alrmLogSeverity, alrmLogCode, alrmLogLineId, 
			  alrmLogHostId, alrmLogProcName, alrmLogMessage,
			  alrmLogTime }
	STATUS		deprecated
	DESCRIPTION
		"When a exceptional condition occurs the VPS/is network
		a component will generate an alarm.  This trap forwards these
		these alarms to the Network Management Station.

		**NOTE: this trap is deprecated and replaced by the
		notifyAlarmByComponentEx trap."
	::= { vruNotifications 9 }

notifyAlarmByComponentEx NOTIFICATION-TYPE
	OBJECTS		{ alrmLogComponentType, alrmLogComponentId,
			  alrmLogSeverity, alrmLogCode, alrmLogLineId, 
			  alrmLogHostId, alrmLogProcName, alrmLogMessage,
			  alrmLogTime, alrmLogComponentIpAddress }
	STATUS		current
	DESCRIPTION
		"When a exceptional condition occurs the VPS/is network
		a component will generate an alarm.  This trap forwards these
		these alarms to the Network Management Station.  This is an
		extended version of notifyAlarmByComponent and includes 
		the IP address of the component generating the alarm."
	::= { vruNotifications 10 }


--
-- Component Events Alarms Subtree
--
-- Defines what component alarms are recorded and for how long
--

alarms OBJECT IDENTIFIER ::= { vruEvents 3 }

-- NOTE that the objects alrmFilterNumber, alrmFilterTbl, and
-- alrmLogPeriod will not be included in our initial MIB definition
-- and agent implementation.
--
-- They will just be described here and their object identifier are reserved
-- for when they are included in the implementation.
-- 
-- These object will allows us to define a way to filter out the number of
-- alarms which are forwarded to the Network Mangers.  By allowing this we will
-- decrease the amount of traffic created by traps.
--
-- alrmFilterNumber OBJECT-TYPE
--	SYNTAX		INTEGER
--	MAX-ACCESS	read-only
--	STATUS		current
--	DESCRIPTION
--		"The number alarm filter definitions currently defined."
--	::= { alarms 1 }
--
-- alrmFilterTable OBJECT-TYPE
--	SYNTAX		SEQUENCE OF AlrmFilterTable
--	MAX-ACCESS	notaccessible
--	STATUS		current
--	DESCRIPTION
--		"A list of alarm filter definitions.  The number of entries
--		is given by the value of alrmPropFilterNumber."
--	::= { alarms 2 }
--
-- alrmLogPeriod OBJECT-TYPE
--	SYNTAX		INTEGER
--	MAX-ACCESS	read-only
--	STATUS		current
--	DESCRIPTION
--		"Rate at which the agent should send alarms as traps regardless
--		of how often the alarms are generated.  A value of 0 indicates
--		send it immediately."
--	::= { alarms 3 }

alrmLogMax OBJECT-TYPE
	SYNTAX		INTEGER (1..2147483647)
	MAX-ACCESS	read-only
	STATUS		current
	DESCRIPTION
		"Specifies the maximum number of alarms that may be logged in
		the alarm log table at once.  When alrmLogNumber is equivalent
		to alrmLogMax, the first alarm in the table will be removed
		when the next alarm is added."
	::= { alarms 4 }

alrmLogNumber OBJECT-TYPE
	SYNTAX		INTEGER (1..2147483647)
	MAX-ACCESS	read-only
	STATUS		current
	DESCRIPTION
		"The number of log entries currently defined."
	::= { alarms 5 }

alrmLogTable OBJECT-TYPE
	SYNTAX SEQUENCE OF AlrmLogTableEntry
	MAX-ACCESS	not-accessible
	STATUS		current
	DESCRIPTION
		"A list of alarm entries.  The number of entries is given by
		alrmLogNumber.  This list could be thought of as a queue.
		When the comonent generates an alarm, it is added to the end
		of the list.  If the number of entries reaches alrmLogMax than
		the first entry will be deleted before a new one is added."
	::= { alarms 6 }

alrmLogTableEntry OBJECT-TYPE
	SYNTAX		AlrmLogTableEntry
	MAX-ACCESS	not-accessible
	STATUS		current
	DESCRIPTION
		"An alarm entry containing objects that describe that alarm."
	INDEX { alrmLogIdx }
	::= { alrmLogTable 1 }

AlrmLogTableEntry ::= SEQUENCE {
		alrmLogIdx			INTEGER,
		alrmLogSeverity			INTEGER,
		alrmLogCode			INTEGER, 
		alrmLogVruId			INTEGER,
		alrmLogLineId			INTEGER,
		alrmLogHostId			INTEGER,
		alrmLogProcName			DisplayString,
		alrmLogMessage			DisplayString,
		alrmLogTime			DateAndTime,
		alrmLogComponentType		INTEGER,
		alrmLogComponentId		INTEGER,
		alrmLogComponentIpAddress	IpAddress
	}

alrmLogIdx OBJECT-TYPE
	SYNTAX		INTEGER (1..2147483647)
	MAX-ACCESS	not-accessible
	STATUS		current
	DESCRIPTION
		"Index into the alarm log table between one and alrmLogNumber."
	::= { alrmLogTableEntry 1 }

alrmLogSeverity OBJECT-TYPE
	SYNTAX		INTEGER (0..9)
	MAX-ACCESS	read-only
	STATUS		current
	DESCRIPTION
		"Integer describing how severe this alarm is.  The lower the
		value, the lower the severity.  A severity value of 0
		indicates that no severity has been assigned to this alarm."
	::= { alrmLogTableEntry 2 }

alrmLogCode OBJECT-TYPE
	SYNTAX		INTEGER (0..2147483647)
	MAX-ACCESS	read-only
	STATUS		current
	DESCRIPTION
		"Code assigned to identify this alarm."
	::= { alrmLogTableEntry 3 }

alrmLogVruId OBJECT-TYPE
	SYNTAX		INTEGER (0..2147483647)
	MAX-ACCESS	read-only
	STATUS		deprecated
	DESCRIPTION
		"VRU identifier which generated this alarm.  A value of 0 is
		used to indicate no VRU is associated with this alarm.

		**NOTE: this object is deprecated and has been replaced by 
		alrmLogComponentId object."
	::= { alrmLogTableEntry 4 }

alrmLogLineId OBJECT-TYPE
	SYNTAX		INTEGER (0..2147483647)
	MAX-ACCESS	read-only
	STATUS		current
	DESCRIPTION
		"The phone line number associated with this alarm.  A value of
		0 indicates no phone line."
	::= { alrmLogTableEntry 5 }

alrmLogHostId OBJECT-TYPE
	SYNTAX		INTEGER (0..2147483647)
	MAX-ACCESS	read-only
	STATUS		current
	DESCRIPTION
		"The host identifier associated with this alarm.  A value of
		0 indicates that no host is associated with this alarm."
	::= { alrmLogTableEntry 6 }

alrmLogProcName OBJECT-TYPE
	SYNTAX		DisplayString
	MAX-ACCESS	read-only
	STATUS		current
	DESCRIPTION
		"The name of the process that generated this alarm."
	::= { alrmLogTableEntry 7 }

alrmLogMessage OBJECT-TYPE
	SYNTAX		DisplayString
	MAX-ACCESS	read-only
	STATUS		current
	DESCRIPTION
		"A message describing the alarm that occurred."
	::= { alrmLogTableEntry 8 }

alrmLogTime OBJECT-TYPE
	SYNTAX		DateAndTime
	MAX-ACCESS	read-only
	STATUS		current
	DESCRIPTION
		"The time that this alarm was generated."
	::= { alrmLogTableEntry 9 }

alrmLogComponentType OBJECT-TYPE
	SYNTAX		INTEGER (0..2147483647)
	MAX-ACCESS	read-only
	STATUS		current
	DESCRIPTION
		"Component type of the VPS/is component which generated this
		alarm."
	::= { alrmLogTableEntry 10 }

alrmLogComponentId OBJECT-TYPE
	SYNTAX		INTEGER (0..2147483647)
	MAX-ACCESS	read-only
	STATUS		current
	DESCRIPTION
		"Component identifier of the VPS/is component which generated
		this alarm."
	::= { alrmLogTableEntry 11 }

alrmLogComponentIpAddress OBJECT-TYPE
	SYNTAX		IpAddress
	MAX-ACCESS	read-only
	STATUS		current
	DESCRIPTION
		"Component IP address of the VPS/is component which generated
		this alarm."
	::= { alrmLogTableEntry 12 }

--
-- VRU Subtree
--


vruTable OBJECT-TYPE
	SYNTAX SEQUENCE OF VruTableEntry
	MAX-ACCESS	not-accessible
	STATUS		current
	DESCRIPTION
		"All Voice Response Units(VRU) a agent knows about"
	::= { vruNetwork 3 }


vruTableEntry OBJECT-TYPE
	SYNTAX		VruTableEntry
	MAX-ACCESS	not-accessible
	STATUS		current
	DESCRIPTION
		"A (conceptual) row entry for one VRU."
	INDEX { vruId }
	::= { vruTable 1 }


VruTableEntry ::= SEQUENCE {
		vruId			INTEGER,
		vruIpAddress		IpAddress,
		vruDescr		DisplayString,
		vruLineCnt		INTEGER,
		vruSpanCnt		INTEGER,
		vruHostCnt		INTEGER,
		vruAdminState		INTEGER,
		vruState		INTEGER,
		vruStateLastChange	DateAndTime
	}


vruId OBJECT-TYPE
	SYNTAX		INTEGER (1..2147483647)
	MAX-ACCESS	not-accessible
	STATUS		current
	DESCRIPTION
		"The VRU number associated with this VRU entity.  Note
		that is a unique number within VRU network."
	::= { vruTableEntry 1 }


vruIpAddress OBJECT-TYPE
	SYNTAX		IpAddress
	MAX-ACCESS	read-only
	STATUS		current
	DESCRIPTION
		"VRU network ip address."
	::= { vruTableEntry 2 }


vruDescr OBJECT-TYPE
	SYNTAX		DisplayString
	MAX-ACCESS	read-write
	STATUS		current
	DESCRIPTION
		"A textual description of this VRU entity.  It is mandatory
		that this contain only printable ASCII characters."
	::= { vruTableEntry 3 }

vruLineCnt OBJECT-TYPE
        SYNTAX          INTEGER (0..2147483647)
        MAX-ACCESS      read-only
        STATUS          current
        DESCRIPTION
                "Number of physical phone lines on this system."
        ::= { vruTableEntry 4 }

vruSpanCnt OBJECT-TYPE
        SYNTAX          INTEGER (0..2147483647)
        MAX-ACCESS      read-only
        STATUS          current
        DESCRIPTION
                "Number of spans on this system.  This also indicates the 
		number of rows in the spanTable(4) for this VRU."
        ::= { vruTableEntry 5 }

vruHostCnt OBJECT-TYPE
        SYNTAX          INTEGER (0..2147483647)
        MAX-ACCESS      read-only
        STATUS          current
        DESCRIPTION
                "Number of hosts defined for this system.  This also indicates
                the number of rows in the hostTable(6) for this VRU."
        ::= { vruTableEntry 6 }

vruAdminState OBJECT-TYPE
	SYNTAX		INTEGER {
				other(1),
				startup(2),
				shutdown(3),
				recycle(4),
				selftest(5),
				checkpoint(6)	-- save any dynamic info to disk
			}
	MAX-ACCESS	read-write
	STATUS		current
	DESCRIPTION
		"The network managers desired state of this VRU entity."
	::= { vruTableEntry 7 }


vruState OBJECT-TYPE
	SYNTAX		INTEGER {
				other(1),
				unknown(2),
				init(3),
				up(4),
				down(5),
				selftest(6)
			}
	MAX-ACCESS	read-only
	STATUS		current
	DESCRIPTION
		"The current status of the VRU entity."
	::= { vruTableEntry 8 }


vruStateLastChange OBJECT-TYPE
	SYNTAX		DateAndTime
	MAX-ACCESS	read-only
	STATUS		current
	DESCRIPTION
		"Date and time that this VRU entity changed its state."
	::= { vruTableEntry 9 }

--
-- Line Subtree
--

lineTable OBJECT-TYPE
	SYNTAX SEQUENCE OF LineTableEntry
	MAX-ACCESS	not-accessible
	STATUS		current
	DESCRIPTION
		"All physical and logical lines that are attached to a 
		Voice Response Units(VRU)."
	::= { vruNetwork 4 }

lineTableEntry OBJECT-TYPE
	SYNTAX		LineTableEntry
	MAX-ACCESS	not-accessible
	STATUS		current
	DESCRIPTION
		"A (conceptual) entry for one physical/logical line."
	INDEX { lineVruId, lineId }
	::= { lineTable 1 }

LineTableEntry ::= SEQUENCE {
		lineVruId		INTEGER,
		lineId			INTEGER,
		lineType		INTEGER,
		lineProtocol		INTEGER,
		lineState		INTEGER,
		lineAppName		DisplayString,
		lineAppOverlay		DisplayString,
		lineAppAdminState	INTEGER,
		lineAppState		INTEGER,
		lineAppStateLastChange	DateAndTime,
		lineAppCfgLastChange	DateAndTime
	}

lineVruId OBJECT-TYPE
	SYNTAX		INTEGER (1..2147483647)
	MAX-ACCESS	not-accessible
	STATUS		current
	DESCRIPTION
		"The VRU identifier that this phone line is associated with."
	::= { lineTableEntry 1 }

lineId OBJECT-TYPE
	SYNTAX		INTEGER (1..2147483647)
	MAX-ACCESS	not-accessible
	STATUS		current
	DESCRIPTION
		"The line number of this phone line.  This number is unique
		for each VRU."
	::= { lineTableEntry 2 }

lineType OBJECT-TYPE
	SYNTAX		INTEGER {
				other(1),
				unknown(2),
				virtual(3),
				analog(4),
				digital(5)
			}
	MAX-ACCESS	read-only
	STATUS		current
	DESCRIPTION
		"Specifies whether this line is a logical(3) or a physical(4)
		phone line.  A line type of unknown(2) indicates that we cant
		determine the line type at this moment."
	::= { lineTableEntry 3 }

lineProtocol OBJECT-TYPE
	SYNTAX		INTEGER (1..2147483647)
	MAX-ACCESS	read-only
	STATUS		current
	DESCRIPTION
		"A value which indicates the set of protocols this phone line
		offers.  The value is a sum.  This value initially takes the
		value of zero which indicates that the protocol is unknown.
		Then for each protocol that this line supports, its protocol
		value is added to the sum.

			Value	Functionality
			0x00001	Uses some other type of protocol
			0x00002	Some analog protocol
			0x00004	AT&T Bell release
			0x00008	British Paging (BTUK/MCP)
			0x00010	Channel bank with 2 wire option
			0x00020	Channel bank with 2 wire FXOR else FXO
			0x00040	Channel bank with 4 wire E&M
			0x00080	Channel bank FSX[r] else FXO[R]
			0x00100	Channel bank loop start else ground
			0x00200	Channel bank standard access
			0x00400	Common channel signalling (SS7)
			0x00800	Galaxy 5/2 ACD
			0x01000	ISDN
			0x02000	Loop hangup supervision
			0x04000	Mercury CAS signalling
			0x08000	Network side protocol
			0x10000	R1 signaling system
			0x20000	R2 signaling with DTMF outdial
			0x40000	R2 signaling system
			"
	::= { lineTableEntry 4 }

lineState OBJECT-TYPE
	SYNTAX		INTEGER {
				other(1),
				unknown(2),
				connected(3),
				idle(4),
				busy(5),
				referral(6),
				down(7)
			}
	MAX-ACCESS	read-only
	STATUS		current
	DESCRIPTION
		"Current state of this line.  The line may be currently
		servicing a call (connected), in service but not in a call
		service or referral state (idle), not in service nor
		down (busy), referral (referral), or down (down).  If
		we are unable to connect to the VRU than the line state will 
		be unknown (unknown).  A logical line line state will always
		be unknown."
	::= { lineTableEntry 5 }

lineAppName OBJECT-TYPE
	SYNTAX		DisplayString
	MAX-ACCESS	read-write
	STATUS		current
	DESCRIPTION
		"The name of the  application that is currently assigned to
		this line.  Any response PDU on this object will return the
		name of the application assigned to this line.  If there is
		no application assigned to this line, a 0 length string is
		returned.

		Assigning a new application to this line is achieved by
		setting lineAppAdminState to assign and this object to the
		applications name."
	::= { lineTableEntry 6 }

lineAppOverlay OBJECT-TYPE
	SYNTAX		DisplayString
	MAX-ACCESS	read-only
	STATUS		current
	DESCRIPTION
		"The name of the  application that has been linked to this 
		line."
	::= { lineTableEntry 7 }

lineAppAdminState OBJECT-TYPE
	SYNTAX		INTEGER {
				other(1),
				startapp(2),
				softterm(3),
				hardterm(4),
				assign(5),
				unassign(6),
				hardrestart(7),
				softrestart(8)
			}
	MAX-ACCESS	read-write
	STATUS		current
	DESCRIPTION
		"Desired state that Network Manager wants the application in."
	::= { lineTableEntry 8 }

lineAppState OBJECT-TYPE
	SYNTAX		INTEGER {
				other(1),
				unknown(2),
				noapp(3),
				init(4),
				up(5),
				down(6),
				config(7),
				exit(8)
			}
	MAX-ACCESS	read-only
	STATUS		current
	DESCRIPTION
		"Current state of the  application that is assigned to this
		logical line.  If no  applications are assigned this entry will
		be noapp(3)"
	::= { lineTableEntry 9 }

lineAppStateLastChange OBJECT-TYPE
	SYNTAX		DateAndTime
	MAX-ACCESS	read-only
	STATUS		current
	DESCRIPTION
		"Date and time that the current application assigned to this 
		line last changed its state."
	::= { lineTableEntry 10 }

lineAppCfgLastChange OBJECT-TYPE
	SYNTAX		DateAndTime
	MAX-ACCESS	read-only
	STATUS		current
	DESCRIPTION
		"Date and time of last application configure or unconfigure
		on this line."
 
	::= { lineTableEntry 11 }


---
--- Span Table
---

spanTable OBJECT-TYPE
	SYNTAX SEQUENCE OF SpanTableEntry
	MAX-ACCESS      not-accessible
	STATUS          current
	DESCRIPTION
		"All spans which are attached to a Voice Response Unit (VRU)."
	::= { vruNetwork 5 }

spanTableEntry OBJECT-TYPE
	SYNTAX          SpanTableEntry
	MAX-ACCESS      not-accessible
	STATUS          current
	DESCRIPTION
		"A (conceptual) entry for one span."
	INDEX { spanVruId, spanId }
	::= { spanTable 1 }

SpanTableEntry ::= SEQUENCE {
		spanVruId		INTEGER,
		spanId			INTEGER,
		spanLineIdStart		INTEGER,
		spanLineNumber		INTEGER,
		spanEnabled		TruthValue,
		spanState		INTEGER,
		spanStateLastChange	DateAndTime
        }

spanVruId OBJECT-TYPE
	SYNTAX		INTEGER (1..2147483647)
	MAX-ACCESS	not-accessible
	STATUS		current
	DESCRIPTION
		"VRU identifier that this span is associated with."
	::= { spanTableEntry 1 }

spanId OBJECT-TYPE
	SYNTAX		INTEGER (1..2147483647)
	MAX-ACCESS	not-accessible
	STATUS		current
	DESCRIPTION
		"Identifier of this span."
	::= { spanTableEntry 2 }

spanLineIdStart OBJECT-TYPE
	SYNTAX		INTEGER (1..2147483647)
	MAX-ACCESS	read-only
	STATUS		current
	DESCRIPTION
		"Line id of the first line in this span."
	::= { spanTableEntry 3 }

spanLineNumber OBJECT-TYPE
	SYNTAX		INTEGER {
		europaLineNumber(30),
		usaLineNumber(24)
	}
	MAX-ACCESS	read-only
	STATUS		current
	DESCRIPTION
		"Number of lines in this span."
	::= { spanTableEntry 4 }

spanEnabled OBJECT-TYPE
	SYNTAX		TruthValue
	MAX-ACCESS	read-only
	STATUS		current
	DESCRIPTION
		"Indicates whether span is enabled or disabled.  A value of 
		true(1) indicates span is enabled and a value of false(2)
		indicates span is disabled."
	::= { spanTableEntry 5 }

spanState OBJECT-TYPE
	SYNTAX		INTEGER {
		other(1),
		unknown(2),	-- span state can not be determined
		init(3),	-- span is in an initial state
		green(4),	-- span is online and ready
		fatal(5),	-- span entered failed signal state
		yellow(6),	-- span is in yellow state
		red(7)		-- span is in red state
	}
	MAX-ACCESS	read-only
	STATUS		current
	DESCRIPTION
		"Current state of this span."
	::= { spanTableEntry 6 }

spanStateLastChange OBJECT-TYPE
	SYNTAX		DateAndTime
	MAX-ACCESS	read-only
	STATUS		current
	DESCRIPTION
		"Date and time that the span last changed its state."
	::= { spanTableEntry 7 }


--
-- Applications Subtree
--

appTable OBJECT-TYPE
	SYNTAX SEQUENCE OF AppTableEntry
	MAX-ACCESS	not-accessible
	STATUS		current
	DESCRIPTION
		"All applications that VRU currently knows about."
	::= { vruNetwork 6 }

appTableEntry OBJECT-TYPE
	SYNTAX		AppTableEntry
	MAX-ACCESS	not-accessible
	STATUS		current
	DESCRIPTION
		"A (conceptual) entry for one VRU application"
	INDEX { appVruId, IMPLIED appName }
	::= { appTable 1 }

AppTableEntry ::= SEQUENCE {
		appVruId	INTEGER,
		appName		DisplayString,
		appDescr	DisplayString,
		appOptions	DisplayString,
		appLineCnt	INTEGER
	}

appVruId OBJECT-TYPE
	SYNTAX		INTEGER(1..2147483647)
	MAX-ACCESS	not-accessible
	STATUS		current	
	DESCRIPTION
		"VRU id that this  application has been assigned to."
	::= { appTableEntry 1 }

appName OBJECT-TYPE
	SYNTAX		DisplayString ( SIZE(1..255) )
	MAX-ACCESS	not-accessible
	STATUS		current	
	DESCRIPTION
		"The name of the application that can been assigned to a
		line.  This name must be unique for each VRU"
	::= { appTableEntry 2 }

appDescr OBJECT-TYPE
	SYNTAX		DisplayString
	MAX-ACCESS	read-write
	STATUS		current	
	DESCRIPTION
		"A textual description of this application.  It is mandatory
		that this contain only printable ASCII characters."
	::= { appTableEntry 3 }

appOptions OBJECT-TYPE
	SYNTAX		DisplayString
	MAX-ACCESS	read-only
	STATUS		current
	DESCRIPTION
		"The options that are needed during this applications startup."
	::= { appTableEntry 4 }

appLineCnt OBJECT-TYPE
	SYNTAX		INTEGER(0..2147483647)
	MAX-ACCESS	read-only
	STATUS		current	
	DESCRIPTION
		"The number of lines that this  application is assigned to."
	::= { appTableEntry 5 }

--
-- Applications Stats Subtree
--

appStatsTable OBJECT-TYPE
	SYNTAX SEQUENCE OF AppStatsTableEntry
	MAX-ACCESS	not-accessible
	STATUS		current
	DESCRIPTION
		"All application specific stats that have been collected."
	::= { vruNetwork 7 }

appStatsTableEntry OBJECT-TYPE
	SYNTAX		AppStatsTableEntry
	MAX-ACCESS	not-accessible
	STATUS		current
	DESCRIPTION
		"A (conceptual) entry for one application stat"
	INDEX { appStatsVruId, IMPLIED appStatsName }
	::= { appStatsTable 1 }

AppStatsTableEntry ::= SEQUENCE {
	appStatsVruId		INTEGER,
	appStatsName		DisplayString,
	appStatsValue		INTEGER,
	appStatsLastChange	DateAndTime
}

appStatsVruId OBJECT-TYPE
	SYNTAX		INTEGER (1..2147483647)
	MAX-ACCESS      not-accessible
	STATUS          current
	DESCRIPTION
		"The VRU identifier that this application statistic is 
		associated with."
::= { appStatsTableEntry 1 }

appStatsName OBJECT-TYPE
	SYNTAX		DisplayString ( SIZE(1..255) )
	MAX-ACCESS      not-accessible
	STATUS          current
	DESCRIPTION
		"Name which identifies this application stat."
::= { appStatsTableEntry 2 }

appStatsValue OBJECT-TYPE
	SYNTAX		INTEGER (1..2147483647)
	MAX-ACCESS 	read-only
	STATUS          current
	DESCRIPTION
		"An application stats value.  This value is gathered on 
		15 minute intervals."
::= { appStatsTableEntry 3 }

appStatsLastChange OBJECT-TYPE
	SYNTAX		DateAndTime
	MAX-ACCESS 	read-only
	STATUS          current
	DESCRIPTION
		"Date and time when this application stat was recorded."
::= { appStatsTableEntry 4 }

--
-- Host Subtree
--

hostTable OBJECT-TYPE
	SYNTAX SEQUENCE OF HostTableEntry
	MAX-ACCESS	not-accessible
	STATUS          current
	DESCRIPTION
		"All hosts defined for a VRU."
	::= { vruNetwork 8 }

hostTableEntry OBJECT-TYPE
	SYNTAX          HostTableEntry
	MAX-ACCESS      not-accessible
	STATUS          current
	DESCRIPTION
		"A (conceptual) entry for one VRU host"
	INDEX { hostVruId, hostId }
	::= { hostTable 1 }

HostTableEntry ::= SEQUENCE {
		hostVruId		INTEGER,
		hostId			INTEGER,
		hostDescr		DisplayString,
		hostLuCnt		INTEGER,
		hostProtocol		INTEGER,
		hostMedia		INTEGER,
--		hostCardOID		OBJECT IDENTIFIER,
		hostAdminState		INTEGER,
		hostState		INTEGER,
		hostStateLastChange	DateAndTime
	}

hostVruId OBJECT-TYPE
	SYNTAX		INTEGER (1..2147483647)
	MAX-ACCESS	not-accessible
	STATUS		current
	DESCRIPTION
		"The VRU identifier that this host is associated with."
	::= { hostTableEntry 1 }

hostId OBJECT-TYPE
	SYNTAX		INTEGER (1..2147483647)
	MAX-ACCESS	not-accessible
	STATUS		current
	DESCRIPTION
		"Unique identifier associated with this host."
	::= { hostTableEntry 2 }

hostDescr OBJECT-TYPE
	SYNTAX		DisplayString
	MAX-ACCESS	read-write
	STATUS		current
	DESCRIPTION
		"A textual description of this host.  It is mandatory that
		this contain only printable ASCII characters."
	::= { hostTableEntry 3 }

hostLuCnt OBJECT-TYPE
	SYNTAX		INTEGER (0..2147483647)
	MAX-ACCESS	read-only
	STATUS		current
	DESCRIPTION
		"Number of lu's defined for this host.  This also indicates
		the number of rows in the luTable(7) for this host."
	::= { hostTableEntry 4 }

			
hostProtocol OBJECT-TYPE
	SYNTAX		INTEGER {
				other(1),
				unknown(2),
				atte(3),
				async(4),
				lu62(5),
				sna3270(6),
				sdlcexp(7),
				vpstn3270(8)
			}
	MAX-ACCESS	read-only
	STATUS		current
	DESCRIPTION
		"Protocol which is used for host communications."
	::= { hostTableEntry 5 }	

hostMedia OBJECT-TYPE
	SYNTAX		INTEGER {
				other(1),
				unknown(2),
				hardwarebased(3),
				softwarebased(4)
			}
	MAX-ACCESS	read-only
	STATUS		current
	DESCRIPTION
		"Media used for communicating with the host."
	::= { hostTableEntry 6 }	

--
-- NOTE that the object hostCardOID will not be included in our initial MIB
-- definition and agent implementation.  It will just be described here and
-- its object identifier will be reserved for when it is implemented.
--
--
--hostCardOId OBJECT-TYPE
--	SYNTAX		OBJECT IDENTIFIER
--	MAX-ACCESS	read-only
--	STATUS		current
--	DESCRIPTION
--		"Hardware id that this host is using for host communications."
--	::= { hostTableEntry 7 }	

hostAdminState OBJECT-TYPE
	SYNTAX		INTEGER {
				other(1),
				init(2),
				up(3),
				down(4),
				recycle(5),
				selftest(6)
			}
	MAX-ACCESS	read-write
	STATUS		current
	DESCRIPTION
		"Desired state that Network Manager wants the host in."
	::= { hostTableEntry 8 }	

hostState OBJECT-TYPE
	SYNTAX		INTEGER {
				other(1),
				unknown(2),
				init(3),
				up(4),
				down(5),
				selftest(6)
			}
	MAX-ACCESS	read-only
	STATUS		current
	DESCRIPTION
		"Current state of the host."
	::= { hostTableEntry 9 }

hostStateLastChange OBJECT-TYPE
	SYNTAX		DateAndTime
	MAX-ACCESS	read-only
	STATUS		current
	DESCRIPTION
		"Date and time this host last changed it state."
	::= { hostTableEntry 10 }

--
-- LU Subtree
--

luTable OBJECT-TYPE
	SYNTAX SEQUENCE OF LuTableEntry
	MAX-ACCESS      not-accessible
	STATUS		current
	DESCRIPTION
		"All logical units(LU) defined for hosts on a VRU."
	::= { vruNetwork 9 }

luTableEntry OBJECT-TYPE
	SYNTAX		LuTableEntry
	MAX-ACCESS	not-accessible
	STATUS		current
	DESCRIPTION
		"A (conceptual) entry for one LU"
	INDEX { luVruId, luHostId, luId }
	::= { luTable 1 }

LuTableEntry ::= SEQUENCE {
		luVruId			INTEGER,
		luHostId		INTEGER,
		luId			INTEGER,
		luDescr			DisplayString,
		luPoolName		DisplayString,
		luState			INTEGER,
		luStateLastChange	DateAndTime
	}

luVruId OBJECT-TYPE
	SYNTAX		INTEGER (1..2147483647)
	MAX-ACCESS	not-accessible
	STATUS		current
	DESCRIPTION
		"VRU entity that this LU is associated with."
	::= { luTableEntry 1 }

luHostId OBJECT-TYPE
	SYNTAX		INTEGER (1..2147483647)
	MAX-ACCESS	not-accessible
	STATUS		current
	DESCRIPTION
		"Host entity that this LU is associated with."
	::= { luTableEntry 2 }

luId OBJECT-TYPE
	SYNTAX		INTEGER (1..2147483647)
	MAX-ACCESS	not-accessible
	STATUS		current
	DESCRIPTION
		"LU identifier that is associated with this LU."
	::= { luTableEntry 3 }

luDescr OBJECT-TYPE
	SYNTAX		DisplayString
	MAX-ACCESS	read-only
	STATUS		current
	DESCRIPTION
		"A textual description of this LU.  It is mandatory that
		this contain only printable ASCII characters."
	::= { luTableEntry 4 }

luPoolName OBJECT-TYPE
	SYNTAX		DisplayString
	MAX-ACCESS	read-only
	STATUS		current
	DESCRIPTION
		"Pool name that this LU is assigned to."
	::= { luTableEntry 5 }

luState OBJECT-TYPE
	SYNTAX		INTEGER {
				other(1),
				unknown(2),
				init(3),
				up(4),
				down(5)
			}
	MAX-ACCESS	read-only
	STATUS		current
	DESCRIPTION
		"Current state of this LU."
	::= { luTableEntry 6 }

luStateLastChange OBJECT-TYPE
	SYNTAX		DateAndTime
	MAX-ACCESS	read-only
	STATUS		current
	DESCRIPTION
		"Date and time this lu last changed it state."
	::= { luTableEntry 7 }

--
-- Component Subtree
--

components	OBJECT IDENTIFIER ::= { vruNetwork 10 } 

--
-- Table of all defined component types
--

componentTypeTable OBJECT-TYPE
	SYNTAX SEQUENCE OF ComponentTypeTableEntry
	MAX-ACCESS	not-accessible
	STATUS		current
	DESCRIPTION
		"All defined component types."
	::= { components 1 }

componentTypeTableEntry OBJECT-TYPE
	SYNTAX		ComponentTypeTableEntry
	MAX-ACCESS	not-accessible
	STATUS		current
	DESCRIPTION
		"A (conceptual) entry for one component type."
	INDEX { componentTypeId }
	::= { componentTypeTable 1 }

ComponentTypeTableEntry ::= SEQUENCE {
	componentTypeId		INTEGER,
	componentTypeName	DisplayString
}

componentTypeId OBJECT-TYPE
	SYNTAX		INTEGER (1..2147483647)
	MAX-ACCESS	not-accessible
	STATUS		current
	DESCRIPTION
		"Identifier for this component type."
	::= { componentTypeTableEntry 1 }

componentTypeName OBJECT-TYPE
	SYNTAX		DisplayString
	MAX-ACCESS	read-only
	STATUS		current
	DESCRIPTION
		"Name of this component type."
	::= { componentTypeTableEntry 2 }

--
-- Table of all defined subcomponent types
--
-- NOTE subcomponents are currently not included in the MIB definition.
-- The subcomponent table will just be described here and their OID is
-- reserved so it may be added in the future.
--
-- subcomponentTypeTable OBJECT-TYPE
--	SYNTAX SEQUENCE OF SubcomponentTypeTableEntry
--	MAX-ACCESS	not-accessible
--	STATUS		current
--	DESCRIPTION
--		"All defined subcomponent types."
--	::= { components 2 }
--

--
-- Table of all components an agent knows about
--

componentTable OBJECT-TYPE
	SYNTAX SEQUENCE OF ComponentTableEntry
	MAX-ACCESS	not-accessible
	STATUS		current
	DESCRIPTION
		"All components found in the system."
	::= { components 3 }

componentTableEntry OBJECT-TYPE
	SYNTAX		ComponentTableEntry
	MAX-ACCESS	not-accessible
	STATUS		current
	DESCRIPTION
		"A (conceptual) entry for one component."
	INDEX { componentType, componentId }
	::= { componentTable 1 }

ComponentTableEntry ::= SEQUENCE {
		componentType			INTEGER,
		componentId			INTEGER,
		componentIpAddress		IpAddress,
		componentState			INTEGER,
		componentStateLastChange	DateAndTime
	}

componentType OBJECT-TYPE
	SYNTAX		INTEGER (1..2147483647)
	MAX-ACCESS	not-accessible
	STATUS		current
	DESCRIPTION
		"Type of this component."
	::= { componentTableEntry 1 }

componentId OBJECT-TYPE
	SYNTAX		INTEGER (1..2147483647)
	MAX-ACCESS	not-accessible
	STATUS		current
	DESCRIPTION
		"Identifier of this component."
	::= { componentTableEntry 2 }

componentIpAddress OBJECT-TYPE
	SYNTAX		IpAddress
	MAX-ACCESS	read-only
	STATUS		current
	DESCRIPTION
		"IP address of this component."
	::= { componentTableEntry 3 }

componentState OBJECT-TYPE
	SYNTAX		INTEGER {
				other(1),
				unknown(2),
				init(3),
				up(4),
				down(5)
			}
	MAX-ACCESS	read-only
	STATUS		current
	DESCRIPTION
		"Current state of this component."
	::= { componentTableEntry 4 }

componentStateLastChange OBJECT-TYPE
	SYNTAX		DateAndTime
	MAX-ACCESS	read-only
	STATUS		current
	DESCRIPTION
		"Date and time this component last changed its state."
	::= { componentTableEntry 5 }

END
