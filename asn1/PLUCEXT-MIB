PLUCEXT-MIB 

   --FORCE-INCLUDE <mib.h>
   --FORCE-INCLUDE <snmpdefs.h>
   --FORCE-INCLUDE <snmpstat.h>
   --FORCE-INCLUDE "mibproto.h"
 
	DEFINITIONS ::= BEGIN

	IMPORTS
		MODULE-IDENTITY, OBJECT-TYPE, IpAddress, Integer32
			FROM SNMPv2-SMI
		plucExt
			FROM APENT-MIB;

--PLUCEXT MIB

    apPlucExtMib MODULE-IDENTITY
	   LAST-UPDATED "9707202000Z" -- Wed July 20 20:00:00 EST 1997
	   ORGANIZATION "ArrowPoint Communications Inc."
	   CONTACT-INFO
	   "                Customer Support
	   Postal:          ArrowPoint Communications, Inc.
				  		50 Nagog Park
				  		Acton, Massachusetts 01720
	   Tel:             +1 978 206 3000
	   E-Mail:          mibsupport@arrowpoint.com"
       DESCRIPTION
	  "The MIB module used to describe the ArrowPoint Communications 
       Proximity Lookup Client functionality."
      ::= { plucExt 1}

--Proximity Lookup Scalars

apPlucCacheSize OBJECT-TYPE
	SYNTAX			Integer32 (0..48000)
	MAX-ACCESS		read-write
	STATUS			current
	DESCRIPTION
		"The number of entries supported by the proximity lookup cache"
	DEFVAL {16000}
	::= {plucExt 2}

--Proximity Lookup
apPlucCacheTable OBJECT-TYPE
	SYNTAX          SEQUENCE OF APPlucCacheEntry
	MAX-ACCESS      not-accessible
	STATUS          current
	DESCRIPTION
		"This table is used to expose the proximity lookup cache"
	::= { plucExt 3}


apPlucCacheEntry OBJECT-TYPE
	SYNTAX          APPlucCacheEntry
	MAX-ACCESS      not-accessible
	STATUS          current
	DESCRIPTION
		""
	INDEX   { apPlucCacheIpAddress, apPlucCacheIpPrefix }
	::= { apPlucCacheTable 1 }

APPlucCacheEntry ::= SEQUENCE {
		apPlucCacheIpAddress     IpAddress,
		apPlucCacheIpPrefix      Integer32,
		apPlucCacheTTL			 Integer32,
		apPlucCacheHits			 Integer32,
		apPlucCacheIndexCount	 Integer32
}

apPlucCacheIpAddress OBJECT-TYPE
	SYNTAX          IpAddress
    MAX-ACCESS      read-only
	STATUS          current
	DESCRIPTION     
			"The IP address associated with this cache entry"
	::= { apPlucCacheEntry 1}

apPlucCacheIpPrefix OBJECT-TYPE
	SYNTAX          Integer32
    MAX-ACCESS      read-only
	STATUS          current
	DESCRIPTION     
			"The IP prefix associated with this cache entry"
	::= { apPlucCacheEntry 2}

apPlucCacheTTL OBJECT-TYPE
	SYNTAX          Integer32
    MAX-ACCESS      read-only
	STATUS          current
	DESCRIPTION     
			"The TTL of this cache entry"
	::= { apPlucCacheEntry 3}

apPlucCacheHits OBJECT-TYPE
	SYNTAX          Integer32
    MAX-ACCESS      read-only
	STATUS          current
	DESCRIPTION     
			"The number of hits for this cache entry"
	::= { apPlucCacheEntry 4}

apPlucCacheIndexCount OBJECT-TYPE
	SYNTAX          Integer32
    MAX-ACCESS      read-only
	STATUS          current
	DESCRIPTION     
			"The number of metrics for this cache entry"
	::= { apPlucCacheEntry 5}


apPlucCacheIndexTable OBJECT-TYPE
	SYNTAX          SEQUENCE OF APPlucCacheIndexEntry
	MAX-ACCESS      not-accessible
	STATUS          current
	DESCRIPTION
		"This table is used to expose the proximity lookup cache Indexs"
	::= { plucExt 4}


apPlucCacheIndexEntry OBJECT-TYPE
	SYNTAX          APPlucCacheIndexEntry
	MAX-ACCESS      not-accessible
	STATUS          current
	DESCRIPTION
		""
	INDEX   { apPlucCacheIndexIpAddress, apPlucCacheIndexIpPrefix, apPlucCacheIndexZoneIndex }
	::= { apPlucCacheIndexTable 1 }

APPlucCacheIndexEntry ::= SEQUENCE {
		apPlucCacheIndexIpAddress  IpAddress,
		apPlucCacheIndexIpPrefix   Integer32,
		apPlucCacheIndexZoneIndex  Integer32,
		apPlucCacheIndexValue      Integer32
}

apPlucCacheIndexIpAddress OBJECT-TYPE
	SYNTAX          IpAddress
    MAX-ACCESS      read-only
	STATUS          current
	DESCRIPTION     
			"The IP address associated with this cache entry"
	::= { apPlucCacheIndexEntry 1}

apPlucCacheIndexIpPrefix OBJECT-TYPE
	SYNTAX          Integer32
    MAX-ACCESS      read-only
	STATUS          current
	DESCRIPTION     
			"The IP prefix associated with this cache entry"
	::= { apPlucCacheIndexEntry 2}

apPlucCacheIndexZoneIndex OBJECT-TYPE
	SYNTAX          Integer32
    MAX-ACCESS      read-only
	STATUS          current
	DESCRIPTION     
			"The zone index associated with this cache entry"
	::= { apPlucCacheIndexEntry 3}

apPlucCacheIndexValue OBJECT-TYPE
	SYNTAX          Integer32
    MAX-ACCESS      read-only
	STATUS          current
	DESCRIPTION     
			"The Index value associated with this cache entry"
	::= { apPlucCacheIndexEntry 4}


END
