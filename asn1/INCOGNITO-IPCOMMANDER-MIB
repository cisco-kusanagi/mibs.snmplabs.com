INCOGNITO-IPCOMMANDER-MIB DEFINITIONS ::= BEGIN

IMPORTS
	incognitoProducts
		FROM INCOGNITO-MIB
	MODULE-IDENTITY
		FROM SNMPv2-SMI;

incognitoIPCommander MODULE-IDENTITY
	LAST-UPDATED "200304151520Z"
	ORGANIZATION "Incognito Software Inc."
	CONTACT-INFO
		"Incognito Software Inc.
		Customer Service

		Postal:
		    1128 Hornby St.
		    Vancouver, BC, Canada
		    V6Z 2L4

		Tel: +1 604-688-4332
		Fax: +1 604-688-4339

		E-Mail: support@incognito.com"
	DESCRIPTION
		""
	::= { incognitoProducts 1 }


END
