--			Ascend mibalarm MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBALARM-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibalarmProfile  OBJECT IDENTIFIER ::= { configuration 33}

	-- The mibalarmProfile table
	--
	-- This table contains parameters for the mibalarmProfile profile
	--

    mibalarmProfileTable	OBJECT-TYPE
	SYNTAX		SEQUENCE OF MibalarmProfileEntry
	ACCESS		not-accessible
	STATUS		mandatory
	DESCRIPTION	"A list of mibalarmProfile profile entries."
	::= { mibalarmProfile 1 }

    mibalarmProfileEntry	OBJECT-TYPE
	SYNTAX		MibalarmProfileEntry
	ACCESS		not-accessible
	STATUS		mandatory
	DESCRIPTION	"A mibalarmProfile entry containing objects that
			 maps to the parameters of mibalarmProfile profile."
	INDEX		{ alarmProfile-Name }
	::= { mibalarmProfileTable 1 }

    MibalarmProfileEntry ::=
	SEQUENCE {
	    alarmProfile-Name
		DisplayString,
	    alarmProfile-Enabled
		INTEGER,
	    alarmProfile-Event
		INTEGER,
	    alarmProfile-PhysicalAddress-Shelf
		INTEGER,
	    alarmProfile-PhysicalAddress-Slot
		INTEGER,
	    alarmProfile-PhysicalAddress-ItemNumber
		INTEGER,
	    alarmProfile-Action-AlarmLedMinor
		INTEGER,
	    alarmProfile-Action-AlarmLedMajor
		INTEGER,
	    alarmProfile-Action-AlarmRelayMinor
		INTEGER,
	    alarmProfile-Action-AlarmRelayMinorDuration
		INTEGER,
	    alarmProfile-Action-AlarmRelayMajor
		INTEGER,
	    alarmProfile-Action-AlarmRelayMajorDuration
		INTEGER,
	    alarmProfile-Action-o
		INTEGER
	}

    alarmProfile-Name	OBJECT-TYPE
	SYNTAX	DisplayString
	ACCESS	read-only
	STATUS	mandatory
	DESCRIPTION	"The name consists of a null terminated ascii string supplied by the user"
	::= { mibalarmProfileEntry 1 }

    alarmProfile-Enabled	OBJECT-TYPE
	SYNTAX	INTEGER {
		    no (1),
		    yes (2)
		}
	ACCESS	read-write
	STATUS	mandatory
	DESCRIPTION	"TRUE if the alarm profile is enabled, otherwise FALSE."
	::= { mibalarmProfileEntry 2 }

    alarmProfile-Event	OBJECT-TYPE
	SYNTAX	INTEGER {
		    lineStateChange (1),
		    slotStateChange (2),
		    primarySwitchover (3),
		    powerFailure (4),
		    fanFailure (5),
		    secondaryControllerStateChange (6),
		    inputRelayClosed (7),
		    inputRelayOpen (8),
		    lowTemperatureTrigger (9),
		    highTemperatureTrigger (10),
		    dpramCbusFailure (11)
		}
	ACCESS	read-write
	STATUS	mandatory
	DESCRIPTION	"Alarm event type"
	::= { mibalarmProfileEntry 3 }

    alarmProfile-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibalarmProfileEntry 4 }

    alarmProfile-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibalarmProfileEntry 5 }

    alarmProfile-PhysicalAddress-ItemNumber	OBJECT-TYPE
	SYNTAX	INTEGER
	ACCESS	read-write
	STATUS	mandatory
	DESCRIPTION	"A number that specifies an addressable entity within the context of shelf and slot."
	::= { mibalarmProfileEntry 6 }

    alarmProfile-Action-AlarmLedMinor	OBJECT-TYPE
	SYNTAX	INTEGER {
		    off (1),
		    on (2)
		}
	ACCESS	read-write
	STATUS	mandatory
	DESCRIPTION	"The LED that indicates a minor alarm"
	::= { mibalarmProfileEntry 7 }

    alarmProfile-Action-AlarmLedMajor	OBJECT-TYPE
	SYNTAX	INTEGER {
		    off (1),
		    on (2)
		}
	ACCESS	read-write
	STATUS	mandatory
	DESCRIPTION	"The LED that indicates a major alarm"
	::= { mibalarmProfileEntry 8 }

    alarmProfile-Action-AlarmRelayMinor	OBJECT-TYPE
	SYNTAX	INTEGER {
		    off (1),
		    on (2)
		}
	ACCESS	read-write
	STATUS	mandatory
	DESCRIPTION	"The relay that is set for a minor alarm"
	::= { mibalarmProfileEntry 9 }

    alarmProfile-Action-AlarmRelayMinorDuration	OBJECT-TYPE
	SYNTAX	INTEGER
	ACCESS	read-write
	STATUS	mandatory
	DESCRIPTION	"The duration in seconds for which the minor relay is set"
	::= { mibalarmProfileEntry 10 }

    alarmProfile-Action-AlarmRelayMajor	OBJECT-TYPE
	SYNTAX	INTEGER {
		    off (1),
		    on (2)
		}
	ACCESS	read-write
	STATUS	mandatory
	DESCRIPTION	"The relay that is set for a major alarm"
	::= { mibalarmProfileEntry 11 }

    alarmProfile-Action-AlarmRelayMajorDuration	OBJECT-TYPE
	SYNTAX	INTEGER
	ACCESS	read-write
	STATUS	mandatory
	DESCRIPTION	"The duration in seconds for which the major relay is set"
	::= { mibalarmProfileEntry 12 }

    alarmProfile-Action-o	OBJECT-TYPE
	SYNTAX	INTEGER {
		    noAction (1),
		    createProfile (2),
		    deleteProfile (3)
		}
	ACCESS	read-write
	STATUS	mandatory
	DESCRIPTION	""
	::= { mibalarmProfileEntry 13 }

END
