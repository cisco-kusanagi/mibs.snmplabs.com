--			Ascend mibuds3net MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBUDS3NET-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibuds3NetworkProfile  OBJECT IDENTIFIER ::= { configuration 5}

	-- The mibuds3NetworkProfile table
	--
	-- This table contains parameters for the mibuds3NetworkProfile profile
	--

    mibuds3NetworkProfileTable	OBJECT-TYPE
	SYNTAX		SEQUENCE OF Mibuds3NetworkProfileEntry
	ACCESS		not-accessible
	STATUS		mandatory
	DESCRIPTION	"A list of mibuds3NetworkProfile profile entries."
	::= { mibuds3NetworkProfile 1 }

    mibuds3NetworkProfileEntry	OBJECT-TYPE
	SYNTAX		Mibuds3NetworkProfileEntry
	ACCESS		not-accessible
	STATUS		mandatory
	DESCRIPTION	"A mibuds3NetworkProfile entry containing objects that
			 maps to the parameters of mibuds3NetworkProfile profile."
	INDEX		{ uds3NetworkProfile-Shelf-o, uds3NetworkProfile-Slot-o, uds3NetworkProfile-Item-o }
	::= { mibuds3NetworkProfileTable 1 }

    Mibuds3NetworkProfileEntry ::=
	SEQUENCE {
	    uds3NetworkProfile-Shelf-o
		INTEGER,
	    uds3NetworkProfile-Slot-o
		INTEGER,
	    uds3NetworkProfile-Item-o
		INTEGER,
	    uds3NetworkProfile-Name
		DisplayString,
	    uds3NetworkProfile-PhysicalAddress-Shelf
		INTEGER,
	    uds3NetworkProfile-PhysicalAddress-Slot
		INTEGER,
	    uds3NetworkProfile-PhysicalAddress-ItemNumber
		INTEGER,
	    uds3NetworkProfile-Enabled
		INTEGER,
	    uds3NetworkProfile-ProfileNumber
		INTEGER,
	    uds3NetworkProfile-LineConfig-TrunkGroup
		INTEGER,
	    uds3NetworkProfile-LineConfig-NailedGroup
		INTEGER,
	    uds3NetworkProfile-LineConfig-RoutePort-SlotNumber-SlotNumber
		INTEGER,
	    uds3NetworkProfile-LineConfig-RoutePort-SlotNumber-ShelfNumber
		INTEGER,
	    uds3NetworkProfile-LineConfig-RoutePort-RelativePortNumber-RelativePortNumber
		INTEGER,
	    uds3NetworkProfile-LineConfig-Activation
		INTEGER,
	    uds3NetworkProfile-LineConfig-LineType
		INTEGER,
	    uds3NetworkProfile-LineConfig-LineCoding
		INTEGER,
	    uds3NetworkProfile-LineConfig-Loopback
		INTEGER,
	    uds3NetworkProfile-LineConfig-ClockSource
		INTEGER,
	    uds3NetworkProfile-LineConfig-ClockPriority
		INTEGER,
	    uds3NetworkProfile-LineConfig-StatusChangeTrapEnable
		INTEGER,
	    uds3NetworkProfile-Action-o
		INTEGER
	}

    uds3NetworkProfile-Shelf-o	OBJECT-TYPE
	SYNTAX	INTEGER
	ACCESS	read-only
	STATUS	mandatory
	DESCRIPTION	""
	::= { mibuds3NetworkProfileEntry 1 }

    uds3NetworkProfile-Slot-o	OBJECT-TYPE
	SYNTAX	INTEGER
	ACCESS	read-only
	STATUS	mandatory
	DESCRIPTION	""
	::= { mibuds3NetworkProfileEntry 2 }

    uds3NetworkProfile-Item-o	OBJECT-TYPE
	SYNTAX	INTEGER
	ACCESS	read-only
	STATUS	mandatory
	DESCRIPTION	""
	::= { mibuds3NetworkProfileEntry 3 }

    uds3NetworkProfile-Name	OBJECT-TYPE
	SYNTAX	DisplayString
	ACCESS	read-write
	STATUS	mandatory
	DESCRIPTION	"For future use. The current design does not use the name field but instead references Uds3 lines by the physical address; we may in the future support referencing Uds3 lines by name as well as by address. The name consists of a null terminated ascii string supplied by the user; it defaults to the ascii form of the Uds3 line physical address."
	::= { mibuds3NetworkProfileEntry 4 }

    uds3NetworkProfile-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibuds3NetworkProfileEntry 5 }

    uds3NetworkProfile-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibuds3NetworkProfileEntry 6 }

    uds3NetworkProfile-PhysicalAddress-ItemNumber	OBJECT-TYPE
	SYNTAX	INTEGER
	ACCESS	read-write
	STATUS	mandatory
	DESCRIPTION	"A number that specifies an addressable entity within the context of shelf and slot."
	::= { mibuds3NetworkProfileEntry 7 }

    uds3NetworkProfile-Enabled	OBJECT-TYPE
	SYNTAX	INTEGER {
		    no (1),
		    yes (2)
		}
	ACCESS	read-write
	STATUS	mandatory
	DESCRIPTION	"TRUE if the line is enabled, otherwise FALSE."
	::= { mibuds3NetworkProfileEntry 8 }

    uds3NetworkProfile-ProfileNumber	OBJECT-TYPE
	SYNTAX	INTEGER
	ACCESS	read-write
	STATUS	mandatory
	DESCRIPTION	"For potential backwards compatibility. The current design consists of one line profile numbered 0."
	::= { mibuds3NetworkProfileEntry 9 }

    uds3NetworkProfile-LineConfig-TrunkGroup	OBJECT-TYPE
	SYNTAX	INTEGER
	ACCESS	read-write
	STATUS	mandatory
	DESCRIPTION	"The trunk group to which this line is assigned. 0 means this line is not part of a trunk group."
	::= { mibuds3NetworkProfileEntry 10 }

    uds3NetworkProfile-LineConfig-NailedGroup	OBJECT-TYPE
	SYNTAX	INTEGER
	ACCESS	read-write
	STATUS	mandatory
	DESCRIPTION	"A number that identifies the set of lines that makes up a nailed group. 0 means this line is not part of a nailed group."
	::= { mibuds3NetworkProfileEntry 11 }

    uds3NetworkProfile-LineConfig-RoutePort-SlotNumber-SlotNumber	OBJECT-TYPE
	SYNTAX	INTEGER
	ACCESS	read-write
	STATUS	mandatory
	DESCRIPTION	""
	::= { mibuds3NetworkProfileEntry 12 }

    uds3NetworkProfile-LineConfig-RoutePort-SlotNumber-ShelfNumber	OBJECT-TYPE
	SYNTAX	INTEGER
	ACCESS	read-write
	STATUS	mandatory
	DESCRIPTION	"TNT is a multi shelf system. To minimise the changes required to existing code the shelf number is added to this structure as it will almost always be needed when a slot number is needed."
	::= { mibuds3NetworkProfileEntry 13 }

    uds3NetworkProfile-LineConfig-RoutePort-RelativePortNumber-RelativePortNumber	OBJECT-TYPE
	SYNTAX	INTEGER
	ACCESS	read-write
	STATUS	mandatory
	DESCRIPTION	""
	::= { mibuds3NetworkProfileEntry 14 }

    uds3NetworkProfile-LineConfig-Activation	OBJECT-TYPE
	SYNTAX	INTEGER {
		    static (1),
		    dsrActive (2),
		    dcdDsrActive (3)
		}
	ACCESS	read-write
	STATUS	mandatory
	DESCRIPTION	"Line activation mode."
	::= { mibuds3NetworkProfileEntry 15 }

    uds3NetworkProfile-LineConfig-LineType	OBJECT-TYPE
	SYNTAX	INTEGER {
		    cBitParity (1)
		}
	ACCESS	read-write
	STATUS	mandatory
	DESCRIPTION	"The variety of DS3 C-bit or E3 application for the line."
	::= { mibuds3NetworkProfileEntry 19 }

    uds3NetworkProfile-LineConfig-LineCoding	OBJECT-TYPE
	SYNTAX	INTEGER {
		    b3zs (1)
		}
	ACCESS	read-write
	STATUS	mandatory
	DESCRIPTION	"The variety of Zero Code suppression used for the DS3 line."
	::= { mibuds3NetworkProfileEntry 20 }

    uds3NetworkProfile-LineConfig-Loopback	OBJECT-TYPE
	SYNTAX	INTEGER {
		    noLoopback (1),
		    facilityLoopback (2),
		    localLoopback (3)
		}
	ACCESS	read-write
	STATUS	mandatory
	DESCRIPTION	"Loopback mode."
	::= { mibuds3NetworkProfileEntry 21 }

    uds3NetworkProfile-LineConfig-ClockSource	OBJECT-TYPE
	SYNTAX	INTEGER {
		    eligible (1),
		    notEligible (2)
		}
	ACCESS	read-write
	STATUS	mandatory
	DESCRIPTION	"Determine whether the 8KHz clock from the UDS3 board is eligible to be used as the system-wide TDM clock source."
	::= { mibuds3NetworkProfileEntry 23 }

    uds3NetworkProfile-LineConfig-ClockPriority	OBJECT-TYPE
	SYNTAX	INTEGER {
		    highPriority (2),
		    middlePriority (3),
		    lowPriority (4)
		}
	ACCESS	read-write
	STATUS	mandatory
	DESCRIPTION	"Clock priority assigned to the UDS3 line. Used to select a particular UDS3 line as clock source."
	::= { mibuds3NetworkProfileEntry 24 }

    uds3NetworkProfile-LineConfig-StatusChangeTrapEnable	OBJECT-TYPE
	SYNTAX	INTEGER {
		    no (1),
		    yes (2)
		}
	ACCESS	read-write
	STATUS	mandatory
	DESCRIPTION	"When set to No, do not send dsx3LineStatusChangeTrapEnable trap. If Yes, send traps. The default is No."
	::= { mibuds3NetworkProfileEntry 25 }

    uds3NetworkProfile-Action-o	OBJECT-TYPE
	SYNTAX	INTEGER {
		    noAction (1),
		    createProfile (2),
		    deleteProfile (3)
		}
	ACCESS	read-write
	STATUS	mandatory
	DESCRIPTION	""
	::= { mibuds3NetworkProfileEntry 22 }

END
