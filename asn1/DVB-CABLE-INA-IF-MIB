-- extracted from draft-ietf-ipcdn-dvbinaif-mib-00.txt
-- at Wed Apr  4 06:04:59 2001

DVB-CABLE-INA-IF-MIB DEFINITIONS ::= BEGIN
IMPORTS
       MODULE-IDENTITY,
       OBJECT-TYPE,
       Counter32,
       Gauge32,
       Integer32,
       Unsigned32,
       experimental,
       TimeTicks,
       transmission
           FROM SNMPv2-SMI
       InetAddress,
       InetAddressType
           FROM INET-ADDRESS-MIB
       RowStatus,
       TruthValue,
       TEXTUAL-CONVENTION,
       MacAddress
           FROM SNMPv2-TC
       OBJECT-GROUP,
       MODULE-COMPLIANCE
           FROM SNMPv2-CONF
       ifIndex,
       InterfaceIndexOrZero,
       InterfaceIndex
           FROM IF-MIB;


   dvbInaIf MODULE-IDENTITY

       LAST-UPDATED    "200102090000Z"

       ORGANIZATION    "DVB/DAVIC Interoperability Consortium Technical
                        Working Group"
       CONTACT-INFO
              "        Ian Wheelock
               Postal: Com21, Ireland
                       4400 Cork Airport Business Park
                       Kinsale Road,
                       Cork,
                       IRELAND

                  Tel: +353 2173 05800
                  Fax: +353 2143 21972
               E-mail: ianw@com21.com"

       DESCRIPTION     "The MIB modules for INAs that
                        conform to the EuroModem specification.  This
                        MIB assumes the INA implements MIB-II RFC 1213


Pedersen         Informational - Expires August 2001               13
                     DVB Cable INA Interface MIB             Feb 2001


                        The original MIB definition work was carried
                        out for the DVB-RC group by
                        Bert Van Willigen
                        Philips Research Laboratory Eindhoven,
                        The Netherlands."

       REVISION         "200102090000Z"
       DESCRIPTION      "Corrected BITS default.
                         jmp@cisco.com"

       REVISION         "200012130000Z"
       DESCRIPTION      "Added transmission import
                         Corrected 32 bit max int.
                        jmp@cisco.com"

       REVISION         "200011160000Z"
       DESCRIPTION      "Corrected display hints for textual
                         conventions.
                        jmp@cisco.com"

       REVISION         "200011060000Z"
       DESCRIPTION      "Proposal for header compression,
                        session binding and reprovisioning.
                        jmp@cisco.com"

       REVISION         "200010270000Z"
       DESCRIPTION      "Proposal for provisioning.
                        jmp@cisco.com"

       REVISION         "200010260000Z"
       DESCRIPTION      "New base version of IF-MIB.
                        jmp@cisco.com"

       REVISION         "200010100000Z"
       DESCRIPTION      "Update of IF-MIB to Cisco guess on
                        how the final MIB will be.
                        THIS IS BY NO MEANS THE CORRECT VERSION
                        BUT A GOOD GUESS.
                        jmp@cisco.com"

       REVISION         "200010020000Z"
       DESCRIPTION      "Update of IF-MIB to include proper conformance
                        section and addition of InetAddress and
                        InetAddressType."

       REVISION         "200008310000Z"
       DESCRIPTION      "The original mib organisation that included the
                        the Device and IF related information in one
                        large MIB. Split of the MIB was proposed by
                        the WGT on the 29 August 2000. This resulted
                        in this IF-MIB being created."

       REVISION         "200008190000Z"

Pedersen         Informational - Expires August 2001               14
                     DVB Cable INA Interface MIB             Feb 2001


       DESCRIPTION      "The original MIB organisation that included the
                        Device and IF related information in one large
                        MIB."

    ::= { transmission 146 }


   -- Sub divided dvbInaIf into MIB Objects and conformance
   dvbInaIfMIBObjects OBJECT IDENTIFIER ::= {dvbInaIf 1}
   dvbInaIfMIBConform OBJECT IDENTIFIER ::= {dvbInaIf 2}

   -- Define groups under dvbInaIfMIBObjects

   dvbInaIfMac            OBJECT IDENTIFIER ::= {dvbInaIfMIBObjects 1}
   dvbInaIfProvision      OBJECT IDENTIFIER ::= {dvbInaIfMIBObjects 2}
   dvbInaIfDsCh           OBJECT IDENTIFIER ::= {dvbInaIfMIBObjects 3}
   dvbInaIfUsCh           OBJECT IDENTIFIER ::= {dvbInaIfMIBObjects 4}
   dvbInaIfNiu            OBJECT IDENTIFIER ::= {dvbInaIfMIBObjects 5}
   dvbInaIfConnection     OBJECT IDENTIFIER ::= {dvbInaIfMIBObjects 6}
   dvbInaIfReprov         OBJECT IDENTIFIER ::= {dvbInaIfMIBObjects 7}


   -- Define groups under dvbInaIfMIBConform

   dvbInaIfCompliances    OBJECT IDENTIFIER ::= {dvbInaIfMIBConform 1}
   dvbInaIfGroups         OBJECT IDENTIFIER ::= {dvbInaIfMIBConform 2}

-- - - - - - - - - - - - - - - - - - - - - - - - - - - - - - - - - - -
-- Local textual conventions
-- - - - - - - - - - - - - - - - - - - - - - - - - - - - - - - - - - -

MacFlagSet ::= TEXTUAL-CONVENTION
        DISPLAY-HINT "d"
        STATUS       current
        DESCRIPTION
            "This data type represents a reference to a set of
             MAC Flags.
             This reference is used in different MAC messages. See also
             ES 200 800, section 5.3.1.3."
        SYNTAX       INTEGER ( 1..16 )

EtsTimeOut ::= TEXTUAL-CONVENTION
        STATUS       current
        DESCRIPTION
            "This data type represents possible timeout values.
             See also ES 200 800, section 5.5.3.2."
        SYNTAX       INTEGER {
            etsTODisabled(0),
            etsTO9ms(1),
            etsTO30ms(2),
            etsTO60ms(3),
            etsTO90ms(4),
            etsTO300ms(5),

Pedersen         Informational - Expires August 2001               15
                     DVB Cable INA Interface MIB             Feb 2001


            etsTO600ms(6),
            etsTO900ms(7),
            etsTO3000ms(8),
            etsTO6000ms(9),
            etsTO9000ms(10),
            etsTO30000ms(11),
            etsTO60000ms(12)
        }

UpFrequency ::= TEXTUAL-CONVENTION
        DISPLAY-HINT "d"
        STATUS       current
        DESCRIPTION
            "Upstream frequency range"
        SYNTAX       Integer32 ( 5000000..65000000 )

DownFrequency ::= TEXTUAL-CONVENTION
        DISPLAY-HINT "d"
        STATUS       current
        DESCRIPTION
            "Downstream frequency range"
        SYNTAX       Integer32 ( 70000000..862000000 )

Modulation      ::= TEXTUAL-CONVENTION
        STATUS          current
        DESCRIPTION
            "Modulation type:
               OOB: qpsk(1)
               IB : qpsk(1),
                    qam16(2),
                    qam32(3),
                    qam64(4),
                    qam128(5),
                    qam256(6)"
        SYNTAX      INTEGER {
                    qpsk(1),
                    qam16(2),
                    qam32(3),
                    qam64(4),
                    qam128(5),
                    qam256(6)
        }

DownstreamSymbolrate    ::= TEXTUAL-CONVENTION
        STATUS          current
        DESCRIPTION
            "The downstream transmission symbol rate used in symbol/s
             The symbol rate is given as an integer.
             Commonly used symbolrates are :
                symbol/s
                ---------------------------------------
                6800000    IB 8Mhz
                6875000    IB 8Mhz

Pedersen         Informational - Expires August 2001               16
                     DVB Cable INA Interface MIB             Feb 2001


                6900000    IB 8Mhz
                4896000    IB 6Mhz
                5168000    IB 6Mhz
                5304000    IB 6Mhz
                 772000    OOB optional,  Grade A
                1544000    OOB mandatory, Grade B"
        SYNTAX      INTEGER ( 0..4294967295 )

UpstreamSymbolrate        ::= TEXTUAL-CONVENTION
        STATUS          current
        DESCRIPTION
            "The upstream transmission symbol rate used.
               symbol/s
              ---------------------------------
              sr0128000    optional  Grade A
              sr0772000    optional  Grade B
              sr1544000    mandatory Grade C
              sr3088000    optional  Grade D"
        SYNTAX      INTEGER {
                    sr0128000(1),
                    sr0772000(2),
                    sr1544000(3),
                    sr3088000(4)
        }


-- - - - - - - - - - - - - - - - - - - - - - - - - - - - - - - - - - -
-- MAC group
--
-- The MAC group contains a table of MAC entries, where each entry
-- represents one MAC entity. A MAC entity is associated with one
-- downstream channel and up to eight upstream channels. Typically a
-- device will have only one MAC entity.
--
-- The MAC table extends the MAC layer entries in the MIB-II interface
-- table [RFC 2233]. Both tables are indexed with the same ifIndex
-- object
--
-- Please note that the desired enable state of the MAC entity can be
-- set by using the ifAdminStatus parameter in the interfaces group.
-- - - - - - - - - - - - - - - - - - - - - - - - - - - - - - - - - - -

dvbInaIfMacTable OBJECT-TYPE
        SYNTAX      SEQUENCE OF DvbInaIfMacEntry
        MAX-ACCESS  not-accessible
        STATUS      current
        DESCRIPTION
            "Describes the attributes of each MAC interface,
            extending the information available from ifEntry."
        ::= { dvbInaIfMac 1 }

dvbInaIfMacEntry OBJECT-TYPE
        SYNTAX      DvbInaIfMacEntry

Pedersen         Informational - Expires August 2001               17
                     DVB Cable INA Interface MIB             Feb 2001


        MAX-ACCESS  not-accessible
        STATUS      current
        DESCRIPTION
            "An entry containing objects describing attributes of each
            MAC entry, extending the information in ifEntry.
            An entry in this table exists for each ifEntry with an
            ifType of dvbRecMacLayer(146).

            The state of the MAC depends on the state of the INA. If
            the INA is not operational also the MAC is not operational."

        INDEX { ifIndex }
        ::= { dvbInaIfMacTable 1 }

DvbInaIfMacEntry ::= SEQUENCE {
            dvbInaIfMacDeviceCapabilities           OCTET STRING,
            dvbInaIfMacDeviceExtendedCapabilities   OCTET STRING,
            dvbInaIfMacCapabilities                 OCTET STRING,
            dvbInaIfMacExtendedCapabilities         OCTET STRING,
            dvbInaIfMacProtocolSupport              INTEGER,
            dvbInaIfMacTimeout0                     EtsTimeOut,
            dvbInaIfMacTimeout1                     EtsTimeOut,
            dvbInaIfMacTimeout2                     EtsTimeOut,
            dvbInaIfMacTimeout3                     EtsTimeOut,
            dvbInaIfMacTimeout4                     EtsTimeOut,
            dvbInaIfMacTimeoutD                     EtsTimeOut,
            dvbInaIfMacTimeoutE                     EtsTimeOut,
            dvbInaIfMacTimeoutF                     EtsTimeOut,
            dvbInaIfMacRapidSignOnEnable            TruthValue,
            dvbInaIfMacRespCollTimeWindow           Unsigned32,
            dvbInaIfMacAddressFilterUse             INTEGER,
            dvbInaIfMacAddressPositionMask          INTEGER,
            dvbInaIfMacAddressComparisonValue       INTEGER,
            dvbInaIfMacGrantProtocolTimeOut         Unsigned32,
            dvbInaIfMacIdleInterval                 Unsigned32,
            dvbInaIfMacIdleInvalidCount             INTEGER,
            dvbInaIfMacN                            INTEGER,
            dvbInaIfMacMaxContentionMsgLen          INTEGER,
            dvbInaIfMacMaxReservationMsgLen         INTEGER,
            dvbInaIfMacNiuCount                     Gauge32,
            dvbInaIfMacConnections                  Gauge32,
            dvbInaIfMacUnknownNiuError              Counter32,
            dvbInaIfMacMsgDataError                 Counter32,
            dvbInaIfMacMsgHdrError                  Counter32,
            dvbInaIfMacInvalidNiu                   Counter32,
            dvbInaIfMacTimingRangingError           Counter32,
            dvbInaIfMacPowerRangingError            Counter32,
            dvbInaIfMacOtherSignOnError             Counter32
        }

dvbInaIfMacDeviceCapabilities           OBJECT-TYPE
        SYNTAX      OCTET STRING ( SIZE (4))
        MAX-ACCESS  read-only

Pedersen         Informational - Expires August 2001               18
                     DVB Cable INA Interface MIB             Feb 2001


        STATUS      current
        DESCRIPTION
            "This 32-bit object specifies the maximum capabilities
             of this MAC entity.
             This is the possible set of capability for this INA."
        REFERENCE
            "ES 200 800 Default Configuration Message."
        ::= { dvbInaIfMacEntry 1 }

dvbInaIfMacDeviceExtendedCapabilities   OBJECT-TYPE
        SYNTAX      OCTET STRING ( SIZE (4))
        MAX-ACCESS  read-only
        STATUS      current
        DESCRIPTION
            "This 32-bit object specifies the maximum extended
             capabilities of this MAC entity.
             This is the possible set of capability for this INA."
        REFERENCE
            "ES 200 800 Default Configuration Message."
        ::= { dvbInaIfMacEntry 2 }

dvbInaIfMacCapabilities OBJECT-TYPE
        SYNTAX      OCTET STRING ( SIZE (4))
        MAX-ACCESS  read-write
        STATUS      current
        DESCRIPTION
            "This 32-bit object specifies the capabilities of this
             MAC entity. It is equal to or a subset of
             dvbInaIfMacDeviceCapabilities. Default this parameter is
             equal to dvbInaIfMacDeviceCapabilities.
             The object can be used to restrict the capabilities for
             this MAC entity."
        ::= { dvbInaIfMacEntry 3 }

dvbInaIfMacExtendedCapabilities     OBJECT-TYPE
        SYNTAX      OCTET STRING ( SIZE (4))
        MAX-ACCESS  read-write
        STATUS      current
        DESCRIPTION
            "This 32-bit object specifies the extended capabilities of
             this MAC entity. It is equal to or a subset of
             dvbInaIfMacDeviceExtendedCapabilities.
             Default this parameter is equal to
             dvbInaIfMacDeviceExtendedCapabilities.
             The object can be used to restrict the extended
             capabilities for this MAC entity."
        ::= { dvbInaIfMacEntry 4 }

dvbInaIfMacProtocolSupport OBJECT-TYPE
        SYNTAX      INTEGER {
                    davic10(0),
                    davic11(1),
                    davic12(2),

Pedersen         Informational - Expires August 2001               19
                     DVB Cable INA Interface MIB             Feb 2001


                    en301199(20),
                    ets300800v20davic15(29),
                    ets300800v10(30)
                    }
        MAX-ACCESS  read-write
        STATUS      current
        DESCRIPTION
            "Specifies the MAC standard version supported by this MAC
            entity. Optional, this parameter can be written to force
            a particular MAC version to be executed by the INA."
        DEFVAL { ets300800v20davic15 }
        ::= { dvbInaIfMacEntry 5 }

dvbInaIfMacTimeout0 OBJECT-TYPE
        SYNTAX      EtsTimeOut
        MAX-ACCESS  read-write
        STATUS      current
        DESCRIPTION
            " Time-out value 0x0. "
        REFERENCE
            "ES 200 800, table 21."
        DEFVAL { etsTO300ms }
        ::= { dvbInaIfMacEntry 6 }

dvbInaIfMacTimeout1 OBJECT-TYPE
        SYNTAX      EtsTimeOut
        MAX-ACCESS  read-write
        STATUS      current
        DESCRIPTION
            "Time-out value 0x1."
        REFERENCE
            "ES 200 800, table 21."
        DEFVAL { etsTO3000ms }
        ::= { dvbInaIfMacEntry 7 }

dvbInaIfMacTimeout2 OBJECT-TYPE
        SYNTAX      EtsTimeOut
        MAX-ACCESS  read-write
        STATUS      current
        DESCRIPTION
            "Time-out value 0x2."
        REFERENCE
            "ES 200 800, table 22."
        DEFVAL { etsTO900ms }
        ::= { dvbInaIfMacEntry 8 }

dvbInaIfMacTimeout3 OBJECT-TYPE
        SYNTAX      EtsTimeOut
        MAX-ACCESS  read-write
        STATUS      current
        DESCRIPTION
            "Time-out value 0x3."
        REFERENCE

Pedersen         Informational - Expires August 2001               20
                     DVB Cable INA Interface MIB             Feb 2001


            "ES 200 800, table 22."
        DEFVAL { etsTO90ms }
        ::= { dvbInaIfMacEntry 9 }

dvbInaIfMacTimeout4 OBJECT-TYPE
        SYNTAX      EtsTimeOut
        MAX-ACCESS  read-write
        STATUS      current
        DESCRIPTION
            "Time-out value 0x4."
        REFERENCE
            "ES 200 800, table 22."
        DEFVAL { etsTO300ms }
        ::= { dvbInaIfMacEntry 10 }

dvbInaIfMacTimeoutD OBJECT-TYPE
        SYNTAX      EtsTimeOut
        MAX-ACCESS  read-write
        STATUS      current
        DESCRIPTION
            "Time-out value 0xD. Terminal Time-Out, Security Sign-On."
        REFERENCE
            "ES 200 800, table 51"
        DEFVAL { etsTO90ms }
        ::= { dvbInaIfMacEntry 11 }

dvbInaIfMacTimeoutE OBJECT-TYPE
        SYNTAX      EtsTimeOut
        MAX-ACCESS  read-write
        STATUS      current
        DESCRIPTION
            "Time-out value 0xE. Terminal Time-Out, Main Key Exchange."
        REFERENCE
            "ES 200 800, table 51"
        DEFVAL { etsTO600ms }
        ::= { dvbInaIfMacEntry 12 }

dvbInaIfMacTimeoutF OBJECT-TYPE
        SYNTAX      EtsTimeOut
        MAX-ACCESS  read-write
        STATUS      current
        DESCRIPTION
            "Time-out value 0xF. Terminal Time-Out, Quick/Explicit Key
             exchange."
        REFERENCE
            "ES 200 800, table 51"
        DEFVAL { etsTO300ms }
        ::= { dvbInaIfMacEntry 13 }

dvbInaIfMacRapidSignOnEnable OBJECT-TYPE
        SYNTAX      TruthValue
        MAX-ACCESS  read-write
        STATUS      current

Pedersen         Informational - Expires August 2001               21
                     DVB Cable INA Interface MIB             Feb 2001


        DESCRIPTION
            "This Boolean parameter specifies whether the NIU's
            are allowed to do a rapid sign-on when they enter the
            sign-on process. (See the Need_Calibration bit in the
            <MAC> Sign-On_Request_Message.). By default this object
            is False."
        DEFVAL { false }
        ::= { dvbInaIfMacEntry 14 }

dvbInaIfMacRespCollTimeWindow OBJECT-TYPE
        SYNTAX      Unsigned32 ( 0..65535 )
        UNITS       "ms"
        MAX-ACCESS  read-write
        STATUS      current
        DESCRIPTION
            "Specifies the maximum time for the sign-on response
             message transmission randomisation."
        DEFVAL { 900 }
        ::= { dvbInaIfMacEntry 15 }

dvbInaIfMacAddressFilterUse OBJECT-TYPE
        SYNTAX      INTEGER {
                    disabled(1),
                    managed(2),
                    automatic(3)
                    }
        MAX-ACCESS  read-write
        STATUS      current
        DESCRIPTION
            "This setting controls the use of the of the Address filter
            in the Sign-On Request Message.

            Disabled    : The address filter is not used.
            Managed     : The manager can control the use of the address
                          filter with dvbInaIfMacAddressPositionMask
                          and dvbInaIfMacAddressComparisonValue
            Automatic   : The INA controls use of the address filter
                          itself. The readback values of
                          dvbInaIfMacAddressPositionMask
                          and dvbInaIfMacAddressComparisonValue will not
                          necessary reflect the values used by the INA."
        REFERENCE
            "ES 200 800 Sign-On Request Message"
        ::= { dvbInaIfMacEntry 16 }

dvbInaIfMacAddressPositionMask OBJECT-TYPE
        SYNTAX      INTEGER ( 0..255 )
        MAX-ACCESS  read-write
        STATUS      current
        DESCRIPTION
            "Indicates the bit positions in the NIU MAC address that
            are used for address filtering comparison."
        REFERENCE

Pedersen         Informational - Expires August 2001               22
                     DVB Cable INA Interface MIB             Feb 2001


            "ES 200 800 Sign-On Request Message"
        ::= { dvbInaIfMacEntry 17 }

dvbInaIfMacAddressComparisonValue OBJECT-TYPE
        SYNTAX      INTEGER ( 0..255 )
        MAX-ACCESS  read-write
        STATUS      current
        DESCRIPTION
            "Specifies the value that the NIU should use for MAC
            address comparison."
        REFERENCE
            "ES 200 800 Sign-On Request Message"
        ::= { dvbInaIfMacEntry 18 }

dvbInaIfMacGrantProtocolTimeOut OBJECT-TYPE
        SYNTAX      Unsigned32 ( 0..65535 )
        UNITS       "ms"
        MAX-ACCESS  read-write
        STATUS      current
        DESCRIPTION
            "Default value for the time that the NIU should wait before
            verifying the status of pending grants.
            See also dvbInaIfNiuGrantProtocolTimeOut."
        DEFVAL { 600 }
        ::= { dvbInaIfMacEntry 19 }

dvbInaIfMacIdleInterval OBJECT-TYPE
        SYNTAX      Unsigned32 ( 0 | 60..600 )
        UNITS       "s"
        MAX-ACCESS  read-write
        STATUS      current
        DESCRIPTION
            "Specifies the transmission interval in seconds to be
            used for the MAC Idle message. When this value is zero,
            no idle messages shall be sent."
        DEFVAL { 60 }
        ::= { dvbInaIfMacEntry 20 }

dvbInaIfMacIdleInvalidCount OBJECT-TYPE
        SYNTAX      INTEGER ( 0..255 )
        UNITS       "Number of dvbInaIfMacIdleIntervals"
        MAX-ACCESS  read-write
        STATUS      current
        DESCRIPTION
            "Specifies a MAC Idle message invalid period in number
            of dvbInaIfMacIdleInterval, after which the NIU is declared
            to be signed-off.
            For example, if dvbInaIfMacIdleInterval is 5 seconds and
            this parameter is 3, then if in 15 seconds no data and/or
            MAC Idle messages are received, the INA will assume that
            the NIU in question has signed-off.
            This object is only valid when dvbInaIfMacIdleInterval
            is non-zero."

Pedersen         Informational - Expires August 2001               23
                     DVB Cable INA Interface MIB             Feb 2001


        DEFVAL { 3 }
        ::= { dvbInaIfMacEntry 21 }

dvbInaIfMacN OBJECT-TYPE
        SYNTAX      INTEGER ( 0..1023 )
        MAX-ACCESS  read-write
        STATUS      current
        DESCRIPTION
            " Maximum value of the upstream slot position register. "
        ::= { dvbInaIfMacEntry 22 }

dvbInaIfMacMaxContentionMsgLen    OBJECT-TYPE
        SYNTAX      INTEGER ( 1..255 )
        UNITS       "ATM cells"
        MAX-ACCESS  read-write
        STATUS      current
        DESCRIPTION
            "The default value for the
             Maximum_Contention_Access_Message_Length
             in the Connect Message.
             This is the maximum length of a message that may be
             transmitted using contention access. Any message greater
             than this should use reservation access.
            See also dvbInaIfConMaxContentionMsgLen."
        REFERENCE
            "ES 200 800 Connect_Message parameter:
             Maximum_Contention_Access_Message_Length"
        DEFVAL      { 1 }
        ::= { dvbInaIfMacEntry 23 }

dvbInaIfMacMaxReservationMsgLen    OBJECT-TYPE
        SYNTAX      INTEGER ( 1..255 )
        UNITS       "ATM cells"
        MAX-ACCESS  read-write
        STATUS      current
        DESCRIPTION
            "The default value for the
             Maximum_Reservation_Access_Message_Length
             in the Connect Message.
             This is the maximum length of a message that may be
             transmitted using a single reservation access.
             Any message greater than this should be transmitted by
             making multiple reservation requests.
             See also dvbInaIfConMaxReservationMsgLen."
        REFERENCE
            "ES 200 800 Connect_Message"
        DEFVAL      { 50 }
        ::= { dvbInaIfMacEntry 24 }

dvbInaIfMacNiuCount OBJECT-TYPE
        SYNTAX      Gauge32
        MAX-ACCESS  read-only
        STATUS      current

Pedersen         Informational - Expires August 2001               24
                     DVB Cable INA Interface MIB             Feb 2001


        DESCRIPTION
            "Number of connected NIUs."
        ::= { dvbInaIfMacEntry 25 }

dvbInaIfMacConnections OBJECT-TYPE
        SYNTAX      Gauge32
        MAX-ACCESS  read-only
        STATUS      current
        DESCRIPTION
            "The number of connections currently active for this MAC
            entity."
        ::= { dvbInaIfMacEntry 26 }

dvbInaIfMacUnknownNiuError      OBJECT-TYPE
        SYNTAX      Counter32
        MAX-ACCESS  read-only
        STATUS      current
        DESCRIPTION
            "This value is incremented if a message is received from a
             unknown NIU, except if it is a SignOn_Response Message."
        ::= { dvbInaIfMacEntry 27 }

dvbInaIfMacMsgDataError         OBJECT-TYPE
        SYNTAX      Counter32
        MAX-ACCESS  read-only
        STATUS      current
        DESCRIPTION
            "This value is incremented if a MAC message is received
             with a data error, i.e.
                1) is too short,
                2) has an illegal Connection ID or Reservation ID,
                3) is a reservation message from a NIU not reservation
                   capable,
                4) is a security message from a NIU not security
                   capable
                5) is an illegal MAC message."
        ::= { dvbInaIfMacEntry 28 }

dvbInaIfMacMsgHdrError          OBJECT-TYPE
        SYNTAX      Counter32
        MAX-ACCESS  read-only
        STATUS      current
        DESCRIPTION
            "This value is incremented if a MAC message is received
             with a header error, i.e.
                1) is too short,
                2) does not contain a MAC address."
        ::= { dvbInaIfMacEntry 29 }

dvbInaIfMacInvalidNiu                   OBJECT-TYPE
        SYNTAX      Counter32
        MAX-ACCESS  read-only
        STATUS      current

Pedersen         Informational - Expires August 2001               25
                     DVB Cable INA Interface MIB             Feb 2001


        DESCRIPTION
            "This value is incremented if a MAC Initialisation
             Complete Message is transmitted with the
             Invalid_STB/NIU bit set."
        REFERENCE
            "ES 200 800 Initialisation Complete Message."
        ::= { dvbInaIfMacEntry 30 }

dvbInaIfMacTimingRangingError           OBJECT-TYPE
        SYNTAX      Counter32
        MAX-ACCESS  read-only
        STATUS      current
        DESCRIPTION
            "This value is incremented if a MAC Initialisation
             Complete Message is transmitted with the
             Timing_Ranging_Error bit set."
        REFERENCE
            "ES 200 800 Initialisation Complete Message."
        ::= { dvbInaIfMacEntry 31 }

dvbInaIfMacPowerRangingError           OBJECT-TYPE
        SYNTAX      Counter32
        MAX-ACCESS  read-only
        STATUS      current
        DESCRIPTION
            "This value is incremented if a MAC Initialisation
             Complete Message is transmitted with the
             Power_Ranging_Error bit set."
        REFERENCE
            "ES 200 800 Initialisation Complete Message."
        ::= { dvbInaIfMacEntry 32 }

dvbInaIfMacOtherSignOnError             OBJECT-TYPE
        SYNTAX      Counter32
        MAX-ACCESS  read-only
        STATUS      current
        DESCRIPTION
            "This value is incremented if a MAC Initialisation
             Complete Message is transmitted with the
             Other_Error bit set."
        REFERENCE
            "ES 200 800 Initialisation Complete Message."
        ::= { dvbInaIfMacEntry 33 }


-- - - - - - - - - - - - - - - - - - - - - - - - - - - - - - - - - - -
-- Provisioning Channel Table
--
-- The Provisioning Channel Table specifies the information for
-- the Default Configuration Message transmitted on the downstram
-- Provisioning channel.
--
-- The timeout values and INA capability also transmitted in the

Pedersen         Informational - Expires August 2001               26
                     DVB Cable INA Interface MIB             Feb 2001


-- Default Configuration Message is in the MAC table, since these
-- values are needed even if the provisioning take place on another INA.
--
-- More than one Provisioning channel can be found on an INA.
--
-- The index of the table is an arbitrary integer.
-- - - - - - - - - - - - - - - - - - - - - - - - - - - - - - - - - - -

dvbInaIfProvChTable OBJECT-TYPE
        SYNTAX      SEQUENCE OF DvbInaIfProvChEntry
        MAX-ACCESS  not-accessible
        STATUS      current
        DESCRIPTION
            "This table specifies the information for the
            Default Configuration Message transmitted on the
            Provisioning channel."
        ::= { dvbInaIfProvision 1 }

dvbInaIfProvChEntry OBJECT-TYPE
        SYNTAX      DvbInaIfProvChEntry
        MAX-ACCESS  not-accessible
        STATUS      current
        DESCRIPTION
            "An entry containing objects describing information
             for the Default Configuration Message
             transmitted on the Provisioning channel.

             More than one downstream can use than same entry
             or different entries can be made for different downstreams.

             If provisioning is done on an other INA, this table
             will be empty."
        INDEX { dvbInaIfProvChIndex }
        ::= { dvbInaIfProvChTable 1 }


DvbInaIfProvChEntry ::= SEQUENCE {
            dvbInaIfProvChIndex                     INTEGER,
            dvbInaIfProvChRowAccessStatus           RowStatus,
            dvbInaIfProvChServiceChIfIndex          InterfaceIndex,
            dvbInaIfProvChBackupServiceChIfIndex    InterfaceIndex,
            dvbInaIfProvChIncrPowerRetryCount       INTEGER,
            dvbInaIfProvChMaxPowerLevel             INTEGER,
            dvbInaIfProvChMinPowerLevel             INTEGER,
            dvbInaIfProvChMaxBackOffExponent        INTEGER,
            dvbInaIfProvChMinBackOffExponent        INTEGER,
            dvbInaIfProvChAbsoluteTimeOffset        INTEGER
        }

dvbInaIfProvChIndex             OBJECT-TYPE
        SYNTAX      INTEGER ( 0..255 )
        MAX-ACCESS  not-accessible
        STATUS      current

Pedersen         Informational - Expires August 2001               27
                     DVB Cable INA Interface MIB             Feb 2001


        DESCRIPTION
            "Index of this table entry. "
        ::= { dvbInaIfProvChEntry 1 }

dvbInaIfProvChRowAccessStatus   OBJECT-TYPE
        SYNTAX      RowStatus
        MAX-ACCESS  read-create
        STATUS      current
        DESCRIPTION
            "Controls and reflects the status of this row in this
            table. "
        ::= { dvbInaIfProvChEntry 2 }

dvbInaIfProvChServiceChIfIndex    OBJECT-TYPE
        SYNTAX      InterfaceIndex
        MAX-ACCESS  read-create
        STATUS      current
        DESCRIPTION
            "The ifIndex of the upstream channel used as
            Service Channel for the provisioning."
        ::= { dvbInaIfProvChEntry 3 }

dvbInaIfProvChBackupServiceChIfIndex    OBJECT-TYPE
        SYNTAX      InterfaceIndex
        MAX-ACCESS  read-create
        STATUS      current
        DESCRIPTION
            "The ifIndex of the upstream channel used as
            Backup Service Channel for the provisioning."
        ::= { dvbInaIfProvChEntry 4 }

dvbInaIfProvChIncrPowerRetryCount OBJECT-TYPE
        SYNTAX      INTEGER ( 0..255 )
        MAX-ACCESS  read-create
        STATUS      current
        DESCRIPTION
            " Specifies the number of attempts the NIU should do to
            enter the system at the same power level before
            incrementing its upstream transmit power for this MAC
            entity. "
        ::= { dvbInaIfProvChEntry 5 }

dvbInaIfProvChMaxPowerLevel OBJECT-TYPE
        SYNTAX      INTEGER ( 0..255 )
        UNITS       "dBuV"
        MAX-ACCESS  read-create
        STATUS      current
        DESCRIPTION
            " Specifies the maximum power in dBuV the NIU is allowed
            to transmit upstream for this MAC entity. "
        ::= { dvbInaIfProvChEntry 6 }

dvbInaIfProvChMinPowerLevel OBJECT-TYPE

Pedersen         Informational - Expires August 2001               28
                     DVB Cable INA Interface MIB             Feb 2001


        SYNTAX      INTEGER ( 0..255 )
        UNITS       "dBuV"
        MAX-ACCESS  read-create
        STATUS      current
        DESCRIPTION
            " Specifies the minimum power in dBuV the NIU has to
            transmit upstream for this MAC entity. "
        ::= { dvbInaIfProvChEntry 7 }

dvbInaIfProvChMaxBackOffExponent OBJECT-TYPE
        SYNTAX      INTEGER ( 0..255 )
        MAX-ACCESS  read-create
        STATUS      current
        DESCRIPTION
            " Specifies the maximum back off exponent counter for
            this MAC entity. "
        ::= { dvbInaIfProvChEntry 8 }

dvbInaIfProvChMinBackOffExponent OBJECT-TYPE
        SYNTAX      INTEGER ( 0..255 )
        MAX-ACCESS  read-create
        STATUS      current
        DESCRIPTION
            " Specifies the minimum back off exponent counter for
            this MAC entity. "
        ::= { dvbInaIfProvChEntry 9 }

dvbInaIfProvChAbsoluteTimeOffset OBJECT-TYPE
        SYNTAX      INTEGER ( -32768..32767 )
        UNITS       "100ns"
        MAX-ACCESS  read-create
        STATUS      current
        DESCRIPTION
            " Specifies the default absolute time offset in 100 ns
            units to be used for first sign-on of a NIU for this MAC
            entity. "
        ::= { dvbInaIfProvChEntry 10 }


-- - - - - - - - - - - - - - - - - - - - - - - - - - - - - - - - - - -
-- Downstream Channel Table
--
-- The Downstream Channel Table extends the downstream channel entries
-- in the MIB-II interfaces table [RFC 2233]. Both tables are indexed
-- with the same ifIndex object.
--
-- - - - - - - - - - - - - - - - - - - - - - - - - - - - - - - - - - -

dvbInaIfDsChTable OBJECT-TYPE
        SYNTAX      SEQUENCE OF DvbInaIfDsChEntry
        MAX-ACCESS  not-accessible
        STATUS      current
        DESCRIPTION

Pedersen         Informational - Expires August 2001               29
                     DVB Cable INA Interface MIB             Feb 2001


            "This table describes the attributes of downstream
            channels (frequency bands)."
        ::= { dvbInaIfDsCh 1 }

dvbInaIfDsChEntry OBJECT-TYPE
        SYNTAX      DvbInaIfDsChEntry
        MAX-ACCESS  not-accessible
        STATUS      current
        DESCRIPTION
            "List of attributes for a single Downstream channel.

            An entry in this table exists for each downstream
            ifEntry."
        INDEX { ifIndex }
        ::= { dvbInaIfDsChTable 1 }

DvbInaIfDsChEntry ::= SEQUENCE {
            dvbInaIfDsChFrequency               DownFrequency,
            dvbInaIfDsChConnections             Gauge32,
            dvbInaIfDsChTxPower                 INTEGER,
            dvbInaIfDsChDownCoaxId              Unsigned32,
            dvbInaIfDsChSymbolRate              DownstreamSymbolrate,
            dvbInaIfDsChModulation              Modulation,
            dvbInaIfDsChType                    INTEGER,
            dvbInaIfDsChDefaultPID              Unsigned32,
            dvbInaIfDsChProvFrequency           DownFrequency,
            dvbInaIfDsChProvDownstreamType      INTEGER,
            dvbInaIfDsChProvEnable              TruthValue,
            dvbInaIfDsChProvTableIndex          INTEGER
        }

dvbInaIfDsChFrequency OBJECT-TYPE
        SYNTAX      DownFrequency
        UNITS       "hertz"
        MAX-ACCESS  read-write
        STATUS      current
        DESCRIPTION
            " The centre of the downstream frequency associated with
            this channel. "
        DEFVAL { 70000000 }
        ::= { dvbInaIfDsChEntry 1 }

dvbInaIfDsChConnections OBJECT-TYPE
        SYNTAX      Gauge32
        MAX-ACCESS  read-only
        STATUS      current
        DESCRIPTION
            " Specifies the number of connections currently active for
            this down stream channel. "
        ::= { dvbInaIfDsChEntry 2 }

dvbInaIfDsChTxPower OBJECT-TYPE
        SYNTAX      INTEGER ( 0..255 )

Pedersen         Informational - Expires August 2001               30
                     DVB Cable INA Interface MIB             Feb 2001


        UNITS       "dBuV"
        MAX-ACCESS  read-write
        STATUS      current
        DESCRIPTION
            " Specifies the down stream transmission power in dBuV of
            this interface. "
        ::= { dvbInaIfDsChEntry 3 }

dvbInaIfDsChDownCoaxId OBJECT-TYPE
        SYNTAX      Unsigned32 ( 0..4294967295 )
        MAX-ACCESS  read-write
        STATUS      current
        DESCRIPTION
            "Specifies the coax ID of the Downstream HFC segment
            to which the downstream channel is connected.
            By default this parameter is zero. "
        DEFVAL { 0 }
        ::= { dvbInaIfDsChEntry 4 }

dvbInaIfDsChSymbolRate OBJECT-TYPE
        SYNTAX      DownstreamSymbolrate
        UNITS       "symbol/s"
        MAX-ACCESS  read-write
        STATUS      current
        DESCRIPTION
            " Specifies the symbol rate for the Downstream channel."
        ::= { dvbInaIfDsChEntry 5 }

dvbInaIfDsChModulation OBJECT-TYPE
        SYNTAX      Modulation
        MAX-ACCESS  read-write
        STATUS      current
        DESCRIPTION
            " Specifies the modulation for the Downstream channel."
        DEFVAL { qpsk }
        ::= { dvbInaIfDsChEntry 6 }

dvbInaIfDsChType    OBJECT-TYPE
        SYNTAX      INTEGER {
                    ib(1),
                    oob(2)
                    }
        MAX-ACCESS  read-write
        STATUS      current
        DESCRIPTION
            "Specifies if the Downstream channel is inband or
             out-of-band."
        ::= { dvbInaIfDsChEntry 7 }

dvbInaIfDsChDefaultPID          OBJECT-TYPE
        SYNTAX      Unsigned32 ( 0..8191 )
        MAX-ACCESS  read-write
        STATUS      current

Pedersen         Informational - Expires August 2001               31
                     DVB Cable INA Interface MIB             Feb 2001


        DESCRIPTION
            "The default value of the MPEG PID of the elementary
             stream that carries the data on this downstream.
             See also dvbInaIfConPID."
        ::= { dvbInaIfDsChEntry 8 }

dvbInaIfDsChProvFrequency       OBJECT-TYPE
        SYNTAX      DownFrequency
        MAX-ACCESS  read-write
        STATUS      current
        DESCRIPTION
            "Specifies the Downstream frequency of the provisioning
             channel.
             This setting is always used, no matter the provisioning
             channel is on this INA or on another.
             If the provisioning channel is on this INA, the value will
             be the frequency of one of the downstreams."
        REFERENCE
            "ES 200 800 Provisioning Channel Message"
        ::= { dvbInaIfDsChEntry 9 }

dvbInaIfDsChProvDownstreamType          OBJECT-TYPE
        SYNTAX      INTEGER ( 0..255 )
        MAX-ACCESS  read-write
        STATUS      current
        DESCRIPTION
            "Specifies the type of the downstream provisioning channel
             in the Provisioning Channel Message.
                0 = QAM_MPEG,
                1 = QPSK_1,544,
                2 = QPSK_3,088
                3..255 Reserved
             This setting is always used, no matter the provisioning
             channel is on this INA or on another.
             If the provisioning channel is on this INA, the value can
             be derived from the ib/oob type and modulation."
        REFERENCE
            "ES 200 800 Provisioning Channel Message"
        ::= { dvbInaIfDsChEntry 10 }

dvbInaIfDsChProvEnable                  OBJECT-TYPE
        SYNTAX      TruthValue
        MAX-ACCESS  read-write
        STATUS      current
        DESCRIPTION
            "Specifies if this downstream channel is a Provisioning
             channel and as such transmits the
             Default Configuration Message.
             true  = Provisioning channel
             false = not a Provisioning channel."
        REFERENCE
            "ES 200 800 Provisioning Channel Message"
        DEFVAL { true }

Pedersen         Informational - Expires August 2001               32
                     DVB Cable INA Interface MIB             Feb 2001


        ::= { dvbInaIfDsChEntry 11 }

dvbInaIfDsChProvTableIndex      OBJECT-TYPE
        SYNTAX      INTEGER ( 0..255 )
        MAX-ACCESS  read-write
        STATUS      current
        DESCRIPTION
            "If this downstream channel is a provisioning channel,
             then an index to the Provisioning tabel must be give here."
        ::= { dvbInaIfDsChEntry 12 }


-- - - - - - - - - - - - - - - - - - - - - - - - - - - - - - - - - - -
-- Upstream Channel Table
--
-- The upstream channel table extends the upstream channel entries in
-- the MIB-II interfaces table [RFC 2233]. Both tables are indexed withi
-- the same ifIndex object.
--
-- - - - - - - - - - - - - - - - - - - - - - - - - - - - - - - - - - -

dvbInaIfUsChTable OBJECT-TYPE
        SYNTAX      SEQUENCE OF DvbInaIfUsChEntry
        MAX-ACCESS  not-accessible
        STATUS      current
        DESCRIPTION
            "Describes the attributes of attached upstream channels
            (frequency bands)."
        ::= { dvbInaIfUsCh 1 }

dvbInaIfUsChEntry OBJECT-TYPE
        SYNTAX      DvbInaIfUsChEntry
        MAX-ACCESS  not-accessible
        STATUS      current
        DESCRIPTION
            "List of attributes for a single upstream channel.
            The state of the upstream channel depends on the state of
            the MAC and downstream channel. If one of both or both are
            non-operational also the state upstream channel(s) shall
            be ready.

            That in the case of Space division Multiplex SDM each
            upstream channel has a different non-zero Coax ID."

        INDEX { ifIndex }
        ::= { dvbInaIfUsChTable 1 }

DvbInaIfUsChEntry ::= SEQUENCE {
            dvbInaIfUsChFrequency                   UpFrequency,
            dvbInaIfUsChSymbolRate                  UpstreamSymbolrate,
            dvbInaIfUsChModulation                  Modulation,
            dvbInaIfUsChMacFlagSet                  MacFlagSet,
            dvbInaIfUsChId                          INTEGER,

Pedersen         Informational - Expires August 2001               33
                     DVB Cable INA Interface MIB             Feb 2001


            dvbInaIfUsChConnections                 Gauge32,
            dvbInaIfUsChCalibrationRxPower          INTEGER,
            dvbInaIfUsChUpCoaxId                    Unsigned32,
            dvbInaIfUsChDownCoaxId                  Unsigned32,
            dvbInaIfUsChAtmCells                    Counter64,
            dvbInaIfUsChAtmTimingErrors             Counter64,
            dvbInaIfUsChAtmPowerErrors              Counter64,
            dvbInaIfUsChAtmRSCorrectableErrors      Counter64,
            dvbInaIfUsChAtmRSNonCorrectableErrors   Counter64,
            dvbInaIfUsChAtmHecErrors                Counter64,
            dvbInaIfUsChAal5CrcErrors               Counter64,
            dvbInaIfUsChAtmCollisionErrors          Counter64
        }

dvbInaIfUsChFrequency OBJECT-TYPE
        SYNTAX      UpFrequency
        UNITS       "hertz"
        MAX-ACCESS  read-write
        STATUS      current
        DESCRIPTION
            " Specifies the frequency in Hz of the carrier used for
            this upstream channel. "
        ::= { dvbInaIfUsChEntry 1 }

dvbInaIfUsChSymbolRate OBJECT-TYPE
        SYNTAX      UpstreamSymbolrate
        MAX-ACCESS  read-write
        STATUS      current
        DESCRIPTION
            " Specifies the symbol rate for this upstream channel. "
        DEFVAL { sr1544000 }
        ::= { dvbInaIfUsChEntry 2 }

dvbInaIfUsChModulation OBJECT-TYPE
        SYNTAX      Modulation
        MAX-ACCESS  read-write
        STATUS      current
        DESCRIPTION
            " Specifies the modulation for this upstream channel. "
        DEFVAL { qpsk }
        ::= { dvbInaIfUsChEntry 3 }

dvbInaIfUsChMacFlagSet OBJECT-TYPE
        SYNTAX      MacFlagSet
        MAX-ACCESS  read-only
        STATUS      current
        DESCRIPTION
            " Specifies the MAC flag set assigned to this upstream
            channel. "
        ::= { dvbInaIfUsChEntry 4 }

dvbInaIfUsChId OBJECT-TYPE
        SYNTAX      INTEGER ( 0..255 )

Pedersen         Informational - Expires August 2001               34
                     DVB Cable INA Interface MIB             Feb 2001


        MAX-ACCESS  read-only
        STATUS      current
        DESCRIPTION
            " Specifies the logical channel number associated with this
            upstream channel. "
        ::= { dvbInaIfUsChEntry 5 }

dvbInaIfUsChConnections OBJECT-TYPE
        SYNTAX      Gauge32
        MAX-ACCESS  read-only
        STATUS      current
        DESCRIPTION
            " Specifies the number of connections currently active for
            this upstream channel. "
        ::= { dvbInaIfUsChEntry 6 }

dvbInaIfUsChCalibrationRxPower OBJECT-TYPE
        SYNTAX      INTEGER ( 0..255 )
        UNITS       "dBuV"
        MAX-ACCESS  read-write
        STATUS      current
        DESCRIPTION
            " Specifies the target receive signal power in dBuV to
            which the NIUs on this upstream channel are calibrated "
        ::= { dvbInaIfUsChEntry 9 }

dvbInaIfUsChUpCoaxId       OBJECT-TYPE
        SYNTAX      Unsigned32 ( 0..4294967295 )
        MAX-ACCESS  read-write
        STATUS      current
        DESCRIPTION
            "Specifies the coax ID of the UpStream HFC segment to
            which the upstream channel is connected.
            By default this parameter is zero."
        DEFVAL { 0 }
        ::= { dvbInaIfUsChEntry 10 }

dvbInaIfUsChDownCoaxId     OBJECT-TYPE
        SYNTAX      Unsigned32 ( 0..4294967295 )
        MAX-ACCESS  read-write
        STATUS      current
        DESCRIPTION
            "Specifies the coax ID of the Downstream HFC segment to
            which the upstream channel is connected.
            By default this parameter is zero."
        DEFVAL { 0 }
        ::= { dvbInaIfUsChEntry 11 }

dvbInaIfUsChAtmCells           OBJECT-TYPE
        SYNTAX      Counter64
        MAX-ACCESS  read-only
        STATUS      current
        DESCRIPTION

Pedersen         Informational - Expires August 2001               35
                     DVB Cable INA Interface MIB             Feb 2001


            "Total number of recieved ATM Cells.
             0 can indicate the counter is not supported."
        ::= { dvbInaIfUsChEntry 12 }

dvbInaIfUsChAtmTimingErrors    OBJECT-TYPE
        SYNTAX      Counter64
        MAX-ACCESS  read-only
        STATUS      current
        DESCRIPTION
            "Number of ATM Cells received with Timing Error.
             0 can indicate the counter is not supported."
        ::= { dvbInaIfUsChEntry 13 }

dvbInaIfUsChAtmPowerErrors     OBJECT-TYPE
        SYNTAX      Counter64
        MAX-ACCESS  read-only
        STATUS      current
        DESCRIPTION
            "Number of ATM Cells received with Signal Level Error.
             0 can indicate the counter is not supported."
        ::= { dvbInaIfUsChEntry 14 }

dvbInaIfUsChAtmRSCorrectableErrors OBJECT-TYPE
        SYNTAX      Counter64
        MAX-ACCESS  read-only
        STATUS      current
        DESCRIPTION
            "Number of ATM Cells received with correctable
             Reed-Solomon Errors.
             0 can indicate the counter is not supported."
        ::= { dvbInaIfUsChEntry 15 }

dvbInaIfUsChAtmRSNonCorrectableErrors OBJECT-TYPE
        SYNTAX      Counter64
        MAX-ACCESS  read-only
        STATUS      current
        DESCRIPTION
            "Number of ATM Cells received with non-correctable
             Reed-Solomon Errors.
             0 can indicate the counter is not supported."
        ::= { dvbInaIfUsChEntry 16 }

dvbInaIfUsChAtmHecErrors        OBJECT-TYPE
        SYNTAX      Counter64
        MAX-ACCESS  read-only
        STATUS      current
        DESCRIPTION
            "Number of ATM Cells received with HEC Error.
             0 can indicate the counter is not supported."
        ::= { dvbInaIfUsChEntry 17 }

dvbInaIfUsChAal5CrcErrors       OBJECT-TYPE
        SYNTAX      Counter64

Pedersen         Informational - Expires August 2001               36
                     DVB Cable INA Interface MIB             Feb 2001


        MAX-ACCESS  read-only
        STATUS      current
        DESCRIPTION
            "Number AAL5 frames received with CRC error.
             0 can indicate the counter is not supported."
        ::= { dvbInaIfUsChEntry 18 }

dvbInaIfUsChAtmCollisionErrors  OBJECT-TYPE
        SYNTAX      Counter64
        MAX-ACCESS  read-only
        STATUS      current
        DESCRIPTION
            "Number of ATM Cells received with Collision detected.
             0 can indicate the counter is not supported."
        ::= { dvbInaIfUsChEntry 19 }


-- - - - - - - - - - - - - - - - - - - - - - - - - - - - - - - - - - - -
-- Network Interface Unit (NIU) Table
--
-- The NIU table provides information on the NIUs connected to the INA.
-- The index into this table is the NIU MAC address
--
-- - - - - - - - - - - - - - - - - - - - - - - - - - - - - - - - - - - -

dvbInaIfNiuTable OBJECT-TYPE
        SYNTAX      SEQUENCE OF DvbInaIfNiuEntry
        MAX-ACCESS  not-accessible
        STATUS      current
        DESCRIPTION
            "Describes the attributes of Network Interface Units."
        ::= { dvbInaIfNiu 1 }

dvbInaIfNiuEntry OBJECT-TYPE
        SYNTAX      DvbInaIfNiuEntry
        MAX-ACCESS  not-accessible
        STATUS      current
        DESCRIPTION
            "Initially the table shall be empty. A new entry for a NIU
            is automatically created when the NIU in question signs on.
            Furthermore, the manager through the
            dvbInaIfNiuRowAccessStatus object can create new entries.
            This can be used in the case of re-provisioning where by
            the manager first makes an entry and sets all relevant
            parameters before the NIU is re-provisioned to this INA.

            When an entry is created for a NIU, also automatically an
            entry is created in the connection table for the default
            connection of the NIU in question.

            When a NIU entry is deleted, also all associated connection
            entries are deleted."


Pedersen         Informational - Expires August 2001               37
                     DVB Cable INA Interface MIB             Feb 2001


        INDEX { dvbInaIfNiuMacAddress }
        ::= { dvbInaIfNiuTable 1 }

DvbInaIfNiuEntry ::= SEQUENCE {
            dvbInaIfNiuMacAddress               MacAddress,
            dvbInaIfNiuRowAccessStatus          RowStatus,
            dvbInaIfNiuState                    INTEGER,
            dvbInaIfNiuDesiredState             INTEGER,
            dvbInaIfNiuDownIfIndex              InterfaceIndexOrZero,
            dvbInaIfNiuUpIfIndex                InterfaceIndexOrZero,
            dvbInaIfNiuUpTxLevel                INTEGER,
            dvbInaIfNiuTimeOffset               Integer32,
            dvbInaIfNiuStatus                   Unsigned32,
            dvbInaIfNiuErrorCode                Unsigned32,
            dvbInaIfNiuRetryCount               INTEGER,
            dvbInaIfNiuCapabilities             OCTET STRING,
            dvbInaIfNiuExtendedCapabilities     OCTET STRING,
            dvbInaIfNiuInitCompletionStatus     INTEGER,
            dvbInaIfNiuRequestStatus            INTEGER,
            dvbInaIfNiuResponseNumber           Counter32,
            dvbInaIfNiuRespTxLevel              INTEGER,
            dvbInaIfNiuRespTimeOffset           Integer32,
            dvbInaIfNiuRespOoBDownFrequency     DownFrequency,
            dvbInaIfNiuRespIBDownFrequency      DownFrequency,
            dvbInaIfNiuRespSNRLevel             INTEGER,
            dvbInaIfNiuRespRxLevel              INTEGER,
            dvbInaIfNiuDefaultConnectionId      Unsigned32,
            dvbInaIfNiuLifetime                 Unsigned32,
            dvbInaIfNiuGrantProtocolTimeOut     Unsigned32,
            dvbInaIfNiuSlotConfigurationErr     Counter32,
            dvbInaIfNiuAtmPacketLoss            Counter32,
            dvbInaIfNiuSlEsCrcErr               Counter32,
            dvbInaIfNiuSlEsFrameCount           Counter32,
            dvbInaIfNiuSlotConfigurationCount   Counter32,
            dvbInaIfNiuRSErrCorrectable         Counter32,
            dvbInaIfNiuRSErrNonCorrectable      Counter32,
            dvbInaIfNiuSignOnTime               TimeTicks,
            dvbInaIfNiuDsChBytes                Counter64,
            dvbInaIfNiuUsChBytes                Counter64,
            dvbInaIfNiuTimeRanging              Counter32,
            dvbInaIfNiuPowerRanging             Counter32
        }

dvbInaIfNiuMacAddress OBJECT-TYPE
        SYNTAX      MacAddress
        MAX-ACCESS  not-accessible
        STATUS      current
        DESCRIPTION
            " A 48-bit value representing the unique MAC address of
            the NIU. "
        ::= { dvbInaIfNiuEntry 1 }

dvbInaIfNiuRowAccessStatus OBJECT-TYPE

Pedersen         Informational - Expires August 2001               38
                     DVB Cable INA Interface MIB             Feb 2001


        SYNTAX      RowStatus
        MAX-ACCESS  read-create
        STATUS      current
        DESCRIPTION
            " Controls and reflects the status of this row in this
            table. "
        ::= { dvbInaIfNiuEntry 2 }

dvbInaIfNiuState    OBJECT-TYPE
        SYNTAX      INTEGER {
                    null(1),
                    ranging(2),
                    rangingAborted(3),
                    rangingComplete(4),
                    connecting(5),
                    connectComplete(6),
                    stopped(7)
                }
        MAX-ACCESS  read-only
        STATUS      current
        DESCRIPTION
            "Returned status information is the NIU status as
             assumed by the INA.
             The following states are possible:

               null(1)
                 Any state other than below.

               ranging(2):
                 The NIU has responded to a [MAC] Sign-on Request
                 Message but the time ranging and power calibration
                 is not yet complete.

               rangingAborted(3),
                 The INA has sent a Initalisation Complete Message
                 to the NIU with Completion_Status_Field != 0

               rangingComplete(4),
                 The INA has sent a Initalisation Complete Message
                 to the NIU with Completion_Status_Field = 0

               connecting(5),
                 The INA has sent a Connect Message for first
                 connection and is waiting for a Connect Response
                 Message from the NIU.

               connectComplete(6)
                 The INA has sent a Connect Confirm Message for first
                 connection to the NIU.

               stopped(7)
                 The NUI is in the stopped transmission state
                 after the INA has send a Stop_Upstream_Transmission to

Pedersen         Informational - Expires August 2001               39
                     DVB Cable INA Interface MIB             Feb 2001


                 the NIU and the NIU has returned a Link Management
                 Response.

            NOTE: The INA only needs to report states
                  it is able to detect."
        REFERENCE
            "ES 200 800 Sign-On and Calibration."
        ::= { dvbInaIfNiuEntry 3 }

dvbInaIfNiuDesiredState OBJECT-TYPE
        SYNTAX      INTEGER {
                    down(1),
                    start(2),
                    stop(3)
                    }
        MAX-ACCESS  read-create
        STATUS      current
        DESCRIPTION
            "Specifies the desired state of the NIU. This parameter
            can be set to one of the following values:
                down    : Initial state. Disable NIU operation.
                start   : Enable NIU operation.
                stop    : Stop upstream transmission from the NIU."

        ::= { dvbInaIfNiuEntry 4 }

dvbInaIfNiuDownIfIndex OBJECT-TYPE
        SYNTAX      InterfaceIndexOrZero
        MAX-ACCESS  read-only
        STATUS      current
        DESCRIPTION
            " Specifies the IfIndex of the downstream channel on which
            the NIU is tuned. "
        ::= { dvbInaIfNiuEntry 5 }

dvbInaIfNiuUpIfIndex OBJECT-TYPE
        SYNTAX      InterfaceIndexOrZero
        MAX-ACCESS  read-only
        STATUS      current
        DESCRIPTION
            " Specifies the IfIndex of the upstream channel that is
            used by the NIU. "
        ::= { dvbInaIfNiuEntry 6 }

dvbInaIfNiuUpTxLevel OBJECT-TYPE
        SYNTAX      INTEGER ( 0..255 )
        UNITS       "dBuV"
        MAX-ACCESS  read-only
        STATUS      current
        DESCRIPTION
            " Specifies the upstream transmit level. This is the INA
            notion of NIU transmit level. (See also
            'dvbInaIfNiuRespTxLevel'.) "

Pedersen         Informational - Expires August 2001               40
                     DVB Cable INA Interface MIB             Feb 2001


        ::= { dvbInaIfNiuEntry 7 }

dvbInaIfNiuTimeOffset OBJECT-TYPE
        SYNTAX      Integer32 ( -32768..32767 )
        UNITS       "100ns"
        MAX-ACCESS  read-only
        STATUS      current
        DESCRIPTION
            " Specifies the time offset. This is the INA notion of NIU
            time offset. (See also 'dvbInaIfNiuRespTimeOffset'.) "
        ::= { dvbInaIfNiuEntry 8 }

dvbInaIfNiuStatus OBJECT-TYPE
        SYNTAX      Unsigned32 ( 0..4294967295 )
        MAX-ACCESS  read-only
        STATUS      current
        DESCRIPTION
            " This 32-bit object specifies the status of this NIU. See
            <MAC> Sign-On Response Message and <MAC> Status Response
            Message [1] for the exact bit assignment. This object is
            updated after the reception of a <MAC> Status Response
            Message [1]. "
        REFERENCE
            "ES 200 800 Sign-on Response Message"
        ::= { dvbInaIfNiuEntry 9 }

dvbInaIfNiuErrorCode OBJECT-TYPE
        SYNTAX      Unsigned32 ( 0..65535 )
        MAX-ACCESS  read-only
        STATUS      current
        DESCRIPTION
            " This 16-bit object specifies the error code in the <MAC>
            Sign-On Response Message. See ES 200 800 for the exact bit
            assignment. "
        REFERENCE
            "ES 200 800 Sign-on Response Message"
        ::= { dvbInaIfNiuEntry 10 }

dvbInaIfNiuRetryCount OBJECT-TYPE
        SYNTAX      INTEGER ( 0..255 )
        MAX-ACCESS  read-only
        STATUS      current
        DESCRIPTION
            " This 8-bit object specifies the number of transmissions
            of the <MAC> Sign-On Response Message. (See [1]). "
        REFERENCE
            "ES 200 800 Sign-on Response Message"
        ::= { dvbInaIfNiuEntry 11 }

dvbInaIfNiuCapabilities             OBJECT-TYPE
        SYNTAX      OCTET STRING ( SIZE (4))
        MAX-ACCESS  read-only
        STATUS      current

Pedersen         Informational - Expires August 2001               41
                     DVB Cable INA Interface MIB             Feb 2001


        DESCRIPTION
            " This 32-bit object specifies the capabilities of this NIU.
            See also ES 200 800 for the bit assignment."
        REFERENCE
            "See the [MAC] Sign-On Response Message in ES 200.800"
        ::= { dvbInaIfNiuEntry 12 }

dvbInaIfNiuExtendedCapabilities     OBJECT-TYPE
        SYNTAX      OCTET STRING ( SIZE (4))
        MAX-ACCESS  read-only
        STATUS      current
        DESCRIPTION
            " This 32-bit object specifies the extended capabilities
            of this NIU.
            See also ES 200 800 and ECR 5 for the bit assignment."
        REFERENCE
            "See the [MAC] Sign-On Response Message in ES 200.800"
        ::= { dvbInaIfNiuEntry 13 }

dvbInaIfNiuInitCompletionStatus OBJECT-TYPE
        SYNTAX      INTEGER ( 0..255 )
        MAX-ACCESS  read-only
        STATUS      current
        DESCRIPTION
            " This 8-bit object indicates the errors in the
            initialisation phase of this NIU. See the <MAC>
            Initialization Complete Message ES 200 800 for the exact bit
            assignment. "
        ::= { dvbInaIfNiuEntry 14 }

dvbInaIfNiuRequestStatus OBJECT-TYPE
        SYNTAX      INTEGER {
            niuReqAddressPars(0),
            niuReqErrorPars(1),
            niuReqConnectionsPars(2),
            niuReqPhyLayerPars(3)
        }
        MAX-ACCESS  read-create
        STATUS      current
        DESCRIPTION
            "This object triggers the transmission of a <MAC> Status
             Request Message [1]. This parameter can be set to one of
             the following parameters: 'NiuReqAddressPars(0)': request
             address parameters, 'NiuReqErrorPars(1)': request
             error parameters, 'NiuReqConnectionsPars(2)': request
             connection parameters, and 'NiuReqPhyLayerPars(3)':
             request physical layer parameters.
             When read this object returns 'NiuReqAddressPars(0)'."
        DEFVAL { niuReqAddressPars }
        ::= { dvbInaIfNiuEntry 15 }

dvbInaIfNiuResponseNumber OBJECT-TYPE
        SYNTAX      Counter32

Pedersen         Informational - Expires August 2001               42
                     DVB Cable INA Interface MIB             Feb 2001


        MAX-ACCESS  read-only
        STATUS      current
        DESCRIPTION
            " This object is incremented when a <MAC> Status Response
            Message [1] is received. This object can be polled to
            detect the reception of this message. After reset this
            object is zero. "
        ::= { dvbInaIfNiuEntry 16 }

dvbInaIfNiuRespTxLevel OBJECT-TYPE
        SYNTAX      INTEGER ( 0..255 )
        UNITS       ".5 dBuV"
        MAX-ACCESS  read-only
        STATUS      current
        DESCRIPTION
            " Specifies the transmit power level of the NIU. This
            object is updated after the reception of a <MAC> Status
            Response Message [1] that is a response on the
            'NiuReqPhyLayerPars(3)' request. "
        ::= { dvbInaIfNiuEntry 17 }

dvbInaIfNiuRespTimeOffset OBJECT-TYPE
        SYNTAX      Integer32 ( -32768..32767 )
        UNITS       "100ns"
        MAX-ACCESS  read-only
        STATUS      current
        DESCRIPTION
            " Specifies the time offset of the NIU. This object is
            updated after the reception of a <MAC> Status Response
            Message [1] that is a response on the
            'NiuReqPhyLayerPars(3)' request. "
        ::= { dvbInaIfNiuEntry 18 }

dvbInaIfNiuRespOoBDownFrequency OBJECT-TYPE
        SYNTAX      DownFrequency
        MAX-ACCESS  read-only
        STATUS      current
        DESCRIPTION
            " Specifies the OoB downstream frequency of the NIU. This
            object is updated after the reception of a <MAC> Status
            Response Message [1] that is a response on the
            'NiuReqPhyLayerPars(3)' request. "
        ::= { dvbInaIfNiuEntry 19 }

dvbInaIfNiuRespIBDownFrequency OBJECT-TYPE
        SYNTAX      DownFrequency
        MAX-ACCESS  read-only
        STATUS      current
        DESCRIPTION
            " Specifies the IB downstream frequency of the NIU. This
            object is updated after the reception of a <MAC> Status
            Response Message [1] that is a response on the
            'NiuReqPhyLayerPars(3)' request. "

Pedersen         Informational - Expires August 2001               43
                     DVB Cable INA Interface MIB             Feb 2001


        ::= { dvbInaIfNiuEntry 20 }

dvbInaIfNiuRespSNRLevel OBJECT-TYPE
        SYNTAX      INTEGER ( 0..255 )
        UNITS       "dB"
        MAX-ACCESS  read-only
        STATUS      current
        DESCRIPTION
            " Specifies the estimated SNR level at the RF input of
            the NIU.  This object is updated after the reception of
            a <MAC> Status Response Message [1] that is a response
            on the 'NiuReqPhyLayerPars(3)' request. "
        ::= { dvbInaIfNiuEntry 21 }

dvbInaIfNiuRespRxLevel OBJECT-TYPE
        SYNTAX      INTEGER ( 0..255 )
        UNITS       "dBuV"
        MAX-ACCESS  read-only
        STATUS      current
        DESCRIPTION
            " Specifies the estimated downstream power level of the
            MAC messages at the RF input of the NIU. This object is
            updated after the reception of a <MAC> Status Response
            Message [1] that is a response on the
            'NiuReqPhyLayerPars(3)' request. "
        ::= { dvbInaIfNiuEntry 22 }

dvbInaIfNiuDefaultConnectionId OBJECT-TYPE
        SYNTAX      Unsigned32 ( 0..4294967295 )
        MAX-ACCESS  read-create
        STATUS      current
        DESCRIPTION
            " Specifies the ConnectionId of the default connection
            that is assigned to this NIU. "
        ::= { dvbInaIfNiuEntry 23 }

dvbInaIfNiuLifetime OBJECT-TYPE
        SYNTAX      Unsigned32 ( 0..4294967295 )
        UNITS       "s"
        MAX-ACCESS  read-create
        STATUS      current
        DESCRIPTION
            "Defines how long after the NIU was signed off,
             the entry is removed from the table.
             An infinite(0) value would mean that the values are
             stored at least until the next reboot of the INA."
        DEFVAL { 300 }
        ::= { dvbInaIfNiuEntry 24 }

dvbInaIfNiuGrantProtocolTimeOut     OBJECT-TYPE
        SYNTAX      Unsigned32 ( 0..65535 )
        UNITS       "ms"
        MAX-ACCESS  read-create

Pedersen         Informational - Expires August 2001               44
                     DVB Cable INA Interface MIB             Feb 2001


        STATUS      current
        DESCRIPTION
            "The time that the NIU should wait before
            verifying the status of pending grants.
            Default value is dvbInaIfMacGrantProtocolTimeOut."
        ::= { dvbInaIfNiuEntry 25 }

dvbInaIfNiuSlotConfigurationErr OBJECT-TYPE
        SYNTAX      Counter32
        MAX-ACCESS  read-only
        STATUS      current
        DESCRIPTION
            "NIU Error Parameter: Slot_Configuration_CRC_Error_Count,
             the number of errors in Slot_Configuration_Count R bytes,
             as found by the CRC decoder."
        ::= { dvbInaIfNiuEntry 26 }

dvbInaIfNiuAtmPacketLoss OBJECT-TYPE
        SYNTAX      Counter32
        MAX-ACCESS  read-only
        STATUS      current
        DESCRIPTION
            "NIU Error Parameter: ATM_Packet_Loss_Count,
             the number of received ATM cells that were lost,
             either due to unrecoverable Reed-Solomon errors or
             because of an erroneous HEC of the ATM cell header."
        ::= { dvbInaIfNiuEntry 27 }

dvbInaIfNiuSlEsCrcErr OBJECT-TYPE
        SYNTAX      Counter32
        MAX-ACCESS  read-only
        STATUS      current
        DESCRIPTION
            "Niu Error Parameter: SL-ESF_CRC_Error_Count,
             the number of CRC errors found in consecutive C1-C6."
        ::= { dvbInaIfNiuEntry 28 }

dvbInaIfNiuSlEsFrameCount OBJECT-TYPE
        SYNTAX      Counter32
        MAX-ACCESS  read-only
        STATUS      current
        DESCRIPTION
            "NIU Error Parameter: SL-ESF_Frame_Count,
             the number of frames the statistics apply to."
        ::= { dvbInaIfNiuEntry 29 }

dvbInaIfNiuSlotConfigurationCount OBJECT-TYPE
        SYNTAX      Counter32
        MAX-ACCESS  read-only
        STATUS      current
        DESCRIPTION
            "NIU Error Parameter: Slot_Configuration_Count,
             the number of R-byte sets (Rxa-Rxc) used to calculate

Pedersen         Informational - Expires August 2001               45
                     DVB Cable INA Interface MIB             Feb 2001


             Slot_Configuration_CRC_Error_Count."
        ::= { dvbInaIfNiuEntry 30 }

dvbInaIfNiuRSErrCorrectable OBJECT-TYPE
        SYNTAX      Counter32
        MAX-ACCESS  read-only
        STATUS      current
        DESCRIPTION
            "NIU Error Parameter: Reed_Solomon_Errors_Correctable,
             MPEG frames received with correctable Reed-Solomon
             Errors (IB only)."
        ::= { dvbInaIfNiuEntry 31 }

dvbInaIfNiuRSErrNonCorrectable OBJECT-TYPE
        SYNTAX      Counter32
        MAX-ACCESS  read-only
        STATUS      current
        DESCRIPTION
            "NIU Error Parameter: Reed_Solomon_Errors_Non_Correctable,
             MPEG frames received with non-correctable
             Reed-Solomon Errors (IB only)."
        ::= { dvbInaIfNiuEntry 32 }

dvbInaIfNiuSignOnTime OBJECT-TYPE
        SYNTAX      TimeTicks
        MAX-ACCESS  read-only
        STATUS      current
        DESCRIPTION
            "The value of sysUpTime at the time this NIU was signed on.
             If the time is unknown, this value shall be zero."
        ::= { dvbInaIfNiuEntry 33 }

dvbInaIfNiuDsChBytes     OBJECT-TYPE
        SYNTAX      Counter64
        MAX-ACCESS  read-only
        STATUS      current
        DESCRIPTION
            "Number of bytes sent in direction INA to NIU."
        ::= { dvbInaIfNiuEntry 34 }

dvbInaIfNiuUsChBytes     OBJECT-TYPE
        SYNTAX      Counter64
        MAX-ACCESS  read-only
        STATUS      current
        DESCRIPTION
            "Number of bytes sent in direction NIU to INA.
             Includes backbone, NIU-to-NIU and
             broadcast/multicast traffic."
        ::= { dvbInaIfNiuEntry 35 }

dvbInaIfNiuTimeRanging OBJECT-TYPE
        SYNTAX      Counter32
        MAX-ACCESS  read-only

Pedersen         Informational - Expires August 2001               46
                     DVB Cable INA Interface MIB             Feb 2001


        STATUS      current
        DESCRIPTION
            "Number of times the NIU has been time ranged."
        ::= { dvbInaIfNiuEntry 36 }

dvbInaIfNiuPowerRanging OBJECT-TYPE
        SYNTAX      Counter32
        MAX-ACCESS  read-only
        STATUS      current
        DESCRIPTION
            "Number of times the NIU has been power ranged."
        ::= { dvbInaIfNiuEntry 37 }


-- - - - - - - - - - - - - - - - - - - - - - - - - - - - - - - - - - -
-- Connection Table
--
-- The Connection Table contains information about DVB-RC MAC
-- connections.
-- Indices into this table are the MAC address and the Connection ID.
--
-- - - - - - - - - - - - - - - - - - - - - - - - - - - - - - - - - - -

dvbInaIfConTable OBJECT-TYPE
        SYNTAX      SEQUENCE OF DvbInaIfConEntry
        MAX-ACCESS  not-accessible
        STATUS      current
        DESCRIPTION
            " Contains information about DVB-RC MAC connections. "
        ::= { dvbInaIfConnection 1 }

dvbInaIfConEntry OBJECT-TYPE
        SYNTAX      DvbInaIfConEntry
        MAX-ACCESS  not-accessible
        STATUS      current
        DESCRIPTION
            "Initially the table shall be empty. A new entry for a
            connection is automatically generated when a <MAC> Resource
            Request Message is received from the NIU in question
            requesting a new connection.
            Also during reprovisioning new entries are created.

            Furthermore, the manager through the dvbInaIfConAccessStatus
            object can create new entries.

            Connection table entries shall be deleted, when the
            associated NIU entry is deleted. Furthermore, the manager
            can delete unused connection entries.

            The following parameters can only be set when the connection
            is in state down(1)

            dvbInaIfConAccessStatus,

Pedersen         Informational - Expires August 2001               47
                     DVB Cable INA Interface MIB             Feb 2001


            dvbInaIfConEncapsulation,
            dvbInaIfConFilterMACAddress,
            dvbInaIfConPID."

        INDEX { dvbInaIfConNiuMacAddress, dvbInaIfConConnectionId }
        ::= { dvbInaIfConTable 1 }

DvbInaIfConEntry ::= SEQUENCE {
            dvbInaIfConNiuMacAddress                MacAddress,
            dvbInaIfConConnectionId                 Unsigned32,
            dvbInaIfConCurrentState                 INTEGER,
            dvbInaIfConDesiredState                 INTEGER,
            dvbInaIfConConnectionType               BITS,
            dvbInaIfConAccessStatus                 RowStatus,
            dvbInaIfConEncapsulation                INTEGER,
            dvbInaIfConAtmDownstreamVCC             Unsigned32,
            dvbInaIfConAtmUpstreamVCC               Unsigned32,
            dvbInaIfConFilterMACAddress             MacAddress,
            dvbInaIfConPID                          Unsigned32,
            dvbInaIfConMaxContentionMsgLen          INTEGER,
            dvbInaIfConMaxReservationMsgLen         INTEGER,
            dvbInaIfConAuxFlags                     INTEGER
        }

dvbInaIfConNiuMacAddress OBJECT-TYPE
        SYNTAX      MacAddress
        MAX-ACCESS  not-accessible
        STATUS      current
        DESCRIPTION
            "MAC address of the NIU that is associated with the
             connection."
        ::= { dvbInaIfConEntry 1 }

dvbInaIfConConnectionId OBJECT-TYPE
        SYNTAX      Unsigned32 ( 0..4294967295 )
        MAX-ACCESS  not-accessible
        STATUS      current
        DESCRIPTION
            "Specifies the connection identifier to be used for this
             connection."
        ::= { dvbInaIfConEntry 2 }

dvbInaIfConCurrentState OBJECT-TYPE
        SYNTAX      INTEGER {
            down(1),
            settingUp(2),
            up(3),
            breakingDown(4),
            downAlloc(5),
            alarm(6)
        }
        MAX-ACCESS  read-only
        STATUS      current

Pedersen         Informational - Expires August 2001               48
                     DVB Cable INA Interface MIB             Feb 2001


        DESCRIPTION
        "Current state of the connection.
         The following states are possible:
         down(1)          In this state an entry is made in the
                          connection table for the connection in
                          question. However, there is not (yet) any
                          connection on MAC layer between the INA
                          and NIU.
         settingUp(2)     Either the NIU in question has requested
                          a connection via a [MAC] Resource Request
                          message, or the manager has initiated
                          a (new) connection by setting
                          dvbInaConDesiredState to the state Up.
         up(3)            In this state the connection in question
                          is up and running.
         breakingDown(4)  Either the NIU in question has requested
                          to release the connection via a [MAC]
                          Resource Request message, or the manager
                          has initiated the release of the
                          connection by setting dvbInaConDesiredState
                          to the state: Down.
         downAlloc(5)     In this state an entry is made in the
                          connection table for the connection in
                          question. Furthermore, the bandwidth
                          for the fixed rate connection is allocated.
                          However, the connection doesn't (yet)
                          exist on MAC layer between the INA and NIU.
         alarm(6)         The connection in question is in the alarm
                          state. his means that either the parameter
                          setting is not valid, or the scheduler of
                          the MAC has not the resources to allocate
                          the requested bandwidth for a fixed rate
                          connection, or the NIU didn't response in
                          time during the set-up of the connection or
                          during the break down of it. This state
                          shall be left, when either the manager sets
                          dvbInaConDesiredState to Down(1) or,
                          the NIU enters the Null(1) state."
        ::= { dvbInaIfConEntry 3 }

dvbInaIfConDesiredState OBJECT-TYPE
        SYNTAX      INTEGER {
            down(1),
            up(3),
            downAlloc(5)
        }
        MAX-ACCESS  read-create
        STATUS      current
        DESCRIPTION
            " Desired state for the connection. The following desired
            states are possible: down(1), up(3) and, downAlloc(5). "
        ::= { dvbInaIfConEntry 4 }


Pedersen         Informational - Expires August 2001               49
                     DVB Cable INA Interface MIB             Feb 2001


dvbInaIfConConnectionType OBJECT-TYPE
        SYNTAX      BITS {
            conTypeFixedRate(0),
            conTypeContention(1),
            conTypeReservation(2)
        }
        MAX-ACCESS  read-create
        STATUS      current
        DESCRIPTION
            "Specifies the kind of connection: fixed rate, contention
            based, or reservation based. This parameter can be set to
            a value that is an OR of the following bits:
                'conTypeFixedRate(0)'
                'conTypeContention(1)'
                'conTypeReservation(2)'
            Default this object is 'conTypeContention(1)'."
        DEFVAL {{ conTypeContention }}
        ::= { dvbInaIfConEntry 5 }

dvbInaIfConAccessStatus OBJECT-TYPE
        SYNTAX      RowStatus
        MAX-ACCESS  read-create
        STATUS      current
        DESCRIPTION
            "Controls and reflects the status of this row in this
            table."
        ::= { dvbInaIfConEntry 6 }

dvbInaIfConEncapsulation OBJECT-TYPE
        SYNTAX      INTEGER {
            directIp(1),
            ethernetMacBridging(2),
            ppp(3)
        }
        MAX-ACCESS  read-create
        STATUS      current
        DESCRIPTION
            "This object indicates the type of encapsulation provided
             on this connection. This object can have one of the
             following values: 'directIp(1)',
             'ethernetMacBridging(2)', or 'ppp(3)'. By default this
             parameter is set to 'directIp(1)'."
        DEFVAL { directIp }
        ::= { dvbInaIfConEntry 7 }

dvbInaIfConAtmDownstreamVCC OBJECT-TYPE
        SYNTAX      Unsigned32 (0..16777215)
        MAX-ACCESS  read-only
        STATUS      current
        DESCRIPTION
            "ATM concatenated VPI and VCI Virtual Path Identifiers
            that is used for downstream OoB transmission."
        ::= { dvbInaIfConEntry 8 }

Pedersen         Informational - Expires August 2001               50
                     DVB Cable INA Interface MIB             Feb 2001



dvbInaIfConAtmUpstreamVCC OBJECT-TYPE
        SYNTAX      Unsigned32 (0..16777215)
        MAX-ACCESS  read-only
        STATUS      current
        DESCRIPTION
            "ATM concatenated VPI and VCI Virtual Path Identifiers
            that is used for upstream transmission."
        ::= { dvbInaIfConEntry 9 }

dvbInaIfConFilterMACAddress OBJECT-TYPE
        SYNTAX      MacAddress
        MAX-ACCESS  read-create
        STATUS      current
        DESCRIPTION
            "Specifies the 'soft' MPEG MPE MAC address used to
            filter the data out of the downstream IB transmission.
            This is found in the Downstream_Multiprotocol_CBD
            substructure in the Connect Message."
        ::= { dvbInaIfConEntry 10 }

dvbInaIfConPID OBJECT-TYPE
        SYNTAX      Unsigned32 ( 0..8191 )
        MAX-ACCESS  read-create
        STATUS      current
        DESCRIPTION
            "Specifies the MPEG PID of the elementary stream that
            carries the data."
        ::= { dvbInaIfConEntry 11 }

dvbInaIfConMaxContentionMsgLen OBJECT-TYPE
        SYNTAX      INTEGER ( 1..255 )
        UNITS       "ATM cells"
        MAX-ACCESS  read-create
        STATUS      current
        DESCRIPTION
            "The Maximum_Contention_Access_Message_Length
             in the Connect Message.
             This is the maximum length of a message that may be
             transmitted using contention access.
             Any message greater than this should use reservation
             access.
             The default value should be
             dvbInaIfMacMaxContentionMsgLen."
        REFERENCE
            "ES 200 800 Connect_Message"
        ::= { dvbInaIfConEntry 12 }

dvbInaIfConMaxReservationMsgLen OBJECT-TYPE
        SYNTAX      INTEGER ( 0..255 )
        UNITS       "ATM cells"
        MAX-ACCESS  read-create
        STATUS      current

Pedersen         Informational - Expires August 2001               51
                     DVB Cable INA Interface MIB             Feb 2001


        DESCRIPTION
            "This is the maximum length of a message that may be
             transmitted using a single reservation access.
             Any message greater than this should be transmitted by
             making multiple reservation requests.
             The default value should be
             dvbInaIfMacMaxReservationMsgLen."
        REFERENCE
            "ES 200 800 Connect Message."
        ::= { dvbInaIfConEntry 13 }

dvbInaIfConAuxFlags OBJECT-TYPE
        SYNTAX      INTEGER ( 0..255 )
        MAX-ACCESS  read-only
        STATUS      current
        DESCRIPTION
            "The Connection_Control_Field_Aux from the Connect Message
             Structure.
             This is used to indicate if the Priority, Downstream
             flowspec and Session binding objects are used
             for the connection."
        REFERENCE
            "ES 200 800 Connect Message."
        ::= { dvbInaIfConEntry 14 }


-- - - - - - - - - - - - - - - - - - - - - - - - - - - - - - - - - - -
-- Connection Quality Table
--
-- The Connection Quality Table entends the Connection table
-- with information about the connection quality.
--
-- The indexes are the same as for the Connection Table -
-- the NIU MAC address and the Connection ID.
--
-- - - - - - - - - - - - - - - - - - - - - - - - - - - - - - - - - - -
dvbInaIfConQosTable OBJECT-TYPE
        SYNTAX      SEQUENCE OF DvbInaIfConQosEntry
        MAX-ACCESS  not-accessible
        STATUS      current
        DESCRIPTION
            "Contains information about connection quality for
             DVB-RC MAC connections.
             Both upstream and downstream quality parameters are found."
        ::= { dvbInaIfConnection 2 }

dvbInaIfConQosEntry OBJECT-TYPE
        SYNTAX      DvbInaIfConQosEntry
        MAX-ACCESS  not-accessible
        STATUS      current
        DESCRIPTION
            "An entry in the table is automatically created when
             a new entry in the connection table connection is created

Pedersen         Informational - Expires August 2001               52
                     DVB Cable INA Interface MIB             Feb 2001


             and the INA supports Quality of Service on the MAC layer.
             You must always create an entry in the Connection table
             first and this will automatically create an entry in
             the QoS table.

             The entries are deleted when the contection table entry
             is deleted."
        INDEX { dvbInaIfConNiuMacAddress, dvbInaIfConConnectionId }
        ::= { dvbInaIfConQosTable 1 }

DvbInaIfConQosEntry ::= SEQUENCE {
            dvbInaIfConQosPriority                  INTEGER,
            dvbInaIfConQosDsReqMaxPacketSize        Unsigned32,
            dvbInaIfConQosDsReqBitrate              Unsigned32,
            dvbInaIfConQosDsReqJitter               INTEGER,
            dvbInaIfConQosDsAllocMaxPacketSize      Unsigned32,
            dvbInaIfConQosDsAllocBitrate            Unsigned32,
            dvbInaIfConQosDsAllocJitter             INTEGER,
            dvbInaIfConQosUsReqBw                   Unsigned32,
            dvbInaIfConQosUsReqMaxDistSlots         Unsigned32,
            dvbInaIfConQosUsReqFrameLength          Unsigned32,
            dvbInaIfConQosUsAllocBw                 Unsigned32,
            dvbInaIfConQosUsAllocMaxDistSlots       Unsigned32,
            dvbInaIfConQosUsAllocFrameLength        Unsigned32,
            dvbInaIfConQosUsReqFixedRateMethod      INTEGER,
            dvbInaIfConQosUsAllocFixedRateMethod    INTEGER
        }

dvbInaIfConQosPriority                  OBJECT-TYPE
        SYNTAX      INTEGER ( 0..255 )
        MAX-ACCESS  read-write
        STATUS      current
        DESCRIPTION
            "The priority of the connection.
             Connections with low priority field value can be
             reprovisioned in order to accommodate the requirements
             of connections with high priority field.
                Standard data flow applications     0-79
                Applications with QoS requirements  80-200
                High priority applications          201-255"
        REFERENCE
            "ES 200 800 Resource Request Message"
        ::= { dvbInaIfConQosEntry 1 }

dvbInaIfConQosDsReqMaxPacketSize        OBJECT-TYPE
        SYNTAX      Unsigned32 ( 0..65535 )
        MAX-ACCESS  read-write
        STATUS      current
        DESCRIPTION
            "A downstream QoS parameter. Defines the requested
             maximum packet size in the downstream.
             The parameter can be set either by the managment system,
             or by the INA according to the NIU resource request.

Pedersen         Informational - Expires August 2001               53
                     DVB Cable INA Interface MIB             Feb 2001


             The packet size includes propriety protocols header,
             transport protocol (UDP/TCP) header, and the IP header.
             The packet size does not include the Ethernet header."
        REFERENCE
            "ES 200 800 Resource Request Message"
        ::= { dvbInaIfConQosEntry 2 }

dvbInaIfConQosDsReqBitrate              OBJECT-TYPE
        SYNTAX      Unsigned32 ( 0..65535 )
        UNITS       "bytes/s"
        MAX-ACCESS  read-write
        STATUS      current
        DESCRIPTION
            "A downstream QoS parameter. Defines requested average
             bit rate in the downstream. The parameter can be set
             either by the managment system, or by the INA according
             to the NIU resource request."
        REFERENCE
            "ES 200 800 Resource Request Message"
        ::= { dvbInaIfConQosEntry 3 }

dvbInaIfConQosDsReqJitter               OBJECT-TYPE
        SYNTAX      INTEGER ( 0..255 )
        UNITS       "ms"
        MAX-ACCESS  read-write
        STATUS      current
        DESCRIPTION
            "A downstream QoS parameter. Defines the requested
             maximum allowed jitter in the downstream.
             The parameter can be set either by the managment system,
             or by the INA according to the NIU resource request."
        REFERENCE
            "ES 200 800 Resource Request Message"
        ::= { dvbInaIfConQosEntry 4 }

dvbInaIfConQosDsAllocMaxPacketSize      OBJECT-TYPE
        SYNTAX      Unsigned32 ( 0..65535 )
        MAX-ACCESS  read-only
        STATUS      current
        DESCRIPTION
            "A downstream QoS parameter. This is the actual
             maximum packet size supported by the INA in the downstream.
             The packet size includes propriety protocols header,
             transport protocol (UDP/TCP) header, and the IP header.
             The packet size does not include the Ethernet header."
        REFERENCE
            "ES 200 800 Resource Request Message"
        ::= { dvbInaIfConQosEntry 5 }

dvbInaIfConQosDsAllocBitrate            OBJECT-TYPE
        SYNTAX      Unsigned32 ( 0..65535 )
        UNITS       "bytes/s"
        MAX-ACCESS  read-only

Pedersen         Informational - Expires August 2001               54
                     DVB Cable INA Interface MIB             Feb 2001


        STATUS      current
        DESCRIPTION
            "A downstream QoS parameter. This is the actual average
             bit rate supported by the INA in the downstream."
        REFERENCE
            "ES 200 800 Resource Request Message"
        ::= { dvbInaIfConQosEntry 6 }

dvbInaIfConQosDsAllocJitter             OBJECT-TYPE
        SYNTAX      INTEGER ( 0..255 )
        UNITS       "ms"
        MAX-ACCESS  read-only
        STATUS      current
        DESCRIPTION
            "A downstream QoS parameter. This is the actual
             maximum jitter supported by the INA in the downstream."
        REFERENCE
            "ES 200 800 Resource Request Message"
        ::= { dvbInaIfConQosEntry 7 }

dvbInaIfConQosUsReqBw                   OBJECT-TYPE
        SYNTAX      Unsigned32 ( 0..16777215 )
        UNITS       "slots/1200 ms"
        MAX-ACCESS  read-write
        STATUS      current
        DESCRIPTION
            "An upstream QoS parameter. The requested bandwidth
             for the upstream.
             The parameter can be set either by the managment system,
             or by the INA according to the NIU resource request."
        REFERENCE
            "ES 200 800 Resource Request Message"
        ::= { dvbInaIfConQosEntry 8 }

dvbInaIfConQosUsReqMaxDistSlots         OBJECT-TYPE
        SYNTAX      Unsigned32 ( 0..65535 )
        UNITS       "slots"
        MAX-ACCESS  read-write
        STATUS      current
        DESCRIPTION
            "An upstream QoS parameter. The requested maximum
             distance between slots for the upstream.
             The parameter can be set either by the managment system,
             or by the INA according to the NIU resource request."
        REFERENCE
            "ES 200 800 Resource Request Message"
        ::= { dvbInaIfConQosEntry 9 }

dvbInaIfConQosUsReqFrameLength          OBJECT-TYPE
        SYNTAX      Unsigned32 ( 0..65535 )
        MAX-ACCESS  read-write
        STATUS      current
        DESCRIPTION

Pedersen         Informational - Expires August 2001               55
                     DVB Cable INA Interface MIB             Feb 2001


            "An upstream QoS parameter. The requested frame
             length for the upstream.
             The parameter can be set either by the managment system,
             or by the INA according to the NIU resource request."
        REFERENCE
            "ES 200 800 Connect Message."
        ::= { dvbInaIfConQosEntry 10 }

dvbInaIfConQosUsAllocBw                 OBJECT-TYPE
        SYNTAX      Unsigned32 ( 0..16777215 )
        UNITS       "slots/1200 ms"
        MAX-ACCESS  read-only
        STATUS      current
        DESCRIPTION
            "An upstream QoS parameter. The actual allocated bandwidth
             for the upstream."
        REFERENCE
            "ES 200 800 Connect Message"
        ::= { dvbInaIfConQosEntry 11 }

dvbInaIfConQosUsAllocMaxDistSlots       OBJECT-TYPE
        SYNTAX      Unsigned32 ( 0..65535 )
        UNITS       "slots"
        MAX-ACCESS  read-only
        STATUS      current
        DESCRIPTION
            "An upstream QoS parameter. The allocated distance
             between slots for the upstream.
             In case of using a cyclic assignment, this is the
             parameter sent by the INA in the connect message.
             In the case of reservation access, this parameter is an
             average number, calculated by the INA to reflect the
             actual allocation."
        REFERENCE
            "ES 200 800 Connect Message"
        ::= { dvbInaIfConQosEntry 12 }

dvbInaIfConQosUsAllocFrameLength        OBJECT-TYPE
        SYNTAX      Unsigned32 ( 0..65535 )
        MAX-ACCESS  read-only
        STATUS      current
        DESCRIPTION
            "An upstream QoS parameter. The allocated frame length
             for the upstream.
             In case of using a cyclic assignment, this is the
             parameter sent by the INA in the connect message.
             In the case of reservation access, this parameter is
             an average number, calculated by the INA to reflect
             the actual allocation."
        REFERENCE
            "ES 200 800 Connect Message."
        ::= { dvbInaIfConQosEntry 13 }


Pedersen         Informational - Expires August 2001               56
                     DVB Cable INA Interface MIB             Feb 2001


dvbInaIfConQosUsReqFixedRateMethod      OBJECT-TYPE
        SYNTAX      INTEGER {
                    cyclic( 1 ),
                    slotList( 2 )
                    }
        MAX-ACCESS  read-write
        STATUS      current
        DESCRIPTION
            "An upstream QoS parameter. Request a specific fixed rate
             slot assignment method to be used.
             If cyclic   then cyclic assignment is used.
             If slotList then the slot list method is used.
             The parameter can be set either by the managment system,
             or by the INA according to the NIU resource request.
             If the bit Cyclic_Assignment_Needed is set, the NIU
             requests the cyclic method.
             Otherwise the slot list method."
        REFERENCE
            "ES 200 800 Connect Message and Resource Request Message"
        ::= { dvbInaIfConQosEntry 14 }

dvbInaIfConQosUsAllocFixedRateMethod    OBJECT-TYPE
        SYNTAX      INTEGER {
                    cyclic( 1 ),
                    slotList( 2 )
                    }
        MAX-ACCESS  read-only
        STATUS      current
        DESCRIPTION
            "An upstream QoS parameter. Reflects the actual fixed rate
             slot assignment method that is used.
             If cyclic   then cyclic assignment is used.
             If slotList then the slot list method is used."
        REFERENCE
            "ES 200 800 Connect Message and Resource Request Message"
        ::= { dvbInaIfConQosEntry 15 }


-- - - - - - - - - - - - - - - - - - - - - - - - - - - - - - - - - - -
-- Connection Session Binding Table
--
-- The Connection Session Binding Table entends the Connection table
-- with information about session binding for the connection.
--
-- The indexes are the same as for the Connection Table -
-- the NIU MAC address and the Connection ID.
--
-- - - - - - - - - - - - - - - - - - - - - - - - - - - - - - - - - - -
dvbInaIfConSesTable OBJECT-TYPE
        SYNTAX      SEQUENCE OF DvbInaIfConSesEntry
        MAX-ACCESS  not-accessible
        STATUS      current
        DESCRIPTION

Pedersen         Informational - Expires August 2001               57
                     DVB Cable INA Interface MIB             Feb 2001


            "Contains information about session binding for
             DVB-RC MAC connections."
        ::= { dvbInaIfConnection 3 }

dvbInaIfConSesEntry OBJECT-TYPE
        SYNTAX      DvbInaIfConSesEntry
        MAX-ACCESS  not-accessible
        STATUS      current
        DESCRIPTION
            "An entry in the table is automatically created when
             a new entry in the connection table connection is created
             if the INA and the NIU supports session binding.

             The entries are deleted when the contection table entry
             is deleted."
        INDEX { dvbInaIfConNiuMacAddress, dvbInaIfConConnectionId }
        ::= { dvbInaIfConSesTable 1 }

DvbInaIfConSesEntry ::= SEQUENCE {
            dvbInaIfConSesUsControl                 Unsigned32,
            dvbInaIfConSesUsNiuClientSrcIpType      InetAddressType,
            dvbInaIfConSesUsNiuClientSrcIp          InetAddress,
            dvbInaIfConSesUsNiuClientDstIpType      InetAddressType,
            dvbInaIfConSesUsNiuClientDstIp          InetAddress,
            dvbInaIfConSesUsNiuClientSrcPort        Unsigned32,
            dvbInaIfConSesUsNiuClientDstPort        Unsigned32,
            dvbInaIfConSesUsTransportProtocol       INTEGER,
            dvbInaIfConSesUsNiuClientSrcMac         MacAddress,
            dvbInaIfConSesUsNiuClientDstMac         MacAddress,
            dvbInaIfConSesUsEthernetProtocol        Unsigned32,
            dvbInaIfConSesUsSessionId               Unsigned32,
            dvbInaIfConSesDsControl                 Unsigned32,
            dvbInaIfConSesDsInaClientSrcIpType      InetAddressType,
            dvbInaIfConSesDsInaClientSrcIp          InetAddress,
            dvbInaIfConSesDsInaClientDstIpType      InetAddressType,
            dvbInaIfConSesDsInaClientDstIp          InetAddress,
            dvbInaIfConSesDsInaClientSrcPort        Unsigned32,
            dvbInaIfConSesDsInaClientDstPort        Unsigned32,
            dvbInaIfConSesDsTransportProtocol       INTEGER,
            dvbInaIfConSesDsInaClientSrcMac         MacAddress,
            dvbInaIfConSesDsInaClientDstMac         MacAddress,
            dvbInaIfConSesDsEthernetProtocol        Unsigned32,
            dvbInaIfConSesDsSessionId               Unsigned32
        }

dvbInaIfConSesUsControl             OBJECT-TYPE
        SYNTAX      Unsigned32 ( 0..4294967295 )
        MAX-ACCESS  read-only
        STATUS      current
        DESCRIPTION
            "Control which fields of the upstream session binding
             parameters that are used."
        REFERENCE

Pedersen         Informational - Expires August 2001               58
                     DVB Cable INA Interface MIB             Feb 2001


            "ES 200 800 version 2"
        ::= { dvbInaIfConSesEntry 1 }

dvbInaIfConSesUsNiuClientSrcIpType  OBJECT-TYPE
        SYNTAX      InetAddressType
        MAX-ACCESS  read-only
        STATUS      current
        DESCRIPTION
            "The type of the IP source address of the NIU client."
        ::= { dvbInaIfConSesEntry 2 }

dvbInaIfConSesUsNiuClientSrcIp      OBJECT-TYPE
        SYNTAX      InetAddress
        MAX-ACCESS  read-only
        STATUS      current
        DESCRIPTION
            "The IP source address of the NIU client.
             Only used if bit 0 of dvbInaIfConSesUsControl is set."
        REFERENCE
            "ES 200 800 version 2"
        ::= { dvbInaIfConSesEntry 3 }

dvbInaIfConSesUsNiuClientDstIpType  OBJECT-TYPE
        SYNTAX      InetAddressType
        MAX-ACCESS  read-only
        STATUS      current
        DESCRIPTION
            "The type of the IP destination address of the NIU client."
        ::= { dvbInaIfConSesEntry 4 }

dvbInaIfConSesUsNiuClientDstIp      OBJECT-TYPE
        SYNTAX      InetAddress
        MAX-ACCESS  read-only
        STATUS      current
        DESCRIPTION
            "The IP destination address of the NIU client.
             Only used if bit 1 of dvbInaIfConSesUsControl is set."
        REFERENCE
            "ES 200 800 version 2"
        ::= { dvbInaIfConSesEntry 5 }

dvbInaIfConSesUsNiuClientSrcPort    OBJECT-TYPE
        SYNTAX      Unsigned32 ( 0..65535 )
        MAX-ACCESS  read-only
        STATUS      current
        DESCRIPTION
            "The source port of the NIU client.
             Only used if bit 2 of dvbInaIfConSesUsControl is set."
        REFERENCE
            "ES 200 800 version 2"
        ::= { dvbInaIfConSesEntry 6 }

dvbInaIfConSesUsNiuClientDstPort    OBJECT-TYPE

Pedersen         Informational - Expires August 2001               59
                     DVB Cable INA Interface MIB             Feb 2001


        SYNTAX      Unsigned32 ( 0..65535 )
        MAX-ACCESS  read-only
        STATUS      current
        DESCRIPTION
            "The destination port of the NIU client.
             Only used if bit 3 of dvbInaIfConSesUsControl is set."
        REFERENCE
            "ES 200 800 version 2"
        ::= { dvbInaIfConSesEntry 7 }

dvbInaIfConSesUsTransportProtocol   OBJECT-TYPE
        SYNTAX      INTEGER ( 0..255 )
        MAX-ACCESS  read-only
        STATUS      current
        DESCRIPTION
            "The transport protocol used by the NIU client (UDP/TCP).
             This is the 8-bit protocol field in the IP header.
             Only used if bit 4 of dvbInaIfConSesUsControl is set."
        REFERENCE
            "ES 200 800 version 2"
        ::= { dvbInaIfConSesEntry 8 }

dvbInaIfConSesUsNiuClientSrcMac     OBJECT-TYPE
        SYNTAX      MacAddress
        MAX-ACCESS  read-only
        STATUS      current
        DESCRIPTION
            "The Ethernet source MAC address of the NIU client.
             Only used if bit 5 of dvbInaIfConSesUsControl is set."
        REFERENCE
            "ES 200 800 version 2"
        ::= { dvbInaIfConSesEntry 9 }

dvbInaIfConSesUsNiuClientDstMac     OBJECT-TYPE
        SYNTAX      MacAddress
        MAX-ACCESS  read-only
        STATUS      current
        DESCRIPTION
            "The Ethernet destination MAC address of the NIU client.
             Only used if bit 6 of dvbInaIfConSesUsControl is set."
        REFERENCE
            "ES 200 800 version 2"
        ::= { dvbInaIfConSesEntry 10 }

dvbInaIfConSesUsEthernetProtocol    OBJECT-TYPE
        SYNTAX      Unsigned32 ( 0..65535 )
        MAX-ACCESS  read-only
        STATUS      current
        DESCRIPTION
            "The ethernet protocol, as described in the ethernet header.
             This is the type field in the Ethernet protocol header.
             Only used if bit 7 of dvbInaIfConSesUsControl is set."
        REFERENCE

Pedersen         Informational - Expires August 2001               60
                     DVB Cable INA Interface MIB             Feb 2001


            "ES 200 800 version 2"
        ::= { dvbInaIfConSesEntry 11 }

dvbInaIfConSesUsSessionId           OBJECT-TYPE
        SYNTAX      Unsigned32 ( 0..4294967295 )
        MAX-ACCESS  read-only
        STATUS      current
        DESCRIPTION
            "The session_Id, as defined for PPPoE protocol.
             Only used if bit 8 of dvbInaIfConSesUsControl is set."
        REFERENCE
            "ES 200 800 version 2"
        ::= { dvbInaIfConSesEntry 12 }

dvbInaIfConSesDsControl             OBJECT-TYPE
        SYNTAX      Unsigned32 ( 0..4294967295 )
        MAX-ACCESS  read-only
        STATUS      current
        DESCRIPTION
            "Control which fields of the downstream session binding
             parameters that are used."
        REFERENCE
            "ES 200 800 version 2"
        ::= { dvbInaIfConSesEntry 13 }

dvbInaIfConSesDsInaClientSrcIpType  OBJECT-TYPE
        SYNTAX      InetAddressType
        MAX-ACCESS  read-only
        STATUS      current
        DESCRIPTION
            "The type of the IP source address of the INA client."
        ::= { dvbInaIfConSesEntry 14 }

dvbInaIfConSesDsInaClientSrcIp      OBJECT-TYPE
        SYNTAX      InetAddress
        MAX-ACCESS  read-only
        STATUS      current
        DESCRIPTION
            "The IP source address of the INA client.
             Only used if bit 0 of dvbInaIfConSesDsControl is set."
        REFERENCE
            "ES 200 800 version 2"
        ::= { dvbInaIfConSesEntry 15 }

dvbInaIfConSesDsInaClientDstIpType  OBJECT-TYPE
        SYNTAX      InetAddressType
        MAX-ACCESS  read-only
        STATUS      current
        DESCRIPTION
            "The type of the IP destination address of the INA client."
        ::= { dvbInaIfConSesEntry 16 }

dvbInaIfConSesDsInaClientDstIp      OBJECT-TYPE

Pedersen         Informational - Expires August 2001               61
                     DVB Cable INA Interface MIB             Feb 2001


        SYNTAX      InetAddress
        MAX-ACCESS  read-only
        STATUS      current
        DESCRIPTION
            "The IP destination address of the INA client.
             Only used if bit 1 of dvbInaIfConSesDsControl is set."
        REFERENCE
            "ES 200 800 version 2"
        ::= { dvbInaIfConSesEntry 17 }

dvbInaIfConSesDsInaClientSrcPort    OBJECT-TYPE
        SYNTAX      Unsigned32 ( 0..65535 )
        MAX-ACCESS  read-only
        STATUS      current
        DESCRIPTION
            "The source port of the INA client.
             Only used if bit 2 of dvbInaIfConSesDsControl is set."
        REFERENCE
            "ES 200 800 version 2"
        ::= { dvbInaIfConSesEntry 18 }

dvbInaIfConSesDsInaClientDstPort    OBJECT-TYPE
        SYNTAX      Unsigned32 ( 0..65535 )
        MAX-ACCESS  read-only
        STATUS      current
        DESCRIPTION
            "The destination port of the INA client.
             Only used if bit 3 of dvbInaIfConSesDsControl is set."
        REFERENCE
            "ES 200 800 version 2"
        ::= { dvbInaIfConSesEntry 19 }

dvbInaIfConSesDsTransportProtocol   OBJECT-TYPE
        SYNTAX      INTEGER ( 0..255 )
        MAX-ACCESS  read-only
        STATUS      current
        DESCRIPTION
            "The transport protocol used by the INA client (UDP/TCP).
             This is the 8-bit protocol field in the IP header.
             Only used if bit 4 of dvbInaIfConSesDsControl is set."
        REFERENCE
            "ES 200 800 version 2"
        ::= { dvbInaIfConSesEntry 20 }

dvbInaIfConSesDsInaClientSrcMac     OBJECT-TYPE
        SYNTAX      MacAddress
        MAX-ACCESS  read-only
        STATUS      current
        DESCRIPTION
            "The Ethernet source MAC address of the INA client.
             Only used if bit 5 of dvbInaIfConSesDsControl is set."
        REFERENCE
            "ES 200 800 version 2"

Pedersen         Informational - Expires August 2001               62
                     DVB Cable INA Interface MIB             Feb 2001


        ::= { dvbInaIfConSesEntry 21 }

dvbInaIfConSesDsInaClientDstMac     OBJECT-TYPE
        SYNTAX      MacAddress
        MAX-ACCESS  read-only
        STATUS      current
        DESCRIPTION
            "The Ethernet destination MAC address of the INA client.
             Only used if bit 6 of dvbInaIfConSesDsControl is set."
        REFERENCE
            "ES 200 800 version 2"
        ::= { dvbInaIfConSesEntry 22 }

dvbInaIfConSesDsEthernetProtocol    OBJECT-TYPE
        SYNTAX      Unsigned32 ( 0..65535 )
        MAX-ACCESS  read-only
        STATUS      current
        DESCRIPTION
            "The ethernet protocol, as described in the ethernet header.
             This is the type field in the Ethernet protocol header.
             Only used if bit 7 of dvbInaIfConSesDsControl is set."
        REFERENCE
            "ES 200 800 version 2"
        ::= { dvbInaIfConSesEntry 23 }

dvbInaIfConSesDsSessionId           OBJECT-TYPE
        SYNTAX      Unsigned32 ( 0..4294967295 )
        MAX-ACCESS  read-only
        STATUS      current
        DESCRIPTION
            "The session_Id, as defined for PPPoE protocol.
             Only used if bit 8 of dvbInaIfConSesDsControl is set."
        REFERENCE
            "ES 200 800 version 2"
        ::= { dvbInaIfConSesEntry 24 }


-- - - - - - - - - - - - - - - - - - - - - - - - - - - - - - - - - - -
-- Header Suppression Table
--
-- The Header Suppression Table contains information about the current
-- state of the header suppression.
--
-- The table is only used during reprovisioning in order to
-- transfer the current header suppression state from INA 1 to INA 2.
--
-- The whole table is read-only and read from INA 1 during
-- reprovisioning.
-- A reprovisioning issue of the table is written to INA 2 during
-- reprovisoning and INA 2 then transfers the information to this
-- table then the reprovisioning takes place.
--
-- Indices into this table are the Connection ID and a Context ID

Pedersen         Informational - Expires August 2001               63
                     DVB Cable INA Interface MIB             Feb 2001


-- - - - - - - - - - - - - - - - - - - - - - - - - - - - - - - - - - -

dvbInaIfConHdrSupTable                  OBJECT-TYPE
        SYNTAX      SEQUENCE OF DvbInaIfConHdrSupEntry
        MAX-ACCESS  not-accessible
        STATUS      current
        DESCRIPTION
            "Table contains information about the header suppression
             for a connection, indexed trough the Connection ID
             and the Context ID."
        ::= { dvbInaIfConnection 4 }

dvbInaIfConHdrSupEntry                  OBJECT-TYPE
        SYNTAX      DvbInaIfConHdrSupEntry
        MAX-ACCESS  not-accessible
        STATUS      current
        DESCRIPTION
            "An entry in the table is automatically generated when
             a new header suppression starts.
             Or when a reprovisioning is made.

             An entry is deleted when the connection is deleted."

        INDEX { dvbInaIfConNiuMacAddress,
                dvbInaIfConConnectionId,
                dvbInaIfConHdrSupContextId,
                dvbInaIfConHdrSupDirection }
        ::= { dvbInaIfConHdrSupTable 1 }

DvbInaIfConHdrSupEntry  ::= SEQUENCE {
            dvbInaIfConHdrSupContextId          INTEGER,
            dvbInaIfConHdrSupDirection          INTEGER,
            dvbInaIfConHdrSupControl            OCTET STRING,
            dvbInaIfConHdrSupGeneration         Integer32,
            dvbInaIfConHdrSupHeaderLength       Integer32,
            dvbInaIfConHdrSupHeader             OCTET STRING
        }

dvbInaIfConHdrSupContextId          OBJECT-TYPE
        SYNTAX      INTEGER ( 0..127 )
        MAX-ACCESS  not-accessible
        STATUS      current
        DESCRIPTION
            "The context ID for the header suppression session."
        REFERENCE
            "ES 200 800 Suppression Data Message"
        ::= { dvbInaIfConHdrSupEntry 1 }

dvbInaIfConHdrSupDirection          OBJECT-TYPE
        SYNTAX      INTEGER {
                    upstream( 1 ),
                    downstream( 2 )
                    }

Pedersen         Informational - Expires August 2001               64
                     DVB Cable INA Interface MIB             Feb 2001


        MAX-ACCESS  not-accessible
        STATUS      current
        DESCRIPTION
            "The direction for this the header suppression session."
        REFERENCE
            "ES 200 800 Suppression Data Message"
        ::= { dvbInaIfConHdrSupEntry 2 }

dvbInaIfConHdrSupControl            OBJECT-TYPE
        SYNTAX      OCTET STRING ( SIZE ( 13 ))
        MAX-ACCESS  read-only
        STATUS      current
        DESCRIPTION
            "String of bits that control the use of the header
             suppression. Each of the first 103 bits, indicates
             if a byte in the header is suppressed or not.
             Bit 103 is used as an overall suppression enable.
             If a mask bit is 0, the matching header byte is
             suppressed.
             If bit 103 is set, suppression is performed.
             Bit 103 is the least significant bit in octet 13.
             See also dvbInaIfConHdrSupHeader."
        REFERENCE
            "ES 200 800 Suppression Data Message"
        ::= { dvbInaIfConHdrSupEntry 3 }

dvbInaIfConHdrSupGeneration         OBJECT-TYPE
        SYNTAX      Integer32 ( 0..15 )
        MAX-ACCESS  read-only
        STATUS      current
        DESCRIPTION
            "The generation number that is attached to the header
             fields value."
        REFERENCE
            "ES 200 800 Suppression Data Message"
        ::= { dvbInaIfConHdrSupEntry 4 }

dvbInaIfConHdrSupHeaderLength       OBJECT-TYPE
        SYNTAX      Integer32 ( 0..103 )
        MAX-ACCESS  read-only
        STATUS      current
        DESCRIPTION
            "The number of usefull bytes in the suppression header.
             This is the number of the last zero in the
             dvbInaIfConHdrSupControl."
        REFERENCE
            "ES 200 800 Suppression Data Message"
        ::= { dvbInaIfConHdrSupEntry 5 }

dvbInaIfConHdrSupHeader             OBJECT-TYPE
        SYNTAX      OCTET STRING ( SIZE ( 103 ))
        MAX-ACCESS  read-only
        STATUS      current

Pedersen         Informational - Expires August 2001               65
                     DVB Cable INA Interface MIB             Feb 2001


        DESCRIPTION
            "The header used for header suppression.
             Both fixed and changing fields together.
             Only the first dvbInaIfConHdrSupHeaderLength is used."
        REFERENCE
            "ES 200 800 Suppression Data Message"
        ::= { dvbInaIfConHdrSupEntry 6 }


-- - - - - - - - - - - - - - - - - - - - - - - - - - - - - - - - - - -
-- Reprovisioning tables
--
-- When a NIU is reprovisioned from INA 1 to INA 2
-- a manager must read the NIU and connections information on INA 1
-- in the
--      NIU Table
--      Connection Table
--      Connection Session Binding Table
--      Connection Quality Table
--      Header Suppression Table
--
-- The manager must then create entries for the NIU, each Connection,
-- each Session and Context on INA 2.
--      Reprovision Dest NIU Table
--      Reprovision Connection Table
--      Reprovision Connection Session Binding Table
--      Reprovision Connection Quality Table
--      Reprovision Header Suppression Table
--
-- This will create information on INA 2 in the reprovisioning tables
-- that will be copied back to INA 1.
--      Reprovision Src NIU Table
--      Reprovision Src Connection Table
--
-- When the NIU sign-on on INA 2, the INA 2 will move the information
-- from the Reprovisioning tables and delete the entries in the
-- Reprovisioning tables.
-- Likewise INA 1 can remove the entries in the reprovisioning tables
-- when the NIU has been reprovisioned.
-- - - - - - - - - - - - - - - - - - - - - - - - - - - - - - - - - - -

    --  - - - - - - - - - - - - - - -
    -- Reprov Src NIU tables
    --  - - - - - - - - - - - - - - -

dvbInaIfReprovSrcNiuTable OBJECT-TYPE
        SYNTAX      SEQUENCE OF DvbInaIfReprovSrcNiuEntry
        MAX-ACCESS  not-accessible
        STATUS      current
        DESCRIPTION
            "The table describes information created on INA 1 for
             a NIU that is about to be reprovisioned."
        ::= { dvbInaIfReprov 1 }

Pedersen         Informational - Expires August 2001               66
                     DVB Cable INA Interface MIB             Feb 2001



dvbInaIfReprovSrcNiuEntry OBJECT-TYPE
        SYNTAX      DvbInaIfReprovSrcNiuEntry
        MAX-ACCESS  not-accessible
        STATUS      current
        DESCRIPTION
            "An entry in the table is created by the manager when
             a NIU is about to be reprovisioned.

             When the reprovisioning is done and the NIU entry is
             deleted after dvbInaIfNiuLifetime this entry will
             be deleted too."
        INDEX { dvbInaIfNiuMacAddress }
        ::= { dvbInaIfReprovSrcNiuTable 1 }

DvbInaIfReprovSrcNiuEntry ::= SEQUENCE {
            dvbInaIfReprovSrcNiuRowAccessStatus RowStatus,
            dvbInaIfReprovSrcNiuCommand         INTEGER,
            dvbInaIfReprovSrcNiuDsChFrequency   DownFrequency,
            dvbInaIfReprovSrcNiuDsChSymbolRate  DownstreamSymbolrate,
            dvbInaIfReprovSrcNiuDsChModulation  Modulation,
            dvbInaIfReprovSrcNiuDsChType        INTEGER,
            dvbInaIfReprovSrcNiuUsChFrequency   UpFrequency,
            dvbInaIfReprovSrcNiuUsChSymbolRate  UpstreamSymbolrate,
            dvbInaIfReprovSrcNiuUsChModulation  Modulation,
            dvbInaIfReprovSrcNiuUsChId          Integer32
        }

dvbInaIfReprovSrcNiuRowAccessStatus     OBJECT-TYPE
        SYNTAX      RowStatus
        MAX-ACCESS  read-create
        STATUS      current
        DESCRIPTION
            "Controls and reflects the status of this row in this
             table."
        ::= { dvbInaIfReprovSrcNiuEntry 1 }

dvbInaIfReprovSrcNiuCommand             OBJECT-TYPE
        SYNTAX      INTEGER {
                    reprovIdle( 1 ),
                    reprovStart( 2 )
                    }
        MAX-ACCESS  read-create
        STATUS      current
        DESCRIPTION
            "Controls the reprovisioning on INA 1.
             When set to reprovStart the actual reporvisioning on INA 1
             is initiated with a Reprovisioning Message to the NIU.
             Everything must be prepared for the reprovisioning when
             this is done.
             When read the response will always be reprovIdle."
        ::= { dvbInaIfReprovSrcNiuEntry 2 }


Pedersen         Informational - Expires August 2001               67
                     DVB Cable INA Interface MIB             Feb 2001


dvbInaIfReprovSrcNiuDsChFrequency       OBJECT-TYPE
        SYNTAX      DownFrequency
        UNITS       "hertz"
        MAX-ACCESS  read-create
        STATUS      current
        DESCRIPTION
            "The centre of the new downstream frequency when
             the NIU is reprovisioned to INA 2."
        ::= { dvbInaIfReprovSrcNiuEntry 3 }

dvbInaIfReprovSrcNiuDsChSymbolRate      OBJECT-TYPE
        SYNTAX      DownstreamSymbolrate
        UNITS       "symbol/s"
        MAX-ACCESS  read-create
        STATUS      current
        DESCRIPTION
            "Specifies the new symbol rate for the Downstream channel
             when the NIU is reprovisioned."
        ::= { dvbInaIfReprovSrcNiuEntry 4 }

dvbInaIfReprovSrcNiuDsChModulation      OBJECT-TYPE
        SYNTAX      Modulation
        MAX-ACCESS  read-create
        STATUS      current
        DESCRIPTION
            "Specifies the new modulation for the Downstream channel
             when the NIU is reprovisioned."
        DEFVAL { qpsk }
        ::= { dvbInaIfReprovSrcNiuEntry 5 }

dvbInaIfReprovSrcNiuDsChType            OBJECT-TYPE
        SYNTAX      INTEGER {
                    ib(1),
                    oob(2)
                    }
        MAX-ACCESS  read-create
        STATUS      current
        DESCRIPTION
            "Specifies if the new Downstream channel is inband or
             out-of-band when the NIU is reprovisioned."
        ::= { dvbInaIfReprovSrcNiuEntry 6 }

dvbInaIfReprovSrcNiuUsChFrequency       OBJECT-TYPE
        SYNTAX      UpFrequency
        UNITS       "hertz"
        MAX-ACCESS  read-create
        STATUS      current
        DESCRIPTION
            "Specifies the new upstream channel frequency in Hz
             when the NIU is reprovisoned."
        ::= { dvbInaIfReprovSrcNiuEntry 7 }

dvbInaIfReprovSrcNiuUsChSymbolRate      OBJECT-TYPE

Pedersen         Informational - Expires August 2001               68
                     DVB Cable INA Interface MIB             Feb 2001


        SYNTAX      UpstreamSymbolrate
        MAX-ACCESS  read-create
        STATUS      current
        DESCRIPTION
            "Specifies the new upstream channel symbol rate
             when the NIU is reprovisoned."
        DEFVAL { sr1544000 }
        ::= { dvbInaIfReprovSrcNiuEntry 8 }

dvbInaIfReprovSrcNiuUsChModulation      OBJECT-TYPE
        SYNTAX      Modulation
        MAX-ACCESS  read-create
        STATUS      current
        DESCRIPTION
            "Specifies the new upstream modulation
             when the NIU is reprovisoned."
        DEFVAL { qpsk }
        ::= { dvbInaIfReprovSrcNiuEntry 9 }

dvbInaIfReprovSrcNiuUsChId              OBJECT-TYPE
        SYNTAX      Integer32 ( 0..255 )
        MAX-ACCESS  read-only
        STATUS      current
        DESCRIPTION
            "Specifies the new logical channel number associated
             with the upstream channel when the NIU is reprovisioned."
        ::= { dvbInaIfReprovSrcNiuEntry 10 }


    --  - - - - - - - - - - - - - - -
    -- Reprov Dst NIU tables
    --  - - - - - - - - - - - - - - -

dvbInaIfReprovDstNiuTable OBJECT-TYPE
        SYNTAX      SEQUENCE OF DvbInaIfReprovDstNiuEntry
        MAX-ACCESS  not-accessible
        STATUS      current
        DESCRIPTION
            "The table describes information created on INA 2 for
             a NIU that is about to be reprovisioned."
        ::= { dvbInaIfReprov 2 }

dvbInaIfReprovDstNiuEntry OBJECT-TYPE
        SYNTAX      DvbInaIfReprovDstNiuEntry
        MAX-ACCESS  not-accessible
        STATUS      current
        DESCRIPTION
            "An entry in the table is created by the manager when
             a NIU is about to be reprovisioned.

             When the reprovisioning is done and the NIU signs on
             to INA 2 the information is transfered to the NIU table
             and the entry in this table is deleted automatically."

Pedersen         Informational - Expires August 2001               69
                     DVB Cable INA Interface MIB             Feb 2001


        INDEX { dvbInaIfReprovDstNiuMacAddress }
        ::= { dvbInaIfReprovDstNiuTable 1 }

DvbInaIfReprovDstNiuEntry  ::= SEQUENCE {
            dvbInaIfReprovDstNiuMacAddress      MacAddress,
            dvbInaIfReprovDstNiuRowAccessStatus RowStatus,
            dvbInaIfReprovDstNiuCommand         INTEGER,
            dvbInaIfReprovDstNiuDownIfIndex     InterfaceIndexOrZero,
            dvbInaIfReprovDstNiuUpIfIndex       InterfaceIndexOrZero,
            dvbInaIfReprovDstNiuLifetime        Unsigned32
        }

dvbInaIfReprovDstNiuMacAddress          OBJECT-TYPE
        SYNTAX      MacAddress
        MAX-ACCESS  not-accessible
        STATUS      current
        DESCRIPTION
            "A 48-bit value representing the unique MAC address of
             the NIU to be reprovisioned.
             This is the index of the table."
        ::= { dvbInaIfReprovDstNiuEntry 1 }

dvbInaIfReprovDstNiuRowAccessStatus     OBJECT-TYPE
        SYNTAX      RowStatus
        MAX-ACCESS  read-create
        STATUS      current
        DESCRIPTION
            "Controls and reflects the status of this row in this
             table."
        ::= { dvbInaIfReprovDstNiuEntry 2 }

dvbInaIfReprovDstNiuCommand             OBJECT-TYPE
        SYNTAX      INTEGER {
                    reprovIdle( 1 ),
                    reprovPrepare( 2 ),
                    reprovReceiveNiu( 3 )
                    }
        MAX-ACCESS  read-create
        STATUS      current
        DESCRIPTION
            "Controls the reprovisioning on INA 2.
             When set to reprovPrepare INA 2 will generate the
             necessary information that needs to be transferred back
             to INA 1.
             This includes:
                New Connection ID's
                New PID for each connection
                New downstream VPI/VCI
                New upstream   VPI/VCI
                New upstream number
             Furthermore new fixed rate parameters are calculated
             if one of the new connections are fixed rate.
             All settings needed to calculate these new parameters

Pedersen         Informational - Expires August 2001               70
                     DVB Cable INA Interface MIB             Feb 2001


             must be given before reprovPrepare is set.

             When set to reprovReceiveNiu this is an indication
             to INA 2 that the NIU is expected to sign-on now.

             When read the response will always be reprovIdle."
        ::= { dvbInaIfReprovDstNiuEntry 3 }

dvbInaIfReprovDstNiuDownIfIndex         OBJECT-TYPE
        SYNTAX      InterfaceIndexOrZero
        MAX-ACCESS  read-create
        STATUS      current
        DESCRIPTION
            "Specifies the IfIndex of the downstream channel on which
             the NIU is tuned after the reprovisioning. "
        ::= { dvbInaIfReprovDstNiuEntry 4 }

dvbInaIfReprovDstNiuUpIfIndex           OBJECT-TYPE
        SYNTAX      InterfaceIndexOrZero
        MAX-ACCESS  read-create
        STATUS      current
        DESCRIPTION
            "Specifies the IfIndex of the upstream channel that is
             used by the NIU after the reprovisioning."
        ::= { dvbInaIfReprovDstNiuEntry 5 }

dvbInaIfReprovDstNiuLifetime            OBJECT-TYPE
        SYNTAX      Unsigned32 ( 0..4294967295 )
        UNITS       "s"
        MAX-ACCESS  read-create
        STATUS      current
        DESCRIPTION
            "Defines how long time after the NIU signs off, the NIU
             entry is removed from the NIU table.
             An infinite(0) value would mean that the values are stored
             at least until the next reboot of the INA"
        DEFVAL { 300 }
        ::= { dvbInaIfReprovDstNiuEntry 6 }


    --  - - - - - - - - - - - - - - -
    -- Reprov Src Connection tables
    --  - - - - - - - - - - - - - - -

dvbInaIfReprovSrcConTable               OBJECT-TYPE
        SYNTAX      SEQUENCE OF DvbInaIfReprovSrcConEntry
        MAX-ACCESS  not-accessible
        STATUS      current
        DESCRIPTION
            "Contains information about DVB-RC MAC connections
             on INA 1 that is about to be reprovisioned."
        ::= { dvbInaIfReprov 3 }


Pedersen         Informational - Expires August 2001               71
                     DVB Cable INA Interface MIB             Feb 2001


dvbInaIfReprovSrcConEntry OBJECT-TYPE
        SYNTAX      DvbInaIfReprovSrcConEntry
        MAX-ACCESS  not-accessible
        STATUS      current
        DESCRIPTION
            "The entries in the table are created by the manager
             when a NIU on INA 1 is about to be reprovisioned.

             After the NIU is reprovisoned the entries are automatically
             deleted when the corresponding NUI entry are deleted
             after dvbInaIfNiuLifetime."
        INDEX { dvbInaIfNiuMacAddress, dvbInaIfConConnectionId }
        ::= { dvbInaIfReprovSrcConTable 1 }

DvbInaIfReprovSrcConEntry ::= SEQUENCE {
            dvbInaIfReprovSrcConRowAccessStatus     RowStatus,
            dvbInaIfReprovSrcConConnectionIdNew     Unsigned32,
            dvbInaIfReprovSrcConPID                 Unsigned32,
            dvbInaIfReprovSrcConDsVc                Unsigned32,
            dvbInaIfReprovSrcConUsVc                Unsigned32
        }

dvbInaIfReprovSrcConRowAccessStatus     OBJECT-TYPE
        SYNTAX      RowStatus
        MAX-ACCESS  read-create
        STATUS      current
        DESCRIPTION
            "Controls and reflects the status of this row in this
            table. "
        ::= { dvbInaIfReprovSrcConEntry 1 }

dvbInaIfReprovSrcConConnectionIdNew     OBJECT-TYPE
        SYNTAX      Unsigned32 ( 0..4294967295 )
        MAX-ACCESS  read-create
        STATUS      current
        DESCRIPTION
            "Specifies the new value for the connection identifier
             to be used for this connection after the reprovisioning.
             The management system must get this value from INA 2."
        ::= { dvbInaIfReprovSrcConEntry 2 }

dvbInaIfReprovSrcConPID                 OBJECT-TYPE
        SYNTAX      Unsigned32 ( 0..8191 )
        MAX-ACCESS  read-create
        STATUS      current
        DESCRIPTION
            "Specifies the new MPEG PID of the elementary stream that
             carries the data after the reprovisioning."
        ::= { dvbInaIfReprovSrcConEntry 3 }

dvbInaIfReprovSrcConDsVc                OBJECT-TYPE
        SYNTAX      Unsigned32 ( 0..16777215 )
        MAX-ACCESS  read-create

Pedersen         Informational - Expires August 2001               72
                     DVB Cable INA Interface MIB             Feb 2001


        STATUS      current
        DESCRIPTION
            "ATM concatenated VPI and VCI Virtual Path Identifiers
             that is used for downstream OoB transmission after
             reprovisioning.
             The management system must get this value from INA 2."
        ::= { dvbInaIfReprovSrcConEntry 4 }

dvbInaIfReprovSrcConUsVc                OBJECT-TYPE
        SYNTAX      Unsigned32 ( 0..16777215 )
        MAX-ACCESS  read-create
        STATUS      current
        DESCRIPTION
            "ATM concatenated VPI and VCI Virtual Path Identifiers
             that is used for upstream transmission after
             reprovisioning.
             The management system must get this value from INA 2."
        ::= { dvbInaIfReprovSrcConEntry 5 }


    --  - - - - - - - - - - - - - - -
    -- Reprov Dst Connection tables
    --  - - - - - - - - - - - - - - -

dvbInaIfReprovDstConTable               OBJECT-TYPE
        SYNTAX      SEQUENCE OF DvbInaIfReprovDstConEntry
        MAX-ACCESS  not-accessible
        STATUS      current
        DESCRIPTION
            "Contains information about DVB-RC MAC connections
             that is about to be reprovisioned to INA 2."
        ::= { dvbInaIfReprov 4 }

dvbInaIfReprovDstConEntry OBJECT-TYPE
        SYNTAX      DvbInaIfReprovDstConEntry
        MAX-ACCESS  not-accessible
        STATUS      current
        DESCRIPTION
            "The entries in the table are created by the manager
             when a NIU is about to be reprovisioned to INA 2.

             After the NIU has signed on to INA 2, the information in
             the tables are used to create entries in the normal
             connection tables.
             When the entries in the normal tables are made
             the entries in the reprovisioning table are automatically
             deleted."
        INDEX { dvbInaIfReprovDstNiuMacAddress,
                dvbInaIfReprovDstConConnectionIdOld }
        ::= { dvbInaIfReprovDstConTable 1 }

DvbInaIfReprovDstConEntry ::= SEQUENCE {
            dvbInaIfReprovDstConConnectionIdOld      Unsigned32,

Pedersen         Informational - Expires August 2001               73
                     DVB Cable INA Interface MIB             Feb 2001


            dvbInaIfReprovDstConRowAccessStatus      RowStatus,
            dvbInaIfReprovDstConConnectionIdNew      Unsigned32,
            dvbInaIfReprovDstConConnectionType       BITS,
            dvbInaIfReprovDstConEncapsulation        INTEGER,
            dvbInaIfReprovDstConAtmDownstreamVCC     Unsigned32,
            dvbInaIfReprovDstConAtmUpstreamVCC       Unsigned32,
            dvbInaIfReprovDstConFilterMACAddress     MacAddress,
            dvbInaIfReprovDstConPID                  Unsigned32,
            dvbInaIfReprovDstConMaxContentionMsgLen  INTEGER,
            dvbInaIfReprovDstConMaxReservationMsgLen INTEGER,
            dvbInaIfReprovDstConAuxFlags             INTEGER
        }

dvbInaIfReprovDstConConnectionIdOld     OBJECT-TYPE
        SYNTAX      Unsigned32 ( 0..4294967295 )
        MAX-ACCESS  not-accessible
        STATUS      current
        DESCRIPTION
            "Specifies the old value for the connection identifier
             that is used on INA 1.
             The management system must get this value from INA 1."
        ::= { dvbInaIfReprovDstConEntry 1 }

dvbInaIfReprovDstConRowAccessStatus     OBJECT-TYPE
        SYNTAX      RowStatus
        MAX-ACCESS  read-create
        STATUS      current
        DESCRIPTION
            "Controls and reflects the status of this row in this
             table."
        ::= { dvbInaIfReprovDstConEntry 2 }

dvbInaIfReprovDstConConnectionIdNew     OBJECT-TYPE
        SYNTAX      Unsigned32 ( 0..4294967295 )
        MAX-ACCESS  read-only
        STATUS      current
        DESCRIPTION
            "Specifies the new value for the connection identifier
             that is used on INA 2.
             INA 2 creates this value when dvbInaIfReprovDstNiuCommand
             is set to reprovPrepare."
        ::= { dvbInaIfReprovDstConEntry 3 }

dvbInaIfReprovDstConConnectionType      OBJECT-TYPE
        SYNTAX      BITS {
            conTypeFixedRate(0),
            conTypeContention(1),
            conTypeReservation(2)
        }
        MAX-ACCESS  read-create
        STATUS      current
        DESCRIPTION
            "Specifies the kind of connection: fixed rate, contention

Pedersen         Informational - Expires August 2001               74
                     DVB Cable INA Interface MIB             Feb 2001


            based, or reservation based. This parameter can be set to
            a value that is an OR of the following bits:
                'conTypeFixedRate(0)'
                'conTypeContention(1)'
                'conTypeReservation(2)'
            Default this object is 'conTypeContention(1)'."
        DEFVAL {{ conTypeContention }}
        ::= { dvbInaIfReprovDstConEntry 4 }

dvbInaIfReprovDstConEncapsulation       OBJECT-TYPE
        SYNTAX      INTEGER {
            directIp(1),
            ethernetMacBridging(2),
            ppp(3)
        }
        MAX-ACCESS  read-create
        STATUS      current
        DESCRIPTION
            "This object indicates the type of encapsulation provided
             on this connection. This object can have one of the
             following values: 'directIp(1)',
             'ethernetMacBridging(2)', or 'ppp(3)'. By default this
             parameter is set to 'directIp(1)'."
        DEFVAL { directIp }
        ::= { dvbInaIfReprovDstConEntry 5 }

dvbInaIfReprovDstConAtmDownstreamVCC    OBJECT-TYPE
        SYNTAX      Unsigned32 (0..16777215)
        MAX-ACCESS  read-only
        STATUS      current
        DESCRIPTION
            "ATM concatenated VPI and VCI Virtual Path Identifiers
             that is used for downstream OoB transmission.
             INA 2 creates this value when dvbInaIfReprovDstNiuCommand
             is set to reprovPrepare."
        ::= { dvbInaIfReprovDstConEntry 6 }

dvbInaIfReprovDstConAtmUpstreamVCC      OBJECT-TYPE
        SYNTAX      Unsigned32 (0..16777215)
        MAX-ACCESS  read-only
        STATUS      current
        DESCRIPTION
            "ATM concatenated VPI and VCI Virtual Path Identifiers
             that is used for upstream transmission.
             INA 2 creates this value when dvbInaIfReprovDstNiuCommand
             is set to reprovPrepare."
        ::= { dvbInaIfReprovDstConEntry 7 }

dvbInaIfReprovDstConFilterMACAddress    OBJECT-TYPE
        SYNTAX      MacAddress
        MAX-ACCESS  read-create
        STATUS      current
        DESCRIPTION

Pedersen         Informational - Expires August 2001               75
                     DVB Cable INA Interface MIB             Feb 2001


            "Specifies the 'soft' MPEG MPE MAC address used to
            filter the data out of the downstream IB transmission.
            This is found in the Downstream_Multiprotocol_CBD
            substructure in the Connect Message."
        ::= { dvbInaIfReprovDstConEntry 8 }

dvbInaIfReprovDstConPID                 OBJECT-TYPE
        SYNTAX      Unsigned32 ( 0..8191 )
        MAX-ACCESS  read-only
        STATUS      current
        DESCRIPTION
            "Specifies the MPEG PID of the elementary stream that
             carries the data.
             INA 2 creates this value when dvbInaIfReprovDstNiuCommand
             is set to reprovPrepare."
        ::= { dvbInaIfReprovDstConEntry 9 }

dvbInaIfReprovDstConMaxContentionMsgLen OBJECT-TYPE
        SYNTAX      INTEGER ( 1..255 )
        UNITS       "ATM cells"
        MAX-ACCESS  read-create
        STATUS      current
        DESCRIPTION
            "The Maximum_Contention_Access_Message_Length
             in the Connect Message.
             This is the maximum length of a message that may be
             transmitted using contention access.
             Any message greater than this should use reservation
             access.
             The default value should be
             dvbInaIfMacMaxContentionMsgLen."
        REFERENCE
            "ES 200 800 Connect_Message"
        ::= { dvbInaIfReprovDstConEntry 10 }

dvbInaIfReprovDstConMaxReservationMsgLen OBJECT-TYPE
        SYNTAX      INTEGER ( 0..255 )
        UNITS       "ATM cells"
        MAX-ACCESS  read-create
        STATUS      current
        DESCRIPTION
            "This is the maximum length of a message that may be
             transmitted using a single reservation access.
             Any message greater than this should be transmitted by
             making multiple reservation requests.
             The default value should be
             dvbInaIfMacMaxReservationMsgLen."
        REFERENCE
            "ES 200 800 Connect Message."
        ::= { dvbInaIfReprovDstConEntry 11 }

dvbInaIfReprovDstConAuxFlags            OBJECT-TYPE
        SYNTAX      INTEGER ( 0..255 )

Pedersen         Informational - Expires August 2001               76
                     DVB Cable INA Interface MIB             Feb 2001


        MAX-ACCESS  read-only
        STATUS      current
        DESCRIPTION
            "The Connection_Control_Field_Aux from the Connect Message
             Structure.
             This is used to indicate if the Priority, Downstream
             flowspec and Session binding objects are used
             for the connection."
        REFERENCE
            "ES 200 800 Connect Message."
        ::= { dvbInaIfReprovDstConEntry 12 }

    --  - - - - - - - - - - - - - - -
    -- Reprov Dst Session Bind tables
    --  - - - - - - - - - - - - - - -

dvbInaIfReprovDstConSesTable            OBJECT-TYPE
        SYNTAX      SEQUENCE OF DvbInaIfReprovDstConSesEntry
        MAX-ACCESS  not-accessible
        STATUS      current
        DESCRIPTION
            "Contains information about DVB-RC MAC connections
             that is about to be reprovisioned to INA 2."
        ::= { dvbInaIfReprov 5 }

dvbInaIfReprovDstConSesEntry            OBJECT-TYPE
        SYNTAX      DvbInaIfReprovDstConSesEntry
        MAX-ACCESS  not-accessible
        STATUS      current
        DESCRIPTION
            "The entries in the table are created automatically
             when an entry in the dvbInaIfReprovDstConTable is created
             and the INA support session binding.
             You must always create an entry in the
             dvbInaIfReprovDstConTable first and this will automatically
             create an entry in the dvbInaIfReprovDstConSesTable table.

             After the NIU has signed on to INA 2, the information in
             the table are used to create entries in the normal
             connection tables.
             When the entries in the normal tables are made
             the entries in the reprovisioning table are automatically
             deleted."
        INDEX { dvbInaIfReprovDstNiuMacAddress,
                dvbInaIfReprovDstConConnectionIdOld }
        ::= { dvbInaIfReprovDstConSesTable 1 }

DvbInaIfReprovDstConSesEntry ::= SEQUENCE {
            dvbInaIfReprovDstConSesUsControl            Unsigned32,
            dvbInaIfReprovDstConSesUsNiuClientSrcIpType InetAddressType,
            dvbInaIfReprovDstConSesUsNiuClientSrcIp     InetAddress,
            dvbInaIfReprovDstConSesUsNiuClientDstIpType InetAddressType,
            dvbInaIfReprovDstConSesUsNiuClientDstIp     InetAddress,

Pedersen         Informational - Expires August 2001               77
                     DVB Cable INA Interface MIB             Feb 2001


            dvbInaIfReprovDstConSesUsNiuClientSrcPort   Unsigned32,
            dvbInaIfReprovDstConSesUsNiuClientDstPort   Unsigned32,
            dvbInaIfReprovDstConSesUsTransportProtocol  INTEGER,
            dvbInaIfReprovDstConSesUsNiuClientSrcMac    MacAddress,
            dvbInaIfReprovDstConSesUsNiuClientDstMac    MacAddress,
            dvbInaIfReprovDstConSesUsEthernetProtocol   Unsigned32,
            dvbInaIfReprovDstConSesUsSessionId          Unsigned32,
            dvbInaIfReprovDstConSesDsControl            Unsigned32,
            dvbInaIfReprovDstConSesDsInaClientSrcIpType InetAddressType,
            dvbInaIfReprovDstConSesDsInaClientSrcIp     InetAddress,
            dvbInaIfReprovDstConSesDsInaClientDstIpType InetAddressType,
            dvbInaIfReprovDstConSesDsInaClientDstIp     InetAddress,
            dvbInaIfReprovDstConSesDsInaClientSrcPort   Unsigned32,
            dvbInaIfReprovDstConSesDsInaClientDstPort   Unsigned32,
            dvbInaIfReprovDstConSesDsTransportProtocol  INTEGER,
            dvbInaIfReprovDstConSesDsInaClientSrcMac    MacAddress,
            dvbInaIfReprovDstConSesDsInaClientDstMac    MacAddress,
            dvbInaIfReprovDstConSesDsEthernetProtocol   Unsigned32,
            dvbInaIfReprovDstConSesDsSessionId          Unsigned32
        }

dvbInaIfReprovDstConSesUsControl                OBJECT-TYPE
        SYNTAX      Unsigned32 ( 0..4294967295 )
        MAX-ACCESS  read-write
        STATUS      current
        DESCRIPTION
            "Control which fields of the upstream session binding
             parameters that are used."
        REFERENCE
            "ES 200 800 version 2"
        ::= { dvbInaIfReprovDstConSesEntry 1 }

dvbInaIfReprovDstConSesUsNiuClientSrcIpType     OBJECT-TYPE
        SYNTAX      InetAddressType
        MAX-ACCESS  read-write
        STATUS      current
        DESCRIPTION
            "The type of the IP source address of the NIU client."
        ::= { dvbInaIfReprovDstConSesEntry 2 }

dvbInaIfReprovDstConSesUsNiuClientSrcIp         OBJECT-TYPE
        SYNTAX      InetAddress
        MAX-ACCESS  read-write
        STATUS      current
        DESCRIPTION
            "The IP source address of the NIU client.
             Only used if bit 0 of dvbInaIfReprovDstConSesUsControl
             is set."
        REFERENCE
            "ES 200 800 version 2"
        ::= { dvbInaIfReprovDstConSesEntry 3 }

dvbInaIfReprovDstConSesUsNiuClientDstIpType     OBJECT-TYPE

Pedersen         Informational - Expires August 2001               78
                     DVB Cable INA Interface MIB             Feb 2001


        SYNTAX      InetAddressType
        MAX-ACCESS  read-write
        STATUS      current
        DESCRIPTION
            "The type of the IP destination address of the NIU client."
        ::= { dvbInaIfReprovDstConSesEntry 4 }

dvbInaIfReprovDstConSesUsNiuClientDstIp         OBJECT-TYPE
        SYNTAX      InetAddress
        MAX-ACCESS  read-write
        STATUS      current
        DESCRIPTION
            "The IP destination address of the NIU client.
             Only used if bit 1 of dvbInaIfReprovDstConSesUsControl
             is set."
        REFERENCE
            "ES 200 800 version 2"
        ::= { dvbInaIfReprovDstConSesEntry 5 }

dvbInaIfReprovDstConSesUsNiuClientSrcPort       OBJECT-TYPE
        SYNTAX      Unsigned32 ( 0..65535 )
        MAX-ACCESS  read-write
        STATUS      current
        DESCRIPTION
            "The source port of the NIU client.
             Only used if bit 2 of dvbInaIfReprovDstConSesUsControl
             is set."
        REFERENCE
            "ES 200 800 version 2"
        ::= { dvbInaIfReprovDstConSesEntry 6 }

dvbInaIfReprovDstConSesUsNiuClientDstPort       OBJECT-TYPE
        SYNTAX      Unsigned32 ( 0..65535 )
        MAX-ACCESS  read-write
        STATUS      current
        DESCRIPTION
            "The destination port of the NIU client.
             Only used if bit 3 of dvbInaIfReprovDstConSesUsControl
             is set."
        REFERENCE
            "ES 200 800 version 2"
        ::= { dvbInaIfReprovDstConSesEntry 7 }

dvbInaIfReprovDstConSesUsTransportProtocol      OBJECT-TYPE
        SYNTAX      INTEGER ( 0..255 )
        MAX-ACCESS  read-write
        STATUS      current
        DESCRIPTION
            "The transport protocol used by the NIU client (UDP/TCP).
             This is the 8-bit protocol field in the IP header.
             Only used if bit 4 of dvbInaIfReprovDstConSesUsControl
             is set."
        REFERENCE

Pedersen         Informational - Expires August 2001               79
                     DVB Cable INA Interface MIB             Feb 2001


            "ES 200 800 version 2"
        ::= { dvbInaIfReprovDstConSesEntry 8 }

dvbInaIfReprovDstConSesUsNiuClientSrcMac        OBJECT-TYPE
        SYNTAX      MacAddress
        MAX-ACCESS  read-write
        STATUS      current
        DESCRIPTION
            "The Ethernet source MAC address of the NIU client.
             Only used if bit 5 of dvbInaIfReprovDstConSesUsControl
             is set."
        REFERENCE
            "ES 200 800 version 2"
        ::= { dvbInaIfReprovDstConSesEntry 9 }

dvbInaIfReprovDstConSesUsNiuClientDstMac        OBJECT-TYPE
        SYNTAX      MacAddress
        MAX-ACCESS  read-write
        STATUS      current
        DESCRIPTION
            "The Ethernet destination MAC address of the NIU client.
             Only used if bit 6 of dvbInaIfReprovDstConSesUsControl
             is set."
        REFERENCE
            "ES 200 800 version 2"
        ::= { dvbInaIfReprovDstConSesEntry 10 }

dvbInaIfReprovDstConSesUsEthernetProtocol       OBJECT-TYPE
        SYNTAX      Unsigned32 ( 0..65535 )
        MAX-ACCESS  read-write
        STATUS      current
        DESCRIPTION
            "The ethernet protocol, as described in the ethernet header.
             This is the type field in the Ethernet protocol header.
             Only used if bit 7 of dvbInaIfReprovDstConSesUsControl
             is set."
        REFERENCE
            "ES 200 800 version 2"
        ::= { dvbInaIfReprovDstConSesEntry 11 }

dvbInaIfReprovDstConSesUsSessionId              OBJECT-TYPE
        SYNTAX      Unsigned32 ( 0..4294967295 )
        MAX-ACCESS  read-write
        STATUS      current
        DESCRIPTION
            "The session_Id, as defined for PPPoE protocol.
             Only used if bit 8 of dvbInaIfReprovDstConSesUsControl
             is set."
        REFERENCE
            "ES 200 800 version 2"
        ::= { dvbInaIfReprovDstConSesEntry 12 }

dvbInaIfReprovDstConSesDsControl                OBJECT-TYPE

Pedersen         Informational - Expires August 2001               80
                     DVB Cable INA Interface MIB             Feb 2001


        SYNTAX      Unsigned32 ( 0..4294967295 )
        MAX-ACCESS  read-write
        STATUS      current
        DESCRIPTION
            "Control which fields of the downstream session binding
             parameters that are used."
        REFERENCE
            "ES 200 800 version 2"
        ::= { dvbInaIfReprovDstConSesEntry 13 }

dvbInaIfReprovDstConSesDsInaClientSrcIpType     OBJECT-TYPE
        SYNTAX      InetAddressType
        MAX-ACCESS  read-write
        STATUS      current
        DESCRIPTION
            "The type of the IP source address of the INA client."
        ::= { dvbInaIfReprovDstConSesEntry 14 }

dvbInaIfReprovDstConSesDsInaClientSrcIp         OBJECT-TYPE
        SYNTAX      InetAddress
        MAX-ACCESS  read-write
        STATUS      current
        DESCRIPTION
            "The IP source address of the INA client.
             Only used if bit 0 of dvbInaIfReprovDstConSesDsControl
             is set."
        REFERENCE
            "ES 200 800 version 2"
        ::= { dvbInaIfReprovDstConSesEntry 15 }

dvbInaIfReprovDstConSesDsInaClientDstIpType     OBJECT-TYPE
        SYNTAX      InetAddressType
        MAX-ACCESS  read-write
        STATUS      current
        DESCRIPTION
            "The type of the IP destination address of the INA client."
        ::= { dvbInaIfReprovDstConSesEntry 16 }

dvbInaIfReprovDstConSesDsInaClientDstIp         OBJECT-TYPE
        SYNTAX      InetAddress
        MAX-ACCESS  read-write
        STATUS      current
        DESCRIPTION
            "The IP destination address of the INA client.
             Only used if bit 1 of dvbInaIfReprovDstConSesDsControl
             is set."
        REFERENCE
            "ES 200 800 version 2"
        ::= { dvbInaIfReprovDstConSesEntry 17 }

dvbInaIfReprovDstConSesDsInaClientSrcPort       OBJECT-TYPE
        SYNTAX      Unsigned32 ( 0..65535 )
        MAX-ACCESS  read-write

Pedersen         Informational - Expires August 2001               81
                     DVB Cable INA Interface MIB             Feb 2001


        STATUS      current
        DESCRIPTION
            "The source port of the INA client.
             Only used if bit 2 of dvbInaIfReprovDstConSesDsControl
             is set."
        REFERENCE
            "ES 200 800 version 2"
        ::= { dvbInaIfReprovDstConSesEntry 18 }

dvbInaIfReprovDstConSesDsInaClientDstPort       OBJECT-TYPE
        SYNTAX      Unsigned32 ( 0..65535 )
        MAX-ACCESS  read-write
        STATUS      current
        DESCRIPTION
            "The destination port of the INA client.
             Only used if bit 3 of dvbInaIfReprovDstConSesDsControl
             is set."
        REFERENCE
            "ES 200 800 version 2"
        ::= { dvbInaIfReprovDstConSesEntry 19 }

dvbInaIfReprovDstConSesDsTransportProtocol      OBJECT-TYPE
        SYNTAX      INTEGER ( 0..255 )
        MAX-ACCESS  read-write
        STATUS      current
        DESCRIPTION
            "The transport protocol used by the INA client (UDP/TCP).
             This is the 8-bit protocol field in the IP header.
             Only used if bit 4 of dvbInaIfReprovDstConSesDsControl
             is set."
        REFERENCE
            "ES 200 800 version 2"
        ::= { dvbInaIfReprovDstConSesEntry 20 }

dvbInaIfReprovDstConSesDsInaClientSrcMac        OBJECT-TYPE
        SYNTAX      MacAddress
        MAX-ACCESS  read-write
        STATUS      current
        DESCRIPTION
            "The Ethernet source MAC address of the INA client.
             Only used if bit 5 of dvbInaIfReprovDstConSesDsControl
             is set."
        REFERENCE
            "ES 200 800 version 2"
        ::= { dvbInaIfReprovDstConSesEntry 21 }

dvbInaIfReprovDstConSesDsInaClientDstMac        OBJECT-TYPE
        SYNTAX      MacAddress
        MAX-ACCESS  read-write
        STATUS      current
        DESCRIPTION
            "The Ethernet destination MAC address of the INA client.
             Only used if bit 6 of dvbInaIfReprovDstConSesDsControl

Pedersen         Informational - Expires August 2001               82
                     DVB Cable INA Interface MIB             Feb 2001


             is set."
        REFERENCE
            "ES 200 800 version 2"
        ::= { dvbInaIfReprovDstConSesEntry 22 }

dvbInaIfReprovDstConSesDsEthernetProtocol       OBJECT-TYPE
        SYNTAX      Unsigned32 ( 0..65535 )
        MAX-ACCESS  read-write
        STATUS      current
        DESCRIPTION
            "The ethernet protocol, as described in the ethernet header.
             This is the type field in the Ethernet protocol header.
             Only used if bit 7 of dvbInaIfReprovDstConSesDsControl
             is set."
        REFERENCE
            "ES 200 800 version 2"
        ::= { dvbInaIfReprovDstConSesEntry 23 }

dvbInaIfReprovDstConSesDsSessionId              OBJECT-TYPE
        SYNTAX      Unsigned32 ( 0..4294967295 )
        MAX-ACCESS  read-write
        STATUS      current
        DESCRIPTION
            "The session_Id, as defined for PPPoE protocol.
             Only used if bit 8 of dvbInaIfReprovDstConSesDsControl
             is set."
        REFERENCE
            "ES 200 800 version 2"
        ::= { dvbInaIfReprovDstConSesEntry 24 }


    --  - - - - - - - - - - - - - - -
    -- Reprov Dst Header Sup tables
    --  - - - - - - - - - - - - - - -

dvbInaIfReprovDstConHdrSupTable         OBJECT-TYPE
        SYNTAX      SEQUENCE OF DvbInaIfReprovDstConHdrSupEntry
        MAX-ACCESS  not-accessible
        STATUS      current
        DESCRIPTION
            "Contains information about DVB-RC MAC connections
             that is about to be reprovisioned to INA 2."
        ::= { dvbInaIfReprov 6 }

dvbInaIfReprovDstConHdrSupEntry               OBJECT-TYPE
        SYNTAX      DvbInaIfReprovDstConHdrSupEntry
        MAX-ACCESS  not-accessible
        STATUS      current
        DESCRIPTION
            "The entries in the table are created by the manager
             when a NIU is about to be reprovisioned to INA 2.

             After the NIU has signed on to INA 2, the information in

Pedersen         Informational - Expires August 2001               83
                     DVB Cable INA Interface MIB             Feb 2001


             the tables are used to create entries in the normal
             connection tables.
             When the entries in the normal tables are made
             the entries in the reprovisioning table are automatically
             deleted."
        INDEX { dvbInaIfReprovDstNiuMacAddress,
                dvbInaIfReprovDstConConnectionIdOld,
                dvbInaIfReprovDstConHdrSupContextId,
                dvbInaIfReprovDstConHdrSupDirection }
        ::= { dvbInaIfReprovDstConHdrSupTable 1 }

DvbInaIfReprovDstConHdrSupEntry  ::= SEQUENCE {
            dvbInaIfReprovDstConHdrSupContextId         INTEGER,
            dvbInaIfReprovDstConHdrSupDirection         INTEGER,
            dvbInaIfReprovDstConHdrSupRowAccessStatus   RowStatus,
            dvbInaIfReprovDstConHdrSupControl           OCTET STRING,
            dvbInaIfReprovDstConHdrSupGeneration        Integer32,
            dvbInaIfReprovDstConHdrSupHeaderLength      Integer32,
            dvbInaIfReprovDstConHdrSupHeader            OCTET STRING
        }

dvbInaIfReprovDstConHdrSupContextId             OBJECT-TYPE
        SYNTAX      INTEGER ( 0..127 )
        MAX-ACCESS  not-accessible
        STATUS      current
        DESCRIPTION
            "The context ID for the header suppression session."
        REFERENCE
            "ES 200 800 Suppression Data Message"
        ::= { dvbInaIfReprovDstConHdrSupEntry 1 }

dvbInaIfReprovDstConHdrSupDirection             OBJECT-TYPE
        SYNTAX      INTEGER {
                    upstream( 1 ),
                    downstream( 2 )
                    }
        MAX-ACCESS  not-accessible
        STATUS      current
        DESCRIPTION
            "The direction for this the header suppression session."
        REFERENCE
            "ES 200 800 Suppression Data Message"
        ::= { dvbInaIfReprovDstConHdrSupEntry 2 }

dvbInaIfReprovDstConHdrSupRowAccessStatus       OBJECT-TYPE
        SYNTAX      RowStatus
        MAX-ACCESS  read-create
        STATUS      current
        DESCRIPTION
            "Controls and reflects the status of this row in this
            table. "
        ::= { dvbInaIfReprovDstConHdrSupEntry 3 }


Pedersen         Informational - Expires August 2001               84
                     DVB Cable INA Interface MIB             Feb 2001


dvbInaIfReprovDstConHdrSupControl               OBJECT-TYPE
        SYNTAX      OCTET STRING ( SIZE ( 13 ))
        MAX-ACCESS  read-only
        STATUS      current
        DESCRIPTION
            "String of bits that control the use of the header
             suppression. Each of the fisrt 103 bits, indicates
             if a byte in the header is suppressed or not.
             Bit 103 is used as an overall suppression enable.
             If a mask bit is 0, the matching header byte is
             suppressed.
             If bit 103 is set, suppression is performed.
             Bit 103 is the least significant bit in octet 13.
             See also dvbInaIfReprovDstConHdrSupHeader."
        REFERENCE
            "ES 200 800 Suppression Data Message"
        ::= { dvbInaIfReprovDstConHdrSupEntry 4 }

dvbInaIfReprovDstConHdrSupGeneration            OBJECT-TYPE
        SYNTAX      Integer32 ( 0..15 )
        MAX-ACCESS  read-only
        STATUS      current
        DESCRIPTION
            "The generation number that is attached to the header
             fields value."
        REFERENCE
            "ES 200 800 Suppression Data Message"
        ::= { dvbInaIfReprovDstConHdrSupEntry 5 }

dvbInaIfReprovDstConHdrSupHeaderLength          OBJECT-TYPE
        SYNTAX      Integer32 ( 0..103 )
        MAX-ACCESS  read-only
        STATUS      current
        DESCRIPTION
            "The number of usefull bytes in the suppression header.
             This is the number of the last zero in the
             dvbInaIfReprovDstConHdrSupControl."
        REFERENCE
            "ES 200 800 Suppression Data Message"
        ::= { dvbInaIfReprovDstConHdrSupEntry 6 }

dvbInaIfReprovDstConHdrSupHeader                OBJECT-TYPE
        SYNTAX      OCTET STRING ( SIZE ( 103 ))
        MAX-ACCESS  read-only
        STATUS      current
        DESCRIPTION
            "The header used for header suppression.
             Both fixed and changing fields together.
             Only the first dvbInaIfReprovDstConHdrSupHeaderLength is
             used."
        REFERENCE
            "ES 200 800 Suppression Data Message"
        ::= { dvbInaIfReprovDstConHdrSupEntry 7 }

Pedersen         Informational - Expires August 2001               85
                     DVB Cable INA Interface MIB             Feb 2001




    --  - - - - - - - - - - - - - - -
    -- Reprov Dst QoS tables
    --  - - - - - - - - - - - - - - -

dvbInaIfReprovDstConQosTable         OBJECT-TYPE
        SYNTAX      SEQUENCE OF DvbInaIfReprovDstConQosEntry
        MAX-ACCESS  not-accessible
        STATUS      current
        DESCRIPTION
            "Contains information about DVB-RC MAC connections
             that is about to be reprovisioned to INA 2."
        ::= { dvbInaIfReprov 7 }

dvbInaIfReprovDstConQosEntry               OBJECT-TYPE
        SYNTAX      DvbInaIfReprovDstConQosEntry
        MAX-ACCESS  not-accessible
        STATUS      current
        DESCRIPTION
            "The entries in the table are created automatically
             when an entry in the dvbInaIfReprovDstConTable is created
             and the INA support QoS settings.

             After the NIU has signed on to INA 2, the information in
             the tables are used to create entries in the normal
             connection tables.
             When the entries in the normal tables are made
             the entries in the reprovisioning table are automatically
             deleted."
        INDEX { dvbInaIfReprovDstNiuMacAddress,
                dvbInaIfReprovDstConConnectionIdOld }
        ::= { dvbInaIfReprovDstConQosTable 1 }


DvbInaIfReprovDstConQosEntry ::= SEQUENCE {
            dvbInaIfReprovDstConQosPriority             INTEGER,
            dvbInaIfReprovDstConQosDsReqMaxPacketSize   Unsigned32,
            dvbInaIfReprovDstConQosDsReqBitrate         Unsigned32,
            dvbInaIfReprovDstConQosDsReqJitter          INTEGER,
            dvbInaIfReprovDstConQosUsReqBw              Unsigned32,
            dvbInaIfReprovDstConQosUsReqMaxDistSlots    Unsigned32,
            dvbInaIfReprovDstConQosUsReqFrameLength     Unsigned32,
            dvbInaIfReprovDstConQosUsReqFixedRateMethod INTEGER
        }

dvbInaIfReprovDstConQosPriority                 OBJECT-TYPE
        SYNTAX      INTEGER ( 0..255 )
        MAX-ACCESS  read-create
        STATUS      current
        DESCRIPTION
            "The priority of the connection.
             Connections with low priority field value can be

Pedersen         Informational - Expires August 2001               86
                     DVB Cable INA Interface MIB             Feb 2001


             reprovisioned in order to accommodate the requirements
             of connections with high priority field.
                Standard data flow applications     0-79
                Applications with QoS requirements  80-200
                High priority applications          201-255"
        REFERENCE
            "ES 200 800 Resource Request Message"
        ::= { dvbInaIfReprovDstConQosEntry 1 }

dvbInaIfReprovDstConQosDsReqMaxPacketSize       OBJECT-TYPE
        SYNTAX      Unsigned32 ( 0..65535 )
        MAX-ACCESS  read-create
        STATUS      current
        DESCRIPTION
            "A downstream QoS parameter. Defines the requested
             maximum packet size in the downstream.
             The parameter can be set either by the managment system,
             or by the INA according to the NIU resource request.
             The packet size includes propriety protocols header,
             transport protocol (UDP/TCP) header, and the IP header.
             The packet size does not include the Ethernet header."
        REFERENCE
            "ES 200 800 Resource Request Message"
        ::= { dvbInaIfReprovDstConQosEntry 2 }

dvbInaIfReprovDstConQosDsReqBitrate             OBJECT-TYPE
        SYNTAX      Unsigned32 ( 0..65535 )
        UNITS       "bytes/s"
        MAX-ACCESS  read-create
        STATUS      current
        DESCRIPTION
            "A downstream QoS parameter. Defines requested average
             bit rate in the downstream."
        REFERENCE
            "ES 200 800 Resource Request Message"
        ::= { dvbInaIfReprovDstConQosEntry 3 }

dvbInaIfReprovDstConQosDsReqJitter              OBJECT-TYPE
        SYNTAX      INTEGER ( 0..255 )
        UNITS       "ms"
        MAX-ACCESS  read-create
        STATUS      current
        DESCRIPTION
            "A downstream QoS parameter. Defines the requested
             maximum allowed jitter in the downstream."
        REFERENCE
            "ES 200 800 Resource Request Message"
        ::= { dvbInaIfReprovDstConQosEntry 4 }

dvbInaIfReprovDstConQosUsReqBw                  OBJECT-TYPE
        SYNTAX      Unsigned32 ( 0..16777215 )
        UNITS       "slots/1200 ms"
        MAX-ACCESS  read-create

Pedersen         Informational - Expires August 2001               87
                     DVB Cable INA Interface MIB             Feb 2001


        STATUS      current
        DESCRIPTION
            "An upstream QoS parameter. The requested bandwidth
             for the upstream."
        REFERENCE
            "ES 200 800 Resource Request Message"
        ::= { dvbInaIfReprovDstConQosEntry 5 }

dvbInaIfReprovDstConQosUsReqMaxDistSlots        OBJECT-TYPE
        SYNTAX      Unsigned32 ( 0..65535 )
        UNITS       "slots"
        MAX-ACCESS  read-create
        STATUS      current
        DESCRIPTION
            "An upstream QoS parameter. The requested maximum
             distance between slots for the upstream."
        REFERENCE
            "ES 200 800 Resource Request Message"
        ::= { dvbInaIfReprovDstConQosEntry 6 }

dvbInaIfReprovDstConQosUsReqFrameLength         OBJECT-TYPE
        SYNTAX      Unsigned32 ( 0..65535 )
        MAX-ACCESS  read-create
        STATUS      current
        DESCRIPTION
            "An upstream QoS parameter. The requested frame
             length for the upstream."
        REFERENCE
            "ES 200 800 Connect Message."
        ::= { dvbInaIfReprovDstConQosEntry 7 }

dvbInaIfReprovDstConQosUsReqFixedRateMethod        OBJECT-TYPE
        SYNTAX      INTEGER {
                    cyclic( 1 ),
                    slotList( 2 )
                    }
        MAX-ACCESS  read-create
        STATUS      current
        DESCRIPTION
            "An upstream QoS parameter. Request a specific fixed rate
             slot assignment method to be used.
             If cyclic   then cyclic assignment is used.
             If slotList then the slot list method is used."
        REFERENCE
            "ES 200 800 Connect Message and Resource Request Message"
        ::= { dvbInaIfReprovDstConQosEntry 8 }


-- - - - - - - - - - - - - - - - - - - - - - - - - - - - - - - - - - -
-- Conformance statements
-- - - - - - - - - - - - - - - - - - - - - - - - - - - - - - - - - - -

dvbInaIfCompliance MODULE-COMPLIANCE

Pedersen         Informational - Expires August 2001               88
                     DVB Cable INA Interface MIB             Feb 2001


        STATUS      current
        DESCRIPTION
            "The compliance statement for EuroModem INAs
             which implement the DVB-CABLE-INA-IF-MIB MIB. An
             implementation only has to support IPv4 addresses
             to be compliant."


MODULE  -- dvbInaIf
        MANDATORY-GROUPS { dvbInaIfMacGroup,
                           dvbInaIfProvisionGroup,
                           dvbInaIfDsChGroup,
                           dvbInaIfUsChGroup,
                           dvbInaIfNiuGroup,
                           dvbInaIfConnectionGroup
                          }

        GROUP dvbInaIfConQosGroup
            DESCRIPTION
                "The QoS group is optional to implement."

        GROUP dvbInaIfConSesGroup
            DESCRIPTION
                "The session binding group is optional to implement."

        GROUP dvbInaIfConHdrSupGroup
            DESCRIPTION
                "The header suppression group is optional to implement."

        GROUP dvbInaIfReprovSrcNiuGroup
            DESCRIPTION
                "The reprovisoning NIU source group is optional to
                 implement."

        GROUP dvbInaIfReprovDstNiuGroup
            DESCRIPTION
                "The reprovisoning NIU destionation group is optional
                 to implement."

        GROUP dvbInaIfReprovSrcConGroup
            DESCRIPTION
                "The reprovisoning connection source group is optional
                 to implement."

        GROUP dvbInaIfReprovDstConGroup
            DESCRIPTION
                "The reprovisoning connection destination group is
                 optional to implement."

        GROUP dvbInaIfReprovDstConSesGroup
            DESCRIPTION
                "The reprovisioning session binding group is optional
                 to implement."

Pedersen         Informational - Expires August 2001               89
                     DVB Cable INA Interface MIB             Feb 2001



        GROUP dvbInaIfReprovDstConHdrSupGroup
            DESCRIPTION
                "The reprovisoning header suppression group is optional
                 to implement."

        GROUP dvbInaIfReprovDstConQosGroup
            DESCRIPTION
                "The reprovisioning QoS group is optional to implement."

        OBJECT dvbInaIfMacTimeout0
           MIN-ACCESS  read-only
           DESCRIPTION
               "It is compliant to implement this object as read-only."

        OBJECT dvbInaIfMacTimeout1
           MIN-ACCESS  read-only
           DESCRIPTION
               "It is compliant to implement this object as read-only."

        OBJECT dvbInaIfMacTimeout2
           MIN-ACCESS  read-only
           DESCRIPTION
               "It is compliant to implement this object as read-only."

        OBJECT dvbInaIfMacTimeout3
           MIN-ACCESS  read-only
           DESCRIPTION
               "It is compliant to implement this object as read-only."

        OBJECT dvbInaIfMacTimeout4
           MIN-ACCESS  read-only
           DESCRIPTION
               "It is compliant to implement this object as read-only."

        OBJECT dvbInaIfMacTimeoutD
           MIN-ACCESS  read-only
           DESCRIPTION
               "It is compliant to implement this object as read-only."

        OBJECT dvbInaIfMacTimeoutE
           MIN-ACCESS  read-only
           DESCRIPTION
               "It is compliant to implement this object as read-only."

        OBJECT dvbInaIfMacTimeoutF
           MIN-ACCESS  read-only
           DESCRIPTION
               "It is compliant to implement this object as read-only."

        OBJECT dvbInaIfMacRapidSignOnEnable
           MIN-ACCESS  read-only
           DESCRIPTION

Pedersen         Informational - Expires August 2001               90
                     DVB Cable INA Interface MIB             Feb 2001


               "It is compliant to implement this object as read-only."

        OBJECT dvbInaIfMacRespCollTimeWindow
           MIN-ACCESS  read-only
           DESCRIPTION
               "It is compliant to implement this object as read-only."

        OBJECT dvbInaIfMacAddressFilterUse
           MIN-ACCESS  read-only
           DESCRIPTION
               "It is compliant to implement this object as read-only."

        OBJECT dvbInaIfMacAddressPositionMask
           MIN-ACCESS  read-only
           DESCRIPTION
               "It is compliant to implement this object as read-only."

        OBJECT dvbInaIfMacAddressComparisonValue
           MIN-ACCESS  read-only
           DESCRIPTION
               "It is compliant to implement this object as read-only."

        OBJECT dvbInaIfMacProtocolSupport
           MIN-ACCESS  read-only
           DESCRIPTION
               "It is compliant to implement this object as read-only."

        OBJECT dvbInaIfMacGrantProtocolTimeOut
           MIN-ACCESS  read-only
           DESCRIPTION
               "It is compliant to implement this object as read-only."

        OBJECT dvbInaIfMacIdleInterval
           MIN-ACCESS  read-only
           DESCRIPTION
               "It is compliant to implement this object as read-only."

        OBJECT dvbInaIfMacIdleInvalidCount
           MIN-ACCESS  read-only
           DESCRIPTION
               "It is compliant to implement this object as read-only."

        OBJECT dvbInaIfMacCapabilities
           MIN-ACCESS  read-only
           DESCRIPTION
               "It is compliant to implement this object as read-only."

        OBJECT dvbInaIfMacExtendedCapabilities
           MIN-ACCESS  read-only
           DESCRIPTION
               "It is compliant to implement this object as read-only."

        OBJECT dvbInaIfMacN

Pedersen         Informational - Expires August 2001               91
                     DVB Cable INA Interface MIB             Feb 2001


           MIN-ACCESS  read-only
           DESCRIPTION
               "It is compliant to implement this object as read-only."

        OBJECT dvbInaIfProvChMaxPowerLevel
           MIN-ACCESS  read-only
           DESCRIPTION
               "It is compliant to implement this object as read-only."

        OBJECT dvbInaIfProvChMinPowerLevel
           MIN-ACCESS  read-only
           DESCRIPTION
               "It is compliant to implement this object as read-only."

        OBJECT dvbInaIfProvChMaxBackOffExponent
           MIN-ACCESS  read-only
           DESCRIPTION
               "It is compliant to implement this object as read-only."

        OBJECT dvbInaIfProvChMinBackOffExponent
           MIN-ACCESS  read-only
           DESCRIPTION
               "It is compliant to implement this object as read-only."

        OBJECT dvbInaIfDsChDownCoaxId
           MIN-ACCESS  read-only
           DESCRIPTION
               "It is compliant to implement this object as read-only."

        OBJECT dvbInaIfUsChCalibrationRxPower
           MIN-ACCESS  read-only
           DESCRIPTION
               "It is compliant to implement this object as read-only."

        OBJECT dvbInaIfUsChUpCoaxId
           MIN-ACCESS  read-only
           DESCRIPTION
               "It is compliant to implement this object as read-only."

        OBJECT dvbInaIfUsChDownCoaxId
           MIN-ACCESS  read-only
           DESCRIPTION
               "It is compliant to implement this object as read-only."

        OBJECT dvbInaIfNiuDefaultConnectionId
           MIN-ACCESS  read-only
           DESCRIPTION
               "It is compliant to implement this object as read-only."

        OBJECT dvbInaIfNiuGrantProtocolTimeOut
           MIN-ACCESS  read-only
           DESCRIPTION
               "It is compliant to implement this object as read-only."

Pedersen         Informational - Expires August 2001               92
                     DVB Cable INA Interface MIB             Feb 2001



        OBJECT dvbInaIfConConnectionType
           MIN-ACCESS  read-only
           DESCRIPTION
               "It is compliant to implement this object as read-only."

        OBJECT dvbInaIfConAccessStatus
           MIN-ACCESS  read-only
           DESCRIPTION
               "It is compliant to implement this object as read-only.
                It can be set only when the connection state is :
                down(1)"

        OBJECT dvbInaIfConEncapsulation
           MIN-ACCESS  read-only
           DESCRIPTION
               "It is compliant to implement this object as read-only.
                It can be set only when the connection state is :
                down(1)"

        OBJECT dvbInaIfConFilterMACAddress
           MIN-ACCESS  read-only
           DESCRIPTION
               "It is compliant to implement this object as read-only.
                It can be set only when the connection state is :
                down(1)"

        OBJECT dvbInaIfConPID
           MIN-ACCESS  read-only
           DESCRIPTION
               "It is compliant to implement this object as read-only.
                It can be set only when the connection state is :
                down(1)"

        OBJECT dvbInaIfConMaxContentionMsgLen
           MIN-ACCESS  read-only
           DESCRIPTION
               "It is compliant to implement this object as read-only."

        OBJECT dvbInaIfConMaxReservationMsgLen
           MIN-ACCESS  read-only
           DESCRIPTION
               "It is compliant to implement this object as read-only."

        ::= { dvbInaIfCompliances 1 }

dvbInaIfMacGroup OBJECT-GROUP
        OBJECTS     {
                    dvbInaIfMacDeviceCapabilities,
                    dvbInaIfMacDeviceExtendedCapabilities,
                    dvbInaIfMacCapabilities,
                    dvbInaIfMacExtendedCapabilities,
                    dvbInaIfMacProtocolSupport,

Pedersen         Informational - Expires August 2001               93
                     DVB Cable INA Interface MIB             Feb 2001


                    dvbInaIfMacTimeout0,
                    dvbInaIfMacTimeout1,
                    dvbInaIfMacTimeout2,
                    dvbInaIfMacTimeout3,
                    dvbInaIfMacTimeout4,
                    dvbInaIfMacTimeoutD,
                    dvbInaIfMacTimeoutE,
                    dvbInaIfMacTimeoutF,
                    dvbInaIfMacRapidSignOnEnable,
                    dvbInaIfMacRespCollTimeWindow,
                    dvbInaIfMacAddressFilterUse,
                    dvbInaIfMacAddressPositionMask,
                    dvbInaIfMacAddressComparisonValue,
                    dvbInaIfMacGrantProtocolTimeOut,
                    dvbInaIfMacIdleInterval,
                    dvbInaIfMacIdleInvalidCount,
                    dvbInaIfMacN,
                    dvbInaIfMacMaxContentionMsgLen,
                    dvbInaIfMacMaxReservationMsgLen,
                    dvbInaIfMacNiuCount,
                    dvbInaIfMacConnections,
                    dvbInaIfMacUnknownNiuError,
                    dvbInaIfMacMsgDataError,
                    dvbInaIfMacMsgHdrError,
                    dvbInaIfMacInvalidNiu,
                    dvbInaIfMacTimingRangingError,
                    dvbInaIfMacPowerRangingError,
                    dvbInaIfMacOtherSignOnError
                    }
        STATUS      current
        DESCRIPTION
            "A collection of objects providing capabilities and
             statistics for the MAC layer."
        ::= { dvbInaIfGroups 1 }

dvbInaIfProvisionGroup OBJECT-GROUP
        OBJECTS     {
                    dvbInaIfProvChIndex,
                    dvbInaIfProvChRowAccessStatus,
                    dvbInaIfProvChServiceChIfIndex,
                    dvbInaIfProvChBackupServiceChIfIndex,
                    dvbInaIfProvChIncrPowerRetryCount,
                    dvbInaIfProvChMaxPowerLevel,
                    dvbInaIfProvChMinPowerLevel,
                    dvbInaIfProvChMaxBackOffExponent,
                    dvbInaIfProvChMinBackOffExponent,
                    dvbInaIfProvChAbsoluteTimeOffset
                    }
        STATUS      current
        DESCRIPTION
            ""
        ::= { dvbInaIfGroups 2 }


Pedersen         Informational - Expires August 2001               94
                     DVB Cable INA Interface MIB             Feb 2001


dvbInaIfDsChGroup OBJECT-GROUP
        OBJECTS     {
                    dvbInaIfDsChFrequency,
                    dvbInaIfDsChConnections,
                    dvbInaIfDsChTxPower,
                    dvbInaIfDsChDownCoaxId,
                    dvbInaIfDsChSymbolRate,
                    dvbInaIfDsChModulation,
                    dvbInaIfDsChType,
                    dvbInaIfDsChDefaultPID,
                    dvbInaIfDsChProvFrequency,
                    dvbInaIfDsChProvDownstreamType,
                    dvbInaIfDsChProvEnable,
                    dvbInaIfDsChProvTableIndex
                    }
        STATUS      current
        DESCRIPTION
            ""
        ::= { dvbInaIfGroups 3 }

dvbInaIfUsChGroup OBJECT-GROUP
        OBJECTS     {
                    dvbInaIfUsChFrequency,
                    dvbInaIfUsChSymbolRate,
                    dvbInaIfUsChModulation,
                    dvbInaIfUsChMacFlagSet,
                    dvbInaIfUsChId,
                    dvbInaIfUsChConnections,
                    dvbInaIfUsChCalibrationRxPower,
                    dvbInaIfUsChUpCoaxId,
                    dvbInaIfUsChDownCoaxId,
                    dvbInaIfUsChAtmCells,
                    dvbInaIfUsChAtmTimingErrors,
                    dvbInaIfUsChAtmPowerErrors,
                    dvbInaIfUsChAtmRSCorrectableErrors,
                    dvbInaIfUsChAtmRSNonCorrectableErrors,
                    dvbInaIfUsChAtmHecErrors,
                    dvbInaIfUsChAal5CrcErrors,
                    dvbInaIfUsChAtmCollisionErrors
                    }
        STATUS      current
        DESCRIPTION
            ""
    ::= { dvbInaIfGroups 4 }

dvbInaIfNiuGroup OBJECT-GROUP
        OBJECTS     {
                    dvbInaIfNiuMacAddress,
                    dvbInaIfNiuRowAccessStatus,
                    dvbInaIfNiuState,
                    dvbInaIfNiuDesiredState,
                    dvbInaIfNiuDownIfIndex,
                    dvbInaIfNiuUpIfIndex,

Pedersen         Informational - Expires August 2001               95
                     DVB Cable INA Interface MIB             Feb 2001


                    dvbInaIfNiuUpTxLevel,
                    dvbInaIfNiuTimeOffset,
                    dvbInaIfNiuStatus,
                    dvbInaIfNiuErrorCode,
                    dvbInaIfNiuRetryCount,
                    dvbInaIfNiuCapabilities,
                    dvbInaIfNiuExtendedCapabilities,
                    dvbInaIfNiuInitCompletionStatus,
                    dvbInaIfNiuRequestStatus,
                    dvbInaIfNiuResponseNumber,
                    dvbInaIfNiuRespTxLevel,
                    dvbInaIfNiuRespTimeOffset,
                    dvbInaIfNiuRespOoBDownFrequency,
                    dvbInaIfNiuRespIBDownFrequency,
                    dvbInaIfNiuRespSNRLevel,
                    dvbInaIfNiuRespRxLevel,
                    dvbInaIfNiuDefaultConnectionId,
                    dvbInaIfNiuLifetime,
                    dvbInaIfNiuGrantProtocolTimeOut,
                    dvbInaIfNiuSlotConfigurationErr,
                    dvbInaIfNiuAtmPacketLoss,
                    dvbInaIfNiuSlEsCrcErr,
                    dvbInaIfNiuSlEsFrameCount,
                    dvbInaIfNiuSlotConfigurationCount,
                    dvbInaIfNiuRSErrCorrectable,
                    dvbInaIfNiuRSErrNonCorrectable,
                    dvbInaIfNiuSignOnTime,
                    dvbInaIfNiuDsChBytes,
                    dvbInaIfNiuUsChBytes,
                    dvbInaIfNiuTimeRanging,
                    dvbInaIfNiuPowerRanging
                    }
        STATUS      current
        DESCRIPTION
            ""
    ::= { dvbInaIfGroups 5 }

dvbInaIfConnectionGroup OBJECT-GROUP
        OBJECTS     {
                    dvbInaIfConNiuMacAddress,
                    dvbInaIfConConnectionId,
                    dvbInaIfConCurrentState,
                    dvbInaIfConDesiredState,
                    dvbInaIfConConnectionType,
                    dvbInaIfConAccessStatus,
                    dvbInaIfConEncapsulation,
                    dvbInaIfConAtmDownstreamVCC,
                    dvbInaIfConAtmUpstreamVCC,
                    dvbInaIfConFilterMACAddress,
                    dvbInaIfConPID,
                    dvbInaIfConMaxContentionMsgLen,
                    dvbInaIfConMaxReservationMsgLen,
                    dvbInaIfConAuxFlags

Pedersen         Informational - Expires August 2001               96
                     DVB Cable INA Interface MIB             Feb 2001


                    }
        STATUS      current
        DESCRIPTION
            ""
    ::= { dvbInaIfGroups 6 }

dvbInaIfConQosGroup OBJECT-GROUP
        OBJECTS     {
                    dvbInaIfConQosPriority,
                    dvbInaIfConQosDsReqMaxPacketSize,
                    dvbInaIfConQosDsReqBitrate,
                    dvbInaIfConQosDsReqJitter,
                    dvbInaIfConQosDsAllocMaxPacketSize,
                    dvbInaIfConQosDsAllocBitrate,
                    dvbInaIfConQosDsAllocJitter,
                    dvbInaIfConQosUsReqBw,
                    dvbInaIfConQosUsReqMaxDistSlots,
                    dvbInaIfConQosUsReqFrameLength,
                    dvbInaIfConQosUsAllocBw,
                    dvbInaIfConQosUsAllocMaxDistSlots,
                    dvbInaIfConQosUsAllocFrameLength,
                    dvbInaIfConQosUsReqFixedRateMethod,
                    dvbInaIfConQosUsAllocFixedRateMethod
                    }
        STATUS      current
        DESCRIPTION
            ""
    ::= { dvbInaIfGroups 7 }

dvbInaIfConSesGroup OBJECT-GROUP
        OBJECTS     {
                    dvbInaIfConSesUsControl,
                    dvbInaIfConSesUsNiuClientSrcIpType,
                    dvbInaIfConSesUsNiuClientSrcIp,
                    dvbInaIfConSesUsNiuClientDstIpType,
                    dvbInaIfConSesUsNiuClientDstIp,
                    dvbInaIfConSesUsNiuClientSrcPort,
                    dvbInaIfConSesUsNiuClientDstPort,
                    dvbInaIfConSesUsTransportProtocol,
                    dvbInaIfConSesUsNiuClientSrcMac,
                    dvbInaIfConSesUsNiuClientDstMac,
                    dvbInaIfConSesUsEthernetProtocol,
                    dvbInaIfConSesUsSessionId,
                    dvbInaIfConSesDsControl,
                    dvbInaIfConSesDsInaClientSrcIpType,
                    dvbInaIfConSesDsInaClientSrcIp,
                    dvbInaIfConSesDsInaClientDstIpType,
                    dvbInaIfConSesDsInaClientDstIp,
                    dvbInaIfConSesDsInaClientSrcPort,
                    dvbInaIfConSesDsInaClientDstPort,
                    dvbInaIfConSesDsTransportProtocol,
                    dvbInaIfConSesDsInaClientSrcMac,
                    dvbInaIfConSesDsInaClientDstMac,

Pedersen         Informational - Expires August 2001               97
                     DVB Cable INA Interface MIB             Feb 2001


                    dvbInaIfConSesDsEthernetProtocol,
                    dvbInaIfConSesDsSessionId
                    }
        STATUS      current
        DESCRIPTION
            ""
    ::= { dvbInaIfGroups 8 }

dvbInaIfConHdrSupGroup OBJECT-GROUP
        OBJECTS     {
                    dvbInaIfConHdrSupContextId,
                    dvbInaIfConHdrSupDirection,
                    dvbInaIfConHdrSupControl,
                    dvbInaIfConHdrSupGeneration,
                    dvbInaIfConHdrSupHeaderLength,
                    dvbInaIfConHdrSupHeader
                    }
        STATUS      current
        DESCRIPTION
            ""
    ::= { dvbInaIfGroups 9 }

dvbInaIfReprovSrcNiuGroup OBJECT-GROUP
        OBJECTS     {
                    dvbInaIfReprovSrcNiuRowAccessStatus,
                    dvbInaIfReprovSrcNiuCommand,
                    dvbInaIfReprovSrcNiuDsChFrequency,
                    dvbInaIfReprovSrcNiuDsChSymbolRate,
                    dvbInaIfReprovSrcNiuDsChModulation,
                    dvbInaIfReprovSrcNiuDsChType,
                    dvbInaIfReprovSrcNiuUsChFrequency,
                    dvbInaIfReprovSrcNiuUsChSymbolRate,
                    dvbInaIfReprovSrcNiuUsChModulation,
                    dvbInaIfReprovSrcNiuUsChId
                    }
        STATUS      current
        DESCRIPTION
            ""
    ::= { dvbInaIfGroups 10 }

dvbInaIfReprovDstNiuGroup OBJECT-GROUP
        OBJECTS     {
                    dvbInaIfReprovDstNiuMacAddress,
                    dvbInaIfReprovDstNiuRowAccessStatus,
                    dvbInaIfReprovDstNiuCommand,
                    dvbInaIfReprovDstNiuDownIfIndex,
                    dvbInaIfReprovDstNiuUpIfIndex,
                    dvbInaIfReprovDstNiuLifetime
                    }
        STATUS      current
        DESCRIPTION
            ""
    ::= { dvbInaIfGroups 11 }

Pedersen         Informational - Expires August 2001               98
                     DVB Cable INA Interface MIB             Feb 2001



dvbInaIfReprovSrcConGroup OBJECT-GROUP
        OBJECTS     {
                    dvbInaIfReprovSrcConRowAccessStatus,
                    dvbInaIfReprovSrcConConnectionIdNew,
                    dvbInaIfReprovSrcConPID,
                    dvbInaIfReprovSrcConDsVc,
                    dvbInaIfReprovSrcConUsVc
                    }
        STATUS      current
        DESCRIPTION
            ""
    ::= { dvbInaIfGroups 12 }

dvbInaIfReprovDstConGroup OBJECT-GROUP
        OBJECTS     {
                    dvbInaIfReprovDstConConnectionIdOld,
                    dvbInaIfReprovDstConRowAccessStatus,
                    dvbInaIfReprovDstConConnectionIdNew,
                    dvbInaIfReprovDstConConnectionType,
                    dvbInaIfReprovDstConEncapsulation,
                    dvbInaIfReprovDstConAtmDownstreamVCC,
                    dvbInaIfReprovDstConAtmUpstreamVCC,
                    dvbInaIfReprovDstConFilterMACAddress,
                    dvbInaIfReprovDstConPID,
                    dvbInaIfReprovDstConMaxContentionMsgLen,
                    dvbInaIfReprovDstConMaxReservationMsgLen,
                    dvbInaIfReprovDstConAuxFlags
                    }
        STATUS      current
        DESCRIPTION
            ""
    ::= { dvbInaIfGroups 13 }

dvbInaIfReprovDstConSesGroup OBJECT-GROUP
        OBJECTS     {
                    dvbInaIfReprovDstConSesUsControl,
                    dvbInaIfReprovDstConSesUsNiuClientSrcIpType,
                    dvbInaIfReprovDstConSesUsNiuClientSrcIp,
                    dvbInaIfReprovDstConSesUsNiuClientDstIpType,
                    dvbInaIfReprovDstConSesUsNiuClientDstIp,
                    dvbInaIfReprovDstConSesUsNiuClientSrcPort,
                    dvbInaIfReprovDstConSesUsNiuClientDstPort,
                    dvbInaIfReprovDstConSesUsTransportProtocol,
                    dvbInaIfReprovDstConSesUsNiuClientSrcMac,
                    dvbInaIfReprovDstConSesUsNiuClientDstMac,
                    dvbInaIfReprovDstConSesUsEthernetProtocol,
                    dvbInaIfReprovDstConSesUsSessionId,
                    dvbInaIfReprovDstConSesDsControl,
                    dvbInaIfReprovDstConSesDsInaClientSrcIpType,
                    dvbInaIfReprovDstConSesDsInaClientSrcIp,
                    dvbInaIfReprovDstConSesDsInaClientDstIpType,
                    dvbInaIfReprovDstConSesDsInaClientDstIp,

Pedersen         Informational - Expires August 2001               99
                     DVB Cable INA Interface MIB             Feb 2001


                    dvbInaIfReprovDstConSesDsInaClientSrcPort,
                    dvbInaIfReprovDstConSesDsInaClientDstPort,
                    dvbInaIfReprovDstConSesDsTransportProtocol,
                    dvbInaIfReprovDstConSesDsInaClientSrcMac,
                    dvbInaIfReprovDstConSesDsInaClientDstMac,
                    dvbInaIfReprovDstConSesDsEthernetProtocol,
                    dvbInaIfReprovDstConSesDsSessionId
                    }
        STATUS      current
        DESCRIPTION
            ""
    ::= { dvbInaIfGroups 14 }

dvbInaIfReprovDstConHdrSupGroup OBJECT-GROUP
        OBJECTS     {
                    dvbInaIfReprovDstConHdrSupContextId,
                    dvbInaIfReprovDstConHdrSupRowAccessStatus,
                    dvbInaIfReprovDstConHdrSupDirection,
                    dvbInaIfReprovDstConHdrSupControl,
                    dvbInaIfReprovDstConHdrSupGeneration,
                    dvbInaIfReprovDstConHdrSupHeaderLength,
                    dvbInaIfReprovDstConHdrSupHeader
                    }
        STATUS      current
        DESCRIPTION
            ""
    ::= { dvbInaIfGroups 15 }

dvbInaIfReprovDstConQosGroup OBJECT-GROUP
        OBJECTS     {
                    dvbInaIfReprovDstConQosPriority,
                    dvbInaIfReprovDstConQosDsReqMaxPacketSize,
                    dvbInaIfReprovDstConQosDsReqBitrate,
                    dvbInaIfReprovDstConQosDsReqJitter,
                    dvbInaIfReprovDstConQosUsReqBw,
                    dvbInaIfReprovDstConQosUsReqMaxDistSlots,
                    dvbInaIfReprovDstConQosUsReqFrameLength,
                    dvbInaIfReprovDstConQosUsReqFixedRateMethod
                    }
        STATUS      current
        DESCRIPTION
            ""
    ::= { dvbInaIfGroups 16 }

END

-- 
--    "Copyright (C) The Internet Society (February 2001). All Rights
--    Reserved. This document and translations of it may be copied and
--    furnished to others, and derivative works that comment on or
--    otherwise explain it or assist in its implementation may be prepared,
--    copied, published and distributed, in whole or in part, without
--    restriction of any kind, provided that the above copyright notice and
--    this paragraph are included on all such copies and derivative works.
--    However, this document itself may not be modified in any way, such as
--    by removing the copyright notice or references to the Internet
--    Society or other Internet organizations, except as needed for the
--    purpose of developing Internet standards in which case the procedures
--    for copyrights defined in the Internet Standards process must be
--    followed, or as required to translate it into.
-- 
-- 
-- 
-- 
-- 
-- 
-- 
-- 
-- 
-- 
-- 
-- 
-- 
-- 
-- 
-- 
-- 
-- 
-- 
-- 
-- 
-- 
-- 
-- 
-- 
-- 
-- 
-- 
-- 
-- 
-- 
-- Pedersen         Informational - Expires August 2001              103
