--******************************************************************
--*
--*         Copyright (c) 1993, 1999 by 3Com Corporation
--*                    All Rights Reserved
--*
--*    $Revision:   1.19  $
--*    $Date:   Jun 29 2000 11:38:56  $
--*
--*    3COM D3I MIB
--*
--******************************************************************


D3I-MIB DEFINITIONS ::= BEGIN

IMPORTS
   enterprises,
   experimental,
   IpAddress,
   TimeTicks,
   Gauge,
   Counter
      FROM RFC1155-SMI
   DisplayString
      FROM RFC1213-MIB
   OBJECT-TYPE
      FROM RFC-1212;


usr OBJECT IDENTIFIER ::= { enterprises 429 }

nas OBJECT IDENTIFIER ::= { usr 1 }

d3i OBJECT IDENTIFIER ::= { nas 43 }

d3iID OBJECT IDENTIFIER ::= { d3i 1 }

d3iIDTable OBJECT-TYPE
SYNTAX SEQUENCE OF D3iIDEntry
ACCESS not-accessible
STATUS mandatory
DESCRIPTION
"This table contains an entry for each of the manageable DS3 
Ingress Cards in the chassis.  It contains objects that 
reflect the current configuration of parameters that affect 
the operation of all the entities that reside on the given 
card."
::= { d3iID 1 }

d3iIDEntry OBJECT-TYPE
SYNTAX D3iIDEntry
ACCESS not-accessible
STATUS mandatory
DESCRIPTION
"There is one Identification table entry per DS3 Card in the 
chassis."
INDEX { d3iIDIndex }
::= { d3iIDTable 1 }

D3iIDEntry ::=
SEQUENCE {
d3iIDIndex
    INTEGER,
d3iIDNACHardwareSerNum
    DisplayString,
d3iIDNICHardwareSerNum
    DisplayString,
d3iIDNACHardwareRev
    DisplayString,
d3iIDNICHardwareRev
    DisplayString,
d3iIDBoardManagerSwRev
    DisplayString,
d3iIDBoardManagerDate
    DisplayString
}

d3iIDIndex OBJECT-TYPE
SYNTAX INTEGER
ACCESS read-only
STATUS mandatory
DESCRIPTION
"A unique value for each card in the chassis. The value of 
d3iIdIndex matches the value of the index for the 
corresponding card entity in the entity table of the 
chassis MIB."
::= { d3iIDEntry 1 }

d3iIDNACHardwareSerNum OBJECT-TYPE
SYNTAX DisplayString (SIZE(0..31))
ACCESS read-only
STATUS mandatory
DESCRIPTION
"This object contains DS3 NAC module hardware serial number 
as stored in EEPROM."
::= { d3iIDEntry 2 }

d3iIDNICHardwareSerNum OBJECT-TYPE
SYNTAX DisplayString (SIZE(0..31))
ACCESS read-only
STATUS mandatory
DESCRIPTION
"This object contains DS3 NIC module hardware serial number 
as stored in EEPROM."
::= { d3iIDEntry 3 }

d3iIDNACHardwareRev OBJECT-TYPE
SYNTAX DisplayString (SIZE(0..11))
ACCESS read-only
STATUS mandatory
DESCRIPTION
"This object contains DS3 NAC module hardware revision as 
stored in EEPROM."
::= { d3iIDEntry 4 }

d3iIDNICHardwareRev OBJECT-TYPE
SYNTAX DisplayString (SIZE(0..11))
ACCESS read-only
STATUS mandatory
DESCRIPTION
"This object contains DS3 NIC module hardware revision as 
stored in EEPROM."
::= { d3iIDEntry 5 }

d3iIDBoardManagerSwRev OBJECT-TYPE
SYNTAX DisplayString (SIZE(0..11))
ACCESS read-only
STATUS mandatory
DESCRIPTION
"This object contains revision of the software being 
executed by the DS3 NAC board manager processor."
::= { d3iIDEntry 6 }

d3iIDBoardManagerDate OBJECT-TYPE
SYNTAX DisplayString (SIZE(0..8))
ACCESS read-only
STATUS mandatory
DESCRIPTION
"This object contains board manager build date."
::= { d3iIDEntry 7 }

d3iCfg OBJECT IDENTIFIER ::= { d3i 2 }

d3iCfgTable OBJECT-TYPE
SYNTAX SEQUENCE OF D3iCfgEntry
ACCESS not-accessible
STATUS mandatory
DESCRIPTION
"This table contains an entry for each of the manageable DS3 
Ingress Cards in the chassis.  It contains objects that 
reflect the current configuration of parameters that affect 
the operation of all the entities that reside on the given 
card."
::= { d3iCfg 1 }

d3iCfgEntry OBJECT-TYPE
SYNTAX D3iCfgEntry
ACCESS not-accessible
STATUS mandatory
DESCRIPTION
"There is one Configuration table entry per DS3 Card in the 
chassis."
INDEX { d3iCfgIndex }
::= { d3iCfgTable 1 }

D3iCfgEntry ::=
SEQUENCE {
d3iCfgIndex
    INTEGER,
d3iCfgPrimaryTimeSource
    INTEGER,
d3iCfgSecondaryTimeSource
    INTEGER,
d3iCfgTimeSourceSwitchMode
    INTEGER,
d3iCfgCLIPromptName
    DisplayString
}

d3iCfgIndex OBJECT-TYPE
SYNTAX INTEGER
ACCESS read-only
STATUS mandatory
DESCRIPTION
"A unique value for each card in the chassis. The value of 
d3iCfgIndex matches the value of the index for the 
corresponding card entity in the entity table of the 
chassis MIB."
::= { d3iCfgEntry 1 }

d3iCfgPrimaryTimeSource OBJECT-TYPE
SYNTAX INTEGER{
  spanBITS(128),
  internal(129),
  throughTDM(130),
  span1(1),
  span2(2),
  span3(3),
  span4(4),
  span5(5),
  span6(6),
  span7(7),
  span8(8),
  span9(9),
  span10(10),
  span11(11),
  span12(12),
  span13(13),
  span14(14),
  span15(15),
  span16(16),
  span17(17),
  span18(18),
  span19(19),
  span20(20),
  span21(21),
  span22(22),
  span23(23),
  span24(24),
  span25(25),
  span26(26),
  span27(27),
  span28(28)
}
ACCESS read-write
STATUS mandatory
DESCRIPTION
"This object contains Designation of primary system clock 
timing reference source."
::= { d3iCfgEntry 2 }

d3iCfgSecondaryTimeSource OBJECT-TYPE
SYNTAX INTEGER{
  spanBITS(128),
  internal(129),
  throughTDM(130),
  span1(1),
  span2(2),
  span3(3),
  span4(4),
  span5(5),
  span6(6),
  span7(7),
  span8(8),
  span9(9),
  span10(10),
  span11(11),
  span12(12),
  span13(13),
  span14(14),
  span15(15),
  span16(16),
  span17(17),
  span18(18),
  span19(19),
  span20(20),
  span21(21),
  span22(22),
  span23(23),
  span24(24),
  span25(25),
  span26(26),
  span27(27),
  span28(28)
}
ACCESS read-write
STATUS mandatory
DESCRIPTION
"This object contains Designation of secondary system clock 
timing reference source."
::= { d3iCfgEntry 3 }

d3iCfgTimeSourceSwitchMode OBJECT-TYPE
SYNTAX INTEGER{
  automatic(1),
  manual(2)
}
ACCESS read-write
STATUS mandatory
DESCRIPTION
"If a clock failure occurs on the currently active clock 
timing reference, this object specifies whether the 
switchover to the backup reference will be performed 
automatically or manually."
::= { d3iCfgEntry 4 }

d3iCfgCLIPromptName OBJECT-TYPE
SYNTAX DisplayString (SIZE(0..31))
ACCESS read-write
STATUS mandatory
DESCRIPTION
"This object is used to identify DS3 module's console prompt 
name."
::= { d3iCfgEntry 5 }

d3iStat OBJECT IDENTIFIER ::= { d3i 3 }

d3iStatTable OBJECT-TYPE
SYNTAX SEQUENCE OF D3iStatEntry
ACCESS not-accessible
STATUS mandatory
DESCRIPTION
"The Status table contains an entry for each DS3 card in the 
chassis."
::= { d3iStat 1 }

d3iStatEntry OBJECT-TYPE
SYNTAX D3iStatEntry
ACCESS not-accessible
STATUS mandatory
DESCRIPTION
"There is one entry for each DS3 card in the chassis."
INDEX { d3iStatIndex }
::= { d3iStatTable 1 }

D3iStatEntry ::=
SEQUENCE {
d3iStatIndex
    INTEGER,
d3iStatSigPBusTxPktOkCnt
    Counter,
d3iStatSigPBusTxPktFldCnt
    Counter,
d3iStatSigPBusRxPktOkCnt
    Counter,
d3iStatSigPBusRxPktRjtCnt
    Counter,
d3iStatSigPBusConnState
    INTEGER,
d3iStatEnfasLinkDownCause
    INTEGER,
d3iStatPbClock
    INTEGER,
d3iStatTdmClock
    INTEGER
}

d3iStatIndex OBJECT-TYPE
SYNTAX INTEGER
ACCESS read-only
STATUS mandatory
DESCRIPTION
"A unique value for each DS3 card in the chassis.  The value 
of this object matches the value of the index of the 
corresponding DS3 card's entry in the entity table of the 
chassis MIB."
::= { d3iStatEntry 1 }

d3iStatSigPBusTxPktOkCnt OBJECT-TYPE
SYNTAX Counter
ACCESS read-only
STATUS mandatory
DESCRIPTION
"The number of successful packets transmitted over the 
signaling packet bus connection."
::= { d3iStatEntry 2 }

d3iStatSigPBusTxPktFldCnt OBJECT-TYPE
SYNTAX Counter
ACCESS read-only
STATUS mandatory
DESCRIPTION
"The number of packets failed to transmit over the signaling 
packet bus connection."
::= { d3iStatEntry 3 }

d3iStatSigPBusRxPktOkCnt OBJECT-TYPE
SYNTAX Counter
ACCESS read-only
STATUS mandatory
DESCRIPTION
"The number of successful packets received over the 
signaling packet bus connection."
::= { d3iStatEntry 4 }

d3iStatSigPBusRxPktRjtCnt OBJECT-TYPE
SYNTAX Counter
ACCESS read-only
STATUS mandatory
DESCRIPTION
"The number of packets rejected by the DS3 NAC module 
message handling application."
::= { d3iStatEntry 5 }

d3iStatSigPBusConnState OBJECT-TYPE
SYNTAX INTEGER{
  closed(1),
  opening(2),
  opened(3),
  configuring(4),
  ready(5),
  closing(6),
  loopback(7)
}
ACCESS read-only
STATUS mandatory
DESCRIPTION
"The state of the signaling packet bus connection to the 
JHDM NAC. The loopback state means the DS3 has been 
requested, over the signaling packet bus link, to loopback 
all of its signaling channel received data. It will stay in 
this state until the DS3 sends an call control message to 
remove the loopback on this signaling connection."
::= { d3iStatEntry 6 }

d3iStatEnfasLinkDownCause OBJECT-TYPE
SYNTAX INTEGER{
  none(1),
  discCmd(2),
  nacRemoval(3)
}
ACCESS read-only
STATUS mandatory
DESCRIPTION
"The reason for the E-NFAS signaling link going down. 
DisCmd: A DISC command was received over the packet bus 
signaling link. NACRemoval: A chassis awareness message 
indicated that the NAC connected to the E-NFAS link has 
been removed."
::= { d3iStatEntry 7 }

d3iStatPbClock OBJECT-TYPE
SYNTAX INTEGER{
  notSupported(1),
  clockMaster(2),
  clockSlave(3),
  noClockPresent(4)
}
ACCESS read-only
STATUS mandatory
DESCRIPTION
"This object defines the current status of the packet bus 
clock."
::= { d3iStatEntry 8 }

d3iStatTdmClock OBJECT-TYPE
SYNTAX INTEGER{
  notSupported(1),
  clockMaster(2),
  clockSlave(3),
  noClockPresent(4)
}
ACCESS read-only
STATUS mandatory
DESCRIPTION
"This object defines the current status of the TDM bus 
system clock."
::= { d3iStatEntry 9 }

d3iCmd OBJECT IDENTIFIER ::= { d3i 4 }

d3iCmdTable OBJECT-TYPE
SYNTAX SEQUENCE OF D3iCmdEntry
ACCESS not-accessible
STATUS mandatory
DESCRIPTION
"The DS3 card command table contains an entry for each of 
the manageable DS3 card in the chassis.  It provides a 
means through which to take specific actions on the DS3 
card in the chassis."
::= { d3iCmd 1 }

d3iCmdEntry OBJECT-TYPE
SYNTAX D3iCmdEntry
ACCESS not-accessible
STATUS mandatory
DESCRIPTION
"There is one DS3 card command entry per DS3 card in the 
chassis."
INDEX { d3iCmdIndex }
::= { d3iCmdTable 1 }

D3iCmdEntry ::=
SEQUENCE {
d3iCmdIndex
    INTEGER,
d3iCmdMgtStationId
    OCTET STRING,
d3iCmdReqId
    INTEGER,
d3iCmdFunction
    INTEGER,
d3iCmdForce
    INTEGER,
d3iCmdParam
    OCTET STRING,
d3iCmdResult
    INTEGER,
d3iCmdCode
    INTEGER
}

d3iCmdIndex OBJECT-TYPE
SYNTAX INTEGER
ACCESS read-only
STATUS mandatory
DESCRIPTION
"A unique value for each DS3 card in the chassis.  The value 
of this object matches the value of the index of the 
corresponding DS3 card's entry in the entity table of the 
chassis MIB."
::= { d3iCmdEntry 1 }

d3iCmdMgtStationId OBJECT-TYPE
SYNTAX OCTET STRING (SIZE(0..8))
ACCESS read-write
STATUS mandatory
DESCRIPTION
"This object is a generic read-write variable that a 
Management Station (MS) can use to guarantee that the 
results from a command are the results of a command issued 
by that specific MS.  Each MS must SET a unique value to 
this object when doing commands and GET the value of this 
object together with d3iCmdReqId and d3iCmdResult to detect 
interference from other MSs."
::= { d3iCmdEntry 2 }

d3iCmdReqId OBJECT-TYPE
SYNTAX INTEGER
ACCESS read-only
STATUS mandatory
DESCRIPTION
"This object contains the value of the request-id field in 
the SNMP PDU which invoked the current or most recent 
command or test on this DS3 card.  If the request-id is 
unknown or undefined, this object contains the value zero."
::= { d3iCmdEntry 3 }

d3iCmdFunction OBJECT-TYPE
SYNTAX INTEGER{
  noCommand(1),
  restoreCfgFromNvram(2),
  softwareReset(3),
  restoreDefaultUIPassword(4),
  restoreCfgFromDefaults(5),
  saveCfgtoNvram(6),
  d3iNICReset(7),
  d3iNICResetHold(8)
}
ACCESS read-write
STATUS mandatory
DESCRIPTION
"This object contains a value which describes the command 
which is being invoked."
::= { d3iCmdEntry 4 }

d3iCmdForce OBJECT-TYPE
SYNTAX INTEGER{
  force(1),
  noForce(2)
}
ACCESS read-write
STATUS mandatory
DESCRIPTION
"In some cases the DS3 card may be in a state such that 
certain commands could adversely affect connections.  In 
such cases, a command request with this object not present 
or set to noForce will result in a warning.  If the 
operator elects to ignore such warnings, this object can be 
set to force in a subsequent issue of the command to cause 
the command to be carried out regardless of its potentially 
hazzardous effects."
::= { d3iCmdEntry 5 }

d3iCmdParam OBJECT-TYPE
SYNTAX OCTET STRING (SIZE(0..24))
ACCESS read-write
STATUS mandatory
DESCRIPTION
"This object contains parameters that are specific to the 
particular command being issued.  In some cases, there will 
be no addtional parameters required."
::= { d3iCmdEntry 6 }

d3iCmdResult OBJECT-TYPE
SYNTAX INTEGER{
  none(1),
  success(2),
  inProgress(3),
  notSupported(4),
  unAbleToRun(5),
  aborted(6),
  failed(7)
}
ACCESS read-only
STATUS mandatory
DESCRIPTION
"This object contains the result of the most recently 
requested command or test, or the value none(1) if no 
commands have been requested since the last reset."
::= { d3iCmdEntry 7 }

d3iCmdCode OBJECT-TYPE
SYNTAX INTEGER{
  userInterfaceActive(58),
  pendingSoftwareDownload(73)
}
ACCESS read-only
STATUS mandatory
DESCRIPTION
"The value of this object upon commad completion indicates a 
futher description of what went wrong if the command was 
unsuccessful.  In the case of tests, a bit mapped result of 
each of the sub-tests performed can be found in the status 
table."
::= { d3iCmdEntry 8 }

d3iTe OBJECT IDENTIFIER ::= { d3i 5 }

d3iTeTable OBJECT-TYPE
SYNTAX SEQUENCE OF D3iTeEntry
ACCESS not-accessible
STATUS mandatory
DESCRIPTION
"The trap table containing an enable for each that the card 
is capable of generating.  Some of these events occur often 
and traps may flood the network if care is not taken to 
avoid such conditions. These traps should be enabled 
sparingly."
::= { d3iTe 1 }

d3iTeEntry OBJECT-TYPE
SYNTAX D3iTeEntry
ACCESS not-accessible
STATUS mandatory
DESCRIPTION
"There is one entry for each DS3 card in the chassis."
INDEX { d3iTeIndex }
::= { d3iTeTable 1 }

D3iTeEntry ::=
SEQUENCE {
d3iTeIndex
    INTEGER,
d3iTePbActive
    INTEGER,
d3iTePbLost
    INTEGER,
d3iTePbClockLossEvent
    INTEGER,
d3iTePbClockRestoreEvent
    INTEGER,
d3iTeTdmClockLost
    INTEGER,
d3iTeTdmClockRestored
    INTEGER,
d3iTeEnfasLinkUp
    INTEGER,
d3iTeEnfasLinkDown
    INTEGER,
d3iTeSystemReset
    INTEGER
}

d3iTeIndex OBJECT-TYPE
SYNTAX INTEGER
ACCESS read-only
STATUS mandatory
DESCRIPTION
"A unique value for each DS3 card in the chassis.  The value 
of this object matches the value of the index of the 
corresponding DS3 card's entry in the entity table of the 
chassis MIB."
::= { d3iTeEntry 1 }

d3iTePbActive OBJECT-TYPE
SYNTAX INTEGER{
  enableTrap(1),
  disableAll(2),
  enableLog(3),
  enableAll(4)
}
ACCESS read-write
STATUS mandatory
DESCRIPTION
"Enables the Packet Bus Active Trap. Default is 
disableAll(2)."
::= { d3iTeEntry 2 }

d3iTePbLost OBJECT-TYPE
SYNTAX INTEGER{
  enableTrap(1),
  disableAll(2),
  enableLog(3),
  enableAll(4)
}
ACCESS read-write
STATUS mandatory
DESCRIPTION
"Enables the Packet Bus lost Trap. Default is 
disableAll(2)."
::= { d3iTeEntry 3 }

d3iTePbClockLossEvent OBJECT-TYPE
SYNTAX INTEGER{
  enableTrap(1),
  disableAll(2),
  enableLog(3),
  enableAll(4)
}
ACCESS read-write
STATUS mandatory
DESCRIPTION
"This object is used to disable the ability for a NAC to 
report when the packet bus clock has been lost. Defaule is 
diableAll(2)."
::= { d3iTeEntry 4 }

d3iTePbClockRestoreEvent OBJECT-TYPE
SYNTAX INTEGER{
  enableTrap(1),
  disableAll(2),
  enableLog(3),
  enableAll(4)
}
ACCESS read-write
STATUS mandatory
DESCRIPTION
"This object is used to disable the ability for a NAC to 
report when the packet bus clock has been restored. Defaule 
is diableAll(2)."
::= { d3iTeEntry 5 }

d3iTeTdmClockLost OBJECT-TYPE
SYNTAX INTEGER{
  enableTrap(1),
  disableAll(2),
  enableLog(3),
  enableAll(4)
}
ACCESS read-write
STATUS mandatory
DESCRIPTION
"Enables generation of an SNMP trap upon detection of TDM 
bus system clock lost. Default is disableAll(2)."
::= { d3iTeEntry 6 }

d3iTeTdmClockRestored OBJECT-TYPE
SYNTAX INTEGER{
  enableTrap(1),
  disableAll(2),
  enableLog(3),
  enableAll(4)
}
ACCESS read-write
STATUS mandatory
DESCRIPTION
"Enables generation of an SNMP trap upon detection of TDM 
bus system clock restored. Default is disableAll(2)."
::= { d3iTeEntry 7 }

d3iTeEnfasLinkUp OBJECT-TYPE
SYNTAX INTEGER{
  enableTrap(1),
  disableAll(2),
  enableLog(3),
  enableAll(4)
}
ACCESS read-write
STATUS mandatory
DESCRIPTION
"The trap enable for ENFAS link coming up trap. Default is 
disable."
::= { d3iTeEntry 8 }

d3iTeEnfasLinkDown OBJECT-TYPE
SYNTAX INTEGER{
  enableTrap(1),
  disableAll(2),
  enableLog(3),
  enableAll(4)
}
ACCESS read-write
STATUS mandatory
DESCRIPTION
"The trap enable for ENFAS link coming down trap. Default is 
disable."
::= { d3iTeEntry 9 }

d3iTeSystemReset OBJECT-TYPE
SYNTAX INTEGER{
  enableTrap(1),
  disableAll(2),
  enableLog(3),
  enableAll(4)
}
ACCESS read-write
STATUS mandatory
DESCRIPTION
"The trap enable disable for the DS3 system reset"
::= { d3iTeEntry 10 }

END
