TERAWAVE-teraAtom-MIB DEFINITIONS ::= BEGIN
        -- Created by sml2mib compiler 
        IMPORTS

	Counter64, Counter32 FROM SNMPv2-SMI
 enterprises,  OBJECT-TYPE,  Counter,  Gauge,  TimeTicks
        FROM RFC1155-SMI;

terawave OBJECT IDENTIFIER ::=  { enterprises 4513 }

teraATMGroup OBJECT IDENTIFIER ::=  { terawave 13 }

teraATMSubGroup1 OBJECT IDENTIFIER ::=  { teraATMGroup 1 }

     -- teraAtmStatsSumTable

teraAtmStatsSumTable OBJECT-TYPE
     SYNTAX SEQUENCE OF TeraAtmStatsSumTableEntryType
     ACCESS not-accessible
     STATUS mandatory
     DESCRIPTION
          " table teraAtmStatsSumTable"
     ::= { teraATMSubGroup1 1 }

teraAtmStatsSumTableEntry OBJECT-TYPE
          SYNTAX TeraAtmStatsSumTableEntryType
          ACCESS not-accessible
          STATUS mandatory
          DESCRIPTION
               " table entry teraAtmStatsSumTableEntry "
          INDEX {                   teraAtmIfIndex,                  teraAtmVpi,                  teraAtmVci }
     ::= { teraAtmStatsSumTable 1 }

TeraAtmStatsSumTableEntryType ::= SEQUENCE {
          teraAtmIfIndex   
             INTEGER,
          teraAtmVpi   
             INTEGER,
          teraAtmVci   
             INTEGER,
          teraAtmStatsSumReceivedCells   
             Counter32,
          teraAtmStatsSumReceivedDiscardCells   
             Counter32,
          teraAtmStatsSumReceivedTaggedCells   
             Counter32,
          teraAtmStatsSumTransmittedCells   
             Counter32
}

teraAtmIfIndex OBJECT-TYPE
          SYNTAX INTEGER
          ACCESS read-only
          STATUS mandatory
          DESCRIPTION
               ""
          ::= { teraAtmStatsSumTableEntry 1 }

teraAtmVpi OBJECT-TYPE
          SYNTAX INTEGER
          ACCESS read-only
          STATUS mandatory
          DESCRIPTION
               ""
          ::= { teraAtmStatsSumTableEntry 2 }

teraAtmVci OBJECT-TYPE
          SYNTAX INTEGER
          ACCESS read-only
          STATUS mandatory
          DESCRIPTION
               ""
          ::= { teraAtmStatsSumTableEntry 3 }

teraAtmStatsSumReceivedCells OBJECT-TYPE
          SYNTAX Counter32
          ACCESS read-only
          STATUS mandatory
          DESCRIPTION
               ""
          ::= { teraAtmStatsSumTableEntry 4 }

teraAtmStatsSumReceivedDiscardCells OBJECT-TYPE
          SYNTAX Counter32
          ACCESS read-only
          STATUS mandatory
          DESCRIPTION
               ""
          ::= { teraAtmStatsSumTableEntry 5 }

teraAtmStatsSumReceivedTaggedCells OBJECT-TYPE
          SYNTAX Counter32
          ACCESS read-only
          STATUS mandatory
          DESCRIPTION
               ""
          ::= { teraAtmStatsSumTableEntry 6 }

teraAtmStatsSumTransmittedCells OBJECT-TYPE
          SYNTAX Counter32
          ACCESS read-only
          STATUS mandatory
          DESCRIPTION
               ""
          ::= { teraAtmStatsSumTableEntry 7 }

     -- teraAtmStatsTable

teraAtmStatsTable OBJECT-TYPE
     SYNTAX SEQUENCE OF TeraAtmStatsTableEntryType
     ACCESS not-accessible
     STATUS mandatory
     DESCRIPTION
          " table teraAtmStatsTable"
     ::= { teraATMSubGroup1 2 }

teraAtmStatsTableEntry OBJECT-TYPE
          SYNTAX TeraAtmStatsTableEntryType
          ACCESS not-accessible
          STATUS mandatory
          DESCRIPTION
               " table entry teraAtmStatsTableEntry "
          INDEX {                   teraAtmIfIndex,                  teraAtmVpi,                  teraAtmVci }
     ::= { teraAtmStatsTable 1 }

TeraAtmStatsTableEntryType ::= SEQUENCE {
          teraAtmStatsReceivedUserClp0Cells   
             Counter32,
          teraAtmStatsReceivedUserClp1Cells   
             Counter32,
          teraAtmStatsReceivedOamClp0Cells   
             Counter32,
          teraAtmStatsReceivedOamClp1Cells   
             Counter32,
          teraAtmStatsReceivedDiscardClp0Cells   
             Counter32,
          teraAtmStatsReceivedDiscardClp1Cells   
             Counter32,
          teraAtmStatsReceivedTaggedCells   
             Counter32,
          teraAtmStatsTransmittedUserClp0Cells   
             Counter32,
          teraAtmStatsTransmittedUserClp1Cells   
             Counter32,
          teraAtmStatsTransmittedOamClp0Cells   
             Counter32,
          teraAtmStatsTransmittedOamClp1Cells   
             Counter32
}

teraAtmStatsReceivedUserClp0Cells OBJECT-TYPE
          SYNTAX Counter32
          ACCESS read-only
          STATUS mandatory
          DESCRIPTION
               ""
          ::= { teraAtmStatsTableEntry 1 }

teraAtmStatsReceivedUserClp1Cells OBJECT-TYPE
          SYNTAX Counter32
          ACCESS read-only
          STATUS mandatory
          DESCRIPTION
               ""
          ::= { teraAtmStatsTableEntry 2 }

teraAtmStatsReceivedOamClp0Cells OBJECT-TYPE
          SYNTAX Counter32
          ACCESS read-only
          STATUS mandatory
          DESCRIPTION
               ""
          ::= { teraAtmStatsTableEntry 3 }

teraAtmStatsReceivedOamClp1Cells OBJECT-TYPE
          SYNTAX Counter32
          ACCESS read-only
          STATUS mandatory
          DESCRIPTION
               ""
          ::= { teraAtmStatsTableEntry 4 }

teraAtmStatsReceivedDiscardClp0Cells OBJECT-TYPE
          SYNTAX Counter32
          ACCESS read-only
          STATUS mandatory
          DESCRIPTION
               ""
          ::= { teraAtmStatsTableEntry 5 }

teraAtmStatsReceivedDiscardClp1Cells OBJECT-TYPE
          SYNTAX Counter32
          ACCESS read-only
          STATUS mandatory
          DESCRIPTION
               ""
          ::= { teraAtmStatsTableEntry 6 }

teraAtmStatsReceivedTaggedCells OBJECT-TYPE
          SYNTAX Counter32
          ACCESS read-only
          STATUS mandatory
          DESCRIPTION
               ""
          ::= { teraAtmStatsTableEntry 7 }

teraAtmStatsTransmittedUserClp0Cells OBJECT-TYPE
          SYNTAX Counter32
          ACCESS read-only
          STATUS mandatory
          DESCRIPTION
               ""
          ::= { teraAtmStatsTableEntry 8 }

teraAtmStatsTransmittedUserClp1Cells OBJECT-TYPE
          SYNTAX Counter32
          ACCESS read-only
          STATUS mandatory
          DESCRIPTION
               ""
          ::= { teraAtmStatsTableEntry 9 }

teraAtmStatsTransmittedOamClp0Cells OBJECT-TYPE
          SYNTAX Counter32
          ACCESS read-only
          STATUS mandatory
          DESCRIPTION
               ""
          ::= { teraAtmStatsTableEntry 10 }

teraAtmStatsTransmittedOamClp1Cells OBJECT-TYPE
          SYNTAX Counter32
          ACCESS read-only
          STATUS mandatory
          DESCRIPTION
               ""
          ::= { teraAtmStatsTableEntry 11 }

teraATMSubGroup2 OBJECT IDENTIFIER ::=  { teraATMGroup 2 }

     -- teraAtmHistoryControlTable

teraAtmHistoryControlTable OBJECT-TYPE
     SYNTAX SEQUENCE OF TeraAtmHistoryControlTableEntryType
     ACCESS not-accessible
     STATUS mandatory
     DESCRIPTION
          " table teraAtmHistoryControlTable"
     ::= { teraATMSubGroup2 1 }

teraAtmHistoryControlTableEntry OBJECT-TYPE
          SYNTAX TeraAtmHistoryControlTableEntryType
          ACCESS not-accessible
          STATUS mandatory
          DESCRIPTION
               " table entry teraAtmHistoryControlTableEntry "
          INDEX {                   teraAtmIfIndex,                  teraAtmVpi,                  teraAtmVci,                  teraAtmHistoryControlIndex }
     ::= { teraAtmHistoryControlTable 1 }

TeraAtmHistoryControlTableEntryType ::= SEQUENCE {
          teraAtmHistoryControlIndex   
             INTEGER (1..65535),
          teraAtmHistoryControlBucketsRequested   
             INTEGER (1..65535),
          teraAtmHistoryControlBucketsGranted   
             INTEGER (1..65535),
          teraAtmHistoryControlInterval   
             INTEGER (1..3600),
          teraAtmHistoryControlStatus   
             INTEGER
}

teraAtmHistoryControlIndex OBJECT-TYPE
          SYNTAX INTEGER (1..65535)
          ACCESS read-only
          STATUS mandatory
          DESCRIPTION
               ""
          ::= { teraAtmHistoryControlTableEntry 1 }

teraAtmHistoryControlBucketsRequested OBJECT-TYPE
          SYNTAX INTEGER (1..65535)
          ACCESS read-write
          STATUS mandatory
          DESCRIPTION
               ""
          ::= { teraAtmHistoryControlTableEntry 2 }

teraAtmHistoryControlBucketsGranted OBJECT-TYPE
          SYNTAX INTEGER (1..65535)
          ACCESS read-only
          STATUS mandatory
          DESCRIPTION
               ""
          ::= { teraAtmHistoryControlTableEntry 3 }

teraAtmHistoryControlInterval OBJECT-TYPE
          SYNTAX INTEGER (1..3600)
          ACCESS read-write
          STATUS mandatory
          DESCRIPTION
               ""
          ::= { teraAtmHistoryControlTableEntry 4 }

teraAtmHistoryControlStatus OBJECT-TYPE
          SYNTAX INTEGER
                  {
                  valid(1),
                  createRequest(2),
                  underCreation(3),
                  invalid(4)
                  }
          ACCESS read-write
          STATUS mandatory
          DESCRIPTION
               ""
          ::= { teraAtmHistoryControlTableEntry 5 }

     -- teraAtmStatsHistoryTable

teraAtmStatsHistoryTable OBJECT-TYPE
     SYNTAX SEQUENCE OF TeraAtmStatsHistoryTableEntryType
     ACCESS not-accessible
     STATUS mandatory
     DESCRIPTION
          " table teraAtmStatsHistoryTable"
     ::= { teraATMSubGroup2 2 }

teraAtmStatsHistoryTableEntry OBJECT-TYPE
          SYNTAX TeraAtmStatsHistoryTableEntryType
          ACCESS not-accessible
          STATUS mandatory
          DESCRIPTION
               " table entry teraAtmStatsHistoryTableEntry "
          INDEX {                   teraAtmIfIndex,                  teraAtmVpi,                  teraAtmVci,                  teraAtmHistoryControlIndex,                  teraAtmStatsHistorySampleIndex }
     ::= { teraAtmStatsHistoryTable 1 }

TeraAtmStatsHistoryTableEntryType ::= SEQUENCE {
          teraAtmStatsHistorySampleIndex   
             INTEGER (1..2147483647),
          teraAtmStatsHistoryIntervalStart   
             TimeTicks,
          teraAtmStatsHistoryReceivedUserClp0Cells   
             Counter32,
          teraAtmStatsHistoryReceivedUserClp1Cells   
             Counter32,
          teraAtmStatsHistoryReceivedOamClp0Cells   
             Counter32,
          teraAtmStatsHistoryReceivedOamClp1Cells   
             Counter32,
          teraAtmStatsHistoryReceivedDiscardClp0Cells   
             Counter32,
          teraAtmStatsHistoryReceivedDiscardClp1Cells   
             Counter32,
          teraAtmStatsHistoryReceivedTaggedCells   
             Counter32,
          teraAtmStatsHistoryTransmittedUserClp0Cells   
             Counter32,
          teraAtmStatsHistoryTransmittedUserClp1Cells   
             Counter32,
          teraAtmStatsHistoryTransmittedOamClp0Cells   
             Counter32,
          teraAtmStatsHistoryTransmittedOamClp1Cells   
             Counter32
}

teraAtmStatsHistorySampleIndex OBJECT-TYPE
          SYNTAX INTEGER (1..2147483647)
          ACCESS read-only
          STATUS mandatory
          DESCRIPTION
               ""
          ::= { teraAtmStatsHistoryTableEntry 1 }

teraAtmStatsHistoryIntervalStart OBJECT-TYPE
          SYNTAX TimeTicks
          ACCESS read-only
          STATUS mandatory
          DESCRIPTION
               ""
          ::= { teraAtmStatsHistoryTableEntry 2 }

teraAtmStatsHistoryReceivedUserClp0Cells OBJECT-TYPE
          SYNTAX Counter32
          ACCESS read-only
          STATUS mandatory
          DESCRIPTION
               ""
          ::= { teraAtmStatsHistoryTableEntry 3 }

teraAtmStatsHistoryReceivedUserClp1Cells OBJECT-TYPE
          SYNTAX Counter32
          ACCESS read-only
          STATUS mandatory
          DESCRIPTION
               ""
          ::= { teraAtmStatsHistoryTableEntry 4 }

teraAtmStatsHistoryReceivedOamClp0Cells OBJECT-TYPE
          SYNTAX Counter32
          ACCESS read-only
          STATUS mandatory
          DESCRIPTION
               ""
          ::= { teraAtmStatsHistoryTableEntry 5 }

teraAtmStatsHistoryReceivedOamClp1Cells OBJECT-TYPE
          SYNTAX Counter32
          ACCESS read-only
          STATUS mandatory
          DESCRIPTION
               ""
          ::= { teraAtmStatsHistoryTableEntry 6 }

teraAtmStatsHistoryReceivedDiscardClp0Cells OBJECT-TYPE
          SYNTAX Counter32
          ACCESS read-only
          STATUS mandatory
          DESCRIPTION
               ""
          ::= { teraAtmStatsHistoryTableEntry 7 }

teraAtmStatsHistoryReceivedDiscardClp1Cells OBJECT-TYPE
          SYNTAX Counter32
          ACCESS read-only
          STATUS mandatory
          DESCRIPTION
               ""
          ::= { teraAtmStatsHistoryTableEntry 8 }

teraAtmStatsHistoryReceivedTaggedCells OBJECT-TYPE
          SYNTAX Counter32
          ACCESS read-only
          STATUS mandatory
          DESCRIPTION
               ""
          ::= { teraAtmStatsHistoryTableEntry 9 }

teraAtmStatsHistoryTransmittedUserClp0Cells OBJECT-TYPE
          SYNTAX Counter32
          ACCESS read-only
          STATUS mandatory
          DESCRIPTION
               ""
          ::= { teraAtmStatsHistoryTableEntry 10 }

teraAtmStatsHistoryTransmittedUserClp1Cells OBJECT-TYPE
          SYNTAX Counter32
          ACCESS read-only
          STATUS mandatory
          DESCRIPTION
               ""
          ::= { teraAtmStatsHistoryTableEntry 11 }

teraAtmStatsHistoryTransmittedOamClp0Cells OBJECT-TYPE
          SYNTAX Counter32
          ACCESS read-only
          STATUS mandatory
          DESCRIPTION
               ""
          ::= { teraAtmStatsHistoryTableEntry 12 }

teraAtmStatsHistoryTransmittedOamClp1Cells OBJECT-TYPE
          SYNTAX Counter32
          ACCESS read-only
          STATUS mandatory
          DESCRIPTION
               ""
          ::= { teraAtmStatsHistoryTableEntry 13 }

teraATMSubGroup3 OBJECT IDENTIFIER ::=  { teraATMGroup 3 }

     -- teraAtmILMIPollCfgTable (special)

teraAtmILMIPollCfgTable OBJECT IDENTIFIER ::=  { teraATMSubGroup3 1 }

teraDefaultRegainTimeout OBJECT-TYPE
          SYNTAX INTEGER (1..2147483647)
          ACCESS read-write
          STATUS mandatory
          DESCRIPTION
               ""
          ::= { teraAtmILMIPollCfgTable 1 }

teraDefaultTestConnectTimeout OBJECT-TYPE
          SYNTAX INTEGER (1..2147483647)
          ACCESS read-write
          STATUS mandatory
          DESCRIPTION
               ""
          ::= { teraAtmILMIPollCfgTable 2 }

teraDefaultAllowedNumOfFailed OBJECT-TYPE
          SYNTAX INTEGER (1..65535)
          ACCESS read-write
          STATUS mandatory
          DESCRIPTION
               ""
          ::= { teraAtmILMIPollCfgTable 3 }

     -- teraATMPhyStatTable

teraATMPhyStatTable OBJECT-TYPE
     SYNTAX SEQUENCE OF TeraATMPhyStatTableEntryType
     ACCESS not-accessible
     STATUS mandatory
     DESCRIPTION
          " table teraATMPhyStatTable"
     ::= { teraATMGroup 4 }

teraATMPhyStatTableEntry OBJECT-TYPE
          SYNTAX TeraATMPhyStatTableEntryType
          ACCESS not-accessible
          STATUS mandatory
          DESCRIPTION
               " table entry teraATMPhyStatTableEntry "
          INDEX {                   teraAtmIfIndex }
     ::= { teraATMPhyStatTable 1 }

TeraATMPhyStatTableEntryType ::= SEQUENCE {
          teraATM-Seconds   
             Counter32,
          teraATM-CorrectHCSError   
             Counter32,
          teraATM-UncorrectHCSError   
             Counter32,
          teraATM-ReceiveCell   
             Counter64,
          teraATM-IDLECell   
             Counter64,
          teraATM-TransmitCell   
             Counter64,
          teraATM-AdminStatus   
             INTEGER
}

teraATM-Seconds OBJECT-TYPE
          SYNTAX Counter32
          ACCESS read-only
          STATUS mandatory
          DESCRIPTION
               ""
          ::= { teraATMPhyStatTableEntry 1 }

teraATM-CorrectHCSError OBJECT-TYPE
          SYNTAX Counter32
          ACCESS read-only
          STATUS mandatory
          DESCRIPTION
               ""
          ::= { teraATMPhyStatTableEntry 2 }

teraATM-UncorrectHCSError OBJECT-TYPE
          SYNTAX Counter32
          ACCESS read-only
          STATUS mandatory
          DESCRIPTION
               ""
          ::= { teraATMPhyStatTableEntry 3 }

teraATM-ReceiveCell OBJECT-TYPE
          SYNTAX Counter64
          ACCESS read-only
          STATUS mandatory
          DESCRIPTION
               ""
          ::= { teraATMPhyStatTableEntry 4 }

teraATM-IDLECell OBJECT-TYPE
          SYNTAX Counter64
          ACCESS read-only
          STATUS mandatory
          DESCRIPTION
               ""
          ::= { teraATMPhyStatTableEntry 5 }

teraATM-TransmitCell OBJECT-TYPE
          SYNTAX Counter64
          ACCESS read-only
          STATUS mandatory
          DESCRIPTION
               ""
          ::= { teraATMPhyStatTableEntry 6 }

teraATM-AdminStatus OBJECT-TYPE
          SYNTAX INTEGER
                  {
                  clear(1),
                  run(2),
                  stop(3)
                  }
          ACCESS read-write
          STATUS mandatory
          DESCRIPTION
               ""
          ::= { teraATMPhyStatTableEntry 7 }

     -- teraAtmPortStatsTable

teraAtmPortStatsTable OBJECT-TYPE
     SYNTAX SEQUENCE OF TeraAtmPortStatsTableEntryType
     ACCESS not-accessible
     STATUS mandatory
     DESCRIPTION
          " table teraAtmPortStatsTable"
     ::= { teraATMGroup 5 }

teraAtmPortStatsTableEntry OBJECT-TYPE
          SYNTAX TeraAtmPortStatsTableEntryType
          ACCESS not-accessible
          STATUS mandatory
          DESCRIPTION
               " table entry teraAtmPortStatsTableEntry "
          INDEX {                   ifIndex }
     ::= { teraAtmPortStatsTable 1 }

TeraAtmPortStatsTableEntryType ::= SEQUENCE {
          teraAtmPortStatsIngressUnassignedCells   
             Counter32,
          teraAtmPortStatsEgressUnassignedCells   
             Counter32,
          teraAtmPortStatsTransmittedClp0Cells   
             Counter32,
          teraAtmPortStatsTransmittedClp1Cells   
             Counter32,
          teraAtmPortStatsReceivedClp0Cells   
             Counter32,
          teraAtmPortStatsReceivedClp1Cells   
             Counter32,
          teraAtmPortStatsReceivedOamCells   
             Counter32,
          teraAtmPortStatsReceivedRmCells   
             Counter32,
          teraAtmPortStatsReceivedErroredOamCells   
             Counter32,
          teraAtmPortStatsReceivedErroredRmCells   
             Counter32,
          teraAtmPortStatsReceivedNonZerroGfcCells   
             Counter32
}

teraAtmPortStatsIngressUnassignedCells OBJECT-TYPE
          SYNTAX Counter32
          ACCESS read-only
          STATUS mandatory
          DESCRIPTION
               ""
          ::= { teraAtmPortStatsTableEntry 1 }

teraAtmPortStatsEgressUnassignedCells OBJECT-TYPE
          SYNTAX Counter32
          ACCESS read-only
          STATUS mandatory
          DESCRIPTION
               ""
          ::= { teraAtmPortStatsTableEntry 2 }

teraAtmPortStatsTransmittedClp0Cells OBJECT-TYPE
          SYNTAX Counter32
          ACCESS read-only
          STATUS mandatory
          DESCRIPTION
               ""
          ::= { teraAtmPortStatsTableEntry 3 }

teraAtmPortStatsTransmittedClp1Cells OBJECT-TYPE
          SYNTAX Counter32
          ACCESS read-only
          STATUS mandatory
          DESCRIPTION
               ""
          ::= { teraAtmPortStatsTableEntry 4 }

teraAtmPortStatsReceivedClp0Cells OBJECT-TYPE
          SYNTAX Counter32
          ACCESS read-only
          STATUS mandatory
          DESCRIPTION
               ""
          ::= { teraAtmPortStatsTableEntry 5 }

teraAtmPortStatsReceivedClp1Cells OBJECT-TYPE
          SYNTAX Counter32
          ACCESS read-only
          STATUS mandatory
          DESCRIPTION
               ""
          ::= { teraAtmPortStatsTableEntry 6 }

teraAtmPortStatsReceivedOamCells OBJECT-TYPE
          SYNTAX Counter32
          ACCESS read-only
          STATUS mandatory
          DESCRIPTION
               ""
          ::= { teraAtmPortStatsTableEntry 7 }

teraAtmPortStatsReceivedRmCells OBJECT-TYPE
          SYNTAX Counter32
          ACCESS read-only
          STATUS mandatory
          DESCRIPTION
               ""
          ::= { teraAtmPortStatsTableEntry 8 }

teraAtmPortStatsReceivedErroredOamCells OBJECT-TYPE
          SYNTAX Counter32
          ACCESS read-only
          STATUS mandatory
          DESCRIPTION
               ""
          ::= { teraAtmPortStatsTableEntry 9 }

teraAtmPortStatsReceivedErroredRmCells OBJECT-TYPE
          SYNTAX Counter32
          ACCESS read-only
          STATUS mandatory
          DESCRIPTION
               ""
          ::= { teraAtmPortStatsTableEntry 10 }

teraAtmPortStatsReceivedNonZerroGfcCells OBJECT-TYPE
          SYNTAX Counter32
          ACCESS read-only
          STATUS mandatory
          DESCRIPTION
               ""
          ::= { teraAtmPortStatsTableEntry 11 }

     -- teraAtmPortStatsHistoryTable

teraAtmPortStatsHistoryTable OBJECT-TYPE
     SYNTAX SEQUENCE OF TeraAtmPortStatsHistoryTableEntryType
     ACCESS not-accessible
     STATUS mandatory
     DESCRIPTION
          " table teraAtmPortStatsHistoryTable"
     ::= { teraATMGroup 6 }

teraAtmPortStatsHistoryTableEntry OBJECT-TYPE
          SYNTAX TeraAtmPortStatsHistoryTableEntryType
          ACCESS not-accessible
          STATUS mandatory
          DESCRIPTION
               " table entry teraAtmPortStatsHistoryTableEntry "
          INDEX {                   teraAtmIfIndex,                  teraAtmHistoryControlIndex,                  teraAtmStatsHistorySampleIndex }
     ::= { teraAtmPortStatsHistoryTable 1 }

TeraAtmPortStatsHistoryTableEntryType ::= SEQUENCE {
          teraAtmPortStatsHistoryIngressUnassignedCells   
             Counter32,
          teraAtmPortStatsHistoryEgressUnassignedCells   
             Counter32,
          teraAtmPortStatsHistoryTransmittedClp0Cells   
             Counter32,
          teraAtmPortStatsHistoryTransmittedClp1Cells   
             Counter32,
          teraAtmPortStatsHistoryReceivedClp0Cells   
             Counter32,
          teraAtmPortStatsHistoryReceivedClp1Cells   
             Counter32,
          teraAtmPortStatsHistoryReceivedOamCells   
             Counter32,
          teraAtmPortStatsHistoryReceivedRmCells   
             Counter32,
          teraAtmPortStatsHistoryReceivedErroredOamCells   
             Counter32,
          teraAtmPortStatsHistoryReceivedErroredRmCells   
             Counter32,
          teraAtmPortStatsHistoryReceivedNonZerroGfcCells   
             Counter32
}

teraAtmPortStatsHistoryIngressUnassignedCells OBJECT-TYPE
          SYNTAX Counter32
          ACCESS read-only
          STATUS mandatory
          DESCRIPTION
               ""
          ::= { teraAtmPortStatsHistoryTableEntry 1 }

teraAtmPortStatsHistoryEgressUnassignedCells OBJECT-TYPE
          SYNTAX Counter32
          ACCESS read-only
          STATUS mandatory
          DESCRIPTION
               ""
          ::= { teraAtmPortStatsHistoryTableEntry 2 }

teraAtmPortStatsHistoryTransmittedClp0Cells OBJECT-TYPE
          SYNTAX Counter32
          ACCESS read-only
          STATUS mandatory
          DESCRIPTION
               ""
          ::= { teraAtmPortStatsHistoryTableEntry 3 }

teraAtmPortStatsHistoryTransmittedClp1Cells OBJECT-TYPE
          SYNTAX Counter32
          ACCESS read-only
          STATUS mandatory
          DESCRIPTION
               ""
          ::= { teraAtmPortStatsHistoryTableEntry 4 }

teraAtmPortStatsHistoryReceivedClp0Cells OBJECT-TYPE
          SYNTAX Counter32
          ACCESS read-only
          STATUS mandatory
          DESCRIPTION
               ""
          ::= { teraAtmPortStatsHistoryTableEntry 5 }

teraAtmPortStatsHistoryReceivedClp1Cells OBJECT-TYPE
          SYNTAX Counter32
          ACCESS read-only
          STATUS mandatory
          DESCRIPTION
               ""
          ::= { teraAtmPortStatsHistoryTableEntry 6 }

teraAtmPortStatsHistoryReceivedOamCells OBJECT-TYPE
          SYNTAX Counter32
          ACCESS read-only
          STATUS mandatory
          DESCRIPTION
               ""
          ::= { teraAtmPortStatsHistoryTableEntry 7 }

teraAtmPortStatsHistoryReceivedRmCells OBJECT-TYPE
          SYNTAX Counter32
          ACCESS read-only
          STATUS mandatory
          DESCRIPTION
               ""
          ::= { teraAtmPortStatsHistoryTableEntry 8 }

teraAtmPortStatsHistoryReceivedErroredOamCells OBJECT-TYPE
          SYNTAX Counter32
          ACCESS read-only
          STATUS mandatory
          DESCRIPTION
               ""
          ::= { teraAtmPortStatsHistoryTableEntry 9 }

teraAtmPortStatsHistoryReceivedErroredRmCells OBJECT-TYPE
          SYNTAX Counter32
          ACCESS read-only
          STATUS mandatory
          DESCRIPTION
               ""
          ::= { teraAtmPortStatsHistoryTableEntry 10 }

teraAtmPortStatsHistoryReceivedNonZerroGfcCells OBJECT-TYPE
          SYNTAX Counter32
          ACCESS read-only
          STATUS mandatory
          DESCRIPTION
               ""
          ::= { teraAtmPortStatsHistoryTableEntry 11 }

teraAtmCc OBJECT IDENTIFIER ::=  { teraATMGroup 7 }

     -- teraAtmCcControlTable

teraAtmCcControlTable OBJECT-TYPE
     SYNTAX SEQUENCE OF TeraAtmCcControlTableEntryType
     ACCESS not-accessible
     STATUS mandatory
     DESCRIPTION
          " table teraAtmCcControlTable"
     ::= { teraAtmCc 1 }

teraAtmCcControlTableEntry OBJECT-TYPE
          SYNTAX TeraAtmCcControlTableEntryType
          ACCESS not-accessible
          STATUS mandatory
          DESCRIPTION
               " table entry teraAtmCcControlTableEntry "
          INDEX {                   teraAtmIfIndex,                  teraAtmVpi,                  teraAtmVci }
     ::= { teraAtmCcControlTable 1 }

TeraAtmCcControlTableEntryType ::= SEQUENCE {
          teraAtmCcSourceControl   
             INTEGER,
          teraAtmCcSinkControl   
             INTEGER,
          teraAtmCcType   
             INTEGER,
          teraAtmCcTargetDir   
             INTEGER,
          teraAtmCcSinkDir   
             INTEGER,
          teraAtmCcSourceResult   
             INTEGER,
          teraAtmCcSinkResult   
             INTEGER,
          teraAtmCcRowStatus   
             INTEGER
}

teraAtmCcSourceControl OBJECT-TYPE
          SYNTAX INTEGER
                  {
                  activate(1),
                  deactivate(2)
                  }
          ACCESS read-write
          STATUS mandatory
          DESCRIPTION
               ""
          ::= { teraAtmCcControlTableEntry 1 }

teraAtmCcSinkControl OBJECT-TYPE
          SYNTAX INTEGER
                  {
                  enable(3),
                  disable(4)
                  }
          ACCESS read-write
          STATUS mandatory
          DESCRIPTION
               ""
          ::= { teraAtmCcControlTableEntry 2 }

teraAtmCcType OBJECT-TYPE
          SYNTAX INTEGER
                  {
                  seg-to-Seg(4),
                  end-to-End(5)
                  }
          ACCESS read-write
          STATUS mandatory
          DESCRIPTION
               ""
          ::= { teraAtmCcControlTableEntry 3 }

teraAtmCcTargetDir OBJECT-TYPE
          SYNTAX INTEGER
                  {
                  upstream(1),
                  downstream(2)
                  }
          ACCESS read-write
          STATUS mandatory
          DESCRIPTION
               ""
          ::= { teraAtmCcControlTableEntry 4 }

teraAtmCcSinkDir OBJECT-TYPE
          SYNTAX INTEGER
                  {
                  none(0),
                  upstream(1),
                  downstream(2)
                  }
          ACCESS read-only
          STATUS mandatory
          DESCRIPTION
               ""
          ::= { teraAtmCcControlTableEntry 5 }

teraAtmCcSourceResult OBJECT-TYPE
          SYNTAX INTEGER
                  {
                  none(1),
                  activationSuccess(2),
                  activationInProgress(3),
                  activationFailed(4)
                  }
          ACCESS read-only
          STATUS mandatory
          DESCRIPTION
               ""
          ::= { teraAtmCcControlTableEntry 6 }

teraAtmCcSinkResult OBJECT-TYPE
          SYNTAX INTEGER
                  {
                  enabled(1),
                  disabled(2),
                  cc-OK(3),
                  cc-Failed(4)
                  }
          ACCESS read-only
          STATUS mandatory
          DESCRIPTION
               ""
          ::= { teraAtmCcControlTableEntry 7 }

teraAtmCcRowStatus OBJECT-TYPE
          SYNTAX INTEGER
                  {
                  ok(1),
                  delete(2)
                  }
          ACCESS read-write
          STATUS mandatory
          DESCRIPTION
               ""
          ::= { teraAtmCcControlTableEntry 8 }

     -- teraAtmPmControlTable

teraAtmPmControlTable OBJECT-TYPE
     SYNTAX SEQUENCE OF TeraAtmPmControlTableEntryType
     ACCESS not-accessible
     STATUS mandatory
     DESCRIPTION
          " table teraAtmPmControlTable"
     ::= { teraATMGroup 8 }

teraAtmPmControlTableEntry OBJECT-TYPE
          SYNTAX TeraAtmPmControlTableEntryType
          ACCESS not-accessible
          STATUS mandatory
          DESCRIPTION
               " table entry teraAtmPmControlTableEntry "
          INDEX {                   teraAtmIfIndex,                  teraAtmVpi,                  teraAtmVci }
     ::= { teraAtmPmControlTable 1 }

TeraAtmPmControlTableEntryType ::= SEQUENCE {
          teraAtmPmSourceControl   
             INTEGER,
          teraAtmPmSourceBlockSize   
             INTEGER,
          teraAtmPmSinkControl   
             INTEGER,
          teraAtmPmSourceType   
             INTEGER,
          teraAtmPmTargetDir   
             INTEGER,
          teraAtmPmSinkDir   
             INTEGER,
          teraAtmPmSourceResult   
             INTEGER,
          teraAtmPmSinkResult   
             INTEGER,
          teraAtmPmRowStatus   
             INTEGER
}

teraAtmPmSourceControl OBJECT-TYPE
          SYNTAX INTEGER
                  {
                  activate(1),
                  deactivate(2)
                  }
          ACCESS read-write
          STATUS mandatory
          DESCRIPTION
               ""
          ::= { teraAtmPmControlTableEntry 1 }

teraAtmPmSourceBlockSize OBJECT-TYPE
          SYNTAX INTEGER
                  {
                  number-1024(1),
                  number-512(2),
                  number-256(4),
                  number-128(8)
                  }
          ACCESS read-write
          STATUS mandatory
          DESCRIPTION
               ""
          ::= { teraAtmPmControlTableEntry 2 }

teraAtmPmSinkControl OBJECT-TYPE
          SYNTAX INTEGER
                  {
                  enable(3),
                  disable(4)
                  }
          ACCESS read-write
          STATUS mandatory
          DESCRIPTION
               ""
          ::= { teraAtmPmControlTableEntry 3 }

teraAtmPmSourceType OBJECT-TYPE
          SYNTAX INTEGER
                  {
                  seg-to-Seg(4),
                  end-to-End(5)
                  }
          ACCESS read-write
          STATUS mandatory
          DESCRIPTION
               ""
          ::= { teraAtmPmControlTableEntry 4 }

teraAtmPmTargetDir OBJECT-TYPE
          SYNTAX INTEGER
                  {
                  upstream(1),
                  downstream(2)
                  }
          ACCESS read-write
          STATUS mandatory
          DESCRIPTION
               ""
          ::= { teraAtmPmControlTableEntry 5 }

teraAtmPmSinkDir OBJECT-TYPE
          SYNTAX INTEGER
                  {
                  none(0),
                  upstream(1),
                  downstream(2)
                  }
          ACCESS read-only
          STATUS mandatory
          DESCRIPTION
               ""
          ::= { teraAtmPmControlTableEntry 6 }

teraAtmPmSourceResult OBJECT-TYPE
          SYNTAX INTEGER
                  {
                  none(1),
                  activationSuccess(2),
                  activationInProgress(3),
                  activationFailed(4)
                  }
          ACCESS read-only
          STATUS mandatory
          DESCRIPTION
               ""
          ::= { teraAtmPmControlTableEntry 7 }

teraAtmPmSinkResult OBJECT-TYPE
          SYNTAX INTEGER
                  {
                  enabled(1),
                  disabled(2)
                  }
          ACCESS read-only
          STATUS mandatory
          DESCRIPTION
               ""
          ::= { teraAtmPmControlTableEntry 8 }

teraAtmPmRowStatus OBJECT-TYPE
          SYNTAX INTEGER
                  {
                  ok(1),
                  delete(2)
                  }
          ACCESS read-write
          STATUS mandatory
          DESCRIPTION
               ""
          ::= { teraAtmPmControlTableEntry 9 }

     -- teraOamPmStatsTable

teraOamPmStatsTable OBJECT-TYPE
     SYNTAX SEQUENCE OF TeraOamPmStatsTableEntryType
     ACCESS not-accessible
     STATUS mandatory
     DESCRIPTION
          " table teraOamPmStatsTable"
     ::= { teraATMGroup 9 }

teraOamPmStatsTableEntry OBJECT-TYPE
          SYNTAX TeraOamPmStatsTableEntryType
          ACCESS not-accessible
          STATUS mandatory
          DESCRIPTION
               " table entry teraOamPmStatsTableEntry "
          INDEX {                   teraAtmIfIndex,                  teraAtmVpi,                  teraAtmVci }
     ::= { teraOamPmStatsTable 1 }

TeraOamPmStatsTableEntryType ::= SEQUENCE {
          teraOamPmStatsTotalTUC0   
             Counter32,
          teraOamPmStatsTotalTUC01   
             Counter32,
          teraOamPmStatsTotalTRCC0   
             Counter32,
          teraOamPmStatsTotalTRCC01   
             Counter32,
          teraOamPmStatsStat   
             INTEGER,
          teraOamPmStatsTotalLostCLP0   
             Counter32,
          teraOamPmStatsTotalLostCLP01   
             Counter32,
          teraOamPmStatsTotalMisinsertedCLP0   
             Counter32,
          teraOamPmStatsTotalMisinsertedCLP01   
             Counter32
}

teraOamPmStatsTotalTUC0 OBJECT-TYPE
          SYNTAX Counter32
          ACCESS read-only
          STATUS mandatory
          DESCRIPTION
               ""
          ::= { teraOamPmStatsTableEntry 1 }

teraOamPmStatsTotalTUC01 OBJECT-TYPE
          SYNTAX Counter32
          ACCESS read-only
          STATUS mandatory
          DESCRIPTION
               ""
          ::= { teraOamPmStatsTableEntry 2 }

teraOamPmStatsTotalTRCC0 OBJECT-TYPE
          SYNTAX Counter32
          ACCESS read-only
          STATUS mandatory
          DESCRIPTION
               ""
          ::= { teraOamPmStatsTableEntry 3 }

teraOamPmStatsTotalTRCC01 OBJECT-TYPE
          SYNTAX Counter32
          ACCESS read-only
          STATUS mandatory
          DESCRIPTION
               ""
          ::= { teraOamPmStatsTableEntry 4 }

teraOamPmStatsStat OBJECT-TYPE
          SYNTAX INTEGER
                  {
                  ok(1),
                  clear(2)
                  }
          ACCESS read-write
          STATUS mandatory
          DESCRIPTION
               ""
          ::= { teraOamPmStatsTableEntry 5 }

teraOamPmStatsTotalLostCLP0 OBJECT-TYPE
          SYNTAX Counter32
          ACCESS read-only
          STATUS mandatory
          DESCRIPTION
               ""
          ::= { teraOamPmStatsTableEntry 6 }

teraOamPmStatsTotalLostCLP01 OBJECT-TYPE
          SYNTAX Counter32
          ACCESS read-only
          STATUS mandatory
          DESCRIPTION
               ""
          ::= { teraOamPmStatsTableEntry 7 }

teraOamPmStatsTotalMisinsertedCLP0 OBJECT-TYPE
          SYNTAX Counter32
          ACCESS read-only
          STATUS mandatory
          DESCRIPTION
               ""
          ::= { teraOamPmStatsTableEntry 8 }

teraOamPmStatsTotalMisinsertedCLP01 OBJECT-TYPE
          SYNTAX Counter32
          ACCESS read-only
          STATUS mandatory
          DESCRIPTION
               ""
          ::= { teraOamPmStatsTableEntry 9 }

     -- teraAtmPVCIfControlTable

teraAtmPVCIfControlTable OBJECT-TYPE
     SYNTAX SEQUENCE OF TeraAtmPVCIfControlTableEntryType
     ACCESS not-accessible
     STATUS mandatory
     DESCRIPTION
          " table teraAtmPVCIfControlTable"
     ::= { teraATMGroup 11 }

teraAtmPVCIfControlTableEntry OBJECT-TYPE
          SYNTAX TeraAtmPVCIfControlTableEntryType
          ACCESS not-accessible
          STATUS mandatory
          DESCRIPTION
               " table entry teraAtmPVCIfControlTableEntry "
          INDEX {                   teraAtmIfIndex }
     ::= { teraAtmPVCIfControlTable 1 }

TeraAtmPVCIfControlTableEntryType ::= SEQUENCE {
          teraAtmPVCIfMaxVpiBits   
             INTEGER (0..12),
          teraAtmPVCIfMaxVciBits   
             INTEGER (0..16),
          teraAtmPVCIfMaxVCCs   
             INTEGER,
          teraAtmPVCIfILMIVpi   
             INTEGER,
          teraAtmPVCIfILMIVci   
             INTEGER,
          teraAtmPVCIfPortBw   
             INTEGER
}

teraAtmPVCIfMaxVpiBits OBJECT-TYPE
          SYNTAX INTEGER (0..12)
          ACCESS read-write
          STATUS mandatory
          DESCRIPTION
               ""
          ::= { teraAtmPVCIfControlTableEntry 1 }

teraAtmPVCIfMaxVciBits OBJECT-TYPE
          SYNTAX INTEGER (0..16)
          ACCESS read-write
          STATUS mandatory
          DESCRIPTION
               ""
          ::= { teraAtmPVCIfControlTableEntry 2 }

teraAtmPVCIfMaxVCCs OBJECT-TYPE
          SYNTAX INTEGER
          ACCESS read-write
          STATUS mandatory
          DESCRIPTION
               ""
          ::= { teraAtmPVCIfControlTableEntry 3 }

teraAtmPVCIfILMIVpi OBJECT-TYPE
          SYNTAX INTEGER
          ACCESS read-write
          STATUS mandatory
          DESCRIPTION
               ""
          ::= { teraAtmPVCIfControlTableEntry 4 }

teraAtmPVCIfILMIVci OBJECT-TYPE
          SYNTAX INTEGER
          ACCESS read-write
          STATUS mandatory
          DESCRIPTION
               ""
          ::= { teraAtmPVCIfControlTableEntry 5 }

teraAtmPVCIfPortBw OBJECT-TYPE
          SYNTAX INTEGER
          ACCESS read-write
          STATUS mandatory
          DESCRIPTION
               ""
          ::= { teraAtmPVCIfControlTableEntry 6 }

     -- teraAtmCardStatsTable

teraAtmCardStatsTable OBJECT-TYPE
     SYNTAX SEQUENCE OF TeraAtmCardStatsTableEntryType
     ACCESS not-accessible
     STATUS mandatory
     DESCRIPTION
          " table teraAtmCardStatsTable"
     ::= { teraATMGroup 12 }

teraAtmCardStatsTableEntry OBJECT-TYPE
          SYNTAX TeraAtmCardStatsTableEntryType
          ACCESS not-accessible
          STATUS mandatory
          DESCRIPTION
               " table entry teraAtmCardStatsTableEntry "
          INDEX {                   teraSlotIndex }
     ::= { teraAtmCardStatsTable 1 }

TeraAtmCardStatsTableEntryType ::= SEQUENCE {
          teraSlotIndex   
             Counter32,
          teraAtmCardStatsLSBState   
             INTEGER,
          teraAtmCardStatsLSBCrcCount   
             Counter32,
          teraAtmCardStatsTransitionUpCount   
             Counter32,
          teraAtmCardStatsRxUnassignedCellCount   
             Counter32,
          teraAtmCardStatsLSBCrcLastSlot   
             INTEGER,
          teraAtmCardStatsMrpVersion   
             INTEGER,
          teraAtmCardStatsMrpFeature   
             INTEGER
}

teraSlotIndex OBJECT-TYPE
          SYNTAX Counter32
          ACCESS read-only
          STATUS mandatory
          DESCRIPTION
               ""
          ::= { teraAtmCardStatsTableEntry 1 }

teraAtmCardStatsLSBState OBJECT-TYPE
          SYNTAX INTEGER
                  {
                  idle(1),
                  waitForBus(2),
                  monitoringBus(3)
                  }
          ACCESS read-only
          STATUS mandatory
          DESCRIPTION
               ""
          ::= { teraAtmCardStatsTableEntry 2 }

teraAtmCardStatsLSBCrcCount OBJECT-TYPE
          SYNTAX Counter32
          ACCESS read-only
          STATUS mandatory
          DESCRIPTION
               ""
          ::= { teraAtmCardStatsTableEntry 3 }

teraAtmCardStatsTransitionUpCount OBJECT-TYPE
          SYNTAX Counter32
          ACCESS read-only
          STATUS mandatory
          DESCRIPTION
               ""
          ::= { teraAtmCardStatsTableEntry 4 }

teraAtmCardStatsRxUnassignedCellCount OBJECT-TYPE
          SYNTAX Counter32
          ACCESS read-only
          STATUS mandatory
          DESCRIPTION
               ""
          ::= { teraAtmCardStatsTableEntry 5 }

teraAtmCardStatsLSBCrcLastSlot OBJECT-TYPE
          SYNTAX INTEGER
          ACCESS read-only
          STATUS mandatory
          DESCRIPTION
               ""
          ::= { teraAtmCardStatsTableEntry 6 }

teraAtmCardStatsMrpVersion OBJECT-TYPE
          SYNTAX INTEGER
          ACCESS read-only
          STATUS mandatory
          DESCRIPTION
               ""
          ::= { teraAtmCardStatsTableEntry 7 }

teraAtmCardStatsMrpFeature OBJECT-TYPE
          SYNTAX INTEGER
          ACCESS read-only
          STATUS mandatory
          DESCRIPTION
               ""
          ::= { teraAtmCardStatsTableEntry 8 }

     -- teraAtmVclTable

teraAtmVclTable OBJECT-TYPE
     SYNTAX SEQUENCE OF TeraAtmVclTableEntryType
     ACCESS not-accessible
     STATUS mandatory
     DESCRIPTION
          " table teraAtmVclTable"
     ::= { teraATMGroup 13 }

teraAtmVclTableEntry OBJECT-TYPE
          SYNTAX TeraAtmVclTableEntryType
          ACCESS not-accessible
          STATUS mandatory
          DESCRIPTION
               " table entry teraAtmVclTableEntry "
          INDEX {                   ifIndex,                  atmVclVpi,                  atmVclVci }
     ::= { teraAtmVclTable 1 }

TeraAtmVclTableEntryType ::= SEQUENCE {
          teraAtmVclTrafficPolicing   
             INTEGER,
          teraAtmVclRowStatus   
             INTEGER
}

teraAtmVclTrafficPolicing OBJECT-TYPE
          SYNTAX INTEGER
                  {
                  on(1),
                  off(2)
                  }
          ACCESS read-write
          STATUS mandatory
          DESCRIPTION
               ""
          ::= { teraAtmVclTableEntry 1 }

teraAtmVclRowStatus OBJECT-TYPE
          SYNTAX INTEGER
                  {
                  active(1),
                  destroy(2)
                  }
          ACCESS read-write
          STATUS mandatory
          DESCRIPTION
               ""
          ::= { teraAtmVclTableEntry 2 }

     -- teraAtmQueueStatsTable

teraAtmQueueStatsTable OBJECT-TYPE
     SYNTAX SEQUENCE OF TeraAtmQueueStatsTableEntryType
     ACCESS not-accessible
     STATUS mandatory
     DESCRIPTION
          " table teraAtmQueueStatsTable"
     ::= { teraATMGroup 14 }

teraAtmQueueStatsTableEntry OBJECT-TYPE
          SYNTAX TeraAtmQueueStatsTableEntryType
          ACCESS not-accessible
          STATUS mandatory
          DESCRIPTION
               " table entry teraAtmQueueStatsTableEntry "
          INDEX {                   teraSlotIndex,                  teraAtmQueueIndex }
     ::= { teraAtmQueueStatsTable 1 }

TeraAtmQueueStatsTableEntryType ::= SEQUENCE {
          teraAtmQueueIndex   
             INTEGER,
          teraAtmQueueStatsSlotMask   
             INTEGER,
          teraAtmQueueStatsCosType   
             INTEGER,
          teraAtmQueueStatsDiscardCellCount   
             Counter32
}

teraAtmQueueIndex OBJECT-TYPE
          SYNTAX INTEGER
          ACCESS read-only
          STATUS mandatory
          DESCRIPTION
               ""
          ::= { teraAtmQueueStatsTableEntry 1 }

teraAtmQueueStatsSlotMask OBJECT-TYPE
          SYNTAX INTEGER
          ACCESS read-only
          STATUS mandatory
          DESCRIPTION
               ""
          ::= { teraAtmQueueStatsTableEntry 2 }

teraAtmQueueStatsCosType OBJECT-TYPE
          SYNTAX INTEGER
                  {
                  none(1),
                  cbr(2),
                  rtVbr(3),
                  nrtVbr(4),
                  ubr(5)
                  }
          ACCESS read-only
          STATUS mandatory
          DESCRIPTION
               ""
          ::= { teraAtmQueueStatsTableEntry 3 }

teraAtmQueueStatsDiscardCellCount OBJECT-TYPE
          SYNTAX Counter32
          ACCESS read-only
          STATUS mandatory
          DESCRIPTION
               ""
          ::= { teraAtmQueueStatsTableEntry 4 }

     -- teraAtmMgmtChannelTable

teraAtmMgmtChannelTable OBJECT-TYPE
     SYNTAX SEQUENCE OF TeraAtmMgmtChannelTableEntryType
     ACCESS not-accessible
     STATUS mandatory
     DESCRIPTION
          " table teraAtmMgmtChannelTable"
     ::= { teraATMGroup 15 }

teraAtmMgmtChannelTableEntry OBJECT-TYPE
          SYNTAX TeraAtmMgmtChannelTableEntryType
          ACCESS not-accessible
          STATUS mandatory
          DESCRIPTION
               " table entry teraAtmMgmtChannelTableEntry "
          INDEX {                   teraAtmIfIndex }
     ::= { teraAtmMgmtChannelTable 1 }

TeraAtmMgmtChannelTableEntryType ::= SEQUENCE {
          teraAtmMgmtChannelVpiLow   
             INTEGER (0..65535),
          teraAtmMgmtChannelVciLow   
             INTEGER (0..65535),
          teraAtmMgmtChannelVpiHigh   
             INTEGER (0..65535),
          teraAtmMgmtChannelVciHigh   
             INTEGER (0..65535)
}

teraAtmMgmtChannelVpiLow OBJECT-TYPE
          SYNTAX INTEGER (0..65535)
          ACCESS read-write
          STATUS mandatory
          DESCRIPTION
               ""
          ::= { teraAtmMgmtChannelTableEntry 1 }

teraAtmMgmtChannelVciLow OBJECT-TYPE
          SYNTAX INTEGER (0..65535)
          ACCESS read-write
          STATUS mandatory
          DESCRIPTION
               ""
          ::= { teraAtmMgmtChannelTableEntry 2 }

teraAtmMgmtChannelVpiHigh OBJECT-TYPE
          SYNTAX INTEGER (0..65535)
          ACCESS read-write
          STATUS mandatory
          DESCRIPTION
               ""
          ::= { teraAtmMgmtChannelTableEntry 3 }

teraAtmMgmtChannelVciHigh OBJECT-TYPE
          SYNTAX INTEGER (0..65535)
          ACCESS read-write
          STATUS mandatory
          DESCRIPTION
               ""
          ::= { teraAtmMgmtChannelTableEntry 4 }

teraAtmDbg OBJECT IDENTIFIER ::=  { teraATMGroup 16 }

     -- teraDebugTable (special)

teraDebugTable OBJECT IDENTIFIER ::=  { teraAtmDbg 1 }

teraDebug1 OBJECT-TYPE
          SYNTAX INTEGER
          ACCESS read-only
          STATUS mandatory
          DESCRIPTION
               ""
          ::= { teraDebugTable 1 }

teraDebug2 OBJECT-TYPE
          SYNTAX INTEGER
          ACCESS read-only
          STATUS mandatory
          DESCRIPTION
               ""
          ::= { teraDebugTable 2 }

teraDebug3 OBJECT-TYPE
          SYNTAX INTEGER
          ACCESS read-only
          STATUS mandatory
          DESCRIPTION
               ""
          ::= { teraDebugTable 3 }

     -- teraAtmPortPVCAlarmStatTable

teraAtmPortPVCAlarmStatTable OBJECT-TYPE
     SYNTAX SEQUENCE OF TeraAtmPortPVCAlarmStatTableEntryType
     ACCESS not-accessible
     STATUS mandatory
     DESCRIPTION
          " table teraAtmPortPVCAlarmStatTable"
     ::= { teraATMGroup 17 }

teraAtmPortPVCAlarmStatTableEntry OBJECT-TYPE
          SYNTAX TeraAtmPortPVCAlarmStatTableEntryType
          ACCESS not-accessible
          STATUS mandatory
          DESCRIPTION
               " table entry teraAtmPortPVCAlarmStatTableEntry "
          INDEX {                   ifIndex,                  atmVclVpi,                  atmVclVci,                  teraAtmPortPVCAlarmStatType }
     ::= { teraAtmPortPVCAlarmStatTable 1 }

TeraAtmPortPVCAlarmStatTableEntryType ::= SEQUENCE {
          teraAtmPortPVCAlarmStatType   
             INTEGER,
          teraAtmPortPVCAlarmStatVPI   
             INTEGER,
          teraAtmPortPVCAlarmStatVCI   
             INTEGER,
          teraAtmPortPVCAlarmStatPort   
             INTEGER,
          teraAtmPortPVCAlarmStatTime   
             INTEGER,
          teraAtmPortPVCAlarmStatReason   
             INTEGER
}

teraAtmPortPVCAlarmStatType OBJECT-TYPE
          SYNTAX INTEGER
          ACCESS read-only
          STATUS mandatory
          DESCRIPTION
               ""
          ::= { teraAtmPortPVCAlarmStatTableEntry 1 }

teraAtmPortPVCAlarmStatVPI OBJECT-TYPE
          SYNTAX INTEGER
          ACCESS read-only
          STATUS mandatory
          DESCRIPTION
               ""
          ::= { teraAtmPortPVCAlarmStatTableEntry 2 }

teraAtmPortPVCAlarmStatVCI OBJECT-TYPE
          SYNTAX INTEGER
          ACCESS read-only
          STATUS mandatory
          DESCRIPTION
               ""
          ::= { teraAtmPortPVCAlarmStatTableEntry 3 }

teraAtmPortPVCAlarmStatPort OBJECT-TYPE
          SYNTAX INTEGER
          ACCESS read-only
          STATUS mandatory
          DESCRIPTION
               ""
          ::= { teraAtmPortPVCAlarmStatTableEntry 4 }

teraAtmPortPVCAlarmStatTime OBJECT-TYPE
          SYNTAX INTEGER
          ACCESS read-only
          STATUS mandatory
          DESCRIPTION
               ""
          ::= { teraAtmPortPVCAlarmStatTableEntry 5 }

teraAtmPortPVCAlarmStatReason OBJECT-TYPE
          SYNTAX INTEGER
          ACCESS read-only
          STATUS mandatory
          DESCRIPTION
               ""
          ::= { teraAtmPortPVCAlarmStatTableEntry 6 }

     -- teraAtmVplTable

teraAtmVplTable OBJECT-TYPE
     SYNTAX SEQUENCE OF TeraAtmVplTableEntryType
     ACCESS not-accessible
     STATUS mandatory
     DESCRIPTION
          " table teraAtmVplTable"
     ::= { teraATMGroup 18 }

teraAtmVplTableEntry OBJECT-TYPE
          SYNTAX TeraAtmVplTableEntryType
          ACCESS not-accessible
          STATUS mandatory
          DESCRIPTION
               " table entry teraAtmVplTableEntry "
          INDEX {                   ifIndex,                  atmVplVpi }
     ::= { teraAtmVplTable 1 }

TeraAtmVplTableEntryType ::= SEQUENCE {
          teraAtmVplTrafficPolicing   
             INTEGER,
          teraAtmVplRowStatus   
             INTEGER
}

teraAtmVplTrafficPolicing OBJECT-TYPE
          SYNTAX INTEGER
                  {
                  on(1),
                  off(2)
                  }
          ACCESS read-write
          STATUS mandatory
          DESCRIPTION
               ""
          ::= { teraAtmVplTableEntry 1 }

teraAtmVplRowStatus OBJECT-TYPE
          SYNTAX INTEGER
                  {
                  active(1),
                  destroy(2)
                  }
          ACCESS read-write
          STATUS mandatory
          DESCRIPTION
               ""
          ::= { teraAtmVplTableEntry 2 }

     -- teraFarEndAtmfAtmLayerTable

teraFarEndAtmfAtmLayerTable OBJECT-TYPE
     SYNTAX SEQUENCE OF TeraFarEndAtmfAtmLayerTableEntryType
     ACCESS not-accessible
     STATUS mandatory
     DESCRIPTION
          " table teraFarEndAtmfAtmLayerTable"
     ::= { teraATMGroup 19 }

teraFarEndAtmfAtmLayerTableEntry OBJECT-TYPE
          SYNTAX TeraFarEndAtmfAtmLayerTableEntryType
          ACCESS not-accessible
          STATUS mandatory
          DESCRIPTION
               " table entry teraFarEndAtmfAtmLayerTableEntry "
          INDEX {                   atmfAtmLayerIndex }
     ::= { teraFarEndAtmfAtmLayerTable 1 }

TeraFarEndAtmfAtmLayerTableEntryType ::= SEQUENCE {
          teraFarEndAtmfAtmLayerIndex   
             INTEGER,
          teraFarEndAtmfAtmLayerMaxVPCs   
             INTEGER (0..4096),
          teraFarEndAtmfAtmLayerMaxVCCs   
             INTEGER (0..268435456),
          teraFarEndAtmfAtmLayerConfiguredVPCs   
             INTEGER (0..4096),
          teraFarEndAtmfAtmLayerConfiguredVCCs   
             INTEGER (0..268435456),
          teraFarEndAtmfAtmLayerMaxVpiBits   
             INTEGER (0..12),
          teraFarEndAtmfAtmLayerMaxVciBits   
             INTEGER (0..16),
          teraFarEndAtmfAtmLayerUniType   
             INTEGER,
          teraFarEndAtmfAtmLayerUniVersion   
             INTEGER,
          teraFarEndAtmfAtmLayerDeviceType   
             INTEGER,
          teraFarEndAtmfAtmLayerIlmiVersion   
             INTEGER,
          teraFarEndAtmfAtmLayerNniSigVersion   
             INTEGER,
          teraFarEndAtmfAtmLayerMaxSvpcVpi   
             INTEGER (0..4096),
          teraFarEndAtmfAtmLayerMaxSvccVpi   
             INTEGER (0..4096),
          teraFarEndAtmfAtmLayerMinSvccVci   
             INTEGER (0..65536)
}

teraFarEndAtmfAtmLayerIndex OBJECT-TYPE
          SYNTAX INTEGER
          ACCESS read-only
          STATUS mandatory
          DESCRIPTION
               ""
          ::= { teraFarEndAtmfAtmLayerTableEntry 1 }

teraFarEndAtmfAtmLayerMaxVPCs OBJECT-TYPE
          SYNTAX INTEGER (0..4096)
          ACCESS read-only
          STATUS mandatory
          DESCRIPTION
               ""
          ::= { teraFarEndAtmfAtmLayerTableEntry 2 }

teraFarEndAtmfAtmLayerMaxVCCs OBJECT-TYPE
          SYNTAX INTEGER (0..268435456)
          ACCESS read-only
          STATUS mandatory
          DESCRIPTION
               ""
          ::= { teraFarEndAtmfAtmLayerTableEntry 3 }

teraFarEndAtmfAtmLayerConfiguredVPCs OBJECT-TYPE
          SYNTAX INTEGER (0..4096)
          ACCESS read-only
          STATUS mandatory
          DESCRIPTION
               ""
          ::= { teraFarEndAtmfAtmLayerTableEntry 4 }

teraFarEndAtmfAtmLayerConfiguredVCCs OBJECT-TYPE
          SYNTAX INTEGER (0..268435456)
          ACCESS read-only
          STATUS mandatory
          DESCRIPTION
               ""
          ::= { teraFarEndAtmfAtmLayerTableEntry 5 }

teraFarEndAtmfAtmLayerMaxVpiBits OBJECT-TYPE
          SYNTAX INTEGER (0..12)
          ACCESS read-only
          STATUS mandatory
          DESCRIPTION
               ""
          ::= { teraFarEndAtmfAtmLayerTableEntry 6 }

teraFarEndAtmfAtmLayerMaxVciBits OBJECT-TYPE
          SYNTAX INTEGER (0..16)
          ACCESS read-only
          STATUS mandatory
          DESCRIPTION
               ""
          ::= { teraFarEndAtmfAtmLayerTableEntry 7 }

teraFarEndAtmfAtmLayerUniType OBJECT-TYPE
          SYNTAX INTEGER
                  {
                  public(1),
                  private(2)
                  }
          ACCESS read-only
          STATUS mandatory
          DESCRIPTION
               ""
          ::= { teraFarEndAtmfAtmLayerTableEntry 8 }

teraFarEndAtmfAtmLayerUniVersion OBJECT-TYPE
          SYNTAX INTEGER
                  {
                  version2point0(1),
                  version3point0(2),
                  version3point1(3),
                  version4point0(4),
                  unsupported(5)
                  }
          ACCESS read-only
          STATUS mandatory
          DESCRIPTION
               ""
          ::= { teraFarEndAtmfAtmLayerTableEntry 9 }

teraFarEndAtmfAtmLayerDeviceType OBJECT-TYPE
          SYNTAX INTEGER
                  {
                  user(1),
                  node(2)
                  }
          ACCESS read-only
          STATUS mandatory
          DESCRIPTION
               ""
          ::= { teraFarEndAtmfAtmLayerTableEntry 10 }

teraFarEndAtmfAtmLayerIlmiVersion OBJECT-TYPE
          SYNTAX INTEGER
                  {
                  unsupported(1),
                  version4point0(2)
                  }
          ACCESS read-only
          STATUS mandatory
          DESCRIPTION
               ""
          ::= { teraFarEndAtmfAtmLayerTableEntry 11 }

teraFarEndAtmfAtmLayerNniSigVersion OBJECT-TYPE
          SYNTAX INTEGER
                  {
                  unsupported(1),
                  iisp(2),
                  pnniVersion1point0(3)
                  }
          ACCESS read-only
          STATUS mandatory
          DESCRIPTION
               ""
          ::= { teraFarEndAtmfAtmLayerTableEntry 12 }

teraFarEndAtmfAtmLayerMaxSvpcVpi OBJECT-TYPE
          SYNTAX INTEGER (0..4096)
          ACCESS read-only
          STATUS mandatory
          DESCRIPTION
               ""
          ::= { teraFarEndAtmfAtmLayerTableEntry 13 }

teraFarEndAtmfAtmLayerMaxSvccVpi OBJECT-TYPE
          SYNTAX INTEGER (0..4096)
          ACCESS read-only
          STATUS mandatory
          DESCRIPTION
               ""
          ::= { teraFarEndAtmfAtmLayerTableEntry 14 }

teraFarEndAtmfAtmLayerMinSvccVci OBJECT-TYPE
          SYNTAX INTEGER (0..65536)
          ACCESS read-only
          STATUS mandatory
          DESCRIPTION
               ""
          ::= { teraFarEndAtmfAtmLayerTableEntry 15 }

     -- teraFarEndAtmfVccTable

teraFarEndAtmfVccTable OBJECT-TYPE
     SYNTAX SEQUENCE OF TeraFarEndAtmfVccTableEntryType
     ACCESS not-accessible
     STATUS mandatory
     DESCRIPTION
          " table teraFarEndAtmfVccTable"
     ::= { teraATMGroup 20 }

teraFarEndAtmfVccTableEntry OBJECT-TYPE
          SYNTAX TeraFarEndAtmfVccTableEntryType
          ACCESS not-accessible
          STATUS mandatory
          DESCRIPTION
               " table entry teraFarEndAtmfVccTableEntry "
          INDEX {                   atmfVccPortIndex }
     ::= { teraFarEndAtmfVccTable 1 }

TeraFarEndAtmfVccTableEntryType ::= SEQUENCE {
          teraFarEndAtmfVccPortIndex   
             INTEGER (0..2147483647),
          teraFarEndAtmfVccVpi   
             INTEGER (0..4095),
          teraFarEndAtmfVccVci   
             INTEGER (0..65535),
          teraFarEndAtmfVccOperStatus   
             INTEGER,
          teraFarEndAtmfVccTransmitTrafficDescriptorType   
             OBJECT IDENTIFIER,
          teraFarEndAtmfVccTransmitTrafficDescriptorParam1   
             INTEGER (0..2147483647),
          teraFarEndAtmfVccTransmitTrafficDescriptorParam2   
             INTEGER (0..2147483647),
          teraFarEndAtmfVccTransmitTrafficDescriptorParam3   
             INTEGER (0..2147483647),
          teraFarEndAtmfVccTransmitTrafficDescriptorParam4   
             INTEGER (0..2147483647),
          teraFarEndAtmfVccTransmitTrafficDescriptorParam5   
             INTEGER (0..2147483647),
          teraFarEndAtmfVccReceiveTrafficDescriptorType   
             OBJECT IDENTIFIER,
          teraFarEndAtmfVccReceiveTrafficDescriptorParam1   
             INTEGER (0..2147483647),
          teraFarEndAtmfVccReceiveTrafficDescriptorParam2   
             INTEGER (0..2147483647),
          teraFarEndAtmfVccReceiveTrafficDescriptorParam3   
             INTEGER (0..2147483647),
          teraFarEndAtmfVccReceiveTrafficDescriptorParam4   
             INTEGER (0..2147483647),
          teraFarEndAtmfVccReceiveTrafficDescriptorParam5   
             INTEGER (0..2147483647),
          teraFarEndAtmfVccQoSCategory   
             INTEGER,
          teraFarEndAtmfVccTransmitQoSClass   
             INTEGER (0..255),
          teraFarEndAtmfVccReceiveQoSClass   
             INTEGER (0..255),
          teraFarEndAtmfVccBestEffortIndicator   
             INTEGER,
          teraFarEndAtmfVccTransmitFrameDiscard   
             INTEGER,
          teraFarEndAtmfVccReceiveFrameDiscard   
             INTEGER,
          teraFarEndAtmfVccServiceCategory   
             INTEGER
}

teraFarEndAtmfVccPortIndex OBJECT-TYPE
          SYNTAX INTEGER (0..2147483647)
          ACCESS read-only
          STATUS mandatory
          DESCRIPTION
               ""
          ::= { teraFarEndAtmfVccTableEntry 1 }

teraFarEndAtmfVccVpi OBJECT-TYPE
          SYNTAX INTEGER (0..4095)
          ACCESS read-only
          STATUS mandatory
          DESCRIPTION
               ""
          ::= { teraFarEndAtmfVccTableEntry 2 }

teraFarEndAtmfVccVci OBJECT-TYPE
          SYNTAX INTEGER (0..65535)
          ACCESS read-only
          STATUS mandatory
          DESCRIPTION
               ""
          ::= { teraFarEndAtmfVccTableEntry 3 }

teraFarEndAtmfVccOperStatus OBJECT-TYPE
          SYNTAX INTEGER
                  {
                  unknown(1),
                  end2endUp(2),
                  end2endDown(3),
                  localUpEnd2endUnknown(4),
                  localDown(5)
                  }
          ACCESS read-only
          STATUS mandatory
          DESCRIPTION
               ""
          ::= { teraFarEndAtmfVccTableEntry 4 }

teraFarEndAtmfVccTransmitTrafficDescriptorType OBJECT-TYPE
          SYNTAX OBJECT IDENTIFIER
          ACCESS read-only
          STATUS mandatory
          DESCRIPTION
               ""
          ::= { teraFarEndAtmfVccTableEntry 5 }

teraFarEndAtmfVccTransmitTrafficDescriptorParam1 OBJECT-TYPE
          SYNTAX INTEGER (0..2147483647)
          ACCESS read-only
          STATUS mandatory
          DESCRIPTION
               ""
          ::= { teraFarEndAtmfVccTableEntry 6 }

teraFarEndAtmfVccTransmitTrafficDescriptorParam2 OBJECT-TYPE
          SYNTAX INTEGER (0..2147483647)
          ACCESS read-only
          STATUS mandatory
          DESCRIPTION
               ""
          ::= { teraFarEndAtmfVccTableEntry 7 }

teraFarEndAtmfVccTransmitTrafficDescriptorParam3 OBJECT-TYPE
          SYNTAX INTEGER (0..2147483647)
          ACCESS read-only
          STATUS mandatory
          DESCRIPTION
               ""
          ::= { teraFarEndAtmfVccTableEntry 8 }

teraFarEndAtmfVccTransmitTrafficDescriptorParam4 OBJECT-TYPE
          SYNTAX INTEGER (0..2147483647)
          ACCESS read-only
          STATUS mandatory
          DESCRIPTION
               ""
          ::= { teraFarEndAtmfVccTableEntry 9 }

teraFarEndAtmfVccTransmitTrafficDescriptorParam5 OBJECT-TYPE
          SYNTAX INTEGER (0..2147483647)
          ACCESS read-only
          STATUS mandatory
          DESCRIPTION
               ""
          ::= { teraFarEndAtmfVccTableEntry 10 }

teraFarEndAtmfVccReceiveTrafficDescriptorType OBJECT-TYPE
          SYNTAX OBJECT IDENTIFIER
          ACCESS read-only
          STATUS mandatory
          DESCRIPTION
               ""
          ::= { teraFarEndAtmfVccTableEntry 11 }

teraFarEndAtmfVccReceiveTrafficDescriptorParam1 OBJECT-TYPE
          SYNTAX INTEGER (0..2147483647)
          ACCESS read-only
          STATUS mandatory
          DESCRIPTION
               ""
          ::= { teraFarEndAtmfVccTableEntry 12 }

teraFarEndAtmfVccReceiveTrafficDescriptorParam2 OBJECT-TYPE
          SYNTAX INTEGER (0..2147483647)
          ACCESS read-only
          STATUS mandatory
          DESCRIPTION
               ""
          ::= { teraFarEndAtmfVccTableEntry 13 }

teraFarEndAtmfVccReceiveTrafficDescriptorParam3 OBJECT-TYPE
          SYNTAX INTEGER (0..2147483647)
          ACCESS read-only
          STATUS mandatory
          DESCRIPTION
               ""
          ::= { teraFarEndAtmfVccTableEntry 14 }

teraFarEndAtmfVccReceiveTrafficDescriptorParam4 OBJECT-TYPE
          SYNTAX INTEGER (0..2147483647)
          ACCESS read-only
          STATUS mandatory
          DESCRIPTION
               ""
          ::= { teraFarEndAtmfVccTableEntry 15 }

teraFarEndAtmfVccReceiveTrafficDescriptorParam5 OBJECT-TYPE
          SYNTAX INTEGER (0..2147483647)
          ACCESS read-only
          STATUS mandatory
          DESCRIPTION
               ""
          ::= { teraFarEndAtmfVccTableEntry 16 }

teraFarEndAtmfVccQoSCategory OBJECT-TYPE
          SYNTAX INTEGER
                  {
                  other(1),
                  deterministic(2),
                  statistical(3),
                  unspecified(4)
                  }
          ACCESS read-only
          STATUS mandatory
          DESCRIPTION
               ""
          ::= { teraFarEndAtmfVccTableEntry 17 }

teraFarEndAtmfVccTransmitQoSClass OBJECT-TYPE
          SYNTAX INTEGER (0..255)
          ACCESS read-only
          STATUS mandatory
          DESCRIPTION
               ""
          ::= { teraFarEndAtmfVccTableEntry 18 }

teraFarEndAtmfVccReceiveQoSClass OBJECT-TYPE
          SYNTAX INTEGER (0..255)
          ACCESS read-only
          STATUS mandatory
          DESCRIPTION
               ""
          ::= { teraFarEndAtmfVccTableEntry 19 }

teraFarEndAtmfVccBestEffortIndicator OBJECT-TYPE
          SYNTAX INTEGER
                  {
                  true(1),
                  false(2)
                  }
          ACCESS read-only
          STATUS mandatory
          DESCRIPTION
               ""
          ::= { teraFarEndAtmfVccTableEntry 20 }

teraFarEndAtmfVccTransmitFrameDiscard OBJECT-TYPE
          SYNTAX INTEGER
                  {
                  true(1),
                  false(2)
                  }
          ACCESS read-only
          STATUS mandatory
          DESCRIPTION
               ""
          ::= { teraFarEndAtmfVccTableEntry 21 }

teraFarEndAtmfVccReceiveFrameDiscard OBJECT-TYPE
          SYNTAX INTEGER
                  {
                  true(1),
                  false(2)
                  }
          ACCESS read-only
          STATUS mandatory
          DESCRIPTION
               ""
          ::= { teraFarEndAtmfVccTableEntry 22 }

teraFarEndAtmfVccServiceCategory OBJECT-TYPE
          SYNTAX INTEGER
                  {
                  other(1),
                  cbr(2),
                  rtVbr(3),
                  nrtVbr(4),
                  abr(5),
                  ubr(6)
                  }
          ACCESS read-only
          STATUS mandatory
          DESCRIPTION
               ""
          ::= { teraFarEndAtmfVccTableEntry 23 }

     -- teraAtmStatsClearTable

teraAtmStatsClearTable OBJECT-TYPE
     SYNTAX SEQUENCE OF TeraAtmStatsClearTableEntryType
     ACCESS not-accessible
     STATUS mandatory
     DESCRIPTION
          " table teraAtmStatsClearTable"
     ::= { teraATMSubGroup1 24 }

teraAtmStatsClearTableEntry OBJECT-TYPE
          SYNTAX TeraAtmStatsClearTableEntryType
          ACCESS not-accessible
          STATUS mandatory
          DESCRIPTION
               " table entry teraAtmStatsClearTableEntry "
          INDEX {                   teraAtmIfIndex,                  teraAtmVpi,                  teraAtmVci }
     ::= { teraAtmStatsClearTable 1 }

TeraAtmStatsClearTableEntryType ::= SEQUENCE {
          teraAtmStatsStat   
             INTEGER
}

teraAtmStatsStat OBJECT-TYPE
          SYNTAX INTEGER
                  {
                  ok(1),
                  clear(2)
                  }
          ACCESS read-write
          STATUS mandatory
          DESCRIPTION
               ""
          ::= { teraAtmStatsClearTableEntry 1 }

END
