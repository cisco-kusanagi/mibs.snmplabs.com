--			Ascend mibfwall MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBFWALL-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibfwallProfile  OBJECT IDENTIFIER ::= { configuration 79}

	-- The mibfwallProfile table
	--
	-- This table contains parameters for the mibfwallProfile profile
	--

    mibfwallProfileTable	OBJECT-TYPE
	SYNTAX		SEQUENCE OF MibfwallProfileEntry
	ACCESS		not-accessible
	STATUS		mandatory
	DESCRIPTION	"A list of mibfwallProfile profile entries."
	::= { mibfwallProfile 1 }

    mibfwallProfileEntry	OBJECT-TYPE
	SYNTAX		MibfwallProfileEntry
	ACCESS		not-accessible
	STATUS		mandatory
	DESCRIPTION	"A mibfwallProfile entry containing objects that
			 maps to the parameters of mibfwallProfile profile."
	INDEX		{ fwallProfile-Name }
	::= { mibfwallProfileTable 1 }

    MibfwallProfileEntry ::=
	SEQUENCE {
	    fwallProfile-Name
		DisplayString,
	    fwallProfile-Version
		INTEGER,
	    fwallProfile-Data
		DisplayString,
	    fwallProfile-Link
		DisplayString,
	    fwallProfile-Action-o
		INTEGER
	}

    fwallProfile-Name	OBJECT-TYPE
	SYNTAX	DisplayString
	ACCESS	read-only
	STATUS	mandatory
	DESCRIPTION	"Descriptive name for this firewall."
	::= { mibfwallProfileEntry 1 }

    fwallProfile-Version	OBJECT-TYPE
	SYNTAX	INTEGER
	ACCESS	read-write
	STATUS	mandatory
	DESCRIPTION	"The version number of software required to load this firewall."
	::= { mibfwallProfileEntry 2 }

    fwallProfile-Data	OBJECT-TYPE
	SYNTAX	DisplayString
	ACCESS	read-write
	STATUS	mandatory
	DESCRIPTION	"The actual contents of the FireWall."
	::= { mibfwallProfileEntry 3 }

    fwallProfile-Link	OBJECT-TYPE
	SYNTAX	DisplayString
	ACCESS	read-write
	STATUS	mandatory
	DESCRIPTION	"Link to an extension firewall profile."
	::= { mibfwallProfileEntry 4 }

    fwallProfile-Action-o	OBJECT-TYPE
	SYNTAX	INTEGER {
		    noAction (1),
		    createProfile (2),
		    deleteProfile (3)
		}
	ACCESS	read-write
	STATUS	mandatory
	DESCRIPTION	""
	::= { mibfwallProfileEntry 5 }

END
