Wellfleet-X25PAD-MIB DEFINITIONS ::= BEGIN

    IMPORTS
      Counter
        FROM RFC1155-SMI
      OBJECT-TYPE
        FROM RFC-1212
      DisplayString
        FROM RFC1213-MIB
      wfX25PadGroup
        FROM Wellfleet-COMMON-MIB;

    wfX25PadDefaultCfgTable OBJECT-TYPE
        SYNTAX  SEQUENCE OF WfX25PadDefaultCfgEntry
        ACCESS  not-accessible
        STATUS  mandatory
        DESCRIPTION
                "Table of X25 PAD Config Objects"
        ::= { wfX25PadGroup 1 }

    wfX25PadDefaultCfgEntry OBJECT-TYPE
        SYNTAX  WfX25PadDefaultCfgEntry
        ACCESS  not-accessible
        STATUS  mandatory
        DESCRIPTION
                "An entry in the X25 Pad Config Table"
        INDEX   { wfX25PadDefaultCfgSlot,
                  wfX25PadDefaultCfgConnector }
        ::= { wfX25PadDefaultCfgTable 1 }

    WfX25PadDefaultCfgEntry ::= SEQUENCE {
            wfX25PadDefaultCfgDelete
                INTEGER,
            wfX25PadDefaultCfgDisable
                INTEGER,
            wfX25PadDefaultCfgState
                INTEGER,
            wfX25PadDefaultCfgSlot
                INTEGER,
            wfX25PadDefaultCfgConnector
                INTEGER,
	    wfX25PadDefaultCfgCircuit
	        INTEGER,
	    wfX25PadDefaultCfgX121Addr
		DisplayString,
	    wfX25PadDefaultCfgDNIC
		DisplayString,
	    wfX25PadDefaultCfgLenSubAddress
		INTEGER,
	    wfX25PadDefaultCfgLCNLow
		INTEGER,
	    wfX25PadDefaultCfgLCNHigh
		INTEGER
    }

    wfX25PadDefaultCfgDelete OBJECT-TYPE
        SYNTAX  INTEGER {
                    created(1),
                    deleted(2)
                }
        ACCESS  read-write
        STATUS  mandatory
        DESCRIPTION
                "Create/Delete parameter"
        DEFVAL  { created }
        ::= { wfX25PadDefaultCfgEntry 1 }

    wfX25PadDefaultCfgDisable OBJECT-TYPE
        SYNTAX  INTEGER {
                    enabled(1),
                    disabled(2)
                }
        ACCESS  read-write
        STATUS  mandatory
        DESCRIPTION
                "Enable/Disable parameter"
        DEFVAL  { enabled }
        ::= { wfX25PadDefaultCfgEntry 2 }

    wfX25PadDefaultCfgState OBJECT-TYPE
        SYNTAX  INTEGER {
                    up(1),
                    down(2),
                    init(3)
                }
        ACCESS  read-only
        STATUS  mandatory
        DESCRIPTION
                "Current state of X.25 PAD sofware on the I-SDB"
        DEFVAL  { down }
        ::= { wfX25PadDefaultCfgEntry 3 }


    wfX25PadDefaultCfgSlot OBJECT-TYPE
        SYNTAX  INTEGER
        ACCESS  read-only
        STATUS  mandatory
        DESCRIPTION
                "Instance ID Slot, filled in by ISDB mib gate"
        ::= { wfX25PadDefaultCfgEntry 4 }

    wfX25PadDefaultCfgConnector OBJECT-TYPE
        SYNTAX  INTEGER
        ACCESS  read-only
        STATUS  mandatory
        DESCRIPTION
                "Instance ID Connector, filled in by ISDB mib gate. For the ASN
                this attribute is an encoded value and is equal to
                'module'*10 + 'connector'. Where 'module' is defined in
                attribute 86 and 'connector' is defined in attribute 78
                of this table. For non-ASN platforms this attribute is
                the physical connector number on the slot."
        ::= { wfX25PadDefaultCfgEntry 5 }

    wfX25PadDefaultCfgCircuit OBJECT-TYPE
        SYNTAX  INTEGER
        ACCESS  read-only
        STATUS  mandatory
        DESCRIPTION
                "Circuit number, filled in by ISDB mib gate"
        ::= { wfX25PadDefaultCfgEntry 6 }

    wfX25PadDefaultCfgX121Addr OBJECT-TYPE
        SYNTAX  DisplayString (SIZE (0..15))
        ACCESS  read-write
        STATUS  mandatory
        DESCRIPTION
                "X.121 address of the X.25 Pad"
        ::= { wfX25PadDefaultCfgEntry 7 }

    wfX25PadDefaultCfgDNIC OBJECT-TYPE
        SYNTAX  DisplayString (SIZE (0..4))
        ACCESS  read-write
        STATUS  mandatory
        DESCRIPTION
                "Data Network Identification Code"
        ::= { wfX25PadDefaultCfgEntry 8 }

    wfX25PadDefaultCfgLenSubAddress OBJECT-TYPE
        SYNTAX  INTEGER(0..8)
        ACCESS  read-write
        STATUS  mandatory
        DESCRIPTION
                "Length of X.121 subaddress "
	DEFVAL  { 2 }
        ::= { wfX25PadDefaultCfgEntry 9 }

    wfX25PadDefaultCfgLCNLow OBJECT-TYPE
        SYNTAX  INTEGER(1..4095)
        ACCESS  read-write
        STATUS  mandatory
        DESCRIPTION
                "Lower range for logical channel numbers"
        ::= { wfX25PadDefaultCfgEntry 10 }

     wfX25PadDefaultCfgLCNHigh OBJECT-TYPE
        SYNTAX  INTEGER(1..4095)
        ACCESS  read-write
        STATUS  mandatory
        DESCRIPTION
                "Upper range for logical channel numbers "
        ::= { wfX25PadDefaultCfgEntry 11 }


    wfX25PadCurrentCfgTable OBJECT-TYPE
        SYNTAX  SEQUENCE OF WfX25PadCurrentCfgEntry
        ACCESS  not-accessible
        STATUS  mandatory
        DESCRIPTION
                "Table of X25 PAD Config Objects"
        ::= { wfX25PadGroup 2 }

    wfX25PadCurrentCfgEntry OBJECT-TYPE
        SYNTAX  WfX25PadCurrentCfgEntry
        ACCESS  not-accessible
        STATUS  mandatory
        DESCRIPTION
                "An entry in the X25 Pad Config Table"
        INDEX   { wfX25PadCurrentCfgSlot,
                  wfX25PadCurrentCfgConnector }
        ::= { wfX25PadCurrentCfgTable 1 }

    WfX25PadCurrentCfgEntry ::= SEQUENCE {
            wfX25PadCurrentCfgState
                INTEGER,
            wfX25PadCurrentCfgSlot
                INTEGER,
            wfX25PadCurrentCfgConnector
                INTEGER,
            wfX25PadCurrentCfgCircuit
                INTEGER,
            wfX25PadCurrentCfgX121Addr
                DisplayString,
	    wfX25PadCurrentCfgDNIC
		DisplayString,
            wfX25PadCurrentCfgLenSubAddress
                INTEGER,
            wfX25PadCurrentCfgLCNLow
                INTEGER,
            wfX25PadCurrentCfgLCNHigh
                INTEGER
    }

    wfX25PadCurrentCfgState OBJECT-TYPE
        SYNTAX  INTEGER {
                    up(1),
                    down(2),
                    init(3)
                }
        ACCESS  read-only
        STATUS  mandatory
        DESCRIPTION
                "Current state of X.25 PAD sofware on the I-SDB"
        DEFVAL  { down }
        ::= { wfX25PadCurrentCfgEntry 1 }

    wfX25PadCurrentCfgSlot OBJECT-TYPE
        SYNTAX  INTEGER
        ACCESS  read-only
        STATUS  mandatory
        DESCRIPTION
                "Instance ID Slot, filled in by ISDB mib gate"
        ::= { wfX25PadCurrentCfgEntry 2 }

    wfX25PadCurrentCfgConnector OBJECT-TYPE
        SYNTAX  INTEGER
        ACCESS  read-only
        STATUS  mandatory
        DESCRIPTION
                "Instance ID Connector, filled in by ISDB mib gate. For the ASN
                this attribute is an encoded value and is equal to
                'module'*10 + 'connector'. Where 'module' is defined in
                attribute 86 and 'connector' is defined in attribute 78
                of this table. For non-ASN platforms this attribute is
                the physical connector number on the slot."
        ::= { wfX25PadCurrentCfgEntry 3 }

    wfX25PadCurrentCfgCircuit OBJECT-TYPE
        SYNTAX  INTEGER
        ACCESS  read-only
        STATUS  mandatory
        DESCRIPTION
                "Circuit number, filled in by ISDB mib gate"
        ::= { wfX25PadCurrentCfgEntry 4 }

    wfX25PadCurrentCfgX121Addr OBJECT-TYPE
        SYNTAX  DisplayString (SIZE (0..15))
        ACCESS  read-only
        STATUS  mandatory
        DESCRIPTION
                "X.121 address of the X.25 Pad"
        ::= { wfX25PadCurrentCfgEntry 5 }

    wfX25PadCurrentCfgDNIC OBJECT-TYPE
        SYNTAX  DisplayString (SIZE (0..4))
        ACCESS  read-only
        STATUS  mandatory
        DESCRIPTION
                "Data Network Identification Code"
        ::= { wfX25PadCurrentCfgEntry 6 }

    wfX25PadCurrentCfgLenSubAddress OBJECT-TYPE
        SYNTAX  INTEGER(0..8)
        ACCESS  read-only
        STATUS  mandatory
        DESCRIPTION
                "Length of X.121 subaddress"
        ::= { wfX25PadCurrentCfgEntry 7 }

    wfX25PadCurrentCfgLCNLow OBJECT-TYPE
        SYNTAX  INTEGER(1..4095)
        ACCESS  read-only
        STATUS  mandatory
        DESCRIPTION
                "Lower range for logical channel numbers"
        ::= { wfX25PadCurrentCfgEntry 8 }

     wfX25PadCurrentCfgLCNHigh OBJECT-TYPE
        SYNTAX  INTEGER(1..4095)
        ACCESS  read-only
        STATUS  mandatory
        DESCRIPTION
                "Upper range for logical channel numbers "
        ::= { wfX25PadCurrentCfgEntry 9 }

	
    wfX25PadStatTable OBJECT-TYPE
        SYNTAX  SEQUENCE OF WfX25PadStatEntry
        ACCESS  not-accessible
        STATUS  mandatory
        DESCRIPTION
                "Table of X25 PAD Stat Objects"
        ::= { wfX25PadGroup 3 }

    wfX25PadStatEntry OBJECT-TYPE
        SYNTAX  WfX25PadStatEntry
        ACCESS  not-accessible
        STATUS  mandatory
        DESCRIPTION
                "An entry in the X25 Pad Config Table"
        INDEX   { wfX25PadStatSlot,
                  wfX25PadStatConnector }
        ::= { wfX25PadStatTable 1 }

    WfX25PadStatEntry ::= SEQUENCE {
            wfX25PadStatState
                INTEGER,
            wfX25PadStatSlot
                INTEGER,
            wfX25PadStatConnector
                INTEGER,
	    wfX25PadStatTotalConnCount
                Counter,
	    wfX25PadStatRxRR
		Counter,
	    wfX25PadStatTxRR
		Counter,
	    wfX25PadStatRxRNR
		Counter,
	    wfX25PadStatTxRNR
		Counter,
	    wfX25PadStatRxRestart
		Counter,
	    wfX25PadStatTxRestart
		Counter
    }
    wfX25PadStatState OBJECT-TYPE
        SYNTAX  INTEGER {
                    up(1),
                    down(2),
                    init(3)
                }
        ACCESS  read-only
        STATUS  mandatory
        DESCRIPTION
                "Current state of X.25 PAD sofware on the I-SDB"
        DEFVAL  { down }
        ::= { wfX25PadStatEntry 1 }


    wfX25PadStatSlot OBJECT-TYPE
        SYNTAX  INTEGER
        ACCESS  read-only
        STATUS  mandatory
        DESCRIPTION
                "Instance ID Slot, filled in by ISDB mib gate"
        ::= { wfX25PadStatEntry 2 }

    wfX25PadStatConnector OBJECT-TYPE
        SYNTAX  INTEGER
        ACCESS  read-only
        STATUS  mandatory
        DESCRIPTION
                "Instance ID Connector, filled in by ISDB mib gate. For the ASN
                this attribute is an encoded value and is equal to
                'module'*10 + 'connector'. Where 'module' is defined in
                attribute 86 and 'connector' is defined in attribute 78
                of this table. For non-ASN platforms this attribute is
                the physical connector number on the slot."
        ::= { wfX25PadStatEntry 3 }

    wfX25PadStatTotalConnCount OBJECT-TYPE
        SYNTAX  Counter
        ACCESS  read-only
        STATUS  mandatory
        DESCRIPTION
                "Total number of connections made to the X.25 Pad "
        ::= { wfX25PadStatEntry 4 }

    wfX25PadStatRxRR OBJECT-TYPE
        SYNTAX  Counter
        ACCESS  read-only
        STATUS  mandatory
        DESCRIPTION
                "Number of receiver ready packets received"
        ::= { wfX25PadStatEntry 5 }

    wfX25PadStatTxRR OBJECT-TYPE
        SYNTAX  Counter
        ACCESS  read-only
        STATUS  mandatory
        DESCRIPTION
                "Number of receiver ready packets transmitted"
        ::= { wfX25PadStatEntry 6 }

    wfX25PadStatRxRNR OBJECT-TYPE
        SYNTAX  Counter
        ACCESS  read-only
        STATUS  mandatory
        DESCRIPTION
                "Number of receiver not ready packets received" 
        ::= { wfX25PadStatEntry 7 }

    wfX25PadStatTxRNR OBJECT-TYPE
        SYNTAX  Counter
        ACCESS  read-only
        STATUS  mandatory
        DESCRIPTION
                "Number of receiver not ready packets transmitted"
        ::= { wfX25PadStatEntry 8 }

    wfX25PadStatRxRestart OBJECT-TYPE
        SYNTAX  Counter
        ACCESS  read-only
        STATUS  mandatory
        DESCRIPTION
                "Number of restart packets received"
        ::= { wfX25PadStatEntry 9 }

    wfX25PadStatTxRestart OBJECT-TYPE
        SYNTAX  Counter
        ACCESS  read-only
        STATUS  mandatory
        DESCRIPTION
                "Number of restart packets transmitted"
        ::= { wfX25PadStatEntry 10 }

    wfX25PadPortDefaultCfgTable OBJECT-TYPE
        SYNTAX  SEQUENCE OF WfX25PadPortDefaultCfgEntry
        ACCESS  not-accessible
        STATUS  mandatory
        DESCRIPTION
                "Table of X25 PAD Port Config Objects"
        ::= { wfX25PadGroup 4 }

    wfX25PadPortDefaultCfgEntry OBJECT-TYPE
        SYNTAX  WfX25PadPortDefaultCfgEntry
        ACCESS  not-accessible
        STATUS  mandatory
        DESCRIPTION
                "An entry in the X25 Pad Port Config Table"
        INDEX   { wfX25PadPortDefaultCfgSlot,
                  wfX25PadPortDefaultCfgConnector,
                  wfX25PadPortDefaultCfgNumber }
        ::= { wfX25PadPortDefaultCfgTable 1 }

    WfX25PadPortDefaultCfgEntry ::= SEQUENCE {
            wfX25PadPortDefaultCfgDelete
                INTEGER,
            wfX25PadPortDefaultCfgDisable
                INTEGER,
            wfX25PadPortDefaultCfgState
                INTEGER,
            wfX25PadPortDefaultCfgSlot
                INTEGER,
            wfX25PadPortDefaultCfgConnector
                INTEGER,
            wfX25PadPortDefaultCfgNumber
                INTEGER,
	    wfX25PadPortDefaultCfgSubAddress
		DisplayString,
	    wfX25PadPortDefaultCfgLenSubAddress
		INTEGER,
            wfX25PadPortDefaultCfgX3escape
                INTEGER,
            wfX25PadPortDefaultCfgX3echo
                INTEGER,
            wfX25PadPortDefaultCfgX3forward
                INTEGER,
            wfX25PadPortDefaultCfgX3idle
                INTEGER,
            wfX25PadPortDefaultCfgX3device
                INTEGER,
            wfX25PadPortDefaultCfgX3signals
                INTEGER,
            wfX25PadPortDefaultCfgX3break
                INTEGER,
            wfX25PadPortDefaultCfgX3discard
                INTEGER,
            wfX25PadPortDefaultCfgX3CRpad
                INTEGER,
            wfX25PadPortDefaultCfgX3folding
                INTEGER,
            wfX25PadPortDefaultCfgX3speed
                INTEGER,
            wfX25PadPortDefaultCfgX3flow
                INTEGER,
            wfX25PadPortDefaultCfgX3LFinsert
                INTEGER,
            wfX25PadPortDefaultCfgX3LFpad
                INTEGER,
            wfX25PadPortDefaultCfgX3Edit
                INTEGER,
            wfX25PadPortDefaultCfgX3Cdelete
                INTEGER,
            wfX25PadPortDefaultCfgX3Ldelete
                INTEGER,
            wfX25PadPortDefaultCfgX3Ldisplay
                INTEGER,
            wfX25PadPortDefaultCfgX3Esignals
                INTEGER,
            wfX25PadPortDefaultCfgX3Mask
                INTEGER,
            wfX25PadPortDefaultCfgX3parity
                INTEGER,
            wfX25PadPortDefaultCfgX3page
                INTEGER,
	    wfX25PadPortDefaultCfgLenUserData
		INTEGER,
	    wfX25PadPortDefaultCfgUserData
		OCTET STRING,
	    wfX25PadPortDefaultCfgLenRawFacilities
		INTEGER,
	    wfX25PadPortDefaultCfgRawFacilitiesData
		OCTET STRING,
	    wfX25PadPortDefaultCfgReverseCharge
		OCTET STRING,
	    wfX25PadPortDefaultCfgThruClassNegotiation
		OCTET STRING,
	    wfX25PadPortDefaultCfgPacketSizeNegotiation
		OCTET STRING,
	    wfX25PadPortDefaultCfgWindowSizeNegotiation
	        OCTET STRING,
	    wfX25PadPortDefaultCfgIntervalTimer
		INTEGER,
	    wfX25PadPortDefaultCfgFullAddressing
                INTEGER
    }
    wfX25PadPortDefaultCfgDelete OBJECT-TYPE
        SYNTAX  INTEGER {
                    created(1),
                    deleted(2)
                }
        ACCESS  read-write
        STATUS  mandatory
        DESCRIPTION
                "Create/Delete parameter"
        DEFVAL  { created }
        ::= { wfX25PadPortDefaultCfgEntry 1 }

    wfX25PadPortDefaultCfgDisable OBJECT-TYPE
        SYNTAX  INTEGER {
                    enabled(1),
                    disabled(2)
                }
        ACCESS  read-write
        STATUS  mandatory
        DESCRIPTION
                "Enable/Disable parameter"
        DEFVAL  { enabled }
        ::= { wfX25PadPortDefaultCfgEntry 2 }


    wfX25PadPortDefaultCfgState OBJECT-TYPE
        SYNTAX  INTEGER {
                    up(1),
                    down(2),
                    init(3)
                }
        ACCESS  read-only
        STATUS  mandatory
        DESCRIPTION
                "Current state of X.25 PAD sofware on the I-SDB"
        DEFVAL  { down }
        ::= { wfX25PadPortDefaultCfgEntry 3 }


    wfX25PadPortDefaultCfgSlot OBJECT-TYPE
        SYNTAX  INTEGER
        ACCESS  read-only
        STATUS  mandatory
        DESCRIPTION
                "Instance ID Slot, filled in by ISDB mib gate"
        ::= { wfX25PadPortDefaultCfgEntry 4 }

    wfX25PadPortDefaultCfgConnector OBJECT-TYPE
        SYNTAX  INTEGER
        ACCESS  read-only
        STATUS  mandatory
        DESCRIPTION
                "Instance ID Connector, filled in by ISDB mib gate. For the ASN
                this attribute is an encoded value and is equal to
                'module'*10 + 'connector'. Where 'module' is defined in
                attribute 86 and 'connector' is defined in attribute 78
                of this table. For non-ASN platforms this attribute is
                the physical connector number on the slot."
        ::= { wfX25PadPortDefaultCfgEntry 5 }

    wfX25PadPortDefaultCfgNumber OBJECT-TYPE
        SYNTAX  INTEGER
        ACCESS  read-only
        STATUS  mandatory
        DESCRIPTION
                "Instance ID Async Port, filled in by ISDB mib gate"
        ::= { wfX25PadPortDefaultCfgEntry 6 }

    wfX25PadPortDefaultCfgSubAddress OBJECT-TYPE
        SYNTAX  DisplayString (SIZE (0..8))
        ACCESS  read-write
        STATUS  mandatory
        DESCRIPTION
                "Subaddress portion of an X.121 address that is used by
		an application and is transparent to the network "
        ::= { wfX25PadPortDefaultCfgEntry 7 }

    wfX25PadPortDefaultCfgLenSubAddress OBJECT-TYPE
        SYNTAX  INTEGER(0..8)
        ACCESS  read-write
        STATUS  mandatory
        DESCRIPTION
                "Size of the Subaddress portion of an X.121 address "
        DEFVAL  { 2 }
        ::= { wfX25PadPortDefaultCfgEntry 8 }

    wfX25PadPortDefaultCfgX3escape OBJECT-TYPE
        SYNTAX  INTEGER(0..126)
        ACCESS  read-write
        STATUS  mandatory
        DESCRIPTION
                "PAD recall using a character"
        DEFVAL  { 1 }
        ::= { wfX25PadPortDefaultCfgEntry 9 }

    wfX25PadPortDefaultCfgX3echo OBJECT-TYPE
        SYNTAX  INTEGER(0..2)
        ACCESS  read-write
        STATUS  mandatory
        DESCRIPTION
                "PAD echo"
        DEFVAL  { 1 }
        ::= { wfX25PadPortDefaultCfgEntry 10 }

    wfX25PadPortDefaultCfgX3forward OBJECT-TYPE
        SYNTAX  INTEGER(0..126)
        ACCESS  read-write
        STATUS  mandatory
        DESCRIPTION
                "Selection of the data forwarding characters"
        DEFVAL  { 2 }
        ::= { wfX25PadPortDefaultCfgEntry 11 }

    wfX25PadPortDefaultCfgX3idle OBJECT-TYPE
        SYNTAX  INTEGER(0..255)
        ACCESS  read-write
        STATUS  mandatory
        DESCRIPTION
                "Selection of the idle timer delay"
        DEFVAL  { 0 }
        ::= { wfX25PadPortDefaultCfgEntry 12 }

    wfX25PadPortDefaultCfgX3device OBJECT-TYPE
        SYNTAX  INTEGER(0..2)
        ACCESS  read-write
        STATUS  mandatory
        DESCRIPTION
                "Ancillary device control"
        DEFVAL  { 2 }
        ::= { wfX25PadPortDefaultCfgEntry 13 }

    wfX25PadPortDefaultCfgX3signals OBJECT-TYPE
        SYNTAX  INTEGER(0..5)
        ACCESS  read-write
        STATUS  mandatory
        DESCRIPTION
                "Control of PAD service signals"
        DEFVAL  { 5 }
        ::= { wfX25PadPortDefaultCfgEntry 14 }

    wfX25PadPortDefaultCfgX3break OBJECT-TYPE
        SYNTAX  INTEGER(0..21)
        ACCESS  read-write
        STATUS  mandatory
        DESCRIPTION
           "Selection of operation of the PAD on receipt of the break signal"
        DEFVAL  { 4 }
        ::= { wfX25PadPortDefaultCfgEntry 15 }

    wfX25PadPortDefaultCfgX3discard OBJECT-TYPE
        SYNTAX  INTEGER(0..1)
        ACCESS  read-write
        STATUS  mandatory
        DESCRIPTION
                "Discard output"
        DEFVAL  { 0 }
        ::= { wfX25PadPortDefaultCfgEntry 16 }

    wfX25PadPortDefaultCfgX3CRpad OBJECT-TYPE
        SYNTAX  INTEGER(0..255)
        ACCESS  read-write
        STATUS  mandatory
        DESCRIPTION
                "Padding after carriage return"
        DEFVAL  { 0 }
        ::= { wfX25PadPortDefaultCfgEntry 17 }

    wfX25PadPortDefaultCfgX3folding OBJECT-TYPE
        SYNTAX  INTEGER(0..255)
        ACCESS  read-write
        STATUS  mandatory
        DESCRIPTION
                "Line folding"
        DEFVAL  { 80 }
        ::= { wfX25PadPortDefaultCfgEntry 18 }

    wfX25PadPortDefaultCfgX3speed OBJECT-TYPE
        SYNTAX  INTEGER(0..18)
        ACCESS  read-write
        STATUS  mandatory
        DESCRIPTION
                "Binary speed"
        DEFVAL  { 14 }
        ::= { wfX25PadPortDefaultCfgEntry 19 }

    wfX25PadPortDefaultCfgX3flow OBJECT-TYPE
        SYNTAX  INTEGER(0..1)
        ACCESS  read-write
        STATUS  mandatory
        DESCRIPTION
                "Flow Control of the PAD by the start-stop mode DTE"
        DEFVAL  { 1 }
        ::= { wfX25PadPortDefaultCfgEntry 20 }

    wfX25PadPortDefaultCfgX3LFinsert OBJECT-TYPE
        SYNTAX  INTEGER(0..7)
        ACCESS  read-write
        STATUS  mandatory
        DESCRIPTION
                "Linefeed insertion after carriage return"
        DEFVAL  { 4 }
        ::= { wfX25PadPortDefaultCfgEntry 21 }

    wfX25PadPortDefaultCfgX3LFpad OBJECT-TYPE
        SYNTAX  INTEGER(0..255)
        ACCESS  read-write
        STATUS  mandatory
        DESCRIPTION
                "Linefeed padding"
        DEFVAL  { 0 }
        ::= { wfX25PadPortDefaultCfgEntry 22 }

    wfX25PadPortDefaultCfgX3Edit OBJECT-TYPE
        SYNTAX  INTEGER(0..1)
        ACCESS  read-write
        STATUS  mandatory
        DESCRIPTION
                "Editing"
        DEFVAL  { 1 }
        ::= { wfX25PadPortDefaultCfgEntry 23 }

    wfX25PadPortDefaultCfgX3Cdelete OBJECT-TYPE
        SYNTAX  INTEGER(0..127)
        ACCESS  read-write
        STATUS  mandatory
        DESCRIPTION
                "Character delete"
        DEFVAL  { 127 }
        ::= { wfX25PadPortDefaultCfgEntry 24 }

    wfX25PadPortDefaultCfgX3Ldelete OBJECT-TYPE
        SYNTAX  INTEGER(0..127)
        ACCESS  read-write
        STATUS  mandatory
        DESCRIPTION
                "Line delete"
        DEFVAL  { 24 }
        ::= { wfX25PadPortDefaultCfgEntry 25 }

    wfX25PadPortDefaultCfgX3Ldisplay OBJECT-TYPE
        SYNTAX  INTEGER(0..127)
        ACCESS  read-write
        STATUS  mandatory
        DESCRIPTION
                "Line display"
        DEFVAL  { 18 }
        ::= { wfX25PadPortDefaultCfgEntry 26 }

    wfX25PadPortDefaultCfgX3Esignals OBJECT-TYPE
        SYNTAX  INTEGER(0..126)
        ACCESS  read-write
        STATUS  mandatory
        DESCRIPTION
                "Editing PAD service signals"
        DEFVAL  { 2 }
        ::= { wfX25PadPortDefaultCfgEntry 27 }

    wfX25PadPortDefaultCfgX3Mask OBJECT-TYPE
        SYNTAX  INTEGER(0..255)
        ACCESS  read-write
        STATUS  mandatory
        DESCRIPTION
                "Echo mask"
        DEFVAL  { 0 }
        ::= { wfX25PadPortDefaultCfgEntry 28 }

    wfX25PadPortDefaultCfgX3parity OBJECT-TYPE
        SYNTAX  INTEGER(0..3)
        ACCESS  read-write
        STATUS  mandatory
        DESCRIPTION
                "Parity treatment"
        DEFVAL  { 3 }
        ::= { wfX25PadPortDefaultCfgEntry 29 }

    wfX25PadPortDefaultCfgX3page OBJECT-TYPE
        SYNTAX  INTEGER(0..255)
        ACCESS  read-write
        STATUS  mandatory
        DESCRIPTION
                "Page wait"
        DEFVAL  { 0 }
        ::= { wfX25PadPortDefaultCfgEntry 30 }

    wfX25PadPortDefaultCfgLenUserData OBJECT-TYPE
        SYNTAX  INTEGER(0..16)
        ACCESS  read-write
        STATUS  mandatory
        DESCRIPTION
                "Length of the user defined data "
        DEFVAL  { 0 }
        ::= { wfX25PadPortDefaultCfgEntry 31 }

    wfX25PadPortDefaultCfgUserData OBJECT-TYPE
        SYNTAX  OCTET STRING (SIZE (0..16))
        ACCESS  read-write
        STATUS  mandatory
        DESCRIPTION
                "User defined data field represented in hexadecimal"
        ::= { wfX25PadPortDefaultCfgEntry 32 }

    wfX25PadPortDefaultCfgLenRawFacilities OBJECT-TYPE
        SYNTAX  INTEGER(0..63)
        ACCESS  read-write
        STATUS  mandatory
        DESCRIPTION
                "Length of the user defined facilities"
        DEFVAL  { 0 }
        ::= { wfX25PadPortDefaultCfgEntry 33 }

    wfX25PadPortDefaultCfgRawFacilitiesData OBJECT-TYPE
        SYNTAX  OCTET STRING (SIZE (0..63)) 
        ACCESS  read-write
        STATUS  mandatory
        DESCRIPTION
                "User defined facilities filed represented in hexadecimal"
        ::= { wfX25PadPortDefaultCfgEntry 34 }

    wfX25PadPortDefaultCfgReverseCharge OBJECT-TYPE
        SYNTAX  OCTET STRING (SIZE (0..2)) 
        ACCESS  read-write
        STATUS  mandatory
        DESCRIPTION
                "If subscribed to, authorizes the DCE to transmit to
		the DTE incoming calls which request the reverse charging
		facility.  In absence of this facility the DCE will not
		transmit to the DTE incoming calls which request the
		reverse charging facility. "
        ::= { wfX25PadPortDefaultCfgEntry 35 }

    wfX25PadPortDefaultCfgThruClassNegotiation OBJECT-TYPE
        SYNTAX  OCTET STRING (SIZE (0..2)) 
        ACCESS  read-write
        STATUS  mandatory
        DESCRIPTION
                "This facility, if subscribed to, allows negotiation on a per
		call basis of the throughput classes.  The throughput classes 
		are considered independently for each direction of data
		transmission. "
        ::= { wfX25PadPortDefaultCfgEntry 36 }

    wfX25PadPortDefaultCfgPacketSizeNegotiation OBJECT-TYPE
        SYNTAX  OCTET STRING (SIZE (0..3)) 
        ACCESS  read-write
        STATUS  mandatory
        DESCRIPTION
                "This facility, if subscribed to, will cause the DTE to
		request packet sizes for both directions of data transmission "
        ::= { wfX25PadPortDefaultCfgEntry 37 }

    wfX25PadPortDefaultCfgWindowSizeNegotiation OBJECT-TYPE
        SYNTAX  OCTET STRING (SIZE (0..3)) 
        ACCESS  read-write
        STATUS  mandatory
        DESCRIPTION
                "This facility, if subscribed to, will cause the DTE to
		request window sizes for both directions of data transmission "
        ::= { wfX25PadPortDefaultCfgEntry 38 }

    wfX25PadPortDefaultCfgIntervalTimer OBJECT-TYPE
        SYNTAX  INTEGER (0..999)
        ACCESS  read-write
        STATUS  mandatory
        DESCRIPTION
                "Time (where 1 equals 10 milliseconds) that the X.25 PAD will
		 wait before forwarding packets with characters in them "
        DEFVAL  { 0 }
        ::= { wfX25PadPortDefaultCfgEntry 39 }

    wfX25PadPortDefaultCfgFullAddressing OBJECT-TYPE
        SYNTAX  INTEGER {
                    enabled(1),
                    disabled(2)
                }
        ACCESS  read-write
        STATUS  mandatory
        DESCRIPTION
                "Determines whether calling addresses should be included or not"
        DEFVAL  { enabled }
        ::= { wfX25PadPortDefaultCfgEntry 40 }

    wfX25PadPortCurrentCfgTable OBJECT-TYPE
        SYNTAX  SEQUENCE OF WfX25PadPortCurrentCfgEntry
        ACCESS  not-accessible
        STATUS  mandatory
        DESCRIPTION
                "Table of X25 PAD Port Config Objects"
        ::= { wfX25PadGroup 5 }

    wfX25PadPortCurrentCfgEntry OBJECT-TYPE
        SYNTAX  WfX25PadPortCurrentCfgEntry
        ACCESS  not-accessible
        STATUS  mandatory
        DESCRIPTION
                "An entry in the X25 Pad Port Config Table"
        INDEX   { wfX25PadPortCurrentCfgSlot,
                  wfX25PadPortCurrentCfgConnector,
                  wfX25PadPortCurrentCfgNumber }
        ::= { wfX25PadPortCurrentCfgTable 1 }

    WfX25PadPortCurrentCfgEntry ::= SEQUENCE {
            wfX25PadPortCurrentCfgState
                INTEGER,
            wfX25PadPortCurrentCfgSlot
                INTEGER,
            wfX25PadPortCurrentCfgConnector
                INTEGER,
            wfX25PadPortCurrentCfgNumber
                INTEGER,
	    wfX25PadPortCurrentCfgSubAddress
		DisplayString,
	    wfX25PadPortCurrentCfgLenSubAddress
		INTEGER,
            wfX25PadPortCurrentCfgX3escape
                INTEGER,
            wfX25PadPortCurrentCfgX3echo
                INTEGER,
            wfX25PadPortCurrentCfgX3forward
                INTEGER,
            wfX25PadPortCurrentCfgX3idle
                INTEGER,
            wfX25PadPortCurrentCfgX3device
                INTEGER,
            wfX25PadPortCurrentCfgX3signals
                INTEGER,
            wfX25PadPortCurrentCfgX3break
                INTEGER,
            wfX25PadPortCurrentCfgX3discard
                INTEGER,
            wfX25PadPortCurrentCfgX3CRpad
                INTEGER,
            wfX25PadPortCurrentCfgX3folding
                INTEGER,
            wfX25PadPortCurrentCfgX3speed
                INTEGER,
            wfX25PadPortCurrentCfgX3flow
                INTEGER,
            wfX25PadPortCurrentCfgX3LFinsert
                INTEGER,
            wfX25PadPortCurrentCfgX3LFpad
                INTEGER,
            wfX25PadPortCurrentCfgX3Edit
                INTEGER,
            wfX25PadPortCurrentCfgX3Cdelete
                INTEGER,
            wfX25PadPortCurrentCfgX3Ldelete
                INTEGER,
            wfX25PadPortCurrentCfgX3Ldisplay
                INTEGER,
            wfX25PadPortCurrentCfgX3Esignals
                INTEGER,
            wfX25PadPortCurrentCfgX3Mask
                INTEGER,
            wfX25PadPortCurrentCfgX3parity
                INTEGER,
            wfX25PadPortCurrentCfgX3page
                INTEGER,
            wfX25PadPortCurrentCfgLenUserData
                INTEGER,
            wfX25PadPortCurrentCfgUserData
                OCTET STRING,
            wfX25PadPortCurrentCfgLenRawFacilities
                INTEGER,
            wfX25PadPortCurrentCfgRawFacilitiesData
                OCTET STRING,
            wfX25PadPortCurrentCfgReverseCharge
                OCTET STRING,
            wfX25PadPortCurrentCfgThruClassNegotiation
                OCTET STRING,
            wfX25PadPortCurrentCfgPacketSizeNegotiation
                OCTET STRING,
            wfX25PadPortCurrentCfgWindowSizeNegotiation
                OCTET STRING,
	    wfX25PadPortCurrentCfgIntervalTimer
                INTEGER,
	    wfX25PadPortCurrentCfgFullAddressing
                INTEGER
    }

    wfX25PadPortCurrentCfgState OBJECT-TYPE
        SYNTAX  INTEGER {
                    up(1),
                    down(2),
                    init(3)
                }
        ACCESS  read-only
        STATUS  mandatory
        DESCRIPTION
                "Current state of X.25 PAD sofware on the I-SDB"
        DEFVAL  { down }
        ::= { wfX25PadPortCurrentCfgEntry 1 }


    wfX25PadPortCurrentCfgSlot OBJECT-TYPE
        SYNTAX  INTEGER
        ACCESS  read-only
        STATUS  mandatory
        DESCRIPTION
                "Instance ID Slot, filled in by ISDB mib gate"
        ::= { wfX25PadPortCurrentCfgEntry 2 }

    wfX25PadPortCurrentCfgConnector OBJECT-TYPE
        SYNTAX  INTEGER
        ACCESS  read-only
        STATUS  mandatory
        DESCRIPTION
                "Instance ID Connector, filled in by ISDB mib gate. For the ASN
                this attribute is an encoded value and is equal to
                'module'*10 + 'connector'. Where 'module' is defined in
                attribute 86 and 'connector' is defined in attribute 78
                of this table. For non-ASN platforms this attribute is
                the physical connector number on the slot."
        ::= { wfX25PadPortCurrentCfgEntry 3 }

    wfX25PadPortCurrentCfgNumber OBJECT-TYPE
        SYNTAX  INTEGER
        ACCESS  read-only
        STATUS  mandatory
        DESCRIPTION
                "Instance ID Async Port, filled in by ISDB mib gate"
        ::= { wfX25PadPortCurrentCfgEntry 4 }

    wfX25PadPortCurrentCfgSubAddress OBJECT-TYPE
        SYNTAX  DisplayString (SIZE (0..8)) 
        ACCESS  read-only
        STATUS  mandatory
        DESCRIPTION
                "Subaddress portion of an X.121 address that is used by
                an application and is transparent to the network "
        ::= { wfX25PadPortCurrentCfgEntry 5 }

    wfX25PadPortCurrentCfgLenSubAddress OBJECT-TYPE
        SYNTAX  INTEGER(0..8)
        ACCESS  read-only
        STATUS  mandatory
        DESCRIPTION
                "Size of the Subaddress portion of an X.121 address "
        ::= { wfX25PadPortCurrentCfgEntry 6 }

    wfX25PadPortCurrentCfgX3escape OBJECT-TYPE
        SYNTAX  INTEGER(0..126)
        ACCESS  read-only
        STATUS  mandatory
        DESCRIPTION
                "PAD recall using a character"
        ::= { wfX25PadPortCurrentCfgEntry 7 }

    wfX25PadPortCurrentCfgX3echo OBJECT-TYPE
        SYNTAX  INTEGER(0..2)
        ACCESS  read-only
        STATUS  mandatory
        DESCRIPTION
                "PAD echo"
        ::= { wfX25PadPortCurrentCfgEntry 8 }

    wfX25PadPortCurrentCfgX3forward OBJECT-TYPE
        SYNTAX  INTEGER(0..126)
        ACCESS  read-only
        STATUS  mandatory
        DESCRIPTION
                "Selection of the data forwarding characters"
        ::= { wfX25PadPortCurrentCfgEntry 9 }

    wfX25PadPortCurrentCfgX3idle OBJECT-TYPE
        SYNTAX  INTEGER(0..255)
        ACCESS  read-only
        STATUS  mandatory
        DESCRIPTION
                "Selection of the idle timer delay"
        ::= { wfX25PadPortCurrentCfgEntry 10 }

    wfX25PadPortCurrentCfgX3device OBJECT-TYPE
        SYNTAX  INTEGER(0..2)
        ACCESS  read-only
        STATUS  mandatory
        DESCRIPTION
                "Ancillary device control"
        ::= { wfX25PadPortCurrentCfgEntry 11 }

    wfX25PadPortCurrentCfgX3signals OBJECT-TYPE
        SYNTAX  INTEGER(0..48)
        ACCESS  read-only
        STATUS  mandatory
        DESCRIPTION
                "Control of PAD service signals"
        ::= { wfX25PadPortCurrentCfgEntry 12 }

    wfX25PadPortCurrentCfgX3break OBJECT-TYPE
        SYNTAX  INTEGER(0..21)
        ACCESS  read-only
        STATUS  mandatory
        DESCRIPTION
           "Selection of operation of the PAD on receipt of the break signal"
        ::= { wfX25PadPortCurrentCfgEntry 13 }

    wfX25PadPortCurrentCfgX3discard OBJECT-TYPE
        SYNTAX  INTEGER(0..1)
        ACCESS  read-only
        STATUS  mandatory
        DESCRIPTION
                "Discard output"
        ::= { wfX25PadPortCurrentCfgEntry 14 }

    wfX25PadPortCurrentCfgX3CRpad OBJECT-TYPE
        SYNTAX  INTEGER(0..255)
        ACCESS  read-only
        STATUS  mandatory
        DESCRIPTION
                "Padding after carriage return"
        ::= { wfX25PadPortCurrentCfgEntry 15 }

    wfX25PadPortCurrentCfgX3folding OBJECT-TYPE
        SYNTAX  INTEGER(0..255)
        ACCESS  read-only
        STATUS  mandatory
        DESCRIPTION
                "Line folding"
        ::= { wfX25PadPortCurrentCfgEntry 16 }

    wfX25PadPortCurrentCfgX3speed OBJECT-TYPE
        SYNTAX  INTEGER(0..18)
        ACCESS  read-only
        STATUS  mandatory
        DESCRIPTION
                "Binary speed"
        ::= { wfX25PadPortCurrentCfgEntry 17 }

    wfX25PadPortCurrentCfgX3flow OBJECT-TYPE
        SYNTAX  INTEGER(0..1)
        ACCESS  read-only
        STATUS  mandatory
        DESCRIPTION
                "Flow Control of the PAD by the start-stop mode DTE"
        ::= { wfX25PadPortCurrentCfgEntry 18 }

    wfX25PadPortCurrentCfgX3LFinsert OBJECT-TYPE
        SYNTAX  INTEGER(0..7)
        ACCESS  read-only
        STATUS  mandatory
        DESCRIPTION
                "Linefeed insertion after carriage return"
        ::= { wfX25PadPortCurrentCfgEntry 19 }

    wfX25PadPortCurrentCfgX3LFpad OBJECT-TYPE
        SYNTAX  INTEGER(0..255)
        ACCESS  read-only
        STATUS  mandatory
        DESCRIPTION
                "Linefeed padding"
        ::= { wfX25PadPortCurrentCfgEntry 20 }

    wfX25PadPortCurrentCfgX3Edit OBJECT-TYPE
        SYNTAX  INTEGER(0..1)
        ACCESS  read-only
        STATUS  mandatory
        DESCRIPTION
                "Editing"
        ::= { wfX25PadPortCurrentCfgEntry 21 }

    wfX25PadPortCurrentCfgX3Cdelete OBJECT-TYPE
        SYNTAX  INTEGER(0..127)
        ACCESS  read-only
        STATUS  mandatory
        DESCRIPTION
                "Character delete"
        ::= { wfX25PadPortCurrentCfgEntry 22 }

    wfX25PadPortCurrentCfgX3Ldelete OBJECT-TYPE
        SYNTAX  INTEGER(0..127)
        ACCESS  read-only
        STATUS  mandatory
        DESCRIPTION
                "Line delete"
        ::= { wfX25PadPortCurrentCfgEntry 23 }

    wfX25PadPortCurrentCfgX3Ldisplay OBJECT-TYPE
        SYNTAX  INTEGER(0..127)
        ACCESS  read-only
        STATUS  mandatory
        DESCRIPTION
                "Line display"
        ::= { wfX25PadPortCurrentCfgEntry 24 }

    wfX25PadPortCurrentCfgX3Esignals OBJECT-TYPE
        SYNTAX  INTEGER(0..126)
        ACCESS  read-only
        STATUS  mandatory
        DESCRIPTION
                "Editing PAD service signals"
        ::= { wfX25PadPortCurrentCfgEntry 25 }

    wfX25PadPortCurrentCfgX3Mask OBJECT-TYPE
        SYNTAX  INTEGER(0..255)
        ACCESS  read-only
        STATUS  mandatory
        DESCRIPTION
                "Echo mask"
        ::= { wfX25PadPortCurrentCfgEntry 26 }

    wfX25PadPortCurrentCfgX3parity OBJECT-TYPE
        SYNTAX  INTEGER(0..3)
        ACCESS  read-only
        STATUS  mandatory
        DESCRIPTION
                "Parity treatment"
        DEFVAL  { 0 }
        ::= { wfX25PadPortCurrentCfgEntry 27 }

    wfX25PadPortCurrentCfgX3page OBJECT-TYPE
        SYNTAX  INTEGER(0..255)
        ACCESS  read-only
        STATUS  mandatory
        DESCRIPTION
                "Page wait"
        ::= { wfX25PadPortCurrentCfgEntry 28 }

    wfX25PadPortCurrentCfgLenUserData OBJECT-TYPE
        SYNTAX  INTEGER(0..16)
        ACCESS  read-only
        STATUS  mandatory
        DESCRIPTION
                "Length of the user defined data "
        ::= { wfX25PadPortCurrentCfgEntry 29 }

    wfX25PadPortCurrentCfgUserData OBJECT-TYPE
        SYNTAX  OCTET STRING (SIZE (0..16)) 
        ACCESS  read-only
        STATUS  mandatory
        DESCRIPTION
                "User defined data field represented in hexadecimal"
        ::= { wfX25PadPortCurrentCfgEntry 30 }

    wfX25PadPortCurrentCfgLenRawFacilities OBJECT-TYPE
        SYNTAX  INTEGER(0..63)
        ACCESS  read-only
        STATUS  mandatory
        DESCRIPTION
                "Length of the user defined facilities"
        ::= { wfX25PadPortCurrentCfgEntry 31 }

    wfX25PadPortCurrentCfgRawFacilitiesData OBJECT-TYPE
        SYNTAX  OCTET STRING (SIZE (0..63)) 
        ACCESS  read-only
        STATUS  mandatory
        DESCRIPTION
                "User defined facilities filed represented in hexadecimal"
        ::= { wfX25PadPortCurrentCfgEntry 32 }

    wfX25PadPortCurrentCfgReverseCharge OBJECT-TYPE
        SYNTAX  OCTET STRING (SIZE (0..2))
        ACCESS  read-only
        STATUS  mandatory
        DESCRIPTION
                "If subscribed to, authorizes the DCE to transmit to
                the DTE incoming calls which request the reverse charging
                facility.  In absence of this facility the DCE will not
                transmit to the DTE incoming calls which request the
                reverse charging facility. "
        ::= { wfX25PadPortCurrentCfgEntry 33 }

    wfX25PadPortCurrentCfgThruClassNegotiation OBJECT-TYPE
        SYNTAX  OCTET STRING (SIZE (0..2))
        ACCESS  read-only
        STATUS  mandatory
        DESCRIPTION
                "This facility, if subscribed to, allows negotiation on a per
                call basis of the throughput classes.  The throughput classes
                are considered independently for each direction of data
                transmission. "
        ::= { wfX25PadPortCurrentCfgEntry 34 }

    wfX25PadPortCurrentCfgPacketSizeNegotiation OBJECT-TYPE
        SYNTAX  OCTET STRING (SIZE (0..3))
        ACCESS  read-only
        STATUS  mandatory
        DESCRIPTION
                "This facility, if subscribed to, will cause the DTE to
                request packet sizes for both directions of data transmission. "
        ::= { wfX25PadPortCurrentCfgEntry 35 }

    wfX25PadPortCurrentCfgWindowSizeNegotiation OBJECT-TYPE
        SYNTAX  OCTET STRING (SIZE (0..3))
        ACCESS  read-only
        STATUS  mandatory
        DESCRIPTION
                "This facility, if subscribed to, will cause the DTE to
                request window sizes for both directions of data transmission. "
        ::= { wfX25PadPortCurrentCfgEntry 36 }

    wfX25PadPortCurrentCfgIntervalTimer OBJECT-TYPE
        SYNTAX  INTEGER (0..999)
        ACCESS  read-write
        STATUS  mandatory
        DESCRIPTION
                "Time (where 1 equals 10 milliseconds) that the X.25 PAD will
                 wait before forwarding packets with characters in them "
        ::= { wfX25PadPortCurrentCfgEntry 37 }

    wfX25PadPortCurrentCfgFullAddressing OBJECT-TYPE
        SYNTAX  INTEGER {
                    enabled(1),
                    disabled(2)
                }
        ACCESS  read-write
        STATUS  mandatory
        DESCRIPTION
                "Determines whether calling addresses should be included or not"
        DEFVAL  { enabled }
        ::= { wfX25PadPortCurrentCfgEntry 38 }


    wfX25PadPortStatTable OBJECT-TYPE
        SYNTAX  SEQUENCE OF WfX25PadPortStatEntry
        ACCESS  not-accessible
        STATUS  mandatory
        DESCRIPTION
                "Table of X25 PAD Port Stat Objects"
        ::= { wfX25PadGroup 6 }

    wfX25PadPortStatEntry OBJECT-TYPE
        SYNTAX  WfX25PadPortStatEntry
        ACCESS  not-accessible
        STATUS  mandatory
        DESCRIPTION
                "An entry in the X25 Pad Port Stat Table"
        INDEX   { wfX25PadPortStatSlot,
                  wfX25PadPortStatConnector,
                  wfX25PadPortStatNumber }
        ::= { wfX25PadPortStatTable 1 }

    WfX25PadPortStatEntry ::= SEQUENCE {
            wfX25PadPortStatState
                INTEGER,
            wfX25PadPortStatSlot
                INTEGER,
            wfX25PadPortStatConnector
                INTEGER,
            wfX25PadPortStatNumber
                INTEGER,
            wfX25PadPortStatRxOctets
                Counter,
            wfX25PadPortStatTxOctets
                Counter,
	    wfX25PadPortStatRxPackets
                Counter,
            wfX25PadPortStatTxPackets
                Counter,
            wfX25PadPortStatRemoteX121Addr
                DisplayString,
            wfX25PadPortStatLCN
                INTEGER,
	    wfX25PadPortStatDuration
		INTEGER,
	    wfX25PadPortStatRxRR
		Counter,
	    wfX25PadPortStatTxRR
		Counter,
	    wfX25PadPortStatRxRNR
		Counter,
	    wfX25PadPortStatTxRNR
		Counter,
	    wfX25PadPortStatRxClr
		Counter,
	    wfX25PadPortStatTxClr
		Counter,
	    wfX25PadPortStatRxReset
		Counter,
	    wfX25PadPortStatTxReset
		Counter,
	    wfX25PadPortStatRxCall
		Counter,
	    wfX25PadPortStatTxCall
		Counter,
	    wfX25PadPortStatConnections
		Counter,
	    wfX25PadPortStatDisconnects
		Counter,
	    wfX25PadPortStatLastCause
		INTEGER,
	    wfX25PadPortStatLastDiag
		INTEGER
	}

    wfX25PadPortStatState OBJECT-TYPE
        SYNTAX  INTEGER {
                    up(1),
                    down(2),
                    init(3)
                }
        ACCESS  read-only
        STATUS  mandatory
        DESCRIPTION
                "Current state of X.25 PAD sofware on the I-SDB"
        DEFVAL  { down }
        ::= { wfX25PadPortStatEntry 1 }


    wfX25PadPortStatSlot OBJECT-TYPE
        SYNTAX  INTEGER
        ACCESS  read-only
        STATUS  mandatory
        DESCRIPTION
                "Instance ID Slot, filled in by ISDB mib gate"
        ::= { wfX25PadPortStatEntry 2 }

    wfX25PadPortStatConnector OBJECT-TYPE
        SYNTAX  INTEGER
        ACCESS  read-only
        STATUS  mandatory
        DESCRIPTION
                "Instance ID Connector, filled in by ISDB mib gate. For the ASN
                this attribute is an encoded value and is equal to
                'module'*10 + 'connector'. Where 'module' is defined in
                attribute 86 and 'connector' is defined in attribute 78
                of this table. For non-ASN platforms this attribute is
                the physical connector number on the slot."
        ::= { wfX25PadPortStatEntry 3 }

    wfX25PadPortStatNumber OBJECT-TYPE
        SYNTAX  INTEGER
        ACCESS  read-only
        STATUS  mandatory
        DESCRIPTION
                "Instance ID Async Port, filled in by ISDB mib gate"
        ::= { wfX25PadPortStatEntry 4 }

    wfX25PadPortStatRxOctets OBJECT-TYPE
        SYNTAX  Counter
        ACCESS  read-only
        STATUS  mandatory
        DESCRIPTION
                "Number of octets received on this async port"
        ::= { wfX25PadPortStatEntry 5 }

    wfX25PadPortStatTxOctets OBJECT-TYPE
        SYNTAX  Counter
        ACCESS  read-only
        STATUS  mandatory
        DESCRIPTION
                "Number of octets transmitted on this async port"
        ::= { wfX25PadPortStatEntry 6 }

    wfX25PadPortStatRxPackets OBJECT-TYPE
        SYNTAX  Counter
        ACCESS  read-only
        STATUS  mandatory
        DESCRIPTION
                "Number of packets received on this async port "
        ::= { wfX25PadPortStatEntry 7 }

    wfX25PadPortStatTxPackets OBJECT-TYPE
        SYNTAX  Counter
        ACCESS  read-only
        STATUS  mandatory
        DESCRIPTION
                "Number of packets transmitted on this async port"
        ::= { wfX25PadPortStatEntry 8 }

    wfX25PadPortStatRemoteX121Addr OBJECT-TYPE
        SYNTAX  DisplayString (SIZE (0..15))
        ACCESS  read-only
        STATUS  mandatory
        DESCRIPTION
                "Remote X.121 address"
        ::= { wfX25PadPortStatEntry 9 }

    wfX25PadPortStatLCN OBJECT-TYPE
        SYNTAX  INTEGER
        ACCESS  read-only
        STATUS  mandatory
        DESCRIPTION
                "Current connection's logical channel number"
        ::= { wfX25PadPortStatEntry 10 }

    wfX25PadPortStatDuration OBJECT-TYPE
        SYNTAX  INTEGER
        ACCESS  read-only
        STATUS  mandatory
        DESCRIPTION
                "Time in seconds of the call"
        ::= { wfX25PadPortStatEntry 11 }
	
    wfX25PadPortStatRxRR OBJECT-TYPE
        SYNTAX  Counter
        ACCESS  read-only
        STATUS  mandatory
        DESCRIPTION
                "Number of receiver ready packets received"
        ::= { wfX25PadPortStatEntry 12 }

    wfX25PadPortStatTxRR OBJECT-TYPE
        SYNTAX  Counter
        ACCESS  read-only
        STATUS  mandatory
        DESCRIPTION
                "Number of receiver ready packets transmitted"
        ::= { wfX25PadPortStatEntry 13 }

   wfX25PadPortStatRxRNR OBJECT-TYPE
        SYNTAX  Counter
        ACCESS  read-only
        STATUS  mandatory
        DESCRIPTION
                "Number of receiver not ready packets received"
        ::= { wfX25PadPortStatEntry 14 }

   wfX25PadPortStatTxRNR OBJECT-TYPE
        SYNTAX  Counter
        ACCESS  read-only
        STATUS  mandatory
        DESCRIPTION
                "Number of receiver not ready packets transmitted"
        ::= { wfX25PadPortStatEntry 15 }

   wfX25PadPortStatRxClr OBJECT-TYPE
        SYNTAX  Counter
        ACCESS  read-only
        STATUS  mandatory
        DESCRIPTION
                "Number of call clear packets received"
        ::= { wfX25PadPortStatEntry 16 }

   wfX25PadPortStatTxClr OBJECT-TYPE
        SYNTAX  Counter
        ACCESS  read-only
        STATUS  mandatory
        DESCRIPTION
                "Number of call clear packets transmitted"
        ::= { wfX25PadPortStatEntry 17 }

   wfX25PadPortStatRxReset OBJECT-TYPE
        SYNTAX  Counter
        ACCESS  read-only
        STATUS  mandatory
        DESCRIPTION
                "Number of reset packets received"
        ::= { wfX25PadPortStatEntry 18 }

   wfX25PadPortStatTxReset OBJECT-TYPE
        SYNTAX  Counter
        ACCESS  read-only
        STATUS  mandatory
        DESCRIPTION
                "Number of reset packets transmitted"
        ::= { wfX25PadPortStatEntry 19 }

   wfX25PadPortStatRxCall OBJECT-TYPE
        SYNTAX  Counter
        ACCESS  read-only
        STATUS  mandatory
        DESCRIPTION
                "Number of call request packets received"
        ::= { wfX25PadPortStatEntry 20 }

   wfX25PadPortStatTxCall OBJECT-TYPE
        SYNTAX  Counter
        ACCESS  read-only
        STATUS  mandatory
        DESCRIPTION
                "Number of call request packets transmitted"
        ::= { wfX25PadPortStatEntry 21 }

   wfX25PadPortStatConnections OBJECT-TYPE
        SYNTAX  Counter
        ACCESS  read-only
        STATUS  mandatory
        DESCRIPTION
                "Number of connections made"
        ::= { wfX25PadPortStatEntry 22 }

   wfX25PadPortStatDisconnects OBJECT-TYPE
        SYNTAX  Counter
        ACCESS  read-only
        STATUS  mandatory
        DESCRIPTION
                "Number of disconnects made"
        ::= { wfX25PadPortStatEntry 23 }

   wfX25PadPortStatLastCause OBJECT-TYPE
        SYNTAX  INTEGER
        ACCESS  read-only
        STATUS  mandatory
        DESCRIPTION
                "Last cause code"
        ::= { wfX25PadPortStatEntry 24 }

   wfX25PadPortStatLastDiag OBJECT-TYPE
        SYNTAX  INTEGER
        ACCESS  read-only
        STATUS  mandatory
        DESCRIPTION
                "Last diag code"
        ::= { wfX25PadPortStatEntry 25 }

END  -- Wellfleet-X25PAD-MIB
