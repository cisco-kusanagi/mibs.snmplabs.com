MLB-MIB DEFINITIONS ::= BEGIN

-- Title:      RADWARE
--             This Private MIB supports the Vgate
-- Version:    2.9
-- Date:       27 Oct 1995
-- By:         Rina Nethaniel.
-- E-mail:         rina@rnd-gate.rad.co.il
--
IMPORTS
       IpAddress,
       Counter
              FROM RFC1155-SMI
      OBJECT-TYPE
              FROM RFC-1212
       DisplayString
              FROM RFC1213-MIB
       rsMLB
                    FROM RADWARE-MIB;

-- Some MIB compilers require that the following 7 lines which define the path
-- to RND MIB are commented out:

-- mib            OBJECT IDENTIFIER ::= { mgmt 1  }
-- directory      OBJECT IDENTIFIER ::= { internet 1  }
-- experimental   OBJECT IDENTIFIER ::= { internet 3  }
-- private        OBJECT IDENTIFIER ::= { internet 4  }
-- enterprises    OBJECT IDENTIFIER ::= { private 1  }

rsMLBApplicationServersTable OBJECT-TYPE
    SYNTAX SEQUENCE OF RsMLBApplicationServerEntry
    ACCESS not-accessible
    STATUS mandatory
    DESCRIPTION
      "Table containing the list of application servers to which the
      clients requested are dispatched."
    ::=  { rsMLB 1}

rsMLBApplicationServerEntry OBJECT-TYPE
    SYNTAX RsMLBApplicationServerEntry
    ACCESS not-accessible
    STATUS  mandatory
    DESCRIPTION
       " The row definition for this table."
   INDEX { rsMLBServerAddr }
    ::=  {rsMLBApplicationServersTable 1}

RsMLBApplicationServerEntry ::= SEQUENCE {
  rsMLBServerAddr                IpAddress,
  rsMLBServerName                DisplayString,
  rsMLBServerOperStatus          INTEGER,
  rsMLBServerWeight              INTEGER,
  rsMLBServerAttachedUsersNumber INTEGER,
  rsMLBServerPeakLoad            INTEGER,
  rsMLBServerFramesRate          INTEGER,
  rsMLBServerFramesLoad          Counter,
  rsMLBServerStatus              INTEGER,
  rsMLBServerOperMode            INTEGER,
  rsMLBServerConnectionLimit     INTEGER,
  rsMLBServerAdminStatus         INTEGER,
  rsMLBServerType                INTEGER,
  rsMLBServerMacStatus	     	 INTEGER,
  rsMLBServerPortNumber		     INTEGER,
  rsMLBServerPeakBytesLoad       INTEGER,
  rsMLBServerBytesRate           INTEGER,
  rsMLBServerBytesLoad           Counter,
  rsMLBServerRecoveryTime        INTEGER,
  rsMLBServerWarmUpTime          INTEGER,
  rsMLBServerTotalFramesLoad     Counter,
  rsMLBServerProximityCheck      INTEGER
  }

rsMLBServerAddr  OBJECT-TYPE
    SYNTAX  IpAddress
    ACCESS  read-only
    STATUS  mandatory
    DESCRIPTION
     "Application  IP address"
 ::=  {rsMLBApplicationServerEntry 1 }

rsMLBServerName  OBJECT-TYPE
    SYNTAX DisplayString (SIZE(1..20))
    ACCESS  read-write
    STATUS  mandatory
    DESCRIPTION
      "The name assigned by the user to the server."
 ::=  {rsMLBApplicationServerEntry 2}

rsMLBServerOperStatus OBJECT-TYPE
    SYNTAX INTEGER {
      active(1),
      notInService(2),
      noNewSessions(3)
    }
    ACCESS  read-only
    STATUS  mandatory
    DESCRIPTION
      "Operational status of application on  server.
       active        - server is active
       notInService  - server is or will become inactive. Existing sessions
                       will be redirected to other servers.
       noNewSessions - server will receive no new sessions. Existing sessions
                       are allowed to complete."
 ::=  {rsMLBApplicationServerEntry 3 }

rsMLBServerWeight OBJECT-TYPE
    SYNTAX  INTEGER  (1..10)
    ACCESS  read-write
    STATUS  mandatory
    DESCRIPTION
      "A numerical weight assigned by the user in order to impose some
       priority mechanism on the server dispatchers considerations of which
       server to choose for attaching a client ."
 ::=  {rsMLBApplicationServerEntry 4}

rsMLBServerAttachedUsersNumber OBJECT-TYPE
    SYNTAX  INTEGER
    ACCESS  read-only
    STATUS  mandatory
    DESCRIPTION
      "Number of currently active users attached to this server."
    ::=  {rsMLBApplicationServerEntry 5 }

rsMLBServerPeakLoad OBJECT-TYPE
    SYNTAX  INTEGER
    ACCESS  read-only
    STATUS  mandatory
    DESCRIPTION
      "Maximal number of frames per second dispatched to server
       since last reset."
    ::=  {rsMLBApplicationServerEntry 6}

rsMLBServerFramesRate OBJECT-TYPE
    SYNTAX  INTEGER
    ACCESS  read-only
    STATUS  mandatory
    DESCRIPTION
      "Number of frames per second dispatched to server."
    ::=  {rsMLBApplicationServerEntry 7}

rsMLBServerFramesLoad OBJECT-TYPE
    SYNTAX  Counter
    ACCESS  read-only
    STATUS  mandatory
    DESCRIPTION
      "Number of frames per second dispatched to server."
    ::=  {rsMLBApplicationServerEntry 8}

rsMLBServerStatus OBJECT-TYPE
    SYNTAX INTEGER {
        active(1),
        notInService(2),
        notReady(3),
        createAndGo(4),
        createAndWait(5),
        destroy(6) }
    ACCESS  read-write
    STATUS  mandatory
    DESCRIPTION
      "Administative status of appliaction on  server."
    ::=  {rsMLBApplicationServerEntry 9}

rsMLBServerOperMode OBJECT-TYPE
    SYNTAX INTEGER { regular(1), backup(2) }
    ACCESS  read-write
    STATUS  mandatory
    DESCRIPTION
      "This variable indicate the status of the server,
      the MLB will not send any messages to a backup server
      unless all other server are down  status.
      In case of more then one backup server, the MLB will decide  to which
      backup server to send the massages acordinf to rsMLBWeight."
    ::=  { rsMLBApplicationServerEntry 10}

rsMLBServerConnectionLimit OBJECT-TYPE
    SYNTAX INTEGER
    ACCESS  read-write
    STATUS  mandatory
    DESCRIPTION
      "The maximal number of client sessions which can be opened on this sever."
-- DEFVAL {0}
    ::= { rsMLBApplicationServerEntry 11 }

rsMLBServerAdminStatus OBJECT-TYPE
    SYNTAX INTEGER {
      enable(1),
      disable(2),
      shutdown(3)
          }
    ACCESS  read-write
    STATUS  mandatory
    DESCRIPTION
      "Administrative status of application on server.
       enable -   activates the server.
                  The rsMLBServerOperStatus will change to active.
       disable -  stops the server.
                  The rsMLBServerOperStatus will change to notInService.
       shutdown - gracefully shuts down the server.
                  The rsMLBServerOperStatus will change to noNewSessions."

 ::=  {rsMLBApplicationServerEntry 12 }

rsMLBServerType OBJECT-TYPE
    SYNTAX INTEGER {
      regular(1),
      nextHopRouter(2)
    }
    ACCESS  read-only
    STATUS  mandatory
    DESCRIPTION
      "The type of Firewall.
       regular -   indicates that the firewall is a regular server.
       nextHopRouter - the Firewall is a next hop in the router table."

--  DEFVAL  { 1 }
 ::=  {rsMLBApplicationServerEntry 13 }

rsMLBServerMacStatus OBJECT-TYPE
    SYNTAX INTEGER {
      found(1),
      notFound(2)
    }
    ACCESS  read-only
    STATUS  mandatory
    DESCRIPTION
      "Indicates if the Mac address of the server was obtained. THe mac
       address is retrieve either from the Arp table or by sending Arp request.
       found - mac address was found
       notFound - mac address was not found "

--  DEFVAL  { 2 }
 ::=  {rsMLBApplicationServerEntry 14 }

rsMLBServerPortNumber OBJECT-TYPE
    SYNTAX  INTEGER
    ACCESS  read-only
    STATUS  mandatory
    DESCRIPTION
      "The FireProof port this server is connected to"
    ::=  {rsMLBApplicationServerEntry 15 }

rsMLBServerPeakBytesLoad OBJECT-TYPE
    SYNTAX  INTEGER
    ACCESS  read-only
    STATUS  mandatory
    DESCRIPTION
      "Maximal number of bytes per second dispatched to server
       since last reset."
    ::=  {rsMLBApplicationServerEntry 16}

rsMLBServerBytesRate OBJECT-TYPE
    SYNTAX  INTEGER
    ACCESS  read-only
    STATUS  mandatory
    DESCRIPTION
      "Number of bytes per second dispatched to server."
    ::=  {rsMLBApplicationServerEntry 17}

rsMLBServerBytesLoad OBJECT-TYPE
    SYNTAX  Counter
    ACCESS  read-only
    STATUS  mandatory
    DESCRIPTION
      "Number of bytes per second dispatched to server."
    ::=  {rsMLBApplicationServerEntry 18}

rsMLBServerRecoveryTime OBJECT-TYPE
    SYNTAX INTEGER
    ACCESS  read-write
    STATUS  mandatory
    DESCRIPTION
      "Number of seconds after server initialization during which ISD won't
       send any requests."
   ::= {rsMLBApplicationServerEntry 19}

rsMLBServerWarmUpTime OBJECT-TYPE
    SYNTAX INTEGER
    ACCESS  read-write
    STATUS  mandatory
    DESCRIPTION
      "Number of seconds after server recovery during which the server will get
       less requests than permitted by his weight and load."
   ::= {rsMLBApplicationServerEntry 20}

rsMLBServerTotalFramesLoad OBJECT-TYPE
    SYNTAX  Counter
    ACCESS  read-only
    STATUS  mandatory
    DESCRIPTION
      "Total number of frames dispatched to server."
    ::=  {rsMLBApplicationServerEntry 21}


rsMLBServerProximityCheck OBJECT-TYPE
    SYNTAX INTEGER {
      enable(1),
      disable(2)
          }
    ACCESS  read-write
    STATUS  mandatory
    DESCRIPTION
      "Enable\Disable proximity check through this router."
-- DEFVAL { 1 }
 ::=  {rsMLBApplicationServerEntry 22 }

rsMLBdummy1 OBJECT-TYPE
    SYNTAX INTEGER
    ACCESS  read-only
    STATUS  mandatory
    DESCRIPTION
       " Dummy variable for stopping getnext."
    ::=  {rsMLBApplicationServersTable 2}


rsMLBAdminStatus  OBJECT-TYPE
    SYNTAX INTEGER {
      enable(1),
      disable(2)
   }
    ACCESS  read-write
    STATUS  mandatory
    DESCRIPTION
      "Enable/Disable server dispatcher."
    ::=  {rsMLB 2}

rsMLBClientsLifeTime OBJECT-TYPE
    SYNTAX  INTEGER
    ACCESS  read-write
    STATUS  mandatory
    DESCRIPTION
      "Maximal period of time in seconds a non-active client is kept
      in the clients table."
--  DEFVAL  { 60 }
    ::=  {rsMLB 3}

  rsMLBDispatchMethod OBJECT-TYPE
    SYNTAX INTEGER {
      cyclic(1),
      leastTraffic(2),
      leastUsersNumber(3),
      nt-1(4),
      nt-2(5),
      private-1(6),
      private-2(7),
      leastBytesNumber(8)
   }
    ACCESS  read-write
    STATUS  mandatory
    DESCRIPTION
      "Type of dispatching required."
    ::=  {rsMLB 4}

  rsMLBCheckConnectivityStatus OBJECT-TYPE
    SYNTAX INTEGER {
      enable(1),
      disable(2)
   }
    ACCESS  read-write
    STATUS  mandatory
    DESCRIPTION
      "Enable or Disable servers polling."
--  DEFVAL  { enable }
    ::=  {rsMLB 5}

  rsMLBCheckConnectivityMethod OBJECT-TYPE
    SYNTAX INTEGER
    ACCESS  read-write
    STATUS  mandatory
    DESCRIPTION
       "This variable indicate the method the MLB check the connectivity.
        where the value 1 means check connectiotivity by ping, other value serve
        as a tcp port number."
    ::=  {rsMLB 6}

  rsMLBCheckConnectivityInterval OBJECT-TYPE
    SYNTAX  INTEGER  (1..3600)
    ACCESS  read-write
    STATUS  mandatory
    DESCRIPTION
      "Polling interval in seconds for servers polling."
--  DEFVAL  { 10 }
    ::=  {rsMLB 7}

  rsMLBCheckConnectivityRetries OBJECT-TYPE
    SYNTAX  INTEGER  (1..20)
    ACCESS  read-write
    STATUS  mandatory
    DESCRIPTION
      "This variable indicate the Minimal number of unsuccessful polling
       attempts before considering a server disconnected."
--  DEFVAL  { 5 }
    ::=  {rsMLB 8}

  rsMLBClientsConnectDenials OBJECT-TYPE
    SYNTAX Counter
    ACCESS  read-only
    STATUS  mandatory
    DESCRIPTION
      "This variable indicate the Number of connection requests from clients
       that were denied by the the server dispatcher."
    ::=  {rsMLB 9}

rsMLBClientsTable OBJECT-TYPE
    SYNTAX SEQUENCE OF RsMLBClientEntry
    ACCESS not-accessible
    STATUS  mandatory
    DESCRIPTION
      "Table containing the list of clients currently attached to a server."
    ::=  {rsMLB 10}

rsMLBClientEntry OBJECT-TYPE
    SYNTAX RsMLBClientEntry
    ACCESS not-accessible
    STATUS  mandatory
    DESCRIPTION
       " The row definition for this table."
   INDEX { rsMLBClientAddr,
           rsMLBDestinationAddr }
    ::=  {rsMLBClientsTable 1}

RsMLBClientEntry ::= SEQUENCE {
  rsMLBClientAddr                IpAddress,
  rsMLBDestinationAddr           IpAddress,
  rsMLBAttachedServerAddr        IpAddress,
  rsMLBClientLastActivityTime    INTEGER,
  rsMLBClientAttachmentTime      INTEGER,
  rsMLBClientStatus              INTEGER
  }

rsMLBClientAddr  OBJECT-TYPE
    SYNTAX  IpAddress
    ACCESS  read-only
    STATUS  mandatory
    DESCRIPTION
      "Client IP Address."
    ::=  {rsMLBClientEntry 1}

rsMLBDestinationAddr OBJECT-TYPE
    SYNTAX  IpAddress
    ACCESS  read-write
    STATUS  mandatory
    DESCRIPTION
      "IP Address of server currently serving this client."
    ::=  {rsMLBClientEntry 2 }

rsMLBAttachedServerAddr OBJECT-TYPE
    SYNTAX  IpAddress
    ACCESS  read-write
    STATUS  mandatory
    DESCRIPTION
      "IP Address of server currently serving this client."
    ::=  {rsMLBClientEntry 3 }


rsMLBClientLastActivityTime  OBJECT-TYPE
    SYNTAX  INTEGER
    ACCESS  read-only
    STATUS  mandatory
    DESCRIPTION
      "Indicates when the last frame from the client was dispatched.
       Measured in seconds since device re-initialization."
    ::=  {rsMLBClientEntry 4}

rsMLBClientAttachmentTime OBJECT-TYPE
    SYNTAX  INTEGER
    ACCESS  read-only
    STATUS  mandatory
    DESCRIPTION
      "Indicates when the client was attached.
       Measured in seconds since device re-initialization."
    ::=  {rsMLBClientEntry 5}

rsMLBClientStatus OBJECT-TYPE
    SYNTAX INTEGER {
                    active(1),
                    notInService(2),
                    notReady(3),
                    createAndGo(4),
                    createAndWait(5),
                    destroy(6)
                   }
    ACCESS  read-write
    STATUS  mandatory
    DESCRIPTION
       "This variable indicates the administrative status of this entry.
        Used to delete an entry of this table."
    ::=  { rsMLBClientEntry 6}

rsMLBdummy2 OBJECT-TYPE
    SYNTAX INTEGER
    ACCESS  read-only
    STATUS  mandatory
    DESCRIPTION
       " Dummy variable for stopping getnext."
    ::=  {rsMLBClientsTable 2}

  rsMLBSessionTracking OBJECT-TYPE
    SYNTAX INTEGER {
      enable(1),
      disable(2)
   }
    ACCESS  read-write
    STATUS  mandatory
    DESCRIPTION
      "Enable or Disable session tracking. Usually, when working with Firewall
	we need to send the whole traffic of a specific session through the same Firewall.
	For this purpose we should keep track of the session and use the enable option.
	When working with routers, sending the whole traffic through the same Firewall
	is not necessary. Therefor there is no need to keep track of the sessions and
	we can use the disable option."
--  DEFVAL  { enable }
    ::=  {rsMLB 11}


rsMLBRemoteConnectivityTable OBJECT-TYPE
    SYNTAX SEQUENCE OF RsMLBRemoteConnectivityEntry
    ACCESS not-accessible
    STATUS mandatory
    DESCRIPTION
      "Table containing the list of IPs which the connectivity check is performed on them."
    ::=  { rsMLB 12}

rsMLBRemoteConnectivityEntry OBJECT-TYPE
    SYNTAX RsMLBRemoteConnectivityEntry
    ACCESS not-accessible
    STATUS  mandatory
    DESCRIPTION
       " The row definition for this table."
   INDEX {rsMLBRmtConSrvrAddr,
           rsMLBRmtConIpAddr }
    ::=  {rsMLBRemoteConnectivityTable 1}


RsMLBRemoteConnectivityEntry ::= SEQUENCE {
  rsMLBRmtConSrvrAddr            IpAddress,
  rsMLBRmtConIpAddr              IpAddress,
  rsMLBRmtConStatus              INTEGER,
  rsMLBRmtConOperStatus		 INTEGER

  }

rsMLBRmtConSrvrAddr  OBJECT-TYPE
    SYNTAX  IpAddress
    ACCESS  read-only
    STATUS  mandatory
    DESCRIPTION
     "Server  IP address"
 ::=  {rsMLBRemoteConnectivityEntry 1 }

rsMLBRmtConIpAddr  OBJECT-TYPE
    SYNTAX  IpAddress
    ACCESS  read-only
    STATUS  mandatory
    DESCRIPTION
     "The IP address that the connectivity check will be performed on."
 ::=  {rsMLBRemoteConnectivityEntry 2 }

rsMLBRmtConStatus  OBJECT-TYPE
    SYNTAX INTEGER {
        active(1),
        notInService(2),
        notReady(3),
        createAndGo(4),
        createAndWait(5),
        destroy(6) }
    ACCESS  read-write
    STATUS  mandatory
    DESCRIPTION
      "Administative status of appliaction on the concection check IP address."
 ::=  {rsMLBRemoteConnectivityEntry 3 }


rsMLBRmtConOperStatus OBJECT-TYPE
	SYNTAX  INTEGER{
		active(1),
		notInService(2)
	}
	ACCESS read-only
	STATUS mandatory
	DESCRIPTION
	"Hold the operational status of the checked IP address."
	DEFVAL {1}
::= {rsMLBRemoteConnectivityEntry 4}


rsMLBdummy3 OBJECT-TYPE
    SYNTAX INTEGER
    ACCESS  read-only
    STATUS  mandatory
    DESCRIPTION
       " Dummy variable for stopping getnext."
    ::=  {rsMLBRemoteConnectivityTable 2}



  rsMLBClientTableMode OBJECT-TYPE
    SYNTAX INTEGER {
      layer3(1),
      layer4(2)
   }
    ACCESS  read-write
    STATUS  mandatory
    DESCRIPTION
      "Determine the mode of keep entries in the client table.
       layer 3 means that entries are kept according to source Ip and destination IP
       layer 4 means that entries are kept according to source Ip, destination IP and ports"
--  DEFVAL  { Layer3 }
    ::=  {rsMLB 13}


rsMLBRulesTable OBJECT-TYPE
    SYNTAX SEQUENCE OF RsMLBRulesEntry
    ACCESS not-accessible
    STATUS mandatory
    DESCRIPTION
      "Table containing the list of "
    ::=  { rsMLB 14}

rsMLBRulesEntry OBJECT-TYPE
    SYNTAX RsMLBRulesEntry
    ACCESS not-accessible
    STATUS  mandatory
    DESCRIPTION
       " The row definition for this table."
   INDEX {rsMLBRulesPortNumber }
    ::=  {rsMLBRulesTable 1}


RsMLBRulesEntry ::= SEQUENCE {
    rsMLBRulesPortNumber    INTEGER,
    rsMLBRulesLeavingPort     INTEGER,
    rsMLBRulesNumOfServers    INTEGER
    }

rsMLBRulesPortNumber OBJECT-TYPE
    SYNTAX  INTEGER
    ACCESS  read-only
    STATUS  mandatory
    DESCRIPTION
      ""
    ::= {rsMLBRulesEntry 1}

rsMLBRulesLeavingPort  OBJECT-TYPE
    SYNTAX  INTEGER
    ACCESS  read-write
    STATUS  mandatory
    DESCRIPTION
      ""
    ::= {rsMLBRulesEntry 2}

rsMLBRulesNumOfServers    OBJECT-TYPE
    SYNTAX  INTEGER
    ACCESS  read-only
    STATUS  mandatory
    DESCRIPTION
      ""
    ::= {rsMLBRulesEntry 3}

rsMLBdummy4 OBJECT-TYPE
    SYNTAX INTEGER
    ACCESS  read-only
    STATUS  mandatory
    DESCRIPTION
       " Dummy variable for stopping getnext."
    ::=  {rsMLBRulesTable 2}

rsMLBTranslateOutBoundMode OBJECT-TYPE
    SYNTAX INTEGER {
        enable(1),
        disable(2)
    }
    ACCESS  read-write
    STATUS  mandatory
    DESCRIPTION "Translate FW NAT IP address to a virtual IP address
		for traffic that originated inside"
--  DEFVAL  { disable }
    ::= {rsMLB 15}

rsMLBVirtualIPTable OBJECT-TYPE
    SYNTAX SEQUENCE OF RsMLBVirtualIPEntry
    ACCESS not-accessible
    STATUS mandatory
    DESCRIPTION "The table for storing the VIP's"
    ::= {rsMLB 16}

rsMLBVirtualIPEntry OBJECT-TYPE
    SYNTAX RsMLBVirtualIPEntry
    ACCESS not-accessible
    STATUS mandatory
    DESCRIPTION "The row definition for the VIP table"
    INDEX {rsMLBVirtualIPAddress}
    ::= {rsMLBVirtualIPTable 1}

RsMLBVirtualIPEntry ::= SEQUENCE {
    rsMLBVirtualIPAddress IpAddress,
    rsMLBVirtualMode INTEGER,
    rsMLBVirtualStatus INTEGER
}

rsMLBVirtualIPAddress OBJECT-TYPE
    SYNTAX IpAddress
    ACCESS read-only
    STATUS mandatory
    DESCRIPTION "The Virtual IP entry"
    ::= {rsMLBVirtualIPEntry 1}

rsMLBVirtualMode OBJECT-TYPE
    SYNTAX INTEGER {
           regular(1),
           backup(2)
    }
    ACCESS  read-write
    STATUS  mandatory
    DESCRIPTION
        "The virtual IP mode - either backup/regular"
--  DEFVAL { 1 }
    ::= {rsMLBVirtualIPEntry 2}

rsMLBVirtualStatus OBJECT-TYPE
    SYNTAX INTEGER {
              active(1),
              notInService(2),
              notReady(3),
              createAndGo(4),
              createAndWait(5),
              destroy(6) }
    ACCESS read-write
    STATUS mandatory
    DESCRIPTION
       "This variable indicates the administrative status of this entry."
    ::=  {rsMLBVirtualIPEntry 3}

rsMLBdummy5 OBJECT-TYPE
    SYNTAX INTEGER
    ACCESS  read-only
    STATUS  mandatory
    DESCRIPTION "Dummy variable for stopping getnext."
    ::= {rsMLBVirtualIPTable 2}

rsMLBMappedIPTable OBJECT-TYPE
    SYNTAX SEQUENCE OF RsMLBMappedIPEntry
    ACCESS not-accessible
    STATUS mandatory
    DESCRIPTION "The table for storing the mapped VIP entries"
    ::= {rsMLB 17}

rsMLBMappedIPEntry OBJECT-TYPE
    SYNTAX RsMLBMappedIPEntry
    ACCESS not-accessible
    STATUS mandatory
    DESCRIPTION "The row definition for the mapped table"
    INDEX {rsMLBMappedVirtualAddress, rsMLBMappedFirewallIP}
    ::= {rsMLBMappedIPTable 1}

RsMLBMappedIPEntry ::= SEQUENCE {
    rsMLBMappedVirtualAddress IpAddress,
    rsMLBMappedFirewallIP IpAddress,
    rsMLBMappedFirewallNAT IpAddress,
    rsMLBMappedStatus INTEGER
}

rsMLBMappedVirtualAddress OBJECT-TYPE
    SYNTAX IpAddress
    ACCESS read-only
    STATUS mandatory
    DESCRIPTION "The Virtual IP entry"
    ::= {rsMLBMappedIPEntry 1}

rsMLBMappedFirewallIP OBJECT-TYPE
    SYNTAX IpAddress
    ACCESS read-only
    STATUS mandatory
    DESCRIPTION "The firewall IP address"
    ::= {rsMLBMappedIPEntry 2}

rsMLBMappedFirewallNAT OBJECT-TYPE
    SYNTAX IpAddress
    ACCESS read-write
    STATUS mandatory
    DESCRIPTION "The firewall NAT IP address"
    ::= {rsMLBMappedIPEntry 3}

rsMLBMappedStatus OBJECT-TYPE
    SYNTAX INTEGER {
              active(1),
              notInService(2),
              notReady(3),
              createAndGo(4),
              createAndWait(5),
              destroy(6) }
    ACCESS read-write
    STATUS mandatory
    DESCRIPTION
       "This variable indicates the administrative status of this entry."
    ::=  {rsMLBMappedIPEntry 4}

rsMLBdummy6 OBJECT-TYPE
    SYNTAX INTEGER
    ACCESS  read-only
    STATUS  mandatory
    DESCRIPTION "Dummy variable for stopping getnext."
    ::= {rsMLBMappedIPTable 2}



rsMLBVirtualConnectivityIP OBJECT-TYPE
    SYNTAX IpAddress
    ACCESS read-write
    STATUS mandatory
    DESCRIPTION "The virtual connectivity IP address"
    ::= {rsMLB 18}

rsMLBVirtualConnectivityMode OBJECT-TYPE
    SYNTAX INTEGER {
           regular(1),
           backup(2)
    }
    ACCESS  read-write
    STATUS  mandatory
    DESCRIPTION
        "The virtual IP mode - either backup/regular"
--  DEFVAL { 1 }
    ::= {rsMLB 19}

rsMLBRemoveEntryAtSessionEnd OBJECT-TYPE
    SYNTAX INTEGER {
      enable(1),
      disable(2)
   }
    ACCESS  read-write
    STATUS  mandatory
    DESCRIPTION
      "Remove client entry at session end."
-- DEFVAL  { disable }
    ::= {rsMLB 20}

rsMLBFirewallPortID OBJECT-TYPE
    SYNTAX INTEGER {
      enable(1),
      disable(2)
   }
    ACCESS read-write
    STATUS mandatory
    DESCRIPTION "Identify Firewall not only by Mac but also by port"
    ::= {rsMLB 21}


rsMLBSubnetGroupTable OBJECT-TYPE
    SYNTAX SEQUENCE OF RsMLBSubnetGroupEntry
    ACCESS not-accessible
    STATUS mandatory
    DESCRIPTION
    "Table containing the list of FW which belong to a particular destination subnet   group."
    ::=  { rsMLB 23}

rsMLBSubnetGroupEntry OBJECT-TYPE
    SYNTAX RsMLBSubnetGroupEntry
    ACCESS not-accessible
    STATUS  mandatory
    DESCRIPTION
       " The row definition for this table."
   INDEX {rsMLBDestSubnetAddr,
	  rsMLBDestSubnetMask,
          rsMLBSubnetSrvrAddr}
    ::=  {rsMLBSubnetGroupTable 1}

RsMLBSubnetGroupEntry ::= SEQUENCE {
  rsMLBDestSubnetAddr            	 IpAddress,
  rsMLBDestSubnetMask            	 IpAddress,
  rsMLBSubnetSrvrAddr                    IpAddress,
  rsMLBSubnetSrvrStatus                  INTEGER,
  rsMLBSubnetSrvrOperMode	         INTEGER
  }

rsMLBDestSubnetAddr  OBJECT-TYPE
    SYNTAX  IpAddress
    ACCESS  read-only
    STATUS  mandatory
    DESCRIPTION
     "Destination subnet address"
 ::=  {rsMLBSubnetGroupEntry 1 }

rsMLBDestSubnetMask OBJECT-TYPE
    SYNTAX  IpAddress
    ACCESS  read-only
    STATUS  mandatory
    DESCRIPTION
     "Destination subnet mask."
 ::=  {rsMLBSubnetGroupEntry 2 }

rsMLBSubnetSrvrAddr OBJECT-TYPE
    SYNTAX  IpAddress
    ACCESS  read-only
    STATUS  mandatory
    DESCRIPTION
     "The IP address of the server that belong to the destination subnet group."
 ::=  {rsMLBSubnetGroupEntry 3 }

rsMLBSubnetSrvrStatus  OBJECT-TYPE
    SYNTAX INTEGER {
        active(1),
        notInService(2),
        notReady(3),
        createAndGo(4),
        createAndWait(5),
        destroy(6) }
    ACCESS  read-write
    STATUS  mandatory
    DESCRIPTION
      "Administrative status of the server."
 ::=  {rsMLBSubnetGroupEntry 4 }

rsMLBSubnetSrvrOperMode  OBJECT-TYPE
    SYNTAX INTEGER { regular(1), backup(2) }
    ACCESS  read-write
    STATUS  mandatory
    DESCRIPTION
     "define the operational mode (regular or backup) of the server in the subnet group"
 ::=  {rsMLBSubnetGroupEntry 5 }


rsMLBdummy8 OBJECT-TYPE
    SYNTAX INTEGER
    ACCESS  read-only
    STATUS  mandatory
    DESCRIPTION
       " Dummy variable for stopping getnext."
    ::=  { rsMLBSubnetGroupTable 2}


rsMLBApplicationPortGroupTable OBJECT-TYPE
    SYNTAX SEQUENCE OF RsMLBApplPortGroupEntry
    ACCESS not-accessible
    STATUS mandatory
    DESCRIPTION
    "Table containing the list of FW which belong to a particular application port group."
    ::=  { rsMLB 24}

rsMLBApplPortGroupEntry OBJECT-TYPE
    SYNTAX RsMLBApplPortGroupEntry
    ACCESS not-accessible
    STATUS  mandatory
    DESCRIPTION
       " The row definition for this table."
   INDEX {rsMLBApplPort,
      rsMLBApplPortSrvrAddr}
    ::=  {rsMLBApplicationPortGroupTable 1}


RsMLBApplPortGroupEntry ::= SEQUENCE {
  rsMLBApplPort            		    INTEGER,
  rsMLBApplPortSrvrAddr                    IpAddress,
  rsMLBApplPortSrvrStatus                  INTEGER,
  rsMLBApplPortSrvrOperMode		   INTEGER
  }

rsMLBApplPort  OBJECT-TYPE
    SYNTAX INTEGER
    ACCESS  read-only
    STATUS  mandatory
    DESCRIPTION
     "The application port of the group"
 ::=  {rsMLBApplPortGroupEntry 1 }

rsMLBApplPortSrvrAddr OBJECT-TYPE
    SYNTAX  IpAddress
    ACCESS  read-only
    STATUS  mandatory
    DESCRIPTION
     "The IP address of the server that belong to the application port group."
 ::=  {rsMLBApplPortGroupEntry 2 }

rsMLBApplPortSrvrStatus  OBJECT-TYPE
    SYNTAX INTEGER {
        active(1),
        notInService(2),
        notReady(3),
        createAndGo(4),
        createAndWait(5),
        destroy(6) }
    ACCESS  read-write
    STATUS  mandatory
    DESCRIPTION
      "Administrative status of the server."
 ::=  {rsMLBApplPortGroupEntry 3 }

rsMLBApplPortSrvrOperMode  OBJECT-TYPE
    SYNTAX INTEGER { regular(1), backup(2) }
    ACCESS  read-write
    STATUS  mandatory
    DESCRIPTION
     "define the operational mode (regular or backup) of the server in the subnet group."
 ::=  {rsMLBApplPortGroupEntry 4 }


rsMLBdummy9 OBJECT-TYPE
    SYNTAX INTEGER
    ACCESS  read-only
    STATUS  mandatory
    DESCRIPTION
       " Dummy variable for stopping getnext."
    ::=  { rsMLBApplicationPortGroupTable 2}


rsMLBSrcSbntGroupTable OBJECT-TYPE
    SYNTAX SEQUENCE OF RsMLBSrcSbntGroupEntry
    ACCESS not-accessible
    STATUS mandatory
    DESCRIPTION
    "Table containing the list of FW which belong to a particular source subnet group."
    ::=  { rsMLB 25}

rsMLBSrcSbntGroupEntry OBJECT-TYPE
    SYNTAX RsMLBSrcSbntGroupEntry
    ACCESS not-accessible
    STATUS  mandatory
    DESCRIPTION
       " The row definition for this table."
   INDEX {rsMLBSrcSbntAddr,
  	  rsMLBSrcSbntMask,
          rsMLBSrcSbntSrvrAddr}
    ::=  {rsMLBSrcSbntGroupTable 1}

RsMLBSrcSbntGroupEntry ::= SEQUENCE {
  rsMLBSrcSbntAddr            	IpAddress,
  rsMLBSrcSbntMask            	IpAddress,
  rsMLBSrcSbntSrvrAddr          IpAddress,
  rsMLBSrcSbntSrvrStatus        INTEGER,
  rsMLBSrcSbntSrvrOperMode	INTEGER
  }

rsMLBSrcSbntAddr  OBJECT-TYPE
    SYNTAX  IpAddress
    ACCESS  read-only
    STATUS  mandatory
    DESCRIPTION
     "Source subnet address"
 ::=  {rsMLBSrcSbntGroupEntry 1 }

rsMLBSrcSbntMask OBJECT-TYPE
    SYNTAX  IpAddress
    ACCESS  read-only
    STATUS  mandatory
    DESCRIPTION
     "source subnet mask."
 ::=  {rsMLBSrcSbntGroupEntry 2 }

rsMLBSrcSbntSrvrAddr OBJECT-TYPE
    SYNTAX  IpAddress
    ACCESS  read-only
    STATUS  mandatory
    DESCRIPTION
     "The IP address of the server that belong to the source subnet group."
 ::=  {rsMLBSrcSbntGroupEntry 3 }

rsMLBSrcSbntSrvrStatus  OBJECT-TYPE
    SYNTAX INTEGER {
        active(1),
        notInService(2),
        notReady(3),
        createAndGo(4),
        createAndWait(5),
        destroy(6) }
    ACCESS  read-write
    STATUS  mandatory
    DESCRIPTION
      "Administrative status of the server."
 ::=  {rsMLBSrcSbntGroupEntry 4 }

rsMLBSrcSbntSrvrOperMode  OBJECT-TYPE
    SYNTAX INTEGER { regular(1), backup(2) }
    ACCESS  read-write
    STATUS  mandatory
    DESCRIPTION
     "define the operational mode (regular or backup) of the server in the source subnet group"
 ::=  {rsMLBSrcSbntGroupEntry 5 }


rsMLBdummy10 OBJECT-TYPE
    SYNTAX INTEGER
    ACCESS  read-only
    STATUS  mandatory
    DESCRIPTION
       " Dummy variable for stopping getnext."
    ::=  { rsMLBSrcSbntGroupTable 2}



rsMLBNatTable OBJECT-TYPE
    SYNTAX SEQUENCE OF RsMLBNatEntry
    ACCESS not-accessible
    STATUS mandatory
    DESCRIPTION
       "In this table the FP saves the NAT addresses."
    ::= {rsMLB 26}

rsMLBNatEntry OBJECT-TYPE
    SYNTAX RsMLBNatEntry
    ACCESS not-accessible
    STATUS  mandatory
    DESCRIPTION
       " The row definition for this table."
   INDEX  {rsMLBNatRouterAddress, rsMLBNatAddress}
   ::= {rsMLBNatTable 1}

RsMLBNatEntry  ::= SEQUENCE {
   rsMLBNatRouterAddress                 IpAddress,
   rsMLBNatAddress                       IpAddress,
   rsMLBNatStatus                        INTEGER,
   rsMLBNatMode                          INTEGER
   }


rsMLBNatRouterAddress    OBJECT-TYPE
   SYNTAX IpAddress
   ACCESS  read-only
   STATUS  mandatory
   DESCRIPTION
     "The Router IP Address."
   ::= {rsMLBNatEntry 1}


rsMLBNatAddress    OBJECT-TYPE
   SYNTAX IpAddress
   ACCESS  read-only
   STATUS  mandatory
   DESCRIPTION
     "The NAT IP Address."
   ::= {rsMLBNatEntry 2}


rsMLBNatStatus OBJECT-TYPE
    SYNTAX INTEGER {
              active(1),
              notInService(2),
              notReady(3),
              createAndGo(4),
              createAndWait(5),
              destroy(6) }
    ACCESS read-write
    STATUS mandatory
    DESCRIPTION
       "This variable indicates the administrative status of this entry."
--  DEFVAL  { 2 }
    ::=  {rsMLBNatEntry 3}

rsMLBNatMode OBJECT-TYPE
    SYNTAX INTEGER {
           regular(1),
           backup(2)
    }
    ACCESS  read-write
    STATUS  mandatory
    DESCRIPTION
        "The  NAT mode - either backup/regular"
--  DEFVAL { 1 }
    ::= {rsMLBNatEntry 4}

rsMLBdummy11 OBJECT-TYPE
    SYNTAX INTEGER
    ACCESS  read-only
    STATUS  mandatory
    DESCRIPTION
       " Dummy variable for stopping getnext."
    ::=  {rsMLBNatTable 2}


rsMLBFpNatStatus  OBJECT-TYPE
   SYNTAX  INTEGER {
            enable(1),
            disable(2)
   }
   ACCESS  read-write
   STATUS  mandatory
   DESCRIPTION
      "Nat Status."
--  DEFVAL  { 2 }
    ::=  {rsMLB 27}



rsMLBStaticNatTable OBJECT-TYPE
    SYNTAX SEQUENCE OF RsMLBStaticNatEntry
    ACCESS not-accessible
    STATUS mandatory
    DESCRIPTION
       "In this table the FP saves the static NAT addresses."
    ::= {rsMLB 28}

rsMLBStaticNatEntry OBJECT-TYPE
    SYNTAX RsMLBStaticNatEntry
    ACCESS not-accessible
    STATUS  mandatory
    DESCRIPTION
       " The row definition for this table."
   INDEX  {rsMLBStaticNatLclServerAddress,
           rsMLBStaticNatRouterAddress }
   ::= {rsMLBStaticNatTable 1}

RsMLBStaticNatEntry  ::= SEQUENCE {
   rsMLBStaticNatLclServerAddress                IpAddress,
   rsMLBStaticNatRouterAddress                  IpAddress,
   rsMLBStaticNatAddress                  IpAddress,
   rsMLBStaticNatStatus                      INTEGER,
   rsMLBStaticNatMode                      INTEGER
   }


rsMLBStaticNatLclServerAddress    OBJECT-TYPE
   SYNTAX IpAddress
   ACCESS  read-only
   STATUS  mandatory
   DESCRIPTION
     "IP Address of the local machine whost IP address should be translated."
   ::= {rsMLBStaticNatEntry 1}

rsMLBStaticNatRouterAddress    OBJECT-TYPE
   SYNTAX IpAddress
   ACCESS  read-only
   STATUS  mandatory
   DESCRIPTION
     "The Router IP Address."
   ::= {rsMLBStaticNatEntry 2}

rsMLBStaticNatAddress    OBJECT-TYPE
   SYNTAX IpAddress
   ACCESS  read-write
   STATUS  mandatory
   DESCRIPTION
     "The Static NAT IP Address who is related to the local machine and router."
   ::= {rsMLBStaticNatEntry 3}

rsMLBStaticNatStatus OBJECT-TYPE
    SYNTAX INTEGER {
              active(1),
              notInService(2),
              notReady(3),
              createAndGo(4),
              createAndWait(5),
              destroy(6) }
    ACCESS read-write
    STATUS mandatory
    DESCRIPTION
       "This variable indicates the administrative status of this entry."
--  DEFVAL  { 2 }
    ::=  {rsMLBStaticNatEntry 4}

rsMLBStaticNatMode OBJECT-TYPE
    SYNTAX INTEGER {
           regular(1),
           backup(2)
    }
    ACCESS  read-write
    STATUS  mandatory
    DESCRIPTION
        "The Static NAT mode - either backup/regular"
--  DEFVAL { 1 }
    ::= {rsMLBStaticNatEntry 5}

rsMLBdummy12 OBJECT-TYPE
    SYNTAX INTEGER
    ACCESS  read-only
    STATUS  mandatory
    DESCRIPTION
       " Dummy variable for stopping getnext."
    ::=  {rsMLBStaticNatTable 2}


rsMLBProximity  OBJECT IDENTIFIER ::= { rsMLB 29 }

rsMLBStaticProximityTable OBJECT-TYPE
   SYNTAX SEQUENCE OF RsMLBStaticProximityEntry
   ACCESS not-accessible
   STATUS mandatory
   DESCRIPTION
          "In this table the MLB saves the static proximity ranges per server farm IP Address"
   ::= {rsMLBProximity 1}


rsMLBStaticProximityEntry OBJECT-TYPE
    SYNTAX RsMLBStaticProximityEntry
    ACCESS not-accessible
    STATUS  mandatory
    DESCRIPTION
       " The row definition for this table."
   INDEX  {rsMLBStaticProximityRangeFrom }
   ::= {rsMLBStaticProximityTable 1}


RsMLBStaticProximityEntry  ::= SEQUENCE {
  rsMLBStaticProximityRangeFrom                 IpAddress,
  rsMLBStaticProximityRangeTo                   IpAddress,
  rsMLBStaticProximityStatus                    INTEGER,
  rsMLBStaticProximityServer1                   IpAddress,
  rsMLBStaticProximityServer2                   IpAddress,
  rsMLBStaticProximityServer3                   IpAddress
  }


rsMLBStaticProximityRangeFrom OBJECT-TYPE
    SYNTAX IpAddress
    ACCESS  read-only
    STATUS  mandatory
    DESCRIPTION
      "The IP Address of the low boundary of the interval."
    ::= {rsMLBStaticProximityEntry 1}

rsMLBStaticProximityRangeTo OBJECT-TYPE
    SYNTAX IpAddress
    ACCESS  read-write
    STATUS  mandatory
    DESCRIPTION
      "The IP Address of the high boundary of the interval."
    ::= {rsMLBStaticProximityEntry 2}

rsMLBStaticProximityStatus OBJECT-TYPE
      SYNTAX INTEGER {
        active(1),
        notInService(2),
        notReady(3),
        createAndGo(4),
        createAndWait(5),
        destroy(6) }
    ACCESS  read-write
    STATUS  mandatory
    DESCRIPTION
      "This variable indicate the Administative status of this entry.
       Use for delete an entry in this table."
  ::= {rsMLBStaticProximityEntry 3}

rsMLBStaticProximityServer1 OBJECT-TYPE
    SYNTAX IpAddress
    ACCESS  read-write
    STATUS  mandatory
    DESCRIPTION
"The first priority server that this range of clients will be redirected to"
    ::= {rsMLBStaticProximityEntry 4}

rsMLBStaticProximityServer2 OBJECT-TYPE
    SYNTAX IpAddress
    ACCESS  read-write
    STATUS  mandatory
    DESCRIPTION
"The second priority server that this range of clients will be redirected to"
       ::= {rsMLBStaticProximityEntry 5}

rsMLBStaticProximityServer3 OBJECT-TYPE
    SYNTAX IpAddress
    ACCESS  read-write
    STATUS  mandatory
    DESCRIPTION
" The third priority server that this range of clients will be redirected to "
    ::= {rsMLBStaticProximityEntry 6}

rsMLBProximityOperationMode  OBJECT-TYPE
   SYNTAX INTEGER {
        noProximity(1),
        staticProximity(2),
	fullProximityInbound(3),
	fullProximityOutbound(4),
	fullProximityBoth(5)
   }
   ACCESS  read-write
   STATUS  mandatory
   DESCRIPTION
       "Allow proximity operation, and choose between operating only static proximity or dynamic proximity as well "
-- DEFVAL { 1 }
   ::=  {rsMLBProximity 2}

rsMLBProximityMainDNS OBJECT-TYPE
SYNTAX IpAddress
    ACCESS  read-write
    STATUS  mandatory
    DESCRIPTION
        "The IP Address of the main DNS to be ignored in the proximity operation"
    ::= { rsMLBProximity 3}

rsMLBProximityBackupDNS OBJECT-TYPE
SYNTAX IpAddress
    ACCESS  read-write
    STATUS  mandatory
    DESCRIPTION
        "The IP Address of the backup DNS to be ignored in the proximity operation"
    ::= { rsMLBProximity 4}

rsMLBProximityAgingPeriod OBJECT-TYPE
    SYNTAX INTEGER
    ACCESS  read-write
    STATUS  mandatory
    DESCRIPTION
        "The time in hours after which an old dynamic entry is invalid."
--     DEFVAL   { 48 }
    ::=  { rsMLBProximity 5}

rsMLBProximityRetries  OBJECT-TYPE
   SYNTAX INTEGER (1..5)
   ACCESS  read-write
   STATUS  mandatory
   DESCRIPTION
       "The number of tries for checking the client distance"
-- DEFVAL { 2 }
   ::=  {rsMLBProximity 6}

rsMLBProximityTimeout  OBJECT-TYPE
   SYNTAX INTEGER (1..10)
   ACCESS  read-write
   STATUS  mandatory
   DESCRIPTION
       "The timeout between proximity checks"
-- DEFVAL { 5 }
   ::=  {rsMLBProximity 7}

rsMLBProximityTuning OBJECT IDENTIFIER ::= { rsMLBProximity 8}

rsMLBMaxDynEntries OBJECT-TYPE
    SYNTAX INTEGER
    ACCESS  read-only
    STATUS  mandatory
    DESCRIPTION
      "Maximal number of entries in the dynamic proximity table."
    ::=  { rsMLBProximityTuning 1 }

rsMLBMaxDynEntriesAfterReset OBJECT-TYPE
    SYNTAX INTEGER
    ACCESS  read-write
    STATUS  mandatory
    DESCRIPTION
      "Future maximal number of entries in the dynamic proximity table."
    ::=  { rsMLBProximityTuning 2 }


rsMLBProximityHopsWeight  OBJECT-TYPE
   SYNTAX INTEGER (1..100)
   ACCESS  read-write
   STATUS  mandatory
   DESCRIPTION
       "The weight given to the clients hops distance in the dispatching decision"
-- DEFVAL { 50 }
   ::=  {rsMLBProximity 9}

rsMLBProximityLatencyWeight  OBJECT-TYPE
   SYNTAX INTEGER (1..100)
   ACCESS  read-write
   STATUS  mandatory
   DESCRIPTION
       "The weight given to the clients latency in the dispatching decision"
-- DEFVAL { 50 }
   ::=  {rsMLBProximity 10}

rsMLBProximityLoadWeight  OBJECT-TYPE
   SYNTAX INTEGER (1..100)
   ACCESS  read-write
   STATUS  mandatory
   DESCRIPTION
       "The weight given to the site load in the dispatching decision"
-- DEFVAL { 50 }
   ::=  {rsMLBProximity 11}


rsMLBPrxyCheckFPIPTable OBJECT-TYPE
    SYNTAX SEQUENCE OF RsMLBPrxyCheckFPIPEntry
    ACCESS not-accessible
    STATUS mandatory
    DESCRIPTION
    "Table containing FP IP address for each server. This FP IP serves as the source IP for the proximity check packet which is send through this server."
    ::=  {rsMLBProximity 12}

rsMLBPrxyCheckFPIPEntry OBJECT-TYPE
    SYNTAX RsMLBPrxyCheckFPIPEntry
    ACCESS not-accessible
    STATUS  mandatory
    DESCRIPTION
       " The row definition for this table."
   INDEX {rsMLBRouterAddr }
    ::=  {rsMLBPrxyCheckFPIPTable 1}

RsMLBPrxyCheckFPIPEntry ::= SEQUENCE {
  rsMLBRouterAddr            	IpAddress,
  rsMLBFPIPAddr            	IpAddress,
  rsMLBPrxyCheckFPIPStatus        INTEGER
}

rsMLBRouterAddr   OBJECT-TYPE
    SYNTAX  IpAddress
    ACCESS  read-only
    STATUS  mandatory
    DESCRIPTION
     "Server address"
 ::=  {rsMLBPrxyCheckFPIPEntry 1 }

rsMLBFPIPAddr OBJECT-TYPE
    SYNTAX  IpAddress
    ACCESS read-write
    STATUS  mandatory
    DESCRIPTION
     "FP IP address."
 ::=  {rsMLBPrxyCheckFPIPEntry 2 }

rsMLBPrxyCheckFPIPStatus OBJECT-TYPE
    SYNTAX INTEGER {
        active(1),
        notInService(2),
        notReady(3),
        createAndGo(4),
        createAndWait(5),
        destroy(6) }
    ACCESS  read-write
    STATUS  mandatory
    DESCRIPTION
      "Administrative status of the row."
 ::=  {rsMLBPrxyCheckFPIPEntry 4 }


rsMLBdummy15 OBJECT-TYPE
    SYNTAX INTEGER
    ACCESS  read-only
    STATUS  mandatory
    DESCRIPTION
       " Dummy variable for stopping getnext."
    ::=  { rsMLBPrxyCheckFPIPTable 2}


rsMLBDNS OBJECT IDENTIFIER ::= { rsMLB 30 }

rsMLBDNSURLtoIPTable OBJECT-TYPE
    SYNTAX SEQUENCE OF RsMLBURLtoIPEntry
    ACCESS not-accessible
    STATUS mandatory
    DESCRIPTION
    "The table for storing the IPs for URLs"
    ::= {rsMLBDNS 1}

rsMLBURLtoIPEntry OBJECT-TYPE
    SYNTAX RsMLBURLtoIPEntry
    ACCESS not-accessible
    STATUS mandatory
    DESCRIPTION
       "The row definition for IPs for URLs table"
    INDEX {rsMLBURL}
    ::= { rsMLBDNSURLtoIPTable 1}

RsMLBURLtoIPEntry ::= SEQUENCE {
 rsMLBURL                        DisplayString,
 rsMLBURLLocDeviceIP           IpAddress,
 rsMLBURLStatus             INTEGER
}

rsMLBURL     OBJECT-TYPE
    SYNTAX DisplayString (SIZE(1..50))
    ACCESS  read-only
    STATUS  mandatory
    DESCRIPTION
    "The URL address"
    ::= { rsMLBURLtoIPEntry 1}

rsMLBURLLocDeviceIP OBJECT-TYPE
    SYNTAX IpAddress
    ACCESS read-write
    STATUS mandatory
    DESCRIPTION
    "The local device's IP "
    ::= { rsMLBURLtoIPEntry 2}

rsMLBURLStatus OBJECT-TYPE
    SYNTAX INTEGER {
                    active(1),
                    notInService(2),
                    notReady(3),
                    createAndGo(4),
                    createAndWait(5),
                    destroy(6)
                   }
    ACCESS  read-write
    STATUS  mandatory
    DESCRIPTION
       "This variable indicates the administrative status of this entry.
        Used to delete an entry of this table."
    ::=  { rsMLBURLtoIPEntry 3}

 rsMLBdummy13 OBJECT-TYPE
    SYNTAX INTEGER
    ACCESS  read-only
    STATUS  mandatory
    DESCRIPTION
    "Dummy variable for stopping getnext."
    ::= { rsMLBDNSURLtoIPTable 2}

rsMLBDNSttl OBJECT-TYPE
    SYNTAX INTEGER
    ACCESS read-write
    STATUS mandatory
    DESCRIPTION
      "DNS time to live"
-- DEFVAL  {0}
    ::= {rsMLBDNS 2}

rsMLBDNSTwoAnswers OBJECT-TYPE
 SYNTAX INTEGER {
      enable(1),
      disable(2)
   }
    ACCESS read-write
    STATUS mandatory
    DESCRIPTION
      "Sending two DNS answers"
-- DEFVAL  {disable}
    ::= {rsMLBDNS 3}


rsMLBDNSVirtualTable OBJECT-TYPE
    SYNTAX SEQUENCE OF RsMLBDNSVirtualEntry
    ACCESS not-accessible
    STATUS mandatory
    DESCRIPTION
    "The table for DNS virtual IPs "
    ::= {rsMLBDNS 4}

rsMLBDNSVirtualEntry OBJECT-TYPE
    SYNTAX RsMLBDNSVirtualEntry
    ACCESS not-accessible
    STATUS mandatory
    DESCRIPTION
    "The row definition for DNS virtual IPs table"
    INDEX {rsMLBDNSVirtualIP}
    ::= { rsMLBDNSVirtualTable 1}

RsMLBDNSVirtualEntry ::= SEQUENCE {
 rsMLBDNSVirtualIP      IpAddress,
 rsMLBDNSVirIPMode      INTEGER,
 rsMLBDNSStatus         INTEGER
}

rsMLBDNSVirtualIP OBJECT-TYPE
 SYNTAX   IpAddress
    ACCESS read-only
    STATUS mandatory
    DESCRIPTION
    "The DNS Virtual IP status"
::= { rsMLBDNSVirtualEntry 1}

rsMLBDNSVirIPMode OBJECT-TYPE
 SYNTAX INTEGER {
      regular(1),
      backup(2)
   }
    ACCESS read-write
    STATUS mandatory
    DESCRIPTION
    "The DNS Virtual IP mode (regular/backup)"
--  DEFVAL  {regular}
    ::= { rsMLBDNSVirtualEntry 2}

rsMLBDNSStatus OBJECT-TYPE
    SYNTAX INTEGER {
                    active(1),
                    notInService(2),
                    notReady(3),
                    createAndGo(4),
                    createAndWait(5),
                    destroy(6)
                   }
    ACCESS  read-write
    STATUS  mandatory
    DESCRIPTION
       "This variable indicates the administrative status of this entry.
        Used to delete an entry of this table."
    ::=  { rsMLBDNSVirtualEntry 3}

rsMLBdummy14 OBJECT-TYPE
    SYNTAX INTEGER
    ACCESS  read-only
    STATUS  mandatory
    DESCRIPTION
    "Dummy variable for stopping getnext."
    ::= { rsMLBDNSVirtualTable 2}


rsMLBSrcPortInClientHash OBJECT-TYPE
    SYNTAX INTEGER {
      enable(1),
      disable(2)
    }
    ACCESS  read-write
    STATUS  mandatory
    DESCRIPTION
      "enable - client's source port is used in client table hashing, disable
      - only client IP and destination IP are used."
    DEFVAL  { 2 }
    ::=  { rsMLB 31 }


rsMLBAgingTimeTable OBJECT-TYPE
    SYNTAX SEQUENCE OF RsMLBAgingTimeEntry
    ACCESS not-accessible
    STATUS mandatory
    DESCRIPTION
    "This table determine the aging time for specific applications."
    ::=  { rsMLB 32}

rsMLBAgingTimeEntry OBJECT-TYPE
    SYNTAX RsMLBAgingTimeEntry
    ACCESS not-accessible
    STATUS  mandatory
    DESCRIPTION
       " The row definition for this table."
   INDEX {rsMLBAgingTimeApplPort}
    ::=  {rsMLBAgingTimeTable 1}

RsMLBAgingTimeEntry  ::= SEQUENCE {
  rsMLBAgingTimeApplPort            	 INTEGER,
  rsMLBAgingTime            	 	 INTEGER,
  rsMLBAgingTimeStatus                   INTEGER
  }

rsMLBAgingTimeApplPort  OBJECT-TYPE
    SYNTAX  INTEGER
    ACCESS  read-only
    STATUS  mandatory
    DESCRIPTION
     "Application port"
 ::=  {rsMLBAgingTimeEntry 1 }

rsMLBAgingTime  OBJECT-TYPE
    SYNTAX INTEGER 
    ACCESS  read-write
    STATUS  mandatory
    DESCRIPTION
     "define the aging time for the aplication port in seconds"
    DEFVAL  { 60 }
 ::=  {rsMLBAgingTimeEntry 2 }


rsMLBAgingTimeStatus  OBJECT-TYPE
    SYNTAX INTEGER {
        active(1),
        notInService(2),
        notReady(3),
        createAndGo(4),
        createAndWait(5),
        destroy(6) }
    ACCESS  read-write
    STATUS  mandatory
    DESCRIPTION
      "Administrative status of the entry."
 ::=  {rsMLBAgingTimeEntry 3 }



rsMLBdummy16 OBJECT-TYPE
    SYNTAX INTEGER
    ACCESS  read-only
    STATUS  mandatory
    DESCRIPTION
       " Dummy variable for stopping getnext."
    ::=  { rsMLBAgingTimeTable 2}




     END
