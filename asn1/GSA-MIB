GSA-MIB DEFINITIONS ::= BEGIN

-- The MIB Containing all the search specific
-- variables that are available on the SNMP
-- interface of the Google Search Appliance

IMPORTS
    OBJECT-TYPE, Integer32, NOTIFICATION-TYPE FROM SNMPv2-SMI

    TEXTUAL-CONVENTION, DisplayString, TruthValue
        FROM SNMPv2-TC

    gsa FROM GOOGLE-MIB;

-- Crawling related information

crawl	OBJECT IDENTIFIER ::= { gsa 1 }

crawlRunning	OBJECT-TYPE
	SYNTAX		INTEGER {
			    paused(0),  -- crawl paused
			    running(1) -- crawl running
			}
	MAX-ACCESS	read-only
	STATUS		current
	DESCRIPTION
		"Crawling activity of GSA"
	::= { crawl 1 }

status	OBJECT IDENTIFIER ::= { crawl 2 }

docsServed	OBJECT-TYPE
	SYNTAX		Integer32
	MAX-ACCESS	read-only
	STATUS		current
	DESCRIPTION
		"The number of documents being served by the
		 Google Search Appliance"
	::= { status 1 }

crawlingRate	OBJECT-TYPE
	SYNTAX		Integer32
--	UNITS		pages per second
	MAX-ACCESS	read-only
	STATUS		current
	DESCRIPTION
		"The current crawling rate of the
		 Google Search Appliance"
	::= { status 2 }

docBytes	OBJECT-TYPE
	SYNTAX		Integer32
--	UNITS		total megabytes crawled
	MAX-ACCESS	read-only
	STATUS		current
	DESCRIPTION
		"The total megabytes processed so far by the
		 Google Search Appliance"
	::= { status 3 }

todayDocsCrawled	OBJECT-TYPE
	SYNTAX		Integer32
	MAX-ACCESS	read-only
	STATUS		current
	DESCRIPTION
		"The number of documents crawled
		 today"
	::= { status 4 }

docErrors		OBJECT-TYPE
	SYNTAX		Integer32
	MAX-ACCESS	read-only
	STATUS		current
	DESCRIPTION
		"Number of times an error occurred
		 while trying to crawl a document"
	::= { status 5 }

docsFound		OBJECT-TYPE
	SYNTAX		Integer32
	MAX-ACCESS	read-only
	STATUS		current
	DESCRIPTION
		"Total documents found by the 
		 Google Search Appliance"
	::= { status 6 }
	

batchCrawlRunning	OBJECT-TYPE
	SYNTAX		INTEGER {
			    off(0),  -- batch crawl off
			    on(1) -- batch crawl on
			}
	MAX-ACCESS	read-only
	STATUS		current
	DESCRIPTION
		"Batch crawl activity of the GSA"
	::= { status 7 }

batchCrawlStartTime	OBJECT-TYPE
	SYNTAX		Integer32
	MAX-ACCESS	read-only
	STATUS		current
	DESCRIPTION
		"Time the most recent batch crawl started 
		 on the Google Search Appliance"
	::= { status 8 }

batchCrawlEndTime	OBJECT-TYPE
	SYNTAX		Integer32
	MAX-ACCESS	read-only
	STATUS		current
	DESCRIPTION
		"Time the most recent batch crawl ended 
		 on the Google Search Appliance"
	::= { status 9 }

batchCrawlEndReason	OBJECT-TYPE
	SYNTAX		INTEGER {
			    urllimit(0),  -- hit license limit or ran out of urls
			    schedulestopped(1) -- stopped by schedule
			}
	MAX-ACCESS	read-only
	STATUS		current
	DESCRIPTION
		"Reason the most recent batch crawl ended
		 on the Google Search Appliance"
	::= { status 10 }

diagnostics	OBJECT IDENTIFIER ::= { crawl 3 }

serving		OBJECT IDENTIFIER ::= { gsa 2 }

qpm	OBJECT-TYPE
	SYNTAX		Integer32
--	UNITS		queries per minute
	MAX-ACCESS	read-only
	STATUS		current
	DESCRIPTION
		"The serving status, in terms of
		 queries per minute being handled"
	::= { serving 1 }

system	OBJECT IDENTIFIER ::= { gsa 3 }

gsaDisk 	OBJECT IDENTIFIER ::= { system 1 }

diskHealth	OBJECT-TYPE
	SYNTAX		INTEGER {
			    green(0),  -- state OK
			    yellow(1), -- warning
			    red(2)     -- critical warning
			}
	MAX-ACCESS	read-only
	STATUS		current
	DESCRIPTION
		"Information about status of the disk(s) in GSA"
	::= { gsaDisk 1 }

diskErrors	OBJECT-TYPE
	SYNTAX      DisplayString
	MAX-ACCESS  read-only
	STATUS      current
	DESCRIPTION
	    "Errors associated with disk"
	::= { gsaDisk 2 }

temperature	OBJECT IDENTIFIER ::= { system 2 }

temperatureHealth    OBJECT-TYPE
        SYNTAX          INTEGER {
                            green(0),  -- state OK
                            yellow(1), -- warning
                            red(2)     -- critical warning
                        }
        MAX-ACCESS      read-only
        STATUS          current
        DESCRIPTION
                "Information about temperature of GSA"
        ::= { temperature 1 }

temperatureErrors    OBJECT-TYPE
	SYNTAX	    DisplayString
	MAX-ACCESS  read-only
	STATUS	    current
	DESCRIPTION
		"Error string associated with temperature"
	::= { temperature 2 }

machine		OBJECT IDENTIFIER ::= { system 3 }

machineHealth    OBJECT-TYPE
        SYNTAX          INTEGER {
                            green(0),  -- state OK
                            yellow(1), -- warning
                            red(2)     -- critical warning
                        }
        MAX-ACCESS      read-only
        STATUS          current
        DESCRIPTION
                "Information about status of the machine"
        ::= { machine 1 }

machineErrors    OBJECT-TYPE
	SYNTAX	    DisplayString
	MAX-ACCESS  read-only
	STATUS	    current
	DESCRIPTION
		"Error string associated with machine"
	::= { machine 2 }

search	OBJECT IDENTIFIER ::= { gsa 4 }

reports OBJECT IDENTIFIER ::= { search 1 }

logs	OBJECT IDENTIFIER ::= { search 2 }

eventLogs  OBJECT IDENTIFIER ::= { gsa 5 }

END
