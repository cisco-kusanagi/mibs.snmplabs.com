-- |**********************************************************************|
 -- | Copyright 1998 - Sonoma Systems, Inc. Marina del Rey, CA 90292       |
 -- |    Unpublished software - All rights reserved.                       |
 -- |                                                                      |
 -- | The information in this software is subject to change without notice |
 -- | and should not be construed as a commitment by Sonoma Systems, Inc.  |
 -- |                                                                      |
 -- | Sonoma Systems, Inc. assumes no responsibility for the use or        |
 -- | reliability of its software on equipment which is not supplied by    |
 -- | Sonoma Systems, Inc.                                                 |
 -- |                                                                      |
 -- | This software is furnished under a license and may be copied only    |
 -- | under the terms of that license and with the inclusion of this       |
 -- | notice. This software, or any other copies thereof, may not be       |
 -- | provided or otherwise made available to any other person except to   |
 -- | one who agrees to these license terms. Title to and ownership of the |
 -- | software shall at all times remain with Sonoma Systems, Inc.         |
 -- |**********************************************************************|
 --
 -- Sonoma Systems Inc.,
 -- 4640 Admiralty Way, Suite #600,
 -- Marina Del Rey,
 -- California 90292-6695.
 --
 -- Web : www.sonoma-systems.com
 -- Phone:  310.827.8000
 --
 -- NAME        : e3mib.def
 --
 -- DESCRIPTION : This is the MIB for the Sonoma ATM/E3 interface.
 --
 -- ARCHIVE : $Archive:   M:\pvcs\pvcsproj\sonoma3\src\mib\e3mib.dev  $
 -- REVISION: $Revision:   1.8  $
 -- AUTHOR  : $Author:   TMANCOUR  $
 -- DATE    : $Date:   Feb 08 1999 14:08:26  $

      SONOMASYSTEMS-SONOMA-ATM-E3-MIB DEFINITIONS ::= BEGIN

      IMPORTS
        Counter
        FROM RFC1155-SMI
        OBJECT-TYPE
        FROM RFC-1212
        sonomaATM
        FROM SONOMASYSTEMS-SONOMA-MIB;

    --  This MIB module uses the extended OBJECT-TYPE macro as
    --  defined in [14];
    --
    -- Hierarchy for these groups
    -- enterprises OBJECT IDENTIFIER ::= { private 4 }
    -- sonomaSystems OBJECT IDENTIFIER ::= {  enterprises 2926 }
    -- sonomaSeries OBJECT IDENTIFIER ::= { sonomaSystems 25 }
    -- sonomaATM OBJECT IDENTIFIER ::= { sonomaSeries 7 }
    sonomaE3ATMAdapterGroup OBJECT IDENTIFIER ::= { sonomaATM 3 }
        
      --   Sonoma E3 ATM Adapter Specific Group MIB groups
      atmE3ConfGroup OBJECT IDENTIFIER ::= { sonomaE3ATMAdapterGroup 1 }
      atmE3StatsGroup OBJECT IDENTIFIER ::= { sonomaE3ATMAdapterGroup 2 }

    -- Sonoma E3 ATM Adapter Specific Group MIB groups

    -- This group contains all informat specificly for
    -- Sonoma Systems E3 adapter. It includes the configuration and
    -- some statistics information

    --  atmE3ConfGroup

    atmE3ConfPhyTable  OBJECT-TYPE
        SYNTAX  SEQUENCE OF AtmE3ConfPhyEntry
        ACCESS  not-accessible
        STATUS  mandatory
        DESCRIPTION
            "A table of physical layer configuration for the E3
         interface"
        ::= { atmE3ConfGroup 1 }

    atmE3ConfPhyEntry  OBJECT-TYPE
        SYNTAX  AtmE3ConfPhyEntry
        ACCESS  not-accessible
        STATUS  mandatory
        DESCRIPTION
          "A entry in the table, containing information about the
           physical layer of a E3 interface"
        INDEX  { atmE3ConfPhysIndex }
        ::= { atmE3ConfPhyTable 1 }
    
    AtmE3ConfPhyEntry ::= SEQUENCE {
      atmE3ConfPhysIndex     INTEGER,
      atmE3ConfFraming       INTEGER,
      atmE3ConfInsGFCBits    INTEGER,
      atmE3ConfSerBipolarIO  INTEGER,
      atmE3ConfPayloadScrambling   INTEGER,
      atmE3ConfOverheadProcessing  INTEGER,
      atmE3ConfHDB3Encoding  INTEGER,
      atmE3ConfLoopback      INTEGER,
      atmE3ConfCableLength   INTEGER,
      atmE3ConfInternalEqualizer   INTEGER,
      atmE3ConfFillerCells   INTEGER,
      atmE3ConfGenerateClock INTEGER
    }

    atmE3ConfPhysIndex   OBJECT-TYPE
        SYNTAX  INTEGER
        ACCESS  read-only
        STATUS  mandatory
        DESCRIPTION
            "The physical interface index."
        ::= { atmE3ConfPhyEntry 1 }   

    atmE3ConfFraming OBJECT-TYPE
        SYNTAX  INTEGER { 
                        framingE3(2)
                        }
        ACCESS  read-only
        STATUS  mandatory
        DESCRIPTION
            "Indicates the type of framing supported."
        DEFVAL { framingE3 }
        ::= { atmE3ConfPhyEntry 2 }

    atmE3ConfInsGFCBits   OBJECT-TYPE
        SYNTAX  INTEGER { 
                        enabled (1), 
                        disabled (2)
                        }
        ACCESS  read-write
        STATUS  mandatory
        DESCRIPTION
            "Enable/disable the insertion of GFC bits."
            DEFVAL { disabled }
        ::= { atmE3ConfPhyEntry 3 }

    atmE3ConfSerBipolarIO OBJECT-TYPE
        SYNTAX  INTEGER { 
                        enabled (1), 
                        disabled (2)
                        }
        ACCESS  read-write
        STATUS  mandatory
        DESCRIPTION
            "Enable/disable bipolar serial I/O."
            DEFVAL { enabled }
        ::= { atmE3ConfPhyEntry 4 }

    atmE3ConfPayloadScrambling OBJECT-TYPE
        SYNTAX  INTEGER { 
                        enabled (1), 
                        disabled (2)
                        }
        ACCESS  read-write
        STATUS  mandatory
        DESCRIPTION
            "Enable/disable payload scrambling."
            DEFVAL { enabled }
        ::= { atmE3ConfPhyEntry 5 }

    atmE3ConfOverheadProcessing    OBJECT-TYPE
        SYNTAX  INTEGER { 
                        enabled (1), 
                        disabled (2)
                        }
        ACCESS  read-write
        STATUS  mandatory
        DESCRIPTION
            "Enable/disable Overhead processing."
            DEFVAL { enabled }
        ::= { atmE3ConfPhyEntry 6 }

    atmE3ConfHDB3Encoding    OBJECT-TYPE
        SYNTAX  INTEGER { 
                        enabled (1), 
                        disabled (2)
                        }
        ACCESS  read-write
        STATUS  mandatory
        DESCRIPTION
            "Enable/disable HDB3 (High Density Bipolar 3) Encoding."
          DEFVAL { enabled }
        ::= { atmE3ConfPhyEntry 7 }

    atmE3ConfLoopback OBJECT-TYPE
        SYNTAX  INTEGER { 
                        disabled(1),
                        internal(2), 
                        external(3)
                        }
        ACCESS  read-write
        STATUS  mandatory
        DESCRIPTION
            "This object is used to modify the state of internal
             loopback...."
          DEFVAL { disabled }
        ::= { atmE3ConfPhyEntry 8 }

    atmE3ConfCableLength OBJECT-TYPE
        SYNTAX  INTEGER {
                        notGreaterThan225Feet(1), 
                        greaterThan225Feet(2) 
                        } 
        ACCESS  read-write
        STATUS  mandatory
        DESCRIPTION
            "Configure for the length of the cable."
            DEFVAL { notGreaterThan225Feet }
        ::= { atmE3ConfPhyEntry 9 }

    atmE3ConfInternalEqualizer OBJECT-TYPE
        SYNTAX  INTEGER { 
                        use(1),
                        bypass(2)
                        }
        ACCESS  read-write
        STATUS  mandatory
        DESCRIPTION
            "Configure to use or bypass the internal equalizer."
            DEFVAL { use }
        ::= { atmE3ConfPhyEntry 10 }

    atmE3ConfFillerCells OBJECT-TYPE
        SYNTAX  INTEGER { 
			unassigned(1), 
			idle(2)
			}
        ACCESS  read-write
        STATUS  mandatory
        DESCRIPTION
            "This parameter indicates the type of filler cells to send
             when there are no data cells."
            DEFVAL { unassigned }
        ::= { atmE3ConfPhyEntry 11 }

     atmE3ConfGenerateClock OBJECT-TYPE
        SYNTAX  INTEGER {
                enabled (1),
                disabled (2)
                }
        ACCESS  read-write
        STATUS  mandatory
        DESCRIPTION
            "Enable/disable clock generation."
            DEFVAL { disabled }
        ::= { atmE3ConfPhyEntry 12 }


    --  atmE3StatsGroup

    atmE3StatsTable  OBJECT-TYPE
        SYNTAX  SEQUENCE OF AtmE3StatsEntry
        ACCESS  not-accessible
        STATUS  mandatory
        DESCRIPTION
            "A table of physical layer statistics information for the E3
         interface"
        ::= { atmE3StatsGroup 1 }

    atmE3StatsEntry  OBJECT-TYPE
        SYNTAX  AtmE3StatsEntry
        ACCESS  not-accessible
        STATUS  mandatory
        DESCRIPTION
          "A entry in the table, containing information about the
           physical layer of a E3 interface"
        INDEX  { atmE3StatsPhysIndex }
        ::= { atmE3StatsTable 1 }
    
    AtmE3StatsEntry ::= SEQUENCE {
      atmE3StatsPhysIndex      INTEGER,
      atmE3StatsNoSignals      Counter,
      atmE3StatsNoE3Frames     Counter,
      atmE3StatsFrameErrors    Counter,
      atmE3StatsHECErrors      Counter,
      atmE3StatsEMErrors       Counter,
      atmE3StatsFeBlockErrors  Counter,
      atmE3StatsBpvErrors      Counter,
      atmE3StatsPayloadTypeMismatches Counter,
      atmE3StatsTimingMarkers     Counter,
      atmE3StatsAISDetects        Counter,
      atmE3StatsRDIDetects        Counter,
      atmE3StatsSignalLoss        INTEGER,
      atmE3StatsFrameLoss         INTEGER,
      atmE3StatsSyncLoss          INTEGER,
      atmE3StatsOutOfCell         INTEGER,
      atmE3StatsFIFOOverflow      INTEGER,
      atmE3StatsPayloadTypeMismatch   INTEGER,     
      atmE3StatsTimingMarker      INTEGER,
      atmE3StatsAISDetect         INTEGER,
      atmE3StatsRDIDetect         INTEGER,
      atmE3StatsClearCounters     INTEGER
    }

    atmE3StatsPhysIndex  OBJECT-TYPE
        SYNTAX  INTEGER
        ACCESS  read-only
        STATUS  mandatory
        DESCRIPTION
            "The physical interface index."
        ::= { atmE3StatsEntry 1 }  

    atmE3StatsNoSignals  OBJECT-TYPE
        SYNTAX  Counter
        ACCESS  read-only
        STATUS  mandatory
        DESCRIPTION
            "No signal error counter."
        ::= { atmE3StatsEntry 2 }

    atmE3StatsNoE3Frames  OBJECT-TYPE
        SYNTAX  Counter
        ACCESS  read-only
        STATUS  mandatory
        DESCRIPTION
            "No E3 frames error counter."
        ::= { atmE3StatsEntry 3 }
    
    atmE3StatsFrameErrors  OBJECT-TYPE
        SYNTAX  Counter
        ACCESS  read-only
        STATUS  mandatory
        DESCRIPTION
            "A count of the number of Frames in error."
        ::= { atmE3StatsEntry 4 }

    atmE3StatsHECErrors  OBJECT-TYPE
        SYNTAX  Counter
        ACCESS  read-only
        STATUS  mandatory
        DESCRIPTION
            "HEC (Header Error Check) error counter."
        ::= { atmE3StatsEntry 5 }

    atmE3StatsEMErrors  OBJECT-TYPE
        SYNTAX  Counter
        ACCESS  read-only
        STATUS  mandatory
        DESCRIPTION
            "EM (error monitoring) error counter."
        ::= { atmE3StatsEntry 6 }

    atmE3StatsFeBlockErrors  OBJECT-TYPE
        SYNTAX  Counter
        ACCESS  read-only
        STATUS  mandatory
        DESCRIPTION
            "Far End Block error counter."
        ::= { atmE3StatsEntry 7 }

    atmE3StatsBpvErrors  OBJECT-TYPE
        SYNTAX  Counter
        ACCESS  read-only
        STATUS  mandatory
        DESCRIPTION
            "Bipolar Violation error counter."
        ::= { atmE3StatsEntry 8 }

    atmE3StatsPayloadTypeMismatches  OBJECT-TYPE
        SYNTAX  Counter
        ACCESS  read-only
        STATUS  mandatory
        DESCRIPTION
            "Payload Type Mismatches error counter."
        ::= { atmE3StatsEntry 9 }

    atmE3StatsTimingMarkers  OBJECT-TYPE
        SYNTAX  Counter
        ACCESS  read-only
        STATUS  mandatory
        DESCRIPTION
            "Timing Markers error counter."
        ::= { atmE3StatsEntry 10 }

    atmE3StatsAISDetects  OBJECT-TYPE
        SYNTAX  Counter
        ACCESS  read-only
        STATUS  mandatory
        DESCRIPTION
            "AIS (Alarm Indication Signal) detect counter."
        ::= { atmE3StatsEntry 11 }

    atmE3StatsRDIDetects  OBJECT-TYPE
        SYNTAX  Counter
        ACCESS  read-only
        STATUS  mandatory
        DESCRIPTION
            "RDI (Remote Defect Indication) error counter."
        ::= { atmE3StatsEntry 12 }

    atmE3StatsSignalLoss  OBJECT-TYPE
        SYNTAX  INTEGER {
                        true (1), 
                        false (2)
                        }
        ACCESS  read-only
        STATUS  mandatory
        DESCRIPTION
            "Signal loss indication."
        ::= { atmE3StatsEntry 13 }

    atmE3StatsFrameLoss  OBJECT-TYPE
        SYNTAX  INTEGER {
                        true (1), 
                        false (2)
                        }
        ACCESS  read-only
        STATUS  mandatory
        DESCRIPTION
            "Frame loss indication."
        ::= { atmE3StatsEntry 14 }

    atmE3StatsSyncLoss  OBJECT-TYPE
        SYNTAX  INTEGER {
                        true (1), 
                        false (2)
                        }
        ACCESS  read-only
        STATUS  mandatory
        DESCRIPTION
            "Synchronization loss counter."
        ::= { atmE3StatsEntry 15 }

    atmE3StatsOutOfCell  OBJECT-TYPE
        SYNTAX  INTEGER {
                        true (1), 
                        false (2)
                        }
        ACCESS  read-only
        STATUS  mandatory
        DESCRIPTION
            "ATM out-of-cell delineation."
        ::= { atmE3StatsEntry 16 }

    atmE3StatsFIFOOverflow  OBJECT-TYPE
        SYNTAX  INTEGER {
                        true (1), 
                        false (2)
                        }
        ACCESS  read-only
        STATUS  mandatory
        DESCRIPTION
            "ATM FIFO overflow."
        ::= { atmE3StatsEntry 17 }

    atmE3StatsPayloadTypeMismatch OBJECT-TYPE
        SYNTAX  INTEGER {
                        true (1), 
                        false (2)
                        }
        ACCESS  read-only
        STATUS  mandatory
        DESCRIPTION
            "The Payload Type Mismatch state."
        ::= { atmE3StatsEntry 18 }

    atmE3StatsTimingMarker   OBJECT-TYPE
        SYNTAX  INTEGER {
                        true (1), 
                        false (2)
                        }
        ACCESS  read-only
        STATUS  mandatory
        DESCRIPTION
            "The Timing Marker state."
        ::= { atmE3StatsEntry 19 }

    atmE3StatsAISDetect   OBJECT-TYPE
        SYNTAX  INTEGER {
                        true (1), 
                        false (2)
                        }
        ACCESS  read-only
        STATUS  mandatory
        DESCRIPTION
            "The AIS (Alarm Indication Signal) state."
        ::= { atmE3StatsEntry 20 }

    atmE3StatsRDIDetect OBJECT-TYPE
        SYNTAX  INTEGER {
                        true (1), 
                        false (2)
                        }
        ACCESS  read-only
        STATUS  mandatory
        DESCRIPTION
            "RDI (Remote Defect Indication) state."
        ::= { atmE3StatsEntry 21 }

    atmE3StatsClearCounters  OBJECT-TYPE
        SYNTAX  INTEGER {
                        true (1), 
                        false (2)
                        }
        ACCESS  read-write
        STATUS  mandatory
        DESCRIPTION
            "Clear all counters in this group ONLY."
        DEFVAL { false }
        ::= { atmE3StatsEntry 22 }

END
