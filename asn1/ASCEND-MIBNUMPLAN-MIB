--			Ascend mibnumplan MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBNUMPLAN-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibnumberPlanProfile  OBJECT IDENTIFIER ::= { configuration 96}

	-- The mibnumberPlanProfile table
	--
	-- This table contains parameters for the mibnumberPlanProfile profile
	--

    mibnumberPlanProfileTable	OBJECT-TYPE
	SYNTAX		SEQUENCE OF MibnumberPlanProfileEntry
	ACCESS		not-accessible
	STATUS		mandatory
	DESCRIPTION	"A list of mibnumberPlanProfile profile entries."
	::= { mibnumberPlanProfile 1 }

    mibnumberPlanProfileEntry	OBJECT-TYPE
	SYNTAX		MibnumberPlanProfileEntry
	ACCESS		not-accessible
	STATUS		mandatory
	DESCRIPTION	"A mibnumberPlanProfile entry containing objects that
			 maps to the parameters of mibnumberPlanProfile profile."
	INDEX		{ numberPlanProfile-Name }
	::= { mibnumberPlanProfileTable 1 }

    MibnumberPlanProfileEntry ::=
	SEQUENCE {
	    numberPlanProfile-Name
		DisplayString,
	    numberPlanProfile-Active
		INTEGER,
	    numberPlanProfile-DialPrefix
		DisplayString,
	    numberPlanProfile-NumDigits
		INTEGER,
	    numberPlanProfile-Action-o
		INTEGER
	}

    numberPlanProfile-Name	OBJECT-TYPE
	SYNTAX	DisplayString
	ACCESS	read-only
	STATUS	mandatory
	DESCRIPTION	""
	::= { mibnumberPlanProfileEntry 1 }

    numberPlanProfile-Active	OBJECT-TYPE
	SYNTAX	INTEGER {
		    no (1),
		    yes (2)
		}
	ACCESS	read-write
	STATUS	mandatory
	DESCRIPTION	"TRUE to allow use of this prefix, FALSE otherwise."
	::= { mibnumberPlanProfileEntry 2 }

    numberPlanProfile-DialPrefix	OBJECT-TYPE
	SYNTAX	DisplayString
	ACCESS	read-write
	STATUS	mandatory
	DESCRIPTION	"Dial prefix to match."
	::= { mibnumberPlanProfileEntry 3 }

    numberPlanProfile-NumDigits	OBJECT-TYPE
	SYNTAX	INTEGER
	ACCESS	read-write
	STATUS	mandatory
	DESCRIPTION	"Number of digits in a phone number matching the associated dial prefix."
	::= { mibnumberPlanProfileEntry 4 }

    numberPlanProfile-Action-o	OBJECT-TYPE
	SYNTAX	INTEGER {
		    noAction (1),
		    createProfile (2),
		    deleteProfile (3)
		}
	ACCESS	read-write
	STATUS	mandatory
	DESCRIPTION	""
	::= { mibnumberPlanProfileEntry 5 }

END
