-- **********************************************************************
-- * Artem private WLAN Management Information Base
-- **********************************************************************
ARTEM-COMPOINT-WLAN-MIB DEFINITIONS ::= BEGIN

	IMPORTS
		enterprises, IpAddress, Integer32, Counter32, 
		OBJECT-TYPE, MODULE-IDENTITY, OBJECT-IDENTITY, NOTIFICATION-TYPE
			FROM SNMPv2-SMI
		OBJECT-GROUP, NOTIFICATION-GROUP
			FROM SNMPv2-CONF
		TruthValue, MacAddress, RowStatus, TEXTUAL-CONVENTION
			FROM SNMPv2-TC
		ifIndex
			FROM RFC1213-MIB;
			
-- **********************************************************************
-- *  MODULE IDENTITY
-- **********************************************************************
	artem MODULE-IDENTITY
		LAST-UPDATED "200504210958Z"
		ORGANIZATION
			"Funkwerk Enterprise Communications."
		CONTACT-INFO
			"juergen.lachmann@funkwerk-ec.com."
		DESCRIPTION
			"Funkwerk Enterprise Communications MIB file that provides 
			 additional attributes not covered by standard MIBs 
			 for WLAN functionality in artem products."
		REVISION "200505121005Z"
		DESCRIPTION
			"Added missing index artemBridgePeerIndex for 
			 artemBridgePeersTable."
		REVISION "200504211400Z"
		DESCRIPTION
			"Initial version."
		::= { enterprises 4280 }
		

-- **********************************************************************
-- *  Textual conventions
-- **********************************************************************
	ArtemRSSI ::= TEXTUAL-CONVENTION
		STATUS current
		DESCRIPTION
			"This type is used to represent receiver input levels in dBm."
		SYNTAX INTEGER (-110..0)

-- **********************************************************************
-- *   Node definitions
-- **********************************************************************


-- **********************************************************************
-- *   artemWLAN
-- **********************************************************************
	artemWLAN OBJECT-IDENTITY
		STATUS current
		DESCRIPTION
			"Definitions and attributes that apply to a radio module. 
			 The radio module may host one or more interfaces 
			 (AP service sets or bridge links)."
		::= { artem 5 }


-- **********************************************************************
-- *   artemBridge
-- **********************************************************************
	artemBridge OBJECT IDENTIFIER
		 ::= { artemWLAN 1 }

	artemBridgeConfigScanTimeout OBJECT-TYPE
        SYNTAX INTEGER (10..600)
      	UNITS "seconds"
        MAX-ACCESS read-write
        STATUS current
        DESCRIPTION
            "This attribute defines the maximum time a bridge 
             auto-configuration scan may take. After this timeout has 
             expired, any auto-configuration scan will be aborted, 
             regardless of current state."
        DEFVAL { 120 }
    	::= { artemBridge 1 }

	artemBridgeConfigSetupTimeout OBJECT-TYPE
        SYNTAX INTEGER (10..600)
      	UNITS "seconds"
        MAX-ACCESS read-write
        STATUS current
        DESCRIPTION
            "This attribute defines the maximum time a bridge 
             auto-configuration setup may take. After this timeout 
             has expired, any auto-configuration setup will be aborted, 
             regardless of current state. 
             In this case, artemBridgePeerConfigSetupResult 
             will be set to 'timeout'."
        DEFVAL { 300 }
    	::= { artemBridge 2 }

-- **********************************************************************
-- *    artemBridgeLinksTable  TABLE
-- **********************************************************************
	artemBridgeLinksTable OBJECT-TYPE
		SYNTAX SEQUENCE OF ArtemBridgeLinksEntry
		MAX-ACCESS not-accessible
		STATUS current
		DESCRIPTION
			"Attributes for artem bridge links."
		::= {  artemBridge 3 }
		
	artemBridgeLinksEntry OBJECT-TYPE
		SYNTAX ArtemBridgeLinksEntry
		MAX-ACCESS not-accessible
		STATUS current
		DESCRIPTION
			"An entry in artemBridgeLinksTable."
		INDEX {artemRadioIndex, artemBridgeLinkIndex}
		::= { artemBridgeLinksTable 1 }

	ArtemBridgeLinksEntry ::=
		SEQUENCE {
			artemBridgeLinkIndex					INTEGER,
			artemBridgeLinkRowStatus				INTEGER,
			artemBridgeLinkIfIndex					INTEGER,
			artemBridgeLinkAdminStatus				TruthValue,
			artemBridgeLinkAliasName				OCTET STRING,
			artemBridgeLinkCurrentSpeed				INTEGER,
			artemBridgeLinkPartnerRadioMacAddress	MacAddress,
			artemBridgeLinkOperStatus				TruthValue
		}

	artemBridgeLinkIndex OBJECT-TYPE
        SYNTAX INTEGER (1..2147483647)
        MAX-ACCESS not-accessible
        STATUS current
        DESCRIPTION
            "This is the unique index number for a bridge 
             link of the given radio."
    	::= { artemBridgeLinksEntry 1 }

	artemBridgeLinkRowStatus OBJECT-TYPE
        SYNTAX RowStatus
        MAX-ACCESS read-create
        STATUS current
        DESCRIPTION
            "Auxiliary variable for creation of new object instances 
             and/or the deletion of existing object instances."
    	::= { artemBridgeLinksEntry 2 }
	
	artemBridgeLinkIfIndex OBJECT-TYPE
        SYNTAX INTEGER (1..2147483647)
        MAX-ACCESS read-only
        STATUS current
        DESCRIPTION
            "ifIndex that is associated to the combination of 
             artemRadioIndex and artemBridgeLinkIndex."
    	::= { artemBridgeLinksEntry 3 }

	artemBridgeLinkAdminStatus OBJECT-TYPE
        SYNTAX TruthValue
        MAX-ACCESS read-create
        STATUS current
        DESCRIPTION
            "This attribute defines if the associated bridge 
             link is currently active."
        DEFVAL { false }
    	::= { artemBridgeLinksEntry 4 }

	artemBridgeLinkAliasName OBJECT-TYPE
        SYNTAX OCTET STRING (SIZE(0..13))
        MAX-ACCESS read-create
        STATUS current
        DESCRIPTION
            "This attribute can be used to set a textual alias 
             name for this bridge link. Default is 'wl?_br?', 
             where first '?' is radio number and second '?' 
             is link number on this radio."
    	::= { artemBridgeLinksEntry 5 }

	artemBridgeLinkCurrentSpeed OBJECT-TYPE
        SYNTAX INTEGER (0..54)
        MAX-ACCESS read-only
        STATUS current
        DESCRIPTION
            "This attribute returns the current transmission speed 
             for this link, or 0 if no connection can be established."
    	::= { artemBridgeLinksEntry 6 }

	artemBridgeLinkPartnerRadioMacAddress OBJECT-TYPE
        SYNTAX MacAddress
        MAX-ACCESS read-create
        STATUS current
        DESCRIPTION
            "This attribute contains the MAC address of the remote 
             radio module. It can be set directly, or via the 
             auto-configuration mechanism."
    	::= { artemBridgeLinksEntry 7 }

	artemBridgeLinkOperStatus OBJECT-TYPE
        SYNTAX TruthValue
        MAX-ACCESS read-only
        STATUS current
        DESCRIPTION
            "This attribute shows if the bridge link connection 
             is currently operative."
    	::= { artemBridgeLinksEntry 8 }

-- **********************************************************************
-- *    End of artemBridgeLinksTable  TABLE
-- **********************************************************************

-- **********************************************************************
-- *    artemBridgePrivacyTable  TABLE
-- **********************************************************************
	artemBridgePrivacyTable OBJECT-TYPE
		SYNTAX SEQUENCE OF ArtemBridgePrivacyEntry
		MAX-ACCESS not-accessible
		STATUS current
		DESCRIPTION
			"Table of privacy settings, with special 
			 privacy modes for bridge links."
		::= {  artemBridge 4 }
		
	artemBridgePrivacyEntry OBJECT-TYPE
		SYNTAX ArtemBridgePrivacyEntry
		MAX-ACCESS not-accessible
		STATUS current
		DESCRIPTION
			"An entry in artemBridgePrivacyTable."
		INDEX { artemRadioIndex }
		::= { artemBridgePrivacyTable 1 }

	ArtemBridgePrivacyEntry ::=
		SEQUENCE {
			artemBridgePrivacyMode		INTEGER,
			artemBridgePrivacyAutoKey	INTEGER
		}

	artemBridgePrivacyMode OBJECT-TYPE
        SYNTAX INTEGER
			{
			none(0),
			wep(1),
			tkip(2),
			aes(3)
			}
        MAX-ACCESS read-write
        STATUS current
        DESCRIPTION
            "This attribute selects privacy mode to use for all 
             bridge links on this radio. Privacy is immediately 
             enabled anything different from 'none' is selected 
             and an appropriate key has been set."
        DEFVAL { none }
    	::= { artemBridgePrivacyEntry 1 }

	artemBridgePrivacyAutoKey OBJECT-TYPE
        SYNTAX INTEGER (0..1)
        MAX-ACCESS read-write
        STATUS current
        DESCRIPTION
            "Writing this attribute triggers automatic bridge 
             privacy setup. Depending on artemBridgePrivacyMode, 
             a pseudo-random WEP key or passphrase is generated, 
             and privacy is activated. 
             If non-empty keys have previously been set, 
             writing this attribute returns an error."
    	::= { artemBridgePrivacyEntry 2 }

-- **********************************************************************
-- *    End of artemBridgePrivacyTable  TABLE
-- **********************************************************************

-- **********************************************************************
-- *    artemBridgeAutoConfigTable  TABLE
-- **********************************************************************
	artemBridgeAutoConfigTable OBJECT-TYPE
		SYNTAX SEQUENCE OF ArtemBridgeAutoConfigEntry
		MAX-ACCESS not-accessible
		STATUS current
		DESCRIPTION
			"Attributes for artem bridge link auto-configuration."
		::= {  artemBridge 5 }
		
	artemBridgeAutoConfigEntry OBJECT-TYPE
		SYNTAX ArtemBridgeAutoConfigEntry
		MAX-ACCESS not-accessible
		STATUS current
		DESCRIPTION
			"An entry in artemBridgeAutoConfigTable."
		INDEX { ifIndex }
		::= { artemBridgeAutoConfigTable 1 }

	ArtemBridgeAutoConfigEntry ::=
		SEQUENCE {
			artemBridgeLinkLockState		TruthValue,
			artemBridgeLinkConfigScanState	INTEGER
		}

	artemBridgeLinkLockState OBJECT-TYPE
        SYNTAX TruthValue
        MAX-ACCESS read-write
        STATUS current
        DESCRIPTION
            "This attribute defines if the bridge is locked. 
             Lock state is common for all bridge links 
             using the same radio.
			 If the bridge is locked, it cannot be discovered 
			 by auto-configuration scan, and remote changing of any 
			 parameters is blocked."
        DEFVAL { false }
    	::= { artemBridgeAutoConfigEntry 1 }

	artemBridgeLinkConfigScanState OBJECT-TYPE
		SYNTAX INTEGER
			{
			idle(0),
			scanning(1),
			busy(2)
			}
        MAX-ACCESS read-write
        STATUS current
        DESCRIPTION
            "This attribute defines the current auto-configuration 
             state.
			 idle(0) - In this state, writing any value starts an 
			 		auto-configuration scan for bridge link peers. 
			 		State will change to scanning(1) while the scan 
			 		is in progress. When the scan is finished, the 
			 		results are available in the artemBidgePeersTable.
			 scanning(1) - An auto-configuration scan for bridge 
			 		link peers is currently in progress. When scanning 
			 		has finished, the state will automatically 
			 		change to idle(0).
			 busy(2) - An auto-configuration setup is currently in 
			 		progress on this radio module.
			 Writing this attribute in any state other than 
			 idle(0) will return an error."
        DEFVAL { idle }
    	::= { artemBridgeAutoConfigEntry 2 }
	    	
-- **********************************************************************
-- *    End of artemBridgeAutoConfigTable  TABLE
-- **********************************************************************

-- **********************************************************************
-- *    artemBridgePeersTable  TABLE
-- **********************************************************************
	artemBridgePeersTable OBJECT-TYPE
		SYNTAX SEQUENCE OF ArtemBridgePeersEntry
		MAX-ACCESS not-accessible
		STATUS current
		DESCRIPTION
			"This table contains the results of bridge link 
			 auto-configuration scans. Each line represents 
			 a possible link partner."
		::= {  artemBridge 6 }
		
	artemBridgePeersEntry OBJECT-TYPE
		SYNTAX ArtemBridgePeersEntry
		MAX-ACCESS not-accessible
		STATUS current
		DESCRIPTION
			"An entry in artemBridgePeersTable."
		INDEX { ifIndex, artemBridgePeerIndex }
		::= { artemBridgePeersTable 1 }

	ArtemBridgePeersEntry ::=
		SEQUENCE {
			artemBridgePeerIndex				INTEGER,
			artemBridgePeerLinkAliasName		OCTET STRING,
			artemBridgePeerCompointName			OCTET STRING,
			artemBridgePeerRSSI					ArtemRSSI,
			artemBridgePeerLinkAdminStatus		TruthValue, 
			artemBridgePeerLockState			TruthValue,      
			artemBridgePeerCompointMacAddress	MacAddress,
			artemBridgePeerRadioMacAddress		MacAddress,
			artemBridgePeerConfigSetupState		INTEGER,
			artemBridgePeerConfigSetupResult	INTEGER
		}

	artemBridgePeerIndex OBJECT-TYPE
        SYNTAX INTEGER (1..2147483647)
        MAX-ACCESS not-accessible
        STATUS current
        DESCRIPTION
            "The auxiliary variable used to identify instances 
             of the columnar objects in the artemBridgePeersTable."
    	::= { artemBridgePeersEntry 1 }
	    	
	artemBridgePeerLinkAliasName OBJECT-TYPE
        SYNTAX OCTET STRING (SIZE(0..13))
        MAX-ACCESS read-only
        STATUS current
        DESCRIPTION
            "This attribute shows the user-defined alias 
             name for the peer's bridge link."
    	::= { artemBridgePeersEntry 2 }

	artemBridgePeerCompointName OBJECT-TYPE
        SYNTAX OCTET STRING (SIZE(0..32))
        MAX-ACCESS read-only
        STATUS current
        DESCRIPTION
            "This attribute displays the given node name of the 
             peer ComPoint."
    	::= { artemBridgePeersEntry 3 }

	artemBridgePeerRSSI OBJECT-TYPE
        SYNTAX ArtemRSSI
      	UNITS "dBm"
        MAX-ACCESS read-only
        STATUS current
        DESCRIPTION
            "This attribute shows the receive signal 
             strength for the signal received from the peer in dBm."
    	::= { artemBridgePeersEntry 4 }

	artemBridgePeerLinkAdminStatus OBJECT-TYPE
        SYNTAX TruthValue
        MAX-ACCESS read-only
        STATUS current
        DESCRIPTION
            "This attribute shows is the peer's bridge 
             link is currently enabled."
    	::= { artemBridgePeersEntry 5 }

	artemBridgePeerLockState OBJECT-TYPE
        SYNTAX TruthValue
        MAX-ACCESS read-only
        STATUS current
        DESCRIPTION
            "This attribute defines if the peer's bridge is locked. 
             Lock state is common for all bridge links 
             using the same radio.
			 If the bridge is locked, it cannot be discovered 
			 by auto-configuration scan, and changing of any 
			 parameters is blocked."
    	::= { artemBridgePeersEntry 6 }

	artemBridgePeerCompointMacAddress OBJECT-TYPE
        SYNTAX MacAddress
        MAX-ACCESS read-only
        STATUS current
        DESCRIPTION
            "This attribute displays the MAC address 
             of the peer ComPoint.
			 This is not the WLAN radio's MAC address, but rather 
			 the MAC address of the first ethernet port."
    	::= { artemBridgePeersEntry 7 }
	    	
	artemBridgePeerRadioMacAddress OBJECT-TYPE
        SYNTAX MacAddress
        MAX-ACCESS read-only
        STATUS current
        DESCRIPTION
            "This attribute displays the peer's WLAN radio's MAC address."
    	::= { artemBridgePeersEntry 8 }
	    	
	artemBridgePeerConfigSetupState OBJECT-TYPE
		SYNTAX INTEGER
			{
			idle(0),
			setup(1),
			busy(2)
			}
        MAX-ACCESS read-write
        STATUS current
        DESCRIPTION
            "This attribute defines the current auto-configuration
             setup state of the bridge link.
			 idle(0) - No auto-configuration is currently in progress. 
			 		In this state, writing to this attribute 
			 		starts auto-configuration of a bridge link to 
			 		the partner defined by the table row. The state 
			 		automatically changes to setup(1) for this peer, 
			 		and to busy(3) for all other peers.
			 setup(1) - Auto-configuration of this bridge link to 
			 		connect to this peer is currently in progress. 
			 		As soon as auto-config setup is finished, the 
			 		state changes back to idle(0). You can check 
			 		whether auto-config setup succeeded by reading 
			 		artemBridgePeerConfigSetupResult.
			 busy(2) - Either the bridge link is currently scanning 
			 		for peers, or auto-configuration setup with another 
			 		peer is currently in progress for this bridge link.
			 Writing this attribute in any state other than idle(0) 
			 returns an error."
        DEFVAL { idle }
    	::= { artemBridgePeersEntry 9 }

	artemBridgePeerConfigSetupResult OBJECT-TYPE
        SYNTAX INTEGER
			{
			noError(0),
			unknownCommand(1),
			locked(2),
			invalidPortID(3),
			deviceError(4),
			invalidTag(5),
			timeout(6),
			outOfBuffers(7),
			notFound(8),
			internalError(9),
			receivedNAK(10)
			}
        MAX-ACCESS read-only
        STATUS current
        DESCRIPTION
            "This attribute holds the result after a bridge link 
             auto-config setup.
             It is reset whenever a new auto-config setup is triggered."
    	::= { artemBridgePeersEntry 10 }

	
-- **********************************************************************
-- *    End of artemBridgePeersTable  TABLE
-- **********************************************************************


-- **********************************************************************
-- *    artemLinkTestTable  TABLE
-- **********************************************************************
	artemLinkTestTable OBJECT-TYPE
		SYNTAX SEQUENCE OF ArtemLinkTestEntry
		MAX-ACCESS not-accessible
		STATUS current
		DESCRIPTION
			"This table contains the link test results for every 
			 bridge link. Reading the artemLinkTestSignalRemote 
			 attribute triggers transmission of a new link request frame."
		::= {  artemBridge 7 }
		
	artemLinkTestEntry OBJECT-TYPE
		SYNTAX ArtemLinkTestEntry
		MAX-ACCESS not-accessible
		STATUS current
		DESCRIPTION
			"An entry in artemLinkTestEntry."
		INDEX { ifIndex }
		::= { artemLinkTestTable 1 }

	ArtemLinkTestEntry ::=
		SEQUENCE {
			artemLinkTestSignalLocal		ArtemRSSI,
			artemLinkTestSignalRemote		ArtemRSSI,
			artemLinkTestNoiseLocal			ArtemRSSI,
			artemLinkTestNoiseRemote		ArtemRSSI,
			artemLinkTestSNRLocal			INTEGER,
			artemLinkTestSNRRemote			INTEGER,
			artemLinkTestFramesTransmitted	Counter32,
			artemLinkTestFramesReceived		Counter32,
			artemLinkTestFramesLost			Counter32,
			artemLinkTestRxFrames54			Counter32,
			artemLinkTestRxFrames48			Counter32,
			artemLinkTestRxFrames36			Counter32,
			artemLinkTestRxFrames24			Counter32,
			artemLinkTestRxFrames18			Counter32,
			artemLinkTestRxFrames12			Counter32,
			artemLinkTestRxFrames11			Counter32,
			artemLinkTestRxFrames9			Counter32,
			artemLinkTestRxFrames6			Counter32,
			artemLinkTestRxFrames5			Counter32,
			artemLinkTestRxFrames2			Counter32,
			artemLinkTestRxFrames1			Counter32
		}

	artemLinkTestSignalLocal OBJECT-TYPE
        SYNTAX ArtemRSSI
        MAX-ACCESS read-only
        STATUS current
        DESCRIPTION
            "This attribute shows the received signal strength in dBm."
    	::= { artemLinkTestEntry 1 }
	    	
	artemLinkTestSignalRemote OBJECT-TYPE
        SYNTAX ArtemRSSI
        MAX-ACCESS read-only
        STATUS current
        DESCRIPTION
            "This attribute shows the received signal in dBm, as 
             measured by remote bridge link partner. Reading 
             this attribute triggers transmission of a 
             new link request frame."
    	::= { artemLinkTestEntry 2 }

	artemLinkTestNoiseLocal OBJECT-TYPE
        SYNTAX ArtemRSSI
      		UNITS "dBm"
        MAX-ACCESS read-only
        STATUS current
        DESCRIPTION
            "This attribute shows the measured noise level in dBm."
    	::= { artemLinkTestEntry 3 }
	    	
	artemLinkTestNoiseRemote OBJECT-TYPE
        SYNTAX ArtemRSSI
      		UNITS "dBm"
        MAX-ACCESS read-only
        STATUS current
        DESCRIPTION
            "This attribute shows the noise level in dBm, as 
             measured by remote bridge link partner."
    	::= { artemLinkTestEntry 4 }
	    	
	artemLinkTestSNRLocal OBJECT-TYPE
        SYNTAX INTEGER (0..90)
      		UNITS "dB"
        MAX-ACCESS read-only
        STATUS current
        DESCRIPTION
            "This attribute shows the calculated Signal 
             to Noise ratio in dB."
    	::= { artemLinkTestEntry 5 }
	    	
	artemLinkTestSNRRemote OBJECT-TYPE
        SYNTAX INTEGER (0..90)
      		UNITS "dB"
        MAX-ACCESS read-only
        STATUS current
        DESCRIPTION
            "This attribute shows the calculated Signal to Noise 
             ratio in dB, as measured by remote bridge link partner."
    	::= { artemLinkTestEntry 6 }
	    	
	artemLinkTestFramesTransmitted OBJECT-TYPE
        SYNTAX Counter32
        MAX-ACCESS read-only
        STATUS current
        DESCRIPTION
            "This attribute shows the number of link test 
             frames transmitted."
    	::= { artemLinkTestEntry 7 }
	    	
	artemLinkTestFramesReceived OBJECT-TYPE
        SYNTAX Counter32
        MAX-ACCESS read-only
        STATUS current
        DESCRIPTION
            "This attribute shows the number of link test 
             frames successfully received."
    	::= { artemLinkTestEntry 8 }
	    	
	artemLinkTestFramesLost OBJECT-TYPE
        SYNTAX Counter32
        MAX-ACCESS read-only
        STATUS current
        DESCRIPTION
            "This attribute shows the number of link test frames 
             for which no reply has been received and 
             therefore are considered lost."
    	::= { artemLinkTestEntry 9 }
	    	
	artemLinkTestRxFrames54 OBJECT-TYPE
        SYNTAX Counter32
        MAX-ACCESS read-only
        STATUS current
        DESCRIPTION
            "This attribute shows the number of link 
             test frames that were received at 54 Mbps."
    	::= { artemLinkTestEntry 10 }
	    	
	artemLinkTestRxFrames48 OBJECT-TYPE
        SYNTAX Counter32
        MAX-ACCESS read-only
        STATUS current
        DESCRIPTION
            "This attribute shows the number of link 
             test frames that were received at 48 Mbps."
    	::= { artemLinkTestEntry 11 }
	    	
	artemLinkTestRxFrames36 OBJECT-TYPE
        SYNTAX Counter32
        MAX-ACCESS read-only
        STATUS current
        DESCRIPTION
            "This attribute shows the number of link 
             test frames that were received at 36 Mbps."
    	::= { artemLinkTestEntry 12 }
	    	
	artemLinkTestRxFrames24 OBJECT-TYPE
        SYNTAX Counter32
        MAX-ACCESS read-only
        STATUS current
        DESCRIPTION
            "This attribute shows the number of link 
             test frames that were received at 24 Mbps."
    	::= { artemLinkTestEntry 13 }
	    	
	artemLinkTestRxFrames18 OBJECT-TYPE
        SYNTAX Counter32
        MAX-ACCESS read-only
        STATUS current
        DESCRIPTION
            "This attribute shows the number of link 
             test frames that were received at 18 Mbps."
    	::= { artemLinkTestEntry 14 }
	    	
	artemLinkTestRxFrames12 OBJECT-TYPE
        SYNTAX Counter32
        MAX-ACCESS read-only
        STATUS current
        DESCRIPTION
            "This attribute shows the number of link 
             test frames that were received at 12 Mbps."
    	::= { artemLinkTestEntry 15 }
	    	
	artemLinkTestRxFrames11 OBJECT-TYPE
        SYNTAX Counter32
        MAX-ACCESS read-only
        STATUS current
        DESCRIPTION
            "This attribute shows the number of link 
             test frames that were received at 11 Mbps."
    	::= { artemLinkTestEntry 16 }
	    	
	artemLinkTestRxFrames9 OBJECT-TYPE
        SYNTAX Counter32
        MAX-ACCESS read-only
        STATUS current
        DESCRIPTION
            "This attribute shows the number of link 
             test frames that were received at 9 Mbps."
    	::= { artemLinkTestEntry 17 }
	    	
	artemLinkTestRxFrames6 OBJECT-TYPE
        SYNTAX Counter32
        MAX-ACCESS read-only
        STATUS current
        DESCRIPTION
            "This attribute shows the number of link 
             test frames that were received at 6 Mbps."
    	::= { artemLinkTestEntry 18 }
	    	
	artemLinkTestRxFrames5 OBJECT-TYPE
        SYNTAX Counter32
        MAX-ACCESS read-only
        STATUS current
        DESCRIPTION
            "This attribute shows the number of link 
             test frames that were received at 5.5 Mbps."
    	::= { artemLinkTestEntry 19 }
	    	
	artemLinkTestRxFrames2 OBJECT-TYPE
        SYNTAX Counter32
        MAX-ACCESS read-only
        STATUS current
        DESCRIPTION
            "This attribute shows the number of link 
             test frames that were received at 2 Mbps."
    	::= { artemLinkTestEntry 20 }
	    	
	artemLinkTestRxFrames1 OBJECT-TYPE
        SYNTAX Counter32
        MAX-ACCESS read-only
        STATUS current
        DESCRIPTION
            "This attribute shows the number of link 
             test frames that were received at 1 Mbps."
    	::= { artemLinkTestEntry 21 }
	    	
-- **********************************************************************
-- *    End of artemLinkTestTable  TABLE
-- **********************************************************************

-- **********************************************************************
-- *    Bridge notification Objects
-- **********************************************************************
    artemBridgeNotification OBJECT IDENTIFIER 
    	::= { artemBridge 8 }

	artemBridgeLinkOperState NOTIFICATION-TYPE
		OBJECTS {
			ifIndex, 
			artemBridgeLinkOperStatus 
			}
		STATUS current
		DESCRIPTION
			"This notification is triggered whenever the connection state 
			 of the bridge link changes, i.e. link connection is lost, 
			 or link connection is restored."
		::= { artemBridgeNotification 1 }

	artemBridgeLinkConfigScan NOTIFICATION-TYPE
		OBJECTS {
			ifIndex, 
			artemBridgeLinkConfigScanState 
			}
		STATUS current
		DESCRIPTION
			"This notification is thrown whenever the bridge link 
			 auto-configuration scanning state changes."
		::= { artemBridgeNotification 2 }

	artemBridgePeerConfigSetup NOTIFICATION-TYPE
		OBJECTS {
			ifIndex, 
			artemBridgePeerConfigSetupState,
			artemBridgePeerConfigSetupResult
			}
		STATUS current
		DESCRIPTION
			"This notification is thrown whenever the bridge 
			 link auto-configuration setup state changes."
		::= { artemBridgeNotification 3 }
		    
	artemBridgeLinkLock NOTIFICATION-TYPE
		OBJECTS {
			ifIndex, 
			artemBridgeLinkLockState 
			}
		STATUS current
		DESCRIPTION
			"This notification is triggered whenever the 
			 lock state of the bridge link changes."
		::= { artemBridgeNotification 4 }
		    
-- **********************************************************************
-- *    End of Bridge notification Objects
-- **********************************************************************

-- ********************************************************************
-- * Groups 
-- ********************************************************************
	artemBridgeGroup OBJECT-GROUP
		OBJECTS {
				artemBridgeLinkRowStatus,
				artemBridgeLinkIfIndex,
				artemBridgeLinkAdminStatus,
				artemBridgeLinkAliasName,
				artemBridgeLinkCurrentSpeed,
				artemBridgeLinkPartnerRadioMacAddress,
				artemBridgeLinkOperStatus,
				artemBridgeLinkLockState
				}
		STATUS current
		DESCRIPTION
			"artem bridge-specific attributes."
		::= { artemBridge 9 }

	artemBridgePrivacyGroup OBJECT-GROUP
		OBJECTS {
				artemBridgePrivacyMode,
				artemBridgePrivacyAutoKey
				}
		STATUS current
		DESCRIPTION
			"artem bridge-specific privacy attributes."
		::= { artemBridge 10 }

	artemBridgePeersGroup OBJECT-GROUP
		OBJECTS {
				artemBridgePeerLinkAliasName,
				artemBridgePeerCompointName,
				artemBridgePeerRSSI,
				artemBridgePeerLinkAdminStatus,
				artemBridgePeerLockState,
				artemBridgePeerCompointMacAddress,
				artemBridgePeerRadioMacAddress,
				artemBridgePeerConfigSetupState,
				artemBridgePeerConfigSetupResult
				}
		STATUS current
		DESCRIPTION
			"Attributes of the results of bridge link 
			 auto-configuration scans."
		::= { artemBridge 11 }

	artemBridgeLinkTestGroup OBJECT-GROUP
		OBJECTS {
				artemLinkTestSignalLocal,
				artemLinkTestSignalRemote,
				artemLinkTestNoiseLocal,
				artemLinkTestNoiseRemote,
				artemLinkTestSNRLocal,
				artemLinkTestSNRRemote,
				artemLinkTestFramesTransmitted,
				artemLinkTestFramesReceived,
				artemLinkTestFramesLost,
				artemLinkTestRxFrames54,
				artemLinkTestRxFrames48,
				artemLinkTestRxFrames36,
				artemLinkTestRxFrames24,
				artemLinkTestRxFrames18,
				artemLinkTestRxFrames12,
				artemLinkTestRxFrames11,
				artemLinkTestRxFrames9,
				artemLinkTestRxFrames6,
				artemLinkTestRxFrames5,
				artemLinkTestRxFrames2,
				artemLinkTestRxFrames1
				}
		STATUS current
		DESCRIPTION
			"Attributes for bridge link test."
		::= { artemBridge 12 }

	artemBridgeLinkNotificationGroup NOTIFICATION-GROUP
		NOTIFICATIONS {
				artemBridgeLinkOperState, 
				artemBridgeLinkConfigScan,
				artemBridgePeerConfigSetup,
				artemBridgeLinkLock
				}
		STATUS current
		DESCRIPTION
			"artem notifications for bridge links"
		::= { artemBridge 13 }
	

-- ********************************************************************
-- * End of Groups 
-- ********************************************************************

-- ********************************************************************
-- *   End of artemBridge
-- ********************************************************************

-- ********************************************************************
-- *   artemAP
-- ********************************************************************
	artemAP OBJECT IDENTIFIER
		 ::= { artemWLAN 2 }

-- **********************************************************************
-- *    artemAPServiceSetsTable  TABLE
-- **********************************************************************
	artemAPServiceSetsTable OBJECT-TYPE
		SYNTAX SEQUENCE OF ArtemAPServiceSetsEntry
		MAX-ACCESS not-accessible
		STATUS current
		DESCRIPTION
			"Attributes for artem AP service sets."
		::= {  artemAP 1 }
		
	artemAPServiceSetsEntry OBJECT-TYPE
		SYNTAX ArtemAPServiceSetsEntry
		MAX-ACCESS not-accessible
		STATUS current
		DESCRIPTION
			"An entry in artemAPServiceSetsTable."
		INDEX {artemRadioIndex, artemAPServiceSetIndex}
		::= { artemAPServiceSetsTable 1 }

	ArtemAPServiceSetsEntry ::=
		SEQUENCE {
			artemAPServiceSetIndex			INTEGER,
			artemAPServiceSetsRowStatus		RowStatus,
			artemAPIfIndex					INTEGER,
			artemAPServiceSetAdminStatus	TruthValue
		}

	artemAPServiceSetIndex OBJECT-TYPE
        SYNTAX INTEGER (1..2147483647)
        MAX-ACCESS not-accessible
        STATUS current
        DESCRIPTION
            "This is the unique index number for a service 
             set of the given radio."
    	::= { artemAPServiceSetsEntry 1 }

	artemAPServiceSetsRowStatus OBJECT-TYPE
        SYNTAX RowStatus
        MAX-ACCESS read-create
        STATUS current
        DESCRIPTION
            "Auxiliary variable for creation of new object instances 
             and/or the deletion of existing object instances."
    	::= { artemAPServiceSetsEntry 2 }
	
	artemAPIfIndex OBJECT-TYPE
        SYNTAX INTEGER (1..2147483647)
        MAX-ACCESS read-only
        STATUS current
        DESCRIPTION
            "ifIndex that is associated to the combination of 
             artemRadioIndex and artemAPServiceSetIndex."
    	::= { artemAPServiceSetsEntry 3 }

	artemAPServiceSetAdminStatus OBJECT-TYPE
        SYNTAX TruthValue
        MAX-ACCESS read-create
        STATUS current
        DESCRIPTION
            "This attribute defines if the associated AP 
             service is currently active."
        DEFVAL { false }
    	::= { artemAPServiceSetsEntry 4 }

-- **********************************************************************
-- *    End of artemAPServiceSetsTable  TABLE
-- **********************************************************************

-- ********************************************************************
-- * Groups - artemAPGroup
-- ********************************************************************
	artemAPGroup OBJECT-GROUP
		OBJECTS {
				artemAPServiceSetsRowStatus,
				artemAPIfIndex, 
				artemAPServiceSetAdminStatus
				}
		STATUS current
		DESCRIPTION
			"Extended AP parameters not covered in 
			 standard 802.11 MIB."
		::= { artemAP 10 }

-- ********************************************************************
-- * End of artemAPGroup
-- ********************************************************************

-- ********************************************************************
-- *   artemAPNotification
-- ********************************************************************
	artemAPNotification OBJECT IDENTIFIER
		 ::= { artemAP 9 }
		 
-- ********************************************************************
-- *   End of artemAPNotification
-- ********************************************************************
		 
-- ********************************************************************
-- *   End of artemAP
-- ********************************************************************

-- ********************************************************************
-- *    artemRadioParametersTable  TABLE
-- ********************************************************************
	artemRadioParametersTable OBJECT-TYPE
		SYNTAX SEQUENCE OF ArtemRadioParametersEntry
		MAX-ACCESS not-accessible
		STATUS current
		DESCRIPTION
			"Table of WLAN radio parameters not covered in standard 802.11 MIB."
		::= {  artemWLAN 3 }
		
	artemRadioParametersEntry OBJECT-TYPE
		SYNTAX ArtemRadioParametersEntry
		MAX-ACCESS not-accessible
		STATUS current
		DESCRIPTION
			"An entry in artemRadioParametersTable."
		INDEX { artemRadioIndex }
		::= { artemRadioParametersTable 1 }

	ArtemRadioParametersEntry ::=
		SEQUENCE {
			artemRadioIndex					INTEGER,
			artemRadioChannel				INTEGER,
			artemRadioSpeedMode				INTEGER,
			artemRadioTxPower				INTEGER,
			artemRadioAntennaDiversity		INTEGER,
			artemRadioNitroMode				TruthValue,
			artemRadioAckWindow				INTEGER,
			artemRadioWwrMode				INTEGER,
			artemRadioOperatingMode			INTEGER
		}

	artemRadioIndex OBJECT-TYPE
        SYNTAX INTEGER (1..2147483647)
        MAX-ACCESS not-accessible
        STATUS current
        DESCRIPTION
            "The auxiliary variable used to identify instances of 
             the columnar objects in the artemRadioParametersTable."
    	::= { artemRadioParametersEntry 1 }

	artemRadioChannel OBJECT-TYPE
        SYNTAX INTEGER (0..199)
        MAX-ACCESS read-write
        STATUS current
        DESCRIPTION
        	"Selecting a radio channel by writing this attribute 
        	 implicitly defines the radio band to use.
        	    Channels 1..14 implies 2.4 GHz
        	    Channels 30..  implies 5 GHz 
        	 Selecting any channel outside the ranges above 
        	 selects 2.4 GHz with DFS.
        	 Is the selected channel part of a DFS-only subband 
        	 or is it outside of any allowed subband, then DFS 
        	 will be activated.
        	 Reading this attribute always returns the actually 
        	 working channel, even with DFS. A returned value 
        	 of 0 means no channel has (yet) been selected, 
        	 perhaps due to 5 GHz band scanning."
    	::= { artemRadioParametersEntry 2 }

	artemRadioSpeedMode OBJECT-TYPE
		SYNTAX INTEGER
			{
			autoFallback(0),
			fixed1Mbps(1),
			fixed2Mpbs(2),
			fixed5Mbps(5),
			fixed6Mbps(6),
			fixed9Mbps(9),
			fixed11Mbps(11),
			fixed12Mbps(12),
			fixed18Mbps(18),
			fixed24Mbps(24),
			fixed36Mbps(36),
			fixed48Mbps(48),
			fixed54Mbps(54)
			}
        MAX-ACCESS read-write
        STATUS current
        DESCRIPTION
        	"This attribute selects the data rate to be used 
        	 for transmissions.
        	 Selecting autoFallback activates automatic adaption 
        	 of the data rate to the transmission conditions."
        DEFVAL { autoFallback }
    	::= { artemRadioParametersEntry 3 }
	    	
	artemRadioTxPower OBJECT-TYPE
        SYNTAX INTEGER (0..30)
     		UNITS "dBm"
        MAX-ACCESS read-write
        STATUS current
        DESCRIPTION
            "Transmit power in dBm."
    	::= { artemRadioParametersEntry 4 }

	artemRadioAntennaDiversity OBJECT-TYPE
		SYNTAX INTEGER
			{
			none(0),
			receive(1),
			transmit(2),
			both(3)
			}
        MAX-ACCESS read-write
        STATUS current
        DESCRIPTION
            "This attribute selects the mode of antenna diversity.
			 none(0) - No diversity, the main antenna is always 
			 		used for transmission and receival.
			 receive(1) - The main antenna is always used for 
			 		transmission. Both main and aux antennas are 
			 		used for receival, depending on signal levels.
			 transmit(2) - The main antenna is always used for 
			 		receival. Both main and aux antennas are used 
			 		for transmission.
			 both(3) - Both main and aux antennas are used for 
			 		transmission and receival, depending on signal 
			 		levels."
        DEFVAL { none }
    	::= { artemRadioParametersEntry 5 }
	    	
	artemRadioNitroMode OBJECT-TYPE
        SYNTAX TruthValue
        MAX-ACCESS read-write
        STATUS current
        DESCRIPTION
            "This attribute enables Conexant proprietary (but 100% 
             802.11g standard interoperable) frame bursting for 
             increased data throughput, especially with mixed 
             operation of 802.11b and 802.11g stations."
        DEFVAL { true }
    	::= { artemRadioParametersEntry 6 }

	artemRadioAckWindow OBJECT-TYPE
        SYNTAX INTEGER (0..199)
     		UNITS "microseconds"
        MAX-ACCESS read-write
        STATUS current
        DESCRIPTION
            "Additional 802.11 ACK timeout in microseconds.
			 This must be set to non-zero value for radio distances 
			 larger than about 700m.
			 Recommended setting is about 10 microseconds per kilometer."
        DEFVAL { 0 }
    	::= { artemRadioParametersEntry 7 }

	artemRadioWwrMode OBJECT-TYPE
        SYNTAX INTEGER
			{
			none(0),
			wwr11d(1),
			wwr11dhFlexible(2),
			wwr11dhStrict(3)
			}
        MAX-ACCESS read-write
        STATUS current
        DESCRIPTION
            "This attribute enables/disables 802.11d and 802.11h support.
			 none(0) - 802.11d disabled, 802.11h disabled.
			 wwr11d(1) - 802.11d enabled, 802.11h disabled.
			 wwr11d11hFlexible(2) - 802.11d enabled, 802.11h enabled; 
			 		access point allows non-spectrum-management 
			 		capable clients to join.
			 wwr11dhStrict(3) - 802.11d enabled, 802.11h enabled; 
			 		access point requires clients to be 
			 		spectrum-management capable."
        DEFVAL { wwr11dhFlexible }
    	::= { artemRadioParametersEntry 8 }

	artemRadioOperatingMode OBJECT-TYPE
        SYNTAX INTEGER
			{
			accessPoint(1),
			bridge(2),
			doubleBridge(3)
			}
        MAX-ACCESS read-write
        STATUS current
        DESCRIPTION
            "This attribute selects the operation mode for this radio.
			 accessPoint(1) - select access point mode.
			 bridge(2) - select bridge mode, up to 6 bridge links may be generated.
			 doubleBridge(3) - selects double bridge mode. Only available with 802.11b products."
    	::= { artemRadioParametersEntry 9 }

-- **********************************************************************
-- *    End of artemRadioParametersTable  TABLE
-- **********************************************************************

-- **********************************************************************
-- *    artemInterfaceRadioTable  TABLE
-- **********************************************************************
	artemInterfaceRadioTable OBJECT-TYPE
		SYNTAX SEQUENCE OF ArtemInterfaceRadioEntry
		MAX-ACCESS not-accessible
		STATUS current
		DESCRIPTION
			"Table of connection between interfaces (ifIndex) and 
			 radio indices (artemWLANRadioIndex)."
		::= {  artemWLAN 4 }
		
	artemInterfaceRadioEntry OBJECT-TYPE
		SYNTAX ArtemInterfaceRadioEntry
		MAX-ACCESS not-accessible
		STATUS current
		DESCRIPTION
			"An entry in artemInterfaceRadioTable."
		INDEX { ifIndex }
		::= { artemInterfaceRadioTable 1 }

	ArtemInterfaceRadioEntry ::=
		SEQUENCE {
			artemWLANRadioIndex		INTEGER
		}

	artemWLANRadioIndex OBJECT-TYPE
        SYNTAX INTEGER (1..2147483647)
        MAX-ACCESS read-only
        STATUS current
        DESCRIPTION
            "The auxiliary variable used to identify instances of 
             the columnar objects in the artemRadioParametersTable."
    	::= { artemInterfaceRadioEntry 1 }

-- **********************************************************************
-- *    End of artemInterfaceRadioTable  TABLE
-- **********************************************************************

-- ********************************************************************
-- *   artemWLANNotification
-- ********************************************************************
	artemWLANNotification OBJECT IDENTIFIER
		 ::= { artemWLAN 8 }
		 
-- ********************************************************************
-- *   End of artemWLANNotification
-- ********************************************************************

-- ********************************************************************
-- * Groups - artemWLANGroup
-- ********************************************************************
	artemWLANGroup OBJECT-GROUP
		OBJECTS {
--				artemRadioIndex,
				artemRadioChannel,
				artemRadioSpeedMode,
				artemRadioTxPower,
				artemRadioAntennaDiversity,
				artemRadioNitroMode,
				artemRadioAckWindow,
				artemRadioWwrMode,
				artemRadioOperatingMode,
				artemWLANRadioIndex
				}
		STATUS current
		DESCRIPTION
			"Extended WLAN radio parameters not covered in 
			 standard 802.11 MIB."
		::= { artemWLAN 9 }

-- ********************************************************************
-- * End of artemWLANGroup
-- ********************************************************************

-- **********************************************************************
-- *   End of artemWLAN
-- **********************************************************************

END
