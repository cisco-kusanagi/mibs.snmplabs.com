-- extracted from draft-ietf-isms-secshell-04.txt
-- at Wed Jun 28 06:06:35 2006

   SSHSM-MIB DEFINITIONS ::= BEGIN

   IMPORTS
       MODULE-IDENTITY, OBJECT-TYPE,
       OBJECT-IDENTITY, mib-2, Counter32, Integer32
         FROM SNMPv2-SMI
       TestAndIncr, AutonomousType
         FROM SNMPv2-TC
       MODULE-COMPLIANCE, OBJECT-GROUP
         FROM SNMPv2-CONF
       SnmpAdminString,  SnmpSecurityLevel, SnmpEngineID
          FROM SNMP-FRAMEWORK-MIB
       TransportAddress, TransportAddressType
         FROM TRANSPORT-ADDRESS-MIB
       ;

   sshsmMIB MODULE-IDENTITY
       LAST-UPDATED "200509020000Z"
       ORGANIZATION "ISMS Working Group"
       CONTACT-INFO "WG-EMail:   isms@lists.ietf.org
                     Subscribe:  isms-request@lists.ietf.org

                  Chairs:
                    Juergen Quittek
                    NEC Europe Ltd.
                    Network Laboratories
                    Kurfuersten-Anlage 36
                    69115 Heidelberg
                    Germany
                    +49 6221 90511-15
                     quittek@netlab.nec.de

                     Juergen Schoenwaelder
                     International University Bremen
                     Campus Ring 1
                     28725 Bremen
                     Germany
                     +49 421 200-3587
                     j.schoenwaelder@iu-bremen.de

                  Co-editors:
                     David Harrington
                     Effective Software
                     50 Harding Rd
                     Portsmouth, New Hampshire 03801
                     USA
                     +1 603-436-8634
                     ietfdbh@comcast.net

                     Joseph Salowey
                     Cisco Systems
                     2901 3rd Ave
                     Seattle, WA 98121
                     USA
                     jsalowey@cisco.com
                       "
          DESCRIPTION  "The Secure Shell Security Model MIB

                        Copyright (C) The Internet Society (2006). This
                        version of this MIB module is part of RFC XXXX;
                        see the RFC itself for full legal notices.
   -- NOTE to RFC editor: replace XXXX with actual RFC number
   --                     for this document and remove this note
                       "

          REVISION     "200509020000Z"         -- 02 September 2005
          DESCRIPTION  "The initial version, published in RFC XXXX.
   -- NOTE to RFC editor: replace XXXX with actual RFC number
   --                     for this document and remove this note
                       "

       ::= { mib-2 xxxx }
   -- RFC Ed.: replace xxxx with IANA-assigned number and
   --          remove this note
   -- ---------------------------------------------------------- --
   -- subtrees in the SSHSM-MIB
   -- ---------------------------------------------------------- --

   sshsmNotifications OBJECT IDENTIFIER ::= { sshsmMIB 0 }
   sshsmObjects       OBJECT IDENTIFIER ::= { sshsmMIB 1 }
   sshsmConformance   OBJECT IDENTIFIER ::= { sshsmMIB 2 }

   -- -------------------------------------------------------------
   -- Objects
   -- -------------------------------------------------------------

   TransportAddressSSH ::= TEXTUAL-CONVENTION
       DISPLAY-HINT "1a"
       STATUS      current
       DESCRIPTION
           "Represents either a hostname encoded in ASCII
           using the IDNA protocol, as specified in RFC3490, followed by
           a colon ':' (ASCII character 0x3A) and a decimal port number
           in ASCII, or an IP address followed by a colon ':'
           (ASCII character 0x3A) and a decimal port number in ASCII.
            The name SHOULD be fully qualified whenever possible.

            Values of this textual convention are not directly useable
            as transport-layer addressing information, and require
            runtime resolution. As such, applications that write them
            must be prepared for handling errors if such values are
            not supported, or cannot be resolved (if resolution occurs
            at the time of the management operation).

            The DESCRIPTION clause of TransportAddress objects that may
            have TransportAddressSSH values must fully describe how (and
            when) such names are to be resolved to IP addresses and vice
            versa.

            This textual convention SHOULD NOT be used directly in
            object definitions since it restricts addresses to a
            specific format. However, if it is used, it MAY be used
            either on its own or in conjunction with
            TransportAddressType or TransportDomain as a pair.

            When this textual convention is used as a syntax of an
            index object, there may be issues with the limit of 128
            sub-identifiers specified in SMIv2, STD 58. In this case,
            the OBJECT-TYPE declaration MUST include a 'SIZE' clause
            to limit the number of potential instance sub-identifiers."
       SYNTAX      OCTET STRING (SIZE (1..255))

    transportDomainSSH OBJECT-IDENTITY
       STATUS      current
       DESCRIPTION
           "The SSH transport domain. The corresponding transport
           address is of type TransportAddressSSH.

           When an SNMP entity uses the transportDomainSSH transport
           mapping, it must be capable of accepting messages up to
           and including 8192 octets in size.  Implementation of
           larger values is encouraged whenever possible."
       ::= { snmpDomains xxxx }
   -- RFC Ed.: replace xxxx with IANA-assigned number and
   --          remove this note



   -- Statistics for the Secure Shell Security Model


   sshsmStats         OBJECT IDENTIFIER ::= { sshsmObjects 1 }

   -- [todo] do we need any stats?


   -- -------------------------------------------------------------
   -- sshsmMIB - Conformance Information
   -- -------------------------------------------------------------

   sshsmGroups OBJECT IDENTIFIER ::= { sshsmConformance 1 }

   sshsmCompliances OBJECT IDENTIFIER ::= { sshsmConformance 2 }

   -- -------------------------------------------------------------
   -- Units of conformance
   -- -------------------------------------------------------------
   sshsmGroup OBJECT-GROUP
       OBJECTS {

       }
       STATUS      current
       DESCRIPTION "A collection of objects for maintaining
                    information of an SNMP engine which implements the
                    SNMP Secure Shell Security Model.
                   "

       ::= { sshsmGroups 2 }

   -- -------------------------------------------------------------
   -- Compliance statements
   -- -------------------------------------------------------------

   sshsmCompliance MODULE-COMPLIANCE
       STATUS      current
       DESCRIPTION
           "The compliance statement for SNMP engines that support the
           SSHSM-MIB"
       MODULE
           MANDATORY-GROUPS { sshsmGroup }
       ::= { sshsmCompliances 1 }

   END

-- 
--    Copyright (C) The Internet Society (2006).
-- 
--    This document is subject to the rights, licenses and restrictions
--    contained in BCP 78, and except as set forth therein, the authors
--    retain all their rights.
-- 
--    This document and the information contained herein are provided on an
--    "AS IS" basis and THE CONTRIBUTOR, THE ORGANIZATION HE/SHE REPRESENTS
--    OR IS SPONSORED BY (IF ANY), THE INTERNET SOCIETY AND THE INTERNET
--    ENGINEERING TASK FORCE DISCLAIM ALL WARRANTIES, EXPRESS OR IMPLIED,
--    INCLUDING BUT NOT LIMITED TO ANY WARRANTY THAT THE USE OF THE
--    INFORMATION HEREIN WILL NOT INFRINGE ANY RIGHTS OR ANY IMPLIED
--    WARRANTIES OF MERCHANTABILITY OR FITNESS FOR A PARTICULAR PURPOSE.
-- 
-- Intellectual Property
-- 
--    The IETF takes no position regarding the validity or scope of any
--    Intellectual Property Rights or other rights that might be claimed to
--    pertain to the implementation or use of the technology described in
--    this document or the extent to which any license under such rights
--    might or might not be available; nor does it represent that it has
--    made any independent effort to identify any such rights.  Information
--    on the procedures with respect to rights in RFC documents can be
--    found in BCP 78 and BCP 79.
-- 
--    Copies of IPR disclosures made to the IETF Secretariat and any
--    assurances of licenses to be made available, or the result of an
--    attempt made to obtain a general license or permission for the use of
--    such proprietary rights by implementers or users of this
--    specification can be obtained from the IETF on-line IPR repository at
--    http://www.ietf.org/ipr.
-- 
--    The IETF invites any interested party to bring to its attention any
--    copyrights, patents or patent applications, or other proprietary
--    rights that may cover technology that may be required to implement
--    this standard.  Please address the information to the IETF at
--    ietf-ipr@ietf.org.
--
