-- Copyright 1994 General DataComm Inc., Inc. All Rights Reserved.
--
-- Reproduction of this document is authorized on condition that the
-- foregoing copyright notice is included. This General DataComm, GDC,
-- SNMP Management Information Base Specification embodies GDCs'
-- confidential and proprietary intellectual property. GDC retains all
-- title and ownership in the Specification, including any revisions.
--
-- It is GDCs intent to encourage the widespread use of this Specification
-- in connection with the management of GDC's products. GDC grants vendors,
-- end-users, and other interested parties a non-exclusive license to use
-- this Specification in connection with the management of GDC's products.
--
-- This Specification is supplied "AS IS," and GDC makes no warranty,
-- either expressed or implied, as to the use operation, condition, or
-- performance of the Specification.
--
-- GDC UAS7022 MIB
--
-- Revision History
-- Version		Date		Name			Description
-- 1.00A		17-Feb-98	C. Amorossi  	Initial Revision
-- 1.00B		27-Mar-98	C. Amorossi	Added uas7022InterfaceType
--							and uas7022FDLMode
-- 1.00C		15-Jun-98	C. Amorossi	Remove uas7022CRC4 and change
--							enums for uas7022Framing
-- 1.00D		26-Jun-98	C. Amorossi     Added uas7022TimeSlot16Content
-- 1.00E		08-Jul-98	C. Amorossi     Fixed comments
-- 1.00F		01-Dec-98	C. Amorossi     Added uas7022Impedance

--
GDCUAS7022-MIB DEFINITIONS ::= BEGIN

 IMPORTS
	 enterprises		FROM RFC1155-SMI
	 OBJECT-TYPE            FROM RFC-1212
	 DisplayString          FROM RFC1213-MIB
	 SCinstance             FROM GDCMACRO-MIB;

 gdc			OBJECT IDENTIFIER ::= { enterprises 498 }
 dsx1           	OBJECT IDENTIFIER ::= { gdc 6 }
 uas7022	   	OBJECT IDENTIFIER ::= { dsx1 13 }

 uas7022Version         OBJECT IDENTIFIER ::= { uas7022 1 }
 uas7022Maintenance    	OBJECT IDENTIFIER ::= { uas7022 2 }
 uas7022Configuration	OBJECT IDENTIFIER ::= { uas7022 3 }
 uas7022Diagnostics	OBJECT IDENTIFIER ::= { uas7022 4 }
 uas7022Performance	OBJECT IDENTIFIER ::= { uas7022 5 }
 uas7022Alarms   	OBJECT IDENTIFIER ::= { uas7022 6 } 
 uas7022AlarmConfig   	OBJECT IDENTIFIER ::= { uas7022 7 } 
 
 -- This MIB module uses the extended OBJECT-TYPE macro as
 -- defined in RFC 1212.

 -- The implementation of all groups is mandatory for all products that
 -- support a E1 interface.

 -- Note:  All rows in all tables defined within this MIB module are
 -- virtual.  They can neither be created or deleted by management
 -- operations.

--****************************************************************************
-- 	SCinstance is defined as the addressing/indexing method of accessing
--	table objects in this MIB. The SCinstance represents the SpectraComm
--	shelf Slot, Line, Drop and interface address.
--	Represented as SLDi, (Slot, Line, Drop, interface).
--
--
-- 	For the uas7022: 
--
--		Byte		Range (dec.)		Identifies	
--		----		------------		----------
--		[S]lot		1 - 32			Physical Slot
--							1-16:  1st Shelf
--							17-32: 2nd Shelf
--
--		[L]ine		1
--		
--		[D]rop		0		
--
--		[i]nterface     0 - 2			0: Unit
--							1: NIU A
--							2: NIU B
--
-- ****************************************************************************
--
-- The Version Group. This group identifies the version information
-- for the MIB.
--

uas7022MIBversion OBJECT-TYPE
     SYNTAX DisplayString (SIZE (5))
     ACCESS read-only
     STATUS mandatory
     DESCRIPTION
	 "Identifies the version of the MIB. The format of the version
	 is x.yzT, where 'x' identifies the major revision number, 'y'
	 identifies the minor revision number, 'z' identifies the
	 typographical revision, and T identifies the test revision.
	 Acceptable values for the individual revision components are
	 as follows:

		 x: 1 - 9
		 y: 0 - 9
		 z: 0 - 9
		 T: A - Z

	 Upon formal release, no designation for the test revision will
	 be present."
     ::= { uas7022Version 1 }

-- ****************************************************************************
--                                Version Table
-- ****************************************************************************
	
uas7022VersionTable OBJECT-TYPE
    SYNTAX  SEQUENCE OF Uas7022VersionEntry
    ACCESS  not-accessible
    STATUS  mandatory
    DESCRIPTION 
	    "The 7022 version table "
    ::= { uas7022Version 2  }

uas7022VersionEntry OBJECT-TYPE
    SYNTAX  Uas7022VersionEntry
    ACCESS  not-accessible
    STATUS  mandatory
    DESCRIPTION
	    "An entry in the GDC uas7022 Version Table."
    INDEX  { uas7022VersionIndex }
    ::= { uas7022VersionTable 1 }
									
Uas7022VersionEntry ::=
    SEQUENCE {
	uas7022VersionIndex          SCinstance,
	uas7022ActiveFirmwareRev     DisplayString,
	uas7022StoredFirmwareRev     DisplayString,
	uas7022StoredFirmwareStatus  INTEGER,
	uas7022SwitchActiveFirmware  INTEGER,
	uas7022DownloadingMode       INTEGER
	}

uas7022VersionIndex OBJECT-TYPE
    SYNTAX  SCinstance
    ACCESS  read-only
    STATUS  mandatory
    DESCRIPTION
        "Integer value which uniquely identifies the UAS7022 to which this
         entry is applicable. SCinstance is defined to be SLDi where:
         S (byte value) - physical shelf slot location (01-32)
         L (byte value) - line number (01)
         D (byte value) - drop number (00)
         i (byte value) - interface number (00)"
    ::= { uas7022VersionEntry 1 }

uas7022ActiveFirmwareRev OBJECT-TYPE
    SYNTAX  DisplayString (SIZE(8))
    ACCESS  read-only
    STATUS  mandatory
    DESCRIPTION
        "The version number of the firmware currently executing.
	 The format is MM.NN.BB where:
		MM: Major Revision (0-99)
		NN: Minor Revision (0-99)
		BB: Bug Fix Revision (0-99)
	 Valid [i]nterface = 0"
    ::= { uas7022VersionEntry 2 }

uas7022StoredFirmwareRev OBJECT-TYPE
    SYNTAX DisplayString (SIZE(8))
    ACCESS read-only
    STATUS mandatory
    DESCRIPTION
        "The version number of the firmware stored (in a compressed format) 
         but not currently executing.
		MM: Major Revision (0-99)
		NN: Minor Revision (0-99)
		BB: Bug Fix Revision (0-99)
	 Valid [i]nterface = 0"
    ::= { uas7022VersionEntry 3 }

uas7022StoredFirmwareStatus OBJECT-TYPE
    SYNTAX INTEGER {
        statBlank(1),                       
        statDownLoading(2),
	statOK(3),
	statCheckSumBad(4),    
	statUnZipping(5),
	statBadUnZip(6),
	statDownloadAborted(7)
                    
    }
    ACCESS read-only
    STATUS mandatory
    DESCRIPTION
        "This object represents the state of the Non-Active or Stored firmware:

         statBlank(1)    	Factory Default                  
         statDownLoading(2)	In process of downloading firmware
	 statOK(3)		Zipped version checksum succesful (OK to switch)
				(can set uas7022SwitchActiveFirmware to	
				switchActive(2))
	 statCheckSumBad(4)    	Failed checksum after download
	 statUnZipping(5)	In process of uncompressing into active area
	 statBadUnZip(6)      	Failed last uncompress 
	 statDownloadAborted(7) Download aborted by user             

	 Valid [i]nterface = 0"
    ::= { uas7022VersionEntry 4 }


uas7022SwitchActiveFirmware OBJECT-TYPE
    SYNTAX INTEGER {
        switchNorm(1),                  -- Read only
        switchActive(2)			-- Write only
    }
    ACCESS read-write
    STATUS mandatory
    DESCRIPTION
        "This object is used to switch the active executing firmware from 
	 the version in uas7022ActiveFirmwareRev to the version in 
	 uas7022StoredFirmwareRev.

	 When a  switchActive(2) is set (write only) the element will:
		1) reboot
		2) uncompress stored code into active area
		3) perform checksum on active area
		4) Set uas7022StoredStatus object to indicate results
		5) If succesfull:
		    update uas7022ActiveFirmwareRev and uas7022StoredFirmwareRev
		    and begin executing
		   If failed: 
		    replace active area with previous revision

	 The switchNorm(1) enumeration will always be read. 

	 Setting switchActive(2) when the uas7022StoredFirmwareStatus is 
	 not statOK(3) will result in an error.
	 Valid [i]nterface = 0"
    ::= { uas7022VersionEntry 5 }


uas7022DownloadingMode OBJECT-TYPE
    SYNTAX INTEGER {
        disableAll(1),
        enableAndWait(2),
	enableAndSwitch(3)
    }
    ACCESS read-write
    STATUS mandatory
    DESCRIPTION
        "This object is used to configure the download mode:

         disableAll(1)	       Prevents any firmware downloading to UAS7022

         enableAndWait(2)      Allows downloading zipped code to be stored only!
								
	 enableAndSwitch(3)    Allows downloading and then unzips and begins executing
			       the new code
	 Valid [i]nterface = 0"
    ::= { uas7022VersionEntry 6 }



--
-- ********************************************************************
--  Maintenance Table
-- ********************************************************************

uas7022MaintenanceTable OBJECT-TYPE
    SYNTAX SEQUENCE OF Uas7022MaintenanceEntry
    ACCESS not-accessible
    STATUS mandatory
    DESCRIPTION
	"The uas7022 maintenance table."
    ::= { uas7022Maintenance 1  }

uas7022MaintenanceEntry OBJECT-TYPE
    SYNTAX Uas7022MaintenanceEntry
    ACCESS not-accessible
    STATUS mandatory
    DESCRIPTION
        "An entry in the 7022 Maintenance Table."
    INDEX  { uas7022MaintenanceLineIndex }
    ::= { uas7022MaintenanceTable 1 }

Uas7022MaintenanceEntry ::=
    SEQUENCE {
        uas7022MaintenanceLineIndex  SCinstance,
        uas7022SoftReset             INTEGER,
        uas7022SysUpTime	     INTEGER,
	uas7022DefaultInit	     INTEGER,
	uas7022LedStatus	     OCTET STRING,
        uas7022AlarmStatus    	     OCTET STRING,
	uas7022NearEndResetStats     INTEGER,
	uas7022FarEndResetStats	     INTEGER,
	uas7022NearEndStatLastInit   INTEGER,
	uas7022FarEndStatLastInit    INTEGER,
	uas7022NearEndValidIntervals INTEGER,
	uas7022FarEndValidIntervals  INTEGER,
	uas7022NIUaCircuitID         DisplayString,
	uas7022SystemTimingGenStatus INTEGER,
	uas7022NIUbCircuitID         DisplayString
    }

uas7022MaintenanceLineIndex OBJECT-TYPE
    SYNTAX SCinstance
    ACCESS read-only
    STATUS mandatory
    DESCRIPTION
        "Integer value which uniquely identifies the UAS7022 to which this
         entry is applicable. SCinstance is defined to be SLDi where:
         S (byte value) - physical shelf slot location (01-32)
         L (byte value) - line number (01)
         D (byte value) - drop number (00)
         i (byte value) - interface number (00-02)"
    ::= { uas7022MaintenanceEntry 1 }

uas7022SoftReset OBJECT-TYPE
    SYNTAX INTEGER {
	       norm(1),
	       reset(2)
	    }
    ACCESS read-write
    STATUS mandatory
    DESCRIPTION
        "Supports the action of soft resetting the unit.  When this
	 object is set to reset(2), then the unit performs a soft
	 reset, whose meaning is specific to the type of unit being
	 managed. The value of norm(1) will be returned when 
	 the reset is complete.
	 The value of norm(1) can not be set by management.
	 Valid [i]nterface = 0"
    ::= { uas7022MaintenanceEntry 2 }

uas7022SysUpTime OBJECT-TYPE
    SYNTAX INTEGER (1..2147483647)
    ACCESS read-only
    STATUS mandatory
    DESCRIPTION
	"This variable is used to report the elapsed system tick
	 time for conversion to real time at the controller and is
	 not related to the sysUpTime referenced in MIB-II.
	 Upon power-up of the unit, the elapsed time is cleared.
	 The elapsed time counter rolls over upon reaching the
	 maximum count.
	 Valid [i]nterface = 0"
    ::= { uas7022MaintenanceEntry 3 }

uas7022DefaultInit OBJECT-TYPE
    SYNTAX INTEGER {
	       normal(1),
	       factoryDefault(2)
	   }
    ACCESS read-write
    STATUS mandatory
    DESCRIPTION
	"This is used to allow the NonVolatile Configuration to 
	 be set to a factory default state.  When this value is set to
	 factoryDefault(1) the unit will perform
	 a reset to make the default configuration take affect. 
	 The value of normal(2) will be returned when the initialization
	 is complete.
	 The value of normal(2) can not be set by management.
	 Valid [i]nterface = 0"
    ::= { uas7022MaintenanceEntry 4 }

uas7022LedStatus OBJECT-TYPE
    SYNTAX  OCTET STRING (SIZE(3))
    ACCESS  read-only
    STATUS  mandatory
    DESCRIPTION
	"Returns a bitwise snapshot of the front panel LED state.
	 Octet 1 bit 7 - not used
		 bit 6 - future use
		 bit 5 - INSV
		 bit 4 - RSP
		 bit 3 - TMG
		 bit 2 - TM
		 bit 1 - ALM
		 bit 0 - future use

	 Octet 2 bit 7 - not used
		 bit 6 - future use
		 bit 5 - NIUA AIS
		 bit 4 - NIUA LCV
		 bit 3 - NIUA LOS
		 bit 2 - NIUA OOF
		 bit 1 - future use
		 bit 0 - future use

	 Octet 3 bit 7 - not used
		 bit 6 - ST- future use
		 bit 5 - NIUB AIS
		 bit 4 - NIUB LCV
		 bit 3 - NIUB LOS
		 bit 2 - NIUB OOF
		 bit 1 - future use
		 bit 0 - future use
	 Valid [i]nterface = 0"
    ::= { uas7022MaintenanceEntry 5 }

uas7022AlarmStatus OBJECT-TYPE
    SYNTAX OCTET STRING (SIZE(5))
    ACCESS read-only
    STATUS mandatory
    DESCRIPTION
	"Returns a bit-wise Status of alarms
	 Octet 1 bit 7 - not used
		 bit 6 - NIUA_LOS
		 bit 5 - NIUA_LOF
		 bit 4 - NIUA_AIS
		 bit 3 - NIUA_LCV
		 bit 2 - NIUA TIMING LOSS
		 bit 1 - NIUA_NE_ES
		 bit 0 - NIUA_NE_BBE

	 Octet 2 bit 7 - not used
		 bit 6 - NIUA_NE_SES
		 bit 5 - NIUA_NE_UAS
		 bit 4 - NIUA_FE_ES
		 bit 3 - NIUA_FE_BBE
		 bit 2 - NIUA_FE_SES
		 bit 1 - NIUA_FE_UAS
		 bit 0 - NIUA_RAI

	 Octet 3 bit 7 - not used
		 bit 6 - NIUB_LOS
		 bit 5 - NIUB_LOF
		 bit 4 - NIUB_AIS
		 bit 3 - NIUB_LCV
		 bit 2 - NIUB TIMING LOSS
		 bit 1 - NIUB_NE_ES
		 bit 0 - NIUB_NE_BBE

	 Octet 4 bit 7 - not used
		 bit 6 - NIUB_NE_SES
		 bit 5 - NIUB_NE_UAS
		 bit 4 - NIUB_FE_ES
		 bit 3 - NIUB_FE_BBE
		 bit 2 - NIUB_FE_SES
		 bit 1 - NIUB_FE_UAS
		 bit 0 - NIUB_RAI
	
	 Octet 5 bit 7 - not used
		 bit 6 - future use 
		 bit 5 - future use 
		 bit 4 - future use
		 bit 3 - future use 
		 bit 2 - future use 
		 bit 1 - future use 
		 bit 0 - Power-up Alarm
	 Valid [i]nterface = 0"
    ::= { uas7022MaintenanceEntry 6 }

uas7022NearEndResetStats OBJECT-TYPE
    SYNTAX INTEGER {
		norm(1),
		reset(2)
	   }
    ACCESS  read-write
    STATUS  mandatory
    DESCRIPTION
	"Supports the action of soft resetting the uas7022NearEndValidIntervals
	 object.  When this object is set to reset(2), then the unit
	 will reset the uas7022NearEndValidIntervals object to zero.
	 The value of norm(1) can not be set by management.
	 Valid [i]nterface = 1-2"
    ::= { uas7022MaintenanceEntry 7 }

uas7022FarEndResetStats OBJECT-TYPE
    SYNTAX INTEGER        {
	       	norm(1),
	   	reset(2)
	   }
    ACCESS  read-write
    STATUS  mandatory
    DESCRIPTION
	"Supports the action of soft resetting the uas7022FarEndValidIntervals
	 object.  When this object is set to reset(2), then the unit
	 will reset the uas7022FarEndValidIntervals object to zero.
	 The value of norm(1) can not be set by management.
	 Valid [i]nterface = 1-2"
    ::= { uas7022MaintenanceEntry 8 }

uas7022NearEndStatLastInit OBJECT-TYPE
    SYNTAX  INTEGER (1..2147483647)
    ACCESS  read-only
    STATUS  mandatory
    DESCRIPTION
	"Number of seconds from midnight Dec 31, 1969 up until
         uas7022NearEndValidIntervals was last initialized to zero
	 Valid [i]nterface = 1-2"
    ::= { uas7022MaintenanceEntry 9 }

uas7022FarEndStatLastInit OBJECT-TYPE
    SYNTAX  INTEGER (1..2147483647)
    ACCESS  read-only
    STATUS  mandatory
    DESCRIPTION
	"Number of seconds from midnight Dec 31, 1969 up until
         uas7022FarEndValidIntervals was last initialized to zero
	 Valid [i]nterface = 1-2"
    ::= { uas7022MaintenanceEntry 10 }

uas7022NearEndValidIntervals OBJECT-TYPE
    SYNTAX  INTEGER (0..16)
    ACCESS  read-only
    STATUS  mandatory
    DESCRIPTION
	"The number of  previous  intervals  for  which
	 valid data was collected.  The value will be 16
	 unless the interface was brought on-line within
	 the last 4 hours, in which case the value will
	 be the number of complete 15  minute  intervals
	 the since interface has been online.
	 Valid [i]nterface = 1-2"
    ::= { uas7022MaintenanceEntry 11 }

uas7022FarEndValidIntervals OBJECT-TYPE
    SYNTAX  INTEGER (0..16)
    ACCESS  read-only
    STATUS  mandatory
    DESCRIPTION
	"The number of  previous  intervals  for  which
         valid data was collected.  The value will be 16
	 unless the interface was brought on-line within
	 the last 4 hours, in which case the value will
	 be the number of complete 15  minute  intervals
	 the since interface has been online.
	 Valid [i]nterface = 1-2"
    ::= { uas7022MaintenanceEntry 12 }

uas7022NIUaCircuitID	OBJECT-TYPE
    SYNTAX DisplayString (SIZE(16))
    ACCESS read-write
    STATUS mandatory
    DESCRIPTION
    	"This variable is used for general purpose storage.
	 Valid [i]nterface = 1"
    ::= { uas7022MaintenanceEntry 13 }

uas7022SystemTimingGenStatus OBJECT-TYPE
    SYNTAX INTEGER {
	       none(1),
	       clk8khz(2),
	       clk4mhz(3),
	       clk8khzand4mhz(4)
	   }
    ACCESS read-only
    STATUS mandatory
    DESCRIPTION
	"Indicates if the units configured for primary or secondary
	 system clock are actually supplying clock and if it is the 
	 8hkz, 4mhz, or both.
	 Valid [i]nterface = 1-2"
    ::= { uas7022MaintenanceEntry 14 }

uas7022NIUbCircuitID	OBJECT-TYPE
    SYNTAX DisplayString (SIZE(16))
    ACCESS read-write
    STATUS mandatory
    DESCRIPTION
    	"This variable is used for general purpose storage.
	 Valid [i]nterface = 2"
    ::= { uas7022MaintenanceEntry 15 }


--
-- ********************************************************************
-- The Configuration Table
-- ********************************************************************

uas7022ConfigTable OBJECT-TYPE
    SYNTAX SEQUENCE OF Uas7022ConfigEntry
    ACCESS not-accessible
    STATUS mandatory
    DESCRIPTION
	"The Configuration table."
    ::= { uas7022Configuration 1 }

uas7022ConfigEntry OBJECT-TYPE
    SYNTAX Uas7022ConfigEntry
    ACCESS not-accessible
    STATUS mandatory
    DESCRIPTION
	"The Configuration table entry."
    INDEX { uas7022ConfigIndex }
    ::= { uas7022ConfigTable 1 }

Uas7022ConfigEntry ::= 
    SEQUENCE {
	uas7022ConfigIndex         SCinstance,
	uas7022RcvrRange           INTEGER,
	uas7022Framing             INTEGER,
	uas7022SysTimingGen        INTEGER,
	uas7022Highway             INTEGER,
	uas7022TransmitClockSource INTEGER,
	uas7022FallbackClockSource INTEGER,
	uas7022InterfaceType       INTEGER,
	uas7022FDLMode		   INTEGER,
	uas7022TimeSlot16Content   INTEGER,
	uas7022Impedance	   INTEGER
    }

uas7022ConfigIndex 	OBJECT-TYPE
    SYNTAX SCinstance
    ACCESS read-only
    STATUS mandatory
    DESCRIPTION
        "Integer value which uniquely identifies the UAS7022 to which this
         entry is applicable. SCinstance is defined to be SLDi where:
         S (byte value) - physical shelf slot location (01-32)
         L (byte value) - line number (01)
         D (byte value) - drop number (00)
         i (byte value) - interface number (01-02)"
    ::= { uas7022ConfigEntry 1 }

uas7022RcvrRange OBJECT-TYPE
    SYNTAX INTEGER {
		short(1),
		long(2)
	   }
    ACCESS read-write
    STATUS mandatory
    DESCRIPTION
	"Sets the receiver range to short (6dB) or long (36dB)
	 Valid [i]nterface = 1-2"
    ::= { uas7022ConfigEntry 2 }

uas7022Framing OBJECT-TYPE
    SYNTAX INTEGER {
		cCSwithoutCRC4(1),
		cASwithoutCRC4(2),
		cCSwithCRC4(3),
		cASwithCRC4(4)
	   }
    ACCESS read-write
    STATUS mandatory
    DESCRIPTION
	"Set the framing for the interface.
	 Abbreviations are as follows:
			CCS  -  common-channel signaling
			CAS  -  channel-associated signaling
	 Default is CAS
	 If uas7022Framing is CAS then TimeSlot 16 contains
	 idle code.  If uas7022Framing is CCS then TimeSlot
	 16 contains either marks or user data. See
	 uas7022TimeSlot16Content.
	 Valid [i]nterface = 1-2"
    ::= { uas7022ConfigEntry 3 }

uas7022SysTimingGen     OBJECT-TYPE 
    SYNTAX INTEGER {
		none(1),
		primary(2),
		secondary(3)
	   }
    ACCESS read-write
    STATUS mandatory
    DESCRIPTION
	"Selects if the unit provides system timing.
	 none(1)      - does not provide Timing Generator
	 primary(2)   - unit is primary Timing Generator for the shelf.
	 secondary(3) - unit is secondary Timing Generator for the 
		        shelf.
  	 Only 1 unit in the shelf can the primary or secondary 
	 timing generator. All other must be none.
	 Valid [i]nterface = 1-2"
    ::= { uas7022ConfigEntry 4 }

uas7022Highway      OBJECT-TYPE
    SYNTAX INTEGER {
		notAssigned(1),
		highway1(2),
		highway2(3),
		highway3(4),
		highway4(5),
		highway5(6),
		highway6(7),
		highway7(8),
		highway8(9)
   	   }
    ACCESS read-write
    STATUS mandatory
    DESCRIPTION
	"Defines the highway allocation. No two
	 NIU interfaces in the shelf can be assigned
	 to the same highway.
	 Valid [i]nterface = 1-2"
    ::= { uas7022ConfigEntry 5 }

uas7022TransmitClockSource OBJECT-TYPE
    SYNTAX INTEGER {
		system(1),
		recovered(2),
		internal(3)
            }
    ACCESS read-write
    STATUS mandatory
    DESCRIPTION
	"Sets the transmit clock source.
 	 Valid [i]nterface = 1-2"
    ::= { uas7022ConfigEntry 6 }

uas7022FallbackClockSource OBJECT-TYPE
    SYNTAX INTEGER {
		system(1),
		recovered(2),
		internal(3)
	    }
    ACCESS read-write
    STATUS mandatory
    DESCRIPTION
	"Identifies the fallback transmit clock source.
 	 Valid [i]nterface = 1-2"
    ::= { uas7022ConfigEntry 7 }

uas7022InterfaceType OBJECT-TYPE
    SYNTAX INTEGER {
		network(1),
		unassigned(2)
            }
    ACCESS read-write
    STATUS mandatory
    DESCRIPTION
	"Sets the interface type.
 	 Valid [i]nterface = 1-2"
    ::= { uas7022ConfigEntry 8 }

uas7022FDLMode OBJECT-TYPE
    SYNTAX INTEGER {
		none(1),
		active(2),
		inactive(3)
            }
    ACCESS read-write
    STATUS mandatory
    DESCRIPTION
	"Sets the interface type.
 	 Valid [i]nterface = 1-2"
    ::= { uas7022ConfigEntry 9 }

uas7022TimeSlot16Content OBJECT-TYPE
    SYNTAX INTEGER {
		idle (1),
		marks(2),
		data (3)
            }
    ACCESS read-write
    STATUS mandatory
    DESCRIPTION
	"Selects the content for TimeSlot 16.
 	 Valid [i]nterface = 1-2"
    ::= { uas7022ConfigEntry 10 }

uas7022Impedance OBJECT-TYPE
    SYNTAX INTEGER {
		impedance120Ohm(1),
		impedance75Ohm(2)
            }
    ACCESS read-write
    STATUS mandatory
    DESCRIPTION
	"Selects the impedance.
 	 Valid [i]nterface = 1-2"
    ::= { uas7022ConfigEntry 11}

-- ********************************************************************
-- Diagnostics
-- ********************************************************************

uas7022DiagTable OBJECT-TYPE
    SYNTAX SEQUENCE OF Uas7022DiagEntry
    ACCESS not-accessible
    STATUS mandatory
    DESCRIPTION
	"The Diagnostics table.  Information in the entries of
	 this table support diagnostics testing via loopbacks."
     ::= { uas7022Diagnostics 1 }

uas7022DiagEntry OBJECT-TYPE
    SYNTAX Uas7022DiagEntry
    ACCESS not-accessible
    STATUS mandatory
    DESCRIPTION
        "The Diagnostics table entry."
    INDEX { uas7022DiagIndex }
    ::= { uas7022DiagTable 1 }

Uas7022DiagEntry ::= 
    SEQUENCE {
        uas7022DiagIndex           SCinstance,
	uas7022DiagConfig          INTEGER,
	uas7022TestLimit           INTEGER,
	uas7022TestExecutionStatus INTEGER,
	uas7022TestExceptions      INTEGER
    }

uas7022DiagIndex OBJECT-TYPE
    SYNTAX SCinstance
    ACCESS read-only
    STATUS mandatory
    DESCRIPTION
        "Integer value which uniquely identifies the UAS7022 to which this
         entry is applicable. SCinstance is defined to be SLDi where:
         S (byte value) - physical shelf slot location (01-32)
         L (byte value) - line number (01)
         D (byte value) - drop number (00)
         i (byte value) - interface number (01-02)"
    ::= { uas7022DiagEntry 1 }

uas7022DiagConfig OBJECT-TYPE
    SYNTAX INTEGER {
		noLoop(1),
		lineLoopback(2),
		payloadLoopback(3)
            }
    ACCESS read-write
    STATUS mandatory
    DESCRIPTION
	"Selects the test to run. noLoop(1) ends the test.
	 Valid [i]nterface = 1-2"
    ::= { uas7022DiagEntry 2 }

uas7022TestLimit OBJECT-TYPE
    SYNTAX INTEGER {
		testTime10Mins(1),
		testTime20Mins(2),
		noLimit(3)
     	   }                  
    ACCESS read-write
    STATUS mandatory
    DESCRIPTION
        "Selects the duration to run a diagnostic test.  The value
	 noLimit(3) signifies that the test should run indefinitely until
	 explicitly terminated. 
	 Default value: testTime10Mins(1)
	 Valid [i]nterface = 1-2"
    ::= { uas7022DiagEntry 3 }

uas7022TestExecutionStatus OBJECT-TYPE
    SYNTAX INTEGER {
		notInTest(1),                  -- a test is not running
	 	testInProgress(2),             -- the test is running
	 	testCompleted(4),              -- the test is complete
	 	testCompletedNotInTest(5)      -- a test has completed,nolonger in test
	   }
    ACCESS read-only
    STATUS mandatory
    DESCRIPTION
        "This variable reports the status of a test.  notInTest(1) indicates
         a test is not running.  testInProgress(2) indicates that a test is
         currently running.  testCompleted(4) indicates that a test has run
         and is completed. testCompletedNotInTest(5) indicates that a test has
         completed and it is no longer in test.
 	 Valid [i]nterface = 1-2"
   ::= { uas7022DiagEntry 4 }

uas7022TestExceptions OBJECT-TYPE
    SYNTAX INTEGER (0..7)
    ACCESS read-only
    STATUS mandatory
    DESCRIPTION
       "Indicates exceptions that have occurred that may affect
	interpretation of the test results.
        The value of this object is a sum.  This sum initially take
	the value zero.  Then, for each exception, the value
	associated with the exception is added to the sum.

	The exception values are:
		 value  exception
		     1   a timed test was preempted so the result
			 cannot be viewed in relation to the test
			 duration
		     2   the results overflowed so the result cannot be
			 viewed as an absolute value
		     4   the test was performed while synchronization
			 could not be performed so the result may not
			 be accurate.
	 Valid [i]nterface = 1-2"
    ::= { uas7022DiagEntry 5 }



--
-- ********************************************************************
-- Near End Performance Tables
-- ********************************************************************


-- ********************************************************************
-- Current 15 Near End Minute Performance Table
-- ********************************************************************

uas7022NearEndCurrent15MinTable OBJECT-TYPE
    SYNTAX  SEQUENCE OF Uas7022NearEndCurrent15MinEntry
    ACCESS  not-accessible
    STATUS  mandatory
    DESCRIPTION
       "The uas7022 Near End Current table."
    ::= { uas7022Performance 1 }

uas7022NearEndCurrent15MinEntry OBJECT-TYPE
    SYNTAX  Uas7022NearEndCurrent15MinEntry
    ACCESS  not-accessible
    STATUS  mandatory
    DESCRIPTION
       "An entry in the uas7022 Near End Current table."
    INDEX   { uas7022NearEndCurrent15MinIndex }
    ::= { uas7022NearEndCurrent15MinTable 1 }

Uas7022NearEndCurrent15MinEntry ::=
    SEQUENCE {
	uas7022NearEndCurrent15MinIndex SCinstance,
        uas7022NearEndCurrent15MinStat  OCTET STRING
    }

uas7022NearEndCurrent15MinIndex    OBJECT-TYPE
    SYNTAX  SCinstance
    ACCESS  read-only
    STATUS  mandatory
    DESCRIPTION
        "Integer value which uniquely identifies the UAS7022 to which this
         entry is applicable. SCinstance is defined to be SLDi where:
         S (byte value) - physical shelf slot location (01-32)
         L (byte value) - line number (01)
         D (byte value) - drop number (00)
         i (byte value) - interface number (01-02)"
    ::= { uas7022NearEndCurrent15MinEntry 1 }

--
uas7022NearEndCurrent15MinStat    OBJECT-TYPE
    SYNTAX OCTET STRING (SIZE(12))
    ACCESS read-only
    STATUS mandatory
    DESCRIPTION
       "Returns a bitwise snapshot of the current 15Min statistics.
		1.7	f/u
		1.6	f/u
		1.5	f/u
		1.4	f/u
		1.3	f/u
		1.2	2^9	ES
		 .
		1.0	2^7

		2.7	f/u
		2.6	2^6
		  .
		2.0	2^0

		3.7	f/u
		3.6	f/u
		3.5	f/u
		3.4	f/u
		3.3	f/u
		3.2	2^9	SES
		  .
		3.0	2^7

		4.7	f/u
		4.6	2^6	SES
		 .
		4.0	2^0

		5.7	f/u
		5.6	f/u
		5.5	f/u
		5.4	f/u
		5.3	f/u
		5.2	Counter Overflow (>65535)	BBE
		5.1	2^15
		5.0	2^14

		6.7	f/u
		6.6	2^13	BBE
		  .
		6.0	2^7

		7.7	f/u
		7.6	2^6	BBE
		  .
		7.0	2^0

		8.7	f/u
		8.6	f/u
		8.5	f/u
		8.4	f/u
		8.3	f/u
		8.2	2^9	UAS
		 .
		8.0	2^7

		9.7	f/u
		9.6	2^6	UAS
		  .
		9.0	2^0

		10.7	f/u
		10.6	f/u
		10.5	f/u
		10.4	f/u
		10.3	f/u
		10.2	Counter Overflow (>65535)	LCV
		10.1	2^15
		10.0	2^14

		11.7	f/u
		11.6	2^13	LCV
		  .
		11.0	2^7

		12.7	f/u
		12.6	2^6	LCV
		  .
		12.0	2^0
	 Valid [i]nterface = 1-2"
    ::= {uas7022NearEndCurrent15MinEntry 2 }

--
-- ********************************************************************
-- Interval Near End Performance Table
-- ********************************************************************

uas7022NearEndIntervalTable OBJECT-TYPE
    SYNTAX  SEQUENCE OF Uas7022NearEndIntervalEntry
    ACCESS  not-accessible
    STATUS  mandatory
    DESCRIPTION
	"The uas7022 Near End Interval table."
    ::= { uas7022Performance 2 }


uas7022NearEndIntervalEntry OBJECT-TYPE
    SYNTAX  Uas7022NearEndIntervalEntry
    ACCESS  not-accessible
    STATUS  mandatory
    DESCRIPTION
	"An entry in the Near End Interval table."
    INDEX { uas7022NearEndIntervalIndex, uas7022NearEndIntervalNumber }
    ::= { uas7022NearEndIntervalTable 1 }

Uas7022NearEndIntervalEntry ::=
    SEQUENCE {
	uas7022NearEndIntervalIndex  SCinstance,
        uas7022NearEndIntervalNumber INTEGER,
	uas7022NearEndIntervalStat   OCTET STRING
    }

uas7022NearEndIntervalIndex OBJECT-TYPE
    SYNTAX  SCinstance
    ACCESS  read-only
    STATUS  mandatory
    DESCRIPTION
        "Integer value which uniquely identifies the UAS7022 to which this
         entry is applicable. SCinstance is defined to be SLDi where:
         S (byte value) - physical shelf slot location (01-32)
         L (byte value) - line number (01)
         D (byte value) - drop number (00)
         i (byte value) - interface number (01-02)"
    ::= { uas7022NearEndIntervalEntry 1 }

uas7022NearEndIntervalNumber OBJECT-TYPE
    SYNTAX INTEGER (1..16)
    ACCESS read-only
    STATUS mandatory
    DESCRIPTION
        "The number of Errored Seconds encountered by an E1
	 interface in one of the previous 16, individual 15 minute,
	 intervals."
    ::= {uas7022NearEndIntervalEntry 2 }

--
uas7022NearEndIntervalStat OBJECT-TYPE
    SYNTAX OCTET STRING (SIZE(12))
    ACCESS read-only
    STATUS mandatory
    DESCRIPTION
	"Returns a bitwise map of the
	 interface in one of the previous 16, individual 15 minute,
	 intervals.
		1.7	f/u
		1.6	f/u
		1.5	f/u
		1.4	f/u
		1.3	f/u
		1.2	2^9	ES
		 .
		1.0	2^7

		2.7	f/u
		2.6	2^6
		  .
		2.0	2^0

		3.7	f/u
		3.6	f/u
		3.5	f/u
		3.4	f/u
		3.3	f/u
		3.2	2^9	SES
		  .
		3.0	2^7

		4.7	f/u
		4.6	2^6	SES
		 .
		4.0	2^0

		5.7	f/u
		5.6	f/u
		5.5	f/u
		5.4	f/u
		5.3	f/u
		5.2	Counter Overflow (>65535)	BBE
		5.1	2^15
		5.0	2^14

		6.7	f/u
		6.6	2^13	BBE
		  .
		6.0	2^7

		7.7	f/u
		7.6	2^6	BBE
		  .
		7.0	2^0

		8.7	f/u
		8.6	f/u
		8.5	f/u
		8.4	f/u
		8.3	f/u
		8.2	2^9	UAS
		 .
		8.0	2^7

		9.7	f/u
		9.6	2^6	UAS
		  .
		9.0	2^0

		10.7	f/u
		10.6	f/u
		10.5	f/u
		10.4	f/u
		10.3	f/u
		10.2	Counter Overflow (>65535)	LCV
		10.1	2^15
		10.0	2^14

		11.7	f/u
		11.6	2^13	LCV
		  .
		11.0	2^7

		12.7	f/u
		12.6	2^6	LCV
		  .
		12.0	2^0
	 Valid [i]nterface = 1-2"
    ::= {uas7022NearEndIntervalEntry 3 }

-- ********************************************************************
-- Current 24 Hour Near End Performance Table
-- ********************************************************************

uas7022NearEndCurrent24HrTable OBJECT-TYPE
    SYNTAX  SEQUENCE OF Uas7022NearEndCurrent24HrEntry
    ACCESS  not-accessible
    STATUS  mandatory
    DESCRIPTION
	"The Near End Current 24 Hr table."
    ::= { uas7022Performance 3}

uas7022NearEndCurrent24HrEntry OBJECT-TYPE
    SYNTAX  Uas7022NearEndCurrent24HrEntry
    ACCESS  not-accessible
    STATUS  mandatory
    DESCRIPTION
        "An entry in the Near End Current 24 hr table."
    INDEX   { uas7022NearEndCurrent24HrIndex }
    ::= { uas7022NearEndCurrent24HrTable 1 }

Uas7022NearEndCurrent24HrEntry ::=
    SEQUENCE {
	uas7022NearEndCurrent24HrIndex  SCinstance,
	uas7022NearEndCurrent24HrStat   OCTET STRING
    }

uas7022NearEndCurrent24HrIndex OBJECT-TYPE
    SYNTAX  SCinstance
    ACCESS  read-only
    STATUS  mandatory
    DESCRIPTION
        "Integer value which uniquely identifies the UAS7022 to which this
         entry is applicable. SCinstance is defined to be SLDi where:
         S (byte value) - physical shelf slot location (01-32)
         L (byte value) - line number (01)
         D (byte value) - drop number (00)
         i (byte value) - interface number (01-02)"
    ::= { uas7022NearEndCurrent24HrEntry 1 }

 --
uas7022NearEndCurrent24HrStat OBJECT-TYPE
    SYNTAX OCTET STRING (SIZE (15))
    ACCESS read-only
    STATUS mandatory
    DESCRIPTION
	"Returns a bitwise map of the current 24 hour table
		1.7	f/u
		1.6	f/u
		1.5	f/u
		1.4	f/u
		1.3	f/u
		1.2	1: Counter Overflow (>65535)	ES
		1.1	2^15
		1.0	2^14

		2.7	f/u
		2.6	2^13				ES
		 .
		2.0	2^7

		3.7	f/u
		3.6	2^6				ES
		 .
		3.0	2^0

		4.7	f/u
		4.6	f/u
		4.5	f/u
		4.4	f/u
		4.3	f/u
		4.2	1: Counter Overflow (>65535)	SES
		4.1	2^15
		4.0	2^14

		5.7	f/u
		5.6	2^13				SES
		 .
		5.0	2^7

		6.7	f/u
		6.6	2^6				SES
		 .
		6.0	2^0

		7.7	f/u
		7.6	f/u
		7.5	f/u
		7.4	f/u
		7.3	f/u
		7.2	1: Counter Overflow (>65535)	BBE
		7.1	2^15
		7.0	2^14

		8.7	f/u
		8.6	2^13				BBE
		 .
		8.0	2^7

		9.7	f/u
		9.6	2^6				BBE
		 .
		9.0	2^0

		10.7	f/u
		10.6	f/u
		10.5	f/u
		10.4	f/u
		10.3	f/u
		10.2	1: Counter Overflow (>65535)	UAS
		10.1	2^15
		10.0	2^14

		11.7	f/u
		11.6	2^13				UAS
		 .
		11.0	2^7

		12.7	f/u
		12.6	2^6				UAS
		 .
		12.0	2^0

		13.7	f/u
		13.6	f/u
		13.5	f/u
		13.4	f/u
		13.3	f/u
		13.2	1: Counter Overflow (>65535)	LCV
		13.1	2^15
		13.0	2^14

		14.7	f/u
		14.6	2^13				LCV
		 .
		14.0	2^7

		15.7	f/u
		15.6	2^6				LCV
		 .
		15.0	2^0
	 Valid [i]nterface = 1-2"
   ::= {uas7022NearEndCurrent24HrEntry 2 }
--
-- ********************************************************************
-- Recent 24 Hour Near End Performance Table
-- ********************************************************************

uas7022NearEndRecent24HrTable OBJECT-TYPE
    SYNTAX  SEQUENCE OF Uas7022NearEndRecent24HrEntry
    ACCESS  not-accessible
    STATUS  mandatory
    DESCRIPTION
	"The Near End Recent 24Hr table."
    ::= { uas7022Performance 4}

uas7022NearEndRecent24HrEntry OBJECT-TYPE
    SYNTAX  Uas7022NearEndRecent24HrEntry
    ACCESS  not-accessible
    STATUS  mandatory
    DESCRIPTION
	"An entry in the E1 Total table."
    INDEX   { uas7022NearEndRecent24HrIndex }
    ::= { uas7022NearEndRecent24HrTable 1 }

Uas7022NearEndRecent24HrEntry ::=
    SEQUENCE {
	uas7022NearEndRecent24HrIndex SCinstance,
	uas7022NearEndRecent24HrStat  OCTET STRING
    }

uas7022NearEndRecent24HrIndex OBJECT-TYPE
    SYNTAX  SCinstance
    ACCESS  read-only
    STATUS  mandatory
    DESCRIPTION
        "Integer value which uniquely identifies the UAS7022 to which this
         entry is applicable. SCinstance is defined to be SLDi where:
         S (byte value) - physical shelf slot location (01-32)
         L (byte value) - line number (01)
         D (byte value) - drop number (00)
         i (byte value) - interface number (01-02)"
    ::= { uas7022NearEndRecent24HrEntry 1 }

--
uas7022NearEndRecent24HrStat OBJECT-TYPE
    SYNTAX OCTET STRING (SIZE (15))
    ACCESS read-only
    STATUS mandatory
    DESCRIPTION
	"Returns a bitwise map of the current 24 hour table
		1.7	f/u
		1.6	f/u
		1.5	f/u
		1.4	f/u
		1.3	f/u
		1.2	1: Counter Overflow (>65535)	ES
		1.1	2^15
		1.0	2^14

		2.7	f/u
		2.6	2^13				ES
		 .
		2.0	2^7

		3.7	f/u
		3.6	2^6				ES
		 .
		3.0	2^0

		4.7	f/u
		4.6	f/u
		4.5	f/u
		4.4	f/u
		4.3	f/u
		4.2	1: Counter Overflow (>65535)	SES
		4.1	2^15
		4.0	2^14

		5.7	f/u
		5.6	2^13				SES
		 .
		5.0	2^7

		6.7	f/u
		6.6	2^6				SES
		 .
		6.0	2^0

		7.7	f/u
		7.6	f/u
		7.5	f/u
		7.4	f/u
		7.3	f/u
		7.2	1: Counter Overflow (>65535)	BBE
		7.1	2^15
		7.0	2^14

		8.7	f/u
		8.6	2^13				BBE
		 .
		8.0	2^7

		9.7	f/u
		9.6	2^6				BBE
		 .
		9.0	2^0

		10.7	f/u
		10.6	f/u
		10.5	f/u
		10.4	f/u
		10.3	f/u
		10.2	1: Counter Overflow (>65535)	UAS
		10.1	2^15
		10.0	2^14

		11.7	f/u
		11.6	2^13				UAS
		 .
		11.0	2^7

		12.7	f/u
		12.6	2^6				UAS
		 .
		12.0	2^0

		13.7	f/u
		13.6	f/u
		13.5	f/u
		13.4	f/u
		13.3	f/u
		13.2	1: Counter Overflow (>65535)	LCV
		13.1	2^15
		13.0	2^14

		14.7	f/u
		14.6	2^13				LCV
		 .
		14.0	2^7

		15.7	f/u
		15.6	2^6				LCV
		 .
		15.0	2^0
	 Valid [i]nterface = 1-2"
    ::= {uas7022NearEndRecent24HrEntry 2 }

--
-- ********************************************************************
-- Near End Unavailable Time Registers
-- ********************************************************************

uas7022NearEndUnavailableTimeRegTable OBJECT-TYPE
    SYNTAX  SEQUENCE OF Uas7022NearEndUnavailableTimeRegEntry
    ACCESS  not-accessible
    STATUS  mandatory
    DESCRIPTION
	"The uas7022 Near End Unavailable Time Register table."
    ::= { uas7022Performance 9 }

uas7022NearEndUnavailableTimeRegEntry OBJECT-TYPE
    SYNTAX  Uas7022NearEndUnavailableTimeRegEntry
    ACCESS  not-accessible
    STATUS  mandatory
    DESCRIPTION
	"An entry in the Near End Unavailable Time Register table."
    INDEX   { uas7022NearEndUnavailableTimeRegIndex, uas7022NearEndUnavailableTimeRegNumber }
    ::= { uas7022NearEndUnavailableTimeRegTable 1 }

Uas7022NearEndUnavailableTimeRegEntry ::=
    SEQUENCE {
	uas7022NearEndUnavailableTimeRegIndex  SCinstance,
	uas7022NearEndUnavailableTimeRegNumber INTEGER,
	uas7022NearEndUnavailableTimeRegStart  INTEGER,
	uas7022NearEndUnavailableTimeRegStop   INTEGER
    }

uas7022NearEndUnavailableTimeRegIndex OBJECT-TYPE
    SYNTAX  SCinstance
    ACCESS  read-only
    STATUS  mandatory
    DESCRIPTION
        "Integer value which uniquely identifies the UAS7022 to which this
         entry is applicable. SCinstance is defined to be SLDi where:
         S (byte value) - physical shelf slot location (01-32)
         L (byte value) - line number (01)
         D (byte value) - drop number (00)
         i (byte value) - interface number (01-02)"
    ::= { uas7022NearEndUnavailableTimeRegEntry 1 }

uas7022NearEndUnavailableTimeRegNumber OBJECT-TYPE
    SYNTAX  INTEGER (1..6)
    ACCESS  read-only
    STATUS  mandatory
    DESCRIPTION
	"A number between 1 and 6, where the number is the number of the 
	 NearEndUnavailable Time Register.
	 Valid [i]nterface = 1-2"
    ::= { uas7022NearEndUnavailableTimeRegEntry 2 }

uas7022NearEndUnavailableTimeRegStart OBJECT-TYPE
    SYNTAX  INTEGER (1..2147483647)
    ACCESS  read-only
    STATUS  mandatory
    DESCRIPTION
	"Start time of one of the NearEndUnavailable Time Registers.
	 Valid [i]nterface = 1-2"
    ::= {uas7022NearEndUnavailableTimeRegEntry 3}

uas7022NearEndUnavailableTimeRegStop OBJECT-TYPE
    SYNTAX  INTEGER (1..2147483647)
    ACCESS  read-only
    STATUS  mandatory
    DESCRIPTION
	"Stop time of one of the NearEndUnavailable Time Registers.
	 Valid [i]nterface = 1-2"
    ::= {uas7022NearEndUnavailableTimeRegEntry 4}

--
-- ********************************************************************
-- Far End Performance Tables
-- ********************************************************************


-- ********************************************************************
-- Far End Current 15 Minute Performance Table
-- ********************************************************************

uas7022FarEndCurrent15MinTable OBJECT-TYPE
    SYNTAX  SEQUENCE OF Uas7022FarEndCurrent15MinEntry
    ACCESS  not-accessible
    STATUS  mandatory
    DESCRIPTION
	"The uas7022 Far End Current 15 minute table."
    ::= { uas7022Performance 5 }

uas7022FarEndCurrent15MinEntry OBJECT-TYPE
    SYNTAX  Uas7022FarEndCurrent15MinEntry
    ACCESS  not-accessible
    STATUS  mandatory
    DESCRIPTION
	"An entry in the uas7022 Far End Current 15 Minute table."
    INDEX   { uas7022FarEndCurrent15MinIndex }
    ::= { uas7022FarEndCurrent15MinTable 1 }

Uas7022FarEndCurrent15MinEntry ::=
    SEQUENCE {
	uas7022FarEndCurrent15MinIndex SCinstance,
	uas7022FarEndCurrent15MinStat  OCTET STRING
    }

uas7022FarEndCurrent15MinIndex OBJECT-TYPE
    SYNTAX  SCinstance
    ACCESS  read-only
    STATUS  mandatory
    DESCRIPTION
        "Integer value which uniquely identifies the UAS7022 to which this
         entry is applicable. SCinstance is defined to be SLDi where:
         S (byte value) - physical shelf slot location (01-32)
         L (byte value) - line number (01)
         D (byte value) - drop number (00)
         i (byte value) - interface number (01-02)"
    ::= { uas7022FarEndCurrent15MinEntry 1 }

--
uas7022FarEndCurrent15MinStat OBJECT-TYPE
    SYNTAX OCTET STRING (SIZE(9))
    ACCESS read-only
    STATUS mandatory
    DESCRIPTION
	"Returns a bitwise map of the far end
	 interface in one of the previous 16, individual 15 minute,
	 intervals.
		1.7	f/u
		1.6	f/u
		1.5	f/u
		1.4	f/u
		1.3	f/u
		1.2	2^9	ES
		 .
		1.0	2^7

		2.7	f/u
		2.6	2^6
		  .
		2.0	2^0

		3.7	f/u
		3.6	f/u
		3.5	f/u
		3.4	f/u
		3.3	f/u
		3.2	2^9	SES
		  .
		3.0	2^7

		4.7	f/u
		4.6	2^6	SES
		 .
		4.0	2^0

		5.7	f/u
		5.6	f/u
		5.5	f/u
		5.4	f/u
		5.3	f/u
		5.2	Counter Overflow (>65535)	BBE
		5.1	2^15
		5.0	2^14

		6.7	f/u
		6.6	2^13	BBE
		  .
		6.0	2^7

		7.7	f/u
		7.6	2^6	BBE
		  .
		7.0	2^0

		8.7	f/u
		8.6	f/u
		8.5	f/u
		8.4	f/u
		8.3	f/u
		8.2	2^9	UAS
		 .
		8.0	2^7

		9.7	f/u
		9.6	2^6	UAS
		  .
		9.0	2^0
	 Valid [i]nterface = 1-2"
    ::= {uas7022FarEndCurrent15MinEntry 2 }


--
-- ********************************************************************
-- Interval Far End Performance Table
-- ********************************************************************

uas7022FarEndIntervalTable OBJECT-TYPE
    SYNTAX  SEQUENCE OF Uas7022FarEndIntervalEntry
    ACCESS  not-accessible
    STATUS  mandatory
    DESCRIPTION
	"The uas7022 FarEnd Interval table."
    ::= { uas7022Performance 6 }

uas7022FarEndIntervalEntry OBJECT-TYPE
    SYNTAX  Uas7022FarEndIntervalEntry
    ACCESS  not-accessible
    STATUS  mandatory
    DESCRIPTION
	"An entry in the Interval table."
    INDEX   { uas7022FarEndIntervalIndex, uas7022FarEndIntervalNumber }
    ::= { uas7022FarEndIntervalTable 1 }

Uas7022FarEndIntervalEntry ::=
    SEQUENCE {
	uas7022FarEndIntervalIndex  SCinstance,
	uas7022FarEndIntervalNumber INTEGER,
	uas7022FarEndIntervalStat   OCTET STRING
    }

uas7022FarEndIntervalIndex OBJECT-TYPE
    SYNTAX  SCinstance
    ACCESS  read-only
    STATUS  mandatory
    DESCRIPTION
        "Integer value which uniquely identifies the UAS7022 to which this
         entry is applicable. SCinstance is defined to be SLDi where:
         S (byte value) - physical shelf slot location (01-32)
         L (byte value) - line number (01)
         D (byte value) - drop number (00)
         i (byte value) - interface number (01-02)"
    ::= { uas7022FarEndIntervalEntry 1 }

uas7022FarEndIntervalNumber OBJECT-TYPE
    SYNTAX  INTEGER (1..16)
    ACCESS  read-only
    STATUS  mandatory
    DESCRIPTION
	"A number between 1 and 16, where 1 is the most recently completed 
	 15 minute interval and 16 is the least recently completed 15 minutes  
	 interval   (assuming   that  all  16  intervals  are valid)."
    ::= { uas7022FarEndIntervalEntry 2 }

uas7022FarEndIntervalStat     OBJECT-TYPE
    SYNTAX OCTET STRING (SIZE(9))
    ACCESS read-only
    STATUS mandatory
    DESCRIPTION
	"Returns a bitwise map of statistics for the far end
	 interface in the current 15 minute interval.
		1.7	f/u
		1.6	f/u
		1.5	f/u
		1.4	f/u
		1.3	f/u
		1.2	2^9	ES
		 .
		1.0	2^7

		2.7	f/u
		2.6	2^6
		  .
		2.0	2^0

		3.7	f/u
		3.6	f/u
		3.5	f/u
		3.4	f/u
		3.3	f/u
		3.2	2^9	SES
		  .
		3.0	2^7

		4.7	f/u
		4.6	2^6	SES
		 .
		4.0	2^0

		5.7	f/u
		5.6	f/u
		5.5	f/u
		5.4	f/u
		5.3	f/u
		5.2	Counter Overflow (>65535)	BBE
		5.1	2^15
		5.0	2^14

		6.7	f/u
		6.6	2^13	BBE
		  .
		6.0	2^7

		7.7	f/u
		7.6	2^6	BBE
		  .
		7.0	2^0

		8.7	f/u
		8.6	f/u
		8.5	f/u
		8.4	f/u
		8.3	f/u
		8.2	2^9	UAS
		 .
		8.0	2^7

		9.7	f/u
		9.6	2^6	UAS
		  .
		9.0	2^0
	 Valid [i]nterface = 1-2"
    ::= {uas7022FarEndIntervalEntry 3 }

--
-- ********************************************************************
-- Current 24 Hour Far End Performance Table
-- ********************************************************************

uas7022FarEndCurrent24HrTable OBJECT-TYPE
    SYNTAX  SEQUENCE OF Uas7022FarEndCurrent24HrEntry
    ACCESS  not-accessible
    STATUS  mandatory
    DESCRIPTION
	"The Far End Current 24 Hour table."
    ::= { uas7022Performance 7 }

uas7022FarEndCurrent24HrEntry OBJECT-TYPE
    SYNTAX  Uas7022FarEndCurrent24HrEntry
    ACCESS  not-accessible
    STATUS  mandatory
    DESCRIPTION
	"An entry in the Far End Current 24 Hr table."
    INDEX   { uas7022FarEndCurrent24HrIndex }
    ::= { uas7022FarEndCurrent24HrTable 1 }

Uas7022FarEndCurrent24HrEntry ::=
    SEQUENCE {
	uas7022FarEndCurrent24HrIndex SCinstance,
	uas7022FarEndCurrent24HrStat  OCTET STRING
    }

uas7022FarEndCurrent24HrIndex OBJECT-TYPE
    SYNTAX  SCinstance
    ACCESS  read-only
    STATUS  mandatory
    DESCRIPTION
        "Integer value which uniquely identifies the UAS7022 to which this
         entry is applicable. SCinstance is defined to be SLDi where:
         S (byte value) - physical shelf slot location (01-32)
         L (byte value) - line number (01)
         D (byte value) - drop number (00)
         i (byte value) - interface number (01-02)"
    ::= { uas7022FarEndCurrent24HrEntry 1 }

--
uas7022FarEndCurrent24HrStat OBJECT-TYPE
    SYNTAX OCTET STRING (SIZE(12))
    ACCESS read-only
    STATUS mandatory
    DESCRIPTION
	"Returns a bitwise map of statistics for the
	 interface in the current 24 hour interval.
		1.7	f/u
		1.6	f/u
		1.5	f/u
		1.4	f/u
		1.3	f/u
		1.2	1: Counter Overflow (>65535)	ES
		1.1	2^15
		1.0	2^14

		2.7	f/u
		2.6	2^13				ES
		 .
		2.0	2^7

		3.7	f/u
		3.6	2^6				ES
		 .
		3.0	2^0

		4.7	f/u
		4.6	f/u
		4.5	f/u
		4.4	f/u
		4.3	f/u
		4.2	1: Counter Overflow (>65535)	SES
		4.1	2^15
		4.0	2^14

		5.7	f/u
		5.6	2^13				SES
		 .
		5.0	2^7

		6.7	f/u
		6.6	2^6				SES
		 .
		6.0	2^0

		7.7	f/u
		7.6	f/u
		7.5	f/u
		7.4	f/u
		7.3	f/u
		7.2	1: Counter Overflow (>65535)	BBE
		7.1	2^15
		7.0	2^14

		8.7	f/u
		8.6	2^13				BBE
		 .
		8.0	2^7

		9.7	f/u
		9.6	2^6				BBE
		 .
		9.0	2^0

		10.7	f/u
		10.6	f/u
		10.5	f/u
		10.4	f/u
		10.3	f/u
		10.2	1: Counter Overflow (>65535)	UAS
		10.1	2^15
		10.0	2^14

		11.7	f/u
		11.6	2^13				UAS
		 .
		11.0	2^7

		12.7	f/u
		12.6	2^6				UAS
		 .
		12.0	2^0
	 Valid [i]nterface = 1-2"
    ::= {uas7022FarEndCurrent24HrEntry 2 }

--
-- ********************************************************************
-- Far End Recent 24 Hour Performance Table
-- ********************************************************************

uas7022FarEndRecent24HrTable OBJECT-TYPE
    SYNTAX  SEQUENCE OF Uas7022FarEndRecent24HrEntry
    ACCESS  not-accessible
    STATUS  mandatory
    DESCRIPTION
	"The Far End Recent 24 Hour table."
    ::= { uas7022Performance 8 }

uas7022FarEndRecent24HrEntry OBJECT-TYPE
    SYNTAX  Uas7022FarEndRecent24HrEntry
    ACCESS  not-accessible
    STATUS  mandatory
    DESCRIPTION
	"An entry in the Far End Recent 24 Hr table."
    INDEX   { uas7022FarEndRecent24HrIndex }
    ::= { uas7022FarEndRecent24HrTable 1 }

Uas7022FarEndRecent24HrEntry ::=
    SEQUENCE {
	uas7022FarEndRecent24HrIndex SCinstance,
	uas7022FarEndRecent24HrStat  OCTET STRING
    }

uas7022FarEndRecent24HrIndex OBJECT-TYPE
    SYNTAX  SCinstance
    ACCESS  read-only
    STATUS  mandatory
    DESCRIPTION
        "Integer value which uniquely identifies the UAS7022 to which this
         entry is applicable. SCinstance is defined to be SLDi where:
         S (byte value) - physical shelf slot location (01-32)
         L (byte value) - line number (01)
         D (byte value) - drop number (00)
         i (byte value) - interface number (01-02)"
    ::= { uas7022FarEndRecent24HrEntry 1 }

uas7022FarEndRecent24HrStat OBJECT-TYPE
    SYNTAX OCTET STRING (SIZE(12))
    ACCESS read-only
    STATUS mandatory
    DESCRIPTION
	"Returns a bitwise map of statistics for the
	 interface in the Recent 24 hour interval.
		1.7	f/u
		1.6	f/u
		1.5	f/u
		1.4	f/u
		1.3	f/u
		1.2	1: Counter Overflow (>65535)	ES
		1.1	2^15
		1.0	2^14

		2.7	f/u
		2.6	2^13				ES
		 .
		2.0	2^7

		3.7	f/u
		3.6	2^6				ES
		 .
		3.0	2^0

		4.7	f/u
		4.6	f/u
		4.5	f/u
		4.4	f/u
		4.3	f/u
		4.2	1: Counter Overflow (>65535)	SES
		4.1	2^15
		4.0	2^14

		5.7	f/u
		5.6	2^13				SES
		 .
		5.0	2^7

		6.7	f/u
		6.6	2^6				SES
		 .
		6.0	2^0

		7.7	f/u
		7.6	f/u
		7.5	f/u
		7.4	f/u
		7.3	f/u
		7.2	1: Counter Overflow (>65535)	BBE
		7.1	2^15
		7.0	2^14

		8.7	f/u
		8.6	2^13				BBE
		 .
		8.0	2^7

		9.7	f/u
		9.6	2^6				BBE
		 .
		9.0	2^0

		10.7	f/u
		10.6	f/u
		10.5	f/u
		10.4	f/u
		10.3	f/u
		10.2	1: Counter Overflow (>65535)	UAS
		10.1	2^15
		10.0	2^14

		11.7	f/u
		11.6	2^13				UAS
		 .
		11.0	2^7

		12.7	f/u
		12.6	2^6				UAS
		 .
		12.0	2^0
	 Valid [i]nterface = 1-2"
   ::= {uas7022FarEndRecent24HrEntry 2 }


-- 
-- ********************************************************************
-- Far End Unavailable Time Registers
-- ********************************************************************
uas7022FarEndUnavailableTimeRegTable OBJECT-TYPE
    SYNTAX  SEQUENCE OF Uas7022FarEndUnavailableTimeRegEntry
    ACCESS  not-accessible
    STATUS  mandatory
    DESCRIPTION
	"The uas7022 Far End Unavailable Time Register table."
    ::= { uas7022Performance 10 }

uas7022FarEndUnavailableTimeRegEntry OBJECT-TYPE
    SYNTAX  Uas7022FarEndUnavailableTimeRegEntry
    ACCESS  not-accessible
    STATUS  mandatory
    DESCRIPTION
	"An entry in the Far End Unavailable Time Register table."
    INDEX   { uas7022FarEndUnavailableTimeRegIndex, uas7022FarEndUnavailableTimeRegNumber }
    ::= { uas7022FarEndUnavailableTimeRegTable 1 }

Uas7022FarEndUnavailableTimeRegEntry ::=
    SEQUENCE {
	uas7022FarEndUnavailableTimeRegIndex  SCinstance,
	uas7022FarEndUnavailableTimeRegNumber INTEGER,
	uas7022FarEndUnavailableTimeRegStart  INTEGER,
	uas7022FarEndUnavailableTimeRegStop   INTEGER
    }

uas7022FarEndUnavailableTimeRegIndex OBJECT-TYPE
    SYNTAX  SCinstance
    ACCESS  read-only
    STATUS  mandatory
    DESCRIPTION
        "Integer value which uniquely identifies the UAS7022 to which this
         entry is applicable. SCinstance is defined to be SLDi where:
         S (byte value) - physical shelf slot location (01-32)
         L (byte value) - line number (01)
         D (byte value) - drop number (00)
         i (byte value) - interface number (01-02)"
    ::= { uas7022FarEndUnavailableTimeRegEntry 1 }

uas7022FarEndUnavailableTimeRegNumber OBJECT-TYPE
    SYNTAX  INTEGER (1..6)
    ACCESS  read-only
    STATUS  mandatory
    DESCRIPTION
	"A number between 1 and 6, where the number is the number of the 
	 Unavailable Time Register.
	 Valid [i]nterface = 1-2"
   ::= { uas7022FarEndUnavailableTimeRegEntry 2 }

uas7022FarEndUnavailableTimeRegStart OBJECT-TYPE
    SYNTAX  INTEGER (1..2147483647)
    ACCESS  read-only
    STATUS  mandatory
    DESCRIPTION
	"Start time of one of the Unavailable Time Registers.
	 Valid [i]nterface = 1-2"
    ::= {uas7022FarEndUnavailableTimeRegEntry 3}

uas7022FarEndUnavailableTimeRegStop OBJECT-TYPE
    SYNTAX  INTEGER (1..2147483647)
    ACCESS  read-only
    STATUS  mandatory
    DESCRIPTION
	"Stop time of one of the Unavailable Time Registers.
	 Valid [i]nterface = 1-2"
    ::= {uas7022FarEndUnavailableTimeRegEntry 4}

--
-- ********************************************************************
-- Alarm Object Identifier Definitions
-- ********************************************************************

uas7022NoResponseAlm	OBJECT IDENTIFIER ::= { uas7022Alarms 1  }
uas7022DiagRxErrAlm	OBJECT IDENTIFIER ::= { uas7022Alarms 2  }
uas7022PowerUpAlm	OBJECT IDENTIFIER ::= { uas7022Alarms 3  }
uas7022TimingLoss       OBJECT IDENTIFIER ::= { uas7022Alarms 4  }
uas7022LCV		OBJECT IDENTIFIER ::= { uas7022Alarms 5  }
uas7022LossOfSignal     OBJECT IDENTIFIER ::= { uas7022Alarms 6  }
uas7022LossOfFrame      OBJECT IDENTIFIER ::= { uas7022Alarms 7  }
uas7022AlarmIndSignal	OBJECT IDENTIFIER ::= { uas7022Alarms 8  }
uas7022NEES		OBJECT IDENTIFIER ::= { uas7022Alarms 9  }
uas7022NEBBE		OBJECT IDENTIFIER ::= { uas7022Alarms 10 }
uas7022NESES		OBJECT IDENTIFIER ::= { uas7022Alarms 11 }
uas7022NEUAS		OBJECT IDENTIFIER ::= { uas7022Alarms 12 }
uas7022FEES		OBJECT IDENTIFIER ::= { uas7022Alarms 13 }
uas7022FEBBE		OBJECT IDENTIFIER ::= { uas7022Alarms 14 }
uas7022FESES		OBJECT IDENTIFIER ::= { uas7022Alarms 15 }
uas7022FEUAS		OBJECT IDENTIFIER ::= { uas7022Alarms 16 }
uas7022RAI		OBJECT IDENTIFIER ::= { uas7022Alarms 17 }

-- ALARM                     Maskable      Valid interfaces         window/thres
-- ====================================================================================
-- uas7022NoResponseAlm		no		unit			no
-- uas7022DiagRxErrAlm		no		unit			no
-- uas7022PowerUpAlm		no		unit			no
-- uas7022TimingLoss		yes		NIUA/NIUB		no
-- uas7022LCV			yes		NIUA/NIUB		yes
-- uas7022LossofSignal		yes		NIUA/NIUB		no
-- uas7022LossOfFrame		yes		NIUA/NIUB		no
-- uas7022Ais			yes		NIUA/NIUB		no
-- uas7022NEES			yes		NIUA/NIUB		yes
-- uas7022NEBBE			yes		NIUA/NIUB		yes
-- uas7022NESES			yes		NIUA/NIUB		yes
-- uas7022NEUAS			yes		NIUA/NIUB		yes
-- uas7022FEES			yes		NIUA/NIUB		yes
-- uas7022FEBBE			yes		NIUA/NIUB		yes
-- uas7022FESES			yes		NIUA/NIUB		yes
-- uas7022FEUAS			yes		NIUA/NIUB		yes
-- uas7022RAI			yes		NIUA/NIUB		no
-- 

--
-- ********************************************************************
-- GDC UAS7022 Alarm Configuration
-- ********************************************************************

-- ********************************************************************
-- Near End Alarm Configuration
-- ********************************************************************
uas7022NearEndAlarmConfigTable OBJECT-TYPE
    SYNTAX SEQUENCE OF Uas7022NearEndAlarmConfigEntry
    ACCESS not-accessible
    STATUS mandatory
    DESCRIPTION
	"The uas7022NearEndAlarmConfigTable contains entries that configure 
	 alarm  reporting.  The structure of the table is such that alarm
	 configuration is supported on a unit and interface basis, and
	 then on an alarm type basis within the interface."
    ::= { uas7022AlarmConfig 1 }

uas7022NearEndAlarmConfigEntry OBJECT-TYPE
    SYNTAX Uas7022NearEndAlarmConfigEntry
    ACCESS not-accessible
    STATUS mandatory
    DESCRIPTION
	"An entry in the Near End Alarm Configuration table."
    INDEX { uas7022NearEndAlarmConfigIndex, uas7022NearEndAlarmConfigIdentifier }
    ::= { uas7022NearEndAlarmConfigTable 1 }

Uas7022NearEndAlarmConfigEntry ::=
    SEQUENCE {
	uas7022NearEndAlarmConfigIndex      SCinstance,
	uas7022NearEndAlarmConfigIdentifier OBJECT IDENTIFIER,
	uas7022NearEndAlarmCountWindow      INTEGER,
	uas7022NearEndAlarmCountThreshold   INTEGER
    }

uas7022NearEndAlarmConfigIndex OBJECT-TYPE
    SYNTAX SCinstance
    ACCESS read-only
    STATUS mandatory
    DESCRIPTION
        "Integer value which uniquely identifies the UAS7022 to which this
         entry is applicable. SCinstance is defined to be SLDi where:
         S (byte value) - physical shelf slot location (01-32)
         L (byte value) - line number (01)
         D (byte value) - drop number (00)
         i (byte value) - interface number (01-02)"
    ::= { uas7022NearEndAlarmConfigEntry 1 }

uas7022NearEndAlarmConfigIdentifier OBJECT-TYPE
    SYNTAX OBJECT IDENTIFIER
    ACCESS read-only
    STATUS mandatory
    DESCRIPTION
    "format: iso.org.dod.internet.private.enterprises.gdc.
             dsx1.uas7022.uas7022Alarms.ALM
     example:  1.3.6.1.4.1.498.6.13.6.ALM
     where ALM = 1 for uas7022NoResponse alarm, 2 for uas7022DiagRxErr alarm,
                 etc., as specified in the Alarm Definitions above."
    ::= { uas7022NearEndAlarmConfigEntry 2 }

uas7022NearEndAlarmCountWindow OBJECT-TYPE
    SYNTAX INTEGER{
		disabled(1),
		last1sec(2),
		last10sec(3),
		last30sec(4),
		last1min(5),
		last15min(6),
		last1hr(7),
		last24hr(8),
		infinite(9)
	   }
    ACCESS  read-write
    STATUS  mandatory
    DESCRIPTION
	"This variable sets/reads the alarm window.
 	 This window is used with the alarm threshold to determine
	 how long the alarm should be active before reporting.
         Default: disabled(1)"
    ::= { uas7022NearEndAlarmConfigEntry 3 }

uas7022NearEndAlarmCountThreshold OBJECT-TYPE
    SYNTAX INTEGER {
		thresGT1(1),
		thresGT3(2),
		thresGT10(3),
		thresGT100(4),
		thresGT1000(5),
		thresGT10000(6)
	   }
    ACCESS  read-write
    STATUS  mandatory
    DESCRIPTION
	"This function sets/reads the alarm threshold criteria.
 	 This threshold is used along with the the alarm window to 
	 determine the number of instances in a given time frame for
	 an alarm to occur before the alarm is considered active.
	 Default: thresGT1(1)"
    ::= { uas7022NearEndAlarmConfigEntry 4 }

-- ********************************************************************
-- Far End Alarm Configuration
-- ********************************************************************

uas7022FarEndAlarmConfigTable OBJECT-TYPE
    SYNTAX SEQUENCE OF Uas7022FarEndAlarmConfigEntry
    ACCESS not-accessible
    STATUS mandatory
    DESCRIPTION
	"The uas7022FarEndAlarmConfigTable contains entries that configure alarm
	 reporting.  The structure of the table is such that alarm
	 configuration is supported on a unit and interface basis, and
	 then on an alarm type basis within the interface."
    ::= { uas7022AlarmConfig 2 }

uas7022FarEndAlarmConfigEntry OBJECT-TYPE
    SYNTAX Uas7022FarEndAlarmConfigEntry
    ACCESS not-accessible
    STATUS mandatory
    DESCRIPTION
	 "An entry in the Far End Alarm Configuration table."
    INDEX { uas7022FarEndAlarmConfigIndex, uas7022FarEndAlarmConfigIdentifier }
    ::= { uas7022FarEndAlarmConfigTable 1 }

Uas7022FarEndAlarmConfigEntry ::=
    SEQUENCE {
	uas7022FarEndAlarmConfigIndex      SCinstance,
	uas7022FarEndAlarmConfigIdentifier OBJECT IDENTIFIER,
	uas7022FarEndAlarmCountWindow      INTEGER,
	uas7022FarEndAlarmCountThreshold   INTEGER
    }

uas7022FarEndAlarmConfigIndex OBJECT-TYPE
    SYNTAX SCinstance
    ACCESS read-only
    STATUS mandatory
    DESCRIPTION
        "Integer value which uniquely identifies the UAS7022 to which this
         entry is applicable. SCinstance is defined to be SLDi where:
         S (byte value) - physical shelf slot location (01-32)
         L (byte value) - line number (01)
         D (byte value) - drop number (00)
         i (byte value) - interface number (01-02)"
    ::= { uas7022FarEndAlarmConfigEntry 1 }

uas7022FarEndAlarmConfigIdentifier OBJECT-TYPE
    SYNTAX OBJECT IDENTIFIER
    ACCESS read-only
    STATUS mandatory
    DESCRIPTION
    "format: iso.org.dod.internet.private.enterprises.gdc.
             dsx1.uas7022.uas7022Alarms.ALM
     example:  1.3.6.1.4.1.498.6.13.6.ALM
     where ALM = 1 for uas7022NoResponse alarm, 2 for uas7022DiagRxErr alarm,
                 etc., as specified in the Alarm Definitions above."

    ::= { uas7022FarEndAlarmConfigEntry 2 }

uas7022FarEndAlarmCountWindow OBJECT-TYPE
    SYNTAX INTEGER {
		disabled(1),
		last1sec(2),
		last10sec(3),
		last30sec(4),
		last1min(5),
		last15min(6),
		last1hr(7),
		last24hr(8),
		infinite(9)
	   }
    ACCESS  read-write
    STATUS  mandatory
    DESCRIPTION
	"This variable sets/reads the alarm window.
	 This window is used with the alarm threshold to determine
	 how long the alarm should be active before reporting.
	 Default: disabled(1)"
    ::= { uas7022FarEndAlarmConfigEntry 3 }

uas7022FarEndAlarmCountThreshold OBJECT-TYPE
    SYNTAX INTEGER {
		thresGT1(1),
		thresGT3(2),
		thresGT10(3),
		thresGT100(4),
		thresGT1000(5),
		thresGT10000(6)
	   }
     ACCESS  read-write
     STATUS  mandatory
     DESCRIPTION
	 "This function sets/reads the alarm threshold criteria.
	  This threshold is used along with the the alarm window to 
	  determine the number of instances in a given time frame for
	  an alarm to occur before the alarm is considered active.
	  Default: thresGT1(1)"
     ::= { uas7022FarEndAlarmConfigEntry 4 }

--
-- ********************************************************************
-- GDC Local UAS7022 Alarm Configuration
-- ********************************************************************
-- Local Alarms are alarms that optionally activate the backplane
-- Major or Minor buses. These alarms changes are never reported in an
-- unsolicited message to the proxy agent hence, the reason for the alarm
-- card. These alarms are different from the previously defined alarms
-- in that the mask state has three possible values.

uas7022LocalAlarmConfigTable OBJECT-TYPE
    SYNTAX SEQUENCE OF Uas7022LocalAlarmConfigEntry
    ACCESS not-accessible
    STATUS mandatory
    DESCRIPTION
	"The uas7022LocalAlarmConfigTable contains entries 
	 that configure alarm reporting to the alarm card."
     ::= { uas7022AlarmConfig 3 }

uas7022LocalAlarmConfigEntry OBJECT-TYPE
    SYNTAX Uas7022LocalAlarmConfigEntry
    ACCESS not-accessible
    STATUS mandatory
    DESCRIPTION
	"An entry in the Local Alarm Configuration table."
    INDEX { uas7022LocalAlarmConfigIndex }
    ::= { uas7022LocalAlarmConfigTable 1 }

Uas7022LocalAlarmConfigEntry ::=
    SEQUENCE {
	uas7022LocalAlarmConfigIndex SCinstance,
	uas7022UASNE                 INTEGER,
	uas7022SESNE                 INTEGER,
	uas7022BBENE                 INTEGER,
	uas7022ESNE                  INTEGER,
	uas7022UASFE                 INTEGER,
	uas7022SESFE                 INTEGER,
	uas7022BBEFE                 INTEGER,
	uas7022ESFE                  INTEGER,
	uas7022LOS                   INTEGER,
	uas7022LOF                   INTEGER,
	uas7022AIS                   INTEGER,
	uas7022TmgLoss               INTEGER,
	uas7022LCVs                  INTEGER,
	uas7022NtwkRAI               INTEGER
    }

uas7022LocalAlarmConfigIndex OBJECT-TYPE
    SYNTAX SCinstance
    ACCESS read-only
    STATUS mandatory
    DESCRIPTION
        "Integer value which uniquely identifies the UAS7022 to which this
         entry is applicable. SCinstance is defined to be SLDi where:
         S (byte value) - physical shelf slot location (01-32)
         L (byte value) - line number (01)
         D (byte value) - drop number (00)
         i (byte value) - interface number (01-02)"
    ::= { uas7022LocalAlarmConfigEntry 1 }

uas7022UASNE OBJECT-TYPE
    SYNTAX INTEGER {
		disabled(1),
		enabledMajor(2),
		enabledMinor(3)
		}
    ACCESS  read-write
    STATUS  mandatory
    DESCRIPTION
	"Disables or enables the alarm on the Major buss or Minor
	 buss.
	 Valid [i]nterface = 1-2"
    ::= { uas7022LocalAlarmConfigEntry 2 }

uas7022SESNE       OBJECT-TYPE
    SYNTAX INTEGER {
		disabled(1),
		enabledMajor(2),
		enabledMinor(3)
		}
    ACCESS  read-write
    STATUS  mandatory
    DESCRIPTION
	"Disables or enables the alarm on the Major buss or Minor
	 buss.
	 Valid [i]nterface = 1-2"
    ::= { uas7022LocalAlarmConfigEntry 3 }

uas7022BBENE       OBJECT-TYPE
    SYNTAX INTEGER {
		disabled(1),
		enabledMajor(2),
		enabledMinor(3)
		}
    ACCESS  read-write
    STATUS  mandatory
    DESCRIPTION
	"Disables or enables the alarm on the Major buss or Minor
	 buss.
	 Valid [i]nterface = 1-2"
    ::= { uas7022LocalAlarmConfigEntry 4 }

uas7022ESNE       OBJECT-TYPE
    SYNTAX INTEGER {
		disabled(1),
		enabledMajor(2),
		enabledMinor(3)
		}
    ACCESS  read-write
    STATUS  mandatory
    DESCRIPTION
	"Disables or enables the alarm on the Major buss or Minor
	 buss.
	 Valid [i]nterface = 1-2"
    ::= { uas7022LocalAlarmConfigEntry 5 }

uas7022UASFE       OBJECT-TYPE
    SYNTAX INTEGER {
		disabled(1),
		enabledMajor(2),
		enabledMinor(3)
		}
    ACCESS  read-write
    STATUS  mandatory
    DESCRIPTION
	"Disables or enables the alarm on the Major buss or Minor
	 buss.
	 Valid [i]nterface = 1-2"
    ::= { uas7022LocalAlarmConfigEntry 6 }

uas7022SESFE       OBJECT-TYPE
    SYNTAX INTEGER {
		disabled(1),
		enabledMajor(2),
		enabledMinor(3)
		}
    ACCESS  read-write
    STATUS  mandatory
    DESCRIPTION
	"Disables or enables the alarm on the Major buss or Minor
	 buss.
	 Valid [i]nterface = 1-2"
    ::= { uas7022LocalAlarmConfigEntry 7 }

uas7022BBEFE       OBJECT-TYPE
    SYNTAX INTEGER {
		disabled(1),
		enabledMajor(2),
		enabledMinor(3)
		}
    ACCESS  read-write
    STATUS  mandatory
    DESCRIPTION
	"Disables or enables the alarm on the Major buss or Minor
	 buss.
	 Valid [i]nterface = 1-2"
    ::= { uas7022LocalAlarmConfigEntry 8 }

uas7022ESFE       OBJECT-TYPE
    SYNTAX INTEGER {
		disabled(1),
		enabledMajor(2),
		enabledMinor(3)
		}
    ACCESS  read-write
    STATUS  mandatory
    DESCRIPTION
	"Disables or enables the alarm on the Major buss or Minor
	 buss.
	 Valid [i]nterface = 1-2"
    ::= { uas7022LocalAlarmConfigEntry 9 }

uas7022LOS       OBJECT-TYPE
    SYNTAX INTEGER {
		disabled(1),
		enabledMajor(2),
		enabledMinor(3)
		}
    ACCESS  read-write
    STATUS  mandatory
    DESCRIPTION
	"Disables or enables the alarm on the Major buss or Minor
	 buss.
	 Valid [i]nterface = 1-2"
    ::= { uas7022LocalAlarmConfigEntry 10 }

uas7022LOF       OBJECT-TYPE
    SYNTAX INTEGER {
		disabled(1),
		enabledMajor(2),
		enabledMinor(3)
		}
    ACCESS  read-write
    STATUS  mandatory
    DESCRIPTION
	"Disables or enables the alarm on the Major buss or Minor
	 buss.
	 Valid [i]nterface = 1-2"
    ::= { uas7022LocalAlarmConfigEntry 11 }

uas7022AIS       OBJECT-TYPE
    SYNTAX INTEGER {
		disabled(1),
		enabledMajor(2),
		enabledMinor(3)
		}
    ACCESS  read-write
    STATUS  mandatory
    DESCRIPTION
	"Disables or enables the alarm on the Major buss or Minor
	 buss.
	 Valid [i]nterface = 1-2"
    ::= { uas7022LocalAlarmConfigEntry 12 }

uas7022TmgLoss       OBJECT-TYPE
    SYNTAX INTEGER {
		disabled(1),
		enabledMajor(2),
		enabledMinor(3)
		}
    ACCESS  read-write
    STATUS  mandatory
    DESCRIPTION
	"Disables or enables the alarm on the Major buss or Minor
	 buss.
	 Valid [i]nterface = 1-2"
    ::= { uas7022LocalAlarmConfigEntry 13 }

uas7022LCVs       OBJECT-TYPE
    SYNTAX INTEGER {
		disabled(1),
		enabledMajor(2),
		enabledMinor(3)
		}
    ACCESS  read-write
    STATUS  mandatory
    DESCRIPTION
	"Disables or enables the alarm on the Major buss or Minor
	 buss.
	 Valid [i]nterface = 1-2"
    ::= { uas7022LocalAlarmConfigEntry 14 }

uas7022NtwkRAI    OBJECT-TYPE
    SYNTAX INTEGER {
		disabled(1),
		enabledMajor(2),
		enabledMinor(3)
		}
    ACCESS  read-write
    STATUS  mandatory
    DESCRIPTION
	"Disables or enables the alarm on the Major buss or Minor
	 buss.
	 Valid [i]nterface = 1-2"
    ::= { uas7022LocalAlarmConfigEntry 15 }

END
