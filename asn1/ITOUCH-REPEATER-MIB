-- $Id: it-repeater-mib.mib,v 1.3 2001/07/25 15:14:53 sse Exp $
           ITOUCH-REPEATER-MIB DEFINITIONS ::= BEGIN

                    IMPORTS
                            Counter, TimeTicks, Gauge
                                    FROM RFC1155-SMI
                            DisplayString
                                    FROM RFC1213-MIB
                            MacAddress
                                    FROM BRIDGE-MIB
                            OBJECT-TYPE
                                    FROM RFC-1212
                            TRAP-TYPE
                                    FROM RFC-1215
                            iTouch, TypedAddress
                                    FROM ITOUCH-MIB;

            hubDeprecated   OBJECT IDENTIFIER ::= { iTouch 9 }
            xRepeater       OBJECT IDENTIFIER ::= { iTouch 17 }

            -- MIB Groups

            xRepeaterInfo       OBJECT IDENTIFIER ::= { xRepeater 1 }
            xRepeaterGroupInfo  OBJECT IDENTIFIER ::= { xRepeater 2 }
            xRepeaterPortInfo   OBJECT IDENTIFIER ::= { xRepeater 3 }
            xRepeaterSlotInfo   OBJECT IDENTIFIER ::= { xRepeater 4 }
            xRepeaterSecurity   OBJECT IDENTIFIER ::= { xRepeater 5 }
            xRepeaterRepeater   OBJECT IDENTIFIER ::= { xRepeater 6 }
            xRepeaterRedundancy OBJECT IDENTIFIER ::= { xRepeater 7 }

            -- This is a MIB module for all iTouch Ethernet repeaters.

            -- Copyright 2000 iTouch Communications, Inc. All Rights Reserved.
            -- Reproduction of this document is authorized on
            -- condition that this copyright notice is included.
            -- This MIB document embodies iTouch Communications, Inc.'s 
            -- proprietary intellectual property.  iTouch Communications, Inc.
            -- retains all title and ownership in this MIB, including any
            -- revisions.
            --
            -- It is iTouch Communications, Inc.'s intent to encourage the
            -- widespread use of this MIB in connection with the management of
            -- iTouch Communications, Inc. products. iTouch Communications,
            -- Inc. grants vendors,end-users, and other interested parties a
            -- non-exclusive license to use this MIB in connection with the
            -- management of iTouch Communications, Inc. products.
            --
            -- This MIB document is supplied "AS IS," and iTouch 
            -- Communications, Inc. makes no warranty, either express or
            -- implied, as to the use operation, condition, or performance of
            -- the MIB.


            -- Textual Conventions

            Segment ::=
                INTEGER { a(1), b(2), c(3), d(4), e(5), f(6), g(7),
                          h(8), i(9), j(10), k(11), l(12), m(13),
                          n(14), o(15), p(16), q(17), r(18), s(19),
                          t(20), u(21), v(22), w(23), x(24), y(25),
                          z(26), disabled(27), notApplicable(28) }
            -- This data type is used in the ITouch Repeater MIB
            -- to identify a Network 9000 network segment.  Except
            -- for the final two values, it is the same as the
            -- ITouch Chassis MIB convention named Letter.

            Repeater ::=
                INTEGER { notApplicable(1), repeater1(2),
                                 repeater2(3), repeater3(4) }
            -- This data type is used in the ITouch Repeater MIB to
            -- identify a logical repeater in repeaters that implement
            -- non-proxy management for logical repeaters.


            -- the Repeater Basic Information group

            -- Implementation of this group is mandatory for all ITouch
            -- Ethernet repeaters that support SNMP management

            repeaterAccessViolation OBJECT-TYPE
                SYNTAX INTEGER { both(1), disable(2), trap(3) }
                ACCESS read-write
                STATUS mandatory
                DESCRIPTION
                    "Controls action to take when an access violation 
                    occurs."
                DEFVAL { disable }
                ::= { xRepeaterInfo 1 }

            repeaterMyGroup OBJECT-TYPE
                SYNTAX INTEGER
                ACCESS read-only
                STATUS mandatory
                DESCRIPTION
                    "The index value of the group that is directly 
                    associated with the agent.  The snmp support for the 
                    group associated with the agent is a superset of the 
                    support for other groups."
                ::= { xRepeaterInfo 2 }

            repeaterFifoOverflows OBJECT-TYPE
                SYNTAX Counter
                ACCESS read-only
                STATUS deprecated
                DESCRIPTION
                    "Deprecated, use repeaterRepeaterFifoOverflows in the
                     repeaterRepeater group for the desired repeater."
                ::= { xRepeaterInfo 3 }

            repeaterLEDDisplay OBJECT-TYPE
                SYNTAX INTEGER { activity(1), collisions(2) }
                ACCESS read-write
                STATUS mandatory
                DESCRIPTION
                    "Controls reason for flashing front panel LEDs."
                DEFVAL { activity }
                ::= { xRepeaterInfo 4 }

            repeaterReports OBJECT-TYPE
                SYNTAX INTEGER { disabled(1), enabled(2) }
                ACCESS read-write
                STATUS deprecated
                DESCRIPTION
                    "Deprecated, use repeaterRepeaterReports in the
                     repeaterRepeater group for the desired repeater on
                     which report generation is to be controlled."
                DEFVAL { enabled }
                ::= { xRepeaterInfo 5 }

            repeaterHealthTrap OBJECT-TYPE
                SYNTAX INTEGER { disabled(1), enabled(2) }
                ACCESS read-write
                STATUS mandatory
                DESCRIPTION
                    "Controls the generation of the repeater health trap."
                DEFVAL { enabled }
                ::= { xRepeaterInfo 6 }

            repeaterStatusChangeTrap OBJECT-TYPE
                SYNTAX INTEGER { disabled(1), enabled(2) }
                ACCESS read-write
                STATUS mandatory
                DESCRIPTION
                    "Controls the generation of the repeater status change
                    trap."
                DEFVAL { enabled }
                ::= { xRepeaterInfo 7 }

            repeaterAccessViolationTrap OBJECT-TYPE
                SYNTAX INTEGER { disabled(1), enabled(2) }
                ACCESS read-write
                STATUS mandatory
                DESCRIPTION
                    "Controls the generation of the repeater access
                    violation trap."
                DEFVAL { enabled }
                ::= { xRepeaterInfo 8 }

            repeaterIntegrityLossTrap OBJECT-TYPE
                SYNTAX INTEGER { disabled(1), enabled(2) }
                ACCESS read-write
                STATUS mandatory
                DESCRIPTION
                    "Controls the generation of the repeater integrity
                    loss trap."
                DEFVAL { disabled }
                ::= { xRepeaterInfo 9 }

            repeaterRedundancyPathChangeTrap OBJECT-TYPE
                SYNTAX INTEGER { disabled(1), enabled(2) }
                ACCESS read-write
                STATUS mandatory
                DESCRIPTION
                    "Controls the generation of the repeater redundancy
					path change trap."
                DEFVAL { enabled }
                ::= { xRepeaterInfo 10 }


            -- the Repeater Group group

            -- Implementation of this group is mandatory for all ITouch
            -- Ethernet repeaters that support SNMP management

            -- the Group table

            repeaterGroupTable OBJECT-TYPE
                SYNTAX SEQUENCE OF RepeaterGroupEntry
                ACCESS not-accessible
                STATUS mandatory
                DESCRIPTION
                    "Table of descriptive and status information about 
                    the groups."
                ::= { xRepeaterGroupInfo 1 }

            repeaterGroupEntry OBJECT-TYPE
                SYNTAX RepeaterGroupEntry
                ACCESS not-accessible
                STATUS mandatory
                DESCRIPTION
                    "An entry in the table, containing information about 
                    a group."
                INDEX { repeaterGroupIndex }
                ::= { repeaterGroupTable 1 }

            RepeaterGroupEntry ::=
                SEQUENCE {
                    repeaterGroupIndex
                        INTEGER,
                    repeaterGroupSQE
                        Counter,
                    repeaterGroupJabbers
                        Counter,
                    repeaterGroupSegment
                        Segment,
                    repeaterGroupSecurityLock
                        INTEGER,
                    repeaterGroupIOCardType
                        INTEGER,
                    repeaterGroupIOCardFirmwareVersion
                        INTEGER,
                    repeaterGroupIOCardOperStatus
                        INTEGER,
                    repeaterGroupManagement
                        INTEGER,
                    repeaterGroupRepeaterNumber
                        INTEGER,
                    repeaterGroupRepeaterHardwareVersion
                        INTEGER,
                    repeaterGroupManagerRepeater
                        Repeater,
                    repeaterGroupFifoErrors
                        Counter,
                    repeaterGroupCpuUtilization
                        INTEGER,
                    repeaterGroupMemoryUtilization
                        INTEGER,
                    repeaterGroupAlarmCount
                        INTEGER
                }

            repeaterGroupIndex OBJECT-TYPE
                SYNTAX INTEGER
                ACCESS read-only
                STATUS mandatory
                DESCRIPTION
                    "This variable identifies the group within the  
                    repeater for which this entry contains information.  
                    This value is the same as  rptrGroupIndex."
                ::= { repeaterGroupEntry 1 }

            repeaterGroupSQE OBJECT-TYPE
                SYNTAX Counter
                ACCESS read-only
                STATUS deprecated
                DESCRIPTION
                    "Deprecated, use repeaterRepeaterSQE in the
                     repeaterRepeaterGroup for the SQE count on the
                     desired repeater.  This object will always return
                     the count for repeater #1."
                ::= { repeaterGroupEntry 2 }

            repeaterGroupJabbers OBJECT-TYPE
                SYNTAX Counter
                ACCESS read-only
                STATUS deprecated
                DESCRIPTION
                    "Deprecated, use repeaterRepeaterJabbers in the
                     repeaterRepeaterGroup for the Jabber count on the
                     desired repeater.  This object will always return
                     the count for repeater #1."
                ::= { repeaterGroupEntry 3 }

            repeaterGroupSegment OBJECT-TYPE
                SYNTAX Segment
                ACCESS read-write
                STATUS deprecated
                DESCRIPTION
                    "Deprecated, use repeaterRepeaterSegment in the
                     repeaterRepeaterGroup to control the segment
                     mapping for the desired repeater.  This object will
                     always control the mapping for repeater #1."
                ::= { repeaterGroupEntry 4 }

            repeaterGroupSecurityLock OBJECT-TYPE
                SYNTAX INTEGER { unlocked(1), locked(2) }
                ACCESS read-write
                STATUS mandatory
                DESCRIPTION
                    "This variable indicates the state of security 
                    lockdown on an unmanaged repeater.  The only 
                    writable value is 'unlocked'."
                ::= { repeaterGroupEntry 5 }

            repeaterGroupIOCardType OBJECT-TYPE
                SYNTAX INTEGER
                ACCESS read-only
                STATUS mandatory
                DESCRIPTION
                    "The hardware type of the I/O card, as defined in 
                    ITouch Assigned Numbers."
                ::= { repeaterGroupEntry 6 }

            repeaterGroupIOCardFirmwareVersion OBJECT-TYPE
                SYNTAX INTEGER
                ACCESS read-only
                STATUS mandatory
                DESCRIPTION
                    "The firmware revision level of the I/O card ROM."
                ::= { repeaterGroupEntry 7 }

            repeaterGroupIOCardOperStatus OBJECT-TYPE
                SYNTAX INTEGER { loadRequested(1),
                                 loading(2),
                                 dumpRequested(3),
                                 dumping(4),
                                 paramRequested(5),
                                 paramLoading(6),
                                 running(7),
                                 initializing(8),     -- ROM wait
                                 attended(9),         -- in config menu
                                 internal10(10),      -- read chas info
                                 internal11(11),      -- read config
                                 inhibited(12),       -- run inhibited
                                 maxserverCard(13),
                                 invalidConfigStorage(14), -- suspended
                                 securityLockdown(15) }
                ACCESS read-only
                STATUS mandatory
                DESCRIPTION
                    "Relative to the chassis, the current operating 
                    status of the I/O card."
                ::= { repeaterGroupEntry 8 }

            repeaterGroupManagement OBJECT-TYPE
                SYNTAX INTEGER { minimal(1), full(2) }
                ACCESS read-only
                STATUS mandatory
                DESCRIPTION
                    "This variable indicates the level of management 
                    control and observation available."
                ::= { repeaterGroupEntry 9 }

            repeaterGroupRepeaterNumber OBJECT-TYPE
                SYNTAX INTEGER
                ACCESS read-only
                STATUS mandatory
                DESCRIPTION
                    "The number of logical repeaters visible via this 
                    repeater."
                ::= { repeaterGroupEntry 10 }

            repeaterGroupRepeaterHardwareVersion OBJECT-TYPE
                SYNTAX INTEGER
                ACCESS read-only
                STATUS mandatory
                DESCRIPTION
                    "The repeater chip set hardware revision level."
                ::= { repeaterGroupEntry 11 }

            repeaterGroupManagerRepeater OBJECT-TYPE
                SYNTAX Repeater
                ACCESS read-write
                STATUS mandatory
                DESCRIPTION
                    "The logical repeater to which the manager card, if 
                    present, is attached."
                ::= { repeaterGroupEntry 12 }

            repeaterGroupFifoErrors OBJECT-TYPE
                SYNTAX Counter
                ACCESS read-only
                STATUS mandatory
                DESCRIPTION
                    "This variable will reflect the number of times that the report
                    FIFO has gone out of synchronization."
                ::= { repeaterGroupEntry 13 }

            repeaterGroupCpuUtilization OBJECT-TYPE
                SYNTAX INTEGER (0..10000)
                ACCESS read-only
                STATUS mandatory
                DESCRIPTION
                    "The average CPU utilization for the processor which
                    maintains statistics and implements monitoring for the
                    group, expressed as percentage times 100."
                ::= { repeaterGroupEntry 14 }

            repeaterGroupMemoryUtilization OBJECT-TYPE
                SYNTAX INTEGER (0..10000)
                ACCESS read-only
                STATUS mandatory
                DESCRIPTION
                    "The current memory utilization for the processor which
                    maintains statistics and implements monitoring for the
                    group, expressed as percentage used times 100."
                ::= { repeaterGroupEntry 15 }

            repeaterGroupAlarmCount OBJECT-TYPE
                SYNTAX INTEGER
                ACCESS read-only
                STATUS mandatory
                DESCRIPTION
                    "The number of alarms currently being monitored by the
                    processor for comparison with RMON thresholds."
                ::= { repeaterGroupEntry 16 }


            -- the Repeater Port group

            -- Implementation of this group is mandatory for all ITouch
            -- Ethernet repeaters that support SNMP management

            -- the Port table

            repeaterPortTable OBJECT-TYPE
                SYNTAX SEQUENCE OF RepeaterPortEntry
                ACCESS not-accessible
                STATUS mandatory
                DESCRIPTION
                    "Table of descriptive and status information about 
                    the ports."
                ::= { xRepeaterPortInfo 1 }

            repeaterPortEntry OBJECT-TYPE
                SYNTAX RepeaterPortEntry
                ACCESS not-accessible
                STATUS mandatory
                DESCRIPTION
                    "An entry in the table, containing information about 
                    a port."
                INDEX { repeaterPortGroupIndex, repeaterPortIndex }
                ::= { repeaterPortTable 1 }

            RepeaterPortEntry ::=
                SEQUENCE {
                    repeaterPortGroupIndex
                        INTEGER,
                    repeaterPortIndex
                        INTEGER,
                    repeaterPortName
                        DisplayString,
                    repeaterPortAutoPolarity
                        INTEGER,
                    repeaterPortPolarityDirection
                        INTEGER,
                    repeaterPortPulse
                        INTEGER,
                    repeaterPortPulseStatus
                        INTEGER,
                    repeaterPortPulseLosses
                        Counter,
                    repeaterPortDistance
                        INTEGER,
                    repeaterPortSofMissing
                        Counter,
                    repeaterPortMCVs
                        Counter,
                    repeaterPortZero
                        INTEGER,
                    repeaterPortSinceZero
                        TimeTicks,
                    repeaterPortAccessAction
                        INTEGER,
                    repeaterPortAccessState
                        INTEGER,
                    repeaterPortAccessType
                        INTEGER,
                    repeaterPortAccessAllStatus
                        INTEGER,
                    repeaterPortPortLastViolationAddress
                        MacAddress,
                    repeaterPortPortAddressViolations
                        Counter,
                    repeaterPortSegment
                        Segment,
                    repeaterPortAccessLearn
                        INTEGER,
                    repeaterPortEthernetRepeater
                        INTEGER,
                    repeaterPortRepeatersAllowed
                        OCTET STRING,
                    repeaterPortGlobalSecurityAddress
                        MacAddress,
                    repeaterPortGlobalAddressChanges
                        Counter,
                    repeaterPortPercentUtilization
                        Gauge
                }

            repeaterPortGroupIndex OBJECT-TYPE
                SYNTAX INTEGER
                ACCESS read-only
                STATUS mandatory
                DESCRIPTION
                    "This variable identifies the group containing the 
                    port for which this entry contains infromation."
                ::= { repeaterPortEntry 1 }

            repeaterPortIndex OBJECT-TYPE
                SYNTAX INTEGER
                ACCESS read-only
                STATUS mandatory
                DESCRIPTION
                    "This variable identifies the port within the group 
                    within the repeater for which this entry contains 
                    management information.  This value can never be 
                    greater than rptrGroupPortCapacity for the 
                    associated group."
                ::= { repeaterPortEntry 2 }

            repeaterPortName OBJECT-TYPE
                SYNTAX DisplayString (SIZE (0..16))
                ACCESS read-write
                STATUS mandatory
                DESCRIPTION
                    "The port's display name."
                ::= { repeaterPortEntry 3 }

            repeaterPortAutoPolarity OBJECT-TYPE
                SYNTAX INTEGER { disabled(1), enabled(2) }
                ACCESS read-write
                STATUS mandatory
                DESCRIPTION
                    "Controls whether the port will automatically 
                    determine  its polarity."
                DEFVAL { enabled }
                ::= { repeaterPortEntry 4 }

            repeaterPortPolarityDirection OBJECT-TYPE
                SYNTAX INTEGER { reversed(1), normal(2), unknown(3) }
                ACCESS read-only
                STATUS mandatory
                DESCRIPTION
                    "If repeaterPortAutoPolarity is enabled, this is the 
                    current polarity of the port."
                ::= { repeaterPortEntry 5 }

            repeaterPortPulse OBJECT-TYPE
                SYNTAX INTEGER { disabled(1), enabled(2) }
                ACCESS read-write
                STATUS mandatory
                DESCRIPTION
                    "Controls whether the port will periodically 
                    generate a test pulse to determine the status of the 
                    port."
                DEFVAL { enabled }
                ::= { repeaterPortEntry 6 }

            repeaterPortPulseStatus OBJECT-TYPE
                SYNTAX INTEGER { notDetected(1), detected(2) }
                ACCESS read-only
                STATUS mandatory
                DESCRIPTION
                    "If repeaterPortPulse is enabled, this is indicates 
                    whether the test pulse response is being detected."
                ::= { repeaterPortEntry 7 }

            repeaterPortPulseLosses OBJECT-TYPE
                SYNTAX Counter
                ACCESS read-only
                STATUS mandatory
                DESCRIPTION
                    "The number of times that a test pulse has been sent  
                    and a response was not received."
                ::= { repeaterPortEntry 8 }

            repeaterPortDistance OBJECT-TYPE
                SYNTAX INTEGER { disabled(1), enabled(2) }
                ACCESS read-write
                STATUS mandatory
                DESCRIPTION
                    "Controls whether the port will support extended 
                    distances on the port."
                DEFVAL { enabled }
                ::= { repeaterPortEntry 9 }

            repeaterPortSofMissing OBJECT-TYPE
                SYNTAX Counter
                ACCESS read-only
                STATUS mandatory
                DESCRIPTION
                    "The number of times that alternating zero/one bits 
                    were seen after an inter-packet gap and were not 
                    followed by two one bits."
                ::= { repeaterPortEntry 10 }

            repeaterPortMCVs OBJECT-TYPE
                SYNTAX Counter
                ACCESS read-only
                STATUS mandatory
                DESCRIPTION
                    "The number of manchester violation errors detected 
                    on this port."
                ::= { repeaterPortEntry 11 }

            repeaterPortZero OBJECT-TYPE
                SYNTAX INTEGER { ready(1), execute(2) }
                ACCESS read-write
                STATUS mandatory
                DESCRIPTION
                    "Control to zero the hub port's counters.  The agent 
                    always returns 'ready' for this value.  Setting the 
                    value to 'ready' has no effect."
                ::= { repeaterPortEntry 12 }

            repeaterPortSinceZero OBJECT-TYPE
                SYNTAX TimeTicks
                ACCESS read-only
                STATUS mandatory
                DESCRIPTION
                    "Number of time ticks since the port's counters were 
                    zeroed."
                ::= { repeaterPortEntry 13 }

            repeaterPortAccessAction OBJECT-TYPE
                SYNTAX INTEGER { discard(1), accept(2) }
                ACCESS read-write
                STATUS mandatory
                DESCRIPTION
                    "Control whether packets will be accepted or 
                    discarded if they are in the access list.  The 
                    inverse action is applied to packets from all 
                    addresses not in the list."
                DEFVAL { discard }
                ::= { repeaterPortEntry 14 }

            repeaterPortAccessState OBJECT-TYPE
                SYNTAX INTEGER { disabled(1), notDisabled(2) }
                ACCESS read-only 
                STATUS mandatory
                DESCRIPTION
                    "Indicates whether the port was disabled due to 
                    receiving a frame from an invalid source address."
                ::= { repeaterPortEntry 15 }

            repeaterPortAccessType OBJECT-TYPE
                SYNTAX INTEGER { tenBaseT(1), aui(2), foirl(3),
                                 mac(4), lanbus(5), tenBase2(6),
                                 tenBaseFL(7) }
                ACCESS read-only 
                STATUS mandatory
                DESCRIPTION
                    "Indicates the type of the port."
                ::= { repeaterPortEntry 16 }

            repeaterPortAccessAllStatus OBJECT-TYPE
                SYNTAX INTEGER { invalid(1), valid(2) }
                ACCESS read-write
                STATUS mandatory
                DESCRIPTION
                    "Setting this field to invalid will delete all 
                    access addresses associated with this port. Setting 
                    this field to valid has no effect."
                ::= { repeaterPortEntry 17 }

            repeaterPortPortLastViolationAddress OBJECT-TYPE
                SYNTAX MacAddress
                ACCESS read-only
                STATUS mandatory
                DESCRIPTION
                    "Address that last caused an access violation."
                ::= { repeaterPortEntry 18 }

            repeaterPortPortAddressViolations OBJECT-TYPE
                SYNTAX Counter
                ACCESS read-only
                STATUS mandatory
                DESCRIPTION
                    "Number of access violations."
                ::= { repeaterPortEntry 19 }

            repeaterPortSegment OBJECT-TYPE
                SYNTAX Segment
                ACCESS read-only
                STATUS mandatory
                DESCRIPTION
                    "Returns the indirect mapping of the ethernet repeater
                     to which this port is connected."
                ::= { repeaterPortEntry 20 }

            repeaterPortAccessLearn OBJECT-TYPE
                SYNTAX INTEGER { disabled(1), single(2), continuous(3) }
                ACCESS read-write
                STATUS mandatory
                DESCRIPTION
                    "Controls how the port will learn the source 
                    addresses that can come in on the port."
                DEFVAL { disabled }
                ::= { repeaterPortEntry 21 }

            repeaterPortEthernetRepeater OBJECT-TYPE
                SYNTAX INTEGER { repeater1 (1), repeater2 (2), repeater3 (3) }
                ACCESS read-write
                STATUS mandatory
                DESCRIPTION
                    "For repeaters that implement non-proxy management 
                    of logical repeaters, this variable selects the 
                    logical Ethernet repeater to which the port is 
                    attached."
                ::= { repeaterPortEntry 22 }

            repeaterPortRepeatersAllowed OBJECT-TYPE
                SYNTAX OCTET STRING
                ACCESS read-only
                STATUS mandatory
                DESCRIPTION
                    "The list of repeaters to which this port can be 
                    attached.  The OCTET STRING contains a bitmap, with 
                    a bit for 'none' and one bit for each repeater, and 
                    enough octets for all the repeaters on the device.  
                    The high order bit of the first octet corresponds to 
                    'none', the following bits correspond to the 
                    repeaters, in order, beginning with 1."
                ::= { repeaterPortEntry 23 }

            repeaterPortGlobalSecurityAddress OBJECT-TYPE
                SYNTAX MacAddress
                ACCESS read-only
                STATUS mandatory
                DESCRIPTION
                    "This variable represents the global address which is
                    currently applied to the port."
                ::= { repeaterPortEntry 24 }

            repeaterPortGlobalAddressChanges OBJECT-TYPE
                SYNTAX    Counter
                ACCESS    read-only
                STATUS    mandatory
                DESCRIPTION
                    "This variable represents the number of times since
                    counters have been zeroed, that a global address
                    change occured on the port."
                ::= { repeaterPortEntry 25 }

            repeaterPortPercentUtilization OBJECT-TYPE
                SYNTAX Gauge
                ACCESS read-only
                STATUS mandatory
                DESCRIPTION
                    "This variable will reflect the percentage of a full
                    ethernet load that this port has received since last
                    zeroed.  The value is calculated as
                    '(8(bytesReceived + (20*framesReceived))) /107(time)'."
                ::= { repeaterPortEntry 26 }

            -- More scalars follow Port Access Table

            -- the Port Access table

            repeaterPortAccessTable OBJECT-TYPE
                SYNTAX SEQUENCE OF RepeaterPortAccessEntry
                ACCESS not-accessible
                STATUS mandatory
                DESCRIPTION
                    "Table of access control for the ports."
                ::= { xRepeaterPortInfo 2 }

            repeaterPortAccessEntry OBJECT-TYPE
                SYNTAX RepeaterPortAccessEntry
                ACCESS not-accessible
                STATUS mandatory
                DESCRIPTION
                    "An entry in the table, containing access 
                    information about a port."
                INDEX { repeaterPortAccessGroupIndex,
                        repeaterPortAccessPortIndex,
                        repeaterPortAccessAddress }
                ::= { repeaterPortAccessTable 1 }

            RepeaterPortAccessEntry ::=
                SEQUENCE {
                    repeaterPortAccessGroupIndex
                        INTEGER,
                    repeaterPortAccessPortIndex
                        INTEGER,
                    repeaterPortAccessAddress
                        MacAddress,
                    repeaterPortAccessStatus
                        INTEGER
                }

            repeaterPortAccessGroupIndex OBJECT-TYPE
                SYNTAX INTEGER
                ACCESS read-only
                STATUS mandatory
                DESCRIPTION
                    "This variable identifies the group containing the
                    access entry for which this entry contains information.
                    The group ID may only be that of the target agent.
                    Specifying a group ID of an agent in a different slot
                    will result in `badValue` being returned."
                ::= { repeaterPortAccessEntry 1 }

            repeaterPortAccessPortIndex OBJECT-TYPE
                SYNTAX INTEGER
                ACCESS read-only
                STATUS mandatory
                DESCRIPTION
                    "This variable identifies the port containing the
                    access entry for which this entry contains information."
                ::= { repeaterPortAccessEntry 2 }

            repeaterPortAccessAddress OBJECT-TYPE
                SYNTAX MacAddress
                ACCESS read-only
                STATUS mandatory
                DESCRIPTION
                    "This value will be compared to the source address of
                    all packets received on the port in applying the access
                    action"
                ::= { repeaterPortAccessEntry 3 }

            repeaterPortAccessStatus OBJECT-TYPE
                SYNTAX INTEGER { invalid(1), valid(2) }
                ACCESS read-write
                STATUS mandatory
                DESCRIPTION
                    "The status of the entry.  Set to 'invalid' to 
                    remove the rule."
                ::= { repeaterPortAccessEntry 4 }

            -- Additional Repeater Info scalars

            repeaterPortAccessGroupIndexShadow OBJECT-TYPE
                SYNTAX INTEGER
                ACCESS read-write
                STATUS mandatory
                DESCRIPTION
                    "This variable identifies the group which contains a
                    port to which an access address is to be assigned.  The
                    group ID may only be that of the target agent.  Specifying
                    a group ID of an agent in a different slot will result in
                    `badValue` being returned."
                ::= { xRepeaterPortInfo 3 }
            
            repeaterPortAccessPortIndexShadow OBJECT-TYPE
                SYNTAX INTEGER
                ACCESS read-write
                STATUS mandatory
                DESCRIPTION
                    "This variable identifies the port of a group to which
                    an access address is to be assigned."
                ::= { xRepeaterPortInfo 4 }
            
            repeaterPortAccessAddressShadow OBJECT-TYPE
                SYNTAX MacAddress
                ACCESS read-write
                STATUS mandatory
                DESCRIPTION
                    "This value contains the ethernet address which is to be
                    added to the access address table for the port specified
                    by repeaterPortAccessGroupIndexShadow and
                    repeaterPortAccessPortIndexShadow."
                ::= { xRepeaterPortInfo 5 }
            
            repeaterPortAccessStatusShadow OBJECT-TYPE
                SYNTAX INTEGER { ready(1), execute(2) }
                ACCESS read-write
                STATUS mandatory
                DESCRIPTION
                     "When read, this variable will always return 'ready'.  When
                     this variable is set to 'execute' the address specified by
                     repeaterPortAccessAddressShadow will be added to the access
                     address table for the port specified by
                     repeaterPortAccessGroupIndexShadow and
                     repeaterPortAccessPortIndexShadow.  If any of the above
                     variables are zero when this object is set to 'execute',
                     'bad value' will be returned."
                DEFVAL { ready }
                ::= { xRepeaterPortInfo 6 }

            -- extensions to the Port table

            repeaterPort2Table OBJECT-TYPE
                SYNTAX SEQUENCE OF RepeaterPort2Entry
                ACCESS not-accessible
                STATUS mandatory
                DESCRIPTION
                    "Table of more descriptive and status information
                     about the ports."
                ::= { xRepeaterPortInfo 7 }

            repeaterPort2Entry OBJECT-TYPE
                SYNTAX RepeaterPort2Entry
                ACCESS not-accessible
                STATUS mandatory
                DESCRIPTION
                    "An entry in the table, containing information about 
                    a port.  Index is identical to repeaterPortTable."
                INDEX { repeaterPortGroupIndex, repeaterPortIndex }
                ::= { repeaterPort2Table 1 }

            RepeaterPort2Entry ::=
                SEQUENCE {
                    repeaterPort2RmonOctets
                        Counter,
                    repeaterPort2RmonPkts
                        Counter,
                    repeaterPort2RmonBroadcastPkts
                        Counter,
                    repeaterPort2RmonMulticastPkts
                        Counter,
                    repeaterPort2RmonCRCAlignErrors
                        Counter,
                    repeaterPort2RmonPkts64Octets
                        Counter,
                    repeaterPort2RmonPkts65to127Octets
                        Counter,
                    repeaterPort2RmonPkts128to255Octets
                        Counter,
                    repeaterPort2RmonPkts256to511Octets
                        Counter,
                    repeaterPort2RmonPkts512to1023Octets
                        Counter,
                    repeaterPort2RmonPkts1024to1518Octets
                        Counter,
                    repeaterPort2TrafficRatio
                        INTEGER,
                    repeaterPort2CollisionRatio
                        INTEGER,
                    repeaterPort2ErrorRatio
                        INTEGER,
                    repeaterPort2BroadcastRatio
                        INTEGER,
                    repeaterPort2MulticastRatio
                        INTEGER,
                    repeaterPort2UnicastRatio
                        INTEGER
                }

            repeaterPort2RmonOctets OBJECT-TYPE
                SYNTAX Counter
                ACCESS read-only
                STATUS mandatory
                DESCRIPTION
                    "The total number of octets of data (including
                    those in bad packets) received on the port
                    (excluding framing bits but including FCS octets)."
                ::= { repeaterPort2Entry 1 }

            repeaterPort2RmonPkts OBJECT-TYPE
                  SYNTAX Counter
                  ACCESS read-only
                  STATUS mandatory
                  DESCRIPTION
                    "The total number of packets (including error packets)
                    received on the port."
                ::= { repeaterPort2Entry 2 }

            repeaterPort2RmonBroadcastPkts OBJECT-TYPE
                  SYNTAX Counter
                  ACCESS read-only
                  STATUS mandatory
                  DESCRIPTION
                    "The total number of good packets received on the port
                    that were directed to the broadcast address."
                ::= { repeaterPort2Entry 3 }

            repeaterPort2RmonMulticastPkts OBJECT-TYPE
                SYNTAX Counter
                ACCESS read-only
                STATUS mandatory
                DESCRIPTION
                    "The total number of good packets received on the port
                    that were directed to a multicast address.  Note that
                    this number does not include packets directed to the
                    broadcast address."
                ::= { repeaterPort2Entry 4 }

            repeaterPort2RmonCRCAlignErrors OBJECT-TYPE
                SYNTAX Counter
                ACCESS read-only
                STATUS mandatory
                DESCRIPTION
                    "The total number of packets received on the port that
                    had a length (excluding framing bits, but including
                    FCS octets) of between 64 and 1518 octets, inclusive,
                    but were not an integral number of octets in length or
                    had a bad Frame Check Sequence (FCS)."
                ::= { repeaterPort2Entry 5 }

            repeaterPort2RmonPkts64Octets OBJECT-TYPE
                SYNTAX Counter
                ACCESS read-only
                STATUS mandatory
                DESCRIPTION
                    "The total number of packets (including error packets)
                     received on the port that were 64 octets in length
                    (excluding framing bits but including FCS octets)."
                ::= { repeaterPort2Entry 6 }

            repeaterPort2RmonPkts65to127Octets OBJECT-TYPE
                SYNTAX Counter
                ACCESS read-only
                STATUS mandatory
                DESCRIPTION
                    "The total number of packets (including error packets)
                    received on the port that were between 65 and 127
                    octets in length inclusive (excluding framing bits but
                    including FCS octets)."
                ::= { repeaterPort2Entry 7 }

            repeaterPort2RmonPkts128to255Octets OBJECT-TYPE
                SYNTAX Counter
                ACCESS read-only
                STATUS mandatory
                DESCRIPTION
                    "The total number of packets (including error packets)
                    received on the port that were between 128 and 255
                    octets in length inclusive (excluding framing bits but
                    including FCS octets)."
                ::= { repeaterPort2Entry 8 }

            repeaterPort2RmonPkts256to511Octets OBJECT-TYPE
                SYNTAX Counter
                ACCESS read-only
                STATUS mandatory
                DESCRIPTION
                    "The total number of packets (including error packets)
                    received on the port that were between 256 and 511
                    octets in length inclusive (excluding framing bits but
                    including FCS octets)."
                ::= { repeaterPort2Entry 9 }

            repeaterPort2RmonPkts512to1023Octets OBJECT-TYPE
                SYNTAX Counter
                ACCESS read-only
                STATUS mandatory
                DESCRIPTION
                    "The total number of packets (including error packets)
                    received on the port that were between 512 and 1023
                    octets in length inclusive (excluding framing bits but
                    including FCS octets)."
                ::= { repeaterPort2Entry 10 }

            repeaterPort2RmonPkts1024to1518Octets OBJECT-TYPE
                SYNTAX Counter
                ACCESS read-only
                STATUS mandatory
                DESCRIPTION
                    "The total number of packets (including error packets)
                    received on the port that were between 1024 and 1518
                    octets in length inclusive (excluding framing bits but
                    including FCS octets)."
                ::= { repeaterPort2Entry 11 }

            repeaterPort2TrafficRatio OBJECT-TYPE
                SYNTAX INTEGER (0..10000)
                ACCESS read-only
                STATUS mandatory
                DESCRIPTION
                    "The portion of segment bandwidth used by the port
                    over a 5 second interval, expressed as percentage
                    times 100."
                ::= { repeaterPort2Entry 12 }

            repeaterPort2CollisionRatio OBJECT-TYPE
                SYNTAX INTEGER (0..10000)
                ACCESS read-only
                STATUS mandatory
                DESCRIPTION
                    "The ratio of collisions the port participated in
                    to total packets over a 5 second interval, expressed
                    as percentage times 100."
                ::= { repeaterPort2Entry 13 }

            repeaterPort2ErrorRatio OBJECT-TYPE
                SYNTAX INTEGER (0..10000)
                ACCESS read-only
                STATUS mandatory
                DESCRIPTION
                    "The ratio of total number of error frames on the
                    port to total packets over a 5 second interval,
                    expressed as percentage times 100."
                ::= { repeaterPort2Entry 14 }

            repeaterPort2BroadcastRatio OBJECT-TYPE
                SYNTAX INTEGER (0..10000)
                ACCESS read-only
                STATUS mandatory
                DESCRIPTION
                    "The ratio of good packets directed by the port to the
                    broadcast address to total packets over a 5 second
                    interval, expressed as percentage times 100."
                ::= { repeaterPort2Entry 15 }

            repeaterPort2MulticastRatio OBJECT-TYPE
                SYNTAX INTEGER (0..10000)
                ACCESS read-only
                STATUS mandatory
                DESCRIPTION
                    "The ratio of good packets directed by the port to any
                    multicast address (but not the broadcast address) to
                    total packets over a 5 second interval, expressed as
                    percentage times 100."
                ::= { repeaterPort2Entry 16 }

            repeaterPort2UnicastRatio OBJECT-TYPE
                SYNTAX INTEGER (0..10000)
                ACCESS read-only
                STATUS mandatory
                DESCRIPTION
                    "The ratio of good packets directed by the port to any
                    address other than a multicast or broadcast address to
                    total packets over a 5 second interval, expressed as
                    percentage times 100."
                ::= { repeaterPort2Entry 17 }


            -- the Repeater Slot group

            -- The slot group is deprecated, and there is no replacement
            -- group.

            -- the Slot Segment table

            repeaterSlotSegmentTable OBJECT-TYPE
                SYNTAX SEQUENCE OF RepeaterSlotSegmentEntry
                ACCESS not-accessible
                STATUS deprecated
                DESCRIPTION
                    "Deprecated, no replacement."
                ::= { xRepeaterSlotInfo 1 }

            repeaterSlotSegmentEntry OBJECT-TYPE
                SYNTAX RepeaterSlotSegmentEntry
                ACCESS not-accessible
                STATUS deprecated
                DESCRIPTION
                    "Deprecated, no replacement."
                INDEX { repeaterSlotIndex, repeaterSlotSegment }
                ::= { repeaterSlotSegmentTable 1 }

            RepeaterSlotSegmentEntry ::=
                SEQUENCE {
                    repeaterSlotIndex
                        INTEGER,
                    repeaterSlotSegment
                        Segment,
                    repeaterSlotSegmentStatus
                        INTEGER
                }

            repeaterSlotIndex OBJECT-TYPE
                SYNTAX INTEGER
                ACCESS read-only
                STATUS deprecated
                DESCRIPTION
                    "Deprecated, no replacement."
                ::= { repeaterSlotSegmentEntry 1 }

            repeaterSlotSegment OBJECT-TYPE
                SYNTAX Segment
                ACCESS read-only
                STATUS deprecated
                DESCRIPTION
                    "Deprecated, no replacement."
                ::= { repeaterSlotSegmentEntry 2 }

            repeaterSlotSegmentStatus OBJECT-TYPE
                SYNTAX INTEGER { disabled(1), enabled(2) }
                ACCESS read-write
                STATUS deprecated
                DESCRIPTION
                    "Deprecated, no replacement."
                ::= { repeaterSlotSegmentEntry 3 }


            -- the Repeater Security group

            -- Implementation of this group is mandatory for all ITouch
            -- Ethernet repeaters that support security

            repeaterSecurityState OBJECT-TYPE
                SYNTAX INTEGER { disabled(1), enabled(2) }
                ACCESS read-write
                STATUS mandatory
                DESCRIPTION
                    "Controls whether security operation will be applied 
                    to all ports on the repeater.  If security is not
                    supported by the device, 'badValue' will be returned
                    if the variable is set to 'enabled'."
                DEFVAL { disabled }
                ::= { xRepeaterSecurity 1 }

            -- the Security Port table

            repeaterSecurityPortTable OBJECT-TYPE
                SYNTAX SEQUENCE OF RepeaterSecurityPortEntry
                ACCESS not-accessible
                STATUS mandatory
                DESCRIPTION
                    "Table of descriptive and status information about 
                    the ports."
                ::= { xRepeaterSecurity 2 }

            repeaterSecurityPortEntry OBJECT-TYPE
                SYNTAX RepeaterSecurityPortEntry
                ACCESS not-accessible
                STATUS mandatory
                DESCRIPTION
                    "An entry in the table, containing information about 
                    a port."
                INDEX { repeaterPortGroupIndex, repeaterPortIndex }
                ::= { repeaterSecurityPortTable 1 }

            RepeaterSecurityPortEntry ::=
                SEQUENCE {
                    repeaterSecurityPortUnicast
                        INTEGER,
                    repeaterSecurityPortMulticast
                        INTEGER,
                    repeaterSecurityPortAllStatus
                        INTEGER,
                    repeaterSecurityPortSecurityLearn 
                        INTEGER
                }

            repeaterSecurityPortUnicast OBJECT-TYPE
                SYNTAX INTEGER { jam(1), allow(2) }
                ACCESS read-write
                STATUS mandatory
                DESCRIPTION
                    "The action to take when the destination address is 
                    unicast and does not have an entry in 
                    repeaterSecurityTable.  If repeaterPortGroupIndex is
                    equal to the group number of the agent, this object
                    is read-write, otherwise it is read-only."
                DEFVAL { jam }
                ::= { repeaterSecurityPortEntry 1 }

            repeaterSecurityPortMulticast OBJECT-TYPE
                SYNTAX INTEGER { jam(1), allow(2) }
                ACCESS read-write
                STATUS mandatory
                DESCRIPTION
                    "The action to take when the destination address is 
                    multicast and does not have an entry in 
                    repeaterSecurityTable.  If repeaterPortGroupIndex is
                    equal to the group number of the agent, this object
                    is read-write, otherwise it is read-only"
                DEFVAL { jam }
                ::= { repeaterSecurityPortEntry 2 }

            repeaterSecurityPortAllStatus OBJECT-TYPE
                SYNTAX INTEGER { invalid(1), valid(2) }
                ACCESS read-write
                STATUS mandatory
                DESCRIPTION
                    "Setting this field to invalid will delete all 
                    security addresses associated with this port. 
                    Setting this field to valid has no effect.  If
                    repeaterPortGroupIndex is equal to the group number
                    of the agent, this object is read-write, otherwise it
                    is read-only"
                DEFVAL { valid }
                ::= { repeaterSecurityPortEntry 3 }

            repeaterSecurityPortSecurityLearn OBJECT-TYPE
                SYNTAX INTEGER { disabled(1), single(2), continuous(3) }
                ACCESS read-write
                STATUS mandatory
                DESCRIPTION
                    "Controls how the port will learn the destination 
                    addresses that can be sent to the port.  If
                    repeaterPortGroupIndex is equal to the group number
                    of the agent, this object is read-write, otherwise
                    it is read-only"
                DEFVAL { disabled }
                ::= { repeaterSecurityPortEntry 4 }

            -- additional scalars follow the Security table

            -- the Security table

            repeaterSecurityTable OBJECT-TYPE
                SYNTAX SEQUENCE OF RepeaterSecurityEntry
                ACCESS not-accessible
                STATUS mandatory
                DESCRIPTION
                    "Table of security control for the ports."
                ::= { xRepeaterSecurity 3 }

            repeaterSecurityEntry OBJECT-TYPE
                SYNTAX RepeaterSecurityEntry
                ACCESS not-accessible
                STATUS mandatory
                DESCRIPTION
                    "An entry in the table, containing security 
                    information about a port."
                INDEX { repeaterSecurityGroupIndex,
                        repeaterSecurityPortIndex,
                        repeaterSecurityAddress }
                ::= { repeaterSecurityTable 1 }

            RepeaterSecurityEntry ::=
                SEQUENCE {
                    repeaterSecurityGroupIndex
                        INTEGER,
                    repeaterSecurityPortIndex
                        INTEGER,
                    repeaterSecurityAddress
                        MacAddress,
                    repeaterSecurityStatus
                        INTEGER,
                    repeaterSecurityAction
                        INTEGER
                }

            repeaterSecurityGroupIndex OBJECT-TYPE
                SYNTAX INTEGER
                ACCESS read-only
                STATUS mandatory
                DESCRIPTION
                    "This variable identifies the group containing the 
                    security entry for which this entry contains 
                    information.  The group ID may only be that of the
                    target agent.  Specifying a group ID of an agent in
                    a different slot will result in `badValue` being returned."
                ::= { repeaterSecurityEntry 1 }

            repeaterSecurityPortIndex OBJECT-TYPE
                SYNTAX INTEGER
                ACCESS read-only
                STATUS mandatory
                DESCRIPTION
                    "This variable identifies the port containing the  
                    security entry for which this entry contains 
                    infromation."
                ::= { repeaterSecurityEntry 2 }

            repeaterSecurityAddress OBJECT-TYPE
                SYNTAX MacAddress
                ACCESS read-only
                STATUS mandatory
                DESCRIPTION
                    "This value will be compared to the destination 
                    address of all packets received on the port in 
                    applying the security action."
                ::= { repeaterSecurityEntry 3 }

            repeaterSecurityStatus OBJECT-TYPE
                SYNTAX INTEGER { invalid(1), valid(2) }
                ACCESS read-write
                STATUS mandatory
                DESCRIPTION
                    "The status of the entry.  Set to 'invalid' to 
                    remove the rule."
                DEFVAL { valid }
                ::= { repeaterSecurityEntry 4 }

            repeaterSecurityAction OBJECT-TYPE
                SYNTAX INTEGER { jam(1), allow(2) }
                ACCESS read-write
                STATUS mandatory
                DESCRIPTION
                    "The action to take when the destination address 
                    matches."
                DEFVAL { jam }
                ::= { repeaterSecurityEntry 5 }

            -- additional security scalars

            repeaterSecurityGroupIndexShadow OBJECT-TYPE
                SYNTAX INTEGER
                ACCESS read-write
                STATUS mandatory
                DESCRIPTION
                    "This variable identifies the group containing a 
                    port to which a security address is to be assigned.  The
                    group ID may only be that of the target agent.  Specifying
                    a group ID of an agent in a different slot will result in
                    `badValue` being returned."
                ::= { xRepeaterSecurity 4 }
            
            repeaterSecurityPortIndexShadow OBJECT-TYPE
                SYNTAX INTEGER
                ACCESS read-write
                STATUS mandatory
                DESCRIPTION
                    "This variable identifies the port of a group to which
                    a security address is to be assigned."
                ::= { xRepeaterSecurity 5 }
            
            repeaterSecurityAddressShadow OBJECT-TYPE
                SYNTAX MacAddress
                ACCESS read-write
                STATUS mandatory
                DESCRIPTION
                    "This value contains the ethernet address which is to be
                    added to the security address table for the port specified
                    by repeaterSecurityGroupIndexShadow and
                    repeaterSecurityPortIndexShadow."
                ::= { xRepeaterSecurity 6 }
            
            repeaterSecurityStatusShadow OBJECT-TYPE
                SYNTAX INTEGER { ready(1), execute(2) }
                ACCESS read-write
                STATUS mandatory
                DESCRIPTION
                     "When read, this variable will always return 'ready'.  When
                     this variable is set to 'execute' the address specified by
                     repeaterSecurityAddressShadow will be added to the security
                     address table for the port specified by
                     repeaterSecurityGroupIndexShadow and
                     repeaterSecurityPortIndexShadow.  If any of the above variables
                     are zero when this object is set to 'execute', 'bad value' will
                     be returned."
                DEFVAL { ready }
                ::= { xRepeaterSecurity 7 }

            -- The global Security Table

            -- More scalars follow the global security table

            repeaterSecurityGlobalAddressTable OBJECT-TYPE
                SYNTAX SEQUENCE OF RepeaterSecurityGlobalAddressEntry
                ACCESS not-accessible
                STATUS mandatory
                DESCRIPTION
                    "Table of ethernet addresses which are applied globally
                    (intra Network 9000 chassis) to ports."
                ::= { xRepeaterSecurity 8 }

            repeaterSecurityGlobalAddressEntry OBJECT-TYPE
                SYNTAX RepeaterSecurityGlobalAddressEntry
                ACCESS not-accessible
                STATUS mandatory
                DESCRIPTION
                    "An entry in the table containing information about a
                    specific address."
                INDEX { repeaterSecurityGlobalAddress }
                ::= { repeaterSecurityGlobalAddressTable 1 }

            RepeaterSecurityGlobalAddressEntry ::=
                SEQUENCE {
                    repeaterSecurityGlobalAddress
                        MacAddress,
                    repeaterSecurityGlobalAddressStatus
                        INTEGER,
                    repeaterSecurityGlobalAddressAction
                        INTEGER
                }

            repeaterSecurityGlobalAddress OBJECT-TYPE
                SYNTAX MacAddress
                ACCESS read-only
                STATUS mandatory
                DESCRIPTION
                    "This variable identifies the address."
                ::= { repeaterSecurityGlobalAddressEntry 1 }

            repeaterSecurityGlobalAddressStatus OBJECT-TYPE
                SYNTAX INTEGER { invalid(1), valid(2) }
                ACCESS read-write
                STATUS mandatory
                DESCRIPTION
                    "This variable represents the status of the entry.
                    Setting this object (or any other writable object) to
                    'valid' will cause the row in the table to be created.
                    Setting this object to 'invalid' will cause the row to be
                    removed."
                ::= { repeaterSecurityGlobalAddressEntry 2 }

            repeaterSecurityGlobalAddressAction OBJECT-TYPE
                SYNTAX INTEGER { jam(1), allow(2) }
                ACCESS read-write
                STATUS mandatory
                DESCRIPTION
                    "This variable determines the action which is applied to
                    the packet in the event of an address match.  The packet is
                    either passed untouched when set to 'pass', or it is
                    forced to an alternating pattern of ones and zeros if
                    set to 'jam'."
                DEFVAL { allow }
                ::= { repeaterSecurityGlobalAddressEntry 3 }

            -- Additional Security group scalars

            repeaterSecurityGlobalDBID OBJECT-TYPE
                SYNTAX INTEGER
                ACCESS read-only
                STATUS mandatory
                DESCRIPTION
                    "This variable contains the current version number
                     of the global security database."
                ::= { xRepeaterSecurity 9 }

            repeaterSecurityGlobalSecurityAdminState OBJECT-TYPE
                SYNTAX INTEGER { disabled(1), enabled(2) } 
                ACCESS read-write
                STATUS mandatory
                DESCRIPTION
                    "This variable controls whether global security is
                     enabled or disabled.  Global security will not function
                     unless repeaterSecurityState and
                     this variable are both set to `enabled`."
                DEFVAL { disabled }
                ::= { xRepeaterSecurity 10 }

            repeaterSecurityGlobalSecurityOperState OBJECT-TYPE
                SYNTAX INTEGER { disabled(1), enabled(2), securityDisabled(3) } 
                ACCESS read-only
                STATUS mandatory
                DESCRIPTION
                    "This variable indicates the operational state of global
                     security.  If repeaterSecurityState is set to 'enabled'
                     this variable will reflect the value of
                     repeaterSecurityGlobalSecurityAdminState. if
                     repeaterSecurityState is set to 'disabled', this variable
                     will return 'securityDisabled'."
                ::= { xRepeaterSecurity 11 }

            -- Repeater Repeater table

            -- This table is for repeaters that implement non-proxy
            -- management of multiple logical repeaters.

            repeaterRepeaterTable OBJECT-TYPE
                SYNTAX SEQUENCE OF RepeaterRepeaterEntry
                ACCESS not-accessible
                STATUS mandatory
                DESCRIPTION
                    "For repeaters that implement non-proxy management 
                    of logical repeaters, a table of descriptive and 
                    status information about a logical Ethernet 
                    repeater."
                ::= { xRepeaterRepeater 1 }

                repeaterRepeaterEntry OBJECT-TYPE
                SYNTAX RepeaterRepeaterEntry
                ACCESS not-accessible
                STATUS mandatory
                DESCRIPTION
                    "An entry for a logical Ethernet repeater."
                INDEX { repeaterRepeaterGroupIndex,
                        repeaterRepeaterIndex }
                ::= { repeaterRepeaterTable 1 }

            RepeaterRepeaterEntry ::=
                SEQUENCE {
                    repeaterRepeaterGroupIndex
                        INTEGER,
                    repeaterRepeaterIndex
                        INTEGER,
                    repeaterRepeaterSegment
                        Segment,
                    repeaterRepeaterReports
                        INTEGER,
                    repeaterRepeaterCollisions
                        Counter,
                    repeaterRepeaterJabbers
                        Counter,
                    repeaterRepeaterSQE
                        Counter,
                    repeaterRepeaterFifoOverflows
                        Counter,
                    repeaterRepeaterZero
                        INTEGER,
                    repeaterRepeaterSinceZero
                        TimeTicks,
                    repeaterRepeaterSegmentsAllowed
                        OCTET STRING,
                    repeaterRepeaterTotalOctets
                        Counter,
                    repeaterRepeaterTotalFrames
                        Counter,
                    repeaterRepeaterPercentUtilization
                        Gauge
                }

            repeaterRepeaterGroupIndex OBJECT-TYPE
                SYNTAX INTEGER
                ACCESS read-only
                STATUS mandatory
                DESCRIPTION
                    "The slot of the chassis."
                ::= { repeaterRepeaterEntry 1 }

            repeaterRepeaterIndex OBJECT-TYPE
                SYNTAX INTEGER
                ACCESS read-only
                STATUS mandatory
                DESCRIPTION
                    "The logical Ethernet repeater within the group."
                ::= { repeaterRepeaterEntry 2 }

            repeaterRepeaterSegment OBJECT-TYPE
                SYNTAX Segment
                ACCESS read-write
                STATUS mandatory
                DESCRIPTION
                    "The Network 9000 Ethernet network segment to which 
                    the logical repeater is attached."
                ::= { repeaterRepeaterEntry 3 }

            repeaterRepeaterReports OBJECT-TYPE
                SYNTAX INTEGER { disabled(1), enabled(2) }
                ACCESS read-write
                STATUS mandatory
                DESCRIPTION
                    "Control for whether statistical reports will be 
                    collected for this logical repeater."
                DEFVAL { enabled }
                ::= { repeaterRepeaterEntry 4 }

            repeaterRepeaterCollisions OBJECT-TYPE
                SYNTAX Counter
                ACCESS read-only
                STATUS mandatory
                DESCRIPTION
                    "The number of packet collisions detected on the 
                    Ethernet network segment to which this logical 
                    repeater is attached."
                ::= { repeaterRepeaterEntry 5 }

            repeaterRepeaterJabbers OBJECT-TYPE
                SYNTAX Counter
                ACCESS read-only
                STATUS mandatory
                DESCRIPTION
                    "The number of Jabber events detected for this 
                    logical repeater."
                ::= { repeaterRepeaterEntry 6 }

            repeaterRepeaterSQE OBJECT-TYPE
                SYNTAX Counter
                    ACCESS read-only
                STATUS mandatory
                    DESCRIPTION
                    "The number of SQE failure events detected for this 
                    logical repeater."
                ::= { repeaterRepeaterEntry 7 }

            repeaterRepeaterFifoOverflows OBJECT-TYPE
                SYNTAX Counter
                ACCESS read-only
                STATUS mandatory
                DESCRIPTION
                    "The number of times the report FIFO was full when 
                    this logical repeater attemped to write a packet 
                    report."
                ::= { repeaterRepeaterEntry 8 }

            repeaterRepeaterZero OBJECT-TYPE
                SYNTAX INTEGER { ready(1), execute(2) }
                ACCESS read-write
                STATUS mandatory
                DESCRIPTION
                    "Control for zeroing the logical repeater's 
                    counters.  The agent always returns 'ready' for this 
                    value.  Setting the value to 'ready' has no effect.  
                    Setting the value to 'execute' will zero the 
                    counters for the logical repeater."
                ::= { repeaterRepeaterEntry 9 }

            repeaterRepeaterSinceZero OBJECT-TYPE
                SYNTAX TimeTicks
                ACCESS read-only
                STATUS mandatory
                DESCRIPTION
                    "The number of hundredths of a second since the 
                    counters for this logical repeater were last zeroed.  
                    This variable is set to zero when 
                    repeaterRepeaterZero is written with the value 
                    'execute'."
                ::= { repeaterRepeaterEntry 10 }

            repeaterRepeaterSegmentsAllowed OBJECT-TYPE
                SYNTAX OCTET STRING
                ACCESS read-only
                STATUS mandatory
                DESCRIPTION
                    "The list of segments to which this repeater can be 
                    attached.  The OCTET STRING contains a bitmap, with 
                    a bit for 'none' and one bit for each segment, and 
                    enough octets for all the Ethernet segments in the 
                    chassis.  The high order bit of the first octet 
                    corresponds to 'none', the following bits correspond 
                    to the segments, in order, beginning with A."
                ::= { repeaterRepeaterEntry 11 }

            repeaterRepeaterTotalOctets OBJECT-TYPE
                SYNTAX Counter
                ACCESS read-only
                STATUS mandatory
                DESCRIPTION
                    "This variable will reflect the total number of bytes that
                    the repeater both received from and sent to the segment.
                    Bytes in both good and error frames are counted."
                ::= { repeaterRepeaterEntry 12 }

            repeaterRepeaterTotalFrames OBJECT-TYPE
                SYNTAX Counter
                ACCESS read-only
                STATUS mandatory
                DESCRIPTION
                    "This variable will reflect the total number of frames that
                    the repeater both received from and sent to the segment.
                    Both good and error frames are counted."
                ::= { repeaterRepeaterEntry 13 }

            repeaterRepeaterPercentUtilization OBJECT-TYPE
                SYNTAX Gauge
                ACCESS read-only
                STATUS mandatory
                DESCRIPTION
                    "This variable will reflect the percentage of a full
                    ethernet load that this repeater has handled since last
                    zeroed.  The value is calculated as
                    `(8(totalBytes + (20*totalFrames)))/10 7(time)`."
                ::= { repeaterRepeaterEntry 14 }


            -- The Repeater Redundancy group

            -- Implementation of this group is mandatory for all ITouch
            -- Ethernet repeaters.
            -- The repeater Redundancy group contains:

            repeaterRedundancyState OBJECT-TYPE
                SYNTAX INTEGER { disabled(1), enabled(2) }
                ACCESS read-write
                STATUS mandatory
                DESCRIPTION
                    "This variable controls whether hub redundancy is enabled"
                DEFVAL { enabled }
                ::= { xRepeaterRedundancy 1 }
            -- The Redundancy Group table

            repeaterRedundancyGroupTable OBJECT-TYPE
                SYNTAX SEQUENCE OF RepeaterRedundancyGroupEntry
                ACCESS not-accessible
                STATUS mandatory
                DESCRIPTION
                    "Table of descriptive and status information
                    concerning hub redundancy groups."
                ::= { xRepeaterRedundancy 2 }

            repeaterRedundancyGroupEntry OBJECT-TYPE
                SYNTAX RepeaterRedundancyGroupEntry
                ACCESS not-accessible
                STATUS mandatory
                DESCRIPTION
                    "An entry in the table containing information about a
                    specific hub redundancy group."
                INDEX { repeaterRedundancyGroupGroupIndex }
                ::= { repeaterRedundancyGroupTable 1 }

            RepeaterRedundancyGroupEntry ::=
                SEQUENCE {
                    repeaterRedundancyGroupGroupIndex
                        INTEGER,
                    repeaterRedundancyGroupStatus
                        INTEGER,
                    repeaterRedundancyGroupName
                        DisplayString,
                    repeaterRedundancyGroupAdminState
                        INTEGER,
                    repeaterRedundancyGroupTestInterval
                        INTEGER,
                    repeaterRedundancyGroupRollbackAdminState
                        INTEGER,
                    repeaterRedundancyGroupRollbackInterval
                        INTEGER,
                    repeaterRedundancyGroupOperPath
                        INTEGER,
                    repeaterRedundancyGroupPathChanges
                        Counter,
                    repeaterRedundancyGroupRollbackAttempts
                        Counter,
                    repeaterRedundancyGroupZero
                        INTEGER,
                    repeaterRedundancyGroupSinceZero
                        TimeTicks,
                    repeaterRedundancyGroupConfigStatus
                        INTEGER
                }

            repeaterRedundancyGroupGroupIndex OBJECT-TYPE
                SYNTAX INTEGER
                ACCESS read-only
                STATUS mandatory
                DESCRIPTION
                    "This variable identifies the group."
                ::= { repeaterRedundancyGroupEntry 1 }

            repeaterRedundancyGroupStatus OBJECT-TYPE
                SYNTAX INTEGER { invalid(1), valid(2) }
                ACCESS read-write
                STATUS mandatory
                DESCRIPTION
                    "This variable represents the status of the entry.
                    Setting this object (or any other writable object) to
                    'valid' will cause the row in the table to be created.
                    Setting this object to 'invalid' will cause the row to be
                    removed.  If a row is removed from the group table, all
                    related rows in the path table and address table are
                    also removed."
                ::= { repeaterRedundancyGroupEntry 2 }

            repeaterRedundancyGroupName OBJECT-TYPE
                SYNTAX DisplayString (SIZE (0..16))
                ACCESS read-write
                STATUS mandatory
                DESCRIPTION
                    "This variable represents the definable name of the
                    group.  Prior to being set, this object will return
                    the default name 'Groupn' where n is the value of
                    repeaterRedundancyGroupIndex.  Setting this object to a zero
                    length string will cause the default name to be assumed."
                ::= { repeaterRedundancyGroupEntry 3 }

            repeaterRedundancyGroupAdminState OBJECT-TYPE
                SYNTAX INTEGER { disabled(1), enabled(2) }
                ACCESS read-write
                STATUS mandatory
                DESCRIPTION
                    "This variable represents the desired state of the
                    group.  When this variable is set to 'enabled', the group
                    will be activly monitored for integrity, and back-
                    up paths will be brought up as higher priority paths
                    disappear.  When set to 'disabled', the path will not be
                    tested for integrity."
                DEFVAL { enabled }
                ::= { repeaterRedundancyGroupEntry 4 }

            repeaterRedundancyGroupTestInterval OBJECT-TYPE
                SYNTAX INTEGER (250..180000)
                ACCESS read-write
                STATUS mandatory
                DESCRIPTION
                    "This variable determines the rate at which testing is
                    performed on the path which is currently active
                    (repeaterRedundancyGroupOperPath) in order to determine
                    integrity.  The value is in milliseconds."
                DEFVAL { 3000 }
                ::= { repeaterRedundancyGroupEntry 5 }

            repeaterRedundancyGroupRollbackAdminState OBJECT-TYPE
                SYNTAX INTEGER { disabled(1), enabled(2) }
                ACCESS read-write
                STATUS mandatory
                DESCRIPTION
                    "This variable represents the desired state of path
                    rollback.  Path rollback is defined as the automatic
                    testing and reactivation of higher priority
                    paths.  It should be noted that in order to test higher
                    priority paths, the currently enabled path will be
                    interrupted.  Setting this variable to 'enabled' will cause
                    rollback testing to occur every
                    repeaterRedundancyGroupRollbackInterval number of milliseconds.
                    Setting this variable to 'disabled' will force the group to
                    remain on lower priority paths, until they themselves fail."
                DEFVAL { enabled }
                ::= { repeaterRedundancyGroupEntry 6 }

            repeaterRedundancyGroupRollbackInterval OBJECT-TYPE
                SYNTAX INTEGER (500..180000)
                ACCESS read-write
                STATUS mandatory
                DESCRIPTION
                    "This variable determines the rate at which rollback
                    testing is performed. The value is in milliseconds."
                DEFVAL { 10000 }
                ::= { repeaterRedundancyGroupEntry 7 }

            repeaterRedundancyGroupOperPath OBJECT-TYPE
                SYNTAX INTEGER
                ACCESS read-only
                STATUS mandatory
                DESCRIPTION
                    "This variable represents the index of the path which is
                    currently being used as the active path. This value may be
                    used as the value for repeaterRedundancyPathIndex to index the
                    path table."
                ::= { repeaterRedundancyGroupEntry 8 }

            repeaterRedundancyGroupPathChanges OBJECT-TYPE
                SYNTAX Counter
                ACCESS read-only
                STATUS mandatory
                DESCRIPTION
                    "The value of this variable represents the number of times
                    that this group has changed paths."
                ::= { repeaterRedundancyGroupEntry 9 }

            repeaterRedundancyGroupRollbackAttempts OBJECT-TYPE
                SYNTAX Counter
                ACCESS read-only
                STATUS mandatory
                DESCRIPTION
                    "The value of this variable represents the number of times
                    that the current path has been interrupted in interest of
                    testing a higher priority path."
                ::= { repeaterRedundancyGroupEntry 10 }

            repeaterRedundancyGroupZero OBJECT-TYPE
                SYNTAX INTEGER { ready(1), execute(2) }
                ACCESS read-write
                STATUS mandatory
                DESCRIPTION
                    "This variable is used to zero all counters associated
                    with a group.  This variable when read will always read
                    'ready'.  When set to 'execute', all counters associated
                    with the group (group counters and path counters) will be set
                    to zero."
                ::= { repeaterRedundancyGroupEntry 11 }

            repeaterRedundancyGroupSinceZero OBJECT-TYPE
                SYNTAX TimeTicks
                ACCESS read-only
                STATUS mandatory
                DESCRIPTION
                    "The value of this variable represents the number of seconds
                    which have elapsed since the counters associated with the
                    group have been zeroed."
                ::= { repeaterRedundancyGroupEntry 12 }

            repeaterRedundancyGroupConfigStatus OBJECT-TYPE
				SYNTAX INTEGER { incomplete(1), complete(2) }
                ACCESS read-only
                STATUS mandatory
                DESCRIPTION
                    "In order for a particular redundancy group to be used by the
                    system, it must have at least one redundancy path defined.
                    This variable indicates whether a redundancy group has been
                    completely configured, and can therefore become active."
                ::= { repeaterRedundancyGroupEntry 13 }

            -- The Redundancy Path table

            repeaterRedundancyPathTable OBJECT-TYPE
                SYNTAX SEQUENCE OF RepeaterRedundancyPathEntry
                ACCESS not-accessible
                STATUS mandatory
                DESCRIPTION
                    "Table of descriptive and status information concerning hub
                    redundancy paths."
                ::= { xRepeaterRedundancy 3 }

            repeaterRedundancyPathEntry OBJECT-TYPE
                SYNTAX RepeaterRedundancyPathEntry
                ACCESS not-accessible
                STATUS mandatory
                DESCRIPTION
                    "An entry in the table containing information about a
                    specific hub redundancy path."
                INDEX { repeaterRedundancyPathGroupIndex,
                        repeaterRedundancyPathPathIndex }
                ::= { repeaterRedundancyPathTable 1 }

            RepeaterRedundancyPathEntry ::=
                SEQUENCE {
                    repeaterRedundancyPathGroupIndex
                        INTEGER,
                    repeaterRedundancyPathPathIndex
                        INTEGER,
                    repeaterRedundancyPathStatus
                        INTEGER,
                    repeaterRedundancyPathSlot
                        INTEGER,
                    repeaterRedundancyPathPort
                        INTEGER,
                    repeaterRedundancyPathPriority
                        INTEGER,
                    repeaterRedundancyPathActivate
                        INTEGER,
                    repeaterRedundancyPathTimeout
                        INTEGER,
                    repeaterRedundancyPathRetryCount
                        INTEGER,
                    repeaterRedundancyPathTestAttempts
                        Counter,
                    repeaterRedundancyPathLastTestStatus
                        INTEGER,
                    repeaterRedundancyPathDisposition
                        INTEGER,
                    repeaterRedundancyPathConfigStatus
                        INTEGER,
                    repeaterRedundancyPathAdminState
                        INTEGER
                }

            repeaterRedundancyPathGroupIndex OBJECT-TYPE
                SYNTAX INTEGER
                ACCESS read-only
                STATUS mandatory
                DESCRIPTION
                    "This variable identifies the group."
                ::= { repeaterRedundancyPathEntry 1 }

            repeaterRedundancyPathPathIndex OBJECT-TYPE
                SYNTAX INTEGER
                ACCESS read-only
                STATUS mandatory
                DESCRIPTION
                    "This variable identifies the path of the group."
                ::= { repeaterRedundancyPathEntry 2 }

            repeaterRedundancyPathStatus OBJECT-TYPE
                SYNTAX INTEGER { invalid(1), valid(2) }
                ACCESS read-write
                STATUS mandatory
                DESCRIPTION
                    "This variable represents the status of the entry.
                    Setting this object (or any other writable object) to
                    'valid' will cause the row in the table to be created.
                    Setting this object to 'invalid' will cause the row to be
                    removed.  If a row is removed from the path table, all related
                    rows in the address table are also removed."
                ::= { repeaterRedundancyPathEntry 3 }

            repeaterRedundancyPathSlot OBJECT-TYPE
                SYNTAX INTEGER
                ACCESS read-write
                STATUS mandatory
                DESCRIPTION
                    "This variable represents the slot of the Network 9000
                    chassis which contains the repeater on which the path
                    interface resides."
                ::= { repeaterRedundancyPathEntry 4 }

            repeaterRedundancyPathPort OBJECT-TYPE
                SYNTAX INTEGER
                ACCESS read-write
                STATUS mandatory
                DESCRIPTION
                    "This variable represents the port of the repeater to
                    which the path is connected."
                ::= { repeaterRedundancyPathEntry 5 }

            repeaterRedundancyPathPriority OBJECT-TYPE
                SYNTAX INTEGER
                ACCESS read-write
                STATUS mandatory
                DESCRIPTION
                    "This variable represents the order of preferred priority
                    for the path.  Lower numbed paths are preferred over higher
                    numbered paths."
                DEFVAL { 5 }
                ::= { repeaterRedundancyPathEntry 6 }

            repeaterRedundancyPathActivate OBJECT-TYPE
                SYNTAX INTEGER { ready(1), execute(2) }
                ACCESS read-write
                STATUS mandatory
                DESCRIPTION
                    "This variable is used to immediately make a specific path
                    active.  This variable when read will always read
                    'ready'.  When set to 'execute', the selected path will
                    become the active path for the group. Note that if rollback
                    is enabled and this path is lower in priority, the system
                    will attempt to restore the higher priority path."
                ::= { repeaterRedundancyPathEntry 7 }

            repeaterRedundancyPathTimeout OBJECT-TYPE
                SYNTAX INTEGER (250..10000)
                ACCESS read-write
                STATUS mandatory
                DESCRIPTION
                    "This variable represents the amount of time in
                    milliseconds that the syatem will wait for test responses from
                    targets on the path."
                DEFVAL { 3000 }
                ::= { repeaterRedundancyPathEntry 8 }

            repeaterRedundancyPathRetryCount OBJECT-TYPE
                SYNTAX INTEGER (1..50)
                ACCESS read-write
                STATUS mandatory
                DESCRIPTION
                    "This variable represents the number of times a test is
                    retried on the path in the event of a timeout before the
                    path is considered useless."
                DEFVAL { 3 }
                ::= { repeaterRedundancyPathEntry 9 }

            repeaterRedundancyPathTestAttempts OBJECT-TYPE
                SYNTAX Counter
                ACCESS read-only
                STATUS mandatory
                DESCRIPTION
                    "The value of this variable represents the number of times
                    that an integrity test was performed on the path."
                ::= { repeaterRedundancyPathEntry 10 }

            repeaterRedundancyPathLastTestStatus OBJECT-TYPE
                SYNTAX INTEGER { notTested(1),
                                 responded(2),
                                 timeout(3),
                                 noIntegrity(4) }
                ACCESS read-only
                STATUS mandatory
                DESCRIPTION
                    "This variable indicates the result of the last test of
                    the path. 'notTested' indicates that the path has yet
                    to be tested. 'responded' indicates that a target on the
                    path path has responded to the last test,  'timeout'
                    indicates that no target on the path responded to the last
                    test.  'integrity' indicates that a test was not performed on
                    the path due to an abscense of port integrity."
                ::= { repeaterRedundancyPathEntry 11 }

            repeaterRedundancyPathDisposition OBJECT-TYPE
                SYNTAX INTEGER { disable(1), null(2) }
                ACCESS read-write
                STATUS mandatory
                DESCRIPTION
                    "This variable controls the action that will be taken when
                    a path is considered bad.  'disable' indicates that the
                    path is to be disabled prior to switching to an alternate path.
                    'null' indicates that the failed path is to be left in its
                    current state prior to switching to an alternate path."
                DEFVAL { disable }
                ::= { repeaterRedundancyPathEntry 12 }

            repeaterRedundancyPathConfigStatus OBJECT-TYPE
				SYNTAX INTEGER { incomplete(1), complete(2) }
                ACCESS read-only
                STATUS mandatory
                DESCRIPTION
                    "In order for a particular redundancy path to be used by the
                    system, it must have at least one target address and the slot
                    and the port on which it originates defined.  This variable
                    indicates whether a redundancy path has been completely
                    configured, and can therefore become active."
                ::= { repeaterRedundancyPathEntry 13 }

            repeaterRedundancyPathAdminState OBJECT-TYPE
				SYNTAX INTEGER { disabled(1), enabled(2) }
                ACCESS read-write
                STATUS mandatory
                DESCRIPTION
                    "This variable represents the desired state of the path.
                    When this variable is set to 'disabled' the path will not
                    be used by the group.  When set to 'enabled', the path is
                    available as an alternate or primary path."
                DEFVAL { enabled }
                ::= { repeaterRedundancyPathEntry 14 }

            -- The Redundancy Target Address table

            repeaterRedundancyAddressTable OBJECT-TYPE
                SYNTAX SEQUENCE OF RepeaterRedundancyAddressEntry
                ACCESS not-accessible
                STATUS mandatory
                DESCRIPTION
                    "Table of descriptive and status information
                    concerning hub redundancy target addresses."
                ::= { xRepeaterRedundancy 4 }

            repeaterRedundancyAddressEntry OBJECT-TYPE
                SYNTAX RepeaterRedundancyAddressEntry
                ACCESS not-accessible
                STATUS mandatory
                DESCRIPTION
                    "An entry in the table containing information about a specific
                    target address associated with a hub redundancy path."
                INDEX { repeaterRedundancyAddressGroupIndex,
                        repeaterRedundancyAddressPathIndex,
                        repeaterRedundancyAddressAddress }
                ::= { repeaterRedundancyAddressTable 1 }

            RepeaterRedundancyAddressEntry ::=
                SEQUENCE {
                    repeaterRedundancyAddressGroupIndex
                        INTEGER,
                    repeaterRedundancyAddressPathIndex
                        INTEGER,
                    repeaterRedundancyAddressAddress
                        TypedAddress,
                    repeaterRedundancyAddressStatus
                        INTEGER,
                    repeaterRedundancyAddressResponses
                        Counter,
                    repeaterRedundancyAddressLastTestStatus
                        INTEGER
                }

            repeaterRedundancyAddressGroupIndex OBJECT-TYPE
                SYNTAX INTEGER
                ACCESS read-only
                STATUS mandatory
                DESCRIPTION
                    "This variable identifies the group."
                ::= { repeaterRedundancyAddressEntry 1 }

            repeaterRedundancyAddressPathIndex OBJECT-TYPE
                SYNTAX INTEGER
                ACCESS read-only
                STATUS mandatory
                DESCRIPTION
                    "This variable identifies the path of the group."
                ::= { repeaterRedundancyAddressEntry 2 }

            repeaterRedundancyAddressAddress OBJECT-TYPE
                SYNTAX TypedAddress
                ACCESS read-only
                STATUS mandatory
                DESCRIPTION
                    "This variable identifies the specific target address."
                ::= { repeaterRedundancyAddressEntry 3 }

            repeaterRedundancyAddressStatus OBJECT-TYPE
                SYNTAX INTEGER { invalid(1), valid(2) }
                ACCESS read-write
                STATUS mandatory
                DESCRIPTION
                    "This variable represents the status of the entry. Setting
                     this object (or any other writable object) to 'valid' will
                     cause the row in the table to be created.  Setting this 
                     object to 'invalid' will cause the row to be removed."
                ::= { repeaterRedundancyAddressEntry 4 }

            repeaterRedundancyAddressResponses OBJECT-TYPE
                SYNTAX Counter
                ACCESS read-only
                STATUS mandatory
                DESCRIPTION
                    "This value of this variable represents the number of times
                    this specific address has responded to a test attempt."
                ::= { repeaterRedundancyAddressEntry 5 }

            repeaterRedundancyAddressLastTestStatus OBJECT-TYPE
                SYNTAX INTEGER { notTested(1),
                                 responded(2),
                                 timeout(3) }
                ACCESS read-only
                STATUS mandatory
                DESCRIPTION
                    "This variable indicates whether this particular address responded to
                    the last test of the path.  'notTested' indicates that the
                    path has yet to be tested.  'responded' indicates that the
                    target responded to the last test, 'timeout' indicates
                    that the target responded to the last test."
                ::= { repeaterRedundancyAddressEntry 6 }

            -- Repeater traps

            accessViolation TRAP-TYPE
                ENTERPRISE xRepeater
                VARIABLES {
                    repeaterPortIndex
                    }
                DESCRIPTION
                    "Access violation by connected system with Ethernet 
                    address not allowed by repeaterPortAccessTable and 
                    repeaterPortAccessAction."
                ::= 1

            integrityLoss TRAP-TYPE
                ENTERPRISE xRepeater
                VARIABLES {
                    repeaterPortIndex,
                    repeaterPortGroupIndex
                    }
                DESCRIPTION
                    "This port has lost link integrity."
                ::= 2

            redundancyPathChange TRAP-TYPE
                ENTERPRISE xRepeater
                VARIABLES { repeaterRedundancyGroupGroupIndex,
                            repeaterRedundancyGroupOperPath }
                DESCRIPTION
                    "This trap issued to indicate that a redundancy group has
                    experienced a path change.  The offending group and
                    the new path are included in the trap."
                ::= 3


END
