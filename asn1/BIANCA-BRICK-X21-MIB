-- This file is corresponding to Release 6.1.2.100 from 2001/09/26 00:00:00
-- (C)opyright 1991-1999 BinTec Communications AG, All Rights Reserved
--  $RCSfile: mibx21,v $ 
-- $Revision: 1.10 $ 

BIANCA-BRICK-X21-MIB DEFINITIONS ::= BEGIN
 
        IMPORTS
            Counter
                FROM RFC1155-SMI
 
            OBJECT-TYPE
                FROM RFC-1212;

    org		OBJECT IDENTIFIER ::= { iso 3 }
    dod		OBJECT IDENTIFIER ::= { org 6 }
    internet	OBJECT IDENTIFIER ::= { dod 1 }
    private	OBJECT IDENTIFIER ::= { internet 4 }
    enterprises	OBJECT IDENTIFIER ::= { private 1 }
    bintec 	OBJECT IDENTIFIER ::= { enterprises 272 }
    bibo	OBJECT IDENTIFIER ::= { bintec 4 }
    x21		OBJECT IDENTIFIER 
	::= { bibo 10 }


    -- Interfaces Group

    -- Management Information for the X21 Subsystem of the BIANCA/BRICK

	Date ::= INTEGER
	HexValue ::= INTEGER


        x21IfTable OBJECT-TYPE
            SYNTAX  SEQUENCE OF X21IfEntry
            ACCESS  not-accessible
            STATUS  mandatory
            DESCRIPTION
		"The x21IfTable contains information relating to the 
                interfaces found on the system. Each entry corresponds to
                a connected X21 interface. Entries can only be added or 
		deleted by the system. 

                Creating entries: Entries are created by the system
                only when a new X21 module is installed.

                Deleting entries: Entries are removed by the system
                after the appropriate X21 module is removed."
	::= { x21 1 }

	x21IfEntry OBJECT-TYPE
            SYNTAX  X21IfEntry
            ACCESS  not-accessible
            STATUS  mandatory
            DESCRIPTION
		""
	    INDEX   { x21IfIndex }
              ::= { x21IfTable 1 }

	X21IfEntry ::=
            SEQUENCE {
                x21IfIndex			INTEGER,
		x21IfL1State			INTEGER,
		x21IfL1Mode			INTEGER,
		x21IfIfLeads			INTEGER,
		x21IfSpeed			INTEGER,
		x21IfL2Mode			INTEGER,

		-- Statistics
		x21IfSpeedReal			Counter,
		x21IfRxPackets			Counter,
		x21IfRxOctets			Counter,
		x21IfTxPackets			Counter,
		x21IfTxOctets			Counter,
		x21IfRxResets			Counter,
		x21IfRxAborts			Counter,
		x21IfRxOverruns			Counter,
		x21IfRxCRCErrors		Counter,
		x21IfRxGiantFrames		Counter,
		x21IfTxResets			Counter,
		x21IfTxAborts			Counter,
		x21IfTxUnderruns		Counter,
		x21IfTxGiantFrames		Counter
            }

	x21IfIndex OBJECT-TYPE
            SYNTAX  INTEGER
            ACCESS  read-only
            STATUS  mandatory

            DESCRIPTION
                "Unique index of the X21 interface."
	::= { x21IfEntry 1 }

	x21IfL1State OBJECT-TYPE
            SYNTAX  INTEGER {
	          dn(1), 	-- inactive
                  up(2) 	-- active
        	}
            ACCESS  read-only
            STATUS  mandatory

            DESCRIPTION
                "The X21 physical layer state

 		  dn(1)		physical layer is inactive;
                  up(2)		physical layer is active;"
	::= { x21IfEntry 2 }

	x21IfL1Mode OBJECT-TYPE
            SYNTAX  INTEGER {
		dte(1), dce(2)
	    }
            ACCESS  read-write
            STATUS  mandatory

            DESCRIPTION
                "The physical layer (layer 1) mode. When configured as
		 DCE(2) the X21 interface provides the clock."
	::= { x21IfEntry 3 }

	x21IfIfLeads OBJECT-TYPE
            SYNTAX  INTEGER {
		enabled(1), disabled(2)
	    }
            ACCESS  read-write
            STATUS  mandatory

            DESCRIPTION
		"The value of IfLeads has influence on the state of the
		 physical layer (L1State). When configured as
		 IfLeads=enabled(1), the state of the physical layer
		 depends on the signals of the X.21 interface pins
		 `Indication' and `Control'. When configured as
		 IfLeads=disabled(2), the state of the physical layer
		 stays always up." 
	::= { x21IfEntry 4 }

	x21IfSpeed OBJECT-TYPE
	    SYNTAX  INTEGER {
		s2048k(1), s1024k(2), s512k(3), s256k(4), s128k(5),
		s64000(6), s38400(7), s19200(8), s14400(9),
		s9600(10), s2400(11)
	    }
	    ACCESS  read-write
	    STATUS  mandatory

	    DESCRIPTION
		"The X21 interface speed in bits per second. The range
		 can be configured between 2Mbits and 2400 Bits per
		 second." 
	::= { x21IfEntry 5 }
		
	x21IfL2Mode OBJECT-TYPE
            SYNTAX  INTEGER {
		dte(1), dce(2), auto(3)
	    }
            ACCESS  read-write
            STATUS  mandatory

            DESCRIPTION
                "The layer 2 mode. This value has influence on the
		 HDLC address field (first byte of a HDCL frame). When
		 configured as DTE(1) the address in a command frame is
		 0x01, when configured as DCE(2) it is 0x03. For
		 response frames it is vice versa. When configured as
		 AUTO(3), layer 2 is set to the same mode like L1Mode is
		 set." 
	::= { x21IfEntry 6 }


	x21IfSpeedReal OBJECT-TYPE
            SYNTAX  Counter
            ACCESS  read-only
            STATUS  mandatory

            DESCRIPTION
		"The measured X21 interface speed in bits per second." 

	::= { x21IfEntry 7 }

	x21IfRxPackets OBJECT-TYPE
            SYNTAX  Counter
            ACCESS  read-only
            STATUS  mandatory

            DESCRIPTION
                "Count of received valid Frames."

	::= { x21IfEntry 8 }

	x21IfRxOctets OBJECT-TYPE
            SYNTAX  Counter
            ACCESS  read-only
            STATUS  mandatory

            DESCRIPTION
		"Count of received bytes."

	::= { x21IfEntry 9 }

	x21IfTxPackets OBJECT-TYPE
            SYNTAX  Counter
            ACCESS  read-only
            STATUS  mandatory

            DESCRIPTION
                "Count of transmitted valid Frames."

	::= { x21IfEntry 10 }

	x21IfTxOctets OBJECT-TYPE
            SYNTAX  Counter
            ACCESS  read-only
            STATUS  mandatory

            DESCRIPTION
		"Count of transmitted bytes."

	::= { x21IfEntry 11 }

	x21IfRxResets OBJECT-TYPE
            SYNTAX  Counter
            ACCESS  read-only
            STATUS  mandatory

            DESCRIPTION
		"Count of receiver resets. Under rare circumstances it
		might be necessary to reset the receiver to work
		properly." 

	::= { x21IfEntry 12 }

	x21IfRxAborts OBJECT-TYPE
            SYNTAX  Counter
            ACCESS  read-only
            STATUS  mandatory

            DESCRIPTION
		"Count of receiver aborts. The sender of a frame can
		indicate a frame as aborted with a special Abort
		sequence." 

	::= { x21IfEntry 13 }

	x21IfRxOverruns OBJECT-TYPE
            SYNTAX  Counter
            ACCESS  read-only
            STATUS  mandatory

            DESCRIPTION
		"Count of receiver overruns. If the X21 card is unable
		to grant sufficiently soon/often the bus, the
		32-character RxFIFO may fill up. This leads to loss of
		data." 

	::= { x21IfEntry 14 }

	x21IfRxCRCErrors OBJECT-TYPE
            SYNTAX  Counter
            ACCESS  read-only
            STATUS  mandatory

            DESCRIPTION
		"Count of corrupted frames. Errors due to interference
		on the X21 cable."
		
	::= { x21IfEntry 15 }

	x21IfRxGiantFrames OBJECT-TYPE
            SYNTAX  Counter
            ACCESS  read-only
            STATUS  mandatory

            DESCRIPTION
		"Count of received frames with illegal framesize. This
 		 can occur if a frame delimiter is destroyed." 
		
	::= { x21IfEntry 16 }

	x21IfTxResets OBJECT-TYPE
            SYNTAX  Counter
            ACCESS  read-only
            STATUS  mandatory

            DESCRIPTION
		"Count of transmitter resets. Under rare circumstances
		it might be necessary to reset the transmitter to work
		properly." 


	::= { x21IfEntry 17 }

	x21IfTxAborts OBJECT-TYPE
            SYNTAX  Counter
            ACCESS  read-only
            STATUS  mandatory

            DESCRIPTION
		"Count of transmitter aborts. While sending a frame it
		might be necessary to indicate this frame as aborted. In
		this case the receiver regards this frame as illegal." 

	::= { x21IfEntry 18 }

	x21IfTxUnderruns OBJECT-TYPE
            SYNTAX  Counter
            ACCESS  read-only
            STATUS  mandatory

            DESCRIPTION
		"Count of transmitter underruns. The serial data for the
		X21 card is supplied too slowly." 

	::= { x21IfEntry 19 }

	x21IfTxGiantFrames OBJECT-TYPE
            SYNTAX  Counter
            ACCESS  read-only
            STATUS  mandatory

            DESCRIPTION
		"Count of transmitted frames with illegal
		framesize. This can occur if an upper module creates
		packets with more than the maximum allowed packet size."

	::= { x21IfEntry 20 }


END		-- of BIANCA-BRICK definitions
