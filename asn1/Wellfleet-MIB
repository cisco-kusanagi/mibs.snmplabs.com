-- Wellfleet Enterprise MIB (V1.3b) v5.70
-- Wed Dec 11 1991
-- J. Burruss & S. Willis

               Wellfleet-MIB DEFINITIONS ::= BEGIN

               IMPORTS
                       enterprises, Counter, NetworkAddress,
		       IpAddress, Gauge, TimeTicks
                           FROM RFC1155-SMI
                       DisplayString
                           FROM RFC1213-MIB;

               wellfleet	OBJECT IDENTIFIER ::= { enterprises 18 }

               commServer	OBJECT IDENTIFIER ::= { wellfleet 1 }

	       wfMib		OBJECT IDENTIFIER ::= { commServer 1 }

	       wfXns		OBJECT IDENTIFIER ::= { wfMib 6 }
	       wfDrs		OBJECT IDENTIFIER ::= { wfMib 29 }
	       wfBridge		OBJECT IDENTIFIER ::= { wfMib 31 }
	       wfTftp		OBJECT IDENTIFIER ::= { wfMib 32 }
	       wfApple		OBJECT IDENTIFIER ::= { wfMib 34 }
	       wfConfig		OBJECT IDENTIFIER ::= { wfMib 35 }
	       wfIpx		OBJECT IDENTIFIER ::= { wfMib 41 }
	
	-- The XNS Group
	
	-- The XNS Group contains information about the XNS
	-- module of a Wellfleet Communications Server
	
	wfxnsMib   OBJECT IDENTIFIER ::= { wfXns 1 }

	wfxnsidp   OBJECT IDENTIFIER ::= { wfxnsMib 1 }

	wfxnsidpForwarding OBJECT-TYPE
		SYNTAX INTEGER {
			forwarding(1),
			host(2)
		}
		ACCESS read-only
		STATUS mandatory
		DESCRIPTION
			"Indicates whether the node is a router."
		::= { wfxnsidp 1 }
	
	wfxnsidpInReceives OBJECT-TYPE
		SYNTAX INTEGER
		ACCESS read-only
		STATUS mandatory
		DESCRIPTION
			" Contains the total number of all IDP datagrams 
			(including those received in error) received from
			all interfaces."
		::= { wfxnsidp 2 }
	
	wfxnsidpInHdrErrors OBJECT-TYPE
		SYNTAX INTEGER
		ACCESS read-only
		STATUS mandatory
		DESCRIPTION
			"Contains the number of IDP datagrams discarded
			because of errors in their IDP headers. Such errors
			include bad checksums, format errors and bad hop 
			counts. "
		::= { wfxnsidp 3 }
	
	wfxnsidpInAddrErrors OBJECT-TYPE
		SYNTAX INTEGER
		ACCESS read-only
		STATUS mandatory
		DESCRIPTION
			"The number of IDP datagrams discarded because of
			invalid destination fields. "
		::= { wfxnsidp 4 }
	
	wfxnsidpForwDatagrams OBJECT-TYPE
		SYNTAX INTEGER
		ACCESS read-only
		STATUS mandatory
		DESCRIPTION
			"The number of received IDP datagrams not addressed
			to the XNS router. The router attempts to forward
			these datagrams to their ultimate destination. "
		::= { wfxnsidp 5 }

	wfxnsidpInUnknownProtos OBJECT-TYPE
		SYNTAX INTEGER
		ACCESS read-only
		STATUS mandatory
		DESCRIPTION
			"The number of IDP datagrams discarded because of
			an invalid protocol field."
		::= { wfxnsidp 6 }
	
	wfxnsidpInDiscards OBJECT-TYPE
		SYNTAX INTEGER
		ACCESS read-only
		STATUS mandatory
		DESCRIPTION
			"The number of input IDP datagrams discarded because of
			of insufficient Server resources. "
		::= { wfxnsidp 7 }
	
	wfxnsidpInDelivers OBJECT-TYPE
		SYNTAX INTEGER
		ACCESS read-only
		STATUS mandatory
		DESCRIPTION
			"The number of IDP datagrams delivered to the IDP
			user protocols. (Error, Echo, RIP). "
		::= { wfxnsidp 8 }

	wfxnsidpOutRequests OBJECT-TYPE
		SYNTAX INTEGER
		ACCESS read-only
		STATUS mandatory
		DESCRIPTION
			"The number of IDP datagrams generated by the local
			IDP user protocols. "
		::= { wfxnsidp 9 }
	
	wfxnsidpOutDiscards OBJECT-TYPE
		SYNTAX INTEGER
		ACCESS read-only
		STATUS mandatory
		DESCRIPTION
			"The number of output IDP datagrams discarded because of
			of insufficient Server resources. "
		::= { wfxnsidp 10 }
	
	wfxnsidpOutNoRoutes OBJECT-TYPE
		SYNTAX INTEGER
		ACCESS read-only
		STATUS mandatory
		DESCRIPTION
			"The number of IDP datagrams discarded because no route
			could be found for their destination. "
		::= { wfxnsidp 11 }
	
	wfxnsidpErrs OBJECT IDENTIFIER ::= { wfxnsidp 12 }
	-- "A list of error Counters. "
	
	wfxnsidpErrSupressed OBJECT-TYPE
		SYNTAX INTEGER
		ACCESS read-only
		STATUS mandatory
		DESCRIPTION
			"The number of packet dropped because their length
			is below minimum. "
		::= { wfxnsidpErrs 1 }
	
	wfxnsidpErrDestUnspec OBJECT-TYPE
		SYNTAX INTEGER
		ACCESS read-only
		STATUS mandatory
		DESCRIPTION
			"The number of destination-host-generated Error packets
			 with an Error Number of 0 relayed by the router.  This
			 indicates an IDP packet rejected for unspecified reasons."
		::= { wfxnsidpErrs 2 }
	
	wfxnsidpErrDestHdrLen OBJECT-TYPE
		SYNTAX INTEGER
		ACCESS read-only
		STATUS mandatory
		DESCRIPTION
			"The number of packets rejected by a destination host
			 because the packet header was of insufficient length."
		::= { wfxnsidpErrs 3 }
	
	wfxnsidpErrDestProto OBJECT-TYPE
		SYNTAX INTEGER
		ACCESS read-only
		STATUS mandatory
		DESCRIPTION
			"The number of packets rejected by a destination host
			because the protocol type field contained an invalid or
			unknown value."
		::= { wfxnsidpErrs 4 }
	
	wfxnsidpErrDestCksum OBJECT-TYPE
		SYNTAX INTEGER
		ACCESS read-only
		STATUS mandatory
		DESCRIPTION
			"The number of packets rejected by a destination host
			because of a faulty or corrupted IDP checksum."
		::= { wfxnsidpErrs 5 }
	
	wfxnsidpErrDestBadSock OBJECT-TYPE
		SYNTAX INTEGER
		ACCESS read-only
		STATUS mandatory
		DESCRIPTION
			"The number of packets rejected by a destination host
			because the packet was addressed to an unknown socket."
		::= { wfxnsidpErrs 6 }
	
	wfxnsidpErrDestNoResrcs OBJECT-TYPE
		SYNTAX INTEGER
		ACCESS read-only
		STATUS mandatory
		DESCRIPTION
			"The number of packets rejected by a destination host
			because of a lack of processing resources."
		::= { wfxnsidpErrs 7 }
	
	wfxnsidpErrDestXitUnspec OBJECT-TYPE
		SYNTAX INTEGER
		ACCESS read-only
		STATUS mandatory
		DESCRIPTION
			"The number of packets rejected by the router
			for unspecified reasons."
		::= { wfxnsidpErrs 8 }
	
	wfxnsidpErrXitCksum OBJECT-TYPE
		SYNTAX INTEGER
		ACCESS read-only
		STATUS mandatory
		DESCRIPTION
			"The number of packets rejected by the router
			because of a faulty or corrupted checksum."
		::= { wfxnsidpErrs 9 }
	
	wfxnsidpErrXitUnreach OBJECT-TYPE
		SYNTAX INTEGER
		ACCESS read-only
		STATUS mandatory
		DESCRIPTION
			"The number of packets rejected by the router
			because the destination is unreachable."
		::= { wfxnsidpErrs 10 }
	
	wfxnsidpErrXitHopCnt OBJECT-TYPE
		SYNTAX INTEGER
		ACCESS read-only
		STATUS mandatory
		DESCRIPTION
			"The number of packets rejected by the router
			becuase the packet had passed through more than the
			maximum number of routers before arriving at its
			destination."
		::= { wfxnsidpErrs 11 }
	
	wfxnsidpErrXitTooBig OBJECT-TYPE
		SYNTAX INTEGER
		ACCESS read-only
		STATUS mandatory
		DESCRIPTION
			"The number of packets rejected by the router
			becuase the packet was too long for the router
			to relay."
		::= { wfxnsidpErrs 12 }
	
	wfxnsidpAddrTable OBJECT-TYPE
		SYNTAX SEQUENCE OF WfXnsIdpAddrEntry 
		ACCESS not-accessible
		STATUS mandatory
		DESCRIPTION
			"The IDP Address table. "
		::= { wfxnsidp 13 }
	
	wfxnsidpAddrEntry OBJECT-TYPE
		SYNTAX WfXnsIdpAddrEntry
		ACCESS not-accessible
		STATUS mandatory
		DESCRIPTION
			"An entry in the IDP address table."
		INDEX { wfxnsidpAddrAddress }
		::= { wfxnsidpAddrTable 1 }
	
	WfXnsIdpAddrEntry ::= SEQUENCE {
		wfxnsidpAddrAddress
			OCTET STRING,
		wfxnsidpAddrIfIndex
			INTEGER
	}

	wfxnsidpAddrAddress OBJECT-TYPE
		SYNTAX OCTET STRING (SIZE (6))
		ACCESS read-only
		STATUS mandatory
		DESCRIPTION
			"The IDP network number. "
		::= { wfxnsidpAddrEntry 1 }
	
	wfxnsidpAddrIfIndex OBJECT-TYPE
		SYNTAX INTEGER
		ACCESS read-only
		STATUS mandatory
		DESCRIPTION
			"The interface index. "
		::= { wfxnsidpAddrEntry 2 }
	
	wfxnsidpRoutingTable OBJECT-TYPE
		SYNTAX SEQUENCE OF WfXnsIdpRouteEntry
		ACCESS not-accessible
		STATUS mandatory
		DESCRIPTION
			"The XNS IDP routing table."
		::= { wfxnsidp 14 }
	
	wfxnsidpRouteEntry OBJECT-TYPE
		SYNTAX WfXnsIdpRouteEntry
		ACCESS not-accessible
		STATUS mandatory
		DESCRIPTION
			"Information about a routing table entry. "
		INDEX { wfxnsidpRouteDest }
		::= { wfxnsidpRoutingTable 1 }
	
	WfXnsIdpRouteEntry ::= SEQUENCE {
		wfxnsidpRouteDest
			INTEGER,
		wfxnsidpRouteIfIndex
			INTEGER,
		wfxnsidpRouteMetric
			INTEGER,
		wfxnsidpRouteNextHop
			OCTET STRING,
		wfxnsidpRouteType
			INTEGER,
		wfxnsidpRouteProto
			INTEGER,
		wfxnsidpRouteAge
			INTEGER
	}

	wfxnsidpRouteDest OBJECT-TYPE
		SYNTAX INTEGER
		ACCESS read-only
		STATUS mandatory
		DESCRIPTION
			"The destination network. "
		::= { wfxnsidpRouteEntry 1 }
	
	wfxnsidpRouteIfIndex OBJECT-TYPE
		SYNTAX INTEGER
		ACCESS read-only
		STATUS mandatory
		DESCRIPTION
			"An index to the next hop interface. "
		::= { wfxnsidpRouteEntry 2 }
	
	wfxnsidpRouteMetric OBJECT-TYPE
		SYNTAX INTEGER
		ACCESS read-only
		STATUS mandatory
		DESCRIPTION
			"The RIP hop count to the destination. 0 means the
			host is locally attached. "
		::= { wfxnsidpRouteEntry 3 }
	
	wfxnsidpRouteNextHop OBJECT-TYPE
		SYNTAX OCTET STRING (SIZE (6))
		ACCESS read-only
		STATUS mandatory
		DESCRIPTION
			"The host address of the next hop gateway. "
		::= { wfxnsidpRouteEntry 4 }
	
	wfxnsidpRouteType OBJECT-TYPE
		SYNTAX INTEGER
		ACCESS read-only
		STATUS mandatory
		DESCRIPTION
			"Indicates whether the route was statically configured,
			direct or learned via RIP. "
		::= { wfxnsidpRouteEntry 5 }
	
	wfxnsidpRouteProto OBJECT-TYPE
		SYNTAX INTEGER
		ACCESS read-only
		STATUS mandatory
		DESCRIPTION
			"The actual routing protocol used to determine the route."
		::= { wfxnsidpRouteEntry 6 }
	
	wfxnsidpRouteAge OBJECT-TYPE
		SYNTAX INTEGER
		ACCESS read-only
		STATUS mandatory
		DESCRIPTION
			"The age (in seconds) of the route. "
		::= { wfxnsidpRouteEntry 7 }
	
	
	-- The DECNET Phase IV Group
	
	-- The DECNET Phase IV Group contains information about Wellfleet's
	-- DECNET implementation. 
	
	wfdrsState OBJECT-TYPE
		SYNTAX INTEGER {
			enabled(1),	-- router is enabled and forwarding
			disabled(2)	-- router is disabled
		}
		ACCESS read-only
		STATUS mandatory
		DESCRIPTION
			"Indicates the state of the router."
		::= { wfDrs 1 }
	
	wfdrsArea OBJECT-TYPE
		SYNTAX INTEGER (1..63)
		ACCESS read-only
		STATUS mandatory
		DESCRIPTION
			"The number of the local DECNET area."
		::= { wfDrs 2 }
	
	wfdrsNode OBJECT-TYPE
		SYNTAX INTEGER (1..1023)
		ACCESS read-only
		STATUS mandatory
		DESCRIPTION
			"The DECNET node number."
		::= { wfDrs 3 }
	
	wfdrsRouting OBJECT-TYPE
		SYNTAX INTEGER
		ACCESS read-only
		STATUS mandatory
		DESCRIPTION
			" / tbs /"
		::= { wfDrs 4 }
	
	wfdrsMaxArea OBJECT-TYPE
		SYNTAX INTEGER
		ACCESS read-only
		STATUS mandatory
		DESCRIPTION
			"The maximum number of areas in the network."
		::= { wfDrs 5 }
	
	wfdrsMaxNode OBJECT-TYPE
		SYNTAX INTEGER
		ACCESS read-only
		STATUS mandatory
		DESCRIPTION
			"The maximum number of nodes in any area."
		::= { wfDrs 6 }
	
	wfdrsAreaMaxHop OBJECT-TYPE
		SYNTAX INTEGER
		ACCESS read-only
		STATUS mandatory
		DESCRIPTION
			"Maximum number of areas a packet can transit from source to 
			destination."
		::= { wfDrs 7 }
	wfdrsAreaMaxCost OBJECT-TYPE
		SYNTAX INTEGER
		ACCESS read-only
		STATUS mandatory
		DESCRIPTION
			"The maximum area-to-area transit cost."
		::= { wfDrs 8 }
	
	wfdrsNodeMaxHop OBJECT-TYPE
		SYNTAX INTEGER
		ACCESS read-only
		STATUS mandatory
		DESCRIPTION
			"The maximum number of hops a packet can transit from source
			to destination."
		::= { wfDrs 9 }
	
	wfdrsNodeMaxCost OBJECT-TYPE
		SYNTAX INTEGER
		ACCESS read-only
		STATUS mandatory
		DESCRIPTION
			"The maximum node-to-node transit cost."
		::= { wfDrs 10 }
	
	wfdrsMaxVisits OBJECT-TYPE
		SYNTAX INTEGER
		ACCESS read-only
		STATUS mandatory
		DESCRIPTION
			"Maximum number of times packet can transit the same router."
		::= { wfDrs 11 }
	
	wfdrsRoutingTimer OBJECT-TYPE
		SYNTAX INTEGER
		ACCESS read-only
		STATUS mandatory
		DESCRIPTION
			"Time interval between topology packets on non-broadcast media."
		::= { wfDrs 12 }
	
	wfdrsBcastRoutTimer OBJECT-TYPE
		SYNTAX INTEGER
		ACCESS read-only
		STATUS mandatory
		DESCRIPTION
			"Time interval between topology packets on bradcast media."
		::= { wfDrs 13 }
	
	wfdrsBcastEnodeAdj OBJECT-TYPE
		SYNTAX INTEGER
		ACCESS read-only
		STATUS mandatory
		DESCRIPTION
			"Maximum number of adjacent nodes"
		::= { wfDrs 14 }
	
	wfdrsIfTable OBJECT-TYPE
		SYNTAX SEQUENCE OF WfDrsIfTabEntry
		ACCESS not-accessible
		STATUS mandatory
		DESCRIPTION
			"The DECNET Interface table. "
		::= { wfDrs 15 }
	
	wfdrsIfTabEntry OBJECT-TYPE
		SYNTAX WfDrsIfTabEntry
		ACCESS not-accessible
		STATUS mandatory
		DESCRIPTION
			"An entry in the DECNET interface table. "
		INDEX { wfdrsIfTabEntIfIndex }
		::= { wfdrsIfTable 1 }
	
	WfDrsIfTabEntry ::= SEQUENCE {
		wfdrsIfTabEntIfIndex
			INTEGER,
		wfdrsIfTabEntState
			INTEGER,
		wfdrsIfTabEntName
			DisplayString,
		wfdrsIfTabEntCost
			INTEGER,
		wfdrsIfTabEntHelloTimr
			INTEGER,
		wfdrsIfTabEntRtrPrior
			INTEGER,
		wfdrsIfTabEntNumRtrs
			INTEGER
	}
	
	wfdrsIfTabEntIfIndex OBJECT-TYPE
		SYNTAX INTEGER
		ACCESS read-only
		STATUS mandatory
		DESCRIPTION
			"The router assigned interface number. "
		::= { wfdrsIfTabEntry 1 }
	
	wfdrsIfTabEntState OBJECT-TYPE
		SYNTAX INTEGER
		ACCESS read-only
		STATUS mandatory
		DESCRIPTION
			"The state of the interface. "
		::= { wfdrsIfTabEntry 2 }
	
	wfdrsIfTabEntName OBJECT-TYPE
		SYNTAX INTEGER
		ACCESS read-only
		STATUS mandatory
		DESCRIPTION
			"The circuit group name for this interface. "
		::= { wfdrsIfTabEntry 3 }
	
	wfdrsIfTabEntCost OBJECT-TYPE
		SYNTAX INTEGER
		ACCESS read-only
		STATUS mandatory
		DESCRIPTION
			"The DECNET circuit cost for this interface. "
		::= { wfdrsIfTabEntry 4 }
	
	wfdrsIfTabEntHelloTimr OBJECT-TYPE
		SYNTAX INTEGER
		ACCESS read-only
		STATUS mandatory
		DESCRIPTION
			"The time interval between DECNET hello packets."
		::= { wfdrsIfTabEntry 5 }
	
	wfdrsIfTabEntRtrPrior OBJECT-TYPE
		SYNTAX INTEGER
		ACCESS read-only
		STATUS mandatory
		DESCRIPTION
			" The router priority."
		::= { wfdrsIfTabEntry 6 }
	
	wfdrsIfTabEntNumRtrs OBJECT-TYPE
		SYNTAX INTEGER
		ACCESS read-only
		STATUS mandatory
		DESCRIPTION
			"Maximum number of adjacent routers on this interface."
		::= { wfdrsIfTabEntry 7 }
	
	wfdrsAreaRoutingTable OBJECT-TYPE
		SYNTAX SEQUENCE OF WfDrsAreaRoute
		ACCESS not-accessible
		STATUS mandatory
		DESCRIPTION
			"The level 2 (area) routing table. "
		::= { wfDrs 16 }
	
	wfdrsAreaRoute OBJECT-TYPE
		SYNTAX WfDrsAreaRoute
		ACCESS not-accessible
		STATUS mandatory
		DESCRIPTION
			"Information about a route to an area. "
		INDEX { wfdrsAreaRouteDest }
		::= { wfdrsAreaRoutingTable 1 }
	
	WfDrsAreaRoute ::= SEQUENCE {
		wfdrsAreaRouteDest
			INTEGER,
		wfdrsAreaRouteCost
			INTEGER,
		wfdrsAreaRouteHopCount
			INTEGER,
		wfdrsAreaRouteNextArea
			INTEGER,
		wfdrsAreaRouteNextNode
			INTEGER,
		wfdrsAreaRouteIf
			INTEGER
	}
	wfdrsAreaRouteDest OBJECT-TYPE
		SYNTAX INTEGER
		ACCESS read-only
		STATUS mandatory
		DESCRIPTION
			"Destination area. "
		::= { wfdrsAreaRoute 1 }
	
	wfdrsAreaRouteCost OBJECT-TYPE
		SYNTAX INTEGER
		ACCESS read-only
		STATUS mandatory
		DESCRIPTION
			"Aggregate cost to reach destination area."
		::= { wfdrsAreaRoute 2 }
	
	wfdrsAreaRouteHopCount OBJECT-TYPE
		SYNTAX INTEGER
		ACCESS read-only
		STATUS mandatory
		DESCRIPTION
			"Number of hops to reach destination area."
		::= { wfdrsAreaRoute 3 }
	
	wfdrsAreaRouteNextArea OBJECT-TYPE
		SYNTAX INTEGER
		ACCESS read-only
		STATUS mandatory
		DESCRIPTION
			"The next area to forward the packet. "
		::= { wfdrsAreaRoute 4 }
	wfdrsAreaRouteNextNode OBJECT-TYPE
		SYNTAX INTEGER
		ACCESS read-only
		STATUS mandatory
		DESCRIPTION
			"The next node to forward the packet to."
		::= { wfdrsAreaRoute 5 }
	wfdrsAreaRouteIf OBJECT-TYPE
		SYNTAX INTEGER
		ACCESS read-only
		STATUS mandatory
		DESCRIPTION
			"The interface to forward the packet on."
		::= { wfdrsAreaRoute 6 }
	
	wfdrsNodeRoutingTable OBJECT-TYPE	
		SYNTAX SEQUENCE OF WfDrsNodeRoute
		ACCESS not-accessible
		STATUS mandatory
		DESCRIPTION
			"The level 1 (node) routing table. "
		::= { wfDrs 17 }
	
	wfdrsNodeRoute OBJECT-TYPE
		SYNTAX WfDrsNodeRoute
		ACCESS not-accessible
		STATUS mandatory
		DESCRIPTION
			"Information about how to reach an node
			within the area. "
		INDEX { wfdrsNodeRouteDest }
		::= { wfdrsNodeRoutingTable 1 }
	 
	WfDrsNodeRoute ::= SEQUENCE {
		wfdrsNodeRouteDest
			INTEGER,
		wfdrsNodeRouteCost
			INTEGER,
		wfdrsNodeRouteHopCount
			INTEGER,
		wfdrsNodeRouteNextHop
			INTEGER,
		wfdrsNodeRouteIf
			INTEGER
	}
	wfdrsNodeRouteDest OBJECT-TYPE
		SYNTAX INTEGER
		ACCESS read-only
		STATUS mandatory
		DESCRIPTION
			"The destination node number."
		::= { wfdrsNodeRoute 1 }
	
	wfdrsNodeRouteCost OBJECT-TYPE
		SYNTAX INTEGER
		ACCESS read-only
		STATUS mandatory
		DESCRIPTION
			"The aggregate cost to the destination node."
		::= { wfdrsNodeRoute 2 }
	
	wfdrsNodeRouteHopCount OBJECT-TYPE
		SYNTAX INTEGER
		ACCESS read-only
		STATUS mandatory
		DESCRIPTION
			"Number of hops to destination node."
		::= { wfdrsNodeRoute 3 }
	
	wfdrsNodeRouteNextHop OBJECT-TYPE
		SYNTAX INTEGER
		ACCESS read-only
		STATUS mandatory
		DESCRIPTION
			"The node number of the next hop."
		::= { wfdrsNodeRoute 4 }
	wfdrsNodeRouteIf OBJECT-TYPE
		SYNTAX INTEGER
		ACCESS read-only
		STATUS mandatory
		DESCRIPTION
			"The interface index of the next hop."
		::= { wfdrsNodeRoute 5 }
		
	
          -- the Bridge Group

          -- The Bridge Group contains information about the Learning Bridge
	  -- module of a Wellfleet Communications Server

          wflbFwdTable OBJECT-TYPE
                  SYNTAX  SEQUENCE OF WfBridgeFwdEntry
                  ACCESS  not-accessible
                  STATUS  mandatory
                  DESCRIPTION
			"The bridge modules's table of MAC address-interface
			mappings."
                  ::= { wfBridge 1 }

          wflbFwdEntry OBJECT-TYPE
                  SYNTAX  WfBridgeFwdEntry
                  ACCESS  not-accessible
                  STATUS  mandatory
                  DESCRIPTION
			"Each entry describes one MAC address-interface
			mapping; that is, each entry describes a station
			which has been or is being learned."
		  INDEX { wflbFwdEntMacAddr }
                  ::= { wflbFwdTable 1 }

	  WfBridgeFwdEntry ::= SEQUENCE {
		wflbFwdEntIf
			INTEGER,
		wflbFwdEntMacAddr
			OCTET STRING,
		wflbFwdEntSrcDisp
			INTEGER,
		wflbFwdEntDstDisp
			INTEGER,
		wflbFwdEntIfName
			DisplayString,
		wflbFwdEntFloodStat
			INTEGER
	  }

  	  wflbFwdEntIf OBJECT-TYPE
		  SYNTAX  INTEGER
                  ACCESS  read-only
                  STATUS  mandatory
                  DESCRIPTION
			"A number identifying the interface on which the station
			addressed by wflbFwdEntMacAddr was learned.  The interface
			identified by a particular value of this index is the same
			interface as identified	by the same value of ifIndex."
                  ::= { wflbFwdEntry 1 }

  	  wflbFwdEntMacAddr OBJECT-TYPE
		  SYNTAX  OCTET STRING (SIZE (6))
                  ACCESS  read-only
                  STATUS  mandatory
                  DESCRIPTION
			"The MAC-level (physical) address of the station described
			by this wflbFwdEntry."
                  ::= { wflbFwdEntry 2 }

  	  wflbFwdEntSrcDisp OBJECT-TYPE
		  SYNTAX  INTEGER
                  ACCESS  read-only
                  STATUS  mandatory
                  DESCRIPTION
			"Identifies the disposition of frames containing
			wflbFwdEntMacAddr as the source address field of the
			frame.  0 signifies drop; 1 signifies forward."
                  ::= { wflbFwdEntry 3 }

  	  wflbFwdEntDstDisp OBJECT-TYPE
		  SYNTAX  INTEGER
                  ACCESS  read-only
                  STATUS  mandatory
                  DESCRIPTION
			"Identifies the disposition of frames containing
			wflbFwdEntMacAddr as the destination address field of the
			frame.  0 signifies drop; 1 signifies forward."
                  ::= { wflbFwdEntry 4 }

  	  wflbFwdEntIfName OBJECT-TYPE
		  SYNTAX  DisplayString
                  ACCESS  read-only
                  STATUS  mandatory
                  DESCRIPTION
			"A text string contining the circuit group name of interface
			wflbFwdEntIf."
                  ::= { wflbFwdEntry 5 }


  	  wflbFwdEntFloodStat OBJECT-TYPE
		  SYNTAX  INTEGER {
				forwarding(1),
				flooding(2),
				dropping(3)
			 	}
                  ACCESS  read-only
                  STATUS  mandatory
                  DESCRIPTION
			"Denotes whether frames destined for wflbFwdEntMacAddr
			are being flooded or dropped if the MAC Address-interface
			mapping for wflbFwdEntMacAddr has not yet been learned.
			If the value of wflbFwdEntFloodStat is forwarding(1), the
			MAC Address-interface mapping has been learned."
                  ::= { wflbFwdEntry 6 }

          wflbRifTable OBJECT-TYPE
                  SYNTAX  SEQUENCE OF WfBridgeRifEntry
                  ACCESS  not-accessible
                  STATUS  mandatory
                  DESCRIPTION
                        "The bridge modules's source routing RIF (Routing 
                         Information Field) table." 
                  ::= { wfBridge 2 }

          wflbRifEntry OBJECT-TYPE
                  SYNTAX  WfBridgeRifEntry
                  ACCESS  not-accessible
                  STATUS  mandatory
                  DESCRIPTION
                        "Each entry contains a RIF cache for a network node.
                         The table is indexed by an arbitrary set of 6
                         integers."
                  INDEX { INTEGER, INTEGER, INTEGER,
                          INTEGER, INTEGER, INTEGER }
                  ::= { wflbRifTable 1 }

          WfBridgeRifEntry ::= SEQUENCE {
                wflbRifMacSrcAddress
                        OCTET STRING,
                wflbRifMacAddress
                        OCTET STRING,
                wflbRifCg
                        DisplayString,
                wflbRif
                        OCTET STRING
          }

          wflbRifMacSrcAddress OBJECT-TYPE
                  SYNTAX  OCTET STRING (SIZE (6))
                  ACCESS  read-only
                  STATUS  mandatory
                  DESCRIPTION
                        "The MAC-level (physical) address of the source
                         interface."
                  ::= { wflbRifEntry 1 }

          wflbRifMacAddress OBJECT-TYPE
                  SYNTAX  OCTET STRING (SIZE (6))
                  ACCESS  read-only
                  STATUS  mandatory
                  DESCRIPTION
                        "The MAC-level (physical) address of the destination
                         interface."
                  ::= { wflbRifEntry 2 }

          wflbRifCg OBJECT-TYPE
		  SYNTAX  DisplayString (SIZE (0..32))
                  ACCESS  read-only
                  STATUS  mandatory
                  DESCRIPTION
                        "The name of the circuit group that connects the source
                         interface to token ring."
                  ::= { wflbRifEntry 3 }

          wflbRif OBJECT-TYPE
                  SYNTAX  OCTET STRING (SIZE (3..18))
                  ACCESS  read-only
                  STATUS  mandatory
                  DESCRIPTION
                        "A description of the path used to source route packets
                         between the source route and the destination.  The
                         first two bytes contain the routing control (RC) field
                         that describes the routing type, field length,
                         direction bit and largest frame size as follows.
                              bits 1-2:   RIF type
                                   00: Specifically Routed Frame (SRF)
                                   11: Spanning Tree Explorer (STE)
                                   10: All Routes Explorer (ARE)

                              bit 3:      Reserved

                              bits 4-8:   Length of RIF
                                   Maximum = 18 bytes 

                              bit 9:      Direction that frames traverses LAN
                                    0: Forward
                                    1: Reverse
                              bits 10-12: Largest Frame size for this route
                                   Maximum is 4472 bytes

                              bits 13-16: Reserved

                         Next are a series of two-byte route descriptors; each
                         contains a 12-bit LAN ID followed by a 4-bit bridge ID
                         number which indicate the next hop in the route."
                  ::= { wflbRifEntry 4 }


          -- the TFTP Group

          -- The TFTP Group contains information about the Trivial File Transfer
	  -- Protocol module of a Wellfleet Communications Server.

	
          wftftpFilesIn OBJECT-TYPE
                  SYNTAX  INTEGER
                  ACCESS  read-only
                  STATUS  mandatory
                  DESCRIPTION
			"The number of successful transfers of files to this
			 entity since the system was last initialized."
                  ::= { wfTftp 1 }


          wftftpFilesOut OBJECT-TYPE
                  SYNTAX  INTEGER
                  ACCESS  read-only
                  STATUS  mandatory
                  DESCRIPTION
			"The number of successful transfers of files from this
			 entity since the system was last initialized."
                  ::= { wfTftp 2 }


          wftftpWRQIn OBJECT-TYPE
                  SYNTAX  INTEGER
                  ACCESS  read-only
                  STATUS  mandatory
                  DESCRIPTION
			"The number of WRQ PDUs received by the TFTP
			 entity since the system was last initialized.
			 This is the number of requests to deposit a file
			 made by a remote TFTP client."
                  ::= { wfTftp 3 }


          wftftpWRQOut OBJECT-TYPE
                  SYNTAX  INTEGER
                  ACCESS  read-only
                  STATUS  mandatory
                  DESCRIPTION
			"The number of WRQ PDUs sent by the TFTP
			 entity since the system was last initialized.
			 This is the number of requests made by this system
			 to send a file to a remote TFTP client."
                  ::= { wfTftp 4 }


          wftftpRRQIn OBJECT-TYPE
                  SYNTAX  INTEGER
                  ACCESS  read-only
                  STATUS  mandatory
                  DESCRIPTION
			"The number of RRQ PDUs received by the TFTP
			 entity since the system was last initialized.
			 This is the number of requests to retreive a file
			 made by a remote TFTP client."
                  ::= { wfTftp 5 }


          wftftpRRQOut OBJECT-TYPE
                  SYNTAX  INTEGER
                  ACCESS  read-only
                  STATUS  mandatory
                  DESCRIPTION
			"The number of RRQ PDUs sent by the TFTP
			 entity since the system was last initialized.
			 This is the number of requests made by this system
			 to retrieve a file from a remote TFTP client."
                  ::= { wfTftp 6 }


          wftftpRxmits OBJECT-TYPE
                  SYNTAX  INTEGER
                  ACCESS  read-only
                  STATUS  mandatory
                  DESCRIPTION
			"The number of TFTP PDUs that have been retransmitted
			 by this entity."
                  ::= { wfTftp 7 }


          wftftpERRIn OBJECT-TYPE
                  SYNTAX  INTEGER
                  ACCESS  read-only
                  STATUS  mandatory
                  DESCRIPTION
			"The number of ERR PDUs received by the TFTP entity since
			 the system was last initialized."
                  ::= { wfTftp 8 }


          wftftpERROut OBJECT-TYPE
                  SYNTAX  INTEGER
                  ACCESS  read-only
                  STATUS  mandatory
                  DESCRIPTION
			"The number of ERR PDUs sent by the TFTP entity since
			 the system was last initialized."
                  ::= { wfTftp 9 }


          wftftpAborts OBJECT-TYPE
                  SYNTAX  INTEGER
                  ACCESS  read-only
                  STATUS  mandatory
                  DESCRIPTION
			"The number of unsuccessful TFTP file transfer that
			 have been abnormally terminated."
                  ::= { wfTftp 10 }

	

          -- the AppleTalk group

          -- The AppleTalk Group contains information about the AppleTalk
	  -- Router module of a Wellfleet Communications Server


          wfappleStation	OBJECT IDENTIFIER ::= { wfApple 1 }

          wfappleStationRouting OBJECT-TYPE
                  SYNTAX  INTEGER
                  ACCESS  read-only
                  STATUS  mandatory
                  DESCRIPTION 
			"Indicates whether this entity is routing (i.e.,
			forwarding) AppleTalk datagrams.  1 signifies
			forwarding; 0 not forwarding."
                  ::= { wfappleStation 1 }

          wfappleStationVersion OBJECT-TYPE
                  SYNTAX  INTEGER
                  ACCESS  read-only
                  STATUS  mandatory
                  DESCRIPTION
			"The version number of the AppleTalk protocol supported
			by this entity (i.e., Wellfleet supports Version 2)."
                  ::= { wfappleStation 2 }


          wfapplePortTable OBJECT-TYPE
                  SYNTAX  SEQUENCE OF WfApplePortEntry
                  ACCESS  not-accessible
                  STATUS  mandatory
                  DESCRIPTION
			"The wfapplePortTable is a table of per-interface
			AppleTalk Configuration parameters.  An interface will
			have a corresponding entry in this table only if AppleTalk
			routing is defined for that interface."
                  ::= { wfApple 2 }

          wfapplePortEntry OBJECT-TYPE
                  SYNTAX  WfApplePortEntry
                  ACCESS  not-accessible
                  STATUS  mandatory
                  DESCRIPTION
			"Each entry describes an interface of the AppleTalk
			Router."
		  INDEX { wfapplePortIfIndex }
                  ::= { wfapplePortTable 1 }

	  WfApplePortEntry ::= SEQUENCE {
		wfapplePortIfIndex
			INTEGER,
		wfapplePortSeed
			INTEGER,
		wfapplePortMinNet
			INTEGER,
		wfapplePortMaxNet
			INTEGER,
		wfapplePortNetwork
			INTEGER,
		wfapplePortNodeID
			INTEGER,
		wfapplePortDefaultZone
			DisplayString
	  }

  	  wfapplePortIfIndex OBJECT-TYPE
		  SYNTAX  INTEGER
                  ACCESS  read-only
                  STATUS  mandatory
                  DESCRIPTION
			"A number identifying the interface described by this
			wfapplePortEntry. The interface identified by a particular
			value of this index is the same interface as identified
			by the same value of ifIndex."
                  ::= { wfapplePortEntry 1 }

	  wfapplePortSeed OBJECT-TYPE
		  SYNTAX  INTEGER
                  ACCESS  read-only
                  STATUS  mandatory
                  DESCRIPTION
			"Describes whether this interface was configured as a 'seed'
			port.  1 indicates a seed port; 0 a non-seed port."
                  ::= { wfapplePortEntry 2 }

	  wfapplePortMinNet OBJECT-TYPE
		  SYNTAX  INTEGER
                  ACCESS  read-only
                  STATUS  mandatory
                  DESCRIPTION
			"The minimum network number in the range of network numbers
			assigned to this interface."
                  ::= { wfapplePortEntry 3 }

	  wfapplePortMaxNet OBJECT-TYPE
		  SYNTAX  INTEGER
                  ACCESS  read-only
                  STATUS  mandatory
                  DESCRIPTION
			"The maximum network number in the range of network numbers
			assigned to this interface."
                  ::= { wfapplePortEntry 4 }

	  wfapplePortNetwork OBJECT-TYPE
		  SYNTAX  INTEGER
                  ACCESS  read-only
                  STATUS  mandatory
                  DESCRIPTION
			"The  network number within the range wfapplePortMinNet to
			wfapplePortMaxNet which is assigned to the network attached to
			this interface."
                  ::= { wfapplePortEntry 5 }

	  wfapplePortNodeID OBJECT-TYPE
		  SYNTAX  INTEGER
                  ACCESS  read-only
                  STATUS  mandatory
                  DESCRIPTION
			"The node identification which denotes this AppleTalk entity on
			network wfapplePortNetwork.  The pair (wfapplePortNetwork, 
			wfapplePortNodeID) constitutes a complete AppleTalk address."
                  ::= { wfapplePortEntry 6 }

	  wfapplePortDefaultZone OBJECT-TYPE
		  SYNTAX  DisplayString
                  ACCESS  read-only
                  STATUS  mandatory
                  DESCRIPTION
			"The name of the default zone for this interface (a zero-length
			string means that no default zone was assigned to this interface."
                  ::= { wfapplePortEntry 7 }


       wfappleDDP	OBJECT IDENTIFIER ::= { wfApple 3 }

          wfappleDDPPktsIn OBJECT-TYPE
                  SYNTAX  INTEGER
                  ACCESS  read-only
                  STATUS  mandatory
                  DESCRIPTION
			"The total number of DDP packets received by this entity."
                  ::= { wfappleDDP 1 }

          wfappleDDPPktsOut OBJECT-TYPE
                  SYNTAX  INTEGER
                  ACCESS  read-only
                  STATUS  mandatory
                  DESCRIPTION
			"The total number of DDP packets transmitted by this entity."
                  ::= { wfappleDDP 2 }

          wfappleDDPPktsFwd OBJECT-TYPE
                  SYNTAX  INTEGER
                  ACCESS  read-only
                  STATUS  mandatory
                  DESCRIPTION
       			"The total number of DDP packets forwarded by this entity."
                  ::= { wfappleDDP 3 }

          wfappleDDPDelivers OBJECT-TYPE
                  SYNTAX  INTEGER
                  ACCESS  read-only
                  STATUS  mandatory
                  DESCRIPTION
			"The total number of DDP packets received by this entity which
			were delivered to a higher-layer AppleTalk protocol for processing."
                  ::= { wfappleDDP 4 }

          wfappleDDPUnknownNet OBJECT-TYPE
                  SYNTAX  INTEGER
                  ACCESS  read-only
                  STATUS  mandatory
                  DESCRIPTION
       			"The total number of DDP packets discarded by this entity
			because the destination network to which the packet was directed
			was unknown."
                  ::= { wfappleDDP 5 }

          wfappleDDPHopsExceeded OBJECT-TYPE
                  SYNTAX  INTEGER
                  ACCESS  read-only
                  STATUS  mandatory
                  DESCRIPTION
       			"The total number of DDP packets discarded by this entity
			because the packet's hop count exceeded 15."
                  ::= { wfappleDDP 6 }

          wfappleDDPBadChksum OBJECT-TYPE
                  SYNTAX  INTEGER
                  ACCESS  read-only
                  STATUS  mandatory
                  DESCRIPTION
       			"The total number of DDP packets discarded by this entity
			because the contained an incorrect DDP checksum."
                  ::= { wfappleDDP 7 }

          wfappleDDPDropped OBJECT-TYPE
                  SYNTAX  INTEGER
                  ACCESS  read-only
                  STATUS  mandatory
                  DESCRIPTION
       			"The total number of DDP packets discarded by this entity."
                  ::= { wfappleDDP 8 }

       wfappleEcho	OBJECT IDENTIFIER ::= { wfApple 4 }

          wfappleEchoRequestIn OBJECT-TYPE
                  SYNTAX  INTEGER
                  ACCESS  read-only
                  STATUS  mandatory
                  DESCRIPTION
			"The number of AEP Echo Request Packets received by this
			entity."
                  ::= { wfappleEcho 1 }

          wfappleEchoResponseOut OBJECT-TYPE
                  SYNTAX  INTEGER
                  ACCESS  read-only
                  STATUS  mandatory
                  DESCRIPTION
			"The number of AEP Echo Response Packets sent by this
			entity."
                  ::= { wfappleEcho 2 }

       wfappleRTMP	OBJECT IDENTIFIER ::= { wfApple 5 }

          wfappleRTMPRequestIn OBJECT-TYPE
                  SYNTAX  INTEGER
                  ACCESS  read-only
                  STATUS  mandatory
                  DESCRIPTION
			"The total number of RTMP Request packets received by this entity."
                  ::= { wfappleRTMP 1 }

          wfappleRTMPResponseOut OBJECT-TYPE
                  SYNTAX  INTEGER
                  ACCESS  read-only
                  STATUS  mandatory
                  DESCRIPTION
			"The total number of RTMP Response packets transmitted by this entity."
                  ::= { wfappleRTMP 2 }


          wfappleRoutingTable OBJECT-TYPE
                  SYNTAX  SEQUENCE OF WfAppleRouteEntry
                  ACCESS  not-accessible
                  STATUS  mandatory
                  DESCRIPTION
			"The AppleTalk Routing Table contains an entry for each
			AppleTalk Route known to this entity."
                  ::= { wfApple 6 }

          wfappleRouteEntry OBJECT-TYPE
                  SYNTAX  WfAppleRouteEntry
                  ACCESS  not-accessible
                  STATUS  mandatory
                  DESCRIPTION
			"A route to a particular AppleTalk destination."
		  INDEX { wfappleRouteMinNet }
                  ::= { wfappleRoutingTable 1 }

	  WfAppleRouteEntry ::= SEQUENCE {
		wfappleRouteMinNet
			INTEGER,
		wfappleRouteMaxNet
			INTEGER,
		wfappleRouteIfIndex
			INTEGER,
		wfappleRouteDistance
			INTEGER,
		wfappleRouteNextNet
			INTEGER,
		wfappleRouteNextNode
			INTEGER,
		wfappleRouteState
			INTEGER
	  }

  	  wfappleRouteMinNet OBJECT-TYPE
		  SYNTAX  INTEGER
                  ACCESS  read-only
                  STATUS  mandatory
                  DESCRIPTION
			"The minimum network number in the destination's network
			number range."
                  ::= { wfappleRouteEntry 1 }

  	  wfappleRouteMaxNet OBJECT-TYPE
		  SYNTAX  INTEGER
                  ACCESS  read-only
                  STATUS  mandatory
                  DESCRIPTION
			"The maximum network number in the destination's network
			number range."
                  ::= { wfappleRouteEntry 2 }

  	  wfappleRouteIfIndex OBJECT-TYPE
		  SYNTAX  INTEGER
                  ACCESS  read-only
                  STATUS  mandatory
                  DESCRIPTION
			"The index value which uniquely identifies the local
			interface through which the next hop of this route should
			be reached.  The interface identified by a particular
			value of this index is the same interface as identified
			by the same value of ifIndex."
                  ::= { wfappleRouteEntry 3 }

  	  wfappleRouteDistance OBJECT-TYPE
		  SYNTAX  INTEGER
                  ACCESS  read-only
                  STATUS  mandatory
                  DESCRIPTION
			"The AppleTalk routing metric for this route."
                  ::= { wfappleRouteEntry 4 }

  	  wfappleRouteNextNet OBJECT-TYPE
		  SYNTAX  INTEGER
                  ACCESS  read-only
                  STATUS  mandatory
                  DESCRIPTION
			"The network number of the Next Hop Router for this destination."
                  ::= { wfappleRouteEntry 5 }

  	  wfappleRouteNextNode OBJECT-TYPE
		  SYNTAX  INTEGER
                  ACCESS  read-only
                  STATUS  mandatory
                  DESCRIPTION
			"The node identification of the Next Hop Router for this destination."
                  ::= { wfappleRouteEntry 6 }

  	  wfappleRouteState OBJECT-TYPE
		  SYNTAX  INTEGER
                  ACCESS  read-only
                  STATUS  mandatory
                  DESCRIPTION
			"The status of this route.  Valid routes are marked
			Good (2); invalidated or timed-out routes (if present)
			are marked Bad (0); a Suspect route (1) is still valid
			for routing but has been noted as marginal."
                  ::= { wfappleRouteEntry 7 }


       wfappleNBP	OBJECT IDENTIFIER ::= { wfApple 7 }

          wfappleNBPFwdReqOut OBJECT-TYPE
                  SYNTAX  INTEGER
                  ACCESS  read-only
                  STATUS  mandatory
                  DESCRIPTION
			"The number of NBP Forward Request packets transmitted by
			this entity."
                  ::= { wfappleNBP 1 }

          wfappleNBPLookupOut OBJECT-TYPE
                  SYNTAX  INTEGER
                  ACCESS  read-only
                  STATUS  mandatory
                  DESCRIPTION
			"The number of NBP Lookup packets transmitted by this entity."
                  ::= { wfappleNBP 2 }

          wfappleNBPBcastReqIn OBJECT-TYPE
                  SYNTAX  INTEGER
                  ACCESS  read-only
                  STATUS  mandatory
                  DESCRIPTION
			"The number of NBP Broadcast Request packets received by
			this entity."
                  ::= { wfappleNBP 3 }

          wfappleNBPFwdReqIn OBJECT-TYPE
                  SYNTAX  INTEGER
                  ACCESS  read-only
                  STATUS  mandatory
                  DESCRIPTION
			"The number of NBP Forward Request packets received by
			this entity."
                  ::= { wfappleNBP 4 }


       wfappleZIP	OBJECT IDENTIFIER ::= { wfApple 8 }

          wfappleZIPRequestOut OBJECT-TYPE
                  SYNTAX  INTEGER
                  ACCESS  read-only
                  STATUS  mandatory
                  DESCRIPTION
			"The number of Zone Information Protocol (ZIP) Request
			packets transmitted by this entity."
                  ::= { wfappleZIP 1 }

          wfappleZIPReplyOut OBJECT-TYPE
                  SYNTAX  INTEGER
                  ACCESS  read-only
                  STATUS  mandatory
                  DESCRIPTION
			"The number of Zone Information Protocol (ZIP) Reply
			packets transmitted by this entity."
                  ::= { wfappleZIP 2 }

          wfappleZIPNetInfoRepOut OBJECT-TYPE
                  SYNTAX  INTEGER
                  ACCESS  read-only
                  STATUS  mandatory
                  DESCRIPTION
			"The number of ZIP GetNetInfo Reply packets
			transmitted by this entity."
                  ::= { wfappleZIP 3 }

          wfappleZIPGetLclZoneOut OBJECT-TYPE
                  SYNTAX  INTEGER
                  ACCESS  read-only
                  STATUS  mandatory
                  DESCRIPTION
			"The number of ZIP GetLocalZones packets
			transmitted by this entity."
                  ::= { wfappleZIP 4 }

          wfappleZIPGetLclZoneRepOut OBJECT-TYPE
                  SYNTAX  INTEGER
                  ACCESS  read-only
                  STATUS  mandatory
                  DESCRIPTION
			"The number of ZIP GetLocalZones Reply packets
			transmitted by this entity."
                  ::= { wfappleZIP 5 }

          wfappleZIPGetZoneListOut OBJECT-TYPE
                  SYNTAX  INTEGER
                  ACCESS  read-only
                  STATUS  mandatory
                  DESCRIPTION
			"The number of ZIP GetZoneList packets
			transmitted by this entity."
                  ::= { wfappleZIP 6 }

          wfappleZIPGetNetInfoOut OBJECT-TYPE
                  SYNTAX  INTEGER
                  ACCESS  read-only
                  STATUS  mandatory
                  DESCRIPTION
			"The number of ZIP GetNetInfo packets
			transmitted by this entity."
                  ::= { wfappleZIP 7 }

          wfappleZIPGetNetInfoIn OBJECT-TYPE
                  SYNTAX  INTEGER
                  ACCESS  read-only
                  STATUS  mandatory
                  DESCRIPTION
			"The number of ZIP GetNetInfo packets
			received by this entity."
                  ::= { wfappleZIP 8 }

          wfappleZIPNetInfoRepIn OBJECT-TYPE
                  SYNTAX  INTEGER
                  ACCESS  read-only
                  STATUS  mandatory
                  DESCRIPTION
			"The number of ZIP GetNetInfo Reply packets
			received by this entity."
                  ::= { wfappleZIP 9 }

          wfappleZIPRequestIn OBJECT-TYPE
                  SYNTAX  INTEGER
                  ACCESS  read-only
                  STATUS  mandatory
                  DESCRIPTION
			"The number of ZIP Request packets received by this entity."
                  ::= { wfappleZIP 10 }

          wfappleZIPReplyIn OBJECT-TYPE
                  SYNTAX  INTEGER
                  ACCESS  read-only
                  STATUS  mandatory
                  DESCRIPTION
			"The number of ZIP Reply packets received by this entity."
                  ::= { wfappleZIP 11 }

          wfappleZIPGetZoneListIn OBJECT-TYPE
                  SYNTAX  INTEGER
                  ACCESS  read-only
                  STATUS  mandatory
                  DESCRIPTION
			"The number of ZIP GetZoneList packets
			received by this entity."
                  ::= { wfappleZIP 12 }

          wfappleZIPGetLclZoneIn OBJECT-TYPE
                  SYNTAX  INTEGER
                  ACCESS  read-only
                  STATUS  mandatory
                  DESCRIPTION
			"The number of ZIP GetLocalZones packets
			received by this entity."
                  ::= { wfappleZIP 13 }

          wfappleZIPGetLclZoneRepIn OBJECT-TYPE
                  SYNTAX  INTEGER
                  ACCESS  read-only
                  STATUS  mandatory
                  DESCRIPTION
			"The number of ZIP GetLocalZones Reply packets
			received by this entity."
                  ::= { wfappleZIP 14 }

	
          wfappleLocalZoneTable OBJECT-TYPE
                  SYNTAX  SEQUENCE OF WfAppleLZTEntry
                  ACCESS  not-accessible
                  STATUS  mandatory
                  DESCRIPTION
			"A list of all the zone names for the network to which
			the entity is connected."	
                  ::= { wfApple 9 }

          wfappleLZTEntry OBJECT-TYPE
                  SYNTAX  WfAppleLZTEntry
                  ACCESS  not-accessible
                  STATUS  mandatory
                  DESCRIPTION
			"Each entry associates a zone name with an interface."
		  INDEX { wfappleLZTIfIndex } 
                  ::= { wfappleLocalZoneTable 1 }

	  WfAppleLZTEntry ::= SEQUENCE {
		wfappleLZTZoneName
			DisplayString,
		wfappleLZTIfIndex
			INTEGER
	  }

  	  wfappleLZTZoneName OBJECT-TYPE
		  SYNTAX  DisplayString
                  ACCESS  read-only
                  STATUS  mandatory
                  DESCRIPTION
			"The name of an AppleTalk zone associated with a particular
			interface of the AppleTalk router."
                  ::= { wfappleLZTEntry 1 }

  	  wfappleLZTIfIndex OBJECT-TYPE
		  SYNTAX  INTEGER
                  ACCESS  read-only
                  STATUS  mandatory
                  DESCRIPTION
			"The interface to the network with which the named zone
			is associated.  The interface identified by a particular
			value of this index is the same interface as identified
			by the same value of ifIndex."
                  ::= { wfappleLZTEntry 2 }


          wfappleAARPTable OBJECT-TYPE
                  SYNTAX  SEQUENCE OF WfAppleAARPEntry
                  ACCESS  not-accessible
                  STATUS  mandatory
                  DESCRIPTION
			"The AppleTalk Address Resolution Protocol Table used
			for mapping from AppleTalk Net/Node addresses to physical
			addresses."
                  ::= { wfApple 10 }
	
          wfappleAARPEntry OBJECT-TYPE
                  SYNTAX  WfAppleAARPEntry
                  ACCESS  not-accessible
                  STATUS  mandatory
                  DESCRIPTION 
			"Each entry contains one AppleTalk Net/Node address to
			'physical' address equivalence."
		  INDEX { wfappleAARPNet, wfappleAARPNode }
                  ::= { wfappleAARPTable 1 }

	  WfAppleAARPEntry ::= SEQUENCE {
		wfappleAARPNet
			INTEGER,
		wfappleAARPNode
			INTEGER,
  	  	wfappleAARPMacAddress
			OCTET STRING,
  	  	wfappleAARPIfIndex
			INTEGER
	  }

  	  wfappleAARPNet OBJECT-TYPE
		  SYNTAX  INTEGER
                  ACCESS  read-only
                  STATUS  mandatory
                  DESCRIPTION
			"The network number of the AppleTalk entity described by this
			address equivalence."
                  ::= { wfappleAARPEntry 1 }

  	  wfappleAARPNode OBJECT-TYPE
		  SYNTAX  INTEGER
                  ACCESS  read-only
                  STATUS  mandatory
                  DESCRIPTION
			"The node identification of the AppleTalk entity described by this
			address equivalence."
                  ::= { wfappleAARPEntry 2 }

  	  wfappleAARPMacAddress OBJECT-TYPE
		  SYNTAX  OCTET STRING (SIZE (6))
                  ACCESS  read-only
                  STATUS  mandatory
                  DESCRIPTION
			"The media-dependent 'physical' address of this AppleTalk entity."
                  ::= { wfappleAARPEntry 3 }

  	  wfappleAARPIfIndex OBJECT-TYPE
		  SYNTAX  INTEGER
                  ACCESS  read-only
                  STATUS  mandatory
                  DESCRIPTION
			"The interface on which this entry's equivalence is
			effective.  The interface identified by a particular
			value of this index is the same interface as identified
			by the same value of ifIndex."
                  ::= { wfappleAARPEntry 4 }



          -- the Configuration Group

          -- The Configuration Group contains information about various
	  -- aspects of a Wellfleet Communication Server's configuration:
	  -- Notably, software release number and hardware config.

          wfconfigVersionMajor OBJECT-TYPE
                  SYNTAX  INTEGER
                  ACCESS  read-only
                  STATUS  mandatory
                  DESCRIPTION
                          "The Major Version Number of the Software Release
			   running in the Communications Server."

                  ::= { wfConfig 1 }

          wfconfigVersionMinor OBJECT-TYPE
                  SYNTAX  INTEGER
                  ACCESS  read-only
                  STATUS  mandatory
                  DESCRIPTION
                          "The Minor Version Number of the Software Release
			   running in the Communications Server."

                  ::= { wfConfig 2 }

          wfconfigImageFileName OBJECT-TYPE
                  SYNTAX  OCTET STRING (SIZE (0..12))
                  ACCESS  read-only
                  STATUS  mandatory
                  DESCRIPTION
                          "The name of the binary load image file from which
			   the Communications Server was loaded."
                  ::= { wfConfig 3 }

          wfconfigConfigFileName OBJECT-TYPE
                  SYNTAX  OCTET STRING (SIZE (0..12))
                  ACCESS  read-only
                  STATUS  mandatory
                  DESCRIPTION
                          "The name of the text file from which the current
			   configuration of the Communications Server was read."
                  ::= { wfConfig 4 }

	wfconfigKeys       OBJECT IDENTIFIER ::= { wfConfig 5 }

          wfconfigKeysBridge OBJECT-TYPE
                  SYNTAX  INTEGER
                  ACCESS  read-only
                  STATUS  mandatory
                  DESCRIPTION
                          "Indicates whether the Bridge software option is
                           active in the Communications Server's software
                           configuration.  0 indicates that the option is
			   absent; 1 that it is present."
                  ::= { wfconfigKeys 1 }

          wfconfigKeysDrs OBJECT-TYPE
                  SYNTAX  INTEGER
                  ACCESS  read-only
                  STATUS  mandatory
                  DESCRIPTION
                          "Indicates whether the DecNet routing software
                           option is active in the Communications Server's 
                           software configuration.  0 indicates that the
			   option is absent; 1 that it is present."
                  ::= { wfconfigKeys 2 }

          wfconfigKeysIp OBJECT-TYPE
                  SYNTAX  INTEGER
                  ACCESS  read-only
                  STATUS  mandatory
                  DESCRIPTION
                          "Indicates whether the Ip routing software option
                           is active in the Communications Server's software
                           configuration.  0 indicates that the option is
			   absent; 1 that it is present."
                  ::= { wfconfigKeys 3 }

          wfconfigKeysX25 OBJECT-TYPE
                  SYNTAX  INTEGER
                  ACCESS  read-only
                  STATUS  mandatory
                  DESCRIPTION
                          "Indicates whether the X.25 software option is 
                           active in the Communications Server's software
                           configuration.  0 indicates that the option is
			   absent; 1 that it is present."
                  ::= { wfconfigKeys 4 }

          wfconfigKeysXns OBJECT-TYPE
                  SYNTAX  INTEGER
                  ACCESS  read-only
                  STATUS  mandatory
                  DESCRIPTION
                          "Indicates whether the XNS/IPX routing software
                           option is active in the Communications Server's
                           software configuration.  0 indicates that the
			   option is absent; 1 that it is present."
                  ::= { wfconfigKeys 5 }

          wfconfigKeysApple OBJECT-TYPE
                  SYNTAX  INTEGER
                  ACCESS  read-only
                  STATUS  mandatory
                  DESCRIPTION
                          "Indicates whether the AppleTalk routing software
                           option is active in the Communications Server's
                           software configuration.  0 indicates that the
			   option is absent; 1 that it is present."
                  ::= { wfconfigKeys 6 }

          wfconfigHwTable OBJECT-TYPE
                  SYNTAX  SEQUENCE OF CardEntry
                  ACCESS  not-accessible
                  STATUS  mandatory
                  DESCRIPTION
                          "The Hw Table records the Hardware present in the 
			  Communications Server."

                  ::= { wfConfig 6 }

          wfconfigHwEntry OBJECT-TYPE
                  SYNTAX  CardEntry
                  ACCESS  not-accessible
                  STATUS  mandatory
                  DESCRIPTION
 			   "Describes the Processor and ILI Cards present in
			    a slot of the Communications Server.
			    Slots are numbered from 1 to n, and there may be gaps.
			    Conventionally, the System Controller and Floppy I/O
			    module are present in slot 1."
                  INDEX   { wfconfigHwSlot }
                  ::= { wfconfigHwTable 1 }

          CardEntry ::= SEQUENCE {
              wfconfigHwAceSn
                  INTEGER,
              wfconfigHwAceRev
                  INTEGER,
              wfconfigHwModSn
                  INTEGER,
              wfconfigHwModRev
                  INTEGER,
              wfconfigHwModID
                  INTEGER,
              wfconfigHwSlot
                  INTEGER
          }

          wfconfigHwAceSn OBJECT-TYPE
                  SYNTAX  INTEGER
                  ACCESS  read-only
                  STATUS  mandatory
                  DESCRIPTION
                          "The serial number of the processor board in this slot.
			   Conventionally the processor board in slot 1 is not
			   an ACE but a System Controller."
                  ::= { wfconfigHwEntry 1 }

          wfconfigHwAceRev OBJECT-TYPE
                  SYNTAX  INTEGER
                  ACCESS  read-only
                  STATUS  mandatory
                  DESCRIPTION
                          "The revision level of the processor board in this slot.
			   Conventionally the processor board in slot 1 is not
			   an ACE but a System Controller."
                  ::= { wfconfigHwEntry 2 }

          wfconfigHwModSn OBJECT-TYPE
                  SYNTAX  INTEGER
                  ACCESS  read-only
                  STATUS  mandatory
                  DESCRIPTION
                          "The serial number of the ILI board (Link Module)
			   in this slot."
                  ::= { wfconfigHwEntry 3 }

          wfconfigHwModRev OBJECT-TYPE
                  SYNTAX  INTEGER
                  ACCESS  read-only
                  STATUS  mandatory
                  DESCRIPTION
                          "The revision level of the ILI board (Link Module)
			   in this slot."
                  ::= { wfconfigHwEntry 4 }

          wfconfigHwModID OBJECT-TYPE
                  SYNTAX  INTEGER
                  ACCESS  read-only
                  STATUS  mandatory
                  DESCRIPTION
                          "The ID number of the ILI board (Link Module)
			   in this slot. ID numbers are documented in
			   section A.13 of the Operator's Guide."
                  ::= { wfconfigHwEntry 5 }

          wfconfigHwSlot OBJECT-TYPE
                  SYNTAX  INTEGER
                  ACCESS  read-only
                  STATUS  mandatory
                  DESCRIPTION
                          "The slot in which the boards described in this
			   entry are present.  Slots are numbered from 1,
			   and there need not be processor-ILI pair in every
			   slot.  wfconfigHwEntrys will be defined only for
			   populated slots."
                  ::= { wfconfigHwEntry 6 }

	   wfconfigBootpRqSrvr OBJECT-TYPE
                  SYNTAX  IpAddress
                  ACCESS  read-only
                  STATUS  mandatory
                  DESCRIPTION
                          "The IP Address of the BOOTP Server which initialized the
			   entity's Load Image and Configuration name."
                  ::= { wfConfig 7 }

	   wfconfigBootpFileSrvr OBJECT-TYPE
                  SYNTAX  IpAddress
                  ACCESS  read-only
                  STATUS  mandatory
                  DESCRIPTION
                          "The IP Address of the TFTP Server from which the
			   entity's Load Image and Configuration file were downloaded."
                  ::= { wfConfig 8 }

	-- The IPX Group
	
	-- The IPX Group contains information about the IPX
	-- module of a Wellfleet Communications Server
	
	wfipxMib   OBJECT IDENTIFIER ::= { wfIpx 1 }

	wfipxidp   OBJECT IDENTIFIER ::= { wfipxMib 1 }

	wfipxidpForwarding OBJECT-TYPE
		SYNTAX INTEGER {
			forwarding(1),
			host(2)
		}
		ACCESS read-only
		STATUS mandatory
		DESCRIPTION
			"Indicates whether the node is a router."
		::= { wfipxidp 1 }
	
	wfipxidpInReceives OBJECT-TYPE
		SYNTAX INTEGER
		ACCESS read-only
		STATUS mandatory
		DESCRIPTION
			" Contains the total number of all IDP datagrams 
			(including those received in error) received from
			all interfaces."
		::= { wfipxidp 2 }
	
	wfipxidpInHdrErrors OBJECT-TYPE
		SYNTAX INTEGER
		ACCESS read-only
		STATUS mandatory
		DESCRIPTION
			"Contains the number of IDP datagrams discarded
			because of errors in their IDP headers. Such errors
			include bad checksums, format errors and bad hop 
			counts. "
		::= { wfipxidp 3 }
	
	wfipxidpInAddrErrors OBJECT-TYPE
		SYNTAX INTEGER
		ACCESS read-only
		STATUS mandatory
		DESCRIPTION
			"The number of IDP datagrams discarded because of
			invalid destination fields. "
		::= { wfipxidp 4 }
	
	wfipxidpForwDatagrams OBJECT-TYPE
		SYNTAX INTEGER
		ACCESS read-only
		STATUS mandatory
		DESCRIPTION
			"The number of received IDP datagrams not addressed
			to the IPX router. The router attempts to forward
			these datagrams to their ultimate destination. "
		::= { wfipxidp 5 }

	wfipxidpInUnknownProtos OBJECT-TYPE
		SYNTAX INTEGER
		ACCESS read-only
		STATUS mandatory
		DESCRIPTION
			"The number of IDP datagrams discarded because of
			an invalid protocol field."
		::= { wfipxidp 6 }
	
	wfipxidpInDiscards OBJECT-TYPE
		SYNTAX INTEGER
		ACCESS read-only
		STATUS mandatory
		DESCRIPTION
			"The number of input IDP datagrams discarded because of
			of insufficient Server resources. "
		::= { wfipxidp 7 }
	
	wfipxidpInDelivers OBJECT-TYPE
		SYNTAX INTEGER
		ACCESS read-only
		STATUS mandatory
		DESCRIPTION
			"The number of IDP datagrams delivered to the IDP
			user protocols. (Error, Echo, RIP). "
		::= { wfipxidp 8 }

	wfipxidpOutRequests OBJECT-TYPE
		SYNTAX INTEGER
		ACCESS read-only
		STATUS mandatory
		DESCRIPTION
			"The number of IDP datagrams generated by the local
			IDP user protocols. "
		::= { wfipxidp 9 }
	
	wfipxidpOutDiscards OBJECT-TYPE
		SYNTAX INTEGER
		ACCESS read-only
		STATUS mandatory
		DESCRIPTION
			"The number of output IDP datagrams discarded because of
			of insufficient Server resources. "
		::= { wfipxidp 10 }
	
	wfipxidpOutNoRoutes OBJECT-TYPE
		SYNTAX INTEGER
		ACCESS read-only
		STATUS mandatory
		DESCRIPTION
			"The number of IDP datagrams discarded because no route
			could be found for their destination. "
		::= { wfipxidp 11 }
	
	wfipxidpAddrTable OBJECT-TYPE
		SYNTAX SEQUENCE OF WfIpxIdpAddrEntry 
		ACCESS not-accessible
		STATUS mandatory
		DESCRIPTION
			"The IDP Address table. "
		::= { wfipxidp 13 }
	
	wfipxidpAddrEntry OBJECT-TYPE
		SYNTAX WfIpxIdpAddrEntry
		ACCESS not-accessible
		STATUS mandatory
		DESCRIPTION
			"An entry in the IDP address table."
		INDEX { wfipxidpAddrAddress }
		::= { wfipxidpAddrTable 1 }
	
	WfIpxIdpAddrEntry ::= SEQUENCE {
		wfipxidpAddrAddress
			OCTET STRING,
		wfipxidpAddrIfIndex
			INTEGER
	}

	wfipxidpAddrAddress OBJECT-TYPE
		SYNTAX OCTET STRING (SIZE (6))
		ACCESS read-only
		STATUS mandatory
		DESCRIPTION
			"The IDP network number. "
		::= { wfipxidpAddrEntry 1 }
	
	wfipxidpAddrIfIndex OBJECT-TYPE
		SYNTAX INTEGER
		ACCESS read-only
		STATUS mandatory
		DESCRIPTION
			"The interface index. "
		::= { wfipxidpAddrEntry 2 }
	
	wfipxidpRoutingTable OBJECT-TYPE
		SYNTAX SEQUENCE OF WfIpxIdpRouteEntry
		ACCESS not-accessible
		STATUS mandatory
		DESCRIPTION
			"The IPX IDP routing table."
		::= { wfipxidp 14 }
	
	wfipxidpRouteEntry OBJECT-TYPE
		SYNTAX WfIpxIdpRouteEntry
		ACCESS not-accessible
		STATUS mandatory
		DESCRIPTION
			"Information about a routing table entry. "
		INDEX { wfipxidpRouteDest }
		::= { wfipxidpRoutingTable 1 }
	
	WfIpxIdpRouteEntry ::= SEQUENCE {
		wfipxidpRouteDest
			INTEGER,
		wfipxidpRouteIfIndex
			INTEGER,
		wfipxidpRouteMetric
			INTEGER,
		wfipxidpRouteNextHop
			OCTET STRING,
		wfipxidpRouteType
			INTEGER,
		wfipxidpRouteProto
			INTEGER,
		wfipxidpRouteAge
			INTEGER
	}

	wfipxidpRouteDest OBJECT-TYPE
		SYNTAX INTEGER
		ACCESS read-only
		STATUS mandatory
		DESCRIPTION
			"The destination network. "
		::= { wfipxidpRouteEntry 1 }
	
	wfipxidpRouteIfIndex OBJECT-TYPE
		SYNTAX INTEGER
		ACCESS read-only
		STATUS mandatory
		DESCRIPTION
			"An index to the next hop interface. "
		::= { wfipxidpRouteEntry 2 }
	
	wfipxidpRouteMetric OBJECT-TYPE
		SYNTAX INTEGER
		ACCESS read-only
		STATUS mandatory
		DESCRIPTION
			"The RIP hop count to the destination. 0 means the
			host is locally attached. "
		::= { wfipxidpRouteEntry 3 }
	
	wfipxidpRouteNextHop OBJECT-TYPE
		SYNTAX OCTET STRING (SIZE (6))
		ACCESS read-only
		STATUS mandatory
		DESCRIPTION
			"The host address of the next hop gateway. "
		::= { wfipxidpRouteEntry 4 }
	
	wfipxidpRouteType OBJECT-TYPE
		SYNTAX INTEGER
		ACCESS read-only
		STATUS mandatory
		DESCRIPTION
			"Indicates whether the route was statically configured,
			direct or learned via RIP. "
		::= { wfipxidpRouteEntry 5 }
	
	wfipxidpRouteProto OBJECT-TYPE
		SYNTAX INTEGER
		ACCESS read-only
		STATUS mandatory
		DESCRIPTION
			"The actual routing protocol used to determine the route."
		::= { wfipxidpRouteEntry 6 }
	
	wfipxidpRouteAge OBJECT-TYPE
		SYNTAX INTEGER
		ACCESS read-only
		STATUS mandatory
		DESCRIPTION
			"The age (in seconds) of the route. "
		::= { wfipxidpRouteEntry 7 }
	

	wfipxidpSAPTable OBJECT-TYPE
		SYNTAX SEQUENCE OF WfIpxIdpSAPEntry
		ACCESS not-accessible
		STATUS mandatory
		DESCRIPTION
			"The IPX SAP Servers table."
		::= { wfipxidp 15 }
	
	wfipxidpSAPEntry OBJECT-TYPE
		SYNTAX WfIpxIdpSAPEntry
		ACCESS not-accessible
		STATUS mandatory
		DESCRIPTION
			"Information about a SAP table entry. "
		INDEX { wfipxidpSAPType, wfipxidpSAPNet, wfipxidpSAPHost, 
		        wfipxidpSAPSocket, wfipxidpSAPIndex }
		::= { wfipxidpSAPTable 1 }
	
	WfIpxIdpSAPEntry ::= SEQUENCE {
		wfipxidpSAPType
			INTEGER,
		wfipxidpSAPNet
			INTEGER,
		wfipxidpSAPHost
			OCTET STRING,
		wfipxidpSAPSocket
			INTEGER,
		wfipxidpSAPName
			OCTET STRING,
		wfipxidpSAPAge
			INTEGER,
		wfipxidpSAPHops
			INTEGER,
		wfipxidpSAPIfIndex
			INTEGER,
		wfipxidpSAPIndex
			INTEGER
	}


	wfipxidpSAPType OBJECT-TYPE
		SYNTAX INTEGER
		ACCESS read-only
		STATUS mandatory
		DESCRIPTION
			"The IPX numerical type of server described by this
			 server entry. "
		::= { wfipxidpSAPEntry 1 }
	
	wfipxidpSAPNet OBJECT-TYPE
		SYNTAX INTEGER
		ACCESS read-only
		STATUS mandatory
		DESCRIPTION
			"The IPX network number of the server described by this
			 server entry. "
		::= { wfipxidpSAPEntry 2 }
	
	wfipxidpSAPHost OBJECT-TYPE
		SYNTAX OCTET STRING (SIZE (6))
		ACCESS read-only
		STATUS mandatory
		DESCRIPTION
			"The IPX host address of the server described by this
			 server entry. "
		::= { wfipxidpSAPEntry 3 }
	
	wfipxidpSAPSocket OBJECT-TYPE
		SYNTAX INTEGER
		ACCESS read-only
		STATUS mandatory
		DESCRIPTION
			"The IPX socket number at which the server is advertising
			 service."
		::= { wfipxidpSAPEntry 4 }
	
	wfipxidpSAPName OBJECT-TYPE
		SYNTAX OCTET STRING (SIZE (48))
		ACCESS read-only
		STATUS mandatory
		DESCRIPTION
			"The name of the server described by this
			 server entry. "
		::= { wfipxidpSAPEntry 5 }
	
	wfipxidpSAPAge OBJECT-TYPE
		SYNTAX INTEGER
		ACCESS read-only
		STATUS mandatory
		DESCRIPTION
			"The age (in seconds) of the server entry.  That is, the
			 number of seconds since the entry was updated by the SAP
			 protocol. "
		::= { wfipxidpSAPEntry 6 }
	
	wfipxidpSAPHops OBJECT-TYPE
		SYNTAX INTEGER
		ACCESS read-only
		STATUS mandatory
		DESCRIPTION
			"The number of network hops needed to reach the server
			 described by this server entry. "
		::= { wfipxidpSAPEntry 7 }
	
	wfipxidpSAPIfIndex OBJECT-TYPE
		SYNTAX INTEGER
		ACCESS read-only
		STATUS mandatory
		DESCRIPTION
			"The index, corresponding of a value of ifIndex, identifying
			 the interface through which the server is reachable."
		::= { wfipxidpSAPEntry 8 }
	
	wfipxidpSAPIndex OBJECT-TYPE
		SYNTAX INTEGER
		ACCESS read-only
		STATUS mandatory
		DESCRIPTION
			"A unique number identifying servers advertised at the same IPX
			 network and host address."
		::= { wfipxidpSAPEntry 9 }
	

               END
