--
-- SYMM-COMMON-SMI.my
-- MIB generated by MG-SOFT Visual MIB Builder 2013 (64-bit) Version 9.0  Build 760
-- Friday, May 13, 2016 at 04:35:00
--
-- MIB generated by MG-SOFT Visual MIB Builder Version 7.0  Build 209
-- Monday, July 18, 2011 at 13:18:53
--

--  SYMM-COMMON-SMI.my
-- MIB generated by MG-SOFT Visual MIB Builder Version 7.0  Build 209
-- Wednesday, May 25, 2011 at 17:39:54
-- 
--  SYMM-COMMON-SMI.my
-- MIB generated by MG-SOFT Visual MIB Builder Version 7.0  Build 209
-- Monday, February 14, 2011 at 13:41:51
-- 

	SYMM-COMMON-SMI DEFINITIONS ::= BEGIN
 
		IMPORTS
			enterprises, MODULE-IDENTITY, OBJECT-IDENTITY			
				FROM SNMPv2-SMI;
	
	
--    Sept. 30, 2005
-- 1.3.6.1.4.1.9070
-- February 01, 2011 at 00:00 GMT
-- February 01, 2011 at 00:00 GMT
-- 1.3.6.1.4.1.9070
-- February 16, 2011 at 12:08 GMT
-- February 01, 2011 at 00:00 GMT
		-- 1.3.6.1.4.1.9070
		symmetricom MODULE-IDENTITY 
			LAST-UPDATED "201808230822Z"		-- August, 2018 at 08:22 GMT
			ORGANIZATION 
				"Symmetricom, Inc."
			CONTACT-INFO 
				"
				Symmetricom, Inc.
				2300 Orchard Parkway
				San Jose, CA 95131"
			DESCRIPTION 
				"This is the MIB Module for Symmetricom's enterprise specific parameters"
			REVISION "201808230822Z"		-- August, 2018 at 08:22 GMT
			DESCRIPTION 
				"Initial revision of this MIB module."
			::= { enterprises 9070 }

		
	
--
-- Type definitions
--
	
--  Type definitions
-- 
		EnableValue ::= INTEGER
			{
			enable(1),
			disable(2)
			}

		TP5000MODULEID ::= INTEGER
			{
			sys(1),
			imc(2),
			ioc1(3),
			ioc2(4),
			io(5),
			exp0(6),
			exp1(7),
			exp2(8),
			exp3(9),
			exp4(10),
			exp5(11),
			exp6(12),
			exp7(13),
			exp8(14),
			exp9(15)
			}

		ONVALUETYPE ::= INTEGER
			{
			on(1),
			off(2)
			}

		ACTIONONLY ::= INTEGER
			{
			apply(1),
			nonapply(2)
			}

		OPMODETYPE ::= INTEGER
			{
			auto(1),
			manual(2)
			}

		ACTIVEVALUETYPE ::= INTEGER
			{
			active(1),
			inactive(2)
			}

		YESVALUETYPE ::= INTEGER
			{
			yes(1),
			no(2)
			}

		OKVALUETYPE ::= INTEGER
			{
			ok(1),
			fault(2)
			}

		VALIDTYPE ::= INTEGER
			{
			valid(1),
			invalid(2),
			nurture(3)
			}

		GNSSHealthStatus ::= INTEGER
			{
			healthy(1),
			unhealthy(2)
			}

--   Type definitions
-- 
-- Type definitions
-- 
-- Type definitions
-- 
-- Type definitions
-- 
		GNSSReceiverMode ::= INTEGER
			{
			beidou(1),
			gps(2),
			priorityBeidou(4),
			priorityGps(5),
			gnssGPS(17),
			gnssGlonass(18),
			gnssGPSGlonass(19),
			gnssGalileo(20),
			gnssGPSGalileo(21),
			gnssGlonassGalileo(22),
			gnssGPSGlonassGalileo(23),
            		gnssBeidou(24),
            		gnssBeidouGPS(25),
            		gnssBeidouGlonass(26),
            		gnssBeidouGlonassGPSReserved(27),
            		gnssBeidouGalileo(28),
            		gnssBeidouGalileoGPS(29),
            		gnssBeidouGalileoGlonassReserved(30),
            		gnssBeidouGalileoGlonassGPSReserved(31),
			notApplicable(128)
			}

		GNSSPositionMode ::= INTEGER
			{
			auto(1),
			manual(2)
			}

	
--
-- Node definitions
--
	
--  Node definitions
-- 
-- Node definitions
-- 
-- assigned by IANA
-- 1.3.6.1.4.1.9070.1
-- 1.3.6.1.4.1.9070.1
		-- 1.3.6.1.4.1.9070.1
		symmNetworkManagement OBJECT-IDENTITY
			STATUS current
			DESCRIPTION 
				"This is the root object identifier for all MIBs under the Symmetricom tree. "
			::= { symmetricom 1 }

		
--   1.3.6.1.4.1.9070.1.1
-- 1.3.6.1.4.1.9070.1.1
		-- 1.3.6.1.4.1.9070.1.1
		symmCmipManagement OBJECT-IDENTITY
			STATUS current
			DESCRIPTION 
				"This is the root object identifier for CMIP based objects"
			::= { symmNetworkManagement 1 }

		
--   1.3.6.1.4.1.9070.1.2
-- 1.3.6.1.4.1.9070.1.2
		-- 1.3.6.1.4.1.9070.1.2
		symmSnmpManagement OBJECT-IDENTITY
			STATUS current
			DESCRIPTION 
				"This is the root identifier object for SNMP based objects."
			::= { symmNetworkManagement 2 }

		
--   1.3.6.1.4.1.9070.1.2.1
-- 1.3.6.1.4.1.9070.1.2.1
		-- 1.3.6.1.4.1.9070.1.2.1
		symmTimePictra OBJECT-IDENTITY
			STATUS current
			DESCRIPTION 
				"This is reserved for objects related to Symmetricom's TimePictra product        s."
			::= { symmSnmpManagement 1 }

		
--   1.3.6.1.4.1.9070.1.2.2
-- 1.3.6.1.4.1.9070.1.2.2
		-- 1.3.6.1.4.1.9070.1.2.2
		symmBroadband OBJECT-IDENTITY
			STATUS current
			DESCRIPTION 
				"The subtree that contains objects related to Symmetricom's GoWide product       s. "
			::= { symmSnmpManagement 2 }

		
--   1.3.6.1.4.1.9070.1.2.3
-- 1.3.6.1.4.1.9070.1.2.3
		-- 1.3.6.1.4.1.9070.1.2.3
		symmTTM OBJECT-IDENTITY
			STATUS current
			DESCRIPTION 
				"The subtree that contains objects related to Symmetricom's
				Timing, Test and Measurement products."
			::= { symmSnmpManagement 3 }

		
--   1.3.6.1.4.1.9070.1.2.4
-- 1.3.6.1.4.1.9070.1.2.4
		-- 1.3.6.1.4.1.9070.1.2.4
		symmTSD OBJECT-IDENTITY
			STATUS current
			DESCRIPTION 
				"The subtree that contains objects related to Symmetricom's
				Telecom Solutions products."
			::= { symmSnmpManagement 4 }

		
--   1.3.6.1.4.1.9070.1.2.5
-- 1.3.6.1.4.1.9070.1.2.5
		-- 1.3.6.1.4.1.9070.1.2.5
		symmCommonModelV1 OBJECT-IDENTITY
			STATUS current
			DESCRIPTION 
				"This subtree contains Symmetricom Common MIB subsets 
				for multiple projects.Some are common MIBs that can be
				reused across some Symmetricom products. Some MIBs are
				specific to particular Symmetricom equipment."
			::= { symmSnmpManagement 5 }

		
--   1.3.6.1.4.1.9070.1.2.5.1
-- 1.3.6.1.4.1.9070.1.2.5.1
		-- 1.3.6.1.4.1.9070.1.2.5.1
		symmPacketService OBJECT-IDENTITY
			STATUS current
			DESCRIPTION 
				"This subtree contains objects related to the status and 
				configuration of Symmetricom Common packet service ports, 
				such as PTP and NTP."
			::= { symmCommonModelV1 1 }

		
--   1.3.6.1.4.1.9070.1.2.5.2
-- 1.3.6.1.4.1.9070.1.2.5.2
		-- 1.3.6.1.4.1.9070.1.2.5.2
		symmPhysicalSignal OBJECT-IDENTITY
			STATUS current
			DESCRIPTION 
				"This subtree contains objects related to the status and 
				configurations of Symmetricom Common physical signal ports, 
				such as E1, PPS, 10MHz, etc."
			::= { symmCommonModelV1 2 }

		
--   1.3.6.1.4.1.9070.1.2.5.3
-- 1.3.6.1.4.1.9070.1.2.5.3
		-- 1.3.6.1.4.1.9070.1.2.5.3
		symmClock OBJECT-IDENTITY
			STATUS current
			DESCRIPTION 
				"This subtree contains objects related to Symmetricom Common 
				date and time setting MIB."
			::= { symmCommonModelV1 3 }

		
--   1.3.6.1.4.1.9070.1.2.5.5
-- 1.3.6.1.4.1.9070.1.2.5.4
		-- 1.3.6.1.4.1.9070.1.2.5.4
		symmNetwork OBJECT-IDENTITY
			STATUS current
			DESCRIPTION 
				"This subtree contains objects related to Symmetricom Common
				L2 and L3 network configurations."
			::= { symmCommonModelV1 4 }

		
--   1.3.6.1.4.1.9070.1.2.5.6
-- 1.3.6.1.4.1.9070.1.2.5.5
		-- 1.3.6.1.4.1.9070.1.2.5.5
		symmEntPhysicalExtension OBJECT-IDENTITY
			STATUS current
			DESCRIPTION 
				"This subtree contains objects related to Symmetricom Common
				entity physical extension MIB."
			::= { symmCommonModelV1 5 }

		
--   1.3.6.1.4.1.9070.1.2.5.7
-- 1.3.6.1.4.1.9070.1.2.5.6
		-- 1.3.6.1.4.1.9070.1.2.5.6
		symmInterfaceExtension OBJECT-IDENTITY
			STATUS current
			DESCRIPTION 
				"This subtree contains objects related to Symmetricom Common
				interface extension MIB."
			::= { symmCommonModelV1 6 }

		
--   1.3.6.1.4.1.9070.1.2.5.8
-- 1.3.6.1.4.1.9070.1.2.5.7
		-- 1.3.6.1.4.1.9070.1.2.5.7
		symmDeviceDependent OBJECT-IDENTITY
			STATUS current
			DESCRIPTION 
				"This subtree contains objects related to Symmetricom's
				device specific MIBs."
			::= { symmCommonModelV1 7 }

		
	
	END

--
-- SYMM-COMMON-SMI.my
--
