FN100-MIB DEFINITIONS ::= BEGIN

        --  ctFN100-mib.txt
        --  Revision: 01.00.00
        --  Part Number:
        --  Date: March 26, 1997

        --  Cabletron Systems, Inc.
        --  35 Industrial Way, P.O. Box 5005
        --  Rochester, NH 03867-0505
        --  (603) 332-9400
        --  support@ctron.com

        --  This module provides authoritative definitions for Cabletron's
        --  FastNET 100 mib.
        --
        --  This module will be extended, as required.
        --
        --  Cabletron Systems reserves the right to make changes in
        --  specification and other information contained in this document
        --  without prior notice.  The reader should consult Cabletron Systems
        --  to determine whether any such changes have been made.
        --
        --  In no event shall Cabletron Systems be liable for any incidental,
        --  indirect, special, or consequential damages whatsoever (including
        --  but not limited to lost profits) arising out of or related to this
        --  document or the information contained in it, even if Cabletron
        --  Systems has been advised of, known, or should have known, the
        --  possibility of such damages.
        --
        --  Cabletron grants vendors, end-users, and other interested parties
        --  a non-exclusive license to use this Specification in connection
        --  with the management of Cabletron products.

        --  Copyright (c)1996 Cabletron Systems


IMPORTS

      OBJECT-TYPE
                FROM RFC-1212

      DisplayString, PhysAddress
                FROM RFC1213-MIB

      Counter, Gauge, IpAddress,
      mgmt, TimeTicks, enterprises
                FROM RFC1155-SMI;

--===============   Group Definitions   ===================

         cmu          OBJECT IDENTIFIER ::= { enterprises 3 }
	 sigma        OBJECT IDENTIFIER ::= { enterprises 97 }
	 sys          OBJECT IDENTIFIER ::= { sigma 1 }
	 platform     OBJECT IDENTIFIER ::= { sigma 5 }
	 es-1fe       OBJECT IDENTIFIER ::= { platform 3 }
	 sfhw         OBJECT IDENTIFIER ::= { es-1fe 1 }
	 sfsw         OBJECT IDENTIFIER ::= { es-1fe 2 }
	 sfadmin      OBJECT IDENTIFIER ::= { es-1fe 3 }
	 sfswdis      OBJECT IDENTIFIER ::= { es-1fe 4 }
	 sfaddr       OBJECT IDENTIFIER ::= { es-1fe 5 }
	 sfif         OBJECT IDENTIFIER ::= { es-1fe 6 }
	 sfuart       OBJECT IDENTIFIER ::= { es-1fe 7 }
	 sfdebug      OBJECT IDENTIFIER ::= { es-1fe 8 }
         sfproto      OBJECT IDENTIFIER ::= { es-1fe 9 }
         sftrunk      OBJECT IDENTIFIER ::= { es-1fe 10 }
         sfworkGroup  OBJECT IDENTIFIER ::= { es-1fe 11 }

	 systems      OBJECT IDENTIFIER ::= { cmu 1 }
	 mibs         OBJECT IDENTIFIER ::= { cmu 2 }
	 cmuSNMP      OBJECT IDENTIFIER ::= { systems 1 }
	 cmuKip       OBJECT IDENTIFIER ::= { systems 2 }
	 cmuRouter    OBJECT IDENTIFIER ::= { systems 3 }




   -- SMC MIB
   -- System group

	sysID OBJECT-TYPE
	  	SYNTAX  INTEGER {
                 es-1fe-bridge(2)
                }
		ACCESS	read-only
		STATUS	mandatory
        DESCRIPTION ""
		::= { sys 1 }

	sysReset	OBJECT-TYPE
		SYNTAX  TimeTicks
		ACCESS	read-write
		STATUS	mandatory
        DESCRIPTION ""
		::= { sys 2 }

	sysTrapAck	OBJECT-TYPE
        SYNTAX  INTEGER {
                    traps-need-acks(1),
                    traps-not-acked(2)
                }
		ACCESS	read-write
		STATUS	mandatory
        DESCRIPTION ""
		::= { sys 3 }

	sysTrapTime	OBJECT-TYPE
		SYNTAX  TimeTicks
		ACCESS	read-write
		STATUS	mandatory
        DESCRIPTION ""
		::= { sys 4 }

	sysTrapRetry OBJECT-TYPE
		SYNTAX  TimeTicks
		ACCESS	read-write
		STATUS	mandatory
        DESCRIPTION ""
		::= { sys 5 }

	sysTrapPort OBJECT-TYPE
		SYNTAX  INTEGER
		ACCESS	read-write
		STATUS	mandatory
        DESCRIPTION ""
		::= { sys 6 }


	-- Trojan HW Configuration Group


	sfhwDiagCode	OBJECT-TYPE
		SYNTAX	OCTET STRING
		ACCESS	read-only
		STATUS	mandatory
        DESCRIPTION ""
		::= { sfhw 1 }

	sfhwManufData	OBJECT-TYPE
        SYNTAX  DisplayString
		ACCESS	read-only
		STATUS	mandatory
        DESCRIPTION ""
		::= { sfhw 2 }

	sfhwPortCount	OBJECT-TYPE
		SYNTAX	INTEGER
		ACCESS	read-only
		STATUS	mandatory
        DESCRIPTION ""
		::= { sfhw 3 }

	sfhwPortTable	OBJECT-TYPE
		SYNTAX	SEQUENCE OF SfhwPortEntry
		ACCESS	not-accessible
		STATUS	mandatory
        DESCRIPTION ""
		::= { sfhw 4 }

	sfhwPortEntry	OBJECT-TYPE
		SYNTAX	SfhwPortEntry
		ACCESS  	not-accessible
		STATUS	mandatory
        DESCRIPTION ""
        INDEX 	{ sfhwPortIndex }
		::= { sfhwPortTable 1 }

	SfhwPortEntry ::= SEQUENCE {
			sfhwPortIndex
				INTEGER,
			sfhwPortType
				INTEGER,
			sfhwPortSubType
				INTEGER,
			sfhwPortDiagPassed
				INTEGER,
			sfhwAddr
				OCTET STRING
			}

	sfhwPortIndex	OBJECT-TYPE
		SYNTAX	INTEGER
		ACCESS	read-only
		STATUS	mandatory
        DESCRIPTION ""
		::= { sfhwPortEntry 1 }

	sfhwPortType	OBJECT-TYPE
		SYNTAX	INTEGER {
 							port-csma(1),
 							port-uart(6),
 							port-none(255)
                        }
		ACCESS	read-only
		STATUS	mandatory
        DESCRIPTION ""
		::= { sfhwPortEntry 2 }

	sfhwPortSubType	OBJECT-TYPE
		SYNTAX	INTEGER { csmacd-fx(10),
						  csmacd-tpx(13),
                          csmacd-tpx-fx(16),
                          uart-female-9pin(80),
                          no-information(255)
                        }
		ACCESS	read-only
		STATUS	mandatory
        DESCRIPTION ""
		::= { sfhwPortEntry 3 }

	sfhwPortDiagPassed	OBJECT-TYPE
		SYNTAX	INTEGER { diag-passed(1), diag-failed(2) }
		ACCESS	read-only
		STATUS	mandatory
        DESCRIPTION ""
		::= { sfhwPortEntry 4 }

	sfhwAddr	OBJECT-TYPE
		SYNTAX	OCTET STRING
		ACCESS	read-only
		STATUS	mandatory
        DESCRIPTION ""
		::= { sfhwPortEntry 5 }



	-- Trojan SFSW Configuration Group

	sfswNumber	OBJECT-TYPE
		SYNTAX	INTEGER
		ACCESS	read-only
		STATUS	mandatory
        DESCRIPTION ""
		::= { sfsw 1 }

	sfswFilesetTable	OBJECT-TYPE
		SYNTAX	SEQUENCE OF SfswFileset
		ACCESS	not-accessible
		STATUS	mandatory
        DESCRIPTION ""
		::= { sfsw 2 }

	sfswFileset	OBJECT-TYPE
		SYNTAX	SfswFileset
		ACCESS	not-accessible
		STATUS	mandatory
        DESCRIPTION ""
        INDEX { sfswIndex }
		::= { sfswFilesetTable 1 }

	SfswFileset ::= SEQUENCE {
			sfswIndex
				INTEGER,
			sfswDesc
				DisplayString,
			sfswCount
				INTEGER,
			sfswType
				OCTET STRING,
			sfswSizes
				OCTET STRING,
			sfswStarts
				OCTET STRING,
			sfswBases
				OCTET STRING,
			sfswFlashBank
				INTEGER
			}

	sfswIndex	OBJECT-TYPE
        SYNTAX  INTEGER {
                    currently-executing(1),
                    next-boot(2)
                }
		ACCESS	read-only
		STATUS	mandatory
        DESCRIPTION ""
		::= { sfswFileset 1 }

	sfswDesc	OBJECT-TYPE
		SYNTAX	DisplayString
		ACCESS	read-only
		STATUS	mandatory
        DESCRIPTION ""
		::= { sfswFileset 2 }

	sfswCount	OBJECT-TYPE
		SYNTAX	INTEGER
		ACCESS	read-only
		STATUS	mandatory
        DESCRIPTION ""
		::= { sfswFileset 3 }

	sfswType		OBJECT-TYPE
		SYNTAX	OCTET STRING
--					{ file-mp(1),
--					  file-pcp(2),
--					  file-powerup(10),
--					  file-diagnostics(11)
--					}
		ACCESS	read-only
		STATUS	mandatory
        DESCRIPTION ""
		::= { sfswFileset 4 }

	sfswSizes	OBJECT-TYPE
		SYNTAX	OCTET STRING
		ACCESS	read-only
		STATUS	mandatory
        DESCRIPTION ""
		::= { sfswFileset 5 }

	sfswStarts	OBJECT-TYPE
		SYNTAX	OCTET STRING
		ACCESS	read-only
		STATUS	mandatory
        DESCRIPTION ""
		::= { sfswFileset 6 }

	sfswBases	OBJECT-TYPE
		SYNTAX	OCTET STRING
		ACCESS	read-only
		STATUS	mandatory
        DESCRIPTION ""
		::= { sfswFileset 7 }

	sfswFlashBank	OBJECT-TYPE
        SYNTAX  INTEGER {
                    first-bank(1),
                    second-bank(2)
                }
		ACCESS	read-only
		STATUS	mandatory
        DESCRIPTION ""
		::= { sfswFileset 8 }



	-- SFADMIN Group

	sfadminFatalErr 	OBJECT-TYPE
		SYNTAX 	OCTET STRING
		ACCESS	read-only
		STATUS	mandatory
        DESCRIPTION ""
		::= { sfadmin 1 }

  sfadminAnyPass  OBJECT-TYPE
		SYNTAX   OCTET STRING
	   ACCESS   read-write
	   STATUS   mandatory
        DESCRIPTION ""
	   ::= { sfadmin 2 }

  sfadminGetPass  OBJECT-TYPE
	  SYNTAX   OCTET STRING
	  ACCESS   read-write
	  STATUS   mandatory
      DESCRIPTION ""
	  ::= { sfadmin 3 }
																		
	sfadminNMSIPAddr OBJECT-TYPE
		SYNTAX 	IpAddress
		ACCESS 	read-write
		STATUS 	mandatory
        DESCRIPTION ""
		::= { sfadmin 4 }
																		
	sfadminAlarmDynamic OBJECT-TYPE
		SYNTAX 	INTEGER	{ true(1), false(2) }
		ACCESS 	read-write
		STATUS 	mandatory
        DESCRIPTION ""
		::= { sfadmin 5 }
																		
	sfadminAlarmAddressChange OBJECT-TYPE
		SYNTAX 	INTEGER	{ true(1), false(2) }
		ACCESS 	read-write
		STATUS 	mandatory
        DESCRIPTION ""
		::= { sfadmin 6 }

	sfadminStorageFailure OBJECT-TYPE
	   SYNTAX  INTEGER { true(1), false(2) }
	   ACCESS   read-only
	   STATUS   mandatory
       DESCRIPTION ""
	   ::= { sfadmin 7 }

  sfadminAuthenticationFailure OBJECT-TYPE
	   SYNTAX   IpAddress
	   ACCESS   read-only
	   STATUS   mandatory
       DESCRIPTION ""
	   ::= { sfadmin 8 }

	sfadminMPReceiveCongests  OBJECT-TYPE
		SYNTAX   Counter
		ACCESS   read-only
		STATUS   mandatory
       DESCRIPTION ""
		::= { sfadmin 9 }
										
	sfadminArpEntries  OBJECT-TYPE
		SYNTAX   Counter
		ACCESS   read-only
		STATUS   mandatory
       DESCRIPTION ""
		::= { sfadmin 10 }
																				
	sfadminArpStatics OBJECT-TYPE
		SYNTAX 	Counter
		ACCESS 	read-only
		STATUS 	mandatory
       DESCRIPTION ""
		::= { sfadmin 11 }
																							
	sfadminArpOverflows   OBJECT-TYPE
		SYNTAX   Counter
		ACCESS   read-only
		STATUS   mandatory
       DESCRIPTION ""
		::= { sfadmin 12 }

	sfadminIpEntries   OBJECT-TYPE
		SYNTAX   Counter
		ACCESS   read-only
		STATUS   mandatory
       DESCRIPTION ""
		::= { sfadmin 13 }
									
	sfadminIpStatics   OBJECT-TYPE
		SYNTAX   Counter
		ACCESS   read-only
		STATUS   mandatory
       DESCRIPTION ""
		::= { sfadmin 14 }
																			
	sfadminStaticPreference  OBJECT-TYPE
		SYNTAX 	INTEGER
		ACCESS 	read-write
		STATUS 	mandatory
       DESCRIPTION ""
		::= { sfadmin 15 }

	sfadminRipPreference  OBJECT-TYPE
		SYNTAX   INTEGER
		ACCESS   read-write
		STATUS   mandatory
       DESCRIPTION ""
		::= { sfadmin 16 }

	sfadminRipRouteDiscards  OBJECT-TYPE
		SYNTAX   Counter
		ACCESS   read-only
		STATUS   mandatory
       DESCRIPTION ""
		::= { sfadmin 17 }

	sfadminRebootConfig   OBJECT-TYPE
		SYNTAX  INTEGER {
						no-change(1),
						tftp-config(2),
						revert-to-defaults(3)
					}
		ACCESS 	read-write
		STATUS 	mandatory
       DESCRIPTION ""
		::= { sfadmin 18 }

	sfadminTempOK OBJECT-TYPE
		SYNTAX  INTEGER {
					   temperature-normal(1),
						temperature-too-hot(2)
				  }
		ACCESS   read-only
		STATUS 	mandatory
       DESCRIPTION ""
		::= { sfadmin 19 }

	sfadminDisableButton 	OBJECT-TYPE
		SYNTAX 	INTEGER  { true(1), false(2) }
		ACCESS	read-write
		STATUS	mandatory
       DESCRIPTION ""
		::= { sfadmin 20 }

	sfadminButtonSelection 	OBJECT-TYPE
		SYNTAX 	INTEGER {
						led-any-activity(1),
						led-rx-activity(2),
						led-tx-activity(3),
						led-any-collision(4),
						led-programmed(5),
						led-speed(6)
					}
		ACCESS	read-write
		STATUS	mandatory
        DESCRIPTION ""
		::= { sfadmin 21 }

	sfadminLEDProgramOption 	OBJECT-TYPE
		SYNTAX 	INTEGER {
						program-led-any-error(1)
					}
		ACCESS	read-write
		STATUS	mandatory
        DESCRIPTION ""
		::= { sfadmin 22 }

	sfadminVirtualSwitch1  	OBJECT-TYPE
		SYNTAX   OCTET STRING
		ACCESS   read-write
		STATUS   mandatory
		DESCRIPTION ""
		::= { sfadmin 23 }
																		  
	sfadminVirtualSwitch2  	OBJECT-TYPE
		SYNTAX   OCTET STRING
		ACCESS   read-write
		STATUS   mandatory
		DESCRIPTION ""
		::= { sfadmin 24 }
																		  
	sfadminVirtualSwitch3  	OBJECT-TYPE
		SYNTAX   OCTET STRING
		ACCESS   read-write
		STATUS   mandatory
		DESCRIPTION ""
		::= { sfadmin 25 }
																		  
	sfadminVirtualSwitch4  	OBJECT-TYPE
		SYNTAX   OCTET STRING
		ACCESS   read-write
		STATUS   mandatory
		DESCRIPTION ""
		::= { sfadmin 26 }
																		  
	sfadminDefaultVirtualSwitch 	OBJECT-TYPE
		SYNTAX 	INTEGER { 
						virtual-switch-1(1),
						virtual-switch-2(2),
						virtual-switch-3(3),
						virtual-switch-4(4)
					}
		ACCESS	read-write
		STATUS	mandatory
        DESCRIPTION "Default virtual switch number when accessing 
					 the MIB via SNMP. Set this attribute prior to 
					 accessing the Bridge MIB records."
		::= { sfadmin 27 }



	-- Software Distribution Group

	sfswdisDesc 	OBJECT-TYPE
		SYNTAX 	OCTET STRING
		ACCESS	read-only
		STATUS	mandatory
        DESCRIPTION ""
		::= { sfswdis 1 }

	sfswdisAccess	OBJECT-TYPE
		SYNTAX 	INTEGER {
                    protected(1),
                    any-software(2)
                }
		ACCESS	read-write
		STATUS	mandatory
        DESCRIPTION ""
		::= { sfswdis 2 }

	sfswdisWriteStatus	OBJECT-TYPE
        SYNTAX  INTEGER {
                    in-progress(1),
                    success(2),
                    config-error(3),
                    flash-error(4),
                    config-and-flash-errors(5)
                }
		ACCESS	read-only
		STATUS	mandatory
        DESCRIPTION ""
		::= { sfswdis 3 }

	sfswdisConfigIp	OBJECT-TYPE
		SYNTAX	IpAddress
		ACCESS	read-write
		STATUS	mandatory
        DESCRIPTION ""
		::= { sfswdis 4 }

	sfswdisConfigRetryTime	OBJECT-TYPE
		SYNTAX	INTEGER
		ACCESS	read-write
		STATUS	mandatory
        DESCRIPTION ""
		::= { sfswdis 5 }

	sfswdisConfigTotalTimeout	OBJECT-TYPE
		SYNTAX	INTEGER
		ACCESS	read-write
		STATUS	mandatory
        DESCRIPTION ""
		::= { sfswdis 6 }

	-- Address Configuration

	sfaddrDynamics	OBJECT-TYPE
		SYNTAX	Counter
		ACCESS	read-only
		STATUS	mandatory
        DESCRIPTION ""
		::= { sfaddr 1 }

	sfaddrDynamicMax	OBJECT-TYPE
		SYNTAX	Gauge
		ACCESS	read-write
		STATUS	mandatory
        DESCRIPTION ""
		::= { sfaddr 2 }

	sfaddrFlags	OBJECT-TYPE
		SYNTAX	INTEGER
		ACCESS	read-write
		STATUS	mandatory
        DESCRIPTION ""
		::= { sfaddr 3 }

	sfaddrMAC	OBJECT-TYPE
		SYNTAX	OCTET STRING
		ACCESS	read-write
		STATUS	mandatory
        DESCRIPTION ""
		::= { sfaddr 4 }

	sfaddrPort	OBJECT-TYPE
		SYNTAX	INTEGER
		ACCESS	read-write
		STATUS	mandatory
        DESCRIPTION ""
		::= { sfaddr 5 }


	sfaddrOperation	OBJECT-TYPE
        SYNTAX  INTEGER {
                    read-random(1),
                    read-next(2),
                    reserved(3),
                    update(4),
                    delete(5),
                    read-block(6)
                }
		ACCESS	read-write
		STATUS	mandatory
        DESCRIPTION ""
		::= { sfaddr 6 }

	sfaddrIndex	OBJECT-TYPE
		SYNTAX	INTEGER
		ACCESS	read-write
		STATUS	mandatory
        DESCRIPTION ""
		::= { sfaddr 7 }

	sfaddrNext	OBJECT-TYPE
		SYNTAX	INTEGER
		ACCESS	read-write
		STATUS	mandatory
        DESCRIPTION ""
		::= { sfaddr 8 }

	sfaddrBlockSize	OBJECT-TYPE
		SYNTAX	INTEGER
		ACCESS	read-write
		STATUS	mandatory
        DESCRIPTION ""
		::= { sfaddr 9 }

	sfaddrBlock	OBJECT-TYPE
		SYNTAX	OCTET STRING
		ACCESS	read-write
		STATUS	mandatory
        DESCRIPTION ""
		::= { sfaddr 10 }

	sfaddrAlarmMAC	OBJECT-TYPE
		SYNTAX	OCTET STRING
		ACCESS	read-only
		STATUS	mandatory
        DESCRIPTION ""
		::= { sfaddr 11 }


	sfaddrDbFullBuckets	OBJECT-TYPE
		SYNTAX	INTEGER
		ACCESS	read-only
		STATUS	mandatory
        DESCRIPTION ""
		::= { sfaddr 12 }

	sfaddrDbMaxFullBuckets	OBJECT-TYPE
		SYNTAX	INTEGER
		ACCESS	read-write
		STATUS	mandatory
        DESCRIPTION ""
		::= { sfaddr 13 }

	sfaddrDbMaxSize	OBJECT-TYPE
		SYNTAX	INTEGER
		ACCESS	read-only
		STATUS	mandatory
        DESCRIPTION ""
		::= { sfaddr 14 }

	sfaddrDbBuckets	OBJECT-TYPE
		SYNTAX	INTEGER
		ACCESS	read-only
		STATUS	mandatory
        DESCRIPTION ""
		::= { sfaddr 15 }

	sfaddrDbSearchDepth	OBJECT-TYPE
		SYNTAX	INTEGER
		ACCESS	read-write
		STATUS	mandatory
        DESCRIPTION ""
		::= { sfaddr 16 }

	sfaddrDbDistribution	OBJECT-TYPE
		SYNTAX	OCTET STRING
		ACCESS	read-only
		STATUS	mandatory
        DESCRIPTION ""
		::= { sfaddr 17 }

	-- the Physical Address table

	sfaddrDbTable OBJECT-TYPE
		SYNTAX  SEQUENCE OF SfaddrDbEntry
		ACCESS  not-accessible
		STATUS  mandatory
		DESCRIPTION ""
		::= { sfaddr 18 }

	sfaddrDbEntry OBJECT-TYPE
		SYNTAX  SfaddrDbEntry
		ACCESS  not-accessible
		STATUS  mandatory
		DESCRIPTION ""
		INDEX { sfaddrDbBucketAddress }
		::= { sfaddrDbTable 1 }

	SfaddrDbEntry ::= SEQUENCE {
			sfaddrDbBucketAddress
				OCTET STRING,
			sfaddrDbBucketEntCnt
				INTEGER,
			sfaddrDbBucketEntries	
				OCTET STRING
		}

	sfaddrDbBucketAddress OBJECT-TYPE
		SYNTAX  OCTET STRING  (SIZE(0..4))
		ACCESS  read-only
		STATUS  mandatory
		DESCRIPTION ""
		::= { sfaddrDbEntry 1 }

	sfaddrDbBucketEntCnt	OBJECT-TYPE
		SYNTAX	INTEGER
		ACCESS	read-only
		STATUS	mandatory
        DESCRIPTION ""
		::= { sfaddrDbEntry 2 }

	sfaddrDbBucketEntries	OBJECT-TYPE
		SYNTAX	OCTET STRING
		ACCESS	read-only
		STATUS	mandatory
        DESCRIPTION ""
		::= { sfaddrDbEntry 3 }

-- SMC Interfaces (sfif) Group


	sfifTable	OBJECT-TYPE
		SYNTAX	SEQUENCE OF SfifEntry
		ACCESS	not-accessible
		STATUS	mandatory
        DESCRIPTION ""
		::= { sfif 1  }

	sfifEntry	OBJECT-TYPE
		SYNTAX	SfifEntry
		ACCESS	not-accessible
		STATUS	mandatory
        DESCRIPTION ""
        INDEX { sfifIndex }
		::= { sfifTable 1 }

	SfifEntry ::= SEQUENCE {
			sfifIndex
				INTEGER,
			sfifRxCnt
				INTEGER,
			sfifTxCnt
				INTEGER,
			sfifTxStormCnt
				INTEGER,
			sfifTxStormTime
				TimeTicks,
			sfifFilterFloodSourceSame
				INTEGER,
			sfifFunction
				INTEGER,
			sfifRxPacket
				OCTET STRING,
			sfifRxHwFCSs
				Counter,
			sfifRxQueues
				Counter,
			sfifTxPacket
				OCTET STRING,
			sfifTxStorms
				Counter,
			sfifStatisticsTime
				TimeTicks,
			sfifIpAddr
				IpAddress,
			sfifIpGroupAddr
				IpAddress,
			sfifRxForwardChars
				Counter,
			sfifRxFilteredChars
				Counter,
			sfifSpeed
				INTEGER,
			sfifMgntRxQueueSize
				INTEGER,
			sfifVirtualSwitchID
				INTEGER,
			sfifTPLinkOK
				INTEGER,
			sfifLedOn
				INTEGER,
			sfifTxCollisions
				Counter,
			sfifFuseOkay
				INTEGER,
			sfifCrashEvents
				Counter,
			sfifCrashTime
				TimeTicks,
			sfifMinimumUpTime
				TimeTicks,
			sfifDMAFlowControlEnable 
				INTEGER,
			sfifDMARetryCount 
				INTEGER,
			sfifDMARetryBufferCount 
				INTEGER,
			sfifDMAPeakRetries 
				Counter,
			sfifDMATotalRetries 
				Counter,
			sfifDMAPackets
				Counter,
			sfifDMADroppedPackets
				Counter,
			sfifDescr
				DisplayString,
			sfifMgtDroppedPackets
				Counter,
			sfifLinkStatusOutages
				Counter,
			sfifLocalFilter
				INTEGER
			}

	sfifIndex	OBJECT-TYPE
		SYNTAX	INTEGER
		ACCESS	read-only
		STATUS	mandatory
        DESCRIPTION ""
		::= { sfifEntry 1 }

	sfifRxCnt	OBJECT-TYPE
		SYNTAX	INTEGER
		ACCESS	read-only
		STATUS	mandatory
        DESCRIPTION ""
		::= { sfifEntry 2 }

	sfifTxCnt	OBJECT-TYPE
		SYNTAX	INTEGER
		ACCESS	read-only
		STATUS	mandatory
        DESCRIPTION ""
		::= { sfifEntry 3 }

	sfifTxStormCnt	OBJECT-TYPE
		SYNTAX	INTEGER
		ACCESS	read-write
		STATUS	mandatory
        DESCRIPTION ""
		::= { sfifEntry 4 }

	sfifTxStormTime	OBJECT-TYPE
		SYNTAX	TimeTicks
		ACCESS	read-write
		STATUS	mandatory
        DESCRIPTION ""
		::= { sfifEntry 5 }

	sfifFilterFloodSourceSame	OBJECT-TYPE
		SYNTAX	INTEGER { true(1), false(2) }
		ACCESS	read-write
		STATUS	mandatory
        DESCRIPTION ""
		::= { sfifEntry 6 }

	sfifFunction	OBJECT-TYPE
		SYNTAX	INTEGER 
		ACCESS	read-only
		STATUS	mandatory
        DESCRIPTION ""
		::= { sfifEntry 7 }

	sfifRxPacket	OBJECT-TYPE
		SYNTAX	OCTET STRING
		ACCESS	read-only
		STATUS	mandatory
        DESCRIPTION ""
		::= { sfifEntry 8 }

	sfifRxHwFCSs	OBJECT-TYPE
		SYNTAX	Counter
		ACCESS	read-only
		STATUS	mandatory
        DESCRIPTION ""
		::= { sfifEntry 9 }

	sfifRxQueues	OBJECT-TYPE
		SYNTAX	Counter
		ACCESS	read-only
		STATUS	mandatory
        DESCRIPTION ""
		::= { sfifEntry 10 }

	sfifTxPacket	OBJECT-TYPE
		SYNTAX	OCTET STRING
		ACCESS	read-only
		STATUS	mandatory
        DESCRIPTION ""
		::= { sfifEntry 11 }

	sfifTxStorms	OBJECT-TYPE
		SYNTAX	Counter
		ACCESS	read-only
		STATUS	mandatory
        DESCRIPTION ""
		::= { sfifEntry 12 }

	sfifStatisticsTime	OBJECT-TYPE
		SYNTAX	TimeTicks
		ACCESS	read-only
		STATUS	mandatory
        DESCRIPTION ""
		::= { sfifEntry 13 }

	sfifIpAddr	OBJECT-TYPE
		SYNTAX	IpAddress
		ACCESS	read-write
		STATUS	mandatory
        DESCRIPTION ""
		::= { sfifEntry 14 }

	sfifIpGroupAddr	OBJECT-TYPE
		SYNTAX	IpAddress
		ACCESS	read-write
		STATUS	mandatory
        DESCRIPTION ""
		::= { sfifEntry 15 }

	sfifRxForwardChars OBJECT-TYPE
		SYNTAX	Counter
		ACCESS	read-only
		STATUS	mandatory
        DESCRIPTION ""
		::= { sfifEntry 16 }

	sfifRxFilteredChars OBJECT-TYPE
		SYNTAX	Counter
		ACCESS	read-only
		STATUS	mandatory
        DESCRIPTION ""
		::= { sfifEntry 17 }

	sfifSpeed OBJECT-TYPE
		SYNTAX	INTEGER
		ACCESS	read-write
		STATUS	mandatory
        DESCRIPTION ""
		::= { sfifEntry 18 }

	sfifMgntRxQueueSize OBJECT-TYPE
		SYNTAX	INTEGER
		ACCESS	read-write
		STATUS	mandatory
        DESCRIPTION ""
		::= { sfifEntry 19 }

	sfifVirtualSwitchID OBJECT-TYPE
		SYNTAX	INTEGER
		ACCESS	read-only
		STATUS	mandatory
        DESCRIPTION ""
		::= { sfifEntry 20 }

	sfifTPLinkOK OBJECT-TYPE
		SYNTAX	INTEGER
		ACCESS	read-only
		STATUS	mandatory
        DESCRIPTION ""
		::= { sfifEntry 21 }

	sfifLedOn OBJECT-TYPE
        SYNTAX  INTEGER {
                    led-on(1),
                    led-off(2)
                }
		ACCESS	read-only
		STATUS	mandatory
        DESCRIPTION ""
		::= { sfifEntry 22 }

	sfifTxCollisions OBJECT-TYPE
		SYNTAX	Counter
		ACCESS	read-only
		STATUS	mandatory
        DESCRIPTION ""
		::= { sfifEntry 23 }

	sfifFuseOkay OBJECT-TYPE
        SYNTAX  INTEGER {
                    true(1),
                    false(2)
                }
		ACCESS	read-only
		STATUS	mandatory
        DESCRIPTION ""
		::= { sfifEntry 24 }

	sfifCrashEvents OBJECT-TYPE
        SYNTAX  Counter 
		ACCESS	read-write
		STATUS	mandatory
        DESCRIPTION ""
		::= { sfifEntry 25 }

	sfifCrashTime	OBJECT-TYPE
		SYNTAX	TimeTicks
		ACCESS	read-write
		STATUS	mandatory
        DESCRIPTION ""
		::= { sfifEntry 26 }

	sfifMinimumUpTime	OBJECT-TYPE
		SYNTAX	TimeTicks
		ACCESS	read-write
		STATUS	mandatory
        DESCRIPTION ""
		::= { sfifEntry 27 }

	sfifDMAFlowControlEnable OBJECT-TYPE
        SYNTAX  INTEGER { enabled(1), disabled(2) }
		ACCESS	read-write
		STATUS	mandatory
        DESCRIPTION ""
		::= { sfifEntry 28 }

	sfifDMARetryCount OBJECT-TYPE
		SYNTAX	INTEGER
		ACCESS	read-write
		STATUS	mandatory
        DESCRIPTION ""
		::= { sfifEntry 29 }

	sfifDMARetryBufferCount OBJECT-TYPE
		SYNTAX	INTEGER
		ACCESS	read-write
		STATUS	mandatory
        DESCRIPTION ""
		::= { sfifEntry 30 }

	sfifDMAPeakRetries OBJECT-TYPE
		SYNTAX	Counter
		ACCESS	read-only
		STATUS	mandatory
        DESCRIPTION ""
		::= { sfifEntry 31 }

	sfifDMATotalRetries OBJECT-TYPE
		SYNTAX  Counter
		ACCESS	read-only
		STATUS	mandatory
        DESCRIPTION ""
		::= { sfifEntry 32 }

	sfifDMAPackets OBJECT-TYPE
		SYNTAX  Counter
		ACCESS	read-only
		STATUS	mandatory
        DESCRIPTION ""
		::= { sfifEntry 33 }

	sfifDMADroppedPackets OBJECT-TYPE
		SYNTAX  Counter
		ACCESS	read-only
		STATUS	mandatory
        DESCRIPTION ""
		::= { sfifEntry 34 }

	sfifDescr OBJECT-TYPE
		SYNTAX  DisplayString
		ACCESS	read-write
		STATUS	mandatory
        DESCRIPTION ""
		::= { sfifEntry 35 }

	sfifMgtDroppedPackets OBJECT-TYPE
		SYNTAX  Counter
		ACCESS	read-only
		STATUS	mandatory
        DESCRIPTION ""
		::= { sfifEntry 36 }

	sfifLinkStatusOutages OBJECT-TYPE
		SYNTAX  Counter
		ACCESS	read-only
		STATUS	mandatory
        DESCRIPTION ""
		::= { sfifEntry 37 }

	sfifLocalFilter OBJECT-TYPE
        SYNTAX  INTEGER {
                    hardware(1),
                    software(2)
                }
		ACCESS	read-write
		STATUS	mandatory
        DESCRIPTION ""
		::= { sfifEntry 38 }


	-- SMC SFUART Interface Group

	sfuartTable	OBJECT-TYPE
		SYNTAX	SEQUENCE OF SfuartEntry
		ACCESS 	not-accessible
		STATUS	mandatory
        DESCRIPTION ""
		::= { sfuart 1 }

	sfuartEntry	OBJECT-TYPE
		SYNTAX	SfuartEntry
		ACCESS	not-accessible
		STATUS	mandatory
        DESCRIPTION ""
        INDEX { sfuartIndex }
		::= { sfuartTable 1 }

	SfuartEntry ::= SEQUENCE {
				sfuartIndex
					INTEGER,
				sfuartBaud
					INTEGER,
				sfuartAlignmentErrors
					Counter,
				sfuartOverrunErrors
					Counter
				}

	sfuartIndex	OBJECT-TYPE
		SYNTAX	INTEGER
		ACCESS	read-only
		STATUS	mandatory
        DESCRIPTION ""
		::= { sfuartEntry 1 }

	sfuartBaud	OBJECT-TYPE
        SYNTAX  INTEGER {
                    external-clock(1),
                    b1200-baud(2),
                    b2400-baud(3),
                    b4800-baud(4),
                    b9600-baud(5),
                    b19200-baud(6),
                    b38400-baud(7),
                    b56-kilobits(8),
                    b1544-kilobits(9),
                    b2048-kilobits(10),
                    b45-megabits(11)
                }
		ACCESS	read-write
		STATUS	mandatory
        DESCRIPTION ""
		::= { sfuartEntry 2 }

	sfuartAlignmentErrors	OBJECT-TYPE
		SYNTAX	Counter
		ACCESS	read-only
		STATUS	mandatory
        DESCRIPTION ""
		::= { sfuartEntry 3 }

	sfuartOverrunErrors	OBJECT-TYPE
		SYNTAX	Counter
		ACCESS	read-only
		STATUS	mandatory
        DESCRIPTION ""
		::= { sfuartEntry 4 }


	-- Debug Command Group

	sfdebugStringID	OBJECT-TYPE
		SYNTAX	INTEGER
		ACCESS	read-only
		STATUS	mandatory
        DESCRIPTION ""
		::= { sfdebug 1 }

	sfdebugString	OBJECT-TYPE
		SYNTAX	OCTET STRING
		ACCESS	read-only
		STATUS	mandatory
        DESCRIPTION ""
		::= { sfdebug 2 }

	sfdebugTable	OBJECT-TYPE
		SYNTAX	SEQUENCE OF SfdebugEntry
		ACCESS	not-accessible
		STATUS	mandatory
        DESCRIPTION ""
		::= { sfdebug 3 }

	sfdebugEntry	OBJECT-TYPE
		SYNTAX	SfdebugEntry
		ACCESS	not-accessible
		STATUS	mandatory
        DESCRIPTION ""
        INDEX { sfdebugIndex }
		::= { sfdebugTable 1 }

	SfdebugEntry ::= SEQUENCE {
			sfdebugIndex
				INTEGER,
			sfdebugOperation
				INTEGER,
			sfdebugBase
				INTEGER,
			sfdebugLength
				INTEGER,
			sfdebugData
				OCTET STRING
			}

	sfdebugIndex	OBJECT-TYPE
		SYNTAX	INTEGER {
		   debug-port1(1),
		   debug-port2(2),
		   debug-port3(3),
		   debug-port4(4),
		   debug-port5(5),
		   debug-port6(6),
		   debug-port7(7),
		   debug-port8(8),
		   debug-port9(9),
		   debug-port10(10),
		   debug-port11(11),
		   debug-port12(12),
		   debug-mp(100)
		   }
		ACCESS	read-only
		STATUS	mandatory
        DESCRIPTION ""
		::= { sfdebugEntry 1 }

	sfdebugOperation	OBJECT-TYPE
        SYNTAX  INTEGER {
                    examine(1),
                    modify(2)
                }
		ACCESS	read-write
		STATUS	mandatory
        DESCRIPTION ""
		::= { sfdebugEntry 2 }

	sfdebugBase	OBJECT-TYPE
		SYNTAX	INTEGER
		ACCESS	read-write
		STATUS	mandatory
        DESCRIPTION ""
		::= { sfdebugEntry 3 }

	sfdebugLength	OBJECT-TYPE
		SYNTAX	INTEGER
		ACCESS	read-write
		STATUS	mandatory
        DESCRIPTION ""
		::= { sfdebugEntry 4 }

	sfdebugData	OBJECT-TYPE
		SYNTAX	OCTET STRING
		ACCESS	read-write
		STATUS	mandatory
        DESCRIPTION ""
		::= { sfdebugEntry 5 }


	-- SMC Protocols Group

sfprotoTable OBJECT-TYPE
     SYNTAX  SEQUENCE OF SfprotoEntry
     ACCESS  not-accessible
     STATUS  mandatory
     DESCRIPTION
          "This table contains configuration information specify-
          ing the types of protocols used to bridge, route,
          translate, and filter frames for each port."
     ::= { sfproto 1 }

sfprotoEntry OBJECT-TYPE
     SYNTAX  SfprotoEntry
     ACCESS  not-accessible
     STATUS  mandatory
     DESCRIPTION
          "Each entry in this table specifies which protocols are
          used by a particular port in the ES/1."
     INDEX { sfprotoIfIndex }
     ::= { sfprotoTable 1 }

SfprotoEntry ::=
     SEQUENCE { 
	  		sfprotoIfIndex
				 INTEGER,
          sfprotoBridge
             INTEGER,
          sfprotoSuppressBpdu
             INTEGER,
          sfprotoRipListen
             INTEGER,
          sfprotoTrunking
             INTEGER
     }

sfprotoIfIndex OBJECT-TYPE
	  SYNTAX  INTEGER
	  ACCESS  read-only
	  STATUS  mandatory
	  DESCRIPTION
			 "Identifies the interface (port) to which this entry's
			 information belongs. The value of this variable
			 corresponds to ifIndex, as well as most of the other
			 port identification values in related MIBs."
	  ::= { sfprotoEntry 1 }

sfprotoBridge OBJECT-TYPE
     SYNTAX  INTEGER { transparent(1), none(4) }
     ACCESS  read-write
     STATUS  mandatory
     DESCRIPTION
          "Defines the bridging method to be applied to frames
          received at, or destined for, this port. Ethernet and
          FDDI ports may be configured for transparent, srt, or
          none.  Token Ring ports may be configured for any of
          the four options. The UART may only be configured to
          none."
     ::= { sfprotoEntry 2 }

sfprotoSuppressBpdu OBJECT-TYPE
     SYNTAX  INTEGER { normal(1), suppressed(2) }
     ACCESS  read-write
     STATUS  mandatory
     DESCRIPTION
          "Allows transmission of spanning tree protocol packets
          to be suppressed.  If normal(1), 802.1d spanning tree
          packets and source-routing spanning tree packets are
          transmitted as usual. If suppressed(2), these packets
          are not transmitted. This option may be needed for in-
          teroperability with non-802.1d spanning tree protocols
          (e.g., DEC LanBridge 100)."
     ::= { sfprotoEntry 3 }

sfprotoRipListen OBJECT-TYPE
     SYNTAX  INTEGER { enabled(1), disabled(2) }
     ACCESS  read-write
     STATUS  mandatory
     DESCRIPTION
          "Specifies whether the port should listen for internet
          Routing Information Protocol (RFC-1058) packets, in order to
          build the routing table for the unit."
     ::= { sfprotoEntry 4 }

sfprotoTrunking OBJECT-TYPE
     SYNTAX  INTEGER { enabled(1), disabled(2) }
     ACCESS  read-write
     STATUS  mandatory
     DESCRIPTION
          "Specifies whether SMC's trunking protocol (an extension
          to the standard Spanning Tree) is to be used over this port."
     ::= { sfprotoEntry 5 }


	-- SMC Trunking Group


sftrunkTable OBJECT-TYPE
	SYNTAX	SEQUENCE OF SftrunkEntry
	ACCESS	not-accessible
	STATUS	mandatory
	DESCRIPTION
		"This table describes the trunking status and attributes of
		 the interfaces that are configured for bridge trunking."
	::= { sftrunk 1 }

sftrunkEntry OBJECT-TYPE
	SYNTAX	SftrunkEntry
	ACCESS	not-accessible
	STATUS	mandatory
	DESCRIPTION
		"An entry exists in this table for each physical interface
		 (port) that is configured for trunking."
	INDEX { sftrunkIfIndex }
	::= { sftrunkTable 1 }

	SftrunkEntry ::=
		SEQUENCE {
			sftrunkIfIndex
				INTEGER,
			sftrunkState
				INTEGER,
			sftrunkRemoteBridgeId
				OCTET STRING,
			sftrunkRemoteIp
				IpAddress,
			sftrunkLastError
				INTEGER,
			sftrunkLinkOrdinal
				INTEGER,
			sftrunkLinkCount
				INTEGER,
			sftrunkLastChange
				INTEGER
			}

sftrunkIfIndex OBJECT-TYPE
	SYNTAX	INTEGER
	ACCESS	read-only
	STATUS	mandatory
	DESCRIPTION
		"Identifies a physical interface (port) which is
		configured for LAN trunking. The value of this variable
		corresponds to ifIndex, as well as most of the other
		port identification values in related MIBs."
	::= { sftrunkEntry 1 }

sftrunkState OBJECT-TYPE
	SYNTAX	INTEGER { closed(1), oneway(2), joined(3), helddown(4) }
	ACCESS	read-only
	STATUS	mandatory
	DESCRIPTION
		"If closed(1) then this link has not yet received any Trunking
		 PDUs. If oneway(2) then incoming Trunking PDUs do not indicate
		 that our PDUs are being successfully received by the far end.
		 If joined(3) then this link is actively participating in the
		 trunk group. If helddown(4) then an error has been detected
		 and the link is being held out-of-service until the error
		 clears."
	::= { sftrunkEntry 2 }

sftrunkRemoteBridgeId OBJECT-TYPE
	SYNTAX	OCTET STRING
	ACCESS	read-only
	STATUS	mandatory
	DESCRIPTION
		"The bridge ID of the remote bridge."
	::= { sftrunkEntry 3 }

sftrunkRemoteIp OBJECT-TYPE
	SYNTAX	IpAddress
	ACCESS	read-only
	STATUS	mandatory
	DESCRIPTION
		"The IP address of the remote bridge, as reported by that
		 bridge for administrative purposes."
	::= { sftrunkEntry 4 }

sftrunkLastError OBJECT-TYPE
	SYNTAX	INTEGER { none(1), in-bpdu(2), multiple-bridges(3), no-ack(4) }
	ACCESS	read-only
	STATUS	mandatory
	DESCRIPTION
		"The reason for failure when the link is in helddown state."
	::= { sftrunkEntry 5 }

sftrunkLinkOrdinal OBJECT-TYPE
	SYNTAX	INTEGER
	ACCESS	read-only
	STATUS	mandatory
	DESCRIPTION
		"The position of this link within the trunk group."
	::= { sftrunkEntry 6 }

sftrunkLinkCount OBJECT-TYPE
	SYNTAX	INTEGER
	ACCESS	read-only
	STATUS	mandatory
	DESCRIPTION
		"The number of links within the trunk group."
	::= { sftrunkEntry 7 }

sftrunkLastChange OBJECT-TYPE
	SYNTAX	INTEGER
	ACCESS	read-only
	STATUS	mandatory
	DESCRIPTION "The number of seconds since sftrunkState changed."
	::= { sftrunkEntry 8 }



	-- SMC WorkGroup Group


sfworkGroupNextIndex	OBJECT-TYPE
	SYNTAX	INTEGER
	ACCESS	read-only
	STATUS	mandatory
    DESCRIPTION
        "The next available workgroup index to be used.  When creating
         a new workgroup, it is recommended to read the value of the variable
         and use it to key into the workgroup table."
	::= { sfworkGroup 1 }

sfworkGroupCurrentCounts	OBJECT-TYPE
	SYNTAX	INTEGER
	ACCESS	read-only
	STATUS	mandatory
    DESCRIPTION
        "The total number of workgroups currently defined."
	::= { sfworkGroup 2 }

sfworkGroupMaxCount	OBJECT-TYPE
	SYNTAX	INTEGER
	ACCESS	read-only
	STATUS	mandatory
    DESCRIPTION
        "The maximum number of workgroups allowed."
	::= { sfworkGroup 3 }

sfworkGroupTable OBJECT-TYPE
	SYNTAX	SEQUENCE OF SfworkGroupEntry
	ACCESS	not-accessible
	STATUS	mandatory
    DESCRIPTION
        "This table contains work group definitions for the interfaces."
	::= { sfworkGroup 4 }

sfworkGroupEntry OBJECT-TYPE
	SYNTAX	SfworkGroupEntry
	ACCESS	not-accessible
	STATUS	mandatory
    DESCRIPTION
        "Each entry in this table contains a definition of a work group."
		 
	INDEX { sfworkGroupIndex }
	::= { sfworkGroupTable 1 }

	SfworkGroupEntry ::=
		SEQUENCE {
			sfworkGroupIndex
				INTEGER,
			sfworkGroupName
                DisplayString,
			sfworkGroupPort
				OCTET STRING,
			sfworkGroupType
				INTEGER
			}

sfworkGroupIndex OBJECT-TYPE
	SYNTAX	INTEGER
	ACCESS	read-only
	STATUS	mandatory
    DESCRIPTION
        "An integer that identifies the work group, used as an index
         to this table."
	::= { sfworkGroupEntry 1 }

sfworkGroupName  OBJECT-TYPE
	SYNTAX	DisplayString
	ACCESS	read-write
	STATUS	mandatory
    DESCRIPTION
        "A 1-16 character work group name."
	::= { sfworkGroupEntry 2 }

sfworkGroupType OBJECT-TYPE
	SYNTAX	INTEGER {
		 workgroup-all(1),
		 workgroup-multicast(2),
		 workgroup-unicast(3),
		 workgroup-invalid(4)  -- Delete a work group entry.
		 }
	ACCESS	read-write
	STATUS	mandatory
    DESCRIPTION
        "The type of work group."
	::= { sfworkGroupEntry 3 }

sfworkGroupPort OBJECT-TYPE
	SYNTAX	OCTET STRING
	ACCESS	read-write
	STATUS	mandatory
    DESCRIPTION
        "A list of all ports within the group.  The first
         octet specified ports 1-8, the second 9-16, etc."
	::= { sfworkGroupEntry 4 }


END
