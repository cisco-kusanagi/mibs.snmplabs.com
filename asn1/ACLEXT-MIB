ACLEXT-MIB 

   --FORCE-INCLUDE <mib.h>
   --FORCE-INCLUDE <snmpdefs.h>
   --FORCE-INCLUDE <snmpstat.h>
   --FORCE-INCLUDE "mibproto.h"
 
	DEFINITIONS ::= BEGIN

	IMPORTS
		MODULE-IDENTITY, OBJECT-TYPE, Integer32, IpAddress
			FROM SNMPv2-SMI
		DisplayString, RowStatus
			FROM SNMPv2-TC
		aclExt
			FROM APENT-MIB;

--ACLEXT MIB

    apAclExtMib MODULE-IDENTITY
	   LAST-UPDATED "9710092000Z" -- Thu October 9 20:00:00 EST 1997
	   ORGANIZATION "ArrowPoint Communications Inc."
	   CONTACT-INFO
	   "                      
	   Postal:                ArrowPoint Communications Inc.
				              50 Nagog Park
				              Acton, Massachusetts 01720
	   Tel:                   +1 978 206 3000
	   E-Mail:                support@arrowpoint.com"
       DESCRIPTION
	  "The MIB module used to describe the ArrowPoint Control List
	  clause table"
      ::= { aclExt 1}


apAclExtEnable OBJECT-TYPE
	  SYNTAX          INTEGER {
							disable(0)                       ,
							enable(1)                      
					  		  }
  	  MAX-ACCESS      read-write
      STATUS          current
      DESCRIPTION
      "The global state of the ACLs, either enabled or disabled"
	  ::= { aclExt 2}

apAclExtLogEnable OBJECT-TYPE
	SYNTAX          INTEGER {
							enable(1),
							disable(0)
							}
	MAX-ACCESS      read-write
    STATUS          obsolete
    DESCRIPTION
      "This MIB is Obsoleted"
	::= { aclExt 3}

apMainAclTable OBJECT-TYPE
	SYNTAX          SEQUENCE OF APMainAclEntry
	MAX-ACCESS      not-accessible
	STATUS          current
	DESCRIPTION
		"A list of ACLs."
	::= { aclExt 4 }

apMainAclEntry OBJECT-TYPE
	SYNTAX          APMainAclEntry
	MAX-ACCESS      not-accessible
	STATUS          current	
	DESCRIPTION	
		"A set of parameters which describe an access control list."
	INDEX   { apMainAclIndex }
	--DEFAULT apjam-group apMainAclInst, apMainAclIndex
	--DEFAULT apjam-popup-def apMainAclInst, Properties, local
	--DEFAULT apjam-wizard	ACL Wizard, 1, images/arrowlogo.gif, "Add an ACL"
	::= { apMainAclTable 1 }

APMainAclEntry ::= SEQUENCE {
		apMainAclIndex             Integer32,
		apMainAclStatus            RowStatus,
        apMainAclCountZero         INTEGER
}

apMainAclIndex    OBJECT-TYPE
	SYNTAX			Integer32 (1..99)
	MAX-ACCESS      read-create
	STATUS  		current
	DESCRIPTION     
		"The ACL Index"
	--DEFAULT ap-display-name	ACLs
	--DEFAULT apjam-popup-ref apMainAclInst, Properties
	--DEFAULT apjam-wizard-field	1, normal
	::= {apMainAclEntry 1}

apMainAclStatus OBJECT-TYPE
	SYNTAX          RowStatus
	MAX-ACCESS      read-create
	STATUS          current
	DESCRIPTION      
		"Status entry for this row "
	::= {apMainAclEntry 2}

apMainAclCountZero OBJECT-TYPE
	SYNTAX          INTEGER { reset(0) }
	MAX-ACCESS      read-create
    STATUS          current
    DESCRIPTION
      "Reset all clause hit counts for the ACL"
	::= { apMainAclEntry 3}

-- The following is the clause mib.
apAclTable OBJECT-TYPE
	SYNTAX          SEQUENCE OF APAclEntry
	MAX-ACCESS      not-accessible
	STATUS          current
	DESCRIPTION
		"A list of ACL clauses."
	::= { aclExt 5 }

apAclEntry OBJECT-TYPE
	SYNTAX          APAclEntry
	MAX-ACCESS      not-accessible
	STATUS          current	
	DESCRIPTION	
		"A set of parameters which describe an access control list clause."
	INDEX   { apMainAclIndex, apAclSubIndex }
	--DEFAULT apjam-group apAclInst, apAclSubIndex
	--DEFAULT apjam-popup-def apAclInst, Properties, local
	--DEFAULT apjam-popup-def apAclInst, Action, local
	--DEFAULT apjam-popup-def apAclInst, Protocol, local
	--DEFAULT apjam-popup-def apAclInst, Source, local
	--DEFAULT apjam-popup-def apAclInst, Destination, local
	--DEFAULT apjam-popup-def apAclInst, Time, local
	--DEFAULT apjam-popup-def apAclInst, Logging, local
	--DEFAULT apjam-popup-def apAclInst, Delete, special, apAclStatus
	--DEFAULT apjam-wizard	ACL Clause Wizard, 1, images/arrowlogo.gif, "Add a Clause to an ACL"
	--DEFAULT apjam-wizard	ACL Clause Wizard, 2, images/arrowlogo.gif, ""
	--DEFAULT apjam-wizard	ACL Clause Wizard, 3, images/arrowlogo.gif, ""
	--DEFAULT apjam-wizard	ACL Clause Wizard, 4, images/arrowlogo.gif, ""
	--DEFAULT apjam-wizard	ACL Clause Wizard, 5, images/arrowlogo.gif, ""
	--DEFAULT apjam-wizard	ACL Clause Wizard, 6, images/arrowlogo.gif, ""
	::= { apAclTable 1 }

APAclEntry ::= SEQUENCE {
		apAclIndex             Integer32,
		apAclSubIndex          Integer32,
		apAclAction            INTEGER,
		apAclProtocol          INTEGER,
		apAclSourceIpAddr      IpAddress,
		apAclSourceMask        IpAddress,
		apAclSourceGroup       DisplayString,
		apAclDestIpAddr        IpAddress,
		apAclDestMask          IpAddress,
		apAclDestContent       DisplayString,
		apAclPrecedence        Integer32,
		apAclTOS               Integer32,
		apAclLog               INTEGER,
		apAclStartTime         Integer32,
		apAclStopTime          Integer32,
		apAclQOSClass          Integer32,
		apAclSourcePortOperator INTEGER,
		apAclSourcePortStart   Integer32,
		apAclSourcePortEnd	   Integer32,
		apAclDestPortOperator  INTEGER,
		apAclDestPortEnum 	   INTEGER,
		apAclDestPortStart     Integer32,
		apAclDestPortEnd	   Integer32,
		apAclEnable            INTEGER,
		apAclProtocolNumber    Integer32,
		apAclStatus			   RowStatus,
	    apAclPreferredService  DisplayString,
		apAclSourceNQLName     DisplayString,
		apAclDestNQLName       DisplayString,
        apAclCountContentHits  Integer32,
        apAclCountRouterHits   Integer32,
        apAclCountDNSHits      Integer32
}

apAclIndex    OBJECT-TYPE
	SYNTAX			Integer32 (0..99)
	MAX-ACCESS      read-create
	STATUS  		current
	DESCRIPTION     
		"The ACL Index"
	--DEFAULT ap-display-name	ACL
	--DEFAULT apjam-popup-ref apAclInst, Properties
	--DEFAULT ap-create-requires Yes
	--DEFAULT apjam-noedit-dlg	True
	--DEFAULT apjam-wizard-field 1, choice, apMainAclIndex( ), nodepend
	::= {apAclEntry 1}

apAclSubIndex    OBJECT-TYPE
	SYNTAX			Integer32 (1..254)
	MAX-ACCESS      read-create
	STATUS  		current
	DESCRIPTION     
		"The ACL Current line Index"
	--DEFAULT ap-display-name	Clause
	--DEFAULT apjam-popup-ref apAclInst, Properties
	--DEFAULT ap-create-requires Yes
	--DEFAULT apjam-noedit-dlg	True
	--DEFAULT apjam-wizard-field	1, normal
	::= {apAclEntry 2}

apAclAction	OBJECT-TYPE
	SYNTAX          INTEGER {
							permit(1)                        ,
							deny(2)                      ,
							bypass(3)                                      
							}
	MAX-ACCESS      read-create
	STATUS  		current
	DESCRIPTION     
		"The ACL Permit or Deny Action"
	--DEFAULT ap-display-name	Action
	--DEFAULT apjam-popup-ref apAclInst, Action
	--DEFAULT apjam-wizard-field	2, normal
	::= {apAclEntry 3}

apAclProtocol OBJECT-TYPE
	SYNTAX			INTEGER {
						any(0)                             ,
						icmp(1)                              ,
						igmp(2)                              ,
						igp(9)                             ,
						udp(17)                             ,
						tcp(6)                             ,
						ospf(89)                              
					}
	MAX-ACCESS      read-create
	STATUS  		current
	DESCRIPTION     
		"The IP Protocol"
	--DEFAULT ap-display-name	Protocol
	--DEFAULT apjam-popup-ref apAclInst, Protocol
	--DEFAULT apjam-wizard-field	5, normal
	::= {apAclEntry 4}

apAclSourceIpAddr OBJECT-TYPE
	SYNTAX          IpAddress
	MAX-ACCESS      read-create
	STATUS  		current
	DESCRIPTION     
		"The source IP Address"
	--DEFAULT ap-display-name	Source IP Address
	--DEFAULT apjam-popup-ref apAclInst, Source
	--DEFAULT apjam-wizard-field	3, normal
	::= {apAclEntry 5}

apAclSourceMask OBJECT-TYPE
	SYNTAX          IpAddress
	MAX-ACCESS      read-create
	STATUS  		current
	DESCRIPTION     
		"The source IP Address Mask"
	--DEFAULT ap-display-name	Source IP Mask
	--DEFAULT apjam-popup-ref apAclInst, Source
	--DEFAULT apjam-wizard-field	3, normal
	::= {apAclEntry 6}

apAclSourceGroup OBJECT-TYPE
	SYNTAX          DisplayString
	MAX-ACCESS      read-create
	STATUS  		current
	DESCRIPTION     
		"The source group name"
	--DEFAULT ap-display-name	Source Group Name
	--DEFAULT apjam-popup-ref apAclInst, Source
	::= {apAclEntry 7}

apAclDestIpAddr OBJECT-TYPE
	SYNTAX          IpAddress
	MAX-ACCESS      read-create
	STATUS  		current
	DESCRIPTION     
		"The destination IP Address"
	--DEFAULT ap-display-name	Dest IP Address
	--DEFAULT apjam-popup-ref apAclInst, Destination
	--DEFAULT apjam-wizard-field	4, normal
	::= {apAclEntry 8}

apAclDestMask OBJECT-TYPE
	SYNTAX          IpAddress
	MAX-ACCESS      read-create
	STATUS  		current
	DESCRIPTION     
		"The destination IP Address mask"
	--DEFAULT ap-display-name	Dest IP Address Mask
	--DEFAULT apjam-popup-ref apAclInst, Destination
	--DEFAULT apjam-wizard-field	4, normal
	::= {apAclEntry 9}

apAclDestContent OBJECT-TYPE
	SYNTAX          DisplayString
	MAX-ACCESS      read-create
	STATUS  		current
	DESCRIPTION     
		"The destination Content Rule name"
	--DEFAULT ap-display-name	Dest Content Rule
	--DEFAULT apjam-popup-ref apAclInst, Destination
	--DEFAULT apjam-wizard-field	4, normal
	::= {apAclEntry 10}

apAclPrecedence OBJECT-TYPE
	SYNTAX			Integer32
	MAX-ACCESS      read-create
	STATUS  		current
	DESCRIPTION     
		"The IP precedence field"
	--DEFAULT ap-display-name	IP precedence
	--DEFAULT apjam-popup-ref apAclInst, Properties
	::= {apAclEntry 11}

apAclTOS      OBJECT-TYPE
	SYNTAX			Integer32
	MAX-ACCESS      read-create
	STATUS  		current
	DESCRIPTION     
		"The IP TOS field"
	--DEFAULT ap-display-name	IP TOS
	--DEFAULT apjam-popup-ref apAclInst, Properties
	::= {apAclEntry 12}

apAclLog      OBJECT-TYPE
	SYNTAX          INTEGER {
							enable(1)                                                   ,
							disable(2)                                                    
							}
	MAX-ACCESS      read-create
	STATUS  		current
	DESCRIPTION     
		"Log hits on this clause"
	--DEFAULT ap-display-name	Log
	--DEFAULT apjam-popup-ref apAclInst, Logging
	--DEFAULT apjam-wizard-field	6, normal
	::= {apAclEntry 13}

apAclStartTime  OBJECT-TYPE
	SYNTAX			Integer32
	MAX-ACCESS      read-create
	STATUS  		current
	DESCRIPTION     
		"Time for this clause to take effect"
	--DEFAULT ap-display-name	Start time
	--DEFAULT apjam-popup-ref apAclInst, Time
	::= {apAclEntry 14}

apAclStopTime  OBJECT-TYPE
	SYNTAX			Integer32
	MAX-ACCESS      read-create
	STATUS  		current
	DESCRIPTION     
		"Time for this clause to cease having an effect"
	--DEFAULT ap-display-name	Stop time
	--DEFAULT apjam-popup-ref apAclInst, Time
	::= {apAclEntry 15}

apAclQOSClass OBJECT-TYPE
	SYNTAX          Integer32 (1..7)
	MAX-ACCESS      read-create
	STATUS  		current
	DESCRIPTION     
		"Log hits on this clause"
	--DEFAULT ap-display-name	QOS Class
	--DEFAULT apjam-popup-ref apAclInst, Properties
	::= {apAclEntry 16}

apAclSourcePortOperator OBJECT-TYPE
	SYNTAX          INTEGER  {
						lt(1)                   ,
						gt(2)                      ,
						eq(3)                  ,
						neq(4)                      ,
						range(5)                      
					}
	MAX-ACCESS      read-create
	STATUS  		current
	DESCRIPTION     
		"Source Port Operator"
	--DEFAULT ap-display-name	Port Operator
	--DEFAULT apjam-popup-ref apAclInst, Source
	--DEFAULT apjam-wizard-field	3, normal
	::= {apAclEntry 17}

apAclSourcePortStart  OBJECT-TYPE
	SYNTAX			Integer32 (1..65535)
	MAX-ACCESS      read-create
	STATUS  		current
	DESCRIPTION     
		"Source Port Range Start"
	--DEFAULT ap-display-name	Range Start
	--DEFAULT apjam-popup-ref apAclInst, Source
	--DEFAULT apjam-wizard-field	3, normal
	::= {apAclEntry 18}

apAclSourcePortEnd  OBJECT-TYPE
	SYNTAX			Integer32 (1..65535)
	MAX-ACCESS      read-create
	STATUS  		current
	DESCRIPTION     
		"Source Port Range End"
	--DEFAULT ap-display-name	Range End
	--DEFAULT apjam-popup-ref apAclInst, Source
	--DEFAULT apjam-wizard-field	3, normal
	::= {apAclEntry 19}

apAclDestPortOperator OBJECT-TYPE
	SYNTAX          INTEGER  {
						lt(1)                   ,
						gt(2)                      ,
						eq(3)                  ,
						neq(4)                      ,
						range(5)                      
					}
	MAX-ACCESS      read-create
	STATUS  		current
	DESCRIPTION     
		"Destination Port Operator"
	--DEFAULT ap-display-name	Port Operator
	--DEFAULT apjam-popup-ref apAclInst, Destination
	--DEFAULT apjam-wizard-field	4, normal
	::= {apAclEntry 20}

apAclDestPortEnum OBJECT-TYPE
	SYNTAX          INTEGER  {
						none(0)              ,
						ftp-data(20)                          ,
						ftp(21)                     ,
						telnet(23)                        ,
						smtp(25)                      ,
						domain(53)                        ,
						gopher(70)                        ,
						http(80)                      ,
						pop(110)                      ,
						nntp(119)                       ,
						ntp(123)                      ,
						bgp(179)                      ,
						ldap(389)                       ,
						https(443)                        
						}
	MAX-ACCESS      read-create
	STATUS  		current
	DESCRIPTION     
		"Destination Port Enumeration"
	--DEFAULT ap-display-name	Port Enumeration
	--DEFAULT apjam-popup-ref apAclInst, Destination
	--DEFAULT apjam-wizard-field	4, normal
	::= {apAclEntry 21}

apAclDestPortStart  OBJECT-TYPE
	SYNTAX			Integer32 (1..65535)
	MAX-ACCESS      read-create
	STATUS  		current
	DESCRIPTION     
		"Destination Port Range Start"
	--DEFAULT ap-display-name	Range Start
	--DEFAULT apjam-popup-ref apAclInst, Destination
	--DEFAULT apjam-wizard-field	4, normal
	::= {apAclEntry 22}

apAclDestPortEnd  OBJECT-TYPE
	SYNTAX			Integer32 (1..65535)
	MAX-ACCESS      read-create
	STATUS  		current
	DESCRIPTION     
		"Destination Port Range End"
	--DEFAULT ap-display-name	Range End
	--DEFAULT apjam-popup-ref apAclInst, Destination
	--DEFAULT apjam-wizard-field	4, normal
	::= {apAclEntry 23}

apAclEnable  OBJECT-TYPE
	SYNTAX  INTEGER {
					disable(0)                               ,
					enable(1)                              
 					}
	MAX-ACCESS      read-create
	STATUS 			current
	DESCRIPTION     
		"The state of the ACL, either enabled or disabled"
	DEFVAL { disable }
	::= {apAclEntry 24}

apAclProtocolNumber OBJECT-TYPE
	SYNTAX			Integer32 (0..65535)
	MAX-ACCESS      read-create
	STATUS  		current
	DESCRIPTION     
		"The IP Protocol"
	::= {apAclEntry 25}

apAclStatus   OBJECT-TYPE
	SYNTAX          RowStatus
	MAX-ACCESS      read-create
	STATUS          current
	DESCRIPTION      
		"Status entry for this row "
	::= {apAclEntry 26}

apAclPreferredService OBJECT-TYPE
	SYNTAX          DisplayString(SIZE(1..31))
	MAX-ACCESS      read-create
	STATUS  		current
	DESCRIPTION     
		"Preferred Service based on hits on this ACL clause"
	--DEFAULT ap-display-name	Preferred Service
	--DEFAULT apjam-popup-ref apAclInst, Properties
	::= {apAclEntry 27}

apAclSourceNQLName OBJECT-TYPE
	SYNTAX          DisplayString(SIZE(0..31))
	MAX-ACCESS      read-create
	STATUS  		current
	DESCRIPTION     
		"Network Qualifier List used in the source this ACL clause"
	--DEFAULT ap-display-name	Source address Network Qualifier List name
	--DEFAULT apjam-popup-ref apAclInst, Properties
	::= {apAclEntry 28}

apAclDestNQLName OBJECT-TYPE
	SYNTAX          DisplayString(SIZE(0..31))
	MAX-ACCESS      read-create
	STATUS  		current
	DESCRIPTION     
		"Network Qualifier List used in the source this ACL clause"
	--DEFAULT ap-display-name	Source address Network Qualifier List name
	--DEFAULT apjam-popup-ref apAclInst, Properties
	::= {apAclEntry 29}

apAclCountContentHits OBJECT-TYPE
	SYNTAX			Integer32
	MAX-ACCESS      read-create
	STATUS  		current
	DESCRIPTION     
		"Count of content hits on this ACL clause"
	::= {apAclEntry 30}

apAclCountRouterHits OBJECT-TYPE
	SYNTAX			Integer32
	MAX-ACCESS      read-create
	STATUS  		current
	DESCRIPTION     
		"Count of router hits on this ACL clause"
	::= {apAclEntry 31}

apAclCountDNSHits OBJECT-TYPE
	SYNTAX			Integer32
	MAX-ACCESS      read-create
	STATUS  		current
	DESCRIPTION     
		"Count of DNS hits on this ACL clause"
	::= {apAclEntry 32}

END
