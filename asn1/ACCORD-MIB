--
--	Accord MIB	(Rev1.0)
--  Oshi Keren-Zur
--	Wed Jun 20 2000
--	Accord Networks, Ltd.
--	84 Em-hamoshavot Str. 
--  Petah-Tikva, Israel
--
-- 	Notes:

--      { iso(1) org(3) dod(6) internet(1) private(4) enterprises(1) 6333 }

ACCORD-MIB DEFINITIONS ::= BEGIN	

    IMPORTS
   	enterprises
			FROM RFC1155-SMI;
 
	accord		OBJECT IDENTIFIER ::= { enterprises 6333 }
 
	products	OBJECT IDENTIFIER ::= { accord 1 }
 
	mgc-100		OBJECT IDENTIFIER ::= { products 1 }
 
END
