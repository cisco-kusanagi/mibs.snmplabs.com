COMPUTERM-COMMON-MIB

DEFINITIONS ::= BEGIN

-- Section 1: Top Level Definitions

-- Imports

IMPORTS
    enterprises, Gauge, Counter,
    TimeTicks, IpAddress          FROM RFC1155-SMI
    DisplayString                 FROM RFC1213-MIB;


-- Textual Conventions

-- Categories
            computerm     OBJECT IDENTIFIER ::= { enterprises 2439 }
            ctChannelExtensionMIB   OBJECT IDENTIFIER ::= { computerm 1 }

-- Groups
            ctSystem        OBJECT IDENTIFIER ::=   { ctChannelExtensionMIB 1}
            ctInventory     OBJECT IDENTIFIER ::=   { ctChannelExtensionMIB 2}
            ctTopology      OBJECT IDENTIFIER ::=   { ctChannelExtensionMIB 3}
            ctPerformance   OBJECT IDENTIFIER ::=   { ctChannelExtensionMIB 4}
            ctDiagnostics   OBJECT IDENTIFIER ::=   { ctChannelExtensionMIB 5}
            ctPowerSupply   OBJECT IDENTIFIER ::=   { ctChannelExtensionMIB 6}
            ctTraps         OBJECT IDENTIFIER ::=   { ctChannelExtensionMIB 7}

-- Section 2:
--
        --
        -- Some of the groups have Channel Extender Address, Slot
        -- Index, Board Index, Port Number and Device Number as the
        -- indexes. BoardIndex can be used for cases where there are
        -- multiple boards in the same slot e.g. ARTIC card and
        -- daughter cards. Port Index can be used for MUX cards and
        -- Device Index is used for Peripheral Devices and other
        -- externally connected devices e.g. OC3/DS3 converter.
        --
        --
        -- The following Slot, Board, Port and Device Indexes are
        -- reserved to be used where "system level" information
        -- needs to be expressed in Slot,Board, Port and Device
        -- Indexes.
        --
        --      Slot#   Board#  Port# Device#    Description
        --     =======================================
        --       0x00       0     0     1   CPU
        --       0x00       0     0     2   ONLINE Unit (TopoTable)
        --       0x00       0     0     3   OFFLINE Unit(TopoTable)
        --       0x00       0     0     4   Power Supply Unit
        --       0x00       0     0     5   Redundant PowerSupplyUnit
        --
        --       0x00       0     0    20   GoldDisk (Software Module)
        --       0x00       0     0    21   EXEC (Software Module)
        --       0x00       0     0    22   OS/2 Driver (SW Module)
        --       0x00       0     0    23   GMX  (SW Module)
        --       0x00       0     0    24   VMC Agent (SW Module)
        --       0x00       0     0    25   VMC Agent INI File(SW Module)
        --       0x00       0     0    26   VMC Agent MIB File(Text File)
        --
        --

        --
        -- The ctSysTable group
        --
        -- Provides the system level information for the Channel
        -- Extenders. Implementation of this group is mandatory.
        --

        ctSysName OBJECT-TYPE
           SYNTAX DisplayString (SIZE(0..255))
           ACCESS read-write
           STATUS mandatory
           DESCRIPTION
                 "System Name."
           ::= { ctSystem 1 }

        ctSysType OBJECT-TYPE
           SYNTAX DisplayString (SIZE(0..80))
           ACCESS read-only
           STATUS mandatory
           DESCRIPTION
                 "System Type ie. VMC8250, Other etc., "
           ::= { ctSystem 2 }

        ctSysPrimaryBackupMode OBJECT-TYPE
           SYNTAX INTEGER {
                    primary (1),
                    backup  (2),
                    primaryOnly (3),
                    unknown (4)
                  }
           ACCESS read-only
           STATUS mandatory
           DESCRIPTION
                 "Primary/Backup Mode of the Channel Extender. This is
                  defined in PARAMTAB.DAT"
           ::= { ctSystem 3 }

        ctSysAutoStartFlag OBJECT-TYPE
           SYNTAX INTEGER {
                    disabled (0),
                    enabled  (1),
                    offline  (2),
                    online   (3)
                  }
           ACCESS read-write
           STATUS mandatory
           DESCRIPTION
                 "State of the auto start flag.
                  Set to 1, enable or online to turn channel extender ONLINE
                  or to 0 disable or offline to turn channel extender OFFLINE
                  Note! Turning OFFLINE will automatically restart the
                  the channel extender with a RESTARTEXEC request."
           ::= { ctSystem 4 }

        ctSysPowerSupplyMonitorFlag OBJECT-TYPE
           SYNTAX INTEGER {
                    disabled (0),
                    enabled  (1)
                  }
           ACCESS read-only
           STATUS mandatory
           DESCRIPTION
                 "Whether EXEC is monitoring the power supply or not"
           ::= { ctSystem 5 }

        ctSysChannelExtenderMode OBJECT-TYPE
           SYNTAX DisplayString (SIZE(1..80))
           ACCESS read-only
           STATUS mandatory
           DESCRIPTION
                 "State of the EXEC i.e. whether it is in diagnostics
                  mode or channel extender mode"
           ::= { ctSystem 6 }

        ctSysElapsedTime OBJECT-TYPE
           SYNTAX DisplayString (SIZE(1..80))
           ACCESS read-only
           STATUS mandatory
           DESCRIPTION
                 "For how long the system has been running expressed in
                  days, hours, minutes."
           ::= { ctSystem 7 }

        ctSysStartupTime OBJECT-TYPE
           SYNTAX DisplayString (SIZE(1..80))
           ACCESS read-only
           STATUS mandatory
           DESCRIPTION
                 "The last time EXEC was restarted expressed in Month,
                  Day, Year, Hour, Minute format in the local time
                  zone."
           ::= { ctSystem 8 }

        ctSysCurrentTime OBJECT-TYPE
           SYNTAX DisplayString (SIZE(1..80))
           ACCESS read-only
           STATUS mandatory
           DESCRIPTION
                 "Current Time expressed in Month,Day,Year,Hour,Minute
                  format in the local time zone."
           ::= { ctSystem 9 }

        ctSysCustomerName OBJECT-TYPE
           SYNTAX  DisplayString (SIZE (0..255))
           ACCESS  read-only
           STATUS  mandatory
           DESCRIPTION
                 "Textual Identification of the name of the customer"
           ::= { ctSystem 10 }

        ctSysCustomerServiceNumber OBJECT-TYPE
           SYNTAX  DisplayString (SIZE (6))
           ACCESS  read-only
           STATUS  mandatory
           DESCRIPTION
                 "A six(6) digit identification code"
           ::= { ctSystem 11 }

        ctSysComputermContact OBJECT-TYPE
           SYNTAX  DisplayString (SIZE (0..255))
           ACCESS  read-only
           STATUS  mandatory
           DESCRIPTION
                 "The textual identification of the contact person at
                  Computerm, together with information on how to
                  contact this person."
             ::= { ctSystem 12 }

        ctSysGMXCommand OBJECT-TYPE
           SYNTAX  DisplayString (SIZE (0..255))
           ACCESS  read-write
           STATUS  mandatory
           DESCRIPTION
                 "Issue select GMX command via SNMP.
                  Supported Commands:
                  SWC, <channel_number_and_address>, <network_address>, <num_contiguous>
                  channel_number_and_address-Hexadecimal-Mandotory
                  network_address-Hexadecimal-Mandatory
                  num_contiguous-Decimal-Optional"
             ::= { ctSystem 13 }

         --
         -- The ctInventory Group
         --
         -- The ctSwInventory group contains the Software and
         -- hardware inventory groups.
         --

         --
         -- The ctHwTable Group
         --
         -- The ctHwTable group contains the list of all the physical
         -- boards in a Channel Extender. This includes adapter,
         -- emulator, communications boards and all the system level
         -- hardware e.g. power supply units.
         --
         --

        ctHwTable OBJECT-TYPE
           SYNTAX SEQUENCE OF ctHwEntry
           ACCESS not-accessible
           STATUS mandatory
           DESCRIPTION
                 "Channel Extender Hardware Inventory Table"
           ::= { ctInventory 1 }

        ctHwEntry OBJECT-TYPE
           SYNTAX ctHwEntry
           ACCESS not-accessible
           STATUS mandatory
           DESCRIPTION
                 "Information about each hardware module installed"
           INDEX { ctHwSlotIndex, ctHwBoardIndex,
                   ctHwPortIndex, ctHwDeviceIndex }
           ::= { ctHwTable 1 }

        ctHwEntry ::=
           SEQUENCE {
               ctHwSlotIndex
                    INTEGER,
               ctHwBoardIndex
                    INTEGER,
               ctHwPortIndex
                    INTEGER,
               ctHwDeviceIndex
                    INTEGER,
               ctHwName
                    DisplayString,
               ctHwType
                    DisplayString,
               ctHwSpeed
                    INTEGER,
               ctHwChannelOrLineNumber
                    INTEGER,
               ctHwPromNumber
                    DisplayString,
               ctHwMNumber
                    DisplayString,
               ctHwSerialNumber
                    DisplayString,
               ctHwRevisionLevel
                    DisplayString,
               ctHwStatus
                    DisplayString
           }

        ctHwSlotIndex OBJECT-TYPE
           SYNTAX  INTEGER
           ACCESS  read-only
           STATUS  mandatory
           DESCRIPTION
                 "Slot Index of the hardware board. For system level
                  modules, a specific slot number will be reserved.
                  See the top of this document for details."
           ::= { ctHwEntry 1 }

        ctHwBoardIndex OBJECT-TYPE
           SYNTAX  INTEGER
           ACCESS  read-only
           STATUS  mandatory
           DESCRIPTION
                 "The board index for a specific slot e.g. ARTIC card
                  and AIB daughter cards. This can also be used to
                  include the extenally connected modules e.g. OC3/DS3
                  converter, Control Unit etc.,"
           ::= { ctHwEntry 2 }

        ctHwPortIndex OBJECT-TYPE
           SYNTAX  INTEGER
           ACCESS  read-only
           STATUS  mandatory
           DESCRIPTION
                 "Port Number of the board. This can be potentially
                  used for MUX cards and Peripheral devices."
           ::= { ctHwEntry 3 }

        ctHwDeviceIndex OBJECT-TYPE
           SYNTAX  INTEGER
           ACCESS  read-only
           STATUS  mandatory
           DESCRIPTION
                 "Externally connected devices index. This can be
                  potentially used for peripheral devices and OC3/DS3
                  converters"
           ::= { ctHwEntry 4 }

        ctHwName OBJECT-TYPE
           SYNTAX  DisplayString (SIZE(0..255))
           ACCESS  read-write
           STATUS  mandatory
           DESCRIPTION
                 "Name of the hardware module"
           ::= { ctHwEntry 5 }

        ctHwType OBJECT-TYPE
           SYNTAX  DisplayString (SIZE(1..80))
           ACCESS  read-only
           STATUS  mandatory
           DESCRIPTION
                 "Type of the hardware module"
           ::= { ctHwEntry 6 }

        ctHwSpeed OBJECT-TYPE
           SYNTAX  INTEGER
           ACCESS  read-only
           STATUS  mandatory
           DESCRIPTION
                 "Speed of the hardware module. This is the baud rate
                  for comm. modules"
           ::= { ctHwEntry 7 }

        ctHwChannelOrLineNumber OBJECT-TYPE
           SYNTAX  INTEGER
           ACCESS  read-only
           STATUS  mandatory
           DESCRIPTION
                 "Channel Number of the Adapter/Emulator boards and
                  Line Number of the Comm boards. For other board
                  types, this value will be zero."
           ::= { ctHwEntry 8 }

        ctHwPromNumber OBJECT-TYPE
           SYNTAX  DisplayString (SIZE(1..255))
           ACCESS  read-only
           STATUS  mandatory
           DESCRIPTION
                 "PROM Number of the module"
           ::= { ctHwEntry 9 }

        ctHwMNumber OBJECT-TYPE
           SYNTAX  DisplayString (SIZE(1..255))
           ACCESS  read-only
           STATUS  mandatory
           DESCRIPTION
                 "M-Number of the module"
           ::= { ctHwEntry 10 }

        ctHwSerialNumber OBJECT-TYPE
           SYNTAX  DisplayString (SIZE(1..255))
           ACCESS  read-only
           STATUS  mandatory
           DESCRIPTION
                 "Serial Number of the module"
           ::= { ctHwEntry 11 }

        ctHwRevisionLevel OBJECT-TYPE
           SYNTAX  DisplayString (SIZE(1..255))
           ACCESS  read-only
           STATUS  mandatory
           DESCRIPTION
                 "Revision level of the hardware module"
           ::= { ctHwEntry 12 }

        ctHwStatus OBJECT-TYPE
           SYNTAX  DisplayString (SIZE(1..80))
           ACCESS  read-only
           STATUS  mandatory
           DESCRIPTION
                 "Status of the hardware module"
           ::= { ctHwEntry 13 }

         --
         -- The ctSwTable Group
         --
         -- The ctSwTable group contains the list of all the Channel
         -- extender software modules that are currently loaded. This
         -- includes both the system level modules (e.g. EXEC, OS/2
         -- Device Driver, GMX Program and Network Management Agent)
         -- and the board level modules. Also, if there are multiple
         -- boards of the same type e.g. multiple Adapter and Emulator
         -- boards, they will be counted multiple times.
         --
         --

        ctSwTable OBJECT-TYPE
           SYNTAX SEQUENCE OF ctSwEntry
           ACCESS not-accessible
           STATUS mandatory
           DESCRIPTION
                 "Channel Extender Software Inventory Table"
           ::= { ctInventory 2 }

        ctSwEntry OBJECT-TYPE
           SYNTAX ctSwEntry
           ACCESS not-accessible
           STATUS mandatory
           DESCRIPTION
                 "Information about each software module running."
           INDEX { ctSwSlotIndex, ctSwBoardIndex,
                   ctSwPortIndex, ctSwDeviceIndex }
           ::= { ctSwTable 1 }

        ctSwEntry ::=
           SEQUENCE {
               ctSwSlotIndex
                    INTEGER,
               ctSwBoardIndex
                    INTEGER,
               ctSwPortIndex
                    INTEGER,
               ctSwBoardIndex
                    INTEGER,
               ctSwName
                    DisplayString,
               ctSwPartNumber
                    DisplayString
           }

        ctSwSlotIndex OBJECT-TYPE
           SYNTAX  INTEGER
           ACCESS  read-only
           STATUS  mandatory
           DESCRIPTION
                 "Slot Index of the hardware module where this
                  software module is running. For system level
                  modules, a specific slot number will be reserved.
                  See the top of this document for details."
           ::= { ctSwEntry 1 }

        ctSwBoardIndex OBJECT-TYPE
           SYNTAX  INTEGER
           ACCESS  read-only
           STATUS  mandatory
           DESCRIPTION
                 "The board index for a specific slot e.g. ARTIC card
                  and AIB daughter cards where this software module is
                  running. This can also be used to include the
                  extenally connected modules e.g. OC3/DS3 converter,
                  Control Unit etc.,"
           ::= { ctSwEntry 2 }

        ctSwPortIndex OBJECT-TYPE
           SYNTAX  INTEGER
           ACCESS  read-only
           STATUS  mandatory
           DESCRIPTION
                 "Port Number of the board this software module is
                  running. This can be potentially used for MUX cards"
           ::= { ctSwEntry 3 }

        ctSwDeviceIndex OBJECT-TYPE
           SYNTAX  INTEGER
           ACCESS  read-only
           STATUS  mandatory
           DESCRIPTION
                 "Externally connected devices index. This can be
                  potentially used for peripheral devices and OC3/DS3
                  converters"
           ::= { ctSwEntry 4 }

        ctSwName OBJECT-TYPE
           SYNTAX  DisplayString (SIZE(0..255))
           ACCESS  read-only
           STATUS  mandatory
           DESCRIPTION
                 "Name of this software module"
           ::= { ctSwEntry 5 }

        ctSwPartNumber OBJECT-TYPE
           SYNTAX  DisplayString (SIZE(1..255))
           ACCESS  read-only
           STATUS  mandatory
           DESCRIPTION
                 "Software Driver Part Number"
           ::= { ctSwEntry 6 }

        --
        -- The ctTopologyTable
        -- Provides the connectivity information between the channel
        -- extender hosting the agent and all the remote units
        -- including their twin units.
        --
        --

        ctTopologyTable OBJECT-TYPE
              SYNTAX   SEQUENCE OF ctTopologyEntry
              ACCESS   not-accessible
              STATUS   mandatory
              DESCRIPTION
                 "Provides the connectivity information between the
                  current channel extender and all the remote units
                  including their twin units."
              ::= { ctTopology 1 }

         ctTopologyEntry OBJECT-TYPE
              SYNTAX  ctTopologyEntry
              ACCESS  not-accessible
              STATUS  mandatory
              DESCRIPTION
                  "Defines each remote connection"
              INDEX { ctTopoSlotIndex, ctTopoBoardIndex,
                      ctTopoPortIndex, ctTopoDeviceIndex }
              ::= { ctTopologyTable 1 }

          ctTopologyEntry ::=
              SEQUENCE {
                 ctTopoSlotIndex
                       INTEGER,
                 ctTopoBoardIndex
                       INTEGER,
                 ctTopoPortIndex
                       INTEGER,
                 ctTopoDeviceIndex
                       INTEGER,
                 ctTopoName
                       DisplayString,
                 ctTopoRemoteUnit
                       IpAddress,
                 ctTopoRemoteTwinUnit
                       INTEGER
                }

        ctTopoSlotIndex OBJECT-TYPE
           SYNTAX  INTEGER
           ACCESS  read-only
           STATUS  mandatory
           DESCRIPTION
                 "Slot Index of the hardware module this connection
                  is describing. To describe the current unit's
                  twin unit, a specific slot number will be
                  reserved. See the top of this document for details."
           ::= { ctTopologyEntry 1 }

        ctTopoBoardIndex OBJECT-TYPE
           SYNTAX  INTEGER
           ACCESS  read-only
           STATUS  mandatory
           DESCRIPTION
                 "The board index of the slot this connection is
                  describing."
           ::= { ctTopologyEntry 2 }

        ctTopoPortIndex OBJECT-TYPE
           SYNTAX  INTEGER
           ACCESS  read-only
           STATUS  mandatory
           DESCRIPTION
                 "The port index of the slot this connection is
                  describing."
           ::= { ctTopologyEntry 3 }

        ctTopoDeviceIndex OBJECT-TYPE
           SYNTAX  INTEGER
           ACCESS  read-only
           STATUS  mandatory
           DESCRIPTION
                 "Externally connected devices index. This can be
                  potentially used for peripheral devices and OC3/DS3
                  converters"
           ::= { ctTopologyEntry 4 }

        ctTopoName OBJECT-TYPE
           SYNTAX  DisplayString (SIZE(0..255))
           ACCESS  read-write
           STATUS  mandatory
           DESCRIPTION
                 "Textual description of this connection. Same as
                  ctHwName."
           ::= { ctTopologyEntry 5 }

        ctTopoRemoteUnit OBJECT-TYPE
           SYNTAX  IpAddress
           ACCESS  read-write
           STATUS  mandatory
           DESCRIPTION
                 "Address of the remote channel extender unit."
           ::= { ctTopologyEntry 6 }

        ctTopoRemoteTwinUnit OBJECT-TYPE
           SYNTAX  IpAddress
           ACCESS  read-write
           STATUS  mandatory
           DESCRIPTION
                 "Address of the remote twin channel extender."
           ::= { ctTopologyEntry 7 }

        --
        -- ctPerformance Group
        --
        -- This group supports the performance related control and
        -- data tables
        --
        --
        -- The ctPerfControlTable
        --
        --

        ctPerfResetAllCompressionRatios OBJECT-TYPE
              SYNTAX  INTEGER { reset (1) }
              ACCESS  read-write
              STATUS  mandatory
              DESCRIPTION
                     "This variable is used to reset the compression
                      ratios for all different device types"
              ::= { ctPerformance 1 }

        ctPerfResetAllPeakThroughputs OBJECT-TYPE
              SYNTAX  INTEGER { reset (1) }
              ACCESS  read-write
              STATUS  mandatory
              DESCRIPTION
                     "Use this object to reset the peak throughput
                      values (Tx, Rx and Total) associated with
                      this conceptual row. This will start a new
                      data collection and new peak values will be
                      computed. Modifying this object will also reset
                      the ctPerfPeakThroughputStartTime to the
                      current system time"
              ::= { ctPerformance 2 }

        ctPerfResetAllReceiveErrorCounts OBJECT-TYPE
              SYNTAX  INTEGER { reset (1) }
              ACCESS  read-write
              STATUS  mandatory
              DESCRIPTION
                     "Use this object to reset the receive error
                      values associated with all the comm. lines.
                      This will start a new data collection. Modifying
                      this object will also reset the
                      ctPerfReceiveErrorCountStartTime to the
                      current system time"
              ::= { ctPerformance 3 }

        ctPerfShowFractions OBJECT-TYPE
              SYNTAX  INTEGER { Off (0),
                                On  (1)
                      }
              ACCESS  read-write
              STATUS  mandatory
              DESCRIPTION
                     "Use this object to display the CPU/Line Utilization
                      and CompressionRatio in 1/100th of a percentage.

                      Example: CompressionRatio: 1.59

                      Please note that 1.59 cannot be reported to the NMS
                      since SNMP doesn't support Floating Point Arithmetic.

                      The following are the alternatives::

                      ctPerfShowFractions=Off:
                           Agent Reports 2 (1.59 rounded up) as the
                           CompRatio to the NMS

                      ctPerfShowFractions=On:
                           Agent Reports 159 (1/100th of a percentage) as the
                           CompRatio to the NMS. This will give better
                           precision.

                           If the NMS has the capability to devide by 100,
                           using this method, the actual CompRatio of 1.59
                           can be displayed by the NMS.

                     By Default, ctPerfShowFractions is OFF"
           ::= { ctPerformance 4 }

        ctPerfControlTable OBJECT-TYPE
           SYNTAX   SEQUENCE OF ctPerfControlEntry
           ACCESS   not-accessible
           STATUS   mandatory
           DESCRIPTION
                 "Provides the user modifiable values for performance
                  data"
           ::= { ctPerformance 5 }

        ctPerfControlEntry OBJECT-TYPE
              SYNTAX  ctPerfControlEntry
              ACCESS  not-accessible
              STATUS  mandatory
              DESCRIPTION
                  "Provides the objects to configure performance data
                   collection"
              INDEX  { ctPerfControlSlotIndex,
                       ctPerfControlBoardIndex,
                       ctPerfControlPortIndex,
                       ctPerfControlDeviceIndex }
              ::= { ctPerfControlTable 1 }

        ctPerfControlEntry ::=
              SEQUENCE {
                 ctPerfControlSlotIndex,
                       INTEGER,
                 ctPerfControlBoardIndex,
                       INTEGER,
                 ctPerfControlPortIndex,
                       INTEGER,
                 ctPerfControlDeviceIndex,
                       INTEGER,
                 ctPerfControlName,
                       DisplayString,
                 ctPerfControlInterval
                       INTEGER,
                 ctPerfControlUtilThreshold
                       INTEGER,
              }

        ctPerfControlSlotIndex OBJECT-TYPE
           SYNTAX  INTEGER
           ACCESS  read-only
           STATUS  mandatory
           DESCRIPTION
                 "Slot index"
           ::= { ctPerfControlEntry 1 }

        ctPerfControlBoardIndex OBJECT-TYPE
           SYNTAX  INTEGER
           ACCESS  read-only
           STATUS  mandatory
           DESCRIPTION
                 "Board Index"
           ::= { ctPerfControlEntry 2 }

        ctPerfControlPortIndex OBJECT-TYPE
           SYNTAX  INTEGER
           ACCESS  read-only
           STATUS  mandatory
           DESCRIPTION
                 "Port Index"
           ::= { ctPerfControlEntry 3 }

        ctPerfControlDeviceIndex OBJECT-TYPE
           SYNTAX  INTEGER
           ACCESS  read-only
           STATUS  mandatory
           DESCRIPTION
                 "Externally connected devices index. This can be
                  potentially used for peripheral devices and OC3/DS3
                  converters"
           ::= { ctPerfControlEntry 4 }

        ctPerfControlName OBJECT-TYPE
           SYNTAX  DisplayString (SIZE(0..255))
           ACCESS  read-write
           STATUS  mandatory
           DESCRIPTION
                 "Same as the ctHwName"
           ::= { ctPerfControlEntry 5 }

        ctPerfControlInterval OBJECT-TYPE
           SYNTAX  INTEGER
           ACCESS  read-write
           STATUS  mandatory
           DESCRIPTION
                 "Data collection interval specified in seconds"
           DEFVAL  { 10 }
           ::= { ctPerfControlEntry 6 }

          ctPerfControlUtilThreshold OBJECT-TYPE
              SYNTAX  INTEGER
              ACCESS  read-write
              STATUS  mandatory
              DESCRIPTION
                     "Utilization threshold value"
              DEFVAL  { 10 }
              ::= { ctPerfControlEntry 7 }

        --
        -- ctPerformanceTable
        --
        --

        ctPerformanceTable OBJECT-TYPE
           SYNTAX   SEQUENCE OF ctPerformanceEntry
           ACCESS   not-accessible
           STATUS   mandatory
           DESCRIPTION
                 "Performance data for the channel extender units"
           ::= { ctPerformance 6 }

        ctPerformanceEntry OBJECT-TYPE
              SYNTAX  ctPerformanceEntry
              ACCESS  not-accessible
              STATUS  mandatory
              DESCRIPTION
                  "Provides the performance data for different
                   hardware modules of a Channel Extender"
              INDEX { ctPerfSlotIndex, ctPerfBoardIndex,
                      ctPerfPortIndex, ctPerfDeviceIndex }
              ::= { ctPerformanceTable 1 }

        ctPerformanceEntry ::=
              SEQUENCE {
                 ctPerfSlotIndex,
                       INTEGER,
                 ctPerfBoardIndex,
                       INTEGER,
                 ctPerfPortIndex,
                       INTEGER,
                 ctPerfDeviceIndex,
                       INTEGER,

                 ctPerfName
                       DisplayString,
                 ctPerfChannelOrLineNumber
                       INTEGER,
                 ctPerfType
                       DisplayString,
                 ctPerfStatus
                       DisplayString,
                 ctPerfTxThroughput
                       INTEGER,
                 ctPerfRxThroughput
                       INTEGER,
                 ctPerfTotalThroughput
                       INTEGER,
                 ctPerfPeakTxThroughput
                       INTEGER,
                 ctPerfPeakTxThroughputTime
                       DisplayString,
                 ctPerfPeakRxThroughput
                       INTEGER,
                 ctPerfPeakRxThroughputTime
                       DisplayString,
                 ctPerfPeakTotalThroughput
                       INTEGER,
                 ctPerfPeakTotalThroughputTime
                       DisplayString,
                 ctPerfPeakThroughputStartTime
                       DisplayString,
                 ctPerfResetPeakThroughput
                       INTEGER,

                 ctPerfTxUtilization
                       INTEGER,
                 ctPerfRxUtilization
                       INTEGER,
                 ctPerfCPUUtilization
                       INTEGER,
                 ctPerfDataRate
                       INTEGER,
                 ctPerfReceiveErrorCount
                       INTEGER,
                 ctPerfReceiveErrorCountStartTime
                       DisplayString,
                 ctPerfResetReceiveErrorCount
                       INTEGER,

                 ctPerfCommLineDelay
                       INTEGER,

                 ctPerfCompressionRatio
                       INTEGER,
                 ctPerfCompressionRatioStartTime
                       INTEGER,
                 ctPerfResetCompressionRatio
                       INTEGER,

                 ctPerfDeviceTxUncompressedCounts
                       INTEGER,
                 ctPerfDeviceTxCompressedCounts
                       INTEGER,
                 ctPerfDeviceRxUncompressedCounts
                       INTEGER,
                 ctPerfDevcieRxCompressedCounts
                       INTEGER,
                 ctPerfDeviceCountsStartTime
                       INTEGER,
                 ctPerfResetDeviceCounts
                       INTEGER,

                 ctPerfDeviceTxCompressionRatio
                       INTEGER,
                 ctPerfDeviceRxCompressionRatio
                       INTEGER
              }

        ctPerfSlotIndex OBJECT-TYPE
           SYNTAX  INTEGER
           ACCESS  read-only
           STATUS  mandatory
           DESCRIPTION
                 "Slot index of the collection"
           ::= { ctPerformanceEntry 1 }

        ctPerfBoardIndex OBJECT-TYPE
           SYNTAX  INTEGER
           ACCESS  read-only
           STATUS  mandatory
           DESCRIPTION
                 "Board index for a specific slot"
           ::= { ctPerformanceEntry 2 }

        ctPerfPortIndex OBJECT-TYPE
           SYNTAX  INTEGER
           ACCESS  read-only
           STATUS  mandatory
           DESCRIPTION
                 "Port index of a board"
           ::= { ctPerformanceEntry 3 }

        ctPerfDeviceIndex OBJECT-TYPE
           SYNTAX  INTEGER
           ACCESS  read-only
           STATUS  mandatory
           DESCRIPTION
                 "Externally connected devices index. This can be
                  potentially used for peripheral devices and OC3/DS3
                  converters"
           ::= { ctPerformanceEntry 4 }

        ctPerfName OBJECT-TYPE
           SYNTAX  DisplayString (SIZE(0..255))
           ACCESS  read-write
           STATUS  mandatory
           DESCRIPTION
                 "Same as the ctHwName"
           ::= { ctPerformanceEntry 5 }

        ctPerfChannelOrLineNumber OBJECT-TYPE
              SYNTAX  INTEGER
              ACCESS  read-only
              STATUS  mandatory
              DESCRIPTION
                     "Same as the ctHwChannelOrLineNumber"
              ::= { ctPerformanceEntry 6 }

        ctPerfType OBJECT-TYPE
              SYNTAX  DisplayString (SIZE(1..80))
              ACCESS  read-only
              STATUS  mandatory
              DESCRIPTION
                     "Same as the ctHwType"
              ::= { ctPerformanceEntry 7 }

          ctPerfStatus OBJECT-TYPE
              SYNTAX  DisplayString (SIZE(1..80))
              ACCESS  read-only
              STATUS  mandatory
              DESCRIPTION
                     "Same as the ctHwStatus"
              ::= { ctPerformanceEntry 8 }

          ctPerfTxThroughput OBJECT-TYPE
              SYNTAX  INTEGER
              ACCESS  read-only
              STATUS  mandatory
              DESCRIPTION
                     "Transmit thorughput specified in bits/second
                      (including any overhead bits). This value is
                      defined for communication adapters only and
                      calculated for each pyhsical line. If a
                      physical line is using multiple virtual lines,
                      this value accounts for all the virtual lines"
              ::= { ctPerformanceEntry 9 }

          ctPerfRxThroughput OBJECT-TYPE
              SYNTAX  INTEGER
              ACCESS  read-only
              STATUS  mandatory
              DESCRIPTION
                     "Receive thorughput specified in bits/second
                      (including any overhead bits). This value is
                      defined for communication adapters only and
                      calculated for each pyhsical line. If a
                      physical line is using multiple virtual lines,
                      this value accounts for all the virtual lines"
              ::= { ctPerformanceEntry 10 }

          ctPerfTotalThroughput OBJECT-TYPE
              SYNTAX  INTEGER
              ACCESS  read-only
              STATUS  mandatory
              DESCRIPTION
                     "Total thorughput specified in uncompressed
                      bytes/second. This value is defined for
                      adapters, emulators, compression boards,
                      and for each device assigned to a particular
                      adapter or emulator"
              ::= { ctPerformanceEntry 11 }

          ctPerfPeakTxThroughput OBJECT-TYPE
              SYNTAX  INTEGER
              ACCESS  read-only
              STATUS  mandatory
              DESCRIPTION
                     "Peak Transmit thorughput specified in
                      bits/second (including any overhead bits).

                      This value is defined for communication
                      adapters only and calculated for each pyhsical
                      line. If a physical line is using multiple
                      virtual lines, this value accounts for all the
                      virtual lines.

                      ctPerfPeakThroughputStartTime and
                      ctPerfPeakTxThrouthputTime identify
                      start time of the data sampling and the actual
                      the time when the peak value was noted.

                      User can reset the current peak value and start
                      new data collection by using the
                      ctPerfResetPeakThroughput mib object"
              ::= { ctPerformanceEntry 12 }

          ctPerfPeakTxThroughputTime OBJECT-TYPE
              SYNTAX  DisplayString (SIZE( 1..80))
              ACCESS  read-only
              STATUS  mandatory
              DESCRIPTION
                     "Time stamp when the peak  transmit
                      throuput value was noted. Time is specified
                      in the local time zone"
              ::= { ctPerformanceEntry 13 }

          ctPerfPeakRxThroughput OBJECT-TYPE
              SYNTAX  INTEGER
              ACCESS  read-only
              STATUS  mandatory
              DESCRIPTION
                     "Peak receive thorughput specified in
                      bits/second (including any overhead bits).

                      This value is defined for communication
                      adapters only and calculated for each pyhsical
                      line. If a physical line is using multiple
                      virtual lines, this value accounts for all the
                      virtual lines.

                      ctPerfPeakThroughputStartTime and
                      ctPerfPeakRxThrouthputTime identify
                      start time of the data sampling and the actual
                      the time when the peak value was noted.

                      User can reset the current peak value and start
                      new data collection by using the
                      ctPerfResetPeakThroughput mib object"
              ::= { ctPerformanceEntry 14 }

          ctPerfPeakRxThroughputTime OBJECT-TYPE
              SYNTAX  DisplayString (SIZE( 1..80))
              ACCESS  read-only
              STATUS  mandatory
              DESCRIPTION
                     "Time stamp when the peak  receive
                      throuput value was noted. Time is specified
                      in the local time zone"
              ::= { ctPerformanceEntry 15 }

          ctPerfPeakTotalThroughput OBJECT-TYPE
              SYNTAX  INTEGER
              ACCESS  read-only
              STATUS  mandatory
              DESCRIPTION
                     "Peak total thorughput specified in
                      uncompressed bytes/second.

                      This value is defined for adapters, emulators,
                      compression board and for all the devices
                      assigned to each adaptor or emulator.

                      ctPerfPeakThroughputStartTime and
                      ctPerfPeakTotalThrouthputTime identify
                      start time of the data sampling and the actual
                      the time when the peak value was noted.

                      User can reset the current peak value and start
                      new data collection by using the
                      ctPerfResetPeakThroughput mib object"
              ::= { ctPerformanceEntry 16 }

          ctPerfPeakTotalThroughputTime OBJECT-TYPE
              SYNTAX  DisplayString (SIZE( 1..80))
              ACCESS  read-only
              STATUS  mandatory
              DESCRIPTION
                     "Time stamp when the peak  total
                      throughput value was noted. Time is specified
                      in the local time zone."
              ::= { ctPerformanceEntry 17 }

          ctPerfPeakThroughputStartTime OBJECT-TYPE
              SYNTAX  DisplayString (SIZE( 1..80))
              ACCESS  read-only
              STATUS  mandatory
              DESCRIPTION
                     "Time stamp when the data sampling was started
                      for determining peak values. Time is specified
                      in the local time zone.

                      Whenever user resets the peak values by setting
                      the ctPerfResetPeakThroughput, this
                      object will be updated with the current system
                      time"
              ::= { ctPerformanceEntry 18 }

          ctPerfResetPeakThroughput OBJECT-TYPE
              SYNTAX  INTEGER { reset (1) }
              ACCESS  read-write
              STATUS  mandatory
              DESCRIPTION
                     "Use this object to reset the peak throughput
                      values (Tx, Rx and Total) associated with
                      this conceptual row. This will start a new
                      data collection and new peak values will be
                      computed. Modifying this object will also reset
                      the ctPerfPeakThroughputStartTime to the
                      current system time"
              ::= { ctPerformanceEntry 19 }

          ctPerfTxUtilization OBJECT-TYPE
              SYNTAX  INTEGER
              ACCESS  read-only
              STATUS  mandatory
              DESCRIPTION
                     "This value is defined only for the
                      communication adapters and computed for each
                      physical line. This value is expressed as the
                      transmit bits/second as a percentage of the line
                      data rate. This value can be between 0 and 100
                      inclusive"
              ::= { ctPerformanceEntry 20 }

          ctPerfRxUtilization OBJECT-TYPE
              SYNTAX  INTEGER
              ACCESS  read-only
              STATUS  mandatory
              DESCRIPTION
                     "This value is defined only for the
                      communication adapters and computed for each
                      physical line. This value is expressed as the
                      receive bits/second as a percentage of the line
                      data rate. This value can be between 0 and 100
                      inclusive"
              ::= { ctPerformanceEntry 21 }

          ctPerfCPUUtilization OBJECT-TYPE
              SYNTAX  INTEGER
              ACCESS  read-only
              STATUS  mandatory
              DESCRIPTION
                     "This value is defined only for adapters,
                      emulators, compression board and
                      mother board.

                      This value represents the extent the CPU
                      on the specified board is busy servicing
                      all of the hardware and software components
                      installed in the system.

                      This value can be between 0 and 100
                      inclusive"
              ::= { ctPerformanceEntry 22 }

          ctPerfDataRate OBJECT-TYPE
              SYNTAX  INTEGER
              ACCESS  read-only
              STATUS  mandatory
              DESCRIPTION
                     "The data rate associated with the communication
                      line and is expressed in bits/second.

                      For SDLC lines, although both Tx and Rx data
                      rates are available, only Tx clock will be used
                      to represent the data rate.

                      For ATM and LAN cards, the data rate values
                      specified in the PARAMTAB.DAT will be provided"
              ::= { ctPerformanceEntry 23 }

          ctPerfReceiveErrorCount OBJECT-TYPE
              SYNTAX  INTEGER
              ACCESS  read-only
              STATUS  mandatory
              DESCRIPTION
                     "This value is defined only for communication
                      adapters and shown as the number of errors
                      received over the sampling interval(default
                      =60 secs). Ideally this value will be
                      calculated using a rolling 60 second window
                      to allow errors to be displayed as they occur"
              ::= { ctPerformanceEntry 24 }

         ctPerfReceiveErrorCountStartTime OBJECT-TYPE
              SYNTAX  DisplayString (SIZE(1..80))
              ACCESS  read-only
              STATUS  mandatory
              DESCRIPTION
                     "This is the system time when the last reset
                      Receive Errors command was received"
              ::= { ctPerformanceEntry 25 }

        ctPerfResetReceiveErrorCount OBJECT-TYPE
              SYNTAX  INTEGER { reset (1) }
              ACCESS  read-write
              STATUS  mandatory
              DESCRIPTION
                     "This variable is used to reset the Receive
                      Erors associated with this conceptual row.
                      Resetting will start a new data collection.
                      This will also set the
                      ctPerfReceiveErrorCountStartTime to current
                      time."
              ::= { ctPerformanceEntry 26 }

          ctPerfCommLineDelay OBJECT-TYPE
              SYNTAX  INTEGER
              ACCESS  read-only
              STATUS  mandatory
              DESCRIPTION
                     "Communication line delay expressed in milli
                      seconds. Valid only for Comm. adapters"
              ::= { ctPerformanceEntry 27 }

          ctPerfCompressionRatio OBJECT-TYPE
              SYNTAX  INTEGER
              ACCESS  read-only
              STATUS  mandatory
              DESCRIPTION
                     "Compression ratio is defined for the
                      compression board, for each channel adapter,
                      and emulator and for each device assigned to
                      the adapter and emulator.

                      This is a cumulative value calculated from the
                      time when the customer sends a reset
                      compression ratio using the ctPerfResetCompre
                      -ssionRatio object."
              ::= { ctPerformanceEntry 28 }

         ctPerfCompressionRatioStartTime OBJECT-TYPE
              SYNTAX  DisplayString (SIZE(1..80))
              ACCESS  read-only
              STATUS  mandatory
              DESCRIPTION
                     "This is the system time when the last reset
                      compression ration command was received"
              ::= { ctPerformanceEntry 29 }

        ctPerfResetCompressionRatio OBJECT-TYPE
              SYNTAX  INTEGER { reset (1) }
              ACCESS  read-write
              STATUS  mandatory
              DESCRIPTION
                     "This variable is used to reset the compression
                      ratio associated with this conceptual row"
              ::= { ctPerformanceEntry 30 }

        ctPerfDeviceTxUncompressedCounts OBJECT-TYPE
              SYNTAX  INTEGER
              ACCESS  read-only
              STATUS  mandatory
              DESCRIPTION
                     "This is the transmit uncompressed byte count for a device

                      Note: When ctPerfShowFractions is OFF this value is
                            expressed in kilobytes"
              ::= { ctPerformanceEntry 31 }

        ctPerfDeviceTxCompressedCounts OBJECT-TYPE
              SYNTAX  INTEGER
              ACCESS  read-only
              STATUS  mandatory
              DESCRIPTION
                     "This is the transmit compressed byte count for a device

                      Note: When ctPerfShowFractions is OFF this value is
                            expressed in kilobytes"

              ::= { ctPerformanceEntry 32 }

        ctPerfDeviceRxUncompressedCounts OBJECT-TYPE
              SYNTAX  INTEGER
              ACCESS  read-only
              STATUS  mandatory
              DESCRIPTION
                     "This is the receive uncompressed byte count for a device

                      Note: When ctPerfShowFractions is OFF this value is
                            expressed in kilobytes"
              ::= { ctPerformanceEntry 33 }

        ctPerfDeviceRxCompressedCounts OBJECT-TYPE
              SYNTAX  INTEGER
              ACCESS  read-only
              STATUS  mandatory
              DESCRIPTION
                     "This is the receive compressed byte count for a device

                      Note: When ctPerfShowFractions is OFF this value is
                            expressed in kilobytes"
              ::= { ctPerformanceEntry 34 }

        ctPerfDeviceCountsStartTime OBJECT-TYPE
              SYNTAX  DisplayString (SIZE(1..80))
              ACCESS  read-only
              STATUS  mandatory
              DESCRIPTION
                     "This is the system time when the last reset
                      device counts command was received"
              ::= { ctPerformanceEntry 35 }

        ctPerfResetDeviceCounts OBJECT-TYPE
              SYNTAX  INTEGER { reset (1) }
              ACCESS  read-write
              STATUS  mandatory
              DESCRIPTION
                     "This variable is used to reset the transmit, receive,
                      compressed and uncompressed counts for a device"
              ::= { ctPerformanceEntry 36 }

          ctPerfTxDeviceCompressionRatio OBJECT-TYPE
              SYNTAX  INTEGER
              ACCESS  read-only
              STATUS  mandatory
              DESCRIPTION
                     "This is the transmit compression ratio for a device"
              ::= { ctPerformanceEntry 37 }

          ctPerfRxDeviceCompressionRatio OBJECT-TYPE
              SYNTAX  INTEGER
              ACCESS  read-only
              STATUS  mandatory
              DESCRIPTION
                     "This is the receive compression ratio for a device"
              ::= { ctPerformanceEntry 38 }

        ctPerfResetAllDeviceCounts OBJECT-TYPE
              SYNTAX  INTEGER { reset (1) }
              ACCESS  read-write
              STATUS  mandatory
              DESCRIPTION
                     "This variable is used to reset the transmit, receive,
                      compressed and uncompressed byte counts of all devices
                      back to zero"
              ::= { ctPerformance 7 }

        --
        -- ctDiagnosticsTable
        -- Provides the results of the EXEC diagnostics phase
        -- information.
        --

        ctDiagnosticsTable OBJECT-TYPE
           SYNTAX   SEQUENCE OF ctDiagnosticsEntry
           ACCESS   not-accessible
           STATUS   mandatory
           DESCRIPTION
                 "Diagnostics information for the Channel Extenders"
           ::= { ctDiagnostics 1 }

        ctDiagnosticsEntry OBJECT-TYPE
              SYNTAX  ctDiagnosticsEntry
              ACCESS  not-accessible
              STATUS  mandatory
              DESCRIPTION
                  "Diagnostics information for each hardware module
                   of the Channel Extender."
              INDEX { ctDiagSlotIndex, ctDiagBoardIndex,
                      ctDiagPortIndex, ctDiagDeviceIndex }
              ::= { ctDiagnosticsTable 1 }

        ctDiagnosticsEntry ::=
              SEQUENCE {
                 ctDiagSlotIndex,
                       INTEGER,
                 ctDiagBoardIndex,
                       INTEGER,
                 ctDiagPortIndex,
                       INTEGER,
                 ctDiagDeviceIndex,
                       INTEGER,
                 ctDiagName
                       DisplayString,
                 ctDiagType
                       DisplayString,
                 ctDiagTestNumber
                       DisplayString,
                 ctDiagPassCount
                       DisplayString,
                 ctDiagStatus
                       DisplayString
              }

        ctDiagSlotIndex OBJECT-TYPE
           SYNTAX  INTEGER
           ACCESS  read-only
           STATUS  mandatory
           DESCRIPTION
                 "Slot index of the hardware module where the
                  diagnostics test is being performed"
           ::= { ctDiagnosticsEntry 1 }

        ctDiagBoardIndex OBJECT-TYPE
           SYNTAX  INTEGER
           ACCESS  read-only
           STATUS  mandatory
           DESCRIPTION
                 "Board index of the slot where the diagnostics
                  test is being performed."
           ::= { ctDiagnosticsEntry 2 }

        ctDiagPortIndex OBJECT-TYPE
           SYNTAX  INTEGER
           ACCESS  read-only
           STATUS  mandatory
           DESCRIPTION
                 "Port index of the board where the diagnostics test
                  is being performed."
           ::= { ctDiagnosticsEntry 3 }

        ctPerfDeviceIndex OBJECT-TYPE
           SYNTAX  INTEGER
           ACCESS  read-only
           STATUS  mandatory
           DESCRIPTION
                 "Externally connected devices index. This can be
                  potentially used for peripheral devices and OC3/DS3
                  converters"
           ::= { ctDiagnosticsEntry 4 }

        ctDiagName OBJECT-TYPE
           SYNTAX  DisplayString (SIZE(0..255))
           ACCESS  read-write
           STATUS  mandatory
           DESCRIPTION
                 "Same as the ctHwName object"
           ::= { ctDiagnosticsEntry 5 }

          ctDiagType OBJECT-TYPE
              SYNTAX  DisplayString (SIZE(1..80))
              ACCESS  read-only
              STATUS  mandatory
              DESCRIPTION
                     "Same as the ctHwType"
              ::= { ctDiagnosticsEntry 6 }

          ctDiagTestNumber OBJECT-TYPE
              SYNTAX  DisplayString (SIZE(1..80))
              ACCESS  read-only
              STATUS  mandatory
              DESCRIPTION
                    "Current Test Number"
              ::= { ctDiagnosticsEntry 7 }

          ctDiagPassCount OBJECT-TYPE
              SYNTAX  DisplayString (SIZE(1..80))
              ACCESS  read-only
              STATUS  mandatory
              DESCRIPTION
                     ""
              ::= { ctDiagnosticsEntry 8 }

          ctDiagStatus OBJECT-TYPE
              SYNTAX  DisplayString (SIZE(1..80))
              ACCESS  read-only
              STATUS  mandatory
              DESCRIPTION
                     "Same as the ctHwStatus"
              ::= { ctDiagnosticsEntry 9 }

        --
        -- ctPowerSupply Group
        --
        --

        ctPsA_Status OBJECT-TYPE
           SYNTAX  INTEGER {
                      AC-Failed,DC-Failed (0),
                      AC-Good,DC-Failed (1),
                      AC-Failed,DC-Good (2),
                      AC-Good,DC-Good (3)
                      N/A (5)
                   }
           ACCESS  read-only
           STATUS  mandatory
           DESCRIPTION
                 ""
           ::= { ctPowerSupply 1 }

        ctPsB_Status OBJECT-TYPE
           SYNTAX  INTEGER {
                      AC-Failed,DC-Failed (0),
                      AC-Good,DC-Failed (1),
                      AC-Failed,DC-Good (2),
                      AC-Good,DC-Good (3)
                      N/A (5)
                   }
           ACCESS  read-only
           STATUS  mandatory
           DESCRIPTION
                 ""
           ::= { ctPowerSupply 2 }

        ctPsAlertFlag OBJECT-TYPE
           SYNTAX  INTEGER
           ACCESS  read-only
           STATUS  mandatory
           DESCRIPTION
                 ""
           ::= { ctPowerSupply 3 }

        ctPsFirstFailTime OBJECT-TYPE
           SYNTAX  DisplayString (SIZE(1..80))
           ACCESS  read-only
           STATUS  mandatory
           DESCRIPTION
                 ""
           ::= { ctPowerSupply 4 }

        ctPsA_ACErrors OBJECT-TYPE
           SYNTAX  Counter
           ACCESS  read-only
           STATUS  mandatory
           DESCRIPTION
                 ""
           ::= { ctPowerSupply 5 }

        ctPsA_DCErrors OBJECT-TYPE
           SYNTAX  Counter
           ACCESS  read-only
           STATUS  mandatory
           DESCRIPTION
                 ""
           ::= { ctPowerSupply 6 }

        ctPsB_ACErrors OBJECT-TYPE
           SYNTAX  Counter
           ACCESS  read-only
           STATUS  mandatory
           DESCRIPTION
                 ""
           ::= { ctPowerSupply 7 }

        ctPsB_DCErrors OBJECT-TYPE
           SYNTAX  Counter
           ACCESS  read-only
           STATUS  mandatory
           DESCRIPTION
                 ""
           ::= { ctPowerSupply 8 }

        --
        -- ctTraps Group
        --
        -- This group has the variables that describe the Computerm
        -- Alerts. These objects can be used universally to define
        -- any trap.
        -- This group also maintains the history of aborts that occured
        -- on the system to avoid any aborts not reaching NMS (NMS down
        -- or other problems). History will be limited to the last 20.
        --

        ctAbortTable OBJECT-TYPE
           SYNTAX SEQUENCE OF ctAbortEntry
           ACCESS not-accessible
           STATUS mandatory
           DESCRIPTION
                 "Channel Extender Aborts History Table"
           ::= { ctTraps 1 }

        ctAbortEntry OBJECT-TYPE
           SYNTAX ctAbortEntry
           ACCESS not-accessible
           STATUS mandatory
           DESCRIPTION
                 "Channel Extender Aborts History Table Entry"
           INDEX  { ctAbortIndex }
           ::= { ctAbortTable 1 }

        ctAbortEntry ::=
           SEQUENCE {
               ctAbortIndex
                     INTEGER,
               ctAbortAlertTimeStamp
                     DisplayString,
               ctAbortAlertShortDescription
                     DisplayString,
               ctAbortAlertDescription
                     DisplayString
           }

        ctAbortIndex OBJECT-TYPE
           SYNTAX  INTEGER (1..65535)
           ACCESS  read-only
           STATUS  mandatory
           DESCRIPTION
                 "This index uniquely identifies an entry in the
                  Abort Table. Although the maximum number of entries
                  in the table is limited to some pre-determined value
                  (20 in phase I), ctAbortIndex can assume values in
                  the 1..65535 range"
           ::= { ctAbortEntry 1 }

        ctAbortAlertTimeStamp OBJECT-TYPE
           SYNTAX  DisplayString (SIZE(1..80))
           ACCESS  read-only
           STATUS  mandatory
           DESCRIPTION
                 "Trap occurence time expressed in local time zone"
           ::= { ctAbortEntry 2 }

        ctAbortAlertShortDescription OBJECT-TYPE
           SYNTAX  DisplayString (SIZE(0..255))
           ACCESS  read-only
           STATUS  mandatory
           DESCRIPTION
                 "Short Description of the abort or alert being described"
           ::= { ctAbortEntry 3 }

        ctAbortAlertDescription OBJECT-TYPE
           SYNTAX  DisplayString (SIZE(0..255))
           ACCESS  read-only
           STATUS  mandatory
           DESCRIPTION
                 "Full description of the abort or alert being described"
           ::= { ctAbortEntry 4 }
END

--
--
--

COMPUTERM-TRAP-MIB

--
-- Computerm Trap MIB
-- Author  : Raja Kolli
-- Created : 8/1/97
-- Revision: 1.0
-- Last Modified: 8/1/97
-- Last Modified By:
--
--
-- Copyright 1997 Computerm Corp. All Rights reserved. This Computerm
-- SNMP Management Information Base Specification embodies Computerm's
-- confidential and proprietary intellectual property. Computerm
-- retains all title and ownership in the Specification, including any
-- revisions.
--

-- This Specification is supplied "AS IS," and Computerm makes no
-- warranty, either express or implied, as to the use, operation,
-- condition, or performance of the specification.
--


DEFINITIONS ::= BEGIN

-- Section 1: Top Level Definitions

-- Imports

IMPORTS
    snmp                          FROM RFC1213-MIB
    TRAP-TYPE                     FROM RFC-1215
    computerm                     FROM COMPUTERM-COMMON-MIB;

-- Section 2: Generic Trap Definitions

-- Section 3: Computerm Enterprise Specific Definitions

   ctAbort  TRAP-TYPE
       ENTERPRISE  ctSystem
       VARIABLES   { ctAbortAlertShortDescription,
                     ctAbortAlertDescription}
       DESCRIPTION "Signifies that an abort has occured. Short and Long
                    descriptions provide further information. All the
                    Computerm aborts will be notified to the user using
                    this trap. This trap will be defined in the NMS
                    with a severity level of Critical."
       ::= 1

   ctAlert  TRAP-TYPE
       ENTERPRISE  ctSystem
       VARIABLES   { ctAbortAlertShortDescription,
                     ctAbortAlertDescription }
       DESCRIPTION "Signifies a Computerm alert e.g. ErrorRate or
                    Utilization values have exceeded the threshold
                    values. Short and Long descriptions provide
                    further information.

                    This trap will be defined in the NMS with a
                    severity of level of WARNING."
       ::= 2

   ctInformationalAbort  TRAP-TYPE
       ENTERPRISE  ctSystem
       VARIABLES   { ctAbortAlertShortDescription,
                     ctAbortAlertDescription}
       DESCRIPTION "Signifies that an informational abort has occured.
                    Short and Long descriptions provide further
                    information. All the Computerm aborts will be
                    divided into those that require user attention and
                    those that are informational to the user. This
                    will be used to notify the user that an
                    informational abort has occured. This trap will
                    be defined in the NMS with a severity level of
                    Informational.

                    This trap is not used in Phase I"
       ::= 3

   ctCxNormalMode TRAP-TYPE
       ENTERPRISE  ctSystem
       VARIABLES   { ctAbortAlertShortDescription,
                     ctAbortAlertDescription }
       DESCRIPTION "Used for normal mode traps.

                    This trap will be defined in the NMS with a
                    Normal Severity level."
       ::= 4

   ctCxDiagnosticsMode TRAP-TYPE
       ENTERPRISE  ctSystem
       VARIABLES   { ctAbortAlertShortDescription,
                     ctAbortAlertDescription }
       DESCRIPTION "Channel Extender is in diagnostics mode. This
                    trap will be used to distinguish between the
                    ONLINE and OFFLINE unit.

                    This trap will be defined in the NMS with a
                    Disabled Severity level.

                    When Traps are configured in the NMS, this trap
                    should be auto-acknoledged by
                    ctCxNormalChannelExtenderMode trap"
       ::= 5

   ctCxNormalChannelExtenderMode TRAP-TYPE
       ENTERPRISE  ctSystem
       VARIABLES   { ctAbortAlertShortDescription,
                     ctAbortAlertDescription }
       DESCRIPTION "Channel Extender is in Channel Extension mode
                    and operating in normal mode.

                    This trap will be defined in the NMS with a
                    Normal Severity level."
       ::= 6
END
