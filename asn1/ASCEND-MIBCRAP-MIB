--			Ascend mibcrap MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBCRAP-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibcrapProfile  OBJECT IDENTIFIER ::= { configuration 70}

	-- The mibcrapProfile table
	--
	-- This table contains parameters for the mibcrapProfile profile
	--

    mibcrapProfileTable	OBJECT-TYPE
	SYNTAX		SEQUENCE OF MibcrapProfileEntry
	ACCESS		not-accessible
	STATUS		mandatory
	DESCRIPTION	"A list of mibcrapProfile profile entries."
	::= { mibcrapProfile 1 }

    mibcrapProfileEntry	OBJECT-TYPE
	SYNTAX		MibcrapProfileEntry
	ACCESS		not-accessible
	STATUS		mandatory
	DESCRIPTION	"A mibcrapProfile entry containing objects that
			 maps to the parameters of mibcrapProfile profile."
	INDEX		{ crapProfile-Index-DeviceAddress-PhysicalAddress-Shelf, crapProfile-Index-DeviceAddress-PhysicalAddress-Slot, crapProfile-Index-DeviceAddress-PhysicalAddress-ItemNumber, crapProfile-Index-DeviceAddress-LogicalItem, crapProfile-Index-EntryNumber }
	::= { mibcrapProfileTable 1 }

    MibcrapProfileEntry ::=
	SEQUENCE {
	    crapProfile-Index-DeviceAddress-PhysicalAddress-Shelf
		INTEGER,
	    crapProfile-Index-DeviceAddress-PhysicalAddress-Slot
		INTEGER,
	    crapProfile-Index-DeviceAddress-PhysicalAddress-ItemNumber
		INTEGER,
	    crapProfile-Index-DeviceAddress-LogicalItem
		INTEGER,
	    crapProfile-Index-EntryNumber
		INTEGER,
	    crapProfile-TrunkGroup
		INTEGER,
	    crapProfile-PhoneNumber
		DisplayString,
	    crapProfile-PreferredSource-PhysicalAddress-Shelf
		INTEGER,
	    crapProfile-PreferredSource-PhysicalAddress-Slot
		INTEGER,
	    crapProfile-PreferredSource-PhysicalAddress-ItemNumber
		INTEGER,
	    crapProfile-PreferredSource-LogicalItem
		INTEGER,
	    crapProfile-CallRouteType
		INTEGER,
	    crapProfile-LcdIndex
		INTEGER,
	    crapProfile-Name
		DisplayString,
	    crapProfile-Active
		INTEGER,
	    crapProfile-SrcChannelGroup
		INTEGER,
	    crapProfile-ChannelGroup
		INTEGER,
	    crapProfile-DialPlan
		INTEGER,
	    crapProfile-RewritePattern
		DisplayString,
	    crapProfile-RewriteReplacement
		DisplayString,
	    crapProfile-RemoteVoipgw
		IpAddress,
	    crapProfile-Cost
		INTEGER,
	    crapProfile-Action-o
		INTEGER
	}

    crapProfile-Index-DeviceAddress-PhysicalAddress-Shelf	OBJECT-TYPE
	SYNTAX	INTEGER
	ACCESS	read-only
	STATUS	mandatory
	DESCRIPTION	"The number of the shelf that the addressed physical device resides on."
	::= { mibcrapProfileEntry 1 }

    crapProfile-Index-DeviceAddress-PhysicalAddress-Slot	OBJECT-TYPE
	SYNTAX	INTEGER
	ACCESS	read-only
	STATUS	mandatory
	DESCRIPTION	"The number of the slot that the addressed physical device resides on."
	::= { mibcrapProfileEntry 2 }

    crapProfile-Index-DeviceAddress-PhysicalAddress-ItemNumber	OBJECT-TYPE
	SYNTAX	INTEGER
	ACCESS	read-only
	STATUS	mandatory
	DESCRIPTION	"A number that specifies an addressable entity within the context of shelf and slot."
	::= { mibcrapProfileEntry 3 }

    crapProfile-Index-DeviceAddress-LogicalItem	OBJECT-TYPE
	SYNTAX	INTEGER
	ACCESS	read-only
	STATUS	mandatory
	DESCRIPTION	"A number that specifies an addressable logical entity within the context of a physical address."
	::= { mibcrapProfileEntry 4 }

    crapProfile-Index-EntryNumber	OBJECT-TYPE
	SYNTAX	INTEGER
	ACCESS	read-only
	STATUS	mandatory
	DESCRIPTION	"An identifying number. There may be many profile entries for a given device-address. This number is used to discriminate the various entries."
	::= { mibcrapProfileEntry 5 }

    crapProfile-TrunkGroup	OBJECT-TYPE
	SYNTAX	INTEGER
	ACCESS	read-write
	STATUS	mandatory
	DESCRIPTION	"The trunk group, if any, associated with this device. Calls that originate on a line assigned to a trunk group will be routed to devices assigned to the same trunk group, if available."
	::= { mibcrapProfileEntry 6 }

    crapProfile-PhoneNumber	OBJECT-TYPE
	SYNTAX	DisplayString
	ACCESS	read-write
	STATUS	mandatory
	DESCRIPTION	"The phone number of the indexed device. Incoming calls to this phone number may be routed to the device. Multiple devices may have the same phone number. The phone number may contain a sub-address, e.g. (xxx) yyy-zzzz,s."
	::= { mibcrapProfileEntry 7 }

    crapProfile-PreferredSource-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibcrapProfileEntry 8 }

    crapProfile-PreferredSource-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibcrapProfileEntry 9 }

    crapProfile-PreferredSource-PhysicalAddress-ItemNumber	OBJECT-TYPE
	SYNTAX	INTEGER
	ACCESS	read-write
	STATUS	mandatory
	DESCRIPTION	"A number that specifies an addressable entity within the context of shelf and slot."
	::= { mibcrapProfileEntry 10 }

    crapProfile-PreferredSource-LogicalItem	OBJECT-TYPE
	SYNTAX	INTEGER
	ACCESS	read-write
	STATUS	mandatory
	DESCRIPTION	"A number that specifies an addressable logical entity within the context of a physical address."
	::= { mibcrapProfileEntry 11 }

    crapProfile-CallRouteType	OBJECT-TYPE
	SYNTAX	INTEGER {
		    anyCallType (1),
		    voiceCallType (2),
		    digitalCallType (3),
		    trunkCallType (4),
		    phsCallType (5),
		    voipCallType (6),
		    v110CallType (7),
		    trunkVoiceCallType (8),
		    trunkDigitalCallType (9),
		    wormarqCallType (10),
		    mtpLinkType (11),
		    iptoipVoipCallType (12),
		    rtfaxCallType (13),
		    g729CallType (14),
		    g728CallType (15),
		    g723CallType (16),
		    frgsmCallType (17),
		    rt24CallType (18)
		}
	ACCESS	read-write
	STATUS	mandatory
	DESCRIPTION	"The type of call that should be routed to the indexed device."
	::= { mibcrapProfileEntry 12 }

    crapProfile-LcdIndex	OBJECT-TYPE
	SYNTAX	INTEGER
	ACCESS	read-write
	STATUS	mandatory
	DESCRIPTION	"Index for this profile instance. Only used in lcd screens."
	::= { mibcrapProfileEntry 13 }

    crapProfile-Name	OBJECT-TYPE
	SYNTAX	DisplayString
	ACCESS	read-write
	STATUS	mandatory
	DESCRIPTION	"User-meaningful name for lcd menu display only."
	::= { mibcrapProfileEntry 14 }

    crapProfile-Active	OBJECT-TYPE
	SYNTAX	INTEGER {
		    false (1),
		    true (2)
		}
	ACCESS	read-write
	STATUS	mandatory
	DESCRIPTION	"Profile is only used if active."
	::= { mibcrapProfileEntry 15 }

    crapProfile-SrcChannelGroup	OBJECT-TYPE
	SYNTAX	INTEGER
	ACCESS	read-write
	STATUS	mandatory
	DESCRIPTION	"If non-zero, the call must come in on this channel group to match."
	::= { mibcrapProfileEntry 16 }

    crapProfile-ChannelGroup	OBJECT-TYPE
	SYNTAX	INTEGER
	ACCESS	read-write
	STATUS	mandatory
	DESCRIPTION	"If non-zero, route matching call to this channel group"
	::= { mibcrapProfileEntry 17 }

    crapProfile-DialPlan	OBJECT-TYPE
	SYNTAX	INTEGER
	ACCESS	read-write
	STATUS	mandatory
	DESCRIPTION	"If non-zero, use this dial plan number for ISDN call setup parameters."
	::= { mibcrapProfileEntry 18 }

    crapProfile-RewritePattern	OBJECT-TYPE
	SYNTAX	DisplayString
	ACCESS	read-write
	STATUS	mandatory
	DESCRIPTION	"Pattern for replacement in actual phone number."
	::= { mibcrapProfileEntry 19 }

    crapProfile-RewriteReplacement	OBJECT-TYPE
	SYNTAX	DisplayString
	ACCESS	read-write
	STATUS	mandatory
	DESCRIPTION	"Replacement for pattern in actual phone number."
	::= { mibcrapProfileEntry 20 }

    crapProfile-RemoteVoipgw	OBJECT-TYPE
	SYNTAX	IpAddress
	ACCESS	read-write
	STATUS	mandatory
	DESCRIPTION	"IP address of remote VoIP gateway to terminate this call."
	::= { mibcrapProfileEntry 21 }

    crapProfile-Cost	OBJECT-TYPE
	SYNTAX	INTEGER
	ACCESS	read-write
	STATUS	mandatory
	DESCRIPTION	"Calls will be routed to lower cost routes first"
	::= { mibcrapProfileEntry 23 }

    crapProfile-Action-o	OBJECT-TYPE
	SYNTAX	INTEGER {
		    noAction (1),
		    createProfile (2),
		    deleteProfile (3)
		}
	ACCESS	read-write
	STATUS	mandatory
	DESCRIPTION	""
	::= { mibcrapProfileEntry 22 }

END
