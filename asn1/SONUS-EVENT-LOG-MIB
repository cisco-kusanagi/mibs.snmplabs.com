--
-- This SMIv2 module has been generated by smidump 0.2-cvs. Do not edit.
--

SONUS-EVENT-LOG-MIB DEFINITIONS ::= BEGIN

IMPORTS
    Integer32, MODULE-IDENTITY, NOTIFICATION-TYPE, OBJECT-TYPE
        FROM SNMPv2-SMI
    DisplayString
        FROM SNMPv2-TC
    sonusEventClass, sonusEventDescription, sonusEventLevel, 
    sonusShelfIndex
        FROM SONUS-COMMON-MIB
    sonusSystemMIBs
        FROM SONUS-SMI
    SonusEventClass, SonusEventFilterLevel, SonusEventString, 
    SonusShelfIndex, SonusSlotIndex
        FROM SONUS-TC;

sonusEventLogMIB MODULE-IDENTITY
    LAST-UPDATED    "200107310000Z"
    ORGANIZATION    
            "Sonus Networks, Inc."
    CONTACT-INFO    
            "   Customer Support    
             Sonus Networks, Inc,
             5 carlisle Road
             Westford, MA 01886
             USA
             
             Tel: 978-692-8999
             Fax: 978-392-9118
             E-mail: cs.snmp@sonusnet.com"
    DESCRIPTION     
            "The MIB Module for Event Log Management."
    ::= { sonusSystemMIBs 2 }


sonusEventLogMIBObjects OBJECT IDENTIFIER
    ::= { sonusEventLogMIB 1 }

sonusEvLogTypeTable OBJECT-TYPE
    SYNTAX          SEQUENCE OF SonusEvLogTypeEntry
    MAX-ACCESS      not-accessible
    STATUS          current
    DESCRIPTION     
            "Event Log configuration table for configuration items
             related to each Event Log type."
    ::= { sonusEventLogMIBObjects 1 }

sonusEvLogTypeEntry OBJECT-TYPE
    SYNTAX          SonusEvLogTypeEntry
    MAX-ACCESS      not-accessible
    STATUS          current
    DESCRIPTION     
            "An entry of Event Log configuration related to each
             event log type."
    INDEX           { sonusEvLogType }
    ::= { sonusEvLogTypeTable 1 }

SonusEvLogTypeEntry ::=
    SEQUENCE {
        sonusEvLogType                  INTEGER,
        sonusEvLogTypeAdminState        INTEGER,
        sonusEvLogTypeFileCount         Integer32,
        sonusEvLogTypeFileSize          Integer32,
        sonusEvLogTypeFileMsgQueue      Integer32,
        sonusEvLogTypeBaseDirectory     DisplayString,
        sonusEvLogTypeSaveTo            INTEGER,
        sonusEvLogTypeMaxEventMemSize   Integer32,
        sonusEvLogTypeFilterLevel       SonusEventFilterLevel
    }

sonusEvLogType OBJECT-TYPE
    SYNTAX          INTEGER { system(1), debug(2), trace(3), acct(4) }
    MAX-ACCESS      read-only
    STATUS          current
    DESCRIPTION     
            "The type of the event log.  Each type has separate
             configuration parameters and logs to a separate file."
    ::= { sonusEvLogTypeEntry 1 }

sonusEvLogTypeAdminState OBJECT-TYPE
    SYNTAX          INTEGER { disabled(1), enabled(2), rollfile(3) }
    MAX-ACCESS      read-write
    STATUS          current
    DESCRIPTION     
            "The requested state of the given Event Log type.  Rollfile
             will close an enabled log file and reopen, incrementing the
             suffix.  If a file is disabled and rolled, the command is
             ignored."
    DEFVAL          { enabled }
    ::= { sonusEvLogTypeEntry 2 }

sonusEvLogTypeFileCount OBJECT-TYPE
    SYNTAX          Integer32 (1..1000)
    MAX-ACCESS      read-write
    STATUS          current
    DESCRIPTION     
            "The number of event log files that will be maintained
             for this event type.  All event types except accounting
             will overwrite the oldest file when the file count is
             exceeded.  Accounting will issue warnings as the file
             count approaches the maximum and shutdown if it is exceeded."
    DEFVAL          { 32 }
    ::= { sonusEvLogTypeEntry 3 }

sonusEvLogTypeFileSize OBJECT-TYPE
    SYNTAX          Integer32 (256..65535)
    MAX-ACCESS      read-write
    STATUS          current
    DESCRIPTION     
            "The maximum size (in KB) that a single event log
             file will ever grow to."
    DEFVAL          { 2048 }
    ::= { sonusEvLogTypeEntry 4 }

sonusEvLogTypeFileMsgQueue OBJECT-TYPE
    SYNTAX          Integer32 (2..32)
    MAX-ACCESS      read-write
    STATUS          current
    DESCRIPTION     
            "The number of event log message entries to buffer
             before writing them to disk.
             
             The size may be a value between 2 and 32 (inclusive)."
    DEFVAL          { 10 }
    ::= { sonusEvLogTypeEntry 5 }

sonusEvLogTypeBaseDirectory OBJECT-TYPE
    SYNTAX          DisplayString
    MAX-ACCESS      read-only
    STATUS          current
    DESCRIPTION     
            "The directory in which to place the event log files.
             Each event log type has its own base directory"
    ::= { sonusEvLogTypeEntry 6 }

sonusEvLogTypeSaveTo OBJECT-TYPE
    SYNTAX          INTEGER { none(0), disk(1), memory(2), both(3) }
    MAX-ACCESS      read-write
    STATUS          current
    DESCRIPTION     
            "Save events to memory, disk, both, or neither."
    DEFVAL          { both }
    ::= { sonusEvLogTypeEntry 7 }

sonusEvLogTypeMaxEventMemSize OBJECT-TYPE
    SYNTAX          Integer32 (1..64)
    MAX-ACCESS      read-write
    STATUS          current
    DESCRIPTION     
            "The maximum size of the memory event log buffer
             (in KB)."
    DEFVAL          { 16 }
    ::= { sonusEvLogTypeEntry 8 }

sonusEvLogTypeFilterLevel OBJECT-TYPE
    SYNTAX          SonusEventFilterLevel
    MAX-ACCESS      read-write
    STATUS          current
    DESCRIPTION     
            "Events that are at least as severe as the designated
             level will be logged. noevents suppresses all events
             of this type from being logged."
    DEFVAL          { major }
    ::= { sonusEvLogTypeEntry 9 }

sonusEvLogTypeStatusTable OBJECT-TYPE
    SYNTAX          SEQUENCE OF SonusEvLogTypeStatusEntry
    MAX-ACCESS      not-accessible
    STATUS          current
    DESCRIPTION     
            "Event Log status table for status items
             related to each Event Log type."
    ::= { sonusEventLogMIBObjects 2 }

sonusEvLogTypeStatusEntry OBJECT-TYPE
    SYNTAX          SonusEvLogTypeStatusEntry
    MAX-ACCESS      not-accessible
    STATUS          current
    DESCRIPTION     
            "An entry of Event Log status related to each
             event log type."
    INDEX           { sonusEvLogTypeStatusShelf, 
                      sonusEvLogTypeStatusType }
    ::= { sonusEvLogTypeStatusTable 1 }

SonusEvLogTypeStatusEntry ::=
    SEQUENCE {
        sonusEvLogTypeStatusShelf       Integer32,
        sonusEvLogTypeStatusType        INTEGER,
        sonusEvLogTypeStatusCurrentFile DisplayString,
        sonusEvLogTypeStatusFileRecs    Integer32,
        sonusEvLogTypeStatusFileBytes   Integer32,
        sonusEvLogTypeStatusMemRecs     Integer32,
        sonusEvLogTypeStatusMemBytes    Integer32,
        sonusEvLogTypeStatusFileDropped Integer32,
        sonusEvLogTypeStatusMemDropped  Integer32
    }

sonusEvLogTypeStatusShelf OBJECT-TYPE
    SYNTAX          Integer32
    MAX-ACCESS      read-only
    STATUS          current
    DESCRIPTION     
            "The shelf number for which these table entries
             apply."
    ::= { sonusEvLogTypeStatusEntry 1 }

sonusEvLogTypeStatusType OBJECT-TYPE
    SYNTAX          INTEGER { system(1), debug(2), trace(3), acct(4) }
    MAX-ACCESS      read-only
    STATUS          current
    DESCRIPTION     
            "The type of the event log.  Each type has separate
             configuration parameters and logs to a separate file."
    ::= { sonusEvLogTypeStatusEntry 2 }

sonusEvLogTypeStatusCurrentFile OBJECT-TYPE
    SYNTAX          DisplayString
    MAX-ACCESS      read-only
    STATUS          current
    DESCRIPTION     
            "The filename that is currently being used for logging.
             No name is displayed when disk logging is disabled. The
             name RECOVERING is displayed when an attempt to automatically
             restart disk logging is in progress."
    ::= { sonusEvLogTypeStatusEntry 3 }

sonusEvLogTypeStatusFileRecs OBJECT-TYPE
    SYNTAX          Integer32
    MAX-ACCESS      read-only
    STATUS          current
    DESCRIPTION     
            "Count of the number of event records written to
             the current event log file."
    ::= { sonusEvLogTypeStatusEntry 4 }

sonusEvLogTypeStatusFileBytes OBJECT-TYPE
    SYNTAX          Integer32
    MAX-ACCESS      read-only
    STATUS          current
    DESCRIPTION     
            "Count of the number of bytes written to
             the current event log file."
    ::= { sonusEvLogTypeStatusEntry 5 }

sonusEvLogTypeStatusMemRecs OBJECT-TYPE
    SYNTAX          Integer32
    MAX-ACCESS      read-only
    STATUS          current
    DESCRIPTION     
            "Count of the number of event records written to
             the event log memory buffer."
    ::= { sonusEvLogTypeStatusEntry 6 }

sonusEvLogTypeStatusMemBytes OBJECT-TYPE
    SYNTAX          Integer32
    MAX-ACCESS      read-only
    STATUS          current
    DESCRIPTION     
            "Count of the number of bytes written to
             the event log memory buffer."
    ::= { sonusEvLogTypeStatusEntry 7 }

sonusEvLogTypeStatusFileDropped OBJECT-TYPE
    SYNTAX          Integer32
    MAX-ACCESS      read-only
    STATUS          current
    DESCRIPTION     
            "Count of the number of event records dropped when writing
             to an Event Log file."
    ::= { sonusEvLogTypeStatusEntry 8 }

sonusEvLogTypeStatusMemDropped OBJECT-TYPE
    SYNTAX          Integer32
    MAX-ACCESS      read-only
    STATUS          current
    DESCRIPTION     
            "Count of the number of event records dropped when writing
             to an Event Log memory buffer."
    ::= { sonusEvLogTypeStatusEntry 9 }

sonusEvLogMemTable OBJECT-TYPE
    SYNTAX          SEQUENCE OF SonusEvLogMemEntry
    MAX-ACCESS      not-accessible
    STATUS          current
    DESCRIPTION     
            "Events logged to memory."
    ::= { sonusEventLogMIBObjects 3 }

sonusEvLogMemEntry OBJECT-TYPE
    SYNTAX          SonusEvLogMemEntry
    MAX-ACCESS      not-accessible
    STATUS          current
    DESCRIPTION     
            "An entry of the Event Log memory table."
    INDEX           { sonusEvLogMemShelf, sonusEvLogMemType, 
                      sonusEvLogMemIndex }
    ::= { sonusEvLogMemTable 1 }

SonusEvLogMemEntry ::=
    SEQUENCE {
        sonusEvLogMemShelf              Integer32,
        sonusEvLogMemType               INTEGER,
        sonusEvLogMemIndex              Integer32,
        sonusEvLogMemText               SonusEventString
    }

sonusEvLogMemShelf OBJECT-TYPE
    SYNTAX          Integer32
    MAX-ACCESS      read-only
    STATUS          current
    DESCRIPTION     
            "The shelf number for which these table entries
             apply."
    ::= { sonusEvLogMemEntry 1 }

sonusEvLogMemType OBJECT-TYPE
    SYNTAX          INTEGER { system(1), debug(2), trace(3), acct(4) }
    MAX-ACCESS      read-only
    STATUS          current
    DESCRIPTION     
            "The Event Log Type to which these table entries
             apply."
    ::= { sonusEvLogMemEntry 2 }

sonusEvLogMemIndex OBJECT-TYPE
    SYNTAX          Integer32
    MAX-ACCESS      read-only
    STATUS          current
    DESCRIPTION     
            "The index for the entry."
    ::= { sonusEvLogMemEntry 3 }

sonusEvLogMemText OBJECT-TYPE
    SYNTAX          SonusEventString
    MAX-ACCESS      read-only
    STATUS          current
    DESCRIPTION     
            "The event log text."
    ::= { sonusEvLogMemEntry 4 }

sonusEvLogFilterTable OBJECT-TYPE
    SYNTAX          SEQUENCE OF SonusEvLogFilterEntry
    MAX-ACCESS      not-accessible
    STATUS          current
    DESCRIPTION     
            "Event Log Class Filter configuration table per card."
    ::= { sonusEventLogMIBObjects 6 }

sonusEvLogFilterEntry OBJECT-TYPE
    SYNTAX          SonusEvLogFilterEntry
    MAX-ACCESS      not-accessible
    STATUS          current
    DESCRIPTION     
            "An entry of Event Log Class Filter configuration per card."
    INDEX           { sonusEvLogFilterShelf, sonusEvLogFilterSlot, 
                      sonusEvLogFilterType, sonusEvLogFilterEventClass }
    ::= { sonusEvLogFilterTable 1 }

SonusEvLogFilterEntry ::=
    SEQUENCE {
        sonusEvLogFilterShelf           SonusShelfIndex,
        sonusEvLogFilterSlot            SonusSlotIndex,
        sonusEvLogFilterType            INTEGER,
        sonusEvLogFilterEventClass      SonusEventClass,
        sonusEvLogFilterLevel           SonusEventFilterLevel,
        sonusEvLogFilterState           INTEGER
    }

sonusEvLogFilterShelf OBJECT-TYPE
    SYNTAX          SonusShelfIndex
    MAX-ACCESS      read-write
    STATUS          current
    DESCRIPTION     
            "The shelf number for which these table entries
             apply."
    ::= { sonusEvLogFilterEntry 1 }

sonusEvLogFilterSlot OBJECT-TYPE
    SYNTAX          SonusSlotIndex
    MAX-ACCESS      read-write
    STATUS          current
    DESCRIPTION     
            "The slot number for which these table entries
             apply."
    ::= { sonusEvLogFilterEntry 2 }

sonusEvLogFilterType OBJECT-TYPE
    SYNTAX          INTEGER { system(1), debug(2), trace(3) }
    MAX-ACCESS      read-write
    STATUS          current
    DESCRIPTION     
            "The event log type for which these filter table entries
             apply."
    ::= { sonusEvLogFilterEntry 3 }

sonusEvLogFilterEventClass OBJECT-TYPE
    SYNTAX          SonusEventClass
    MAX-ACCESS      read-write
    STATUS          current
    DESCRIPTION     
            "The class of events to which the filter entry applies."
    ::= { sonusEvLogFilterEntry 4 }

sonusEvLogFilterLevel OBJECT-TYPE
    SYNTAX          SonusEventFilterLevel
    MAX-ACCESS      read-write
    STATUS          current
    DESCRIPTION     
            "Events that are at least as severe as the designated
             level will be logged. noevents suppresses all events
             of this type from being logged."
    DEFVAL          { major }
    ::= { sonusEvLogFilterEntry 5 }

sonusEvLogFilterState OBJECT-TYPE
    SYNTAX          INTEGER { off(1), on(2) }
    MAX-ACCESS      read-write
    STATUS          current
    DESCRIPTION     
            "On if this filter entry should take precedence over the
             per-node settings."
    DEFVAL          { off }
    ::= { sonusEvLogFilterEntry 6 }

sonusEvLogFilterStatusTable OBJECT-TYPE
    SYNTAX          SEQUENCE OF SonusEvLogFilterStatusEntry
    MAX-ACCESS      not-accessible
    STATUS          current
    DESCRIPTION     
            "Event Log Class Filter status table per card."
    ::= { sonusEventLogMIBObjects 7 }

sonusEvLogFilterStatusEntry OBJECT-TYPE
    SYNTAX          SonusEvLogFilterStatusEntry
    MAX-ACCESS      not-accessible
    STATUS          current
    DESCRIPTION     
            "An entry of Event Log Class Filter status per card."
    INDEX           { sonusEvLogFilterStatusShelf, 
                      sonusEvLogFilterStatusSlot, 
                      sonusEvLogFilterStatusType, 
                      sonusEvLogFilterStatusEventClass }
    ::= { sonusEvLogFilterStatusTable 1 }

SonusEvLogFilterStatusEntry ::=
    SEQUENCE {
        sonusEvLogFilterStatusShelf     Integer32,
        sonusEvLogFilterStatusSlot      Integer32,
        sonusEvLogFilterStatusType      INTEGER,
        sonusEvLogFilterStatusEventClass SonusEventClass,
        sonusEvLogFilterStatusFiltered  Integer32
    }

sonusEvLogFilterStatusShelf OBJECT-TYPE
    SYNTAX          Integer32
    MAX-ACCESS      read-only
    STATUS          current
    DESCRIPTION     
            "The shelf number for which these table entries
             apply."
    ::= { sonusEvLogFilterStatusEntry 1 }

sonusEvLogFilterStatusSlot OBJECT-TYPE
    SYNTAX          Integer32
    MAX-ACCESS      read-only
    STATUS          current
    DESCRIPTION     
            "The slot number for which these table entries
             apply."
    ::= { sonusEvLogFilterStatusEntry 2 }

sonusEvLogFilterStatusType OBJECT-TYPE
    SYNTAX          INTEGER { system(1), debug(2), trace(3) }
    MAX-ACCESS      read-only
    STATUS          current
    DESCRIPTION     
            "The event log type for which these table entries
             apply."
    ::= { sonusEvLogFilterStatusEntry 3 }

sonusEvLogFilterStatusEventClass OBJECT-TYPE
    SYNTAX          SonusEventClass
    MAX-ACCESS      read-only
    STATUS          current
    DESCRIPTION     
            "The event class to which the filter entry applies."
    ::= { sonusEvLogFilterStatusEntry 4 }

sonusEvLogFilterStatusFiltered OBJECT-TYPE
    SYNTAX          Integer32
    MAX-ACCESS      read-only
    STATUS          current
    DESCRIPTION     
            "The number of events that were filtered."
    ::= { sonusEvLogFilterStatusEntry 5 }

sonusEventLogMIBNotifications OBJECT IDENTIFIER
    ::= { sonusEventLogMIB 2 }

sonusEventLogMIBNotificationsPrefix OBJECT IDENTIFIER
    ::= { sonusEventLogMIBNotifications 0 }

sonusEventLogMIBNotificationsObjects OBJECT IDENTIFIER
    ::= { sonusEventLogMIBNotifications 1 }

sonusEvLogAdminState OBJECT-TYPE
    SYNTAX          INTEGER { disabled(1), enabled(2), rollfile(3) }
    MAX-ACCESS      read-only
    STATUS          current
    DESCRIPTION     
            "The requested state of the given Event Log type.  Rollfile
             will close an enabled log file and reopen, incrementing the
             suffix.  If a file is disabled and rolled, the command is
             ignored."
    ::= { sonusEventLogMIBNotificationsObjects 1 }

sonusEvLogShutdownReason OBJECT-TYPE
    SYNTAX          INTEGER { fileWriteFailed(1), nfsError(2), 
                        createDirectoryFailed(3), 
                        maximumFileCountReached(4), fileRemoveFailed(5), 
                        fileOpenFailed(6), fileHeaderWriteFailed(7), 
                        memoryAllocationFailed(8), 
                        administrativeShutdown(9) }
    MAX-ACCESS      read-only
    STATUS          current
    DESCRIPTION     
            "The reason that event file logging has been shutdown."
    ::= { sonusEventLogMIBNotificationsObjects 2 }

sonusEvLogDirName OBJECT-TYPE
    SYNTAX          DisplayString
    MAX-ACCESS      read-only
    STATUS          current
    DESCRIPTION     
            "The event file log directory name."
    ::= { sonusEventLogMIBNotificationsObjects 3 }

sonusEvLogFilePercentage OBJECT-TYPE
    SYNTAX          Integer32
    MAX-ACCESS      read-only
    STATUS          current
    DESCRIPTION     
            "The percentage the event log directory is full based on file count."
    ::= { sonusEventLogMIBNotificationsObjects 4 }

sonusEvLogCurFileCount OBJECT-TYPE
    SYNTAX          Integer32
    MAX-ACCESS      read-only
    STATUS          current
    DESCRIPTION     
            "The current count of event files."
    ::= { sonusEventLogMIBNotificationsObjects 5 }

sonusEventLogFileStateNotification NOTIFICATION-TYPE
    OBJECTS         { sonusShelfIndex, sonusEvLogType, 
                      sonusEvLogAdminState, sonusEventDescription, 
                      sonusEventClass, sonusEventLevel }
    STATUS          current
    DESCRIPTION     
            "This trap indicates the current state of event file logging."
    ::= { sonusEventLogMIBNotificationsPrefix 1 }

sonusEventLogFileCreatedNotification NOTIFICATION-TYPE
    OBJECTS         { sonusShelfIndex, sonusEvLogType, 
                      sonusEvLogTypeStatusCurrentFile, 
                      sonusEventDescription, sonusEventClass, 
                      sonusEventLevel }
    STATUS          current
    DESCRIPTION     
            "This trap indicates the name of the event file which has been created for logging."
    ::= { sonusEventLogMIBNotificationsPrefix 2 }

sonusEventLogAcctFileCreatedNotification NOTIFICATION-TYPE
    OBJECTS         { sonusShelfIndex, sonusEvLogTypeStatusCurrentFile, 
                      sonusEventDescription, sonusEventClass, 
                      sonusEventLevel }
    STATUS          current
    DESCRIPTION     
            "This trap indicates the name of the accounting event file which has been created for logging."
    ::= { sonusEventLogMIBNotificationsPrefix 3 }

sonusEventLogFileRestartNotification NOTIFICATION-TYPE
    OBJECTS         { sonusShelfIndex, sonusEvLogType, 
                      sonusEventDescription, sonusEventClass, 
                      sonusEventLevel }
    STATUS          current
    DESCRIPTION     
            "This trap indicates that file event logging has been automatically restarted."
    ::= { sonusEventLogMIBNotificationsPrefix 4 }

sonusEventLogAcctFileRestartNotification NOTIFICATION-TYPE
    OBJECTS         { sonusShelfIndex, sonusEventDescription, 
                      sonusEventClass, sonusEventLevel }
    STATUS          current
    DESCRIPTION     
            "This trap indicates that accounting file event logging has been automatically restarted."
    ::= { sonusEventLogMIBNotificationsPrefix 5 }

sonusEventLogFileClosedNotification NOTIFICATION-TYPE
    OBJECTS         { sonusShelfIndex, sonusEvLogType, 
                      sonusEvLogTypeStatusCurrentFile, 
                      sonusEventDescription, sonusEventClass, 
                      sonusEventLevel }
    STATUS          current
    DESCRIPTION     
            "This trap indicates the name of the event file which has been closed."
    ::= { sonusEventLogMIBNotificationsPrefix 6 }

sonusEventLogAcctFileClosedNotification NOTIFICATION-TYPE
    OBJECTS         { sonusShelfIndex, sonusEvLogTypeStatusCurrentFile, 
                      sonusEventDescription, sonusEventClass, 
                      sonusEventLevel }
    STATUS          current
    DESCRIPTION     
            "This trap indicates the name of the accounting event file which has been closed."
    ::= { sonusEventLogMIBNotificationsPrefix 7 }

sonusEventLogFileShutdownNotification NOTIFICATION-TYPE
    OBJECTS         { sonusShelfIndex, sonusEvLogType, 
                      sonusEvLogShutdownReason, sonusEvLogAdminState, 
                      sonusEventDescription, sonusEventClass, 
                      sonusEventLevel }
    STATUS          current
    DESCRIPTION     
            "This trap indicates that a shutdown of file event logging has occurred."
    ::= { sonusEventLogMIBNotificationsPrefix 8 }

sonusEventLogFileCountNotification NOTIFICATION-TYPE
    OBJECTS         { sonusEvLogDirName, sonusEvLogFilePercentage, 
                      sonusEvLogCurFileCount, sonusEvLogTypeFileCount, 
                      sonusEventDescription, sonusEventClass, 
                      sonusEventLevel }
    STATUS          current
    DESCRIPTION     
            "This trap indicates that the number of event log files is approaching the configured maximum."
    ::= { sonusEventLogMIBNotificationsPrefix 9 }

sonusEventLogFileCountChngNotification NOTIFICATION-TYPE
    OBJECTS         { sonusShelfIndex, sonusEvLogType, 
                      sonusEvLogTypeFileCount, sonusEventDescription, 
                      sonusEventClass, sonusEventLevel }
    STATUS          current
    DESCRIPTION     
            "This trap indicates the number of Event Log files that will be maintained for this event type is changed"
    ::= { sonusEventLogMIBNotificationsPrefix 10 }

sonusEventLogFileSizeChngNotification NOTIFICATION-TYPE
    OBJECTS         { sonusShelfIndex, sonusEvLogType, 
                      sonusEvLogTypeFileSize, sonusEventDescription, 
                      sonusEventClass, sonusEventLevel }
    STATUS          current
    DESCRIPTION     
            "This trap indicates that the maximum size of a single event log file has changed."
    ::= { sonusEventLogMIBNotificationsPrefix 11 }

sonusEventLogFileMsgQueueChngNotification NOTIFICATION-TYPE
    OBJECTS         { sonusShelfIndex, sonusEvLogType, 
                      sonusEvLogTypeFileMsgQueue, sonusEventDescription, 
                      sonusEventClass, sonusEventLevel }
    STATUS          current
    DESCRIPTION     
            "This trap indicates that the number event log message entries to the buffer changed"
    ::= { sonusEventLogMIBNotificationsPrefix 12 }

sonusEventLogSaveToChngNotification NOTIFICATION-TYPE
    OBJECTS         { sonusShelfIndex, sonusEvLogType, 
                      sonusEvLogTypeSaveTo, sonusEventDescription, 
                      sonusEventClass, sonusEventLevel }
    STATUS          current
    DESCRIPTION     
            "This Trap indicates that the location where events are saved is being changed "
    ::= { sonusEventLogMIBNotificationsPrefix 13 }

sonusEventLogFileMaxEventMemSizeChngNotification NOTIFICATION-TYPE
    OBJECTS         { sonusShelfIndex, sonusEvLogType, 
                      sonusEvLogTypeMaxEventMemSize, 
                      sonusEventDescription, sonusEventClass, 
                      sonusEventLevel }
    STATUS          current
    DESCRIPTION     
            "This trap indicates that the maximum size of the memory event log buffer is changed"
    ::= { sonusEventLogMIBNotificationsPrefix 14 }

sonusEventLogFileFilterLevelChngNotification NOTIFICATION-TYPE
    OBJECTS         { sonusShelfIndex, sonusEvLogType, 
                      sonusEvLogTypeFilterLevel, sonusEventDescription, 
                      sonusEventClass, sonusEventLevel }
    STATUS          current
    DESCRIPTION     
            "This trap indicates that the level of event logging for this event type is changed"
    ::= { sonusEventLogMIBNotificationsPrefix 15 }

END -- end of module SONUS-EVENT-LOG-MIB.
