Wellfleet-BRIDGE-MIB DEFINITIONS ::= BEGIN

-- Created by mdl2asn version 3.1
-- Creation date: Wed Aug 30 16:38:44 EDT 1995


    IMPORTS

      Counter, Opaque
        FROM RFC1155-SMI
      OBJECT-TYPE
        FROM RFC-1212
      DisplayString
        FROM RFC1213-MIB
      wfBridgeGroup
        FROM Wellfleet-COMMON-MIB;


    wfBrLearning  	OBJECT IDENTIFIER ::= { wfBridgeGroup 1 }
    wfBrTp		OBJECT IDENTIFIER ::= { wfBrLearning 1 }

    wfBrTpBaseDelete OBJECT-TYPE
        SYNTAX	INTEGER {
    		    created(1),
    		    deleted(2)
    		}
        ACCESS	read-write
        STATUS	mandatory
        DESCRIPTION
                "Create/Delete parameter. Default is created.
                Users perform an SNMP SET operation on this
                object in order to create/delete the bridge."
        DEFVAL	{ created }
        ::= { wfBrTp 1 }

    wfBrTpBaseEnable OBJECT-TYPE
        SYNTAX	INTEGER {
    		    enabled(1),
    		    disabled(2)
    		}
        ACCESS	read-write
        STATUS	mandatory
        DESCRIPTION
                "Enable/Disable parameter. Default is enabled.
                Users perform an SNMP SET operation on this
                object in order to enable/disable the bridge."
        DEFVAL	{ enabled }
        ::= { wfBrTp 2 }

    wfBrTpBaseState OBJECT-TYPE
        SYNTAX	INTEGER {
    		    up(1),
    		    down(2),
    		    init(3),
    		    pres(4)
    		}
        ACCESS	read-only
        STATUS	mandatory
        DESCRIPTION
                "The current state of the entire Bridge."
        DEFVAL	{ down }
        ::= { wfBrTp 3 }

    wfBrTpBaseFDBEntries OBJECT-TYPE
        SYNTAX	Counter
        ACCESS	read-only
        STATUS	mandatory
        DESCRIPTION
                "The current number of forward table entries"
        ::= { wfBrTp 4 }

    wfBrTpBaseFDBSize OBJECT-TYPE
        SYNTAX	INTEGER {
    		    size1024(1024),
    		    size2048(2048),
    		    size4096(4096),
    		    size8192(8192),
    		    size16384(16384),
    		    size32768(32768),
    		    size65536(65536),
    		    size131072(131072)
    		}
        ACCESS	read-write
        STATUS	mandatory
        DESCRIPTION
                "Size of the bridge table - only looked at at boot time"
        DEFVAL	{ size1024 }
        ::= { wfBrTp 5 }

    wfBrTpBaseFDBEnable OBJECT-TYPE
        SYNTAX	INTEGER {
    		    enabled(1),
    		    disabled(2)
    		}
        ACCESS	read-write
        STATUS	mandatory
        DESCRIPTION
                "Disable placing fdb entries on the mib.
                This attribute only inspected at boot time."
        DEFVAL	{ enabled }
        ::= { wfBrTp 6 }

    wfBrTpBaseFlushFwdTbl OBJECT-TYPE
        SYNTAX	INTEGER {
    		    flushed(1),
    		    noflushed(2)
    		}
        ACCESS	read-write
        STATUS	mandatory
        DESCRIPTION
                "Flush the bridge fwd tables"
        DEFVAL	{ noflushed }
        ::= { wfBrTp 7 }

    wfBrTpBaseFDBPortChange OBJECT-TYPE
        SYNTAX	Counter
        ACCESS	read-only
        STATUS	mandatory
        DESCRIPTION
                "The amount that all the stations move from
                one port to anotherard table entries"
        ::= { wfBrTp 8 }

    wfBrTpFdbTable OBJECT-TYPE
        SYNTAX	SEQUENCE OF WfBrTpFdbEntry
        ACCESS	not-accessible
        STATUS	mandatory
        DESCRIPTION
                "A table that contains information about unicast
                entries for which the bridge has forwarding and/or
                filtering information.  This information is used
                by the transparent bridging function in
                determining how to propagate a received frame.
                inst = wfBrTpBaseFdbAddress"
        ::= { wfBrLearning 2 }

    wfBrTpFdbEntry OBJECT-TYPE
        SYNTAX	WfBrTpFdbEntry
        ACCESS	not-accessible
        STATUS	mandatory
        DESCRIPTION
                "An entry in the wfBrTpFdbTable."
        INDEX	{ wfBrTpBaseFdbAddress }
        ::= { wfBrTpFdbTable 1 }

    WfBrTpFdbEntry ::= SEQUENCE {
    	    wfBrTpBaseFdbAddress
    		OCTET STRING,
    	    wfBrTpBaseFdbPort
    		INTEGER,
    	    wfBrTpBaseFdbStatus
    		INTEGER
        }

    wfBrTpBaseFdbAddress OBJECT-TYPE
        SYNTAX	OCTET STRING (SIZE (6))
        ACCESS	read-only
        STATUS	mandatory
        DESCRIPTION
                "A unicast MAC address for which the bridge has
                forwarding and/or filtering information."
        ::= { wfBrTpFdbEntry 1 }

    wfBrTpBaseFdbPort OBJECT-TYPE
        SYNTAX	INTEGER
        ACCESS	read-only
        STATUS	mandatory
        DESCRIPTION
                "The port number on which the wfBrTpBaseFdbAddress
                was learned."
        ::= { wfBrTpFdbEntry 2 }

    wfBrTpBaseFdbStatus OBJECT-TYPE
        SYNTAX	INTEGER {
    		    learned(3)
    		}
        ACCESS	read-only
        STATUS	mandatory
        DESCRIPTION
                "The status of this entry. The meanings of the
                values are:
                  learned(3) : the value of the corresponding
                              instance of wfBrTpFdbPort was
                              learned, and is being used."
        DEFVAL	{ learned }
        ::= { wfBrTpFdbEntry 3 }

    wfBrTpAggrStats	OBJECT IDENTIFIER ::= { wfBrLearning 3 }

    wfBrTpAggrInPkts OBJECT-TYPE
        SYNTAX	Counter
        ACCESS	read-only
        STATUS	mandatory
        DESCRIPTION
                "The total number of packets received by the transparent bridge"
        ::= { wfBrTpAggrStats 1 }

    wfBrTpAggrOutPkts OBJECT-TYPE
        SYNTAX	Counter
        ACCESS	read-only
        STATUS	mandatory
        DESCRIPTION
                "The total number of packets sent by the transparent bridge"
        ::= { wfBrTpAggrStats 2 }

    wfBrTpAggrDiscardPkts OBJECT-TYPE
        SYNTAX	Counter
        ACCESS	read-only
        STATUS	mandatory
        DESCRIPTION
                "The total number of packets discarded by the transparent bridge"
        ::= { wfBrTpAggrStats 3 }

    wfBrTpInterfaceTable OBJECT-TYPE
        SYNTAX	SEQUENCE OF WfBrTpInterfaceEntry
        ACCESS	not-accessible
        STATUS	mandatory
        DESCRIPTION
                "A table that contains information about every
                interface that is associated with this
                transparent bridge.
                inst_id[1] = wfBrTpInterfaceCircuit"
        ::= { wfBridgeGroup 3 }

    wfBrTpInterfaceEntry OBJECT-TYPE
        SYNTAX	WfBrTpInterfaceEntry
        ACCESS	not-accessible
        STATUS	mandatory
        DESCRIPTION
                "An entry in wfBrTpInterface."
        INDEX	{ wfBrTpInterfaceCircuit }
        ::= { wfBrTpInterfaceTable 1 }

    WfBrTpInterfaceEntry ::= SEQUENCE {
    	    wfBrTpInterfaceDelete
    		INTEGER,
    	    wfBrTpInterfaceEnable
    		INTEGER,
    	    wfBrTpInterfaceState
    		INTEGER,
    	    wfBrTpInterfaceCircuit
    		INTEGER,
    	    wfBrTpInterfaceMaxInfo
    		INTEGER,
    	    wfBrTpInterfaceInFrames
    		Counter,
    	    wfBrTpInterfaceOutFrames
    		Counter,
    	    wfBrTpInterfaceInDiscards
    		Counter,
    	    wfBrTpInterfaceTranslationDisable
    		INTEGER
        }

    wfBrTpInterfaceDelete OBJECT-TYPE
        SYNTAX	INTEGER {
    		    created(1),
    		    deleted(2)
    		}
        ACCESS	read-write
        STATUS	mandatory
        DESCRIPTION
                "Create/Delete parameter. Default is created.
                Users perform an SNMP SET operation on this
                object in order to create/delete an interface."
        DEFVAL	{ created }
        ::= { wfBrTpInterfaceEntry 1 }

    wfBrTpInterfaceEnable OBJECT-TYPE
        SYNTAX	INTEGER {
    		    enabled(1),
    		    disabled(2),
    		    circuitdump(33),
    		    fwdtbldump(17)
    		}
        ACCESS	read-write
        STATUS	mandatory
        DESCRIPTION
                "Enable/Disable parameter. Default is enabled.
                Users perform an SNMP SET operation on this
                object in order to enable/disable an interface."
        DEFVAL	{ enabled }
        ::= { wfBrTpInterfaceEntry 2 }

    wfBrTpInterfaceState OBJECT-TYPE
        SYNTAX	INTEGER {
    		    up(1),
    		    down(2),
    		    init(3),
    		    pres(4)
    		}
        ACCESS	read-only
        STATUS	mandatory
        DESCRIPTION
                "The current state of the interface."
        DEFVAL	{ down }
        ::= { wfBrTpInterfaceEntry 3 }

    wfBrTpInterfaceCircuit OBJECT-TYPE
        SYNTAX	INTEGER
        ACCESS	read-only
        STATUS	mandatory
        DESCRIPTION
                "The circuit that this interface runs over."
        ::= { wfBrTpInterfaceEntry 4 }

    wfBrTpInterfaceMaxInfo OBJECT-TYPE
        SYNTAX	INTEGER
        ACCESS	read-only
        STATUS	mandatory
        DESCRIPTION
                "The maximum size of the INFO (non-MAC) field that
                this port will receive or transmit."
        ::= { wfBrTpInterfaceEntry 5 }

    wfBrTpInterfaceInFrames OBJECT-TYPE
        SYNTAX	Counter
        ACCESS	read-only
        STATUS	mandatory
        DESCRIPTION
                "The number of frames that have been received by
                this interface from its circuit."
        ::= { wfBrTpInterfaceEntry 6 }

    wfBrTpInterfaceOutFrames OBJECT-TYPE
        SYNTAX	Counter
        ACCESS	read-only
        STATUS	mandatory
        DESCRIPTION
                "The number of frames that have been transmitted
                by this interface to its circuit."
        ::= { wfBrTpInterfaceEntry 7 }

    wfBrTpInterfaceInDiscards OBJECT-TYPE
        SYNTAX	Counter
        ACCESS	read-only
        STATUS	mandatory
        DESCRIPTION
                "Count of valid frames received which were
                received on this interface but then discarded."
        ::= { wfBrTpInterfaceEntry 8 }

    wfBrTpInterfaceTranslationDisable OBJECT-TYPE
        SYNTAX	INTEGER {
    		    enabled(1),
    		    disabled(2)
    		}
        ACCESS	read-write
        STATUS	mandatory
        DESCRIPTION
                "Enable/Disable translation bridging parameter. Default is enabled."
        DEFVAL	{ disabled }
        ::= { wfBrTpInterfaceEntry 9 }

    wfBrTrafficFilterTable OBJECT-TYPE
        SYNTAX	SEQUENCE OF WfBrTrafficFilterEntry
        ACCESS	not-accessible
        STATUS	mandatory
        DESCRIPTION
                "Bridge Traffic Filters"
        ::= { wfBridgeGroup 4 }

    wfBrTrafficFilterEntry OBJECT-TYPE
        SYNTAX	WfBrTrafficFilterEntry
        ACCESS	not-accessible
        STATUS	mandatory
        DESCRIPTION
                "An entry in WfBrTrafficFilterTable."
        INDEX	{ wfBrTrafficFilterCircuit,
    		  wfBrTrafficFilterRuleNumber,
    		  wfBrTrafficFilterFragment }
        ::= { wfBrTrafficFilterTable 1 }

    WfBrTrafficFilterEntry ::= SEQUENCE {
    	    wfBrTrafficFilterCreate
    		INTEGER,
    	    wfBrTrafficFilterEnable
    		INTEGER,
    	    wfBrTrafficFilterStatus
    		INTEGER,
    	    wfBrTrafficFilterCounter
    		Counter,
    	    wfBrTrafficFilterDefinition
    		Opaque,
    	    wfBrTrafficFilterReserved
    		INTEGER,
    	    wfBrTrafficFilterCircuit
    		INTEGER,
    	    wfBrTrafficFilterRuleNumber
    		INTEGER,
    	    wfBrTrafficFilterFragment
    		INTEGER,
    	    wfBrTrafficFilterName
    		DisplayString
        }

    wfBrTrafficFilterCreate OBJECT-TYPE
        SYNTAX	INTEGER {
    		    created(1),
    		    deleted(2)
    		}
        ACCESS	read-write
        STATUS	mandatory
        DESCRIPTION
                "Defines the existence of the traffic filter rule:
                created - traffic filter exists
                delete - traffic filter does not exist and can be deleted."
        DEFVAL	{ created }
        ::= { wfBrTrafficFilterEntry 1 }

    wfBrTrafficFilterEnable OBJECT-TYPE
        SYNTAX	INTEGER {
    		    enabled(1),
    		    disabled(2)
    		}
        ACCESS	read-write
        STATUS	mandatory
        DESCRIPTION
                "Defines whether or not the traffic filter rule should be used:
                enabled - activate the rule.
                disabled - inactivate the rule."
        DEFVAL	{ enabled }
        ::= { wfBrTrafficFilterEntry 2 }

    wfBrTrafficFilterStatus OBJECT-TYPE
        SYNTAX	INTEGER {
    		    active(1),
    		    error(2),
    		    inactive(3)
    		}
        ACCESS	read-only
        STATUS	mandatory
        DESCRIPTION
                "Defines the current status of the traffic filter:
                inactive - the rule is not in use.
                active - the rule is being used.
                error - the application detected an error in the rule."
        DEFVAL	{ inactive }
        ::= { wfBrTrafficFilterEntry 3 }

    wfBrTrafficFilterCounter OBJECT-TYPE
        SYNTAX	Counter
        ACCESS	read-only
        STATUS	mandatory
        DESCRIPTION
                "The number of received packets that have
                matched this rule."
        ::= { wfBrTrafficFilterEntry 4 }

    wfBrTrafficFilterDefinition OBJECT-TYPE
        SYNTAX	Opaque
        ACCESS	read-write
        STATUS	mandatory
        DESCRIPTION
                "The filter rule definition."
        ::= { wfBrTrafficFilterEntry 5 }

    wfBrTrafficFilterReserved OBJECT-TYPE
        SYNTAX	INTEGER
        ACCESS	read-only
        STATUS	mandatory
        DESCRIPTION
                "Reserved field."
        ::= { wfBrTrafficFilterEntry 6 }

    wfBrTrafficFilterCircuit OBJECT-TYPE
        SYNTAX	INTEGER
        ACCESS	read-only
        STATUS	mandatory
        DESCRIPTION
                "The ID of the Bridge Circuit to which the
                filter is applied."
        ::= { wfBrTrafficFilterEntry 7 }

    wfBrTrafficFilterRuleNumber OBJECT-TYPE
        SYNTAX	INTEGER
        ACCESS	read-only
        STATUS	mandatory
        DESCRIPTION
                "ID for the rule."
        ::= { wfBrTrafficFilterEntry 8 }

    wfBrTrafficFilterFragment OBJECT-TYPE
        SYNTAX	INTEGER
        ACCESS	read-only
        STATUS	mandatory
        DESCRIPTION
                "Fragment number - for large rules."
        ::= { wfBrTrafficFilterEntry 9 }

    wfBrTrafficFilterName OBJECT-TYPE
        SYNTAX	DisplayString
        ACCESS	read-write
        STATUS	mandatory
        DESCRIPTION
                "name of the rule number"
        ::= { wfBrTrafficFilterEntry 10 }

    END  -- Wellfleet-BRIDGE-MIB
