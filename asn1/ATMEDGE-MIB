--========================================================
--
-- MIB      : ATMEdge                                                     Madge Networks Ltd
--
-- Version  : 8.5.2                                                                         20 Nov. 1997
--
-- RCS Id   : Yigal Nehaysi
--
--========================================================
--
-- Copyright 1992,1993, 1994, 1995, 1996, 1997 MADGE NETWORKS, Ltd.  
-- All Rights Reserved.  
--
-- Reproduction of this document is authorized on condition 
-- that the foregoing copyright notice is included.
--
-- This MADGE ESD SNMP Management Information Base Specification
-- (Specification) embodies MADGE ESD confidential and
-- proprietary intellectual property.  MADGE retains all
-- title and ownership in the Specification, including any revisions
--
-- It is MADGE's intent to encourage the widespread use of this
-- Specification in connection with the management of MADGE products.
-- MADGE grants vendors, end-users, and other interested parties
-- a non-exclusive license to use this Specification in connection
-- with the management of MADGE products.
--
-- This Specification is supplied "as is," and MADGE makes
-- no warranty, either express or implied, as to the use,
-- operation, condition, or performance of the Specification.
--
--========================================================
--
-- RCS
--
-- Version 8.5.2
-- 20 Nov. 1997
-- 1. Change header lines to be compile by emmbedded compiler.
--
-- Version 8.5.1
-- 29 Sep. 1997
-- 1. add two mib items to atmEdgePort table. atmEdgePortDormantHealthStatus and
--     atmEdgePortRedundancyStatus. The trap file & Fault doc were updated. - Zion S.
--
-- Version 8.5
-- Revision A. -	1. Change lntAtm to atmEdge - Gidi N.
-- 20 July 1997	2. Add association table.         - Gidi N.
--	3. Change associationEntryStatus to associationRowStatus and its
--                             enumartion
--	4. Add 4 new items atmEdgePortILMIStatus, atmEdgePortSignalStatus,
--                            atmEdgePortActualUNIVersion and atmEdgePortNetworkPrefix to 
--                            atmEdgePort Table. - Zion S.
--	5. Splited from modules.mib file to atmedge.mib
--	6. Change the access of associationIndex from RW to RO - Gidi N.
--
--========================================================

ATMEDGE-MIB DEFINITIONS ::= BEGIN


IMPORTS
      OBJECT-TYPE
    FROM RFC-1212
      DisplayString
    FROM RFC1213-MIB
      lannet 
    FROM GEN-MIB;

-- Some MIB Compilers need these two lines:
--  enterprises  OBJECT IDENTIFIER ::= 
--                { iso org(3) dod(6) internet(1) private(4) 1 }


atmEdge              OBJECT IDENTIFIER ::= { lannet 26 }
cti                     OBJECT IDENTIFIER ::= { lannet 29 } -- LBT155


-- For ATM Edge device modules

atmEdgePort OBJECT IDENTIFIER ::= {atmEdge 1}

atmEdgePortTable OBJECT-TYPE
	SYNTAX SEQUENCE OF AtmEdgePortEntry
	ACCESS not-accessible
	STATUS mandatory
              DESCRIPTION ""
	::= { atmEdgePort 1}

atmEdgePortEntry OBJECT-TYPE
	SYNTAX AtmEdgePortEntry
	ACCESS not-accessible
	STATUS mandatory
              DESCRIPTION ""
	INDEX {atmEdgePortGroupId, atmEdgePortId}
	::= {atmEdgePortTable 1}

AtmEdgePortEntry ::=
	SEQUENCE {
	atmEdgePortGroupId
		INTEGER,
	atmEdgePortId
		INTEGER,
	atmEdgePortHealthStatus
		INTEGER,
	atmEdgePortMACAddr
		OCTET STRING,
	atmEdgePortATMAddr
		OCTET STRING,
	atmEdgePortLanType
		INTEGER,
	atmEdgePortILMIStatus
		INTEGER,
	atmEdgePortSignalStatus
		INTEGER,
	atmEdgePortActualUNIVersion
		INTEGER,
	atmEdgePortNetworkPrefix
		OCTET STRING,
	atmEdgePortDormantHealthStatus
		INTEGER,
	atmEdgePortRedundancyStatus
		INTEGER
	}

atmEdgePortGroupId OBJECT-TYPE
	SYNTAX INTEGER (1..255)
	ACCESS read-only
	STATUS mandatory
	DESCRIPTION
	"Id of the slot to which the atm port belongs." 
	::= {atmEdgePortEntry 1 }

atmEdgePortId OBJECT-TYPE
	SYNTAX INTEGER (1..255)
	ACCESS read-only
	STATUS mandatory
	DESCRIPTION
	"Id of the port." 
	::= { atmEdgePortEntry 2 }

atmEdgePortHealthStatus OBJECT-TYPE
	SYNTAX INTEGER {
		ok(1),  
		atmError(2),
		sonetLinkError(3),
		sonetRemoteLinkError(4),
		notSupported(255)       
	}
	ACCESS read-only
	STATUS mandatory
	DESCRIPTION
	"Indicates the health state of the port. When this
	  field indicates carrierFailure, it means that there
	  is no carrier: the agent should send a trap of
	  type fault." 
	::= {atmEdgePortEntry 3 }

atmEdgePortMACAddr OBJECT-TYPE
	SYNTAX OCTET STRING ( SIZE(0..6))
	ACCESS read-only
	STATUS mandatory
	DESCRIPTION
	"MAC address of the ATM port. If the port has no
	  MAC address, this value should be zero length
	  octet string."
	::= { atmEdgePortEntry  4}

atmEdgePortATMAddr OBJECT-TYPE
	SYNTAX OCTET STRING ( SIZE(0..20))
	ACCESS read-only
	STATUS mandatory
	DESCRIPTION
	"ATM address of the ATM port. If the port has no
	  ATM address, this value should be zero length
	  octet string."
	::= { atmEdgePortEntry  5}

atmEdgePortLanType OBJECT-TYPE
	SYNTAX  INTEGER {
		ethernet(1),
		token-ring(2),
		notSupported(255)
	}
	ACCESS  read-only
	STATUS  mandatory
	DESCRIPTION
	"The type of the up link port. This is used do find whether
	the port wants to receive the association table and from what kind.
	ethernet - an Ethernet Edge device.
	token-ring - a Token Ring Edge device.
	notSupported means that currently the device doesn't currently act as an Edge Devices"
	DEFVAL {ethernet}
	::= { atmEdgePortEntry 6 }

atmEdgePortILMIStatus OBJECT-TYPE
	SYNTAX INTEGER	{
		up(1),
		down(2),
		notsupported(255)
	}
	ACCESS	read-only
	STATUS	mandatory
	DESCRIPTION
		"The current state of the ILMI signalling of this port."
	::= { atmEdgePortEntry 7}
	
atmEdgePortSignalStatus OBJECT-TYPE
	SYNTAX INTEGER	{
		up(1),
		down(2),
		notsupported(255)
	}
	ACCESS	read-only
	STATUS	mandatory
	DESCRIPTION
		"The current state of the ATM signalling for this port."
	::= { atmEdgePortEntry 8 }

atmEdgePortActualUNIVersion OBJECT-TYPE
	SYNTAX  INTEGER	{
		unknown(1),
		uni-30(2),
		uni-31(3),
		uni-40(4),
		notsupported(255)
	}
	ACCESS  read-only
	STATUS  mandatory
	DESCRIPTION
		"The type of signalling that is currently being used on this port.  "
	::= { atmEdgePortEntry 9}

atmEdgePortNetworkPrefix  OBJECT-TYPE
	SYNTAX  OCTET STRING( SIZE(13))
	ACCESS  read-write
	STATUS  mandatory
	DESCRIPTION
		"The prefix of the ATM switch connected to this ATM port."
	::= { atmEdgePortEntry 10}

atmEdgePortDormantHealthStatus OBJECT-TYPE
	SYNTAX INTEGER {
		ok(1),  
		atmError(2),
		sonetLinkError(3),
		sonetRemoteLinkError(4),
		notSupported(255)       
	}
	ACCESS read-only
	STATUS mandatory
	DESCRIPTION
	"Indicates the health state of the Dormant port. When this
	field indicates carrierFailure, it means that there
	is no carrier: the agent should send a trap of type fault."
	::= { atmEdgePortEntry 11 }

atmEdgePortRedundancyStatus OBJECT-TYPE
	SYNTAX  INTEGER{
		masterNicActive(1),
		secondaryNicActive(2),
		notSupported(255)
		}
	ACCESS  read-only
	STATUS  mandatory
	DESCRIPTION
	"This item is relevant for ports which includes redundant
             links. This item indicates which of the links is active.
	Default value=masterNicActive(1). "
	::= { atmEdgePortEntry 12 }


atmEdgeGroup OBJECT IDENTIFIER ::= {atmEdge 2}

atmEdgeGroupTable OBJECT-TYPE
SYNTAX SEQUENCE OF AtmEdgeGroupEntry
ACCESS not-accessible
STATUS mandatory
              DESCRIPTION ""
::= { atmEdgeGroup 1}

atmEdgeGroupEntry OBJECT-TYPE
	SYNTAX AtmEdgeGroupEntry
	ACCESS not-accessible
	STATUS mandatory
              DESCRIPTION ""
	INDEX {atmEdgeGroupGroupId }
	::= {atmEdgeGroupTable 1}

AtmEdgeGroupEntry ::=
	SEQUENCE {
	atmEdgeGroupGroupId
		INTEGER,
	atmEdgeGroupWorkState
		INTEGER,
	atmEdgeGroupBITResult
		INTEGER
	}

atmEdgeGroupGroupId OBJECT-TYPE
	SYNTAX  INTEGER
	ACCESS  read-only
	STATUS  mandatory
	DESCRIPTION
	"Slot number in which the module is located."
	::= { atmEdgeGroupEntry 1 }

atmEdgeGroupWorkState OBJECT-TYPE
	SYNTAX  INTEGER { 
		run(1), 
		boot(2), 
		runAndBoot(3), 
		none(4), 
		notSupported(255)
	}
	ACCESS  read-only
	STATUS  mandatory
	DESCRIPTION
	"One of the possible states of the module: this item
	indicates if the module is runing or booting. The value
	runAndBoot(3) indicates a serious software problem."
	::= { atmEdgeGroupEntry 2 }


atmEdgeGroupBITResult OBJECT-TYPE
	SYNTAX  INTEGER { 
		ok(1), 
		faulty(2), 
		notSupported(255) 
	}
	ACCESS  read-only
	STATUS  mandatory
	DESCRIPTION
	"The  Bit Indication Test in state faulty indicates a problem.
	The agent should send a fault trap in this case."
	::= { atmEdgeGroupEntry 3 }


-- Association information between VLAN and ELAN names

atmEdgeAssociation OBJECT IDENTIFIER ::= {atmEdge 3}

associationTable  OBJECT-TYPE
	SYNTAX SEQUENCE OF AssociationEntry
	ACCESS  not-accessible
	STATUS  mandatory
	DESCRIPTION
	"This table contains all the information 
	concerning the association between VLAN
	and ELAN names."
	::= { atmEdgeAssociation 1}

associationEntry OBJECT-TYPE
	SYNTAX  AssociationEntry
	ACCESS  not-accessible
	STATUS  mandatory
	DESCRIPTION
	"An entry in the table, contains information about a VLAN
	associated to an ELAN on a particular up link port."
	INDEX {associationSlotIndex, associationPortIndex, associationIndex}
	::= { associationTable 1 }

AssociationEntry ::=
	SEQUENCE {
		associationSlotIndex		INTEGER,
	 	associationPortIndex		INTEGER,
		associationIndex		INTEGER,
		associationVlan			INTEGER,
		associationElan			DisplayString,
		associationRowStatus		INTEGER,
		associationIfIndex		INTEGER
		}

associationSlotIndex OBJECT-TYPE
	SYNTAX  INTEGER
	ACCESS   read-only
	STATUS  mandatory
	DESCRIPTION 
	"Index which identifies the Slot inside the chassis."
	::= { associationEntry 1}

associationPortIndex OBJECT-TYPE
	SYNTAX  INTEGER
	ACCESS   read-only
	STATUS  mandatory
	DESCRIPTION 
	"Index which identifies the Port inside the Slot."
	::= { associationEntry 2}

associationIndex OBJECT-TYPE
	SYNTAX  INTEGER
	ACCESS   read-only
	STATUS  mandatory
	DESCRIPTION 
	"An arbitrary integer which uniquely identifies an association number."
	::= { associationEntry 3}

associationVlan OBJECT-TYPE
	SYNTAX  INTEGER
	ACCESS   read-write
	STATUS  mandatory
	DESCRIPTION 
	"The VLAN number."
	DEFVAL {0}
	::= { associationEntry 4}

associationElan OBJECT-TYPE
	SYNTAX  DisplayString
	ACCESS   read-write
	STATUS  mandatory
	DESCRIPTION 
	"The ELAN name.
	For Ethernet devices the default is default.
	For Token Ring devices the default is defaultTrn"
	::= { associationEntry 5}

associationRowStatus OBJECT-TYPE
	SYNTAX  INTEGER {
		active(1),
		notInService(2),
		notReady(3),
		createAndGo(4),
		createAndWait (5),
		destroy (6)
	}
	ACCESS  read-write
	STATUS  mandatory
	DESCRIPTION
	"The status of the entry, not a standard RowStatus.
	To create an entry, the console finds the next
	available entry. It changes the entry to 'notReady',
	it fills the VLAN number and the ELAN name,
	and it changes the entry to 'createAndGo'.
	The device creates the interface and the LEC,
	when it finishes, it changes the entry to 'active'.
	To delete an entry, the console changes the entry to 'destroy'.
	To disable an entry, the console changes the entry to 'notInService'."
	DEFVAL {active}
	::= { associationEntry 6 }


associationIfIndex OBJECT-TYPE
	SYNTAX  INTEGER
	ACCESS   read-only
	STATUS  mandatory
	DESCRIPTION 
	"Creating a row in this table causes the agent to add 
	one row in the interface table. Before setting the row status to
	active, the agent fills this field with the value of the ifIndex of the
	new created row."
	DEFVAL {0}
	::= { associationEntry 7}




-- Addition for LBT155

genCTIGroup  OBJECT IDENTIFIER ::= { cti 1 }   -- used in CTI module

genCTIGroupTable OBJECT-TYPE
	SYNTAX  SEQUENCE OF GenCTIGroupEntry
	ACCESS  not-accessible
	STATUS  mandatory
	DESCRIPTION
	"Attributes pertaining to the CTI module."
	::= { genCTIGroup 1 }

genCTIGroupEntry OBJECT-TYPE
	SYNTAX  GenCTIGroupEntry
	ACCESS  not-accessible
	STATUS  mandatory
	DESCRIPTION
	"An entry in the table."
	INDEX   { genCTIGroupId }
	::= { genCTIGroupTable 1 }

GenCTIGroupEntry ::=
	SEQUENCE {
	    genCTIGroupId
		INTEGER,
	    genCTIGroupCellLossAlarm
		INTEGER,
	    genCTIGroupRedunAvailable
		INTEGER,
	    genCTIGroupRedunFlip
		INTEGER,
	 genCTIGroupFiberActive
		INTEGER,
	 genCTIGroupVmuxMaster
		INTEGER
	    }

genCTIGroupId OBJECT-TYPE
	SYNTAX  INTEGER
	ACCESS  read-only
	STATUS  mandatory
	DESCRIPTION
	"Slot number in which the module is located."
	::= { genCTIGroupEntry 1 }

genCTIGroupCellLossAlarm OBJECT-TYPE
	SYNTAX  INTEGER { ok(1), cellLossAlarm(2) }
	ACCESS  read-only
	STATUS  mandatory
	DESCRIPTION
	"Indicates a condition of significant cell loss 
	which results in performance degradation"
	::= { genCTIGroupEntry 2 }

genCTIGroupRedunAvailable OBJECT-TYPE
	SYNTAX  INTEGER { noRedun (1), redunAvailable(2) }
	ACCESS  read-only
	STATUS  mandatory
	DESCRIPTION
	"Indication on the availability of
	external redundancy unit"
	::= { genCTIGroupEntry 3 }

genCTIGroupRedunFlip OBJECT-TYPE
	SYNTAX  INTEGER { noFlip(1), flipFiber(2) }
	ACCESS  read-write
	STATUS  mandatory
	DESCRIPTION
	"In regular conditions this item  is in the noFlip
	state. Changing the item value to flipFiber  will
	result in flipping to the other link. After this flip is 
	completed the value will return back to the
	noFlip sate. this item is relevant only when
	a redundant link is available"
	::= {genCTIGroupEntry 4 }

genCTIGroupFiberActive OBJECT-TYPE
	SYNTAX  INTEGER { fiberActiveA(1), fiberActiveB(2) }
	ACCESS  read-only
	STATUS  mandatory
	DESCRIPTION
	"When there is an external fiber redundancy
	this item shows which of the links is active"
	::= {genCTIGroupEntry 5 }

genCTIGroupVmuxMaster OBJECT-TYPE
	SYNTAX  INTEGER { localMaster(1), localSlave(2) }
	ACCESS  read-only
	STATUS  mandatory
	DESCRIPTION
	"On the poit to point voice connection via
	the FIM port one side is a master and the 
	other side is a slave. This item shows whether
	the local module is master or slave"
	::= {genCTIGroupEntry 6 }

genCTIPortTable OBJECT-TYPE
	SYNTAX  SEQUENCE OF GenCTIPortEntry
	ACCESS  not-accessible
	STATUS  mandatory
	DESCRIPTION
	"Table of ports in a CTI module."
	::= { genCTIGroup 2 }

genCTIPortEntry OBJECT-TYPE
	SYNTAX  GenCTIPortEntry
	ACCESS  not-accessible
	STATUS  mandatory
	DESCRIPTION
	"Entry in the table."
	INDEX           { genCTIPortGroupId, genCTIPortId }
	::= { genCTIPortTable 1 }

GenCTIPortEntry ::=
	SEQUENCE {
	     genCTIPortGroupId
		INTEGER,
	     genCTIPortId
		INTEGER,
	     genCTIPortSync
		INTEGER,
	     genCTIPortRxAlarm
		INTEGER,
	    genCTIPortTxAlarm
		INTEGER
	}

genCTIPortGroupId OBJECT-TYPE
	SYNTAX  INTEGER
	ACCESS  read-only
	STATUS  mandatory
	DESCRIPTION
	"Slot number in which the module is located."
	::= { genCTIPortEntry 1 }

genCTIPortId OBJECT-TYPE
	SYNTAX  INTEGER
	ACCESS  read-only
	STATUS  mandatory
	DESCRIPTION
	"The port index.
	The numbering  scheme for the CTI ports follows:
	1 - FIM Voice port
	2 - UTP ATM Port
	3 - SONET port"
	::= { genCTIPortEntry 2 }

genCTIPortSync OBJECT-TYPE
	SYNTAX  INTEGER { ok(1), noSync(2), notSupported(255)}
	ACCESS  read-only
	STATUS  mandatory
	DESCRIPTION
	"Sync status for the port."
	::= { genCTIPortEntry 3 }

genCTIPortRxAlarm OBJECT-TYPE
	SYNTAX  INTEGER { ok(1), rxAlarm(2), notSupported(255) }
	ACCESS  read-only
	STATUS  mandatory
	DESCRIPTION
	"Rx Alarm status for the port"
	::= { genCTIPortEntry 4 }

genCTIPortTxAlarm OBJECT-TYPE
	SYNTAX  INTEGER { ok(1), txAlarm(2), notSupported(255) }
	ACCESS  read-only
	STATUS  mandatory
	DESCRIPTION
	" Tx Alarm status for the port "
	::= { genCTIPortEntry 5 }
 
END
