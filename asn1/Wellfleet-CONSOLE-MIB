Wellfleet-CONSOLE-MIB DEFINITIONS ::= BEGIN

-- Created by mdl2asn version 3.1
-- Creation date: Wed Aug 30 16:39:11 EDT 1995


    IMPORTS

      Counter
        FROM RFC1155-SMI
      OBJECT-TYPE
        FROM RFC-1212
      DisplayString
        FROM RFC1213-MIB
      wfSerialPortGroup, wfServices
        FROM Wellfleet-COMMON-MIB;


    wfConsole	OBJECT IDENTIFIER ::= { wfServices 1 }

    wfBaudRate OBJECT-TYPE
        SYNTAX	INTEGER
        ACCESS	read-write
        STATUS	obsolete
        DESCRIPTION
                "Baud rate configured on the Technician Interface console"
        DEFVAL	{ 9600 }
        ::= { wfConsole 1 }

    wfDataBits OBJECT-TYPE
        SYNTAX	INTEGER
        ACCESS	read-write
        STATUS	obsolete
        DESCRIPTION
                "Number of data bits configured on the Technician Interface console"
        DEFVAL	{ 8 }
        ::= { wfConsole 2 }

    wfParity OBJECT-TYPE
        SYNTAX	INTEGER {
    		    none(1),
    		    odd(2),
    		    even(3)
    		}
        ACCESS	read-write
        STATUS	obsolete
        DESCRIPTION
                "Type of parity configured on the Technician Interface console"
        DEFVAL	{ none }
        ::= { wfConsole 3 }

    wfStopBits OBJECT-TYPE
        SYNTAX	INTEGER {
    		    s1bit(1),
    		    s15bit(2),
    		    s2bit(3)
    		}
        ACCESS	read-write
        STATUS	obsolete
        DESCRIPTION
                "Number of stop bits configured on the Technician Interface console"
        DEFVAL	{ s1bit }
        ::= { wfConsole 4 }

    wfModemEnable OBJECT-TYPE
        SYNTAX	INTEGER {
    		    enabled(1),
    		    disabled(2)
    		}
        ACCESS	read-write
        STATUS	obsolete
        DESCRIPTION
                "Enable the Technician Interface console to run over a modem"
        DEFVAL	{ disabled }
        ::= { wfConsole 5 }

    wfLinesPerScreen OBJECT-TYPE
        SYNTAX	INTEGER
        ACCESS	read-write
        STATUS	obsolete
        DESCRIPTION
                "Number of lines which can be displayed in one screen on the Technician
                Interface console"
        DEFVAL	{ 24 }
        ::= { wfConsole 6 }

    wfMoreEnable OBJECT-TYPE
        SYNTAX	INTEGER {
    		    enabled(1),
    		    disabled(2)
    		}
        ACCESS	read-write
        STATUS	obsolete
        DESCRIPTION
                "Enable the 'more' feature on the Technician Interface console"
        DEFVAL	{ enabled }
        ::= { wfConsole 7 }

    wfPrompt OBJECT-TYPE
        SYNTAX	DisplayString
        ACCESS	read-write
        STATUS	obsolete
        DESCRIPTION
                "Character string which will be used as the system prompt on
                the Technician Interface console"
        ::= { wfConsole 8 }

    wfLoginTimeOut OBJECT-TYPE
        SYNTAX	INTEGER(1..99)
        ACCESS	read-write
        STATUS	obsolete
        DESCRIPTION
                "IF MODEM_ENABLED then time out in minutes to HUP when at the login prompt"
        DEFVAL	{ 1 }
        ::= { wfConsole 9 }

    wfPasswordTimeOut OBJECT-TYPE
        SYNTAX	INTEGER(1..99)
        ACCESS	read-write
        STATUS	obsolete
        DESCRIPTION
                "Timout on Password entry"
        DEFVAL	{ 1 }
        ::= { wfConsole 10 }

    wfCommandTimeOut OBJECT-TYPE
        SYNTAX	INTEGER(1..99)
        ACCESS	read-write
        STATUS	obsolete
        DESCRIPTION
                "IF MODEM_ENABLED then time out in minutes to HUP when at the command prompt"
        DEFVAL	{ 15 }
        ::= { wfConsole 11 }

    wfLoginRetries OBJECT-TYPE
        SYNTAX	INTEGER(1..99)
        ACCESS	read-write
        STATUS	obsolete
        DESCRIPTION
                "IF MODEM_ENABLED then limit # of login attempts then HUP"
        DEFVAL	{ 3 }
        ::= { wfConsole 12 }

    wfTotalLogins OBJECT-TYPE
        SYNTAX	Counter
        ACCESS	read-only
        STATUS	obsolete
        DESCRIPTION
                "Total number of TI login attempts"
        ::= { wfConsole 13 }

    wfUserLoginErrors OBJECT-TYPE
        SYNTAX	Counter
        ACCESS	read-only
        STATUS	obsolete
        DESCRIPTION
                "Total number of FAILED User login attempts"
        ::= { wfConsole 14 }

    wfManagerLoginErrors OBJECT-TYPE
        SYNTAX	Counter
        ACCESS	read-only
        STATUS	obsolete
        DESCRIPTION
                "Total number of FAILED Manager login attempts"
        ::= { wfConsole 15 }

    wfOtherLoginErrors OBJECT-TYPE
        SYNTAX	Counter
        ACCESS	read-only
        STATUS	obsolete
        DESCRIPTION
                "Total number of FAILED Other login attempts"
        ::= { wfConsole 16 }

    wfTtyFrameErrors OBJECT-TYPE
        SYNTAX	Counter
        ACCESS	read-only
        STATUS	obsolete
        DESCRIPTION
                "Count of TTY Frame errors"
        ::= { wfConsole 17 }

    wfTtyOverrunErrors OBJECT-TYPE
        SYNTAX	Counter
        ACCESS	read-only
        STATUS	obsolete
        DESCRIPTION
                "Count of TTY Overrun errors"
        ::= { wfConsole 18 }

    wfTtyParityErrors OBJECT-TYPE
        SYNTAX	Counter
        ACCESS	read-only
        STATUS	obsolete
        DESCRIPTION
                "Count of TTY Parity errors"
        ::= { wfConsole 19 }

    wfTtyInfifoErrors OBJECT-TYPE
        SYNTAX	Counter
        ACCESS	read-only
        STATUS	obsolete
        DESCRIPTION
                "Count of TTY Input Fifo errors"
        ::= { wfConsole 20 }

    wfSerialPortTable OBJECT-TYPE
        SYNTAX	SEQUENCE OF WfSerialPortEntry
        ACCESS	not-accessible
        STATUS	mandatory
        DESCRIPTION
                "Configuration of system serial port(s)"
        ::= { wfSerialPortGroup 1 }

    wfSerialPortEntry OBJECT-TYPE
        SYNTAX	WfSerialPortEntry
        ACCESS	not-accessible
        STATUS	mandatory
        DESCRIPTION
                "Information for each serial port."
        INDEX	{ wfSerialPortNumber }
        ::= { wfSerialPortTable 1 }

    WfSerialPortEntry ::= SEQUENCE {
    	    wfSerialPortDelete
    		INTEGER,
    	    wfSerialPortDisable
    		INTEGER,
    	    wfSerialPortState
    		INTEGER,
    	    wfSerialPortNumber
    		INTEGER,
    	    wfSerialPortName
    		DisplayString,
    	    wfSerialPortSlot
    		INTEGER,
    	    wfSerialPortType
    		INTEGER,
    	    wfSerialPortBaudRate
    		INTEGER,
    	    wfSerialPortDataBits
    		INTEGER,
    	    wfSerialPortParity
    		INTEGER,
    	    wfSerialPortStopBits
    		INTEGER,
    	    wfSerialPortModemEnable
    		INTEGER,
    	    wfSerialPortLinesPerScreen
    		INTEGER,
    	    wfSerialPortMoreEnable
    		INTEGER,
    	    wfSerialPortPrompt
    		DisplayString,
    	    wfSerialPortLoginTimeOut
    		INTEGER,
    	    wfSerialPortPasswordTimeOut
    		INTEGER,
    	    wfSerialPortCommandTimeOut
    		INTEGER,
    	    wfSerialPortLoginRetries
    		INTEGER,
    	    wfSerialPortTotalLogins
    		Counter,
    	    wfSerialPortUserLoginErrors
    		Counter,
    	    wfSerialPortManagerLoginErrors
    		Counter,
    	    wfSerialPortOtherLoginErrors
    		Counter,
    	    wfSerialPortTtyFrameErrors
    		Counter,
    	    wfSerialPortTtyOverrunErrors
    		Counter,
    	    wfSerialPortTtyParityErrors
    		Counter,
    	    wfSerialPortTtyInfifoErrors
    		Counter,
    	    wfSerialPortInitialSearchPath
    		DisplayString,
    	    wfSerialPortManagerAutoScript
    		DisplayString,
    	    wfSerialPortUserAutoScript
    		DisplayString,
    	    wfSerialPortUserAbortLogoutDisable
    		INTEGER,
    	    wfSerialPortHistoryDepth
    		INTEGER,
	    wfSerialPortAutoSaveNumFiles
    		INTEGER,
	    wfSerialPortAutoSaveVolume
    		DisplayString,
            wfSerialPortModemIdSwRev
                DisplayString,
            wfSerialPortModemIdHwRev
                DisplayString,
            wfSerialPortModemLineState
                INTEGER,
            wfSerialPortModemCfgFactoryDefaults
                INTEGER,
            wfSerialPortModemCfgInitString
                DisplayString,
            wfSerialPortModemCfgDefaultString
                DisplayString,
            wfSerialPortModemCfgResultCodeString
                DisplayString,
            wfSerialPortModemCfgState
                INTEGER,
            wfSerialPortModemCfgCountry
                INTEGER,
            wfSerialPortModemInitState
                INTEGER
        }

    wfSerialPortDelete OBJECT-TYPE
        SYNTAX	INTEGER {
    		    created(1),
    		    deleted(2)
    		}
        ACCESS	read-write
        STATUS	mandatory
        DESCRIPTION
                "Flag to indicate Serial Port instance deletion"
        DEFVAL	{ created }
        ::= { wfSerialPortEntry 1 }

    wfSerialPortDisable OBJECT-TYPE
        SYNTAX	INTEGER {
    		    enabled(1),
    		    disabled(2)
    		}
        ACCESS	read-write
        STATUS	mandatory
        DESCRIPTION
                "Enable or disable this Serial Port"
        DEFVAL	{ enabled }
        ::= { wfSerialPortEntry 2 }

    wfSerialPortState OBJECT-TYPE
        SYNTAX	INTEGER {
    		    up(1),
    		    down(2),
    		    init(3),
    		    notpresent(4)
    		}
        ACCESS	read-only
        STATUS	mandatory
        DESCRIPTION
                "The state of this Serial Port"
        DEFVAL	{ notpresent }
        ::= { wfSerialPortEntry 3 }

    wfSerialPortNumber OBJECT-TYPE
        SYNTAX	INTEGER
        ACCESS	read-only
        STATUS	mandatory
        DESCRIPTION
                "Serial Port number"
        ::= { wfSerialPortEntry 4 }

    wfSerialPortName OBJECT-TYPE
        SYNTAX	DisplayString
        ACCESS	read-only
        STATUS	mandatory
        DESCRIPTION
                "Serial Port name"
        ::= { wfSerialPortEntry 5 }

    wfSerialPortSlot OBJECT-TYPE
        SYNTAX	INTEGER
        ACCESS	read-only
        STATUS	mandatory
        DESCRIPTION
                "Slot number of Serial Port session"
        DEFVAL	{ 0 }
        ::= { wfSerialPortEntry 6 }

    wfSerialPortType OBJECT-TYPE
        SYNTAX	INTEGER {
    		    ti(1),
    		    printer(2),
                    rtelnet(3)
    		}
        ACCESS	read-write
        STATUS	mandatory
        DESCRIPTION
                "Type of Serial Port"
        DEFVAL	{ ti }
        ::= { wfSerialPortEntry 7 }

    wfSerialPortBaudRate OBJECT-TYPE
        SYNTAX	INTEGER
        ACCESS	read-write
        STATUS	mandatory
        DESCRIPTION
                "Baud rate configured on this Serial Port"
        DEFVAL	{ 9600 }
        ::= { wfSerialPortEntry 8 }

    wfSerialPortDataBits OBJECT-TYPE
        SYNTAX	INTEGER
        ACCESS	read-write
        STATUS	mandatory
        DESCRIPTION
                "Number of data bits configured on this Serial Port"
        DEFVAL	{ 8 }
        ::= { wfSerialPortEntry 9 }

    wfSerialPortParity OBJECT-TYPE
        SYNTAX	INTEGER {
    		    none(1),
    		    odd(2),
    		    even(3)
    		}
        ACCESS	read-write
        STATUS	mandatory
        DESCRIPTION
                "Type of parity configured on this Serial Port"
        DEFVAL	{ none }
        ::= { wfSerialPortEntry 10 }

    wfSerialPortStopBits OBJECT-TYPE
        SYNTAX	INTEGER {
    		    s1bit(1),
    		    s15bit(2),
    		    s2bit(3)
    		}
        ACCESS	read-write
        STATUS	mandatory
        DESCRIPTION
                "Number of stop bits configured on this Serial Port"
        DEFVAL	{ s1bit }
        ::= { wfSerialPortEntry 11 }

    wfSerialPortModemEnable OBJECT-TYPE
        SYNTAX	INTEGER {
    		    enabled(1),
    		    disabled(2)
    		}
        ACCESS	read-write
        STATUS	mandatory
        DESCRIPTION
                "Enable the Serial Port to run with modem leads enabled"
        DEFVAL	{ disabled }
        ::= { wfSerialPortEntry 12 }

    wfSerialPortLinesPerScreen OBJECT-TYPE
        SYNTAX	INTEGER
        ACCESS	read-write
        STATUS	mandatory
        DESCRIPTION
                "Number of lines which can be displayed in one screen on the
                Serial Port"
        DEFVAL	{ 24 }
        ::= { wfSerialPortEntry 13 }

    wfSerialPortMoreEnable OBJECT-TYPE
        SYNTAX	INTEGER {
    		    enabled(1),
    		    disabled(2)
    		}
        ACCESS	read-write
        STATUS	mandatory
        DESCRIPTION
                "Enable the 'more' feature on the Serial Port"
        DEFVAL	{ enabled }
        ::= { wfSerialPortEntry 14 }

    wfSerialPortPrompt OBJECT-TYPE
        SYNTAX	DisplayString
        ACCESS	read-write
        STATUS	mandatory
        DESCRIPTION
                "Character string which will be used as the system prompt on
                the Serial Port"
        ::= { wfSerialPortEntry 15 }

    wfSerialPortLoginTimeOut OBJECT-TYPE
        SYNTAX	INTEGER(1..99)
        ACCESS	read-write
        STATUS	mandatory
        DESCRIPTION
                "IF MODEM_ENABLED then time out in minutes to HUP when at the
                login prompt"
        DEFVAL	{ 1 }
        ::= { wfSerialPortEntry 16 }

    wfSerialPortPasswordTimeOut OBJECT-TYPE
        SYNTAX	INTEGER(1..99)
        ACCESS	read-write
        STATUS	mandatory
        DESCRIPTION
                "Timout on Password entry"
        DEFVAL	{ 1 }
        ::= { wfSerialPortEntry 17 }

    wfSerialPortCommandTimeOut OBJECT-TYPE
        SYNTAX	INTEGER(1..99)
        ACCESS	read-write
        STATUS	mandatory
        DESCRIPTION
                "IF MODEM_ENABLED then time out in minutes to HUP when at the
                command prompt"
        DEFVAL	{ 15 }
        ::= { wfSerialPortEntry 18 }

    wfSerialPortLoginRetries OBJECT-TYPE
        SYNTAX	INTEGER(1..99)
        ACCESS	read-write
        STATUS	mandatory
        DESCRIPTION
                "IF MODEM_ENABLED then limit # of login attempts then HUP"
        DEFVAL	{ 3 }
        ::= { wfSerialPortEntry 19 }

    wfSerialPortTotalLogins OBJECT-TYPE
        SYNTAX	Counter
        ACCESS	read-only
        STATUS	mandatory
        DESCRIPTION
                "Total number of TI login attempts on Serial Port"
        ::= { wfSerialPortEntry 20 }

    wfSerialPortUserLoginErrors OBJECT-TYPE
        SYNTAX	Counter
        ACCESS	read-only
        STATUS	mandatory
        DESCRIPTION
                "Total number of FAILED User login attempts on Serial Port"
        ::= { wfSerialPortEntry 21 }

    wfSerialPortManagerLoginErrors OBJECT-TYPE
        SYNTAX	Counter
        ACCESS	read-only
        STATUS	mandatory
        DESCRIPTION
                "Total number of FAILED Manager login attempts on Serial Port"
        ::= { wfSerialPortEntry 22 }

    wfSerialPortOtherLoginErrors OBJECT-TYPE
        SYNTAX	Counter
        ACCESS	read-only
        STATUS	mandatory
        DESCRIPTION
                "Total number of FAILED Other login attempts on Serial Port"
        ::= { wfSerialPortEntry 23 }

    wfSerialPortTtyFrameErrors OBJECT-TYPE
        SYNTAX	Counter
        ACCESS	read-only
        STATUS	mandatory
        DESCRIPTION
                "Count of TTY Frame errors on Serial Port"
        ::= { wfSerialPortEntry 24 }

    wfSerialPortTtyOverrunErrors OBJECT-TYPE
        SYNTAX	Counter
        ACCESS	read-only
        STATUS	mandatory
        DESCRIPTION
                "Count of TTY Overrun errors on Serial Port"
        ::= { wfSerialPortEntry 25 }

    wfSerialPortTtyParityErrors OBJECT-TYPE
        SYNTAX	Counter
        ACCESS	read-only
        STATUS	mandatory
        DESCRIPTION
                "Count of TTY Parity errors on Serial Port"
        ::= { wfSerialPortEntry 26 }

    wfSerialPortTtyInfifoErrors OBJECT-TYPE
        SYNTAX	Counter
        ACCESS	read-only
        STATUS	mandatory
        DESCRIPTION
                "Count of TTY Input Fifo errors on Serial Port"
        ::= { wfSerialPortEntry 27 }

    wfSerialPortInitialSearchPath OBJECT-TYPE
        SYNTAX	DisplayString
        ACCESS	read-write
        STATUS	obsolete
        DESCRIPTION
                "Example:  'A:;1:;2:' or '2:;4:6:;9:"
        ::= { wfSerialPortEntry 28 }

    wfSerialPortManagerAutoScript OBJECT-TYPE
        SYNTAX	DisplayString
        ACCESS	read-write
        STATUS	mandatory
        DESCRIPTION
                "for each login."
        ::= { wfSerialPortEntry 29 }

    wfSerialPortUserAutoScript OBJECT-TYPE
        SYNTAX	DisplayString
        ACCESS	read-write
        STATUS	mandatory
        DESCRIPTION
                "for each login."
        ::= { wfSerialPortEntry 30 }

    wfSerialPortUserAbortLogoutDisable OBJECT-TYPE
        SYNTAX	INTEGER {
    		    enabled(1),
    		    disabled(2)
    		}
        ACCESS	read-write
        STATUS	mandatory
        DESCRIPTION
                "a USER from escaping out of the User Autoscript"
        DEFVAL	{ disabled }
        ::= { wfSerialPortEntry 31 }

    wfSerialPortHistoryDepth OBJECT-TYPE
        SYNTAX	INTEGER(1..40)
        ACCESS	read-write
        STATUS	mandatory
        DESCRIPTION
                "TI command history table size"
        DEFVAL	{ 20 }
        ::= { wfSerialPortEntry 32 }

    wfSerialPortAutoSaveNumFiles OBJECT-TYPE
        SYNTAX	INTEGER(0..99)
        ACCESS	read-write
        STATUS	mandatory
        DESCRIPTION
                "Number of times AutoSave will save the log
		0 - disable the AutoSave log"
        DEFVAL	{ 0 }
        ::= { wfSerialPortEntry 33 }

    wfSerialPortAutoSaveVolume OBJECT-TYPE
        SYNTAX	DisplayString
        ACCESS	read-write
        STATUS	mandatory
        DESCRIPTION
                "Volume, to which AutoSave will save logs
		Example:  'A:' or '2:'"
        ::= { wfSerialPortEntry 34 }
       wfSerialPortModemIdSwRev OBJECT-TYPE
          SYNTAX   DisplayString (SIZE (0..79))
          ACCESS   read-only
          STATUS   mandatory
          DESCRIPTION
                  "A textual description of the modem's
                   firmware version number."
          ::= { wfSerialPortEntry 35 }

       wfSerialPortModemIdHwRev OBJECT-TYPE
          SYNTAX   DisplayString (SIZE (0..79))
          ACCESS   read-only
          STATUS   mandatory
          DESCRIPTION
                  "A textual description of the revision
                   number of the modem daughter card."
          ::= { wfSerialPortEntry 36 }

       wfSerialPortModemLineState OBJECT-TYPE
          SYNTAX  INTEGER {
                       unknown(1),
                       onHook(2),
                       offHook(3),
                       connected(4),
                       busiedOut(5),
                       reset(6)
                  }
          ACCESS  read-only
          STATUS  mandatory
          DESCRIPTION
                  "Indicates the state of the modem."
          DEFVAL { unknown }
          ::= { wfSerialPortEntry 37 } 

       wfSerialPortModemCfgFactoryDefaults OBJECT-TYPE
          SYNTAX  INTEGER {
                       enabled(1),
                       disabled(2)
                  }
          ACCESS  read-write
          STATUS  mandatory
          DESCRIPTION
                  "This object indicates if factory defaults are to be loaded.
                   If set to enabled(1), factory defaults are loaded. If set
                   to disabled(2), the initialization string in 
                   wfModemCfgInitString is not sent to the modem."
          DEFVAL { enabled }
          ::= { wfSerialPortEntry 38 }

       wfSerialPortModemCfgInitString OBJECT-TYPE
          SYNTAX  DisplayString
          ACCESS  read-write
          STATUS  mandatory
          DESCRIPTION
                  "An initialization string that will be sent to the modem
                   each time the modem is rebooted."
          ::= { wfSerialPortEntry 39 }

       wfSerialPortModemCfgDefaultString OBJECT-TYPE
          SYNTAX  DisplayString
          ACCESS  read-only
          STATUS  mandatory
          DESCRIPTION
                  "The string contains AT comands for initializing the
                   modem every time the modem comes up, regardless of 
                   configuration."
          ::= { wfSerialPortEntry 40 }

       wfSerialPortModemCfgResultCodeString OBJECT-TYPE
          SYNTAX  DisplayString
          ACCESS  read-only
          STATUS  mandatory
          DESCRIPTION
                  "The ASCII response string returned by the modem.
                   Response strings will be returned in response to
                   last command to the modem and in response to activity
                   on the line."
          ::= { wfSerialPortEntry 41 }

       wfSerialPortModemCfgState OBJECT-TYPE
          SYNTAX  INTEGER {
                       cfgIdle(1),
                       cfgInProgress(2),
                       cfgResponseReturned(3)
                  }
          ACCESS  read-write
          STATUS  mandatory
          DESCRIPTION
                  "Indicates the state of AT command processing. When a
                   new initialization string is to be sent to the modem, 
                   the sender sets the state to cfgInProgress(2). After the
                   command has been sent to the modem, and a result code
                   has been returned, the state is set to 
                   cfgResponseReturned(3). Once the sender
                   has received the return code, the sender sets the state
                   to cfgIdle(1)."
          DEFVAL { cfgIdle }
          ::= { wfSerialPortEntry 42 }

       wfSerialPortModemCfgCountry OBJECT-TYPE
          SYNTAX   INTEGER {
                        northAmerica(1),
                        japan(2),
                        uk(3),
                        germany(4)
                    }
          ACCESS    read-write
          STATUS    mandatory
          DESCRIPTION
                   "Identifies the country the modem is designed to operate
                    in. This object is not read from the modem directly.
                    It must be entered manually when configuring the modem."
          DEFVAL { northAmerica }
          ::= { wfSerialPortEntry 43 }

        wfSerialPortModemInitState OBJECT-TYPE
          SYNTAX       INTEGER {
                            startup(1),
                            getInfo(3),
                            setDefaults(4),
                            initialization(5),
                            initComplete(8)
                       }
          ACCESS       read-only
          STATUS       mandatory
          DESCRIPTION
             "Indictes the state of the modem initialization sequence. The state will
              freeze in the state that fails when a failure is detected. Otherwise,
              the state will be set to initComplete when initialization completes
              successfully. The state number correspond to those for the COM port
modems. Some of the states are not valid for the console modem."
          ::= { wfSerialPortEntry 44 }

    END  -- Wellfleet-CONSOLE-MIB
