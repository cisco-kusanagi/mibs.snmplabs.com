SHIVA-VPN-UTILIZATION-MIB DEFINITIONS ::= BEGIN

-- This MIB contains objects for monitoring system utilization
-- of Shiva VPN products.

IMPORTS
  OBJECT-TYPE
      FROM RFC-1212
  vpnUtilization
      FROM SHIVA-VPN-DEF;

  loadAverage1Minute OBJECT-TYPE
      SYNTAX INTEGER(0..1000000)
      ACCESS read-only
      STATUS mandatory
      DESCRIPTION
             "This is a measure of the offered compute load to the CPU
             of the system as a percentage of CPU capacity.  A value of
             100 means that there is just enough load to keep the CPU
             fully occupied.  Values over 100 indicate a backlog of
             offered computes.  The system will perform acceptably
             with values up to 1000.

             This variable offers the load average over approximately
             the last 1 minute."
      ::= { vpnUtilization 1 }    

  loadAverage5Minutes OBJECT-TYPE
      SYNTAX INTEGER(0..1000000)
      ACCESS read-only
      STATUS mandatory
      DESCRIPTION
             "This is a measure of the offered compute load to the CPU
             of the system as a percentage of CPU capacity.  A value of
             100 means that there is just enough load to keep the CPU
             fully occupied.  Values over 100 indicate a backlog of
             offered computes.  The system will perform acceptably
             with values up to 1000.

             This variable offers the load average over approximately
             the last 5 minutes."
      ::= { vpnUtilization 2 }    

  loadAverage15Minutes OBJECT-TYPE
      SYNTAX INTEGER(0..1000000)
      ACCESS read-only
      STATUS mandatory
      DESCRIPTION
             "This is a measure of the offered compute load to the CPU
             of the system as a percentage of CPU capacity.  A value of
             100 means that there is just enough load to keep the CPU
             fully occupied.  Values over 100 indicate a backlog of
             offered computes.  The system will perform acceptably
             with values up to 1000.

             This variable offers the load average over approximately
             the last 15 minutes."
      ::= { vpnUtilization 3 }    
  totalBytesPerSecIn OBJECT-TYPE
      SYNTAX INTEGER(0..1000000)
      ACCESS read-only
      STATUS mandatory
      DESCRIPTION
             "This is the number of bytes per second received and
             decrypted from all tunnels in the system, averaged over
             approximately the last minute."
     ::= { vpnUtilization 4 }    
  totalBytesPerSecOut OBJECT-TYPE
      SYNTAX INTEGER(0..1000000)
      ACCESS read-only
      STATUS mandatory
      DESCRIPTION
             "This is the number of bytes per second transmitted and
             encrypted from all tunnels in the system, averaged over
             approximately the last minute."
      ::= { vpnUtilization 5 }    

END
