BRS-MIB DEFINITIONS ::= BEGIN

------------------------------------------------------------------
-- Bandwidth Reservation MIB (SNMP Version 1 Format)
------------------------------------------------------------------
--
--    This MIB defines the enterprise specific management
--    objects for the Bandwidth Reservation System (BRS).
--
--    This definition is based on the Proteon BRS MIB with
--    new support for IBM enhancements to the BRS protocol.
--    It is, however, still anchored under the Proteon
--    subtree.
--
--    Note that even though BRS is supported for PPP and
--    FR links, this MIB currently only provides information
--    for BRS running on PPP links.
--
--    This MIB is defined in the SNMP version 1 SMI format.
--
--    February 24, 1997
--
--    Contact Information:
--
--            Randy Worzella
--            IBM Corp.
--            G420/664
--            Research Triangle Park, NC 27709
--
--            phone:    919-254-2202
--            email:    worzella@ralvm29.vnet.ibm.com
--
------------------------------------------------------------------

IMPORTS
        enterprises, Counter, IpAddress
                FROM RFC1155-SMI
        OBJECT-TYPE
                FROM RFC-1212
        ifIndex, DisplayString
                FROM RFC1213-MIB;

-- This is the MIB module for Proteon BRS

proteon         OBJECT IDENTIFIER ::= { enterprises 1 }

proAdmin        OBJECT IDENTIFIER ::= { proteon 1 }

proFeature      OBJECT IDENTIFIER ::= { proAdmin 7 }

proFeatureBrs   OBJECT IDENTIFIER ::= { proFeature 1 }

proBrsMib       OBJECT IDENTIFIER ::= { proFeatureBrs 1 }

-- BRS types
BRSPriority ::= INTEGER { low(1), normal(2), high(3), urgent(4) }

-- Number of interfaces enabled for BRS
proBrsNumber OBJECT-TYPE
        SYNTAX INTEGER
        ACCESS read-only
        STATUS mandatory
        DESCRIPTION
                "The number of interfaces enabled for BRS."
        ::= { proBrsMib 1 }


-- Bandwidth Reservation Port group
--      The term "Port" is used to be consistent with the RS232 mib
--      and because "Interfaces" start at zero, whereas "Ports"
--      start at one.

proBrsPortTable OBJECT-TYPE
        SYNTAX SEQUENCE OF ProBrsPortEntry
        ACCESS not-accessible
        STATUS mandatory
        DESCRIPTION
                "A list of BRS ports/interfaces.  The number of entries is
                 given by the value of proBrsNumber.  Only ports/interfaces
                 that have BRS enabled will appear in this table."
        ::= { proBrsMib 2 }

proBrsPortEntry OBJECT-TYPE
        SYNTAX ProBrsPortEntry
        ACCESS not-accessible
        STATUS mandatory
        DESCRIPTION
                "Status and parameter values for an interface."
        INDEX { ifIndex }
        ::= { proBrsPortTable 1 }

ProBrsPortEntry ::=
        SEQUENCE {
                proBrsClassNumber
                        INTEGER,
                proBrsDefaultClassName
                        DisplayString(SIZE(0..10)),
                proBrsDefaultPriority
                        BRSPriority
        }

proBrsClassNumber OBJECT-TYPE
        SYNTAX INTEGER
        ACCESS read-only
        STATUS mandatory
        DESCRIPTION
                "The number of classes on this interface."
        ::= { proBrsPortEntry 1 }

proBrsDefaultClassName OBJECT-TYPE
        SYNTAX DisplayString(SIZE(0..10))
        ACCESS read-only
        STATUS mandatory
        DESCRIPTION
                "The name of the default class."
        ::= { proBrsPortEntry 2 }

proBrsDefaultPriority OBJECT-TYPE
        SYNTAX BRSPriority
        ACCESS read-only
        STATUS mandatory
        DESCRIPTION
                "The default priority for the default class."
        ::= { proBrsPortEntry 3 }


-- Bandwidth Reservation Class Group
--     The BRS Class group is indexed by port number and
--     Class ID.  This table reports on the class information
--     like Class Name, Allocation and traffic.

proBrsClassTable OBJECT-TYPE
        SYNTAX SEQUENCE OF ProBrsClassEntry
        ACCESS not-accessible
        STATUS mandatory
        DESCRIPTION
                "A list of BRS Classes per interface.  The number of
                 entries is given by the value of proBrsClassNumber in
                 the previous proBrsPortTable group."
        ::= { proBrsMib 3 }

proBrsClassEntry OBJECT-TYPE
        SYNTAX ProBrsClassEntry
        ACCESS not-accessible
        STATUS mandatory
        DESCRIPTION
                "Status and parameter values for a class."
        INDEX { ifIndex, proBrsClassId }
        ::= { proBrsClassTable 1 }

ProBrsClassEntry ::=
        SEQUENCE {
                proBrsClassId
                        INTEGER,
                proBrsClassName
                        DisplayString(SIZE(0..10)),
                proBrsClassAlloc
                        INTEGER,
                proBrsClassBytes
                        INTEGER,
                proBrsClassPkts
                        INTEGER,
                proBrsClassDiscs
                        INTEGER
        }

-- Items within the BRS class entry

proBrsClassId OBJECT-TYPE
        SYNTAX INTEGER
        ACCESS read-only
        STATUS mandatory
        DESCRIPTION
                "A unique ID for each class.  Its value ranges
                 between 1 and the value of proBrsClassNumber in the
                 proBrsPortTable."
        ::= { proBrsClassEntry 1 }


proBrsClassName OBJECT-TYPE
        SYNTAX DisplayString(SIZE(0..10))
        ACCESS read-only
        STATUS mandatory
        DESCRIPTION
                "The class name."
        ::= { proBrsClassEntry 2 }

proBrsClassAlloc OBJECT-TYPE
        SYNTAX INTEGER
        ACCESS read-write
        STATUS mandatory
        DESCRIPTION
                "Bandwidth Allocation percentage."
        ::= { proBrsClassEntry 3 }

proBrsClassBytes OBJECT-TYPE
        SYNTAX INTEGER
        ACCESS read-only
        STATUS mandatory
        DESCRIPTION
                "The number of bytes transmitted in this class."
        ::= { proBrsClassEntry 4 }

proBrsClassPkts OBJECT-TYPE
        SYNTAX INTEGER
        ACCESS read-only
        STATUS mandatory
        DESCRIPTION
                "The number of packets transmitted in this class."
        ::= { proBrsClassEntry 5 }

proBrsClassDiscs OBJECT-TYPE
        SYNTAX INTEGER
        ACCESS read-only
        STATUS mandatory
        DESCRIPTION
                "The number of bytes discarded in this class."
        ::= { proBrsClassEntry 6 }

-- Bandwidth Reservation Protocol/Filter Group
--    This group contains information that details what
--    protocols or filters are assigned to what class and
--    at what priority.  This table is indexed by port,
--    class ID and filter ID.  Seperate groups where not
--    made for protocols and filters as the variables reported
--    are very similar and the difference is only symantic.

proBrsFilterTable OBJECT-TYPE
        SYNTAX SEQUENCE OF ProBrsFilterEntry
        ACCESS not-accessible
        STATUS mandatory
        DESCRIPTION
                "A list of BRS Protocols/Filters."
        ::= { proBrsMib 4 }

proBrsFilterEntry OBJECT-TYPE
        SYNTAX ProBrsFilterEntry
        ACCESS not-accessible
        STATUS mandatory
        DESCRIPTION
                "Status and parameter values for a filter."
        INDEX { ifIndex, proBrsClassId, proBrsFilterId }
        ::= { proBrsFilterTable 1 }

ProBrsFilterEntry ::=
        SEQUENCE {
                proBrsFilterId
                        INTEGER,
                proBrsFilterName
                        DisplayString(SIZE(0..10)),
                proBrsFilterPriority
                        INTEGER,
                proBrsFilterPortType
                        INTEGER,
                proBrsFilterLowPortNum
                        INTEGER,
                proBrsFilterHighPortNum
                        INTEGER,
                proBrsFilterIpAddr
                        IpAddress,
                proBrsFilterTag
                        INTEGER
        }

-- Items within the BRS filter entry

proBrsFilterId OBJECT-TYPE
        SYNTAX INTEGER
        ACCESS read-only
        STATUS mandatory
        DESCRIPTION
                "A unique value for each filter.  Its value is the
                 protocol number or a filter number + the maximum
                 protocol number."
        ::= { proBrsFilterEntry 1 }


proBrsFilterName OBJECT-TYPE
        SYNTAX DisplayString(SIZE(0..10))
        ACCESS read-only
        STATUS mandatory
        DESCRIPTION
                "The filter name."
        ::= { proBrsFilterEntry 2 }

proBrsFilterPriority OBJECT-TYPE
        SYNTAX INTEGER { low(1), normal(2), high(3), urgent(4) }
        ACCESS read-only
        STATUS mandatory
        DESCRIPTION
                "The priority of the filter."
        ::= { proBrsFilterEntry 3 }

proBrsFilterPortType OBJECT-TYPE
        SYNTAX INTEGER {
                         tcp(1),
                         udp(2),
                         other(3)
                       }
        ACCESS read-only
        STATUS mandatory
        DESCRIPTION
                "This field is relevent to the UDP_TCP port filters only
                 (where proBRSFilterId is UDP_TCP1, UDP_TCP2, UDP_TCP3,
                  UDP_TCP4 or UDP_TCP5).
                 It signifies whether UDP/IP or TCP/IP traffic should be
                 filtered. Valid values are tcp(1), udp(2) or other(3),
                 which is specified for other protocol/filter types."
        ::= { proBrsFilterEntry 4 }

proBrsFilterLowPortNum OBJECT-TYPE
        SYNTAX INTEGER (0..65535)
        ACCESS read-only
        STATUS mandatory
        DESCRIPTION
                "This field is relevent to the UDP_TCP port filters only
                 (where proBRSFilterId is UDP_TCP1, UDP_TCP2, UDP_TCP3,
                  UDP_TCP4 or UDP_TCP5).
                 It signifies the low end of a range of port numbers on
                 which a UDP_TCP filter is based. Valid values for
                 UDP_TCP filters are from 1 to 65535.

                 This field will be zero for other protocol/filter types."
        ::= { proBrsFilterEntry 5 }

proBrsFilterHighPortNum OBJECT-TYPE
        SYNTAX INTEGER (0..65535)
        ACCESS read-only
        STATUS mandatory
        DESCRIPTION
                 "This is field relevent to the UDP_TCP port filters only
                  (where proBRSFilterId is UDP_TCP1, UDP_TCP2, UDP_TCP3,
                   UDP_TCP4 or UDP_TCP5).
                  It signifies the high end of a range of port numbers. It
                  can range from 1 to 65535 and is equal to or greater
                  than the low port range.

                  This field will be 0 for other protocol/filter types."
        ::= { proBrsFilterEntry 6 }

proBrsFilterIpAddr OBJECT-TYPE
        SYNTAX IpAddress
        ACCESS read-only
        STATUS mandatory
        DESCRIPTION
                 "This field is relevent to the UDP_TCP port filters only.
                  If the IP address is non zero, the IP address and
                  the port number range (defined by the Low Port and High
                  Port) are used together to define a socket in the
                  filtering  criteria for the UDP_TCP filter.
                  If the IP address is zero, only the port range criteria
                  criteria is used for the UDP_TCP filter.

                  This field will be zero for other protocol/filter types."
        ::= { proBrsFilterEntry 7 }

proBrsFilterTag OBJECT-TYPE
        SYNTAX INTEGER (0..64)
        ACCESS read-only
        STATUS mandatory
        DESCRIPTION
                 "This field is relevent only for BRS tags  (where
                  proBRSFilterId is TAG1, TAG2, TAG3, TAG4 or TAG5).

                  The Tag Value identifies a set of filter items
                  associated with a specific tag value via MAC
                  Filtering configuration. The association of a
                  Tag Value with one of the 5 BRS tags allows the set
                  of filtered items to be assigned to a class and
                  priority configured for the BRS tag.

                  Valid values are 1 to 64.

                  This field will be 0 for other protocol/filter types."
        ::= { proBrsFilterEntry 8 }

END
