H323Filter-MIB DEFINITIONS ::= BEGIN

        IMPORTS
                enterprises,
                OBJECT-TYPE,
                Counter
                        FROM RFC1155-SMI
                internetServer
                        FROM InternetServer-MIB;

--      microsoft       OBJECT IDENTIFIER ::= { enterprises 311 }
--      software        OBJECT IDENTIFIER ::= { microsoft 1 }
--      internetServer  OBJECT IDENTIFIER ::= { software 7 }
        wspServer       OBJECT IDENTIFIER ::= { internetServer 12 }
        h323Statistics  OBJECT IDENTIFIER ::= { wspServer 2 }

-- H323 Filter Statistics
	numTotalCalls OBJECT-TYPE
		SYNTAX	INTEGER
		ACCESS	read-only
		STATUS	mandatory
		DESCRIPTION 
			"The number of total calls for H323 Proxy Filter."
		::= { h323Statistics 1 }
	
    numActiveCalls OBJECT-TYPE
		SYNTAX	INTEGER
		ACCESS	read-only
		STATUS	mandatory
		DESCRIPTION 
			"The number of active calls for H323 Proxy Filter."
		::= { h323Statistics 2 }

END
