-- ################################################################################

EXTREME-IDMGR-MIB DEFINITIONS ::= BEGIN

        IMPORTS
                MODULE-IDENTITY     FROM SNMPv2-SMI
                OBJECT-TYPE         FROM SNMPv2-SMI
                NOTIFICATION-TYPE   FROM SNMPv2-SMI
                Integer32           FROM SNMPv2-SMI
                extremeAgent        FROM EXTREME-BASE-MIB;

        extremeIdMgr MODULE-IDENTITY
                LAST-UPDATED "200906100000Z"
                ORGANIZATION "Extreme Networks, Inc."
                CONTACT-INFO "www.extremenetworks.com"
                DESCRIPTION "Extreme Identity Management MIB"
        ::= { extremeAgent 36 }

        extremeIdMgrTraps          OBJECT IDENTIFIER
        ::= { extremeIdMgr 1 }

        extremeIdMgrTrapPrefix     OBJECT IDENTIFIER
        ::= { extremeIdMgrTraps 0 }

        extremeIdMgrMemLevelChange NOTIFICATION-TYPE
                OBJECTS { extremeIdMgrTrapSeverity,
                          extremeIdMgrMemUsageLevel,
                          extremeIdMgrMemUsage,
                          extremeIdMgrMemMaxSize,
                          extremeIdMgrEffectiveStaleAgingTime }
                STATUS      current
                DESCRIPTION
                    "If Identity Management feature is enabled, this trap will be generated when the memory usage level changes."
        ::= { extremeIdMgrTrapPrefix 1 }

-- internal object
        extremeIdMgrTrapSeverity OBJECT-TYPE
                SYNTAX INTEGER {
                    critical(1),
                    error(2),
                    warning(3),
                    notice(4),
                    info(5),
                    debug-summary(6),
                    debug-verbose(7),
                    debug-data(8)
                }
                MAX-ACCESS accessible-for-notify
                STATUS current
                DESCRIPTION
                    "Severity of Identity Management Trap"
        ::= { extremeIdMgrTraps 1}

        extremeIdMgrMemUsageLevel OBJECT-TYPE
                SYNTAX INTEGER {
                     normal(1),
                     high(2),
                     critical(3),
                     maximum(4)
                }
                MAX-ACCESS accessible-for-notify
                STATUS current
                DESCRIPTION
                    "The current memory usage level
                    -normal(1)
                        The Memory usage is within normal usage limits, <= 80% of configured maximum database size.
                    -high(2)
                        The memory usage level is high.  Memory usage is more than 80% and less than or equal to 90% of configured maximum database size.
                    -critical(3)
                        The memory usage level is at critical level. Memory usage is more than 90% of configured maximum database size.
                    -maximum(4)
                        The memory usage level reached to maximum. Memory usage almost at 98% or more of configured maximum database size."
        ::= { extremeIdMgrTraps 2 }

        extremeIdMgrMemUsage  OBJECT-TYPE
                SYNTAX Integer32
                MAX-ACCESS accessible-for-notify
                STATUS current
                DESCRIPTION
                    "The current memory usage (in KBytes)."
        ::= { extremeIdMgrTraps 3}

        extremeIdMgrMemMaxSize  OBJECT-TYPE
                SYNTAX Integer32
                MAX-ACCESS accessible-for-notify
                STATUS current
                DESCRIPTION
                    "Configured identity management maximum database memory size (in KBytes)."
        ::= { extremeIdMgrTraps 4}

        extremeIdMgrEffectiveStaleAgingTime  OBJECT-TYPE
                SYNTAX Integer32
                MAX-ACCESS accessible-for-notify
                STATUS current
                DESCRIPTION
                    "The effective stale aging time because of memory usage level change (in seconds)."
        ::= { extremeIdMgrTraps 5}

END
