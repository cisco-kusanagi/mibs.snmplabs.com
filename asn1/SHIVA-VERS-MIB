-- 	$Id: shiva-vers.asn,v 1.23 1996/08/12 14:58:26 sdaigle Exp $

--
-- 	Copyright 1992, 1993, 1995, 1996 Shiva Corporation
--

--	Shiva systems version MIB

SHIVA-VERS-MIB DEFINITIONS ::= BEGIN

IMPORTS
    	DisplayString
    		FROM RFC1213-MIB
    	OBJECT-TYPE
    		FROM RFC-1212		-- Concise MIB Definitions
    	version
    		FROM SHIVA-MIB;

-- textual convention for Shiva version encoding

	VersionNumber ::=	-- 5 bytes of version information
		OCTET STRING (SIZE (5))
		-- coded as follows:
		-- byte 1:	major release version
		-- byte 2:	dot release version
		-- byte 3:	dot-dot release version
		-- byte 4:	type of release ("letter" in parentheses):
		--		0x10	internal developer
		--		0x20	development checkpoint (d)
		--		0x40	Alpha (a)
		--		0x60	Beta (b)
		--		0x70	Final - release candidate (f)
		--		0x80	Full Release
		--		0x90	Patch (p)
		-- byte 5:	For development checkpoint, alpha, beta,
		--		final, and patch, the sequence number thereof.
		--		For internal developer, the UNIX UID of the
		--		developer.  For full release, 0.
		--
		-- So, if a VersionNumber were 03 05 00 90 0C, 
		-- it would be "3.5p12" in print.  Similarly,
		-- 04 00 00 80 00 would be "4.0" in print,
		-- and 04 00 01 80 00 would be "4.0.1" in print.


    vImage OBJECT-TYPE
	SYNTAX	VersionNumber
	ACCESS  read-only
	STATUS  mandatory
	DESCRIPTION
		"The version number of the image represented
		as seperate octets."
	::= { version 1 }

    vPROM OBJECT-TYPE
	SYNTAX	VersionNumber
	ACCESS  read-only
	STATUS  mandatory
	DESCRIPTION
		"The version number of the PROM or VROM."
	::= { version 2 }

    vHardware OBJECT-TYPE
	SYNTAX	INTEGER {
		fp123(1),		-- Kinetics FastPath 1/2/3
		fp4(2),			-- Kinetics or Shiva FastPath 4
		fp5(3),			-- Shiva FastPath 5
		nme1(4),		-- Shiva NetModem/E
		lre1(5),		-- Shiva LanRover/4E, LanRover/8E
		lrt1(6),		-- Shiva LanRover/4T, LanRover/8T
		ibm8235-002(7), 	-- IBM 8235-002 (E Classic)
		ibm8235-001(8), 	-- IBM 8235-001 (T Classic)
		lreplus(9),		-- Shiva LanRover/E PLUS
		lrtplus(10),		-- Shiva LanRover/T PLUS
		ibm8235-012(11),	-- IBM 8235-012/032 (E PLUS)
		ibm8235-011(12),	-- IBM 8235-011/031 (T PLUS)
		ibm8235-022(13),	-- IBM 8235-022/052 (E 115)
		ibm8235-021(14),	-- IBM 8235-021/051 (T 115)
		hp-j2624a(15),		-- HP Dial-A-LAN J2624A (4-port async)
		hp-j2623a(16),		-- HP Dial-A-LAN J2623A (2-port modem)
		ibm8235e-Module(17),	-- IBM 8235E-Module
		ibm8235t-Module(18),	-- IBM 8235T-Module
		racal-ERAS(19),		-- RACAL-Datacom
		rapporteplus(20),	-- Nortel Rapport DS 8E
		rapporttplus(21),	-- Nortel Rapport DS 8T
		lreaccessswitch(22),	-- Shiva LanRover Access Switch
					-- (Ethernet)
		lrtaccessswitch(23),	-- Shiva LanRover Access Switch
					-- (Token-Ring)
		rapport112(24),	        -- Nortel Rapport Dialup Switch 112E
		ibm8235-i40e(25),	-- IBM 8235-I40E DIALs Switch
		ibm8235-i40t(26),	-- IBM 8235-I40T DIALs Switch
		-- 27			   Cancelled
		rapport112t(28),	-- Nortel Rapport Token Ring Dialup
					-- Switch 112
		-- 29			   Cancelled
		lanroverd56(30),	-- Shiva LanRover D56
		lrxp16(31)		-- Shiva LanRover/E XP16
		-- 32			   Cancelled
		-- 33			   Cancelled
		}
	ACCESS  read-only
	STATUS  mandatory
	DESCRIPTION
		"The hardware platform ID."
	::= { version 3 }

    vSoftwareArch OBJECT-TYPE
	SYNTAX	DisplayString
	ACCESS  read-only
	STATUS  mandatory
	DESCRIPTION
		"The name of the software architecture provided
		by the PROM or VROM"
	::= { version 4 }

    vHardwareRev OBJECT-TYPE
	SYNTAX	INTEGER
	ACCESS  read-only
	STATUS  mandatory
	DESCRIPTION
		"The h/w platform revision register"
	::= { version 5 }

    vBoot OBJECT-TYPE
	SYNTAX	VersionNumber
	ACCESS  read-only
	STATUS  mandatory
	DESCRIPTION
		"The version number of the boostrap PROM that loads the VROM."
	::= { version 6 }

END
