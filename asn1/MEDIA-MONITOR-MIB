-- extracted from draft-welch-mdi-02.txt
-- at Thu Jun 16 06:33:15 2005

   MEDIA-MONITOR-MIB DEFINITIONS ::= BEGIN 
    
   IMPORTS 
       MODULE-IDENTITY,  
       OBJECT-TYPE,  
       Integer32, 
       Unsigned32,  
       mib-2, 
       NOTIFICATION-TYPE, 
       OBJECT-IDENTITY, 
       IpAddress 
           FROM SNMPv2-SMI                  -- RFC2578 
       DisplayString 
           FROM SNMPv2-TC 
       MODULE-COMPLIANCE, OBJECT-GROUP, 
       NOTIFICATION-GROUP 
           FROM SNMPv2-CONF;                -- RFC2580 
    
   mediaMonitorMIB MODULE-IDENTITY 
       LAST-UPDATED "200404040000Z"         -- 04 April 2004 
    
       ORGANIZATION " xx " 
       CONTACT-INFO 
         "IneoQuest Technologies, Inc. 
              Postal: 170 Forbes Boulevard 
                      Mansfield, MA, 02048  
              Tel:    +1 508 618 0312 
              E-mail: jim.welch@ineoquest.com" 
    
       DESCRIPTION 
           "The media Monitor MIB (MEDIA-MONITOR-MIB) provides 
           Metrics for Monitoring IP streaming media Flows." 
    
        --  Revision history 
    
        REVISION     "200404040000Z"         -- 04 April 2004 
        DESCRIPTION 
            "Initial version, published as RFC xxxx. (this RFC)" 
    
       ::= { xxxx } 
    
    -- Top level structure of the MIB 
    
     mediaMonitorObjects    OBJECT IDENTIFIER ::= { mediaMonitorMIB 1 } 
    
   ipMediaStreamMonitorTable OBJECT-TYPE 
       SYNTAX      SEQUENCE OF IpMediaStreamMonitorEntry 
       MAX-ACCESS  not-accessible 
       STATUS      current 
       DESCRIPTION 
           "IP Stream Monitor Table. This table is indexed by the 
           Stream Handle. This Table only shows the currently ACTIVE 
           Streams." 
       ::= { mediaMonitorObjects 1 } 
    
   ipMediaStreamMonitorEntry OBJECT-TYPE 
       SYNTAX IpMediaStreamMonitorEntry 
       MAX-ACCESS not-accessible 
       STATUS     current 
       DESCRIPTION 
            "IP Stream Monitor Table Entry." 
       INDEX  { ipMediaStreamMonitorHandle } 
       ::= { ipMediaStreamMonitorTable 1 } 
    
   IpMediaStreamMonitorEntry ::= SEQUENCE { 
       ipMediaStreamHandle 
           Unsigned32, 
       ipMediaStreamSourceIpAddress 
           IpAddress, 
       ipMediaStreamSourcePort 
           Unsigned32, 
       ipMediaStreamDestinationIpAddress 
           IpAddress, 
       ipMediaStreamDestinationPort 
           Unsigned32, 
       ipMediaStreamBitRate 
           Unsigned32, 
       ipMediaStreamInterval 
           Unsigned32, 
       ipMediaStreamStartTime 
           DisplayString, 
        ipMediaStreamMDIDelayFactor 
           Unsigned32, 
       ipMediaStreamMDILossRate 
           Unsigned32, 
       ipMediaStreamMDIDFThreshold 
           Unsigned32, 
       ipMediaStreamMDILRThreshold 
           Unsigned32, 
       ipMediaStreamMDIDFErrorIntervals 
           Unsigned32 
       ipMediaStreamMonitorMDIMLRErrorIntervals 
           Unsigned32 
           } 

   ipMediaStreamHandle OBJECT-TYPE 
       SYNTAX  Unsigned32 
       MAX-ACCESS read-only 
       STATUS     current 
       DESCRIPTION 
            "Table is indexed by stream Handle. The table has one row 
            for each Media Stream detected from the Ip Interface.  The 
            Stream Handle shall be a unique value for the life of the 
            stream." 
       ::= { ipMediaStreamMonitorEntry 1 } 
    
   ipMediaStreamSourceIpAddress OBJECT-TYPE 
       SYNTAX     IpAddress  
       MAX-ACCESS read-only 
       STATUS     current 
       DESCRIPTION 
              "Source IpAddress for the Stream indexed by the Stream 
              Handle." 
       ::= { ipMediaStreamMonitorEntry 2 } 
    
   ipMediaStreamSourcePort OBJECT-TYPE 
       SYNTAX   Unsigned32  
       MAX-ACCESS read-only 
       STATUS     current 
       DESCRIPTION 
              "The Source port for the Stream indexed by the Stream 
              Handle." 
       ::= { ipMediaStreamMonitorEntry 3 } 
    
   ipMediaStreamDestinationIpAddress OBJECT-TYPE 
       SYNTAX     IpAddress  
       MAX-ACCESS read-only 
       STATUS     current 
       DESCRIPTION 
              "Destination IpAddress for the Stream indexed by the 
              Stream Handle." 
       ::= { ipMediaStreamMonitorEntry 4 } 
    
   ipMediaStreamDestinationPort OBJECT-TYPE 
       SYNTAX    Unsigned32 
       MAX-ACCESS read-only 
       STATUS     current 
       DESCRIPTION 
              "The Destination port for the Stream indexed by the 
              Stream Handle." 
       ::= { ipMediaStreamMonitorEntry 5 } 
    
   ipMediaStreamBitRate OBJECT-TYPE 
       SYNTAX   Unsigned32  
       MAX-ACCESS read-only 
       STATUS     current 
       DESCRIPTION 
              "The nominal Bit Rate of the Media Stream in bits/second."  
       ::= { ipMediaStreamMonitorEntry 6 } 
    
   ipMediaStreamInterval OBJECT-TYPE 
       SYNTAX   Unsigned32  
       MAX-ACCESS read-only 
       STATUS     current 
       DESCRIPTION 
              "The number indicates the minimum Interval in seconds for 
              a good MDI Measurement. The Interval is based on the 
              current Bit Rate of the Stream.  The minimum interval 
              should be chosen such that at least 10 IP packets occur 
              per interval.  This value defaults to 1 second and the 
              Interval is typically configured to 1 second unless the 
              above criteria is not met."  
       ::= { ipMediaStreamMonitorEntry 7 } 
       
   ipMediaStreamStartTime OBJECT-TYPE 
       SYNTAX     DisplayString  
       MAX-ACCESS read-only 
       STATUS     current 
       DESCRIPTION 
              "The Timestamp shows the Real time at which the stream was 
              detected.  The Timestamp format is YYYY/MM/DD/HH/MM/SS." 
       ::= { ipMediaStreamMonitorEntry 8 } 
    
   ipMediaStreamMDIDelayFactor OBJECT-TYPE 
       SYNTAX  Unsigned32 
       MAX-ACCESS read-only 
       STATUS     current 
       DESCRIPTION 
              "This object displays the Media Delivery Index Delay 
              Factor parameter in units of milliseconds.  This parameter 
              indicates the burstiness of the stream." 
       ::= { ipMediaStreamMonitorEntry 9 } 
    
   ipMediaStreamMDILossRate OBJECT-TYPE 
       SYNTAX Unsigned32  
       MAX-ACCESS read-only 
       STATUS     current 
       DESCRIPTION 
              "This object displays the Media Delivery Index Media Loss 
              Rate in packets/sec. This parameter indicates rate of 
              lost media packets of the of the  stream." 
       ::= { ipMediaStreamMonitorEntry 10 } 

   ipMediaStreamMDIDFThreshold OBJECT-TYPE 
       SYNTAX  Unsigned32  
       MAX-ACCESS  read-write 
       STATUS current 
       DESCRIPTION 
              "The Threshold for Media Delivery Index Delay Factor in 
              milliSeconds.  The default value is set to 0 indicating 
              that it is invalid until configured." 
       ::= { ipMediaStreamMonitorEntry 11 } 
    
   ipMediaStreamMDILRThreshold OBJECT-TYPE 
       SYNTAX  Unsigned32  
       MAX-ACCESS  read-write 
       STATUS current 
       DESCRIPTION 
              "The Threshold for Media Delivery Loss Rate 
              in Packets/second. The default value is set to 0xffffffff 
              indicating that it is invalid until configured." 
       ::= { ipMediaStreamMonitorEntry 12 } 
    
   ipMediaStreamMDIDFErrorIntervals OBJECT-TYPE 
       SYNTAX   Unsigned32  
       MAX-ACCESS read-only 
       STATUS     current 
       DESCRIPTION 
              "The number indicates the number of MDI DF Threshold 
              (ipMediaStreamMonitorMDIDFThreshold) Crossed Intervals 
              during the life of a stream. This shall be 0 and invalid 
              until the MDI DF Thresholds are configured." 
       ::= { ipMediaStreamMonitorEntry 13 } 
    
   ipMediaStreamMDIMLRErrorIntervals OBJECT-TYPE 
       SYNTAX   Unsigned32  
       MAX-ACCESS read-only 
       STATUS     current 
       DESCRIPTION 
              "The number indicates the number of MDI MLR Threshold 
              (ipMediaStreamMDILRThreshold)Crossed Intervals 
              during the life of a stream. This shall be 0 and invalid 
              until the MDI MLR Thresholds are configured." 
       ::= { ipMediaStreamMonitorEntry 14 } 
    
   END
