--			Ascend mibredundancystats MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBREDUNDANCYSTATS-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibredundancyStatistics  OBJECT IDENTIFIER ::= { configuration 104}
    mibredundancyStatsProfile  OBJECT IDENTIFIER ::= { configuration 17}

	-- The mibredundancyStatistics table
	--
	-- This table contains parameters for the mibredundancyStatistics profile
	--

    mibredundancyStatisticsTable	OBJECT-TYPE
	SYNTAX		SEQUENCE OF MibredundancyStatisticsEntry
	ACCESS		not-accessible
	STATUS		mandatory
	DESCRIPTION	"A list of mibredundancyStatistics profile entries."
	::= { mibredundancyStatistics 1 }

    mibredundancyStatisticsEntry	OBJECT-TYPE
	SYNTAX		MibredundancyStatisticsEntry
	ACCESS		not-accessible
	STATUS		mandatory
	DESCRIPTION	"A mibredundancyStatistics entry containing objects that
			 maps to the parameters of mibredundancyStatistics profile."
	INDEX		{ redundancyStatistics-Index-o }
	::= { mibredundancyStatisticsTable 1 }

    MibredundancyStatisticsEntry ::=
	SEQUENCE {
	    redundancyStatistics-Index-o
		INTEGER,
	    redundancyStatistics-SerialNumber
		INTEGER,
	    redundancyStatistics-Action-o
		INTEGER
	}

    redundancyStatistics-Index-o	OBJECT-TYPE
	SYNTAX	INTEGER
	ACCESS	read-only
	STATUS	mandatory
	DESCRIPTION	""
	::= { mibredundancyStatisticsEntry 1 }

    redundancyStatistics-SerialNumber	OBJECT-TYPE
	SYNTAX	INTEGER
	ACCESS	read-only
	STATUS	mandatory
	DESCRIPTION	"Identity of the card"
	::= { mibredundancyStatisticsEntry 2 }

    redundancyStatistics-Action-o	OBJECT-TYPE
	SYNTAX	INTEGER {
		    noAction (1),
		    createProfile (2),
		    deleteProfile (3)
		}
	ACCESS	read-write
	STATUS	mandatory
	DESCRIPTION	""
	::= { mibredundancyStatisticsEntry 3 }


	-- The mibredundancyStatsProfile table
	--
	-- This table contains parameters for the mibredundancyStatsProfile profile
	--

    mibredundancyStatsProfileTable	OBJECT-TYPE
	SYNTAX		SEQUENCE OF MibredundancyStatsProfileEntry
	ACCESS		not-accessible
	STATUS		mandatory
	DESCRIPTION	"A list of mibredundancyStatsProfile profile entries."
	::= { mibredundancyStatsProfile 1 }

    mibredundancyStatsProfileEntry	OBJECT-TYPE
	SYNTAX		MibredundancyStatsProfileEntry
	ACCESS		not-accessible
	STATUS		mandatory
	DESCRIPTION	"A mibredundancyStatsProfile entry containing objects that
			 maps to the parameters of mibredundancyStatsProfile profile."
	INDEX		{ redundancyStatsProfile-Index-o }
	::= { mibredundancyStatsProfileTable 1 }

    MibredundancyStatsProfileEntry ::=
	SEQUENCE {
	    redundancyStatsProfile-Index-o
		INTEGER,
	    redundancyStatsProfile-Action-o
		INTEGER
	}

    redundancyStatsProfile-Index-o	OBJECT-TYPE
	SYNTAX	INTEGER
	ACCESS	read-only
	STATUS	mandatory
	DESCRIPTION	""
	::= { mibredundancyStatsProfileEntry 1 }

    redundancyStatsProfile-Action-o	OBJECT-TYPE
	SYNTAX	INTEGER {
		    noAction (1),
		    createProfile (2),
		    deleteProfile (3)
		}
	ACCESS	read-write
	STATUS	mandatory
	DESCRIPTION	""
	::= { mibredundancyStatsProfileEntry 2 }


	-- The mibredundancyStatsProfile__context_stats table
	--
	-- This table contains parameters for the mibredundancyStatsProfile__context_stats profile
	--

    mibredundancyStatsProfile-ContextStatsTable	OBJECT-TYPE
	SYNTAX		SEQUENCE OF MibredundancyStatsProfile-ContextStatsEntry
	ACCESS		not-accessible
	STATUS		mandatory
	DESCRIPTION	"A list of mibredundancyStatsProfile__context_stats profile entries."
	::= { mibredundancyStatsProfile 2 }

    mibredundancyStatsProfile-ContextStatsEntry	OBJECT-TYPE
	SYNTAX		MibredundancyStatsProfile-ContextStatsEntry
	ACCESS		not-accessible
	STATUS		mandatory
	DESCRIPTION	"A mibredundancyStatsProfile__context_stats entry containing objects that
			 maps to the parameters of mibredundancyStatsProfile__context_stats profile."
	INDEX		{ redundancyStatsProfile-ContextStats-Index-o, redundancyStatsProfile-ContextStats-Index1-o }
	::= { mibredundancyStatsProfile-ContextStatsTable 1 }

    MibredundancyStatsProfile-ContextStatsEntry ::=
	SEQUENCE {
	    redundancyStatsProfile-ContextStats-Index-o
		INTEGER,
	    redundancyStatsProfile-ContextStats-Index1-o
		INTEGER,
	    redundancyStatsProfile-ContextStats-State
		INTEGER,
	    redundancyStatsProfile-ContextStats-Function
		INTEGER,
	    redundancyStatsProfile-ContextStats-SelectReason
		INTEGER,
	    redundancyStatsProfile-ContextStats-PriorFunction
		INTEGER,
	    redundancyStatsProfile-ContextStats-LastReboot
		INTEGER,
	    redundancyStatsProfile-ContextStats-Local-SerialNumber
		INTEGER,
	    redundancyStatsProfile-ContextStats-Pair-SerialNumber
		INTEGER,
	    redundancyStatsProfile-ContextStats-ChassisSerialNumber
		INTEGER,
	    redundancyStatsProfile-ContextStats-InitializationTime
		INTEGER,
	    redundancyStatsProfile-ContextStats-PostStart
		INTEGER,
	    redundancyStatsProfile-ContextStats-PostEnd
		INTEGER,
	    redundancyStatsProfile-ContextStats-SelectionStart
		INTEGER,
	    redundancyStatsProfile-ContextStats-SelectionEnd
		INTEGER,
	    redundancyStatsProfile-ContextStats-LoadStart
		INTEGER,
	    redundancyStatsProfile-ContextStats-LoadEnd
		INTEGER,
	    redundancyStatsProfile-ContextStats-InaugurationTime
		INTEGER,
	    redundancyStatsProfile-ContextStats-LastSent
		INTEGER,
	    redundancyStatsProfile-ContextStats-LastReceived
		INTEGER,
	    redundancyStatsProfile-ContextStats-LastProfileSync
		INTEGER,
	    redundancyStatsProfile-ContextStats-LastCodeSync
		INTEGER,
	    redundancyStatsProfile-ContextStats-LastLogRecv
		INTEGER,
	    redundancyStatsProfile-ContextStats-UpdateTime
		INTEGER
	}

    redundancyStatsProfile-ContextStats-Index-o	OBJECT-TYPE
	SYNTAX	INTEGER
	ACCESS	read-only
	STATUS	mandatory
	DESCRIPTION	""
	::= { mibredundancyStatsProfile-ContextStatsEntry 1 }

    redundancyStatsProfile-ContextStats-Index1-o	OBJECT-TYPE
	SYNTAX	INTEGER
	ACCESS	read-only
	STATUS	mandatory
	DESCRIPTION	""
	::= { mibredundancyStatsProfile-ContextStatsEntry 2 }

    redundancyStatsProfile-ContextStats-State	OBJECT-TYPE
	SYNTAX	INTEGER {
		    initial (1),
		    loadContext (2),
		    startPost (3),
		    localPost (4),
		    remotePost (5),
		    selecting (6),
		    selectionComplete (7),
		    inauguration (8),
		    primaryToOperational (9),
		    loading (10),
		    secondaryToOperational (11),
		    monitoring (12),
		    dead (13),
		    restrictRedundancy (14)
		}
	ACCESS	read-only
	STATUS	mandatory
	DESCRIPTION	"Current state of the redundancy state machine"
	::= { mibredundancyStatsProfile-ContextStatsEntry 3 }

    redundancyStatsProfile-ContextStats-Function	OBJECT-TYPE
	SYNTAX	INTEGER {
		    noFunction (1),
		    primary (2),
		    secondary (3)
		}
	ACCESS	read-only
	STATUS	mandatory
	DESCRIPTION	"Current function of this controller"
	::= { mibredundancyStatsProfile-ContextStatsEntry 4 }

    redundancyStatsProfile-ContextStats-SelectReason	OBJECT-TYPE
	SYNTAX	INTEGER {
		    noReason (1),
		    deferToRunningPrimary (2),
		    noRunningPrimary (3),
		    singleControllerOperation (4),
		    localPrimaryPreference (5),
		    remotePrimaryPreference (6),
		    localCrash (7),
		    remoteCrash (8),
		    localLocalLocalError (9),
		    remoteLocalLocalError (10),
		    localRemoteLocalError (11),
		    remoteRemoteLocalError (12),
		    localMatchesChassis (13),
		    remoteMatchesChassis (14),
		    priorPairFunction (15),
		    localPrimaryResources (16),
		    remotePrimaryResources (17),
		    localSecondaryResources (18),
		    remoteSecondaryResources (19),
		    priorLocalPrimary (20),
		    priorRemotePrimary (21),
		    localCrashHistory (22),
		    remoteCrashHistory (23),
		    localLocalLocalErrorHistory (24),
		    remoteLocalLocalErrorHistory (25),
		    localRemoteLocalErrorHistory (26),
		    remoteRemoteLocalErrorHistory (27),
		    localSlotNumber (28),
		    remoteSlotNumber (29),
		    contentionResolution (30),
		    unableToAcquireBuses (31),
		    communicationLoss (32)
		}
	ACCESS	read-only
	STATUS	mandatory
	DESCRIPTION	"Basis on which this controller was assigned the current function"
	::= { mibredundancyStatsProfile-ContextStatsEntry 5 }

    redundancyStatsProfile-ContextStats-PriorFunction	OBJECT-TYPE
	SYNTAX	INTEGER {
		    noFunction (1),
		    primary (2),
		    secondary (3)
		}
	ACCESS	read-only
	STATUS	mandatory
	DESCRIPTION	"Prior function of this controller"
	::= { mibredundancyStatsProfile-ContextStatsEntry 6 }

    redundancyStatsProfile-ContextStats-LastReboot	OBJECT-TYPE
	SYNTAX	INTEGER {
		    crash (1),
		    localReportLocalError (2),
		    remoteReportLocalError (3),
		    localReportRemoteError (4),
		    remoteReportRemoteError (5),
		    localManualReboot (6),
		    remoteManualReboot (7),
		    redundantControllerSwitchCmd (8),
		    numberOfRebootTypes (9),
		    primaryOperationalReboot (10),
		    secondaryOperationalReboot (11)
		}
	ACCESS	read-only
	STATUS	mandatory
	DESCRIPTION	"Reason the controller was last rebooted"
	::= { mibredundancyStatsProfile-ContextStatsEntry 7 }

    redundancyStatsProfile-ContextStats-Local-SerialNumber	OBJECT-TYPE
	SYNTAX	INTEGER
	ACCESS	read-only
	STATUS	mandatory
	DESCRIPTION	"Identity of the card"
	::= { mibredundancyStatsProfile-ContextStatsEntry 8 }

    redundancyStatsProfile-ContextStats-Pair-SerialNumber	OBJECT-TYPE
	SYNTAX	INTEGER
	ACCESS	read-only
	STATUS	mandatory
	DESCRIPTION	"Identity of the card"
	::= { mibredundancyStatsProfile-ContextStatsEntry 9 }

    redundancyStatsProfile-ContextStats-ChassisSerialNumber	OBJECT-TYPE
	SYNTAX	INTEGER
	ACCESS	read-only
	STATUS	mandatory
	DESCRIPTION	"Identity of the chassis"
	::= { mibredundancyStatsProfile-ContextStatsEntry 11 }

    redundancyStatsProfile-ContextStats-InitializationTime	OBJECT-TYPE
	SYNTAX	INTEGER
	ACCESS	read-only
	STATUS	mandatory
	DESCRIPTION	"Time at which this controller was initialized"
	::= { mibredundancyStatsProfile-ContextStatsEntry 12 }

    redundancyStatsProfile-ContextStats-PostStart	OBJECT-TYPE
	SYNTAX	INTEGER
	ACCESS	read-only
	STATUS	mandatory
	DESCRIPTION	"Time at which this controller started local POST"
	::= { mibredundancyStatsProfile-ContextStatsEntry 13 }

    redundancyStatsProfile-ContextStats-PostEnd	OBJECT-TYPE
	SYNTAX	INTEGER
	ACCESS	read-only
	STATUS	mandatory
	DESCRIPTION	"Time at which this controller detected the end of remote POST"
	::= { mibredundancyStatsProfile-ContextStatsEntry 14 }

    redundancyStatsProfile-ContextStats-SelectionStart	OBJECT-TYPE
	SYNTAX	INTEGER
	ACCESS	read-only
	STATUS	mandatory
	DESCRIPTION	"Time at which this controller selected a function"
	::= { mibredundancyStatsProfile-ContextStatsEntry 15 }

    redundancyStatsProfile-ContextStats-SelectionEnd	OBJECT-TYPE
	SYNTAX	INTEGER
	ACCESS	read-only
	STATUS	mandatory
	DESCRIPTION	"Time at which this controller detected the end of remote selection"
	::= { mibredundancyStatsProfile-ContextStatsEntry 16 }

    redundancyStatsProfile-ContextStats-LoadStart	OBJECT-TYPE
	SYNTAX	INTEGER
	ACCESS	read-only
	STATUS	mandatory
	DESCRIPTION	"Time at which this controller started waiting for the other controller to load the operational code"
	::= { mibredundancyStatsProfile-ContextStatsEntry 17 }

    redundancyStatsProfile-ContextStats-LoadEnd	OBJECT-TYPE
	SYNTAX	INTEGER
	ACCESS	read-only
	STATUS	mandatory
	DESCRIPTION	"Time at which this controller detected that the other controller completed loading the operational code"
	::= { mibredundancyStatsProfile-ContextStatsEntry 18 }

    redundancyStatsProfile-ContextStats-InaugurationTime	OBJECT-TYPE
	SYNTAX	INTEGER
	ACCESS	read-only
	STATUS	mandatory
	DESCRIPTION	"Time at which this controller set its function. This is used to prevent oscillation of the primary function between controllers"
	::= { mibredundancyStatsProfile-ContextStatsEntry 19 }

    redundancyStatsProfile-ContextStats-LastSent	OBJECT-TYPE
	SYNTAX	INTEGER
	ACCESS	read-only
	STATUS	mandatory
	DESCRIPTION	"Time at which this controller last got an ACK for a sent redundancyMsg"
	::= { mibredundancyStatsProfile-ContextStatsEntry 20 }

    redundancyStatsProfile-ContextStats-LastReceived	OBJECT-TYPE
	SYNTAX	INTEGER
	ACCESS	read-only
	STATUS	mandatory
	DESCRIPTION	"Time at which this controller last received a redundancyMsg"
	::= { mibredundancyStatsProfile-ContextStatsEntry 21 }

    redundancyStatsProfile-ContextStats-LastProfileSync	OBJECT-TYPE
	SYNTAX	INTEGER
	ACCESS	read-only
	STATUS	mandatory
	DESCRIPTION	"Time at which this controller last synchronized its profile repository with its partner"
	::= { mibredundancyStatsProfile-ContextStatsEntry 22 }

    redundancyStatsProfile-ContextStats-LastCodeSync	OBJECT-TYPE
	SYNTAX	INTEGER
	ACCESS	read-only
	STATUS	mandatory
	DESCRIPTION	"Time at which this controller last synchronized its code repository with its partner"
	::= { mibredundancyStatsProfile-ContextStatsEntry 23 }

    redundancyStatsProfile-ContextStats-LastLogRecv	OBJECT-TYPE
	SYNTAX	INTEGER
	ACCESS	read-only
	STATUS	mandatory
	DESCRIPTION	"Time at which this controller last received a Fatal log entry from its partner"
	::= { mibredundancyStatsProfile-ContextStatsEntry 24 }

    redundancyStatsProfile-ContextStats-UpdateTime	OBJECT-TYPE
	SYNTAX	INTEGER
	ACCESS	read-only
	STATUS	mandatory
	DESCRIPTION	"Absolute time at which this context was last updated"
	::= { mibredundancyStatsProfile-ContextStatsEntry 25 }

END
