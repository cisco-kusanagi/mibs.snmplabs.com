MEMOTECADMIN-MIB DEFINITIONS ::= BEGIN

--#CURRENT_VERSION 1

IMPORTS
  OBJECT-TYPE
    FROM RFC-1212
  DisplayString
    FROM RFC1213-MIB
  IpAddress
    FROM RFC1155-SMI
  memotecAdmin
    FROM MEMOTEC-SMI
  Alias
    FROM CXProduct-SMI;
    
memotecAdminCommunity OBJECT-TYPE
    SYNTAX  DisplayString (SIZE (0..64))
    ACCESS  write-only
    STATUS mandatory
    DESCRIPTION
"Determines the super-user community name (password) that has full 
Read/Write access to all MIB objects within the system. You must enter 
this community name when defining other community names using the object 
memotecCommunityName of the memotecAdminSecurity Table.

The setting of this object is dynamic. The system immediately implements 
the community name you enter.

Range of Values: From 0 to 64, alphanumeric characters. 

You can use any combination of letters and numbers, however you cannot use 
blank spaces. Use a dash or underscore as a delimiter.

Default Value: memotec

Configuration Changed: operative"

    DEFVAL { "memotec" }
    ::= { memotecAdmin 1 }

memotecAdminViewInacTimer OBJECT-TYPE
    SYNTAX  INTEGER (5..65535)
    ACCESS  read-write
    STATUS  mandatory
    DESCRIPTION
"THE CX900 DOES NOT SUPPORT THIS OBJECT.

Determines the length of time, in minutes, that an SNMP session can remain 
inactive before the system logs out the user. Once the timer expires, the 
user needs to log in again to regain access to the SNMP agent.

The setting of this object is dynamic. The system immediately implements 
the value you enter.

Range of Values: a maximum of 5 digits from 5 to 65535

Default Value: 30"

    DEFVAL { 30 }
    ::= { memotecAdmin 2 }

memotecAdminAgentInterfaceAlias OBJECT-TYPE
    SYNTAX  Alias
    ACCESS  read-write
    STATUS  mandatory
    DESCRIPTION
"THE CX900 DOES NOT SUPPORT THIS OBJECT.

Determines the textual name the network administrator assigns to the SNMP 
Agent.

The setting of this object is dynamic. The system immediately implements 
the name you enter.

Range of Values: from 0 to 32 alphanumeric characters. You can use any 
combination of letters and numbers however, you cannot use blank spaces. 
Use a dash or underscore as a delimiter.

Default Value: none"

    ::= { memotecAdmin 3 }

memotecAdminStatisticsHeartBeat OBJECT-TYPE
    SYNTAX  INTEGER (1..65535)
    ACCESS  read-write
    STATUS  mandatory
    DESCRIPTION
"THE CX900 DOES NOT SUPPORT THIS OBJECT.

Determines the length of time, in seconds, after which the system 
refreshes its SNMP statistics for each module.

The setting of this object is dynamic. The system immediately implements 
the value you enter.

Range of Values: a maximum of 5 digits from 1 to 65535

Default Value: 15"

    DEFVAL { 15 }
    ::= { memotecAdmin 4 }

memotecAdminCardAliveHeartBeat OBJECT-TYPE
    SYNTAX  INTEGER (1..65535)
    ACCESS  read-write
    STATUS  mandatory
    DESCRIPTION
"THE CX900 DOES NOT SUPPORT THIS OBJECT.

Determines the length of time, in seconds, after which the system checks 
too see if each module is alive.

The setting of this object is dynamic. The system immediately implements 
the value you enter.

Range of Values: a maximum of 5 digits from 1 to 65535

Default Value: 15"

    DEFVAL { 15 }
    ::= { memotecAdmin 5 }

memotecAdminSecurity OBJECT IDENTIFIER 
    ::= { memotecAdmin 6 }


memotecCommunityTable OBJECT-TYPE
    SYNTAX SEQUENCE OF MemotecCommunityEntry 
    ACCESS not-accessible
    STATUS mandatory
    DESCRIPTION
   "The community table."
    ::= { memotecAdminSecurity 1 }

memotecCommunityEntry OBJECT-TYPE
    SYNTAX MemotecCommunityEntry 
    ACCESS not-accessible
    STATUS mandatory
    DESCRIPTION
   "Information about a community table entry. "
    INDEX { memotecCommunityIndex }
    ::= { memotecCommunityTable 1 }
    
MemotecCommunityEntry ::= SEQUENCE {
    memotecCommunityIndex
   INTEGER,
    memotecCommunityName
   DisplayString (SIZE (0..64)),
    memotecCommunityNetAddress
   IpAddress,
    memotecCommunityAccess
   INTEGER,
    memotecCommunitySecurityLevel
   INTEGER,
    memotecCommunityRowStatus
   INTEGER
    }


memotecCommunityIndex OBJECT-TYPE
    SYNTAX INTEGER (1..65535)
    ACCESS read-only
    STATUS mandatory
    DESCRIPTION
"Displays the index number of the community name. The software assigns 
this number automatically to uniquely identify the communicty name. The 
index acts as a pointer to this table.

You cannot modify this object. It is a display that the software provides.

Range of Values: a maximum of 5 digits from 1 to 65535

Default Value: none"

    ::= { memotecCommunityEntry 1 }


memotecCommunityName OBJECT-TYPE
    SYNTAX  DisplayString (SIZE (0..64))
    ACCESS  read-write
    STATUS mandatory
    DESCRIPTION
"Determines the community name (password) the system acceptes for all SNMP 
requests.

Note: 
When defining the community name, you must enter the super-user 
community name (defined using the object memotecAdminCommunity of the 
memotecAdmin Table) or the system will not accept the command.

The setting of the object is dynamic. The system immediately begins 
checking all incoming SNMP requests for the community name you enter.

Range of Values: from 0 to 64 alphanumeric characters. You can use any 
combination of letters and numbers, however you cannot use blank spaces. 
Use a dash or underscore as a delimiter.

Default Value: public

Configuration Changed: operative"

    DEFVAL { "public" }
    ::= { memotecCommunityEntry 2 }

memotecCommunityNetAddress OBJECT-TYPE
    SYNTAX  IpAddress
    ACCESS  read-write
    STATUS mandatory
    DESCRIPTION
"Associates an IP address with a community name. The object 
memotecCommunityName (of this table) identifies the community name this 
object applies to. The system only processes those SNMP requests that have 
the proper community name and that arrive from the IP address you specify 
with this object.

The setting of this object is dynamic. The system immediately begins 
checking the IP address and community name of all incoming SNMP requests.

Range of Values: 4 octets, each digit ranging from 0 to 255. A value of 
0.0.0.0 indicates that the system accepts all SNMP requests as long as 
they have a valid community name.

Default Value: 0

Configuration Changed: operative"

    DEFVAL { 0 }
    ::= { memotecCommunityEntry 3 }


memotecCommunityAccess OBJECT-TYPE
    SYNTAX  INTEGER {
       readOnly(1), 
       writeOnly(2), 
       readWrite(3),
       notAccess(4)
       }
    ACCESS  read-write
    STATUS mandatory
    DESCRIPTION
"Determines the privileges of the community name when accessing the MIB 
objects. The object memotecCommunityName (of this table) identifies the 
community name this object applies to.

The setting of this object is dynamic. The system immediately implements 
the option you enter.

Options:
readOnly(1)

writeOnly(2)

readWrite(3)

notAccess(4)

Default Value: readOnly

Configuration Changed: operative"

    DEFVAL { readOnly }
    ::= { memotecCommunityEntry 4 }
    
memotecCommunitySecurityLevel OBJECT-TYPE
    SYNTAX  INTEGER
    ACCESS  read-write
    STATUS mandatory
    DESCRIPTION
"THE CX900 DOES NOT SUPPORT THIS OBJECT.

Determines the memotecSecurityLevelIndex defined in the Security Level 
Group. Currently it is set to 1 and cannot be changed.

Range of Values: none

Default Value: 1"

    DEFVAL { 1 }
    ::= { memotecCommunityEntry 5 }

memotecCommunityRowStatus OBJECT-TYPE
    SYNTAX INTEGER {
      invalid(1),
      valid(2)
      }
    ACCESS read-write
    STATUS mandatory
    DESCRIPTION
"Determines the status of objects in a table row.

The setting of this object is dynamic. When set to 'valid', the system 
immediately implements the configuration entry.

Options:
invalid (1): row is flagged; after the next reset the values will be 
disabled and the row will be deleted from the table.

valid (2): values are enabled.

Default Value: valid (2)

Configuration Changed: operative"

    DEFVAL { valid }
    ::= { memotecCommunityEntry 6 }

memotecSecurityTable OBJECT-TYPE
    SYNTAX SEQUENCE OF MemotecSecurityEntry 
    ACCESS not-accessible
    STATUS mandatory
    DESCRIPTION
"The security level and group within privilege association table.   
Currently this table is NOT accessible."
    ::= {  memotecAdminSecurity 2 }


memotecSecurityEntry OBJECT-TYPE
    SYNTAX MemotecSecurityEntry
    ACCESS not-accessible
    STATUS mandatory
    DESCRIPTION
   "Information about a security entry. "
    INDEX { memotecSecurityLevelIndex, memotecSecurityViewIndex }
    ::= { memotecSecurityTable 1 }
    
MemotecSecurityEntry ::= SEQUENCE {
    memotecSecurityLevelIndex
   INTEGER,
    memotecSecurityViewIndex
   INTEGER,
    memotecSecurityView
   OBJECT IDENTIFIER,
    memotecSecurityRowStatus
   INTEGER
    }


memotecSecurityLevelIndex OBJECT-TYPE
    SYNTAX INTEGER (1..65535)
    ACCESS read-only
    STATUS mandatory
    DESCRIPTION
"THE CX900 DOES NOT SUPPORT THIS OBJECT.

Displays the index number of the community name's security level.The 
software automatically assigns this number to uniquely identify the 
security level. The index acts as a pointer to this table.

You cannot modify this object. It is a display that the software provides.

Range of Values: a maximum of 5 digits from 1 to 65535

Default Value: none"

    ::= { memotecSecurityEntry 1 }

memotecSecurityViewIndex OBJECT-TYPE
    SYNTAX INTEGER (1..65535)
    ACCESS read-only
    STATUS mandatory
    DESCRIPTION
"THE CX900 DOES NOT SUPPORT THIS OBJECT.

Displays the index number of the memotecSecurityLevelIndex MIB object 
group. The software assigns this number automatically to uniquely identify 
the MIB group. The index acts as a pointer to this table.

You cannot modify this object. It is a display that the software provides.

Range of Values: a maximum of 5 digits from 1 to 65535

Default Value: none"

    ::= { memotecSecurityEntry 2 }

memotecSecurityView OBJECT-TYPE
    SYNTAX  OBJECT IDENTIFIER
    ACCESS  read-write
    STATUS mandatory
    DESCRIPTION
"THE CX900 DOES NOT SUPPORT THIS OBJECT.

An MIB object group defined for this view index of the security level.

Range of Values: none

Default Value: none"

    ::= { memotecSecurityEntry 3 }

memotecSecurityRowStatus OBJECT-TYPE
    SYNTAX INTEGER {
      invalid(1),
      valid(2)
      }
    ACCESS read-write
    STATUS mandatory
    DESCRIPTION
"Determines the status of the objects in a table row.

The setting of this object is dynamic. When set to 'valid', the system 
immediately implements the configuration entry.

Options:
invalid (1): row is flagged; after next reset the values will be disabled 
and the row will be deleted from the table.

valid: (2): values are enabled.

Default Value: valid (2)

Configuration Changed: operative"

    DEFVAL { valid }
    ::= { memotecSecurityEntry 5 }       

memotecTrapTable OBJECT-TYPE
    SYNTAX SEQUENCE OF MemotecTrapEntry 
    ACCESS not-accessible
    STATUS mandatory
    DESCRIPTION
" This is a trap table. It contains a list of IP addresses of SNMP 
consoles to which SNMP traps are sent."
    ::= { memotecAdminSecurity 3 }

memotecTrapEntry OBJECT-TYPE
    SYNTAX MemotecTrapEntry 
    ACCESS not-accessible
    STATUS mandatory
    DESCRIPTION
"An entry of the trap table. "
    INDEX { memotecTrapIndex }
    ::= { memotecTrapTable 1 }
    
MemotecTrapEntry ::= SEQUENCE {
    memotecTrapIndex
   INTEGER,
    memotecTrapNetAddress
   IpAddress,
    memotecTrapCommunity
   DisplayString,
    memotecTrapRowStatus
   INTEGER
    }


memotecTrapIndex OBJECT-TYPE
    SYNTAX INTEGER (1..65535)
    ACCESS read-only
    STATUS mandatory
    DESCRIPTION
"Displays the index number of the trap entry. The software assigns this 
number automatically to uniquely identify the trap entry. The index acts 
as a pointer to this table.

Range of Values: a maximum of 5 digits from 1 to 65535

Default Value: none"

    ::= { memotecTrapEntry 1 }

memotecTrapNetAddress OBJECT-TYPE
    SYNTAX  IpAddress
    ACCESS  read-write
    STATUS mandatory
    DESCRIPTION
"Determines the network address (i.e. IP address) of the system to which 
traps are sent.

The setting of the object is dynamic. Traps are immediately sent to the IP 
address you enter.

Range of Values: 4 octets, each digit ranging from 0 to 255.

Default Value: 0

Configuration Changed: operative"

    DEFVAL { 0 }
    ::= { memotecTrapEntry 2 }

memotecTrapCommunity OBJECT-TYPE
    SYNTAX  DisplayString
    ACCESS  read-write
    STATUS mandatory
    DESCRIPTION
"Determines the community name included in all traps. The object 
memotecTrapNetAddress (of this table) identifies the IP address to which 
these traps are sent. The system receiving the traps will not accept any 
that do not contain this community name.

The setting of this object is dynamic. The system immediately begins 
checking the traps for the community name you define.

Range of Values: from 0 to 64 alphanumeric characters. You can use any 
combination of letters and numbers however, you cannot use blank spaces. 
Use a dash or underscore as a delimiter.

Default Value: public

Configuration Changed: operative"

    DEFVAL { "public" }
    ::= { memotecTrapEntry 3 }
    
memotecTrapRowStatus OBJECT-TYPE
    SYNTAX INTEGER {
      invalid(1),
      valid(2)
      }
    ACCESS read-write
    STATUS mandatory
    DESCRIPTION
"Determines the status of the objects in a table row.

The setting of this object is dynamic. When set to 'valid', the system 
immediately implements the trap entry.

Options:
invalid (1): row is flagged; after the next reset the values will be 
disabled and the row will be deleted from the table.

valid (2): values are enabled.

Default Value: valid

Configuration Changed: operative"

    DEFVAL { valid }
    ::= { memotecTrapEntry 4 }   

memotecAdminMibs OBJECT IDENTIFIER 
    ::= { memotecAdmin 7 }
    

memotecAdminMibModules  OBJECT-TYPE
   SYNTAX  OCTET STRING (SIZE (32))
   ACCESS  read-only
   STATUS  mandatory
   DESCRIPTION
"This objects represents the presence of the various MIB modules 
in the CPU. Each MIB module is represented by a bit. If the bit 
is set, then it implies that the MIB Module is present. Bits are
numbered starting with zero, which is positioned as the high 
order bit of the first byte. Bits are packed eight to a byte. 
Unused bits should be set to zero. For example, to find out if
layer id 15 is present,  the bit number 15 is tested if it is set.


   MIB Module      Module id (bit position)
   --------------  ----------
   COMPR.MIB               0
   CXADXI.MIB              1
   CXASYIO.MIB             2
   CXASYNC.MIB             3
   CXBCM.MIB               4
   CXBOPD.MIB              5
   CXBOPIO.MIB             6
   CXCC.MIB                7
   CXCD.MIB                8       
   CXCFGBR.MIB             9
   CXCFGIP.MIB             10
   CXCFGIPX.MIB            11
   CXCHASSI.MIB            12
   CXCONV.MIB              13
   CXDDS.MIB               14
   CXDIAL.MIB              15
   CXDL.MIB                16
   CXETHIO.MIB             17
   CXEVM.MIB               18
   CXFLTIP.MIB             19
   CXFLTIPX.MIB            20
   CXFR.MIB                21
   CXFRIM.MIB              22
   CXFS.MIB                23
   CXGFF.MIB               24
   CXGMF.MIB               25
   CXIH.MIB                26
   CXIHI.MIB               27
   CXIPNCP.MIB             28
   CXIPX.MIB               29
   CXIPXSAP.MIB            30
   CXISDN.MIB              31
   CXLANIO.MIB             32
   CXLAPBD.MIB             33
   CXLBCNV.MIB             34
   CXLFC.MIB               35
   CXLIG.MIB               36
   CXLLCIM.MIB             37
   CXLLCL.MIB              38
   CXMCDL.MIB              39
   CXMCPRT.MIB             40
   CXMCVOX.MIB             41
   CXMH.MIB                42
   CXMLPPP.MIB             43
   CXOS.MIB                44
   CXOSP.MIB               45
   CXPHYIF.MIB             46
   CXPORT.MIB              47
   CXPPP.MIB               48
   CXPPPIP.MIB             49
   CXQLLC.MIB              50
   CXSDLC.MIB              51
   CXSDXI.MIB              52
   CXSM.MIB                53
   CXSNALC.MIB             54
   CXT1E1.MIB              55
   CXTB.MIB                56
   CXTRDIO.MIB             57
   CXUDRV.MIB              58
   CXUI.MIB                59
   CXUTST.MIB              60
   CXV34.MIB               61
   CXVIEWIN.MIB            62
   CXVR.MIB                63
   CXVSHELL.MIB            64
   CXX25.MIB               65
   MEMOTADM.MIB            66
   RFC1213R.MIB            67
   RFC1231.MIB             68
   RFC1253.MIB             69
   RFC1284M.MIB            70
   RFC1286.MIB             71
   RFC1389.MIB             72
   CXDHCP.MIB              73
   CXGIM.MIB               74
   RFC1406.MIB             75
   RFC1406X.MIB            76
   CXACTE.MIB              77
   CXBSC.MIB               78
   CXDSP.MIB               79
   CX_T1E1.MIB             80
"
   ::= { memotecAdminMibs 1 }

memotecAdminMibLevel OBJECT-TYPE
   SYNTAX  INTEGER
   ACCESS  read-only
   STATUS  mandatory
   DESCRIPTION
"Used to determine current MIB module release supported
by the agent. Object is in decimal."
   DEFVAL { 0 }
   --#STARTING_VERSION 1
   ::= { memotecAdmin 8 }


END
