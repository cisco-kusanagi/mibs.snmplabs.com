LIVINGSTON-PM4-MIB DEFINITIONS ::= BEGIN

IMPORTS
	IpAddress, Counter, Gauge, TimeTicks
		FROM RFC1155-SMI
	OBJECT-TYPE
		FROM RFC-1212
	TRAP-TYPE
		FROM RFC-1215
	DisplayString, PhysAddress, sysName
		FROM RFC1213-MIB
	lucentPM4
		FROM LIVINGSTON-ROOT-MIB;


-- ++++++++++++++++++++++++++++++++++++++++++++++++++++++++++++++++++++++++++
-- Lucent PortMaster private MIB Begin Textual Conventions
-- ++++++++++++++++++++++++++++++++++++++++++++++++++++++++++++++++++++++++++

-- Lucent PortMaster Equipment Types

PMUnitType ::= INTEGER {
	mrgmodule(1),
	quadt1(2),
	trie1(3),
	modem(4),
	serialport(5),
	ether0(6),
	ether1(7),
	console(8),
	acpwrsup(9),
	fan(10),
	dcpwrsup(11),
	allunits(255)
	}

PMEquipPRIStatus ::= INTEGER {
	up(1),
	down(2),
	loopback(3),
	fault(4)
	}

PMEquipStatus ::= INTEGER {
	up(1),
	down(2),
	maintenance(3),
	fault(4),
	other(5)
	}

PMDiagCmdStatus ::= INTEGER {
	success(1),
	fail(2),
	inprogress(3),
	notsupported(4),
	aborted(5),
	other(6)
	}

PMDiagTestCntrl ::= INTEGER {
	normal(1),
	start(2),
	stop(3),
	abort(4)
	}

PMAlarmType ::= INTEGER {
	informational(1),
	warning(2),
	minor(3),
	major(4),
	critical(5)
	}

-- ++++++++++++++++++++++++++++++++++++++++++++++++++++++++++++++++++++++++++
-- Lucent PortMaster private MIB End of Textual Conventions
-- ++++++++++++++++++++++++++++++++++++++++++++++++++++++++++++++++++++++++++


-- ++++++++++++++++++++++++++++++++++++++++++++++++++++++++++++++++++++++++++
--  Lucent PortMaster 4 Enterprise MIB
-- ++++++++++++++++++++++++++++++++++++++++++++++++++++++++++++++++++++++++++
lucentPM4Mib	OBJECT IDENTIFIER ::= { lucentPM4 1 }
lucentPM4Traps	OBJECT IDENTIFIER ::= { lucentPM4 2 }

-- ++++++++++++++++++++++++++++++++++++++++++++++++++++++++++++++++++++++++++
-- Lucent MIB Information Group
-- ++++++++++++++++++++++++++++++++++++++++++++++++++++++++++++++++++++++++++
lucentPM4MibRev	OBJECT-TYPE
	SYNTAX	DisplayString (SIZE(1..6))
	ACCESS	read-only
	STATUS	mandatory
	DESCRIPTION
	"This object specifies the current MIB revision number. Example of the
	MIB revision can be PM4xxx for PM4 product and PM3xxx for PM3 products etc.
	Where xxx can be any combination of alpha-numeric characters."
	::= { lucentPM4Mib 1 }

lucentPM4SWRev	OBJECT-TYPE
	SYNTAX	DisplayString (SIZE(1..10))
	ACCESS	read-only
	STATUS	mandatory
	DESCRIPTION
	"This object specifies the ComOS revision number. Example of the
	ComOS revision can be ComOS4.xx. Where xxx can be any combination
	of alpha-numeric characters."
	::= { lucentPM4Mib 2 }

-- ++++++++++++++++++++++++++++++++++++++++++++++++++++++++++++++++++++++++++
-- Lucent chassis Group
-- ++++++++++++++++++++++++++++++++++++++++++++++++++++++++++++++++++++++++++
lucentPM4Chassis	OBJECT IDENTIFIER ::= { lucentPM4Mib     3 }

lucentPM4ChasSummary	OBJECT-TYPE
	SYNTAX	DisplayString (SIZE(55))
	ACCESS	read-only
	STATUS	mandatory
	DESCRIPTION
	"This object provides general information about the 
	PortMaster 4 chassis operational status. This object is 
 	read-only. The DisplayString represents a summary of all
	the devices in the chassis as follows:
	Bytes 1 - 2		'0''0'
	Byte  3		'U', 'D', 'M', 'F', 'O'
	Byte  4		space
	Bytes 5 - 6		'0''1'
	Byte  7		'U', 'D', 'M', 'F', 'O'
	Byte  8		space
	Bytes 9 - 10	'0''2'
	Byte  11		'U', 'D', 'M', 'F', 'O'
	Byte  12		space
	Bytes 13 - 14	'0''3'
	Byte  15		'U', 'D', 'M', 'F', 'O'
	Byte  16		space
	Bytes 17 - 18	'0''4'
	Byte  19		'U', 'D', 'M', 'F', 'O'
	Byte  20		space
	Bytes 21 - 22	'0''5'
	Byte  23		'U', 'D', 'M', 'F', 'O'
	Byte  24		space
	Bytes 25 - 26	'0''6'
	Byte  27		'U', 'D', 'M', 'F', 'O'
	Byte  28		space
	Bytes 29 - 30	'0''7'
	Byte  31		'U', 'D', 'M', 'F', 'O'
	Byte  32		space
	Bytes 33 - 34	'0''8'
	Byte  35		'U', 'D', 'M', 'F', 'O'
	Byte  36		space
	Bytes 37 - 38	'0''9'
	Byte  39		'U', 'D', 'M', 'F', 'O'
	Byte  40		space
	Bytes 41 - 42	'1''0'
	Byte  43		'U', 'D', 'M', 'F', 'O'
	Byte  44		space
	Bytes 45 - 46	'1''1'
	Byte  47		'U', 'D', 'M', 'F', 'O'
	Byte  48		space
	Bytes 49 - 50	'1''2'
	Byte  51		'U', 'D', 'M', 'F', 'O'
	Byte  52		space
	Bytes 53 - 54	'1''3'
	Byte  55		'U', 'D', 'M', 'F', 'O'
	Byte  56		space
	Bytes 57 - 58	'1''4'
	Byte  59		'U', 'D', 'M', 'F', 'O'
	Byte  60		space
	Bytes 61 - 62	'1''5'
	Byte  63		'U', 'D', 'M', 'F', 'O'
	Byte  64		space
	Bytes 65 - 66	'P''1'
	Byte  67		'U', 'D', 'M', 'F', 'O'
	Byte  68		space
	Bytes 69 - 70	'P''2'
	Byte  71		'U', 'D', 'M', 'F', 'O'
	Byte  72		space
	Bytes 73 - 74	'P''3'
	Byte  75		'U', 'D', 'M', 'F', 'O'
	Byte  76		space
	Bytes 77 - 78	'D''1'
	Byte  79		'U', 'D', 'M', 'F', 'O'
	Byte  80		space
	Bytes 81 - 82	'D''2'
	Byte  83		'U', 'D', 'M', 'F', 'O'
	Byte  84		space
	Bytes 85 - 86	'F''1'
	Byte  87		'U', 'D', 'M', 'F', 'O'
	Byte  88		space
	Bytes 89 - 90	'F''2'
	Byte  91		'U', 'D', 'M', 'F', 'O'
	Byte  92		space
	Bytes 93 - 94	'F''3'
	Byte  95		'U', 'D', 'M', 'F', 'O'
	Byte  96		space
	Bytes 97 - 98	'F''4'
	Byte  99		'U', 'D', 'M', 'F', 'O'
	Legend		'#''#' 	Represents the board number
				'F''#'	Represents the Fan #
				'P''#'	Represents the Power Supply #
				'D''#'	Represents the DC Power Supply #
				'U'	Up
				'D'	Down
				'M'	Maintenance
				'F'	Failed
				'O'	Other unknown state."
	::= { lucentPM4Chassis 1 }

-- ++++++++++++++++++++++++++++++++++++++++++++++++++++++++++++++++++++++++++
-- Lucent Chassis Command Table
-- ++++++++++++++++++++++++++++++++++++++++++++++++++++++++++++++++++++++++++

lucentPM4ChasCmdTable	OBJECT-TYPE
	SYNTAX	SEQUENCE OF LucentPM4ChasCmdEntry
	ACCESS	not-accessible
	STATUS	mandatory
	DESCRIPTION
	"Table describing the commands that can be issued to the
	agent to perform specific actions to any card, port or
	device in the system. For example to erase the flash or
	a particular file from the flash. Note that only a station
	configured with the appropriate authentication string can
	issue commands to the agent."
	::= { lucentPM4Chassis 2 }

lucentPM4ChasCmdEntry	OBJECT-TYPE
	SYNTAX	LucentPM4ChasCmdEntry
	ACCESS	not-accessible
	STATUS	mandatory
	DESCRIPTION
	"Entries in the command table for the chassis commands. This
	describes one entry or row in the command table."
	INDEX	{ lucentPM4ChasCmdIndex }
	::= { lucentPM4ChasCmdTable 1 }

LucentPM4ChasCmdEntry ::=
	SEQUENCE {
		lucentPM4ChasCmdIndex
			INTEGER,
		lucentPM4ChasCmdBoardId
			INTEGER,
		lucentPM4ChasCmdUnitType
			PMUnitType,
		lucentPM4ChasCmdUnitIndex
			INTEGER,
		lucentPM4ChasCmdDevId
			INTEGER,
		lucentPM4ChasCmdId
			INTEGER,
		lucentPM4ChasCmdParams
			OCTET STRING,
		lucentPM4ChasCmdResult
			INTEGER
	}

lucentPM4ChasCmdIndex	OBJECT-TYPE
	SYNTAX	INTEGER (1..10)
	ACCESS	read-write
	STATUS	mandatory
	DESCRIPTION
	"This object specifies the index in the command table.
	The values for this object is limited to the size of
	the command table on the network element. The size of
	the command table is set to 10 which can be changed if
	and when users need to schedule more than 10 commands
	at a given time."
	::= { lucentPM4ChasCmdEntry 1 }

lucentPM4ChasCmdBoardId	OBJECT-TYPE
	SYNTAX	INTEGER
	ACCESS	read-write
	STATUS	mandatory
	DESCRIPTION
	"This object specifies the board for which the command is to
	be applied. The values for this object is limited to the Max
	number of boards."
	::= { lucentPM4ChasCmdEntry 2 }

lucentPM4ChasCmdUnitType	OBJECT-TYPE
	SYNTAX	PMUnitType
	ACCESS	read-write
	STATUS	mandatory
	DESCRIPTION
	"This object specifies the type of the device to which
	this command must apply."
	::= { lucentPM4ChasCmdEntry 3 }

lucentPM4ChasCmdUnitIndex	OBJECT-TYPE
	SYNTAX	INTEGER
	ACCESS	read-write
	STATUS	mandatory
	DESCRIPTION
	"This object specifies the interface index."
	::= { lucentPM4ChasCmdEntry 4 }

lucentPM4ChasCmdDevId	OBJECT-TYPE
	SYNTAX	INTEGER (1..96)
	ACCESS	read-write
	STATUS	mandatory
	DESCRIPTION
	"This object specifies the sub-unit id for which the command
	must be applied to. This value will be used by the agent to
	index to the correct sub-device on a board. For example, this
	object can have values from 1 - 96 for the modems or 1 - 4 for
	T1 or 1 - 3 for the E1."
	::= { lucentPM4ChasCmdEntry 5 }

lucentPM4ChasCmdId		OBJECT-TYPE
	SYNTAX	INTEGER {
		eraseflashfile(1),
		eraseallflash(2),
		saveall(3),
		resetport(4),
		resetfilter(5),
		adduser(6),
		deleteuser(7),
		addlocation(8),
		diallocation(9),
		addfilter(10),
		deletefilter(11),
		addmodem(12),
		resetvirtport(13),
		addospfarea(14),
		resetospf(15),
		addprop(16),
		deleteprop(17),
		resetprop(18),
		resetether0(19),
		resetether1(20),
		resetall(21),
		resetconsole(22),
		version(23),
		traceroutes(24),
		ptrace(25),
		ifconfig(26),
		eraseconfig(27),
		erasecomos(28),
		reboot(29)
	}
	ACCESS	read-write
	STATUS	mandatory
	DESCRIPTION
	"This object specifies the command. Each command takes a unique
	value. The completion status of this command is set in the result
	object of the table."
	::= { lucentPM4ChasCmdEntry 6 }

lucentPM4ChasCmdParams	OBJECT-TYPE
	SYNTAX	OCTET STRING (SIZE(0..255))
	ACCESS	read-write
	STATUS	mandatory
	DESCRIPTION
	"This object specifies the command parameters. Each parameter must be
	seperated by a blank space. The last parameter is terminated with a
	';'."
	::= { lucentPM4ChasCmdEntry 7 }

lucentPM4ChasCmdResult	OBJECT-TYPE
	SYNTAX	PMDiagCmdStatus
	ACCESS	read-only
	STATUS	mandatory
	DESCRIPTION
	"This object specifies the command result. The result for each
	of the previous 10 commands will be stored in a table, which
	can be retrieved by the client when needed."
	::= { lucentPM4ChasCmdEntry 8 }

-- ++++++++++++++++++++++++++++++++++++++++++++++++++++++++++++++++++++++++++
-- Lucent Configuration Management Group
-- ++++++++++++++++++++++++++++++++++++++++++++++++++++++++++++++++++++++++++
lucentPM4ConfigMgmt		OBJECT IDENTIFIER ::= { lucentPM4Mib 4 }

-- ++++++++++++++++++++++++++++++++++++++++++++++++++++++++++++++++++++++++++
-- The Lucent Interfaces Group
-- ++++++++++++++++++++++++++++++++++++++++++++++++++++++++++++++++++++++++++
lucentPM4CmInterfaces	OBJECT IDENTIFIER ::= { lucentPM4ConfigMgmt 1}

-- ++++++++++++++++++++++++++++++++++++++++++++++++++++++++++++++++++++++++++
-- The Lucent Serial Interfaces table
-- ++++++++++++++++++++++++++++++++++++++++++++++++++++++++++++++++++++++++++
lucentPM4CmSerial		OBJECT IDENTIFIER ::= { lucentPM4CmInterfaces 1 }

lucentPM4SerialTable OBJECT-TYPE
	SYNTAX  SEQUENCE OF LucentPM4SerialEntry
	ACCESS  not-accessible
	STATUS  mandatory
	DESCRIPTION
	"A list of serial interface entries."
	::= { lucentPM4CmSerial 1 }

lucentPM4SerialEntry OBJECT-TYPE
	SYNTAX  LucentPM4SerialEntry
	ACCESS  not-accessible
	STATUS  mandatory
	DESCRIPTION
	"A serial interface entry containing objects at the
	physical and session layer."
	INDEX   { lucentPM4SerialBoardIndex,
		  lucentPM4SerialIndex }
	::= { lucentPM4SerialTable 1 }

LucentPM4SerialEntry ::=
	SEQUENCE {
		lucentPM4SerialBoardIndex
			INTEGER,
		lucentPM4SerialUnitType
			PMUnitType,
		lucentPM4SerialIndex
			INTEGER,
		lucentPM4ModemId
			INTEGER,
		lucentPM4SerialPortNumber
			INTEGER,
		lucentPM4SerialPhysType
			INTEGER,
		lucentPM4SerialPortStatus
			INTEGER,
		lucentPM4SerialDS0State
			INTEGER,
		lucentPM4SerialUser
			DisplayString,
		lucentPM4SerialSessionId
			DisplayString,
		lucentPM4SerialTypeHardwired
			INTEGER,
		lucentPM4SerialTypeNwDialIn
			INTEGER,
		lucentPM4SerialTypeNwDialout
			INTEGER,
		lucentPM4SerialTypeLogin
			INTEGER,
		lucentPM4SerialTypeDevice
			INTEGER,
		lucentPM4SerialTypeDeviceName
			DisplayString,
		lucentPM4SerialDirection
			INTEGER,
		lucentPm4SerialStarted
			TimeTicks,
		lucentPM4SerialIdle
			TimeTicks,
		lucentPM4SerialInSpeed
			Gauge,
		lucentPM4SerialOutSpeed
			Gauge,
		lucentPM4SerialIpAddress
			IpAddress,
		lucentPM4SerialifDescr
			DisplayString,
		lucentPM4SerialInOctets
			Counter,
		lucentPM4SerialOutOctets
			Counter,
		lucentPm4SerialQOctets
			Counter
	}

lucentPM4SerialBoardIndex OBJECT-TYPE
	SYNTAX  INTEGER
	ACCESS  read-only
	STATUS  mandatory
	DESCRIPTION
	"A unique value for each board in the PortMaster chassis.
	The Max value of this variable is limited by the number
	of boards in the chassis. This value is limited to 255."
	::= { lucentPM4SerialEntry 1 }

lucentPM4SerialUnitType OBJECT-TYPE
	SYNTAX  PMUnitType
	ACCESS  read-only
	STATUS  mandatory
	DESCRIPTION
	"Unit type indicates the serial port. The interface table
	ifIndex is a combination of board index, unit type and
	unit index."
	::= { lucentPM4SerialEntry 2 }

lucentPM4SerialIndex OBJECT-TYPE
	SYNTAX  INTEGER
	ACCESS  read-only
	STATUS  mandatory
	DESCRIPTION
	"A unique value for each serial interface on a given board."
	::= { lucentPM4SerialEntry 3 }

lucentPM4ModemId OBJECT-TYPE
	SYNTAX  INTEGER
	ACCESS  read-only
	STATUS  mandatory
	DESCRIPTION
	"This object is the cross reference to the modem interface table index.
	The value is dynamically assigned when the call is established."
	::= { lucentPM4SerialEntry 4 }

lucentPM4SerialPortNumber OBJECT-TYPE
	SYNTAX  INTEGER
	ACCESS  read-only
	STATUS  mandatory
	DESCRIPTION
	"A serial port to which this modem is assigned for this call."
	::= { lucentPM4SerialEntry 5 }

lucentPM4SerialPhysType OBJECT-TYPE
	SYNTAX  INTEGER {
		other(1),          -- none of the following
		async(2),
		sync(3),
		isdn(4)
	}
	ACCESS  read-only
	STATUS  mandatory
	DESCRIPTION
	"The type of physical serial interface, distinguished
	according to the physical/link protocol(s) being
	currently used on the interface. When this object is
	set to asyn(2), then the service types dial-in, dial-
	out, login, and device are valid. When this object is
	set to sync(3), the serial service types dial-in, dial-
	out and hardwired are valid."
	::= { lucentPM4SerialEntry 6 }

lucentPM4SerialPortStatus OBJECT-TYPE
	SYNTAX  INTEGER {
		idle(1),
		connecting(2),
		established(3),
		disconnecting(4),
		command(5),
		noservice(6)
	}
	ACCESS  read-only
	STATUS  mandatory
	DESCRIPTION
	"The status of the serial interface."
	::= { lucentPM4SerialEntry 7 }

lucentPM4SerialDS0State	OBJECT-TYPE
	SYNTAX	INTEGER {
		notavailable(1),
		busyout(2),
		havecomport(3)
	}
	ACCESS	read-write
	STATUS	mandatory
	DESCRIPTION
	"Cross reference value for each DS0 for a given T1/E1 line and a 
	given board in the PM4 chassis."
	::= { lucentPM4SerialEntry 8 }

lucentPM4SerialUser OBJECT-TYPE
	SYNTAX  DisplayString (SIZE (0..255))
	ACCESS  read-only
	STATUS  mandatory
	DESCRIPTION
	"Name of the active user.  Blank if not active."
	::= { lucentPM4SerialEntry 9 }

lucentPM4SerialSessionId OBJECT-TYPE
	SYNTAX  DisplayString (SIZE (0..255))
	ACCESS  read-only
	STATUS  mandatory
	DESCRIPTION
	"A unique Session Identifier which matches the RADIUS
	session ID.  Blank when not using RADIUS."
	::= { lucentPM4SerialEntry 10 }

lucentPM4SerialTypeHardwired OBJECT-TYPE
	SYNTAX  INTEGER {
		disable(1),
		enable(2)
	}
	ACCESS  read-write
	STATUS  mandatory
	DESCRIPTION
	"The active type of service being provided by the
	serial interface."
	::= { lucentPM4SerialEntry 11 }

lucentPM4SerialTypeNwDialIn OBJECT-TYPE
	SYNTAX  INTEGER {
		disable(1),
		enable(2)
	}
	ACCESS  read-write
	STATUS  mandatory
	DESCRIPTION
	"The active type of service being provided by the
	serial interface."
	::= { lucentPM4SerialEntry 12 }

lucentPM4SerialTypeNwDialout OBJECT-TYPE
	SYNTAX  INTEGER {
		disable(1),
		enable(2)
	}
	ACCESS  read-write
	STATUS  mandatory
	DESCRIPTION
	"The active type of service being provided by the
	serial interface."
	::= { lucentPM4SerialEntry 13 }

lucentPM4SerialTypeLogin OBJECT-TYPE
	SYNTAX  INTEGER {
		disable(1),
		enable(2)
	}
	ACCESS  read-write
	STATUS  mandatory
	DESCRIPTION
	"The active type of service being provided by the
	serial interface."
	::= { lucentPM4SerialEntry 14 }

lucentPM4SerialTypeDevice OBJECT-TYPE
	SYNTAX  INTEGER {
		disable(1),
		enable(2)
	}
	ACCESS  read-write
	STATUS  mandatory
	DESCRIPTION
	"The active type of service being provided by the
	serial interface."
	::= { lucentPM4SerialEntry 15 }

lucentPM4SerialTypeDeviceName OBJECT-TYPE
	SYNTAX  DisplayString
	ACCESS  read-write
	STATUS  mandatory
	DESCRIPTION
	"Device name if the lucentPM4SerialTypeDevice is enabled.
	This is a string of characters (e.g. /dev/tty1) indicating
	the device name."
	::= { lucentPM4SerialEntry 16 }

lucentPM4SerialDirection OBJECT-TYPE
	SYNTAX  INTEGER {
		in(1),
		out(2),
		inout(3)
	}
	ACCESS  read-only
	STATUS  mandatory
	DESCRIPTION
	"The direction the active session was initiated."
	::= { lucentPM4SerialEntry 17 }

lucentPM4SerialStarted OBJECT-TYPE
	SYNTAX  TimeTicks
	ACCESS  read-only
	STATUS  mandatory
	DESCRIPTION
	"The amount of time this session has been active."
	::= { lucentPM4SerialEntry 18 }

lucentPM4SerialIdle OBJECT-TYPE
	SYNTAX  TimeTicks
	ACCESS  read-only
	STATUS  mandatory
	DESCRIPTION
	"The amount of time this session has been idle."
	::= { lucentPM4SerialEntry 19 }

lucentPM4SerialInSpeed OBJECT-TYPE
	SYNTAX  Gauge
	ACCESS  read-only
	STATUS  mandatory
	DESCRIPTION
	"An estimate of the serial interface's current inbound
	bandwidth in bits per second."
	::= { lucentPM4SerialEntry 20 }

lucentPM4SerialOutSpeed OBJECT-TYPE
	SYNTAX  Gauge
	ACCESS  read-only
	STATUS  mandatory
	DESCRIPTION
	"An estimate of the serial interface's current outbound
	bandwidth in bits per second."
	::= { lucentPM4SerialEntry 21 }

lucentPM4SerialIpAddress OBJECT-TYPE
	SYNTAX  IpAddress
	ACCESS  read-only
	STATUS  mandatory
	DESCRIPTION
	"The IP address associated with the serial interface.
	If being used as a network type port, this is the
	remote user's IP address.  If being used as a device or
	login, this is the IP address of the host the user is
	connected to."
	::= { lucentPM4SerialEntry 22 }

lucentPM4SerialifDescr OBJECT-TYPE
	SYNTAX  DisplayString (SIZE (0..255))
	ACCESS  read-only
	STATUS  mandatory
	DESCRIPTION
	"A textual string containing information about the
	network interface bound to the serial interface."
	::= { lucentPM4SerialEntry 23 }

lucentPM4SerialInOctets OBJECT-TYPE
	SYNTAX  Counter
	ACCESS  read-only
	STATUS  mandatory
	DESCRIPTION
	"The total number of octets received on the
	serial interface."
	::= { lucentPM4SerialEntry 24 }

lucentPM4SerialOutOctets OBJECT-TYPE
	SYNTAX  Counter
	ACCESS  read-only
	STATUS  mandatory
	DESCRIPTION
	"The total number of octets transmitted on the
	serial interface."
	::= { lucentPM4SerialEntry 25 }

lucentPM4SerialQOctets OBJECT-TYPE
	SYNTAX  Counter
	ACCESS  read-only
	STATUS  mandatory
	DESCRIPTION
	"The total number of octets queued on the
	serial interface."
	::= { lucentPM4SerialEntry 26 }

-- ++++++++++++++++++++++++++++++++++++++++++++++++++++++++++++++++++++++++++
-- The Lucent T1/E1 Interface table
-- ++++++++++++++++++++++++++++++++++++++++++++++++++++++++++++++++++++++++++
lucentPM4CmT1E1	OBJECT IDENTIFIER ::= { lucentPM4CmInterfaces 2 }

lucentPM4T1E1Table OBJECT-TYPE
	SYNTAX  SEQUENCE OF LucentPM4T1E1Entry
	ACCESS  not-accessible
	STATUS  mandatory
	DESCRIPTION
	"A list of T1/E1 interface entries."
	::= { lucentPM4CmT1E1 1 }

lucentPM4T1E1Entry OBJECT-TYPE
	SYNTAX  LucentPM4T1E1Entry
	ACCESS  not-accessible
	STATUS  mandatory
	DESCRIPTION
	"A T1/E1 entry containing objects at the physical layer."
	INDEX   { lucentPM4T1E1BoardIndex,
		    lucentPM4T1E1Index }
	::= { lucentPM4T1E1Table 1 }

LucentPM4T1E1Entry ::=
	SEQUENCE {
		lucentPM4T1E1BoardIndex
			INTEGER,
		lucentPM4T1E1UnitType
			PMUnitType,
		lucentPM4T1E1Index
			INTEGER,
		lucentPM4T1E1SerialIndex
			INTEGER,
		lucentPM4T1E1SerialCount
			INTEGER,
		lucentPM4T1E1PhysType
			INTEGER,
		lucentPM4T1E1Status
			INTEGER,
		lucentPM4T1E1Function
			INTEGER,
		lucentPM4T1E1Framing
			INTEGER,
		lucentPM4T1E1Encoding
			INTEGER,
		lucentPM4T1E1PCM
			INTEGER,
		lucentPM4T1E1SuperSignal
			INTEGER,
		lucentPM4T1E1StartMode
			INTEGER,
		lucentPM4T1E1ChangeTime
			TimeTicks,
		lucentPM4T1E1RecvLevel
			Gauge,
		lucentPM4T1E1BlueAlarms
			Counter,
		lucentPM4T1E1YellowAlarms
			Counter,
		lucentPM4T1E1CarrierLoss
			Counter,
		lucentPM4T1E1SyncLoss
			Counter,
		lucentPM4T1E1BipolarErrors
			Counter,
		lucentPM4T1E1CRCErrors
			Counter,
		lucentPM4T1E1SyncErrors
			Counter
	}

lucentPM4T1E1BoardIndex OBJECT-TYPE
	SYNTAX  INTEGER
	ACCESS  read-only
	STATUS  mandatory
	DESCRIPTION
	"A unique value for each board in the PM4 chassis."
	::= { lucentPM4T1E1Entry 1 }

lucentPM4T1E1UnitType OBJECT-TYPE
	SYNTAX  PMUnitType
	ACCESS  read-only
	STATUS  mandatory
	DESCRIPTION
	"This object specifies the type of the unit as the T1/E1
	line. This value is a part of the interface table ifIndex."
	::= { lucentPM4T1E1Entry 2 }

lucentPM4T1E1Index OBJECT-TYPE
	SYNTAX  INTEGER
	ACCESS  read-only
	STATUS  mandatory
	DESCRIPTION
	"A unique value for each T1/E1 interface."
	::= { lucentPM4T1E1Entry 3 }

lucentPM4T1E1SerialIndex OBJECT-TYPE
	SYNTAX  INTEGER
	ACCESS  read-only
	STATUS  mandatory
	DESCRIPTION
	"The value of the instance for the serial port. This object
	provides a cross reference from the T1/E1 interface to the
	serial port to which it is mapped."
	::= { lucentPM4T1E1Entry 4 }

lucentPM4T1E1SerialCount OBJECT-TYPE
	SYNTAX  INTEGER
	ACCESS  read-only
	STATUS  mandatory
	DESCRIPTION
	"The number of serial ports assigned to this interface. If this is
	a Channelized T1/E1, then the count is 24/32. If this is a fractional
	T1/E1, then the count can be any number between 1 and a number less
	than 24/32."
	::= { lucentPM4T1E1Entry 5 }

lucentPM4T1E1PhysType OBJECT-TYPE
	SYNTAX  INTEGER {
		t1(1),
		e1(2)
	}
	ACCESS  read-only
	STATUS  mandatory
	DESCRIPTION
	"The type of interface (T1 or E1)."
	::= { lucentPM4T1E1Entry 6 }

lucentPM4T1E1Status OBJECT-TYPE
	SYNTAX  PMEquipPRIStatus
	ACCESS  read-only
	STATUS  mandatory
	DESCRIPTION
	"The current operational status of the interface."
	::= { lucentPM4T1E1Entry 7 }

lucentPM4T1E1Function OBJECT-TYPE
	SYNTAX  INTEGER {
		isdn(1),
		channelized(2),
		clear(3),
		fractional(4),
		isdnfrac(5)
	}
	ACCESS  read-only
	STATUS  mandatory
	DESCRIPTION
	"The configured function of the interface."
	::= { lucentPM4T1E1Entry 8 }

lucentPM4T1E1Framing OBJECT-TYPE
	SYNTAX  INTEGER {
		esf(1),
		d4(2),
		crc4(3),
		fas(4)
	}
	ACCESS  read-only
	STATUS  mandatory
	DESCRIPTION
	"The configured line framing."
	::= { lucentPM4T1E1Entry 9 }

lucentPM4T1E1Encoding OBJECT-TYPE
	SYNTAX  INTEGER {
		ami(1),
		b8zs(2),
		hdb3(3)
	}
	ACCESS  read-only
	STATUS  mandatory
	DESCRIPTION
	"The configured line signal encoding."
	::= { lucentPM4T1E1Entry 10 }

lucentPM4T1E1PCM OBJECT-TYPE
	SYNTAX  INTEGER {
		ulaw(1),
		alaw(2)
	}
	ACCESS  read-only
	STATUS  mandatory
	DESCRIPTION
	"The configured voice modulation."
	::= { lucentPM4T1E1Entry 11 }

lucentPM4T1E1SuperSignal OBJECT-TYPE
	SYNTAX  INTEGER {
		em(1),
		groundstart(2)
	}
	ACCESS  read-write
	STATUS  mandatory
	DESCRIPTION
	"The configured supervisory signalling mode for this interface."
	::= { lucentPM4T1E1Entry 12 }

lucentPM4T1E1StartMode OBJECT-TYPE
	SYNTAX  INTEGER {
		wink(1),
		immediate(2)
	}
	ACCESS  read-write
	STATUS  mandatory
	DESCRIPTION
	"The configured start mode for this interface."
	::= { lucentPM4T1E1Entry 13 }

lucentPM4T1E1ChangeTime OBJECT-TYPE
	SYNTAX  TimeTicks
	ACCESS  read-only
	STATUS  mandatory
	DESCRIPTION
	"The amount of time since the last status change."
	::= { lucentPM4T1E1Entry 14 }

lucentPM4T1E1RecvLevel OBJECT-TYPE
	SYNTAX  Gauge
	ACCESS  read-only
	STATUS  mandatory
	DESCRIPTION
	"An estimate of the serial interface's current recieve
	signal level in DB."
	::= { lucentPM4T1E1Entry 15 }

lucentPM4T1E1BlueAlarms OBJECT-TYPE
	SYNTAX  Counter
	ACCESS  read-only
	STATUS  mandatory
	DESCRIPTION
	"The total number of Blue Alarms on the interface."
	::= { lucentPM4T1E1Entry 16 }

lucentPM4T1E1YellowAlarms OBJECT-TYPE
	SYNTAX  Counter
	ACCESS  read-only
	STATUS  mandatory
	DESCRIPTION
	"The total number of Yellow Alarms on the interface."
	::= { lucentPM4T1E1Entry 17 }

lucentPM4T1E1CarrierLoss OBJECT-TYPE
	SYNTAX  Counter
	ACCESS  read-only
	STATUS  mandatory
	DESCRIPTION
	"The total number of times the interface has lost
	carrier."
	::= { lucentPM4T1E1Entry 18 }

lucentPM4T1E1SyncLoss OBJECT-TYPE
	SYNTAX  Counter
	ACCESS  read-only
	STATUS  mandatory
	DESCRIPTION
	"The total number of times the interface has lost
	frame synchronization."
	::= { lucentPM4T1E1Entry 19 }

lucentPM4T1E1BipolarErrors OBJECT-TYPE
	SYNTAX  Counter
	ACCESS  read-only
	STATUS  mandatory
	DESCRIPTION
	"The total number of bipolar violations detected
	on the interface."
	::= { lucentPM4T1E1Entry 20 }

lucentPM4T1E1CRCErrors OBJECT-TYPE
	SYNTAX  Counter
	ACCESS  read-only
	STATUS  mandatory
	DESCRIPTION
	"The total number of frame level CRC errors detected
	on the interface."
	::= { lucentPM4T1E1Entry 21 }

lucentPM4T1E1SyncErrors OBJECT-TYPE
	SYNTAX  Counter
	ACCESS  read-only
	STATUS  mandatory
	DESCRIPTION
	"The total number of frame synchronization errors
	detected on the interface."
	::= { lucentPM4T1E1Entry 22 }

-- ++++++++++++++++++++++++++++++++++++++++++++++++++++++++++++++++++++++++++
-- The Lucent Modem Interface Configuration table
-- ++++++++++++++++++++++++++++++++++++++++++++++++++++++++++++++++++++++++++
lucentPM4CmModem	OBJECT IDENTIFIER ::= { lucentPM4CmInterfaces 3 }

lucentPM4ModemTable OBJECT-TYPE
	SYNTAX  SEQUENCE OF LucentPM4ModemEntry
	ACCESS  not-accessible
	STATUS  mandatory
	DESCRIPTION
	"A list of modem entries."
	::= { lucentPM4CmModem 1 }

lucentPM4ModemEntry OBJECT-TYPE
	SYNTAX  LucentPM4ModemEntry
	ACCESS  not-accessible
	STATUS  mandatory
	DESCRIPTION
	"A modem entry containing objects at the session layer."
	INDEX   { lucentPM4ModemBoardIndex,
		    lucentPM4ModemUnitType,
		    lucentPM4ModemIndex }
	::= { lucentPM4ModemTable 1 }

LucentPM4ModemEntry ::=
	SEQUENCE {
		lucentPM4ModemBoardIndex
			INTEGER,
		lucentPM4ModemUnitType
			PMUnitType,
		lucentPM4ModemIndex
			INTEGER,
		lucentPM4ModemPortName
			DisplayString,
		lucentPM4ModemStatus
			INTEGER,
		lucentPM4ModemProtocol
			INTEGER,
		lucentPM4ModemCompression
			INTEGER,
		lucentPM4ModemInSpeed
			Gauge,
		lucentPM4ModemOutSpeed
			Gauge,
		lucentPM4ModemInByteCount
			Counter,
		lucentPM4ModemOutByteCount
			Counter,
		lucentPM4ModemRetrains
			Counter,
		lucentPM4ModemRenegotiates
			Counter,
		lucentPM4ModemCalls
			Counter,
		lucentPM4ModemDetects
			Counter,
		lucentPM4ModemConnects
			Counter
	}

lucentPM4ModemBoardIndex OBJECT-TYPE
	SYNTAX  INTEGER
	ACCESS  read-only
	STATUS  mandatory
	DESCRIPTION
	"A unique value for each modem interface."
	::= { lucentPM4ModemEntry 1 }

lucentPM4ModemUnitType OBJECT-TYPE
	SYNTAX  PMUnitType
	ACCESS  read-only
	STATUS  mandatory
	DESCRIPTION
	"Unit type specifies the type of device or interface."
	::= { lucentPM4ModemEntry 2 }

lucentPM4ModemIndex OBJECT-TYPE
	SYNTAX  INTEGER
	ACCESS  read-only
	STATUS  mandatory
	DESCRIPTION
	"A unique value for each modem interface. The value of
	this object can be 1 - 96 for a Quad T1, 1 - 94 for a
	Tri E1 card."
	::= { lucentPM4ModemEntry 3 }

lucentPM4ModemPortName OBJECT-TYPE
	SYNTAX  DisplayString (SIZE (0..8))
	ACCESS  read-only
	STATUS  mandatory
	DESCRIPTION
	"A textual string containing the name of the serial
	interface (ie. S0, S1, etc)."
	::= { lucentPM4ModemEntry 4 }

lucentPM4ModemStatus OBJECT-TYPE
	SYNTAX  INTEGER {
		none(1),
		bound(2),
		connecting(3),
		active(4),
		test(5),
		down(6),
		ready(7),
		halt(8),
		admin(9)
	}
	ACCESS  read-only
	STATUS  mandatory
	DESCRIPTION
	"A current state of the modem."
	::= { lucentPM4ModemEntry 5 }

lucentPM4ModemProtocol OBJECT-TYPE
	SYNTAX  INTEGER {
		none(1),
		lapm(2),
		mnp(3),
		bufferd(4),
		direct(5),
		cellular(6)
	}
	ACCESS  read-only
	STATUS  mandatory
	DESCRIPTION
	"The error correcting protocol being used in the modem."
	::= { lucentPM4ModemEntry 6 }

lucentPM4ModemCompression OBJECT-TYPE
	SYNTAX  INTEGER {
		none(1),
		v42bis(2),
		mnp5(3),
		stac(4)
	}
	ACCESS  read-only
	STATUS  mandatory
	DESCRIPTION
	"The compression being used in the modem interface."
	::= { lucentPM4ModemEntry 7 }

lucentPM4ModemInSpeed OBJECT-TYPE
	SYNTAX  Gauge
	ACCESS  read-only
	STATUS  mandatory
	DESCRIPTION
	"An estimate of the modem interface's current inbound
	bandwidth in bits per second."
	::= { lucentPM4ModemEntry 8 }

lucentPM4ModemOutSpeed OBJECT-TYPE
	SYNTAX  Gauge
	ACCESS  read-only
	STATUS  mandatory
	DESCRIPTION
	"An estimate of the modem interface's current outbound
	bandwidth in bits per second."
	::= { lucentPM4ModemEntry 9 }

lucentPM4ModemInByteCount OBJECT-TYPE
	SYNTAX  Counter
	ACCESS  read-only
	STATUS  mandatory
	DESCRIPTION
	"The total number of bytes received on the
	serial interface."
	::= { lucentPM4ModemEntry 10 }

lucentPM4ModemOutByteCount OBJECT-TYPE
	SYNTAX  Counter
	ACCESS  read-only
	STATUS  mandatory
	DESCRIPTION
	"The total number of bytes transmitted on the
	serial interface."
	::= { lucentPM4ModemEntry 11 }

lucentPM4ModemRetrains OBJECT-TYPE
	SYNTAX  Counter
	ACCESS  read-only
	STATUS  mandatory
	DESCRIPTION
	"The number of retrains attempted by the modem."
	::= { lucentPM4ModemEntry 12 }

lucentPM4ModemRenegotiates OBJECT-TYPE
	SYNTAX  Counter
	ACCESS  read-only
	STATUS  mandatory
	DESCRIPTION
	"The number of renegotiates attempted by the modem."
	::= { lucentPM4ModemEntry 13 }

lucentPM4ModemCalls OBJECT-TYPE
	SYNTAX  Counter
	ACCESS  read-only
	STATUS  mandatory
	DESCRIPTION
	"The number of times a call received by the modem."
	::= { lucentPM4ModemEntry 14 }

lucentPM4ModemDetects OBJECT-TYPE
	SYNTAX  Counter
	ACCESS  read-only
	STATUS  mandatory
	DESCRIPTION
	"The number of analog calls received by the modem."
	::= { lucentPM4ModemEntry 15 }

lucentPM4ModemConnects OBJECT-TYPE
	SYNTAX  Counter
	ACCESS  read-only
	STATUS  mandatory
	DESCRIPTION
	"The number of successful calls received by the modem."
	::= { lucentPM4ModemEntry 16 }

-- ++++++++++++++++++++++++++++++++++++++++++++++++++++++++++++++++++++++++++
-- The Lucent Ethernet Interface table
-- ++++++++++++++++++++++++++++++++++++++++++++++++++++++++++++++++++++++++++
lucentPM4CmEther	OBJECT IDENTIFIER ::= { lucentPM4CmInterfaces 4 }

lucentPM4EtherTable OBJECT-TYPE
	SYNTAX  SEQUENCE OF LucentPM4EtherEntry
	ACCESS  not-accessible
	STATUS  mandatory
	DESCRIPTION
	"A list of ethernet interface entries. This object is not
	accessible"
	::= { lucentPM4CmEther 1 }

lucentPM4EtherEntry OBJECT-TYPE
	SYNTAX  LucentPM4EtherEntry
	ACCESS  not-accessible
	STATUS  mandatory
	DESCRIPTION
	"Ethernet interface entry containing objects at the 
	Session/Physical layers."
	INDEX   { lucentPM4EtherBoardIndex,
		    lucentPM4EtherIfType,
		    lucentPM4EtherIndex }
	::= { lucentPM4EtherTable 1 }

LucentPM4EtherEntry ::=
	SEQUENCE {
		lucentPM4EtherBoardIndex
			INTEGER,
		lucentPM4EtherIfType
			PMUnitType,
		lucentPM4EtherIndex
			INTEGER,
		lucentPM4EtherIfIndex
			INTEGER,
		lucentPM4EtherPortName
			DisplayString,
		lucentPM4EtherMacAddr
			PhysAddress,
		lucentPM4EtherIPAddr
			IpAddress,
		lucentPM4EtherIPGateway
			IpAddress,
		lucentPM4EtherPriNameServer
			IpAddress,
		lucentPM4EtherAltNameServer
			IpAddress,
		lucentPM4EtherSubnetMask
			IpAddress,
		lucentPM4EtherInFilter
			DisplayString,
		lucentPM4EtherOutFilter
			DisplayString,
		lucentPM4EtherOptRip
			INTEGER,
		lucentPM4EtherOptSlip
			INTEGER,
		lucentPM4EtherOptEtherDown
			INTEGER,
		lucentPM4EtherOptBcastHigh
			INTEGER,
		lucentPM4EtherOptSnmp
			INTEGER,
		lucentPM4EtherOptNoListen
			INTEGER,
		lucentPM4EtherOptDefaultRip
			INTEGER,
		lucentPM4EtherOptDefaultListen
			INTEGER,
		lucentPM4EtherOptIPFilter
			INTEGER,
		lucentPM4EtherOptDns
			INTEGER,
		lucentPM4EtherOptPmeMsg
			INTEGER,
		lucentPM4EtherOptNoClip
			INTEGER,
		lucentPM4EtherOptEtherIpx
			INTEGER,
		lucentPM4EtherOptNetBIOS
			INTEGER,
		lucentPM4EtherOptAccounting
			INTEGER,
		lucentPM4EtherOptNoPAP
			INTEGER
	}

lucentPM4EtherBoardIndex OBJECT-TYPE
	SYNTAX  INTEGER
	ACCESS  read-only
	STATUS  mandatory
	DESCRIPTION
	"A unique value for each ethernet board. The manager card
	has two ethernet interfaces at present. The ethernet interface
	in slot 4 has a board ID 10 and if there is a manager card in
	slot 5, the board ID for the interface would be 11."
	::= { lucentPM4EtherEntry 1 }

lucentPM4EtherIfType OBJECT-TYPE
	SYNTAX  PMUnitType
	ACCESS  read-only
	STATUS  mandatory
	DESCRIPTION
	"The interface type which together with the board ID and 
	the interface number will uniquely identify the interface."
	::= { lucentPM4EtherEntry 2 }

lucentPM4EtherIndex OBJECT-TYPE
	SYNTAX  INTEGER {
		ether0(1),
		ether1(2),
		other(3)
	}
	ACCESS  read-only
	STATUS  mandatory
	DESCRIPTION
	"A unique value for each ethernet interface. The manager card
	has two ethernet interfaces at present. ether0(1) represents
	10 Base-T interface and ether1(2) specifies the 10/100 Base-T
	auto-sensing ethernet interface."
	::= { lucentPM4EtherEntry 3 }

lucentPM4EtherIfIndex OBJECT-TYPE
	SYNTAX  INTEGER {
		ether0(67436545),
		ether1(168099841)
	}
	ACCESS  read-only
	STATUS  mandatory
	DESCRIPTION
	"IfIndex cross reference value for the ethernet interfaces. 
	The manager card has two ethernet interfaces at present. 
	ether0(67436545) represents 10 Base-T interface which corresponds
	to board 4 and interface 1. The enumerated value ether1(168099841) 
	specifies the 10/100 Base-T auto-sensing ethernet interface
	which corresponds to board 4 and interface 2. We can add the
	standby manager card ethernet interfaces when they are available."
	::= { lucentPM4EtherEntry 4 }

lucentPM4EtherPortName OBJECT-TYPE
	SYNTAX  DisplayString (SIZE(1..8))
	ACCESS  read-write
	STATUS  mandatory
	DESCRIPTION
	"A printable ASCII string specifying the name of the ethernet
	port."
	::= { lucentPM4EtherEntry 5 }

lucentPM4EtherMacAddress OBJECT-TYPE
	SYNTAX  PhysAddress
	ACCESS  read-only
	STATUS  mandatory
	DESCRIPTION
	"Physical address of the interface."
	::= { lucentPM4EtherEntry 6 }

lucentPM4EtherIpAddress OBJECT-TYPE
	SYNTAX  IpAddress
	ACCESS  read-write
	STATUS  mandatory
	DESCRIPTION
	"IP address of the interface."
	::= { lucentPM4EtherEntry 7 }

lucentPM4EtherIpGateway OBJECT-TYPE
	SYNTAX  IpAddress
	ACCESS  read-write
	STATUS  mandatory
	DESCRIPTION
	"IP address of the gateway machine."
	::= { lucentPM4EtherEntry 8 }

lucentPM4EtherPriNameServer OBJECT-TYPE
	SYNTAX  IpAddress
	ACCESS  read-write
	STATUS  mandatory
	DESCRIPTION
	"IP address of the primary name server."
	::= { lucentPM4EtherEntry 9 }

lucentPM4EtherAltNameServer OBJECT-TYPE
	SYNTAX  IpAddress
	ACCESS  read-write
	STATUS  mandatory
	DESCRIPTION
	"IP address of the alternate name server."
	::= { lucentPM4EtherEntry 10 }

lucentPM4EtherSubnetMask OBJECT-TYPE
	SYNTAX  IpAddress
	ACCESS  read-write
	STATUS  mandatory
	DESCRIPTION
	"Subnet mask of the interface. Used to partition the network
	into different branches."
	::= { lucentPM4EtherEntry 11 }

lucentPM4EtherInFilter OBJECT-TYPE
	SYNTAX  DisplayString (SIZE(1..16))
	ACCESS  read-write
	STATUS  mandatory
	DESCRIPTION
	"IP Input packet filter. Used to control the type of IP packets
	reaching the interface."
	::= { lucentPM4EtherEntry 12 }

lucentPM4EtherOutFilter OBJECT-TYPE
	SYNTAX  DisplayString (SIZE(1..16))
	ACCESS  read-write
	STATUS  mandatory
	DESCRIPTION
	"IP output packet filter. Used to control the type of packets
	sent out of the interface."
	::= { lucentPM4EtherEntry 13 }

lucentPM4EtherOptRip OBJECT-TYPE
	SYNTAX INTEGER {
		disable(1),
		enable(2)
	}
	ACCESS read-write
	STATUS mandatory
	DESCRIPTION
	"The RIP protocol enable/disable option."
	::= { lucentPM4EtherEntry 14 }

lucentPM4EtherOptSlip OBJECT-TYPE
	SYNTAX INTEGER {
		disable(1),
		enable(2)
	}
	ACCESS read-write
	STATUS mandatory
	DESCRIPTION
	"The SLIP protocol enable/disable option."
	::= { lucentPM4EtherEntry 15 }

lucentPM4EtherOptEtherDown OBJECT-TYPE
	SYNTAX INTEGER {
		disable(1),
		enable(2)
	}
	ACCESS read-write
	STATUS mandatory
	DESCRIPTION
	"Ethernet interface down enable/disable option."
	::= { lucentPM4EtherEntry 16 }

lucentPM4EtherOptBcastHigh OBJECT-TYPE
	SYNTAX INTEGER {
		disable(1),
		enable(2)
	}
	ACCESS read-write
	STATUS mandatory
	DESCRIPTION
	"Use high one(s) broadcast address enable/disable option."
	::= { lucentPM4EtherEntry 17 }

lucentPM4EtherOptSnmp OBJECT-TYPE
	SYNTAX INTEGER {
		disable(1),
		enable(2)
	}
	ACCESS read-write
	STATUS mandatory
	DESCRIPTION
	"Default SNMP protocol enable/disable option."
	::= { lucentPM4EtherEntry 18 }

lucentPM4EtherOptNoListen OBJECT-TYPE
	SYNTAX INTEGER {
		disable(1),
		enable(2)
	}
	ACCESS read-write
	STATUS mandatory
	DESCRIPTION
	"Do not listen to RIP on the ether interface."
	::= { lucentPM4EtherEntry 19 }

lucentPM4EtherOptDefaultRip OBJECT-TYPE
	SYNTAX INTEGER {
		disable(1),
		enable(2)
	}
	ACCESS read-write
	STATUS mandatory
	DESCRIPTION
	"Default RIP protocol enable/disable option."
	::= { lucentPM4EtherEntry 20 }

lucentPM4EtherOptDefaultListen OBJECT-TYPE
	SYNTAX INTEGER {
		disable(1),
		enable(2)
	}
	ACCESS read-write
	STATUS mandatory
	DESCRIPTION
	"Default listen enable/disable option."
	::= { lucentPM4EtherEntry 21 }

lucentPM4EtherOptIPFilter OBJECT-TYPE
	SYNTAX INTEGER {
		disable(1),
		enable(2)
	}
	ACCESS read-write
	STATUS mandatory
	DESCRIPTION
	"IP filter enable/disable option."
	::= { lucentPM4EtherEntry 22 }

lucentPM4EtherOptDns OBJECT-TYPE
	SYNTAX INTEGER {
		disable(1),
		enable(2)
	}
	ACCESS read-write
	STATUS mandatory
	DESCRIPTION
	"DNS enable/disable option."
	::= { lucentPM4EtherEntry 23 }

lucentPM4EtherOptPmeMsg OBJECT-TYPE
	SYNTAX INTEGER {
		disable(1),
		enable(2)
	}
	ACCESS read-write
	STATUS mandatory
	DESCRIPTION
	"PME Msg. enable/disable option. Whatever that means."
	::= { lucentPM4EtherEntry 24 }

lucentPM4EtherOptNoClip OBJECT-TYPE
	SYNTAX INTEGER {
		disable(1),
		enable(2)
	}
	ACCESS read-write
	STATUS mandatory
	DESCRIPTION
	"No Clip enable/disable option. Whatever that means."
	::= { lucentPM4EtherEntry 25 }

lucentPM4EtherOptEtherIpx OBJECT-TYPE
	SYNTAX INTEGER {
		disable(1),
		enable(2)
	}
	ACCESS read-write
	STATUS mandatory
	DESCRIPTION
	"Ether IPX enable/disable option."
	::= { lucentPM4EtherEntry 26 }

lucentPM4EtherOptNetBIOS OBJECT-TYPE
	SYNTAX INTEGER {
		disable(1),
		enable(2)
	}
	ACCESS read-write
	STATUS mandatory
	DESCRIPTION
	"Net BIOS enable/disable option."
	::= { lucentPM4EtherEntry 27 }

lucentPM4EtherOptAccounting OBJECT-TYPE
	SYNTAX INTEGER {
		disable(1),
		enable(2)
	}
	ACCESS read-write
	STATUS mandatory
	DESCRIPTION
	"Accounting enable/disable option."
	::= { lucentPM4EtherEntry 28 }

lucentPM4EtherOptNoPAP OBJECT-TYPE
	SYNTAX INTEGER {
		disable(1),
		enable(2)
	}
	ACCESS read-write
	STATUS mandatory
	DESCRIPTION
	"PAP enable/disable option."
	::= { lucentPM4EtherEntry 29 }

-- ++++++++++++++++++++++++++++++++++++++++++++++++++++++++++++++++++++++++++
-- Lucent Fault Management Group
-- ++++++++++++++++++++++++++++++++++++++++++++++++++++++++++++++++++++++++++
lucentPM4FaultMgmt	OBJECT IDENTIFIER	::= { lucentPM4Mib 5 }

-- ++++++++++++++++++++++++++++++++++++++++++++++++++++++++++++++++++++++++++
-- Lucent Fault Isolation Group
-- ++++++++++++++++++++++++++++++++++++++++++++++++++++++++++++++++++++++++++
lucentPM4FaultMgmtIsolation	OBJECT IDENTIFIER	::= { lucentPM4FaultMgmt 1 }

-- ++++++++++++++++++++++++++++++++++++++++++++++++++++++++++++++++++++++++++
-- Lucent Chassis Global Fault management table
-- ++++++++++++++++++++++++++++++++++++++++++++++++++++++++++++++++++++++++++
lucentPM4FaultMgmtChasTrap	OBJECT-TYPE
	SYNTAX	SEQUENCE OF LucentPM4FMChasTrapEntry
	ACCESS	not-accessible
	STATUS	mandatory
	DESCRIPTION
	"Chassis Trap table which indicates one of several Traps. The
	chassis trap table stores the previous history of the traps
	which can be retrieved by the management stations at a later
	time. This object is not-accessible and present for MIB clarity."
	::= { lucentPM4FaultMgmtIsolation 1 }

lucentPM4FMChasTrapEntry	OBJECT-TYPE
	SYNTAX	LucentPM4FMChasTrapEntry
	ACCESS	not-accessible
	STATUS	mandatory
	DESCRIPTION
	"Entry in the chassis Trap table. Each trap is uniquely
	identified by an index. This object is not accessible and
	present for MIB clarity."
	INDEX	{ lucentPM4FMChasTrapIndex }
	::= { lucentPM4FaultMgmtChasTrap 1 }

LucentPM4FMChasTrapEntry ::=
	SEQUENCE {
		lucentPM4FMChasTrapIndex
			INTEGER,
		lucentPM4FMChasBoardID
			INTEGER,
		lucentPM4FMChasTrapUnitType
			PMUnitType,
		lucentPM4FMChasTrapUnitIndex
			INTEGER,
		lucentPM4FMChasTrapStatus
			INTEGER,
		lucentPM4FMChasTrapSeverity
			INTEGER,
		lucentPM4FMChasTrapTimeStamp
			TimeTicks,
		lucentPM4FMChasTrapState
			INTEGER
	}

lucentPM4FMChasTrapIndex	OBJECT-TYPE
	SYNTAX	INTEGER
	ACCESS	read-only
	STATUS	mandatory
	DESCRIPTION
	"Index into the Trap table on the agent. This table stores the
	previous 500 traps which can be retrieved at any given time."
	::= { lucentPM4FMChasTrapEntry 1 }

lucentPM4FMChasTrapBoardID	OBJECT-TYPE
	SYNTAX	INTEGER
	ACCESS	read-only
	STATUS	mandatory
	DESCRIPTION
	"Board ID is the board number for which this trap is stored. If
	the trap is for an auxillary device such as a power supply or
	fan, this value is set to zero."
	::= { lucentPM4FMChasTrapEntry 2 }

lucentPM4FMChasTrapUnitType	OBJECT-TYPE
	SYNTAX	PMUnitType
	ACCESS	read-only
	STATUS	mandatory
	DESCRIPTION
	"Uniquely specifies the unit type for this trap. The unit can be
	a board or any other device in the chassis such as a fan or a power
	supply."
	::= { lucentPM4FMChasTrapEntry 3 }

lucentPM4FMChasTrapUnitIndex	OBJECT-TYPE
	SYNTAX	INTEGER
	ACCESS	read-only
	STATUS	mandatory
	DESCRIPTION
	"Uniquely specifies the unit index. The unit index is same as the
	ifIndex for T1/E1 interfaces, or the modemIndex for the modems or
	fan or power supply index for fan or power supplies."
	::= { lucentPM4FMChasTrapEntry 4 }

lucentPM4FMChasTrapStatus	OBJECT-TYPE
	SYNTAX	INTEGER {
		other(1),
		online(2),
		offline(3),
		maintenance(4),
		fault(5),
		notinstalled(6)
	}
	ACCESS	read-only
	STATUS	mandatory
	DESCRIPTION
	"Trap status specifies the associated object in the Trap is online(2), 
	offline(3), maintenance(4) or fault(5)."
	::= { lucentPM4FMChasTrapEntry 5 }

lucentPM4FMChasTrapSeverity	OBJECT-TYPE
	SYNTAX	PMAlarmType
	ACCESS	read-only
	STATUS	mandatory
	DESCRIPTION
	"Trap severity specifies the severity of the Trap for the associated
	object."
	::= { lucentPM4FMChasTrapEntry 6 }

lucentPM4FMChasTrapTimeStamp	OBJECT-TYPE
	SYNTAX	TimeTicks
	ACCESS	read-only
	STATUS	mandatory
	DESCRIPTION
	"This object stores the timestamp of this trap."
	::= { lucentPM4FMChasTrapEntry 7 }

lucentPM4FMChasTrapState	OBJECT-TYPE
	SYNTAX	INTEGER {
		trapsent(1),
		ackdue(2),
		acked(3)
	}
	ACCESS	read-write
	STATUS	mandatory
	DESCRIPTION
	"This object stores the Trap state of this trap."
	::= { lucentPM4FMChasTrapEntry 8 }

-- ++++++++++++++++++++++++++++++++++++++++++++++++++++++++++++++++++++++++++
-- Lucent Fault management objects
-- ++++++++++++++++++++++++++++++++++++++++++++++++++++++++++++++++++++++++++
lucentPM4FMBoardIndex	OBJECT-TYPE
	SYNTAX	INTEGER
	ACCESS	not-accessible
	STATUS	mandatory
	DESCRIPTION
	"Board index uniquely specifies the board in the chassis. 
	This object is set to zero for power supplies, fans and
	other auxillary devices. This object is not accessible 
	through Get, Get-Next or Set PDUs. It is sent out as part
	of the Trap."
	::= { lucentPM4FaultMgmtIsolation 2 }

lucentPM4FMUnitIndex	OBJECT-TYPE
	SYNTAX	INTEGER
	ACCESS	not-accessible
	STATUS	mandatory
	DESCRIPTION
	"Unit index uniquely specifies the T1/E1 line, or modem or 
	any device (logical/physical) in the chassis. This object
	is not accessible through Get, Get-Next or Set PDUs. It is
	sent out as part of the Trap."
	::= { lucentPM4FaultMgmtIsolation 3 }

lucentPM4FMUnitType	OBJECT-TYPE
	SYNTAX	PMUnitType
	ACCESS	not-accessible
	STATUS	mandatory
	DESCRIPTION
	"Unit type specifies the T1/E1 line, or modem or any device
 	in the chassis. This object is not accessible through Get,
	Get-Next or Set PDUs. It is sent out as part of the Trap."
	::= { lucentPM4FaultMgmtIsolation 4 }

lucentPM4FMUnitTrapStatus	OBJECT-TYPE
	SYNTAX	INTEGER {
		other(1),
		offline(2),
		online(3),
		failed(4),
		restored(5),
		pwrwarn(6),
		tempwarn(7),
		temphot(8),
		dtrloss(9),
		carrierloss(10),
		renegotiation(11),
		los(12),		-- Loss of Signal
		ais(13),		-- Alarm Indication Signal
		redalarm(14), 	-- Loss of Framing
		yellowalarm(15),	-- Remote Alarm Indication (indicating remote red alarm)
		cv(16),		-- Code Violation
		crc(17),		-- Cyclic Redundancy Check
		bpv(18),		-- Bipolar Violations
		fer(19),		-- Framing Errors
		pll(20),		-- Phase Locked Loop
		es(21),		-- Errored Seconds
		ses(22),		-- Severely Errored Seconds
		sefs(23),		-- Severely Errored Framing Seconds
		uas(24),		-- Unavailable Seconds
		dm(25),		-- Degraded Minutes
		les(26),		-- Line Errored Seconds
		css(27),		-- Controlled Slip Seconds
		bes(28)		-- Bursty Errored Seconds
	}
	ACCESS	not-accessible
	STATUS	mandatory
	DESCRIPTION
	"Trap status specifies the associated object in the Trap. 
	This object is not accessible other than when produced as 
	the result of a trap."
	::= { lucentPM4FaultMgmtIsolation 5 }

lucentPM4FMUnitTrapSeverity	OBJECT-TYPE
	SYNTAX	PMAlarmType
	ACCESS	not-accessible
	STATUS	mandatory
	DESCRIPTION
	"Trap severity specifies the severity of the Trap for the associated
	object. This object is not accessible except when produced as the 
	result of a trap."
	::= { lucentPM4FaultMgmtIsolation 6 }

-- ++++++++++++++++++++++++++++++++++++++++++++++++++++++++++++++++++++++++++
-- Lucent Alarm Configuration Group
-- ++++++++++++++++++++++++++++++++++++++++++++++++++++++++++++++++++++++++++
lucentPM4FMTrapConfig	OBJECT IDENTIFIER	::= { lucentPM4FaultMgmt 2 }

-- ++++++++++++++++++++++++++++++++++++++++++++++++++++++++++++++++++++++++++
-- Lucent Equipment Traps configuration table
-- ++++++++++++++++++++++++++++++++++++++++++++++++++++++++++++++++++++++++++
lucentPM4FMEqpTrapCfg	OBJECT-TYPE
	SYNTAX	SEQUENCE OF LucentPM4FMEqpTrapCfgEntry
	ACCESS	not-accessible
	STATUS	mandatory
	DESCRIPTION
	"Equipment Trap configuration table configure Traps. The
	objects in this table are used to enable or disable traps
	on a per board/interface/device basis. This object is 
	not-accessible and present for MIB clarity."
	::= { lucentPM4FMTrapConfig 1 }

lucentPM4FMEqpTrapCfgEntry	OBJECT-TYPE
	SYNTAX	LucentPM4FMEqpTrapCfgEntry
	ACCESS	not-accessible
	STATUS	mandatory
	DESCRIPTION
	"Entry in the equipment Trap config table. Each trap is 
	uniquely identified by the board ID, Unit type and unit
	index. For auxillary devices such as power supplies and
	fans, the board index will be zero, the unit index 
	identifies the units and the unit type specifies if the
	unit is a fan, power supplies etc. This object is not 
	accessible and present for MIB clarity."
	INDEX	{ lucentPM4FMEqpBoardIndex,
		  lucentPM4FMEqpUnitType,
		  lucentPM4FMEqpUnitIndex }
	::= { lucentPM4FMEqpTrapCfg 1 }

LucentPM4FMEqpTrapCfgEntry ::=
	SEQUENCE {
		lucentPM4FMEqpBoardIndex
			INTEGER,
		lucentPM4FMEqpUnitType
			PMUnitType,
		lucentPM4FMEqpunitIndex
			INTEGER,
		lucentPM4FMEqpTrapId
			INTEGER,
		lucentPM4FMEqpTrapCtl
			INTEGER,
		lucentPM4FMEqpTrapRepTimer
			INTEGER
	}

lucentPM4FMEqpBoardIndex	OBJECT-TYPE
	SYNTAX	INTEGER
	ACCESS	read-only
	STATUS	mandatory
	DESCRIPTION
	"Board ID for which the Trap configuration need to apply.
	The board ID is zero if this trap configuration is for an
	auxillary device such as fans or power supplies."
	::= { lucentPM4FMEqpTrapCfgEntry 1 }

lucentPM4FMEqpUnitType	OBJECT-TYPE
	SYNTAX	PMUnitType
	ACCESS	read-only
	STATUS	mandatory
	DESCRIPTION
	"Unit type alongwith the board index and unit index specifies
	uniquely the device/interface which is being configured."
	::= { lucentPM4FMEqpTrapCfgEntry 2 }

lucentPM4FMEqpUnitIndex	OBJECT-TYPE
	SYNTAX	INTEGER
	ACCESS	read-only
	STATUS	mandatory
	DESCRIPTION
	"Unit index refers to the interface or sub-device such as a
	modem, serial port etc. For devices such as power supplies
	and fans this object is zero."
	::= { lucentPM4FMEqpTrapCfgEntry 3 }

lucentPM4FMEqpTrapId	OBJECT-TYPE
	SYNTAX	INTEGER {
		boardoffline(1),
		boardonline(2),
		pwrsupfail(3),
		pwrsuprestored(4),
		fanfail(5),
		fanrestored(6),
		boardtempwarn(7),
		boardtempnormal(8),
		boardtoohot(9),
		modemfail(10),
		linedown(11),
		lineup(12),
		linethresh(13),
		boardpwrshutdown(14),
		radiusauthfail(15)
	}
	ACCESS	read-write
	STATUS	mandatory
	DESCRIPTION
	"Trap ID indicating the trap for which the configuration must
	apply."
	::= { lucentPM4FMEqpTrapCfgEntry 4 }

lucentPM4FMEqpTrapCtl	OBJECT-TYPE
	SYNTAX	INTEGER {
		disable(1),
		enable(2)
	}
	ACCESS	read-write
	STATUS	mandatory
	DESCRIPTION
	"Trap control which configures the trap off(1) or on(2).
	When the trap is configured as off(1), the trap is not sent
	out to the management station. When configures as on(2),
	the trap is sent to all the management stations configured
	to receive the trap."
	::= { lucentPM4FMEqpTrapCfgEntry 5 }

lucentPM4FMEqpRepTimer	OBJECT-TYPE
	SYNTAX	INTEGER
	ACCESS	read-write
	STATUS	mandatory
	DESCRIPTION
	"If the trap is to be repeated, this object specifies the time
	in seconds. When this object value is set to 0, it indicates
	the trap is non-repeat trap."
	::= { lucentPM4FMEqpTrapCfgEntry 6 }

-- ++++++++++++++++++++++++++++++++++++++++++++++++++++++++++++++++++++++++++
-- Lucent T1/E1 Threshold Traps configuration table
-- ++++++++++++++++++++++++++++++++++++++++++++++++++++++++++++++++++++++++++
lucentPM4FMT1E1ThreshTrapCfg	OBJECT-TYPE
	SYNTAX	SEQUENCE OF LucentPM4FMThreshT1E1TrapCfgEntry
	ACCESS	not-accessible
	STATUS	mandatory
	DESCRIPTION
	"T1/E1 Threshold Trap configuration table to configure the
	thresholds for various T1/E1 traps. This object is 
	not-accessible and present for MIB clarity."
	::= { lucentPM4FMTrapConfig 2 }

lucentPM4FMT1E1ThreshTrapCfgEntry	OBJECT-TYPE
	SYNTAX	LucentPM4FMThreshT1E1TrapCfgEntry
	ACCESS	not-accessible
	STATUS	mandatory
	DESCRIPTION
	"Entry in the T1/E1 threshold trap config table. Each 
	trap is uniquely identified by the board index, unit 
	type and unit index which is the T1/E1 interface number.
	This object is not accessible and present for MIB clarity."
	INDEX	{ lucentPM4FMThreshBoardIndex,
		  lucentPM4FMThreshUnitType,
		  lucentPM4FMThreshUnitIndex }
	::= { lucentPM4FMT1E1ThreshTrapCfg 1 }

LucentPM4FMThreshT1E1TrapCfgEntry ::=
	SEQUENCE {
		lucentPM4FMT1E1ThreshBoardIndex
			INTEGER,
		lucentPM4FMT1E1ThreshUnitType
			INTEGER,
		lucentPM4FMT1E1ThreshUnitIndex
			INTEGER,
		lucentPM4FMT1E1ThreshESs
			Gauge,
		lucentPM4FMT1E1ThreshSESs
			Gauge,
		lucentPM4FMT1E1ThreshSEFSs
			Gauge,
		lucentPM4FMT1E1ThreshUASs
			Gauge,
		lucentPM4FMT1E1ThreshCSSs
			Gauge,
		lucentPM4FMT1E1ThreshPCVs
			Gauge,
		lucentPM4FMT1E1ThreshLESs
			Gauge,
		lucentPM4FMT1E1ThreshBESs
			Gauge,
		lucentPM4FMT1E1ThreshDMs
			Gauge,
		lucentPM4FMT1E1ThreshTrapRepTimer
			INTEGER,
		lucentPM4FMT1E1ThreshTrapAck
			INTEGER
	}

lucentPM4FMT1E1ThreshBoardIndex	OBJECT-TYPE
	SYNTAX	INTEGER
	ACCESS	read-only
	STATUS	mandatory
	DESCRIPTION
	"Board ID for which the Trap threshold configuration must
	apply. It includes boards 1 - 10 and other devices such as
	power supplies and fans etc."
	::= { lucentPM4FMT1E1ThreshTrapCfgEntry 1 }

lucentPM4FMT1E1ThreshUnitType	OBJECT-TYPE
	SYNTAX	PMUnitType
	ACCESS	read-only
	STATUS	mandatory
	DESCRIPTION
	"Unit type for which the Trap threshold configuration 
	must be applied."
	::= { lucentPM4FMT1E1ThreshTrapCfgEntry 2 }

lucentPM4FMT1E1ThreshESs	OBJECT-TYPE
	SYNTAX  Gauge
	ACCESS  read-write
	STATUS  mandatory
	DESCRIPTION
	"The threshold for errored seconds on the interface. A trap is
	issued when this set limit is exceeded. When this threshold
	exceeds, the performance of the interface will degrade. A trap
	is generated to notify the adminstrator to take appropriate
	action."
	::= { lucentPM4FMT1E1ThreshTrapCfgEntry 3 }

lucentPM4FMT1E1ThreshSESs	OBJECT-TYPE
	SYNTAX  Gauge
	ACCESS  read-write
	STATUS  mandatory
	DESCRIPTION
	"The threshold for severely errored seconds on the interface.
	A trap is issued when this limit is exceeded. A severely errored
	seconds is a second with 320 or more path code violation error
	events or one or more out of frame defects or detected AIS defect."
	::= { lucentPM4FMT1E1ThreshTrapCfgEntry 4 }

lucentPM4FMT1E1ThreshSEFSs	OBJECT-TYPE
	SYNTAX	Gauge
	ACCESS	read-write
	STATUS	mandatory
	DESCRIPTION
	"The threshold for severely errored framing seconds.
	A trap is issued when this threshold is exceeded. A severely
	errored framing second is a second with one or more frame
	defects or detected AIS defect."
	::= { lucentPM4FMT1E1ThreshTrapCfgEntry 5 }

lucentPM4FMT1E1ThreshUASs	OBJECT-TYPE
	SYNTAX 	Gauge
	ACCESS	read-write
	STATUS	mandatory
	DESCRIPTION
	"The threshold for unavailable seconds. A trap is issued 
	when this set threshold is exceeded. Unavailable seconds
	are calculated by counting the number of seconds that the
	interface is unavailable from the onset of 10 SESs. Once
	unavailable, the interface becomes available at the onset
	of 10 contiguous no SESs."
	::= { lucentPM4FMT1E1ThreshTrapCfgEntry 6 }

lucentPM4FMT1E1ThreshCSSs	OBJECT-TYPE
	SYNTAX	Gauge
	ACCESS	read-write
	STATUS	mandatory
	DESCRIPTION
	"The threshold for controlled slip seconds on the interface.
	A trap is issued when this set threshold is exceeded. A
	controlled slip second is a one-second interval containing
	one or more controlled slips."
	::= { lucentPM4FMT1E1ThreshTrapCfgEntry 7 }

lucentPM4FMT1E1ThreshPCVs	OBJECT-TYPE
	SYNTAX	Gauge
	ACCESS	read-write
	STATUS	mandatory
	DESCRIPTION
	"The threshold for path code violations on the interface. 
	A trap is issued when this set threshold is exceeded. PCV
	is a frame syncronization bit error in the D4 and E1-noCRC
	format interfaces or a CRC error in the ESF (extended super
	frame) and E1-CRC interface formats."
	::= { lucentPM4FMT1E1ThreshTrapCfgEntry 8 }

lucentPM4FMT1E1ThreshLESs	OBJECT-TYPE
	SYNTAX	Gauge
	ACCESS	read-write
	STATUS	mandatory
	DESCRIPTION
	"The threshold for line errored seconds on the interface.
	A trap is sent to the manager when this set threshold 
	is exceeded. A line errored second, according to T1M1.3
	is a second in which one or more line code violations
	were detected."
	::= { lucentPM4FMT1E1ThreshTrapCfgEntry 9 }

lucentPM4FMT1E1ThreshBESs	OBJECT-TYPE
	SYNTAX	Gauge
	ACCESS	read-write
	STATUS	mandatory
	DESCRIPTION
	"The threshold for bursty errored seconds on the interface.
	A trap is sent to the manager when this set threshold 
	is exceeded. A bursty errored second is a second with fewer
	than 320 and more than 1 path code violations."
	::= { lucentPM4FMT1E1ThreshTrapCfgEntry 10 }

lucentPM4FMT1E1ThreshDMs	OBJECT-TYPE
	SYNTAX	Gauge
	ACCESS	read-write
	STATUS	mandatory
	DESCRIPTION
	"The threshold for degraded minutes on the interface.
	A trap is sent to the manager when this set threshold 
	is exceeded. Degraded minutes are determined by collecting 
	all of the available seconds, after removing any severely 
	errored seconds. The resulting seconds is grouped into
	60 second intervals and if the cumulative errors during
	the seconds present in the group exceeds 1E-6."
	::= { lucentPM4FMT1E1ThreshTrapCfgEntry 11 }

lucentPM4FMT1E1ThreshRepTimer	OBJECT-TYPE
	SYNTAX	INTEGER
	ACCESS	read-write
	STATUS	mandatory
	DESCRIPTION
	"If the trap is to be repeated, this object specifies the time
	in seconds. When this object value is set to 0, it indicates
	the trap is non-repeat trap."
	::= { lucentPM4FMT1E1ThreshTrapCfgEntry 12 }

lucentPM4FMT1E1ThreshTrapAck	OBJECT-TYPE
	SYNTAX	INTEGER {
		other(1),
		noack(2),
		ack(3)
	}
	ACCESS	read-write
	STATUS	mandatory
	DESCRIPTION
	"If set to ack(3), clears the trap condition. If the value is
	set to noack(2), leaves the trap condition unchanged."
	::= { lucentPM4FMT1E1ThreshTrapCfgEntry 13 }

-- ++++++++++++++++++++++++++++++++++++++++++++++++++++++++++++++++++++++++++
-- Lucent Environment Traps configuration table
-- ++++++++++++++++++++++++++++++++++++++++++++++++++++++++++++++++++++++++++
lucentPM4FMEnvTrapCfg	OBJECT-TYPE
	SYNTAX	SEQUENCE OF LucentPM4FMEnvTrapCfgEntry
	ACCESS	not-accessible
	STATUS	mandatory
	DESCRIPTION
	"Environment Trap configuration table. This table
	enables configuration of voltage, power levels and
	temperature ranges for different units in the chassis.
	This object is not-accessible and present for MIB clarity."
	::= { lucentPM4FMTrapConfig 3 }

lucentPM4FMEnvTrapCfgEntry	OBJECT-TYPE
	SYNTAX	LucentPM4FMEnvTrapCfgEntry
	ACCESS	not-accessible
	STATUS	mandatory
	DESCRIPTION
	"Entry in the environment trap config table. Each trap
	is uniquely identified by the board index, unit type 
	and unit index. This object is not accessible and present
	for MIB clarity."
	INDEX	{ lucentPM4FMEnvBoardID,
		  lucentPM4FMEnvUnitType,
		  lucentPM4FMEnvUnitIndex }
	::= { lucentPM4FMEnvTrapCfg 1 }

LucentPM4FMEnvTrapCfgEntry ::=
	SEQUENCE {
		lucentPM4FMEnvBoardID
			INTEGER,
		lucentPM4FMEnvUnitType
			PMUnitType,
		lucentPM4FMEnvUnitIndex
			INTEGER,
		lucentPM4FMEnvOptUnitTemp
			INTEGER,
		lucentPM4FMEnvUnitTempRange
			INTEGER,
		lucentPM4FMEnvOptUnitPwrLvl
			INTEGER,
		lucentPM4FMEnvUnitPwrRange
			INTEGER,
		lucentPM4FMEnvTrapCtl
			INTEGER,
		lucentPM4FMEnvTrapRepTimer
			INTEGER
	}

lucentPM4FMEnvBoardID	OBJECT-TYPE
	SYNTAX	INTEGER
	ACCESS	read-only
	STATUS	mandatory
	DESCRIPTION
	"Board ID specifies the board identifier for this trap.
	If the trap configuration is for an auxillary device
	such as a power supply or fan, this object will be set
	to zero. The unit type and the unit index will uniquely
	identify the auxillary devices."
	::= { lucentPM4FMEnvTrapCfgEntry 1 }

lucentPM4FMEnvUnitType	OBJECT-TYPE
	SYNTAX	PMUnitType
	ACCESS	read-only
	STATUS	mandatory
	DESCRIPTION
	"Unit for which the Trap configuration must to apply."
	::= { lucentPM4FMEnvTrapCfgEntry 2 }

lucentPM4FMEnvUnitIndex	OBJECT-TYPE
	SYNTAX	INTEGER
	ACCESS	read-only
	STATUS	mandatory
	DESCRIPTION
	"Unit index specifies the interface or sub-unit for 
	this trap (modem or T1/E1 interface etc.). The unit
	type and the unit index will uniquely identify the
	auxillary devices."
	::= { lucentPM4FMEnvTrapCfgEntry 3 }

lucentPM4FMEnvOptUnitTemp	OBJECT-TYPE
	SYNTAX 	INTEGER
	ACCESS	read-write
	STATUS	mandatory
	DESCRIPTION
	"The optimum temperature for this unit. A trap is 
	generated when the temperature deviates from the 
	specified range. The temperature is specified as 
	an integer in degrees farenheit."
	::= { lucentPM4FMEnvTrapCfgEntry 4 }

lucentPM4FMEnvUnitTempRange	OBJECT-TYPE
	SYNTAX	INTEGER
	ACCESS	read-write
	STATUS	mandatory
	DESCRIPTION
	"The temperature range above which a trap is generated.
	The temperature must be specified as an integer in degree
	Farenhiet (for example +/- 5 degree Far.)."
	::= { lucentPM4FMEnvTrapCfgEntry 5 }

lucentPM4FMEnvOptUnitPwrLvl	OBJECT-TYPE
	SYNTAX	INTEGER
	ACCESS	read-write
	STATUS	mandatory
	DESCRIPTION
	"The optimal power level that is appropriate for this unit.
	A trap is generated when the power level fluctuates outside
	the limits set."
	::= { lucentPM4FMEnvTrapCfgEntry 6 }

lucentPM4FMEnvUnitPwrRange	OBJECT-TYPE
	SYNTAX	INTEGER
	ACCESS	read-write
	STATUS	mandatory
	DESCRIPTION
	"The power range specified in volts. A trap is generated 
	when the power level fluctuates outside the Opt Pwr +/- Range 
	set."
	::= { lucentPM4FMEnvTrapCfgEntry 7 }

lucentPM4FMEnvTrapCtl	OBJECT-TYPE
	SYNTAX	INTEGER {
		disable(1),
		enable(2)
	}
	ACCESS	read-write
	STATUS	mandatory
	DESCRIPTION
	"The trap control used to turn the environment traps on or off
	for the specified unit(s)."
	::= { lucentPM4FMEnvTrapCfgEntry 8 }

-- ++++++++++++++++++++++++++++++++++++++++++++++++++++++++++++++++++++++++++
-- Lucent Performance Management Group
-- ++++++++++++++++++++++++++++++++++++++++++++++++++++++++++++++++++++++++++
lucentPM4PerfMgmt	OBJECT IDENTIFIER	::= { lucentPM4Mib 6 }

-- ++++++++++++++++++++++++++++++++++++++++++++++++++++++++++++++++++++++++++
-- Lucent T1/E1 Performance Management Current Interval Table
-- ++++++++++++++++++++++++++++++++++++++++++++++++++++++++++++++++++++++++++
lucentPM4T1E1PerfMgmt	OBJECT IDENTIFIER ::= { lucentPM4PerfMgmt 1 }

lucentPM4T1E1PMCur	OBJECT-TYPE
	SYNTAX	SEQUENCE OF LucentPM4T1E1PMCurEntry
	ACCESS	not-accessible
	STATUS	mandatory
	DESCRIPTION
	"Performance management table representing the performance
	statistics of T1/E1 interfaces in the box. This table represents
	the current 15 mins statistics. This object is not accessible and 
	present for clarity purpose. This table is part of RFC 1406."
	::= { lucentPM4T1E1PerfMgmt 1 }

lucentPM4T1E1PMCurEntry	OBJECT-TYPE
	SYNTAX	LucentPM4T1E1PMCurEntry
	ACCESS	not-accessible
	STATUS	mandatory
	DESCRIPTION
	"Performance management table entries for all the T1/E1 interfaces 
	in the box. This table represents the current 15 mins statistics. 
	This object is not accessible and present for clarity purpose."
	INDEX	{ lucentPM4T1E1PMBoardID,
		  lucentPM4T1E1PMUnitType,
		  lucentPM4T1E1PMLineNum }
	::= { lucentPM4T1E1PMCur 1 }

LucentPM4T1E1PMCurEntry ::=
	SEQUENCE {
		lucentPM4T1E1PMCurBoardID
			INTEGER,
		lucentPM4T1E1PMCurUnitType
			PMUnitType,
		lucentPM4T1E1PMCurLineNum
			INTEGER,
		lucentPM4T1E1PMCurIfIndex
			INTEGER,
		lucentPM4T1E1PMCurESs
			Gauge,
		lucentPM4T1E1PMCurSESs
			Gauge,
		lucentPM4T1E1PMCurSEFs
			Gauge,
		lucentPM4T1E1PMCurUASs
			Gauge,
		lucentPM4T1E1PMCurCSSs
			Gauge,
		lucentPM4T1E1PMCurPCVs
			Gauge,
		lucentPM4T1E1PMCurLESs
			Gauge,
		lucentPM4T1E1PMCurBESs
			Gauge,
		lucentPM4T1E1PMCurDMs
			Gauge,
		lucentPM4T1E1PMCurLCVs
			Gauge
	}

lucentPM4T1E1PMCurBoard	OBJECT-TYPE
	SYNTAX	INTEGER
	ACCESS	read-only
	STATUS	mandatory
	DESCRIPTION
	"Board number of the interface. The global interface number is 
	computed by using the Most Significant byte of the ifIndex 
	and the Least Significant 2 bytes represents the interface index.
	Byte 3 will represent the unit type which would be a T1 or E1."
	::= { lucentPM4T1E1PMCurEntry 1 }

lucentPM4T1E1PMCurUnitType	OBJECT-TYPE
	SYNTAX	PMUnitType
	ACCESS	read-only
	STATUS	mandatory
	DESCRIPTION
	"Unit type indicates the type of interface as T1/E1 or T3/E3
	in future. This is part of the interface table ifIndex which
	is constructed with boardID, unit type and unit index."
	::= { lucentPM4T1E1PMCurEntry 2 }

lucentPM4T1E1PMCurLineNum	OBJECT-TYPE
	SYNTAX	INTEGER
	ACCESS	read-only
	STATUS	mandatory
	DESCRIPTION
	"Line number uniquely identifies the T1/E1 interface on a
	given board."
	::= { lucentPM4T1E1PMCurEntry 3 }

lucentPM4T1E1PMCurIfIndex	OBJECT-TYPE
	SYNTAX	INTEGER
	ACCESS	read-only
	STATUS	mandatory
	DESCRIPTION
	"Interface table ifIndex cross reference. The global interface 
	number is computed by using the Most Significant byte as the 
	board ID and the Least Significant 2 bytes represents the 
	interface index. The third byte represents the unit type which
	will be a T1 or E1. Thus board 0 interface 3 is represented as 
	0x00050003. The global interface number corresponds to the 
	IfIndex in MIB II."
	::= { lucentPM4T1E1PMCurEntry 4 }

lucentPM4T1E1PMCurESs	OBJECT-TYPE
	SYNTAX	Gauge
	ACCESS	read-only
	STATUS	mandatory
	DESCRIPTION
	"The number of errored seconds, encountered by the line
	in the current 15 mins interval."
	::= { lucentPM4T1E1PMCurEntry 5 }

lucentPM4T1E1PMCurSESs	OBJECT-TYPE
	SYNTAX	Gauge
	ACCESS	read-only
	STATUS	mandatory
	DESCRIPTION
	"The number of Severely Errored Seconds encountered by
	the line in the current 15 mins interval."
	::= { lucentPM4T1E1PMCurEntry 6 }

lucentPM4T1E1PMCurSEFSs	OBJECT-TYPE
	SYNTAX	Gauge
	ACCESS	read-only
	STATUS	mandatory
	DESCRIPTION
	"The number of Severely Errored Framing Seconds 
	encountered by the line in the current 15 mins interval."
	::= { lucentPM4T1E1PMCurEntry 7 }

lucentPM4T1E1PMCurUASs	OBJECT-TYPE
	SYNTAX	Gauge
	ACCESS	read-only
	STATUS	mandatory
	DESCRIPTION
	"The number of Unavailable Seconds encountered by the line 
	in the current 15 mins interval."
	::= { lucentPM4T1E1PMCurEntry 8 }

lucentPM4T1E1PMCurCSSs	OBJECT-TYPE
	SYNTAX	Gauge
	ACCESS	read-only
	STATUS	mandatory
	DESCRIPTION
	"The number of Controlled Slip Seconds encountered by the line 
	in the current 15 mins interval."
	::= { lucentPM4T1E1PMCurEntry 9 }

lucentPM4T1E1PMCurPCVs	OBJECT-TYPE
	SYNTAX	Gauge
	ACCESS	read-only
	STATUS	mandatory
	DESCRIPTION
	"The number of Path Coding Violations encountered by the line 
	in the current 15 mins interval."
	::= { lucentPM4T1E1PMCurEntry 10 }

lucentPM4T1E1PMCurLESs	OBJECT-TYPE
	SYNTAX	Gauge
	ACCESS	read-only
	STATUS	mandatory
	DESCRIPTION
	"The number of Line Errored Seconds encountered by the line 
	in the current 15 mins interval."
	::= { lucentPM4T1E1PMCurEntry 11 }

lucentPM4T1E1PMCurBESs	OBJECT-TYPE
	SYNTAX	Gauge
	ACCESS	read-only
	STATUS	mandatory
	DESCRIPTION
	"The number of Bursty Errored Seconds encountered by the line 
	in the current 15 mins interval."
	::= { lucentPM4T1E1PMCurEntry 12 }

lucentPM4T1E1PMCurDMs	OBJECT-TYPE
	SYNTAX	Gauge
	ACCESS	read-only
	STATUS	mandatory
	DESCRIPTION
	"The number of Degraded Minutes encountered by the line 
	in the current 15 mins interval."
	::= { lucentPM4T1E1PMCurEntry 13 }

lucentPM4T1E1PMCurLCVs	OBJECT-TYPE
	SYNTAX	Gauge
	ACCESS	read-only
	STATUS	mandatory
	DESCRIPTION
	"The number of Line Code Violations encountered by the line 
	in the current 15 mins interval."
	::= { lucentPM4T1E1PMCurEntry 14 }

-- ++++++++++++++++++++++++++++++++++++++++++++++++++++++++++++++++++++++++++
-- Lucent T1/E1 Performance Management Previous Intervals Table
-- ++++++++++++++++++++++++++++++++++++++++++++++++++++++++++++++++++++++++++
lucentPM4T1E1PMInt	OBJECT-TYPE
	SYNTAX	SEQUENCE OF LucentPM4T1E1PMIntEntry
	ACCESS	not-accessible
	STATUS	mandatory
	DESCRIPTION
	"Performance management table representing the performance
	statistics of T1/E1 interfaces in the box. This table represents
	the 24 hr statistics divided into 96 15 mins intervals. This 
	object is not accessible and present for clarity purpose. 
	This table is part of RFC 1406."
	::= { lucentPM4PerfMgmt 2 }

lucentPM4T1E1PMIntEntry	OBJECT-TYPE
	SYNTAX	LucentPM4T1E1PMIntEntry
	ACCESS	not-accessible
	STATUS	mandatory
	DESCRIPTION
	"Performance management table entries for all the T1/E1 interfaces 
	in the box. This table represents the 24 hr statistics divided into
	96 15 mins intervals. This object is not accessible and present for 
	clarity purpose."
	INDEX	{ lucentPM4T1E1PMIntBoard,
		  lucentPM4T1E1PMIntUnitType,
		  lucentPM4T1E1PMIntLineNum,
		  lucentPM4T1E1PMIntInterval }
	::= { lucentPM4T1E1PMInt 1 }

LucentPM4T1E1PMIntEntry ::=
	SEQUENCE {
		lucentPM4T1E1PMIntBoard
			INTEGER,
		lucentPM4T1E1PMIntUnitType
			PMUnitType,
		lucentPM4T1E1PMIntLineNum
			INTEGER,
		lucentPM4T1E1PMIntIfIndex
			INTEGER,
		lucentPM4T1E1PMIntInterval
			INTEGER,
		lucentPM4T1E1PMIntESs
			Gauge,
		lucentPM4T1E1PMIntSESs
			Gauge,
		lucentPM4T1E1PMIntSEFs
			Gauge,
		lucentPM4T1E1PMIntUASs
			Gauge,
		lucentPM4T1E1PMIntCSSs
			Gauge,
		lucentPM4T1E1PMIntPCVs
			Gauge,
		lucentPM4T1E1PMIntLESs
			Gauge,
		lucentPM4T1E1PMIntBESs
			Gauge,
		lucentPM4T1E1PMIntDMs
			Gauge,
		lucentPM4T1E1PMIntLCVs
			Gauge
	}

lucentPM4T1E1PMIntBoard	OBJECT-TYPE
	SYNTAX	INTEGER
	ACCESS	read-only
	STATUS	mandatory
	DESCRIPTION
	"Board number of the interface. The global interface number is 
	computed by using the Most Significant nibble of the ifIndex 
	and the Least Significant nibble represents the interface index.
	Thus board 0 interface 3 is represented as 0x03 or 03 decimal 
	and board 10 interface 3 is represented as 0xa3 or 163 decimal.
	In an integer, of 4 bytes wide, the 3 MSBytes will all be zeros.
	The global interface number corresponds to the IfIndex of MIB II."
	::= { lucentPM4T1E1PMIntEntry 1 }

lucentPM4T1E1PMIntUnitType	OBJECT-TYPE
	SYNTAX	PMUnitType
	ACCESS	read-only
	STATUS	mandatory
	DESCRIPTION
	"Unit type indicates the type of physical or logical device. The
	unit type for this table is either T1 or E1."
	::= { lucentPM4T1E1PMIntEntry 2 }

lucentPM4T1E1PMIntLineNum	OBJECT-TYPE
	SYNTAX	INTEGER
	ACCESS	read-only
	STATUS	mandatory
	DESCRIPTION
	"Line number uniquely identifies the T1/E1 interface for this
	board."
	::= { lucentPM4T1E1PMIntEntry 3 }

lucentPM4T1E1PMIntInterval	OBJECT-TYPE
	SYNTAX	INTEGER (1..96)
	ACCESS	read-only
	STATUS	mandatory
	DESCRIPTION
	"Interval number for a given board. The 24 hr period is
	divided into 96 15 min intervals, where 1 is the most recent 
	and 96 is the least recent."
	::= { lucentPM4T1E1PMIntEntry 4 }

lucentPM4T1E1PMIntIfIndex	OBJECT-TYPE
	SYNTAX	INTEGER
	ACCESS	read-only
	STATUS	mandatory
	DESCRIPTION
	"Interface table ifIndex cross reference. The global interface 
	number is computed by using the Most Significant byte as the 
	board ID and the Least Significant 2 bytes represents the 
	interface index. The third byte represents the unit type which
	will be a T1 or E1. Thus board 0 interface 3 is represented as 
	0x00050003. The global interface number corresponds to the 
	IfIndex in MIB II."
	::= { lucentPM4T1E1PMIntEntry 5 }

lucentPM4T1E1PMIntESs	OBJECT-TYPE
	SYNTAX	Gauge
	ACCESS	read-only
	STATUS	mandatory
	DESCRIPTION
	"The number of errored seconds, encountered by the line
	in the last 24 hrs divided into 96 15 mins intervals."
	::= { lucentPM4T1E1PMIntEntry 6 }

lucentPM4T1E1PMIntSESs	OBJECT-TYPE
	SYNTAX	Gauge
	ACCESS	read-only
	STATUS	mandatory
	DESCRIPTION
	"The number of Severely Errored Seconds encountered by
	the line for one of the 96 15 mins intervals."
	::= { lucentPM4T1E1PMIntEntry 7 }

lucentPM4T1E1PMIntSEFSs	OBJECT-TYPE
	SYNTAX	Gauge
	ACCESS	read-only
	STATUS	mandatory
	DESCRIPTION
	"The number of Severely Errored Framing Seconds 
	encountered by the line for one of the 96 15 mins 
	intervals."
	::= { lucentPM4T1E1PMIntEntry 8 }

lucentPM4T1E1PMIntUASs	OBJECT-TYPE
	SYNTAX	Gauge
	ACCESS	read-only
	STATUS	mandatory
	DESCRIPTION
	"The number of Unavailable Seconds encountered by the line 
	for one of the 96 15 mins intervals."
	::= { lucentPM4T1E1PMIntEntry 9 }

lucentPM4T1E1PMIntCSSs	OBJECT-TYPE
	SYNTAX	Gauge
	ACCESS	read-only
	STATUS	mandatory
	DESCRIPTION
	"The number of Controlled Slip Seconds encountered by the line 
	for one of the 96 15 mins intervals."
	::= { lucentPM4T1E1PMIntEntry 10 }

lucentPM4T1E1PMIntPCVs	OBJECT-TYPE
	SYNTAX	Gauge
	ACCESS	read-only
	STATUS	mandatory
	DESCRIPTION
	"The number of Path Coding Violations encountered by the line 
	for one of the 96 15 mins intervals."
	::= { lucentPM4T1E1PMIntEntry 11 }

lucentPM4T1E1PMIntLESs	OBJECT-TYPE
	SYNTAX	Gauge
	ACCESS	read-only
	STATUS	mandatory
	DESCRIPTION
	"The number of Line Errored Seconds encountered by the line 
	for one of the 96 15 mins intervals."
	::= { lucentPM4T1E1PMIntEntry 12 }

lucentPM4T1E1PMIntBESs	OBJECT-TYPE
	SYNTAX	Gauge
	ACCESS	read-only
	STATUS	mandatory
	DESCRIPTION
	"The number of Bursty Errored Seconds encountered by the line 
	for one of the 96 15 mins intervals."
	::= { lucentPM4T1E1PMIntEntry 13 }

lucentPM4T1E1PMIntDMs	OBJECT-TYPE
	SYNTAX	Gauge
	ACCESS	read-only
	STATUS	mandatory
	DESCRIPTION
	"The number of Degraded Minutes encountered by the line 
	for one of the 96 15 mins intervals."
	::= { lucentPM4T1E1PMIntEntry 14 }

lucentPM4T1E1PMIntLCVs	OBJECT-TYPE
	SYNTAX	Gauge
	ACCESS	read-only
	STATUS	mandatory
	DESCRIPTION
	"The number of Line Code Violations encountered by the line 
	for one of the 96 15 mins intervals."
	::= { lucentPM4T1E1PMIntEntry 15 }

-- ++++++++++++++++++++++++++++++++++++++++++++++++++++++++++++++++++++++++++
-- Lucent T1/E1 Performance Management Total Cumulative Values Table
-- ++++++++++++++++++++++++++++++++++++++++++++++++++++++++++++++++++++++++++
lucentPM4T1E1PMTotal	OBJECT-TYPE
	SYNTAX	SEQUENCE OF LucentPM4T1E1PMTotalEntry
	ACCESS	not-accessible
	STATUS	mandatory
	DESCRIPTION
	"Performance management table representing the performance
	statistics of T1/E1 interfaces in the box. This table represents
	the 24 hr statistics divided into 96 15 mins intervals. This 
	object is not accessible and present for clarity purpose. 
	This table is part of RFC 1406."
	::= { lucentPM4PerfMgmt 3 }

lucentPM4T1E1PMTotalEntry	OBJECT-TYPE
	SYNTAX	LucentPM4T1E1PMIntEntry
	ACCESS	not-accessible
	STATUS	mandatory
	DESCRIPTION
	"Performance management table entries for all the T1/E1 interfaces 
	in the box. This table represents the 24 hr statistics divided into
	96 15 mins intervals. This object is not accessible and present for 
	clarity purpose."
	INDEX	{ lucentPM4T1E1PMTotalBoard,
		  lucentPM4T1E1PMTotalUnitType,
		  lucentPM4T1E1PMTotalLineNum,
		  lucentPM4T1E1PMTotalInterval }
	::= { lucentPM4T1E1PMTotal 1 }

LucentPM4T1E1PMTotalEntry ::=
	SEQUENCE {
		lucentPM4T1E1PMTotalBoard
			INTEGER,
		lucentPM4T1E1PMTotalUnitType
			PMUnitType,
		lucentPM4T1E1PMTotalLineNum
			INTEGER,
		lucentPM4T1E1PMTotalIfIndex
			INTEGER,
		lucentPM4T1E1PMTotalESs
			Gauge,
		lucentPM4T1E1PMTotalSESs
			Gauge,
		lucentPM4T1E1PMTotalSEFs
			Gauge,
		lucentPM4T1E1PMTotalUASs
			Gauge,
		lucentPM4T1E1PMTotalCSSs
			Gauge,
		lucentPM4T1E1PMTotalPCVs
			Gauge,
		lucentPM4T1E1PMTotalLESs
			Gauge,
		lucentPM4T1E1PMTotalBESs
			Gauge,
		lucentPM4T1E1PMTotalDMs
			Gauge,
		lucentPM4T1E1PMTotalLCVs
			Gauge
	}

lucentPM4T1E1PMTotalBoard	OBJECT-TYPE
	SYNTAX	INTEGER
	ACCESS	read-only
	STATUS	mandatory
	DESCRIPTION
	"Board number of the interface. The global interface number is 
	computed by using the Most Significant nibble of the ifIndex 
	and the Least Significant nibble represents the interface index.
	Thus board 0 interface 3 is represented as 0x03 or 03 decimal 
	and board 10 interface 3 is represented as 0xa3 or 163 decimal.
	In an integer, of 4 bytes wide, the 3 MSBytes will all be zeros.
	The global interface number corresponds to the IfIndex of MIB II.
	This table stores the cumulative values for the past 24 hr period."
	::= { lucentPM4T1E1PMTotalEntry 1 }

lucentPM4T1E1PMTotalUnitType	OBJECT-TYPE
	SYNTAX	PMUnitType
	ACCESS	read-only
	STATUS	mandatory
	DESCRIPTION
	"Unit type indicates the type of physical or logical device. The
	unit type for this table is either T1 or E1."
	::= { lucentPM4T1E1PMTotalEntry 2 }

lucentPM4T1E1PMTotalLineNum	OBJECT-TYPE
	SYNTAX	INTEGER
	ACCESS	read-only
	STATUS	mandatory
	DESCRIPTION
	"Interface number for a given board. The global interface number is
	computed by using the Most Significant nibble of the ifIndex and 
	the Least Significant nibble represents the interface index. Thus 
	board 0 interface 3 is represented as 0x03 or 03 decimal and board 10
	interface 3 is represented as 0xa3 or 163 decimal. In an integer,
	of 4 bytes wide, the 3 MSBytes will all be zeros. The global interface
	number corresponds to the IfIndex in MIB II."
	::= { lucentPM4T1E1PMTotalEntry 3 }

lucentPM4T1E1PMTotalIfIndex	OBJECT-TYPE
	SYNTAX	INTEGER
	ACCESS	read-only
	STATUS	mandatory
	DESCRIPTION
	"IfIndex cross reference value. This value is obtained from the
	Board/board number and interface number by combining them into
	the LSByte. The upper nibble represents the board and the lower
	nibble represents the line number."
	::= { lucentPM4T1E1PMTotalEntry 4 }

lucentPM4T1E1PMTotalESs	OBJECT-TYPE
	SYNTAX	Gauge
	ACCESS	read-only
	STATUS	mandatory
	DESCRIPTION
	"The cumulative value of errored seconds, encountered by the line
	in the last 24 hrs."
	::= { lucentPM4T1E1PMTotalEntry 5 }

lucentPM4T1E1PMTotalSESs	OBJECT-TYPE
	SYNTAX	Gauge
	ACCESS	read-only
	STATUS	mandatory
	DESCRIPTION
	"The cumulative value Severely Errored Seconds encountered by
	the line for the 24 hr period."
	::= { lucentPM4T1E1PMTotalEntry 6 }

lucentPM4T1E1PMTotalSEFSs	OBJECT-TYPE
	SYNTAX	Gauge
	ACCESS	read-only
	STATUS	mandatory
	DESCRIPTION
	"The cumulative value of Severely Errored Framing Seconds 
	encountered by the line for the 24 hr period."
	::= { lucentPM4T1E1PMTotalEntry 7 }

lucentPM4T1E1PMTotalUASs	OBJECT-TYPE
	SYNTAX	Gauge
	ACCESS	read-only
	STATUS	mandatory
	DESCRIPTION
	"The cumulative value of Unavailable Seconds encountered by the line 
	for the 24 hr period."
	::= { lucentPM4T1E1PMTotalEntry 8 }

lucentPM4T1E1PMTotalCSSs	OBJECT-TYPE
	SYNTAX	Gauge
	ACCESS	read-only
	STATUS	mandatory
	DESCRIPTION
	"The cumulative value of Controlled Slip Seconds encountered by the line 
	for the 24 hr period."
	::= { lucentPM4T1E1PMTotalEntry 9 }

lucentPM4T1E1PMTotalPCVs	OBJECT-TYPE
	SYNTAX	Gauge
	ACCESS	read-only
	STATUS	mandatory
	DESCRIPTION
	"The cumulative value of Path Coding Violations encountered by the line 
	for the 24 hr period."
	::= { lucentPM4T1E1PMTotalEntry 10 }

lucentPM4T1E1PMTotalLESs	OBJECT-TYPE
	SYNTAX	Gauge
	ACCESS	read-only
	STATUS	mandatory
	DESCRIPTION
	"The cumulative value of Line Errored Seconds encountered by the line 
	for the 24 hr period."
	::= { lucentPM4T1E1PMTotalEntry 11 }

lucentPM4T1E1PMTotalBESs	OBJECT-TYPE
	SYNTAX	Gauge
	ACCESS	read-only
	STATUS	mandatory
	DESCRIPTION
	"The cumulative value of Bursty Errored Seconds encountered by the line 
	for the 24 hr period."
	::= { lucentPM4T1E1PMTotalEntry 12 }

lucentPM4T1E1PMTotalDMs	OBJECT-TYPE
	SYNTAX	Gauge
	ACCESS	read-only
	STATUS	mandatory
	DESCRIPTION
	"The cumulative value of Degraded Minutes encountered by the line 
	for the 24 hr period."
	::= { lucentPM4T1E1PMTotalEntry 13 }

lucentPM4T1E1PMTotalLCVs	OBJECT-TYPE
	SYNTAX	Gauge
	ACCESS	read-only
	STATUS	mandatory
	DESCRIPTION
	"The cumulative value of Line Code Violations encountered by 
	the line for the 24 hr period."
	::= { lucentPM4T1E1PMTotalEntry 14 }

-- ++++++++++++++++++++++++++++++++++++++++++++++++++++++++++++++++++++++++++
-- Lucent Security Management Group
-- ++++++++++++++++++++++++++++++++++++++++++++++++++++++++++++++++++++++++++
lucentPM4SecurityMgmt	OBJECT IDENTIFIER	::= { lucentPM4Mib 7 }

-- ++++++++++++++++++++++++++++++++++++++++++++++++++++++++++++++++++++++++++
-- Lucent Administration Management Group
-- ++++++++++++++++++++++++++++++++++++++++++++++++++++++++++++++++++++++++++
lucentPM4AcctMgmt	OBJECT IDENTIFIER	::= { lucentPM4Mib 8 }

-- ++++++++++++++++++++++++++++++++++++++++++++++++++++++++++++++++++++++++++
-- Lucent Administration Management Group
-- ++++++++++++++++++++++++++++++++++++++++++++++++++++++++++++++++++++++++++
lucentPM4AcctMgmtComm	OBJECT IDENTIFIER	::= { lucentPM4AcctMgmt 1 }

-- ++++++++++++++++++++++++++++++++++++++++++++++++++++++++++++++++++++++++++
-- Lucent SNMP Read/Write Community Table
-- ++++++++++++++++++++++++++++++++++++++++++++++++++++++++++++++++++++++++++
lucentPM4SnmpCommTable	OBJECT-TYPE
	SYNTAX	SEQUENCE OF LucentPM4SnmpCommEntry
	ACCESS	not-accessible
	STATUS	mandatory
	DESCRIPTION
	"The SNMP Community Table. This table contains entries to restrict
	the SNMP get and set operations."
	::= { lucentPM4AcctMgmtComm 1 }

lucentPM4SnmpCommEntry	OBJECT-TYPE
	SYNTAX	LucentPM4SnmpCommEntry
	ACCESS	not-accessible
	STATUS	mandatory
	DESCRIPTION
	"The entries in the community table."
	INDEX	{ lucentPM4SnmpCommName }
	::= { lucentPM4SnmpCommTable 1 }

LucentPM4SnmpCommEntry ::=
	SEQUENCE {
		lucentPM4SnmpCommIndex
			INTEGER,
		lucentPM4SnmpCommName
			DisplayString,
		lucentPM4SnmpCommIpAddr
			IpAddress,
		lucentPM4SnmpCommReadAccess
			INTEGER,
		lucentPM4SnmpCommWriteAccess
			INTEGER,
		lucentPM4SnmpCommTraps
			INTEGER,
		lucentPM4SnmpCommStatus
			INTEGER,
		lucentPM4SnmpCommLastError
			DisplayString
	}

lucentPM4SnmpCommIndex	OBJECT-TYPE
	SYNTAX	INTEGER (1..10)
	ACCESS	read-only
	STATUS	mandatory
	DESCRIPTION
	"The index of the command in the command table. A MAX of
	10 network management stations must be specified along with
	their community names."
	::= { lucentPM4SnmpCommEntry 1 }

lucentPM4SnmpCommName	OBJECT-TYPE
	SYNTAX	DisplayString (SIZE (1..32))
	ACCESS	not-accessible
	STATUS	mandatory
	DESCRIPTION
	"The name of the SNMP Community for SNMP readers and writers. The size
	of the string is limited to 32 characters. All characters in the string
	must be printable."
	::= { lucentPM4SnmpCommEntry 2 }

lucentPM4SnmpCommIpAddr	OBJECT-TYPE
	SYNTAX	IpAddress
	ACCESS	read-write
	STATUS	mandatory
	DESCRIPTION
	"The IP Address of the remote community."
	::= { lucentPM4SnmpCommEntry 3 }

lucentPM4SnmpCommReadAccess	OBJECT-TYPE
	SYNTAX	INTEGER {
		disable(1),
		ensable(2)
	}
	ACCESS	read-write
	STATUS	mandatory
	DESCRIPTION
	"Read access enable or disable for this community. When
	enabled, it allows read-only variable access using this
	community string by the SNMP client."
	::= { lucentPM4SnmpCommEntry 4 }

lucentPM4SnmpCommWriteAccess	OBJECT-TYPE
	SYNTAX	INTEGER {
		disable(1),
		ensable(2)
	}
	ACCESS	read-write
	STATUS	mandatory
	DESCRIPTION
	"Write access enable or disable for this community. When
	enabled, the agent allows write access to the parameters
	on the agent by the SNMP clients."
	::= { lucentPM4SnmpCommEntry 5 }

lucentPM4SnmpCommTraps	OBJECT-TYPE
	SYNTAX	INTEGER {
		disable(1),
		ensable(2)
	}
	ACCESS	read-write
	STATUS	mandatory
	DESCRIPTION
	"Traps receiving capability enable or disable for 
	this community. When enabled, the SNMP agent forwards
	the traps generated in the box to this SNMP client."
	::= { lucentPM4SnmpCommEntry 6 }

lucentPM4SnmpCommStatus	OBJECT-TYPE
	SYNTAX	INTEGER {
		normal(1),
		delete(2)
	}
	ACCESS	read-write
	STATUS	mandatory
	DESCRIPTION
	"The status of the entry for this community. If the
	status is set to normal, it allows requests from this
	SNMP client else it discards the requests from this
	client."
	::= { lucentPM4SnmpCommEntry 7 }

lucentPM4SnmpCommLastError	OBJECT-TYPE
	SYNTAX	DisplayString (SIZE (0..511))
	ACCESS	read-only
	STATUS	mandatory
	DESCRIPTION
	"If there is an error on a request, this variable may
	contain a message indicating the error."
	::= { lucentPM4SnmpCommEntry 8 }

-- ++++++++++++++++++++++++++++++++++++++++++++++++++++++++++++++++++++++++++
-- Lucent Administration Management Group
-- ++++++++++++++++++++++++++++++++++++++++++++++++++++++++++++++++++++++++++
lucentPM4AcctMgmtCallEvent	OBJECT IDENTIFIER	::= { lucentPM4AcctMgmt 2 }

-- ++++++++++++++++++++++++++++++++++++++++++++++++++++++++++++++++++++++++++
-- Lucent Billing/Accounting Information Table
-- ++++++++++++++++++++++++++++++++++++++++++++++++++++++++++++++++++++++++++
lucentPM4AMCallEventTable	OBJECT-TYPE
	SYNTAX	SEQUENCE OF LucentPM4AMCallEventEntry
	ACCESS	not-accessible
	STATUS	mandatory
	DESCRIPTION
	"Call accounting table containing a list of call events,
	which may be used for billing purposes."
	::= { lucentPM4AcctMgmtCallEvent 1 }

lucentPM4AMCallEventEntry	OBJECT-TYPE
	SYNTAX	LucentPM4AMCallEventEntry
	ACCESS	not-accessible
	STATUS	mandatory
	DESCRIPTION
	"The entries in the accounting/billing table."
	INDEX	{ lucentPM4AMCEIndex }
	::= { lucentPM4AMCallEventTable 1 }

LucentPM4AMCallEventEntry ::=
	SEQUENCE {
		lucentPM4AMCEIndex
			INTEGER,
		lucentPM4AMCETimeStamp
			INTEGER,
		lucentPM4AMCEType
			INTEGER,
		lucentPM4AMCESvcType
			INTEGER,
		lucentPM4AMCEUName
			DisplayString,
		lucentPM4AMCEModemBoard
			INTEGER,
		lucentPM4AMCEModemID
			INTEGER,
		lucentPM4AMCEModemPort
			DisplayString,
		lucentPM4AMCEDataRate
			INTEGER,
		lucentPM4AMCECallingPartyID
			DisplayString,
		lucentPM4AMCECalledPartyID
			DisplayString,
		lucentPM4AMCEInOctets
			INTEGER,
		lucentPM4AMCEOutOctets
			INTEGER,
		lucentPM4AMCECallCharge
			INTEGER,
		lucentPM4AMCEDisconnReason
			INTEGER
	}

lucentPM4AMCEIndex	OBJECT-TYPE
	SYNTAX	INTEGER
	ACCESS	read-only
	STATUS	mandatory
	DESCRIPTION
	"Call event index used as an index into the call event table.
	The table stores call events which may be used for billing."
	::= { lucentPM4AMCallEventEntry 1 }

lucentPM4AMCETimeStamp	OBJECT-TYPE
	SYNTAX	INTEGER
	ACCESS	read-only
	STATUS	mandatory
	DESCRIPTION
	"Time stamp for this event in seconds since the last reboot."
	::= { lucentPM4AMCallEventEntry 2 }

lucentPM4AMCEType	OBJECT-TYPE
	SYNTAX	INTEGER {
		calloriginated(1),
		callanswered(2),
		callcleared(3),
		servicechanged(4),
		namechanged(5),
		baudratechanged(6)
	}
	ACCESS	read-only
	STATUS	mandatory
	DESCRIPTION
	"Specifies the type of event associated with this entry in the
	call event table."
	::= { lucentPM4AMCallEventEntry 3 }

lucentPM4AMCESvcType	OBJECT-TYPE
	SYNTAX	INTEGER {
		none(1),
		ppp(2),
		slip(3),
		mpp(4),
		x25(5),
		combinet(6),
		frameRelay(7),
		euraw(8),
		euui(9),
		telnet(10),	
		telnetBinary(11),
		rawTcp(12),
		terminalServer(13),
		mp(14),
		virtualConnect(15),
		x25DChannel(16)
	}
	ACCESS	read-only
	STATUS	mandatory
	DESCRIPTION
	"The type of service provided to the user. This field is
	meaningful if the event type is servicechanged(4), or
	namechanged(5) events. In all other cases, this object
	must return none(1)."
	::= { lucentPM4AMCallEventEntry 4 }

lucentPM4AMCEUName	OBJECT-TYPE
	SYNTAX	DisplayString
	ACCESS	read-only
	STATUS	mandatory
	DESCRIPTION
	"User name of the dialed in user. This object returns the
	valid user name when the event type is servicechanged(4)
	or namechanged(5). In all other cases, it returns a NULL."
	::= { lucentPM4AMCallEventEntry 5 }

lucentPM4AMCEModemBoard	OBJECT-TYPE
	SYNTAX	INTEGER
	ACCESS	read-only
	STATUS	mandatory
	DESCRIPTION
	"Board ID of the modem which handled this call. This value
	can be used to diagnose modem related problems (dropping the
	call, retraining too frequently etc.)."
	::= { lucentPM4AMCallEventEntry 6 }

lucentPM4AMCEModemID	OBJECT-TYPE
	SYNTAX	INTEGER
	ACCESS	read-only
	STATUS	mandatory
	DESCRIPTION
	"Identifies the specific modem on a board which handled this
	call. Can be used to diagnose modem related problems."
	::= { lucentPM4AMCallEventEntry 7 }

lucentPM4AMCEModemPort	OBJECT-TYPE
	SYNTAX	DisplayString
	ACCESS	read-only
	STATUS	mandatory
	DESCRIPTION
	"A textual string containing the name of the serial
	interface (ie. S0, S1, etc)."
	::= { lucentPM4AMCallEventEntry 8 }

lucentPM4AMCEDataRate	OBJECT-TYPE
	SYNTAX	INTEGER
	ACCESS	read-only
	STATUS	mandatory
	DESCRIPTION
	"Specifies the speed of this connection. Speed is specified
	as baud rate for modem calls and receive data rate for ISDN
	calls. This object returns a 0 for call answered and call
	cleared events."
	::= { lucentPM4AMCallEventEntry 9 }

lucentPM4AMCECallingPartyID	OBJECT-TYPE
	SYNTAX	DisplayString
	ACCESS	read-only
	STATUS	mandatory
	DESCRIPTION
	"Calling party ID. This object is valid only for call answered,
	call originated, and call cleared events. For all invalid event
	types, this object is set to NULL."
	::= { lucentPM4AMCallEventEntry 10 }

lucentPM4AMCECalledPartyID	OBJECT-TYPE
	SYNTAX	DisplayString
	ACCESS	read-only
	STATUS	mandatory
	DESCRIPTION
	"Called party ID. This object is valid only for call answered,
	call originated, and call cleared events. For all invalid event
	types, this object is set to NULL."
	::= { lucentPM4AMCallEventEntry 11 }

lucentPM4AMCEInOctets	OBJECT-TYPE
	SYNTAX	INTEGER
	ACCESS	read-only
	STATUS	mandatory
	DESCRIPTION
	"Total octets received during this call. This object is cleared
	at the end of each call."
	::= { lucentPM4AMCallEventEntry 12 }

lucentPM4AMCEOutOctets	OBJECT-TYPE
	SYNTAX	INTEGER
	ACCESS	read-only
	STATUS	mandatory
	DESCRIPTION
	"Total octets sent out during this call. This object is cleared
	at the end of each call."
	::= { lucentPM4AMCallEventEntry 13 }

lucentPM4AMCECallCharge	OBJECT-TYPE
	SYNTAX	INTEGER
	ACCESS	read-only
	STATUS	mandatory
	DESCRIPTION
	"Call charge for this call. This object is valid only when the
	event is call cleared. For all other events this object is set
	to zero."
	::= { lucentPM4AMCallEventEntry 14 }

lucentPM4AMCEDisconnReason	OBJECT-TYPE
	SYNTAX	INTEGER {
		notApplicable(1),
		unknown(2),
		disconnected(3),
		clidAuthFailed(4),		-- Radius authorization failed
		clidAuthServTimeout(5), 	-- Radius client timeout
		clidAuthRequestCallback(6),
		preT310Timeout(7),		-- disconnect timer timeout
		noModemAvailable(9),		-- all modems assigned to calls
		noModemNoCarrier(10),		-- no carrier detected
		noModemLossCarrier(11),		-- lost carrier during call
		noModemResultCodes(12),
		noModemOpenFailed(13),
		noModemOpenFailedDiag(14),
		tsUserExit(20),			-- user exited the terminal server
		tsIdleTimeout(21),		-- timed out waiting for user input
		tsExitTelnet(22),			-- user exited telnet session
		tsNoIPAddr(23),			-- no IP address, cannot assign one
		tsExitTcp(24),
		tsPassWordFail(25),		-- exit due to failed password
		tsRawTCPDisable(26),
		tsControlC(27),			-- Control C detected
		tsDestroyed(28),
		tsClosedVirtualConnect(29),	-- virtual terminal connection closed
		tsVirtualConnectDestroyed(30),
		tsExitRlogin(31),
		tsRloginBadOption(32),		-- bad rlogin command option
		tsErrorResource(33),
		mpNullMessageTimeout(35),
		pppLcpTimeout(40),		-- Link Control Protocol timeout
		pppLcpNegotiateFail(41),	-- LCP negotiation failed
		pppPAPAuthFail(42),		-- PAP authentication failed
		pppCHAPAuthFail(43),		-- CHAP authentication failed
		pppRemoteAuthFail(44),
		pppRcvTerminate(45),		-- received terminate request from far end
		pppCloseEvent(46),		-- PPP close event
		pppCloseNoNcpsOpened(47),
		pppCloseUnknownMpBundle(48),
		pppCloseMpAddChanFail(49),
		tsExitErrTooMany(50),
		tsExitErrResource(51),
		tsExitErrInvalidIP(52),
		tsExitErrHostName(53),
		tsExitErrBadPort(54),
		tsExitErrHostReset(60),
		tsExitErrConnRefused(61),
		tsExitErrTimedOut(62),
		tsExitErrClosed(63),
		tsExitErrNetUnreach(64),
		tsExitErrHostUnreach(65),
		tsExitErrNetAdminUnreach(66),
		tsExitErrHostAdminUnreach(67),
		tsExitErrPortUnreach(68),
		sessTimeOut(100),
		sessFailSecurity(101),
		sessCallback(102),
		invalidProtocol(120),
		requestByRadiusClient(150),
		localAdmin(151),
		localSnmp(152),				-- disconnected by SNMP request
		v110Timeout(160),
		pppAuthTimeout(170),
		userCallClearRequest(180),
		remoteEndHungUp(185),
		resourceQuiesced(190),
		maxCallDurationReached(195),
		lowMemory(201),
		boardDied(210)
	}
	ACCESS	read-only
	STATUS	mandatory
	DESCRIPTION
	"Reason for the disconnect."
	::= { lucentPM4AMCallEventEntry 15 }

-- ++++++++++++++++++++++++++++++++++++++++++++++++++++++++++++++++++++++++++
-- Lucent PortMaster 4 Traps
-- ++++++++++++++++++++++++++++++++++++++++++++++++++++++++++++++++++++++++++

lucentPM4BoardOfflineTrap	TRAP-TYPE
	ENTERPRISE	lucentPM4Traps
	VARIABLES	{ sysName,
			  lucentPM4FMBoardIndex,
			  lucentPM4FMUnitType,
			  lucentPM4FMUnitTrapStatus }
	DESCRIPTION
	"Board down trap. The variable bindings in the Trap packet provide 
	information about the chassis name, board number and the trap 
	status. This Trap must be cleared manually."
	::= 1

lucentPM4BoardOnlineTrap	TRAP-TYPE
	ENTERPRISE	lucentPM4Traps
	VARIABLES	{ sysName,
			  lucentPM4FMBoardIndex,
			  lucentPM4FMUnitType,
			  lucentPM4FMUnitTrapStatus }
	DESCRIPTION
	"Board up trap. The variable bindings in the Trap packet provide 
	information about the chassis name, board number and the trap 
	status. This Trap must be cleared manually."
	::= 2

lucentPM4PwrSupFailTrap	TRAP-TYPE
	ENTERPRISE	lucentPM4Traps
	VARIABLES	{ sysName,
			  lucentPM4FMUnitType,
			  lucentPM4FMUnitIndex,
			  lucentPM4FMUnitTrapStatus }
	DESCRIPTION
	"Power supply failed trap. The variable bindings in the Trap packet provide 
	information about the chassis name, power supply unit and the trap 
	status. This Trap must be cleared manually."
	::= 3

lucentPM4PwrSupWarnTrap	TRAP-TYPE
	ENTERPRISE	lucentPM4Traps
	VARIABLES	{ sysName,
			  lucentPM4FMUnitType,
			  lucentPM4FMUnitIndex,
			  lucentPM4FMUnitTrapStatus }
	DESCRIPTION
	"Power supply warning trap. The variable bindings in the Trap packet provide 
	information about the chassis name, power supply unit and the trap 
	status. This Trap is issued when the power supply fluctuates between a set
      threshold. This Trap must be cleared manually."
	::= 4

lucentPM4PwrSupRestoredTrap	TRAP-TYPE
	ENTERPRISE	lucentPM4Traps
	VARIABLES	{ sysName,
			  lucentPM4FMUnitType,
			  lucentPM4FMUnitIndex,
			  lucentPM4FMUnitTrapStatus }
	DESCRIPTION
	"Power supply restored trap. The variable bindings in the Trap packet provide 
	information about the chassis name, power supply unit and the trap 
	status. This Trap is issued when a failed power supply is restored.
	This must be cleared manually."
	::= 5

lucentPM4FanFailTrap	TRAP-TYPE
	ENTERPRISE	lucentPM4Traps
	VARIABLES	{ sysName,
			  lucentPM4FMUnitType,
			  lucentPM4FMUnitIndex,
			  lucentPM4FMUnitTrapStatus }
	DESCRIPTION
	"Fan failure trap. The variable bindings in the Trap packet provide 
	information about the chassis name, fan number and the trap 
	status. This Trap must be cleared manually."
	::= 6

lucentPM4FanRestoredTrap	TRAP-TYPE
	ENTERPRISE	lucentPM4Traps
	VARIABLES	{ sysName,
			  lucentPM4FMUnitType,
			  lucentPM4FMUnitIndex,
			  lucentPM4FMUnitTrapStatus }
	DESCRIPTION
	"Fan restored trap. The variable bindings in the Trap packet provide 
	information about the chassis name, fan number and the trap 
	status. This Trap is issued when the failed fan is restored.
	This trap must be cleared manually."
	::= 7

lucentPM4BoardTempWarnTrap	TRAP-TYPE
	ENTERPRISE	lucentPM4Traps
	VARIABLES	{ sysName,
			  lucentPM4FMBoardIndex,
			  lucentPM4FMUnitType,
			  lucentPM4FMUnitTrapStatus }
	DESCRIPTION
	"Board temperature warning trap. The variable bindings in the Trap 
	packet provide information about the chassis name, unit and the trap 
	status. This Trap is issued when the board temperature exceeds a set
	threshold value. This trap must be cleared manually."
	::= 8

lucentPM4BoardTempNormalTrap	TRAP-TYPE
	ENTERPRISE	lucentPM4Traps
	VARIABLES	{ sysName,
			  lucentPM4FMBoardIndex,
			  lucentPM4FMUnitType,
			  lucentPM4FMUnitTrapStatus }
	DESCRIPTION
	"Board temperature normal trap. The variable bindings in the Trap 
	packet provide information about the chassis name, unit and the trap 
	status. This Trap is issued when the board temperature returns to
	normal. This trap must be cleared manually."
	::= 9

lucentPM4BoardTooHotTrap	TRAP-TYPE
	ENTERPRISE	lucentPM4Traps
	VARIABLES	{ sysName,
			  lucentPM4FMBoardIndex,
			  lucentPM4FMUnitType,
			  lucentPM4FMUnitTrapStatus }
	DESCRIPTION
	"Board trap. The variable bindings in the Trap packet provide 
	information about the chassis name, board number and the trap 
	status. This Trap must be cleared manually."
	::= 10

lucentPM4ModemFailTrap	TRAP-TYPE
	ENTERPRISE	lucentPM4Traps
	VARIABLES	{ sysName,
			  lucentPM4FMBoardIndex,
			  lucentPM4FMUnitType,
			  lucentPM4FMUnitIndex,
			  lucentPM4FMUnitTrapStatus }
	DESCRIPTION
	"Modem failure trap. The variable bindings in the Trap packet provide 
	information about the chassis name, modem number and the trap 
	status. This Trap must be cleared manually."
	::= 11

lucentPM4T1E1LineDownTrap	TRAP-TYPE
	ENTERPRISE	lucentPM4Traps
	VARIABLES	{ sysName,
			  lucentPM4FMBoardIndex,
			  lucentPM4FMUnitType,
			  lucentPM4FMUnitIndex,
			  lucentPM4FMUnitTrapStatus }
	DESCRIPTION
	"T1/E1 Line trap. The variable bindings in the Trap packet
	provide all the information for the clients to display the
	Board ID, Line ID and the status of the line. This Trap could
	be generated when the line comes up or goes down once. It must
	be cleared manually."
	::= 12

lucentPM4T1E1LineUpTrap	TRAP-TYPE
	ENTERPRISE	lucentPM4Traps
	VARIABLES	{ sysName,
			  lucentPM4FMBoardIndex,
			  lucentPM4FMUnitType,
			  lucentPM4FMUnitIndex,
			  lucentPM4FMUnitTrapStatus }
	DESCRIPTION
	"T1/E1 Line trap. The variable bindings in the Trap packet
	provide all the information for the clients to display the
	Board ID, Line ID and the status of the line. This Trap could
	be generated when the line comes up or goes down once. It must
	be cleared manually."
	::= 13

lucentPM4T1E1LineThreshTrap	TRAP-TYPE
	ENTERPRISE	lucentPM4Traps
	VARIABLES	{ sysName,
			  lucentPM4FMBoardIndex,
			  lucentPM4FMUnitType,
			  lucentPM4FMUnitIndex,
			  lucentPM4FMUnitTrapStatus }
	DESCRIPTION
	"T1/E1 Line trap. The variable bindings in the Trap packet
	provide all the information for the clients to display the
	Board ID, Line ID and the trap type. This Trap could
	be generated when the thresholds for the various performance
	statistics (ES, SES etc.) exceed. It must be cleared manually."
	::= 14

lucentPM4BoardPwrOffTrap	TRAP-TYPE
	ENTERPRISE	lucentPM4Traps
	VARIABLES	{ sysName,
			  lucentPM4FMBoardIndex,
			  lucentPM4FMUnitType,
			  lucentPM4FMUnitTrapStatus }
	DESCRIPTION
	"This trap is issued when the power supply to the board is not enough.
	The variable bindings in the Trap packet provide information about the 
	chassis name, board/board number and the trap status. This Trap must be 
	cleared manually."
	::= 15

lucentPM4RadiusAuthFailTrap	TRAP-TYPE
	ENTERPRISE	lucentPM4Traps
	VARIABLES	{ sysName,
			  lucentPM4FMBoardIndex,
			  lucentPM4FMUnitIndex }
	DESCRIPTION
	"This trap is issued when the Radius authentication fails. 
	This Trap must be cleared manually. The trap provides 
	information about the board and the modem number."
	::= 16

END
