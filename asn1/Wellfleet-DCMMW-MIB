-- @(#)WSCCS k/mibs-dcmmw.mib 1.4 6/28/96
Wellfleet-DCMMW-MIB DEFINITIONS ::= BEGIN

-- Created by mdl2asn version 3.1
-- Creation date: Wed Aug 30 16:39:23 EDT 1995

    IMPORTS

      OBJECT-TYPE
        FROM RFC-1212
      DisplayString
        FROM RFC1213-MIB
      wfDCMmwGroup
        FROM Wellfleet-COMMON-MIB;


    wfDCMmw		OBJECT IDENTIFIER ::= { wfDCMmwGroup 1 }

    wfDCMmwDelete OBJECT-TYPE
        SYNTAX	INTEGER {
    		    created(1),
    		    deleted(2)
    		}
        ACCESS	read-write
        STATUS	obsolete
        DESCRIPTION
                "DCMMW is dynamically loaded. This object specifies that the 
		 users can perform a set operation on this object in order to 
                 create/delete DCMMW base record. Default is created."
        DEFVAL	{ created }
        ::= { wfDCMmw 1 }

    wfDCMmwDisable OBJECT-TYPE
        SYNTAX  INTEGER {
                    enabled(1),
                    disabled(2)
                }
        ACCESS  read-write
        STATUS  obsolete
        DESCRIPTION
                "Enables or Disables DCMMW Subsystem. By disabling DCMMW,
		 can disable the DCM board."
        DEFVAL  { enabled }
        ::= { wfDCMmw 2 }

    wfDCMmwImageName OBJECT-TYPE
        SYNTAX	DisplayString (SIZE (0..127))
        ACCESS	read-write
        STATUS	obsolete
        DESCRIPTION
                "A textual string to describe the name of DCM image
		 to be download on to DCM. The image name should be 
		 a fully qualified filename. For ex: vol:filename."
        ::= { wfDCMmw 3 }

    wfDCMmwBootOption OBJECT-TYPE
        SYNTAX	INTEGER {
    		    local(1),
    		    download(2)
    		}
        ACCESS	read-write
        STATUS	obsolete
        DESCRIPTION
                "Specifies DCM's image load mode to DCMMW. If the option 
		 specified is local, DCMMW will not load a new image to DCM's
		 shared memory. If the option specified is download, then DCMMW
                 will load an image into DCM's shared memory. Name of the image
                 is specified using wfDCMMWImageName"
        DEFVAL	{ local }
        ::= { wfDCMmw 4 }

    wfDCMmwImageSaveMode OBJECT-TYPE
        SYNTAX	INTEGER {
    		    save(1),
    		    nosave(2)
    		}
        ACCESS	read-write
        STATUS	obsolete
        DESCRIPTION
                "Specifies DCM's image save mode. If the mode is save, then
		 DCMMW indicates it to DCM, to save the image on to its(DCM's)
		 FLASH memory. This saved image will be used by DCM in its next
		 boot time if the boot option is set to local.  If the mode
		 is nosave then the image will not be saved."
        DEFVAL	{ save }
        ::= { wfDCMmw 5 }

    wfDCMmwCfgMode OBJECT-TYPE
        SYNTAX	INTEGER {
    		    local(1),
    		    shmem(2)
    		}
        ACCESS	read-write
        STATUS	obsolete
        DESCRIPTION
                "Specifies whether DCMMW should let DCM use the config info 
		 from the shared memory or use the config info from DCM's FLASH
		 memory. If the mode is local, then DCMMW will write `0' in 
		 DCM's config file, which indicates the DCM that it should use
		 the config info from its FLASH memory. If the mode is shared
		 memory, then DCMMW will write the config info in DCM's config
		 file, for DCM to use."
        DEFVAL	{ local }
        ::= { wfDCMmw 6 }

    wfDCMmwWriteConfigInfo OBJECT-TYPE
        SYNTAX	INTEGER {
    		    save(1),
    		    nosave(2)
    		}
        ACCESS	read-write
        STATUS	obsolete
        DESCRIPTION
                "DCMMW uses this object to specify DCM whether it should commit
		 the configuration information into its Flash memory or not"
        DEFVAL	{ save }
        ::= { wfDCMmw 7 }

    wfDCMmwRMONMaxHost OBJECT-TYPE
        SYNTAX	INTEGER(100..8128)
        ACCESS	read-write
        STATUS	obsolete
        DESCRIPTION
                "Indicates the maximum number of hosts each RMON host control
		 entry on DCM will store. When the table reaches this value, 
		 entries will be deleted based on an LRU algorithm. The max 
		 limit depends on the amount of memory installed in DCM. It 
		 is in the range 2048..8128. DCMMW uses this object to provide
		 the value to DCM.  Check the MIB object wfDCMmwRMONHost to 
		 verify the number of hosts that got configured in the RMON 
		 host control entry."
        DEFVAL	{ 500 }
        ::= { wfDCMmw 8 }

    wfDCMmwRMONDfltHost OBJECT-TYPE
        SYNTAX	INTEGER {
    		    enabled(1),
    		    disabled(2)
    		}
        ACCESS	read-write
        STATUS	obsolete
        DESCRIPTION
                "DCMMW uses this to specify DCM that it should create or not 
		 create the hostControlTable. If enabled DCMMW indicates DCM
		 to create default host entries for the interface it is 
	         configured to."
        DEFVAL	{ disabled }
        ::= { wfDCMmw 9 }

    wfDCMmwRMONDfltMtrix OBJECT-TYPE
        SYNTAX	INTEGER {
    		    enabled(1),
    		    disabled(2)
    		}
        ACCESS	read-write
        STATUS	obsolete
        DESCRIPTION
                "DCMMW uses this to specify DCM that it should create or not 
		 create the matrixControlTable. If enabled DCMMW indicates DCM
		 to create default matrix entries for the interface it is 
		 configured to."
        DEFVAL	{ disabled }
        ::= { wfDCMmw 10 }

    wfDCMmwRMONHost OBJECT-TYPE
        SYNTAX  INTEGER
        ACCESS  read-only
        STATUS  obsolete
        DESCRIPTION
                "This specifies the configured number of hosts in each 
		 RMON host control entry on DCM"
        ::= { wfDCMmw 11 }
   
    wfDCMRmonAgent OBJECT-TYPE
        SYNTAX  INTEGER {
                    ready(1),
                    down(2)
                }
        ACCESS  read-only
        STATUS  obsolete
        DESCRIPTION
                "The state of the RMON agent. A ready state(1) indicates that
                 the RMON agent instrumentation is up and ready to process
                 SNMP requests"
        DEFVAL  { down }
        ::= { wfDCMmw 12 }

    wfDCMMemSize OBJECT-TYPE
        SYNTAX	INTEGER 
        ACCESS	read-only
        STATUS	obsolete
        DESCRIPTION
                "This specifies DCM board's memory size."
        ::= { wfDCMmw 13 }

    wfDCMHwRev OBJECT-TYPE
        SYNTAX	DisplayString (SIZE (0..127))
        ACCESS	read-only
        STATUS	obsolete
        DESCRIPTION
                "This specifies DCM board's HW revision number"
        ::= { wfDCMmw 14 }

    wfDCMFwRev OBJECT-TYPE
        SYNTAX	DisplayString (SIZE (0..127))
        ACCESS	read-only
        STATUS	obsolete
        DESCRIPTION
                "This specifies DCM board's FW revision number"
        ::= { wfDCMmw 15 }

    wfDCMAgentImageVersion OBJECT-TYPE
        SYNTAX	DisplayString (SIZE (0..127))
        ACCESS	read-only
        STATUS	obsolete
        DESCRIPTION
                "This specifies DCM board's Agent Image version number"
        ::= { wfDCMmw 16 }

    wfDCMmwNumDCM OBJECT-TYPE
	SYNTAX  INTEGER 
	ACCESS  read-only
        STATUS  obsolete
        DESCRIPTION
                "This specifies how many DCMs are present"
        ::= { wfDCMmw 17 }

    -- The DCM Group
    --
    -- This group provides the DCM specific information
    --

    wfDCMTable OBJECT-TYPE
        SYNTAX  SEQUENCE OF WfDCMEntry
        ACCESS  not-accessible
        STATUS  mandatory
        DESCRIPTION
                "Table containing DCM records"
        ::= { wfDCMmwGroup 2 }

    wfDCMEntry OBJECT-TYPE
        SYNTAX  WfDCMEntry
        ACCESS  not-accessible
        STATUS  mandatory
        DESCRIPTION
                "Information concerning a specific DCM entry. 
		 Each DCM entry corresponds to a physical probe."
        INDEX   { wfDCMIndex }
        ::= { wfDCMTable 1 }

    WfDCMEntry ::= SEQUENCE {
            wfDCMDelete
		INTEGER,
	    wfDCMIndex
		INTEGER,
            wfDCMDisable
                INTEGER,
            wfDCMOperStatus
                INTEGER,
	    wfDCMStreamCount
		INTEGER,
	    wfDCMIntfType
		INTEGER,
	    wfDCMImageName
		DisplayString,
	    wfDCMBootOption
		INTEGER,
	    wfDCMImageSaveMode
		INTEGER,
	    wfDCMCfgMode
		INTEGER,
	    wfDCMSaveConfigInfo 
		INTEGER,
	    wfDCMRMONMaxHost
		INTEGER,
	    wfDCMRMONDfltHost
		INTEGER,
	    wfDCMRMONDfltMtrix
		INTEGER,
	    wfDCMRMONHost
		INTEGER,
	    wfDCMmemSize
		INTEGER,
	    wfDCMhwRev
		DisplayString,
	    wfDCMfwRev
		DisplayString,
	    wfDCMagentImageVersion
		DisplayString,
   	    wfDCMRmonObjectSupport	
		INTEGER	
        }

    wfDCMDelete OBJECT-TYPE
        SYNTAX  INTEGER {
                    created(1),
                    deleted(2)
                }
        ACCESS  read-write
        STATUS  mandatory
        DESCRIPTION
                 "Create/Delete flag. Default is created. User
		  can perform a set operation on this object to
		  create/delete a DCMEntry instance."
        DEFVAL  { created }
        ::= { wfDCMEntry 1 }


    wfDCMIndex OBJECT-TYPE
	SYNTAX  INTEGER
	ACCESS  read-only
	STATUS	mandatory
        DESCRIPTION
	    "An index that uniquely identifies an entry in the
             DCM table. Each such entry defines one DCM."
        ::= { wfDCMEntry 2 }

    wfDCMDisable OBJECT-TYPE
	SYNTAX  INTEGER {
    		    enabled(1),
    		    disabled(2)
    		}   
	ACCESS  read-write
	STATUS	mandatory
        DESCRIPTION
	    "Enables or Disables the DCM"
	DEFVAL { enabled }
        ::= { wfDCMEntry 3 }
   
    wfDCMOperStatus OBJECT-TYPE
	SYNTAX  INTEGER {
		    up(1),
		    down(2),
		    init(3)
		}
	ACCESS  read-only
	STATUS	mandatory
        DESCRIPTION
          "This object indicates the operational state of the DCM"
        DEFVAL { down }
        ::= { wfDCMEntry 4 }

    wfDCMStreamCount OBJECT-TYPE
	SYNTAX  INTEGER (1..4) 
	ACCESS  read-only
	STATUS	mandatory
        DESCRIPTION
          "This object indicates the number of Streams this DCM
	   configured to support."
        ::= { wfDCMEntry 5 } 

    wfDCMIntfType OBJECT-TYPE
        SYNTAX  INTEGER {
		    ether(6),
		    tokenring(9)
                }
        ACCESS  read-only
        STATUS  mandatory
        DESCRIPTION
	   "This object identifies the type of interface this
	    DCM is configured to."
	::= { wfDCMEntry 6 }

    wfDCMImageName OBJECT-TYPE
        SYNTAX	DisplayString
        ACCESS	read-write
        STATUS	mandatory
        DESCRIPTION
                "A textual string to describe the name of the DCM image
		 to be download on to the DCM. The image name should be 
		 a fully qualified filename. For ex: vol:filename."
        ::= { wfDCMEntry 7 }

    wfDCMBootOption OBJECT-TYPE
        SYNTAX	INTEGER {
    		    local(1),
    		    download(2)
    		}
        ACCESS	read-write
        STATUS	mandatory
        DESCRIPTION
                "Specifies DCM's image load mode to DCMMW. If the option 
		 specified is local, DCMMW will not load a new image to DCM's
		 shared memory. If the option specified is download, then DCMMW
                 will load an image into DCM's shared memory. Name of the image
                 is specified using wfDCMMWImageName"
        DEFVAL	{ local }
        ::= { wfDCMEntry 8 }

    wfDCMImageSaveMode OBJECT-TYPE
        SYNTAX	INTEGER {
    		    save(1),
    		    nosave(2)
    		}
        ACCESS	read-write
        STATUS	mandatory
        DESCRIPTION
                "Specifies DCM's image save mode. If the mode is save, then
		 DCMMW indicates it to DCM, to save the image on to its(DCM's)
		 FLASH memory. This saved image will be used by DCM in its next
		 boot time if the boot option is set to local.  If the mode
		 is nosave then the image will not be saved."
        DEFVAL	{ save }
        ::= { wfDCMEntry 9 }

    wfDCMCfgMode OBJECT-TYPE
        SYNTAX	INTEGER {
    		    local(1),
    		    shmem(2)
    		}
        ACCESS	read-write
        STATUS	mandatory
        DESCRIPTION
                "Specifies whether DCMMW should let DCM use the config info 
		 from the shared memory or use the config info from DCM's FLASH
		 memory. If the mode is local, then DCMMW will write `0' in 
		 DCM's config file, which indicates the DCM that it should use
		 the config info from its FLASH memory. If the mode is shared
		 memory, then DCMMW will write the config info in DCM's config
		 file, for DCM to use."
        DEFVAL	{ local }
        ::= { wfDCMEntry 10 }

    wfDCMSaveConfigInfo OBJECT-TYPE
        SYNTAX	INTEGER {
    		    save(1),
    		    nosave(2)
    		}
        ACCESS	read-write
        STATUS	mandatory
        DESCRIPTION
                "DCMMW uses this object to specify DCM whether it should commit
		 the configuration information into its Flash memory or not"
        DEFVAL	{ save }
        ::= { wfDCMEntry 11 }

    wfDCMRMONMaxHost OBJECT-TYPE
        SYNTAX	INTEGER(100..8128)
        ACCESS	read-write
        STATUS	mandatory
        DESCRIPTION
                "Indicates the maximum number of hosts each RMON host control
		 entry on DCM will store. When the table reaches this value, 
		 entries will be deleted based on an LRU algorithm. The max 
		 limit depends on the amount of memory installed in DCM. It 
		 is in the range 2048..8128. DCMMW uses this object to provide
		 the value to DCM.  Check the MIB object wfDCMmwRMONHost to 
		 verify the number of hosts that got configured in the RMON 
		 host control entry."
        DEFVAL	{ 500 }
        ::= { wfDCMEntry 12 }

    wfDCMRMONDfltHost OBJECT-TYPE
        SYNTAX	INTEGER {
    		    enabled(1),
    		    disabled(2)
    		}
        ACCESS	read-write
        STATUS	mandatory
        DESCRIPTION
                "DCMMW uses this to specify DCM that it should create or not 
		 create the hostControlTable. If enabled DCMMW indicates DCM
		 to create default host entries for the interface it is 
	         configured to."
        DEFVAL	{ disabled }
        ::= { wfDCMEntry 13 }

    wfDCMRMONDfltMtrix OBJECT-TYPE
        SYNTAX	INTEGER {
    		    enabled(1),
    		    disabled(2)
    		}
        ACCESS	read-write
        STATUS	mandatory
        DESCRIPTION
                "DCMMW uses this to specify DCM that it should create or not 
		 create the matrixControlTable. If enabled DCMMW indicates DCM
		 to create default matrix entries for the interface it is 
		 configured to."
        DEFVAL	{ disabled }
        ::= { wfDCMEntry 14 }

    wfDCMRMONHost OBJECT-TYPE
        SYNTAX	INTEGER
        ACCESS	read-only
        STATUS	mandatory
        DESCRIPTION
                "This specifies the configured number of hosts in each RMON 
		 host control entry on DCM"
        ::= { wfDCMEntry 15 }

    wfDCMmemSize OBJECT-TYPE
        SYNTAX	INTEGER
        ACCESS	read-only
        STATUS	mandatory
        DESCRIPTION
                "This specifies DCM board's memory size"
        ::= { wfDCMEntry 16 }

    wfDCMhwRev OBJECT-TYPE
        SYNTAX	DisplayString
        ACCESS	read-only
        STATUS	mandatory
        DESCRIPTION
                "This specifies DCM board's HW revision number"
        ::= { wfDCMEntry 17 }

    wfDCMfwRev OBJECT-TYPE
        SYNTAX	DisplayString
        ACCESS	read-only
        STATUS	mandatory
        DESCRIPTION
                "This specifies DCM board's FW revision number"
        ::= { wfDCMEntry 18 }

    wfDCMagentImageVersion OBJECT-TYPE
        SYNTAX	DisplayString
        ACCESS	read-only
        STATUS	mandatory
        DESCRIPTION
                "This specifies DCM board's Agent Image version number"
        ::= { wfDCMEntry 19 }

    wfDCMRmonObjectSupport OBJECT-TYPE
        SYNTAX	INTEGER {
    		 rmon(1),
    	 	 rmon2(2)
    		}
        ACCESS	read-write
        STATUS	mandatory
        DESCRIPTION
            	 "Allows a user to specify whether they want to access RMON
		 and RMON2 stats rmon2(2), or just RMON stats rmon(1) from a
		 specific DCM. This attribute is only used when two DCMs are
		 present on a system. If only one DCM is present the default 
		 value will be rmon(2) and sets to this attribute will have 
		 no affect."
        DEFVAL	{ rmon }
        ::= { wfDCMEntry 20 }

    --
    -- DCM Stream group
    --
    -- This group provides DCM's stream specific 
    -- information
    --
  
    wfDCMStreamTable OBJECT-TYPE
        SYNTAX  SEQUENCE OF WfDCMStreamEntry
        ACCESS  not-accessible
        STATUS  obsolete
        DESCRIPTION
                "Table containing DCM stream records"
        ::= { wfDCMmwGroup 3 }

    wfDCMStreamEntry OBJECT-TYPE
        SYNTAX  WfDCMStreamEntry
        ACCESS  not-accessible
        STATUS  obsolete
        DESCRIPTION
                "Information concerning a specific DCM stream entry.
		 Each stream entry corresponds to the interface the
		 DCM is associated with." 
        INDEX   { wfDCMStreamDCMIndex, wfDCMStreamIndex }
        ::= { wfDCMStreamTable 1 }

    WfDCMStreamEntry ::= SEQUENCE {
	wfDCMStreamDCMIndex
	    INTEGER,
	wfDCMStreamIndex
	    INTEGER,
	wfDCMStreamDisable
	    INTEGER,
	wfDCMStreamDataSource
	    OBJECT IDENTIFIER
    }

    wfDCMStreamDCMIndex OBJECT-TYPE
        SYNTAX  INTEGER 
        ACCESS  read-only
        STATUS  obsolete
        DESCRIPTION
            "An index that identifies the DCM entry of which 
             this stream is associated with."
        ::= { wfDCMStreamEntry 1 }


    wfDCMStreamIndex OBJECT-TYPE
        SYNTAX INTEGER (1..4)
        ACCESS read-only
        STATUS obsolete
        DESCRIPTION
            "An index that uniquely identifies the particular
            stream this entry is associated with."
        ::= { wfDCMStreamEntry 2 }


    wfDCMStreamDisable OBJECT-TYPE
        SYNTAX  INTEGER {
                    enabled(1),
                    disabled(2)
                }
        ACCESS  read-only
        STATUS  obsolete
        DESCRIPTION
            "Enables or Disables DCM stream"
        DEFVAL { enabled }
        ::= { wfDCMStreamEntry 3 }

    wfDCMStreamDataSource OBJECT-TYPE
        SYNTAX OBJECT IDENTIFIER
        ACCESS read-only
        STATUS obsolete
	DESCRIPTION
	  "This object identifies the source of the data that
           this DCM stream entry is configured to analyze.
           This is the ifIndex value of the stream(interface)."
        ::= { wfDCMStreamEntry 4 }

    END  -- Wellfleet-DCMMW-MIB
