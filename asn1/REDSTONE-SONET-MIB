-- *****************************************************************
-- REDSTONE-SONET-MIB
--
-- Redstone Communications Inc. Enterprise MIB
-- SONET MIB
--
-- Copyright 1998 Redstone Communications, Incorporated.
-- All Rights Reserved.
-- *****************************************************************

REDSTONE-SONET-MIB DEFINITIONS ::= BEGIN

IMPORTS
	MODULE-IDENTITY,
	OBJECT-TYPE
		FROM SNMPv2-SMI
	OBJECT-GROUP, MODULE-COMPLIANCE FROM SNMPv2-CONF

	DisplayString
		FROM SNMPv2-TC

    ifIndex
        FROM IF-MIB

	rsMgmt
		FROM REDSTONE-SMI;



rsSonetMIB  MODULE-IDENTITY
	LAST-UPDATED "9801010000Z"
	ORGANIZATION "Redstone Communications, Inc."
	CONTACT-INFO
        "
        Redstone Communications, Inc.
		5 Carlisle Road
        Westford MA 01886
        USA
        Tel:    +1-978-692-1999
		Email:  mib@redstonecom.com
        "
	DESCRIPTION
		"The SONET MIB for the 
		Redstone Communications Inc. enterprise."
	REVISION      "9801010000Z"
	DESCRIPTION
		"Initial version of this MIB module."
	::= { rsMgmt 7 }

-- ++++++++++++++++++++++++++++++++++++++++++++++++++++++++++++++++++++++
-- Textual conventions
-- ++++++++++++++++++++++++++++++++++++++++++++++++++++++++++++++++++++++

-- No textual conventions are defined in this MIB module.

-- ++++++++++++++++++++++++++++++++++++++++++++++++++++++++++++++++++++++
-- Managed objects
-- ++++++++++++++++++++++++++++++++++++++++++++++++++++++++++++++++++++++

rsSonetObjects     OBJECT IDENTIFIER ::= { rsSonetMIB 1 }

-- 
-- This MIB contains managed objects for SONET interfaces.
-- Management objects for configuration of interface attributes
-- that either are absent from, or read-only in, RFC1595
-- SONET MIB.
--



-- //////////////////////////////////////////////////////////////////////
--
-- SONET Interfaces
--
-- //////////////////////////////////////////////////////////////////////

--
-- The SONET Interface Table
--

rsSonetMediumTable OBJECT-TYPE
    SYNTAX      SEQUENCE OF RsSonetMediumEntry
    MAX-ACCESS  not-accessible
    STATUS      current
    DESCRIPTION
        "This table contains entries for SONET interfaces present in the system."
    ::= { rsSonetObjects 1 }

rsSonetMediumEntry OBJECT-TYPE
    SYNTAX      RsSonetMediumEntry
    MAX-ACCESS  not-accessible
    STATUS      current
    DESCRIPTION
        "Each entry describes the characteristics of an SONET interface."
    INDEX       { ifIndex }
    ::= { rsSonetMediumTable 1 }

RsSonetMediumEntry ::= SEQUENCE {
    rsSonetMediumType
        INTEGER,
    rsSonetMediumLoopbackConfig
        INTEGER,
    rsSonetMediumTimingSource
        INTEGER,
    rsSonetMediumCircuitIdentifier
        DisplayString
}


rsSonetMediumType OBJECT-TYPE
    SYNTAX      INTEGER {
                    sonet(1),
                    sdh(2)
                }
    MAX-ACCESS  read-write
    STATUS      current
    DESCRIPTION
        "This variable identifies whether a SONET
        or a SDH signal is used across this interface."
    ::= { rsSonetMediumEntry 1 }


rsSonetMediumLoopbackConfig OBJECT-TYPE
    SYNTAX      INTEGER {
                    sonetNoLoop(0),
                    sonetFacilityLoop(1),
                    sonetTerminalLoop(2),
                    sonetOtherLoop(3) }
    MAX-ACCESS  read-write
    STATUS      current
    DESCRIPTION
        "The current loopback state of the SONET/SDH interface.  The
        values mean:

        sonetNoLoop
        Not in the loopback state. A device that is not
        capable of performing a loopback on this interface
        shall always return this value.

        sonetFacilityLoop
        The received signal at this interface is looped back
        out through the corresponding transmitter in the return
        direction.

        sonetTerminalLoop
        The signal that is about to be transmitted is connected
        to the associated incoming receiver.

        sonetOtherLoop
        Loopbacks that are not defined here."
    ::= { rsSonetMediumEntry 2 }


rsSonetMediumTimingSource OBJECT-TYPE
    SYNTAX      INTEGER {
                    loop(0),
                    internal(1)
                }
    MAX-ACCESS  read-write
    STATUS      current
    DESCRIPTION
        "Selects the source from which transmit timing is derived.
        loop(1) indicates timing is recovered from the receiver;
        internal(2) indicates timing is taken from the internal
        system timing reference."
    ::= { rsSonetMediumEntry 3 }


rsSonetMediumCircuitIdentifier OBJECT-TYPE
    SYNTAX      DisplayString(SIZE(0..255))
    MAX-ACCESS  read-write
    STATUS      current
    DESCRIPTION
        "This variable contains the transmission
        vendor's circuit identifier, for the
        purpose of facilitating troubleshooting."
    ::= { rsSonetMediumEntry 4 }


-- ++++++++++++++++++++++++++++++++++++++++++++++++++++++++++++++++++++++
-- Notification control objects
-- ++++++++++++++++++++++++++++++++++++++++++++++++++++++++++++++++++++++

-- No notifications are defined in this MIB. Placeholder follows.

-- rsSonetTrapControl      OBJECT IDENTIFIER ::= { rsSonetMIB 2 }



-- ++++++++++++++++++++++++++++++++++++++++++++++++++++++++++++++++++++++
-- Notifications
-- ++++++++++++++++++++++++++++++++++++++++++++++++++++++++++++++++++++++

-- No notifications are defined in this MIB. Placeholder follows.

-- The following two OBJECT IDENTIFIERS are used to define SNMPv2 
-- Notifications that are easily translated into SNMPv1 Traps.

-- rsSonetTraps            OBJECT IDENTIFIER ::= { rsSonetMIB 3 }
-- rsSonetTrapPrefix       OBJECT IDENTIFIER ::= { rsSonetTraps 0 }



-- ++++++++++++++++++++++++++++++++++++++++++++++++++++++++++++++++++++++
-- Conformance information
-- ++++++++++++++++++++++++++++++++++++++++++++++++++++++++++++++++++++++

rsSonetConformance OBJECT IDENTIFIER ::= { rsSonetMIB 4 }
rsSonetCompliances OBJECT IDENTIFIER ::= { rsSonetConformance 1 }
rsSonetGroups      OBJECT IDENTIFIER ::= { rsSonetConformance 2 }

-- compliance statements

rsSonetCompliance MODULE-COMPLIANCE
        STATUS  current
        DESCRIPTION
                "The compliance statement for entities which implement
                the Redstone SONET MIB."
        MODULE  -- this module
                MANDATORY-GROUPS { rsSonetGroup }
        ::= { rsSonetCompliances 1 }

-- units of conformance

rsSonetGroup OBJECT-GROUP
        OBJECTS {
		rsSonetMediumType,
		rsSonetMediumLoopbackConfig,
		rsSonetMediumTimingSource,
		rsSonetMediumCircuitIdentifier
	}
	STATUS  current
	DESCRIPTION
		"A collection of objects providing management of SONET interfaces
		in a Redstone product."
    ::= { rsSonetGroups 1 }

END
