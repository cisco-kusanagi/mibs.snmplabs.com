Wellfleet-5000-CHASSIS-MIB DEFINITIONS ::= BEGIN

    IMPORTS

      IpAddress
        FROM RFC1155-SMI
      OBJECT-TYPE
        FROM RFC-1212
      DisplayString
        FROM RFC1213-MIB
      wfHardwareConfig
        FROM Wellfleet-COMMON-MIB;

    wfHw5000Chassis OBJECT IDENTIFIER     ::= { wfHardwareConfig 6 }
    wfHw5000ChassisBase OBJECT IDENTIFIER ::= { wfHw5000Chassis 1 }

    wfHw5000NumSlots OBJECT-TYPE
        SYNTAX	INTEGER (1..14)
        ACCESS	read-only
        STATUS	mandatory
        DESCRIPTION
                "The number of slots in this 5000 chassis."
        ::= { wfHw5000ChassisBase 1 }

    wfHw5000BpSerialNumber OBJECT-TYPE
        SYNTAX	DisplayString (SIZE (0..32))
        ACCESS	read-only
        STATUS	mandatory
        DESCRIPTION
                "The serial number of the chassis."
        ::= { wfHw5000ChassisBase 2 }

    wfHw5000ModuleTable OBJECT-TYPE
        SYNTAX	SEQUENCE OF WfHw5000ModuleEntry
        ACCESS	not-accessible
        STATUS	mandatory
        DESCRIPTION
                "Hardware Table of module descriptors - indexed by slot number"
        ::= { wfHw5000Chassis 2 }

    wfHw5000ModuleEntry OBJECT-TYPE
        SYNTAX	WfHw5000ModuleEntry
        ACCESS	not-accessible
        STATUS	mandatory
        DESCRIPTION
                "Specific information about a module, indexed by slot."
        INDEX	{ wfHw5000ModuleSlot }
        ::= { wfHw5000ModuleTable 1 }

    WfHw5000ModuleEntry ::= SEQUENCE {
    	    wfHw5000ModuleSlot
    		INTEGER,
    	    wfHw5000ModuleDescription
    		DisplayString,
    	    wfHw5000ModuleId
    		INTEGER,
    	    wfHw5000ModuleRev
    		DisplayString,
    	    wfHw5000ModuleSerialNumber
    		DisplayString,
    	    wfHw5000ModuleIpAddress
    		IpAddress
        }

    wfHw5000ModuleSlot OBJECT-TYPE
        SYNTAX	INTEGER (0..14)
        ACCESS	read-only
        STATUS	mandatory
        DESCRIPTION
                "A unique value for each slot.
                Its value ranges between 0 and 14.
                There are products in this family that contain less than 14 slots."
        ::= { wfHw5000ModuleEntry 1 }

    wfHw5000ModuleDescription OBJECT-TYPE
        SYNTAX  DisplayString (SIZE (0..255))
        ACCESS	read-only
        STATUS	mandatory
        DESCRIPTION
                "A textual description of the module."

        ::= { wfHw5000ModuleEntry 2 }

    wfHw5000ModuleId OBJECT-TYPE
        SYNTAX	INTEGER
        ACCESS	read-only
        STATUS	mandatory
        DESCRIPTION
                "The unique module identification number."

        ::= { wfHw5000ModuleEntry 3 }

    wfHw5000ModuleRev OBJECT-TYPE
        SYNTAX	DisplayString (SIZE (0..16))
        ACCESS	read-only
        STATUS	mandatory
        DESCRIPTION
                "The revision level of the module."

        ::= { wfHw5000ModuleEntry 4 }

    wfHw5000ModuleSerialNumber OBJECT-TYPE
        SYNTAX	DisplayString (SIZE (0..16))
        ACCESS	read-only
        STATUS	mandatory
        DESCRIPTION
                "The serial number of the module."

        ::= { wfHw5000ModuleEntry 5 }

    wfHw5000ModuleIpAddress OBJECT-TYPE
        SYNTAX	IpAddress
        ACCESS	read-only
        STATUS	mandatory
        DESCRIPTION
                "The IP Address of the module, null if none exists"

        ::= { wfHw5000ModuleEntry 6 }

    END  -- Wellfleet-5000-CHASSIS-MIB
