AI198CLC-MIB DEFINITIONS ::= BEGIN

-- Applied Innovation Series 1 198 CLC Proprietary MIB definitions
-- @(#) aiclc.my 1.70@(#)

IMPORTS
		DisplayString FROM SNMPv2-TC
        MODULE-IDENTITY, OBJECT-TYPE,
        Integer32, TimeTicks,
        Counter32, IpAddress, enterprises
                FROM SNMPv2-SMI
        DateAndTime
                FROM SNMPv2-TC;


-- group object IDs

aii             OBJECT IDENTIFIER ::= { enterprises 539 }
aiSystemOID     OBJECT IDENTIFIER ::= { aii 2 }

aiCLC   MODULE-IDENTITY
        LAST-UPDATED "9505081700Z"
        ORGANIZATION "Applied Innovation Incorporated"
        CONTACT-INFO
            "           Engineering MIB Administrator
            Postal:     Applied Innovation Inc.
                        5800 Innovation Drive
                        Dublin, OH 43016

               Tel:     614/798-2000
               Fax:     614/798-1770
            E-mail:     snmp@aiinet.com"
        DESCRIPTION
            "The MIB Module for Series 1 Common Logic Controllers (CLC)"
        ::= { aii 9 }

-- System group for Series 1 Common Logic Controllers

aiCLCSystem             OBJECT IDENTIFIER ::= { aiCLC 1 }

-- sysObjectIDs

ai198           OBJECT IDENTIFIER ::= { aiSystemOID 198 }
ai198Ver1       OBJECT IDENTIFIER ::= { ai198 1 }
ai198Ver10      OBJECT IDENTIFIER ::= { ai198Ver1 0 }
ai198Ver102     OBJECT IDENTIFIER ::= { ai198Ver10 2 }
ai198Ver103     OBJECT IDENTIFIER ::= { ai198Ver10 3 }
ai198Ver104     OBJECT IDENTIFIER ::= { ai198Ver10 4 }
ai198Ver12      OBJECT IDENTIFIER ::= { ai198Ver1 2 }
ai198Ver120     OBJECT IDENTIFIER ::= { ai198Ver12 0 }
ai198Ver13	OBJECT IDENTIFIER ::= { ai198Ver1 3 }
ai198Ver130	OBJECT IDENTIFIER ::= { ai198Ver13 0 }

-- System Group

-- Implementation of this group is mandatory for all Applied Innovation
-- Series 1 CLCs that support SNMP Management

    aiCLCBox1DensAdmin OBJECT-TYPE
        SYNTAX INTEGER {
                   disabled(1),
                   four(4),
                   eight(8),
                   sixteen(16),
                   thirtytwo(32)
                }
        MAX-ACCESS read-write
        STATUS current
        DESCRIPTION
                "The administration value for the slot density for Chassis 1
                 of and AISwitch."
        DEFVAL { 16 }
        ::= { aiCLCSystem 1 }

    aiCLCBox2DensAdmin OBJECT-TYPE
        SYNTAX INTEGER {
                   disabled(1),
                   four(4),
                   eight(8),
                   sixteen(16),
                   thirtytwo(32)
                }
        MAX-ACCESS read-write
        STATUS current
        DESCRIPTION
                "The administration value for the slot density for Chassis 2
                 of and AISwitch."
        DEFVAL { 16 }
        ::= { aiCLCSystem 2 }

    aiCLCBox3DensAdmin OBJECT-TYPE
        SYNTAX INTEGER {
                   disabled(1),
                   four(4),
                   eight(8),
                   sixteen(16),
                   thirtytwo(32)
                }
        MAX-ACCESS read-write
        STATUS current
        DESCRIPTION
                "The administration value for the slot density for Chassis 3
                 of and AISwitch."
        DEFVAL { 1 }
        ::= { aiCLCSystem 3 }

    aiCLCBox4DensAdmin OBJECT-TYPE
        SYNTAX INTEGER {
                   disabled(1),
                   four(4),
                   eight(8),
                   sixteen(16),
                   thirtytwo(32)
                }
        MAX-ACCESS read-write
        STATUS current
        DESCRIPTION
                "The administration value for the slot density for Chassis 4
                 of and AISwitch."
        DEFVAL { 1 }
        ::= { aiCLCSystem 4 }

    aiCLCBox5DensAdmin OBJECT-TYPE
        SYNTAX INTEGER {
                   disabled(1),
                   four(4),
                   eight(8),
                   sixteen(16),
                   thirtytwo(32)
                }
        MAX-ACCESS read-write
        STATUS current
        DESCRIPTION
                "The administration value for the slot density for Chassis 5 
                 of and AISwitch."
        DEFVAL { 1 }
        ::= { aiCLCSystem 5 }

    aiCLCBox6DensAdmin OBJECT-TYPE
    	SYNTAX INTEGER {
                   disabled(1),
                   four(4),
                   eight(8),
                   sixteen(16),
                   thirtytwo(32)
                }
        MAX-ACCESS read-write
        STATUS current
        DESCRIPTION
                "The administration value for the slot density for Chassis 6 
                 of and AISwitch."
        DEFVAL { 1 }
        ::= { aiCLCSystem 6 }


    aiCLCBox7DensAdmin OBJECT-TYPE
    	SYNTAX INTEGER {
                   disabled(1),
                   four(4),
                   eight(8),
                   sixteen(16),
                   thirtytwo(32)
                }
        MAX-ACCESS read-write
        STATUS current
        DESCRIPTION
                "The administration value for the slot density for Chassis 7 
                 of and AISwitch."
        DEFVAL { 1 }
        ::= { aiCLCSystem 7 }

    aiCLCBox8DensAdmin OBJECT-TYPE
    	SYNTAX INTEGER {
                   disabled(1),
                   four(4),
                   eight(8),
                   sixteen(16),
                   thirtytwo(32)
                }
        MAX-ACCESS read-write
        STATUS current
        DESCRIPTION
                "The administration value for the slot density for Chassis 8 
                 of and AISwitch."
        DEFVAL { 1 }
        ::= { aiCLCSystem 8 }

    aiCLCNodeName OBJECT-TYPE
        SYNTAX DisplayString(0..29)
        MAX-ACCESS read-write
        STATUS current       
	DESCRIPTION
                "This associates a name with an AI Switch. This string 
                 is part of the prompt for a user port." 
        DEFVAL { "NODE-XXX" }
        ::= { aiCLCSystem 9 }

    aiCLCLogPortEnable OBJECT-TYPE
        SYNTAX INTEGER {
                   on(1),
                   off(2)
                }
        MAX-ACCESS read-write
        STATUS current
        DESCRIPTION
                "Enable/Disable the display of Alarm and Activity Information."
        DEFVAL { 1 }
        ::= { aiCLCSystem 10 }
 

    aiCLCAlmLogPort OBJECT-TYPE
        SYNTAX INTEGER (0..255)
        MAX-ACCESS read-write
        STATUS current
        DESCRIPTION
        "The Alarm and Activity Log Port Number." 
        DEFVAL { 0 }
        ::= { aiCLCSystem 11 }

    aiCLCActLogLvl OBJECT-TYPE
        SYNTAX INTEGER (0..9)
        MAX-ACCESS read-write
        STATUS current
        DESCRIPTION
        "The alarm level which when met or exceeded will cause messages 
        to be printed on the log port." 
        DEFVAL { 1 }
        ::= { aiCLCSystem 12 }

    aiCLCMinorAlmMin OBJECT-TYPE
        SYNTAX INTEGER (0..9)
        MAX-ACCESS read-write
        STATUS current
        DESCRIPTION
        "The alarm level which when met or exceeded will cause a minor 
        alarm to be reported." 
        DEFVAL { 2 }
        ::= { aiCLCSystem 13 }

    aiCLCMinorAlmMax OBJECT-TYPE
        SYNTAX INTEGER (0..9)
        MAX-ACCESS read-write
        STATUS current
        DESCRIPTION
        "The alarm level which when exceeded will not cause a minor alarm 
        to be reported." 
        DEFVAL { 4 }
        ::= { aiCLCSystem 14 }

    aiCLCMajorAlmMin OBJECT-TYPE
        SYNTAX INTEGER (0..9)
        MAX-ACCESS read-write
        STATUS current
        DESCRIPTION
        "The alarm level which when met or exceeded will cause a major 
        alarm to be reported." 
        DEFVAL { 5 }
        ::= { aiCLCSystem 15 }

    aiCLCMajorAlmMax OBJECT-TYPE
        SYNTAX INTEGER (0..9)
        MAX-ACCESS read-write
        STATUS current
        DESCRIPTION
        "The alarm level which when exceeded will not cause a major alarm 
        to be reported." 
        DEFVAL { 9 }
        ::= { aiCLCSystem 16 }

    aiCLCCraftLogEcho OBJECT-TYPE
    	SYNTAX INTEGER {
                   on(1),
                   off(2)
                }
        MAX-ACCESS read-write
        STATUS current
        DESCRIPTION
                "Echo Alarm and Activity information on the craft port."
        DEFVAL { 1 }
        ::= { aiCLCSystem 17 }

    aiCLCCaamlRoute OBJECT-TYPE
        SYNTAX DisplayString(0..200)
        MAX-ACCESS read-write
        STATUS current
        DESCRIPTION
        "Name of the destination used for the CAAML Log." 
        ::= { aiCLCSystem 18 }

    aiCLCCaamlIdleTmr OBJECT-TYPE
        SYNTAX INTEGER (0..255)
        MAX-ACCESS read-write
        STATUS current
        DESCRIPTION
        "The number of seconds that must pass without any messages being 
        printed on CAAML, before the CAAML connection is torn down." 
        DEFVAL { 10 }
        ::= { aiCLCSystem 19 }

    aiCLCCaamlRetryTmr OBJECT-TYPE
        SYNTAX INTEGER (0..255)
        MAX-ACCESS read-write
        STATUS current
        DESCRIPTION
        "The number of seconds that must pass after an unsuccessful 
        attempt at bringing the CAAML connection up before a retry will 
        occur." 
        DEFVAL { 10 }
        ::= { aiCLCSystem 20 }

    aiCLCConnInfo OBJECT-TYPE
    	SYNTAX INTEGER {
                   on(1),
                   off(2)
                }
        MAX-ACCESS read-write
        STATUS current
        DESCRIPTION
                "Print connection information on user terminals."
        DEFVAL { 1 }
        ::= { aiCLCSystem 21 }

    aiCLCLongBrkLen OBJECT-TYPE
    	SYNTAX INTEGER (1875..50000)
        MAX-ACCESS read-write
        STATUS current
        DESCRIPTION
                "Long Break length in milliseconds rounded to the nearest
                 1/64th second."
        DEFVAL { 1875 }
        ::= { aiCLCSystem 22 }

    aiCLCDestMenu OBJECT-TYPE
        SYNTAX INTEGER {
                    on(1),
                    off(2)
                }
        MAX-ACCESS read-write
        STATUS current
        DESCRIPTION
                "Print Destination Menu on user terminals."
        DEFVAL { 1 }
        ::= { aiCLCSystem 23 }

    aiCLCDownSpd OBJECT-TYPE
    	SYNTAX INTEGER {
                   on(1),
                   off(2)
                }
        MAX-ACCESS read-write
        STATUS current
        DESCRIPTION
                "Allow ports of different speeds to be connected."
        DEFVAL { 1 }
        ::= { aiCLCSystem 24 }

    aiCLCFaultSwitch OBJECT-TYPE
    	SYNTAX INTEGER {
                   on(1),
                   off(2)
                }
        MAX-ACCESS read-write
        STATUS current
        DESCRIPTION
                "In dual CLC systems, a fault on the active CLC will cause
                 automatic switchover from the faulted CLC to the backup
                 CLC."
        DEFVAL { 1 }
        ::= { aiCLCSystem 25 }

    aiCLCDestMenuFmt OBJECT-TYPE
    	SYNTAX INTEGER {
                   oneCol(1),
                   fourCol(4)
                }
        MAX-ACCESS read-write
        STATUS current
        DESCRIPTION
                "The number of columns used to print the destination menu."
        DEFVAL { 1 }
        ::= { aiCLCSystem 26 }

    aiCLCAutoCLCUpdate OBJECT-TYPE
    	SYNTAX INTEGER {
                   on(1),
                   off(2)
                }
        MAX-ACCESS read-write
        STATUS current
        DESCRIPTION
                "Automatic configuration of the backup CLC when the active
                 CLC's configuration changes."
        DEFVAL { 2 }
        ::= { aiCLCSystem 27 }

    aiCLCAlarmLvl OBJECT-TYPE
        SYNTAX INTEGER (0..9)
        MAX-ACCESS read-write
        STATUS current
        DESCRIPTION
        "Current Alarm Level. A write clears the alarms. A read returns 
        the current alarm level." 
        ::= { aiCLCSystem 28 }

    aiCLCTimeDate OBJECT-TYPE
        SYNTAX DateAndTime
        MAX-ACCESS read-write
        STATUS current
        DESCRIPTION
        "This is the Current Time and Date. 
         The DateAndTime type is a structured OCTET STRING, defined
         in v2-tc.my (SNMPv2 Textual Conventions)."
        ::= { aiCLCSystem 29 }

    aiCLCRstTimeDate OBJECT-TYPE
        SYNTAX DateAndTime
        MAX-ACCESS read-only
        STATUS current
        DESCRIPTION
        "This is the Time and Date of Last Reset.
         The DateAndTime type is a structured OCTET STRING, defined
         in v2-tc.my (SNMPv2 Textual Conventions)."
        ::= { aiCLCSystem 30 }

    aiCLCHoldConn OBJECT-TYPE
        SYNTAX INTEGER (0..65536)
        MAX-ACCESS read-only
        STATUS current
        DESCRIPTION
        "Number of connections placed on hold " 
        DEFVAL { 0 }
        ::= { aiCLCSystem 31 }

    aiCLCNumPorts OBJECT-TYPE
        SYNTAX INTEGER (0..256)
        MAX-ACCESS read-only
        STATUS current
        DESCRIPTION
        "Number of ports detected " 
        ::= { aiCLCSystem 32 }

    aiCLCQueuedPorts OBJECT-TYPE
        SYNTAX INTEGER (0..255)
        MAX-ACCESS read-only
        STATUS current
        DESCRIPTION
        "Number of ports in wait queue " 
        DEFVAL { 0 }
        ::= { aiCLCSystem 33 }

    aiCLCEEPromFaults OBJECT-TYPE
        SYNTAX INTEGER (0..65536)
        MAX-ACCESS read-only
        STATUS current
        DESCRIPTION
        "Number of EEProm failures" 
        DEFVAL { 0 }
        ::= { aiCLCSystem 34 }

    aiCLCFreeEE OBJECT-TYPE
        SYNTAX Integer32 (0..1048576)
        MAX-ACCESS read-only
        STATUS current
        DESCRIPTION
        "Number of free EEProm bytes " 
        ::= { aiCLCSystem 35 }

    aiCLCBuffers OBJECT-TYPE
        SYNTAX INTEGER (0..65536)
        MAX-ACCESS read-only
        STATUS current
        DESCRIPTION
        "Number of buffers created " 
        ::= { aiCLCSystem 36 }

    aiCLCFreeBuffers OBJECT-TYPE
        SYNTAX INTEGER (0..65536)
        MAX-ACCESS read-only
        STATUS current
        DESCRIPTION
        "Number of free buffers " 
        ::= { aiCLCSystem 37 }

    aiCLCBufAllocErr OBJECT-TYPE
        SYNTAX INTEGER (0..65536)
        MAX-ACCESS read-only
        STATUS current
        DESCRIPTION
        "Number of buffer allocation errors " 
        ::= { aiCLCSystem 38 }

    aiCLCBufAlign OBJECT-TYPE
        SYNTAX INTEGER (0..65536)
        MAX-ACCESS read-only
        STATUS current
        DESCRIPTION
        "Number of buffer re-alignments " 
        ::= { aiCLCSystem 39 }

    aiCLCCpuXacts OBJECT-TYPE
        SYNTAX INTEGER (0..65536)
        MAX-ACCESS read-only
        STATUS current
        DESCRIPTION
        "Number of inter-cpu transactions" 
        ::= { aiCLCSystem 40 }

    aiCLCSLCXacts OBJECT-TYPE
        SYNTAX INTEGER (0..65536)
        MAX-ACCESS read-only
        STATUS current
        DESCRIPTION
        "Number of SLC Window transactions " 
        ::= { aiCLCSystem 41 }

    aiCLCConnectionsPlaced OBJECT-TYPE
        SYNTAX INTEGER (0..65536)
        MAX-ACCESS read-only
        STATUS current
        DESCRIPTION
        "Number of connections placed" 
        ::= { aiCLCSystem 42 }

    aiCLCTxTail OBJECT-TYPE
        SYNTAX INTEGER (0..65536)
        MAX-ACCESS read-only
        STATUS current
        DESCRIPTION
        "Number of TXTail misses " 
        ::= { aiCLCSystem 43 }

    aiCLCEECRC OBJECT-TYPE
        SYNTAX INTEGER (0..'ffffffff'h)
        MAX-ACCESS read-only
        STATUS current
        DESCRIPTION
        "Configuration EEPROM CRC." 
        ::= { aiCLCSystem 44 }

    aiCLCVersion OBJECT-TYPE
        SYNTAX DisplayString
        MAX-ACCESS read-only
        STATUS current
        DESCRIPTION
        "Software version, time, and date of currently executing software" 
        ::= { aiCLCSystem 45 }

    aiCLCBackupCLC OBJECT-TYPE
    	SYNTAX INTEGER {
                   present(1),
                   notPresent(2)
                }
        MAX-ACCESS read-only
        STATUS current
        DESCRIPTION
                "Status of the Backup CLC."
        ::= { aiCLCSystem 46 }

    aiCLCCpu OBJECT-TYPE
    	SYNTAX INTEGER {
                   slotA(1),
                   slotB(2)
                }
        MAX-ACCESS read-only
        STATUS current
        DESCRIPTION
                "The location of the active CLC."
        ::= { aiCLCSystem 47 }

    aiCLCCpyConfig OBJECT-TYPE
        SYNTAX INTEGER {
                    none(1),
                    copy(2)
                }
        MAX-ACCESS read-write
        STATUS current
        DESCRIPTION
        "Copy configuration from active CLC to backup CLC.
         A write of copy(2) causes the transfer to begin.
         A read will return copy(2) if a transfer is in progress
         and a none(1) if idle.  A write of none(1) is not 
         permitted and is flagged as an error." 
        ::= { aiCLCSystem 48 }

    aiCLCDLWinVerbose OBJECT-TYPE
    	SYNTAX INTEGER {
                   on(1),
                   off(2)
                }
        MAX-ACCESS read-write
        STATUS current
        DESCRIPTION
                "Verbose report of Window Transactions."
        DEFVAL { 2 }
        ::= { aiCLCSystem 49 }

    aiCLCDLWinIn OBJECT-TYPE
    	SYNTAX INTEGER {
                   on(1),
                   off(2)
                }
        MAX-ACCESS read-write
        STATUS current
        DESCRIPTION
                "Verbose report of incoming Window Transactions."
        DEFVAL { 2 }
        ::= { aiCLCSystem 50 }

    aiCLCDLWinOut OBJECT-TYPE
    	SYNTAX INTEGER {
                   on(1),
                   off(2)
                }
        MAX-ACCESS read-write
        STATUS current
        DESCRIPTION
                "Verbose report of outgoing Window Transactions."
        DEFVAL { 2 }
        ::= { aiCLCSystem 51 }
        
    aiCLCDLWinUni OBJECT-TYPE
    	SYNTAX INTEGER {
                   on(1),
                   off(2)
                }
        MAX-ACCESS read-write
        STATUS current
        DESCRIPTION
                "Verbose report of unified Window Transactions."
        DEFVAL { 2 }
        ::= { aiCLCSystem 52 }

    aiCLCDLMsgAll OBJECT-TYPE
    	SYNTAX INTEGER {
                   on(1),
                   off(2)
                }
        MAX-ACCESS read-write
        STATUS current
        DESCRIPTION
                "Verbose report of log messages."
        DEFVAL { 2 }
        ::= { aiCLCSystem 53 }

    aiCLCDLNoBody OBJECT-TYPE
    	SYNTAX INTEGER {
                   on(1),
                   off(2)
                }
        MAX-ACCESS read-write
        STATUS current
        DESCRIPTION
                "Report log messages headers only."
        DEFVAL { 2 }
        ::= { aiCLCSystem 54 }

    aiCLCDLAlias OBJECT-TYPE
    	SYNTAX INTEGER {
                   on(1),
                   off(2)
                }
        MAX-ACCESS read-write
        STATUS current
        DESCRIPTION
                "Verbose report of alias translations."
        DEFVAL { 2 }
        ::= { aiCLCSystem 55 }

    aiCLCDebugVal OBJECT-TYPE
    	SYNTAX INTEGER (0.. '8f'h)
        MAX-ACCESS read-write
        STATUS current
        DESCRIPTION
                "Value of the debug variable representing all debug combinations."
        ::= { aiCLCSystem 56 }

    aiCLCSwitchRestart OBJECT-TYPE
    	SYNTAX INTEGER {
                   restart(1),
                   restartCfg(2),
                   nextCLC(3),
                   reset(4),
                   resetSLC(5)
                }
        MAX-ACCESS read-write
        STATUS current
        DESCRIPTION
                "A write of this object causes the switch to be
                restarted in the designated mode. A read of this 
                object always returns the value restart(1), which
                has no particular significance."
        ::= { aiCLCSystem 57 }

    aiCLCInitStrings OBJECT-TYPE
        SYNTAX INTEGER {
                    good(1),
                    bad(2)
                }
        MAX-ACCESS read-only
        STATUS current
        DESCRIPTION
        "This object is used to test the condition of the strings on the 
        CLC.  A read of this object causes the test to be performed and
        then reports the outcome." 
        ::= { aiCLCSystem 58 }

    aiCLCCopyFlash OBJECT-TYPE
    	SYNTAX INTEGER {
                none(1),
                apbs(2),
                apas(3),
                asbs(4),
                asap(5),
                bpas(6),
                bpbs(7),
                bsbp(8),
                bsas(9)
        }
        MAX-ACCESS read-write
        STATUS current
        DESCRIPTION
                "Copy Flash from one bank to another. 
                 AP - Active Primary
                 AS - Active Secondary 
                 BP - Backup Primary 
                 BS - Backup Secondary
                 A read returns a value corresponding to the 
                 activity in progress.  A write causes the 
                 requested transfer to begin.  A write of 
                 none(1) is not permitted and is flagged as an
                 error."
        ::= { aiCLCSystem 59 }

    aiCLCCopyFlashToSLC OBJECT-TYPE
    	SYNTAX INTEGER (0..256)
        MAX-ACCESS read-write
        STATUS current
        DESCRIPTION
                "This object is used to begin or obtain the status of
                 the SLC Download process. Writing a SLC base port to this
                 object will cause the SLC at that baseport to search for 
                 new firmware on the active or backup CLC. If a valid SLC 
                 image is located, then the SLC will download that code and 
                 begin to run. A read of this variable will return the value
                 1 if a SLC download is in process, or a 0 if there aren't 
                 downloads in progress."
        ::= { aiCLCSystem 60 }

    aiCLCReadCommunity OBJECT-TYPE
    	SYNTAX DisplayString(0..32)
        MAX-ACCESS read-write
        STATUS current
        DESCRIPTION
                "The read community string for the CLC."
        ::= { aiCLCSystem 61 }

    aiCLCWriteCommunity OBJECT-TYPE
    	SYNTAX DisplayString(1..32)
        MAX-ACCESS read-write
        STATUS current
        DESCRIPTION
                "The write community string for the CLC."
        ::= { aiCLCSystem 62 }

    aiCLCIPAdrs OBJECT-TYPE
    	SYNTAX IpAddress
        MAX-ACCESS read-write
        STATUS current
        DESCRIPTION
                "The IP address for the CLC."
        ::= { aiCLCSystem 63 }

    aiCLCRouterIPAdrs OBJECT-TYPE
    	SYNTAX IpAddress
        MAX-ACCESS read-write
        STATUS current
        DESCRIPTION
                "The router ip address for the CLC."
        ::= { aiCLCSystem 64 }

    aiCLCSubnetIPAdrs OBJECT-TYPE
    	SYNTAX IpAddress
        MAX-ACCESS read-write
        STATUS current
        DESCRIPTION
                "The subnet mask for the CLC. "
        ::= { aiCLCSystem 65 }


    aiCLCTrapTable OBJECT-TYPE
    	SYNTAX SEQUENCE OF AiCLCTrapTableEntry
        MAX-ACCESS not-accessible
        STATUS current
        DESCRIPTION
                "A table of Trap destination IP addresses."
        ::= { aiCLCSystem 66 }

    aiCLCLastTrapMsgText OBJECT-TYPE
        SYNTAX DisplayString (SIZE(0..512))
        MAX-ACCESS read-only
        STATUS current
        DESCRIPTION
                "This is the message text associated with
                 the last generated trap."
        ::= { aiCLCSystem 67 }

    aiCLCLastTrapMsgNum OBJECT-TYPE
    	SYNTAX INTEGER (0..'ffff'h)
        MAX-ACCESS read-only
        STATUS current
        DESCRIPTION
                "This is the message number of the last 
                generated trap log message."
        ::= { aiCLCSystem 68 }

    aiCLCCrashMsgText OBJECT-TYPE
    	SYNTAX DisplayString (SIZE(0..1024))
        MAX-ACCESS read-only
        STATUS current
        DESCRIPTION
                "This is a place holder.  It
                 is required to allow verification of OID 
                 of trap crash message object. A read of this
                 object will return an empty string."
        ::= { aiCLCSystem 69 }

    aiCLCNumEventsSinceLastTrap OBJECT-TYPE
    	SYNTAX INTEGER (0..'ffff'h)
        MAX-ACCESS read-only
        STATUS current
        DESCRIPTION
                "This is the number of times an event that would generate
                 a trap has occurred since the last time that trap was
                 transmitted.  The traps are not transmitted while the
                 aiCLCTrapTimer is running.  This number will accompany
                 the next transmitted trap.  This object is really a place
                 holder.  It is required to allow verification of the OID 
                 of this information in a trap (var-bind).  A read of this
                 object will result in an error from the snmp agent."
        ::= { aiCLCSystem 70 }

    aiCLCTrapTimer OBJECT-TYPE
    	SYNTAX INTEGER (5..'ffff'h)
        MAX-ACCESS read-write
        STATUS current
        DESCRIPTION
                "After a trap is generated, a timer is
                 started.  If the event that generated the 
                 trap occurs while the timer is running, no
                 trap will be generated for the event.  The
                 value of this object is the duration of the
                 timer in SECONDS."
        DEFVAL { 300 }
        ::= { aiCLCSystem 71 }

    aiCLCAsyncTrap OBJECT-TYPE
    	SYNTAX INTEGER {
                enabled(1),
                disabled(2)
        }
        MAX-ACCESS read-write
        STATUS current
        DESCRIPTION
                "When this object is enabled, link up/link down traps
                 are sent to managers listed in the trap table. The
                 traps are normally not used and must specifically
                 be enabled by a manager."
        DEFVAL { disabled }
        ::= { aiCLCSystem 72 }

    aiCLCTelnetServerPort OBJECT-TYPE
    	SYNTAX INTEGER (1..65535)
        MAX-ACCESS read-write
        STATUS current
        DESCRIPTION
                "The tcp port number used by the telnet server may be
                 configured using the aiCLCTelnetServerPort object. By
                 default this object uses the well known port number 23."
        DEFVAL { 23 }
        ::= { aiCLCSystem 73 }

    aiCLCColdStartTrapDelay OBJECT-TYPE
    	SYNTAX INTEGER (0..600)
        MAX-ACCESS read-write
        STATUS current
        DESCRIPTION
                "The sending of the cold start trap may be delayed
                 to allow system startup and link startup to occur.
                 This will typically be done on systems using IP over
                 X.25 links. This value is specified in seconds."
        DEFVAL { 0 }
        ::= { aiCLCSystem 74 }

    aiCLCFtpCtrlPort OBJECT-TYPE
    	SYNTAX INTEGER (1..65535)
        MAX-ACCESS read-write
        STATUS current
        DESCRIPTION
                "The FTP Server control port number. New values
                 for this object take affect after a reset. The
                 FTP Server data port is automatically selected 
                 to be one less than the control port."
        DEFVAL { 21 }
        ::= { aiCLCSystem 75 }

    aiCLCBackupCLCHealth OBJECT-TYPE
    	SYNTAX INTEGER {
                   present(1),
                   notPresent(2),
		   presentFaulted(3)
                }
        MAX-ACCESS read-only
        STATUS current
        DESCRIPTION
                "Health status of the Backup CLC."
        ::= { aiCLCSystem 76 }

    aiCLCBanner OBJECT-TYPE
    	SYNTAX DisplayString(0..1170)
        MAX-ACCESS read-write
        STATUS current
        DESCRIPTION
                "The banner for the CLC.  There is a maximum 15 
                 lines with 76 characters allowed per line."
        ::= { aiCLCSystem 77 }

    aiCLCTimeZone OBJECT-TYPE
        SYNTAX INTEGER (-720..720)
        MAX-ACCESS read-write
        STATUS current
        DESCRIPTION
                "The time zone offset for the CLC in minutes."
        ::= { aiCLCSystem 78 }

    aiCLCDaylightSavings OBJECT-TYPE
        SYNTAX INTEGER {
                   on(1),
                   off(2)
                }
        MAX-ACCESS read-write
        STATUS current
        DESCRIPTION
                "Daylight Savings"
        DEFVAL { 1 }
        ::= { aiCLCSystem 79 }

    aiCLCSNTP OBJECT-TYPE
        SYNTAX INTEGER {
                   on(1),
                   off(2)
                }
        MAX-ACCESS read-write
        STATUS current
        DESCRIPTION
                "SNTP"
        DEFVAL { 1 }
        ::= { aiCLCSystem 80 }

    aiCLCSNTPPrimaryServer OBJECT-TYPE
    	SYNTAX IpAddress
        MAX-ACCESS read-write
        STATUS current
        DESCRIPTION
                "The IP address for the Primary SNTP Server."
        ::= { aiCLCSystem 81 }

    aiCLCSNTPSecondaryServer OBJECT-TYPE
    	SYNTAX IpAddress
        MAX-ACCESS read-write
        STATUS current
        DESCRIPTION
                "The IP address for the Secondary SNTP Server."
        ::= { aiCLCSystem 82 }

    aiCLCSNTPPollInterval OBJECT-TYPE
        SYNTAX INTEGER (1..65535)
        MAX-ACCESS read-write
        STATUS current
        DESCRIPTION
                "SNTP Poll Interval" 
        DEFVAL { 0 }
        ::= { aiCLCSystem 83 }

    aiCLCRadiusEnabled OBJECT-TYPE
        SYNTAX INTEGER {
                   disabled(0),
                   enabled(1),
		   localFallback(2)
                }
        MAX-ACCESS read-write
        STATUS current
        DESCRIPTION
		"RADIUS enabled/disabled state."

        DEFVAL { 0 }
        ::= { aiCLCSystem 84 }

    aiCLCRadiusAddr1 OBJECT-TYPE
    	SYNTAX IpAddress
        MAX-ACCESS read-write
        STATUS current
        DESCRIPTION
                "The IP address for the Primary RADIUS Server."
        ::= { aiCLCSystem 85 }

    aiCLCRadiusPort1 OBJECT-TYPE
    	SYNTAX INTEGER (1..65535)
        MAX-ACCESS read-write
        STATUS current
        DESCRIPTION
                 "The port number associated with the Primary
                  RADIUS Server."
        DEFVAL { 1812 }
        ::= { aiCLCSystem 86 }

    aiCLCRadiusSecret1 OBJECT-TYPE
    	SYNTAX DisplayString(SIZE(0..24))
        MAX-ACCESS read-write
        STATUS current
        DESCRIPTION
		"The Secret for the Primary RADIUS Server."
	DEFVAL { "applied" }
        ::= { aiCLCSystem 87 }

    aiCLCRadiusAddr2 OBJECT-TYPE
    	SYNTAX IpAddress
        MAX-ACCESS read-write
        STATUS current
        DESCRIPTION
                "The IP address for the Secondary RADIUS Server."
        ::= { aiCLCSystem 88 }

    aiCLCRadiusPort2 OBJECT-TYPE
    	SYNTAX INTEGER (1..65535)
        MAX-ACCESS read-write
        STATUS current
        DESCRIPTION
                 "The port number associated with the Secondary
                  RADIUS Server."
        DEFVAL { 1812 }
        ::= { aiCLCSystem 89 }

    aiCLCRadiusSecret2 OBJECT-TYPE
    	SYNTAX DisplayString(SIZE(0..24))
        MAX-ACCESS read-write
        STATUS current
        DESCRIPTION
		"The Secret for the Secondary RADIUS Server."
	DEFVAL { "applied" }
        ::= { aiCLCSystem 90 }

    aiCLCTrapInterval OBJECT-TYPE
    	SYNTAX INTEGER (0..65535)
        MAX-ACCESS read-write
        STATUS current
        DESCRIPTION
                "The interval of the faulted primary CLC trap. If the primary
                 CLC was faulted and the interval was set between 1 and 65535 
                 minutes, the backup CLC will repeatedly send the faulted primary
                 CLC trap. To disable this trap, set the interval to 0. If reset 
                 the interval to 0 after the primary CLC has been faulted, the 
                 backup CLC will stop sending the trap. New value for this object 
                 will take affect without rebooting the switch. This object has no  
                 effect on other traps."
        DEFVAL { 0 }
        ::= { aiCLCSystem 91 }

    aiCLCTacacsEnabled OBJECT-TYPE
        SYNTAX INTEGER {
                   disabled(0),
                   enabled(1),
		   localFallback(2)
                }
        MAX-ACCESS read-write
        STATUS current
        DESCRIPTION
		"TACACS+ enabled/disabled state."

        DEFVAL { 0 }
        ::= { aiCLCSystem 92 }

    aiCLCTacacsAddr1 OBJECT-TYPE
    	SYNTAX IpAddress
        MAX-ACCESS read-write
        STATUS current
        DESCRIPTION
                "The IP address for the Primary TACACS Server."
        ::= { aiCLCSystem 93 }

    aiCLCTacacsPort1 OBJECT-TYPE
    	SYNTAX INTEGER (1..65535)
        MAX-ACCESS read-write
        STATUS current
        DESCRIPTION
                 "The port number associated with the Primary
                  TACACS Server."
        DEFVAL { 49 }
        ::= { aiCLCSystem 94 }

    aiCLCTacacsSecret1 OBJECT-TYPE
    	SYNTAX DisplayString(SIZE(0..24))
        MAX-ACCESS read-write
        STATUS current
        DESCRIPTION
		"The Secret for the Primary TACACS Server."
	DEFVAL { "applied" }
        ::= { aiCLCSystem 95 }

    aiCLCTacacsAddr2 OBJECT-TYPE
    	SYNTAX IpAddress
        MAX-ACCESS read-write
        STATUS current
        DESCRIPTION
                "The IP address for the Secondary TACACS Server."
        ::= { aiCLCSystem 96 }

    aiCLCTacacsPort2 OBJECT-TYPE
    	SYNTAX INTEGER (1..65535)
        MAX-ACCESS read-write
        STATUS current
        DESCRIPTION
                 "The port number associated with the Secondary
                  TACACS Server."
        DEFVAL { 49 }
        ::= { aiCLCSystem 97 }

    aiCLCTacacsSecret2 OBJECT-TYPE
    	SYNTAX DisplayString(SIZE(0..24))
        MAX-ACCESS read-write
        STATUS current
        DESCRIPTION
		"The Secret for the Secondary TACACS Server."
	DEFVAL { "applied" }
        ::= { aiCLCSystem 98 }

-- the CLC Trap Table
-- The CLC Trap Table contains IP addresses for destinations to which 
-- traps are to be sent. 

    aiCLCTrapTableEntry OBJECT-TYPE
    	SYNTAX AiCLCTrapTableEntry
        MAX-ACCESS not-accessible
        STATUS current
        DESCRIPTION
                "Information about a particular Trap destination."
        INDEX {	aiCLCTrapIPAdrs }
        ::= { aiCLCTrapTable 1 }

    AiCLCTrapTableEntry ::=
    	SEQUENCE {
            aiCLCTrapIPAdrs	IpAddress,
            aiCLCTrapRowStatus INTEGER
        }
    aiCLCTrapIPAdrs OBJECT-TYPE
        SYNTAX IpAddress
        MAX-ACCESS read-create
        STATUS current
        DESCRIPTION
                "The IP Address of the destination to which SNMP Traps will be sent."
        ::= { aiCLCTrapTableEntry 1 }

    aiCLCTrapRowStatus OBJECT-TYPE
    	SYNTAX INTEGER {
                   active(1),
                   notInService(2),
                   notReady(3),
                   createAndGo(4),
                   createAndWait(5),
                   destroy(6)
                }
                          MAX-ACCESS read-create
        STATUS current
        DESCRIPTION
                "The aiCLC Trap Table entry row status."
        ::= { aiCLCTrapTableEntry 2 }


-- Card List Table
-- The Card List Table contains the list of cards and card attributes for 
-- line cards in an AISwitch. There will be one entry in the table for 
-- each card that is present in the switch.

    aiCLCCardTable OBJECT-TYPE
    	SYNTAX SEQUENCE OF AiCLCCardTableEntry
        MAX-ACCESS not-accessible
        STATUS current
        DESCRIPTION
                "A table of line cards contained in an AISwitch."
        ::= { aiCLC 2 }

    aiCLCCardTableEntry OBJECT-TYPE
    	SYNTAX AiCLCCardTableEntry
        MAX-ACCESS not-accessible
        STATUS current
        DESCRIPTION
                "Information about a particular line card."
        INDEX { aiCLCCTIndex }

        ::= { aiCLCCardTable 1 }

    AiCLCCardTableEntry ::=
    	SEQUENCE {
            aiCLCCTIndex		INTEGER,
            aiCLCCTAdminStatus		INTEGER,
            aiCLCCTBasePort		INTEGER,
            aiCLCCTHighPort		INTEGER,
            aiCLCCTRdCommStr		DisplayString,
            aiCLCCTWrCommStr		DisplayString,
            aiCLCCTCardSnmpState	INTEGER,
            aiCLCCTCardType		INTEGER,
            aiCLCCTSlotExp		INTEGER,
            aiCLCCTIPAdrs 		IpAddress,
            aiCLCCTRtrIPAdrs		IpAddress,
            aiCLCCTSubnetMask		IpAddress,
	    aiCLCCTAutoIdIndex		INTEGER,
            aiCLCCTSysOID		OBJECT IDENTIFIER,
	    aiCLCCTRealCardType         INTEGER,
	    aiCLCCTIPRange		INTEGER,
	    aiCLCCTTelnetPort           INTEGER,
            aiCLCCTCardReset            INTEGER,
            aiCLCCTLastSequenceNumber   Counter32,
            aiCLCCTRtr2IPAdrs           IpAddress
        }

    aiCLCCTIndex OBJECT-TYPE
    	SYNTAX INTEGER (1..64)
        MAX-ACCESS read-write
        STATUS current
        DESCRIPTION
                "The card table index."
        ::= { aiCLCCardTableEntry 1 }

    aiCLCCTAdminStatus OBJECT-TYPE
    	SYNTAX INTEGER {
                up(1),
                down(2)
        }
        MAX-ACCESS read-write
        STATUS current
        DESCRIPTION
                "This represents the state of the card and may be used to change
                 the state of the card. For DUMB cards if one port on the card
                 is up, then the entire card is considered to be up.
                "
        ::= { aiCLCCardTableEntry 2 }
    
    aiCLCCTBasePort OBJECT-TYPE
    	SYNTAX INTEGER (0..255)
        MAX-ACCESS read-write
        STATUS current
        DESCRIPTION
                "The base port number for the line card."
        ::= { aiCLCCardTableEntry 3 }

    aiCLCCTHighPort OBJECT-TYPE
     	SYNTAX INTEGER (0..255)
        MAX-ACCESS read-only
        STATUS current
        DESCRIPTION
                "The highest port number accessible by the line card."
        ::= { aiCLCCardTableEntry 4 }

    aiCLCCTRdCommStr OBJECT-TYPE
    	SYNTAX DisplayString
        MAX-ACCESS read-write
        STATUS current
        DESCRIPTION
                "The SNMP read community string by which this card is known."
        ::= { aiCLCCardTableEntry 5 }

    aiCLCCTWrCommStr OBJECT-TYPE
    	SYNTAX DisplayString
        MAX-ACCESS read-write
        STATUS current
        DESCRIPTION
                "The SNMP write community string by which this card is known."
        ::= { aiCLCCardTableEntry 6 }

    aiCLCCTCardSnmpState OBJECT-TYPE
    	SYNTAX INTEGER {
                nosnmp(1),
                snmpProxy(2),
                snmpDirect(3)
        }
    	MAX-ACCESS read-only
    	STATUS current
    	DESCRIPTION
                "This field describes the capabilities of the card. A card may not
                 be snmp capable and will have the value nosnmp(1). A card may be
                 snmp capable but isn't present on the IP network. This card is may
                 proxied for and will have the type snmpProxy(2). The last type of 
                 snmp capability is where are card is present on the IP network and 
                 can be managed directly. This card will have a type of snmpDirect(3).
                "
        ::= { aiCLCCardTableEntry 7 }

    aiCLCCTCardType OBJECT-TYPE
    	SYNTAX INTEGER {
                   asynch(1),
                   aslc(2),
                   ethernet(3),
                   x25(4),
                   asp(5),
                   islc(6),
                   ai2524(7),
                   ai294(8),
    	           ai196im(9),
        	   x25m(10),
	           islc1(11),
                   ai296(12), 
	           ai285(13),
       		   ai232(14),   	-- not supported in 1.30
       		   ai196ILEG(15),	-- not supported in 1.30
		   aimod(16), 
	           aiflx(17),
                   empty(18),
		   ai120(19),	        -- in 1.60
		   aie1(20),	        -- in 1.70
		   aitc(21),	        -- in 1.80
     	           aifocus(22),         -- in 2.00
		   wanE1(23),
		   wanT1(24)
         }
        MAX-ACCESS read-write
        STATUS current
        DESCRIPTION
                "The line card type."
        DEFVAL { 1 }
        ::= { aiCLCCardTableEntry 8 }

    aiCLCCTSlotExp OBJECT-TYPE
    	SYNTAX INTEGER (0..7)
        MAX-ACCESS read-write
        STATUS current
        DESCRIPTION
                "The number of slots the line card is to logically occupy."
        DEFVAL { 0 }
        ::= { aiCLCCardTableEntry 9 }

      aiCLCCTIPAdrs OBJECT-TYPE
      	SYNTAX IpAddress
  	MAX-ACCESS read-write
  	STATUS current
  	DESCRIPTION
  		"The IP address associated with the line card."
  	::= { aiCLCCardTableEntry 10 }

    aiCLCCTRtrIPAdrs OBJECT-TYPE
    	SYNTAX IpAddress
        MAX-ACCESS read-write
        STATUS current
        DESCRIPTION
                "The router ip address for this line card."
        ::= { aiCLCCardTableEntry 11 }

    aiCLCCTSubnetMask OBJECT-TYPE
    	SYNTAX IpAddress
        MAX-ACCESS read-write
        STATUS current
        DESCRIPTION
                "The subnet mask for this line card. "
        ::= { aiCLCCardTableEntry 12 }

    aiCLCCTAutoIdIndex OBJECT-TYPE
    	SYNTAX INTEGER (0..128)
        MAX-ACCESS read-only
        STATUS current
        DESCRIPTION
                "The index into the Auto Id table associated 
                 with this line card."
        ::= { aiCLCCardTableEntry 13 }

    aiCLCCTSysOID OBJECT-TYPE
    	SYNTAX OBJECT IDENTIFIER
        MAX-ACCESS read-only
        STATUS current
        DESCRIPTION
                "The SNMP System OID associated with this line card."
        ::= { aiCLCCardTableEntry 14 }

    aiCLCCTRealCardType OBJECT-TYPE
    	SYNTAX INTEGER {
                   asynch(1),
                   aslc(2),
                   ethernet(3),
                   x25(4),
                   asp(5),
                   islc(6),
                   ai2524(7),
                   ai294(8),
      	           ai196im(9),
        	   x25m(10),
       		   islc1(11),
      	           ai296(12),
        	   ai285(13),
       		   ai232(14),   	-- not supported in 1.30
       		   ai196ILEG(15),	-- not supported in 1.30
		   aimod(16), 
	           aiflx(17),
                   empty(18),
		   ai120(19),	        -- in 1.60
		   aie1(20),	        -- in 1.70
		   aitc(21),	        -- in 1.80
		   aifocus(22),         -- in 2.00
 		   wanE1(23),
		   wanT1(24)
        }
        MAX-ACCESS read-only
        STATUS current
        DESCRIPTION
                "The real line card type."
        DEFVAL { 1 }
        ::= { aiCLCCardTableEntry 15 }

    aiCLCCTIPRange OBJECT-TYPE
    	SYNTAX INTEGER (1..255)
        MAX-ACCESS read-write
        STATUS current
        DESCRIPTION
                "The IP address range of this line card."
        DEFVAL { 0 }
        ::= { aiCLCCardTableEntry 16 }

    aiCLCCTTelnetPort OBJECT-TYPE
    	SYNTAX INTEGER (1..65534)
        MAX-ACCESS read-write
        STATUS current
        DESCRIPTION
                "The telnet port of this line card."
        DEFVAL { 0 }
        ::= { aiCLCCardTableEntry 17 }

    aiCLCCTCardReset OBJECT-TYPE
        SYNTAX INTEGER {
                   on(1),
                   off(2),
                   na(3)
                }
        MAX-ACCESS read-write
        STATUS current
        DESCRIPTION
                "Card is included when * is used with STPSLC, DISABL, or ENABL."
        ::= { aiCLCCardTableEntry 18 }

    aiCLCCTLastSequenceNumber OBJECT-TYPE
        SYNTAX          Counter32
        MAX-ACCESS      read-only
        STATUS          current
        DESCRIPTION
            "This is the sequence number of the last trap sent by 
             this card.  The sequence number starts at zero 
             following a hardware reset or power-up.  When the 
             sequence number reaches 0xffffffff, it rolls over to 0 
             on the next trap."
        DEFVAL { 0 }
        ::= { aiCLCCardTableEntry 19 }

    aiCLCCTRtr2IPAdrs OBJECT-TYPE
    	SYNTAX IpAddress
        MAX-ACCESS read-write
        STATUS current
        DESCRIPTION
                "The secondary router ip address for this line card."
        ::= { aiCLCCardTableEntry 20 }

-- Port Table
-- The Port Table contains information specifically related to ports 
-- and their attributes including some status information. There will 
-- be one entry in the table for each configured port.

    aiCLCPortTable OBJECT-TYPE
    	SYNTAX SEQUENCE OF AiCLCPortTableEntry
        MAX-ACCESS not-accessible
        STATUS current
        DESCRIPTION
                "A table of port information."
        ::= { aiCLC 3 }

    aiCLCPortTableEntry OBJECT-TYPE
    	SYNTAX AiCLCPortTableEntry
        MAX-ACCESS not-accessible
        STATUS current
        DESCRIPTION
                "Information unique to a particular port."
        INDEX { aiCLCPortNumber }
        ::= { aiCLCPortTable 1 }

    AiCLCPortTableEntry ::=
    	SEQUENCE {
            aiCLCPortNumber		INTEGER,
            aiCLCPortType  		INTEGER,
            aiCLCPortDedicated		INTEGER,
            aiCLCPortDestName		DisplayString,
            aiCLCPortEcho 		INTEGER,
            aiCLCPortDestMenu		INTEGER,
            aiCLCPortQueue 		INTEGER,
            aiCLCSLCProtocolCode	INTEGER,
            aiCLCPortState		INTEGER,
            aiCLCPortStatus		INTEGER,
            aiCLCPortAlm		INTEGER,
            aiCLCPortDesc		DisplayString,
            aiCLCPortReset              INTEGER
        }

    aiCLCPortNumber OBJECT-TYPE
    	SYNTAX INTEGER (0..255)
        MAX-ACCESS read-only
        STATUS current
        DESCRIPTION
                "The AISwitch Port Number associated with the entry."
        ::= { aiCLCPortTableEntry 1 }

    aiCLCPortType OBJECT-TYPE
    	SYNTAX INTEGER {
                   user(1),
                   destination(2),
                   actConn(3),
                   dedicated(4)
                }
        MAX-ACCESS read-write
        STATUS current
        DESCRIPTION
                "This is used to configure how the port is being used."
        DEFVAL { 1 }
        ::= { aiCLCPortTableEntry 2 }

    aiCLCPortDedicated OBJECT-TYPE
    	SYNTAX INTEGER (0..255)
        MAX-ACCESS read-write
        STATUS current
        DESCRIPTION
                "The port number to which this port is dedicated when
                 the type is 'dedicated'."
        ::= { aiCLCPortTableEntry 3 }

    aiCLCPortDestName OBJECT-TYPE
    	SYNTAX DisplayString (SIZE(0..8))
        MAX-ACCESS read-write
        STATUS current	     
        DESCRIPTION
                "The destination to which this port is assigned."
        ::= { aiCLCPortTableEntry 4 }

    aiCLCPortEcho OBJECT-TYPE
    	SYNTAX INTEGER {
                   on(1),
                   off(2)
                }
        MAX-ACCESS read-write
        STATUS current
        DESCRIPTION
                "This determines whether echoing is on when the port
                 is connected to the AISwitch."
        DEFVAL { 1 }
        ::= { aiCLCPortTableEntry 5 }

    aiCLCPortDestMenu OBJECT-TYPE
    	SYNTAX INTEGER {
                   on(1),
                   off(2)
                }
        MAX-ACCESS read-write
        STATUS current
        DESCRIPTION
                "This determines whether the destination menu is 
                 displayed when the port type is 'user'."
        DEFVAL { 1 }
        ::= { aiCLCPortTableEntry 6 }

    aiCLCPortQueue OBJECT-TYPE
    	SYNTAX INTEGER {
                   on(1),
                   off(2)
                }
        MAX-ACCESS read-write
        STATUS current
        DESCRIPTION
                "This determines whether the port is allowed to be
                 put on hold when the destination port is busy."
        DEFVAL { 2 }
        ::= { aiCLCPortTableEntry 7 }

    aiCLCSLCProtocolCode OBJECT-TYPE
    	SYNTAX INTEGER (0..255)
        MAX-ACCESS read-write
        STATUS current
        DESCRIPTION
                "This is the slc protocol processing code."
        ::= { aiCLCPortTableEntry 8 }

    aiCLCPortState OBJECT-TYPE
    	SYNTAX INTEGER {
                   enabled(1),
                   disabled(2)
                }
        MAX-ACCESS read-only
        STATUS current
        DESCRIPTION
                "This is used to determine whether the port is
                 enabled or disabled."
        ::= { aiCLCPortTableEntry 9 }

    aiCLCPortStatus OBJECT-TYPE
    	SYNTAX INTEGER {
                   idle(1),
                   selcos(2),
                   pswd(3),
                   uname(4),
                   dna(5),
                   tcp(6),
                   queue(7),
                   holdq(8),
                   waitq(9),
                   ai(10),
                   conn(11),
                   preconn(12),
                   predisc(13),
                   hold(14),
                   netconn(15),
                   file(16),
                   inact(17),
                   swdwn(18),
                   telnetClient(19),
                   unknown(20)
                }
        MAX-ACCESS read-only
        STATUS current
        DESCRIPTION
                "This value is the port status which include the following
                 values; idle(1), selecting class of service selcos(2),
                 entering password pswd(3), entering username(4),
                 entering destination network address dna(5), 
                 entering a TCP address tcp(6), answering
                 'wish to queue' queue(7), answering 'wish to hold' holdq(8),
                 connected to switch ai(9), connected conn(10), in the 
                 process of connecting preconn(11), in the process of 
                 disconnecting predisc(12), hold(13), network connect
                 pending netconn(14), performing a file transfer file(15),
                 inactive inact(16), slc is receiving software download swdwn(17),
                 port is using a telnet client telnetClient(18), unknown(20)."
        ::= { aiCLCPortTableEntry 10 }

    aiCLCPortAlm OBJECT-TYPE
    	SYNTAX INTEGER (0..9)
        MAX-ACCESS read-only
        STATUS current
        DESCRIPTION
                "The current alarm value for the port."
        ::= { aiCLCPortTableEntry 11 }

    aiCLCPortDesc OBJECT-TYPE
    	SYNTAX DisplayString (SIZE(0..29))
        MAX-ACCESS read-write
        STATUS current
        DESCRIPTION
                "This is used to describe the port in textual form."
        ::= { aiCLCPortTableEntry 12 }

    aiCLCPortReset OBJECT-TYPE
        SYNTAX INTEGER {
                   on(1),
                   off(2)
                }
        MAX-ACCESS read-write
        STATUS current
        DESCRIPTION
                "Port is included when * is used with DISABL or ENABL."
        ::= { aiCLCPortTableEntry 13 }


-- Alias Table
-- The Alias Table is contains information for call aliases and their 
-- attributes. There will be one entry in the table for each configured
-- alias.

    aiCLCAliasTable OBJECT-TYPE
    	SYNTAX SEQUENCE OF AiCLCAliasTableEntry
        MAX-ACCESS not-accessible
        STATUS current 
        DESCRIPTION
                "A table of call alias information."
        ::= { aiCLC 4 }

    aiCLCAliasTableEntry OBJECT-TYPE
    	SYNTAX AiCLCAliasTableEntry
        MAX-ACCESS not-accessible
        STATUS current
        DESCRIPTION
                "Information unique to a particular alias."
        INDEX { IMPLIED aiCLCAliasIndex }  
        ::= { aiCLCAliasTable 1 }

    AiCLCAliasTableEntry ::= 
        SEQUENCE {
            aiCLCAliasIndex		DisplayString, 
            aiCLCAliasRowStatus		INTEGER,
            aiCLCXlatType		INTEGER,
            aiCLCAliasDestName		DisplayString, 
            aiCLCCalledAdrs		DisplayString, 
            aiCLCAliasDestMenu		INTEGER,
            aiCLCLinkNum		DisplayString, 
            aiCLCCallerAdrs		DisplayString, 
            aiCLCCallData		DisplayString, 
            aiCLCApplicString		DisplayString, 
            aiCLCCalledProtoStr		DisplayString, 
            aiCLCCallerProtoStr		DisplayString,
            aiCLCAlternRoute		DisplayString,
	    aiCLCAliasPosition		DisplayString 
    	}

    aiCLCAliasIndex OBJECT-TYPE
    	SYNTAX DisplayString (SIZE(1..200))
        MAX-ACCESS read-create
        STATUS current
        DESCRIPTION
                "The alias name in the form of a DisplayString. This
                 is the key field for the Alias Table."
        ::= { aiCLCAliasTableEntry 1 }

    aiCLCAliasRowStatus OBJECT-TYPE
    	SYNTAX INTEGER {
                   active(1),
                   notInService(2),
                   notReady(3),
                   createAndGo(4),
                   createAndWait(5),
                   destroy(6)
                }
        MAX-ACCESS read-create
        STATUS current
        DESCRIPTION
                "The Alias Table Entry row status."
        ::= { aiCLCAliasTableEntry 2 }

    aiCLCXlatType OBJECT-TYPE
    	SYNTAX INTEGER {
                   simple(1),
                   muxconn(2),
                   muxxlat(3),
                   slcroute(4)
                }
        MAX-ACCESS read-write
        STATUS current
        DESCRIPTION
                "The type of alias translation to be performed."
        DEFVAL { 1 }
        ::= { aiCLCAliasTableEntry 3 }

    aiCLCAliasDestName OBJECT-TYPE
    	SYNTAX DisplayString
        MAX-ACCESS read-write
        STATUS current
        DESCRIPTION
                "The destination to be used for the alias."
        ::= { aiCLCAliasTableEntry 4 }

    aiCLCCalledAdrs OBJECT-TYPE
    	SYNTAX DisplayString
        MAX-ACCESS read-write
        STATUS current
        DESCRIPTION
                "The called address used in the macro."
        ::= { aiCLCAliasTableEntry 5 }

    aiCLCAliasDestMenu OBJECT-TYPE
    	SYNTAX INTEGER {
                   on(1),
                   off(2)	    
                }
        MAX-ACCESS read-write
        STATUS current
        DESCRIPTION
                "This determines whether the alias appears on the
                 destination menu."
        DEFVAL { 1 }
        ::= { aiCLCAliasTableEntry 6 }

    aiCLCLinkNum OBJECT-TYPE
    	SYNTAX DisplayString
        MAX-ACCESS read-write
        STATUS current
        DESCRIPTION
                "The link number or alias macro used for the link
                 number."
        ::= { aiCLCAliasTableEntry 7 }

    aiCLCCallerAdrs OBJECT-TYPE
    	SYNTAX DisplayString
        MAX-ACCESS read-write
        STATUS current
        DESCRIPTION
                "The caller address used in the macro."
        ::= { aiCLCAliasTableEntry 8 }

    aiCLCCallData OBJECT-TYPE
    	SYNTAX DisplayString
        MAX-ACCESS read-write
        STATUS current
        DESCRIPTION
                "The call data which may be a destination or
                 an alias macro."
        ::= { aiCLCAliasTableEntry 9 }

    aiCLCApplicString OBJECT-TYPE
    	SYNTAX DisplayString
        MAX-ACCESS read-write
        STATUS current
        DESCRIPTION
                "The application string which may be a string or
                 an alias macro."
        ::= { aiCLCAliasTableEntry 10 }

    aiCLCCalledProtoStr OBJECT-TYPE
    	SYNTAX DisplayString
        MAX-ACCESS read-write
        STATUS current
        DESCRIPTION
                "The string that may specify the called protocol
                 for a call using the alias macro."
        ::= { aiCLCAliasTableEntry 11 }

    aiCLCCallerProtoStr OBJECT-TYPE
    	SYNTAX DisplayString
        MAX-ACCESS read-write
        STATUS current
        DESCRIPTION
                "The string that may specify the calling protocol
                 for a call using the alias macro."
        ::= { aiCLCAliasTableEntry 12 }

    aiCLCAlternRoute OBJECT-TYPE
    	SYNTAX DisplayString
        MAX-ACCESS read-write
        STATUS current
        DESCRIPTION
                "The string may specify a destination or an alias
                 macro that is used as an alternate route."
        ::= { aiCLCAliasTableEntry 13 }

    aiCLCAliasPosition OBJECT-TYPE
    	SYNTAX DisplayString (SIZE(1..5))
        MAX-ACCESS read-write
        STATUS current
        DESCRIPTION
                "The position of the alias in the alias list.
		 When 'set' a new or an existing alias, this value can 
		 be used as a flag to request a saving to the beginning (0)
		 or to the end (99999) of the alias list. 
		 As default, the CLC always saves a new alias to the end and
		 a modified alias to its old position."
		  
        DEFVAL { 1 }
        ::= { aiCLCAliasTableEntry 14 }


-- Destination Table
-- The Destination Table contains information pertaining to destinations
-- and their attributes. There will be one entry in the table for each
-- configured destination.

    aiCLCDestTable OBJECT-TYPE
    	SYNTAX SEQUENCE OF AiCLCDestTableEntry
        MAX-ACCESS not-accessible
        STATUS current
        DESCRIPTION
                "This table contains information pertaining to
                 destinations and their attributes."
        ::= { aiCLC 5 }

    aiCLCDestTableEntry OBJECT-TYPE
    	SYNTAX AiCLCDestTableEntry
        MAX-ACCESS not-accessible
        STATUS current
        DESCRIPTION
                "This information pertains to one entry in the
                 destination table."
        INDEX { IMPLIED aiCLCDestName  }
        ::= { aiCLCDestTable 1 }

    AiCLCDestTableEntry ::=
    	SEQUENCE {
            aiCLCDestName	DisplayString, 
            aiCLCDestRowStatus	INTEGER,
            aiCLCDestCallInit	INTEGER,     
            aiCLCDestDisc	INTEGER, 
            aiCLCDestDispMenu	INTEGER, 
            aiCLCDestBaud	INTEGER,      
            aiCLCDestIsSwitch	INTEGER, 
            aiCLCDestTmrType	INTEGER, 
            aiCLCDestTmrVal	INTEGER, 
            aiCLCDestTmrDelay	INTEGER, 
            aiCLCDestPswd	DisplayString, 
            aiCLCDestQPswd	DisplayString,     
            aiCLCDestMenuMsg	DisplayString, 
            aiCLCDestConnMsg	DisplayString, 
            aiCLCDestDiscMsg	DisplayString, 
            aiCLCDestState	INTEGER, 
            aiCLCDestNumPorts	INTEGER, 
            aiCLCDestNumUsed	INTEGER,  
            aiCLCDestNumFree	INTEGER, 
            aiCLCDestQHigh	INTEGER, 
            aiCLCDestPortList	DisplayString,
            aiCLCDestWaitForPort	INTEGER
        } 

    aiCLCDestName OBJECT-TYPE
    	SYNTAX DisplayString (SIZE(1..8))
        MAX-ACCESS read-create
        STATUS current
        DESCRIPTION
                "The name of the destination in the form of an OCTET STRING."
        ::= { aiCLCDestTableEntry 1 }

    aiCLCDestRowStatus OBJECT-TYPE
    	SYNTAX INTEGER {
                   active(1),
                   notInService(2),
                   notReady(3),
                   createAndGo(4),
                   createAndWait(5),
                   destroy(6)
                }
        MAX-ACCESS read-create
        STATUS current
        DESCRIPTION
                "The key field for the Destination table entry."
        ::= { aiCLCDestTableEntry 2 }

    aiCLCDestCallInit OBJECT-TYPE
    	SYNTAX INTEGER {
                   on(1),
                   off(2)
                }
        MAX-ACCESS read-write
        STATUS current
        DESCRIPTION
                "This is used to turn on or turn off call initiation
                 on ports assigned to this destination."
        DEFVAL { 2 }
        ::= { aiCLCDestTableEntry 3}

    aiCLCDestDisc OBJECT-TYPE
    	SYNTAX INTEGER {
                   on(1),
                   off(2)
                }
        MAX-ACCESS read-write
        STATUS current
        DESCRIPTION
                "This is used to turn on or turn off the user's 
                 disconnect keys when connected to this destination."
        DEFVAL { 2 }
        ::= { aiCLCDestTableEntry 4 }

    aiCLCDestDispMenu OBJECT-TYPE
    	SYNTAX INTEGER {
                   on(1),
                   off(2)
                }
        MAX-ACCESS read-write
        STATUS current
        DESCRIPTION
                "This is used to turn on or turn off the display
                 of the destination name on the destination menu."
        DEFVAL { 1 }
        ::= { aiCLCDestTableEntry 5 }
            
    aiCLCDestBaud OBJECT-TYPE
    	SYNTAX INTEGER {
                   on(1),
                   off(2)
                }
        MAX-ACCESS read-write
        STATUS current
        DESCRIPTION
                "This is used to turn on or turn off whether the
                 baud rate is checked before connecting to the 
                 destination."
        DEFVAL { 1 }
        ::= { aiCLCDestTableEntry 6 }

    aiCLCDestIsSwitch OBJECT-TYPE
    	SYNTAX INTEGER {
                   yes(1),
                   no(2)
                }
        MAX-ACCESS read-write
        STATUS current
        DESCRIPTION
                "This is used to indicate that the destination is
                 another AI switch."
        DEFVAL { 2 }
        ::= { aiCLCDestTableEntry 7 }

    aiCLCDestTmrType OBJECT-TYPE
    	SYNTAX INTEGER {
                   actTmr(1),
                   sessTmr(2)
                }
        MAX-ACCESS read-write
        STATUS current
        DESCRIPTION
                "This is used to set the type of timer associated
                 with the destination."
        DEFVAL { 2 }
        ::= { aiCLCDestTableEntry 8 }

    aiCLCDestTmrVal OBJECT-TYPE
    	SYNTAX Integer32 (0..4368000)
        MAX-ACCESS read-write
        STATUS current
        DESCRIPTION
                "This value is the timer duration in milliseconds
                 ranging from 1mS to 4368000mS or about 72 hours."
        DEFVAL { 1 }
        ::= { aiCLCDestTableEntry 9 }

    aiCLCDestTmrDelay OBJECT-TYPE
    	SYNTAX Integer32 (0..4368000)
        MAX-ACCESS read-write
        STATUS current
        DESCRIPTION
                "This value is the delay in milliseconds before
                 allowing further calls on the destination after a
                 call terminates. The range is 1mS to 4368000mS or
                 about 72 hours."
        DEFVAL { 1 }
        ::= { aiCLCDestTableEntry 10 }

    aiCLCDestPswd OBJECT-TYPE
    	SYNTAX DisplayString (SIZE(0..8))
        MAX-ACCESS read-write
        STATUS current
        DESCRIPTION
                "This is password associated with the destination."
        ::= { aiCLCDestTableEntry 11 }

    aiCLCDestQPswd OBJECT-TYPE
    	SYNTAX DisplayString (SIZE(0..8))
        MAX-ACCESS read-write
        STATUS current
        DESCRIPTION
                "This is password used to control access to the
                 queue management functions associated with the
                 destination."
        ::= { aiCLCDestTableEntry 12 }

    aiCLCDestMenuMsg OBJECT-TYPE
    	SYNTAX DisplayString 
        MAX-ACCESS read-write
        STATUS current
        DESCRIPTION
                "This string is displayed next to the destination in
                 the destination menu."
        ::= { aiCLCDestTableEntry 13 }

    aiCLCDestConnMsg OBJECT-TYPE
    	SYNTAX DisplayString 
        MAX-ACCESS read-write
        STATUS current
        DESCRIPTION
                "This string is forced out the destination port when
                 a connection begins."
        ::= { aiCLCDestTableEntry 14 }

    aiCLCDestDiscMsg OBJECT-TYPE
    	SYNTAX DisplayString 
        MAX-ACCESS read-write
        STATUS current
        DESCRIPTION
                "This string is forced out the destination port when
                 a connection terminates."
        ::= { aiCLCDestTableEntry 15 }

    aiCLCDestState OBJECT-TYPE
    	SYNTAX INTEGER {
                   enabled(1),
                   disabled(2)
                }
        MAX-ACCESS read-write
        STATUS current
        DESCRIPTION
                "This is used to enable or disable the destination."
        DEFVAL { 1 }
        ::= { aiCLCDestTableEntry 16 }

    aiCLCDestNumPorts OBJECT-TYPE
    	SYNTAX INTEGER (0..256)
        MAX-ACCESS read-only
        STATUS current
        DESCRIPTION
                "This is used to determine the number of ports
                 assigned to this destination."
        ::= { aiCLCDestTableEntry 17 }

    aiCLCDestNumUsed OBJECT-TYPE
    	SYNTAX INTEGER (0..256)
        MAX-ACCESS read-only
        STATUS current
        DESCRIPTION
                "This is used to determine the number of ports
                 in use for this destination."
        ::= { aiCLCDestTableEntry 18 }

    aiCLCDestNumFree OBJECT-TYPE
    	SYNTAX INTEGER (0..256)
        MAX-ACCESS read-only
        STATUS current
        DESCRIPTION
                "This is used to determine the number of ports
                 that are free for this destination."
        ::= { aiCLCDestTableEntry 19 }

    aiCLCDestQHigh OBJECT-TYPE
    	SYNTAX INTEGER (0..65536)
        MAX-ACCESS read-only
        STATUS current
        DESCRIPTION
                "This is used to determine the maximum number of ports
                 that were queued to this destination."
        ::= { aiCLCDestTableEntry 20 }

    aiCLCDestPortList OBJECT-TYPE
    	SYNTAX DisplayString 
        MAX-ACCESS read-only
        STATUS current
        DESCRIPTION
                "This string contains a list of port numbers assigned
                 to this destination."
        ::= { aiCLCDestTableEntry 21 }

    aiCLCDestWaitForPort OBJECT-TYPE
    	SYNTAX INTEGER {
                   on(1),
                   off(2)
                }
        MAX-ACCESS read-write
        STATUS current
        DESCRIPTION
                "This is used to allow the user to wait for a port 
                 when all ports for the destination are busy."
        DEFVAL { 1 }
        ::= { aiCLCDestTableEntry 22 }

-- Async Table
-- The Async Table contains information pertaining to asynchronous
-- ports. This information does not fit very well in the RS-232 MIB
-- and therefore resides in this table. There will be one entry in
-- this table for each configured asynchronous port.

    aiCLCAsyncTable OBJECT-TYPE
    	SYNTAX SEQUENCE OF AiCLCAsyncTableEntry
        MAX-ACCESS not-accessible
        STATUS current
        DESCRIPTION
                "The Async Table."
        ::= { aiCLC 6 }

    aiCLCAsyncTableEntry OBJECT-TYPE
    	SYNTAX AiCLCAsyncTableEntry
        MAX-ACCESS not-accessible
        STATUS current
        DESCRIPTION
                "An Async Table entry."
        INDEX { aiCLCAsyncifIndex }
        ::= { aiCLCAsyncTable 1 }

    AiCLCAsyncTableEntry ::=
    	SEQUENCE {
            aiCLCAsyncifIndex		INTEGER, 
            aiCLCAsyncPort		INTEGER,
            aiCLCAsyncAdminStatus	INTEGER,
            aiCLCAsyncDiscType		INTEGER, 
            aiCLCEIASignals		INTEGER, 
            aiCLCEIARtsDisc		INTEGER, 
            aiCLCEIADtrDisc		INTEGER,   
            aiCLCEIARtsConn		INTEGER, 
            aiCLCEIADtrConn		INTEGER, 
            aiCLCEIARtsToggle		INTEGER, 
            aiCLCEIADtrToggle 		INTEGER                                   
        }

    aiCLCAsyncifIndex OBJECT-TYPE
    	SYNTAX Integer32 
        MAX-ACCESS read-only
        STATUS current
        DESCRIPTION
                "The ifIndex from the interfaces table."
        ::= { aiCLCAsyncTableEntry 1 }

    aiCLCAsyncPort OBJECT-TYPE
    	SYNTAX INTEGER (0..255)
        MAX-ACCESS read-only
        STATUS current
        DESCRIPTION
                "The AISwitch port number."
        ::= { aiCLCAsyncTableEntry 2 }


    aiCLCAsyncAdminStatus OBJECT-TYPE
    	SYNTAX INTEGER {
                   up(1),
                   down(2)
                }
        MAX-ACCESS read-write
        STATUS current
        DESCRIPTION
                "The key field for the Async table entry."
        ::= { aiCLCAsyncTableEntry 3 }

    aiCLCAsyncDiscType OBJECT-TYPE
    	SYNTAX INTEGER {
                   nobrkdisc(1),
                   brkdisc(2),
                   longbrkdisc(3)
                }
        MAX-ACCESS read-write
        STATUS current
        DESCRIPTION
                "The disconnect type for the async port."
        DEFVAL { 2 }
        ::= { aiCLCAsyncTableEntry 4 }

    aiCLCEIASignals OBJECT-TYPE
    	SYNTAX INTEGER {
                   eiaDisabled(1),
                   dsrRtsPass(2),
                   dsrOffDisc(3),
                   dsrOnOffDisc(4),
                   dcdOffDisc(5),
                   dcdOnOffDisc(6)
                }
        MAX-ACCESS read-write
        STATUS current
        DESCRIPTION
                "The EIA signals may be disabled (eiaDisabled(1)) or configured for
                 pass through (dsrRtsPass(2)). Additionally the port can
                 be configured to disconnect on loss of DSR (dsrOffDisc(3)),
                 disconnect on change of state of DSR (dsrOnOffDisc(4)), 
                 disconnect on loss of DCD (dcdOffDisc(5)), or disconnect
                 on change of state of DCD (dcdOnOffDisc(6))."
        DEFVAL { 1 }
        ::= { aiCLCAsyncTableEntry 5 }

    aiCLCEIARtsDisc OBJECT-TYPE
    	SYNTAX INTEGER {
                   on(1),
                   off(2)
                }
        MAX-ACCESS read-write
        STATUS current
        DESCRIPTION
                "Upon disconnect RTS may be configured to be on(1), or
                 off(2)."
        DEFVAL { 1 }
        ::= { aiCLCAsyncTableEntry 6 }

    aiCLCEIADtrDisc OBJECT-TYPE
    	SYNTAX INTEGER {
                   on(1),
                   off(2)
                }
        MAX-ACCESS read-write
        STATUS current
        DESCRIPTION
                "Upon disconnect DTR may be configured to be on(1), or
                 off(2)."
        DEFVAL { 1 }
        ::= { aiCLCAsyncTableEntry 7 }

    aiCLCEIARtsConn OBJECT-TYPE
    	SYNTAX INTEGER {
                   on(1),
                   off(2)
                }
        MAX-ACCESS read-write
        STATUS current
        DESCRIPTION
                "Upon connect RTS may be configured to be on(1), or
                 off(2)."
        DEFVAL { 1 }
        ::= { aiCLCAsyncTableEntry 8 }

    aiCLCEIADtrConn OBJECT-TYPE
    	SYNTAX INTEGER {
                   on(1),
                   off(2)
                }
        MAX-ACCESS read-write
        STATUS current
        DESCRIPTION
                "Upon connect DTR may be configured to be on(1), or
                 off(2)."
        DEFVAL { 1 }
        ::= { aiCLCAsyncTableEntry 9 }

    aiCLCEIARtsToggle OBJECT-TYPE
    	SYNTAX INTEGER {
                   on(1),
                   off(2)
                }
        MAX-ACCESS read-write
        STATUS current
        DESCRIPTION
                "Upon disconnect RTS may be configured to 
                 toggle (on(1)) or not (off(2))."
        DEFVAL { 2 }
        ::= { aiCLCAsyncTableEntry 10 }

    aiCLCEIADtrToggle OBJECT-TYPE
    	SYNTAX INTEGER {
                   on(1),
                   off(2)
                }
        MAX-ACCESS read-write
        STATUS current
        DESCRIPTION
                "Upon disconnect DTR may be configured to 
                 toggle (on(1)) or not (off(2))."
        DEFVAL { 2 }
        ::= { aiCLCAsyncTableEntry 11 }

-- Auto ID Table
-- The Auto ID Table contains board identification information for
-- boards that contain an auto id device and can be accessed using
-- the auto id bus.

    aiCLCAutoIDTable OBJECT-TYPE
    	SYNTAX SEQUENCE OF AiCLCAutoIDTableEntry
        MAX-ACCESS not-accessible
        STATUS current
        DESCRIPTION
                "A table of board identification information for an AISwitch."
        ::= { aiCLC 7 }

    aiCLCAutoIDTableEntry OBJECT-TYPE
    	SYNTAX AiCLCAutoIDTableEntry
        MAX-ACCESS not-accessible
        STATUS current
        DESCRIPTION
                "Board Identification information for a particular card."
        INDEX { aiCLCAIDIndex }

        ::= { aiCLCAutoIDTable 1 }

    AiCLCAutoIDTableEntry ::=
    	SEQUENCE {
            aiCLCAIDIndex		INTEGER,
            aiCLCAIDPort		INTEGER,
            aiCLCAIDProduct		DisplayString,
            aiCLCAIDSerialNumber	DisplayString,
            aiCLCAIDManufDate		DisplayString,
            aiCLCAIDMACAdrs		DisplayString
        }

    aiCLCAIDIndex OBJECT-TYPE
    	SYNTAX INTEGER (1..64)
        MAX-ACCESS read-only
        STATUS current
        DESCRIPTION
                "The Auto ID Table index."
        ::= { aiCLCAutoIDTableEntry 1 }

    aiCLCAIDPort OBJECT-TYPE
    	SYNTAX INTEGER (0..256)
        MAX-ACCESS read-only
        STATUS current
        DESCRIPTION
                "The port number where the card resides. 
                 If the port number is not valid then 256 
                 will be reported."
        ::= { aiCLCAutoIDTableEntry 2 }

    aiCLCAIDProduct OBJECT-TYPE
    	SYNTAX DisplayString
        MAX-ACCESS read-only
        STATUS current
        DESCRIPTION
                "The product name for the card."
        ::= { aiCLCAutoIDTableEntry 3 }

    aiCLCAIDSerialNumber OBJECT-TYPE
    	SYNTAX DisplayString
        MAX-ACCESS read-only
        STATUS current
        DESCRIPTION
                "The serial number for the card."
        ::= { aiCLCAutoIDTableEntry 4 }

    aiCLCAIDManufDate OBJECT-TYPE
    	SYNTAX DisplayString
        MAX-ACCESS read-only
        STATUS current
        DESCRIPTION
                "The date of manufacture for the card."
        ::= { aiCLCAutoIDTableEntry 5 }

    aiCLCAIDMACAdrs OBJECT-TYPE
    	SYNTAX DisplayString
        MAX-ACCESS read-only
        STATUS current
        DESCRIPTION
                "The MAC address for the card."
        ::= { aiCLCAutoIDTableEntry 6 }

-- AI2524 10BT Link Status Table
-- This table contains the 10BT link status for AI2524 Router Cards.

    aiCLCAI2524LinkTable OBJECT-TYPE
    	SYNTAX SEQUENCE OF AiCLCAI2524LinkTableEntry
        MAX-ACCESS not-accessible
        STATUS current
        DESCRIPTION
                "A table of link status for AI2524 Router Cards."
        ::= { aiCLC 8 }

    aiCLCAI2524LinkTableEntry OBJECT-TYPE
    	SYNTAX AiCLCAI2524LinkTableEntry
        MAX-ACCESS not-accessible
        STATUS current
        DESCRIPTION
                "Link information particular to AI2524 Router Cards."
        INDEX { aiCLCAI2524Port }

        ::= { aiCLCAI2524LinkTable 1 }

    AiCLCAI2524LinkTableEntry ::=
    	SEQUENCE {
            aiCLCAI2524Port		INTEGER,
            aiCLCAI2524LinkStatus	INTEGER
        }

    aiCLCAI2524Port OBJECT-TYPE
    	SYNTAX INTEGER (0..255)
        MAX-ACCESS read-only
        STATUS current
        DESCRIPTION
                "The port number for the AI2524 Router Card. "
        ::= { aiCLCAI2524LinkTableEntry 1 }

    aiCLCAI2524LinkStatus OBJECT-TYPE
    	SYNTAX INTEGER {
                up(1),
                down(2)
        }
        MAX-ACCESS read-only
        STATUS current
        DESCRIPTION
                "The 10BT link status for the AI2524 Router Card."
        ::= { aiCLCAI2524LinkTableEntry 2 }

END
