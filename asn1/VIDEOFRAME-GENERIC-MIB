VIDEOFRAME-GENERIC-MIB DEFINITIONS ::= BEGIN

	--  Relationship to Other MIBs
	--
	--
	--  The objects defined in this MIB are located under the
	--  private.enterprises subtree as shown below:
	--
	--               iso(1).org(3).dod(6).internet(1)
	--                            |
	--                         private(4)
	--                            |
	--                       enterprises(1)
	--                            |
	--                       videoframe(4596)
	--                            |
	--                        vfGeneric(3)
	--                                 
	--
	--  References
	--
	--  [1]  RFC 1902.  McCloghrie, K., and M. Rose, "Structure 
	--       of Management Information for Version 2 of the Simple
	--       Network Management Protocol (SNMPv2)".  
	--       January, 1996.
	--
	--  [2]  RFC 1903.  McCloghrie, K., and M. Rose, "Textual
	--       Conventions for Version 2 of the Simple Network
	--       Management Protocol (SNMPv2)".  
	--       January, 1996.
	--
	--  [3]  RFC 1904.  McCloghrie, K., and M. Rose, "Conformance
	--       Statements for Version 2 of the Simple Network
	--       Management Protocol (SNMPv2)".  
	--       January, 1996.
	--
	--  [4]  RFC 1907.  McCloghrie, K., and M. Rose, "Management 
	--       Information Base for Version 2 of the Simple Network
	--       Management Protocol (SNMPv2)".  
	--       January, 1996.
	--
	--	[5]  Perkins, David and McGinnis, Evan; "Understanding SNMP
	--		 MIBs".  Prentice Hall, ISBN 0-13-437708-7, 1997.
	--
	--
	--  Object Synopsis
	--  
	--
	--  All objects within this MIB are prefixed with the OBJECT
	--  IDENTIFIER "p", where "p" is:
	--
	--  iso(1).org(3).dod(6).internet(1).private(4).enterprises(1).
	--          videoframe(4596).vfGeneric(3)
	--	
	--  or, 1.3.6.1.4.1.4596.3
	--
	--
	--  Object Name                               Object Id         
	--  --------------------------------          --------------
	--
	--	vfBox									p.1
	--		vfBoxEvents							p.1.0
	--		vfMaxBoxes							p.1.1
	--		vfBoxTableNextIndex					p.1.2
	--		vfBoxTable							p.1.3
	--		vfBoxTableEntry						p.1.3.1
	--			vfBoxId							p.1.3.1.1.n
	--			vfBoxPartNo						p.1.3.1.2.n
	--			vfBoxPsAStatus					p.1.3.1.3.n
	--			vfBoxPsBStatus					p.1.3.1.4.n
	--			vfBoxFailoverStatus				p.1.3.1.5.n
	--			vfBoxTrapEnable					p.1.3.1.6.n
	--			vfBoxSoftwareRev				p.1.3.1.7.n
	--			vfBoxState						p.1.3.1.8.n
	--			vfBoxEntryStatus				p.1.3.1.9.n
	--	vfAgent									p.2
	--		vfAgentTrapEnable					p.2.1
	--		vfTrapTargMaxTargets				p.2.2
	--		vfTrapTargCfgTableNextIndex			p.2.3
	--		vfTrapTargCfgTable					p.2.4
	--      vfTrapTargCfgEntry					p.2.4.1
	--			vfTrapTargCfgIndex				p.2.4.1.1.n
	--			vfTrapTargCfgIpAddress			p.2.4.1.2.n
	--			vfTrapTargCfgCommunity			p.2.4.1.3.n
	--			vfTrapTargCfgEntryStatus		p.2.4.1.4.n
	--    

	IMPORTS
		OBJECT-TYPE FROM RFC1155-SMI
		MODULE-IDENTITY, OBJECT-IDENTITY, NOTIFICATION-TYPE,
		Integer32, IpAddress
			FROM SNMPv2-SMI
		DisplayString, RowStatus
			FROM SNMPv2-TC
		MODULE-COMPLIANCE, OBJECT-GROUP
			FROM SNMPv2-CONF
		system
			FROM SNMPv2-MIB
		vfGeneric, vfMIBModules
			FROM VIDEOFRAME-REGISTRATIONS-MIB;

	videoframeGenericMIB MODULE-IDENTITY
		LAST-UPDATED "0101190000Z"
		ORGANIZATION "Videoframe Systems"
		CONTACT-INFO
			"Videoframe Systems
			P.O. Box 1991,
			Grass Valley, CA 95945, USA.

			+1 (530) 477-2000

			http://www.videoframesystems.com"
	DESCRIPTION
		"This MIB module describes the generic 
		objects for a manageable device
		in the Videoframe Systems product line.

		This MIB does not describe the device
		specific objects of the managed system, 
		and augments MIB-2 in the identification 
		of a Videoframe Systems managed device.

		This module will be extended, or modified 
		as required.

		Videoframe Systems reserves the right to
		make changes in specification and other 
		information contained in this document without 
		prior notice. The reader should consult Videoframe Systems
		to determine whether any such changes have been made.

		In no event shall Videoframe Systems be 
		liable for any incidental, indirect, special, 
		or consequential damages whatsoever (including 
		but not limited to lost profits) arising out of 
		or related to this document or the information 
		contained in it.

		Videoframe Systems grants vendors, end users, 
		and other interested parties a non-exclusive 
		license to use this specification in connection 
		with the management of Videoframe Systems products.

		Copyright 2001 Videoframe, Inc."
	REVISION      "0101190000Z"
	DESCRIPTION
		"First release."
	::= { vfMIBModules 2 }

	--
	-- Implement sysObjectID from the SNMPv2-MIB 'system' group
	-- here
	--
sysObjectID	OBJECT-TYPE
			SYNTAX		OBJECT IDENTIFIER
			MAX-ACCESS	read-only
			STATUS		current
			DESCRIPTION
				"The standard identification of the managed system this
				 agent represents.  These are OIDs from the
				 vfRegistrations branch of the videoframe MIB namespace."
		::= { system 2 }

	--
	--  The Generic MIB top-level groups
	--

vfBox		OBJECT IDENTIFIER ::= { vfGeneric 1 }
vfAgent		OBJECT IDENTIFIER ::= { vfGeneric 2 }
vfBoxEvents	OBJECT IDENTIFIER ::= { vfBox 0 }

	--
	--  The vfBox MIB Object Definitions
	--

vfMaxBoxes OBJECT-TYPE
		SYNTAX		Integer32
		MAX-ACCESS	read-only
		STATUS		current
		DESCRIPTION
			"The maximum number of managed boxes that this
			agent can represent. 

			If the value of this variable is -1, the device
			is capable of representing a theoretically
			infinite number of boxes dynamically. In
			othercases, the maximum number of boxes 
			that can be represented by this device is limited
			to the value of this variable."
	::= { vfBox 1 }

vfBoxTableNextIndex OBJECT-TYPE
		SYNTAX		Integer32
		MAX-ACCESS	read-only
		STATUS		current
		DESCRIPTION
			"Identifies a hint for the next value of  
			vfBoxEntryIndex to be used in a row creation attempt
			for the vfBoxTable table. If no new rows can be
			created, this object will have a value of 0."
	::= { vfBox 2 }


--
-- Table for describing generic Box Status
--

vfBoxTable	OBJECT-TYPE
	SYNTAX	SEQUENCE OF BoxEntry
	MAX-ACCESS	not-accessible
	STATUS	current
	DESCRIPTION
		"Each row contains information about one generic Videoframe
		 managed box."

	::=	{ vfBox 3}

vfBoxEntry	OBJECT-TYPE
	SYNTAX	BoxEntry
	MAX-ACCESS	not-accessible
	STATUS	current
	DESCRIPTION
		"Information about one generic Videoframe
		 managed box."
	INDEX	{ vfBoxId }

	::= 	{ vfBoxTable 1 }


BoxEntry ::=
	SEQUENCE
		{
			vfBoxEntryIndex		Integer32,
			vfBoxId				DisplayString,
			vfBoxPartNo			DisplayString,
			vfBoxPsAStatus		INTEGER,
			vfBoxPsBStatus		INTEGER,
			vfBoxFailoverStatus	INTEGER,
			vfBoxTrapEnable		INTEGER,
			vfBoxSoftwareRev	DisplayString,
			vfBoxState			INTEGER,
			vfBoxEntryStatus	RowStatus
		}


vfBoxEntryIndex	OBJECT-TYPE
	SYNTAX	Integer32
	MAX-ACCESS	not-accessible
	STATUS	current
	DESCRIPTION
		"The index of a row in the box table."

	::= { vfBoxEntry 1 }

vfBoxId	OBJECT-TYPE
	SYNTAX	DisplayString (SIZE ( 0..20 ))
	MAX-ACCESS	read-create
	STATUS	current
	DESCRIPTION
		"Name of box in system drawings.  e.g. GPICTLR-5."

	::= { vfBoxEntry 2 }

vfBoxPartNo	OBJECT-TYPE
	SYNTAX	DisplayString (SIZE ( 0..20 ))
	MAX-ACCESS	read-create
	STATUS	current
	DESCRIPTION
		"Videoframe part no. from nameplate."

	::= { vfBoxEntry 3 }

vfBoxPsAStatus	OBJECT-TYPE
	SYNTAX	INTEGER
			{
				off(1),
				on(2)
			}
	MAX-ACCESS	read-only
	STATUS	current
	DESCRIPTION
		"Power Supply A Status is on/off."

	::= { vfBoxEntry 4 }


vfBoxPsBStatus	OBJECT-TYPE
	SYNTAX	INTEGER
			{
				off(1),
				on(2)
			}
	MAX-ACCESS	read-only
	STATUS	current
	DESCRIPTION
		"Power Supply B Status is on/off."

	::= { vfBoxEntry 5 }

vfBoxFailoverStatus	OBJECT-TYPE
	SYNTAX	INTEGER
			{
				backup(1),
				main(2)
			}
	MAX-ACCESS read-only
	STATUS current
	DESCRIPTION
		"This box is currently main(2) or backup(1) of a redundant pair."

	::= { vfBoxEntry 6 }

vfBoxTrapEnable	OBJECT-TYPE
	SYNTAX	INTEGER
			{
				enabled(1),
				disabled(2)
			}
	MAX-ACCESS	read-create
	STATUS	current
	DESCRIPTION
		"Enables or disables the Trap that is associated
		 with a box status change event."

	::= { vfBoxEntry 7 }

vfBoxSoftwareRev OBJECT-TYPE
		SYNTAX		DisplayString (SIZE(0..64))
		MAX-ACCESS	read-only
		STATUS		current
		DESCRIPTION
			"The revision of the software (if any) running on 
			the box."
	::= { vfBoxEntry 8 }

vfBoxState OBJECT-TYPE
		SYNTAX		INTEGER {
						vfBoxRunning(1),
						vfBoxInMaintenance(2),
						vfBoxFaulty(3),
						vfBoxDisabled(4),
						vfBoxIdling(5),
						vfBoxInitializing(6),
						vfBoxResetting(7)
					}
		MAX-ACCESS	read-only
		STATUS		current
		DESCRIPTION
			"The operational state of a device.

			NOTE: It is not mandatory that a managed device
			support all of the enumerated device states.

			vfBoxActive(1) - The device is running and 
			processing load.

			vfBoxInMaintenance(2) - The device is online, 
			but either the device as a whole, or one or more of 
			its components are in maintenance mode. Maintenance 
			mode could be described as a mode where diagnostics 
			are being run on the device, or some tasks such as 
			device configuration are being excuted on the 
			device that has inhibited its normal operation.

			vfBoxFaulty(3) - The device has experienced a 
			faulty condition in one or more of its components.

			vfBoxDisabled(4) - The device may not be in a 
			faulty condition, but has been explicitly disabled 
			from its normal mode of operation, such as when
			selected as the backup of a redundant pair.

			vfBoxIdling(5) - The device is running in an 
			idle state (no clients are currently active).

			vfBoxInitializing(6) - This is a post bootstrap 
			state where the device has been restarted, and is 
			initializing its hardware and software components.

			vfBoxResetting(7) - The device is in a post-
			reset cycle. Any information collected, or dynamic 
			configuration of the device prior to this state 
			may be lost."
	::= { vfBoxEntry 9 }

vfBoxEntryStatus OBJECT-TYPE
		SYNTAX	RowStatus
		MAX-ACCESS	read-create
		STATUS	current
		DESCRIPTION
			"This object controls the creation, activation
			and deletion of a row in the box table."
	::= { vfBoxEntry 10 }

	--
	--  The vfBoxEvents group is assigned the OID '0' (above)
	--  to comply with the trap handling in the different SNMP versions.
	--	See [5], Section 8.2
	--

	--
	-- Events for describing generic Box Status changes
	--


boxPsAEvent	NOTIFICATION-TYPE
	OBJECTS	{
			vfBoxId,
			vfBoxPsAStatus
		}
	STATUS	current
	DESCRIPTION
		"Box Power Supply A
		 changed status."
	::= { vfBoxEvents 1 }


boxPsBEvent	NOTIFICATION-TYPE
	OBJECTS	{
			vfBoxId,
			vfBoxPsAStatus
		}
	STATUS	current
	DESCRIPTION
		"Box Power Supply B
		 changed status."
	::= { vfBoxEvents 2 }


boxFailoverEvent	NOTIFICATION-TYPE
	OBJECTS	{
			vfBoxId,
			vfBoxFailoverStatus
		}
	STATUS	current
	DESCRIPTION
		"Box failover status changed."
	::= { vfBoxEvents 3 }


boxStateChangeEvent NOTIFICATION-TYPE
		OBJECTS	{
			vfBoxId,
			vfBoxState
		}
		STATUS	current
		DESCRIPTION
			"Notifies when a state change occurs on an device.
			 The vfBoxState variable will hold the new state that
			 the device is operating in."
	::= { vfBoxEvents 4 }

	--
	-- The vfAgent Group
	-- The vfAgent group includes a table of trap targets for this agent.
	-- It also contains a global enable or disable flag for all traps from this agent.
	--

vfAgentTrapEnable	OBJECT-TYPE
	SYNTAX	INTEGER
			{
				enabled(1),
				disabled(2)
			}
	MAX-ACCESS	read-write
	STATUS	current
	DESCRIPTION
		"Enables or disables all Traps from this agent."

	::= { vfAgent 1 }

vfTrapTargMaxTargets OBJECT-TYPE
		SYNTAX		Integer32
		MAX-ACCESS	read-only
		STATUS		current
		DESCRIPTION
			"The maximum number of trap targets that this
			device can support. 

			If the value of this variable is -1, the device
			is capable of supporting a theoretically
			infinite number of trap targets dynamically. In
			othercases, the maximum number of trap targets 
			that can be supported by this device is limited
			to the value of this variable."
	::= { vfAgent 2 }

vfTrapTargCfgTableNextIndex OBJECT-TYPE
		SYNTAX		Integer32
		MAX-ACCESS	read-only
		STATUS		current
		DESCRIPTION
			"Identifies a hint for the next value of  
			vfTrapTargCfgIndex to be used in a row creation attempt
			for the vfTrapTargCfgTable table. If no new rows can be
			created, this object will have a value of 0."
	::= { vfAgent 3 }

vfTrapTargCfgTable OBJECT-TYPE
		SYNTAX	SEQUENCE OF VfTrapTargCfgEntry
		MAX-ACCESS	not-accessible
		STATUS	current
		DESCRIPTION
			"A list of trap target configuration entries on
			this device.

			Trap Target Configuration Entry Creation:
			=========================================

			When creating a trap target configuration entry
			the manager should use a GET operation to 
			determine the value of vfTrapTargCfgTableNextIndex.0.
			If this value is non-zero, the manager can then 
			use this value as the index while creating a 
			table row.

			The process of creating and activating a row of 
			this table takes two forms: the one-set mode and 
			the multiple-set mode.

			In the one-set mode, a manager must specify the
			values of vfTrapTargCfgIpAddress and vfTrapTargCfgCommunity
			required to activate a row in a single SET operation
			along with an assignment of the vfTrapTargCfgEntryStatus
			to 'createAndGo(4)'. If the values and instances
			supplied are correct, an instance of the trap target
			configuration is created and the value of 
			vfTrapTargCfgEntryStatus transitions to 'active(1)'.

			for example:
			============

			SnmpGet(<vfTrapTargCfgTableNextIndex.0, NULL>)
				returns
					<vfTrapTargCfgTableNextIndex.0, 2>

			SnmpSet(<vfTrapTargCfgIpAddress.2, 192.168.1.8>,
                    <vfTrapTargCfgCommunity.2, 'public'>,
                    <vfTrapTargCfgEntryStatus.2, createAndGo(4)>)
				returns 
					<vfTrapTargCfgIpAddress.2, 192.168.1.8>,
                    <vfTrapTargCfgCommunity.2, 'public'>,
                    <vfTrapTargCfgEntryStatus.2, active(1)>

			In the multiple-set mode, creating a trap target
			configuration table row, filling it with values,
			and activating it are carried out in discrete steps.

			To create the row, the manager specifies a value
			of 'createAndWait(5)' for the vfTrapTargCfgEntryStatus
			status variable. This SET request could contain
			values of vfTrapTargCfgIpAddress and vfTrapTargCfgCommunity
			but it is not required. More often, the values for 
			these columnar objects are specified in additional
			SET requests. After each SET operation, the 
			vfTrapTargCfgEntryStatus variable takes on the value 
			'notReady(3)' or 'notInService(2)'. To place the
			entry into service, the manager requests that the
			vfTrapTargCfgEntryStatus variable transition to the
			'active(1)' state.

			for example:
			============

			SnmpGet(<vfTrapTargCfgTableNextIndex.0>, NULL)
				returns
					<vfTrapTargCfgTableNextIndex.0, 2>

			SnmpSet(<vfTrapTargCfgEntryStatus.2, createAndWait(5)>)
				returns
					<vfTrapTargCfgEntryStatus.2, notReady(3)>

			SnmpSet(<vfTrapTargCfgIpAddress.2, 192.168.1.8>,
                    <vfTrapTargCfgCommunity.2, 'public'>)
				returns
					<vfTrapTargCfgIpAddress.2, 192.168.1.8>,
                    <vfTrapTargCfgCommunity.2, 'public'>

			SnmpSet(<vfTrapTargCfgEntryStatus.2, active(1)>)
				returns
					<vfTrapTargCfgEntryStatus.2, active(1)>

			Trap Target Configuration Entry Deletion:
			=========================================

			To delete an existing trap target configuration
			entry, the manager performs a SET operation on the
			vfTrapTargCfgEntryStatus variable with the value
			'destroy(6)'."
		::= { vfAgent 4 }

vfTrapTargCfgEntry OBJECT-TYPE
		SYNTAX	VfTrapTargCfgEntry
		MAX-ACCESS	not-accessible
		STATUS current	
		DESCRIPTION
			"A trap target configuration entry."
		INDEX	{ vfTrapTargCfgIndex }
		::= { vfTrapTargCfgTable 1 }

VfTrapTargCfgEntry ::=
		SEQUENCE {
			vfTrapTargCfgIndex
				Integer32,
			vfTrapTargCfgIpAddress
				IpAddress,
			vfTrapTargCfgCommunity
				DisplayString,
			vfTrapTargCfgEntryStatus
				RowStatus
		}

vfTrapTargCfgIndex OBJECT-TYPE
		SYNTAX	Integer32
		MAX-ACCESS	not-accessible
		STATUS	current
		DESCRIPTION
			"The index of a trap target configuration row.

			Note that the value of this object will not
			be visible to a manager and any GET/SET 
			operations on this variable will fail."
		::= { vfTrapTargCfgEntry 1 }

vfTrapTargCfgIpAddress OBJECT-TYPE
		SYNTAX	IpAddress
		MAX-ACCESS	read-create
		STATUS	current
		DESCRIPTION
			"The IP address of the target/manager to which
			this device is supposed to send notifications."
		::= { vfTrapTargCfgEntry 2 }

vfTrapTargCfgCommunity OBJECT-TYPE
		SYNTAX	DisplayString(SIZE(0..128))
		MAX-ACCESS	read-create
		STATUS	current
		DESCRIPTION
			"The community name to be used when this device
			sends notifications to the target identified by 
			the value of this entries vfTrapTargCfgIpAddress."
		::= { vfTrapTargCfgEntry 3 }

vfTrapTargCfgEntryStatus OBJECT-TYPE
		SYNTAX	RowStatus
		MAX-ACCESS	read-create
		STATUS	current
		DESCRIPTION
			"This object controls the creation, activation
			and deletion of a row in the trap target configuration
			table."
		::= { vfTrapTargCfgEntry 4 }



END
