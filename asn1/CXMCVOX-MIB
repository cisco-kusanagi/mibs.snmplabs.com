CXMCVOX-MIB DEFINITIONS ::= BEGIN                               
--
--
--
--
--  cxMcVox VOICE CORE MIB
--
--            starting point: MIB rev.1.4
--            includes: All options already implemented in the MIB rev.1.4
--                      All configuration objects in "private mode"
--            note: This MIB is shared by all voice products (AC600, CX900,
--                  DI600, AI600, ....).
--
--

--#CURRENT-VERSION 11

IMPORTS
    OBJECT-TYPE          FROM RFC-1212
    TRAP-TYPE            FROM RFC-1215
    DisplayString        FROM RFC1213-MIB
    cxMc600              FROM CXProduct-SMI
    cxModuleHwPhysSlot   FROM CXModuleHardware-MIB;

cxMcVox  OBJECT IDENTIFIER ::= { cxMc600 2 }




-- ==================================================================

--  cxMcVox GLOBAL CONFIGURATION GROUP.


cxMcVoxGlobal        OBJECT IDENTIFIER ::= {cxMcVox 1 }

-- obsolete: The Administrative Path Length commands 
--           are now in the Administrative Path table.
 
cxMcVoxGlobalAdmPathLng OBJECT-TYPE
   SYNTAX INTEGER (2..4)
   ACCESS  read-write
   STATUS  obsolete
   DESCRIPTION
"obsolete. The ReinitNet/ReinitPath commands have been replaced by 
ReinitRouting."
   DEFVAL { 3 }
   ::= { cxMcVoxGlobal 1 }


-- obsolete: The ReinitNet/ReinitPath commands
--           have been replaced by ReinitRouting

cxMcVoxGlobalReinitPath OBJECT-TYPE
   SYNTAX  INTEGER {
           no      (1),
           yes     (2)
        }
   ACCESS  read-write
   STATUS  obsolete
   DESCRIPTION
"The ReinitNet/ReinitPath commands have been replaced by ReinitRouting.

"
   DEFVAL { no }
   ::= { cxMcVoxGlobal 2 }


cxMcVoxGlobalClearPath OBJECT-TYPE
   SYNTAX  INTEGER {
           no      (1),
           yes     (2)
        }
   ACCESS  read-write
   STATUS  deprecated
   DESCRIPTION
"Path ID no longer exists with the new voice routing scheme 

Determines whether to restore all administrative Path IDs to the default 
factory settings.

The setting of this object is dynamic. When set to 'yes' all 
administrative Path IDs will immediately change to the factory defaults.

Options:
no (1)

yes (2)

Default Value: no (1)

Configuration Change: administrative
(Voice Routing or VR)."
   DEFVAL { no }
   --#ENDING-VERSION 1
   ::= { cxMcVoxGlobal 3 }



-- obsolete: The ReinitNet/ReinitPath commands
--           have been replaced by ReinitRouting

cxMcVoxGlobalReinitNet OBJECT-TYPE
   SYNTAX  INTEGER {
           no      (1),
           yes     (2)
        }
   ACCESS  read-write
   STATUS  obsolete
   DESCRIPTION
"The ReinitNet/ReinitPath commands have been replaced by 
ReinitRouting."
   DEFVAL { no }
   ::= { cxMcVoxGlobal 4 }

cxMcVoxGlobalClearNet OBJECT-TYPE
   SYNTAX  INTEGER {
           no      (1),
           yes     (2)
        }
   ACCESS  read-write
   STATUS  deprecated
   DESCRIPTION
"Network ID no longer exists in the new voice routing scheme (Voice 
Routing or VR).

Determines whether to restore all administrative routing entries (i.e. 
network routing entries, Path IDs and Group IDs) to the default factory 
settings.

The setting of this object is dynamic. When set to 'yes' all 
administrative routing entries will immediately change to the factory 
defaults.

Options:
no (1)

yes (2)

Default Value: no (1)

Configuration Changed: administrative"
   DEFVAL { no }
   --#ENDING-VERSION 1
   ::= { cxMcVoxGlobal 5 }

cxMcVoxGlobalAdmLocalId OBJECT-TYPE
   SYNTAX  DisplayString (SIZE (0..10))
   ACCESS  read-write
   STATUS  optional
   DESCRIPTION
"Determines the administrative ID (name) for the local voice station.

Note:

This object must be defined in order to obtain a successful voice 
connection.

Range of Values: a maximum of 10 alphanumeric characters in upper-case 
only. You can use any combination of letters and numbers; however you 
cannot use blank spaces. Use a dash or underscore as a delimiter.

Default Value: none

Configuration Changed: administrative"
   DEFVAL { "          " }
   ::= { cxMcVoxGlobal 6 }

cxMcVoxGlobalOpeLocalId OBJECT-TYPE
   SYNTAX  DisplayString (SIZE (0..10))
   ACCESS  read-only
   STATUS  optional
   DESCRIPTION
"Displays the operative ID (name) for the local voice station.

Note: This object must be defined in order to obtain a successful voice 
connection.

You cannot modify this object. If you want to change the ID you must 
modify the object cxMcVoxGlobalAdmLocalId (of this table).

Range of Values: a maximum of 10 alphanumeric characters in upper-case 
only. You can use any combination of letters and numbers; however you 
cannot use blank spaces. Use a dash or underscore as a delimiter.

Default Value: none"
   ::= { cxMcVoxGlobal 7 }

cxMcVoxGlobalTensionRing OBJECT-TYPE
   SYNTAX  INTEGER {
           down    (1),
           up      (2)
        }
   ACCESS  read-only
   STATUS  mandatory
   DESCRIPTION
"Displays the state of the ring generator power supply. The power supply 
resides on the ring generator card located on the voice I/O card.

You cannot modify this object. 

Options:

down (1)

up (2)

Default Value: none"
   ::= { cxMcVoxGlobal 8 }

cxMcVoxGlobalTensionDc OBJECT-TYPE
   SYNTAX  INTEGER {
           down    (1),
           up      (2)
        }
   ACCESS  read-only
   STATUS  mandatory
   DESCRIPTION
"Displays the state of the DC power supply on the voice I/O card.

Options:

down (1): The DC power supply on the voice I/O card is down.

up (2):The DC power supply on the voice I/O card is up.

Default Value: none"
   ::= { cxMcVoxGlobal 9 }

cxMcVoxGlobalTrapRing OBJECT-TYPE
   SYNTAX  INTEGER  {
           disable (1),
           enable  (2)
        }
   ACCESS  read-write
   STATUS  mandatory
   DESCRIPTION
"Determines if the ring generator power supply trap is generated.

The setting of this object is dynamic. When set to 'enable', the SNMP 
agent immediately begins to monitor the ring generator power supply.

Options:
disable (1): No trap is generated.

enable (2): Causes a trap message to be sent to the network management 
console each time a change occurs in the functional state (i.e., up or 
down) of the ring generator power supply. 

Default Value: disable (1)

Configuration Changed: operative"
   DEFVAL { disable }
   --#STARTING-VERSION 5
   ::= { cxMcVoxGlobal 10 }

cxMcVoxGlobalTrapDc OBJECT-TYPE
   SYNTAX  INTEGER {
           disable (1),
           enable  (2)
        }
   ACCESS  read-write
   STATUS  mandatory
   DESCRIPTION
"Determines if the DC power supply trap is generated. The setting of this 
object is dynamic. When set to 'enable', the SNMP agent immediately begins 
to monitor the DC power supply.

Options:
disable (1): No trap is generated.

enable (2): Causes a trap message to be sent to the network management 
consoleto each time a change occurs in the functional state (i.e., up or 
down) of the voice I/O card DC power supply. 

Default Value: disable (1)

Configuration Changed: operative"
   DEFVAL { disable }
   --#STARTING-VERSION 5
   ::= { cxMcVoxGlobal 11 }

cxMcVoxGlobalAdmGrpNbPoll OBJECT-TYPE
   SYNTAX INTEGER (1..20)
   ACCESS  read-write
   STATUS  deprecated
   DESCRIPTION
"The maximum number of remote voice station(s) that the the local voice 
station polls within a single call request has been moved from the Global 
Parameters group to the Group ID Entries group.

Determines the maximum number of remote voice stations that the local 
voice station polls with a single call request.

Note: This object is only relevant if at least one Group ID has been 
defined using the objects in the cxMcVox Administrative Grp Group.

Range of Values: 1 to 20

Default Value: 4

Configuration Changed: administrative"
   DEFVAL { 4 }
   --#ENDING-VERSION 1
   ::= { cxMcVoxGlobal 12 }

cxMcVoxGlobalOpeGrpNbPoll OBJECT-TYPE
   SYNTAX INTEGER (1..20)
   ACCESS  read-only
   STATUS  deprecated
   DESCRIPTION
"The the maximum number of remote voice stations the local voice station 
polls with a single call request. has been moved from the Global 
Parameters group to the Group ID Entries group.

Displays the maximum number of remote voice stations the local voice 
station polls with a single call request.

Note: This object is only relevant if at least one Group ID has been 
defined with the objects in the cxMcVox Administrative Grp Group Table.

You cannot modify this object. If you want to change this value you must 
modify the object cxMcVoxGlobalAdmNbPoll (of this table).

Range of Values: 1 to 20

Default Value: 4"
   --#ENDING-VERSION 1
   ::= { cxMcVoxGlobal 13 }

cxMcVoxGlobalClearGrp OBJECT-TYPE
   SYNTAX  INTEGER {
           no      (1),
           yes     (2)
        }
   ACCESS  read-write
   STATUS  optional
   DESCRIPTION
"Determines whether to restore all administrative Group IDs to the default 
factory settings.

The setting of this object is dynamic. When set to 'yes' all 
administrative Group IDs will immediately change to the factory defaults.

Options:

no (1)

yes (2)

Default Value: no

Configuration Changed: administrative"
   DEFVAL { no }
   ::= { cxMcVoxGlobal 14 }


-- obsolete: The Operational Path Length commands 
--           are now in the Operational Path table.

cxMcVoxGlobalOpePathLng OBJECT-TYPE
   SYNTAX INTEGER (2..4)
   ACCESS  read-only
   STATUS  obsolete
   DESCRIPTION
"The Operational Path Length commands are now in the Operational Path 
table."
   DEFVAL { 3 }
   ::= { cxMcVoxGlobal 15 }

cxMcVoxGlobalReinitRouting OBJECT-TYPE
   SYNTAX  INTEGER {
           no      (1),
           yes     (2)
        }
   ACCESS  read-write
   STATUS  optional
   DESCRIPTION
"Triggers the reinitialization of the operative routing table.

The setting of this object is dynamic. When set to 'yes', all 
administrative routing, path and group entries will be written to the 
operative routing table (i.e. will be in the active global configuration).

Options:

no (1)

yes (2)

Default Value: no (1)

Configuration Changed: operative"
   DEFVAL { no }
   ::= { cxMcVoxGlobal 16 }

cxMcVoxGlobalForceDefConfig OBJECT-TYPE
   SYNTAX  INTEGER {
           no      (1),
           yes     (2)
        }
   ACCESS  read-write
   STATUS  optional
   DESCRIPTION
"Determines whether the default factory configuration will replace both 
the administrative and operative configurations.

The setting of this object is dynamic. When set to 'yes', this object 
triggers the immediate reconfiguration of all objects to the default 
factory settings.

Options:

no (1)

yes (2)

Default Value: no (1)

Configuration Changed: administrative"
   DEFVAL { no }
   ::= { cxMcVoxGlobal 17 }

cxMcVoxGlobalReinitPinTable OBJECT-TYPE
   SYNTAX  INTEGER {
           no      (1),
           yes     (2)
        }
   ACCESS  read-write
   STATUS  optional
   DESCRIPTION
"Saves the PIN table configuration in non-volatile memory, but only enables 
it if the object cxMcVoxGlobalAdmEnablePinTable is set to 'yes'.

Options:

no (1)

yes (2)

Default Value: no (1)"
   DEFVAL { no }
   --#STARTING-VERSION 4
   ::= { cxMcVoxGlobal 18 }

cxMcVoxGlobalAdmEnablePinTable OBJECT-TYPE
   SYNTAX  INTEGER {
           no      (1),
           yes     (2)
        }
   ACCESS  read-write
   STATUS  optional
   DESCRIPTION
"Specifies whether the voice station verifies PIN (Personal Identification 
Numbers) codes before allowing a connection to be established.

Options:

no (1)

yes (2)

Default Value: no (1)"
   DEFVAL { no }
   --#STARTING-VERSION 4
   ::= { cxMcVoxGlobal 19 }

cxMcVoxGlobalOpeEnablePinTable OBJECT-TYPE
   SYNTAX  INTEGER {
           no      (1),
           yes     (2)
        }
   ACCESS  read-only
   STATUS  optional
   DESCRIPTION
"Displays the operational state of PIN verification.

Options:

no (1)

yes (2)

Default Value: no (1)"
   DEFVAL { no }
   --#STARTING-VERSION 4
   ::= { cxMcVoxGlobal 20 }

cxMcVoxGlobalReinitCodesTable OBJECT-TYPE
   SYNTAX  INTEGER {
           no      (1),
           yes     (2)
        }
   ACCESS  read-write
   STATUS  optional
   DESCRIPTION
"Copy the planned zone code configuration table into active zone code
table (non-volatile memory).

Options:

no (1)

yes (2)

Default Value: no (1)"
   DEFVAL { no }
   --#STARTING-VERSION 3
   ::= { cxMcVoxGlobal 21 }

cxMcVoxGlobalAdmEnableCodesTable OBJECT-TYPE
   SYNTAX  INTEGER {
           no      (1),
           yes     (2)
        }
   ACCESS  read-write
   STATUS  optional
   DESCRIPTION
"The CX900 does not currently support this object.

Specifies whether the voice station verifies incoming telephone codes 
against its internal remote translation table.

Options:

no (1)

yes (2)

Default Value: no (1)"
   DEFVAL { no }
   ::= { cxMcVoxGlobal 22 }

cxMcVoxGlobalOpeEnableCodesTable OBJECT-TYPE
   SYNTAX  INTEGER {
           no      (1),
           yes     (2)
        }
   ACCESS  read-only
   STATUS  optional
   DESCRIPTION
"The CX900 does not currently support this object.

Displays the operational state of the remote translation table.

Options:

no (1)

yes (2)

Default Value: none"
   ::= { cxMcVoxGlobal 23 }

cxMcVoxGlobalSoftRev OBJECT-TYPE
   SYNTAX  DisplayString (SIZE (0..30))
   ACCESS  read-only
   STATUS  optional
   DESCRIPTION
"Displays the software revision of the local voice station .

You cannot modify this object. It is a display that the software provides.

Range of Values: a maximum of 30 alphanumeric characters

Default Value: none"
   ::= { cxMcVoxGlobal 24 }

--(!!!13 - cxMcVoxGlobalAcelpRev REMOVED and replaced by
--         2 new objects in the cxMcVoxCfgTable; see entries 14 and 15)

-- DO NOT INSERT ANY OBJECT HERE *****************

-- ADVANCED MODE OBJECTS (index from 100)

cxMcVoxGlobalGlmInBetwReqTime OBJECT-TYPE
   SYNTAX INTEGER (10..2000)
   ACCESS  read-write
   STATUS  mandatory
   DESCRIPTION
"WARNING: YOU SHOULD NOT MODIFY THIS OBJECT WITHOUT THE SUPERVISION OF 
MEMOTEC PERSONNEL.

Range of Values: 10 to 2000

Default Value: 500"
   DEFVAL { 500 }
   ::= { cxMcVoxGlobal 100 }

cxMcVoxGlobalGlmMaxTimeToTxReq OBJECT-TYPE
   SYNTAX INTEGER (10..20000)
   ACCESS  read-write
   STATUS  mandatory
   DESCRIPTION
"WARNING: YOU SHOULD NOT MODIFY THIS OBJECT WITHOUT THE SUPERVISION OF 
MEMOTEC PERSONNEL.

Range of Values: 10 to 20000

Default Value: 1500"
   DEFVAL { 1500 }
   ::= { cxMcVoxGlobal 101 }

cxMcVoxGlobalGlmInBetwRespTime OBJECT-TYPE
   SYNTAX INTEGER (10..2000)
   ACCESS  read-write
   STATUS  mandatory
   DESCRIPTION
"WARNING: YOU SHOULD NOT MODIFY THIS OBJECT WITHOUT THE SUPERVISION OF 
MEMOTEC PERSONNEL.

Range of Values: 10 to 20000

Default Value: 500"
   DEFVAL { 500 }
   ::= { cxMcVoxGlobal 102 }

cxMcVoxGlobalGlmMaxTimeToTxResp OBJECT-TYPE
   SYNTAX INTEGER (10..20000)
   ACCESS  read-write
   STATUS  mandatory
   DESCRIPTION
"WARNING: YOU SHOULD NOT MODIFY THIS OBJECT WITHOUT THE SUPERVISION OF 
MEMOTEC PERSONNEL.

Range of Values: 10 to 20000

Default Value: 1500"
   DEFVAL { 1500 }
   ::= { cxMcVoxGlobal 103 }

cxMcVoxGlobalGlmVoiceSilenceTime OBJECT-TYPE
   SYNTAX INTEGER (100..60000)
   ACCESS  read-write
   STATUS  mandatory
   DESCRIPTION
"WARNING: YOU SHOULD NOT MODIFY THIS OBJECT WITHOUT THE SUPERVISION OF 
MEMOTEC PERSONNEL.

Range of Values: 100 to 60000

Default Value: 3000"
   DEFVAL { 3000 }
   ::= { cxMcVoxGlobal 104 }

cxMcVoxGlobalGlmSupervSilenceTime OBJECT-TYPE
   SYNTAX INTEGER (1000..60000)
   ACCESS  read-write
   STATUS  mandatory
   DESCRIPTION
"WARNING: YOU SHOULD NOT MODIFY THIS OBJECT WITHOUT THE SUPERVISION OF 
MEMOTEC PERSONNEL.

Range of Values: 1000 to 60000

Default Value: 3000"
   DEFVAL { 3000 }
   ::= { cxMcVoxGlobal 105 }

cxMcVoxGlobalGsdAutoCnctDelay OBJECT-TYPE
   SYNTAX INTEGER (1..20000)
   ACCESS  read-write
   STATUS  mandatory
   DESCRIPTION
"WARNING: YOU SHOULD NOT MODIFY THIS OBJECT WITHOUT THE SUPERVISION OF 
MEMOTEC PERSONNEL.

Range of Values: 1 to 20000

Default Value: 1"
   DEFVAL { 1 }
   ::= { cxMcVoxGlobal 106 }

cxMcVoxGlobalClearLclExt OBJECT-TYPE
   SYNTAX  INTEGER {
           no      (1),
           yes     (2)
        }
   ACCESS  read-write
   STATUS  optional
   DESCRIPTION
"Clears Local Extensions after the next Reset. Planned Local Extensions 
are cleared immediately.

Options:

no (1): Local Extensions are not cleared.

yes (2): Local Extensions are cleared.

Default Value: no (1)

Configuration Change: administrative"
   DEFVAL { no }
   --#STARTING-VERSION 1
   ::= { cxMcVoxGlobal 107 }


cxMcVoxGlobalClearRmtExt OBJECT-TYPE
   SYNTAX  INTEGER {
           no      (1),
           yes     (2)
        }
   ACCESS  read-write
   STATUS  optional
   DESCRIPTION
"Clears Remote Extensions after the next Reset. Planned Remote Extensions 
are cleared immediately.

Options:

no (1): Remote Extensions are not cleared.

yes (2): Remote Extensions are cleared

Default Value: no (1)

Configuration Change: administrative"
   DEFVAL { no }
   --#STARTING-VERSION 1
   ::= { cxMcVoxGlobal 108 }

cxMcVoxGlobalWanSlot OBJECT-TYPE
   SYNTAX INTEGER (1..16)
   ACCESS  read-write
   STATUS  mandatory
   DESCRIPTION
"Determines the slot number of the FR600 card that is performing Voice 
Routing with the new Voice Routing scheme.

Range of Values: 1 to 16

Default Value: 1"
   DEFVAL { 1 }
   --#STARTING-VERSION 1
   ::= { cxMcVoxGlobal 109 }

cxMcVoxGlobalNetNbDigits OBJECT-TYPE
   SYNTAX INTEGER (1..4)
   ACCESS  read-write
   STATUS  mandatory
   DESCRIPTION
"Determines the number of digits used to represent Local Extensions, 
Remote Extensions and Remote Extension group IDs.

Range of Values: 1 to 4

Default Value: 3"
   DEFVAL { 3 }
   --#STARTING-VERSION 1
   ::= { cxMcVoxGlobal 110 }

cxMcVoxMibLevel OBJECT-TYPE
	SYNTAX	INTEGER
	ACCESS	read-only
	STATUS	mandatory
	DESCRIPTION
"Used to determine current MIB module release supported
by the agent. Object is in decimal."
	DEFVAL { 0 }
	--#STARTING-VERSION 1
	::= { cxMcVoxGlobal 111 }


cxMcVoxGlobalRecogAcc OBJECT-TYPE
   SYNTAX INTEGER {  
          disabled (1),
          enabled (2)
        }
   ACCESS  read-write
   STATUS  mandatory
   DESCRIPTION
"This specifies whether to recognize the defined Access Code.  With the
option enabled, if the Access Code is recognized, it is stripped from the
dialing digit flow and then the remaining digits are interpreted as the
code that has been really dialed."
   DEFVAL { disabled }
   --#STARTING-VERSION 3
  ::= { cxMcVoxGlobal 112 }


cxMcVoxGlobalAccCode OBJECT-TYPE
   SYNTAX  DisplayString (SIZE (1..5))
   ACCESS  read-write
   STATUS  mandatory
   DESCRIPTION
"Determines the numeric code to access the international network.

Range of Values: 1 to 5 numeric digits

Default Value: 011

Configuration Changed: operational"
	DEFVAL { "011" }
   --#STARTING-VERSION 3
  ::= { cxMcVoxGlobal 113 }


cxMcVoxGlobalAccCodeLng OBJECT-TYPE
	SYNTAX	INTEGER
	ACCESS	read-only
	STATUS	mandatory
	DESCRIPTION
"Determines the number of digits in the configured Access Code."
	DEFVAL { 3 }
	--#STARTING-VERSION 3
	::= { cxMcVoxGlobal 114 }

cxMcVoxGlobalAdmPinCodeLng OBJECT-TYPE
	SYNTAX	INTEGER
	ACCESS	read-write
	STATUS	mandatory
	DESCRIPTION
"Determines the administrative number of digits in all Personal
 Identification Numbers (PINs)."
	DEFVAL { 4 }
	--#STARTING-VERSION 4
	::= { cxMcVoxGlobal 115 }

cxMcVoxGlobalOpePinCodeLng OBJECT-TYPE
	SYNTAX	INTEGER
	ACCESS	read-only
	STATUS	mandatory
	DESCRIPTION
"Determines the operational number of digits in all Personal
 Identification Numbers (PINs)."
	DEFVAL { 4 }
	--#STARTING-VERSION 4
	::= { cxMcVoxGlobal 116 }

cxMcVoxGlobalClearHistoryTable  OBJECT-TYPE
     SYNTAX  INTEGER  {
          disable (1),
          enable  (2)
        }
     ACCESS  read-write
     STATUS  mandatory
     DESCRIPTION
"Determines whether to clear ALL logging information from the history table.
Options:

disable(1):     No action
enable(2):      Clear history table completely"
   --#STARTING-VERSION 5
     ::= { cxMcVoxGlobal 117 }

cxMcVoxGlobalHistoryMaxNumberOfEntries  OBJECT-TYPE
     SYNTAX INTEGER (20..256)
     ACCESS  read-write
     STATUS  mandatory
     DESCRIPTION
"The maximum number of entries in the history table."
    DEFVAL { 256 }
   --#STARTING-VERSION 5
     ::= { cxMcVoxGlobal 118 }

cxMcVoxGlobalHistoryPercentageFull  OBJECT-TYPE
     SYNTAX INTEGER (0..95)
     ACCESS  read-write
     STATUS  mandatory
     DESCRIPTION
"The percentage of the history table that must be filled before a trap is
sent to the management station."
    DEFVAL { 70 }
   --#STARTING-VERSION 5
     ::= { cxMcVoxGlobal 119 }

cxMcVoxGlobalTrapHistory OBJECT-TYPE
   SYNTAX  INTEGER  {
           disable (1),
           enable  (2)
        }
   ACCESS  read-write
   STATUS  mandatory
   DESCRIPTION
"Determines if the call history trap is generated.

The setting of this object is dynamic. When set to 'enable', the SNMP 
agent immediately begins to monitor the call history trap.

Options:
disable (1): No trap is generated.

enable (2): Causes a trap message to be sent to the network management 
console each time a change occurs in the functional state (i.e., up or 
down) of the ring generator power supply. 

Default Value: disable (1)

Configuration Changed: operative"
   DEFVAL { disable }
   --#STARTING-VERSION 5
   ::= { cxMcVoxGlobal 120 }

cxMcVoxGlobalLseTimerT2 OBJECT-TYPE
   SYNTAX INTEGER (0..65535)
   ACCESS  read-write
   STATUS  mandatory
   DESCRIPTION
"WARNING: YOU SHOULD NOT MODIFY THIS OBJECT WITHOUT THE SUPERVISION OF 
MEMOTEC PERSONNEL.

Range of Values: 0 to 65535

Default Value: 500"
   DEFVAL { 500 }
   --#STARTING-VERSION 9
   ::= { cxMcVoxGlobal 121 }

cxMcVoxGlobalLseTimerT3 OBJECT-TYPE
   SYNTAX INTEGER (0..65535)
   ACCESS  read-write
   STATUS  mandatory
   DESCRIPTION
"WARNING: YOU SHOULD NOT MODIFY THIS OBJECT WITHOUT THE SUPERVISION OF 
MEMOTEC PERSONNEL.

Range of Values: 0 to 65535

Default Value: 550"
   DEFVAL { 550 }
   --#STARTING-VERSION 9
   ::= { cxMcVoxGlobal 122 }

cxMcVoxGlobalExtBitMask OBJECT-TYPE
   SYNTAX INTEGER (0..255)
   ACCESS  read-write
   STATUS  mandatory
   DESCRIPTION
"This object is a bitmap that selects up to 
cxMcVoxGlobalNetNbDigits, which can be set up to 
4 digits, corresponding to a bit that is set. The default
value corresponds to 7 (or 00000111 in binary).

Range of Values: 0 to 255

Default Value: 7"
   DEFVAL { 7 }
   --#STARTING-VERSION 11
   ::= { cxMcVoxGlobal 123 }


-- ===================================================================

--  cxMcVox CONFIGURATION GROUP


cxMcVoxCfgTable OBJECT-TYPE
   SYNTAX  SEQUENCE OF CxMcVoxCfgEntry
   ACCESS  not-accessible
   STATUS  mandatory
   DESCRIPTION
"Voice station configuration Table."
   ::= { cxMcVox 2 }

cxMcVoxCfgEntry OBJECT-TYPE
   SYNTAX  CxMcVoxCfgEntry
   ACCESS  not-accessible
   STATUS  mandatory
   DESCRIPTION
"Voice station configuration row definition."
   INDEX { cxMcVoxCfgCardIndex,
cxMcVoxCfgPortIndex }
   ::= { cxMcVoxCfgTable 1 }

CxMcVoxCfgEntry ::=
   SEQUENCE {
      cxMcVoxCfgCardIndex     INTEGER,
      cxMcVoxCfgPortIndex     INTEGER,
      cxMcVoxCfgDriverAdmUsed INTEGER,
      cxMcVoxCfgDriverOpeUsed INTEGER,
      cxMcVoxCfgTrapOnLine    INTEGER,
      cxMcVoxCfgTrapOffLine   INTEGER,
      cxMcVoxCfgTrapStatus    INTEGER,
      cxMcVoxCfgTrapState     INTEGER,
      cxMcVoxCfgTestPort      INTEGER,
      cxMcVoxCfgToneTest      INTEGER,
      cxMcVoxCfgReinitPort    INTEGER,
      cxMcVoxCfgClearPort     INTEGER,
      cxMcVoxCfgOpeAcelpRev   DisplayString,
      cxMcVoxCfgCmdImmTest    INTEGER,
      cxMcVoxCfgCmdTest       INTEGER,
      cxMcVoxCfgMaxPktFrame   INTEGER,
      cxMcVoxCfgMaxSkew       INTEGER
    }

      cxMcVoxCfgCardIndex     OBJECT-TYPE
     SYNTAX INTEGER (1..8)
     ACCESS  read-only
     STATUS  mandatory
     DESCRIPTION
"Displays the slot number of the voice I/O card.

You cannot modify this object.

Range of Values:

CX900: 1 to 6

CX1000: 1 to 8

Default Value: none"
     ::= { cxMcVoxCfgEntry 1 }

      cxMcVoxCfgPortIndex  OBJECT-TYPE
     SYNTAX INTEGER (1..15)
     ACCESS  read-only
     STATUS  mandatory
     DESCRIPTION
"Displays the number of the voice port.

You cannot modify this object.

Options:

CX900: 1 is the only acceptable value. Each I/O card only has 1 port.

CX1000: up to 15 for the DI600

Default Value: none"
     ::= { cxMcVoxCfgEntry 2 }

      cxMcVoxCfgDriverAdmUsed OBJECT-TYPE
     SYNTAX   INTEGER {
          em(1),
          fxs(2),
          fxo(3)
           }
     ACCESS  read-write
     STATUS  mandatory
     DESCRIPTION
"Determines the administrative driver of the port. The driver controls 
which signals the port supports. A port can only support one type of 
driver at any one time.

Depending on the type of driver you choose, you must perform further 
configuration using one of the following tables:

- cxMcVoxEmAdmtable (for E&M drivers) - cxMcVoxFxsAdmTable (for FXS 
drivers) - cxMcVoxFxoAdmTable (for FXO drivers)

Options:

em (1): Recommended for a PBX connection. Provides RJ-12 and PB-45 port 
connectors.

fxs (2): Recommended for a standard telephone connection, where the 
Memotec device simulates a Telco. The device provides the ring and dial 
tone. FXS can also be used for a PBX connection, and provides an RJ-12 
port connector.

fxo (3): Recommended for a standard telephone connection, where the 
Memotec device simulates a telephone. FXO can also be used for a PBX 
connection, and provides an RJ-12 port connector.

Default Value: fxs (2)

Configuration Changed: administrative"
     DEFVAL { fxs }
     ::= { cxMcVoxCfgEntry 3 }

      cxMcVoxCfgDriverOpeUsed OBJECT-TYPE
     SYNTAX   INTEGER {
          em(1),
          fxs(2),
          fxo(3)
           }
     ACCESS  read-only
     STATUS  mandatory
     DESCRIPTION
"Displays the operative driver currently running on the port.

You cannot modify this object. If you want to change the value you must 
modify the object cxMcVoxCfgDriverAdmUsed (of this table).

Options:

em (1)

fxs (2)

fxo (3)

Default Value: fxs (2)"
     ::= { cxMcVoxCfgEntry 4 }

      cxMcVoxCfgTrapOnLine    OBJECT-TYPE
     SYNTAX   INTEGER {
           disable (1),
           enable (2)
        }
     ACCESS  read-write
     STATUS  deprecated
     DESCRIPTION
"Determines the state of the port's online trap.
 When set to 'enable', every time a fax or phone call begins (i.e. the 
port switches from online to offline), the SNMP agent generates a trap and 
sends it to the network management console.

The setting of this object is dynamic. When set to'enable' the SNMP agent 
immediately begins to monitor the port.

Options:

disable (1)

enable (2)

Default Value: disable (1)

Configuration Changed: operative"
     DEFVAL { disable }
     ::= { cxMcVoxCfgEntry 5 }

      cxMcVoxCfgTrapOffLine   OBJECT-TYPE
     SYNTAX   INTEGER { 
          disable (1),
          enable (2)
        }
     ACCESS  read-write
     STATUS  deprecated
     DESCRIPTION
"Determines the state of the port's offline trap.

When set to 'enable', every time a fax or phone call ends ( i.e. the port 
switches from offline to online) the SNMP agent generates a trap and sends 
it to the network management console.

The setting of this object is dynamic. When set to'enable' the SNMP agent 
immediately begins to monitor the port.

Options:

disable (1)

enable (2)

Default Value: disable (1)

Configuration Changed: operative"
     DEFVAL { disable }
     ::= { cxMcVoxCfgEntry 6 }

      cxMcVoxCfgTrapStatus    OBJECT-TYPE
     SYNTAX   INTEGER { 
          disable (1),
          enable (2)
        }
     ACCESS  read-write
     STATUS  mandatory
     DESCRIPTION
"Determines the state of the port's status trap.

When set to 'enable', every time the functional state of the voice channel 
changes (i.e. up or down) the SNMP agent generates a trap and sends it to 
the network management console.

The setting of this object is dynamic. When set to'enable' the SNMP agent 
immediately begins to monitor the voice channel.

Options:

disable (1)

enable (2)

Default Value: disable (1)

Configuration Changed: operative"
     DEFVAL { disable }
   --#STARTING-VERSION 5
     ::= { cxMcVoxCfgEntry 7 }

      cxMcVoxCfgTrapState     OBJECT-TYPE
     SYNTAX   INTEGER { 
          disable (1),
          enable (2)
        }
     ACCESS  read-write
     STATUS  deprecated
     DESCRIPTION
"Determines the state of the port's outgoing calls trap.

When set to 'enable', every time an outgoing call request is in process 
the SNMP agent generates a trap and sends it to the network management 
console.

The setting of this object is dynamic. When set to'enable' the SNMP agent 
immediately begins to monitor the port.

Options:

disable (1)

enable (2)

Default Value: disable (1)

Configuration Changed: operative"
     DEFVAL { disable }
     ::= { cxMcVoxCfgEntry 8 }

      cxMcVoxCfgTestPort      OBJECT-TYPE
     SYNTAX   INTEGER { 
          no (1),
          yes (2)
           }
     ACCESS  read-write
     STATUS  optional
     DESCRIPTION
"Determines the state of the port's self test.

When set to 'yes', this object triggers the port to intiate a self-test. 
The port examines various hardware components, for example the RAM, DPRAM 
and I/O access. Each test runs for less than 2 seconds. You can perform 
the test on either an open (call in progress) or closed channel. If you 
perform the test on an open channel the call that is in progress is 
disconnected. The user must place the call again after the test is 
complete.

Note:

The port must be set to 'enable' (using the object cxMcVoxEmAdmPortStatus, 
cxMcVoxFxoAdmstatus or cxMcVoxFxsAdmStatus) to be able to perform the 
self-test.

You can view the results of the test in the cxMcVoxStatusTable.

While the port is running a self-test, it is not functional. It will 
return to normal when the test is complete.

The setting of this object is dynamic. When set to'yes' the port 
immediately begins to monitor itself.

Options:

no (1)

yes (2)

Default Value: no (1)

Configuration Changed: operative "
     DEFVAL { no }
     ::= { cxMcVoxCfgEntry 9 }

      cxMcVoxCfgToneTest      OBJECT-TYPE
     SYNTAX   INTEGER { 
          disable (1),
          enable (2)
        }
     ACCESS  read-write
     STATUS  mandatory
     DESCRIPTION
"Determines the state of the port's standard tone test (1004Hz).

When set to 'enable', this object triggers the port to perform a tone 
test. The port tests its voice sound quality by transmitting a 1004Hz 
tone. You can perform the test on either an open (call in progress) or 
closed channel. However, if you initiate the test on an open channel, the 
connection is not disrupted, but the local user will not be able to hear 
the remote user. The local user will only hear the tone the test 
generates. You must set this object to 'disable' to stop the test. It does 
not stop on its own.

The setting of this object is dynamic. When set to'enable' the tone test 
begins immediately.

Options:

disable (1)

enable (2)

Default Value: disable (1)

Configuration Changed: operative"
     DEFVAL { disable }
     ::= { cxMcVoxCfgEntry 10 }

      cxMcVoxCfgReinitPort    OBJECT-TYPE
     SYNTAX   INTEGER { 
          no (1),
          yes (2)
           }
     ACCESS  read-write
     STATUS  optional
     DESCRIPTION
"Determines the port's reinitialization state.

The setting of this object is dynamic. When set to 'yes', this object 
triggers the port to write all administrative port configuration entries 
to the operative port configuration table (i.e. they will be in the active 
port configuration).

Options:

no (1)

yes (2)

Default Value: no (1)

Configuration Changed: administrative"
     DEFVAL { no }
     ::= { cxMcVoxCfgEntry 11 }

      cxMcVoxCfgClearPort     OBJECT-TYPE
     SYNTAX   INTEGER { 
          no (1),
          yes (2)
           }
     ACCESS  read-write
     STATUS  optional
     DESCRIPTION
"Determines whether to restore all administrative voice port 
configurations to the default factory settings.

The setting of this object is dynamic. When set to 'yes' the configuration 
of the administrative voice port (as displays in the objects 
cxMcVoxCfgCardIndex and cxMcVoxCfgPortIndex) will immediately change to 
the factory defaults.

Options:

no (1)

yes (2)

Default Value: no (1)

Configuration Changed: administrative"
     DEFVAL { no }
     ::= { cxMcVoxCfgEntry 12 }

    cxMcVoxCfgOpeAcelpRev OBJECT-TYPE
       SYNTAX  DisplayString (SIZE (0..12))
       ACCESS  read-only
       STATUS  optional
       DESCRIPTION
"Displays the ACELP software revision currently running on the operative 
voice channel.

Range of Values: 0 to 12 alphanumeric characters. You can use any 
combination of letters and numbers, however you cannot use blank spaces. 
Use a dash or underscore as a delimiter.

Default Value: ACELP-2.BIN"
     ::= { cxMcVoxCfgEntry 14 }

      cxMcVoxCfgCmdImmTest     OBJECT-TYPE
     SYNTAX  INTEGER (0..4294967295)
     ACCESS  read-write
     STATUS  mandatory
     DESCRIPTION
"WARNING: YOU SHOULD NOT MODIFY THIS OBJECT WITHOUT THE SUPERVISION OF 
MEMOTEC PERSONNEL.

Range of Values: 0 to 4294967295

Default Value: 0"
     ::= { cxMcVoxCfgEntry 15 }

      cxMcVoxCfgCmdTest     OBJECT-TYPE
     SYNTAX  INTEGER (0..4294967295)
     ACCESS  read-write
     STATUS  mandatory
     DESCRIPTION
"WARNING: YOU SHOULD NOT MODIFY THIS OBJECT WITHOUT THE SUPERVISION OF 
MEMOTEC PERSONNEL.

Range of Values: 0 to 4294967295

Default Value: 0"
     ::= { cxMcVoxCfgEntry 16 }

     cxMcVoxCfgMaxPktFrame	OBJECT-TYPE
     SYNTAX			INTEGER (1..3)
     ACCESS			read-write
     STATUS			mandatory
     DESCRIPTION
"The number of voice packet included in a voice frame.  Less voice 
packet there is in a frame, bigger is the bandwitdh overhead on the 
WAN link, but better is the voice path end-to-end delay.  The best 
compromise is a size of two (2) voice packets per voice frame, which 
correpsond to the default value."
     DEFVAL	{ 2 }
   --#STARTING-VERSION 5
     ::=	{ cxMcVoxCfgEntry 17 }

     cxMcVoxCfgMaxSkew	OBJECT-TYPE
     SYNTAX			INTEGER (25..125)
     ACCESS			read-write
     STATUS			mandatory
     DESCRIPTION
"The number of msec of skew that the end-to-end synchronization 
algorithm must compensate."
     DEFVAL	{ 50 }
   --#STARTING-VERSION 5
     ::=	{ cxMcVoxCfgEntry 18 }



-- ===================================================================

--  cxMcVox STATISTICS & LOG HISTORY GROUP 


cxMcVoxStatAndLog       OBJECT IDENTIFIER ::= { cxMcVox 3}



--  cxMcVox STATUS GROUP TABLE


cxMcVoxStatusTable OBJECT-TYPE
   SYNTAX  SEQUENCE OF CxMcVoxStatusEntry
   ACCESS  not-accessible
   STATUS  mandatory
   DESCRIPTION
"Voice station status table."
   ::= { cxMcVoxStatAndLog 1 }

cxMcVoxStatusEntry OBJECT-TYPE
   SYNTAX  CxMcVoxStatusEntry
   ACCESS  not-accessible
   STATUS  mandatory
   DESCRIPTION
"Voice station status row definition."
   INDEX { cxMcVoxStatusCardNumber, cxMcVoxStatusPortNumber }
   ::= { cxMcVoxStatusTable 1 }

CxMcVoxStatusEntry ::=
   SEQUENCE {
      cxMcVoxStatusCardNumber     INTEGER,
      cxMcVoxStatusPortNumber     INTEGER,
      cxMcVoxStatusPortStatus     INTEGER,
      cxMcVoxStatusHookLocal      INTEGER,
      cxMcVoxStatusHookRem        INTEGER,
      cxMcVoxStatusIoAccess       INTEGER,
      cxMcVoxStatusChannelAccess  INTEGER,
      cxMcVoxStatusDspRam         INTEGER,
      cxMcVoxStatusDspDpram       INTEGER,
      cxMcVoxStatusSamplingTime   INTEGER,
      cxMcVoxStatusWatchdog       INTEGER,
      cxMcVoxStatusRemPortStatus  INTEGER,
      cxMcVoxStatusInputDbmLevel  INTEGER,
      cxMcVoxStatusDspUtilization INTEGER,
      cxMcVoxStatusPhyIfType      INTEGER,
      cxMcVoxStatusIOResetState   INTEGER
      }

      cxMcVoxStatusCardNumber OBJECT-TYPE
     SYNTAX INTEGER (1..8)
     ACCESS  read-only
     STATUS  mandatory
     DESCRIPTION
"Displays the slot number of the voice I/O card.

You cannot modify this object. It is a display that the software provides.

Range of Values:

CX900: 1 to 6

CX1000: 1 to 8

Default Value: none"
     ::= { cxMcVoxStatusEntry 1 }

      cxMcVoxStatusPortNumber OBJECT-TYPE
     SYNTAX INTEGER (1..15)
     ACCESS  read-only
     STATUS  mandatory
     DESCRIPTION
"Displays the number of the voice I/O port.

You cannot modify this object. It is a display that the software provides.

Options:

CX900: 1 is the only acceptable value. Each I/O card only has 1 port.

CX1000: up to 15 for the DI600

Default Value: none"
     ::= { cxMcVoxStatusEntry 2 }

      cxMcVoxStatusPortStatus    OBJECT-TYPE
     SYNTAX   INTEGER { 
          disable (1),
          enable (2),
          no-voice-io (3),
          boot-err-1 (31),
          boot-err-2 (32),
          boot-err-3 (33),
          boot-err-4 (34),
          appl-err-1 (41),
          appl-err-2 (42),
          appl-err-3 (43),
          appl-err-4 (44)
           }
     ACCESS  read-only
     STATUS  mandatory
     DESCRIPTION
"Displays the functional status of the port.

You cannot modify this object. It is a display that the software provides.

Options:

disable (1): port is not functional

enable (2): port is up and active

no-voice-io (3): Memotec use only. Contact Memotec service personnel if 
this value displays.

boot-err-1 (31): Memotec use only. Contact Memotec service personnel if 
this value displays.

boot-err-2 (32): Memotec use only. Contact Memotec service personnel if 
this value displays.

boot-err-3 (33): Memotec use only. Contact Memotec service personnel if 
this value displays.

boot-err-4 (34): Memotec use only. Contact Memotec service personnel if 
this value displays.

appl-err-1 (41): Memotec use only. Contact Memotec service personnel if 
this value displays.

appl-err-2 (42): Memotec use only. Contact Memotec service personnel if 
this value displays.

appl-err-3 (43): Memotec use only. Contact Memotec service personnel if 
this value displays.

appl-err-4 (44): Memotec use only. Contact Memotec service personnel if 
this value displays.

Default Value: none"
     ::= { cxMcVoxStatusEntry 3 }

      cxMcVoxStatusHookLocal     OBJECT-TYPE
     SYNTAX   INTEGER {
           on      (1),
           off     (2),
           unknown (3)
           }
     ACCESS  read-only
     STATUS  mandatory
     DESCRIPTION
"Displays the state of the local port's ability to establish a connection. 
When the status shows 'on', the port is idle and ready to transmit.

You cannot modify this object. It is a display that the software provides.

Options:

on (1): port is in the on-hook state and is able to establish a 
connection.

off (2): port is in the off-hook state and cannot establish a connection. 
"
     ::= { cxMcVoxStatusEntry 4 }

      cxMcVoxStatusHookRem    OBJECT-TYPE
     SYNTAX   INTEGER {
           on      (1),
           off     (2),
           unknown (3)
           }
     ACCESS  read-only
     STATUS  mandatory
     DESCRIPTION
"Displays the state of the remote port's ability to establish a 
connection. When the status shows 'on', the remote port is idle and ready 
to transmit.

You cannot modify this object. It is a display that the software provides.

Options:

on (1): port is in the on-hook state and is able to establish a 
connection.

off (2): port is in the off-hook state and cannot establish a connection.

unknown (3)
"
     ::= { cxMcVoxStatusEntry 5 }

    cxMcVoxStatusIoAccess   OBJECT-TYPE     
    SYNTAX  INTEGER { fault (1),
                      passed (2),
                      inapplicable (3),
                      running (4)       }     
    ACCESS read-only     
    STATUS mandatory     
    DESCRIPTION 
"Displays the results of the test that the CPU performs on the 
accessibility of the voice channel control registers residing on the voice 
I/O card.

This object displays results from the self-test which you initiate using 
the object cxMcVoxCfgtestPort (of the cxMcVox Configuration Group table).

You cannot modify this object.

Options:

fault (1): CPU cannot access the voice channel registers on the voice I/O 
card. Contact Memotec service personnel.

passed (2): CPU is able to access the voice channel registers on the voice 
I/O card.

inapplicable (3): self-test has not been run since last system reset.

running (4): self-test is currently running. Results are not yet 
available.

Default Value: none"
     ::= { cxMcVoxStatusEntry 6 }

      cxMcVoxStatusChannelAccess OBJECT-TYPE
     SYNTAX   INTEGER { 
           fault (1),
           passed (2),
           inapplicable (3),
           running (4)
           }
     ACCESS  read-only
     STATUS  mandatory
     DESCRIPTION
"Displays the results of the test the CPU performs on the DPRAM.

This object displays results from the self-test which you initiate using 
the object cxMcVoxCfgtestPort (of the cxMcVox Configuration Group table).

You cannot modify this object.

Options:

fault (1): CPU cannot access the DPRAM. Contact Memotec service personnel.

passed (2): CPU is able to access DPRAM.

inapplicable (3): self-test has not been run since last system reset.

running (4): self-test is currently running. Results are not yet 
available.

Default Value: none"
     ::= { cxMcVoxStatusEntry 7 }

      cxMcVoxStatusDspRam     OBJECT-TYPE
     SYNTAX   INTEGER {
           fault (1),
           passed (2),
           inapplicable (3),
           running (4)
           }
     ACCESS  read-only
     STATUS  mandatory
     DESCRIPTION
"Displays the results of the test the DSP performs on the accessibility of 
the RAM memory on the voice I/O card.

This object displays results from the self-test which you initiate using 
the object cxMcVoxCfgtestPort (of the cxMcVox Configuration Group table).

You cannot modify this object.

Options:

fault (1): DSP cannot access the RAM memory on the voice I/O card. Contact 
Memotec service personnel.

passed (2): DSP is able to access RAM memory.

inapplicable (3): self-test has not been run since last system reset.

running (4): self-test is currently running. Results are not yet 
available.

Default Value: none"
     ::= { cxMcVoxStatusEntry 8 }

      cxMcVoxStatusDspDpram      OBJECT-TYPE
     SYNTAX   INTEGER {
           fault (1),
           passed (2),
           inapplicable (3),
           running (4)
           }
     ACCESS  read-only
     STATUS  mandatory
     DESCRIPTION
"Displays the results of the test the DSP performs on the voice I/O card's 
DPRAM memory.

This object displays results from the self-test which you initiate using 
the object cxMcVoxCfgtestPort (of the cxMcVox Configuration Group table).

You cannot modify this object. 

Options:

fault (1): DSP cannot access the DPRAM memory on the voice I/O card. 
Contact Memotec service personnel.

passed (2): DSP is able to access DPRAM memory on the voice I/O card.

inapplicable (3): self-test has not been run since last system reset.

running (4): self-test is currently running. Results are not yet 
available.

Default Value: none"
     ::= { cxMcVoxStatusEntry 9 }

      cxMcVoxStatusSamplingTime  OBJECT-TYPE
     SYNTAX   INTEGER {
           fault (1),
           passed (2),
           inapplicable (3),
           running (4)
           }
     ACCESS  read-only
     STATUS  mandatory
     DESCRIPTION
"Displays the results of the test the DSP performs on the sampling rate of 
a voice stream. The DSP tests that the sampling rate is done at 8KHz.

This object displays results from the self-test which you initiate using 
the object cxMcVoxCfgtestPort (of the cxMcVox Configuration Group table).

You cannot modify this object.

Options:

fault (1): DSP cannot test sampling rate. Contact Memotec service 
personnel.

passed (2): DSP is able to test sampling rate and it is at 8KHz.

inapplicable (3): self-test has not been run since last system reset.

running (4): self-test is currently running. Results are not yet 
available.

Default Value: none"
     ::= { cxMcVoxStatusEntry 10 }

      cxMcVoxStatusWatchdog      OBJECT-TYPE
     SYNTAX   INTEGER { 
           fault (1),
           passed (2),
           inapplicable (3),
           running (4)
        }
     ACCESS  read-only
     STATUS  mandatory
     DESCRIPTION
"Displays the results of the test the CPU performs on the watchdog timer 
which resides on the voice I/O card.

This object displays results from the self-test which you initiate using 
the object cxMcVoxCfgtestPort (of the cxMcVox Configuration Group table).

You cannot modify this object.

Options:

fault (1): CPU cannot access the watchdog timer. Contact Memotec service 
personnel.

passed (2): CPU is able to access watchdog timer and it is performing 
properly.

inapplicable (3): self-test has not been run since last system reset.

running (4): self-test is currently running. Results are not yet 
available.

Default Value: none"
     ::= { cxMcVoxStatusEntry 11 }

      cxMcVoxStatusRemPortStatus  OBJECT-TYPE
     SYNTAX INTEGER (0..4294967295)
     ACCESS  read-only
     STATUS  mandatory
     DESCRIPTION
"Displays the channel number of the attached remote port.

You cannot modify this object. 

Range of Values: 0-4294967295"
     ::= { cxMcVoxStatusEntry 12 }

      cxMcVoxStatusInputDbmLevel  OBJECT-TYPE
     SYNTAX   INTEGER (700..1050)
     ACCESS  read-only
     STATUS  mandatory
     DESCRIPTION
"Displays the current Dbm level of the input analog voice signal.

You cannot modify this object. .

Range of Values: 700 to 1050 (-30dBm to 5dBm)

Default Value: none"
     ::= { cxMcVoxStatusEntry 13 }


      cxMcVoxStatusPhyIfType  OBJECT-TYPE
     SYNTAX   INTEGER {
            if-em      (1),
            if-fxs     (2),
            if-fxo     (3),
            if-absent  (4),
            if-unknown (5)
          }
     ACCESS  read-only
     STATUS  mandatory
     DESCRIPTION
""
     ::= { cxMcVoxStatusEntry 14 }


-- ADVANCED MODE OBJECTS: (start at index 100)

      cxMcVoxStatusDspUtilization  OBJECT-TYPE
     SYNTAX   INTEGER (0..1000)
     ACCESS  read-only
     STATUS  mandatory
     DESCRIPTION
"WARNING: YOU SHOULD NOT MODIFY THIS OBJECT WITHOUT THE SUPERVISION OF 
MEMOTEC PERSONNEL.

Range of Values: 0 to 1000

Default Value: none"
     ::= { cxMcVoxStatusEntry 100 }

      cxMcVoxStatusIOResetState  OBJECT-TYPE
     SYNTAX   INTEGER { 
           in-reset (1),
           normal   (2),
           unknown  (3)
        }
     ACCESS  read-only
     STATUS  mandatory
     DESCRIPTION
"WARNING: YOU SHOULD NOT MODIFY THIS OBJECT WITHOUT THE SUPERVISION OF 
MEMOTEC PERSONNEL.

Options:

in-reset (1)

normal (2)

unknown (3)"
     ::= { cxMcVoxStatusEntry 101 }



-- ...................................................................

--  cxMcVox EVENTS GROUP TABLE 


cxMcVoxEventTable OBJECT-TYPE
   SYNTAX  SEQUENCE OF CxMcVoxEventEntry
   ACCESS  not-accessible
   STATUS  deprecated
   DESCRIPTION
"OnLine/OffLine events table for incoming/outgoing calls."
 	 --#ENDING-VERSION 5
   ::= { cxMcVoxStatAndLog 2 }

cxMcVoxEventEntry OBJECT-TYPE
   SYNTAX  CxMcVoxEventEntry
   ACCESS  not-accessible
   STATUS  deprecated
   DESCRIPTION
"Online/Offline events row definition."
   INDEX { cxMcVoxEventCardNumber, cxMcVoxEventPortNumber, 
   cxMcVoxEventLogIndex }
   ::= { cxMcVoxEventTable 1 }

CxMcVoxEventEntry ::=
   SEQUENCE {
      cxMcVoxEventCardNumber           INTEGER,
      cxMcVoxEventPortNumber           INTEGER,
      cxMcVoxEventLogIndex             INTEGER,
      cxMcVoxEventDateAndTimeOnLine    DisplayString,
      cxMcVoxEventDateAndTimeOffLine   DisplayString,
      cxMcVoxEventPhoneNumber          DisplayString,
      cxMcVoxEventLnkState             INTEGER,
      cxMcVoxEventPin                  DisplayString,
      cxMcVoxEventClrEvts              INTEGER
    }

      cxMcVoxEventCardNumber  OBJECT-TYPE
     SYNTAX INTEGER (1..4)
     ACCESS  read-only
     STATUS  deprecated
     DESCRIPTION
"Displays the slot number of the voice I/O card.

You cannot modify this object.

Range of Values:

CX900: 1 to 6

CX1000: 1 to 4

Default Value: none"
     ::= { cxMcVoxEventEntry 1 }

      cxMcVoxEventPortNumber  OBJECT-TYPE
     SYNTAX INTEGER (1..2)
     ACCESS  read-only
     STATUS  deprecated
     DESCRIPTION
"Displays the number of the voice I/O port.

You cannot modify this object. 

Options:

CX900: 1 is the only acceptable value. Each I/O card only has 1 port.

CX1000: 1 or 2

Default Value: none"
     ::= { cxMcVoxEventEntry 2 }

      cxMcVoxEventLogIndex    OBJECT-TYPE
     SYNTAX   INTEGER (1..4294967295)
     ACCESS  read-only
     STATUS  deprecated
     DESCRIPTION
"Displays the index number of the event log.

You cannot modify this object. 

Range of Values: 1 to 4294967295

Default Value: none"
     ::= { cxMcVoxEventEntry 3 }

      cxMcVoxEventDateAndTimeOnLine    OBJECT-TYPE
     SYNTAX  DisplayString (SIZE (20..20))
     ACCESS  read-only
     STATUS  deprecated
     DESCRIPTION
"Displays the date and time of the last online event. An online event is 
any incoming or outgoing call that the voice station generates. The format 
of the display is as follows:

Year/Month/Date-Day-Hours:Minutes:Seconds

You cannot modify this object. 

Range of Values:

Year: 0-99

Month: 1-12

Date: 1-31 (day of the month)

Day : 0-6 (day of the week - 0 being Sunday)

Hours: 0-23

Minutes: 0-59

Seconds: 0-59

Default Value: none"
     ::= { cxMcVoxEventEntry 4 }

      cxMcVoxEventDateAndTimeOffLine   OBJECT-TYPE
     SYNTAX  DisplayString (SIZE (20..20))
     ACCESS  read-only
     STATUS  deprecated
     DESCRIPTION
"Displays the date and time of the last offline event. An offline event is 
any incoming or outgoing call that the voice station terminates. The 
format of the display is as follows:

Year/Month/Date-Day-Hours:Minutes:Seconds

You cannot modify this object.

Range of Values:

Year: 0-99

Month: 1-12

Date: 1-31 (day of the month)

Day : 0-6 (day of the week - 0 being Sunday)

Hours: 0-23

Minutes: 0-59

Seconds: 0-59

Default Value: none"
     ::= { cxMcVoxEventEntry 5 }

      cxMcVoxEventPhoneNumber   OBJECT-TYPE
     SYNTAX  DisplayString (SIZE (1..32))
     ACCESS  read-only
     STATUS  deprecated
     DESCRIPTION
"Displays the phone number (including any voice mail digits) the user 
enters to reach a remote telephone or fax machine. This object is 
irrelevant for incoming calls.

You cannot modify this object.

Range of Values: 1 to 32 numeric digits

Default Value: none"
     ::= { cxMcVoxEventEntry 6 }

      cxMcVoxEventLnkState OBJECT-TYPE
     SYNTAX INTEGER {
          remUnavailable (1),
          remError (2), 
          busy (3),
          open (4),
          errActiveChn (5),
          errPath (6),
          errLnk (7),
          fixedLnkDown (8),
          fixedLnkUp (9)
        }
     ACCESS  read-only
     STATUS  deprecated
     DESCRIPTION
"Displays the status of the link to the remote telephone or fax machine.

You cannot modify this object.

Options:

remUnavailable (1): the routing specifies a remote chassis location that 
does not exist.

remError (2): all voice ports at the specified remote are inactive and 
therefore cannot accept the call. It is possible that the remote ports are 
disabled or that the I/O card is not installed.

busy (3): all voice ports at the specified remote are busy and therefore 
unavailable to accept the call.

open (4): the call was successfully put through to a voice port at the 
remote location.

errActiveChn (5): the end-user has replaced the receiver (on-hook) at the 
end of a call and then removed the receiver (off-hook) so quickly that the 
connection has not had sufficient time to completely disconnect. The 
end-user should wait a few seconds after replacing the receiver before 
attempting to place another call.

errPath (6): the Path ID (dialing code) the user entered is not listed in 
the routing table. Check that the Path ID and routing are completely 
configured.

errLnk (7): there is an error condition on the line between the local and 
remote link stations causing the link to be inactive.

fixedLnkDown (8): Memotec use only. Contact Memotec service personnel if 
this value displays.

fixedLnkUp (9): Memotec use only. Contact Memotec service personnel if 
this value displays.

Default Value: none"
     ::= { cxMcVoxEventEntry 7 }

    cxMcVoxEventPin OBJECT-TYPE
       SYNTAX  DisplayString (SIZE (2..8))
       ACCESS  read-only
       STATUS  deprecated
       DESCRIPTION
"Displays the Personal Identification Number (PIN) that is validated 
against the local voice station card PIN number table.

Range of Values: 2 to 8 numeric digits, each number from 0 to 9

Default Value: none"
   --#STARTING-VERSION 4
     ::= { cxMcVoxEventEntry 8 }

    cxMcVoxEventClrEvts OBJECT-TYPE
   SYNTAX  INTEGER {
           no      (1),
           yes     (2)
        }
   ACCESS  read-write
   STATUS  deprecated
   DESCRIPTION
"Determines whether to clear ALL logging information from the Event 
group table.

Options:

no (1)

yes (2)

Default Value: no (1)

Configuration Change: none"
   DEFVAL { no }
   --#STARTING-VERSION 1
     ::= { cxMcVoxEventEntry 9 }



-- ...................................................................

--  cxMcVox STATE GROUP TABLE 


cxMcVoxStateTable OBJECT-TYPE
   SYNTAX  SEQUENCE OF CxMcVoxStateEntry
   ACCESS  not-accessible
   STATUS  deprecated
   DESCRIPTION
"Connections table for outgoing calls."
 	 --#ENDING-VERSION 5
   ::= { cxMcVoxStatAndLog 3 }

cxMcVoxStateEntry OBJECT-TYPE
   SYNTAX  CxMcVoxStateEntry
   ACCESS  not-accessible
   STATUS  deprecated
   DESCRIPTION
"Outgoing call connection state row definition."
   INDEX { cxMcVoxStateCardNumber, cxMcVoxStatePortNumber, 
   cxMcVoxStateLogIndex }
   ::= { cxMcVoxStateTable 1 }

CxMcVoxStateEntry ::=
   SEQUENCE {
      cxMcVoxStateCardNumber     INTEGER,
      cxMcVoxStatePortNumber     INTEGER,
      cxMcVoxStateLogIndex       INTEGER,
      cxMcVoxStatePathId         DisplayString,
      cxMcVoxStateDateAndTime    DisplayString,
      cxMcVoxStateLnkState       INTEGER,
      cxMcVoxStateRmtExt         DisplayString
    }

      cxMcVoxStateCardNumber  OBJECT-TYPE
     SYNTAX INTEGER (1..4)
     ACCESS  read-only
     STATUS  deprecated
     DESCRIPTION
"Displays the slot number of the voice I/O card.

You cannot modify this object. It is a display that the software provides.

Range of Values:

CX900: 1 to 6 

CX1000: 1 to 4

Default Value: none"
     ::= { cxMcVoxStateEntry 1 }

      cxMcVoxStatePortNumber  OBJECT-TYPE
     SYNTAX INTEGER (1..2)
     ACCESS  read-only
     STATUS  deprecated
     DESCRIPTION
"Displays the number of the voice I/O port.

You cannot modify this object. It is a display that the software provides.

Options:

CX900: 1 is the only acceptable value. Each I/O card on has 1 port.

CX1000: 1 or 2

Default Value: none"
     ::= { cxMcVoxStateEntry 2 }

      cxMcVoxStateLogIndex    OBJECT-TYPE
     SYNTAX   INTEGER (1..4294967295)
     ACCESS  read-only
     STATUS  deprecated
     DESCRIPTION
"Displays the number of the table row containing objects used for 
monitoring the path state.

You cannot modify this object. 

Range of Values: 1 to 4294967295

Default Value: none"
     ::= { cxMcVoxStateEntry 3 }

      cxMcVoxStatePathId      OBJECT-TYPE
     SYNTAX  DisplayString (SIZE (1..4))
     ACCESS  read-only
     STATUS  deprecated
     DESCRIPTION
"Displays the Path ID or Group ID that the user dials to access 
the remote telephone or fax machine.

Displays the Path ID or Group ID that the user dials to access the remote 
telephone or fax machine.

You cannot modify this object. If you want to change the value you must 
modify the object cxMcVoxPathAdmPathId of the cxMcVox Administrative Path 
Group.

Range of Values: 1 to 4 numeric digits

Default Value: none"
 	 --#ENDING-VERSION 1
     ::= { cxMcVoxStateEntry 4 }

      cxMcVoxStateDateAndTime    OBJECT-TYPE
     SYNTAX  DisplayString (SIZE (20..20))
     ACCESS  read-only
     STATUS  deprecated
     DESCRIPTION
"Displays the date and time the link associated with the Path/Group ID 
changed state (i.e. the call was initiated). The format of the display is 
as follows:

Year/Month/Date-Day-Hours:Minutes:Seconds

You cannot modify this object.

Range of Values:

Year: 0-99

Month: 1-12

Date: 1-31 (day of the month)

Day : 0-6 (day of the week, 0 being Sunday)

Hours: 0-23

Minutes: 0-59

Seconds: 0-59

Default Value: none"
     ::= { cxMcVoxStateEntry 5 }

      cxMcVoxStateLnkState OBJECT-TYPE
     SYNTAX INTEGER {
          remUnavailable (1),
          remError (2), 
          busy (3),
          open (4),
          errActiveChn (5),
          errPath (6),
          errLnk (7),
          fixedLnkDown (8),
          fixedLnkUp (9)
        }
     ACCESS  read-only
     STATUS  deprecated
     DESCRIPTION
"Displays the status of the link to the remote telephone or fax machine.

You cannot modify this object.

Options:

remUnavailable (1): the routing specifies a remote chassis location that 
does not exist.

remError (2): all voice ports at the specified remote are inactive and 
therefore cannot accept the call. It is possible that the remote ports are 
disabled or that the I/O card is not installed.

busy (3): all voice ports at the specified remote are busy and therefore 
unavailable to accept the call.

open (4): the call was successfully put through to a voice port at the 
remote location.

errActiveChn (5): the end-user has replaced the receiver (on-hook) at the 
end of a call and then removed the receiver (off-hook) so quickly that the 
connection has not had sufficient time to completely disconnect. The 
end-user should wait a few seconds after replacing the receiver before 
attempting to place another call.

errPath (6): the Path ID (dialing code) the user entered is not listed in 
the routing table. Check that the Path ID and routing are completely 
configured. 

errLnk (7): there is an error condition on the line between the local and 
remote link stations causing the link to be inactive.

fixedLnkDown (8): Memotec use only. Contact Memotec sevice personnel if 
this value displays.

fixedLnkUp (9): Memotec use only. Contact Memotec service personnel if 
this value displays.

Default Value: none"
     ::= { cxMcVoxStateEntry 6 }

      cxMcVoxStateRmtExt      OBJECT-TYPE
     SYNTAX  DisplayString (SIZE (1..5))
     ACCESS  read-only
     STATUS  deprecated
     DESCRIPTION
"Displays the Remote Extension or Group ID that the user dials to access 
the remote telephone or fax machine.

You cannot modify this object.

Range of Values: 1 to 5 numeric digits

Default Value: none"
	 --#STARTING-VERSION 1
     ::= { cxMcVoxStateEntry 7 }



-- ======================================================================

--  cxMcVox ADMINISTRATIVE PATH GROUP

--  note: The path ID table must be defined after the net ID table.


cxMcVoxPathAdmTable OBJECT-TYPE
   SYNTAX  SEQUENCE OF CxMcVoxPathAdmEntry
   ACCESS  not-accessible
   STATUS  deprecated
   DESCRIPTION
"Planned pathID table."
   --#ENDING-VERSION 1
   ::= { cxMcVox 4 }

cxMcVoxPathAdmEntry OBJECT-TYPE
   SYNTAX  CxMcVoxPathAdmEntry
   ACCESS  not-accessible
   STATUS  deprecated
   DESCRIPTION
"Planned pathID row definition."
   INDEX { cxMcVoxPathAdmIndex }
   ::= { cxMcVoxPathAdmTable 1 }

CxMcVoxPathAdmEntry ::=
   SEQUENCE {
      cxMcVoxPathAdmIndex        INTEGER,
      cxMcVoxPathAdmRowStatus    INTEGER,
      cxMcVoxPathAdmPathId       DisplayString,
      cxMcVoxPathAdmRemStationId DisplayString,
      cxMcVoxPathAdmHunt         INTEGER,
      cxMcVoxPathAdmLng          INTEGER
    }

      cxMcVoxPathAdmIndex  OBJECT-TYPE
     SYNTAX INTEGER (1..300)
     ACCESS  read-only
     STATUS  deprecated 
     DESCRIPTION
"Displays the index number of the Path ID.

You cannot modify this object.

Range of Values: 1 to 300

Default Value: none"
     ::= { cxMcVoxPathAdmEntry 1 }

      cxMcVoxPathAdmRowStatus OBJECT-TYPE
     SYNTAX INTEGER {
          invalid (1),
          valid (2) 
        }
     ACCESS  read-write
     STATUS  deprecated 
     DESCRIPTION
"Determines the status of the objects in a table row.

Options:
invalid (1): Row is deleted from the table immediately, however values are 
still in effect until the next reset. 

valid (2): Use this value to add a new row to the table, or modify an 
existing row.

Default Value: none

Configuration Changed: administrative"
     ::= { cxMcVoxPathAdmEntry 2 }

      cxMcVoxPathAdmPathId       OBJECT-TYPE
     SYNTAX  DisplayString (SIZE (1..4))
     ACCESS  read-write
     STATUS  deprecated 
     DESCRIPTION
"Determines the administrative numeric dialing code that the user enters 
to access the remote telephone or fax machine.

Note: The length of the ID must match the value you define for the object 
cxMcVoxPathAdmPathLng (of this table).

Range of Values: 1 to 4 numeric digits

Default Value: none

Configuration Changed: administrative"
     ::= { cxMcVoxPathAdmEntry 3 }

      cxMcVoxPathAdmRemStationId       OBJECT-TYPE
     SYNTAX  DisplayString (SIZE (0..12))
     ACCESS  read-write
     STATUS  deprecated 
     DESCRIPTION
"Determines the administrative ID (name) of the remote voice station.

Note: The remote voice station must exist in the Network Routing table 
before its ID can be defined.

Range of Values: a maximum of 12 alphanumeric characters. All characters 
must be in capital letters. You can use any combination of letters and 
numbers, however you cannot use blank spaces. Use a dash or underscore as 
a delimiter.

Default Value: none

Configuration Changed: administrative"
     ::= { cxMcVoxPathAdmEntry 4 }

      cxMcVoxPathAdmHunt         OBJECT-TYPE
     SYNTAX INTEGER (1..4294967295)
     ACCESS  read-write
     STATUS  deprecated
     DESCRIPTION
"Determines the port numbers included in the administrative Hunt Group.

A Hunt Group identifies multiple ports on a single remote voice station 
(as defined with the object cxMcVoxPathAdmRemStationId of this table). The 
Path ID (defined using the object cxMcVoxPathAdmId of this table) 
references this Hunt Group during call establishment. Each port in the 
Hunt Group is polled until one of the ports accepts the call. A maximum of 
32 ports can be in a single hunt group.

Range of Values: 1 to 4294967295

Default Value: 65535

Configuration Changed: administrative"
     DEFVAL { 65535 }
     ::= { cxMcVoxPathAdmEntry 5 }

cxMcVoxPathAdmLng OBJECT-TYPE
   SYNTAX INTEGER (1..4)
   ACCESS  read-write
   STATUS  deprecated
   DESCRIPTION
"Determines the length (in digits) of the administrative Path 
ID.

Note: If you modify the current operative value to one that is a lower 
digit, the current operative Path IDs (using the higher value) will be 
lost once the administrative setting is initialized.

Range of Values: 1 to 4

Default Value: 3

Configuration Changed: administrative"
   DEFVAL { 3 }
   ::= { cxMcVoxPathAdmEntry 6 }





-- ==================================================================

--  cxMcVox OPERATIONAL PATH GROUP


cxMcVoxPathOpeTable OBJECT-TYPE
   SYNTAX  SEQUENCE OF CxMcVoxPathOpeEntry
   ACCESS  not-accessible
   STATUS  deprecated
   DESCRIPTION
"Active pathID table."
   --#ENDING-VERSION 1
   ::= { cxMcVox 5 }

cxMcVoxPathOpeEntry OBJECT-TYPE
   SYNTAX  CxMcVoxPathOpeEntry
   ACCESS  not-accessible
   STATUS  deprecated
   DESCRIPTION
"Active pathID row definition."
   INDEX { cxMcVoxPathOpeIndex }
   ::= { cxMcVoxPathOpeTable 1 }

CxMcVoxPathOpeEntry ::=
   SEQUENCE {
      cxMcVoxPathOpeIndex        INTEGER,
      cxMcVoxPathOpePathId       DisplayString,
      cxMcVoxPathOpeRemStationId DisplayString,
      cxMcVoxPathOpeHunt         INTEGER,
      cxMcVoxPathOpeLng          INTEGER
    }

      cxMcVoxPathOpeIndex  OBJECT-TYPE
     SYNTAX INTEGER (1..300)
     ACCESS  read-only
     STATUS  deprecated
     DESCRIPTION
"Displays the index number of the operational Path ID.

You cannot modify this object.

Range of Values: 1 to 300

Default Value: none"
     ::= { cxMcVoxPathOpeEntry 1 }

      cxMcVoxPathOpePathId       OBJECT-TYPE
     SYNTAX  DisplayString (SIZE (1..4))
     ACCESS  read-only
     STATUS  deprecated
     DESCRIPTION
"Displays the operational Path ID.

The Path ID is the numeric dialing code the user enters to gain access to 
the remote telephone or fax machine.

You cannot modify this object. If you want to change the value you must 
modify the object cxMcVoxPathAdmPathId of the cxMcVox Administrative 
Configuration Group.

Range of Values: 1 to 4 digits

Default Value: none "
     ::= { cxMcVoxPathOpeEntry 2 }

      cxMcVoxPathOpeRemStationId       OBJECT-TYPE
     SYNTAX  DisplayString (SIZE (0..12))
     ACCESS  read-only
     STATUS  deprecated
     DESCRIPTION
" Displays the operational ID (name) of the remote voice station.

Note: The remote voice station must exist in the Network Routing table 
before its ID can be defined.

You cannot modify this object. If you want to change the value you must 
modify the object cxMcVoxNetAdmRemStationId of the cxMcVox Administrative 
Net group

Range of Values: a maximum of 12 alphanumeric characters. All characters 
must be in capital letters. You can use any combination of letters and 
numbers, however you cannot use blank spaces. Use a dash or underscore as 
a delimiter.

Default: none"
     ::= { cxMcVoxPathOpeEntry 3 }

      cxMcVoxPathOpeHunt         OBJECT-TYPE
     SYNTAX INTEGER (1..4294967295)
     ACCESS  read-only
     STATUS  deprecated
     DESCRIPTION
"Displays the port numbers included in the operational Hunt Group.

A Hunt Group identifies multiple ports on a single remote voice station 
(as defined with the object cxMcVoxPathAdmRemStationId of this table). The 
Path ID (defined using the object cxMcVoxPathAdmId of this table) 
references this hunt group during call establishment. Each port in the 
Hunt Group is polled until one of the ports accepts the call. A maximum of 
8 ports can be in a single hunt group.

You cannot modify this object. If you want to change the value you must 
modify the object cxMcVoxPathAdmHunt of the cxMcVox Administrative Path 
Group.

Range of Values: 1 to 4294967295

Default Value: 65535"
     DEFVAL { 65535 }
     ::= { cxMcVoxPathOpeEntry 4 }

cxMcVoxPathOpeLng OBJECT-TYPE
   SYNTAX INTEGER (1..4)
   ACCESS  read-only
   STATUS  deprecated
   DESCRIPTION
"Displays the length (in digits) of the operative Path ID.

You cannot modify this object. If you want to change the value you must 
modify the object cxMcVoxPathAdmPathLng of the cxMcVox Administrative Path 
Group.

Range of Values: 1 to 4

Default Value: 3"
   DEFVAL { 3 }
   ::= { cxMcVoxPathOpeEntry 5 }




-- ====================================================================

--  cxMcVox ADMINISTRATIVE NET GROUP


cxMcVoxNetAdmTable OBJECT-TYPE
   SYNTAX  SEQUENCE OF CxMcVoxNetAdmEntry
   ACCESS  not-accessible
   STATUS  deprecated
   DESCRIPTION
"Planned NET entries."
   --#ENDING-VERSION 1
   ::= { cxMcVox 6 }

cxMcVoxNetAdmEntry OBJECT-TYPE
   SYNTAX  CxMcVoxNetAdmEntry
   ACCESS  not-accessible
   STATUS  deprecated
   DESCRIPTION
"Planned NET row."
   INDEX { cxMcVoxNetAdmIndex }
   ::= { cxMcVoxNetAdmTable 1 }

CxMcVoxNetAdmEntry ::=
   SEQUENCE {
      cxMcVoxNetAdmIndex           INTEGER,
      cxMcVoxNetAdmRowStatus       INTEGER,
      cxMcVoxNetAdmRemStationId    DisplayString,
      cxMcVoxNetAdmLocalLnkStation INTEGER,
      cxMcVoxNetAdmRoute           INTEGER,
      cxMcVoxNetAdmRemVoxStation   INTEGER
    }

      cxMcVoxNetAdmIndex   OBJECT-TYPE
     SYNTAX INTEGER (1..300)
     ACCESS  read-only
     STATUS  deprecated
     DESCRIPTION
"Displays the index number of the administrative network routing entry.

You cannot modify this object.

Range of Values: 1 to 300

Default Value: none"
     ::= { cxMcVoxNetAdmEntry 1 }

      cxMcVoxNetAdmRowStatus  OBJECT-TYPE
     SYNTAX INTEGER {
          invalid (1),
          valid (2) 
        }
     ACCESS  read-write
     STATUS  deprecated
     DESCRIPTION
"Determines the status of the objects in a table row.

Options:
invalid (1): row is flagged; after the next reset the values will be 
disabled and the row will be deleted from the table.

valid (2): values are enabled

Default Value: none

Configuration Changed: administrative"
     ::= { cxMcVoxNetAdmEntry 2 }

      cxMcVoxNetAdmRemStationId        OBJECT-TYPE
     SYNTAX  DisplayString (SIZE (0..12))
     ACCESS  read-write
     STATUS  deprecated
     DESCRIPTION
"Determines the administrative ID (name) of the remote voice 
station.

Range of Values: a maximum of 12 alphanumeric characters. All characters 
must be in capital letters. You can use any combination of letters and 
numbers, however you cannot use blank spaces. Use a dash or underscore as 
a delimiter.

Default: none

Configuration Changed: administrative"
     ::= { cxMcVoxNetAdmEntry 3 }

      cxMcVoxNetAdmLocalLnkStation        OBJECT-TYPE
     SYNTAX INTEGER (1..16)
     ACCESS  read-write
     STATUS  deprecated
     DESCRIPTION
"Determines the slot number holding the local CPU board 
supporting the GMF software. This value is always '1' if the CPU is in the 
CX900 architecture.

Range of Values:
CX900: 1 

CX1000: 1 to 16

Default Value: 1

Configuration Changed: administrative"
     DEFVAL { 1 }
     ::= { cxMcVoxNetAdmEntry 4 }

      cxMcVoxNetAdmRoute         OBJECT-TYPE
     SYNTAX INTEGER (1..1024)
     ACCESS  read-write
     STATUS  deprecated
     DESCRIPTION
"Determines the number that identifies the administrative link 
entry in the GMF (Gateway Mux Frame Relay).

The network administrator assigns this number in sequential order starting 
at 1. You then must establish an internal system route from the GMF route 
number to a Frame Relay circuit alias using the objects gmfSRLink and 
gmfSRDestCircuitAlias of the GMF System Routing Definition Group.

Range of Values: 1 to 1024

Default Value: 1

Configuration Changed: administrative"
     DEFVAL { 1 }
     ::= { cxMcVoxNetAdmEntry 5 }

      cxMcVoxNetAdmRemVoxStation       OBJECT-TYPE
     SYNTAX INTEGER (1..16)
     ACCESS  read-write
     STATUS  deprecated
     DESCRIPTION
"Determines the slot number holding the remote CPU board that 
supports the voice software. This value is always '1' if the remote CPU is in the CX900 
architecture.

Range of Values:
CX900: 1 

CX1000: 1 to 16

Default Value: 1

Configuration Changed: administrative"
     DEFVAL { 1 }
     ::= { cxMcVoxNetAdmEntry 6 }




-- ====================================================================

--  cxMcVox OPERATIONAL NET GROUP


cxMcVoxNetOpeTable OBJECT-TYPE
   SYNTAX  SEQUENCE OF CxMcVoxNetOpeEntry
   ACCESS  not-accessible
   STATUS  deprecated
   DESCRIPTION
"Active net entries table."
   --#ENDING-VERSION 1
   ::= { cxMcVox 7 }

cxMcVoxNetOpeEntry OBJECT-TYPE
   SYNTAX  CxMcVoxNetOpeEntry
   ACCESS  not-accessible
   STATUS  deprecated
   DESCRIPTION
"Active net entry row definition."
   INDEX { cxMcVoxNetOpeIndex }
   ::= { cxMcVoxNetOpeTable 1 }

CxMcVoxNetOpeEntry ::=
   SEQUENCE {
      cxMcVoxNetOpeIndex            INTEGER,
      cxMcVoxNetOpeRemStationId     DisplayString,
      cxMcVoxNetOpeLocalLnkStation  INTEGER,
      cxMcVoxNetOpeRoute            INTEGER,
      cxMcVoxNetOpeRemVoxStation    INTEGER
    }

      cxMcVoxNetOpeIndex   OBJECT-TYPE
     SYNTAX INTEGER (1..300)
     ACCESS  read-only
     STATUS  deprecated
     DESCRIPTION
"Displays the index number of the operative network routing 
entry.

You cannot modify this object

Range of Values: 1 to 300

Default Value: none"
     ::= { cxMcVoxNetOpeEntry 1 }

      cxMcVoxNetOpeRemStationId        OBJECT-TYPE
     SYNTAX  DisplayString (SIZE (0..12))
     ACCESS  read-only
     STATUS  deprecated
     DESCRIPTION
"Displays the operative ID (name) of the remote voice station.

You cannot modify this object. If you want to change the value you must 
modify the object cxMcVoxNetAdmOpeRemStationId of the cxMcVox 
Administrative Net Group.

Range of Values: a maximum of 12 alphanumeric characters. All characters 
must be in capital letters. You can use any combination of letters and 
numbers, however you cannot use blank spaces. Use a dash or underscore as 
a delimiter.

Default: none"
     ::= { cxMcVoxNetOpeEntry 2 }

      cxMcVoxNetOpeLocalLnkStation        OBJECT-TYPE
     SYNTAX INTEGER (1..16)
     ACCESS  read-only
     STATUS  deprecated
     DESCRIPTION
"Displays the slot number holding the local CPU board supporting 
the GMF software. This value is always '1' if the CPU is in the CX900 
architecture.

You cannot modify this object. If you want to change the value you must 
modify the object cxMcVoxNetAdmOpeLocalLnkStation of the cxMcVox 
Administrative Net Group.

Range of Values:
CX900: 1 

CX1000: 1 to 16

Default Value: 1"
     DEFVAL { 1 }
     ::= { cxMcVoxNetOpeEntry 3 }
                  
      cxMcVoxNetOpeRoute         OBJECT-TYPE
     SYNTAX INTEGER (1..1024)
     ACCESS  read-only
     STATUS  deprecated
     DESCRIPTION
"Displays the number that identifies the operative link entry. 
The network administrator assigns this number to identify the route in the 
routing table.

You cannot modify this object. If you want to change the value you must 
modify the object cxMcVoxNetAdmOpeRoute of the cxMcVox Administrative Net 
Group.

Range of Values: 1 to 1024

Default Value: 1"
     DEFVAL { 1 }
     ::= { cxMcVoxNetOpeEntry 4 }

      cxMcVoxNetOpeRemVoxStation       OBJECT-TYPE
     SYNTAX INTEGER (1..16)
     ACCESS  read-only
     STATUS  deprecated
     DESCRIPTION
"Displays the slot number holding the remote CPU board that 
supports the voice software. This value is always '1' if the remote CPU is 
in the CX900 architecture.

You cannot modify this object. If you want to change the value you must 
modify the object cxMcVoxNetAdmRemVoxStation of the cxMcVox Administrative 
Net Group.

Range of Values:
CX900: 1 

CX1000: 1 to 16

Default Value: 1"
     DEFVAL { 1 }
     ::= { cxMcVoxNetOpeEntry 5 }

 


-- =====================================================================

--  cxMcVox DRIVERS  


--  cxMcVox ADMINISTRATIVE DRIVER GROUP


cxMcVoxDriverAdm  OBJECT IDENTIFIER ::= {cxMcVox 8 }

--  cxMcVox ADMINISTRATIVE E&M DRIVER GROUP

cxMcVoxEmAdmTable OBJECT-TYPE
   SYNTAX  SEQUENCE OF CxMcVoxEmAdmEntry
   ACCESS  not-accessible
   STATUS  mandatory
   DESCRIPTION
"Voice station planned E&M Table."
   ::= { cxMcVoxDriverAdm 1 }

cxMcVoxEmAdmEntry OBJECT-TYPE
   SYNTAX  CxMcVoxEmAdmEntry
   ACCESS  not-accessible
   STATUS  mandatory
   DESCRIPTION
"Voice station planned E&M row definition."
   INDEX { cxMcVoxEmAdmCardUsed,
cxMcVoxEmAdmPortUsed }
   ::= { cxMcVoxEmAdmTable 1 }

CxMcVoxEmAdmEntry ::=
   SEQUENCE {
      cxMcVoxEmAdmCardUsed           INTEGER,
      cxMcVoxEmAdmPortUsed           INTEGER,
      cxMcVoxEmAdmPortStatus         INTEGER,
      cxMcVoxEmAdmVocoder            INTEGER,
      cxMcVoxEmAdmFaxBw              INTEGER,
      cxMcVoxEmAdmAutoCnx            INTEGER,
      cxMcVoxEmAdmPathId             DisplayString,
      cxMcVoxEmAdmTxGain             INTEGER,
      cxMcVoxEmAdmRxGain             INTEGER,
      cxMcVoxEmAdmEchoCancel         INTEGER,
      cxMcVoxEmAdmType               INTEGER,
      cxMcVoxEmAdmMode               INTEGER,
      cxMcVoxEmAdmDialType           INTEGER,
      cxMcVoxEmAdmSignalType         INTEGER,
      cxMcVoxEmAdmAc15Type           INTEGER,
      cxMcVoxEmAdmAc15TimeOn         INTEGER,
      cxMcVoxEmAdmAc15TimeOff        INTEGER,
      cxMcVoxEmAdmCnctType           INTEGER,
      cxMcVoxEmAdmRingType           INTEGER,
      cxMcVoxEmAdmRmtExt             DisplayString,
      cxMcVoxEmAdmRmtId              DisplayString,
      cxMcVoxEmAdmTranspMode         INTEGER,
      cxMcVoxEmAdmFaxEnable          INTEGER,
      cxMcVoxEmAdmBroadcast          INTEGER,
      cxMcVoxEmAdmImpedance          INTEGER,
      cxMcVoxEmAdmVoiceConnection    INTEGER
    }
    
    
-- USER MODE OBJECTS:    

      cxMcVoxEmAdmCardUsed       OBJECT-TYPE
     SYNTAX INTEGER (1..8)
     ACCESS  read-only
     STATUS  mandatory
     DESCRIPTION
"Displays the slot number of the voice I/O card.

You cannot modify this object. 

 Range of Values:

CX900: 1 to 6 

CX1000: 1 to 8

Default: none"
     ::= { cxMcVoxEmAdmEntry 1 }

      cxMcVoxEmAdmPortUsed       OBJECT-TYPE
     SYNTAX INTEGER (1..15)
     ACCESS  read-only
     STATUS  mandatory
     DESCRIPTION
"Displays the number of the voice port.

You cannot modify this object. It is a display that the software provides.

Options:

CX900: 1 is the only acceptable value. Each I/O card only has 1 port.

CX1000: up to 15 for the DI600

Default Value: none"
     ::= { cxMcVoxEmAdmEntry 2 }

      cxMcVoxEmAdmPortStatus        OBJECT-TYPE
     SYNTAX   INTEGER { 
          disable (1),
          enable (2) 
           }
     ACCESS  read-write
     STATUS  mandatory
     DESCRIPTION
"Determines the functional status of the administrative E&M port.

Options:

disable (1): port is not functional

enable (2): port is up and active

Default Value: disable (1)

Configuration Changed: administrative"
     DEFVAL { disable }
     ::= { cxMcVoxEmAdmEntry 3 }

      cxMcVoxEmAdmVocoder  OBJECT-TYPE
     SYNTAX INTEGER { bps5800 (1),
              bps8000 (2),
              kbps40 (3),
              kbps32 (4),
              kbps24 (5),
              kbps16 (6),
              opt7 (7),
              opt8 (8)
            }
     ACCESS  read-write
     STATUS  mandatory
     DESCRIPTION 
"Determines the transmission speed (in bits per second) of the compressed 
voice stream on the administrative E&M port. Defining the speed also sets 
the ACELP voice compression ratio.

Options:

bps5800 (1): compresses at a higher rate and uses slightly less bandwidth.

bps8000 (2): compresses at approximately an 8:1 ratio (lower rate) with a 
higher quality voice sound at the receiving end.

opt3 (3): ADPCM 40.

opt4 (4): ADPCM 32.

opt5 (5): ADPCM 24.

opt6 (6): ADPCM 16.

opt7 (7): Memotec use only.

opt8 (8): Memotec use only.

Default Value: bps8000

Configuration Changed: administrative"
     DEFVAL { bps8000 }
     ::= { cxMcVoxEmAdmEntry 4 }

      cxMcVoxEmAdmFaxBw    OBJECT-TYPE
     SYNTAX   INTEGER { 
          bps2400 (1),
          bps4800 (2),
          bps7200 (3),
          bps9600 (4)
           }
     ACCESS  read-write
     STATUS  mandatory
     DESCRIPTION
"Determines the speed (in bits per second) of the FAX channel on the 
administrative E&M port. This value also determines the bandwidth required 
to pass FAX traffic through the voice software. This value can be set to 
match the speed of your FAX machine or it can be lowered to reduce 
bandwidth allocation.

Options:

bps2400 (1)

bps4800 (2)

bps7200 (3)

bps9600 (4)

Default Value: bps7200 (3)

Configuration Changed: administrative"
     DEFVAL { bps7200 }
     ::= { cxMcVoxEmAdmEntry 5 }
     
-- obsolete object (has been redefined)

      cxMcVoxEmAdmAutoCnx  OBJECT-TYPE
     SYNTAX   INTEGER { 
          no (1),
          yes (2) 
           }
     ACCESS  read-write
     STATUS  obsolete
     DESCRIPTION
"Obsolete."
     DEFVAL { no }
      ::= { cxMcVoxEmAdmEntry 6 }

      cxMcVoxEmAdmPathId         OBJECT-TYPE
     SYNTAX  DisplayString (SIZE (1..4))
     ACCESS  read-write
     STATUS  deprecated
     DESCRIPTION
"Path IDs no longer exist in the new Voice Routing (VR) scheme.

Determines the Path ID used for auto-connection on the administrative E&M 
port.

The Path ID is a numeric dialing code the user enters to gain access to 
the remote telephone or fax machine.

Note: The number of digits in the Path ID must match the value of the 
object cxMcVoxPathAdmPathLng of the cxMcVox Administrative Path Group.

Range of Values: 1 to 4 numeric digits

Default Value: none

Configuration Changed: administrative"
	 --#ENDING-VERSION 1
	 DEFVAL { "000" }
     ::= { cxMcVoxEmAdmEntry 7 }

      cxMcVoxEmAdmTxGain      OBJECT-TYPE
     SYNTAX INTEGER (820..1180)
     ACCESS  read-write
     STATUS  mandatory
     DESCRIPTION 
"Determines the value defining the sound intensity (loudness) of voice 
transmissions on the administrative E&M port. The transmission gain can be 
modified in the administrative configuration or be fine-tuned dynamically.

Note: Transmission gains should be modified during a connection (i.e. 
dynamically) as changes in the value affect the local listener.

Range of Values: 820 to 1180 (-18.0dB to 18.0dB)

Default Value: 960

Configuration Changed: administrative"
     DEFVAL { 960 }
     ::= { cxMcVoxEmAdmEntry 8 }

      cxMcVoxEmAdmRxGain      OBJECT-TYPE
     SYNTAX INTEGER (820..1180)
     ACCESS  read-write
     STATUS  mandatory
     DESCRIPTION 
"Determines the value defining the sound intensity (loudness) of voice 
reception on the administrative E&M port. The reception gain can be 
modified in the administrative configuration or be fine-tuned dynamically.

Note: Reception gains should be modified during a connection (i.e. 
dynamically) as changes in the value affect the remote listener.

Range of Values: 820 to 1180 (-18.0dB to 18.0dB)

Default Value: 960

Configuration Changed: administrative"
     DEFVAL { 960 }
     ::= { cxMcVoxEmAdmEntry 9 }

      cxMcVoxEmAdmEchoCancel  OBJECT-TYPE
     SYNTAX   INTEGER { 
          disable (1),
          enable (2) 
           }
     ACCESS  read-write
     STATUS  mandatory
     DESCRIPTION
"Determines the state of echo cancellation on the administrative E&M port. 
When set to 'enable', at both the local and remote ends, echo cancellation 
stops echoes from the remote that are heard through the receiver at the 
local end.

Options:

disable (1)

enable (2)

Default Value: enable (2)

Configuration Changed: administrative"
     DEFVAL { enable }
      ::= { cxMcVoxEmAdmEntry 10 }

      cxMcVoxEmAdmType     OBJECT-TYPE
     SYNTAX INTEGER {
          type-1  (1),
          type-2  (2),
          type-3  (3),
          type-4  (4),
          type-5  (5)
        }
     ACCESS  read-write
     STATUS  mandatory
     DESCRIPTION 
"Determines the type of E&M interface on the administrative E&M port. Each 
of the five interface types has a unique signal-to-wire pattern. Make sure 
that you select the interface type that matches your PBX.

Options:

type-1 (1)

type-2 (2)

type-3 (3)

type-4 (4)

type-5 (5)

Default Value: type-2 (2)

Configuration Changed: administrative

NOTE: This object is READ-ONLY for the CX800."
     DEFVAL { type-2 }
     ::= { cxMcVoxEmAdmEntry  11 }

      cxMcVoxEmAdmMode     OBJECT-TYPE
     SYNTAX   INTEGER { 
          normal (1),
          reverse (2) 
           }
     ACCESS  read-write
     STATUS  mandatory
     DESCRIPTION
"Determines the signalling mode for the administrative E&M port. The 
signalling mode refers to the wires of the physical connection and how 
they are connected. The mode you select must match the type the PBX punch 
block uses or the port will not be able to communicate with it.

Options:

normal (1)

reverse (2)

Default Value: normal

Configuration Changed: administrative"
     DEFVAL { normal }
     ::= { cxMcVoxEmAdmEntry  12 }

      cxMcVoxEmAdmDialType OBJECT-TYPE
     SYNTAX   INTEGER { 
          dtmf (1),
          pulse (2),
          mfR1 (3),
          mfR2 (4)
           }
     ACCESS  read-write
     STATUS  mandatory
     DESCRIPTION 
"Determines the dialing method of the administrative E&M port. The dialing 
method refers to the sound that occurs when the user enters each digit of 
the dialing code.

Options:

dtmf (1): (Dual Tone Multifrequence) uses bursts of frequency pairs to 
identify the code the user dials. Tones are generated at a level of -7 
plus or minus 3 dBm for the lower frequency groups and -5 plus or minus 3 
dBm for the higher frequency group. The power level of the higher 
frequency tone is intentionally increased to compensate for the higher 
line loss.

pulse (2): uses bursts (10 plus or minus 0.5 pps) of the main tone 
frequency (2280Hz) to generate the codes the user enters. Tones are 
generated at a level of -4 to -30 dBm for the 2280Hz frequency. The number 
of pulses during one second indicates the code the user dials. With the 
E&M interface, the voice station generates and detects pulses.

mfR1 (3): R1 signaling protocol MultiFrequency (MF) uses bursts of
frequency pairs to identify the code the user dials. Tones are generated
at a level of -7 dBm0 +- 1 dB (CCITT Recommendation Q.322). The difference
in transmission level between the two frequencies comprises a signal that
does not exceed 0.5 dB.

mfR2 (4): R2 signaling protocol MultiFrequency (MF) uses bursts of
frequency pairs to identify the code the user dials. Tones are generated
at a level of -8 dBm0 +- 1 dB (CCITT Recommendation Q.454). The difference
in transmission level between the two frequencies comprises a signal that
does not exceed 1 dB.

Default Value: dtmf (1)

Configuration Changed: administrative"
     DEFVAL { dtmf }
     ::= { cxMcVoxEmAdmEntry  13 }
     
      cxMcVoxEmAdmSignalType  OBJECT-TYPE
     SYNTAX   INTEGER { 
          normal (1),
          delay (2),
          wink (3),
          ac15 (4),
          openchn (5),
          r2 (6),
          mfcr2 (7),
          isdn (8)
           }
     ACCESS  read-write
     STATUS  mandatory
     DESCRIPTION 
"Determines the type of signalling on the administrative E&M port. The 
signalling type refers to the line seizure technique

Options:

normal (1)

delay (2)

wink (3)

ac15 (4)

openChn (5)

R2 (6)

MFCR2 (7)

isdn (8)

Note: If you select 'ac15' you must define the object cxMcVoxEmAdmDialType 
of this table.

Default Value: normal

Configuration Changed: administrative"
     DEFVAL { normal }
     ::= { cxMcVoxEmAdmEntry  14 }

      cxMcVoxEmAdmAc15Type   OBJECT-TYPE
     SYNTAX   INTEGER { 
          normal (1),
          delay (2)
           }
     ACCESS  read-write
     STATUS  mandatory
     DESCRIPTION 
"Determines the type of AC15 signals the administrative E&M port uses to 
seize the line for transmission.

This object is only relevant to E&M ports using the AC15 signalling type 
(as defined using the object cxMcVoxEmAdmSignalType of this table)

Options:

normal (1)

delay (2)

Default Value: normal

Configuration Changed: administrative"
     DEFVAL { normal }
     ::= { cxMcVoxEmAdmEntry  15 }

      cxMcVoxEmAdmAc15TimeOn OBJECT-TYPE
     SYNTAX INTEGER (0..60000)
     ACCESS  read-write
     STATUS  mandatory
     DESCRIPTION 
"Determines the length of time, in milliseconds, the AC15 pulse remains 
on.

This object is only relevant to E&M ports using the AC15 signalling type 
(as defined using the object cxMcVoxEmAdmSignalType of this table)

Range of Values: 0 to 60000

Default Value: 60

Configuration Changed: administrative"
     DEFVAL { 60 }
     ::= { cxMcVoxEmAdmEntry  16 }

      cxMcVoxEmAdmAc15TimeOff   OBJECT-TYPE
     SYNTAX INTEGER (0..60000)
     ACCESS  read-write
     STATUS  mandatory
     DESCRIPTION 
"Determines the length of time, in milliseconds, the AC15 pulse remains 
off.

This object is only relevant to E&M ports using the AC15 signalling type 
(as defined using the object cxMcVoxEmAdmSignalType of this table)

Range of Values: 0 to 60000

Default Value: 40

Configuration Changed: administrative"
     DEFVAL { 40 }
     ::= { cxMcVoxEmAdmEntry  17 }

      cxMcVoxEmAdmCnctType   OBJECT-TYPE
     SYNTAX   INTEGER { 
          switched (1),
          auto-connect (2),
          fixed (3)
           }
     ACCESS  read-write
     STATUS  mandatory
     DESCRIPTION
"Determines the method the administrative E&M port uses to make 
connections.

Options:

switched (1): the port connects each call according to the dialing code 
the user enters.

auto-connect (2): calls passing through this port always terminate at the 
same remote destination. The port connects to the remote as soon as the 
local receiver enters the off-hook state. Any remote can connect to a port 
with an auto-connect configuration but when the local user initiates the 
call it always goes to the same remote.

fixed (3): calls passing through this port always terminate at the same 
remote destination. The port connects to the remote as soon as the local 
receiver enters the off-hook state. Only the local and remote destinations 
of the connection can use this port. No other remote location can gain 
access to this port.

Default Value: switched (1)

Configuration Changed: administrative"
     DEFVAL { switched }
     ::= { cxMcVoxEmAdmEntry  18 }
     
      cxMcVoxEmAdmRingType   OBJECT-TYPE
     SYNTAX   INTEGER { 
          north-american (1),
          international (2)
           }
     ACCESS  read-write
     STATUS  mandatory
     DESCRIPTION
"Determines the ring type of the administrative E&M port. The ring types 
provide different ring timing to match the different ring cycles in 
networks.

Options:

north-american (1)

international (2)

Default Value: north-american (1)

Configuration Changed: administrative"
     DEFVAL { north-american }
     ::= { cxMcVoxEmAdmEntry  19 }

      cxMcVoxEmAdmRmtExt    OBJECT-TYPE
     SYNTAX  DisplayString (SIZE (1..5))
     ACCESS  read-write
     STATUS  mandatory
     DESCRIPTION
"Determines the Remote Extension or Group Id used for auto-connection on 
the E&M port.

The Remote Extension is a numeric dialing code that the user enters to 
gain access to the remote telephone or fax machine.

Auto-connection is the connection method that this port uses. A particular 
Remote Extension or Group Id has been assigned to the port so that no 
dialing is required. 

Note: The number of digits in the Remote Extension is determined by the 
object cxMcVoxNetNbDigits of the cxMcVox Global Parameters Group.

Range of Values: 1 to 5 numeric digits

Default Value: none

Configuration Changed: administrative"
   DEFVAL { "000" }
	 --#STARTING-VERSION 1
     ::= { cxMcVoxEmAdmEntry 20 }
     
      cxMcVoxEmAdmRmtId OBJECT-TYPE
   SYNTAX  DisplayString (SIZE (0..10))
   ACCESS  read-write
   STATUS  optional
   DESCRIPTION
"Determines the ID (name) for the remote voice station.

Note:
This object must be defined in order to obtain a successful voice 
connection via the fixed connection method.

With the fixed connection method, a particular Remote Extension or Group 
Id is assigned to the port so that no dialing is required. The call to the 
remote is established as soon as the connection is configured.

Range of Values: A maximum of 10 alphanumeric characters in upper-case 
only. You can use any combination of letters and numbers; however you 
cannot use blank spaces. Use a dash or underscore as a delimiter.

Default Value: none

Configuration Changed: administrative"
   DEFVAL { "          " }
	--#STARTING-VERSION 1
    ::= { cxMcVoxEmAdmEntry  21 }

      cxMcVoxEmAdmTranspMode   OBJECT-TYPE
     SYNTAX   INTEGER { 
          emulate (1),
          transparent (2) ,
          local (3)
           }
     ACCESS  read-write
     STATUS  mandatory
     DESCRIPTION
"Determines the whether to use the Transparent mode on the administrative
 port.  In the transparent mode, the local port will answer only after
 the called party has answered to the party to which the call is finally
 destinated.

 The Transparent mode is incompatible with Switched type of
 connection and is automatically disabled when Switched mode is selected
 (only applies to autoconnect and fixed connections).

 The Local mode lets the local port answer right away to a seizure.

Options:

emulate (1): Emulation mode is on

transparent (2): Transparent mode on

local (3): Local mode on

Default Value: emulate (1)

Configuration Changed: administrative"
     DEFVAL { emulate }
	 --#STARTING-VERSION 3
     ::= { cxMcVoxEmAdmEntry  22 }
      
      cxMcVoxEmAdmFaxEnable  OBJECT-TYPE
     SYNTAX   INTEGER { 
          disable (1),
          enable (2) 
           }
     ACCESS  read-write
     STATUS  mandatory
     DESCRIPTION
"Determines the state of the Memotec's FAX relay software on the administrative
 E&M port.  When set to 'enable', at both ends, the Memotec's FAX relay 
 software will be used to transfer FAX messages taking into account the 
 'cxMcVoxEmAdmFaxBw' object.  Otherwise, when set to 'disable', at both ends,
 no FAX relay support is provided, and the FAX goes through the voice coder
 if supported.

Options:

disable (1)

enable (2)

Default Value: enable (2)

Configuration Changed: administrative"
     DEFVAL { enable }
	--#STARTING-VERSION 8
      ::= { cxMcVoxEmAdmEntry 23 }


      cxMcVoxEmAdmBroadcast  OBJECT-TYPE
     SYNTAX   INTEGER { 
          none (1),
          master (2) ,
          slave (3)
           }
     ACCESS  read-write
     STATUS  mandatory
     DESCRIPTION
"Cetermines the state of the voice broadcast feature. When set to none, no
broadcast is used. When set to master, ...



Options:

none (1)

master (2)

slave (3)

Default Value: none (1)

Configuration Changed: administrative"
     DEFVAL { none }
	--#STARTING-VERSION 10
      ::= { cxMcVoxEmAdmEntry 24 }

      cxMcVoxEmAdmImpedance   OBJECT-TYPE
     SYNTAX   INTEGER { 
          i600-ohms (1),
          i900-ohms (2),
          att       (3),
          aus       (4)
           }
     ACCESS  read-write
     STATUS  mandatory
     DESCRIPTION
"Displays the input line impedance of the operative E&M interface. 
The value of this object can be modified in operational mode.

Options:

i600-ohms (1)

i900-ohms (2)

att (3)

aus (4)

Default Value: i600-ohms (1)

NOTE: This object is READ-ONLY for the CX800."
     DEFVAL { i600-ohms }
	 --#STARTING-VERSION 11
     ::= { cxMcVoxEmAdmEntry  25 }

      cxMcVoxEmAdmVoiceConnection   OBJECT-TYPE
     SYNTAX   INTEGER { 
          two-wires  (1),
          four-wires (2)
           }
     ACCESS  read-only
     STATUS  mandatory
     DESCRIPTION
"Indicates which voice path is provided by the
E&M interface.

Options:

two-wires (1)

four-wires (2)"
	 --#STARTING-VERSION 11
     ::= { cxMcVoxEmAdmEntry  26 }

-- .......................................................................      

--  cxMcVox ADMINISTRATIVE FXS DRIVER GROUP


cxMcVoxFxsAdmTable OBJECT-TYPE
   SYNTAX  SEQUENCE OF CxMcVoxFxsAdmEntry
   ACCESS  not-accessible
   STATUS  mandatory
   DESCRIPTION
      ""
   ::= { cxMcVoxDriverAdm 2 }

cxMcVoxFxsAdmEntry OBJECT-TYPE
   SYNTAX  CxMcVoxFxsAdmEntry
   ACCESS  not-accessible
   STATUS  mandatory
   DESCRIPTION
      ""
   INDEX { cxMcVoxFxsAdmCardUsed, cxMcVoxFxsAdmPortUsed }
   ::= { cxMcVoxFxsAdmTable 1 }

CxMcVoxFxsAdmEntry ::=
   SEQUENCE {
      cxMcVoxFxsAdmCardUsed           INTEGER,        
      cxMcVoxFxsAdmPortUsed           INTEGER,
      cxMcVoxFxsAdmPortStatus         INTEGER,
      cxMcVoxFxsAdmVocoder            INTEGER,
      cxMcVoxFxsAdmFaxBw              INTEGER,
      cxMcVoxFxsAdmAutoCnx            INTEGER,
      cxMcVoxFxsAdmPathId             DisplayString,
      cxMcVoxFxsAdmTxGain             INTEGER,
      cxMcVoxFxsAdmRxGain             INTEGER,
      cxMcVoxFxsAdmEchoCancel         INTEGER,
      cxMcVoxFxsAdmSignaling          INTEGER,
      cxMcVoxFxsAdmTimeOn             INTEGER,
      cxMcVoxFxsAdmTimeOff            INTEGER,
      cxMcVoxFxsAdmCnctType           INTEGER,
      cxMcVoxFxsAdmRingType           INTEGER,
      cxMcVoxFxsAdmImpedance          INTEGER,
      cxMcVoxFxsAdmDialType           INTEGER,
      cxMcVoxFxsAdmDidSignalType      INTEGER,
      cxMcVoxFxsAdmRmtExt             DisplayString,
      cxMcVoxFxsAdmRmtId              DisplayString,
      cxMcVoxFxsAdmTranspMode         INTEGER,
      cxMcVoxFxsAdmFaxEnable          INTEGER,
      cxMcVoxFxsAdmBroadcast          INTEGER
    }

-- USER MODE OBJECTS:

      cxMcVoxFxsAdmCardUsed         OBJECT-TYPE
     SYNTAX INTEGER (1..8)
     ACCESS  read-only
     STATUS  mandatory
     DESCRIPTION
"Displays the slot number of the voice I/O card.

You cannot modify this object.

Range of Values:

CX900: 1 to 6

CX1000: 1 to 8

Default: none"
     ::= { cxMcVoxFxsAdmEntry 1 }

      cxMcVoxFxsAdmPortUsed         OBJECT-TYPE
     SYNTAX INTEGER (1..15)
     ACCESS  read-only
     STATUS  mandatory
     DESCRIPTION
"Displays the number of the voice port.

You cannot modify this object.

Options:

CX900: 1 is the only acceptable value. Each I/O card only has 1 port

CX1000: 1 or 2

Default Value: none"
     ::= { cxMcVoxFxsAdmEntry 2 }

      cxMcVoxFxsAdmPortStatus       OBJECT-TYPE
     SYNTAX   INTEGER { 
          disable (1),
          enable (2) 
           }
     ACCESS  read-write
     STATUS  mandatory
     DESCRIPTION
"Determines the functional status of the administrative port.

Options:

disable (1): port is not functional

enable (2): port is up and active

Default Value: disable (1)

Configuration Changed: administrative"
     DEFVAL { disable }
     ::= { cxMcVoxFxsAdmEntry 3 }

      cxMcVoxFxsAdmVocoder OBJECT-TYPE
     SYNTAX INTEGER { bps5800 (1),
              bps8000 (2),
              kbps40 (3),
              kbps32 (4),
              kbps24 (5),
              kbps16 (6),
              opt7 (7),
              opt8 (8)
            }
     ACCESS  read-write
     STATUS  mandatory
     DESCRIPTION 
"Determines the transmission speed (in bits per second) of the compressed 
voice stream on the administrative FXS port. Defining the speed also sets 
the ACELP voice compression ratio.

Options:

bps5800 (1): compresses at a higher rate and uses slightly less bandwidth.

bps8000 (2): compresses at approximately an 8:1 ratio (lower rate) with a 
higher quality voice sound at the receiving end.

opt3 (3): ADPCM 40.

opt4 (4): ADPCM 32.

opt5 (5): ADPCM 24.

opt6 (6): ADPCM 16.

opt7 (7): Memotec use only.

opt8 (8): Memotec use only.

Default Value: bps8000 (2)

Configuration Changed: administrative"
     DEFVAL { bps8000 }
     ::= { cxMcVoxFxsAdmEntry 4 }

      cxMcVoxFxsAdmFaxBw      OBJECT-TYPE
     SYNTAX   INTEGER { 
          bps2400 (1),
          bps4800 (2),
          bps7200 (3),
          bps9600 (4)
           }
     ACCESS  read-write
     STATUS  mandatory
     DESCRIPTION
"Determines the speed (in bits per second) of the FAX channel on the 
administrative FXS port. This value also determines the bandwidth required 
to pass FAX traffic through the voice software.This value can be set to 
match the speed of your FAX machine or it can be lowered to reduce 
bandwidth allocation.

Options:

bps2400 (1)

bps4800 (2)

bps7200 (3)

bps9600 (4)

Default Value: bps7200 (3)

Configuration Changed: administrative"
     DEFVAL { bps7200 }
     ::= { cxMcVoxFxsAdmEntry 5 }

-- obsoleted (has been redefined)

      cxMcVoxFxsAdmAutoCnx OBJECT-TYPE
     SYNTAX   INTEGER { 
          no (1),
          yes (2) 
           }
     ACCESS  read-write
     STATUS  obsolete
     DESCRIPTION
"obsolete"
     DEFVAL { no }
      ::= { cxMcVoxFxsAdmEntry 6 }

      cxMcVoxFxsAdmPathId        OBJECT-TYPE
     SYNTAX  DisplayString (SIZE (1..4))
     ACCESS  read-write
     STATUS  deprecated
     DESCRIPTION
"Path IDs no longer exist with the new Voice Routing (VR) scheme.

The Path ID is a numeric dialing code the user enters to gain access to 
the remote telephone or fax machine.

Note: The number of digits in the Path ID must match the value of the 
object cxMcVoxPathAdmPathLng of the cxMcVox Administrative Path Group

Range of Values: 1 to 4 digits

Default Value: none"
	 --#ENDING-VERSION 1
	 DEFVAL { "000" }
     ::= { cxMcVoxFxsAdmEntry 7 }

      cxMcVoxFxsAdmTxGain     OBJECT-TYPE
     SYNTAX INTEGER (820..1180)
     ACCESS  read-write
     STATUS  mandatory
     DESCRIPTION
"Determines the value defining the sound intensity (loudness) of voice 
transmissions on the administrative FXS port. The transmission gain can be 
modified in the administrative configuration or be fine-tuned dynamically.

Note: Transmission gains should be modified during a connection (i.e. 
dynamically) as changes in the value affect the local listener.

Range of Values: 820 to 1180 (-18.0dB to 18.0dB)

Default Value: 960

Configuration Changed: administrative"
     DEFVAL { 960 }
     ::= { cxMcVoxFxsAdmEntry 8 }

      cxMcVoxFxsAdmRxGain     OBJECT-TYPE
     SYNTAX INTEGER (820..1180)
     ACCESS  read-write
     STATUS  mandatory
     DESCRIPTION
"Determines the value defining the sound intensity (loudness) of voice 
reception on the administrative FXS port. The reception gain can be 
modified in the administrative configuration or be fine-tuned dynamically.

Note: Reception gains should be modified during a connection (i.e. 
dynamically) as changes in the value affect the remote listener.

Range of Values: 820 to 1180 (-18.0dB to 18.0dB)

Default Value: 960

Configuration Changed: administrative"
     DEFVAL { 960 }
     ::= { cxMcVoxFxsAdmEntry 9 }

      cxMcVoxFxsAdmEchoCancel OBJECT-TYPE
     SYNTAX   INTEGER { 
          disable (1),
          enable (2) 
           }
     ACCESS  read-write
     STATUS  mandatory
     DESCRIPTION
"Determines the state of echo cancellation on the administrative FXS port. 
When set to 'enable' at both the local and remote ends, echo cancellation 
stops echoes from the remote that are heard through the receiver at the 
local end.

Options:

disable (1)

enable (2)

Default Value: enable (2)

Configuration Changed: administrative"
     DEFVAL { enable }
     ::= { cxMcVoxFxsAdmEntry 10 }


      cxMcVoxFxsAdmSignaling  OBJECT-TYPE
     SYNTAX   INTEGER { 
          ground-start (1),
          loop-start   (2),
          did          (3)
           }
     ACCESS  read-write
     STATUS  mandatory
     DESCRIPTION
"Determines the type of signalling the administrative FXS port uses to 
seize the line.

Options:

ground-start (1)

loop-start (2)

did (3)

Default Value: loop-start (2)

Configuration Changed: administrative"
     DEFVAL { loop-start }
     ::= { cxMcVoxFxsAdmEntry  11 }

-- obsolete object (has been redefined)

      cxMcVoxFxsAdmTimeOn  OBJECT-TYPE
     SYNTAX INTEGER (10..10000)
     ACCESS  read-write
     STATUS  obsolete
     DESCRIPTION 
"obsolete"
     DEFVAL { 2000 }
     ::= { cxMcVoxFxsAdmEntry  12 }

-- obsolete object (has been redefined)

      cxMcVoxFxsAdmTimeOff OBJECT-TYPE
     SYNTAX INTEGER (10..10000)
     ACCESS  read-write
     STATUS  obsolete
     DESCRIPTION 
"obsolete"
     DEFVAL { 4000 }
     ::= { cxMcVoxFxsAdmEntry  13 }

      cxMcVoxFxsAdmCnctType   OBJECT-TYPE
     SYNTAX   INTEGER { 
          switched (1),
          auto-connect (2),
          fixed (3)
           }
     ACCESS  read-write
     STATUS  mandatory
     DESCRIPTION
"Determines the method the administrative FXS port uses to make 
connections.

Options:

switched (1): the port connects each call according to the dialing code 
the user enters.

auto-connect (2): calls passing through this port always terminate at the 
same remote destination. The port connects to the remote as soon as the 
local receiver enters the off-hook state. Any remote can connect to a port 
with an auto-connect configuration but when the local user initiates the 
call it always goes to the same remote.

fixed (3): calls passing through this port always terminate at the same 
remote destination. The port connects to the remote as soon as the local 
receiver enters the off-hook state. Only the local and remote destinations 
of the connection can use this port. No other remote location can gain 
access to this port.

Default Value: switched (1)

Configuration Changed: administrative"
     DEFVAL { switched }
     ::= { cxMcVoxFxsAdmEntry  14 }
     
      cxMcVoxFxsAdmRingType   OBJECT-TYPE
     SYNTAX   INTEGER { 
          north-american (1),
          international (2)
           }
     ACCESS  read-write
     STATUS  mandatory
     DESCRIPTION
"Determines the ring type of the administrative FXS port. The ring types 
provide different ring timing to match the different ring cycles in 
networks.

Options:

north-american (1)

international (2)

Default Value: north-american (1)

Configuration Changed: administrative"
     DEFVAL { north-american }
     ::= { cxMcVoxFxsAdmEntry  15 }

      cxMcVoxFxsAdmImpedance   OBJECT-TYPE
     SYNTAX   INTEGER { 
          i600-ohms (1),
          i900-ohms (2),
          att       (3),
          aus       (4)
           }
     ACCESS  read-write
     STATUS  mandatory
     DESCRIPTION
"Determines the input line impedance of the administrative FXS 
port.

Options:

i600-ohms (1)

i900-ohms (2)

att (3)

aus (4)

Default Value: i600-ohms (1)

Configuration Changed: administrative

NOTE: The option aus(4) is added only starting at version 11.
NOTE: This object is READ-ONLY for the CX800."
     DEFVAL { i600-ohms }
     ::= { cxMcVoxFxsAdmEntry  16 }

      cxMcVoxFxsAdmDialType   OBJECT-TYPE
     SYNTAX   INTEGER { 
          dtmf  (1),
          pulse (2)
           }
     ACCESS  read-write
     STATUS  mandatory
     DESCRIPTION
"Determines the dialing method of the administrative FXS port. The dialing 
method refers to the sound that occurs when the user enters each digit of 
the dialing code.

Options:

dtmf (1): (Dual Tone Multifrequence) uses bursts of frequency pairs to 
identify the code the user dials. Tones are generated at a level of -7 
plus or minus 3 dBm for the lower frequency groups and -5 plus or minus 3 
dBm for the higher frequency group. The power level of the higher 
frequency tone is intentionally increased to compensate for the higher 
line loss.

pulse (2): uses bursts (10 plus or minus 0.5 pps) of the main tone 
frequency (2280Hz) to generate the codes the user enters. Tones are 
generated at a level of -4 to -30 dBm for the 2280Hz frequency. The number 
of pulses during one second indicates the code the user dials. With the 
E&M interface, the voice station generates and detects pulses.

Default Value: dtmf (1)

Configuration Changed: administrative"
     DEFVAL { dtmf }
     ::= { cxMcVoxFxsAdmEntry  17 }

      cxMcVoxFxsAdmDidSignalType   OBJECT-TYPE
     SYNTAX   INTEGER { 
          normal  (1),
          delay   (2),
          wink    (3)
           }
     ACCESS  read-write
     STATUS  mandatory
     DESCRIPTION
"Note: This object only applies to those ports with the object 
cxMcVoxFxsAdmSignaling set to 'did'.

Determines the type of signaling on the administrative FXS port. The 
signaling type refers to the line seizure technique.

Options:

normal (1)

delay (2)

wink (3)

Default Value: normal (1)

Configuration Changed: administrative"
     DEFVAL { normal }
     ::= { cxMcVoxFxsAdmEntry  18 }

      cxMcVoxFxsAdmRmtExt    OBJECT-TYPE
     SYNTAX  DisplayString (SIZE (1..5))
     ACCESS  read-write
     STATUS  mandatory
     DESCRIPTION
"Determines the Remote Extension or Group Id used for auto-connection on 
the FXS port.

The Remote Extension is a numeric dialing code that the user enters to 
access the remote telephone or fax machine.

Auto-connection is the connection method that this port uses. A particular 
Remote Extension or Group Id has been assigned to the port so that no 
dialing is required. 

Note: The number of digits in the Remote Extension is determined by the 
object cxMcVoxNetNbDigits of the cxMcVox Global Parameters Group.

Range of Values: 1 to 5 numeric digits

Default Value: none

Configuration Changed: administrative"
   DEFVAL { "000" }
	 --#STARTING-VERSION 1
     ::= { cxMcVoxFxsAdmEntry  19 }

      cxMcVoxFxsAdmRmtId OBJECT-TYPE
   SYNTAX  DisplayString (SIZE (0..10))
   ACCESS  read-write
   STATUS  optional
   DESCRIPTION
"Determines the ID (name) for the remote voice station.

Note:

This object must be defined in order to obtain a successful voice 
connection with fixed type connection.

With the fixed connection method, a particular Remote Extension or Group 
Id is assigned to the port so that no dialing is required. The call to the 
remote is established as soon as the connection is configured.

Range of Values: a maximum of 10 alphanumeric characters in upper-case 
only. You can use any combination of letters and numbers; however you 
cannot use blank spaces. Use a dash or underscore as a delimiter.

Default Value: none

Configuration Changed: administrative"
   DEFVAL { "          " }
	 --#STARTING-VERSION 1
     ::= { cxMcVoxFxsAdmEntry  20 }

      cxMcVoxFxsAdmTranspMode   OBJECT-TYPE
     SYNTAX   INTEGER { 
          emulate (1),
          transparent (2) ,
          local (3)
           }
     ACCESS  read-write
     STATUS  mandatory
     DESCRIPTION
"Determines the whether to use the Transparent mode on the administrative
 port.  In the transparent mode, the local port will answer only after
 the called party has answered to the party to which the call is finally
 destinated.

 The Transparent mode is incompatible with Switched type of
 connection and is automatically disabled when Switched mode is selected
 (only applies to autoconnect and fixed connections).

 The Local mode lets the local port answer right away to a seizure.

Options:

emulate (1): Emulation mode is on

transparent (2): Transparent mode on

local (3): Local mode on

Default Value: emulate (1)

Configuration Changed: administrative"
     DEFVAL { emulate }
	 --#STARTING-VERSION 3
     ::= { cxMcVoxFxsAdmEntry  21 }

      cxMcVoxFxsAdmFaxEnable OBJECT-TYPE
     SYNTAX   INTEGER { 
          disable (1),
          enable (2) 
           }
     ACCESS  read-write
     STATUS  mandatory
     DESCRIPTION
"Determines the state of the Memotec's FAX relay software on the administrative
 E&M port.  When set to 'enable', at both ends, the Memotec's FAX relay 
 software will be used to transfer FAX messages taking into account the 
 'cxMcVoxFxsAdmFaxBw' object.  Otherwise, when set to 'disable', at both ends,
 no FAX relay support is provided, and the FAX goes through the voice coder
 if supported.

Options:

disable (1)

enable (2)

Default Value: enable (2)

Configuration Changed: administrative"
     DEFVAL { enable }
	--#STARTING-VERSION 8
     ::= { cxMcVoxFxsAdmEntry 22 }


      cxMcVoxFxsAdmBroadcast OBJECT-TYPE
     SYNTAX   INTEGER { 
          none (1),
          master (2) ,
          slave (3)
           }
     ACCESS  read-write
     STATUS  mandatory
     DESCRIPTION
"Cetermines the state of the voice broadcast feature. When set to none, no
broadcast is used. When set to master, ...



Options:

none (1)

master (2)

slave (3)

Default Value: none (1)

Configuration Changed: administrative"
     DEFVAL { none }
	--#STARTING-VERSION 10
      ::= { cxMcVoxFxsAdmEntry 23 }


-- ..........................................................................


--  cxMcVox ADMINISTRATIVE FXO DRIVER GROUP


cxMcVoxFxoAdmTable OBJECT-TYPE
   SYNTAX  SEQUENCE OF CxMcVoxFxoAdmEntry
   ACCESS  not-accessible
   STATUS  mandatory
   DESCRIPTION
      "cx Voice Station Administrative FXO Table."
   ::= { cxMcVoxDriverAdm 3 }

cxMcVoxFxoAdmEntry OBJECT-TYPE
   SYNTAX  CxMcVoxFxoAdmEntry
   ACCESS  not-accessible
   STATUS  mandatory
   DESCRIPTION
      "cx Voice Station Administrative FXO Entry "
   INDEX { cxMcVoxFxoAdmCardUsed, cxMcVoxFxoAdmPortUsed }
   ::= { cxMcVoxFxoAdmTable 1 }

CxMcVoxFxoAdmEntry ::=
   SEQUENCE {
      cxMcVoxFxoAdmCardUsed           INTEGER,        
      cxMcVoxFxoAdmPortUsed           INTEGER,
      cxMcVoxFxoAdmPortStatus         INTEGER,
      cxMcVoxFxoAdmVocoder            INTEGER,
      cxMcVoxFxoAdmFaxBw              INTEGER,
      cxMcVoxFxoAdmAutoCnx            INTEGER,
      cxMcVoxFxoAdmPathId             DisplayString,
      cxMcVoxFxoAdmTxGain             INTEGER,
      cxMcVoxFxoAdmRxGain             INTEGER,
      cxMcVoxFxoAdmEchoCancel         INTEGER,
      cxMcVoxFxoAdmSignaling          INTEGER,
      cxMcVoxFxoAdmCnctType           INTEGER,  
      cxMcVoxFxoAdmRingType           INTEGER,
      cxMcVoxFxoAdmImpedance          INTEGER,
      cxMcVoxFxoAdmDialType           INTEGER,
      cxMcVoxFxoAdmDidSignalType      INTEGER,
      cxMcVoxFxoAdmRmtExt             DisplayString,
      cxMcVoxFxoAdmRmtId              DisplayString,
      cxMcVoxFxoAdmTranspMode         INTEGER,
      cxMcVoxFxoAdmFaxEnable          INTEGER,
      cxMcVoxFxoAdmBroadcast          INTEGER
    }

-- USER MODE OBJECTS:

      cxMcVoxFxoAdmCardUsed         OBJECT-TYPE
     SYNTAX INTEGER (1..8)
     ACCESS  read-only
     STATUS  mandatory
     DESCRIPTION
"Displays the slot number of the voice I/O card.

You cannot modify this object. It is a display that the software provides.

Range of Values

CX900: 1 to 6

CX1000: 1 to 8

Default: none"
     ::= { cxMcVoxFxoAdmEntry 1 }

      cxMcVoxFxoAdmPortUsed         OBJECT-TYPE
     SYNTAX INTEGER (1..15)
     ACCESS  read-only
     STATUS  mandatory
     DESCRIPTION
"Displays the number of the voice I/O port.

You cannot modify this object. It is a display that the software provides.

Options:

CX900: 1 is the only acceptable value. Each I/O card only has 1 port.

CX1000: up to 15 for the DI600

Default: none"
     ::= { cxMcVoxFxoAdmEntry 2 }

      cxMcVoxFxoAdmPortStatus       OBJECT-TYPE
     SYNTAX   INTEGER { 
          disable (1),
          enable (2) 
           }
     ACCESS  read-write
     STATUS  mandatory
     DESCRIPTION
"Determines the functional status of the administrative port.

Options:

disable (1): port is not functional

enable (2): port is up and active

Default Value: disable (1)

Configuration Changed: administrative"
     DEFVAL { disable }
     ::= { cxMcVoxFxoAdmEntry 3 }

      cxMcVoxFxoAdmVocoder OBJECT-TYPE
     SYNTAX INTEGER { bps5800 (1),
              bps8000 (2),
              kbps40 (3),
              kbps32 (4),
              kbps24 (5),
              kbps16 (6),
              opt7 (7),
              opt8 (8)
            }
     ACCESS  read-write
     STATUS  mandatory
     DESCRIPTION 
"Determines the transmission speed (in bits per second) of the compressed 
voice stream on the administrative FXO port. Defining the speed also sets 
the ACELP voice compression ratio.

Options:

bps5800 (1): compresses at a higher rate and uses slightly less bandwidth.

bps8000 (2): compresses at approximately an 8:1 ratio (lower rate) with a 
higher quality voice sound at the receiving end.

opt3 (3): ADPCM 40.

opt4 (4): ADPCM 32.

opt5 (5): ADPCM 24.

opt6 (6): ADPCM 16.

opt7 (7): Memotec use only.

opt8 (8): Memotec use only.

Default Value: bps8000 (2)

Configuration Changed: administrative"
     DEFVAL { bps8000 }
     ::= { cxMcVoxFxoAdmEntry 4 }

      cxMcVoxFxoAdmFaxBw      OBJECT-TYPE
     SYNTAX   INTEGER { 
          bps2400 (1),
          bps4800 (2),
          bps7200 (3),
          bps9600 (4)
           }
     ACCESS  read-write
     STATUS  mandatory
     DESCRIPTION
"Determines the speed (in bits per second) of the FAX channel on the 
administrative FXO port. This value also determines the bandwidth required 
to pass FAX traffic through the voice software. This value can be set to 
match the speed of your FAX machine or it can be lowered to reduce 
bandwidth allocation.

Options:

bps2400 (1)

bps4800 (2)

bps7200 (3)

bps9600 (4)

Default Value: bps7200 (3)

Configuration Changed: administrative"
     DEFVAL { bps7200 }
     ::= { cxMcVoxFxoAdmEntry 5 }

-- obsoleted (has been redefined)

      cxMcVoxFxoAdmAutoCnx OBJECT-TYPE
     SYNTAX   INTEGER { 
          no (1),
          yes (2) 
           }
     ACCESS  read-write
     STATUS  obsolete
     DESCRIPTION
"obsolete"
     DEFVAL { no }
      ::= { cxMcVoxFxoAdmEntry 6 }

      cxMcVoxFxoAdmPathId        OBJECT-TYPE
     SYNTAX  DisplayString (SIZE (1..4))
     ACCESS  read-write
     STATUS  deprecated
     DESCRIPTION
"Path IDs no longer exist with the new Voice Routing (VR) 
scheme.

The Path ID is a numeric dialing code the user enters to gain access to 
the remote telephone or fax machine.

Note: The number of digits in the Path ID must match the value of the 
object cxMcVoxPathAdmPathLng of the cxMcVox Administrative Path Group.

Range of Values: 1 to 4 numeric digits

Default Value: none

Configuration Changed: administrative"
	 --#ENDING-VERSION 1
	 DEFVAL { "000" }
     ::= { cxMcVoxFxoAdmEntry 7 }

      cxMcVoxFxoAdmTxGain     OBJECT-TYPE
     SYNTAX INTEGER (820..1180)
     ACCESS  read-write
     STATUS  mandatory
     DESCRIPTION
"Determines the value defining the sound intensity (loudness) of voice 
transmission on the administrative FXO port. The transmission gain can be 
modified in the administrative configuration or be fine-tuned dynamically.

Note: Transmission gains should be modified during a connection (i.e. 
dynamically) as changes in the value affect the local listener.

Range of Values: 820 to 1180 (-18.0dB to 18.0dB)

Default Value: 960

Configuration Changed: administrative"
     DEFVAL { 960 }
     ::= { cxMcVoxFxoAdmEntry 8 }

      cxMcVoxFxoAdmRxGain     OBJECT-TYPE
     SYNTAX INTEGER (820..1180)
     ACCESS  read-write
     STATUS  mandatory
     DESCRIPTION
"Determines the value defining the sound intensity (loudness) of voice 
reception on the administrative FXO port. The reception gain can be 
modified in the administrative configuration or be fine-tuned dynamically.

Note: Reception gains should be modified during a connection (i.e. 
dynamically) as changes in the value affect the remote listener.

Range of Values: 820 to 1180 (-18.0dB to 18.0dB)

Default Value: 960

Configuration Changed: administrative"
     DEFVAL { 960 }
     ::= { cxMcVoxFxoAdmEntry 9 }

      cxMcVoxFxoAdmEchoCancel OBJECT-TYPE
     SYNTAX   INTEGER { 
          disable (1),
          enable (2) 
           }
     ACCESS  read-write
     STATUS  mandatory
     DESCRIPTION
"Determines the state of echo cancellation on the administrative FXO port. 
When set to 'enable' at both the local and remote ends, echo cancellation 
stops echoes from the remote that are heard through the receiver at the 
local end.

Options:

disable (1)

enable (2)

Default Value: enable (2)

Configuration Changed: administrative"
     DEFVAL { enable }
     ::= { cxMcVoxFxoAdmEntry 10 }

      cxMcVoxFxoAdmSignaling  OBJECT-TYPE
     SYNTAX   INTEGER { 
          ground-start (1),
          loop-start   (2),
          did          (3)
           }
     ACCESS  read-write
     STATUS  mandatory
     DESCRIPTION
"Determines the type of signalling the administrative FXO port uses to 
seize the line.

Options:

ground-start (1)

loop-start (2)

did (3)

Default Value: loop-start (2)

Configuration Changed: administrative"
     DEFVAL { loop-start }
     ::= { cxMcVoxFxoAdmEntry  11 }

      cxMcVoxFxoAdmCnctType   OBJECT-TYPE
     SYNTAX   INTEGER { 
          switched (1),
          auto-connect (2),
          fixed (3)
           }
     ACCESS  read-write
     STATUS  mandatory
     DESCRIPTION
"Determines the method the administrative FXO port uses to make 
connections.

Options:

switched (1): the port connects each call according to the dialing code 
the user enters.

auto-connect (2): calls passing through this port always terminate at the 
same remote destination. The port connects to the remote as soon as the 
local receiver enters the off-hook state. Any remote can connect to a port 
with an auto-connect configuration but when the local user initiates the 
call it always goes to the same remote.

fixed (3): calls passing through this port always terminate at the same 
remote destination. The port connects to the remote as soon as the local 
receiver enters the off-hook state. Only the local and remote destinations 
of the connection can use this port. No other remote location can gain 
access to this port.

Default Value: switched (1)

Configuration Changed: administrative"
     DEFVAL { switched }
     ::= { cxMcVoxFxoAdmEntry  12 }
     
      cxMcVoxFxoAdmRingType   OBJECT-TYPE
     SYNTAX   INTEGER { 
          north-american (1),
          international (2)
           }
     ACCESS  read-write
     STATUS  mandatory
     DESCRIPTION
"Determines the ring type of the administrative FXO port. The ring types 
provide different ring timing to match the different ring cycles in 
networks.

Options:

north-american (1)

international (2)

Default Value: north-american (1)

Configuration Changed: administrative"
     DEFVAL { north-american }
     ::= { cxMcVoxFxoAdmEntry  13 }

      cxMcVoxFxoAdmImpedance   OBJECT-TYPE
     SYNTAX   INTEGER { 
          i600-ohms (1),
          i900-ohms (2),
          att       (3),
          aus       (4)
           }
     ACCESS  read-write
     STATUS  mandatory
     DESCRIPTION
"Determines the input line impedance of the administrative FXO 
interface.

Options:

i600-ohms (1)

i900-ohms (2)

att (3)

aus (4)

Default Value: i600-ohms (1)

Configuration Changed: administrative

NOTE: The option aus(4) is added only starting at version 11.
NOTE: This object is READ-ONLY for the CX800."
     DEFVAL { i600-ohms }
     ::= { cxMcVoxFxoAdmEntry  14 }

      cxMcVoxFxoAdmDialType   OBJECT-TYPE
     SYNTAX   INTEGER { 
          dtmf  (1),
          pulse (2)
           }
     ACCESS  read-write
     STATUS  mandatory
     DESCRIPTION
"Determines the dialing method of the administrative FXO port. The dialing 
method refers to the sound that occurs when the user enters each digit of 
the dialing code.

Options:

dtmf (1): (Dual Tone Multifrequence) uses bursts of frequency pairs to 
identify the code the user dials. Tones are generated at a level of -7 
plus or minus 3 dBm for the lower frequency groups and -5 plus or minus 3 
dBm for the higher frequency group. The power level of the higher 
frequency tone is intentionally increased to compensate for the higher 
line loss.

pulse (2): uses bursts (10 plus or minus 0.5 pps) of the main tone 
frequency (2280Hz) to generate the codes the user enters. Tones are 
generated at a level of -4 to -30 dBm for the 2280Hz frequency. The number 
of pulses during one second indicates the code the user dials. With the 
E&M interface, the voice station generates and detects pulses.

Default Value: dtmf 1)

Configuration Changed: administrative"
     DEFVAL { dtmf }
     ::= { cxMcVoxFxoAdmEntry  15 }

      cxMcVoxFxoAdmDidSignalType   OBJECT-TYPE
     SYNTAX   INTEGER { 
          normal  (1),
          delay   (2),
          wink    (3)
           }
     ACCESS  read-write
     STATUS  mandatory
     DESCRIPTION
"Note: This object only applies to those ports with the object 
cxMcVoxFxoAdmSignaling set to 'did'.

Determines the type of signaling on the administrative FXO port. The 
signaling type refers to the line seizure technique.

Options:

normal (1)

delay (2)

wink (3)

Default Value: normal (1)

Configuration Changed: administrative"

     DEFVAL { normal }
     ::= { cxMcVoxFxoAdmEntry  16 }

      cxMcVoxFxoAdmRmtExt    OBJECT-TYPE
     SYNTAX  DisplayString (SIZE (1..5))
     ACCESS  read-write
     STATUS  mandatory
     DESCRIPTION
"Determines the Remote Extension or Group Id used for auto-connection on 
the FXO port.

The Remote Extension is a numeric dialing code that the user enters to 
gain access to the remote telephone or fax machine.

Auto-connection is the connection method that this port uses. A particular 
Remote Extension or Group Id has been assigned to the port so that no 
dialing is required. 

Note: The number of digits in the Remote Extension is determined by the 
object cxMcVoxNetNbDigits of the cxMcVox Global Parameters Group.

Range of Values: 1 to 5 numeric digits

Default Value: none

Configuration Changed: administrative"
   DEFVAL { "000" }
	 --#STARTING-VERSION 1
     ::= { cxMcVoxFxoAdmEntry  17 }

      cxMcVoxFxoAdmRmtId OBJECT-TYPE
   SYNTAX  DisplayString (SIZE (0..10))
   ACCESS  read-write
   STATUS  optional
   DESCRIPTION
"Determines the ID (name) for the remote voice station.

Note:

This object must be defined in order to obtain a successful voice 
connection with fixed type connection.

With the fixed connection method, a particular Remote Extension or Group 
Id is assigned to the port so that no dialing is required. The call to the 
remote is established as soon as the connection is configured.

Range of Values: a maximum of 10 alphanumeric characters in upper-case 
only. You can use any combination of letters and numbers; however you 
cannot use blank spaces. Use a dash or underscore as a delimiter.

Default Value: none

Configuration Changed: administrative"
   DEFVAL { "          " }
	 --#STARTING-VERSION 1
     ::= { cxMcVoxFxoAdmEntry  18 }

      cxMcVoxFxoAdmTranspMode   OBJECT-TYPE
     SYNTAX   INTEGER { 
          emulate (1),
          transparent (2) ,
          local (3)
           }
     ACCESS  read-write
     STATUS  mandatory
     DESCRIPTION
"Determines the whether to use the Transparent mode on the administrative
 port.  In the transparent mode, the local port will answer only after
 the called party has answered to the party to which the call is finally
 destinated.

 The Transparent mode is incompatible with Switched type of
 connection and is automatically disabled when Switched mode is selected
 (only applies to autoconnect and fixed connections).

 The Local mode lets the local port answer right away to a seizure.

Options:

emulate (1): Emulation mode is on

transparent (2): Transparent mode on

local (3): Local mode on

Default Value: emulate (1)

Configuration Changed: administrative"
     DEFVAL { emulate }
	 --#STARTING-VERSION 3
     ::= { cxMcVoxFxoAdmEntry  19 }

      cxMcVoxFxoAdmFaxEnable OBJECT-TYPE
     SYNTAX   INTEGER { 
          disable (1),
          enable (2) 
           }
     ACCESS  read-write
     STATUS  mandatory
     DESCRIPTION
"Determines the state of the Memotec's FAX relay software on the administrative
 E&M port.  When set to 'enable', at both ends, the Memotec's FAX relay 
 software will be used to transfer FAX messages taking into account the 
 'cxMcVoxFxoAdmFaxBw' object.  Otherwise, when set to 'disable', at both ends,
 no FAX relay support is provided, and the FAX goes through the voice coder
 if supported.

Options:

disable (1)

enable (2)

Default Value: enable (2)

Configuration Changed: administrative"
     DEFVAL { enable }
	--#STARTING-VERSION 8
     ::= { cxMcVoxFxoAdmEntry 20 }


      cxMcVoxFxoAdmBroadcast OBJECT-TYPE
     SYNTAX   INTEGER { 
          none (1),
          master (2) ,
          slave (3)
           }
     ACCESS  read-write
     STATUS  mandatory
     DESCRIPTION
"Cetermines the state of the voice broadcast feature. When set to none, no
broadcast is used. When set to master, ...



Options:

none (1)

master (2)

slave (3)

Default Value: none (1)

Configuration Changed: administrative"
     DEFVAL { none }
	--#STARTING-VERSION 10
      ::= { cxMcVoxFxoAdmEntry 21 }

-- =========================================================================


--  cxMcVox OPERATIONAL DRIVER GROUP

cxMcVoxDriverOpe  OBJECT IDENTIFIER ::= { cxMcVox 9 }

--  cxMcVox OPERATIONAL E&M DRIVER GROUP

cxMcVoxEmOpeTable OBJECT-TYPE
   SYNTAX  SEQUENCE OF CxMcVoxEmOpeEntry
   ACCESS  not-accessible
   STATUS  mandatory
   DESCRIPTION
   ""
   ::= { cxMcVoxDriverOpe 1 }

cxMcVoxEmOpeEntry OBJECT-TYPE
   SYNTAX  CxMcVoxEmOpeEntry
   ACCESS  not-accessible
   STATUS  mandatory
   DESCRIPTION
   ""
   INDEX { cxMcVoxEmOpeCardUsed, cxMcVoxEmOpePortUsed }
   ::= { cxMcVoxEmOpeTable 1 }

CxMcVoxEmOpeEntry ::=
   SEQUENCE {
      cxMcVoxEmOpeCardUsed           INTEGER,
      cxMcVoxEmOpePortUsed           INTEGER,
      cxMcVoxEmOpePortStatus         INTEGER,
      cxMcVoxEmOpeVocoder            INTEGER,
      cxMcVoxEmOpeFaxBw              INTEGER,
      cxMcVoxEmOpeAutoCnx            INTEGER,
      cxMcVoxEmOpePathId             DisplayString,
      cxMcVoxEmOpeTxGain             INTEGER,
      cxMcVoxEmOpeRxGain             INTEGER,
      cxMcVoxEmOpeEchoCancel         INTEGER,
      cxMcVoxEmOpeType               INTEGER,
      cxMcVoxEmOpeMode               INTEGER,
      cxMcVoxEmOpeDialType           INTEGER,
      cxMcVoxEmOpeSignalType         INTEGER,
      cxMcVoxEmOpeAc15Type           INTEGER,
      cxMcVoxEmOpeAc15TimeOn         INTEGER,
      cxMcVoxEmOpeAc15TimeOff        INTEGER,
      cxMcVoxEmOpeCnctType           INTEGER,
      cxMcVoxEmOpeRingType           INTEGER,
      cxMcVoxEmOpeRmtExt             DisplayString,
      cxMcVoxEmOpeRmtId              DisplayString,
      cxMcVoxEmOpeTranspMode         INTEGER,
      cxMcVoxEmOpeFaxEnable          INTEGER,
      cxMcVoxEmOpeBroadcast          INTEGER,
      cxMcVoxEmOpeImpedance          INTEGER,
      cxMcVoxEmOpeVoiceConnection    INTEGER
    }
    
    
-- USER MODE OBJECTS:    

      cxMcVoxEmOpeCardUsed       OBJECT-TYPE
     SYNTAX INTEGER (1..8)
     ACCESS  read-only
     STATUS  mandatory
     DESCRIPTION
"Displays the slot number of the voice I/O card.

You cannot modify this object. 

Range of Values:

CX900: 1 to 6

CX1000: 1 to 8

Default: none"
     ::= { cxMcVoxEmOpeEntry 1 }

      cxMcVoxEmOpePortUsed       OBJECT-TYPE
     SYNTAX INTEGER (1..15)
     ACCESS  read-only
     STATUS  mandatory
     DESCRIPTION
"Displays the number of the voice I/O port.

You cannot modify this object.

Options:

CX900: 1 is the only acceptable value. Each I/O card has only 1 port.

CX1000: up to 15 for the DI600

Default: none"
     ::= { cxMcVoxEmOpeEntry 2 }

      cxMcVoxEmOpePortStatus        OBJECT-TYPE
     SYNTAX   INTEGER { 
          disable (1),
          enable (2),
          no-voice-io (3),
          boot-err-1 (31),
          boot-err-2 (32),
          boot-err-3 (33),
          boot-err-4 (34),
          appl-err-1 (41),
          appl-err-2 (42),
          appl-err-3 (43),
          appl-err-4 (44)
           }
     ACCESS  read-only
     STATUS  mandatory
     DESCRIPTION
"Displays the functional status of the operative port.

You cannot modify this object. If you want to change the value you must 
modify the object cxMcVoxEmAdmportStatus of the cxMcVox Administrative 
Driver Group.

Options:

disable (1): port is not functional

enable (2): port is up and active

no-voice-io (3): Memotec use only. Contact Memotec service personnel if 
this value displays.

boot-err-1 (31): Memotec use only. Contact Memotec service personnel if 
this value displays.

boot-err-2 (32): Memotec use only. Contact Memotec service personnel if 
this value displays.

boot-err-3 (33): Memotec use only. Contact Memotec service personnel if 
this value displays.

boot-err-4 (34): Memotec use only. Contact Memotec service personnel if 
this value displays.

appl-err-1 (41): Memotec use only. Contact Memotec service personnel if 
this value displays.

appl-err-2 (42): Memotec use only. Contact Memotec service personnel if 
this value displays.

appl-err-3 (43): Memotec use only. Contact Memotec service personnel if 
this value displays.

appl-err-4 (44): Memotec use only. Contact Memotec service personnel if 
this value displays.

Default Value: disable (1)"
     DEFVAL { disable }
     ::= { cxMcVoxEmOpeEntry 3 }

      cxMcVoxEmOpeVocoder  OBJECT-TYPE
     SYNTAX INTEGER { bps5800 (1),
              bps8000 (2),
              kbps40 (3),
              kbps32 (4),
              kbps24 (5),
              kbps16 (6),
              opt7 (7),
              opt8 (8)
            }
     ACCESS  read-only
     STATUS  mandatory
     DESCRIPTION 
"Displays the transmission speed (in bits per second) of the compressed 
voice stream on the operative E&M port. Defining the speed also sets the 
ACELP voice compression ratio.

You cannot modify this object. If you want to change the value you must 
modify the object cxMcVoxEmAdmVocoder of the cxMcVox Administrative Driver 
Group.

Options:

bps5800 (1): compresses at a higher rate and uses slightly less bandwidth.

bps8000 (2): compresses at approximately an 8:1 ratio (lower rate) with a 
higher quality voice sound at the receiving end.

opt3 (3): ADPCM 40.

opt4 (4): ADPCM 32.

opt5 (5): ADPCM 24.

opt6 (6): ADPCM 16.

opt7 (7): Memotec use only.

opt8 (8): Memotec use only.

Default Value: bps8000"
     DEFVAL { bps8000 }
     ::= { cxMcVoxEmOpeEntry 4 }

      cxMcVoxEmOpeFaxBw    OBJECT-TYPE
     SYNTAX   INTEGER { 
          bps2400 (1),
          bps4800 (2),
          bps7200 (3),
          bps9600 (4)
           }
     ACCESS  read-write
     STATUS  mandatory
     DESCRIPTION
"Determines the speed (in bits per second) of the FAX channel on the 
operative E&M port. This value also determines the bandwidth required to 
pass FAX traffic through the voice software. This value can be set to 
match the speed of your FAX machine or it can be lowered to reduce 
bandwidth allocation.

Options:

bps2400 (1)

bps4800 (2)

bps7200 (3)

bps9600 (4)

Default Value: bps7200 (3)

Configuration Changed: operative"
     DEFVAL { bps7200 }
     ::= { cxMcVoxEmOpeEntry 5 }
     
-- obsoleted object (has been redefined)

      cxMcVoxEmOpeAutoCnx  OBJECT-TYPE
     SYNTAX   INTEGER { 
          no (1),
          yes (2) 
           }
     ACCESS  read-only
     STATUS  obsolete
     DESCRIPTION
"obsolete"
     DEFVAL { no }
      ::= { cxMcVoxEmOpeEntry 6 }

      cxMcVoxEmOpePathId         OBJECT-TYPE
     SYNTAX  DisplayString (SIZE (1..4))
     ACCESS  read-only
     STATUS  deprecated
     DESCRIPTION
"Path IDs no longer exist in the new Voice Routing (VR) scheme.

The Path ID is a numeric dialing code the user enters to gain access to 
the remote telephone or fax machine.

Note: The number of digits in the Path ID must match the value of the 
object cxMcVoxPathOpePathLng of the cxMcVox Operative Path Group.

You cannot modify this object. If you want to change the value you must 
modify the object cxMcVoxEmAdmPathId of the cxMcVox Administrative Driver 
Group.

Range of Values: 1 to 4 numeric digits

Default Value: none"
	 --#ENDING-VERSION 1
     ::= { cxMcVoxEmOpeEntry 7 }

      cxMcVoxEmOpeTxGain      OBJECT-TYPE
     SYNTAX INTEGER (820..1180)
     ACCESS  read-write
     STATUS  mandatory
     DESCRIPTION 
"Determines the value defining the sound intensity (loudness) of voice 
transmissions on the operative E&M port. The transmission gain can be 
modified in the administrative configuration or be fine-tuned dynamically.

Note: Transmission gains should be modified during a connection (i.e. 
dynamically) as changes in the value affect the local listener.

Range of Values: 820 to 1180 (-18.0dB to 18.0dB)

Default Value: 960

Configuration Changed: operative"
     DEFVAL { 960 }
     ::= { cxMcVoxEmOpeEntry 8 }

      cxMcVoxEmOpeRxGain      OBJECT-TYPE
     SYNTAX INTEGER (820..1180)
     ACCESS  read-write
     STATUS  mandatory
     DESCRIPTION 
"Determines the value defining the sound intensity (loudness) of voice 
reception on the operative E&M port. The reception gain can be modified in 
the administrative configuration or be fine-tuned dynamically.

Note: Reception gains should be modified during a connection (i.e. 
dynamically) as changes in the value affect the remote listener.

Range of Values: 820 to 1180 (-18.0dB to 18.0dB)

Default Value: 960

Configuration Changed: operative"
     DEFVAL { 960 }
     ::= { cxMcVoxEmOpeEntry 9 }

      cxMcVoxEmOpeEchoCancel  OBJECT-TYPE
     SYNTAX   INTEGER { 
          disable (1),
          enable (2) 
           }
     ACCESS  read-only
     STATUS  mandatory
     DESCRIPTION
"Displays the state of echo cancellation on the operative E&M port. When 
set to 'enable' at both the local and remote ends, echo cancellation stops 
echoes from the remote that are heard through the receiver at the local 
end.

You cannot modify this object. If you want to change the value you must 
modify the object cxMcVoxEmAdmEchoCancel of the cxMcVox Administrative 
Driver Group.

Options:

disable (1)

enable (2)

Default Value: enable (2)"
     DEFVAL { enable }
      ::= { cxMcVoxEmOpeEntry 10 }

      cxMcVoxEmOpeType     OBJECT-TYPE
     SYNTAX INTEGER {
          type-1  (1),
          type-2  (2),
          type-3  (3),
          type-4  (4),
          type-5  (5)
        }
     ACCESS  read-only
     STATUS  mandatory
     DESCRIPTION 
"Displays the type of E&M interface of the operative E&M port. Each of the 
five interface types has a unique signal-to-wire pattern. Be sure to 
select the interface type that matches your PBX.

You cannot modify this object. If you want to change thevalue you must 
modify the object cxMcVoxEmAdmType of the cxMcVox Administrative Driver 
Group.

Options:

type-1 (1)

type-2 (2)

type-3 (3)

type-4 (4)

type-5 (5)

Default Value: type-2 (2)"
     DEFVAL { type-2 }
     ::= { cxMcVoxEmOpeEntry  11 }

      cxMcVoxEmOpeMode     OBJECT-TYPE
     SYNTAX   INTEGER { 
          normal (1),
          reverse (2) 
           }
     ACCESS  read-only
     STATUS  mandatory
     DESCRIPTION
"Displays the signalling mode for the operative E&M port. The signalling 
mode refers to the wires of the physical connection and how they are 
connected. The mode you select must match the type the PBX punch block 
uses or the port will not be able to communicate with it.

You cannot modify this object. If you want to change the value you must 
modify the object cxMcVoxEmAdmMode of the cxMcVox Administrative Driver 
Group.

Options:

normal (1)

reverse (2)

Default Value: normal (1)"
     DEFVAL { normal }
     ::= { cxMcVoxEmOpeEntry  12 }

      cxMcVoxEmOpeDialType OBJECT-TYPE
     SYNTAX   INTEGER { 
          dtmf (1),
          pulse (2),
          mfR1 (3),
          mfR2 (4)
           }
     ACCESS  read-only
     STATUS  mandatory
     DESCRIPTION 
"Displays the dialing method of the operative E&M port. The dialing method 
refers to the sound that occurs when the user enters each digit of the 
dialing code.

You cannot modify this object. If you want to change the value you must 
modify the object cxMcVoxEmAdmDialType of the cxMcVox Administrative 
Driver Group

Options:

dtmf (1): Dual Tone MultiFrequency uses bursts of frequency pairs to 
identify the code the user dials. Tones are generated at a level of -7 
plus or minus 3 dBm for the lower frequency groups and -5 plus or minus 3 
dBm for the higher frequency group. The power level of the higher 
frequency tone is intentionally increased to compensate for the higher 
line loss.

pulse (2): uses bursts (10 plus or minus 0.5 pps) of the main tone 
frequency (2280Hz) to generate the codes the user enters. Tones are 
generated at a level of -4 to -30 dBm for the 2280Hz frequency. The number 
of pulses during one second indicates the code the user dials. With the 
E&M interface, the voice station generates and detects pulses.

mfR1 (3): R1 signaling protocol MultiFrequency (MF) uses bursts of
frequency pairs to identify the code the user dials. Tones are generated
at a level of -7 dBm0 +- 1 dB (CCITT Recommendation Q.322). The difference
in transmission level between the two frequencies comprises a signal that
does not exceed 0.5 dB.

mfR2 (4): R2 signaling protocol MultiFrequency (MF) uses bursts of
frequency pairs to identify the code the user dials. Tones are generated
at a level of -8 dBm0 +- 1 dB (CCITT Recommendation Q.454). The difference
in transmission level between the two frequencies comprises a signal that
does not exceed 1 dB.


Default Value: dtmf (1)"
     DEFVAL { dtmf }
     ::= { cxMcVoxEmOpeEntry  13 }
     
      cxMcVoxEmOpeSignalType  OBJECT-TYPE
     SYNTAX   INTEGER { 
          normal (1),
          delay (2),
          wink (3),
          ac15 (4),
          openchn (5),
          r2 (6),
          mfcr2 (7),
          isdn (8)
           }
     ACCESS  read-only
     STATUS  mandatory
     DESCRIPTION 
"Displays the type of signalling the operative E&M port uses to seize the 
line.

You cannot modify this object. If you want to change the value you must 
modify thee object cxMcVoxEmAdmSignalType of the cxMcVox Administrative 
Driver Group.

Options:

normal (1)

delay (2)

wink (3)

ac15 (4)

openChn (5)

R2 (6)

MFCR2 (7)

isdn (8)

Default Value: normal (1)"
     DEFVAL { normal }
     ::= { cxMcVoxEmOpeEntry  14 }

      cxMcVoxEmOpeAc15Type   OBJECT-TYPE
     SYNTAX   INTEGER { 
          normal (1),
          delay (2)
           }
     ACCESS  read-only
     STATUS  mandatory
     DESCRIPTION 
"Displays the type of AC15 signals the operative E&M port uses to seize 
the line for transmission.

This object is only relevant to E&M ports using the AC15 signalling type 
(as defined using the object cxMcVoxEmAdmSignalType of the cxMcVox 
Administrative Driver Group).

You cannot modify this object. If you want to change the value you must 
modify the object cxMcVoxEmAdmAcType of the cxMcVox Administrative Driver 
Group.

Options:

normal (1)

delay (2)

Default Value: normal"
     DEFVAL { normal }
     ::= { cxMcVoxEmOpeEntry  15 }

      cxMcVoxEmOpeAc15TimeOn OBJECT-TYPE
     SYNTAX INTEGER (0..60000)
     ACCESS  read-write
     STATUS  mandatory
     DESCRIPTION 
"Determines the length of time, in milliseconds, the AC15 pulse remains 
on.

This object is only relevant to E&M ports using the AC15 signalling type 
(as defined using the object cxMcVoxEmOpeSignalType of this table).

Range of Values: 0 to 60000

Default Value: 60

Configuration Changed: operative"
     DEFVAL { 60 }
     ::= { cxMcVoxEmOpeEntry  16 }

      cxMcVoxEmOpeAc15TimeOff   OBJECT-TYPE
     SYNTAX INTEGER (0..60000)
     ACCESS  read-write
     STATUS  mandatory
     DESCRIPTION 
"Determines the length of time, in milliseconds, the AC15 pulse remains 
off.

This object is only relevant to E&M ports using the AC15 signalling type 
(as defined using the object cxMcVoxEmOpeSignalType of this table).

Range of Values: 0 to 60000

Default Value: 40

Configuration Changed: operative"
     DEFVAL { 40 }
     ::= { cxMcVoxEmOpeEntry  17 }

      cxMcVoxEmOpeCnctType   OBJECT-TYPE
     SYNTAX   INTEGER { 
          switched (1),
          auto-connect (2),
          fixed (3)
           }
     ACCESS  read-only
     STATUS  mandatory
     DESCRIPTION
"Displays the method the operative E&M port uses to make connections.

This object is only relevant to E&M ports using the AC15 signalling type 
(as defined using the object cxMcVoxEmOpeSignalType of this table).

You cannot modify this object. If you want to change the value you must 
modify the object cxMcVoxEmAdmCnctType of the cxMcVox Administrative 
Driver Group.

Options:

switched (1): the port connects each call according to the dialing code 
the user enters.

auto-connect (2): calls passing through this port always terminate at the 
same remote destination. The port connects to the remote as soon as the 
local receiver enters the off-hook state. Any remote can connect to a port 
with an auto-connect configuration but when the local user initiates the 
call it always goes to the same remote.

fixed (3): calls passing through this port always terminate at the same 
remote destination. The port connects to the remote as soon as the local 
receiver enters the off-hook state. Only the local and remote destinations 
of the connection can use this port. No other remote location can gain 
access to this port.

Default Value: switched (1)"
     DEFVAL { switched }
     ::= { cxMcVoxEmOpeEntry  18 }
     
      cxMcVoxEmOpeRingType   OBJECT-TYPE
     SYNTAX   INTEGER { 
          north-american (1),
          international (2)
           }
     ACCESS  read-only
     STATUS  mandatory
     DESCRIPTION
"Displays the ring type of the operative E&M port. The ring types provide 
different ring timing to match the different ring cycles in networks.

You cannot modify this object. If you want to change the value you must 
modify the object cxMcVoxEmAdmRingType of the cxMcVox Administrative 
Driver Group.

Options:

north-american (1)

international (2)

Default Value: north-american (1)"
     DEFVAL { north-american }
     ::= { cxMcVoxEmOpeEntry  19 }

      cxMcVoxEmOpeRmtExt    OBJECT-TYPE
     SYNTAX  DisplayString (SIZE (1..5))
     ACCESS  read-only
     STATUS  mandatory
     DESCRIPTION
"Determines the Remote Extension or Group Id used for auto-connection on 
the E&M port.

The Remote Extension is a numeric dialing code that the user enters to 
access to the remote telephone or fax machine.

Auto-connection is the connection method that this port uses. A particular 
Remote Extension or Group Id has been assigned to the port so that no 
dialing is required. 

Note: The number of digits in the Remote Extension is determined by the 
object cxMcVoxNetNbDigits of the cxMcVox Global Parameters Group.

Range of Values: 1 to 5 numeric digits

Default Value: none

Configuration Changed: operative"
	 --#STARTING-VERSION 1
     ::= { cxMcVoxEmOpeEntry 20 }

      cxMcVoxEmOpeRmtId OBJECT-TYPE
   SYNTAX  DisplayString (SIZE (0..10))
   ACCESS  read-only
   STATUS  optional
   DESCRIPTION
"Displays the ID (name) for the remote voice station.

Note: This object must be defined in order to obtain a successful voice 
connection via the fixed connection method.

You cannot modify this object. If you want to change the ID you must 
modify the object cxMcVoxEmAdmRmtId (of this table).

With the fixed connection method, a particular Remote Extension or Group 
Id is assigned to the port so that no dialing is required. The call to the 
remote is established as soon as the connection is configured.

Range of Values: a maximum of 10 alphanumeric characters in upper-case 
only. You can use any combination of letters and numbers; however you 
cannot use blank spaces. Use a dash or underscore as a delimiter.

Default Value: none"
	 --#STARTING-VERSION 1
     ::= { cxMcVoxEmOpeEntry  21 }

      cxMcVoxEmOpeTranspMode   OBJECT-TYPE
     SYNTAX   INTEGER { 
          emulate (1),
          transparent (2) ,
          local (3)
           }
     ACCESS  read-only
     STATUS  mandatory
     DESCRIPTION
"Determines the whether to use the Transparent mode on the administrative
 port.  In the transparent mode, the local port will answer only after
 the called party has answered to the party to which the call is finally
 destinated.

 The Transparent mode is incompatible with Switched type of
 connection and is automatically disabled when Switched mode is selected
 (only applies to autoconnect and fixed connections).

 The Local mode lets the local port answer right away to a seizure.

Options:

emulate (1): Emulation mode is on

transparent (2): Transparent mode on

local (3): Local mode on

Default Value: emulate (1)

Configuration Changed: operational"
     DEFVAL { emulate }
	 --#STARTING-VERSION 3
     ::= { cxMcVoxEmOpeEntry  22 }
      
      cxMcVoxEmOpeFaxEnable  OBJECT-TYPE
     SYNTAX   INTEGER { 
          disable (1),
          enable (2) 
           }
     ACCESS  read-only
     STATUS  mandatory
     DESCRIPTION
"Displays the state of the FAX on the operative E&M port. When 
set to 'enable' at both the local and remote ends, the FAX will be
enabled.

You cannot modify this object. If you want to change the value you must 
modify the object cxMcVoxEmAdmFaxEnable of the cxMcVox Administrative 
Driver Group.

Options:

disable (1)

enable (2)

Default Value: enable (2)"
     DEFVAL { enable }
	--#STARTING-VERSION 8
      ::= { cxMcVoxEmOpeEntry 23 }


      cxMcVoxEmOpeBroadcast  OBJECT-TYPE
     SYNTAX   INTEGER { 
          none (1),
          master (2) ,
          slave (3)
           }
     ACCESS  read-only
     STATUS  mandatory
     DESCRIPTION
"Cetermines the state of the voice broadcast feature. When set to none, no
broadcast is used. When set to master, ...



Options:

none (1)

master (2)

slave (3)

Default Value: none (1)"
     DEFVAL { none }
	--#STARTING-VERSION 10
      ::= { cxMcVoxEmOpeEntry 24 }

      cxMcVoxEmOpeImpedance   OBJECT-TYPE
     SYNTAX   INTEGER { 
          i600-ohms (1),
          i900-ohms (2),
          att       (3),
          aus       (4)
           }
     ACCESS  read-write
     STATUS  mandatory
     DESCRIPTION
"Displays the input line impedance of the operative E&M interface. 
The value of this object can be modified in operational mode.

Options:

i600-ohms (1)

i900-ohms (2)

att (3)

aus (4)

Default Value: i600-ohms (1)

NOTE: This object is READ-ONLY for the CX800."
     DEFVAL { i600-ohms }
	 --#STARTING-VERSION 11
     ::= { cxMcVoxEmOpeEntry  25 }

      cxMcVoxEmOpeVoiceConnection   OBJECT-TYPE
     SYNTAX   INTEGER { 
          two-wires  (1),
          four-wires (2)
           }
     ACCESS  read-only
     STATUS  mandatory
     DESCRIPTION
"Indicates which voice path is provided by the 
E&M interface.

Options:

two-wires (1)

four-wires (2)"
	 --#STARTING-VERSION 11
     ::= { cxMcVoxEmOpeEntry  26 }

-- ..........................................................................


--  cxMcVox OPERATIONAL FXS DRIVER GROUP

cxMcVoxFxsOpeTable OBJECT-TYPE
   SYNTAX  SEQUENCE OF CxMcVoxFxsOpeEntry
   ACCESS  not-accessible
   STATUS  mandatory
   DESCRIPTION
      "cx Voice Station active FXS Table."
   ::= { cxMcVoxDriverOpe 2 }

cxMcVoxFxsOpeEntry OBJECT-TYPE
   SYNTAX  CxMcVoxFxsOpeEntry
   ACCESS  not-accessible
   STATUS  mandatory
   DESCRIPTION
      "cx Voice Station active FXS Entry "
   INDEX { cxMcVoxFxsOpeCardUsed, cxMcVoxFxsOpePortUsed }
   ::= { cxMcVoxFxsOpeTable 1 }

CxMcVoxFxsOpeEntry ::=
   SEQUENCE {
      cxMcVoxFxsOpeCardUsed           INTEGER,        
      cxMcVoxFxsOpePortUsed           INTEGER,
      cxMcVoxFxsOpePortStatus         INTEGER,
      cxMcVoxFxsOpeVocoder            INTEGER,
      cxMcVoxFxsOpeFaxBw              INTEGER,
      cxMcVoxFxsOpeAutoCnx            INTEGER,
      cxMcVoxFxsOpePathId             DisplayString,
      cxMcVoxFxsOpeTxGain             INTEGER,
      cxMcVoxFxsOpeRxGain             INTEGER,
      cxMcVoxFxsOpeEchoCancel         INTEGER,
      cxMcVoxFxsOpeSignaling          INTEGER,
      cxMcVoxFxsOpeTimeOn             INTEGER,
      cxMcVoxFxsOpeTimeOff            INTEGER,
      cxMcVoxFxsOpeCnctType           INTEGER,
      cxMcVoxFxsOpeRingType           INTEGER,
      cxMcVoxFxsOpeImpedance          INTEGER,
      cxMcVoxFxsOpeDialType           INTEGER,
      cxMcVoxFxsOpeDidSignalType      INTEGER,
      cxMcVoxFxsOpeRmtExt             DisplayString,
      cxMcVoxFxsOpeRmtId              DisplayString,
      cxMcVoxFxsOpeTranspMode         INTEGER,
      cxMcVoxFxsOpeFaxEnable          INTEGER,
      cxMcVoxFxsOpeBroadcast          INTEGER
    }

-- USER MODE OBJECTS:

      cxMcVoxFxsOpeCardUsed         OBJECT-TYPE
     SYNTAX INTEGER (1..8)
     ACCESS  read-only
     STATUS  mandatory
     DESCRIPTION
"Displays the slot number of the voice I/O card.

You cannot modify this object.

Range of Values:

CX900: 1 to 6

CX1000: 1 to 8

Default: none"
     ::= { cxMcVoxFxsOpeEntry 1 }

      cxMcVoxFxsOpePortUsed         OBJECT-TYPE
     SYNTAX INTEGER (1..15)
     ACCESS  read-only
     STATUS  mandatory
     DESCRIPTION
"Displays the number of the voice I/O port.

You cannot modify this object

Options:

CX900: 1 is the only acceptable value. Each I/O card has only 1 port.

CX1000: up to 15 for the DI600

Default: none"
     ::= { cxMcVoxFxsOpeEntry 2 }

      cxMcVoxFxsOpePortStatus       OBJECT-TYPE
     SYNTAX   INTEGER { 
          disable (1),
          enable (2),
          no-voice-io (3),
          boot-err-1 (31),
          boot-err-2 (32),
          boot-err-3 (33),
          boot-err-4 (34),
          appl-err-1 (41),
          appl-err-2 (42),
          appl-err-3 (43),
          appl-err-4 (44)
           }
     ACCESS  read-only
     STATUS  mandatory
     DESCRIPTION
"Displays the functional status of the operative port.

You cannot modify this object. If you want to change the value you must 
modify the object cxMcVoxFxsAdmportStatus of the cxMcVox Administrative 
FXS Driver Group.

Options:

disable (1): port is not functional

enabled (2): port is up and active

no-voice-io (3): Memotec use only. Contact Memotec service personnel if 
this value displays.

boot-err-1 (31): = Memotec use only. Contact Memotec service personnel if 
this value displays.

boot-err-2 (32): Memotec use only. Contact Memotec service personnel if 
this value displays.

boot-err-3 (33): Memotec use only. Contact Memotec service personnel if 
this value displays.

boot-err-4 (34): Memotec use only. Contact Memotec service personnel if 
this value displays.

appl-err-1 (41): Memotec use only. Contact Memotec service personnel if 
this value displays.

appl-err-2 (42): Memotec use only. Contact Memotec service personnel if 
this value displays.

appl-err-3 (43): Memotec use only. Contact Memotec service personnel if 
this value displays.

appl-err-4 (44): Memotec use only. Contact Memotec service personnel if 
this value displays.

Default Value: disable (1)"
     DEFVAL { disable }
     ::= { cxMcVoxFxsOpeEntry 3 }

      cxMcVoxFxsOpeVocoder OBJECT-TYPE
     SYNTAX INTEGER { bps5800 (1),
              bps8000 (2),
              kbps40 (3),
              kbps32 (4),
              kbps24 (5),
              kbps16 (6),
              opt7 (7),
              opt8 (8)
            }
     ACCESS  read-only
     STATUS  mandatory
     DESCRIPTION 
"Displays the transmission speed (in bits per second) of the compressed 
voice stream on the operative FXS port. Defining the speed also sets the 
ACELP voice compression ratio.

You cannot modify this object. If you want to change the value you must 
modify the object cxMcVoxFxsAdmVocoder of the cxMcVox Administrative FXS 
Driver Group.

Options:

bps5800 (1): compresses at a higher rate and uses slightly less bandwidth.

bps8000 (2): compresses at approximately an 8:1 ratio (lower rate) with a 
higher quality voice sound at the receiving end.

opt3 (3): ADPCM 40.

opt4 (4): ADPCM 32.

opt5 (5): ADPCM 24.

opt6 (6): ADPCM 16.

opt7 (7): Memotec use only.

opt8 (8): Memotec use only.

Default Value: bps8000 (2)"

     DEFVAL { bps8000 }
     ::= { cxMcVoxFxsOpeEntry 4 }

      cxMcVoxFxsOpeFaxBw      OBJECT-TYPE
     SYNTAX   INTEGER { 
          bps2400 (1),
          bps4800 (2),
          bps7200 (3),
          bps9600 (4)
           }
     ACCESS  read-write
     STATUS  mandatory
     DESCRIPTION
"Determines the speed (in bits per second) of the FAX channel on the 
operative FXS port. This value also determines the bandwidth required to 
pass FAX traffic through the voice software. This value can be set to 
match the speed of your FAX machine or it can be lowered to reduce 
bandwidth allocation.

Options:

bps2400 (1)

bps4800 (2)

bps7200 (3)

bps9600 (4)

Default Value: bps7200 (3)

Configuration Changed: operative"
     DEFVAL { bps7200 }
     ::= { cxMcVoxFxsOpeEntry 5 }

-- obsoleted (has been redefined)

      cxMcVoxFxsOpeAutoCnx OBJECT-TYPE
     SYNTAX   INTEGER { 
          no (1),
          yes (2) 
           }
     ACCESS  read-only
     STATUS  obsolete
     DESCRIPTION
"Obsolete"
     DEFVAL { no }
      ::= { cxMcVoxFxsOpeEntry 6 }

      cxMcVoxFxsOpePathId        OBJECT-TYPE
     SYNTAX  DisplayString (SIZE (1..4))
     ACCESS  read-only
     STATUS  deprecated
     DESCRIPTION
"Path IDs no longer exist in the new Voice Routing (VR) scheme.

The PathID was formerly used for auto-connection on the operative FXS 
port.

The Path ID is a numeric dialing code the user enters to gain access to 
the remote telephone or fax machine.

Note: The number of digits in the Path ID must match the value of the 
object cxMcVoxPathOpePathLng of the cxMcVox Operative Path Group.

You cannot modify this object. If you want to change the value you must 
modify the object cxMcVoxFxsAdmPathId of the cxMcVox Administrative FXS 
Driver Group.

Range of Values: 1 to 4 numeric digits

Default Value: none
"
	 --#ENDING-VERSION 1
     ::= { cxMcVoxFxsOpeEntry 7 }

      cxMcVoxFxsOpeTxGain     OBJECT-TYPE
     SYNTAX INTEGER (820..1180)
     ACCESS  read-write
     STATUS  mandatory
     DESCRIPTION
"Determines the value defining the sound intensity (loudness) of voice 
transmissions on the operative FXS port. The transmission gain can be 
modified in the administrative configuration or be fine-tuned dynamically.
 Note: Transmission gains should be modified during a connection (i.e. 
dynamically) as changes in the value affect the local listener.

Range of Values: 820 to 1180 (-18.0dB to 18.0dB)

Default Value: 960

Configuration Changed: operative"
     DEFVAL { 960 }
     ::= { cxMcVoxFxsOpeEntry 8 }

      cxMcVoxFxsOpeRxGain     OBJECT-TYPE
     SYNTAX INTEGER (820..1180)
     ACCESS  read-write
     STATUS  mandatory
     DESCRIPTION
"Determines the value defining the sound intensity (loudness) of voice 
reception on the operative FXS port. The reception gain can be modified in 
the administrative configuration or be fine-tuned dynamically.

Note: Reception gains should be modified during a connection (i.e. 
dynamically) as changes in the value affect the remote listener.

Range of Values: 820 to 1180 (-18.0dB to 18.0dB)

Default Value: 960

Configuration Changed: operative"
     DEFVAL { 960 }
     ::= { cxMcVoxFxsOpeEntry 9 }

      cxMcVoxFxsOpeEchoCancel OBJECT-TYPE
     SYNTAX   INTEGER { 
          disable (1),
          enable (2) 
           }
     ACCESS  read-only
     STATUS  mandatory
     DESCRIPTION
"Displays the state of echo cancellation on the operative FXS port. When 
set to 'enable' at both the local and remote ends, echo cancellation stops 
echoes from the remote that are heard through the receiver at the local 
end.

You cannot modify this object. If you want to change the value you must 
modify the object cxMcVoxFxsAdmEchoCancel of the cxMcVox Administrative 
FXS Driver Group.

Options:

disable (1)

enable (2)

Default Value: enable (2)"
     DEFVAL { enable }
     ::= { cxMcVoxFxsOpeEntry 10 }


      cxMcVoxFxsOpeSignaling  OBJECT-TYPE
     SYNTAX   INTEGER { 
          ground-start (1),
          loop-start   (2),
          did          (3)
           }
     ACCESS  read-only
     STATUS  mandatory
     DESCRIPTION
"Displays the type of signalling the operative FXS port uses to seize the 
line.

You cannot modify this object. If you want to change the value you must 
modify the object cxMcVoxfxsAdmSignaling of the cxMcVox Administrative FXS 
Driver Group.

Options:

ground-start (1)

loop-start (2)

did (3)

Default Value: loop-start"
     DEFVAL { loop-start }
     ::= { cxMcVoxFxsOpeEntry  11 }

-- obsoleted object (has been redefined)

      cxMcVoxFxsOpeTimeOn  OBJECT-TYPE
     SYNTAX INTEGER (10..10000)
     ACCESS  read-only
     STATUS  obsolete
     DESCRIPTION 
"Obsolete"
     DEFVAL { 2000 }
     ::= { cxMcVoxFxsOpeEntry  12 }

-- obsoleted object (has been redefined)

      cxMcVoxFxsOpeTimeOff OBJECT-TYPE
     SYNTAX INTEGER (10..10000)
     ACCESS  read-only
     STATUS  obsolete
     DESCRIPTION 
"Obsoleted"
     DEFVAL { 4000 }
     ::= { cxMcVoxFxsOpeEntry  13 }

      cxMcVoxFxsOpeCnctType   OBJECT-TYPE
     SYNTAX   INTEGER { 
          switched (1),
          auto-connect (2),
          fixed (3)
           }
     ACCESS  read-only
     STATUS  mandatory
     DESCRIPTION
"Displays the method the operative FXS port uses to make connections.

You cannot modify this object. If you want to change the value you must 
modify the object cxMcVoxFxsAdmCnctType of the cxMcVox Administrative FXS 
Driver Group.

Options:

switched (1): the port connects each call according to the dialing code 
the user enters.

auto-connect (2): calls passing through this port always terminate at the 
same remote destination. The port connects to the remote as soon as the 
local receiver enters the off-hook state. Any remote can connect to a port 
with an auto-connect configuration but when the local user initiates the 
call it always goes to the same remote.

fixed (3): calls passing through this port always terminate at the same 
remote destination. The port connects to the remote as soon as the local 
receiver enters the off-hook state. Only the local and remote destinations 
of the connection can use this port. No other remote location can gain 
access to this port.

Default Value: switched (1)"
     DEFVAL { switched }
     ::= { cxMcVoxFxsOpeEntry  14 }
     
      cxMcVoxFxsOpeRingType   OBJECT-TYPE
     SYNTAX   INTEGER { 
          north-american (1),
          international (2)
           }
     ACCESS  read-only
     STATUS  mandatory
     DESCRIPTION
"Displays the ring type of the operative FXS port. The ring types provide 
different ring timing to match the different ring cycles in networks.

You cannot modify this object. If you want to change the value you must 
modify the object cxMcVoxFxsAdmRingType of the cxMcVox Administrative FXS 
Driver Group.

Options:

north-american (1)

international (2)

Default Value: north-american (1)"
     DEFVAL { north-american }
     ::= { cxMcVoxFxsOpeEntry  15 }

      cxMcVoxFxsOpeImpedance   OBJECT-TYPE
     SYNTAX   INTEGER { 
          i600-ohms (1),
          i900-ohms (2),
          att       (3),
          aus       (4)
           }
     ACCESS  read-write
     STATUS  mandatory
     DESCRIPTION
"Displays the input line impedance of the operative FXS interface. 
The value of this object can be modified in operational mode.

Options:

i600-ohms (1)

i900-ohms (2)

att (3)

aus (4)

Default Value: i600-ohms

NOTE: The option aus(4) is added only starting at version 11.
NOTE: This object is READ-ONLY for the CX800."
     DEFVAL { i600-ohms }
     ::= { cxMcVoxFxsOpeEntry  16 }

      cxMcVoxFxsOpeDialType   OBJECT-TYPE
     SYNTAX   INTEGER { 
          dtmf  (1),
          pulse (2)
           }
     ACCESS  read-only
     STATUS  mandatory
     DESCRIPTION
"Displays the dialing method of the operative FXS port. The dialing method 
refers to the sound that occurs when the user enters each digit of the 
dialing code.

You cannot modify this object. If you want to change the value you must 
modify the object cxMcVoxFxsAdmDialType of the cxMcVox Administrative FXS 
Driver Group table.

Options:

dtmf (1): (Dual Tone Multifrequence) uses bursts of frequency pairs to 
identify the code the user dials. Tones are generated at a level of -7 
plus or minus 3 dBm for the lower frequency groups and -5 plus or minus 3 
dBm for the higher frequency group. The power level of the higher 
frequency tone is intentionally increased to compensate for the higher 
line loss.

pulse (2): uses bursts (10 plus or minus 0.5 pps) of the main tone 
frequency (2280Hz) to generate the codes the user enters. Tones are 
generated at a level of -4 to -30 dBm for the 2280Hz frequency. The number 
of pulses during one second indicates the code the user dials. With the 
E&M interface, the voice station generates and detects pulses.

Default Value: dtmf (1)"
     ::= { cxMcVoxFxsOpeEntry  17 }

      cxMcVoxFxsOpeDidSignalType   OBJECT-TYPE
     SYNTAX   INTEGER { 
          normal  (1),
          delay   (2),
          wink    (3)
           }
     ACCESS  read-only
     STATUS  mandatory
     DESCRIPTION
"Displays the type of signaling on the operative FXS port. The signaling 
type refers to the line seizure technique.

You cannot modify this object. If you want to change the value you must 
modify the object cxMcVoxFxsAdmDidSignalType of the cxMcVox Administrative 
FXS Driver Group table.

Options

normal (1)

delay (2)

wink (3)

Default Value: normal (1)"
     ::= { cxMcVoxFxsOpeEntry  18 }

      cxMcVoxFxsOpeRmtExt    OBJECT-TYPE
     SYNTAX  DisplayString (SIZE (1..5))
     ACCESS  read-only
     STATUS  mandatory
     DESCRIPTION
"Determines the Remote Extension or Group Id used for auto-connection on 
the FXS port.

The Remote Extension is a numeric dialing code that the user enters to 
gain access to the remote telephone or fax machine.

Auto-connection is the connection method that this port uses. A particular 
Remote Extension or Group Id has been assigned to the port so that no 
dialing is required. 

Note: The number of digits in the Remote Extension is determined by the 
object cxMcVoxNetNbDigits of the cxMcVox Global Parameters Group.

Range of Values: 1 to 5 numeric digits

Default Value: none

Configuration Changed: operative"
	 --#STARTING-VERSION 1
     ::= { cxMcVoxFxsOpeEntry 19 }

      cxMcVoxFxsOpeRmtId OBJECT-TYPE
   SYNTAX  DisplayString (SIZE (0..10))
   ACCESS  read-only
   STATUS  optional
   DESCRIPTION
"Displays the ID (name) for the remote voice station.

Note: This object must be defined in order to obtain a successful voice 
connection via the fixed connection method.

With the fixed connection method, a particular Remote Extension or Group 
Id is assigned to the port so that no dialing is required. The call to the 
remote is established as soon as the connection is configured.

You cannot modify this object. If you want to change the ID you must 
modify the object cxMcVoxFxsAdmRmtId (of this table). 

Range of Values: a maximum of 10 alphanumeric characters in upper-case 
only. You can use any combination of letters and numbers; however you 
cannot use blank spaces. Use a dash or underscore as a delimiter.

Default Value: none"
	 --#STARTING-VERSION 1
     ::= { cxMcVoxFxsOpeEntry  20 }

      cxMcVoxFxsOpeTranspMode   OBJECT-TYPE
     SYNTAX   INTEGER { 
          emulate (1),
          transparent (2) ,
          local (3)
           }
     ACCESS  read-only
     STATUS  mandatory
     DESCRIPTION
"Determines the whether to use the Transparent mode on the administrative
 port.  In the transparent mode, the local port will answer only after
 the called party has answered to the party to which the call is finally
 destinated.

 The Transparent mode is incompatible with Switched type of
 connection and is automatically disabled when Switched mode is selected
 (only applies to autoconnect and fixed connections).

 The Local mode lets the local port answer right away to a seizure.

Options:

emulate (1): Emulation mode is on

transparent (2): Transparent mode on

local (3): Local mode on

Default Value: emulate (1)

Configuration Changed: operational"
     DEFVAL { emulate }
	 --#STARTING-VERSION 3
     ::= { cxMcVoxFxsOpeEntry  21 }


      cxMcVoxFxsOpeFaxEnable OBJECT-TYPE
     SYNTAX   INTEGER { 
          disable (1),
          enable (2) 
           }
     ACCESS  read-only
     STATUS  mandatory
     DESCRIPTION
"Displays the state of the FAX on the operative FXS port. When 
set to 'enable' at both the local and remote ends, the FAX will be 
enabled.

You cannot modify this object. If you want to change the value you must 
modify the object cxMcVoxFxsAdmFaxEnable of the cxMcVox Administrative 
FXS Driver Group.

Options:

disable (1)

enable (2)

Default Value: enable (2)"
     DEFVAL { enable }
	--#STARTING-VERSION 8
     ::= { cxMcVoxFxsOpeEntry 22 }


      cxMcVoxFxsOpeBroadcast  OBJECT-TYPE
     SYNTAX   INTEGER { 
          none (1),
          master (2) ,
          slave (3)
           }
     ACCESS  read-only
     STATUS  mandatory
     DESCRIPTION
"Cetermines the state of the voice broadcast feature. When set to none, no
broadcast is used. When set to master, ...



Options:

none (1)

master (2)

slave (3)

Default Value: none (1)"
     DEFVAL { none }
	--#STARTING-VERSION 10
      ::= { cxMcVoxFxsOpeEntry 23 }

-- ..........................................................................


--  cxMcVox OPERATIONAL FXO DRIVER GROUP

cxMcVoxFxoOpeTable OBJECT-TYPE
   SYNTAX  SEQUENCE OF CxMcVoxFxoOpeEntry
   ACCESS  not-accessible
   STATUS  mandatory
   DESCRIPTION
      "cx Voice Station active FXO Table."
   ::= { cxMcVoxDriverOpe 3 }

cxMcVoxFxoOpeEntry OBJECT-TYPE
   SYNTAX  CxMcVoxFxoOpeEntry
   ACCESS  not-accessible
   STATUS  mandatory
   DESCRIPTION
      "cx Voice Station active FXO Entry "
   INDEX { cxMcVoxFxoOpeCardUsed, cxMcVoxFxoOpePortUsed }
   ::= { cxMcVoxFxoOpeTable 1 }

CxMcVoxFxoOpeEntry ::=
   SEQUENCE {
      cxMcVoxFxoOpeCardUsed           INTEGER,        
      cxMcVoxFxoOpePortUsed           INTEGER,
      cxMcVoxFxoOpePortStatus         INTEGER,
      cxMcVoxFxoOpeVocoder            INTEGER,
      cxMcVoxFxoOpeFaxBw              INTEGER,
      cxMcVoxFxoOpeAutoCnx            INTEGER,
      cxMcVoxFxoOpePathId             DisplayString,
      cxMcVoxFxoOpeTxGain             INTEGER,
      cxMcVoxFxoOpeRxGain             INTEGER,
      cxMcVoxFxoOpeEchoCancel         INTEGER,
      cxMcVoxFxoOpeSignaling          INTEGER,
      cxMcVoxFxoOpeCnctType           INTEGER,  
      cxMcVoxFxoOpeRingType           INTEGER,
      cxMcVoxFxoOpeImpedance          INTEGER,
      cxMcVoxFxoOpeDialType           INTEGER,
      cxMcVoxFxoOpeDidSignalType      INTEGER,
      cxMcVoxFxoOpeRmtExt             DisplayString,
      cxMcVoxFxoOpeRmtId              DisplayString,
      cxMcVoxFxoOpeTranspMode         INTEGER,
      cxMcVoxFxoOpeFaxEnable          INTEGER,
      cxMcVoxFxoOpeBroadcast          INTEGER
    }

-- USER MODE OBJECTS:

      cxMcVoxFxoOpeCardUsed         OBJECT-TYPE
     SYNTAX INTEGER (1..8)
     ACCESS  read-only
     STATUS  mandatory
     DESCRIPTION
"Displays the slot number of the voice I/O card.

You cannot modify this object.

Range of Values:

CX900: 1 to 6

CX1000 1 to 8

Default: none"
     ::= { cxMcVoxFxoOpeEntry 1 }

      cxMcVoxFxoOpePortUsed         OBJECT-TYPE
     SYNTAX INTEGER (1..15)
     ACCESS  read-only
     STATUS  mandatory
     DESCRIPTION
"Displays the number of the voice I/O port.

You cannot modify this object.

Options:

CX900: 1 is the only acceptable value. Each I/O card has only 1 port.

CX1000: up to 15 for the DI600

Default: none"
     ::= { cxMcVoxFxoOpeEntry 2 }

      cxMcVoxFxoOpePortStatus       OBJECT-TYPE
     SYNTAX   INTEGER { 
          disable (1),
          enable (2),
          no-voice-io (3),
          boot-err-1 (31),
          boot-err-2 (32),
          boot-err-3 (33),
          boot-err-4 (34),
          appl-err-1 (41),
          appl-err-2 (42),
          appl-err-3 (43),
          appl-err-4 (44)
           }
     ACCESS  read-only
     STATUS  mandatory
     DESCRIPTION
"Displays the functional status of the port.

You cannot modify this object. If you want to change the value you must 
modify the object cxMcVoxFxoAdmportStatus of the cxMcVox Administrative 
FXO Driver Group.

Options:

disable (1): port is not functional

enable (2): port is up and active

no-voice-io (3): Memotec use only. Contact Memotec service personnel if 
this value displays.

boot-err-1 (31): Memotec use only. Contact Memotec service personnel if 
this value displays.

boot-err-2 (32): Memotec use only. Contact Memotec service personnel if 
this value displays.

boot-err-3 (33): Memotec use only. Contact Memotec service personnel if 
this value displays.

boot-err-4 (34): Memotec use only. Contact Memotec service personnel if 
this value displays.

appl-err-1 (41): Memotec use only. Contact Memotec service personnel if 
this value displays.

appl-err-2 (42): Memotec use only. Contact Memotec service personnel if 
this value displays.

appl-err-3 (43): Memotec use only. Contact Memotec service personnel if 
this value displays.

appl-err-4 (44): Memotec use only. Contact Memotec service personnel if 
this value displays.

Default Value: disable (1)"
     DEFVAL { disable }
     ::= { cxMcVoxFxoOpeEntry 3 }

      cxMcVoxFxoOpeVocoder OBJECT-TYPE
     SYNTAX INTEGER { bps5800 (1),
              bps8000 (2),
              kbps40 (3),
              kbps32 (4),
              kbps24 (5),
              kbps16 (6),
              opt7 (7),
              opt8 (8)
            }
     ACCESS  read-only
     STATUS  mandatory
     DESCRIPTION 
"Displays the transmission speed (in bits per second) of the compressed 
voice stream on the operative FXO port. Defining the speed also sets the 
ACELP voice compression ratio.

You cannot modify this object. If you want to change the value you must 
modify the object cxMcVoxFxoAdmVocoder of the cxMcVox Administrative FXO 
Driver Group.

Options:

bps5800 (1): compresses at a higher rate and uses slightly less bandwidth.

bps8000 (2): compresses at approximately an 8:1 ratio (lower rate) with a 
higher quality voice sound at the receiving end.

opt3 (3): ADPCM 40.

opt4 (4): ADPCM 32.

opt5 (5): ADPCM 24.

opt6 (6): ADPCM 16.

opt7 (7): Memotec use only.

opt8 (8): Memotec use only.

Default Value: bps8000 (2)"
     DEFVAL { bps8000 }
     ::= { cxMcVoxFxoOpeEntry 4 }

      cxMcVoxFxoOpeFaxBw      OBJECT-TYPE
     SYNTAX   INTEGER { 
          bps2400 (1),
          bps4800 (2),
          bps7200 (3),
          bps9600 (4)
           }
     ACCESS  read-write
     STATUS  mandatory
     DESCRIPTION
"Determines the speed (in bits per second) of the FAX channel on the 
operative FXO port. This value also determines the bandwidth required to 
pass FAX traffic through the voice software. This value can be set to 
match the speed of your FAX machine or it can be lowered to reduce 
bandwidth allocation.

Options:

bps2400 (1)

bps4800 (2)

bps7200 (3)

bps9600 (4)

Default Value: bps7200 (3)

Configuration Changed: operative"
     DEFVAL { bps7200 }
     ::= { cxMcVoxFxoOpeEntry 5 }

-- obsoleted (has been redefined)

      cxMcVoxFxoOpeAutoCnx OBJECT-TYPE
     SYNTAX   INTEGER { 
          no (1),
          yes (2) 
           }
     ACCESS  read-only
     STATUS  obsolete
     DESCRIPTION
"Obsolete"
     DEFVAL { no }
      ::= { cxMcVoxFxoOpeEntry 6 }

      cxMcVoxFxoOpePathId        OBJECT-TYPE
     SYNTAX  DisplayString (SIZE (1..4))
     ACCESS  read-only
     STATUS  deprecated
     DESCRIPTION
"Path IDs no longer exist in the new Voice Routing (VR) scheme.

The PathID was formerly used for auto-connection on the operative FXO 
port.

The Path ID is a numeric dialing code that the user enters to gain access 
to the remote telephone or fax machine.

Note: The number of digits in the Path ID must match the value of the 
object cxMcVoxPathOpePathLng of the cxMcVox Operative Path Group.

You cannot modify this object. If you want to change the value you modify 
the object cxMcVoxFxoAdmPathId of the cxMcVox Administrative FXO Driver 
Group.

Range of Values: 1 to 4 digits

Default Value: none"
	 --#ENDING-VERSION 1
     ::= { cxMcVoxFxoOpeEntry 7 }

      cxMcVoxFxoOpeTxGain     OBJECT-TYPE
     SYNTAX INTEGER (820..1180)
     ACCESS  read-write
     STATUS  mandatory
     DESCRIPTION
"Determines the value defining the sound intensity (loudness) of voice 
transmissions on the operative FXO port. The transmission gain can be 
modified in the administrative configuration or be fine-tuned dynamically.

Note: Transmission gains should be modified during a connection (i.e. 
dynamically) as changes in the value affect the local listener.

Range of Values: 820 to 1180 (-18.0dB to 18.0dB)

Default Value: 960

Configuration Changed: operative"
     DEFVAL { 960 }
     ::= { cxMcVoxFxoOpeEntry 8 }

      cxMcVoxFxoOpeRxGain     OBJECT-TYPE
     SYNTAX INTEGER (820..1180)
     ACCESS  read-write
     STATUS  mandatory
     DESCRIPTION
"Determines the value defining the sound intensity (loudness) of voice 
reception on the operative FXO port. The reception gain can be modified in 
the administrative configuration or be fine-tuned dynamically.

Note: Reception gains should be modified during a connection (i.e. 
dynamically) as changes in the value affect the remote listener.

Range of Values: 820 to 1180 (-18.0dB to 18.0dB)

Default Value: 960

Configuration Changed: operative"
     DEFVAL { 960 }
     ::= { cxMcVoxFxoOpeEntry 9 }

      cxMcVoxFxoOpeEchoCancel OBJECT-TYPE
     SYNTAX   INTEGER { 
          disable (1),
          enable (2) 
           }
     ACCESS  read-only
     STATUS  mandatory
     DESCRIPTION
"Displays the state of echo cancellation on the operative FXO port. When 
set to 'enable' at both the local and remote ends, echo cancellation stops 
echoes from the remote that are heard through the receiver at the local 
end.

You cannot modify this object. If you want to change the value you must 
modify the object cxMcVoxFxoAdmEchoCancel of the cxMcVox Administrative 
FXO Driver Group.

Options:

disable (1)

enable (2)

Default Value: enable (2)"
     DEFVAL { enable }
     ::= { cxMcVoxFxoOpeEntry 10 }

      cxMcVoxFxoOpeSignaling  OBJECT-TYPE
     SYNTAX   INTEGER { 
          ground-start (1),
          loop-start   (2),
          did          (3)
           }
     ACCESS  read-only
     STATUS  mandatory
     DESCRIPTION
"Displays the type of signalling the operative FXO port uses to seize the 
line.

You cannot modify this object. If you want to change the value you must 
modify the object cxMcVoxFxoAdmSignaling of the cxMcVox Administrative FXO 
Driver Group.

Options:

ground-start (1)

loop-start (2)

did (3)

Default Value: loop-start"
     DEFVAL { loop-start }
     ::= { cxMcVoxFxoOpeEntry  11 }

      cxMcVoxFxoOpeCnctType   OBJECT-TYPE
     SYNTAX   INTEGER { 
          switched (1),
          auto-connect (2),
          fixed (3)
           }
     ACCESS  read-only
     STATUS  mandatory
     DESCRIPTION
"Displays the method the operative FXO port uses to make connections.

You cannot modify this object. If you want to change the value you must 
modify the object cxMcVoxFxoAdmCnctType of the cxMcVox Administrative FXO 
Driver Group.

Options:

switched (1): the port connects each call according to the dialing code 
the user enters.

auto-connect (2): calls passing through this port always terminate at the 
same remote destination. The port connects to the remote as soon as the 
local receiver enters the off-hook state. Any remote can connect to a port 
with an auto-connect configuration but when the local user initiates the 
call it always goes to the same remote.

fixed (3): calls passing through this port always terminate at the same 
remote destination. The port connects to the remote as soon as the local 
receiver enters the off-hook state. Only the local and remote destinations 
of the connection can use this port. No other remote location can gain 
access to this port.

Default Value: switched (1)"
     DEFVAL { switched }
     ::= { cxMcVoxFxoOpeEntry  12 }
     
      cxMcVoxFxoOpeRingType   OBJECT-TYPE
     SYNTAX   INTEGER { 
          north-american (1),
          international (2)
           }
     ACCESS  read-only
     STATUS  mandatory
     DESCRIPTION
"Displays the ring type of the operative FXO port. The ring types provide 
different ring timing to match the different ring cycles in networks.

You cannot modify this object. If you want to change the value you must 
modify the object cxMcVoxFxoAdmRingType of the cxMcVox Administrative FXO 
Driver Group.

Options:

north-american (1)

international (2)

Default Value: north-american (1)"
     DEFVAL { north-american }
     ::= { cxMcVoxFxoOpeEntry  13 }

      cxMcVoxFxoOpeImpedance   OBJECT-TYPE
     SYNTAX   INTEGER { 
          i600-ohms (1),
          i900-ohms (2),
          att       (3),
          aus       (4)
           }
     ACCESS  read-write
     STATUS  mandatory
     DESCRIPTION
"Displays the input line impedance of the operative FXO interface. 
The value of this object can be modified in operational mode.

Options:

i600-ohms (1)

i900-ohms (2)

att (3)

aus (4)

Default Value: i600-ohms (1)

NOTE: The option aus(4) is added only starting at version 11.
NOTE: This object is READ-ONLY for the CX800."
     DEFVAL { i600-ohms }
     ::= { cxMcVoxFxoOpeEntry  14 }

      cxMcVoxFxoOpeDialType   OBJECT-TYPE
     SYNTAX   INTEGER { 
          dtmf  (1),
          pulse (2)
           }
     ACCESS  read-only
     STATUS  mandatory
     DESCRIPTION
"Displays the dialing method of the operative FXO port. The dialing method 
refers to the sound that occurs when the user enters each digit of the 
dialing code.

You cannot modify this object. If you want to change the value you must 
modify the object cxMcVoxFxoAdmDialType of the cxMcVox Administrative FXO 
Driver Group table.

Options:

dtmf (1): (Dual Tone Multifrequence) uses bursts of frequency pairs to 
identify the code the user dials. Tones are generated at a level of -7 
plus or minus 3 dBm for the lower frequency groups and -5 plus or minus 3 
dBm for the higher frequency group. The power level of the higher 
frequency tone is intentionally increased to compensate for the higher 
line loss.

pulse (2): uses bursts (10 plus or minus 0.5 pps) of the main tone 
frequency (2280Hz) to generate the codes the user enters. Tones are 
generated at a level of -4 to -30 dBm for the 2280Hz frequency. The number 
of pulses during one second indicates the code the user dials. With the 
E&M interface, the voice station generates and detects pulses.

Default Value: dtmf (1)"
     ::= { cxMcVoxFxoOpeEntry  15 }

      cxMcVoxFxoOpeDidSignalType   OBJECT-TYPE
     SYNTAX   INTEGER { 
          normal  (1),
          delay   (2),
          wink    (3)
           }
     ACCESS  read-only
     STATUS  mandatory
     DESCRIPTION
"Displays the type of signaling on the operative FXO port. The signaling 
type refers to the line seizure technique.

You cannot modify this object. If you want to change the value you must 
modify the object cxMcVoxFxoAdmDidSignalType of the cxMcVox Administrative 
FXO Driver Group table.

Options

normal (1)

delay (2)

wink (3)

Default Value: normal (1)"
     ::= { cxMcVoxFxoOpeEntry  16 }

      cxMcVoxFxoOpeRmtExt    OBJECT-TYPE
     SYNTAX  DisplayString (SIZE (1..5))
     ACCESS  read-only
     STATUS  mandatory
     DESCRIPTION
"Determines the Remote Extension or Group Id used for auto-connection on 
the FXO port.

The Remote Extension is a numeric dialing code that the user enters to 
gain access to the remote telephone or fax machine.

Auto-connection is the connection method that this port uses. A particular 
Remote Extension or Group Id has been assigned to the port so that no 
dialing is required. 

Note: The number of digits in the Remote Extension is determined by the 
object cxMcVoxNetNbDigits of the cxMcVox Global Parameters Group.

Range of Values: 1 to 5 numeric digits

Default Value: none

Configuration Changed: operative"
	 --#STARTING-VERSION 1
     ::= { cxMcVoxFxoOpeEntry 17 }

      cxMcVoxFxoOpeRmtId OBJECT-TYPE
   SYNTAX  DisplayString (SIZE (0..10))
   ACCESS  read-only
   STATUS  optional
   DESCRIPTION
"Displays the ID (name) for the remote voice station.

Note: This object must be defined in order to obtain a successful voice 
connection via the fixed connection method.

With the fixed connection method, a particular Remote Extension or Group 
Id is assigned to the port so that no dialing is required. The call to the 
remote is established as soon as the connection is configured.

You cannot modify this object. If you want to change the ID you must 
modify the object cxMcVoxFxoAdmRmtId (of this table).

Range of Values: a maximum of 10 alphanumeric characters in upper-case 
only. You can use any combination of letters and numbers; however you 
cannot use blank spaces. Use a dash or underscore as a delimiter.

Default Value: none"
	 --#STARTING-VERSION 1
     ::= { cxMcVoxFxoOpeEntry  18 }

      cxMcVoxFxoOpeTranspMode   OBJECT-TYPE
     SYNTAX   INTEGER { 
          emulate (1),
          transparent (2) ,
          local (3)
           }
     ACCESS  read-only
     STATUS  mandatory
     DESCRIPTION
"Determines the whether to use the Transparent mode on the administrative
 port.  In the transparent mode, the local port will answer only after
 the called party has answered to the party to which the call is finally
 destinated.

 The Transparent mode is incompatible with Switched type of
 connection and is automatically disabled when Switched mode is selected
 (only applies to autoconnect and fixed connections).

 The Local mode lets the local port answer right away to a seizure.

Options:

emulate (1): Emulation mode is on

transparent (2): Transparent mode on

local (3): Local mode on

Default Value: emulate (1)

Configuration Changed: operational"
     DEFVAL { emulate }
	 --#STARTING-VERSION 3
     ::= { cxMcVoxFxoOpeEntry  19 }


      cxMcVoxFxoOpeFaxEnable OBJECT-TYPE
     SYNTAX   INTEGER { 
          disable (1),
          enable (2) 
           }
     ACCESS  read-only
     STATUS  mandatory
     DESCRIPTION
"Displays the state of the FAX on the operative FXO port. When 
set to 'enable' at both the local and remote ends, the FAX will be
enabled.

You cannot modify this object. If you want to change the value you must 
modify the object cxMcVoxFxoAdmFaxEnable of the cxMcVox Administrative 
FXO Driver Group.

Options:

disable (1)

enable (2)

Default Value: enable (2)"
     DEFVAL { enable }
	--#STARTING-VERSION 8
     ::= { cxMcVoxFxoOpeEntry 20 }


      cxMcVoxFxoOpeBroadcast  OBJECT-TYPE
     SYNTAX   INTEGER { 
          none (1),
          master (2) ,
          slave (3)
           }
     ACCESS  read-only
     STATUS  mandatory
     DESCRIPTION
"Cetermines the state of the voice broadcast feature. When set to none, no
broadcast is used. When set to master, ...



Options:

none (1)

master (2)

slave (3)

Default Value: none (1)"
     DEFVAL { none }
	--#STARTING-VERSION 10
      ::= { cxMcVoxFxoOpeEntry 21 }

-- ============================================================

cxMcVoxDriverAdmPriv  OBJECT IDENTIFIER ::= {cxMcVox 20 }

--  cxMcVox ADMINISTRATIVE PORTS PRIVATE GROUP
--  (!!! new group)

cxMcVoxAdmPortPrivTable OBJECT-TYPE
   SYNTAX  SEQUENCE OF CxMcVoxAdmPortPrivEntry
   ACCESS  not-accessible
   STATUS  mandatory
   DESCRIPTION
"Voice station planned Table."
   ::= { cxMcVoxDriverAdmPriv 1 }

cxMcVoxAdmPortPrivEntry OBJECT-TYPE
   SYNTAX  CxMcVoxAdmPortPrivEntry
   ACCESS  not-accessible
   STATUS  mandatory
   DESCRIPTION
"Voice station planned row definition."
   INDEX { cxMcVoxAdmCardUsed,
cxMcVoxAdmPortUsed }
   ::= { cxMcVoxAdmPortPrivTable 1 }

CxMcVoxAdmPortPrivEntry ::=
   SEQUENCE {
      cxMcVoxAdmCardUsed            INTEGER,
      cxMcVoxAdmPortUsed            INTEGER,

      cxMcVoxAdmRingTimeOn          INTEGER,
      cxMcVoxAdmRingTimeOff1        INTEGER,
      cxMcVoxAdmRingTimeOff2        INTEGER,
      cxMcVoxAdmEchoCancelLevel     INTEGER,
      cxMcVoxAdmToneDelayAfterCnct  INTEGER,
      cxMcVoxAdmToneDelayAfterFlash INTEGER,
      cxMcVoxAdmToneOffsetTxGain    INTEGER,
      cxMcVoxAdmVoiceOffsetTxGain   INTEGER,
      cxMcVoxAdmAc15InterDigit      INTEGER,
      cxMcVoxAdmMfToneThold         INTEGER,
      cxMcVoxAdmPulseTmin           INTEGER,
      cxMcVoxAdmPulseTmax           INTEGER,
      cxMcVoxAdmPulseInterDigit     INTEGER,
      cxMcVoxAdmDtmfGuard           INTEGER,
      cxMcVoxAdmDtmfOpeLevel        INTEGER,
      cxMcVoxAdmDtmfTxTimeOn        INTEGER,
      cxMcVoxAdmDtmfTxTimeOff       INTEGER,
      cxMcVoxAdmFlashTmin           INTEGER,
      cxMcVoxAdmFlashTmax           INTEGER,
      cxMcVoxAdmFlashTgen           INTEGER,
      cxMcVoxAdmAfterToneSilences   INTEGER,
      cxMcVoxAdmFaxTxGain           INTEGER,
      cxMcVoxAdmFaxRxGain           INTEGER,
      cxMcVoxAdmFaxHdlcFlags        INTEGER,
      cxMcVoxAdmFaxPreambleDuration INTEGER,
      cxMcVoxAdmFaxPreambleDelay    INTEGER,
      cxMcVoxAdmFaxCedToneDuration  INTEGER,
      cxMcVoxAdmFaxInterProtoGap    INTEGER,
      cxMcVoxAdmFaxTimerDetectSync  INTEGER,
      cxMcVoxAdmFaxTimerWaitId      INTEGER,
      cxMcVoxAdmFaxMinPreambleDur   INTEGER,
      cxMcVoxAdmFaxMaxPreambleDur   INTEGER,
      cxMcVoxAdmFaxMinPreambleDly   INTEGER,
      cxMcVoxAdmFaxMaxPreambleDly   INTEGER,
      cxMcVoxAdmFaxCedToneDetection INTEGER,
      cxMcVoxAdmFaxCedMinToneDur    INTEGER,
      cxMcVoxAdmFaxCedMaxToneDur    INTEGER,
      cxMcVoxAdmFaxMaxHdlcFlags     INTEGER
    }                               

      cxMcVoxAdmCardUsed         OBJECT-TYPE
     SYNTAX INTEGER (1..8)
     ACCESS  read-only
     STATUS  mandatory
     DESCRIPTION
"Displays the slot number of the voice I/O card.

You cannot modify this object

Range of Values:

CX900: 1 to 6

CX1000: 1 to 4

Default: none"
     ::= { cxMcVoxAdmPortPrivEntry 1 }

      cxMcVoxAdmPortUsed         OBJECT-TYPE
     SYNTAX INTEGER (1..15)
     ACCESS  read-only
     STATUS  mandatory
     DESCRIPTION
"Displays the number of the voice I/O port.

You cannot modify this object. It is a display that the software provides.

Options:

CX900: 1 is the only acceptable value. Each I/O card has only 1 port.

CX1000: up to 15 for the DI600

Default: none"
     ::= { cxMcVoxAdmPortPrivEntry 2 }

    
      cxMcVoxAdmRingTimeOn   OBJECT-TYPE
     SYNTAX INTEGER (10..10000)
     ACCESS  read-write
     STATUS  mandatory
     DESCRIPTION 
"WARNING: YOU SHOULD NOT MODIFY THIS OBJECT WITHOUT THE SUPERVISION OF 
MEMOTEC PERSONNEL.

Range of Values: 10 to 10000

Default Value: 2000"
     DEFVAL { 2000 }
     ::= { cxMcVoxAdmPortPrivEntry  3 }

      cxMcVoxAdmRingTimeOff1   OBJECT-TYPE
     SYNTAX INTEGER (10..10000)
     ACCESS  read-write
     STATUS  mandatory
     DESCRIPTION
"WARNING: YOU SHOULD NOT MODIFY THIS OBJECT WITHOUT THE SUPERVISION OF 
MEMOTEC PERSONNEL.

Range of Values: 10 to 10000

Default Value: 4000"
     DEFVAL { 4000 }
     ::= { cxMcVoxAdmPortPrivEntry  4 }

      cxMcVoxAdmRingTimeOff2   OBJECT-TYPE
     SYNTAX INTEGER (10..10000)
     ACCESS  read-write
     STATUS  mandatory
     DESCRIPTION
"WARNING: YOU SHOULD NOT MODIFY THIS OBJECT WITHOUT THE SUPERVISION OF 
MEMOTEC PERSONNEL.

Range of Values: 10 to 10000

Default Value: 2000"
     DEFVAL { 2000 }
     ::= { cxMcVoxAdmPortPrivEntry  5 }

      cxMcVoxAdmEchoCancelLevel   OBJECT-TYPE
     SYNTAX INTEGER (0..65535)
     ACCESS  read-write
     STATUS  mandatory
     DESCRIPTION
"WARNING: YOU SHOULD NOT MODIFY THIS OBJECT WITHOUT THE SUPERVISION OF 
MEMOTEC PERSONNEL.

Range of Values: 0 to 65535

Default Value: 100"
     DEFVAL { 100 }
     ::= { cxMcVoxAdmPortPrivEntry  6 }

      cxMcVoxAdmToneDelayAfterCnct   OBJECT-TYPE
     SYNTAX INTEGER (0..6000)
     ACCESS  read-write
     STATUS  mandatory
     DESCRIPTION
"WARNING: YOU SHOULD NOT MODIFY THIS OBJECT WITHOUT THE SUPERVISION OF 
MEMOTEC PERSONNEL.

Range of Values: 0 to 6000

Default Value: 1000"
     DEFVAL { 1000 }
     ::= { cxMcVoxAdmPortPrivEntry  7 }

      cxMcVoxAdmToneDelayAfterFlash   OBJECT-TYPE
     SYNTAX INTEGER (0..6000)
     ACCESS  read-write
     STATUS  mandatory
     DESCRIPTION
"WARNING: YOU SHOULD NOT MODIFY THIS OBJECT WITHOUT THE SUPERVISION OF 
MEMOTEC PERSONNEL.

Range of Values: 0 to 6000

Default Value: 400"
     DEFVAL { 400 }
     ::= { cxMcVoxAdmPortPrivEntry  8 }

      cxMcVoxAdmToneOffsetTxGain   OBJECT-TYPE
     SYNTAX INTEGER (820..1180)
     ACCESS  read-write
     STATUS  mandatory
     DESCRIPTION
"WARNING: YOU SHOULD NOT MODIFY THIS OBJECT WITHOUT THE SUPERVISION OF 
MEMOTEC PERSONNEL.

Range of Values: 820 to 1180 (-18.0dB to 18.0dB)

Default Value: 1000"
     DEFVAL { 1000 }
     ::= { cxMcVoxAdmPortPrivEntry  9 }

      cxMcVoxAdmVoiceOffsetTxGain   OBJECT-TYPE
     SYNTAX INTEGER (820..1180)
     ACCESS  read-write
     STATUS  mandatory
     DESCRIPTION
"WARNING: YOU SHOULD NOT MODIFY THIS OBJECT WITHOUT THE SUPERVISION OF 
MEMOTEC PERSONNEL.

Range of Values: 820 to 1180 (-18.0dB to 18.0dB)

Default Value: 1000"
     DEFVAL { 1000 }
     ::= { cxMcVoxAdmPortPrivEntry  10 }

      cxMcVoxAdmAc15InterDigit   OBJECT-TYPE
     SYNTAX INTEGER (0..60000)
     ACCESS  read-write
     STATUS  mandatory
     DESCRIPTION
"WARNING: YOU SHOULD NOT MODIFY THIS OBJECT WITHOUT THE SUPERVISION OF 
MEMOTEC PERSONNEL.

Range of Values: 0 to 60000

Default Value: 800"
     DEFVAL { 800 }
     ::= { cxMcVoxAdmPortPrivEntry  11 }

      cxMcVoxAdmMfToneThold   OBJECT-TYPE
     SYNTAX INTEGER (0..255)
     ACCESS  read-write
     STATUS  mandatory
     DESCRIPTION
"WARNING: YOU SHOULD NOT MODIFY THIS OBJECT WITHOUT THE SUPERVISION OF 
MEMOTEC PERSONNEL.

Range of Values: 0 to 255

Default Value: 60"
     DEFVAL { 60 }
     ::= { cxMcVoxAdmPortPrivEntry  12 }

      cxMcVoxAdmPulseTmin   OBJECT-TYPE
     SYNTAX INTEGER (0..3000)
     ACCESS  read-write
     STATUS  mandatory
     DESCRIPTION
"WARNING: YOU SHOULD NOT MODIFY THIS OBJECT WITHOUT THE SUPERVISION OF 
MEMOTEC PERSONNEL.

Range of Values: 0 to 3000

Default Value: 15"
     DEFVAL { 15 }
     ::= { cxMcVoxAdmPortPrivEntry  13 }

      cxMcVoxAdmPulseTmax   OBJECT-TYPE
     SYNTAX INTEGER (0..3000)
     ACCESS  read-write
     STATUS  mandatory
     DESCRIPTION
"WARNING: YOU SHOULD NOT MODIFY THIS OBJECT WITHOUT THE SUPERVISION OF 
MEMOTEC PERSONNEL.

Range of Values: 0 to 3000

Default Value: 125"
     DEFVAL { 125 }
     ::= { cxMcVoxAdmPortPrivEntry  14 }

      cxMcVoxAdmPulseInterDigit   OBJECT-TYPE
     SYNTAX INTEGER (0..3000)
     ACCESS  read-write
     STATUS  mandatory
     DESCRIPTION
"WARNING: YOU SHOULD NOT MODIFY THIS OBJECT WITHOUT THE SUPERVISION OF 
MEMOTEC PERSONNEL.

Range of Values: 0 to 3000

Default Value: 275"
     DEFVAL { 275 }
     ::= { cxMcVoxAdmPortPrivEntry  15 }

      cxMcVoxAdmDtmfGuard   OBJECT-TYPE
     SYNTAX INTEGER (0..255)
     ACCESS  read-write
     STATUS  mandatory
     DESCRIPTION
"WARNING: YOU SHOULD NOT MODIFY THIS OBJECT WITHOUT THE SUPERVISION OF 
MEMOTEC PERSONNEL.

Range of Values: 0 to 255

Default Value: 40"
     DEFVAL { 40 }
     ::= { cxMcVoxAdmPortPrivEntry  16 }

      cxMcVoxAdmDtmfOpeLevel   OBJECT-TYPE
     SYNTAX INTEGER {
          minus-25 (1),
          minus-28 (2),
          minus-31 (3),
          minus-34 (4)  
        }
     ACCESS  read-write
     STATUS  mandatory
     DESCRIPTION
"WARNING: YOU SHOULD NOT MODIFY THIS OBJECT WITHOUT THE SUPERVISION OF 
MEMOTEC PERSONNEL.

Options:

minus-25 (1)

minus-28 (2)

minus-31 (3)

minus-34 (4)

Default Value: minus-25 (1)"
     DEFVAL { minus-25 }
     ::= { cxMcVoxAdmPortPrivEntry  17 }

      cxMcVoxAdmDtmfTxTimeOn   OBJECT-TYPE
     SYNTAX INTEGER (0..500)
     ACCESS  read-write
     STATUS  mandatory
     DESCRIPTION
"WARNING: YOU SHOULD NOT MODIFY THIS OBJECT WITHOUT THE SUPERVISION OF 
MEMOTEC PERSONNEL.

Range of Values: 0 to 500

Default Value: 75"
     DEFVAL { 75 }
     ::= { cxMcVoxAdmPortPrivEntry  18 }

      cxMcVoxAdmDtmfTxTimeOff   OBJECT-TYPE
     SYNTAX INTEGER (0..500)
     ACCESS  read-write
     STATUS  mandatory
     DESCRIPTION
"WARNING: YOU SHOULD NOT MODIFY THIS OBJECT WITHOUT THE SUPERVISION OF 
MEMOTEC PERSONNEL.

Range of Values: 0 to 500

Default Value: 75"
     DEFVAL { 75 }
     ::= { cxMcVoxAdmPortPrivEntry  19 }

      cxMcVoxAdmFlashTmin   OBJECT-TYPE
     SYNTAX INTEGER (50..10000)
     ACCESS  read-write
     STATUS  mandatory
     DESCRIPTION
"WARNING: YOU SHOULD NOT MODIFY THIS OBJECT WITHOUT THE SUPERVISION OF 
MEMOTEC PERSONNEL.

Range of Values: 50 to 10000

Default Value: 200"
     DEFVAL { 200 }
     ::= { cxMcVoxAdmPortPrivEntry  20 }

      cxMcVoxAdmFlashTmax   OBJECT-TYPE
     SYNTAX INTEGER (50..10000)
     ACCESS  read-write
     STATUS  mandatory
     DESCRIPTION
"WARNING: YOU SHOULD NOT MODIFY THIS OBJECT WITHOUT THE SUPERVISION OF 
MEMOTEC PERSONNEL.

Range of Values: 50 to 10000

Default Value: 800"
     DEFVAL { 800 }
     ::= { cxMcVoxAdmPortPrivEntry  21 }

      cxMcVoxAdmFlashTgen   OBJECT-TYPE
     SYNTAX INTEGER (50..10000)
     ACCESS  read-write
     STATUS  mandatory
     DESCRIPTION
"WARNING: YOU SHOULD NOT MODIFY THIS OBJECT WITHOUT THE SUPERVISION OF 
MEMOTEC PERSONNEL.

Range of Values: 50 to 10000

Default Value: 500"
     DEFVAL { 500 }
     ::= { cxMcVoxAdmPortPrivEntry  22 }

      cxMcVoxAdmAfterToneSilences   OBJECT-TYPE
     SYNTAX INTEGER (0..127)
     ACCESS  read-write
     STATUS  mandatory
     DESCRIPTION
"WARNING: YOU SHOULD NOT MODIFY THIS OBJECT WITHOUT THE SUPERVISION OF 
MEMOTEC PERSONNEL.

Range of Values: 0 to 127

Default Value: 64"
     DEFVAL { 64 }
     ::= { cxMcVoxAdmPortPrivEntry  23 }

      cxMcVoxAdmFaxTxGain   OBJECT-TYPE
     SYNTAX INTEGER (820..1180)
     ACCESS  read-write
     STATUS  mandatory
     DESCRIPTION
"WARNING: YOU SHOULD NOT MODIFY THIS OBJECT WITHOUT THE SUPERVISION OF 
MEMOTEC PERSONNEL.

Range of Values: 820 to 1180 (-18.0dB to 18.0dB)

Default Value: 1000"
     DEFVAL { 1000 }
     ::= { cxMcVoxAdmPortPrivEntry  24 }

      cxMcVoxAdmFaxRxGain   OBJECT-TYPE
     SYNTAX INTEGER (820..1180)
     ACCESS  read-write
     STATUS  mandatory
     DESCRIPTION
"WARNING: YOU SHOULD NOT MODIFY THIS OBJECT WITHOUT THE SUPERVISION OF 
MEMOTEC PERSONNEL.

Range of Values: 820 to 1180 (-18.0dB to 18.0dB)

Default Value: 1000"
     DEFVAL { 1000 }
     ::= { cxMcVoxAdmPortPrivEntry  25 }

      cxMcVoxAdmFaxHdlcFlags   OBJECT-TYPE
     SYNTAX INTEGER (0..127)
     ACCESS  read-write
     STATUS  mandatory
     DESCRIPTION
"WARNING: YOU SHOULD NOT MODIFY THIS OBJECT WITHOUT THE SUPERVISION OF 
MEMOTEC PERSONNEL.

Range of Values: 0 to 127

Default Value: 2"
     DEFVAL { 2 }
     ::= { cxMcVoxAdmPortPrivEntry  26 }

      cxMcVoxAdmFaxPreambleDuration   OBJECT-TYPE
     SYNTAX INTEGER (0..60000)
     ACCESS  read-write
     STATUS  deprecated
     DESCRIPTION
"WARNING: YOU SHOULD NOT MODIFY THIS OBJECT WITHOUT THE SUPERVISION OF 
MEMOTEC PERSONNEL.

Range of Values: 0 to 60000

Default Value: 1000"
     DEFVAL { 1000 }
 	 --#ENDING-VERSION 1
     ::= { cxMcVoxAdmPortPrivEntry  27 }

      cxMcVoxAdmFaxPreambleDelay   OBJECT-TYPE
     SYNTAX INTEGER (0..60000)
     ACCESS  read-write
     STATUS  deprecated
     DESCRIPTION
"WARNING: YOU SHOULD NOT MODIFY THIS OBJECT WITHOUT THE SUPERVISION OF 
MEMOTEC PERSONNEL.

Range of Values: 0 to 60000

Default Value: 900"
     DEFVAL { 900 }
 	 --#ENDING-VERSION 1
     ::= { cxMcVoxAdmPortPrivEntry  28 }

      cxMcVoxAdmFaxCedToneDuration   OBJECT-TYPE
     SYNTAX INTEGER (0..60000)
     ACCESS  read-write
     STATUS  deprecated
     DESCRIPTION
"WARNING: YOU SHOULD NOT MODIFY THIS OBJECT WITHOUT THE SUPERVISION OF 
MEMOTEC PERSONNEL.

Range of Values: 0 to 60000

Default Value: 500"
     DEFVAL { 500 }
 	 --#ENDING-VERSION 1
     ::= { cxMcVoxAdmPortPrivEntry  29 }

      cxMcVoxAdmFaxInterProtoGap   OBJECT-TYPE
     SYNTAX INTEGER (0..60000)
     ACCESS  read-write
     STATUS  mandatory
     DESCRIPTION
"WARNING: YOU SHOULD NOT MODIFY THIS OBJECT WITHOUT THE SUPERVISION OF 
MEMOTEC PERSONNEL.

Range of Values: 0 to 60000

Default Value: 75"
     DEFVAL { 75 }
     ::= { cxMcVoxAdmPortPrivEntry  30 }

      cxMcVoxAdmFaxTimerDetectSync   OBJECT-TYPE
     SYNTAX INTEGER (0..65000)
     ACCESS  read-write
     STATUS  mandatory
     DESCRIPTION
"WARNING: YOU SHOULD NOT MODIFY THIS OBJECT WITHOUT THE SUPERVISION OF 
MEMOTEC PERSONNEL.

Range of Values: 0 to 65000

Default Value: 7500"
     DEFVAL { 7500 }
     ::= { cxMcVoxAdmPortPrivEntry  31 }

      cxMcVoxAdmFaxTimerWaitId   OBJECT-TYPE
     SYNTAX INTEGER (0..65000)
     ACCESS  read-write
     STATUS  mandatory
     DESCRIPTION
"WARNING: YOU SHOULD NOT MODIFY THIS OBJECT WITHOUT THE SUPERVISION OF 
MEMOTEC PERSONNEL.

Range of Values: 0 to 65000

Default Value: 40000"
     DEFVAL { 40000 }
     ::= { cxMcVoxAdmPortPrivEntry  32 }
     
      cxMcVoxAdmFaxMinPreambleDur   OBJECT-TYPE
     SYNTAX INTEGER (0..60000)
     ACCESS  read-write
     STATUS  mandatory
     DESCRIPTION
"WARNING: YOU SHOULD NOT MODIFY THIS OBJECT WITHOUT THE SUPERVISION OF 
MEMOTEC PERSONNEL.

Range of Values: 0 to 60000

Default Value: 1000"
     DEFVAL { 1000 }
   --#STARTING-VERSION 2
     ::= { cxMcVoxAdmPortPrivEntry  33 }
      
      cxMcVoxAdmFaxMaxPreambleDur   OBJECT-TYPE
     SYNTAX INTEGER (0..60000)
     ACCESS  read-write
     STATUS  mandatory
     DESCRIPTION
"WARNING: YOU SHOULD NOT MODIFY THIS OBJECT WITHOUT THE SUPERVISION OF 
MEMOTEC PERSONNEL.

Range of Values: 0 to 60000

Default Value: 1200"
     DEFVAL { 1200 }
   --#STARTING-VERSION 2
     ::= { cxMcVoxAdmPortPrivEntry  34 }

      cxMcVoxAdmFaxMinPreambleDly   OBJECT-TYPE
     SYNTAX INTEGER (0..60000)
     ACCESS  read-write
     STATUS  mandatory
     DESCRIPTION
"WARNING: YOU SHOULD NOT MODIFY THIS OBJECT WITHOUT THE SUPERVISION OF 
MEMOTEC PERSONNEL.

Range of Values: 0 to 60000

Default Value: 400"
     DEFVAL { 400 }
   --#STARTING-VERSION 2
     ::= { cxMcVoxAdmPortPrivEntry  35 }

      cxMcVoxAdmFaxMaxPreambleDly   OBJECT-TYPE
     SYNTAX INTEGER (0..60000)
     ACCESS  read-write
     STATUS  mandatory
     DESCRIPTION
"WARNING: YOU SHOULD NOT MODIFY THIS OBJECT WITHOUT THE SUPERVISION OF 
MEMOTEC PERSONNEL.

Range of Values: 0 to 60000

Default Value: 900"
     DEFVAL { 900 }
   --#STARTING-VERSION 2
     ::= { cxMcVoxAdmPortPrivEntry  36 }

      cxMcVoxAdmFaxCedToneDetection   OBJECT-TYPE
     SYNTAX INTEGER (0..60000)
     ACCESS  read-write
     STATUS  mandatory
     DESCRIPTION
"WARNING: YOU SHOULD NOT MODIFY THIS OBJECT WITHOUT THE SUPERVISION OF 
MEMOTEC PERSONNEL.

Range of Values: 0 to 60000

Default Value: 500"
     DEFVAL { 500 }
   --#STARTING-VERSION 2
     ::= { cxMcVoxAdmPortPrivEntry  37 }

      cxMcVoxAdmFaxCedMinToneDur   OBJECT-TYPE
     SYNTAX INTEGER (0..60000)
     ACCESS  read-write
     STATUS  mandatory
     DESCRIPTION
"WARNING: YOU SHOULD NOT MODIFY THIS OBJECT WITHOUT THE SUPERVISION OF 
MEMOTEC PERSONNEL.

Range of Values: 0 to 60000

Default Value: 2600"
     DEFVAL { 2600 }
   --#STARTING-VERSION 2
     ::= { cxMcVoxAdmPortPrivEntry  38 }

      cxMcVoxAdmFaxCedMaxToneDur   OBJECT-TYPE
     SYNTAX INTEGER (0..60000)
     ACCESS  read-write
     STATUS  mandatory
     DESCRIPTION
"WARNING: YOU SHOULD NOT MODIFY THIS OBJECT WITHOUT THE SUPERVISION OF 
MEMOTEC PERSONNEL.

Range of Values: 0 to 60000

Default Value: 4000"
     DEFVAL { 4000 }
   --#STARTING-VERSION 2
     ::= { cxMcVoxAdmPortPrivEntry  39 }

      cxMcVoxAdmFaxMaxHdlcFlags   OBJECT-TYPE
     SYNTAX INTEGER (0..127)
     ACCESS  read-write
     STATUS  mandatory
     DESCRIPTION
"WARNING: YOU SHOULD NOT MODIFY THIS OBJECT WITHOUT THE SUPERVISION OF 
MEMOTEC PERSONNEL.

Range of Values: 0 to 127

Default Value: 32"
     DEFVAL { 32 }
   --#STARTING-VERSION 3
     ::= { cxMcVoxAdmPortPrivEntry  40 }

-- ============================================================

cxMcVoxDriverOpePriv  OBJECT IDENTIFIER ::= {cxMcVox 21 }

--  cxMcVox OPERATIONAL PORTS PRIVATE GROUP
-- (!!! new group)

cxMcVoxOpePortPrivTable OBJECT-TYPE
   SYNTAX  SEQUENCE OF CxMcVoxOpePortPrivEntry
   ACCESS  not-accessible
   STATUS  mandatory
   DESCRIPTION
"Voice station planned Table."
   ::= { cxMcVoxDriverOpePriv 1 }

cxMcVoxOpePortPrivEntry OBJECT-TYPE
   SYNTAX  CxMcVoxOpePortPrivEntry
   ACCESS  not-accessible
   STATUS  mandatory
   DESCRIPTION
"Voice station planned row definition."
   INDEX { cxMcVoxOpeCardUsed,
cxMcVoxOpePortUsed }
   ::= { cxMcVoxOpePortPrivTable 1 }

CxMcVoxOpePortPrivEntry ::=
   SEQUENCE {
      cxMcVoxOpeCardUsed            INTEGER,
      cxMcVoxOpePortUsed            INTEGER,

      cxMcVoxOpeRingTimeOn          INTEGER,
      cxMcVoxOpeRingTimeOff1        INTEGER,
      cxMcVoxOpeRingTimeOff2        INTEGER,
      cxMcVoxOpeEchoCancelLevel     INTEGER,
      cxMcVoxOpeToneDelayAfterCnct  INTEGER,
      cxMcVoxOpeToneDelayAfterFlash INTEGER,
      cxMcVoxOpeToneOffsetTxGain    INTEGER,
      cxMcVoxOpeVoiceOffsetTxGain   INTEGER,
      cxMcVoxOpeAc15InterDigit      INTEGER,
      cxMcVoxOpeMfToneThold         INTEGER,
      cxMcVoxOpePulseTmin           INTEGER,
      cxMcVoxOpePulseTmax           INTEGER,
      cxMcVoxOpePulseInterDigit     INTEGER,
      cxMcVoxOpeDtmfGuard           INTEGER,
      cxMcVoxOpeDtmfOpeLevel        INTEGER,
      cxMcVoxOpeDtmfTxTimeOn        INTEGER,
      cxMcVoxOpeDtmfTxTimeOff       INTEGER,
      cxMcVoxOpeFlashTmin           INTEGER,
      cxMcVoxOpeFlashTmax           INTEGER,
      cxMcVoxOpeFlashTgen           INTEGER,
      cxMcVoxOpeAfterToneSilences   INTEGER,
      cxMcVoxOpeFaxTxGain           INTEGER,
      cxMcVoxOpeFaxRxGain           INTEGER,
      cxMcVoxOpeFaxHdlcFlags        INTEGER,
      cxMcVoxOpeFaxPreambleDuration INTEGER,
      cxMcVoxOpeFaxPreambleDelay    INTEGER,
      cxMcVoxOpeFaxCedToneDuration  INTEGER,
      cxMcVoxOpeFaxInterProtoGap    INTEGER,
      cxMcVoxOpeFaxTimerDetectSync  INTEGER,
      cxMcVoxOpeFaxTimerWaitId      INTEGER,
      cxMcVoxOpeFaxMinPreambleDur   INTEGER,
      cxMcVoxOpeFaxMaxPreambleDur   INTEGER,
      cxMcVoxOpeFaxMinPreambleDly   INTEGER,
      cxMcVoxOpeFaxMaxPreambleDly   INTEGER,
      cxMcVoxOpeFaxCedToneDetection INTEGER,
      cxMcVoxOpeFaxCedMinToneDur    INTEGER,
      cxMcVoxOpeFaxCedMaxToneDur    INTEGER,
      cxMcVoxOpeFaxMaxHdlcFlags     INTEGER
    }                               

      cxMcVoxOpeCardUsed         OBJECT-TYPE
     SYNTAX INTEGER (1..8)
     ACCESS  read-only
     STATUS  mandatory
     DESCRIPTION
"Displays the slot number of the voice I/O card.

You cannot modify this object.

Range of Values:

CX900: 1 to 6

CX1000: 1 to 8

Default: none"
     ::= { cxMcVoxOpePortPrivEntry 1 }

      cxMcVoxOpePortUsed         OBJECT-TYPE
     SYNTAX INTEGER (1..15)
     ACCESS  read-only
     STATUS  mandatory
     DESCRIPTION
"Displays the number of the voice I/O port.

You cannot modify this object.

Options:

CX900: 1 is the only acceptable value. Each I/O card has only 1 port.

CX1000: up to 15 for the DI600

Default: none"
     ::= { cxMcVoxOpePortPrivEntry 2 }

    
      cxMcVoxOpeRingTimeOn   OBJECT-TYPE
     SYNTAX INTEGER (10..10000)
     ACCESS  read-write
     STATUS  mandatory
     DESCRIPTION 
"WARNING: YOU SHOULD NOT MODIFY THIS OBJECT WITHOUT THE SUPERVISION OF 
MEMOTEC PERSONNEL.

Range of Values: 10 to 10000

Default Value: 2000"
     DEFVAL { 2000 }
     ::= { cxMcVoxOpePortPrivEntry  3 }

      cxMcVoxOpeRingTimeOff1   OBJECT-TYPE
     SYNTAX INTEGER (10..10000)
     ACCESS  read-write
     STATUS  mandatory
     DESCRIPTION
"WARNING: YOU SHOULD NOT MODIFY THIS OBJECT WITHOUT THE SUPERVISION OF 
MEMOTEC PERSONNEL.

Range of Values: 10 to 10000

Default Value: 4000"
     DEFVAL { 4000 }
     ::= { cxMcVoxOpePortPrivEntry  4 }

      cxMcVoxOpeRingTimeOff2   OBJECT-TYPE
     SYNTAX INTEGER (10..10000)
     ACCESS  read-write
     STATUS  mandatory
     DESCRIPTION
"WARNING: YOU SHOULD NOT MODIFY THIS OBJECT WITHOUT THE SUPERVISION OF 
MEMOTEC PERSONNEL.

Range of Values: 10 to 10000

Default Value: 2000"
     DEFVAL { 2000 }
     ::= { cxMcVoxOpePortPrivEntry  5 }

      cxMcVoxOpeEchoCancelLevel   OBJECT-TYPE
     SYNTAX INTEGER (0..65535)
     ACCESS  read-write
     STATUS  mandatory
     DESCRIPTION
"WARNING: YOU SHOULD NOT MODIFY THIS OBJECT WITHOUT THE SUPERVISION OF 
MEMOTEC PERSONNEL.

Range of Values: 0 to 65535

Default Value: 100"
     DEFVAL { 100 }
     ::= { cxMcVoxOpePortPrivEntry  6 }

      cxMcVoxOpeToneDelayAfterCnct   OBJECT-TYPE
     SYNTAX INTEGER (0..6000)
     ACCESS  read-write
     STATUS  mandatory
     DESCRIPTION
"WARNING: YOU SHOULD NOT MODIFY THIS OBJECT WITHOUT THE SUPERVISION OF 
MEMOTEC PERSONNEL.

Range of Values: 0 to 6000

Default Value: 1000"
     DEFVAL { 1000 }
     ::= { cxMcVoxOpePortPrivEntry  7 }

      cxMcVoxOpeToneDelayAfterFlash   OBJECT-TYPE
     SYNTAX INTEGER (0..6000)
     ACCESS  read-write
     STATUS  mandatory
     DESCRIPTION
"WARNING: YOU SHOULD NOT MODIFY THIS OBJECT WITHOUT THE SUPERVISION OF 
MEMOTEC PERSONNEL.

Range of Values: 0 to 6000

Default Value: 400"
     DEFVAL { 400 }
     ::= { cxMcVoxOpePortPrivEntry  8 }

      cxMcVoxOpeToneOffsetTxGain   OBJECT-TYPE
     SYNTAX INTEGER (820..1180)
     ACCESS  read-write
     STATUS  mandatory
     DESCRIPTION
"WARNING: YOU SHOULD NOT MODIFY THIS OBJECT WITHOUT THE SUPERVISION OF 
MEMOTEC PERSONNEL.

Range of Values: 820 to 1180 (-18.0dB to 18.0dB)

Default Value: 1000"
     DEFVAL { 1000 }
     ::= { cxMcVoxOpePortPrivEntry  9 }

      cxMcVoxOpeVoiceOffsetTxGain   OBJECT-TYPE
     SYNTAX INTEGER (820..1180)
     ACCESS  read-write
     STATUS  mandatory
     DESCRIPTION
"WARNING: YOU SHOULD NOT MODIFY THIS OBJECT WITHOUT THE SUPERVISION OF 
MEMOTEC PERSONNEL.

Range of Values: 820 to 1180 (-18.0dB to 18.0dB)

Default Value: 1000"
     DEFVAL { 1000 }
     ::= { cxMcVoxOpePortPrivEntry  10 }

      cxMcVoxOpeAc15InterDigit   OBJECT-TYPE
     SYNTAX INTEGER (0..60000)
     ACCESS  read-write
     STATUS  mandatory
     DESCRIPTION
"WARNING: YOU SHOULD NOT MODIFY THIS OBJECT WITHOUT THE SUPERVISION OF 
MEMOTEC PERSONNEL.

Range of Values: 0 to 60000

Default Value: 800"
     DEFVAL { 800 }
     ::= { cxMcVoxOpePortPrivEntry  11 }

      cxMcVoxOpeMfToneThold   OBJECT-TYPE
     SYNTAX INTEGER (0..255)
     ACCESS  read-write
     STATUS  mandatory
     DESCRIPTION
"WARNING: YOU SHOULD NOT MODIFY THIS OBJECT WITHOUT THE SUPERVISION OF 
MEMOTEC PERSONNEL.

Range of Values: 0 to 255

Default Value: 60"
     DEFVAL { 60 }
     ::= { cxMcVoxOpePortPrivEntry  12 }

      cxMcVoxOpePulseTmin   OBJECT-TYPE
     SYNTAX INTEGER (0..3000)
     ACCESS  read-write
     STATUS  mandatory
     DESCRIPTION
"WARNING: YOU SHOULD NOT MODIFY THIS OBJECT WITHOUT THE SUPERVISION OF 
MEMOTEC PERSONNEL.

Range of Values: 0 to 3000

Default Value: 15"
     DEFVAL { 15 }
     ::= { cxMcVoxOpePortPrivEntry  13 }

      cxMcVoxOpePulseTmax   OBJECT-TYPE
     SYNTAX INTEGER (0..3000)
     ACCESS  read-write
     STATUS  mandatory
     DESCRIPTION
"WARNING: YOU SHOULD NOT MODIFY THIS OBJECT WITHOUT THE SUPERVISION OF 
MEMOTEC PERSONNEL.

Range of Values: 0 to 3000

Default Value: 125"
     DEFVAL { 125 }
     ::= { cxMcVoxOpePortPrivEntry  14 }

      cxMcVoxOpePulseInterDigit   OBJECT-TYPE
     SYNTAX INTEGER (0..3000)
     ACCESS  read-write
     STATUS  mandatory
     DESCRIPTION
"WARNING: YOU SHOULD NOT MODIFY THIS OBJECT WITHOUT THE SUPERVISION OF 
MEMOTEC PERSONNEL.

Range of Values: 0 to 3000

Default Value: 275"
     DEFVAL { 275 }
     ::= { cxMcVoxOpePortPrivEntry  15 }

      cxMcVoxOpeDtmfGuard   OBJECT-TYPE
     SYNTAX INTEGER (0..255)
     ACCESS  read-write
     STATUS  mandatory
     DESCRIPTION
"WARNING: YOU SHOULD NOT MODIFY THIS OBJECT WITHOUT THE SUPERVISION OF 
MEMOTEC PERSONNEL.

Range of Values: 0 to 255

Default Value: 40"
     DEFVAL { 40 }
     ::= { cxMcVoxOpePortPrivEntry  16 }

      cxMcVoxOpeDtmfOpeLevel   OBJECT-TYPE
     SYNTAX INTEGER {
          minus-25 (1),
          minus-28 (2),
          minus-31 (3),
          minus-34 (4)  
        }
     ACCESS  read-write
     STATUS  mandatory
     DESCRIPTION
"WARNING: YOU SHOULD NOT MODIFY THIS OBJECT WITHOUT THE SUPERVISION OF 
MEMOTEC PERSONNEL.

Options:

minus-25 (1)

minus-28 (2)

minus-31 (3)

minus-34 (4)

Default Value: minus-25 (1)"
     DEFVAL { minus-25 }
     ::= { cxMcVoxOpePortPrivEntry  17 }

      cxMcVoxOpeDtmfTxTimeOn   OBJECT-TYPE
     SYNTAX INTEGER (0..500)
     ACCESS  read-only
     STATUS  mandatory
     DESCRIPTION
"This object is read-only.

Range of Values: 0 to 500"
     DEFVAL { 75 }
     ::= { cxMcVoxOpePortPrivEntry  18 }

      cxMcVoxOpeDtmfTxTimeOff   OBJECT-TYPE
     SYNTAX INTEGER (0..500)
     ACCESS  read-only
     STATUS  mandatory
     DESCRIPTION
"This object is read-only.

Range of Values: 0 to 500"
     DEFVAL { 75 }
     ::= { cxMcVoxOpePortPrivEntry  19 }

      cxMcVoxOpeFlashTmin   OBJECT-TYPE
     SYNTAX INTEGER (50..10000)
     ACCESS  read-write
     STATUS  mandatory
     DESCRIPTION
"WARNING: YOU SHOULD NOT MODIFY THIS OBJECT WITHOUT THE SUPERVISION OF 
MEMOTEC PERSONNEL.

Range of Values: 50 to 10000

Default Value: 200"
     DEFVAL { 200 }
     ::= { cxMcVoxOpePortPrivEntry  20 }

      cxMcVoxOpeFlashTmax   OBJECT-TYPE
     SYNTAX INTEGER (50..10000)
     ACCESS  read-write
     STATUS  mandatory
     DESCRIPTION
"WARNING: YOU SHOULD NOT MODIFY THIS OBJECT WITHOUT THE SUPERVISION OF 
MEMOTEC PERSONNEL.

Range of Values: 50 to 10000

Default Value: 800"
     DEFVAL { 800 }
     ::= { cxMcVoxOpePortPrivEntry  21 }

      cxMcVoxOpeFlashTgen   OBJECT-TYPE
     SYNTAX INTEGER (50..10000)
     ACCESS  read-write
     STATUS  mandatory
     DESCRIPTION
"WARNING: YOU SHOULD NOT MODIFY THIS OBJECT WITHOUT THE SUPERVISION OF 
MEMOTEC PERSONNEL.

Range of Values: 50 to 10000

Default Value: 500"
     DEFVAL { 500 }
     ::= { cxMcVoxOpePortPrivEntry  22 }

      cxMcVoxOpeAfterToneSilences   OBJECT-TYPE
     SYNTAX INTEGER (0..127)
     ACCESS  read-only
     STATUS  mandatory
     DESCRIPTION
"This object is read-only.

Range of Values: 0 to 127"
     DEFVAL { 64 }
     ::= { cxMcVoxOpePortPrivEntry  23 }

      cxMcVoxOpeFaxTxGain   OBJECT-TYPE
     SYNTAX INTEGER (820..1180)
     ACCESS  read-write
     STATUS  mandatory
     DESCRIPTION
"WARNING: YOU SHOULD NOT MODIFY THIS OBJECT WITHOUT THE SUPERVISION OF 
MEMOTEC PERSONNEL.

Range of Values: 820 to 1180 (-18.0dB to 18.0dB)

Default Value: 1000"
     DEFVAL { 1000 }
     ::= { cxMcVoxOpePortPrivEntry  24 }

      cxMcVoxOpeFaxRxGain   OBJECT-TYPE
     SYNTAX INTEGER (820..1180)
     ACCESS  read-write
     STATUS  mandatory
     DESCRIPTION
"WARNING: YOU SHOULD NOT MODIFY THIS OBJECT WITHOUT THE SUPERVISION OF 
MEMOTEC PERSONNEL.

Range of Values: 820 to 1180 (-18.0dB to 18.0dB)

Default Value: 1000"
     DEFVAL { 1000 }
     ::= { cxMcVoxOpePortPrivEntry  25 }

      cxMcVoxOpeFaxHdlcFlags   OBJECT-TYPE
     SYNTAX INTEGER (0..127)
     ACCESS  read-write
     STATUS  mandatory
     DESCRIPTION
"WARNING: YOU SHOULD NOT MODIFY THIS OBJECT WITHOUT THE SUPERVISION OF 
MEMOTEC PERSONNEL.

Range of Values: 0 to 127

Default Value: 2"
     DEFVAL { 2 }
     ::= { cxMcVoxOpePortPrivEntry  26 }

      cxMcVoxOpeFaxPreambleDuration   OBJECT-TYPE
     SYNTAX INTEGER (0..60000)
     ACCESS  read-write
     STATUS  deprecated
     DESCRIPTION
"WARNING: YOU SHOULD NOT MODIFY THIS OBJECT WITHOUT THE SUPERVISION OF 
MEMOTEC PERSONNEL.

Range of Values: 0 to 60000

Default Value: 1000"
     DEFVAL { 1000 }
   --#ENDING-VERSION 1
     ::= { cxMcVoxOpePortPrivEntry  27 }

      cxMcVoxOpeFaxPreambleDelay   OBJECT-TYPE
     SYNTAX INTEGER (0..60000)
     ACCESS  read-write
     STATUS  deprecated
     DESCRIPTION
"WARNING: YOU SHOULD NOT MODIFY THIS OBJECT WITHOUT THE SUPERVISION OF 
MEMOTEC PERSONNEL.

Range of Values: 0 to 60000

Default Value: 900"
     DEFVAL { 900 }
   --#ENDING-VERSION 1
     ::= { cxMcVoxOpePortPrivEntry  28 }

      cxMcVoxOpeFaxCedToneDuration   OBJECT-TYPE
     SYNTAX INTEGER (0..60000)
     ACCESS  read-write
     STATUS  deprecated
     DESCRIPTION
"WARNING: YOU SHOULD NOT MODIFY THIS OBJECT WITHOUT THE SUPERVISION OF 
MEMOTEC PERSONNEL.

Range of Values: 0 to 60000

Default Value: 500"
     DEFVAL { 500 }
   --#ENDING-VERSION 1
     ::= { cxMcVoxOpePortPrivEntry  29 }

      cxMcVoxOpeFaxInterProtoGap   OBJECT-TYPE
     SYNTAX INTEGER (0..60000)
     ACCESS  read-write
     STATUS  mandatory
     DESCRIPTION
"WARNING: YOU SHOULD NOT MODIFY THIS OBJECT WITHOUT THE SUPERVISION OF 
MEMOTEC PERSONNEL.

Range of Values: 0 to 60000

Default Value: 75"
     DEFVAL { 75 }
     ::= { cxMcVoxOpePortPrivEntry  30 }

      cxMcVoxOpeFaxTimerDetectSync   OBJECT-TYPE
     SYNTAX INTEGER (0..65000)
     ACCESS  read-write
     STATUS  mandatory
     DESCRIPTION
"WARNING: YOU SHOULD NOT MODIFY THIS OBJECT WITHOUT THE SUPERVISION OF 
MEMOTEC PERSONNEL.

Range of Values: 0 to 65000

Default Value: 7500"
     DEFVAL { 7500 }
     ::= { cxMcVoxOpePortPrivEntry  31 }

      cxMcVoxOpeFaxTimerWaitId   OBJECT-TYPE
     SYNTAX INTEGER (0..65000)
     ACCESS  read-write
     STATUS  mandatory
     DESCRIPTION
"WARNING: YOU SHOULD NOT MODIFY THIS OBJECT WITHOUT THE SUPERVISION OF 
MEMOTEC PERSONNEL.

Range of Values: 0 to 65000

Default Value: 40000"
     DEFVAL { 40000 }
     ::= { cxMcVoxOpePortPrivEntry  32 }
     
      cxMcVoxOpeFaxMinPreambleDur   OBJECT-TYPE
     SYNTAX INTEGER (0..60000)
     ACCESS  read-write
     STATUS  mandatory
     DESCRIPTION
"WARNING: YOU SHOULD NOT MODIFY THIS OBJECT WITHOUT THE SUPERVISION OF 
MEMOTEC PERSONNEL.

Range of Values: 0 to 60000

Default Value: 1000"
     DEFVAL { 1000 }
   --#STARTING-VERSION 2
     ::= { cxMcVoxOpePortPrivEntry  33 }
      
      cxMcVoxOpeFaxMaxPreambleDur   OBJECT-TYPE
     SYNTAX INTEGER (0..60000)
     ACCESS  read-write
     STATUS  mandatory
     DESCRIPTION
"WARNING: YOU SHOULD NOT MODIFY THIS OBJECT WITHOUT THE SUPERVISION OF 
MEMOTEC PERSONNEL.

Range of Values: 0 to 60000

Default Value: 1200"
     DEFVAL { 1200 }
   --#STARTING-VERSION 2
     ::= { cxMcVoxOpePortPrivEntry  34 }

      cxMcVoxOpeFaxMinPreambleDly   OBJECT-TYPE
     SYNTAX INTEGER (0..60000)
     ACCESS  read-write
     STATUS  mandatory
     DESCRIPTION
"WARNING: YOU SHOULD NOT MODIFY THIS OBJECT WITHOUT THE SUPERVISION OF 
MEMOTEC PERSONNEL.

Range of Values: 0 to 60000

Default Value: 400"
     DEFVAL { 400 }
   --#STARTING-VERSION 2
     ::= { cxMcVoxOpePortPrivEntry  35 }

      cxMcVoxOpeFaxMaxPreambleDly   OBJECT-TYPE
     SYNTAX INTEGER (0..60000)
     ACCESS  read-write
     STATUS  mandatory
     DESCRIPTION
"WARNING: YOU SHOULD NOT MODIFY THIS OBJECT WITHOUT THE SUPERVISION OF 
MEMOTEC PERSONNEL.

Range of Values: 0 to 60000

Default Value: 900"
     DEFVAL { 900 }
   --#STARTING-VERSION 2
     ::= { cxMcVoxOpePortPrivEntry  36 }

      cxMcVoxOpeFaxCedToneDetection   OBJECT-TYPE
     SYNTAX INTEGER (0..60000)
     ACCESS  read-write
     STATUS  mandatory
     DESCRIPTION
"WARNING: YOU SHOULD NOT MODIFY THIS OBJECT WITHOUT THE SUPERVISION OF 
MEMOTEC PERSONNEL.

Range of Values: 0 to 60000

Default Value: 500"
     DEFVAL { 500 }
   --#STARTING-VERSION 2
     ::= { cxMcVoxOpePortPrivEntry  37 }

      cxMcVoxOpeFaxCedMinToneDur   OBJECT-TYPE
     SYNTAX INTEGER (0..60000)
     ACCESS  read-write
     STATUS  mandatory
     DESCRIPTION
"WARNING: YOU SHOULD NOT MODIFY THIS OBJECT WITHOUT THE SUPERVISION OF 
MEMOTEC PERSONNEL.

Range of Values: 0 to 60000

Default Value: 2600"
     DEFVAL { 2600 }
   --#STARTING-VERSION 2
     ::= { cxMcVoxOpePortPrivEntry  38 }

      cxMcVoxOpeFaxCedMaxToneDur   OBJECT-TYPE
     SYNTAX INTEGER (0..60000)
     ACCESS  read-write
     STATUS  mandatory
     DESCRIPTION
"WARNING: YOU SHOULD NOT MODIFY THIS OBJECT WITHOUT THE SUPERVISION OF 
MEMOTEC PERSONNEL.

Range of Values: 0 to 60000

Default Value: 4000"
     DEFVAL { 4000 }
   --#STARTING-VERSION 2
     ::= { cxMcVoxOpePortPrivEntry  39 }

      cxMcVoxOpeFaxMaxHdlcFlags   OBJECT-TYPE
     SYNTAX INTEGER (0..127)
     ACCESS  read-write
     STATUS  mandatory
     DESCRIPTION
"WARNING: YOU SHOULD NOT MODIFY THIS OBJECT WITHOUT THE SUPERVISION OF 
MEMOTEC PERSONNEL.

Range of Values: 0 to 127

Default Value: 32"
     DEFVAL { 32 }
   --#STARTING-VERSION 3
     ::= { cxMcVoxOpePortPrivEntry  40 }

-- ============================================================

cxMcVoxTimerOpePriv  OBJECT IDENTIFIER ::= {cxMcVox 23 }
-- (!!! new group)

--  cxMcVox OPERATIONAL TIMERS PRIVATE GROUP

cxMcVoxOpeTimerPrivTable OBJECT-TYPE
   SYNTAX  SEQUENCE OF CxMcVoxOpeTimerPrivEntry
   ACCESS  not-accessible
   STATUS  mandatory
   DESCRIPTION
"Voice station planned Table."
   ::= { cxMcVoxTimerOpePriv 1 }

cxMcVoxOpeTimerPrivEntry OBJECT-TYPE
   SYNTAX  CxMcVoxOpeTimerPrivEntry
   ACCESS  not-accessible
   STATUS  mandatory
   DESCRIPTION
"Voice station planned row definition."
   INDEX { cxMcVoxOpeInterfaceType }
   ::= { cxMcVoxOpeTimerPrivTable 1 }

CxMcVoxOpeTimerPrivEntry ::=
   SEQUENCE {
      cxMcVoxOpeInterfaceType       INTEGER,

      cxMcVoxOpeTimeSeizeIn         INTEGER,
      cxMcVoxOpeTimeWaitDialOut     INTEGER,
      cxMcVoxOpeTimeWaitDialIn      INTEGER,
      cxMcVoxOpeTimeDialOut         INTEGER,
      cxMcVoxOpeTimeDialIn          INTEGER,
      cxMcVoxOpeTimeSiOff           INTEGER,
      cxMcVoxOpeTimeProceed         INTEGER,
      cxMcVoxOpeTimeAnswer          INTEGER,
      cxMcVoxOpeTimeBeforeToneOff   INTEGER,
      cxMcVoxOpeTimeWinkStartIn     INTEGER,
      cxMcVoxOpeTimeWinkStartOut    INTEGER,
      cxMcVoxOpeTimeWinkMin         INTEGER,
      cxMcVoxOpeTimeWinkMax         INTEGER,
      cxMcVoxOpeTimeSeize           INTEGER,
      cxMcVoxOpeTimeDial            INTEGER,
      cxMcVoxOpeTimeOffIn           INTEGER,
      cxMcVoxOpeTimeSiOn            INTEGER,
      cxMcVoxOpeTimeOffOut          INTEGER,
      cxMcVoxOpeTimeDiscIn          INTEGER,
      cxMcVoxOpeTimeDiscOut         INTEGER,
      cxMcVoxOpeTimeToneOut         INTEGER
    }                               

      cxMcVoxOpeInterfaceType         OBJECT-TYPE
     SYNTAX INTEGER {
               em    (1),
               fxs   (2),
               fxo   (3)
            }
     ACCESS  read-only
     STATUS  mandatory
     DESCRIPTION
"Displays the interface type of the voice I/O port.

You cannot modify this object

Options:

em (1)

fxs (2)

fxo (3)

Default: none"
     ::= { cxMcVoxOpeTimerPrivEntry 1 }


-- scv timers         

      cxMcVoxOpeTimeSeizeIn   OBJECT-TYPE
     SYNTAX INTEGER (0..60000)
     ACCESS  read-write
     STATUS  mandatory
     DESCRIPTION
"WARNING: YOU SHOULD NOT MODIFY THIS OBJECT WITHOUT THE SUPERVISION OF 
MEMOTEC PERSONNEL.

Range of Values: 0 to 60000

Default Value: 50"
     DEFVAL { 50 }
     ::= { cxMcVoxOpeTimerPrivEntry  2 }

      cxMcVoxOpeTimeWaitDialOut   OBJECT-TYPE
     SYNTAX INTEGER (0..60000)
     ACCESS  read-write
     STATUS  mandatory
     DESCRIPTION
"WARNING: YOU SHOULD NOT MODIFY THIS OBJECT WITHOUT THE SUPERVISION OF 
MEMOTEC PERSONNEL.

Range of Values: 0 to 60000

Default Value: 100"
     DEFVAL { 100 }
     ::= { cxMcVoxOpeTimerPrivEntry  3 }

      cxMcVoxOpeTimeWaitDialIn   OBJECT-TYPE
     SYNTAX INTEGER (0..60000)
     ACCESS  read-write
     STATUS  mandatory
     DESCRIPTION
"WARNING: YOU SHOULD NOT MODIFY THIS OBJECT WITHOUT THE SUPERVISION OF 
MEMOTEC PERSONNEL.

Range of Values: 0 to 60000

Default Value: 200"
     DEFVAL { 200 }
     ::= { cxMcVoxOpeTimerPrivEntry  4 }

      cxMcVoxOpeTimeDialOut   OBJECT-TYPE
     SYNTAX INTEGER (0..60000)
     ACCESS  read-write
     STATUS  mandatory
     DESCRIPTION
"WARNING: YOU SHOULD NOT MODIFY THIS OBJECT WITHOUT THE SUPERVISION OF 
MEMOTEC PERSONNEL.

Range of Values: 0 to 60000

Default Value: 50"
     DEFVAL { 50 }
     ::= { cxMcVoxOpeTimerPrivEntry  5 }

      cxMcVoxOpeTimeDialIn   OBJECT-TYPE
     SYNTAX INTEGER (0..60000)
     ACCESS  read-write
     STATUS  mandatory
     DESCRIPTION
"WARNING: YOU SHOULD NOT MODIFY THIS OBJECT WITHOUT THE SUPERVISION OF 
MEMOTEC PERSONNEL.

Range of Values: 0 to 60000

Default Value: 30"
     DEFVAL { 30 }
     ::= { cxMcVoxOpeTimerPrivEntry  6 }

      cxMcVoxOpeTimeSiOff   OBJECT-TYPE
     SYNTAX INTEGER (0..60000)
     ACCESS  read-write
     STATUS  mandatory
     DESCRIPTION
"WARNING: YOU SHOULD NOT MODIFY THIS OBJECT WITHOUT THE SUPERVISION OF 
MEMOTEC PERSONNEL.

Range of Values: 0 to 60000

Default Value: 300"
     DEFVAL { 300 }
     ::= { cxMcVoxOpeTimerPrivEntry  7 }

      cxMcVoxOpeTimeProceed   OBJECT-TYPE
     SYNTAX INTEGER (0..60000)
     ACCESS  read-write
     STATUS  mandatory
     DESCRIPTION
"WARNING: YOU SHOULD NOT MODIFY THIS OBJECT WITHOUT THE SUPERVISION OF 
MEMOTEC PERSONNEL.

Range of Values: 0 to 60000

Default Value: 30000"
     DEFVAL { 30000 }
     ::= { cxMcVoxOpeTimerPrivEntry  8 }

      cxMcVoxOpeTimeAnswer   OBJECT-TYPE
     SYNTAX INTEGER (0..60000)
     ACCESS  read-write
     STATUS  mandatory
     DESCRIPTION
"WARNING: YOU SHOULD NOT MODIFY THIS OBJECT WITHOUT THE SUPERVISION OF 
MEMOTEC PERSONNEL.

Range of Values: 0 to 60000

Default Value: 60000"
     DEFVAL { 60000 }
     ::= { cxMcVoxOpeTimerPrivEntry  9 }

      cxMcVoxOpeTimeBeforeToneOff   OBJECT-TYPE
     SYNTAX INTEGER (0..60000)
     ACCESS  read-write
     STATUS  mandatory
     DESCRIPTION
"WARNING: YOU SHOULD NOT MODIFY THIS OBJECT WITHOUT THE SUPERVISION OF 
MEMOTEC PERSONNEL.

Range of Values: 0 to 60000

Default Value: 4000"
     DEFVAL { 4000 }
     ::= { cxMcVoxOpeTimerPrivEntry  10 }

      cxMcVoxOpeTimeWinkStartIn   OBJECT-TYPE
     SYNTAX INTEGER (0..60000)
     ACCESS  read-write
     STATUS  mandatory
     DESCRIPTION
"WARNING: YOU SHOULD NOT MODIFY THIS OBJECT WITHOUT THE SUPERVISION OF 
MEMOTEC PERSONNEL.

Range of Values: 0 to 60000

Default Value: 220"
     DEFVAL { 220 }
     ::= { cxMcVoxOpeTimerPrivEntry  11 }

      cxMcVoxOpeTimeWinkStartOut   OBJECT-TYPE
     SYNTAX INTEGER (0..60000)
     ACCESS  read-write
     STATUS  mandatory
     DESCRIPTION
"WARNING: YOU SHOULD NOT MODIFY THIS OBJECT WITHOUT THE SUPERVISION OF 
MEMOTEC PERSONNEL.

Range of Values: 0 to 60000

Default Value: 125"
     DEFVAL { 125 }
     ::= { cxMcVoxOpeTimerPrivEntry  12 }

      cxMcVoxOpeTimeWinkMin   OBJECT-TYPE
     SYNTAX INTEGER (0..60000)
     ACCESS  read-write
     STATUS  mandatory
     DESCRIPTION
"WARNING: YOU SHOULD NOT MODIFY THIS OBJECT WITHOUT THE SUPERVISION OF 
MEMOTEC PERSONNEL.

Range of Values: 0 to 60000

Default Value: 140"
     DEFVAL { 140 }
     ::= { cxMcVoxOpeTimerPrivEntry  13 }

      cxMcVoxOpeTimeWinkMax   OBJECT-TYPE
     SYNTAX INTEGER (0..60000)
     ACCESS  read-write
     STATUS  mandatory
     DESCRIPTION
"WARNING: YOU SHOULD NOT MODIFY THIS OBJECT WITHOUT THE SUPERVISION OF 
MEMOTEC PERSONNEL.

Range of Values: 0 to 60000

Default Value: 290"
     DEFVAL { 290 }
     ::= { cxMcVoxOpeTimerPrivEntry  14 }

      cxMcVoxOpeTimeSeize   OBJECT-TYPE
     SYNTAX INTEGER (0..60000)
     ACCESS  read-write
     STATUS  mandatory
     DESCRIPTION
"WARNING: YOU SHOULD NOT MODIFY THIS OBJECT WITHOUT THE SUPERVISION OF 
MEMOTEC PERSONNEL.

Range of Values: 0 to 60000

Default Value: 250"
     DEFVAL { 250 }
     ::= { cxMcVoxOpeTimerPrivEntry  15 }

      cxMcVoxOpeTimeDial   OBJECT-TYPE
     SYNTAX INTEGER (0..60000)
     ACCESS  read-write
     STATUS  mandatory
     DESCRIPTION
"WARNING: YOU SHOULD NOT MODIFY THIS OBJECT WITHOUT THE SUPERVISION OF 
MEMOTEC PERSONNEL.

Range of Values: 0 to 60000

Default Value: 210"
     DEFVAL { 210 }
     ::= { cxMcVoxOpeTimerPrivEntry  16 }

      cxMcVoxOpeTimeOffIn   OBJECT-TYPE
     SYNTAX INTEGER (0..60000)
     ACCESS  read-write
     STATUS  mandatory
     DESCRIPTION
"WARNING: YOU SHOULD NOT MODIFY THIS OBJECT WITHOUT THE SUPERVISION OF 
MEMOTEC PERSONNEL.

Range of Values: 0 to 60000

Default Value: 900"
     DEFVAL { 900 }
     ::= { cxMcVoxOpeTimerPrivEntry  17 }

      cxMcVoxOpeTimeSiOn   OBJECT-TYPE
     SYNTAX INTEGER (0..60000)
     ACCESS  read-write
     STATUS  mandatory
     DESCRIPTION
"WARNING: YOU SHOULD NOT MODIFY THIS OBJECT WITHOUT THE SUPERVISION OF 
MEMOTEC PERSONNEL.

Range of Values: 0 to 60000

Default Value: 100"
     DEFVAL { 100 }
     ::= { cxMcVoxOpeTimerPrivEntry  18 }

      cxMcVoxOpeTimeOffOut   OBJECT-TYPE
     SYNTAX INTEGER (0..60000)
     ACCESS  read-write
     STATUS  mandatory
     DESCRIPTION
"WARNING: YOU SHOULD NOT MODIFY THIS OBJECT WITHOUT THE SUPERVISION OF 
MEMOTEC PERSONNEL.

Range of Values: 0 to 60000

Default Value: 150"
     DEFVAL { 150 }
     ::= { cxMcVoxOpeTimerPrivEntry  19 }

      cxMcVoxOpeTimeDiscIn   OBJECT-TYPE
     SYNTAX INTEGER (0..60000)
     ACCESS  read-write
     STATUS  mandatory
     DESCRIPTION
"WARNING: YOU SHOULD NOT MODIFY THIS OBJECT WITHOUT THE SUPERVISION OF 
MEMOTEC PERSONNEL.

Range of Values: 0 to 60000

Default Value: 250"
     DEFVAL { 250 }
     ::= { cxMcVoxOpeTimerPrivEntry  20 }

      cxMcVoxOpeTimeDiscOut  OBJECT-TYPE
     SYNTAX INTEGER (0..60000)
     ACCESS  read-write
     STATUS  mandatory
     DESCRIPTION
"WARNING: YOU SHOULD NOT MODIFY THIS OBJECT WITHOUT THE SUPERVISION OF 
MEMOTEC PERSONNEL.

Range of Values: 0 to 60000

Default Value: 650"
     DEFVAL { 650 }
     ::= { cxMcVoxOpeTimerPrivEntry  21 }

      cxMcVoxOpeTimeToneOut   OBJECT-TYPE
     SYNTAX INTEGER (0..60000)
     ACCESS  read-write
     STATUS  mandatory
     DESCRIPTION
"WARNING: YOU SHOULD NOT MODIFY THIS OBJECT WITHOUT THE SUPERVISION OF 
MEMOTEC PERSONNEL.

Range of Values: 0 to 60000

Default Value: 15000"
     DEFVAL { 15000 }
     ::= { cxMcVoxOpeTimerPrivEntry  22 }




-- =========================================================================


--  cxMcVox administrative GROUPID identification group


cxMcVoxGrpIdAdmTable OBJECT-TYPE
   SYNTAX  SEQUENCE OF CxMcVoxGrpIdAdmEntry
   ACCESS  not-accessible
   STATUS  mandatory
   DESCRIPTION
"Voice Station Group Id identification Table."
   ::= { cxMcVox 10 }

cxMcVoxGrpIdAdmEntry OBJECT-TYPE
   SYNTAX  CxMcVoxGrpIdAdmEntry
   ACCESS  not-accessible
   STATUS  mandatory
   DESCRIPTION
"Associates an entry in the GroupId table with a pathId-like identifier 
for that groupId."
   INDEX { cxMcVoxGrpIdAdmIndex }
   ::= { cxMcVoxGrpIdAdmTable 1 }

CxMcVoxGrpIdAdmEntry ::=
   SEQUENCE {
      cxMcVoxGrpIdAdmIndex     INTEGER,
      cxMcVoxGrpIdAdm          DisplayString,
      cxMcVoxGrpIdLenAdm       INTEGER,
      cxMcVoxGrpIdAdmRowStatus INTEGER,
      cxMcVoxGrpIdAdmNbPoll    INTEGER
    }

      cxMcVoxGrpIdAdmIndex   OBJECT-TYPE
     SYNTAX INTEGER (1..32)
     ACCESS  read-only
     STATUS  mandatory
     DESCRIPTION
"Displays the index number of the administrative Group ID.

You cannot modify this object. It is a display that the software provides.

Range of Values: 1 to 32

Default Value: none"
     ::= { cxMcVoxGrpIdAdmEntry 1 }

      cxMcVoxGrpIdAdm   OBJECT-TYPE
     SYNTAX  DisplayString (SIZE (1..4))
     ACCESS  read-write
     STATUS  mandatory
     DESCRIPTION
"Determines the administrative Group ID.
 The Group ID is a dialing code that the user enters to gain access to a 
remote telephone or FAX machine. The group contains up to 48 different 
Path IDs. Each of these Path IDs (i.e. specific routes to a destination) 
are polled until one of them is available to handle the call. Each of the 
Path IDs in the group must be on a separate CPU at the destination.

Range of Values: 1 to 4 numeric digits

Default Value: none

Configuration Changed: administrative"
     ::= { cxMcVoxGrpIdAdmEntry 2 }

      cxMcVoxGrpIdLenAdm OBJECT-TYPE
     SYNTAX INTEGER (1..4)
     ACCESS  read-only
     STATUS  mandatory
     DESCRIPTION
"Determines the length (in digits) of the administrative Group ID.

Range of Values: 1 to 4

Default Value: 3

Configuration Changed: administrative"
   DEFVAL { 3 }
   --#STARTING-VERSION 3
     ::= { cxMcVoxGrpIdAdmEntry 3 }

      cxMcVoxGrpIdAdmRowStatus OBJECT-TYPE
     SYNTAX INTEGER {
          invalid (1),
          valid (2) 
        }
     ACCESS  read-write
     STATUS  mandatory
     DESCRIPTION
"Determines the status of the objects in a table row.

Options:

invalid (1): row is flagged; after the next reset the values will be 
disabled and the row will be deleted from the table.

valid (2): values are enabled.

Default Value: valid (2)

Configuration Changed: administrative"
     ::= { cxMcVoxGrpIdAdmEntry 4 }

cxMcVoxGrpIdAdmNbPoll OBJECT-TYPE
   SYNTAX INTEGER (1..20)
   ACCESS  read-write
   STATUS  optional
   DESCRIPTION
"Determines the maximum number of remote voice stations in an Extension 
Group that the local voice station polls with a single call request.

Note: This object is only relevant if at least one Remote Extension Group 
ID has been defined using the objects in the cxMcVox Administrative Grp 
Group.

Range of Values: 1 to 20

Default Value: 4

Configuration Changed: administrative"
   DEFVAL { 4 }
    --#STARTING-VERSION 1
   ::= { cxMcVoxGrpIdAdmEntry 5 }



-- ====================================================================


--  cxMcVox operational GROUPID identification group


cxMcVoxGrpIdOpeTable OBJECT-TYPE
   SYNTAX  SEQUENCE OF CxMcVoxGrpIdOpeEntry
   ACCESS  not-accessible
   STATUS  mandatory
   DESCRIPTION
      "cx Voice Station Group Id identification Table."
   ::= { cxMcVox 11 }

cxMcVoxGrpIdOpeEntry OBJECT-TYPE
   SYNTAX  CxMcVoxGrpIdOpeEntry
   ACCESS  not-accessible
   STATUS  mandatory
   DESCRIPTION
"Associates an entry in the GroupId table with a pathId-like identifier    
for that groupId."
   INDEX { cxMcVoxGrpIdOpeIndex }
   ::= { cxMcVoxGrpIdOpeTable 1 }

CxMcVoxGrpIdOpeEntry ::=
   SEQUENCE {
      cxMcVoxGrpIdOpeIndex    INTEGER,
      cxMcVoxGrpIdOpe         DisplayString,
      cxMcVoxGrpIdLenOpe      INTEGER,
      cxMcVoxGrpIdOpeNbPoll   INTEGER
    }

      cxMcVoxGrpIdOpeIndex   OBJECT-TYPE
     SYNTAX INTEGER (1..32)
     ACCESS  read-only
     STATUS  mandatory
     DESCRIPTION
"Displays the index number of the operative Group ID.

You cannot modify this object.

Range of Values: 1 to 32

Default Value: none"
     ::= { cxMcVoxGrpIdOpeEntry 1 }

      cxMcVoxGrpIdOpe   OBJECT-TYPE
     SYNTAX  DisplayString (SIZE (1..4))
     ACCESS  read-only
     STATUS  mandatory
     DESCRIPTION
"Displays the operative Group ID.

The Group ID is a dialing code the user enters to gain access to the 
remote telephone or FAX machine. The Group ID contains up to 48 different 
Path IDs. Each of these Path IDs (i.e. specific routes to a destination) 
are polled until one of them is available to handle the call. Each of the 
Path IDs in the group must be on a separate CPU at the destination.

You cannot modify this object. If you want to change the value you must 
modify the object cxMcVoxGrpIdAdm of the cxMcVox Administrative Group ID 
Identificastion Group.

Range of Values: 1 to 4 numeric digits

Default Value: none"
     ::= { cxMcVoxGrpIdOpeEntry 2 }

      cxMcVoxGrpIdLenOpe OBJECT-TYPE
     SYNTAX INTEGER (1..4)
     ACCESS  read-only
     STATUS  mandatory
     DESCRIPTION
"Determines the length (in digits) of the operative Group ID.

You cannot moify this object. If you want to change the value you must 
modify the object cxMcVoxGrpIdLenAdm of the cxMcVox Administrative GROUPID 
identification group

Range of Values: 1 to 4

Default Value: 3"
   DEFVAL { 3 }
   --#STARTING-VERSION 3
     ::= { cxMcVoxGrpIdOpeEntry 3 }

cxMcVoxGrpIdOpeNbPoll OBJECT-TYPE
   SYNTAX INTEGER (1..20)
   ACCESS  read-only
   STATUS  optional
   DESCRIPTION
"Determines the maximum number of remote voice stations in an Extension 
Group that the local voice station polls with a single call request.

Note: This object is only relevant if at least one Remote Extension Group 
ID has been defined using the objects in the cxMcVox Operative Grp Group.

Range of Values: 1 to 20

Default Value: 4

Configuration Changed: operative"
   DEFVAL { 4 }
   --#STARTING-VERSION 1
   ::= { cxMcVoxGrpIdOpeEntry 4 }



-- ========================================================================

--  cxMcVox ADMINISTRATIVE GRP GROUP


--  note: The group ID definition table must be defined after the path ID 
--  table.
--        Also, a new group ID must be first identified in the group ID
--        identification table.


cxMcVoxGrpDefAdmTable OBJECT-TYPE
   SYNTAX  SEQUENCE OF CxMcVoxGrpDefAdmEntry
   ACCESS  not-accessible
   STATUS  mandatory
   DESCRIPTION
      "Planned GroupID definition table."
   ::= { cxMcVox 12 }

cxMcVoxGrpDefAdmEntry OBJECT-TYPE
   SYNTAX  CxMcVoxGrpDefAdmEntry
   ACCESS  not-accessible
   STATUS  mandatory
   DESCRIPTION
      "Planned GroupID row definition."
   INDEX { cxMcVoxGrpDefAdmIndex, cxMcVoxGrpDefAdmPriority }
   ::= { cxMcVoxGrpDefAdmTable 1 }

CxMcVoxGrpDefAdmEntry ::=
   SEQUENCE {
      cxMcVoxGrpDefAdmIndex      INTEGER,
      cxMcVoxGrpDefAdmPriority   INTEGER,
      cxMcVoxGrpDefAdmRowStatus  INTEGER,
      cxMcVoxGrpDefAdmPathId     DisplayString,
      cxMcVoxGrpDefAdmRmtExt     DisplayString
    }

      cxMcVoxGrpDefAdmIndex   OBJECT-TYPE
     SYNTAX INTEGER (1..32)
     ACCESS  read-only
     STATUS  mandatory
     DESCRIPTION
"Displays the index number of the administrative Group ID.

You cannot modify this object.

Range of Values: 1 to 32

Default Value: none"
     ::= { cxMcVoxGrpDefAdmEntry 1 }

      cxMcVoxGrpDefAdmPriority         OBJECT-TYPE
     SYNTAX INTEGER (1..48)
     ACCESS  read-only
     STATUS  mandatory
     DESCRIPTION
"Displays the polling priority level of the administrative Path ID.

When the user places a call by entering the Group ID, all Path IDs that 
you include in the group will be polled according to their priority until 
one is available to handle the call.

You add a Path ID to a Group ID using the object cxMcVoxGrpDefAdmPathId of 
this table.

You cannot modify this object.

Range of Values: 1 to 48. A value of 1 assigns the highest priority to the 
Path ID.

Default Value: none"
     ::= { cxMcVoxGrpDefAdmEntry 2 }

      cxMcVoxGrpDefAdmRowStatus  OBJECT-TYPE
     SYNTAX INTEGER {
          invalid (1),
          valid (2)
        }
     ACCESS  read-write
     STATUS  mandatory
     DESCRIPTION
"Determines the status of the objects in a table row.

Options:

invalid (1): row is flagged; after the next reset the values will be 
disabled and the row will be deleted from the table.

valid (2): values are enabled.

Default: valid (2)

Configuration Changed: administrative"
      DEFVAL { valid }
     ::= { cxMcVoxGrpDefAdmEntry 3 }

      cxMcVoxGrpDefAdmPathId        OBJECT-TYPE
     SYNTAX  DisplayString (SIZE (1..4))
     ACCESS  read-write
     STATUS  deprecated
     DESCRIPTION
"Determines the Path ID you want to include in the administrative
Group ID.

When you include a Path ID in the Group ID, the software automatically 
assigns a polling priority to it (see the object cxMcVoxGrpDefAdmPriority 
of this table).

When the user places a call by entering the Group ID, all Path IDs that 
you include in the group will be polled according to their priority until 
one is available to handle the call.

Range of Values: 1 to 4 numeric digits

Default Value: none

Configuration Changed: administrative"
	 --#ENDING-VERSION 1
     ::= { cxMcVoxGrpDefAdmEntry 4 }

      cxMcVoxGrpDefAdmRmtExt        OBJECT-TYPE
     SYNTAX  DisplayString (SIZE (1..5))
     ACCESS  read-write
     STATUS  mandatory
     DESCRIPTION
"Determines the Remote Extension that you want to include in the Group ID.

When you include a Remote Extension in the Group ID, the software 
automatically assigns a polling priority to it (see the object 
cxMcVoxGrpDefAdmPriority of this table).

When the user places a call by entering the Group ID, all Remote 
Extensions that you include in the group will be polled according to their 
priority until one is available to handle the call.

Range of Values: 1 to 5 numeric digits

Default Value: none

Configuration Changed: administrative"
	 --#STARTING-VERSION 1
     ::= { cxMcVoxGrpDefAdmEntry 5 }



-- =========================================================================


--  cxMcVox OPERATIONAL GRP GROUP


cxMcVoxGrpDefOpeTable OBJECT-TYPE
   SYNTAX  SEQUENCE OF CxMcVoxGrpDefOpeEntry
   ACCESS  not-accessible
   STATUS  mandatory
   DESCRIPTION
      "Active GroupID definition table."
   ::= { cxMcVox 13 }

cxMcVoxGrpDefOpeEntry OBJECT-TYPE
   SYNTAX  CxMcVoxGrpDefOpeEntry
   ACCESS  not-accessible
   STATUS  mandatory
   DESCRIPTION
      "Active GroupID row definition."
   INDEX { cxMcVoxGrpDefOpeIndex, cxMcVoxGrpDefOpePriority }
   ::= { cxMcVoxGrpDefOpeTable 1 }

CxMcVoxGrpDefOpeEntry ::=
   SEQUENCE {
      cxMcVoxGrpDefOpeIndex      INTEGER,
      cxMcVoxGrpDefOpePriority   INTEGER,
      cxMcVoxGrpDefOpePathId     DisplayString,
      cxMcVoxGrpDefOpeRmtExt     DisplayString
    }

      cxMcVoxGrpDefOpeIndex   OBJECT-TYPE
     SYNTAX INTEGER (1..32)
     ACCESS  read-only
     STATUS  mandatory
     DESCRIPTION
"Displays the index number of the operative Group ID.

You cannot modify this object.

Range of Values: 1 to 32

Default Value: none"
     ::= { cxMcVoxGrpDefOpeEntry 1 }

      cxMcVoxGrpDefOpePriority         OBJECT-TYPE
     SYNTAX INTEGER (1..48)
     ACCESS  read-only
     STATUS  mandatory
     DESCRIPTION
"Displays the polling priority level of the operative Path ID.

When the user places a call by entering the Group ID, all Path IDs that 
you include in the group will be polled according to their priority until 
one is available to handle the call.

You add a Path ID to a Group ID using the object cxMcVoxGrpDefAdmPathId of 
the cxMcVox Administrative Grp Group.

You cannot modify this object

Range of Values: 1 to 48. A value of 1 assigns the highest priority to the 
Path ID.

Default Value: none"
     ::= { cxMcVoxGrpDefOpeEntry 2 }

      cxMcVoxGrpDefOpePathId        OBJECT-TYPE
     SYNTAX  DisplayString (SIZE (1..4))
     ACCESS  read-only
     STATUS  deprecated
     DESCRIPTION
"Displays the Path ID included in the operative Group ID.

When you include a Path ID in the Group ID, the software automatically 
assigns a polling priority to it (see the object cxMcVoxGrpDefAdmPriority 
of this table).

When the user places a call by entering the Group ID, all Path IDs that 
you include in the group will be polled according to their priority until 
one is available to handle the call.

You cannot modify this object. If you want to change the value you must 
modify the object cxMcVoxGrpDefAdmPathId of the cxMcVox Administrative GRP 
Group

Range of Values: 1 to 4 numeric digits

Default Value: none"
	 --#ENDING-VERSION 1
     ::= { cxMcVoxGrpDefOpeEntry 3 }

      cxMcVoxGrpDefOpeRmtExt        OBJECT-TYPE
     SYNTAX  DisplayString (SIZE (1..5))
     ACCESS  read-only
     STATUS  mandatory
     DESCRIPTION
"Determines the Remote Extension that you want to include in the Group ID.

When you include a Remote Extension in the Group ID, the software 
automatically assigns a polling priority to it (see the object 
cxMcVoxGrpDefOpePriority of this table).

When the user places a call by entering the Group ID, all Remote 
Extensions that you include in the group will be polled according to their 
priority, until one is available to handle the call.

Range of Values: 1 to 5 numeric digits

Default Value: none

Configuration Changed: operative"
	 --#STARTING-VERSION 1
     ::= { cxMcVoxGrpDefOpeEntry 4 }



-- =========================================================================

--  cxMcVox ADMINISTRATION PERSONAL IDENTIFICATION NUMBER GROUP


cxMcVoxAdmPinTable OBJECT-TYPE
   SYNTAX  SEQUENCE OF CxMcVoxAdmPinEntry
   ACCESS  not-accessible
   STATUS  mandatory
   DESCRIPTION
"Personal identification number Table."
   --#STARTING-VERSION 4
   ::= { cxMcVox 14 }

cxMcVoxAdmPinEntry OBJECT-TYPE
   SYNTAX  CxMcVoxAdmPinEntry
   ACCESS  not-accessible
   STATUS  mandatory
   DESCRIPTION
"Personal identification number row definition."
   INDEX { cxMcVoxAdmPinIndex }
   ::= { cxMcVoxAdmPinTable 1 }

CxMcVoxAdmPinEntry ::=
   SEQUENCE {
      cxMcVoxAdmPinIndex         INTEGER,
      cxMcVoxAdmPinCode          DisplayString,
      cxMcVoxAdmPinRowStatus     INTEGER
    }

      cxMcVoxAdmPinIndex     OBJECT-TYPE
     SYNTAX INTEGER (1..256)
     ACCESS  read-only
     STATUS  mandatory
     DESCRIPTION
"Displays the index number of the Personal Identification Number (PIN).

You cannot modify this object.

Range of Values: 1 to 256

Default Value: none"
     ::= { cxMcVoxAdmPinEntry 1 }

    cxMcVoxAdmPinCode OBJECT-TYPE
       SYNTAX  DisplayString (SIZE (2..8))
       ACCESS  read-write
       STATUS  mandatory
       DESCRIPTION
"Determines the Personal Identification Number (PIN) that is validated by 
the local voice station prior to a call being established.

The local voice station verifies that the PIN included in the call request 
packet is listed in its PIN table. If it is not,the call will not be 
established and the user will hear a fast busy signal.

Range of Values: 2 to 8 digits from 0 to 9

Default Value: none"
     ::= { cxMcVoxAdmPinEntry 2 }


      cxMcVoxAdmPinRowStatus OBJECT-TYPE
     SYNTAX INTEGER {
          invalid (1),
          valid (2) 
        }
     ACCESS  read-write
     STATUS  mandatory
     DESCRIPTION
"Determines the status of the objects in a table row.

Options:

invalid (1): row is flagged; after the next reset the values will be 
disabled and the row will be deleted from the table.

valid (2): values are enabled

Default Value: none"
     ::= { cxMcVoxAdmPinEntry 3 }



-- =========================================================================

--  cxMcVox OPERATIONAL PERSONAL IDENTIFICATION NUMBER GROUP


cxMcVoxOpePinTable OBJECT-TYPE
   SYNTAX  SEQUENCE OF CxMcVoxOpePinEntry
   ACCESS  not-accessible
   STATUS  mandatory
   DESCRIPTION
"Personal identification number Table."
   --#STARTING-VERSION 4
   ::= { cxMcVox 15 }

cxMcVoxOpePinEntry OBJECT-TYPE
   SYNTAX  CxMcVoxOpePinEntry
   ACCESS  not-accessible
   STATUS  mandatory
   DESCRIPTION
"Personal identification number row definition."
   INDEX { cxMcVoxOpePinIndex }
   ::= { cxMcVoxOpePinTable 1 }

CxMcVoxOpePinEntry ::=
   SEQUENCE {
      cxMcVoxOpePinIndex         INTEGER,
      cxMcVoxOpePinCode          DisplayString
    }

      cxMcVoxOpePinIndex     OBJECT-TYPE
     SYNTAX INTEGER (1..256)
     ACCESS  read-only
     STATUS  mandatory
     DESCRIPTION
"Displays the index number of the Personal identification Number (PIN).

You cannot modify this object. 

Range of Values: 1 to 256.

Default Value: none"
     ::= { cxMcVoxOpePinEntry 1 }

    cxMcVoxOpePinCode OBJECT-TYPE
       SYNTAX  DisplayString (SIZE (2..8))
       ACCESS  read-only
       STATUS  mandatory
       DESCRIPTION
"Displays the Personal Identification Number (PIN) that is validated by the 
local voice station prior to a call being established.

The local voice station verifies that the PIN included in the call request 
packet is listed in its PIN table. If it is not,the call will not be 
established and the user will hear a fast busy signal.

Range of Values: 2 to 8 digits from 0 to 9

Default Value: none"
     ::= { cxMcVoxOpePinEntry 2 }



-- =======================================================================

--  cxMcVox ADMINISTRATIVE LOCAL ZONE CODES GROUP
-- 

cxMcVoxAdmLclZoneTable OBJECT-TYPE
   SYNTAX  SEQUENCE OF CxMcVoxAdmLclZoneEntry
   ACCESS  not-accessible
   STATUS  mandatory
   DESCRIPTION
"Local Zone Codes Table."
   ::= { cxMcVox 16 }

cxMcVoxAdmLclZoneEntry OBJECT-TYPE
   SYNTAX  CxMcVoxAdmLclZoneEntry
   ACCESS  not-accessible
   STATUS  mandatory
   DESCRIPTION
"Local Zones codes row definition."
   INDEX { cxMcVoxAdmLclZoneIndex }
   ::= { cxMcVoxAdmLclZoneTable 1 }

CxMcVoxAdmLclZoneEntry ::=
   SEQUENCE {
      cxMcVoxAdmLclZoneIndex        INTEGER,
      cxMcVoxAdmLclZoneCode         DisplayString,
      cxMcVoxAdmLclZoneLng          INTEGER,
      cxMcVoxAdmLclZoneRowStatus    INTEGER
    }

      cxMcVoxAdmLclZoneIndex     OBJECT-TYPE
     SYNTAX INTEGER (1..128)
     ACCESS  read-only
     STATUS  mandatory
     DESCRIPTION

"Displays the index number of the administrative local zone code.

Range of Values: 1 to 128.

Default Value: none"
   --#STARTING-VERSION 3
     ::= { cxMcVoxAdmLclZoneEntry 1 }


    cxMcVoxAdmLclZoneCode OBJECT-TYPE
       SYNTAX  DisplayString (SIZE (1..4))
       ACCESS  read-write
       STATUS  mandatory
       DESCRIPTION

"Determines the number of the administrative local zone code which will 
serve in the verification of the phone number to be dialed depending on 
where the remote site is installed. 

Range of Values: 1 to 4 digits from 0 to 9

Note: The * character is used as a wildcard character. Only one wildcard 
character can be used per zone code.

Default Value: none"
   --#STARTING-VERSION 3
     ::= { cxMcVoxAdmLclZoneEntry 2 }


      cxMcVoxAdmLclZoneLng    OBJECT-TYPE
     SYNTAX  INTEGER (1..4)
     ACCESS  read-only
     STATUS  mandatory
     DESCRIPTION

"Determines the length (in digits) of the administrative local zone code.

Range of Values: 1 to 4

Default Value: none"
   --#STARTING-VERSION 3
     ::= { cxMcVoxAdmLclZoneEntry 3 }


      cxMcVoxAdmLclZoneRowStatus OBJECT-TYPE
     SYNTAX INTEGER {
          invalid (1),
          valid (2) 
        }
     ACCESS  read-write
     STATUS  mandatory
     DESCRIPTION

"Determines the status of the objects in a table row.

Options:

invalid (1): row is flagged; after the next reset the values will be 
disabled and the row will be deleted from the table.

valid (2): values are enabled

Default Value: none"
   --#STARTING-VERSION 3
     ::= { cxMcVoxAdmLclZoneEntry 4 }

-- ======================================================================

--  cxMcVox OPERATIONAL LOCAL ZONE CODE GROUP
-- 

cxMcVoxOpeLclZoneTable OBJECT-TYPE
   SYNTAX  SEQUENCE OF CxMcVoxOpeLclZoneEntry
   ACCESS  not-accessible
   STATUS  mandatory
   DESCRIPTION
"Local Zones Codes Table."
   ::= { cxMcVox 17 }

cxMcVoxOpeLclZoneEntry OBJECT-TYPE
   SYNTAX  CxMcVoxOpeLclZoneEntry
   ACCESS  not-accessible
   STATUS  mandatory
   DESCRIPTION
"Local Zones codes row definition."
   INDEX { cxMcVoxOpeLclZoneIndex }
   ::= { cxMcVoxOpeLclZoneTable 1 }

CxMcVoxOpeLclZoneEntry ::=
   SEQUENCE {
      cxMcVoxOpeLclZoneIndex        INTEGER,
      cxMcVoxOpeLclZoneCode         DisplayString,
      cxMcVoxOpeLclZoneLng          INTEGER
    }

      cxMcVoxOpeLclZoneIndex     OBJECT-TYPE
     SYNTAX INTEGER (1..128)
     ACCESS  read-only
     STATUS  mandatory
     DESCRIPTION

"Displays the index number of the operational local zone code.

Range of Values: 1 to 128.

Default Value: none"
   --#STARTING-VERSION 3
     ::= { cxMcVoxOpeLclZoneEntry 1 }


    cxMcVoxOpeLclZoneCode OBJECT-TYPE
       SYNTAX  DisplayString (SIZE (1..4))
       ACCESS  read-only
       STATUS  mandatory
       DESCRIPTION

"Displays the number of the operational local zone code which will serve in 
the verification of the phone number to be dialed depending on where the 
remote CX1000 is installed.

You cannot modify this object. If you want to change the code you must 
change the setting of the cxMcVoxAdmLclZoneCode object in the cxMcVox 
Administrative Zone Codes Group.

Range of Values: 1 to 4 digits from 0 to 9

Note: The * character is used as a wildcard character. Only one wildcard 
character can be used per zone code.

Default Value: none"
   --#STARTING-VERSION 3
     ::= { cxMcVoxOpeLclZoneEntry 2 }


      cxMcVoxOpeLclZoneLng    OBJECT-TYPE
     SYNTAX  INTEGER (1..4)
     ACCESS  read-only
     STATUS  mandatory
     DESCRIPTION

"Displays the length (in digits) of the operational local zone code.

You cannot modify this object. If you want to change the length you must 
change the setting of the object cxMcVoxAdmLclZoneLng of the cxMccVox 
Administrative Local Zone Codes Group.

Range of Values: 1 to 4

Default Value: none"
   --#STARTING-VERSION 3
     ::= { cxMcVoxOpeLclZoneEntry 3 }

-- ======================================================================

--  cxMcVox ADMINISTRATION REMOTE TRANSLATIONS CODES GROUP
--  DEPRECATED


cxMcVoxAdmRTC        OBJECT IDENTIFIER ::= {cxMcVox 18 }

cxMcVoxAdmRTCCountry OBJECT-TYPE
   SYNTAX  DisplayString (SIZE (1..4))
   ACCESS  read-write
   STATUS  deprecated
   DESCRIPTION
"The CX900 does not currently support this object.

Determines the number of the administrative local country code which will 
serve in the verification of the phone number to be dialed depending on 
where the remote CX1000 is installed. 

Range of Values: 1 to 4 digits from 0 to 9

Default Value: none"
   --#ENDING-VERSION 3
   ::= { cxMcVoxAdmRTC 1 }


cxMcVoxAdmRTCCountryLng    OBJECT-TYPE
   SYNTAX  INTEGER (1..4)
   ACCESS  read-write
   STATUS  deprecated
   DESCRIPTION
"The CX900 does not currently support this object.

Determines the length (in digits) of the administrative local country 
code.

Range of Values: 1 to 4

Default Value: none"
   --#ENDING-VERSION 3
   ::= { cxMcVoxAdmRTC 2 }


cxMcVoxAdmRTCNonLclCountry OBJECT-TYPE
   SYNTAX  DisplayString (SIZE (1..4))
   ACCESS  read-write
   STATUS  deprecated
   DESCRIPTION
"The CX900 does not currently support this object.

Determines the number of the administrative local country code which will 
be inserted in front of the Country Code if the latter does not correspond 
to the local country code parameter.

Range of Values: 1 to 4 digits from 0 to 9

Default Value: none"
   --#ENDING-VERSION 3
   ::= { cxMcVoxAdmRTC 3 }


cxMcVoxAdmRTCNonLclCountryLng    OBJECT-TYPE
   SYNTAX  INTEGER (1..4)
   ACCESS  read-write
   STATUS  deprecated
   DESCRIPTION
"The CX900 does not currently support this object.

Determines the length (in digits) of the administrative non local country 
code.

Range of Values: 1 to 4.

Default Value: none"
   --#ENDING-VERSION 3
   ::= { cxMcVoxAdmRTC 4 }


cxMcVoxAdmRTCArea OBJECT-TYPE
   SYNTAX  DisplayString (SIZE (1..4))
   ACCESS  read-write
   STATUS  deprecated
   DESCRIPTION
"The CX900 does not currently support this object.

Determines the number of the administrative local area code which will 
serve in the verification of the phone number to be dialed depending on 
where the remote CX1000 is installed. 

Range of Values: 1 to 4 digits from 0 to 9

Default Value: none"
   --#ENDING-VERSION 3
   ::= { cxMcVoxAdmRTC 5 }


cxMcVoxAdmRTCAreaLng    OBJECT-TYPE
   SYNTAX  INTEGER (1..4)
   ACCESS  read-write
   STATUS  deprecated
   DESCRIPTION
"The CX900 does not currently support this object.

Determines the length (in digits) of the administrative local area code.

Range of Values: 1 to 4

Default Value: none"
   --#ENDING-VERSION 3
   ::= { cxMcVoxAdmRTC 6 }


cxMcVoxAdmRTCNonLclArea OBJECT-TYPE
   SYNTAX  DisplayString (SIZE (1..4))
   ACCESS  read-write
   STATUS  deprecated
   DESCRIPTION
"The CX900 does not currently support this object.

Determines the number of the administrative local area code which will be 
inserted in front of the Area Code if the latter does not correspond to 
the local country code parameter.

Range of Values: 1 to 4 digits from 0 to 9

Default Value: none"
   --#ENDING-VERSION 3
   ::= { cxMcVoxAdmRTC 7 }


cxMcVoxAdmRTCNonLclAreaLng    OBJECT-TYPE
   SYNTAX  INTEGER (1..4)
   ACCESS  read-write
   STATUS  deprecated
   DESCRIPTION
"The CX900 does not currently support this object.

Determines the length (in digits) of the administrative non local area 
code.

Range of Values: 1 to 4.

Default Value: none"
   --#ENDING-VERSION 3
   ::= { cxMcVoxAdmRTC 8 }


cxMcVoxAdmRTCNonLclZone OBJECT-TYPE
   SYNTAX  DisplayString (SIZE (1..4))
   ACCESS  read-write
   STATUS  deprecated
   DESCRIPTION
"The CX900 does not currently support this object.

Determines the number of the administrative local zone code which will be 
inserted in front of the Zone Code if the latter does not correspond to 
the local country code parameter.

Range of Values: 1 to 4 digits from 0 to 9

Default Value: none"
   --#ENDING-VERSION 3
  ::= { cxMcVoxAdmRTC 9 }

cxMcVoxAdmRTCNonLclZoneLng    OBJECT-TYPE
  SYNTAX  INTEGER (1..4)
  ACCESS  read-write
  STATUS  deprecated
  DESCRIPTION
"The CX900 does not currently support this object.

Determines the length (in digits) of the administrative non local zone 
code.

Range of Values: 1 to 4

Default Value: none"
   --#ENDING-VERSION 3
  ::= { cxMcVoxAdmRTC 10 }



-- ======================================================================

--  cxMcVox OPERATIONAL REMOTE TRANSLATIONS CODES GROUP
--  DEPRECATED


cxMcVoxOpeRTC        OBJECT IDENTIFIER ::= {cxMcVox 19 }

cxMcVoxOpeRTCCountry OBJECT-TYPE
   SYNTAX  DisplayString (SIZE (1..4))
   ACCESS  read-only
   STATUS  deprecated
   DESCRIPTION
"The CX900 does not currently support this object.

Displays the number of the operative local country code which will serve 
in the verification of the phone number to be dialed depending on where 
the remote CX1000 is installed.

Range of Values: 1 to 4 digits from 0 to 9

Default Value: none."
   --#ENDING-VERSION 3
   ::= { cxMcVoxOpeRTC 1 }


cxMcVoxOpeRTCCountryLng    OBJECT-TYPE
   SYNTAX  INTEGER (1..4)
   ACCESS  read-only
   STATUS  deprecated
   DESCRIPTION
"The CX900 does not currently support this object.

Displays the length (in digits) of the operative local country code.

Range of Values: 1 to 4.

Default Value: none"
   --#ENDING-VERSION 3
   ::= { cxMcVoxOpeRTC 2 }


cxMcVoxOpeRTCNonLclCountry OBJECT-TYPE
   SYNTAX  DisplayString (SIZE (1..4))
   ACCESS  read-only
   STATUS  deprecated
   DESCRIPTION
"The CX900 does not currently support this object.

Displays the number of the operative local country code which will be 
inserted in front of the Country Code if the latter does not correspond to 
the local country code parameter.

Range of Values: 1 to 4 digits from 0 to 9

Default Value: none"
   --#ENDING-VERSION 3
   ::= { cxMcVoxOpeRTC 3 }


cxMcVoxOpeRTCNonLclCountryLng    OBJECT-TYPE
   SYNTAX  INTEGER (1..4)
   ACCESS  read-only
   STATUS  deprecated
   DESCRIPTION
"The CX900 does not currently support this object.

Displays the length (in digits) of the operative non local country code.

Range of Values: 1 to 4.

Default Value: none"
   --#ENDING-VERSION 3
   ::= { cxMcVoxOpeRTC 4 }


cxMcVoxOpeRTCArea OBJECT-TYPE
   SYNTAX  DisplayString (SIZE (1..4))
   ACCESS  read-only
   STATUS  deprecated
   DESCRIPTION
"The CX900 does not currently support this object.

Displays the number of the operative local area code which will serve in 
the verification of the phone number to be dialed depending on where the 
remote CX1000 is installed.

Range of Values: 1 to 4 digits from 0 to 9

Default Value: none"
   --#ENDING-VERSION 3
   ::= { cxMcVoxOpeRTC 5 }


cxMcVoxOpeRTCAreaLng    OBJECT-TYPE
   SYNTAX  INTEGER (1..4)
   ACCESS  read-only
   STATUS  deprecated
   DESCRIPTION
"The CX900 does not currently support this object.

Displays the length (in digits) of the operative local area code.

Range of Values: 1 to 4.

Default Value: none"
   --#ENDING-VERSION 3
   ::= { cxMcVoxOpeRTC 6 }


cxMcVoxOpeRTCNonLclArea OBJECT-TYPE
   SYNTAX  DisplayString (SIZE (1..4))
   ACCESS  read-only
   STATUS  deprecated
   DESCRIPTION
"The CX900 does not currently support this object.

Displays the number of the operative local area code which will be 
inserted in front of the Area Code if the latter does not correspond to 
the local country code parameter.

Range of Values: 1 to 4 digits from 0 to 9

Default Value: none"
   --#ENDING-VERSION 3
   ::= { cxMcVoxOpeRTC 7 }


cxMcVoxOpeRTCNonLclAreaLng    OBJECT-TYPE
   SYNTAX  INTEGER (1..4)
   ACCESS  read-only
   STATUS  deprecated
   DESCRIPTION
"The CX900 does not currently support this object.

Displays the length (in digits) of the operative non local area code.

Range of Values: 1 to 4

Default Value: none"
   --#ENDING-VERSION 3
   ::= { cxMcVoxOpeRTC 8 }


cxMcVoxOpeRTCNonLclZone OBJECT-TYPE
   SYNTAX  DisplayString (SIZE (1..4))
   ACCESS  read-only
   STATUS  deprecated
   DESCRIPTION
"The CX900 does not currently support this object.

Displays the number of the operative local zone code which will be 
inserted in front of the Zone Code if the latter does not correspond to 
the local country code parameter.

Range of Values: 1 to 4 digits from 0 to 9

Default Value: none"
   --#ENDING-VERSION 3
   ::= { cxMcVoxOpeRTC 9 }


cxMcVoxOpeRTCNonLclZoneLng    OBJECT-TYPE
   SYNTAX  INTEGER (1..4)
   ACCESS  read-only
   STATUS  deprecated
   DESCRIPTION
"The CX900 does not currently support this object.

Displays the length (in digits) of the operative non local zone code.

Range of Values: 1 to 4

Default Value: none"
   --#ENDING-VERSION 3
   ::= { cxMcVoxOpeRTC 10 }



-- ======================================================================

--  cxMcVox DIAGNOSTIC GROUP


cxMcVoxDiagTable OBJECT-TYPE
   SYNTAX  SEQUENCE OF CxMcVoxDiagEntry
   ACCESS  not-accessible
   STATUS  mandatory
   DESCRIPTION
"Voice station diagnostics and events Table."
   ::= { cxMcVox 24 }

cxMcVoxDiagEntry OBJECT-TYPE
   SYNTAX  CxMcVoxDiagEntry
   ACCESS  not-accessible
   STATUS  mandatory
   DESCRIPTION
""
   INDEX { cxMcVoxDiagCardIndex,
cxMcVoxDiagPortIndex }
   ::= { cxMcVoxDiagTable 1 }

CxMcVoxDiagEntry ::=
   SEQUENCE {
      cxMcVoxDiagCardIndex     INTEGER,
      cxMcVoxDiagPortIndex     INTEGER,
      cxMcVoxDiagScvEvents     INTEGER,
      cxMcVoxDiagGsdEvents     INTEGER,
      cxMcVoxDiagToneInEvents  INTEGER,
      cxMcVoxDiagToneOutEvents INTEGER,
      cxMcVoxDiagFaxInEvents   INTEGER,
      cxMcVoxDiagFaxOutEvents  INTEGER,
      cxMcVoxDiagGlmEvents     INTEGER,
      cxMcVoxDiagIbvDiags      INTEGER,
      cxMcVoxDiagPcvDiags      INTEGER,
      cxMcVoxDiagGcvDiags      INTEGER,
      cxMcVoxDiagFaxDiags      INTEGER,
      cxMcVoxDiagLseDiags      INTEGER,
      cxMcVoxDiagScvDiags      INTEGER,
      cxMcVoxDiagGlmDiags      INTEGER
    }

      cxMcVoxDiagCardIndex     OBJECT-TYPE
     SYNTAX INTEGER (1..8)
     ACCESS  read-only
     STATUS  mandatory
     DESCRIPTION
""
     ::= { cxMcVoxDiagEntry 1 }

      cxMcVoxDiagPortIndex  OBJECT-TYPE
     SYNTAX INTEGER (1..15)
     ACCESS  read-only
     STATUS  mandatory
     DESCRIPTION
""
     ::= { cxMcVoxDiagEntry 2 }

      cxMcVoxDiagScvEvents OBJECT-TYPE
     SYNTAX   INTEGER {
          no-action (1),
          trigger   (2),
          reset     (3)
           }
     ACCESS  read-write
     STATUS  mandatory
     DESCRIPTION
""
     DEFVAL { no-action }
     ::= { cxMcVoxDiagEntry 3 }

      cxMcVoxDiagGsdEvents OBJECT-TYPE
     SYNTAX   INTEGER {
          no-action (1),
          trigger   (2),
          reset     (3)
           }
     ACCESS  read-write
     STATUS  mandatory
     DESCRIPTION
""
     DEFVAL { no-action }
     ::= { cxMcVoxDiagEntry 4 }

      cxMcVoxDiagToneInEvents OBJECT-TYPE
     SYNTAX   INTEGER {
          no-action (1),
          trigger   (2),
          reset     (3)
           }
     ACCESS  read-write
     STATUS  mandatory
     DESCRIPTION
""
     DEFVAL { no-action }
     ::= { cxMcVoxDiagEntry 5 }

      cxMcVoxDiagToneOutEvents OBJECT-TYPE
     SYNTAX   INTEGER {
          no-action (1),
          trigger   (2),
          reset     (3)
           }
     ACCESS  read-write
     STATUS  mandatory
     DESCRIPTION
""
     DEFVAL { no-action }
     ::= { cxMcVoxDiagEntry 6 }

      cxMcVoxDiagFaxInEvents OBJECT-TYPE
     SYNTAX   INTEGER {
          no-action (1),
          trigger   (2),
          reset     (3)
           }
     ACCESS  read-write
     STATUS  mandatory
     DESCRIPTION
""
     DEFVAL { no-action }
     ::= { cxMcVoxDiagEntry 7 }

      cxMcVoxDiagFaxOutEvents OBJECT-TYPE
     SYNTAX   INTEGER {
          no-action (1),
          trigger   (2),
          reset     (3)
           }
     ACCESS  read-write
     STATUS  mandatory
     DESCRIPTION
""
     DEFVAL { no-action }
     ::= { cxMcVoxDiagEntry 8 }

      cxMcVoxDiagGlmEvents OBJECT-TYPE
     SYNTAX   INTEGER {
          no-action (1),
          trigger   (2),
          reset     (3)
           }
     ACCESS  read-write
     STATUS  mandatory
     DESCRIPTION
""
     DEFVAL { no-action }
     ::= { cxMcVoxDiagEntry 9 }

      cxMcVoxDiagIbvDiags OBJECT-TYPE
     SYNTAX   INTEGER {
          no-action (1),
          trigger   (2),
          reset     (3)
           }
     ACCESS  read-write
     STATUS  mandatory
     DESCRIPTION
""
     DEFVAL { no-action }
     ::= { cxMcVoxDiagEntry 10 }

      cxMcVoxDiagPcvDiags OBJECT-TYPE
     SYNTAX   INTEGER {
          no-action (1),
          trigger   (2),
          reset     (3)
           }
     ACCESS  read-write
     STATUS  mandatory
     DESCRIPTION
""
     DEFVAL { no-action }
     ::= { cxMcVoxDiagEntry 11 }

      cxMcVoxDiagGcvDiags OBJECT-TYPE
     SYNTAX   INTEGER {
          no-action (1),
          trigger   (2),
          reset     (3)
           }
     ACCESS  read-write
     STATUS  mandatory
     DESCRIPTION
""
     DEFVAL { no-action }
     ::= { cxMcVoxDiagEntry 12 }

      cxMcVoxDiagFaxDiags OBJECT-TYPE
     SYNTAX   INTEGER {
          no-action (1),
          trigger   (2),
          reset     (3)
           }
     ACCESS  read-write
     STATUS  mandatory
     DESCRIPTION
""
     DEFVAL { no-action }
     ::= { cxMcVoxDiagEntry 13 }

      cxMcVoxDiagLseDiags OBJECT-TYPE
     SYNTAX   INTEGER {
          no-action (1),
          trigger   (2),
          reset     (3)
           }
     ACCESS  read-write
     STATUS  mandatory
     DESCRIPTION
""
     DEFVAL { no-action }
     ::= { cxMcVoxDiagEntry 14 }

      cxMcVoxDiagScvDiags OBJECT-TYPE
     SYNTAX   INTEGER {
          no-action (1),
          trigger   (2),
          reset     (3)
           }
     ACCESS  read-write
     STATUS  mandatory
     DESCRIPTION
""
     DEFVAL { no-action }
     ::= { cxMcVoxDiagEntry 15 }

      cxMcVoxDiagGlmDiags OBJECT-TYPE
     SYNTAX   INTEGER {
          no-action (1),
          trigger   (2),
          reset     (3)
           }
     ACCESS  read-write
     STATUS  mandatory
     DESCRIPTION
""
     DEFVAL { no-action }
     ::= { cxMcVoxDiagEntry 16 }


-- ======================================================================
--  cxMcVox Download GROUP.

cxMcVoxDownload        OBJECT IDENTIFIER ::= {cxMcVox 25 }

-- ======================================================================

--  cxMcVox ADMINISTRATIVE LOCAL EXTENSION GROUP


cxMcVoxLclExtAdmTable OBJECT-TYPE
   SYNTAX  SEQUENCE OF CxMcVoxLclExtAdmEntry
   ACCESS  not-accessible
   STATUS  mandatory
   DESCRIPTION
"Planned Local Extensions table."
   --#STARTING-VERSION 1
   ::= { cxMcVox 26 }

cxMcVoxLclExtAdmEntry OBJECT-TYPE
   SYNTAX  CxMcVoxLclExtAdmEntry
   ACCESS  not-accessible
   STATUS  mandatory
   DESCRIPTION
"Planned Local Extensions row definition."
   INDEX { cxMcVoxLclExtAdmIndex }
   ::= { cxMcVoxLclExtAdmTable 1 }

CxMcVoxLclExtAdmEntry ::=
   SEQUENCE {
      cxMcVoxLclExtAdmIndex        INTEGER,
      cxMcVoxLclExtAdmRowStatus    INTEGER,
      cxMcVoxLclExtAdmExt          DisplayString,
      cxMcVoxLclExtAdmHuntChnl     INTEGER
    }

      cxMcVoxLclExtAdmIndex  OBJECT-TYPE
     SYNTAX INTEGER (1..64)
     ACCESS  read-only
     STATUS  mandatory
     DESCRIPTION
"Displays the index number of the Remote Extension.

You cannot modify this object.

Range of Values: 1 to 64

Default Value: none"
     ::= { cxMcVoxLclExtAdmEntry 1 }

      cxMcVoxLclExtAdmRowStatus OBJECT-TYPE
     SYNTAX INTEGER {
          invalid (1),
          valid (2) 
        }
     ACCESS  read-write
     STATUS  mandatory
     DESCRIPTION
"Determines the status of the objects in a table row.

Options:

invalid (1): row is flagged; after the next reset the values are disabled 
and the row is deleted from the table.

valid (2): values are enabled.

Default Value: none

Configuration Changed: administrative"
     ::= { cxMcVoxLclExtAdmEntry 2 }

      cxMcVoxLclExtAdmExt       OBJECT-TYPE
     SYNTAX  DisplayString (SIZE (1..5))
     ACCESS  read-write
     STATUS  mandatory
     DESCRIPTION
"Determines the numeric dialing code to be dialed by remote 
located parties to access the local telephone or fax machine.

Range of Values: 1 to 5 numeric digits

Default Value: none

Configuration Changed: administrative"
     ::= { cxMcVoxLclExtAdmEntry 3 }

      cxMcVoxLclExtAdmHuntChnl     OBJECT-TYPE
     SYNTAX INTEGER (1..1073741823)
     ACCESS  read-write
     STATUS  mandatory
     DESCRIPTION
"Defines the local voice channels to be polled (hunted) during call 
establishment with the Local Extension (specified by object 
cxMcVoxLclExtAdmExt).

This value acts as a mask so that all specified channels are polled until 
the call is accepted. This hunt channel mask includes a maximum of 30 
voice channels.

The default value includes all local voice channels. If you want to 
exclude specific channels, calculate the value by following these steps: 

1.  Decide which ports to include, for example, 1,5,8,29.

2. Convert the list of ports to a series of bits. Start with a list of 30 
zeros. 

00 0000 0000 0000 0000 0000 0000 0000 

To include ports 1, 5, 8, and 29, place 1s in these positions. Numbering 
starts at 1 at the extreme right. 

01 0000 0000 0000 0000 0000 1001 0001 

3.  Convert this number to hexadecimal.
10000091

4.  Convert this number to decimal.
268 435 601

Range of Values: 1 to 1073741823

Default Value: 1073741823

Configuration Changed: administrative"
     DEFVAL { 1073741823 }
     ::= { cxMcVoxLclExtAdmEntry 4 }



-- ==================================================================

--  cxMcVox OPERATIONAL LOCAL EXTENSION GROUP


cxMcVoxLclExtOpeTable OBJECT-TYPE
   SYNTAX  SEQUENCE OF CxMcVoxLclExtOpeEntry
   ACCESS  not-accessible
   STATUS  mandatory
   DESCRIPTION
"Active Local Extensions table."
   --#STARTING-VERSION 1
   ::= { cxMcVox 27 }

cxMcVoxLclExtOpeEntry OBJECT-TYPE
   SYNTAX  CxMcVoxLclExtOpeEntry
   ACCESS  not-accessible
   STATUS  mandatory
   DESCRIPTION
"Active Local Extensions row definition."
   INDEX { cxMcVoxLclExtOpeIndex }
   ::= { cxMcVoxLclExtOpeTable 1 }

CxMcVoxLclExtOpeEntry ::=
   SEQUENCE {
      cxMcVoxLclExtOpeIndex        INTEGER,
      cxMcVoxLclExtOpeExt          DisplayString,
      cxMcVoxLclExtOpeHuntChnl     INTEGER
    }

      cxMcVoxLclExtOpeIndex  OBJECT-TYPE
     SYNTAX INTEGER (1..64)
     ACCESS  read-only
     STATUS  mandatory
     DESCRIPTION
"Displays the index number of the Remote Extension.

You cannot modify this object.

Range of Values: 1 to 64

Default Value: none"
     ::= { cxMcVoxLclExtOpeEntry 1 }

      cxMcVoxLclExtOpeExt          OBJECT-TYPE
     SYNTAX  DisplayString (SIZE (1..5))
     ACCESS  read-only
     STATUS  mandatory
     DESCRIPTION
"Determines the numeric dialing code to be dialed by remote located 
parties to access the local telephone or fax machine.

Range of Values: 1 to 5 numeric digits

Default Value: none

Configuration Changed: operational"
     ::= { cxMcVoxLclExtOpeEntry 2 }

      cxMcVoxLclExtOpeHuntChnl     OBJECT-TYPE
     SYNTAX INTEGER (1..1073741823)
     ACCESS  read-only
     STATUS  mandatory
     DESCRIPTION
"Defines the local voice channels to be polled (hunted) during call 
establishment with the Local Extension (specified by object 
cxMcVoxLclExtAdmExt).

This value acts as a mask so that all specified channels are polled until 
the call is accepted. This hunt channel mask includes a maximum of 30 
voice channels.

The default value includes all local voice channels. If you want to 
exclude specific channels, calculate the value by following these steps: 

1.  Decide which ports to include, for example, 1,5,8,29.

2. Convert the list of ports to a series of bits. Start with a list of 30 
zeros. 

00 0000 0000 0000 0000 0000 0000 0000 

To include ports 1, 5, 8, and 29, place 1s in these positions. Numbering 
starts at 1 at the extreme right. 

01 0000 0000 0000 0000 0000 1001 0001 

3.  Convert this number to hexadecimal.
10000091

4.  Convert this number to decimal.
268 435 601

Range of Values: 1 to 1073741823

Default Value: 1073741823

Configuration Changed: operational"
     DEFVAL { 1073741823 }
     ::= { cxMcVoxLclExtOpeEntry 3 }



-- ======================================================================
--  cxMcVox Regeneration Operational GROUP.

cxMcVoxRegenOpe        OBJECT IDENTIFIER ::= { cxMcVox 28 }

cxMcVoxRegenOpeExt   OBJECT-TYPE
   SYNTAX INTEGER {  
          disabled (1),
          enabled (2)
        }
   ACCESS  read-write
   STATUS  mandatory
   DESCRIPTION
"The RegenOpeExt is used to specify if the local extension tones are
to be regenerated."
   DEFVAL { disabled }
   --#STARTING-VERSION 3
   ::= { cxMcVoxRegenOpe 1 }

cxMcVoxRegenOpeGid      OBJECT-TYPE
   SYNTAX INTEGER {  
          disabled (1),
          enabled (2)
        }
   ACCESS  read-write
   STATUS  mandatory
   DESCRIPTION
"The RegenOpeGid is used to specify if the group ids tones are to be
regenerated."
   DEFVAL { disabled }
   --#STARTING-VERSION 3
   ::= { cxMcVoxRegenOpe 2 }

cxMcVoxRegenOpeNbDigits OBJECT-TYPE
   SYNTAX INTEGER (1..8)
   ACCESS  read-write
   STATUS  mandatory
   DESCRIPTION
"The number of digits to be regenerated."
   DEFVAL { 3 }
   --#STARTING-VERSION 3
   ::= { cxMcVoxRegenOpe 3 }

cxMcVoxRegenOpeExtBitMask OBJECT-TYPE
   SYNTAX INTEGER (0..255)
   ACCESS  read-write
   STATUS  mandatory
   DESCRIPTION
"This object is a bitmap that selects up to 
cxMcVoxRegenOpeNbDigits, which can be set up to 
8 digits, corresponding to a bit that is set. The default
value corresponds to 7 (or 00000111 in binary).

Range of Values: 0 to 255

Default Value: 7"
   DEFVAL { 7 }
   --#STARTING-VERSION 11
   ::= { cxMcVoxRegenOpe 4 }

-- ======================================================================

--  cxMcVox OPERATIONAL CODE TRANSLATION GROUP
-- 


cxMcVoxTranslOpe      OBJECT IDENTIFIER ::= {cxMcVox 29 }

cxMcVoxTranslOpeCntryCodeEnable      OBJECT-TYPE
   SYNTAX INTEGER {  
          disabled (1),
          enabled (2)
        }
   ACCESS  read-write
   STATUS  mandatory
   DESCRIPTION
"This specifies whether to translate the local country code."
   DEFVAL { disabled }
   --#STARTING-VERSION 3
   ::= { cxMcVoxTranslOpe 1 }


cxMcVoxTranslOpeCntryCode OBJECT-TYPE
   SYNTAX  DisplayString (SIZE (1..4))
   ACCESS  read-write
   STATUS  mandatory
   DESCRIPTION

"Displays the number of the operational local country code which will serve 
in the verification of the phone number to be dialed depending on where 
the remote site is installed.

Range of Values: 1 to 4 digits from 0 to 9

Default Value: none."
	DEFVAL { "1" }
   --#STARTING-VERSION 3
   ::= { cxMcVoxTranslOpe 2 }


cxMcVoxTranslOpeCntryCodeLng    OBJECT-TYPE
   SYNTAX  INTEGER (1..4)
   ACCESS  read-only
   STATUS  mandatory
   DESCRIPTION

"Displays the length (in digits) of the operational local country code.

Range of Values: 1 to 4.

Default Value: none"
	DEFVAL { 1 }
   --#STARTING-VERSION 3
   ::= { cxMcVoxTranslOpe 3 }


cxMcVoxTranslOpeCCPrefix OBJECT-TYPE
   SYNTAX  DisplayString (SIZE (1..4))
   ACCESS  read-write
   STATUS  mandatory
   DESCRIPTION

"Displays the number of the operational local country code which will be 
inserted in front of the Country Code if the latter does not correspond to 
the local country code parameter.

Range of Values: 1 to 4 digits from 0 to 9

Default Value: none"
	DEFVAL { "2" }
   --#STARTING-VERSION 3
   ::= { cxMcVoxTranslOpe 4 }


cxMcVoxTranslOpeCCPrefixLng    OBJECT-TYPE
   SYNTAX  INTEGER (1..4)
   ACCESS  read-only
   STATUS  mandatory
   DESCRIPTION

"Displays the length (in digits) of the operational non local country code.

Range of Values: 1 to 4.

Default Value: none"
	DEFVAL { 1 }
   --#STARTING-VERSION 3
   ::= { cxMcVoxTranslOpe 5 }


cxMcVoxTranslOpeAreaCodeEnable      OBJECT-TYPE
   SYNTAX INTEGER {  
          disabled (1),
          enabled (2)
        }
   ACCESS  read-write
   STATUS  mandatory
   DESCRIPTION
"This specifies whether to translate the local area code."
   DEFVAL { disabled }
   --#STARTING-VERSION 3
   ::= { cxMcVoxTranslOpe 6 }


cxMcVoxTranslOpeAreaCode OBJECT-TYPE
   SYNTAX  DisplayString (SIZE (1..4))
   ACCESS  read-write
   STATUS  mandatory
   DESCRIPTION

"Displays the number of the operational local area code which will serve in 
the verification of the phone number to be dialed depending on where the 
remote site is installed.

Range of Values: 1 to 4 digits from 0 to 9

Default Value: none"
	DEFVAL { "514" }
   --#STARTING-VERSION 3
   ::= { cxMcVoxTranslOpe 7 }


cxMcVoxTranslOpeAreaCodeLng    OBJECT-TYPE
   SYNTAX  INTEGER (1..4)
   ACCESS  read-only
   STATUS  mandatory
   DESCRIPTION

"Displays the length (in digits) of the operational local area code.

Range of Values: 1 to 4.

Default Value: none"
	DEFVAL { 3 }
   --#STARTING-VERSION 3
   ::= { cxMcVoxTranslOpe 8 }


cxMcVoxTranslOpeACPrefix OBJECT-TYPE
   SYNTAX  DisplayString (SIZE (1..4))
   ACCESS  read-write
   STATUS  mandatory
   DESCRIPTION

"Displays the number of the operational local area code which will be 
inserted in front of the Area Code if the latter does not correspond to 
the local country code parameter.

Range of Values: 1 to 4 digits from 0 to 9

Default Value: none"
	DEFVAL { "1" }
   --#STARTING-VERSION 3
   ::= { cxMcVoxTranslOpe 9 }


cxMcVoxTranslOpeACPrefixLng    OBJECT-TYPE
   SYNTAX  INTEGER (1..4)
   ACCESS  read-only
   STATUS  mandatory
   DESCRIPTION

"Displays the length (in digits) of the operational non local area code.

Range of Values: 1 to 4

Default Value: none"
	DEFVAL { 1 }
   --#STARTING-VERSION 3
   ::= { cxMcVoxTranslOpe 10 }


cxMcVoxTranslOpeZoneCodeEnable      OBJECT-TYPE
   SYNTAX INTEGER {  
          disabled (1),
          enabled (2)
        }
   ACCESS  read-write
   STATUS  mandatory
   DESCRIPTION
"This specifies whether to translate the local zone code."
   DEFVAL { disabled }
   --#STARTING-VERSION 3
   ::= { cxMcVoxTranslOpe 11 }


cxMcVoxTranslOpeZCPrefix OBJECT-TYPE
   SYNTAX  DisplayString (SIZE (1..4))
   ACCESS  read-write
   STATUS  mandatory
   DESCRIPTION

"Displays the number of the operational local zone code which will be 
inserted in front of the Zone Code if the latter does not correspond to 
the local country code parameter.

Range of Values: 1 to 4 digits from 0 to 9

Default Value: none"
	DEFVAL { "7" }
   --#STARTING-VERSION 3
   ::= { cxMcVoxTranslOpe 12 }


cxMcVoxTranslOpeZCPrefixLng    OBJECT-TYPE
   SYNTAX  INTEGER (1..4)
   ACCESS  read-only
   STATUS  mandatory
   DESCRIPTION

"Displays the length (in digits) of the operational non local zone code.

Range of Values: 1 to 4

Default Value: none"
	DEFVAL { 1 }
   --#STARTING-VERSION 3
   ::= { cxMcVoxTranslOpe 13 }


-- ======================================================================

--  cxMcVox CALL HISTORY GROUP
-- 

cxMcVoxHistoryTable OBJECT-TYPE
   SYNTAX  SEQUENCE OF CxMcVoxHistoryEntry
   ACCESS  not-accessible
   STATUS  mandatory
   DESCRIPTION
"OnLine/OffLine history table for incoming/outgoing calls."
   --#STARTING-VERSION 5
   ::= { cxMcVox 30 }

cxMcVoxHistoryEntry OBJECT-TYPE
   SYNTAX  CxMcVoxHistoryEntry
   ACCESS  not-accessible
   STATUS  mandatory
   DESCRIPTION
"Online/Offline history row definition."
   INDEX { cxMcVoxHistoryIndex }
   ::= { cxMcVoxHistoryTable 1 }

CxMcVoxHistoryEntry ::=
   SEQUENCE {
      cxMcVoxHistoryIndex              INTEGER,
      cxMcVoxHistoryLclCardNumber      INTEGER,
      cxMcVoxHistoryLclPortNumber      INTEGER,
      cxMcVoxHistoryRmtCardNumber      INTEGER,
      cxMcVoxHistoryRmtPortNumber      INTEGER,
      cxMcVoxHistoryTimeStampOnLine    INTEGER,
      cxMcVoxHistoryTimeStampOffLine   INTEGER,
      cxMcVoxHistoryLnkState           DisplayString,
      cxMcVoxHistoryPin                DisplayString,
      cxMcVoxHistoryExtensionOrGrpId   DisplayString,
      cxMcVoxHistoryPhoneNumber        DisplayString
   }

cxMcVoxHistoryIndex  OBJECT-TYPE
     SYNTAX INTEGER (1..256)
     ACCESS  read-only
     STATUS  mandatory
     DESCRIPTION
"The index number of the history log."
     ::= { cxMcVoxHistoryEntry 1 }

cxMcVoxHistoryLclCardNumber  OBJECT-TYPE
     SYNTAX INTEGER (1..4)
     ACCESS  read-only
     STATUS  mandatory
     DESCRIPTION
"Displays the voice I/O card slot displacement from the CPU card slot.
As an example on the CX1000, card number 1 is directly behind the CPU card
and card number 2 is one slot up.  In the case of the CX900 product, this
card number represents the logical slot corresponding to its physical slot
as mapped in the 'voxcard' table.
You cannot modify this object.
Range of Values: 1 to 4
Default Value: none"
     ::= { cxMcVoxHistoryEntry 2 }

cxMcVoxHistoryLclPortNumber  OBJECT-TYPE
     SYNTAX INTEGER (1..15)
     ACCESS  read-only
     STATUS  mandatory
     DESCRIPTION
"Displays the number of the voice I/O port.
You cannot modify this object. 
Range of Values: 1 to 15
Default Value: none"
     ::= { cxMcVoxHistoryEntry 3 }

cxMcVoxHistoryRmtCardNumber  OBJECT-TYPE
     SYNTAX INTEGER (1..4)
     ACCESS  read-only
     STATUS  mandatory
     DESCRIPTION
"Displays the remote voice I/O card slot displacement from the CPU card slot.  As an example on the CX1000, card number 1 is directly behind th
You cannot modify this object.
Range of Values: 1 to 4
Default Value: none"
     ::= { cxMcVoxHistoryEntry 4 }

cxMcVoxHistoryRmtPortNumber  OBJECT-TYPE
     SYNTAX INTEGER (1..15)
     ACCESS  read-only
     STATUS  mandatory
     DESCRIPTION
"Displays the number of the voice I/O port that was reached at the remote
location.
You cannot modify this object. 
Range of Values: 1 to 15
Default Value: none"
     ::= { cxMcVoxHistoryEntry 5 }

cxMcVoxHistoryTimeStampOnLine    OBJECT-TYPE
     SYNTAX  INTEGER(1.. 4294967295)
     ACCESS  read-only
     STATUS  mandatory
     DESCRIPTION
"Displays the time stamp of the last on-line event. An on-line event is
any incoming or outgoing call that is started. The time stamp indicates the
number of seconds elapsed since the last power up.
You cannot modify this object. 
Range of Values:
1 to 4294967295
Default Value: none"
     ::= { cxMcVoxHistoryEntry 6 }

cxMcVoxHistoryTimeStampOffLine    OBJECT-TYPE
     SYNTAX  INTEGER(1.. 4294967295)
     ACCESS  read-only
     STATUS  mandatory
     DESCRIPTION
"Displays the time stamp of the last off-line event. An off-line event is
any incoming or outgoing call that the voice station terminates. The time
stamp indicates the number of seconds elapsed since the last power up.
You cannot modify this object. 

Range of Values:
1 to 4294967295

Default Value: none"
     ::= { cxMcVoxHistoryEntry 7 }

cxMcVoxHistoryLnkState OBJECT-TYPE
     SYNTAX DisplayString (SIZE(1..16))
     ACCESS  read-only
     STATUS  mandatory
     DESCRIPTION
"Displays the status of the link to the remote user.  When the call is
successful the status is either 'Incoming' or 'Outgoing'.  Else the
error type is displayed.

You cannot modify this object.

Options:

Connection established:       either 'Incoming' or 'Outgoing'
Local port unavailable:		   'LclPortUnavail'
Remote extension unavailable:	'RmtExtUnavail'
Remote ports busy:		      'RmtPortsBusy'
Invalid PIN:			         'InvalidPIN'
Call aborted:			         'CallAborted'

Default Value: 'CallAborted'"
	DEFVAL { "CallAborted" }
     ::= { cxMcVoxHistoryEntry 8 }

cxMcVoxHistoryPin OBJECT-TYPE
     SYNTAX  DisplayString (SIZE (2..8))
     ACCESS  read-only
     STATUS  mandatory
     DESCRIPTION
"Displays the Personal Identification Number (PIN) that is validated
against the local voice station card PIN number table.

Range of Values: 2 to 8 numeric digits, each number from 0 to 9

Default Value: none"
     ::= { cxMcVoxHistoryEntry 9 }

cxMcVoxHistoryExtensionOrGrpId   OBJECT-TYPE
     SYNTAX  DisplayString (SIZE (1..4))
     ACCESS  read-only
     STATUS  mandatory
     DESCRIPTION
"Displays the extension or group ID the remote user has dialed to reach
the local user. This object is irrelevant for outgoing calls.

You cannot modify this object.

Range of Values: 1 to 4 numeric digits

Default Value: none"
     ::= { cxMcVoxHistoryEntry 10 }

cxMcVoxHistoryPhoneNumber   OBJECT-TYPE
     SYNTAX  DisplayString (SIZE (1..24))
     ACCESS  read-only
     STATUS  mandatory
     DESCRIPTION
"For outgoing calls, this object displays the complete phone number
(including any voice mail digits) the user entered to reach the remote
user.  This can include access code, country code, area code and zone code
but excludes PIN number.

For incoming calls, this object displays either the regenerated code or
the translated code (or both).

Codes that are dialed after the extension or group ID are also logged
in this object both for outgoing and incoming calls.

You cannot modify this object.

Range of Values: 1 to 24 numeric digits

Default Value: none"
     ::= { cxMcVoxHistoryEntry 11 }



-- TRAPS


cxMcVoxTrapStatus       TRAP-TYPE
    ENTERPRISE      cxMcVox
    VARIABLES {
            cxModuleHwPhysSlot,
            cxMcVoxStatusCardNumber,
            cxMcVoxStatusPortNumber,
            cxMcVoxStatusPortStatus
          }
    DESCRIPTION
"Reports that there is a change in the functional state of the voice 
channel.
cxMcVoxTrapStatus = 1 if the port is disabled
cxMcVoxTrapStatus = 2 if the port is enabled
cxMcVoxTrapStatus = 3 if there is no I/O hardware"
    ::= 1

cxMcVoxTrapRing         TRAP-TYPE
    ENTERPRISE      cxMcVox
    VARIABLES {     
            cxModuleHwPhysSlot,
            cxMcVoxGlobalTensionRing
          }
    DESCRIPTION
"Reports that there is a change in the functional state of the ring 
generator power supply.
cxMcVoxTrapRing = 2 if the ringing generator is good
cxMcVoxTrapRing = 1 otherwise"
    ::= 2

cxMcVoxTrapDc           TRAP-TYPE
    ENTERPRISE      cxMcVox
    VARIABLES {     
            cxModuleHwPhysSlot,
            cxMcVoxGlobalTensionDc
          }
    DESCRIPTION
"Reports that there is a change in the functional state of the DC power 
supply.
cxMcVoxGlobalTensionDc = 2 if the DC power supply is good
cxMcVoxGlobalTensionDc = 1 otherwise"
    ::= 3

cxMcVoxHistoryTrap           TRAP-TYPE
    ENTERPRISE      cxMcVox
    VARIABLES {     
            cxModuleHwPhysSlot,
            cxMcVoxHistoryIndex,
            cxMcVoxGlobalHistoryMaxNumberOfEntries
          }
    DESCRIPTION
"Informs the management station of the fact that the history table needs
servicing."
    ::= 4

END
