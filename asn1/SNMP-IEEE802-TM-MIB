-- extracted from rfc4789.txt
-- at Thu Nov 30 06:07:35 2006

   SNMP-IEEE802-TM-MIB DEFINITIONS ::= BEGIN

   IMPORTS
       MODULE-IDENTITY, OBJECT-IDENTITY, snmpModules, snmpDomains
           FROM SNMPv2-SMI;

       snmpIeee802TmMib MODULE-IDENTITY
           LAST-UPDATED "200611210000Z"
           ORGANIZATION "IETF Operations and Management Area"
           CONTACT-INFO
               "Juergen Schoenwaelder (Editor)
                International University Bremen
                P.O. Box 750 561
                28725 Bremen, Germany

                Phone: +49 421 200-3587
                EMail: j.schoenwaelder@iu-bremen.de

                Send comments to <ietfmibs@ops.ietf.org>."
           DESCRIPTION
               "This MIB module defines the SNMP over IEEE 802
                transport mapping.

                Copyright (C) The IETF Trust (2006).  This version
                of this MIB module is part of RFC 4789; see the RFC
                itself for full legal notices."
           REVISION "200611210000Z"
           DESCRIPTION
               "The initial version, published as RFC 4789."
           ::= { snmpModules 21 }

       snmpIeee802Domain OBJECT-IDENTITY
           STATUS  current
           DESCRIPTION
               "The SNMP over IEEE 802 networks transport domain.  The
                corresponding transport address is of type MacAddress
                as defined in the SNMPv2-TC module (RFC 2579)."
           REFERENCE "RFC 2579"
           ::= { snmpDomains 6 }
   END

-- 
--    Copyright (C) The IETF Trust (2006).
-- 
--    This document is subject to the rights, licenses and restrictions
--    contained in BCP 78, and except as set forth therein, the authors
--    retain all their rights.
-- 
--    This document and the information contained herein are provided on an
--    "AS IS" basis and THE CONTRIBUTOR, THE ORGANIZATION HE/SHE REPRESENTS
--    OR IS SPONSORED BY (IF ANY), THE INTERNET SOCIETY, THE IETF TRUST,
--    AND THE INTERNET ENGINEERING TASK FORCE DISCLAIM ALL WARRANTIES,
--    EXPRESS OR IMPLIED, INCLUDING BUT NOT LIMITED TO ANY WARRANTY THAT
--    THE USE OF THE INFORMATION HEREIN WILL NOT INFRINGE ANY RIGHTS OR ANY
--    IMPLIED WARRANTIES OF MERCHANTABILITY OR FITNESS FOR A PARTICULAR
--    PURPOSE.
-- 
-- Intellectual Property
-- 
--    The IETF takes no position regarding the validity or scope of any
--    Intellectual Property Rights or other rights that might be claimed to
--    pertain to the implementation or use of the technology described in
--    this document or the extent to which any license under such rights
--    might or might not be available; nor does it represent that it has
--    made any independent effort to identify any such rights.  Information
--    on the procedures with respect to rights in RFC documents can be
--    found in BCP 78 and BCP 79.
-- 
--    Copies of IPR disclosures made to the IETF Secretariat and any
--    assurances of licenses to be made available, or the result of an
--    attempt made to obtain a general license or permission for the use of
--    such proprietary rights by implementers or users of this
--    specification can be obtained from the IETF on-line IPR repository at
--    http://www.ietf.org/ipr.
-- 
--    The IETF invites any interested party to bring to its attention any
--    copyrights, patents or patent applications, or other proprietary
--    rights that may cover technology that may be required to implement
--    this standard.  Please address the information to the IETF at
--    ietf-ipr@ietf.org.
--
