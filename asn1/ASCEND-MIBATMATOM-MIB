--			Ascend mibatmatom MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBATMATOM-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibatmVclProfile  OBJECT IDENTIFIER ::= { configuration 39}
    mibatmVplProfile  OBJECT IDENTIFIER ::= { configuration 38}

	-- The mibatmVclProfile table
	--
	-- This table contains parameters for the mibatmVclProfile profile
	--

    mibatmVclProfileTable	OBJECT-TYPE
	SYNTAX		SEQUENCE OF MibatmVclProfileEntry
	ACCESS		not-accessible
	STATUS		mandatory
	DESCRIPTION	"A list of mibatmVclProfile profile entries."
	::= { mibatmVclProfile 1 }

    mibatmVclProfileEntry	OBJECT-TYPE
	SYNTAX		MibatmVclProfileEntry
	ACCESS		not-accessible
	STATUS		mandatory
	DESCRIPTION	"A mibatmVclProfile entry containing objects that
			 maps to the parameters of mibatmVclProfile profile."
	INDEX		{ atmVclProfile-Id-Address-PhysicalAddress-Shelf, atmVclProfile-Id-Address-PhysicalAddress-Slot, atmVclProfile-Id-Address-PhysicalAddress-ItemNumber, atmVclProfile-Id-Address-LogicalItem, atmVclProfile-Id-Vpi, atmVclProfile-Id-Vci }
	::= { mibatmVclProfileTable 1 }

    MibatmVclProfileEntry ::=
	SEQUENCE {
	    atmVclProfile-Id-Address-PhysicalAddress-Shelf
		INTEGER,
	    atmVclProfile-Id-Address-PhysicalAddress-Slot
		INTEGER,
	    atmVclProfile-Id-Address-PhysicalAddress-ItemNumber
		INTEGER,
	    atmVclProfile-Id-Address-LogicalItem
		INTEGER,
	    atmVclProfile-Id-Vpi
		INTEGER,
	    atmVclProfile-Id-Vci
		INTEGER,
	    atmVclProfile-RxTrafficDesc
		INTEGER,
	    atmVclProfile-TxTrafficDesc
		INTEGER,
	    atmVclProfile-AalType
		INTEGER,
	    atmVclProfile-TxSduSize
		INTEGER,
	    atmVclProfile-RxSduSize
		INTEGER,
	    atmVclProfile-Aal5Encaps
		INTEGER,
	    atmVclProfile-McastType
		INTEGER,
	    atmVclProfile-CallKind
		INTEGER,
	    atmVclProfile-Action-o
		INTEGER
	}

    atmVclProfile-Id-Address-PhysicalAddress-Shelf	OBJECT-TYPE
	SYNTAX	INTEGER
	ACCESS	read-only
	STATUS	mandatory
	DESCRIPTION	"The number of the shelf that the addressed physical device resides on."
	::= { mibatmVclProfileEntry 1 }

    atmVclProfile-Id-Address-PhysicalAddress-Slot	OBJECT-TYPE
	SYNTAX	INTEGER
	ACCESS	read-only
	STATUS	mandatory
	DESCRIPTION	"The number of the slot that the addressed physical device resides on."
	::= { mibatmVclProfileEntry 2 }

    atmVclProfile-Id-Address-PhysicalAddress-ItemNumber	OBJECT-TYPE
	SYNTAX	INTEGER
	ACCESS	read-only
	STATUS	mandatory
	DESCRIPTION	"A number that specifies an addressable entity within the context of shelf and slot."
	::= { mibatmVclProfileEntry 3 }

    atmVclProfile-Id-Address-LogicalItem	OBJECT-TYPE
	SYNTAX	INTEGER
	ACCESS	read-only
	STATUS	mandatory
	DESCRIPTION	"A number that specifies an addressable logical entity within the context of a physical address."
	::= { mibatmVclProfileEntry 4 }

    atmVclProfile-Id-Vpi	OBJECT-TYPE
	SYNTAX	INTEGER
	ACCESS	read-only
	STATUS	mandatory
	DESCRIPTION	"The VPI number for this Vcl."
	::= { mibatmVclProfileEntry 5 }

    atmVclProfile-Id-Vci	OBJECT-TYPE
	SYNTAX	INTEGER
	ACCESS	read-only
	STATUS	mandatory
	DESCRIPTION	"The VCI number for this Vcl."
	::= { mibatmVclProfileEntry 6 }

    atmVclProfile-RxTrafficDesc	OBJECT-TYPE
	SYNTAX	INTEGER
	ACCESS	read-only
	STATUS	mandatory
	DESCRIPTION	"The ATM Traffic Descriptor index applied to the receive direction of the Vcl."
	::= { mibatmVclProfileEntry 7 }

    atmVclProfile-TxTrafficDesc	OBJECT-TYPE
	SYNTAX	INTEGER
	ACCESS	read-only
	STATUS	mandatory
	DESCRIPTION	"The Traffic Descriptor index applied to the transmit direction of the Vcl."
	::= { mibatmVclProfileEntry 8 }

    atmVclProfile-AalType	OBJECT-TYPE
	SYNTAX	INTEGER {
		    notPresent (1),
		    aal1 (2),
		    aal34 (3),
		    aal5 (4),
		    aalOther (5),
		    aalUnknown (6),
		    aal2 (7)
		}
	ACCESS	read-only
	STATUS	mandatory
	DESCRIPTION	"The type of the ATM Adaptation Layer used by this Vcl."
	::= { mibatmVclProfileEntry 9 }

    atmVclProfile-TxSduSize	OBJECT-TYPE
	SYNTAX	INTEGER
	ACCESS	read-only
	STATUS	mandatory
	DESCRIPTION	"The maximum AAL5 CPCS SDU size in octets that is supported on the transmit direction of this VCC."
	::= { mibatmVclProfileEntry 10 }

    atmVclProfile-RxSduSize	OBJECT-TYPE
	SYNTAX	INTEGER
	ACCESS	read-only
	STATUS	mandatory
	DESCRIPTION	"The maximum AAL5 CPCS SDU size in octets that is supported on the receive direction of this VCC."
	::= { mibatmVclProfileEntry 11 }

    atmVclProfile-Aal5Encaps	OBJECT-TYPE
	SYNTAX	INTEGER {
		    vcmuxRouted (2),
		    vcmuxBridged8023 (3),
		    vcmuxBridged8025 (4),
		    vcmuxBridged8026 (5),
		    vcmuxLanemul8023 (6),
		    vcmuxLanemul8025 (7),
		    llcEncapsulation (8),
		    multiFrameRelaySscs (9),
		    otherEncapsulation (10),
		    unknownEncapsulation (11)
		}
	ACCESS	read-only
	STATUS	mandatory
	DESCRIPTION	"The type of data encapsulation used over AAL5 SSCS Layer."
	::= { mibatmVclProfileEntry 12 }

    atmVclProfile-McastType	OBJECT-TYPE
	SYNTAX	INTEGER {
		    p2p (2),
		    p2mproot (3),
		    p2mpleaf (4)
		}
	ACCESS	read-only
	STATUS	mandatory
	DESCRIPTION	"The connection topology type."
	::= { mibatmVclProfileEntry 13 }

    atmVclProfile-CallKind	OBJECT-TYPE
	SYNTAX	INTEGER {
		    pvc (2),
		    svcIncoming (3),
		    svcOutgoing (4),
		    spvcInitiator (5),
		    spvcTarget (6)
		}
	ACCESS	read-only
	STATUS	mandatory
	DESCRIPTION	"The use of call control."
	::= { mibatmVclProfileEntry 14 }

    atmVclProfile-Action-o	OBJECT-TYPE
	SYNTAX	INTEGER {
		    noAction (1),
		    createProfile (2),
		    deleteProfile (3)
		}
	ACCESS	read-write
	STATUS	mandatory
	DESCRIPTION	""
	::= { mibatmVclProfileEntry 15 }


	-- The mibatmVplProfile table
	--
	-- This table contains parameters for the mibatmVplProfile profile
	--

    mibatmVplProfileTable	OBJECT-TYPE
	SYNTAX		SEQUENCE OF MibatmVplProfileEntry
	ACCESS		not-accessible
	STATUS		mandatory
	DESCRIPTION	"A list of mibatmVplProfile profile entries."
	::= { mibatmVplProfile 1 }

    mibatmVplProfileEntry	OBJECT-TYPE
	SYNTAX		MibatmVplProfileEntry
	ACCESS		not-accessible
	STATUS		mandatory
	DESCRIPTION	"A mibatmVplProfile entry containing objects that
			 maps to the parameters of mibatmVplProfile profile."
	INDEX		{ atmVplProfile-Id-Address-PhysicalAddress-Shelf, atmVplProfile-Id-Address-PhysicalAddress-Slot, atmVplProfile-Id-Address-PhysicalAddress-ItemNumber, atmVplProfile-Id-Address-LogicalItem, atmVplProfile-Id-Vpi }
	::= { mibatmVplProfileTable 1 }

    MibatmVplProfileEntry ::=
	SEQUENCE {
	    atmVplProfile-Id-Address-PhysicalAddress-Shelf
		INTEGER,
	    atmVplProfile-Id-Address-PhysicalAddress-Slot
		INTEGER,
	    atmVplProfile-Id-Address-PhysicalAddress-ItemNumber
		INTEGER,
	    atmVplProfile-Id-Address-LogicalItem
		INTEGER,
	    atmVplProfile-Id-Vpi
		INTEGER,
	    atmVplProfile-RxTrafficDesc
		INTEGER,
	    atmVplProfile-TxTrafficDesc
		INTEGER,
	    atmVplProfile-McastType
		INTEGER,
	    atmVplProfile-CallKind
		INTEGER,
	    atmVplProfile-Action-o
		INTEGER
	}

    atmVplProfile-Id-Address-PhysicalAddress-Shelf	OBJECT-TYPE
	SYNTAX	INTEGER
	ACCESS	read-only
	STATUS	mandatory
	DESCRIPTION	"The number of the shelf that the addressed physical device resides on."
	::= { mibatmVplProfileEntry 1 }

    atmVplProfile-Id-Address-PhysicalAddress-Slot	OBJECT-TYPE
	SYNTAX	INTEGER
	ACCESS	read-only
	STATUS	mandatory
	DESCRIPTION	"The number of the slot that the addressed physical device resides on."
	::= { mibatmVplProfileEntry 2 }

    atmVplProfile-Id-Address-PhysicalAddress-ItemNumber	OBJECT-TYPE
	SYNTAX	INTEGER
	ACCESS	read-only
	STATUS	mandatory
	DESCRIPTION	"A number that specifies an addressable entity within the context of shelf and slot."
	::= { mibatmVplProfileEntry 3 }

    atmVplProfile-Id-Address-LogicalItem	OBJECT-TYPE
	SYNTAX	INTEGER
	ACCESS	read-only
	STATUS	mandatory
	DESCRIPTION	"A number that specifies an addressable logical entity within the context of a physical address."
	::= { mibatmVplProfileEntry 4 }

    atmVplProfile-Id-Vpi	OBJECT-TYPE
	SYNTAX	INTEGER
	ACCESS	read-only
	STATUS	mandatory
	DESCRIPTION	"The VPI number for this Vpl."
	::= { mibatmVplProfileEntry 5 }

    atmVplProfile-RxTrafficDesc	OBJECT-TYPE
	SYNTAX	INTEGER
	ACCESS	read-only
	STATUS	mandatory
	DESCRIPTION	"The ATM Traffic Descriptor index applied to the receive direction of the Vpl."
	::= { mibatmVplProfileEntry 6 }

    atmVplProfile-TxTrafficDesc	OBJECT-TYPE
	SYNTAX	INTEGER
	ACCESS	read-only
	STATUS	mandatory
	DESCRIPTION	"The ATM Traffic Descriptor index applied to the transmit direction of the Vpl."
	::= { mibatmVplProfileEntry 7 }

    atmVplProfile-McastType	OBJECT-TYPE
	SYNTAX	INTEGER {
		    p2p (2),
		    p2mproot (3),
		    p2mpleaf (4)
		}
	ACCESS	read-only
	STATUS	mandatory
	DESCRIPTION	"The connection topology type."
	::= { mibatmVplProfileEntry 8 }

    atmVplProfile-CallKind	OBJECT-TYPE
	SYNTAX	INTEGER {
		    pvc (2),
		    svcIncoming (3),
		    svcOutgoing (4),
		    spvcInitiator (5),
		    spvcTarget (6)
		}
	ACCESS	read-only
	STATUS	mandatory
	DESCRIPTION	"The use of call control."
	::= { mibatmVplProfileEntry 9 }

    atmVplProfile-Action-o	OBJECT-TYPE
	SYNTAX	INTEGER {
		    noAction (1),
		    createProfile (2),
		    deleteProfile (3)
		}
	ACCESS	read-write
	STATUS	mandatory
	DESCRIPTION	""
	::= { mibatmVplProfileEntry 10 }

END
