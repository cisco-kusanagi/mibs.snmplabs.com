-- *------------------------------------------------------------------
-- * ALTIGA-IP-STATS-MIB.my:  Altiga IP Statistics MIB.
-- *
-- * Altiga Networks was acquired by Cisco Systems on March 29, 2000
-- *
-- * Copyright (c) 2002 by Cisco Systems, Inc.
-- * All rights reserved.
-- *
-- *------------------------------------------------------------------

ALTIGA-IP-STATS-MIB DEFINITIONS ::= BEGIN

   IMPORTS
      MODULE-IDENTITY, OBJECT-TYPE, Integer32
         FROM SNMPv2-SMI
      OBJECT-GROUP, MODULE-COMPLIANCE
         FROM SNMPv2-CONF
      alStatsIp, alIpGroup
         FROM ALTIGA-MIB
      alIpMibModule
         FROM ALTIGA-GLOBAL-REG;

   altigaIpStatsMibModule MODULE-IDENTITY
      LAST-UPDATED   "200209051300Z"
      ORGANIZATION   "Cisco Systems, Inc."
      CONTACT-INFO
         "Cisco Systems
          170 W Tasman Drive
          San Jose, CA  95134
          USA

          Tel: +1 800 553-NETS
          E-mail: cs-cvpn3000@cisco.com"

      DESCRIPTION
         "The Altiga IP Statistics MIB models counters and objects that are
          of management interest for IP.
         
          Acronyms
          The following acronyms are used in this document:

            IP:         Internet Protocol

            LAN:        Local-Area Network 

            MIB:        Management Information Base

         "

        REVISION "200209051300Z"
        DESCRIPTION
                "Added module compliance."

        REVISION "200207100000Z"
        DESCRIPTION
                "Updated with new header"

      ::= { alIpMibModule 2 }

-- +++++++++++++++++++++++++++++++++++++++++++++++++++++++
-- MIB Objects
-- +++++++++++++++++++++++++++++++++++++++++++++++++++++++

alStatsIpGlobal   OBJECT IDENTIFIER ::= { alStatsIp 1 }

alIpInterfaceStatsTable OBJECT-TYPE
   SYNTAX      SEQUENCE OF AlIpInterfaceStatsEntry
   MAX-ACCESS  not-accessible  
   STATUS      current
   DESCRIPTION
      "IP Interface Statistics table."
   ::= { alStatsIpGlobal 1 }

alIpInterfaceStatsEntry OBJECT-TYPE
   SYNTAX      AlIpInterfaceStatsEntry
   MAX-ACCESS  not-accessible
   STATUS      current
   DESCRIPTION
      "An entry in the alIpInterfaceStatsTable."
   INDEX    { alIpInterfaceStatsIndex }
   ::= { alIpInterfaceStatsTable 1 }

AlIpInterfaceStatsEntry ::= SEQUENCE {
   alIpInterfaceStatsIndex         Integer32,
   alIpInterfaceStatsCurrentDuplex INTEGER
}

alIpInterfaceStatsIndex    OBJECT-TYPE
   SYNTAX         Integer32(0..2147483647)
   MAX-ACCESS     read-only
   STATUS         current
   DESCRIPTION
      "The ifIndex of this row."
   ::= { alIpInterfaceStatsEntry 1 }

alIpInterfaceStatsCurrentDuplex     OBJECT-TYPE
   SYNTAX         INTEGER {
                     full(2),
                     half(3)
                  }
   MAX-ACCESS     read-only
   STATUS         current
   DESCRIPTION
      "The current LAN duplex mode for this interface."
   ::= { alIpInterfaceStatsEntry 2 }

altigaIpStatsMibConformance OBJECT IDENTIFIER ::= { altigaIpStatsMibModule 1 }
altigaIpStatsMibCompliances OBJECT IDENTIFIER ::= { altigaIpStatsMibConformance 1 }

altigaIpStatsMibCompliance MODULE-COMPLIANCE
   STATUS         current
   DESCRIPTION
      "The compliance statement for agents which 
       implement the Altiga IP Statistics MIB."
   MODULE
   MANDATORY-GROUPS { 
      altigaIpStatsGroup
   }
   ::= { altigaIpStatsMibCompliances 1 }

altigaIpStatsGroup OBJECT-GROUP
   OBJECTS
   {
      alIpInterfaceStatsIndex,
                alIpInterfaceStatsCurrentDuplex
   }
   STATUS   current
   DESCRIPTION
          "The objects for Ip Statistics."
   ::= { alIpGroup 2 }

END
