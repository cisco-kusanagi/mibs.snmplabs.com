From hagiwara@sm.sony.co.jp Mon Feb 11 19:18:55 1991
To: jkrey@ISI.EDU
Cc: gray@salt.acc.com
Subject: Sony Extension MIB Document (revised version)
From: Takashi 'David' Hagiwara <Hagiwara@sm.sony.co.jp>
Organization: Super Micro Systems Gp., Sony Corporation, Tokyo, Japan
Reply-To: hagiwara@sm.sony.co.jp
Return-Receipt-To: hagiwara@sm.sony.co.jp
Date: Tue, 12 Feb 91 12:17:57 +0900
Sender: hagiwara@sm.sony.co.jp

Here I am sending you a revised Sony Ext. MIB document.
I will be happy that you will install this document as venera:mib/sony
Thanks to Marshall Rose and Gray of ACC, I got fixed.

					Takashi Hagiwara
					(Hagiwara@Sm.Sony.Co.Jp)
=======================================================================
SONY-MIB DEFINITIONS ::= BEGIN

-- Title:	SONY EXTENSION MIB
-- Date:	Nov. 15, 1990 
--		revised Feb. 12, 1991 
-- By:		Takashi Hagiwara, Supermicro Systems Gp. Sony Corp.
--		hagiwara@sm.sony.co.jp

IMPORTS
        enterprises, OBJECT-TYPE, NetworkAddress, IpAddress,
        Counter, Gauge, TimeTicks
        	FROM RFC1155-SMI
	DisplayString
		FROM RFC1158-MIB;

sony                    OBJECT IDENTIFIER ::= { enterprises 122 }

machines                OBJECT IDENTIFIER ::= { sony 1 }

system			OBJECT IDENTIFIER ::= { sony 2 }

mbuf			OBJECT IDENTIFIER ::= { system 1 }
rpc			OBJECT IDENTIFIER ::= { system 2 }
rpcClient		OBJECT IDENTIFIER ::= { rpc 1 }
rpcServer 		OBJECT IDENTIFIER ::= { rpc 2 }

nfs			OBJECT IDENTIFIER ::= { system 3 }
nfsClient		OBJECT IDENTIFIER ::= { nfs 1 }
nfsServer 		OBJECT IDENTIFIER ::= { nfs 2 }

cpu			OBJECT IDENTIFIER ::= { system 4 }

fileSystem		OBJECT IDENTIFIER ::= { system 5 }

interface		OBJECT IDENTIFIER ::= { sony 3 }

basicISDN		OBJECT IDENTIFIER ::= { interface 1 }

snmp			OBJECT IDENTIFIER ::= { sony 4 }


-- sony Machine Group

sonyMachineID OBJECT-TYPE
        SYNTAX  INTEGER
        ACCESS  read-only
        STATUS  mandatory
        ::= { machines 1}

sonyDomainName OBJECT-TYPE
        SYNTAX  DisplayString (SIZE(0..128))
        ACCESS  read-only
        STATUS  mandatory
        ::= { machines 2 }

sonyHostName OBJECT-TYPE
        SYNTAX  DisplayString (SIZE(0..128))
        ACCESS  read-only
        STATUS  mandatory
        ::= { machines 3 }

sonyVerName OBJECT-TYPE
        SYNTAX  DisplayString (SIZE(0..128))
        ACCESS  read-only
        STATUS  mandatory
        ::= { machines 4 }

-- sony system.mbuf group

mbufS OBJECT-TYPE
        SYNTAX  INTEGER
        ACCESS  read-only
        STATUS  mandatory
        ::= { mbuf 1 }

mbufClusters OBJECT-TYPE
        SYNTAX  INTEGER
        ACCESS  read-only
        STATUS  mandatory
        ::= { mbuf 2 }

mbufFreeClusters OBJECT-TYPE
        SYNTAX  INTEGER
        ACCESS  read-only
        STATUS  mandatory
        ::= { mbuf 3 }

mbufDrops OBJECT-TYPE
        SYNTAX  INTEGER
        ACCESS  read-only
        STATUS  mandatory
        ::= { mbuf 4 }

mbufWaits OBJECT-TYPE
        SYNTAX  INTEGER
        ACCESS  read-only
        STATUS  mandatory
        ::= { mbuf 5 }

mbufDrains OBJECT-TYPE
        SYNTAX  INTEGER
        ACCESS  read-only
        STATUS  mandatory
        ::= { mbuf 6 }

mbufType OBJECT-TYPE
        SYNTAX  MbufType
        ACCESS  not-accessible
        STATUS  mandatory
        ::= { mbuf 7 }

MbufType ::= SEQUENCE {
        mbufFree 
                INTEGER,
        mbufData
                INTEGER,
        mbufPcktHeader
                INTEGER,
        mbufSocket
                INTEGER,
        mbufRoutingTable
                INTEGER,
        mbufIMPHostTable
                INTEGER,
        mbufARPTable
                INTEGER,
        mbufSockname
                INTEGER,
        mbufZombie
                INTEGER,
        mbufSockOptions
                INTEGER,
        mbufFragHeader
                INTEGER,
        mbufRights
                INTEGER,
        mbufIfaddr
                INTEGER
}

mbufFree OBJECT-TYPE
        SYNTAX  INTEGER
        ACCESS  read-only
        STATUS  mandatory
        ::= { mbufType 1 }

mbufData OBJECT-TYPE
        SYNTAX  INTEGER
        ACCESS  read-only
        STATUS  mandatory
        ::= { mbufType 2 }

mbufPcktHeader OBJECT-TYPE
        SYNTAX  INTEGER
        ACCESS  read-only
        STATUS  mandatory
        ::= { mbufType 3 }

mbufSocket OBJECT-TYPE
        SYNTAX  INTEGER
        ACCESS  read-only
        STATUS  mandatory
        ::= { mbufType 4 }


mbufPCB OBJECT-TYPE
        SYNTAX  INTEGER
        ACCESS  read-only
        STATUS  mandatory
        ::= { mbufType 5 }

mbufRoutingTable OBJECT-TYPE
        SYNTAX  INTEGER
        ACCESS  read-only
        STATUS  mandatory
        ::= { mbufType 6 }

mbufIMPHostTable OBJECT-TYPE
        SYNTAX  INTEGER
        ACCESS  read-only
        STATUS  mandatory
        ::= { mbufType 7 }

mbufARPTable OBJECT-TYPE
        SYNTAX  INTEGER
        ACCESS  read-only
        STATUS  mandatory
        ::= { mbufType 8 }

mbufSockname OBJECT-TYPE
        SYNTAX  INTEGER
        ACCESS  read-only
        STATUS  mandatory
        ::= { mbufType 9 }

mbufZombie OBJECT-TYPE
        SYNTAX  INTEGER
        ACCESS  read-only
        STATUS  mandatory
        ::= { mbufType 10 }

mbufSockOptions OBJECT-TYPE
        SYNTAX  INTEGER
        ACCESS  read-only
        STATUS  mandatory
        ::= { mbufType 11 }

mbufFragHeader OBJECT-TYPE
        SYNTAX  INTEGER
        ACCESS  read-only
        STATUS  mandatory
        ::= { mbufType 12 }

mbufRights OBJECT-TYPE
        SYNTAX  INTEGER
        ACCESS  read-only
        STATUS  mandatory
        ::= { mbufType 13 }

mbufIfaddr OBJECT-TYPE
        SYNTAX  INTEGER
        ACCESS  read-only
        STATUS  mandatory
        ::= { mbufType 14 }

-- sony system.rpc.Client group

rpcCalls OBJECT-TYPE
        SYNTAX  INTEGER
        ACCESS  read-only
        STATUS  mandatory
        ::= { rpcClient 1 }

rpcBadCalls OBJECT-TYPE
        SYNTAX  INTEGER
        ACCESS  read-only
        STATUS  mandatory
        ::= { rpcClient 2 }

rpcReTrans OBJECT-TYPE
        SYNTAX  INTEGER
        ACCESS  read-only
        STATUS  mandatory
        ::= { rpcClient 3 }

rpcBadXids OBJECT-TYPE
        SYNTAX  INTEGER
        ACCESS  read-only
        STATUS  mandatory
        ::= { rpcClient 4 }

rpcTimeouts OBJECT-TYPE
        SYNTAX  INTEGER
        ACCESS  read-only
        STATUS  mandatory
        ::= { rpcClient 5 }

rpcWaits OBJECT-TYPE
        SYNTAX  INTEGER
        ACCESS  read-only
        STATUS  mandatory
        ::= { rpcClient 6 }

rpcNewCreds OBJECT-TYPE
        SYNTAX  INTEGER
        ACCESS  read-only
        STATUS  mandatory
        ::= { rpcClient 7 }

-- sony system.rpc.Server group

rpcCalls OBJECT-TYPE
        SYNTAX  INTEGER
        ACCESS  read-only
        STATUS  mandatory
        ::= { rpcServer 1 }

rcpBadCalls OBJECT-TYPE
        SYNTAX  INTEGER
        ACCESS  read-only
        STATUS  mandatory
        ::= { rpcServer 2 }

rpcNULLReceive OBJECT-TYPE
        SYNTAX  INTEGER
        ACCESS  read-only
        STATUS  mandatory
        ::= { rpcServer 3 }

rpcBadLen OBJECT-TYPE
        SYNTAX  INTEGER
        ACCESS  read-only
        STATUS  mandatory
        ::= { rpcServer 4 }

rpcXDRCall OBJECT-TYPE
        SYNTAX  INTEGER
        ACCESS  read-only
        STATUS  mandatory
        ::= { rpcServer 5 }

--sony system.nfs.Client group

sleeps OBJECT-TYPE
        SYNTAX  INTEGER
        ACCESS  read-only
        STATUS  mandatory
        ::= { nfsClient 1 }

getReq OBJECT-TYPE
        SYNTAX  INTEGER
        ACCESS  read-only
        STATUS  mandatory
        ::= { nfsClient 2 }

numberCalls OBJECT-TYPE
        SYNTAX  INTEGER
        ACCESS  read-only
        STATUS  mandatory
        ::= { nfsClient 3 }

badCalls OBJECT-TYPE
        SYNTAX  INTEGER
        ACCESS  read-only
        STATUS  mandatory
        ::= { nfsClient 4 }

nfsReqClient OBJECT-TYPE
        SYNTAX  NfsReqEntry
        ACCESS  not-accessible
        STATUS  mandatory
        ::= { nfsClient 5 }

NfsReqEntry ::= SEQUENCE {
        nullFuncReq 
                INTEGER,
        getAttrReq
                INTEGER,
        setAttrReq
                INTEGER,
        rootReq
                INTEGER,
        lookupReq
                INTEGER,
        readLinkReq
                INTEGER,
        readReq
                INTEGER,
        writeCacheReq
                INTEGER,
        writeReq
                INTEGER,
        createReq
                INTEGER,
        removeReq
                INTEGER,
        renameReq
                INTEGER,
        linkReq
                INTEGER,
        symlinkReq
                INTEGER,
        mkDirReq
                INTEGER,
        rmDirReq
                INTEGER,
        readDirReq
                INTEGER,
        fsstatReq
                INTEGER
	}

nullFuncReq OBJECT-TYPE
        SYNTAX  INTEGER
        ACCESS  read-only
        STATUS  mandatory
        ::= { nfsReqClient 1 }

getAttrReq OBJECT-TYPE
        SYNTAX  INTEGER
        ACCESS  read-only
        STATUS  mandatory
        ::= { nfsReqClient 2 }

setAttrReq OBJECT-TYPE
        SYNTAX  INTEGER
        ACCESS  read-only
        STATUS  mandatory
        ::= { nfsReqClient 3 }

rootReq OBJECT-TYPE
        SYNTAX  INTEGER
        ACCESS  read-only
        STATUS  mandatory
        ::= { nfsReqClient 4 }

lookupReq OBJECT-TYPE
        SYNTAX  INTEGER
        ACCESS  read-only
        STATUS  mandatory
        ::= { nfsReqClient 5 }

readLinkReq OBJECT-TYPE
        SYNTAX  INTEGER
        ACCESS  read-only
        STATUS  mandatory
        ::= { nfsReqClient 6 }

readReq OBJECT-TYPE
        SYNTAX  INTEGER
        ACCESS  read-only
        STATUS  mandatory
        ::= { nfsReqClient 7 }

writeCacheReq OBJECT-TYPE
        SYNTAX  INTEGER
        ACCESS  read-only
        STATUS  mandatory
        ::= { nfsReqClient 8 }

writeReq OBJECT-TYPE
        SYNTAX  INTEGER
        ACCESS  read-only
        STATUS  mandatory
        ::= { nfsReqClient 9 }

createReq OBJECT-TYPE
        SYNTAX  INTEGER
        ACCESS  read-only
        STATUS  mandatory
        ::= { nfsReqClient 10 }

removeReq OBJECT-TYPE
        SYNTAX  INTEGER
        ACCESS  read-only
        STATUS  mandatory
        ::= { nfsReqClient 11 }


renameReq OBJECT-TYPE
        SYNTAX  INTEGER
        ACCESS  read-only
        STATUS  mandatory
        ::= { nfsReqClient 12 }

linkReq OBJECT-TYPE
        SYNTAX  INTEGER
        ACCESS  read-only
        STATUS  mandatory
        ::= { nfsReqClient 13 }

symLinkReq OBJECT-TYPE
        SYNTAX  INTEGER
        ACCESS  read-only
        STATUS  mandatory
        ::= { nfsReqClient 14 }

mkDirReq OBJECT-TYPE
        SYNTAX  INTEGER
        ACCESS  read-only
        STATUS  mandatory
        ::= { nfsReqClient 15 }

rmDirReq OBJECT-TYPE
        SYNTAX  INTEGER
        ACCESS  read-only
        STATUS  mandatory
        ::= { nfsReqClient 16 }

readDirReq OBJECT-TYPE
        SYNTAX  INTEGER
        ACCESS  read-only
        STATUS  mandatory
        ::= { nfsReqClient 17 }

fsstatReq OBJECT-TYPE
        SYNTAX  INTEGER
        ACCESS  read-only
        STATUS  mandatory
        ::= { nfsReqClient 18 }

--sony system.nfs.Server group

numberCalls OBJECT-TYPE
        SYNTAX  INTEGER
        ACCESS  read-only
        STATUS  mandatory
        ::= { nfsServer 1 }

badCalls OBJECT-TYPE
        SYNTAX  INTEGER
        ACCESS  read-only
        STATUS  mandatory
        ::= { nfsServer 2 }

nfsReqServer OBJECT-TYPE
        SYNTAX  NFSReqEntry
        ACCESS  not-accessible
        STATUS  mandatory
        ::= { nfsServer 3 }

NFSReqEntry ::= SEQUENCE {
        nullFuncReq 
                INTEGER,
        getAttrReq
                INTEGER,
        setAttrReq
                INTEGER,
        rootReq
                INTEGER,
        lookupReq
                INTEGER,
        readLinkReq
                INTEGER,
        readReq
                INTEGER,
        writeCacheReq
                INTEGER,
        writeReq
                INTEGER,
        createReq
                INTEGER,
        removeReq
                INTEGER,
        renameReq
                INTEGER,
        linkReq
                INTEGER,
        symlinkReq
                INTEGER,
        mkDirReq
                INTEGER,
        rmDirReq
                INTEGER,
        readDirReq
                INTEGER,
        fsstatReq
                INTEGER
	}

nullFuncReq OBJECT-TYPE
        SYNTAX  INTEGER
        ACCESS  read-only
        STATUS  mandatory
        ::= { nfsReqServer 1 }

getAttrReq OBJECT-TYPE
        SYNTAX  INTEGER
        ACCESS  read-only
        STATUS  mandatory
        ::= { nfsReqServer 2 }

setAttrReq OBJECT-TYPE
        SYNTAX  INTEGER
        ACCESS  read-only
        STATUS  mandatory
        ::= { nfsReqServer 3 }

rootReq OBJECT-TYPE
        SYNTAX  INTEGER
        ACCESS  read-only
        STATUS  mandatory
        ::= { nfsReqServer 4 }

lookupReq OBJECT-TYPE
        SYNTAX  INTEGER
        ACCESS  read-only
        STATUS  mandatory
        ::= { nfsReqServer 5 }

readLinkReq OBJECT-TYPE
        SYNTAX  INTEGER
        ACCESS  read-only
        STATUS  mandatory
        ::= { nfsReqServer 6 }

readReq OBJECT-TYPE
        SYNTAX  INTEGER
        ACCESS  read-only
        STATUS  mandatory
        ::= { nfsReqServer 7 }

writeCacheReq OBJECT-TYPE
        SYNTAX  INTEGER
        ACCESS  read-only
        STATUS  mandatory
        ::= { nfsReqServer 8 }

writeReq OBJECT-TYPE
        SYNTAX  INTEGER
        ACCESS  read-only
        STATUS  mandatory
        ::= { nfsReqServer 9 }

createReq OBJECT-TYPE
        SYNTAX  INTEGER
        ACCESS  read-only
        STATUS  mandatory
        ::= { nfsReqServer 10 }

removeReq OBJECT-TYPE
        SYNTAX  INTEGER
        ACCESS  read-only
        STATUS  mandatory
        ::= { nfsReqServer 11 }

renameReq OBJECT-TYPE
        SYNTAX  INTEGER
        ACCESS  read-only
        STATUS  mandatory
        ::= { nfsReqServer 12 }

linkReq OBJECT-TYPE
        SYNTAX  INTEGER
        ACCESS  read-only
        STATUS  mandatory
        ::= { nfsReqServer 13 }

symLinkReq OBJECT-TYPE
        SYNTAX  INTEGER
        ACCESS  read-only
        STATUS  mandatory
        ::= { nfsReqServer 14 }

mkDirReq OBJECT-TYPE
        SYNTAX  INTEGER
        ACCESS  read-only
        STATUS  mandatory
        ::= { nfsReqServer 15 }

rmDirReq OBJECT-TYPE
        SYNTAX  INTEGER
        ACCESS  read-only
        STATUS  mandatory
        ::= { nfsReqServer 16 }

readDirReq OBJECT-TYPE
        SYNTAX  INTEGER
        ACCESS  read-only
        STATUS  mandatory
        ::= { nfsReqServer 17 }

fsstatReq OBJECT-TYPE
        SYNTAX  INTEGER
        ACCESS  read-only
        STATUS  mandatory
        ::= { nfsReqServer 18 }

--sony system.cpu group

cpuUser OBJECT-TYPE
        SYNTAX  INTEGER
        ACCESS  read-only
        STATUS  mandatory
        ::= { cpu 1 }

cpuNice OBJECT-TYPE
        SYNTAX  INTEGER
        ACCESS  read-only
        STATUS  mandatory
        ::= { cpu 2 }

cpuSystem OBJECT-TYPE
        SYNTAX  INTEGER
        ACCESS  read-only
        STATUS  mandatory
        ::= { cpu 3 }

cpuIdle OBJECT-TYPE
        SYNTAX  INTEGER
        ACCESS  read-only
        STATUS  mandatory
        ::= { cpu 4 }

-- sony system.fileSystem group

fsName OBJECT-TYPE
        SYNTAX  DisplayString (SIZE(0..128))
        ACCESS  read-only
        STATUS  mandatory
        ::= { fileSystem 1 }

fsMountedDir OBJECT-TYPE
        SYNTAX  DisplayString (SIZE(0..128))
        ACCESS  read-only
        STATUS  mandatory
        ::= { fileSystem 2 }

fsCapacity OBJECT-TYPE
        SYNTAX  INTEGER
        ACCESS  read-only
        STATUS  mandatory
        ::= { fileSystem 3 }

fsInodeUsage OBJECT-TYPE
        SYNTAX  INTEGER
        ACCESS  read-only
        STATUS  mandatory
        ::= { fileSystem 4 }

-- sony interface.basicISDN group

boardStatus OBJECT-TYPE
        SYNTAX  INTEGER
        ACCESS  read-only
        STATUS  mandatory
        ::= { basicISDN 1 }

callInfo OBJECT-TYPE
        SYNTAX  CallInfoTable
        ACCESS  not-accessible
        STATUS  mandatory
        ::= { basicISDN 2 }

CallInfoTable::= SEQUENCE {
        peerAddress
        	DisplayString (SIZE(0..128)),
        peerSubAddress
        	DisplayString (SIZE(0..128)),
        lineState
                INTEGER
	}

peerAddress OBJECT-TYPE
        SYNTAX  DisplayString (SIZE(0..128))
        ACCESS  read-write
        STATUS  mandatory
        ::= { callInfo 1 }

peerSubAddress OBJECT-TYPE
        SYNTAX  DisplayString (SIZE(0..128))
        ACCESS  read-write
        STATUS  mandatory
        ::= { callInfo 2 }

lineState OBJECT-TYPE
        SYNTAX  INTEGER
        ACCESS  read-write
        STATUS  mandatory
        ::= { callInfo 3 }

-- sony snmp group

snmpInputPkts OBJECT-TYPE
        SYNTAX  INTEGER
        ACCESS  read-only
        STATUS  mandatory
        ::= { snmp 1 }

snmpOutputPkts OBJECT-TYPE
        SYNTAX  INTEGER
        ACCESS  read-only
        STATUS  mandatory
        ::= { snmp 2 }

snmpInREQComm OBJECT-TYPE
        SYNTAX  INTEGER
        ACCESS  read-only
        STATUS  mandatory
        ::= { snmp 3 }

snmpInNXTComm OBJECT-TYPE
        SYNTAX  INTEGER
        ACCESS  read-only
        STATUS  mandatory
        ::= { snmp 4 }

snmpInRSPComm OBJECT-TYPE
        SYNTAX  INTEGER
        ACCESS  read-only
        STATUS  mandatory
        ::= { snmp 5 }

snmpInSETComm OBJECT-TYPE
        SYNTAX  INTEGER
        ACCESS  read-only
        STATUS  mandatory
        ::= { snmp 6 }

snmpInTrpcomm OBJECT-TYPE
        SYNTAX  INTEGER
        ACCESS  read-only
        STATUS  mandatory
        ::= { snmp 7 }

snmpOutREQComm OBJECT-TYPE
        SYNTAX  INTEGER
        ACCESS  read-only
        STATUS  mandatory
        ::= { snmp 8 }

snmpOutNXTComm OBJECT-TYPE
        SYNTAX  INTEGER
        ACCESS  read-only
        STATUS  mandatory
        ::= { snmp 9 }

snmpOutRSPComm OBJECT-TYPE
        SYNTAX  INTEGER
        ACCESS  read-only
        STATUS  mandatory
        ::= { snmp 10 }

snmpOutSETComm OBJECT-TYPE
        SYNTAX  INTEGER
        ACCESS  read-only
        STATUS  mandatory
        ::= { snmp 11 }

snmpOutTrpcomm OBJECT-TYPE
        SYNTAX  INTEGER
        ACCESS  read-only
        STATUS  mandatory
        ::= { snmp 12 }

snmpInputErrs OBJECT-TYPE
        SYNTAX  INTEGER
        ACCESS  read-only
        STATUS  mandatory
        ::= { snmp 13 }

snmpOutputErrs OBJECT-TYPE
        SYNTAX  INTEGER
        ACCESS  read-only
        STATUS  mandatory
        ::= { snmp 14 }

snmpASNParseErrs OBJECT-TYPE
        SYNTAX  INTEGER
        ACCESS  read-only
        STATUS  mandatory
        ::= { snmp 15 }

snmpBADCommunity OBJECT-TYPE
        SYNTAX  INTEGER
        ACCESS  read-only
        STATUS  mandatory
        ::= { snmp 16 }

snmpReplyProcErrs OBJECT-TYPE
        SYNTAX  INTEGER
        ACCESS  read-only
        STATUS  mandatory
        ::= { snmp 17 }

snmpMsgTooBig OBJECT-TYPE
        SYNTAX  INTEGER
        ACCESS  read-only
        STATUS  mandatory
        ::= { snmp 18 }

snmpMsgBadType OBJECT-TYPE
        SYNTAX  INTEGER
        ACCESS  read-only
        STATUS  mandatory
        ::= { snmp 19 }

snmpNumberREQvars OBJECT-TYPE
        SYNTAX  INTEGER
        ACCESS  read-only
        STATUS  mandatory
        ::= { snmp 20 }

snmpNumberSETvars OBJECT-TYPE
        SYNTAX  INTEGER
        ACCESS  read-only
        STATUS  mandatory
        ::= { snmp 21 }
END

=======================================================================
