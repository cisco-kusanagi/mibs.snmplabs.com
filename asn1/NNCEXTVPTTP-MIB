-- file: NncExtVPTTP.mib
--
-- description:
--   This file contains the Virtual Path Trail Termination Point (Vpttp) MIB
--   implementation for Alcatel CID (Carrier Internetworking Division) equipment. 
--
--
-- history:
-- $Log: 2.NncExtVPTTP.mib,v $
-- Revision 1.1.1.2  2000/10/03 14:37:32  sbasinsk
-- 31A1564: Merge from cr_kan_pm_43 to ctl (new file)
--
-- Revision 1.1.1.1.1.2  2000/08/31 14:03:41  atsang
-- 31A1407: Added new MIB for SNMP PVC feature
--
-- %%history-start%%
--  31A1407 / 2000.07.10 / ipandher   / creation
--  31A1407 / 2000.07.21 / ipandher   / updated after review

-- %%history-end%%
--
-- Copyright 2000 Alcatel Networks Corporation.  All Rights Reserved
--------------------------------------------------------------------------------

NNCEXTVPTTP-MIB DEFINITIONS ::= BEGIN

   IMPORTS
       MODULE-IDENTITY, OBJECT-TYPE,
       NOTIFICATION-TYPE                        FROM SNMPv2-SMI
       ifIndex                                  FROM IF-MIB
       atmVclVpi                                FROM ATM-MIB
       MODULE-COMPLIANCE, OBJECT-GROUP          FROM SNMPv2-CONF
       nncExtensions                            FROM NNCGNI0001-SMI;

   nncExtVpttp MODULE-IDENTITY
     LAST-UPDATED    "200007211126Z"
     ORGANIZATION    "Alcatel Networks Corporation"
     CONTACT-INFO
                       "Alcatel CID
                        Postal: 600 March Road
                        Kanata, Ontario
                        Canada K2K 2E6
 
                        Phone:  +1 613 591 3600
                        Fax:    +1 613 591 3680"


     DESCRIPTION     
       "This module contains Alcatel's proprietary MIB definition for 
       configuration of VP Trail Termination Points. This support is
       is provided via nncCrVpTrailTerminationPointTable. 

      Some abreviations:


        VCI/Vci/vci: Virtual channel identifier
        VCL/Vcl/vcl: Virtual channel link
        VPI/Vpi/vpi: Virtual path identifier
        VPL/Vpl/Vpl: Virtual path link
        VPTTP: Virtual path trail termination point

      "
                        
       ::= { nncExtensions 80 }
 
   nncExtVpttpObjects OBJECT IDENTIFIER       ::=    { nncExtVpttp 1 }
   -- nncExtVpttpTraps   OBJECT IDENTIFIER    ::=    { nncExtVpttp 2 }
   nncExtVpttpGroups OBJECT IDENTIFIER        ::=    { nncExtVpttp 3 }
   nncExtVpttpCompliances OBJECT IDENTIFIER   ::=    { nncExtVpttp 4 }

   ---------------------------------------------------------------------------
   -- Table Definition
   --
   -- nncCrVpTrailTerminationPointTable (VP Trail Termination Point Table)
   --
   -- This table contains all information used to manage VP Trail
   --  Termination Points.
   --
   ---------------------------------------------------------------------------
 
   nncCrVpTrailTerminationPointTable   OBJECT-TYPE
     SYNTAX        SEQUENCE OF NncVpTrailTerminationPointEntry
     MAX-ACCESS    not-accessible
     STATUS        current
     DESCRIPTION   "nncCrVpTrailTerminationPointTable contains all the
                    objects used to configure VP Trail Termination Point."
 
     ::= { nncExtVpttpObjects 1 }
 
   nncCrVpTrailTerminationPointEntry OBJECT-TYPE
     SYNTAX        NncVpTrailTerminationPointEntry
     MAX-ACCESS    not-accessible
     STATUS        current
     DESCRIPTION   
                      "An entry of nncCrVpTrailTerminationPointTable"
     INDEX         {ifIndex, atmVclVpi} 
     ::= { nncCrVpTrailTerminationPointTable 1 }
 
   NncVpTrailTerminationPointEntry ::= SEQUENCE{
     nncCrVpTrailTerminationPoint     INTEGER
   }

   nncCrVpTrailTerminationPoint OBJECT-TYPE
     SYNTAX     INTEGER { 
                          disabled (0),            
                          enabledWithNoAlarms (1), -- Prevents VP-AIS and VP-RDI alarms 
                                                   -- to be raised on the VPI.
                          enabledWithAlarms (2)    -- Allows VP-AIS and VP-RDI alarms
                                                   -- to be raised on the VPI.
                        }
     MAX-ACCESS read-write
     STATUS     current
     DESCRIPTION
       " This object is used to configure a VP Trail Termination Point. 
         If it is enabled, the VP will be marked as VP TTP"
  
     ::= {  nncCrVpTrailTerminationPointEntry 1 }



   nncCrVpTrailTerminationPointGroup OBJECT-GROUP
     OBJECTS {
       nncCrVpTrailTerminationPoint
     }
     STATUS      current
     DESCRIPTION
         "Common MIB objects for querying a PVC/SPVC Vp Trail Termination Point
          on Alcatel CID equipment"
     ::= { nncExtVpttpGroups 1 }

   ------------------------------------------------------------------
   -- Compliance Statements
   ------------------------------------------------------------------
   nncVpttpCompliance     MODULE-COMPLIANCE
     STATUS     current
     DESCRIPTION 
           "The compliance statement for Alcatel CID PVC/SPVC Vpttp MIB
             implementation."
     MODULE
       MANDATORY-GROUPS {
         nncCrVpTrailTerminationPointGroup
       }
     ::= { nncExtVpttpCompliances 1 }

END -- DEFINITION OF NNCEXTVPTTP-MIB

-------------------------------------------------------------------------------
-------------------------------------------------------------------------------
--      Review Minutes
-------------------------------------------------------------------------------
--
--------------------------------------------------------------------------------
--      MINUTES-BEGIN
--              REVIEW-DATE  "2000.07.19"
--              BODY  "
--
--      
--      TO:     Chris Anastasiadis, Bruce Brown, Navdeep Dhillon*
--              Andrew Duggan*, Kendall Harvey, Shawn Lips*
--              David Maxwell, Derek Puddicombe, Jack Sinclair*
--              Bruce Slack, John Sullivan*, Greg Winklemaier*
--              George Yu*, Iqbal Pandher*
-- 
--      FROM:   George Yu*
--
--
--      A meeting was held on 2000.07.19 to review NncExtVPTTP.mib.
--      Attendees are marked with * in the TO and CC lists above.
--
--      Outcome
--
--      It was the consensus of the review team that this file is 
--      acceptable with the indicated modifications
--
--      Actions:
--              A1 - Iqbal Pandher to update NncExtVPTTP.mib as described in Decision D1.
--
--                   Response              Status               Closed
--                   2000.07.20        Updated NncExtVPTTP.mib according to D1.
--
--      Decisions:
--      D1 -    NncExtVPTTP.mib shall be updated as follows:
--              a. Line 5 - Correct typos
--
--      "
--
--      END-MINUTES
