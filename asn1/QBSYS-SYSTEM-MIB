--	Quantum Bridge System Management Information Base
--	Version 1.0.0
--	June 12, 1999
--
--	Quantum Bridge Corporation
--	One High Street
--	North Andover, MA 01845
--	(978) 688-9100
--
---------------------------------------------------------------------------------------
--  05/15/01 -   mvaysman - added new objects for Release 2.2 and
--		 Release 3.0 Beta
--  
--  05/15/2001 - bfardy - add scalars for qbSysAlarmHistory, EventHistory and global LastIndex.
--
--  05/11/2001 - dqin - add qbSysSwAccepted (cr5081).
--
--  05/07/2001 - bfardy - modify discrete input table by adding state object(cr2898).
--						removed 'resetToDefault' as choice from enumeration of qbSysIotAdminStatus
--						to fix CR3550.
--
--  04/19/2001 - dqin: extend qbSysModuleType to include all new cards added to the system.
--                     It mapps from product code for each card type rather than the QB500 
--                     IOAS internal module type.
--                     
--  03/20/2001 - mvaysman: added qbSysPortBwSharing, qbSysTestLeds scalars
--  objects and qbSysModuleLeds 
--
--  03/14/2001 - mvaysman Added new objects to qbSysIotTable and new iot type(qbIotSigFmt). 
-- 
--  03/09/2001 - dqin: added enhSwitchProc in the SYNTAX of
--	         qbSysModuleType
--
--  02/28/2001 - dqin: Added qbSysFeatureKeys under qbSysGeneralGroup
--                     to support view the configured feature keys.
--
--  02/26/2001 - dqin: Added qbSysModuleProductName in qbSysModuleTable and
--                     qbSysIotProductName in qbSysIotEntry. 
--  12/13/2000 Change ServiceAffecting enumeration to match sw
--
--  12/12/2000 Changed qbSysModuleOperStatus enumeration
--  12/07/2000  Added service affecting object to qbSysNotificationHistory and related traps.
--
--  11/26/2000  Added a separate protoection tabele(qbSysModuleApsTable). 
--
--  08/28/2000  Added qbSysUnsolicitedEvent and qbSysConfiguration Event, plus the 
--				qbSysNotificationHistory Table.
-- 
--	08/16/2000	Added qbSysResetVersion Object to File System Group to support syscon and
--					system reset via SNMP 
--
-- 08/10/2000			Updated the date of the last changes
--				and a couple minor changes
--
-- 08/07/2000			Made Module Table AdminStatus read-write
--
-- 07/19/2000	Added qbSysIotFileTable to support remote access of IOT files as wells
--				remote download and file accept.
--
-- Release 2:			Added In-band management objects
--
-- 06/15/2000			Fixed led comments and added new traps.
--
-- 06/04/2000			Changed statuses of some objects tho
--				reflect their current states 
--    
-- 05/24/2000			Removed SNMP Read and Write Community string objects, renamed  
--				qbSysEventEntry qbSysEventHistoryEntry. Various minor editorial
--				and typo changes.
--
-- 05/22/2000                   Added qbSysAutonomousStatus,
--				qbSysSnmpRevision, and qbSysModuleLedStatus;
--
-- 05/15/2000                   Changed event and alarm description tables,
--				and added the qbSysIotSerialStr objects
--
-- 05/14/2000                   added the qbSysIotDs1LineCoding object 
--				to qbSysIotTable.
--
-- 03/20/2000                   Changed qbSysModuleType and qbSysPortType objects.
--
-- 03/16/2000                   Merged PON_management.
--			        Made qbSysIoasDwsIfIndex read-write
--		                Modified MIB to accomodate PON management	
--
-- 03/10/2000			Made changes in the Input Discrete table
--
-- 02/18/2000			Added the alarmAction object to the
--				alarm and alarmHistory
--				table. Introduced a new trap type qbSysAlarm
--
-- 01/22/2000			Added defaults for the trap table and
--				community strings
--
--  01/011/2000			Modified ModuleInfoTable and added
--				slot definition.
--
--  01/07/2000			Added Alarm Identifier Table
--
--  12/28/99			Added Alarm History and AlarmTable				
--
--  12/21/99			Changed the index of qbSysIotTable. Used 
--				serial number as an index.
--
--  10/25/99 - mvaysman 	Modified qbSysTransferTable, removed
--                              some objects from the event group. 
--	
--  10/21/99 - mvaysman 	Moved wan traps from qbdws by qbsystem 
--				mib, added flasg add/remove traps, portLoopbackConfig.
--
--  10/20/99                    Removed qbSysSubsystemTable, and qbSysApplTable groups that
--                              were not planned for Beta release. Replaced RT and HUB.
--
--  10/20/99 - mvaysman 	Removed qbSysStorageTable,
--                              qbSysSubsystemTable, and qbSysApplTable groups that
--                              are not planned Beta release. Replaced RT and HUB.
--
--  10/20/99 - mvaysman 	Removed qbSysModuleConfigTable and
--                              added reset to default objects. 
--
--  07/23/99 - mvaysman 	Added qbSysModuleConfigTable, qbSysDiscreteInputTable, 
--	                        qbSysBootImageTable  and some other objects.
--
--  06/24/99 - mvaysman 	Replaced RT with IOT, changed qbSysEventIdFilterTable to
--				qbSysEventIdTable,  then removed some incorrect trap definitions.	
--  04/15/99 - mvaysman    	Originally created
--
----------------------------------------------------------------------------------------
--
	QBSYS-SYSTEM-MIB DEFINITIONS ::= BEGIN

	IMPORTS 
    	MODULE-IDENTITY, OBJECT-TYPE, NOTIFICATION-TYPE, Integer32, 
    	IpAddress, Gauge32, Counter32, Unsigned32, TimeTicks
        	FROM SNMPv2-SMI
    	TEXTUAL-CONVENTION,  DisplayString, RowStatus, TruthValue
        	FROM SNMPv2-TC
    	MODULE-COMPLIANCE, OBJECT-GROUP
        	FROM SNMPv2-CONF
    	qbMibs
        	FROM QUANTUMBRIDGE-REG
    	InterfaceIndex, InterfaceIndexOrZero, ifIndex
		FROM IF-MIB
    	;

    qbSysMIB MODULE-IDENTITY
     	LAST-UPDATED "0103090855Z" -- Mar 9,2001
    	ORGANIZATION "Quantum Bridge Communications, Inc."
    	CONTACT-INFO
        	"mvaysman@quantumbridge.com"
    	DESCRIPTION
        	"This module defines objects for the management of Quantum Bridge devices."
    	::= {  qbMibs 2 } 
 
-- 
-- Overview of Quantum Bridge System MIB
--
-- The Quantum Bridge System MIB defines system level MIB  
-- objects that present a complete view of the Quantum Bridge 
-- IOAS and attached IOTs resources (i.e. chassis, card, port, interface, 
-- software, and hardware level information).
-- 
-- Top-level organization of the MIB

	qbSysObjects          OBJECT IDENTIFIER ::= { qbSysMIB 1 }
	qbSysNotifications    OBJECT IDENTIFIER ::= { qbSysMIB 2 }
	qbSysConformance      OBJECT IDENTIFIER ::= { qbSysMIB 3 }

-- ****************************************************************
-- Textual Conventions
-- ****************************************************************

	DateAndTimeForm ::= TEXTUAL-CONVENTION
    	STATUS      current
    	DESCRIPTION
        	"A Date/Time string  in the format:

                	 'mm/dd/yyyy hh:mm:ss:tt'
  
         	where mm - month, dd - day, yyyy - year,
               	hh - hour, mm - minutes, ss - seconds,
               	tt - ticks."
    	SYNTAX    DisplayString (SIZE (0..22))


	QbStorageType ::= TEXTUAL-CONVENTION
    	STATUS      obsolete
    	DESCRIPTION
        	"Not used."
    	SYNTAX      INTEGER {
        	        network(1),
                	bootflash(2),
                    flash(3),
                    ram(4),
                    nvram(5)
                }

   QbFileType ::= TEXTUAL-CONVENTION
   	STATUS      obsolete
    	DESCRIPTION
        	"Not used."
    	SYNTAX      INTEGER {
        	        image(1),
                	config(2),
                    dump(3),
                    eventLog(4),
		   			diags(5)
                }

    QbFileImageType ::= TEXTUAL-CONVENTION
    	STATUS      obsolete
    	DESCRIPTION
        	"Not used."
    	SYNTAX      INTEGER {
					switchImage(1),
               		systemImage(2),
                    iotImage(3)
                	}

    QbTransferStatus ::= TEXTUAL-CONVENTION
    	STATUS      obsolete
    	DESCRIPTION
        	"not used."
    	SYNTAX      INTEGER {
                    fileNotFound(1),
                    accessViolation(2),
                    notEnoughSpace(3),
                    illegalOperation(4),
                    unknownTransferID(5),
                    fileAlreadyExists(6),
                    noUser(7),
                    generalError(8),
                    incompatibleFile(9),
                    noResponseFromServer(10),
                    checksumError(11),
                    aborted(12),
                    statusUnknown(13),
                    success(14),
                    inProgress(15),
                    alreadyRunning(16)
                }
    
    QbSysApplId ::= TEXTUAL-CONVENTION
	STATUS      obsolete
    	DESCRIPTION
        	"Not used."
    	SYNTAX      INTEGER {
        	        www(1),
                	telnet(2),
                    nfs(3),
                    snmp(4)
		}


    ProtectionMode ::= TEXTUAL-CONVENTION
        STATUS current
        DESCRIPTION
                "The protection status of a module.

		The  protection status of a module is part of the state of
		the protection machine (i.e., the hardware and software
		that implements protection). The protection mode of
		all the modules included in a protection group(pair) together represent
		the state of the protection machine for that
		protection group. The inputs to the protection state machine
		that cause the redundancy mode of a module to transition
		from one value to another are events such as module
		failure, card removal, user configuration, etc.
		The user can  force the redundancy machine transition to a desired state.
		
        The following values typically would be written:

		protection(1) - Creates a protection group that consists of two Main or Switch modules.	
		 
		lockout(3) - Make this module an active member of the protection group and doesn't 
		allow this state to be changed . This option is applicable only to the WAN module.  

		force(4)  - This module is forced to become a standby member of the protection group.
		This option is applicable only to the WAN the swich
		pack module. 

		manual(5)  - Makes this module a standby member of the protection group. This option is 
		applicable only to the WAN and the swich pack module.

		clear(6)      - Undoes all protection commands that have been entered for this module.
		Used to clear user requests: lockout,force, manual. Does not affect whether channel 
		is provisioned for protection).
		This option is applicable only to the WAN module.

        unprotected(7)  - Does not use this module in the protection group. This option is 
        applicable only to the WAN and Switch modules.


        Writing the above values may cause a switchover.

        When read, the values mean:

        active(2) - This module is an active member of the protection group.

		lockout(3) - This module is an active locked member of the protection group.

	    unprotected(7) - This module is not being used at present as a member of the protection  
	    group(unprotected).
                
		standby(8) - This module is a standby member of the protection  group.
		  
		unequipped(9) - This module doesn't have a corresponding redundant module.
               "
	SYNTAX INTEGER {
		     protection(1),
		     active(2),
		     lockout(3),
		     force(4),
		     manual(5),
		     clear(6),
		     unprotected(7),
		     standby(8),
		     unequipped(9)
	}

   QbApsGroupMode ::= TEXTUAL-CONVENTION
       STATUS	current
       DESCRIPTION
		"The APS group mode allows a user to create/delete the 1+1 protection
		group.
		The Switch mode values are:
		protected(1) - creates a protection group that consists of two 
			       modules.	
		unprotected(2) - deletes a protection group."
	SYNTAX	INTEGER {
		     protected(1),
		     unprotected(2)
	}

   QbApsSwitchMode ::= TEXTUAL-CONVENTION
       STATUS       current
       DESCRIPTION
           "The APS switch mode allows a user to perform protection
            switch actions.
            The Switch mode values are:
		noop(1) - this value should be returned by a read request 
		        when no switch command has been written to a
			given slot since initialization. This value
			cannot be used in a write operation.
			
		clear(2) - Undoes all protection commands
			  that have been entered for this module.
			  Used to clear user requests: lockout,force, manual.

		force(3)  - forces the module to become an active
			    member of the protection group.

		manual(4)  - Makes this module an active member of the protection group. 

	

		lockout(5) - makes this module an active member of 
			     the protection group and prevents an active module 
			     from switching to the protection
			     module."
       SYNTAX	INTEGER {
                        noop(1),
                        clear(2),
                        force(3),
                        manual(4),
                        lockout(5)
                 }


    TimeStamp ::= TEXTUAL-CONVENTION
	STATUS		current
	DESCRIPTION
            "The value of the sysUpTime object at which a specific
            occurrence happened.  The specific occurrence must be
            defined in the description of any object defined using this
            type."
	SYNTAX		TimeTicks

    QbEventSrvAffect ::= TEXTUAL-CONVENTION
    	STATUS      current
    	DESCRIPTION
        	"A event service effect. The value reflects the effect of
		this event on a corresponding service."
    	SYNTAX      INTEGER {
        	         nonServiceAffecting(1),
                	 serviceAffecting(2)
                	}

   QbEventSeverity ::= TEXTUAL-CONVENTION
    	STATUS      current
    	DESCRIPTION
        	"A event/alarm  severity."
	SYNTAX      INTEGER {
        	         off(1),
                	 minor(2),
                   	 major(3),
                   	 critical(4)
			}

  QbAlarmCondition ::= TEXTUAL-CONVENTION
    	STATUS      current
    	DESCRIPTION
        	"An alarm  condition."
	SYNTAX      INTEGER {
        	         alarmRaise(1),
                	 alarmClear(2)
			}

   QbIoasSlot ::= TEXTUAL-CONVENTION
	STATUS      current
    	DESCRIPTION
        	"IOAS slots."
	SYNTAX      INTEGER {
        	        au-1(1),
                	au-2(2),
                   	au-3(3),
                   	au-4(4),
			sw-a(5),
			proc-a(6),
			main-a(7),
			main-b(8),
			sw-b(9),
			proc-b(10),
			au-5(11),
			au-6(12),
			au-7(13),
			au-8(14),
			sysctl(15)
			}
    QbSysPortLoc ::= TEXTUAL-CONVENTION
	STATUS      current
    	DESCRIPTION
        	"QB system ports."
	SYNTAX      INTEGER {
		 none(0),
        	 ioasPort(1),
        	 ioasWanPort(2),
        	 ioasDwsPort(3),
		 iotDwsPort(4),
		 iotEnetPort(5),
		 iotDs1Port1(6),
		 iotDs1Port2(7),
		 iotDs1Port3(8),
		 iotDs1Port4(9)
		}
			
    QbSysLedState ::= TEXTUAL-CONVENTION
	STATUS      current
    	DESCRIPTION
        	"QB system LED color."
	SYNTAX      INTEGER {
	         ledOff(0),
        	 ledOn(1)
		}     
		
    QbNotificationAlarmCondition ::= TEXTUAL-CONVENTION
	STATUS      current
    	DESCRIPTION
        	"If this Notification is based on an Alarm conditon, this value
        	is derived from the qbSysAlarmCondition of the alarm's corresponding
        	qbSysAlarmEntry. If this Notification is not derived from an Alarm
        	this value would be 'none(3)'."
	SYNTAX      INTEGER {
	         alarmRaise(1),
        	 alarmClear(2),
        	 none(3)
		}     
		
    QbNotificationType ::= TEXTUAL-CONVENTION
	STATUS      current
    	DESCRIPTION
        	"The type of Notification. If it is based on an Alarm Condition then
        	its type will be qbSysAlarmNotification(1) and the Notification's 
        	corresponding qbSysNotificationHistoryId refers to an entry in
        	the qbSysAlarmIdTable. If it is based on an Event Condition then
        	its type will be qbSysEventNotification(1) and the Notification's 
        	corresponding qbSysNotificationHistoryId refers to an entry in
        	the qbSysEventIdTable. "
	SYNTAX      INTEGER {
	         qbAlarmNotification(1),
        	 qbEventNotification(2),
        	 other(3)
		}     

    QbNotificationAction ::= TEXTUAL-CONVENTION
	STATUS      current
    	DESCRIPTION
        	"The type of action that caused this Notification."
	SYNTAX      INTEGER {
	         added(1),
        	 removed(2),
        	 fault(3),
        	 recovery(4),
        	 operStatusChange(5),
        	 stateChange(6),
        	 provisionedAttributeChange(7),
        	 informational(8)
		}  

   QbIotType ::= TEXTUAL-CONVENTION
	STATUS      current
    	DESCRIPTION
        	"The type of IOT terminal."
	SYNTAX      INTEGER {
	         unknown(1),
        	 qb100(9),   -- IOT100 with quad DS1 
        	 qb100e(20),  -- IOT100 with quad E1
		 qb100s(43),  -- IOT100 with quad DS1 and single fiber PON 
 		 qb100w(42),
		 qb100ew(44),   
		 qb100es(45), -- IOT100 with quad E1 and single fiber PON
		 qb101(46),
		 qb101w(47),
		 qb101s(48),
		 qb101sw(49),
		 qb105(50),
		 qb105w(51),
		 qb105s(52),
		 qb105sw(53),
		 qb616sw(54)  
--		 qb106(xx),
--		 qb106w(xx),
--		 qb106s(xx),
--		 qb106sw(xx)
		}   
--
-- Group Overview
--
-- This is the system resource MIB. 
--
-- This MIB consists of 7 groups (and two sub groups)
--
--
-- 1. qbSysGeneralGroup
--	This group contains objects information about the System Level Resources
--	such as the system time, image version, operational status, power supply,etc.
-- 	It allows the user to change and monitor these resources of the Quantum Bridge
--	system that affect the whole system. It contains boot, save and restore 
-- 	information. The group includes the following sub-groups:
--	qbSysAgentGroup - supports objects that provision the SNMP agent. The group includes
--	       	     the qbSysAgentTrapDestTable trap destination table.
--	qbSysFileGroup (Obsolete)  - includes objects that provision the IOAS software images,
--		     backup and restore the NVRAM database to/from the
--		     remote host, and monitor the storage resources.
--		     The group includes the following tables:	
--		     qbSysBootImageTable - the table that contains a list of software images and 
--				           their locations.
--		     qbSysTransferTable - the table that includes objects for transferring files
--					  from/to a system over the network and from/to remote host(s).
--
--
-- 2. qbSysConfigParamsGroup -  contains objects that provides configuration security. The group 
--    contains only two scalar objects. In the future, this group will be extended.
--
-- 3. qbSysEventsGroup 
--	This group contains 6 tables and an assoicated set of objects that provide a generic mechanism for generation
--  retrieval, and notification of various System events and Alarms.
--
--  An Alarm differs from an Event in that an Alarm has a conditon attribute that
--  can either be 'raised' or 'cleared.' 
--
-- 	 qbSysAlarmTable contains a list of currently raised Alarms in the system.
--                                                                             
--   qbSysAlarmHistoryTable contains a history log of all Alarms that have been raised or cleared 
--    in the system.
--
--   qbSysEventHistoryTable contains a history log of all Events that have occurred 
--    in the system.
--
--   qbSysAlarmIdTable contains a description of all system Alarms and allows the enabling
--    of trap generation on their occurrence.
--
--   qbSysEventIdTable contains a description of all system Events and allows the enabling
--    of trap generation on their occurrence.  
--
--   qbSysNotificationHistoryTable contains a description of r2 qbSys Notifications. 
--
-- 4. qbSysModuleGroup
--      This group contains objects that allow the monitoring and configuring  
--	of the IOAS's cards. It includes objects that describe and provision 
-- 	attributes for individual cards.
--      This group includes the following tables:
--      1. qbSysModuleTable - this table contains attributes of individual modules of the IOAS  
--
-- 5. qbSysPortGroup (not implemented)
--      This group contains objects that allow the monitoring and configuring 
--	of the IOAS's ports. It includes objects that describe and provision attributes
-- 	for individual ports.
--      This group includes the following tables:
--      1. qbSysPortTable - this table contains attributes of individual ports of the IOAS.  
--
-- 6. qbSysIotGroup 
--
--      This group contains objects that allow the monitoring and configuring of  
--	IOTs. It includes objects that describe and provision system attributes
-- 	for individual IOTs.
--      This group includes the following tables:
--      1. qbSysIotTable - this table contains attributes of individual Iots that connect
--	to the IOAS. Some attributes from this table simply mirror the System group of the MIB-2.
--  	2. qbSysIotFileTable - this table contains information pertaining to the
--		   files used on the IOT and download information.
-- 7. qbSysInterfacesGroup 
--     The group provides a logical (ifIndex) to physical (rt.card.port)
--     mapping for the Quantum Bridge Access System. This information extends information
--     that is available in the ifTable table to physical ports. The Unified Quantum
--     Bridge interface table presents not only IOAS interfaces but also remote terminals 
--     physical interfaces.  
--     This group includes the following tables:
--     1. qbSysIfLocationTable - the table that contains the mapping of physical ports 
--	  to interface indexes.
--
--	qbSysNotifications(Notification group) - this groups contains a list of traps that are generated
--			     by the SNMP agent.   
--
-- ****************************************************************
-- The Top level System Groups
-- ****************************************************************

	qbSysGeneralGroup         OBJECT IDENTIFIER ::= { qbSysObjects 1 }      
	qbSysConfigParamsGroup    OBJECT IDENTIFIER ::= { qbSysObjects 2 }
	qbSysEventsGroup          OBJECT IDENTIFIER ::= { qbSysObjects 3 }
	qbSysModuleGroup          OBJECT IDENTIFIER ::= { qbSysObjects 4 }
	qbSysPortGroup            OBJECT IDENTIFIER ::= { qbSysObjects 5 }
	qbSysIotGroup	          OBJECT IDENTIFIER ::= { qbSysObjects 6 }
	qbSysInterfacesGroup      OBJECT IDENTIFIER ::= { qbSysObjects 7 }

-- ****************************************************************
-- The general IOAS system group
-- ****************************************************************

    qbSysDateTime OBJECT-TYPE
    	SYNTAX      DateAndTimeForm
    	MAX-ACCESS  read-write
    	STATUS      current
    	DESCRIPTION
        	"The current date and time of the system. Note that this can
        	also be used to set and reset the current date and time."
    	::= { qbSysGeneralGroup 1 }

    qbSysOperStatus OBJECT-TYPE
        SYNTAX      INTEGER {
                    unknown(1),
                    running(2),
                    warning(3),
                    testing(4)
                }
    MAX-ACCESS  read-only    
    STATUS      current
    DESCRIPTION
        "The current operational status of the Quantum Bridge IOAS System 
		as a whole. A value 'unknown(1)' indicates that the current state 
        of the system could not be determined.  The value 'running(2)'
        indicates that the system is up and running and that no
        unusual error conditions have been detected.  The 'warning(3)' state
        indicates that the agent has been informed of an unusual error
        condition by the operational software (e.g., a device driver)
        but that the system is still 'operational'. (The
        qbSysBootDiagsCode object may provide more information.)  A
        value of 'testing(4)', indicates that the system is not
        available for use because it is in the testing state."
    ::= { qbSysGeneralGroup 2 }

-- The following objects are for boot management:

    qbSysResetCtl OBJECT-TYPE
    	SYNTAX      INTEGER {
        	            ready(1),
                	    reset(2)
                	}
    	MAX-ACCESS  read-write
    	STATUS      current
    	DESCRIPTION
        	"This is the 'software reset button' of the agent. When read,
        	this object always returns the value 'ready(1)'. When set to
        	'reset(2)', the system will reset and reload its configuration
        	from FLASH/NVRAM. 
        	Note that when this object is set, the object qbSysResetVersion 
        	will be used to get the software version to be booted from."
    	::= { qbSysGeneralGroup 3 }

     qbSysBootDiagsCode OBJECT-TYPE
    	SYNTAX      Integer32
    	MAX-ACCESS  read-only
    	STATUS      current
    	DESCRIPTION
        	"An error code giving more details about a boot diagnostics
        	failure indicated by qbSysOperStatus 'warning(1)' or
        	'down(2)'. The value 0 indicates no failure detected."
    	::= { qbSysGeneralGroup 4 }

     qbSysWatchdogUpdate OBJECT-TYPE
    	SYNTAX      INTEGER (0 | 1..60)
    	UNITS       "seconds"
    	MAX-ACCESS  read-write
    	STATUS      current
    	DESCRIPTION
        	"The number of seconds between watchdog timer  
         	updates.  A watch dog reset will occur if the timer
         	is not updated within one cycle.  A value of
         	0 disables the watchdog timeout.  The valid range
         	of a functioning update is 1-60 seconds."
    	DEFVAL      { 1 }
    	::= { qbSysGeneralGroup 5 }

    qbSysRunningImageVersion OBJECT-TYPE
    	SYNTAX      DisplayString
    	MAX-ACCESS  read-only
    	STATUS      current
    	DESCRIPTION
        	"The running image version."
    	::= { qbSysGeneralGroup 6}

    qbSysPowerSupplyType OBJECT-TYPE
    	SYNTAX	INTEGER {
		internal(1),
                external(2)
		}
    	MAX-ACCESS  read-only
    	STATUS      current
    	DESCRIPTION
        	"The type of power supply."
    	::= { qbSysGeneralGroup 7 }

   qbSysAcoCtl OBJECT-TYPE
    	SYNTAX      INTEGER {
		    	on(1),
		    	clear(2)
	} 
    	MAX-ACCESS  read-write
    	STATUS      current
    	DESCRIPTION
        	"The object allows to set the ACO (alarm cut off) function. When
		is set to clear(2) will turn off the ACO LED and
		supress visible alarms.Functionally it is equivalent
		to pushing the ACO button. Any new alarm causes the ACO button
		LED to illuminate. When read, this object always returns the value 'on(1)'"
    	::= { qbSysGeneralGroup 8 }
   qbSysAutonomousStatus OBJECT-TYPE
    	SYNTAX      INTEGER {
		    	on(1),
		    	off(2)
	} 
    	MAX-ACCESS  read-only
    	STATUS      current
    	DESCRIPTION
        	"The object enables or disables alarms at the CLI (when 
		a user logged in). If on, autonomous alarms will	
		display at CLI. If off, they will not be displayed."
	DEFVAL { off }
    	::= { qbSysGeneralGroup 9 }

--
-- Discrete Inputs  Table - this table contains a list of discrete inputs that are defined
-- by an owner of the System.
--

   qbSysDiscreteInputTable OBJECT-TYPE
	SYNTAX	   SEQUENCE OF QbSysDiscreteInputEntry
	MAX-ACCESS not-accessible
	STATUS	   current
	DESCRIPTION
		" A list of discrete inputs entries.

		This table contains information specifying discrete inputs
		that are configured for this system.
		Each entry in the table with a status of 'active' 
		identifies a discrete input that is currently enabled."
	::= { qbSysGeneralGroup 10 }

    qbSysDiscreteInputEntry OBJECT-TYPE
	SYNTAX	    QbSysDiscreteInputEntry
	MAX-ACCESS  not-accessible
	STATUS	    current
	DESCRIPTION
		"Information about a single Discrete Entry."
	INDEX	{ qbSysDiscreteInputType }
	::= { qbSysDiscreteInputTable 1 }
 
   QbSysDiscreteInputEntry ::=
	SEQUENCE {
		qbSysDiscreteInputType
			INTEGER,
	       qbSysDiscreteInputName
		        DisplayString,
		qbSysDiscreteInputAdminStatus
			INTEGER,    
		qbSysDiscreteInputState
			INTEGER
	 }

   qbSysDiscreteInputType OBJECT-TYPE
    	SYNTAX      INTEGER (1..8)
    	MAX-ACCESS  read-only
    	STATUS      current
    	DESCRIPTION
        	"The user defined type of the discrete input."
    	::= { qbSysDiscreteInputEntry 1 }

    qbSysDiscreteInputName  OBJECT-TYPE
    	SYNTAX      DisplayString (SIZE (0..64))
    	MAX-ACCESS  read-write
    	STATUS      current
    	DESCRIPTION
        	"The user defined  discrete input name."
    	::= { qbSysDiscreteInputEntry 2 }

     qbSysDiscreteInputAdminStatus  OBJECT-TYPE
    	SYNTAX      INTEGER {
                         unknown(1),
                         enabled(2),
                         disabled(3)
	            }
    	MAX-ACCESS  read-write
    	STATUS      current
    	DESCRIPTION
         	"The value determines the desired administrative
		status of a discrete input. If enabled, the The enabled
		and disabled states indicate that the discrete-input
		is enabled or disabled respectively. The unknown state 
		indicates that the discrete input was not configured."
    	::= { qbSysDiscreteInputEntry 3 }
                                             
     qbSysDiscreteInputState  OBJECT-TYPE
    	SYNTAX      INTEGER {
                         unknown(1),
                         on(2),
                         off(3)
	            }
    	MAX-ACCESS  read-only
    	STATUS      current
    	DESCRIPTION
         	"The value determines the operational status of a discrete input. 
         The on and off states indicate that the discrete-input
		 is enabled or disabled respectively. The unknown state 
		 indicates that the discrete input was not configured."
    	::= { qbSysDiscreteInputEntry 4 }
                                            
--
-- These variables are used to control or configure the agent 
--
    qbSysAgentGroup         OBJECT IDENTIFIER ::= { qbSysGeneralGroup 11 }

      qbSysSnmpRevision OBJECT-TYPE
	SYNTAX	Unsigned32
	MAX-ACCESS	read-only
	STATUS	current
	DESCRIPTION
		"The revision number of the SNMP agent
		implementation. The first two bytes indicate major revision number,
		the second two bytes indicate the minor revision number"
	::= { qbSysAgentGroup 1 }

    qbSysMgmtIpAddr OBJECT-TYPE
        SYNTAX  IpAddress
        MAX-ACCESS  read-write
        STATUS  current
        DESCRIPTION
    		"Active IP Address for SNMP Management of this chassis.
             This is the IP address used for network mangement."
        ::= { qbSysAgentGroup 2 }

     qbSysMgmtIpMask  OBJECT-TYPE
         SYNTAX     IpAddress
         MAX-ACCESS read-write
         STATUS     current
         DESCRIPTION
             "This is the IP network mask associated with the
             Management interface."
               	::= { qbSysAgentGroup 3 }

     qbSysDefaultIpRouter  OBJECT-TYPE
         SYNTAX     IpAddress
         MAX-ACCESS read-write
         STATUS     current
         DESCRIPTION
            "This is a machine, connected to the same subnet as
           	the sysctl management interface, which is capable of routing
          	IP packets"
          ::= { qbSysAgentGroup 4 }

    qbSysAgentReadCommunity OBJECT-TYPE
	SYNTAX      DisplayString (SIZE (0..48)) 
	MAX-ACCESS  read-write
	STATUS      current
	DESCRIPTION
		"This object is the read community string for the SNMP, see RFC1157."	
	DEFVAL { "public" }   	    
    ::= { qbSysAgentGroup 5 }

    qbSysAgentReadWriteCommunity OBJECT-TYPE
	SYNTAX      DisplayString (SIZE (0..48)) 
	MAX-ACCESS  read-write
	STATUS      current
	DESCRIPTION
		"This object is the read-write community string for
		the SNMP,see RFC1157.  The read-write community string
		is required to modify this object."
	DEFVAL { "private" }   	    
    ::= { qbSysAgentGroup 6 }


  -- The Quantum Bridge System MIB agent trap destination table.

   qbSysAgentTrapDestTable OBJECT-TYPE
	SYNTAX	   SEQUENCE OF QbSysAgentTrapDestEntry
	MAX-ACCESS not-accessible
	STATUS	   current
	DESCRIPTION
		"This table contains information specifying which traps
		will be transmitted to a given destination address.  The
		table is indexed by the 
		destination address.  Each entry in the table with a
		status of 'active' identifies a set of traps which, when
		generated, will be transmitted to the corresponding
		destination address listed in that entry."
	::= { qbSysAgentGroup 7 }

    qbSysAgentTrapDestEntry OBJECT-TYPE
	SYNTAX	    QbSysAgentTrapDestEntry
	MAX-ACCESS  not-accessible
	STATUS	    current
	DESCRIPTION
		"Information relating to a set of traps and a destination
		address to which each trap in this set will be transmitted
		when it is generated.  To create a new entry, 
		a non-existent instance of qbSysAgentTrapDestAddr must 
		be created.
		To remove an entry, an instance of
		qbSysAgentTrapDestEntryStatus of the entry must be set 
		to destroy(6)."
	INDEX	{ qbSysAgentTrapDestAddr }
	::= { qbSysAgentTrapDestTable 1 }

    QbSysAgentTrapDestEntry ::=
	SEQUENCE {
		qbSysAgentTrapDestAddr
			IpAddress,
		qbSysAgentTrapDestFilter
			INTEGER,
	        qbSysAgentTrapDestComm
			DisplayString,
		qbSysAgentTrapDestRowStatus
			RowStatus,
		qbSysAgentTrapDestPort
			INTEGER
	    }

    qbSysAgentTrapDestAddr OBJECT-TYPE
	SYNTAX	   IpAddress
	MAX-ACCESS not-accessible
	STATUS	   current
	DESCRIPTION
		"The destination address to which traps are to be transmitted."
	::= { qbSysAgentTrapDestEntry  1 }

    qbSysAgentTrapDestFilter OBJECT-TYPE
	SYNTAX		INTEGER {
			minor(1),
			major(2),
			critical(3),
			all(4)
	}
	MAX-ACCESS	read-create
	STATUS		current
	DESCRIPTION
		"Indicates which traps are sent to the destination
		address. Note that, currently,for Release 1, the only
		object 'all' can be set"
	DEFVAL		{ all }
	::= {qbSysAgentTrapDestEntry  2 } 

    qbSysAgentTrapDestComm OBJECT-TYPE
	SYNTAX	   DisplayString (SIZE (0..20))
	MAX-ACCESS read-create
	STATUS	   current
	DESCRIPTION
		"Community string used for trap messages to this
		destination."	
	DEFVAL { "public" }   	    
	::= { qbSysAgentTrapDestEntry  3 }

    qbSysAgentTrapDestRowStatus OBJECT-TYPE
       SYNTAX      RowStatus
       MAX-ACCESS  read-create
       STATUS	   current
       DESCRIPTION
		"The status of this conceptual row.

		This OBJECT can be set to:

		createAndGo(4)
            	destroy(6)

		Setting this object to active(1) when its value
		is already active(1) is a no-op.
			
		Setting this object to createAndGo(4) causes the agent
		to attempt to create and commit the row based on
		the contents of the objects in the row. If all necessary
		information is present in the row and the values are
		acceptable to the agent, the agent will change the
		status to active(1).  If any of the necessary objects
		are not available, the agent will reject the creation
		request.	

		Setting this object to destroy(6) will remove the corresponding
		entry in this table.

		The following values may be read:
            	active(1).

             	The following objects cannot be modified while the
             	value of this object is active(1):
	     	qbSysAgentTrapDestAddr."		
	::= { qbSysAgentTrapDestEntry  4 }

     qbSysAgentTrapDestPort OBJECT-TYPE
              SYNTAX  INTEGER (0..65535)
              MAX-ACCESS  read-create
              STATUS  current
              DESCRIPTION
                      "The destination port number for this trap address."
              ::= { qbSysAgentTrapDestEntry 5 }

    qbSysDefaultRouterType OBJECT-TYPE
        SYNTAX  INTEGER {
            unknown(0),
            enetmgt(1),
            atmmgt(2)
            }
        MAX-ACCESS  read-write
        STATUS  current
        DESCRIPTION
                "This indicates the kind of the management port associated with
                  the default gateway."
    ::= { qbSysAgentGroup 8 }

    qbSysCliMsgCode OBJECT-TYPE
	SYNTAX      Unsigned32 
	MAX-ACCESS  read-write
	STATUS      current
	DESCRIPTION
		"This object is the read-write community string for
		the SNMP,see RFC1157.  The read-write community string
		is required to modify this object."
    ::= { qbSysAgentGroup 9 }


    qbRIPConfig     OBJECT-TYPE
	SYNTAX	    INTEGER {
            enable (1),
            disable (2)
            }
	MAX-ACCESS  read-write
	STATUS	    current
	DESCRIPTION
		"This is a singular object in qbSysAgentGroup and is for
		enabling or disabling RIP Configuration system wide"
    ::= { qbSysAgentGroup 10 }


-- ****************************************************************
-- Information pertaining to 'files' in the system. Files can be located 
-- on a remote host, in flash or NVRAM.  OBSOLETE.
-- ****************************************************************
    qbSysFileGroup         OBJECT IDENTIFIER ::= { qbSysGeneralGroup 12 }

    qbSysBootImageTable OBJECT-TYPE
       SYNTAX      SEQUENCE OF QbSysBootImageEntry
       MAX-ACCESS  not-accessible
       STATUS      obsolete
       DESCRIPTION
		"Not used."
	 ::= { qbSysFileGroup 1 }

    qbSysBootImageEntry OBJECT-TYPE
       SYNTAX      QbSysBootImageEntry
       MAX-ACCESS  not-accessible
       STATUS      obsolete
       DESCRIPTION
		"Not used."
	 INDEX       { qbSysBootImageIndex }
	 ::= {  qbSysBootImageTable 1 }

     QbSysBootImageEntry ::= SEQUENCE {
    	qbSysBootImageIndex     INTEGER,
    	qbSysBootImageName      DisplayString,
    	qbSysBootImageAddress   Unsigned32
     }

    qbSysBootImageIndex OBJECT-TYPE
    	SYNTAX      INTEGER (1..1000)
    	MAX-ACCESS  not-accessible
    	STATUS      obsolete
    	DESCRIPTION
        	"Not used."
    	::= {  qbSysBootImageEntry 1 }

    qbSysBootImageName OBJECT-TYPE
    	SYNTAX      DisplayString (SIZE (0..127))
    	MAX-ACCESS  read-write
    	STATUS      obsolete
    	DESCRIPTION
        	"Not used."
    	::= { qbSysBootImageEntry 2 }

   qbSysBootImageAddress OBJECT-TYPE
   	SYNTAX      Unsigned32
    	MAX-ACCESS  read-only
    	STATUS      obsolete
    	DESCRIPTION
        	"Not used."  
    	::= { qbSysBootImageEntry 3 }

--
-- File Transfer Table - This table defines objects for transferring
-- files from/to a system over the network and from/to remote host(s). It also
-- allows for the transfer of files between SWCTL, SYSCTL, and IOT. 
--
    qbSysTransferTable OBJECT-TYPE
    	SYNTAX      SEQUENCE OF QbSysTransferEntry
    	MAX-ACCESS  not-accessible
    	STATUS      obsolete
    	DESCRIPTION
		"Not used."
    	::= { qbSysFileGroup 2 }

    qbSysTransferEntry OBJECT-TYPE
    	SYNTAX      QbSysTransferEntry
    	MAX-ACCESS  not-accessible
    	STATUS      obsolete
    	DESCRIPTION
        	"Not used."
    	INDEX       { qbSysTransferIndex }
    	::= { qbSysTransferTable 1 }

    QbSysTransferEntry ::= SEQUENCE {
	    	qbSysTransferIndex           Unsigned32,
    		qbSysTransferSrc             QbStorageType,
    		qbSysTransferSrcName         DisplayString,
    		qbSysTransferDest            QbStorageType,
    		qbSysTransferDestName        DisplayString,
    		qbSysTransferServerAddr      IpAddress,
		qbSysTransferIot             Unsigned32,
    		qbSysTransferOperStatus      QbTransferStatus,
    		qbSysTransferOperProgress    INTEGER,
    		qbSysTransferRowStatus       RowStatus
	}

   qbSysTransferIndex OBJECT-TYPE
    	SYNTAX      Unsigned32 (1..10)
    	MAX-ACCESS  not-accessible
    	STATUS      obsolete
    	DESCRIPTION
        	"Not used."
    	::= { qbSysTransferEntry 1 }

    qbSysTransferSrc OBJECT-TYPE
    	SYNTAX      QbStorageType
    	MAX-ACCESS  read-create
    	STATUS      obsolete
    	DESCRIPTION
        	"Not used."
	DEFVAL { flash }
	::= { qbSysTransferEntry 2 }

    qbSysTransferSrcName OBJECT-TYPE
    	SYNTAX      DisplayString  (SIZE (0..127))
    	MAX-ACCESS  read-create
    	STATUS      obsolete
    	DESCRIPTION
        	"Not used."
    	DEFVAL      { ''h }
    	::= { qbSysTransferEntry 3 }

    qbSysTransferDest OBJECT-TYPE
    	SYNTAX      QbStorageType
    	MAX-ACCESS  read-create
    	STATUS      obsolete
    	DESCRIPTION
        	"Not used."
    	DEFVAL { flash }
        ::= { qbSysTransferEntry 4 }

    qbSysTransferDestName OBJECT-TYPE
    	SYNTAX      DisplayString  (SIZE (0..127))
    	MAX-ACCESS  read-create
    	STATUS      obsolete
    	DESCRIPTION
        	"Not used."
        DEFVAL      { ''h }
        ::= { qbSysTransferEntry 5 }

    qbSysTransferServerAddr OBJECT-TYPE
    	SYNTAX      IpAddress
    	MAX-ACCESS  read-create
    	STATUS      obsolete
    	DESCRIPTION
        	"Not used."
    	DEFVAL      { 0 }
    	::= { qbSysTransferEntry 6 }

    qbSysTransferIot OBJECT-TYPE
    	SYNTAX      Unsigned32
    	MAX-ACCESS  read-create
    	STATUS      obsolete
    	DESCRIPTION
        	"not used."
        DEFVAL      { ''h }
        ::= { qbSysTransferEntry 7 }

    qbSysTransferOperStatus OBJECT-TYPE
    	SYNTAX      QbTransferStatus
    	MAX-ACCESS  read-only
    	STATUS      obsolete
    	DESCRIPTION
        	"Not used."
    	::= { qbSysTransferEntry 8 }

    qbSysTransferOperProgress OBJECT-TYPE
    	SYNTAX     INTEGER (0..100)
    	MAX-ACCESS  read-only
    	STATUS      obsolete
    	DESCRIPTION
        	"notused."
    	::= { qbSysTransferEntry 9 }

    qbSysTransferRowStatus OBJECT-TYPE
	SYNTAX 	    RowStatus
	MAX-ACCESS  read-create
	STATUS	    obsolete
	DESCRIPTION
		"not used."
	::= { qbSysTransferEntry 10 }   
	
--
-- Version Info - this is used on a remote reset. i.e. a set of qbSysResetCtl (or 
-- the ModuleAdminStatus reset of syscon)
--
    qbSysResetVersion	OBJECT-TYPE
    	SYNTAX      DisplayString (SIZE (1..20))
    	MAX-ACCESS  read-write
    	STATUS      current
    	DESCRIPTION
        	"The version used by the system controller when remotely reset."
    	::= { qbSysGeneralGroup 13 }
--
-- ************************************************************************
-- Information about the software Feature Keys. Each key enables access to
-- a particular feature areas.
-- *************************************************************************
    qbSysFeatureKeys    OBJECT-TYPE
      SYNTAX    BITS {
                  qbSysAtmKey (0),
                  qbSysTdmKey (1)
                }
      MAX-ACCESS   read-only
      STATUS       current
      DESCRIPTION
             "inidcates which features of OAS software are administratively 
             enabled on this system. If a bit is set, then the corresponding
             feature is enabled. 
             Note: unlimited number of features can be enabled or disabled
             via this object.          
             "
     ::= {qbSysGeneralGroup 14}

--
-- ************************************************************************
-- Configuration AU-1 port sharing badwitdh.
-- *************************************************************************
--
    qbSysPortBwSharing OBJECT-TYPE
	SYNTAX 	    INTEGER (155|311|466|622)
	MAX-ACCESS  read-write
	STATUS	    current
	DESCRIPTION
		"This object shows and controls the bandwidth allocation between
		Au-1 and au-2. If it is set to 622, then there is no port sharing enabled
		between the ports. Any other setting will enable port sharing, and the 622 Mbis/sec
		of bandwidth is split between the 2 ports. 
		Note. If protection is being used, 		
		then the bandwidth should be set to 622."
	::= { qbSysGeneralGroup  15 } 

    qbSysTestLeds OBJECT-TYPE
    	SYNTAX      INTEGER {
        	        ready(1),
                	test(2)
                	}
    	MAX-ACCESS  read-write
    	STATUS      current
    	DESCRIPTION
        	"This object tests the system LEDs. If the object is read 
		it should return ready. Setting the value test will initiate the LED test."
    	::= { qbSysGeneralGroup 16 }		       
      
     qbSysSwAccepted OBJECT-TYPE
    	SYNTAX      TruthValue 
    	MAX-ACCESS  read-write
    	STATUS      current
    	DESCRIPTION
        	"if true, the software in the switch is accepted. "
    	::= { qbSysGeneralGroup 17 } 

    qbChassisSysType OBJECT-TYPE
        SYNTAX        INTEGER {
                      other(1),    -- none of the following
                      qb5000(2),   -- 15 Slots OAS Concentrator
                      qb3000(3)    -- 8 Slots OAS Concentrator
                      }
        MAX-ACCESS    read-only
        STATUS        current
        DESCRIPTION   "The chassis system type."
        ::= { qbSysGeneralGroup 18 }

   qbChassisBkplType OBJECT-TYPE
        SYNTAX        INTEGER {
                                other(1),        -- none of the following
                                giga2(2),        -- 2.5 Gigabit switch (QB3000)
                                giga5(3)         -- 5 Gigabit switch (QB5000)
                                }
        MAX-ACCESS    read-only
        STATUS        current
        DESCRIPTION   "The chassis backplane type."
        ::= { qbSysGeneralGroup 19 }

   qbChassisNumSlots OBJECT-TYPE
        SYNTAX        INTEGER (1..15)
        MAX-ACCESS    read-only
        STATUS        current
        DESCRIPTION   "The number of slots in the chassis available for
                      plug-in modules. QB3000 contains 7 slots, QB5000
		      contains 15 slots"
        ::= { qbSysGeneralGroup 20 }

  qbChassisBulkStatsCtl  OBJECT-TYPE
    	SYNTAX INTEGER {
		   enable(1),
		   disable(2)
	} 
    	MAX-ACCESS  read-write
    	STATUS      current
    	DESCRIPTION
        "The object allows to enable and disable bulk statistics collection on the OAS."
	DEFVAL  { disable }
    	::= { qbSysGeneralGroup 21 }


-- ****************************************************************
-- The configuration parameters group - contains values that provide 
-- configuration security
-- ****************************************************************

    qbSysConfigLastWriteDateTime OBJECT-TYPE
    	SYNTAX      DateAndTimeForm
    	MAX-ACCESS  read-only
    	STATUS      current
    	DESCRIPTION
        	"The last time any configuration
        	parameter value was written to flash memory. A
        	zero-length value indicates that no changes have been made and
        	that the system is running using all defaults. Note that this
        	parameter must be saved in non-volatile memory across
        	re-initializations of the system."
    	::= { qbSysConfigParamsGroup 1 }

    qbSysConfigLastWriteSource OBJECT-TYPE
    	SYNTAX      IpAddress
    	MAX-ACCESS  read-only
    	STATUS      current
    	DESCRIPTION
        	"The source address of the entity that made the last
        	configuration change to the system. The value 127.0.0.1 (the
        	loopback address) indicates the local console. This value must
        	also be saved in non-volatile memory across re-initializations
        	of the system."
    	::= { qbSysConfigParamsGroup 2 }

    qbSysProvType OBJECT-TYPE
    	SYNTAX      INTEGER {
		    provIot(1),
		    provConnection(2)
        }
    	MAX-ACCESS  read-only
    	STATUS      current
    	DESCRIPTION
        	"The type of provisioning that occured to the system. 
			provIot indicates that an IOT added/removed, or
			changed state. 
			provConn indicates that a connection added/removed, or
			changed state." 
    	::= { qbSysConfigParamsGroup 3 }


-- ****************************************************************
-- The system events group
-- ****************************************************************
--
-- The Event History Table contains events that have been generated.
--
    qbSysEventHistoryTable OBJECT-TYPE
    	SYNTAX      SEQUENCE OF QbSysEventHistoryEntry
    	MAX-ACCESS  not-accessible
    	STATUS      current
    	DESCRIPTION
        	"A table of events in the order that they were generated. An
        	event may or may not be added to this (conceptual) table based
        	on whether it passes all of the input filter criteria
        	identified below. When the table is retrieved via SNMP
        	operations, it may or may not include a specific event based
        	on the current output filter criteria."
    	::= { qbSysEventsGroup 1 }

    qbSysEventHistoryEntry OBJECT-TYPE
    	SYNTAX      QbSysEventHistoryEntry
    	MAX-ACCESS  not-accessible
    	STATUS      current
    	DESCRIPTION
        	"Information about a single event."
    	INDEX       { qbSysEventHistoryIndex }
        ::= { qbSysEventHistoryTable 1 }

    QbSysEventHistoryEntry ::= SEQUENCE {
    	qbSysEventHistoryIndex      Unsigned32,
    	qbSysEventHistoryDateTime   DateAndTimeForm,
    	qbSysEventHistorySubsystem  DisplayString,
   		qbSysEventHistorySrvAffect  QbEventSrvAffect,
    	qbSysEventHistorySeverity   QbEventSeverity,
    	qbSysEventHistoryId         Unsigned32,
    	qbSysEventHistoryMsg        DisplayString
	}

    qbSysEventHistoryIndex OBJECT-TYPE
    	SYNTAX      Unsigned32
    	MAX-ACCESS  not-accessible
    	STATUS      current
    	DESCRIPTION
        	"Indicates the number of the event. Events are numbered
        	sequentially from 1 - n. A management station can keep track
        	of the last event it uploaded and periodically GET-NEXT from
        	there to determine if there have been any new events. This
        	means that, as events are removed from the table their indices
        	are not reused until the next reset to default configuration
        	(which loses all stored events). The agent must store
        	the 'next available event number' value across
        	re-initializations of the system, resetting it to 1 only when
        	the configuration is reset to defaults."
    	::= { qbSysEventHistoryEntry 1 }

    qbSysEventHistoryDateTime OBJECT-TYPE
    	SYNTAX      DateAndTimeForm
    	MAX-ACCESS  read-only
    	STATUS      current
    	DESCRIPTION
        	"The date and time when this event was generated."
    	::= { qbSysEventHistoryEntry 2 }

    qbSysEventHistorySubsystem OBJECT-TYPE
    	SYNTAX      DisplayString
    	MAX-ACCESS  read-only
    	STATUS      current
    	DESCRIPTION
        	"The subsystem that generated this event."
    	::= { qbSysEventHistoryEntry 3 }

    qbSysEventHistorySrvAffect OBJECT-TYPE
    	SYNTAX      QbEventSrvAffect
    	MAX-ACCESS  read-only
    	STATUS      current
    	DESCRIPTION
        	"Describes whether the event was service affecting."   
    	::= { qbSysEventHistoryEntry 4 }

    qbSysEventHistorySeverity OBJECT-TYPE
        SYNTAX	    QbEventSeverity 
    	MAX-ACCESS  read-only
    	STATUS      current
    	DESCRIPTION
        	"The severity of the event."
    	::= { qbSysEventHistoryEntry 5 }

    qbSysEventHistoryId OBJECT-TYPE
    	SYNTAX      Unsigned32 (0..255)
    	MAX-ACCESS  read-only
    	STATUS      current
    	DESCRIPTION
        	"The identifier of the event. This id is unique within a
        	system. This id maps to a qbSysEventIdEntry. It is used to lookup 
        	the event description in the qbSysEventIdTable."
    	::= { qbSysEventHistoryEntry 6 }

    qbSysEventHistoryMsg OBJECT-TYPE
    	SYNTAX      DisplayString
    	MAX-ACCESS  read-only
    	STATUS      current
    	DESCRIPTION
        	"Textual message associated with the event."
    	::= { qbSysEventHistoryEntry 7 }

    qbSysEventHistoryMaxTableSize OBJECT-TYPE
    	SYNTAX      Integer32 (1..65535)
    	UNITS       "number of events"
    	MAX-ACCESS  read-only
    	STATUS      current
    	DESCRIPTION
        	"The maximum number of entries in the qbSysEventHistoryTable. When the number
        	of entries gets larger than this size, older entries are
        	discarded. The  event level is considered when discarding old
			events because the log is full (old debug or trace messages
        	are discarded before even older warning or fatal
        	messages)."
    	::= { qbSysEventsGroup 2 }

-- 
-- Filter information
-- 
    qbSysEventHistoryOutFilterLevel OBJECT-TYPE
    	SYNTAX      QbEventSeverity 
    	MAX-ACCESS  read-only
    	STATUS      obsolete
    	DESCRIPTION
        	"obsolete."
    	::= { qbSysEventsGroup 3 }

    qbSysEventHistoryOutFilterDateTime OBJECT-TYPE
    	SYNTAX      DateAndTimeForm
    	MAX-ACCESS  read-only
    	STATUS      obsolete
    	DESCRIPTION
        	"obsolete."  
 	::= { qbSysEventsGroup 4 }

    qbSysEventHistoryClearAllCtl OBJECT-TYPE
    	SYNTAX      INTEGER {
                    ready(1),
                    clear(2)
                }
    	MAX-ACCESS  read-write
    	STATUS      current
    	DESCRIPTION
        	"Setting this object to 'clear(2)' removes all entries from
        	the qbSysAlarmHistoryTable, the qbSysEventHistoryTable and the 
        	qbSysNotificationHistoryTable. 
        	 When read, this object always returns the
        	value 'ready(1)'."
    	::= { qbSysEventsGroup 5 }

--
-- This table contains a list  of the currently triggered alarms
--
    qbSysAlarmTable OBJECT-TYPE
    	SYNTAX      SEQUENCE OF QbSysAlarmEntry
    	MAX-ACCESS  not-accessible
    	STATUS      current
    	DESCRIPTION
        	"A table that conatins the currently triggered alarms in the
			order that have not been cleared yet.
         	The index is incremented for each new alarm entry put onto the ring.
			When an alarm is cleared this entry is removed from
			the table."
    	::= { qbSysEventsGroup 6 }

    qbSysAlarmEntry OBJECT-TYPE
    	SYNTAX      QbSysAlarmEntry
    	MAX-ACCESS  not-accessible
    	STATUS      current
    	DESCRIPTION
        	"Information about a single alarm that is currently triggered."
    	INDEX       { qbSysAlarmIndex }
        ::= { qbSysAlarmTable 1 }

    QbSysAlarmEntry ::= SEQUENCE {
    	qbSysAlarmIndex      Unsigned32,
    	qbSysAlarmDateTime   DateAndTimeForm,
		qbSysAlarmSrvAffect  QbEventSrvAffect,	
    	qbSysAlarmSeverity   QbEventSeverity,
		qbSysAlarmCondition  QbAlarmCondition,
    	qbSysAlarmSubsystem  DisplayString,
     	qbSysAlarmId         Unsigned32,
    	qbSysAlarmMsg        DisplayString,
    	qbSysAlarmResource   OBJECT IDENTIFIER
	}

    qbSysAlarmIndex OBJECT-TYPE
    	SYNTAX      Unsigned32
    	MAX-ACCESS  not-accessible
    	STATUS      current
    	DESCRIPTION  
		  "The internal index into the Alarm Table.  The index is incremented
		   for each new alarm entry put into the ring. When
		   the alarm is cleared the entry is removed from the table.
		   On a node reset, the object is reset to 0." 
    	::= { qbSysAlarmEntry 1 }

    qbSysAlarmDateTime OBJECT-TYPE
    	SYNTAX      DateAndTimeForm
    	MAX-ACCESS  read-only
    	STATUS      current
    	DESCRIPTION
        	"The date and time when this alarm was generated."
    	::= { qbSysAlarmEntry 2 }

    qbSysAlarmSubsystem OBJECT-TYPE
    	SYNTAX      DisplayString
    	MAX-ACCESS  read-only
    	STATUS      current
    	DESCRIPTION
        	"The subsystem that generated this alarm."
    	::= { qbSysAlarmEntry 3 }

   qbSysAlarmSrvAffect OBJECT-TYPE
    	SYNTAX      QbEventSrvAffect
    	MAX-ACCESS  read-only
    	STATUS      current
    	DESCRIPTION
        	"The type of the alarm. Can be 2 different modes:
		Service affecting and nonservice affecting."   
    	::= { qbSysAlarmEntry 4 }

    qbSysAlarmSeverity OBJECT-TYPE
        SYNTAX	    QbEventSeverity 
    	MAX-ACCESS  read-only
    	STATUS      current
    	DESCRIPTION
        	"The severity of the alarm."
    	::= { qbSysAlarmEntry 5 }

    qbSysAlarmCondition OBJECT-TYPE
        SYNTAX	    QbAlarmCondition 
    	MAX-ACCESS  read-only
    	STATUS      current
    	DESCRIPTION
        	"The condition of the alarm."
    	::= { qbSysAlarmEntry 6  }


    qbSysAlarmId OBJECT-TYPE
    	SYNTAX      Unsigned32 (0..255)
    	MAX-ACCESS  read-only
    	STATUS      current
    	DESCRIPTION
        	"The identifier of the alarm. This id is unique within a
        	system. This id maps to a qbSysAlarmIdEntry. This is used to 
        	lookup the alarm description in the qbSysAlarmIdTable."
    	::= { qbSysAlarmEntry 7 }

    qbSysAlarmMsg OBJECT-TYPE
    	SYNTAX      DisplayString
    	MAX-ACCESS  read-only
    	STATUS      current
    	DESCRIPTION
        	"Textual message associated with the alarm."
    	::= { qbSysAlarmEntry 8 }
    	
    qbSysAlarmResource OBJECT-TYPE
	SYNTAX OBJECT IDENTIFIER
	MAX-ACCESS	read-only
	STATUS		current
	DESCRIPTION
		"The Resource to which this alarm corresponds. For example, if the alarm
		refers to Module removal, the resource would be the OID 'qbSysModuleOperStatus',
		including the instance ID of the Module removed."
    	::= { qbSysAlarmEntry 9 }
   	 

--
-- The Alarm History Table contains alarms that have been generated.
--
    qbSysAlarmHistoryTable OBJECT-TYPE
    	SYNTAX      SEQUENCE OF QbSysAlarmHistoryEntry
    	MAX-ACCESS  not-accessible
    	STATUS      current
    	DESCRIPTION
        	"A table of alarms in the order that they were generated."
    	::= { qbSysEventsGroup 7 }

    qbSysAlarmHistoryEntry OBJECT-TYPE
    	SYNTAX      QbSysAlarmHistoryEntry
    	MAX-ACCESS  not-accessible
    	STATUS      current
    	DESCRIPTION
        	"Information about a single alarm."
    	INDEX       { qbSysAlarmHistoryIndex }
        ::= { qbSysAlarmHistoryTable 1 }

    QbSysAlarmHistoryEntry ::= SEQUENCE {
    qbSysAlarmHistoryIndex      Unsigned32,
    qbSysAlarmHistoryDateTime   DateAndTimeForm,
	qbSysAlarmHistorySrvAffect  QbEventSrvAffect,
	qbSysAlarmHistorySeverity   QbEventSeverity,
	qbSysAlarmHistoryCondition  QbAlarmCondition,	    			    
    qbSysAlarmHistorySubsystem  DisplayString,
    qbSysAlarmHistoryId         Unsigned32,
    qbSysAlarmHistoryMsg        DisplayString
	}

    qbSysAlarmHistoryIndex OBJECT-TYPE
    	SYNTAX      Unsigned32
    	MAX-ACCESS  not-accessible
    	STATUS      current
    	DESCRIPTION 
        	"Indicates the number of the alarm. Alarms are numbered
        	sequentially from 1 - n. A management station can keep track
        	of the last event it uploaded and periodically GET-NEXT from
        	there to determine if there have been any new events. This
        	means that, as alarms are removed from the table their indices
        	are not reused until the next reset to default configuration
        	(which loses all stored alarms). The agent must store
        	the 'next available alarm number' value across
        	re-initializations of the system, resetting it to 1 only when
        	the configuration is reset to defaults."
    	::= { qbSysAlarmHistoryEntry 1 }

    qbSysAlarmHistoryDateTime OBJECT-TYPE
    	SYNTAX      DateAndTimeForm
    	MAX-ACCESS  read-only
    	STATUS      current
    	DESCRIPTION
        	"The date and time when this alarm was generated."
    	::= { qbSysAlarmHistoryEntry 2 }

    qbSysAlarmHistorySubsystem OBJECT-TYPE
    	SYNTAX      DisplayString
    	MAX-ACCESS  read-only
    	STATUS      current
    	DESCRIPTION
        	"The subsystem that generated this alarm."
    	::= { qbSysAlarmHistoryEntry 3 }

   qbSysAlarmHistorySrvAffect OBJECT-TYPE
    	SYNTAX      QbEventSrvAffect
    	MAX-ACCESS  read-only
    	STATUS      current
    	DESCRIPTION 
    		"Describes whether the event was service affecting."  
    	::= { qbSysAlarmHistoryEntry 4 }

    qbSysAlarmHistorySeverity OBJECT-TYPE
        SYNTAX	    QbEventSeverity 
    	MAX-ACCESS  read-only
    	STATUS      current
    	DESCRIPTION
        	"The severity of the alarm."
    	::= { qbSysAlarmHistoryEntry 5 }

   qbSysAlarmHistoryCondition OBJECT-TYPE
        SYNTAX	    QbAlarmCondition 
    	MAX-ACCESS  read-only
    	STATUS      current
    	DESCRIPTION
        	"The condition of the alarm."
    	::= { qbSysAlarmHistoryEntry 6  }


    qbSysAlarmHistoryId OBJECT-TYPE
    	SYNTAX      Unsigned32 (0..255)
    	MAX-ACCESS  read-only
    	STATUS      current
    	DESCRIPTION
        	"The identifier of the alarm. This id is unique within a
        	system. This is used to lookup the alarm description
		in the qbSysAlarmIdTable"
    	::= { qbSysAlarmHistoryEntry 7 }

    qbSysAlarmHistoryMsg OBJECT-TYPE
    	SYNTAX      DisplayString
    	MAX-ACCESS  read-only
    	STATUS      current
    	DESCRIPTION
        	"Textual message associated with the alarm."
    	::= { qbSysAlarmHistoryEntry 8 }
 
    qbSysAlarmHistoryMaxTableSize OBJECT-TYPE
    	SYNTAX      Integer32 (1..65535)
    	UNITS       "number of events"
    	MAX-ACCESS  read-only
    	STATUS      current
    	DESCRIPTION
        	"The maximum number of entries in the AlarmHistoryTable. When the number
        	of entries gets larger than this size, older entries are
        	discarded."
    	::= { qbSysEventsGroup 8 }
-- 
-- Filter information
-- 
    qbSysAlarmHistoryOutFilterLevel OBJECT-TYPE
    	SYNTAX      QbEventSeverity 
    	MAX-ACCESS  read-only
    	STATUS      obsolete
    	DESCRIPTION
        	"obsolete."
    	::= { qbSysEventsGroup 9 }

    qbSysAlarmHistoryOutFilterDateTime OBJECT-TYPE
    	SYNTAX      DateAndTimeForm
    	MAX-ACCESS  read-only
    	STATUS      current
    	DESCRIPTION
        	"obsolete."
    	::= { qbSysEventsGroup 10 }

    qbSysAlarmHistoryClearAllCtl OBJECT-TYPE
    	SYNTAX      INTEGER {
                    ready(1),
                    clear(2)
                }
    	MAX-ACCESS  read-write
    	STATUS      current
    	DESCRIPTION
        	"Setting this object to 'clear(2)' removes all entries from
        	the qbSysAlarmHistoryTable, the qbSysEventHistoryTable and the 
        	qbSysNotificationHistoryTable. 
        	 When read, this object always returns the
        	value 'ready(1)'."
    	::= { qbSysEventsGroup 11 }

--
-- The Event Id Table. This table contains a list of events, their
-- names,and trap status.
--
--
    qbSysEventIdTable OBJECT-TYPE
    	SYNTAX      SEQUENCE OF QbSysEventIdEntry
    	MAX-ACCESS  not-accessible
    	STATUS      current
    	DESCRIPTION
        	"A table of event information for each identifier."
    	::= { qbSysEventsGroup 12 }

    qbSysEventIdEntry OBJECT-TYPE
    	SYNTAX      QbSysEventIdEntry
    	MAX-ACCESS  not-accessible
    	STATUS      current
    	DESCRIPTION
        	"Information for a particular event id."
    	INDEX       { qbSysEventDescrId }
    	::= { qbSysEventIdTable 1 } 

    QbSysEventIdEntry ::= SEQUENCE {
		qbSysEventDescrId       Unsigned32,
       	qbSysEventIdName       	DisplayString,
		qbSysEventIdSeverity	QbEventSeverity, 
		qbSysEventIdSASeverity  QbEventSeverity,
 		qbSysEventAsTrap	TruthValue
	}

    qbSysEventDescrId  OBJECT-TYPE
	SYNTAX	   Unsigned32
	MAX-ACCESS not-accessible
	STATUS	   current
	DESCRIPTION
		" The unique event identifier."
	::= { qbSysEventIdEntry 1 }

     qbSysEventIdName OBJECT-TYPE
    	SYNTAX      DisplayString (SIZE (1..64))
    	MAX-ACCESS  read-only
    	STATUS      current
    	DESCRIPTION
        	"The textual name of the event."
    	::= { qbSysEventIdEntry 2 }

    qbSysEventIdSeverity OBJECT-TYPE	
        SYNTAX	    QbEventSeverity 
    	MAX-ACCESS  read-only
    	STATUS      current
    	DESCRIPTION
        	"The severity of the event."
    	::= {  qbSysEventIdEntry 3 }  
    	
    qbSysEventIdSASeverity OBJECT-TYPE	
        SYNTAX	    QbEventSeverity 
    	MAX-ACCESS  read-only
    	STATUS      current
    	DESCRIPTION 
        	"The severity of the alarm when it is Service Affecting."
    	::= {  qbSysEventIdEntry 4 }  
 
     qbSysEventAsTrap OBJECT-TYPE
    	SYNTAX      TruthValue
    	MAX-ACCESS  read-only
    	STATUS      current
    	DESCRIPTION
        	"If true, this Event initiates an SNMP Trap."
    	::= { qbSysEventIdEntry 5}

--
-- The Alarm Id Table. This table contains a list of alarms, their
-- names,and trap status.
--
--
    qbSysAlarmIdTable OBJECT-TYPE
    	SYNTAX      SEQUENCE OF QbSysAlarmIdEntry
    	MAX-ACCESS  not-accessible
    	STATUS      current
    	DESCRIPTION
        	"A table of alarm information for each identifier"
    	::= { qbSysEventsGroup 13 }

    qbSysAlarmIdEntry OBJECT-TYPE
    	SYNTAX      QbSysAlarmIdEntry
    	MAX-ACCESS  not-accessible
    	STATUS      current
    	DESCRIPTION
        	"Information for a particular alarm id."
    	INDEX       { qbSysAlarmId }
    	::= { qbSysAlarmIdTable 1 } 

    QbSysAlarmIdEntry ::= SEQUENCE {
	        qbSysAlarmDescrId       Unsigned32,
       		qbSysAlarmIdName       	DisplayString,
       		qbSysAlarmIdSeverity    QbEventSeverity,
       		qbSysAlarmIdSASeverity  QbEventSeverity,	       				
		qbSysAlarmAsTrap	TruthValue
	}


   qbSysAlarmDescrId  OBJECT-TYPE
	SYNTAX	   Unsigned32
	MAX-ACCESS not-accessible
	STATUS	   current
	DESCRIPTION
		" The unique alarm identifier."
	::= { qbSysAlarmIdEntry 1 }

     qbSysAlarmIdName OBJECT-TYPE
    	SYNTAX      DisplayString (SIZE (1..64))
    	MAX-ACCESS  read-only
    	STATUS      current
    	DESCRIPTION
        	"The textual name of the alarm."
    	::= { qbSysAlarmIdEntry 2 }

    qbSysAlarmIdSeverity OBJECT-TYPE	
        SYNTAX	    QbEventSeverity 
    	MAX-ACCESS  read-only
    	STATUS      current
    	DESCRIPTION
        	"The severity of the alarm."
    	::= {  qbSysAlarmIdEntry 3 } 
    	
    
    qbSysAlarmIdSASeverity OBJECT-TYPE	
        SYNTAX	    QbEventSeverity 
    	MAX-ACCESS  read-only
    	STATUS      current
    	DESCRIPTION
        	"The severity of the alarm when it is Service Affecting."
    	::= {  qbSysAlarmIdEntry 4 }   	
 
     qbSysAlarmAsTrap OBJECT-TYPE
    	SYNTAX      TruthValue
    	MAX-ACCESS  read-only
    	STATUS      current
    	DESCRIPTION
        	"If true, this Alarm initiates an SNMP trap."
    	::= { qbSysAlarmIdEntry 5 }

--
    qbSysNotificationHistoryTable OBJECT-TYPE
    	SYNTAX      SEQUENCE OF QbSysNotificationHistoryEntry
    	MAX-ACCESS  not-accessible
    	STATUS      current
    	DESCRIPTION
        	"A table of Notifications in the order that they were generated.
        	Currently these Notifications include qbSysUnsolicitedEvents and 
        	qbSysConfigurationEvents."
    	::= { qbSysEventsGroup 14 }

    qbSysNotificationHistoryEntry OBJECT-TYPE
    	SYNTAX      QbSysNotificationHistoryEntry
    	MAX-ACCESS  not-accessible
    	STATUS      current
    	DESCRIPTION
        	"Information about a single Notification."
    	INDEX       { qbSysNotificationHistoryIndex }
        ::= { qbSysNotificationHistoryTable 1 }

    QbSysNotificationHistoryEntry ::= SEQUENCE {
    	qbSysNotificationHistoryIndex      Unsigned32, 
    	qbSysNotificationOID			   OBJECT IDENTIFIER,
		qbSysNotificationHistoryType	   QbNotificationType,
		qbSysNotificationHistoryTypeId	   Unsigned32,
		qbSysNotificationHistoryAction	   QbNotificationAction,
    	qbSysNotificationHistoryResource   OBJECT IDENTIFIER,   
    	qbSysNotificationHistoryCookie		Unsigned32,
    	qbSysNotificationHistoryDateTime   DateAndTimeForm,
		qbSysNotificationHistoryAlarmCondition   QbNotificationAlarmCondition,
		qbSysNotificationHistoryServiceAffecting QbEventSrvAffect
		
   	}

    qbSysNotificationHistoryIndex OBJECT-TYPE
    	SYNTAX      Unsigned32
    	MAX-ACCESS  not-accessible
    	STATUS      current
    	DESCRIPTION
        	"A unique  number of the 
        	entry."
    	::= { qbSysNotificationHistoryEntry 1 }              
    	
    qbSysNotificationOID OBJECT-TYPE
    	SYNTAX      OBJECT IDENTIFIER
    	MAX-ACCESS  read-only
    	STATUS      current
    	DESCRIPTION
        	"Indicates OID of the Notifcation that this entry refers. Though primarily
        	intended to be the qbSysUnsolicitedEvent or qbSysConfigurationEvent OID, this
        	value could also be another NOTIFICATION OID, for example a standard SNMP
        	NOTIFICATION."
        ::= { qbSysNotificationHistoryEntry 2 }             	

    qbSysNotificationHistoryType OBJECT-TYPE
	SYNTAX	QbNotificationType
	MAX-ACCESS	read-only
	STATUS		current
	DESCRIPTION
		"The type of Resource Event this notification represents.  If this is 
	a qbAlarm Notification, then the qbSysNotificationHistoryId refers to an entry 
	in the qbSysAlarmIdTable. If it is of type qbEvent, the qbSysNotificationHistoryId 
	refers to an entry in the qbSysEventIdTable."
    	::= { qbSysNotificationHistoryEntry 3 }

    qbSysNotificationHistoryTypeId OBJECT-TYPE
	SYNTAX	Unsigned32
	MAX-ACCESS	read-only
	STATUS		current
	DESCRIPTION
		"This Id can optioanlly refer to a structure that augments the Notification."
	::= { qbSysNotificationHistoryEntry 4 }
    
    qbSysNotificationHistoryAction OBJECT-TYPE
	SYNTAX QbNotificationAction
	MAX-ACCESS	read-only
	STATUS		current
	DESCRIPTION
		"The resource action that caused this event."
    	::= { qbSysNotificationHistoryEntry 5 }

    qbSysNotificationHistoryResource OBJECT-TYPE
	SYNTAX OBJECT IDENTIFIER
	MAX-ACCESS	read-only
	STATUS		current
	DESCRIPTION
		"The Resource to which this entry corresponds. For example, if the Notication
		refers to Module removal, the resource would be the OID 'qbSysModuleOperStatus',
		including the instance ID of the Module removed."
    	::= { qbSysNotificationHistoryEntry 6 }

    qbSysNotificationHistoryCookie OBJECT-TYPE
    SYNTAX Unsigned32
    MAX-ACCESS read-only
    STATUS		current
    DESCRIPTION
    	"This cookie is used to store augmenting information pertaining to this
    	Notification. By convention, the cookie contains the value of the object
    	'pointed' to by qbSysNotificationHistoryResource. If this value is not 
    	syntactically consistent with the qbSysNotificationHistoryResource, then
    	it is by convention set to '0'."
    	::= { qbSysNotificationHistoryEntry 7 }
    	 
    qbSysNotificationHistoryDateTime OBJECT-TYPE
    	SYNTAX      DateAndTimeForm
    	MAX-ACCESS  read-only
    	STATUS      current
    	DESCRIPTION
        	"The time when this Notification was generated."
    	::= { qbSysNotificationHistoryEntry 8 }

   qbSysNotificationHistoryAlarmCondition OBJECT-TYPE
        SYNTAX	    QbNotificationAlarmCondition 
    	MAX-ACCESS  read-only
    	STATUS      current
    	DESCRIPTION
        	"The alarm condition of the Notification."
    	::= { qbSysNotificationHistoryEntry 9 }  

   qbSysNotificationHistoryServiceAffecting OBJECT-TYPE
   		SYNTAX	QbEventSrvAffect
   		MAX-ACCESS	read-only
   		STATUS		current
   		DESCRIPTION
   			"If this Notification's  QbNotificationType is an alarm or event, then this obejct 
   			identifies whether the corresponding alarm or event was service affecting. Otherwise,
   			it is nonServiceAffecting."
   		::= { qbSysNotificationHistoryEntry 10 } 
 
--
-- Notification History Table Scalars.
--   	
    qbSysNotificationHistoryMaxTableSize OBJECT-TYPE
    	SYNTAX      Integer32 (1..65535)
    	UNITS       "number of events"
    	MAX-ACCESS  read-only
    	STATUS      current
    	DESCRIPTION
        	"The maximum number of entries in the NotificationHistoryTable. 
        	When the number
        	of entries gets larger than this size, older entries are
        	discarded." 
    	::= { qbSysEventsGroup 15 }
-- 
-- Filter information
-- 
    qbSysNotificationHistoryOutFilterLevel OBJECT-TYPE
    	SYNTAX      QbEventSeverity 
    	MAX-ACCESS  read-only
    	STATUS      obsolete
    	DESCRIPTION
        	"obsolete."
    	::= { qbSysEventsGroup 16 }

    qbSysNotificationHistoryOutFilterDateTime OBJECT-TYPE
    	SYNTAX      DateAndTimeForm
    	MAX-ACCESS  read-write
    	STATUS      obsolete
    	DESCRIPTION
        	"obsolete."
    	::= { qbSysEventsGroup 17 }

    qbSysNotificationHistoryClearAllCtl OBJECT-TYPE
    	SYNTAX      INTEGER {
                    ready(1),
                    clear(2)
                }
    	MAX-ACCESS  read-write
    	STATUS      obsolete
    	DESCRIPTION
        	"obsolete."
    	::= { qbSysEventsGroup 18 }
    	
    qbSysAlarmHistoryLastIndex OBJECT-TYPE
    	SYNTAX		INTEGER
    	MAX-ACCESS  read-only
    	STATUS		current
    	DESCRIPTION 
    		"The index of the last entry in the qbSysAlarmHistoryTable, in time-order."
    	::= { qbSysEventsGroup 19 }
    	
    qbSysEventHistoryLastIndex OBJECT-TYPE
    	SYNTAX	INTEGER
    	MAX-ACCESS  read-only
    	STATUS		current
    	DESCRIPTION 
    		"The index of the last entry in the qbSysEventHistoryTable, in time-order."
    	::= { qbSysEventsGroup 20 }    
    	
   qbSysGlobalHistoryLastIndex OBJECT-TYPE
    	SYNTAX	INTEGER
    	MAX-ACCESS  read-only
    	STATUS		current
    	DESCRIPTION 
    		"This is a currently private value that can be used to retrieve the last entry in
    		the qbSysNotificationHistoryTable, in time-order."
    	::= { qbSysEventsGroup 21 }    
    	


-- ****************************************************************
-- The module group - this table lists all IOAS cards.  
--  
-- ****************************************************************

    qbSysModuleTable OBJECT-TYPE
	SYNTAX        SEQUENCE OF QbSysModuleEntry
    	MAX-ACCESS    not-accessible
    	STATUS        current
    	DESCRIPTION   
		"A list of IOAS's cards.  The number of entries is
         the number of cards in the IOAS chassis."
    ::= { qbSysModuleGroup 1 }

    qbSysModuleEntry OBJECT-TYPE
    	SYNTAX        QbSysModuleEntry
    	MAX-ACCESS    not-accessible
    	STATUS        current
    	DESCRIPTION  
		"Entry containing information about one module in
         the chassis."
    	INDEX         { qbSysModuleSlot }
    	::= { qbSysModuleTable 1 }

    QbSysModuleEntry ::=
    	SEQUENCE {
                qbSysModuleSlot
                        INTEGER,
                qbSysModuleType
                        INTEGER,
                qbSysModuleName
                        DisplayString,
                qbSysModuleOperStatus
                        INTEGER,
                qbSysModuleAdminStatus
                        INTEGER,
                qbSysModuleTestResult
                        INTEGER,
                qbSysModuleNumPorts
                        INTEGER,
                qbSysModulePortStatus
                        OCTET STRING,
                qbSysModuleModel
			DisplayString,
		qbSysModuleSerialNum	
			DisplayString,			
                qbSysModuleEqId
                        DisplayString,
                qbSysModuleHwVersion
                        DisplayString,
                qbSysModuleSwVersion
                        DisplayString,
                qbSysModuleProtectionMode
                        ProtectionMode, 
		qbSysModuleLastSwitchoverTime
			TimeStamp,
		qbSysModuleSwitchoverReason
			INTEGER,
		qbSysModuleLedStatus
			OCTET STRING,
		qbSysModuleProductName
			DisplayString,    
	        qbSysModuleTestLeds
			INTEGER   
	}

    qbSysModuleSlot OBJECT-TYPE
        SYNTAX        INTEGER (1..15)
        MAX-ACCESS    read-only
        STATUS        current
        DESCRIPTION   
		"This value is determined by the OAS slot number
         where the module is located.  Valid range is from 1
         to 15 for QB5000 and from 1 to 7 for QB3000."
        ::= { qbSysModuleEntry 1 }

    qbSysModuleType OBJECT-TYPE
        SYNTAX        INTEGER {
                main(1),	-- WAN module
                dws(2),		-- DWS card
		switchProc(3),	-- Switch processor module
		switch(4),      -- Switch fabric module   
		q155(5),	-- Quad card
		vt155(6),	-- VT card
		s622(7),     	-- S622
		dws622sw(8),    -- DWS 622
		q155-T(9),      -- Quad card with timing children card 
		vt155-T(10),	-- VT card with timing children card 
		s622-T(11),     -- s622 card with timing children card 
		switchGiga2(15),  -- 2.5G ATM Switch card for QB3000
		syscon(17),	  -- System controller
                other(18),	 --  none of the following
                empty(19),	--  nothing installed
                enhSwitchProc(20),  -- enhanced Switch processor module
                dws622w(21),       -- DWS 622-W
                dws155s(22),      -- DWS 155-S
                sysconII(23),     -- System controller II
                dws622s(24),      -- DWS 622-S
                es24-10-100(25),   -- 24ES10/100Tx, 24 port ethernet int   
                t1E1-16(26),       -- 16DS1/E1, 16 port DS1 interface
                s622LR(27),       -- S622 Long Range
                s622LR-T(28),     -- S622 Long range with Timmig card 
		           dws155sw(29),	  -- Gigabit ethernnet switch module
             q155LR(30),	      -- Q155 Long Range
				   q155LR-T(31),	 -- Q155 Long Range with Timming card
				   gigesw(32),	    -- Gigabit ethernnet switch module
             unknown(1000)   -- unknown module type with unused product code        
                }
        MAX-ACCESS    read-only
        STATUS        current
        DESCRIPTION 
		"The module type."
        ::= { qbSysModuleEntry 2 }

    qbSysModuleName OBJECT-TYPE
        SYNTAX        DisplayString (SIZE (0..20))
        MAX-ACCESS    read-write
        STATUS        current
        DESCRIPTION  
               "A descriptive string used by network administrator
                 to name the module."
        ::= { qbSysModuleEntry 3 }

    qbSysModuleOperStatus OBJECT-TYPE
        SYNTAX        INTEGER {   
		other(1),	-- none of the following
		empty(2),	-- slot is empty and cleared 
		init(3),	-- initializing
		recovery(4),    -- recovering
		inService(5),   -- status ok   
		removed(6),     -- slot is empty but not cleared
		failed(7)   	-- out of service        
        }
        MAX-ACCESS    read-only
        STATUS        current
        DESCRIPTION  
		"The operational status of the module.  If the status
		is not ok, the value of the moduleTestResult gives more
		detailed information about the module's failure
		condition(s)."
        ::= { qbSysModuleEntry 4 }

    qbSysModuleAdminStatus OBJECT-TYPE
        SYNTAX        INTEGER {
                               other(1),
                               reset(2),
                               enable(3),
                               disable(4),
                               clearslot(5)
                      }
        MAX-ACCESS    read-write
        STATUS        current
        DESCRIPTION 
		"This object, when read, returns one of the
         following results:
                	other(1):   module permanently enabled
                	enable(3):  module currently enabled
                	disable(4): module currently disabled
                	clearslot(5): used to clear slot
         Setting this object to one of the acceptable values
         gives the following results:
                    other(1):   gives an error
                    reset(2):   resets the module
                    enable(3):  if the module status is configurable,
                                      enables the module, else gives error
                    disable(4): if the module status is configurable,
                                      disables the module, else gives error
          Setting this object to any other value results in
                      an error. Note that, currently, this object 'readonly'"
        ::= { qbSysModuleEntry 5 }

    qbSysModuleTestResult OBJECT-TYPE
        SYNTAX        INTEGER (0..65535)
        MAX-ACCESS    read-only
        STATUS        current
        DESCRIPTION  
		"The result of the module's self test.  A zero
         indicates that the module passed all tests.  Bits
         set in the result indicate error conditions."
        ::= { qbSysModuleEntry 6 }

    qbSysModuleNumPorts OBJECT-TYPE
        SYNTAX        INTEGER (0..255)
        MAX-ACCESS    read-only
        STATUS        current
        DESCRIPTION  
               "The number of ports supported by the module."
        ::= { qbSysModuleEntry 7 }

    qbSysModulePortStatus OBJECT-TYPE
        SYNTAX        OCTET STRING (SIZE (0..32))
        MAX-ACCESS    read-only
        STATUS        current
        DESCRIPTION  
               "A series of bytes containing status information
                about the module and each of the ports in the module.
                The first byte contains the status of the module
                (same value as moduleStatus), and subsequent bytes
                contain statuses for the first through last ports
                on the module (same value as ifOperStatus)."
        ::= { qbSysModuleEntry 8 }

    qbSysModuleModel OBJECT-TYPE
        SYNTAX        DisplayString (SIZE (0..20))
        MAX-ACCESS    read-only
        STATUS        current
        DESCRIPTION 
		"The manufacturer's model part number for the module."
        ::= { qbSysModuleEntry 9 }

    qbSysModuleSerialNum OBJECT-TYPE
        SYNTAX        DisplayString (SIZE (0..20))
        MAX-ACCESS    read-only
        STATUS        current
        DESCRIPTION 
		"The manufacturer's serial number for the module."
        ::= { qbSysModuleEntry 10 }

   qbSysModuleEqId OBJECT-TYPE
        SYNTAX        DisplayString (SIZE (0..20))
        MAX-ACCESS    read-only
        STATUS        current
        DESCRIPTION 
		"The manufacturer's equipment identifier."
        ::= { qbSysModuleEntry 11 }

    qbSysModuleHwVersion OBJECT-TYPE
        SYNTAX        DisplayString (SIZE (0..12))
        MAX-ACCESS    read-only
        STATUS        current
        DESCRIPTION   
  		"The hardware version of the module."
        ::= { qbSysModuleEntry 12 }

    qbSysModuleSwVersion OBJECT-TYPE
        SYNTAX        DisplayString (SIZE (0..40))
        MAX-ACCESS    read-only
        STATUS        current
        DESCRIPTION  
		"The software version of the module."
        ::= { qbSysModuleEntry 13 }


 qbSysModuleProtectionMode OBJECT-TYPE
        SYNTAX        ProtectionMode
        MAX-ACCESS    read-write
        STATUS        current
        DESCRIPTION  
		"Protection mode of a module."
    	DEFVAL      { unprotected }
        ::= { qbSysModuleEntry 14 }   

    qbSysModuleLastSwitchoverTime OBJECT-TYPE
	SYNTAX	   TimeStamp
	MAX-ACCESS read-only
	STATUS     current
	DESCRIPTION		
	        "The value of sysUpTime at the last switchover of the 
		switch cards. 
		The value is zero if there has been no switchover since
		agent initialization."
	::= { qbSysModuleEntry  15 }
    
     qbSysModuleSwitchoverReason OBJECT-TYPE
	SYNTAX	   INTEGER {
			none(1),
			unknown(2),
			userInitiated(3),
			moduleFailed(4),
			moduleRecovered(5), 
			moduleRemoved(6),  -- online removal
			moduleInserted(7)  -- online insertion
			}
	MAX-ACCESS read-only
	STATUS     current
	DESCRIPTION		
	        "The reason for the last switch card switchover.
		
			The value is none(1) if there has been no switchover since
			agent initialization."
	::= { qbSysModuleEntry  16 }

  qbSysModuleLedStatus OBJECT-TYPE
	SYNTAX	   OCTET STRING(SIZE (1..20))
	MAX-ACCESS read-only
	STATUS     current
	DESCRIPTION
			"Led OCTET String
			A series of bytes containing status information
			about each of leds in the module. For every led
			two bytes are allocated. The first byte indicates the led type,
			the second byte indicates the led state (on/off). 
			Therefore byte string size  
			is different depending of the module
			types. The leds of modules as follows: 
		SYSCON:
		1 CR(0)
		2 MJ(1)
		3 MN(2)
		4 MNTC(3)
		5 Fault(4)
		6 ACO(5)
		
		SWITCH/SWPROC - 
		1 FAULT(1)
		2 ACTIVE(2)

		WAN/MOC12
		1 FAULT(0)
		2 ACTIVE(1)
		3 LOS(2)

		AU-1
		1 FAULT(0)
		2 ACTIVE(1)
		3 LOS(2)
		"
	::= { qbSysModuleEntry  17 }
	
	
	qbSysModuleProductName OBJECT-TYPE                                              
	    SYNTAX        DisplayString (SIZE (0..20))                           
	    MAX-ACCESS    read-only                                             
	    STATUS        current                                                
	    DESCRIPTION                                                          
	           "A descriptive string used by vendor           
	             to name the module."                                        
	    ::= { qbSysModuleEntry 18 }                                           
    
   qbSysModuleTestLeds OBJECT-TYPE
    	SYNTAX      INTEGER {
        	        ready(1),
                	test(2)
                	}
    	MAX-ACCESS  read-write
    	STATUS      current
    	DESCRIPTION
        	"This object tests the module LEDs. If the object is read, 
		it should return ready. Setting the value test will
		initiate the LED test for this card."
    	::= { qbSysModuleEntry 19 }
	
   
-- 
--	APS Objects
--	This table allows a user to create protection groups 
--	and execute APS related commands.
-- 
   
   qbSysApsAlarmStatus OBJECT-TYPE
	SYNTAX        INTEGER {
		      enabled(1),
		      disabled(2)
	}
    	MAX-ACCESS    read-write
    	STATUS        current
    	DESCRIPTION 
	       "Indicates whether APS alarms should be
               generated for this interface."
	DEFVAL        { enabled }         
    ::= { qbSysModuleGroup 2 }

  qbSysModuleApsTable OBJECT-TYPE
	SYNTAX        SEQUENCE OF QbSysModuleApsEntry
    	MAX-ACCESS    not-accessible
    	STATUS        current
    	DESCRIPTION   
		"This tables lists OAS's modules.  The number of entries 
		is equals the number of cards in an OAS chassis."
    ::= { qbSysModuleGroup 3}

    qbSysModuleApsEntry OBJECT-TYPE
    	SYNTAX        QbSysModuleApsEntry
    	MAX-ACCESS    not-accessible
    	STATUS        current
    	DESCRIPTION  
		"Entry contains module APS information."
    	INDEX         { qbSysModuleSlot }
    	::= { qbSysModuleApsTable 1 }

    QbSysModuleApsEntry ::=
    	SEQUENCE {
                qbSysModuleApsGroupAdminMode
                        QbApsGroupMode,
                qbSysModuleApsGroupOperMode
                        INTEGER,
                qbSysModuleApsSwitchAdminMode
                        QbApsSwitchMode,
                qbSysModuleApsSwitchOperMode
                        INTEGER,
                qbSysModuleApsLastSwitchoverTime
                        TimeStamp
	}

    qbSysModuleApsGroupAdminMode OBJECT-TYPE
        SYNTAX        QbApsGroupMode
        MAX-ACCESS    read-write
        STATUS        current
        DESCRIPTION 
	       "This object is used to set the protection
	       mode for a given slot. 
	       Note: Only main-a, main-b, au-1, au-2, au-3, au-4, au-5	
	       au-6, au-7 or au-8 may be selected for.
	       this object. Only slots containing SONET interfaces are
	       valid."
        ::= { qbSysModuleApsEntry 1 }

    qbSysModuleApsGroupOperMode OBJECT-TYPE
        SYNTAX        INTEGER {
		      unavailable(1),
		      unprotected(2),
		      active(3),
		      standby(4)
	}
        MAX-ACCESS    read-only
        STATUS        current
        DESCRIPTION  
               "This object indicates a protection mode of a given
	       slot within an SPG group."
        ::= { qbSysModuleApsEntry 2 }

    qbSysModuleApsSwitchAdminMode OBJECT-TYPE
        SYNTAX       QbApsSwitchMode
        MAX-ACCESS    read-write
        STATUS        current
        DESCRIPTION  
		"This object is used to allow a user execution APS
		switch commands for a given slot."
        ::= { qbSysModuleApsEntry 3 }

    qbSysModuleApsSwitchOperMode OBJECT-TYPE
        SYNTAX       INTEGER {
		        noop(1),
                        clear(2),
                        lockout(3),
                        force(4),
                        manual(5),
			sf(6),
			sd(7),
			fail(8)
	}
        MAX-ACCESS    read-only
        STATUS        current
        DESCRIPTION  
		"The object indicates the current highest priority
		switching state of the slot.
		noop - this value should be returned by a read request 
		       when no switch command has been written to a
		       given slot since initialization.
		sf   - signal failure on the slot
		sd   - signal degrade on the slot
		fail     - equipment fail or removed "
        ::= { qbSysModuleApsEntry 4 }

    qbSysModuleApsLastSwitchoverTime OBJECT-TYPE
	SYNTAX	   TimeStamp
	MAX-ACCESS read-only
	STATUS     current
	DESCRIPTION		
	        "The value of sysUpTime at the time of the last switchover 
		of the a given card. 
		The value is zero if there has not been a switchover since
		agent initialization."
	::= { qbSysModuleApsEntry  5 }

-- ****************************************************************
-- The port group - this group contains a list of all OAS ports.
-- ****************************************************************
--
-- Implementation of the port group is current for Quantum Bridge 
-- products.
-- Note that this group has not been implemented for Release 1.

    qbSysPortTable OBJECT-TYPE
        SYNTAX        SEQUENCE OF QbSysPortEntry
        MAX-ACCESS    not-accessible
        STATUS        current
        DESCRIPTION   
		"A list of port entries.  The number of entries is
        determined by the number of modules in the chassis
        and the number of ports in each module."
        ::= { qbSysPortGroup 1 }

     qbSysPortEntry OBJECT-TYPE
        SYNTAX        QbSysPortEntry
        MAX-ACCESS    not-accessible
        STATUS        current
        DESCRIPTION   
		"Entry containing information for a particular port
        in a module."
        INDEX         { qbSysModuleSlot, qbSysPort}
        ::= { qbSysPortTable 1 }

    QbSysPortEntry ::=
        SEQUENCE {
                qbSysPort
                        INTEGER,
                qbSysPortName
                        DisplayString,
                qbSysPortType
                        INTEGER,
                qbSysPortOperStatus
                        INTEGER,
                qbSysPortIfIndex
                        Unsigned32,
		qbSysPortLoopbackConfig
			INTEGER	
        }

     qbSysPort OBJECT-TYPE
        SYNTAX        INTEGER (1..255)
        MAX-ACCESS    read-only
        STATUS        current
        DESCRIPTION  
		"A port number that uniquely identifies this port
         within a card.  The value is determined by the
         location of the port in the module.  Valid entries
         are 1 to the value of moduleNumPorts for this module."
        ::= { qbSysPortEntry 1 }

    qbSysPortName OBJECT-TYPE
        SYNTAX        DisplayString (SIZE (0..20))
        MAX-ACCESS    read-only
        STATUS        current
        DESCRIPTION   
		"A descriptive string used by the network administrator to name the port.
        This string has the same value as the ifName object"
        ::= { qbSysPortEntry 2 }

    qbSysPortType OBJECT-TYPE
        SYNTAX        INTEGER {
            unknown(1),       	-- none of the following
	    e10100BaseT(2),   	-- UTP 10/100 FEC Mbps port type
	    main(3),          	-- wan card OC12C port type
	    dws(4),		-- Passive optical network interface 1 - port card
            atmOc3(5) 	        -- OC-3 ATM OC-3 Edge card. 
            }
        MAX-ACCESS    read-only
        STATUS        current
        DESCRIPTION   
		"The physical layer port type."
        ::= { qbSysPortEntry 3 }

     qbSysPortOperStatus OBJECT-TYPE
        SYNTAX     INTEGER {
        other(1),       -- none of the following
        ok(2),          -- status ok
        minorFault(3),  -- minor problem
        majorFault(4)   -- major problem
                      }
        MAX-ACCESS    read-only
        STATUS        current
        DESCRIPTION   
		"The current operational status of the port."
        ::= { qbSysPortEntry 4 }

    qbSysPortIfIndex OBJECT-TYPE
        SYNTAX        Unsigned32 (1..2147483647)
        MAX-ACCESS    read-only
        STATUS        current
        DESCRIPTION   
		"The value of the instance of the ifIndex object,
                 defined in MIB-II, for the interface corresponding to this port."
        ::= { qbSysPortEntry 5 }
	
   qbSysPortLoopbackConfig OBJECT-TYPE
        SYNTAX        INTEGER {
			      unloop(1),
			      facility(2),
			      terminal(3)
		      }
        MAX-ACCESS    read-write
        STATUS        current
        DESCRIPTION   
	       "The current loopback state of the port. The
	       values mean:

	       unLoop
	       Not in the loopback state. A device that is not
	       capable of performing a loopback on this interface
	       will always return this value.

	       facility
	       The received signal at this interface is looped back
	       out through the corresponding transmitter in the return
	       direction.This test can be performed only on main card interfaces.

	       terminalLoop
		The signal that is about to be transmitted is connected
		to the associated incoming receiver.
		This test can be performed on main and dws interfaces."
        ::= { qbSysPortEntry 6 }

--
-- The Intelligent Terminal Device Table - this table contains a list of all IOTs that
-- connect to the Access Device PONs.
--
--  qbSysIotGroup      OBJECT IDENTIFIER ::= { qbSysObjects 8 }


    qbSysIotTable OBJECT-TYPE
	SYNTAX      SEQUENCE OF QbSysIotEntry
	MAX-ACCESS  not-accessible
	STATUS      current
	DESCRIPTION
		"A table of IOT devices in the system."
	::= { qbSysIotGroup 9 }

    qbSysIotEntry OBJECT-TYPE
	SYNTAX      QbSysIotEntry
	MAX-ACCESS  not-accessible
	STATUS      current
	DESCRIPTION
		"Information about a single IOT device in the system."
	INDEX       { qbSysIotSerialNumber }
	::= { qbSysIotTable 1 }

    QbSysIotEntry ::= 
	SEQUENCE {
		qbSysIotSerialNumber	Unsigned32,
		qbSysIoasDwsIfIndex	InterfaceIndex,
		qbSysIotAddr	        Unsigned32,
		qbSysIotDescr		DisplayString,
		qbSysIotName		DisplayString,
		qbSysIotLocation	DisplayString,
		qbSysIotSwVersion	DisplayString,
		qbSysIotHwVersion	DisplayString,
		qbSysIotOperStatus	INTEGER,
		qbSysIotAdminStatus	INTEGER,
		qbSysIotDsx1LineCoding  INTEGER,
		qbSysIotSerialStr	DisplayString,	
		qbSysIotRowStatus	RowStatus,
		qbSysIotManufSerialNum  DisplayString,
		qbSysIotType		QbIotType,
		qbSysIotProductName	DisplayString,
		qbSysIotSignalFmt	INTEGER,
		 qbSysIotRollSerialNumber Unsigned32,
		qbSysIotNumSlots        INTEGER
	}

    qbSysIotSerialNumber OBJECT-TYPE
	SYNTAX      Unsigned32 
	MAX-ACCESS  not-accessible
	STATUS      current
	DESCRIPTION
		   "The IOT serial number."
	::= { qbSysIotEntry 1 }

    qbSysIoasDwsIfIndex	OBJECT-TYPE
	SYNTAX      InterfaceIndex
	MAX-ACCESS  read-create
	STATUS      current
	DESCRIPTION
		"The IOT's DWS interface index. Indicates the interface index of the 
		IOAS DWS interface to which this IOT is attached."
	::= { qbSysIotEntry 2 }
    
   qbSysIotAddr OBJECT-TYPE  
	SYNTAX      Unsigned32 (0..2147483647)
	MAX-ACCESS  read-only
	STATUS      current
	DESCRIPTION
		"A Quantum Bridge identifier for the IOT device. This value can
		be changed if the IOAS is reset."
	::= { qbSysIotEntry 3 }

   qbSysIotDescr OBJECT-TYPE
	SYNTAX  DisplayString (SIZE (0..255))
	MAX-ACCESS  read-only
	STATUS  current
	DESCRIPTION
		"A textual description of the IOT. This value includes the full name and 
		version	identification of the system's hardware type, software 
		operating-system, and networking software."
	::= { qbSysIotEntry 4 }

   qbSysIotName OBJECT-TYPE
	SYNTAX  DisplayString (SIZE (0..255))
	MAX-ACCESS  read-create
	STATUS  current
	DESCRIPTION
		"An administratively-assigned name for this IOT."
	::= { qbSysIotEntry 5 }

   qbSysIotLocation OBJECT-TYPE
	SYNTAX  DisplayString (SIZE (0..255))
	MAX-ACCESS  read-only
	STATUS  current
	DESCRIPTION
		"The physical location of the IOT.  Note that, currently, this object readonly"
	::= { qbSysIotEntry 6 }

   qbSysIotSwVersion OBJECT-TYPE
        SYNTAX        DisplayString (SIZE(1..20))
        MAX-ACCESS    read-create
        STATUS        current
        DESCRIPTION
		  "When in the same set pdu as qbSysIotAdminStatus, this object indicates
		   the version of software that the IOT will boot from if qbSysIotAdminStatus
		   indicates a reset. If this object is not set, the default image will
		   be used.
		   When read, this value returns a null string. 
		   Note that the running IOT software version
		   can be retrieved from the qbSysIotFileTable entry described below."
        ::= { qbSysIotEntry 7 }

   qbSysIotHwVersion OBJECT-TYPE
        SYNTAX        DisplayString (SIZE(1..40))
        MAX-ACCESS    read-only
        STATUS        current
        DESCRIPTION   
	       "The hardware version of the module."
        ::= { qbSysIotEntry 8 }

   qbSysIotAdminStatus OBJECT-TYPE
        SYNTAX		INTEGER {
			reset(1),
			range(3),
			standby(4),
			enable(5),
			disable(6)
        }
        MAX-ACCESS    read-create
        STATUS        current
        DESCRIPTION 
		"This object, when read, returns one of the
                following results:
                	enable(5): IOT is currently operational
                	disable(6): IOT is currently disabled( range,
				    reset, standby,  maintenance, or resetToDefault mode). 
              	Setting this object to one of the acceptable values
                gives the following results:
		      reset(1):   resets the IOT. This is the 'software reset button' of the agent.
				  When set to 'reset(1)', the system will reset and reload its 
				  configuration from FLASH/NVRAM.
                      resetToDefault(2): When set to resetDefault(2), the system will delete all
			                 provisioned data for this
					 IOT and use default setings at	
					 initialization time.     
					 
					 For both 'reset(1)' and 'resetToDefault(2)', the default 
					 IOT software version will be used unless the set PDU
					 contains a value for qbSysIotSwVersion, in which case it will
					 be used.
		      range(3):	When set to 'range', the IOAS will
		                initiate or re-initiate the ranging
				process for the IOT.
		      standby(4): When set to 'standby', the IOAS will
		                halt communication with IOT, while
				retaining the associated connection
				parameters at both 
				the IOAS and IOT.
                      Setting this object to any other value results in
                      an error.
		      "
        ::= { qbSysIotEntry 9 }

   qbSysIotOperStatus OBJECT-TYPE  
	SYNTAX      INTEGER {
                    other(1),
                    running(2),
		    down(3),
		    standBy(4),
		    rangingInProgress(5),
                    fault(6),
                    maintenance(7),
		    inService(8)
         }
	MAX-ACCESS  read-only
	STATUS      current
	DESCRIPTION
		"This is the operational IOT status."
	::= { qbSysIotEntry 10 }

     qbSysIotDsx1LineCoding OBJECT-TYPE
          SYNTAX  INTEGER {
                     dsx1JBZS (1),
                     dsx1B8ZS (2),
                     dsx1HDB3 (3),
                     dsx1ZBTSI (4),
                     dsx1AMI (5),
                     other(6),
                     dsx1B6ZS(7)
                 }
          MAX-ACCESS  read-create
          STATUS  current
          DESCRIPTION
                 "This variable mirrors the dsx1LineCoding object
		  defined in the RFC2495. When the object is set to a new 
		  value it effects all 4 DS1 ports of the IOT.

		  NOte: The dsx1LineCoding value effects only 
		  one DS1 port." 
	::= { qbSysIotEntry  11 } 

    qbSysIotSerialStr OBJECT-TYPE
	SYNTAX       DisplayString (SIZE(1..20))
	MAX-ACCESS  read-create
	STATUS      current
	DESCRIPTION
		   "This string has the
		    following format for old IOTs(YYWK-PC-XXXXXX) where yy -
		    year, wk - week of  the year, and xxxxxx - serial
		    number.
		    For new IOT models the FSAN serial string has the
		    following format (QMBGXXXXXXXX) where XXXXXXXX -
		    a unique hexedecimal serial number(e.g.1F338BE3)."
	::= { qbSysIotEntry 12 }

    qbSysIotRowStatus OBJECT-TYPE
       SYNTAX      RowStatus
       MAX-ACCESS  read-create
       STATUS	   current
       DESCRIPTION
            "The status of this conceptual row.

	     This OBJECT can be set to:

		createAndGo(4)
            	destroy(6)

		Setting this object to active(1) when its value
		is already active(1) is a no-op.
			
		Setting this object to createAndGo(4) causes the agent
		to attempt to create and commit the row based on
		the contents of the objects in the row.  If all necessary
		information is present in the row and the values are
		acceptable to the agent, the agent will change the
		status to active(1).  If any of the necessary objects
		are not available, the agent will reject the creation
		request.	

		Setting this object to destroy(6) will remove the corresponding
		entry in this table.

            The following values may be read:
            	active(1)."
	::= { qbSysIotEntry  13 } 

   qbSysIotManufSerialNum OBJECT-TYPE
	SYNTAX       DisplayString (SIZE(1..20))
	MAX-ACCESS  read-only
	STATUS      current
	DESCRIPTION
		  "The IOT manufecturing serial number string." 
	::= { qbSysIotEntry 14 }

   qbSysIotType OBJECT-TYPE
	SYNTAX      QbIotType
	MAX-ACCESS  read-create
	STATUS      current
	DESCRIPTION
		   "The IOT type."
	::= { qbSysIotEntry 15 }

   qbSysIotProductName OBJECT-TYPE
	SYNTAX  DisplayString (SIZE (0..255))
	MAX-ACCESS  read-only
	STATUS  current
	DESCRIPTION
		"An product name for this IOT."
	::= { qbSysIotEntry 16 }

    qbSysIotSignalFmt OBJECT-TYPE
	SYNTAX      INTEGER {
		    ds1(1),
		    e1(2)
		    }
	MAX-ACCESS  read-create
	STATUS      current
	DESCRIPTION
		   "The IOT signal format type."
	::= { qbSysIotEntry 17 }

   qbSysIotRollSerialNumber OBJECT-TYPE
   	SYNTAX      Unsigned32 
	MAX-ACCESS  read-create
	STATUS      current
	DESCRIPTION
		   "This object when reads, returns the serial number
		   of the selected IOT(the same as qbSysIotSerialNumber).  
		   When the object is set (the serial number must be
		   be different) the agent ralls all existing configuration	
		   from the old serial number to the serial number. As 
		   a result of this, this row is deleted and a new row
		   is  created in the table."
	::= { qbSysIotEntry 18 }

  qbSysIotNumSlots OBJECT-TYPE
        SYNTAX        INTEGER (0..3)
        MAX-ACCESS    read-only
        STATUS        current
        DESCRIPTION   "The number of slots in the IOT chassis available for
                      plug-in modules. QB616 contains 3 slots, all other
		      IOT return 0"
        ::= { qbSysIotEntry 19 }
--
-- IOT File Table - this table contains a list of Entries that provide the file information
-- for an IOT.
-- 
    qbSysIotFileTable OBJECT-TYPE
       SYNTAX      SEQUENCE OF QbSysIotFileEntry
       MAX-ACCESS  not-accessible
       STATUS      current
       DESCRIPTION
		"."
	 ::= { qbSysIotGroup 10 }

    qbSysIotFileEntry OBJECT-TYPE
       SYNTAX      QbSysIotFileEntry
       MAX-ACCESS  not-accessible
       STATUS      current
       DESCRIPTION
		"Information about files on a single IOT."
	 INDEX       { qbSysIotFileSerialNumber }
	 ::= {  qbSysIotFileTable 1 }

     QbSysIotFileEntry ::= SEQUENCE {
     qbSysIotFileSerialNumber     Unsigned32,  
	 qbSysIotFileAvailableVersion1	DisplayString,
  	 qbSysIotFileAvailableVersion2   DisplayString,
	 qbSysIotFileRunningVersion	    DisplayString,
	 qbSysIotFileAcceptedVersion		DisplayString,
  	 qbSysIotFileDownLoadVersion		DisplayString,  
  	 qbSysIotFileSysUpTime			TimeTicks,
  	 qbSysIotFileLastModification	TimeTicks,   
  	 qbSysIotFileAction				INTEGER,
  	 qbSysIotFileDownLoadStatus		INTEGER,
  	 qbSysIotFileErrorMsg			DisplayString
     }  
    
    qbSysIotFileSerialNumber OBJECT-TYPE
    	SYNTAX      Unsigned32 
		MAX-ACCESS  not-accessible
		STATUS      current
		DESCRIPTION
		   "The IOT serial number that these files should be associated with."
	::= { qbSysIotFileEntry 1 }
 
 	qbSysIotFileAvailableVersion1 OBJECT-TYPE
    	SYNTAX      DisplayString (SIZE (0..20))
    	MAX-ACCESS  read-only
    	STATUS      current
    	DESCRIPTION
        	"The name of a version currently available on this IOT in the first FLASH
        	region."
    	::= { qbSysIotFileEntry 2 }

    qbSysIotFileAvailableVersion2 OBJECT-TYPE
    	SYNTAX      DisplayString (SIZE (0..20))
    	MAX-ACCESS  read-only
    	STATUS      current
    	DESCRIPTION
        	"The name of a version currently running on this IOT in the 
        	second FLASH region."
    	::= { qbSysIotFileEntry 3 }

    qbSysIotFileRunningVersion OBJECT-TYPE
    	SYNTAX      DisplayString (SIZE (0..20))
    	MAX-ACCESS  read-only
    	STATUS      current
    	DESCRIPTION
        	"The name of the version currently running on this IOT."
    	::= { qbSysIotFileEntry 4 }   
    	
     qbSysIotFileAcceptedVersion OBJECT-TYPE
    	SYNTAX      DisplayString (SIZE (0..20))
    	MAX-ACCESS  read-only
    	STATUS      current
    	DESCRIPTION
        	"The name of a version currently accepted as the default image
        	 on this IOT. If no image is currently accepted, this entry will
        	 be null."
    	::= { qbSysIotFileEntry 5 } 
  	
     qbSysIotFileDownLoadVersion OBJECT-TYPE
    	SYNTAX      DisplayString (SIZE (0..20))
    	MAX-ACCESS  read-write
    	STATUS      current
    	DESCRIPTION
        	"The name of a version of a file that the agent should attempt 
        	to download the next time qbSysIotFileAction is set to download."
    	::= { qbSysIotFileEntry 6 } 
	   	 	                                          
     qbSysIotFileSysUpTime OBJECT-TYPE
    	SYNTAX      TimeTicks
    	MAX-ACCESS  read-only
    	STATUS      current
    	DESCRIPTION
        	"The value of time since this IOT was initialized."
    	::= { qbSysIotFileEntry 7 }      	               
   	                                          
     qbSysIotFileLastModification OBJECT-TYPE
    	SYNTAX      TimeTicks
    	MAX-ACCESS  read-only
    	STATUS      current
    	DESCRIPTION
        	"The value of sysUpTime entry was last modified."
    	::= { qbSysIotFileEntry 8 }    
    	
     qbSysIotFileAction OBJECT-TYPE  
     	SYNTAX  INTEGER { 
     				 noAction(1),
                     accept (2),
                     downLoad (3),
                     downLoadAbort(4)
                 	}
     	MAX-ACCESS  read-write
    	STATUS      current
    	DESCRIPTION
        	"This command allow a remote initiation of a file based command.
        	
        	Currently, by convention, if this object's value is set to 'accept',
        	the SNMP response determines its success.
        	
        	If this object's value is succesfully set to 'downLoad' the application 
        	can monitor the action's progress by polling the 
        	qbSysIotFileDownLoadStatus and qbSysIotFileErrorMsg objects.
        	
        	DownLoadAbort ends the current download."
    	::= { qbSysIotFileEntry 9 }
   	
     qbSysIotFileDownLoadStatus OBJECT-TYPE 
    	SYNTAX  INTEGER {
                     idle (1),
                     busy (2),
                     failed (3)  
                     }
    	MAX-ACCESS  read-only
    	STATUS      current
    	DESCRIPTION
        	"The Status of the current download."
    	::= { qbSysIotFileEntry 10 }  
    	
     qbSysIotFileErrorMsg OBJECT-TYPE
    	SYNTAX      DisplayString (SIZE (0..50))
    	MAX-ACCESS  read-only
    	STATUS      current
    	DESCRIPTION
        	"The error message, if any, pertaining to the current download."
    	::= { qbSysIotFileEntry 11 } 
-- ****************************************************************
-- The interfaces group
-- ****************************************************************
--
-- The qbSysIfLocation Table provides a logical (ifIndex) to physical (iot.slot.port)
-- mapping for the Quantum Bridge Access System.
--

   qbSysIfLocationTable OBJECT-TYPE
	SYNTAX      SEQUENCE OF QbSysIfLocationEntry
	MAX-ACCESS  not-accessible
	STATUS      current
	DESCRIPTION
		"The Quantum Bridge Interface location table. This table contains
		physical mapping information for the device interfaces." 
        ::= { qbSysInterfacesGroup 1 }

   qbSysIfLocationEntry OBJECT-TYPE
	SYNTAX      QbSysIfLocationEntry
	MAX-ACCESS  not-accessible
	STATUS      current
	DESCRIPTION
		"An entry in the Quantum Bridge Interface Location Table. 
		 Every row in the ifTable has a corresponding entry in this
		table which contains location information in iotaddr.slot.port 
		format."
	INDEX    { ifIndex }
	::= { qbSysIfLocationTable 1 }

    QbSysIfLocationEntry ::= 
	SEQUENCE {
		qbIfLocationSlot	QbIoasSlot,
		qbIfLocationAddr	Unsigned32,
		qbIfLocationPort	QbSysPortLoc,
		qbIfLocationType    	INTEGER,
		qbIfLocationSerialNumber	 Unsigned32		 
	}

    qbIfLocationSlot OBJECT-TYPE
	SYNTAX		QbIoasSlot 
	MAX-ACCESS	read-only
	STATUS		current
	DESCRIPTION
		"The slot number of the interface. If this is an IOT's interface
		the object is set to 0. "
		::= { qbSysIfLocationEntry 1 }


    qbIfLocationAddr OBJECT-TYPE
	SYNTAX		Unsigned32 
	MAX-ACCESS	read-only
	STATUS		current
	DESCRIPTION
		"The IOT address of the interface. If this is an IOAS's card
		 interface, the object is set to 0."
	::= { qbSysIfLocationEntry 2 }

   qbIfLocationPort	OBJECT-TYPE
	SYNTAX		QbSysPortLoc
	MAX-ACCESS	read-only
	STATUS		current
	DESCRIPTION
		"The port number of the interface."
	::= { qbSysIfLocationEntry 3 }

   qbIfLocationType OBJECT-TYPE
	SYNTAX INTEGER {
		ioas(1),
		iot(2)
	 } 
	MAX-ACCESS read-only
	STATUS       current
	DESCRIPTION
           "Indicates the entity to which this interface belongs: 1 - IOT, 2-IOAS."
    ::= { qbSysIfLocationEntry 4 }
    
    qbIfLocationSerialNumber OBJECT-TYPE
     SYNTAX	Unsigned32                      
     MAX-ACCESS read-only
     STATUS	current
     DESCRIPTION
     	"If the qbIfLocationType indicates that this is an IOT, this object contains
     	the IOT SerialNumber (as defined by qbSysIotSerialNumber) of the IOT to which 
     	this entry refers."
     ::= { qbSysIfLocationEntry 5}
     
-- ****************************************************************
-- Notifications
-- ****************************************************************

  qbSysNotificationPrefix OBJECT IDENTIFIER ::= { qbSysNotifications 0 }

  qbSysAlarm NOTIFICATION-TYPE
	OBJECTS {
		qbSysAlarmDateTime,
		qbSysAlarmSubsystem,
		qbSysAlarmSrvAffect,
		qbSysAlarmSeverity,
		qbSysAlarmCondition,
		qbSysAlarmId,
		qbSysAlarmMsg
    }
    STATUS      current
    DESCRIPTION
        "An SNMP trap definition for carrying Quantum Bridge system
        events. Some events have specific SNMP traps, such as linkUp
        or linkDown traps. (These are generally events with levels of
        info(3), warning(4), or fatal(5).) The events which do not
        have specific SNMP traps defined for them will be sent using
        this NOTIFICATION-TYPE if qbSysAlarmAsTrap is set to
        'true(1)'."
    ::= { qbSysNotificationPrefix 1 }

   qbSysEvent NOTIFICATION-TYPE
	OBJECTS {
		qbSysEventHistoryDateTime,
		qbSysEventHistorySubsystem,
		qbSysEventHistorySrvAffect,
		qbSysEventHistorySeverity,
		qbSysEventHistoryId,
		qbSysEventHistoryMsg
    }
    STATUS      current
    DESCRIPTION
        "An SNMP trap definition for carrying Quantum Bridge system
        events. Some events have specific SNMP traps, such as linkUp
        or linkDown traps. (These are generally events with levels of
        info(3), warning(4), or fatal(5).) The events which do not
        have specific SNMP traps defined for them will be sent using
        this NOTIFICATION-TYPE if qbSysEventAsTrap is set to
        'true(1)'."
    ::= { qbSysNotificationPrefix 2 }

    qbSysModuleDown NOTIFICATION-TYPE
	OBJECTS       { qbSysModuleSlot }
        STATUS        current
        DESCRIPTION   
		"A qbSysModuleDown trap signifies that the agent entity
                 has detected that the qbSysModuleStatus object in this
                 MIB has transitioned from the ok(2) state to one
                 of another state."
        ::= { qbSysNotificationPrefix 3}

    qbSysModuleInserted NOTIFICATION-TYPE
	OBJECTS       { qbSysModuleSlot, qbSysModuleType }
        STATUS        current
        DESCRIPTION 
		  "A qbSysModuleInserted trap signifies that the agent entity
                   has detected that a board has been inserted into a particular slot in 
                   the IOAS."
        ::= { qbSysNotificationPrefix 4}

     qbSysModuleRemoved NOTIFICATION-TYPE
	OBJECTS       { qbSysModuleSlot, qbSysModuleType }
        STATUS        current
        DESCRIPTION 
	       "A qbSysModuleRemoved trap signifies that the agent entity
                has detected that a board has been removed from a particular 
		slot in the IOAS."
        ::= { qbSysNotificationPrefix 5}

    qbSysIotDiscovered NOTIFICATION-TYPE
	OBJECTS       { qbSysModuleSlot, qbSysIotAddr }
        STATUS        current
        DESCRIPTION  
		 "A  qbSysIotDiscovered trap signifies that the agent entity
                  has detected that a new IOT has been
		  discovered/provisioned in the DWS network."	 
        ::= { qbSysNotificationPrefix 6 }

    qbSysIotRemoved NOTIFICATION-TYPE
	OBJECTS       { qbSysModuleSlot, qbSysIotAddr }
        STATUS        current
        DESCRIPTION  
		 "A qbSysIotRemoved  trap signifies that the agent entity
                  has detected that an IOT has been removed from the DWS network."
        ::= { qbSysNotificationPrefix 7 }

    qbSysIotLos NOTIFICATION-TYPE
	OBJECTS       { qbSysModuleSlot, qbSysIotAddr }
        STATUS        current
        DESCRIPTION  
		 "A qbSysIotOutOfService trap signifies that the agent entity
                 has detected that an IOT has LOS condition."
        ::= { qbSysNotificationPrefix 8 }

     qbSysModuleSwitchover NOTIFICATION-TYPE
	OBJECTS       { qbSysModuleSlot, qbSysModuleProtectionMode }
        STATUS        current
        DESCRIPTION 
		"This notification is generated when the value of
		qbSysModuleStandbyStatus changes from active(1) to either
		standby(2) or notProtected(3) or notPresent(4). The notification is also
		generated when the value of qbSysModuleStandbyStatus changes from standby(2)
		to active(1).
		The varbind indicates the current mode of the affected
		card."
        ::= { qbSysNotificationPrefix 9 }

    qbSysFlashInserted NOTIFICATION-TYPE
	OBJECTS       { qbSysModuleSlot }
        STATUS        current
        DESCRIPTION 
		  "A qbSysFlashInserted trap signifies that the agent entity
                   has detected that a flash has been inserted into
		   the  syscon module in the IOAS."
        ::= { qbSysNotificationPrefix 10 }

     qbSysFlashRemoved NOTIFICATION-TYPE
	OBJECTS       { qbSysModuleSlot  }
        STATUS        current
        DESCRIPTION 
	       "A qbSysFlashRemoved trap signifies that the agent entity
                has detected that a flash card has been removed from a syscon 
		module in the IOAS."
        ::= { qbSysNotificationPrefix 11 }

     qbSysProvChanges NOTIFICATION-TYPE
	OBJECTS       { qbSysProvType }
        STATUS        current
        DESCRIPTION  
		 "A qbSysConfigChanges trap that the agent entity
                  has detected that provisoning changes were
		  detected. The varbind indicates that type of changes
		  occured for a  given system. Note: Release 2"
        ::= { qbSysNotificationPrefix 12 }

    qbWanRxLos NOTIFICATION-TYPE
	OBJECTS       { qbSysModuleSlot }
        STATUS        current
        DESCRIPTION
		"A qbDwsRxLos trap indicates Loss of Signal by the WAN/Sonet
		card receiver. The trap is generated by a WAN card
		when a WAN card receiver problem is detected. The trap
		contains the WAN port interface index."
        ::= { qbSysNotificationPrefix 13 }

-- ****************************************************************
-- R2 Notifications Start Here
-- ****************************************************************

  qbSysUnsolicitedEvent NOTIFICATION-TYPE
	OBJECTS {
		qbSysNotificationHistoryType,
		qbSysNotificationHistoryTypeId,
		qbSysNotificationHistoryAction,
		qbSysNotificationHistoryResource,
		qbSysNotificationHistoryCookie,
		qbSysNotificationHistoryDateTime,
		qbSysNotificationHistoryAlarmCondition,
		qbSysNotificationHistoryServiceAffecting
    }
    STATUS      current
    DESCRIPTION
        "The qbSysUnsolicited Event. Unsolicited Events typeically are fault or
        discovery events such as resource added or removed or alarm information."
    ::= { qbSysNotificationPrefix 14 }

  qbSysConfigurationEvent NOTIFICATION-TYPE
	OBJECTS {
		qbSysNotificationHistoryType,
		qbSysNotificationHistoryTypeId,
		qbSysNotificationHistoryAction,
		qbSysNotificationHistoryResource,
		qbSysNotificationHistoryCookie,
		qbSysNotificationHistoryDateTime,
		qbSysNotificationHistoryAlarmCondition
    }
    STATUS      current
    DESCRIPTION
        "the qbSysConfigurationEvent typically represents some sort of configuration
        or provisioning action on the system."
    ::= { qbSysNotificationPrefix 15 }
   
-- ****************************************************************
-- Conformance Information
-- ****************************************************************

qbSysCompliances OBJECT IDENTIFIER ::= { qbSysConformance 1 }
qbSysGroups      OBJECT IDENTIFIER ::= { qbSysConformance 2 }

--
-- Compliance Statements
--

qbSysCompliance MODULE-COMPLIANCE
    STATUS      current
    DESCRIPTION
        "The compliance statement for all agents that support this
        MIB. A compliant agent implements all objects defined in this
        MIB."
    MODULE  -- this module
    MANDATORY-GROUPS {
    	qbSysGeneralGroupInfo, 
    	qbSysEventGroupInfo,
    	qbSysModuleGroupInfo,   
    --  qbSysPortGroupInfo,
    	qbSysIotGroupInfo,
    	qbSysInterfaceGroupInfo
   }
    ::= { qbSysCompliances 1 }

--
-- Object Groups
--

qbSysGeneralGroupInfo OBJECT-GROUP
    OBJECTS {
        qbSysDateTime,
        qbSysOperStatus,
        qbSysResetCtl,
        qbSysBootDiagsCode,
        qbSysWatchdogUpdate,
        qbSysRunningImageVersion,  
        qbSysPowerSupplyType, 
        qbSysAcoCtl,
        qbSysAutonomousStatus,
        qbSysDiscreteInputType,
        qbSysDiscreteInputName,
        qbSysDiscreteInputAdminStatus,  
        qbSysDiscreteInputState,
        qbSysSnmpRevision,
        qbSysMgmtIpAddr,
        qbSysMgmtIpMask,
		qbSysAgentReadCommunity,	
		qbSysAgentReadWriteCommunity,		
        qbSysDefaultIpRouter,
        qbSysAgentTrapDestFilter,
        qbSysAgentTrapDestComm,
        qbSysAgentTrapDestRowStatus,  
		qbSysDefaultRouterType,
		qbSysCliMsgCode ,
		qbSysResetVersion,
		qbSysFeatureKeys		
	}        
	STATUS	current
        DESCRIPTION
        "The set of all accessible objects in the General group of this MIB."
    ::= { qbSysGroups 1 }   
    
 qbSysConfigParamsGroupInfo OBJECT-GROUP
    OBJECTS {               
        qbSysConfigLastWriteDateTime,
        qbSysConfigLastWriteSource,
        qbSysProvType
    }
    STATUS      current
    DESCRIPTION
        "The set of all accessible objects in the Configuration Parmaeters Group in this MIB."
    ::= { qbSysGroups 2 }   
    
  qbSysEventGroupInfo OBJECT-GROUP
    OBJECTS {   
        qbSysEventHistoryDateTime,
        qbSysEventHistorySubsystem,
        qbSysEventHistorySrvAffect,
        qbSysEventHistorySeverity,
        qbSysEventHistoryId,
        qbSysEventHistoryMsg,
        qbSysEventHistoryMaxTableSize,
        qbSysAlarmDateTime,
        qbSysAlarmSubsystem,
        qbSysAlarmSrvAffect,
        qbSysAlarmSeverity,
        qbSysAlarmCondition,
        qbSysAlarmId,
        qbSysAlarmMsg, 
        qbSysAlarmResource,
        qbSysAlarmHistoryDateTime,
        qbSysAlarmHistorySubsystem,
        qbSysAlarmHistorySrvAffect,
        qbSysAlarmHistorySeverity, 
        qbSysAlarmHistoryCondition,
        qbSysEventHistoryId,
        qbSysEventHistoryMsg,      
        qbSysAlarmHistoryMaxTableSize,
        qbSysAlarmHistoryClearAllCtl,
        qbSysEventIdName,
        qbSysEventIdSeverity, 
        qbSysEventIdSASeverity,
        qbSysEventAsTrap,
        qbSysAlarmIdName,
        qbSysAlarmIdSeverity,
        qbSysAlarmIdSASeverity,	
        qbSysAlarmAsTrap, 
       	qbSysNotificationOID,
		qbSysNotificationHistoryType,
		qbSysNotificationHistoryTypeId,
		qbSysNotificationHistoryAction,
    	qbSysNotificationHistoryResource,  
    	qbSysNotificationHistoryCookie,
    	qbSysNotificationHistoryDateTime,
		qbSysNotificationHistoryAlarmCondition,  
		qbSysNotificationHistoryMaxTableSize, 
		qbSysAlarmHistoryLastIndex,
		qbSysEventHistoryLastIndex,
		qbSysGlobalHistoryLastIndex
	    }
    STATUS      current
    DESCRIPTION
        "The set of all accessible objects in the system events group in this MIB."
    ::= { qbSysGroups 3 }   
    
 qbSysModuleGroupInfo OBJECT-GROUP
    OBJECTS {
        qbSysModuleSlot,
        qbSysModuleType,
        qbSysModuleName,
        qbSysModuleOperStatus,
        qbSysModuleAdminStatus,
        qbSysModuleTestResult,
        qbSysModuleNumPorts,
        qbSysModulePortStatus,
        qbSysModuleModel,                      
        qbSysModuleSerialNum,
        qbSysModuleEqId,
        qbSysModuleHwVersion,
        qbSysModuleSwVersion,
        qbSysModuleProtectionMode,
        qbSysModuleLastSwitchoverTime,
        qbSysModuleSwitchoverReason,
        qbSysModuleLedStatus,
        qbSysModuleProductName           
 }      
    STATUS      current
    DESCRIPTION
        "The set of all accessible objects in the Module Group of this MIB."
    ::= { qbSysGroups 4 }   
    
 qbSysPortGroupInfo OBJECT-GROUP
    OBJECTS {
        qbSysPort,
        qbSysPortName,
        qbSysPortType,
        qbSysPortOperStatus,
        qbSysPortIfIndex,
        qbSysPortLoopbackConfig
    }
    STATUS      current
    DESCRIPTION
        "The set of all accessible objects in the Port Group of this MIB."
    ::= { qbSysGroups 5 }   
    
 qbSysIotGroupInfo OBJECT-GROUP
    OBJECTS {
        qbSysIoasDwsIfIndex,
        qbSysIotAddr,
        qbSysIotName,
        qbSysIotLocation,
        qbSysIotSwVersion,
        qbSysIotHwVersion,
        qbSysIotOperStatus,
        qbSysIotAdminStatus,
        qbSysIotDsx1LineCoding,
        qbSysIotSerialStr,
        qbSysIotRowStatus, 
		qbSysIotFileAvailableVersion1,
  		qbSysIotFileAvailableVersion2,
		qbSysIotFileRunningVersion,
		qbSysIotFileAcceptedVersion,
  		qbSysIotFileDownLoadVersion,
  		qbSysIotFileLastModification,
  		qbSysIotFileAction,
  		qbSysIotFileDownLoadStatus,
  		qbSysIotFileErrorMsg,
  		qbSysIotProductName
        }
    STATUS      current
    DESCRIPTION
        "The set of all accessible objects in the Intelligent Terminal Group of this MIB."
    ::= { qbSysGroups 6 }   
    
 qbSysInterfaceGroupInfo OBJECT-GROUP
    OBJECTS {
        qbIfLocationSlot,
        qbIfLocationAddr,
        qbIfLocationPort,
        qbIfLocationType,
        qbIfLocationSerialNumber 
    }
    STATUS      current
    DESCRIPTION
        "The set of all accessible objects in the Interfaces Group of this MIB."
    ::= { qbSysGroups 7 }   
END
