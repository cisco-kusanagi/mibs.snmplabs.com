--******************************************************************
--*
--*         Copyright (c) 1993, 1999 by 3Com Corporation
--*                    All Rights Reserved
--*
--*    $Revision:   7.0  $
--*    $Date:   Jul 15 1999 15:21:14  $
--*
--*    3COM HIST MIB
--*
--******************************************************************


HIST-MIB DEFINITIONS ::= BEGIN

IMPORTS
   enterprises,
   experimental,
   IpAddress,
   TimeTicks,
   Gauge,
   Counter
      FROM RFC1155-SMI
   DisplayString
      FROM RFC1213-MIB
   OBJECT-TYPE
      FROM RFC-1212;


usr OBJECT IDENTIFIER ::= { enterprises 429 }

nas OBJECT IDENTIFIER ::= { usr 1 }

mdmHist OBJECT IDENTIFIER ::= { nas 30 }

mdmNacHistCurrentTable OBJECT-TYPE
SYNTAX SEQUENCE OF NacHistCurrentEntry
ACCESS not-accessible
STATUS mandatory
DESCRIPTION
""
::= { mdmHist 1 }

mdmNacHistCurrentEntry OBJECT-TYPE
SYNTAX NacHistCurrentEntry
ACCESS not-accessible
STATUS mandatory
DESCRIPTION
"Objects that define the history stats for NAC current 
interval."
INDEX { mdmNacHistCurrentIndex }
::= { mdmNacHistCurrentTable 1 }

NacHistCurrentEntry ::=
SEQUENCE {
mdmNacHistCurrentIndex
    INTEGER,
mdmNacHistCurrentStartTime
    INTEGER,
mdmNacHistCurrentMgmtBusFailures
    Gauge,
mdmNacHistCurrentWatchdogTimouts
    Gauge
}

mdmNacHistCurrentIndex OBJECT-TYPE
SYNTAX INTEGER
ACCESS read-only
STATUS mandatory
DESCRIPTION
"Index in to the Current NAC History table.  This index 
contains a unique value for each card in the chassis."
::= { mdmNacHistCurrentEntry 1 }

mdmNacHistCurrentStartTime OBJECT-TYPE
SYNTAX INTEGER
ACCESS read-only
STATUS mandatory
DESCRIPTION
"Specifies current interval start time in GMT."
::= { mdmNacHistCurrentEntry 2 }

mdmNacHistCurrentMgmtBusFailures OBJECT-TYPE
SYNTAX Gauge
ACCESS read-only
STATUS mandatory
DESCRIPTION
"Specifies number of Management Bus Failures occurred in the 
NAC during current interval so for."
::= { mdmNacHistCurrentEntry 3 }

mdmNacHistCurrentWatchdogTimouts OBJECT-TYPE
SYNTAX Gauge
ACCESS read-only
STATUS mandatory
DESCRIPTION
"Specifies number of Watchdog Timeouts occurred in the NAC 
during current interval so for."
::= { mdmNacHistCurrentEntry 4 }

mdmNacHistIntervalTable OBJECT-TYPE
SYNTAX SEQUENCE OF NacHistIntervalEntry
ACCESS not-accessible
STATUS mandatory
DESCRIPTION
""
::= { mdmHist 2 }

mdmNacHistIntervalEntry OBJECT-TYPE
SYNTAX NacHistIntervalEntry
ACCESS not-accessible
STATUS mandatory
DESCRIPTION
"Objects that define history stats for NAC intervals."
INDEX { mdmNacHistIntervalIndex, mdmNacHistIntervalNumber }
::= { mdmNacHistIntervalTable 1 }

NacHistIntervalEntry ::=
SEQUENCE {
mdmNacHistIntervalIndex
    INTEGER,
mdmNacHistIntervalNumber
    INTEGER,
mdmNacHistIntervalStartTime
    INTEGER,
mdmNacHistIntervalMgmtBusFailures
    Gauge,
mdmNacHistIntervalWatchdogTimouts
    Gauge
}

mdmNacHistIntervalIndex OBJECT-TYPE
SYNTAX INTEGER
ACCESS read-only
STATUS mandatory
DESCRIPTION
"Index in to NAC Interval History table.  This index 
contains a unique value for each card in the chassis."
::= { mdmNacHistIntervalEntry 1 }

mdmNacHistIntervalNumber OBJECT-TYPE
SYNTAX INTEGER (1..104)
ACCESS read-only
STATUS mandatory
DESCRIPTION
"This object is the index for one of 104 possibel history 
intervals for this NAC."
::= { mdmNacHistIntervalEntry 2 }

mdmNacHistIntervalStartTime OBJECT-TYPE
SYNTAX INTEGER
ACCESS read-only
STATUS mandatory
DESCRIPTION
"Specifies interval start time in GMT."
::= { mdmNacHistIntervalEntry 3 }

mdmNacHistIntervalMgmtBusFailures OBJECT-TYPE
SYNTAX Gauge
ACCESS read-only
STATUS mandatory
DESCRIPTION
"Specifies number of Management Bus Failures occurred in the 
NAC during the interval."
::= { mdmNacHistIntervalEntry 4 }

mdmNacHistIntervalWatchdogTimouts OBJECT-TYPE
SYNTAX Gauge
ACCESS read-only
STATUS mandatory
DESCRIPTION
"Specifies number of Watchdog Timeouts occurred in the NAC 
during the interval."
::= { mdmNacHistIntervalEntry 5 }

mdmHistCurrentTable OBJECT-TYPE
SYNTAX SEQUENCE OF MdmHistCurrentEntry
ACCESS not-accessible
STATUS mandatory
DESCRIPTION
""
::= { mdmHist 3 }

mdmHistCurrentEntry OBJECT-TYPE
SYNTAX MdmHistCurrentEntry
ACCESS not-accessible
STATUS mandatory
DESCRIPTION
"Objects that define the history stats for modem current 
interval."
INDEX { mdmHistCurrentIndex }
::= { mdmHistCurrentTable 1 }

MdmHistCurrentEntry ::=
SEQUENCE {
mdmHistCurrentIndex
    INTEGER,
mdmHistCurrentStartTime
    INTEGER,
mdmHistCurrentInConnectEstabs
    Gauge,
mdmHistCurrentInConnectFailures
    Gauge,
mdmHistCurrentInConnectTerms
    Gauge,
mdmHistCurrentInConnectTime
    Gauge,
mdmHistCurrentInTotalBytesRx
    Gauge,
mdmHistCurrentInTotalBytesTx
    Gauge,
mdmHistCurrentOutConnectEstabs
    Gauge,
mdmHistCurrentOutConnectFailures
    Gauge,
mdmHistCurrentOutConnectTerms
    Gauge,
mdmHistCurrentOutConnectTime
    Gauge,
mdmHistCurrentOutTotalBytesRx
    Gauge,
mdmHistCurrentOutTotalBytesTx
    Gauge,
mdmHistCurrentBlers
    Gauge,
mdmHistCurrentFallBacks
    Gauge
}

mdmHistCurrentIndex OBJECT-TYPE
SYNTAX INTEGER
ACCESS read-only
STATUS mandatory
DESCRIPTION
"Index in to the Current modem history table.  This index 
contains the unique value associated with the modem as 
defined in the chassis MIB entity table."
::= { mdmHistCurrentEntry 1 }

mdmHistCurrentStartTime OBJECT-TYPE
SYNTAX INTEGER
ACCESS read-only
STATUS mandatory
DESCRIPTION
"Specifies current interval start time in GMT."
::= { mdmHistCurrentEntry 2 }

mdmHistCurrentInConnectEstabs OBJECT-TYPE
SYNTAX Gauge
ACCESS read-only
STATUS mandatory
DESCRIPTION
"Specifies number of incoming calls established during 
current interval so for."
::= { mdmHistCurrentEntry 3 }

mdmHistCurrentInConnectFailures OBJECT-TYPE
SYNTAX Gauge
ACCESS read-only
STATUS mandatory
DESCRIPTION
"Specifies number of incoming call failures during current 
interval so for."
::= { mdmHistCurrentEntry 4 }

mdmHistCurrentInConnectTerms OBJECT-TYPE
SYNTAX Gauge
ACCESS read-only
STATUS mandatory
DESCRIPTION
"Specifies number of incoming calls terminated during 
current interval so for."
::= { mdmHistCurrentEntry 5 }

mdmHistCurrentInConnectTime OBJECT-TYPE
SYNTAX Gauge
ACCESS read-only
STATUS mandatory
DESCRIPTION
"Specifies length of all incoming calls during current 
interval so for."
::= { mdmHistCurrentEntry 6 }

mdmHistCurrentInTotalBytesRx OBJECT-TYPE
SYNTAX Gauge
ACCESS read-only
STATUS mandatory
DESCRIPTION
"Specifies number of bytes received through incoming calls 
during current interval so for."

::= { mdmHistCurrentEntry 7 }

mdmHistCurrentInTotalBytesTx OBJECT-TYPE
SYNTAX Gauge
ACCESS read-only
STATUS mandatory
DESCRIPTION
"Specifies number of bytes sent out through incoming calls 
during current interval so for."
::= { mdmHistCurrentEntry 8 }

mdmHistCurrentOutConnectEstabs OBJECT-TYPE
SYNTAX Gauge
ACCESS read-only
STATUS mandatory
DESCRIPTION
"Specifies number of outgoing calls established during 
current interval so for."
::= { mdmHistCurrentEntry 9 }

mdmHistCurrentOutConnectFailures OBJECT-TYPE
SYNTAX Gauge
ACCESS read-only
STATUS mandatory
DESCRIPTION
"Specifies number of outgoing call failures during current 
interval so for."
::= { mdmHistCurrentEntry 10 }

mdmHistCurrentOutConnectTerms OBJECT-TYPE
SYNTAX Gauge
ACCESS read-only
STATUS mandatory
DESCRIPTION
"Specifies number of outgoing calls terminated during 
current interval so for."
::= { mdmHistCurrentEntry 11 }

mdmHistCurrentOutConnectTime OBJECT-TYPE
SYNTAX Gauge
ACCESS read-only
STATUS mandatory
DESCRIPTION
"Specifies length of all outgoing calls during current 
interval so for."
::= { mdmHistCurrentEntry 12 }

mdmHistCurrentOutTotalBytesRx OBJECT-TYPE
SYNTAX Gauge
ACCESS read-only
STATUS mandatory
DESCRIPTION
"Specifies number of bytes received through outgoing calls 
during current interval so for."
::= { mdmHistCurrentEntry 13 }

mdmHistCurrentOutTotalBytesTx OBJECT-TYPE
SYNTAX Gauge
ACCESS read-only
STATUS mandatory
DESCRIPTION
"Specifies number of bytes sent out through outgoing calls 
during current interval so for."
::= { mdmHistCurrentEntry 14 }

mdmHistCurrentBlers OBJECT-TYPE
SYNTAX Gauge
ACCESS read-only
STATUS mandatory
DESCRIPTION
"Specifies number of block errors received during current 
interval so for."
::= { mdmHistCurrentEntry 15 }

mdmHistCurrentFallBacks OBJECT-TYPE
SYNTAX Gauge
ACCESS read-only
STATUS mandatory
DESCRIPTION
"Specifies number of link speed fallbacks occured during 
current interval so for."
::= { mdmHistCurrentEntry 16 }

mdmHistIntervalTable OBJECT-TYPE
SYNTAX SEQUENCE OF MdmHistIntervalEntry
ACCESS not-accessible
STATUS mandatory
DESCRIPTION
""
::= { mdmHist 4 }

mdmHistIntervalEntry OBJECT-TYPE
SYNTAX MdmHistIntervalEntry
ACCESS not-accessible
STATUS mandatory
DESCRIPTION
"Objects that define history stats for modem intervals."
INDEX { mdmHistIntervalIndex, mdmHistIntervalNumber }
::= { mdmHistIntervalTable 1 }

MdmHistIntervalEntry ::=
SEQUENCE {
mdmHistIntervalIndex
    INTEGER,
mdmHistIntervalNumber
    INTEGER,
mdmHistIntervalStartTime
    INTEGER,
mdmHistIntervalInConnectEstabs
    Gauge,
mdmHistIntervalInConnectFailures
    Gauge,
mdmHistIntervalInConnectTerms
    Gauge,
mdmHistIntervalInConnectTime
    Gauge,
mdmHistIntervalInTotalBytesRx
    Gauge,
mdmHistIntervalInTotalBytesTx
    Gauge,
mdmHistIntervalOutConnectEstabs
    Gauge,
mdmHistIntervalOutConnectFailures
    Gauge,
mdmHistIntervalOutConnectTerms
    Gauge,
mdmHistIntervalOutConnectTime
    Gauge,
mdmHistIntervalOutTotalBytesRx
    Gauge,
mdmHistIntervalOutTotalBytesTx
    Gauge,
mdmHistIntervalBlers
    Gauge,
mdmHistIntervalFallBacks
    Gauge
}

mdmHistIntervalIndex OBJECT-TYPE
SYNTAX INTEGER
ACCESS read-only
STATUS mandatory
DESCRIPTION
"Index in to the interval History table.  This index 
contains the unique value associated with the modem as 
defined in the chassis MIB entity table."
::= { mdmHistIntervalEntry 1 }

mdmHistIntervalNumber OBJECT-TYPE
SYNTAX INTEGER (1..104)
ACCESS read-only
STATUS mandatory
DESCRIPTION
"This object is the index for one of 104 possibel history 
intervals for this modem."
::= { mdmHistIntervalEntry 2 }

mdmHistIntervalStartTime OBJECT-TYPE
SYNTAX INTEGER
ACCESS read-only
STATUS mandatory
DESCRIPTION
"Specifies interval start time in GMT."
::= { mdmHistIntervalEntry 3 }

mdmHistIntervalInConnectEstabs OBJECT-TYPE
SYNTAX Gauge
ACCESS read-only
STATUS mandatory
DESCRIPTION
"Specifies number of incoming calls established during the 
interval."
::= { mdmHistIntervalEntry 4 }

mdmHistIntervalInConnectFailures OBJECT-TYPE
SYNTAX Gauge
ACCESS read-only
STATUS mandatory
DESCRIPTION
"Specifies number of incoming call failures during the 
interval."
::= { mdmHistIntervalEntry 5 }

mdmHistIntervalInConnectTerms OBJECT-TYPE
SYNTAX Gauge
ACCESS read-only
STATUS mandatory
DESCRIPTION
"Specifies number of incoming calls terminated during the 
interval."
::= { mdmHistIntervalEntry 6 }

mdmHistIntervalInConnectTime OBJECT-TYPE
SYNTAX Gauge
ACCESS read-only
STATUS mandatory
DESCRIPTION
"Specifies length of all incoming calls during the 
intervals."
::= { mdmHistIntervalEntry 7 }

mdmHistIntervalInTotalBytesRx OBJECT-TYPE
SYNTAX Gauge
ACCESS read-only
STATUS mandatory
DESCRIPTION
"Specifies number of bytes received through incoming calls 
during the interval."
::= { mdmHistIntervalEntry 8 }

mdmHistIntervalInTotalBytesTx OBJECT-TYPE
SYNTAX Gauge
ACCESS read-only
STATUS mandatory
DESCRIPTION
"Specifies number of bytes sent out through incoming calls 
during the interval."
::= { mdmHistIntervalEntry 9 }

mdmHistIntervalOutConnectEstabs OBJECT-TYPE
SYNTAX Gauge
ACCESS read-only
STATUS mandatory
DESCRIPTION
"Specifies number of outgoing calls established during the 
interval."
::= { mdmHistIntervalEntry 10 }

mdmHistIntervalOutConnectFailures OBJECT-TYPE
SYNTAX Gauge
ACCESS read-only
STATUS mandatory
DESCRIPTION
"Specifies number of outgoing call failures during the 
interval."
::= { mdmHistIntervalEntry 11 }

mdmHistIntervalOutConnectTerms OBJECT-TYPE
SYNTAX Gauge
ACCESS read-only
STATUS mandatory
DESCRIPTION
"Specifies number of outgoing calls terminated during the 
interval."

::= { mdmHistIntervalEntry 12 }

mdmHistIntervalOutConnectTime OBJECT-TYPE
SYNTAX Gauge
ACCESS read-only
STATUS mandatory
DESCRIPTION
"Specifies length of all outgoing calls during the 
interval."
::= { mdmHistIntervalEntry 13 }

mdmHistIntervalOutTotalBytesRx OBJECT-TYPE
SYNTAX Gauge
ACCESS read-only
STATUS mandatory
DESCRIPTION
"Specifies number of bytes received through outgoing calls 
during the interval."
::= { mdmHistIntervalEntry 14 }

mdmHistIntervalOutTotalBytesTx OBJECT-TYPE
SYNTAX Gauge
ACCESS read-only
STATUS mandatory
DESCRIPTION
"Specifies number of bytes sent out through outgoing calls 
during the interval."
::= { mdmHistIntervalEntry 15 }

mdmHistIntervalBlers OBJECT-TYPE
SYNTAX Gauge
ACCESS read-only
STATUS mandatory
DESCRIPTION
"Specifies number of block errors received during the 
interval."
::= { mdmHistIntervalEntry 16 }

mdmHistIntervalFallBacks OBJECT-TYPE
SYNTAX Gauge
ACCESS read-only
STATUS mandatory
DESCRIPTION
"Specifies number of link speed fallbacks occured during the 
interval."
::= { mdmHistIntervalEntry 17 }

END
