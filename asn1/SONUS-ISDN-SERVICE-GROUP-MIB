--
-- This SMIv2 module has been generated by smidump 0.2-cvs. Do not edit.
--

SONUS-ISDN-SERVICE-GROUP-MIB DEFINITIONS ::= BEGIN

IMPORTS
    Counter32, Integer32, MODULE-IDENTITY, NOTIFICATION-TYPE, 
    OBJECT-TYPE
        FROM SNMPv2-SMI
    DisplayString, RowStatus
        FROM SNMPv2-TC
    sonusEventClass, sonusEventDescription, sonusEventLevel
        FROM SONUS-COMMON-MIB
    sonusSignallingMIBs
        FROM SONUS-SMI
    SonusAdminState, SonusName, SonusNameReference, SonusServiceState
        FROM SONUS-TC;

sonusIsdnServiceGroupMIB MODULE-IDENTITY
    LAST-UPDATED    "200107310000Z"
    ORGANIZATION    
            "Sonus Networks, Inc."
    CONTACT-INFO    
            "   Customer Support    
             Sonus Networks, Inc,
             5 Carlisle Road
             Westford, MA 01886
             USA
             
             Tel: 978-692-8999
             Fax: 978-392-9118
             E-mail: cs.snmp@sonusnet.com"
    DESCRIPTION     
            "The MIB Module for ISDN Service Group Management."
    ::= { sonusSignallingMIBs 4 }


sonusIsdnServiceGroupMIBObjects OBJECT IDENTIFIER
    ::= { sonusIsdnServiceGroupMIB 1 }

sonusIsdnsgServiceGroup OBJECT IDENTIFIER
    ::= { sonusIsdnServiceGroupMIBObjects 1 }

sonusIsdnsgServiceGroupNextIndex OBJECT-TYPE
    SYNTAX          Integer32
    MAX-ACCESS      read-only
    STATUS          current
    DESCRIPTION     
            "The next valid index to use when creating a new sonusIsdnsgServiceGroupEntry"
    ::= { sonusIsdnsgServiceGroup 1 }

sonusIsdnsgServiceGroupTable OBJECT-TYPE
    SYNTAX          SEQUENCE OF SonusIsdnsgServiceGroupEntry
    MAX-ACCESS      not-accessible
    STATUS          current
    DESCRIPTION     
            "This table contains information about each ISDN Service Group.
             
             A management entity may create rows for Service Group that are
             anticipated to be supported in the future."
    ::= { sonusIsdnsgServiceGroup 2 }

sonusIsdnsgServiceGroupEntry OBJECT-TYPE
    SYNTAX          SonusIsdnsgServiceGroupEntry
    MAX-ACCESS      not-accessible
    STATUS          current
    DESCRIPTION     
            "This table describes the ISDN Service Groups that are configured
             on the GSX9000."
    INDEX           { sonusIsdnsgServiceGroupListIndex }
    ::= { sonusIsdnsgServiceGroupTable 1 }

SonusIsdnsgServiceGroupEntry ::=
    SEQUENCE {
        sonusIsdnsgServiceGroupListIndex Integer32,
        sonusIsdnsgServiceGroupName     SonusName,
        sonusIsdnsgServiceGroupTrunkGroup SonusNameReference,
        sonusIsdnsgServiceGroupHuntAlgorithm    INTEGER,
        sonusIsdnsgServiceGroupCost     Integer32,
        sonusIsdnsgServiceGroupSwitchSide INTEGER,
        sonusIsdnsgServiceGroupSwitchType INTEGER,
        sonusIsdnsgServiceGroupSwitchProfileName        DisplayString,
        sonusIsdnsgServiceGroupOperation INTEGER,
        sonusIsdnsgServiceGroupPrimaryDchannelInterface               Integer32,
        sonusIsdnsgServiceGroupPrimaryDchannelTimeSlot              Integer32,
        sonusIsdnsgServiceGroupPrimaryDchannelMode          INTEGER,
        sonusIsdnsgServiceGroupBackupDchannelInterface              Integer32,
        sonusIsdnsgServiceGroupBackupDchannelTimeSlot             Integer32,
        sonusIsdnsgServiceGroupBackupDchannelMode         INTEGER,
        sonusIsdnsgServiceGroupLayerTrace INTEGER,
        sonusIsdnsgServiceGroupMode     SonusServiceState,
        sonusIsdnsgServiceGroupAction   INTEGER,
        sonusIsdnsgServiceGroupTimeout  Integer32,
        sonusIsdnsgServiceGroupAdminState SonusAdminState,
        sonusIsdnsgServiceGroupProfileName  DisplayString,
        sonusIsdnsgServiceGroupRowStatus RowStatus,
        sonusIsdnsgServiceGroupDefaultDirectoryNumber             DisplayString,
        sonusIsdnsgServiceGroupCallingPartyNumberProvision                  INTEGER,
        sonusIsdnsgServiceGroupCallingPartyNumberDiscard                INTEGER,
        sonusIsdnsgServiceGroupCallingPartyNumberDelivery                 INTEGER,
        sonusIsdnsgServiceGroupCallingPartySubAddressTransfer                     INTEGER,
        sonusIsdnsgServiceGroupCallingPartySubAddressDelivery                     INTEGER,
        sonusIsdnsgServiceGroupBchannelAvailabilitySignaling                    INTEGER,
        sonusIsdnsgServiceGroupVerboseTrace   INTEGER,
        sonusIsdnsgServiceGroupCallingPartyNumberPresentation                     INTEGER,
        sonusIsdnsgServiceGroupDiscTreatmentProfileName               SonusNameReference,
        sonusIsdnsgServiceGroupTonePackageName      SonusNameReference,
        sonusIsdnsgServiceGroupT302     Integer32,
        sonusIsdnsgServiceGroupT303     Integer32,
        sonusIsdnsgServiceGroupT304     Integer32,
        sonusIsdnsgServiceGroupT305     Integer32,
        sonusIsdnsgServiceGroupT306     Integer32,
        sonusIsdnsgServiceGroupT308     Integer32,
        sonusIsdnsgServiceGroupT309     Integer32,
        sonusIsdnsgServiceGroupT310     Integer32,
        sonusIsdnsgServiceGroupT312     Integer32,
        sonusIsdnsgServiceGroupT313     Integer32,
        sonusIsdnsgServiceGroupT314     Integer32,
        sonusIsdnsgServiceGroupT318     Integer32,
        sonusIsdnsgServiceGroupT319     Integer32,
        sonusIsdnsgServiceGroupT322     Integer32,
        sonusIsdnsgServiceGroupK        Integer32,
        sonusIsdnsgServiceGroupT200     Integer32,
        sonusIsdnsgServiceGroupT203     Integer32,
        sonusIsdnsgServiceGroupN200     Integer32,
        sonusIsdnsgServiceGroupN201     Integer32,
        sonusIsdnsgServiceGroupBchannelInitialRestart             INTEGER,
        sonusIsdnsgServiceGroupIuaApplicationServer           SonusNameReference,
        sonusIsdnsgServiceGroupIuaAutoDatalinkEstablish               INTEGER
    }

sonusIsdnsgServiceGroupListIndex OBJECT-TYPE
    SYNTAX          Integer32
    MAX-ACCESS      read-only
    STATUS          current
    DESCRIPTION     
            "The index of the ISDN Service Group entry."
    ::= { sonusIsdnsgServiceGroupEntry 1 }

sonusIsdnsgServiceGroupName OBJECT-TYPE
    SYNTAX          SonusName
    MAX-ACCESS      read-write
    STATUS          current
    DESCRIPTION     
            "The name of the ISDN Service Group."
    ::= { sonusIsdnsgServiceGroupEntry 2 }

sonusIsdnsgServiceGroupTrunkGroup OBJECT-TYPE
    SYNTAX          SonusNameReference
    MAX-ACCESS      read-write
    STATUS          current
    DESCRIPTION     
            "The Trunk Group, which the ISDN Service Group belongs to."
    ::= { sonusIsdnsgServiceGroupEntry 3 }

sonusIsdnsgServiceGroupHuntAlgorithm OBJECT-TYPE
    SYNTAX          INTEGER { lowlow(1), highhigh(2), circularforward(3), 
                        circularbackward(4) }
    MAX-ACCESS      read-write
    STATUS          current
    DESCRIPTION     
            "The hunting method used to select channels for calls destined
             to the Service Group destination."
    DEFVAL          { lowlow }
    ::= { sonusIsdnsgServiceGroupEntry 4 }

sonusIsdnsgServiceGroupCost OBJECT-TYPE
    SYNTAX          Integer32 (0..100)
    MAX-ACCESS      read-write
    STATUS          current
    DESCRIPTION     
            "The routing cost to the ISDN Service Group."
    DEFVAL          { 50 }
    ::= { sonusIsdnsgServiceGroupEntry 5 }

sonusIsdnsgServiceGroupSwitchSide OBJECT-TYPE
    SYNTAX          INTEGER { network(1), user(2) }
    MAX-ACCESS      read-write
    STATUS          current
    DESCRIPTION     
            "The switch side the ISDN Service Group should act as."
    DEFVAL          { network }
    ::= { sonusIsdnsgServiceGroupEntry 6 }

sonusIsdnsgServiceGroupSwitchType OBJECT-TYPE
    SYNTAX          INTEGER { ni2(1), dms250(2), dms100(3), 
                        lucent5ESS(4), lucent4ESS(5), euroIsdn(6), 
                        ins1500(7) }
    MAX-ACCESS      read-write
    STATUS          current
    DESCRIPTION     
            "The network switch type where the ISDN Service Group resides."
    DEFVAL          { ni2 }
    ::= { sonusIsdnsgServiceGroupEntry 7 }

sonusIsdnsgServiceGroupSwitchProfileName OBJECT-TYPE
    SYNTAX          DisplayString (SIZE(0..23))
    MAX-ACCESS      read-write
    STATUS          current
    DESCRIPTION     
            "The ISDN Service Group switch profile name."
    ::= { sonusIsdnsgServiceGroupEntry 8 }

sonusIsdnsgServiceGroupOperation OBJECT-TYPE
    SYNTAX          INTEGER { outOfService(1), maintenance(2), 
                        inService(3), restart(4), clearStats(5), 
                        dchannelSwitchover(6) }
    MAX-ACCESS      read-write
    STATUS          current
    DESCRIPTION     
            "The operation to be applied to the the ISDN Service Group."
    ::= { sonusIsdnsgServiceGroupEntry 9 }

sonusIsdnsgServiceGroupPrimaryDchannelInterface OBJECT-TYPE
    SYNTAX          Integer32 (0..127)
    MAX-ACCESS      read-write
    STATUS          current
    DESCRIPTION     
            "The ISDN Service Group primary D-channel interface."
    DEFVAL          { 0 }
    ::= { sonusIsdnsgServiceGroupEntry 10 }

sonusIsdnsgServiceGroupPrimaryDchannelTimeSlot OBJECT-TYPE
    SYNTAX          Integer32 (0..31)
    MAX-ACCESS      read-write
    STATUS          current
    DESCRIPTION     
            "The ISDN Service Group primary D-channel time slot."
    DEFVAL          { 24 }
    ::= { sonusIsdnsgServiceGroupEntry 11 }

sonusIsdnsgServiceGroupPrimaryDchannelMode OBJECT-TYPE
    SYNTAX          INTEGER { outOfService(1), inService(2) }
    MAX-ACCESS      read-write
    STATUS          current
    DESCRIPTION     
            "The mode of operation of the primary D-channel in the ISDN Service Group."
    DEFVAL          { inService }
    ::= { sonusIsdnsgServiceGroupEntry 12 }

sonusIsdnsgServiceGroupBackupDchannelInterface OBJECT-TYPE
    SYNTAX          Integer32 (0..127)
    MAX-ACCESS      read-write
    STATUS          current
    DESCRIPTION     
            "The ISDN Service Group backup D-channel interface."
    DEFVAL          { 1 }
    ::= { sonusIsdnsgServiceGroupEntry 13 }

sonusIsdnsgServiceGroupBackupDchannelTimeSlot OBJECT-TYPE
    SYNTAX          Integer32 (0..31)
    MAX-ACCESS      read-write
    STATUS          current
    DESCRIPTION     
            "The ISDN Service Group backup D-channel time slot."
    DEFVAL          { 24 }
    ::= { sonusIsdnsgServiceGroupEntry 14 }

sonusIsdnsgServiceGroupBackupDchannelMode OBJECT-TYPE
    SYNTAX          INTEGER { outOfService(1), inService(2), 
                        unEquipped(3) }
    MAX-ACCESS      read-write
    STATUS          current
    DESCRIPTION     
            "The mode of operation of the backup D-channel in the ISDN Service Group."
    DEFVAL          { unEquipped }
    ::= { sonusIsdnsgServiceGroupEntry 15 }

sonusIsdnsgServiceGroupLayerTrace OBJECT-TYPE
    SYNTAX          INTEGER { none(1), layer2(2), layer3(3), both(4) }
    MAX-ACCESS      read-write
    STATUS          current
    DESCRIPTION     
            "Controls logging of layer events to the trace event log file."
    DEFVAL          { none }
    ::= { sonusIsdnsgServiceGroupEntry 16 }

sonusIsdnsgServiceGroupMode OBJECT-TYPE
    SYNTAX          SonusServiceState
    MAX-ACCESS      read-write
    STATUS          current
    DESCRIPTION     
            "The mode of operation of channels in the ISDN Service Group."
    DEFVAL          { inService }
    ::= { sonusIsdnsgServiceGroupEntry 17 }

sonusIsdnsgServiceGroupAction OBJECT-TYPE
    SYNTAX          INTEGER { dryUp(1), force(2) }
    MAX-ACCESS      read-write
    STATUS          current
    DESCRIPTION     
            "The action taken on the channels in the ISDN Service Group when sonusIsdnsgServiceGroupMode
             is set to out of service. This object should only be set in conjunction with sonusIsdnsgServiceGroupMode."
    ::= { sonusIsdnsgServiceGroupEntry 18 }

sonusIsdnsgServiceGroupTimeout OBJECT-TYPE
    SYNTAX          Integer32 (1..1440)
    MAX-ACCESS      read-write
    STATUS          current
    DESCRIPTION     
            "The timeout value in minutes for dryup action on the ISDN Service Group.
             This object should only be set in conjunction with sonusIsdnsgServiceGroupAction, 
             when sonusIsdnsgServiceGroupAction is set to dryUp."
    ::= { sonusIsdnsgServiceGroupEntry 19 }

sonusIsdnsgServiceGroupAdminState OBJECT-TYPE
    SYNTAX          SonusAdminState
    MAX-ACCESS      read-write
    STATUS          current
    DESCRIPTION     
            "The admin state of the ISDN Service Group."
    DEFVAL          { disabled }
    ::= { sonusIsdnsgServiceGroupEntry 20 }

sonusIsdnsgServiceGroupProfileName OBJECT-TYPE
    SYNTAX          DisplayString (SIZE(0..23))
    MAX-ACCESS      read-write
    STATUS          current
    DESCRIPTION     
            "The ISDN Service Group profile name."
    ::= { sonusIsdnsgServiceGroupEntry 21 }

sonusIsdnsgServiceGroupRowStatus OBJECT-TYPE
    SYNTAX          RowStatus
    MAX-ACCESS      read-write
    STATUS          current
    DESCRIPTION     
            ""
    ::= { sonusIsdnsgServiceGroupEntry 22 }

sonusIsdnsgServiceGroupDefaultDirectoryNumber OBJECT-TYPE
    SYNTAX          DisplayString (SIZE(0..30))
    MAX-ACCESS      read-write
    STATUS          current
    DESCRIPTION     
            "Default Directory number for the ISDN Service Group."
    ::= { sonusIsdnsgServiceGroupEntry 23 }

sonusIsdnsgServiceGroupCallingPartyNumberProvision OBJECT-TYPE
    SYNTAX          INTEGER { necessary(1), notNecessary(2) }
    MAX-ACCESS      read-write
    STATUS          current
    DESCRIPTION     
            "Specifies wether the Calling Party Number is required in the incoming SETUP."
    DEFVAL          { notNecessary }
    ::= { sonusIsdnsgServiceGroupEntry 24 }

sonusIsdnsgServiceGroupCallingPartyNumberDiscard OBJECT-TYPE
    SYNTAX          INTEGER { yes(1), no(2) }
    MAX-ACCESS      read-write
    STATUS          current
    DESCRIPTION     
            "Controls discard of Calling Party Numbers not screened or that failed screening."
    DEFVAL          { no }
    ::= { sonusIsdnsgServiceGroupEntry 25 }

sonusIsdnsgServiceGroupCallingPartyNumberDelivery OBJECT-TYPE
    SYNTAX          INTEGER { yes(1), no(2) }
    MAX-ACCESS      read-write
    STATUS          current
    DESCRIPTION     
            "Controls the delivery of the Calling Party Number within outgoing SETUP messages"
    DEFVAL          { yes }
    ::= { sonusIsdnsgServiceGroupEntry 26 }

sonusIsdnsgServiceGroupCallingPartySubAddressTransfer OBJECT-TYPE
    SYNTAX          INTEGER { yes(1), no(2), conditional(3) }
    MAX-ACCESS      read-write
    STATUS          current
    DESCRIPTION     
            "Controls the transfer of the Calling Party Subaddress Information Element"
    DEFVAL          { yes }
    ::= { sonusIsdnsgServiceGroupEntry 27 }

sonusIsdnsgServiceGroupCallingPartySubAddressDelivery OBJECT-TYPE
    SYNTAX          INTEGER { yes(1), no(2), conditional(3) }
    MAX-ACCESS      read-write
    STATUS          current
    DESCRIPTION     
            "Controls the delivery of the Calling Party Subaddress Information Element to the CPE"
    DEFVAL          { yes }
    ::= { sonusIsdnsgServiceGroupEntry 28 }

sonusIsdnsgServiceGroupBchannelAvailabilitySignaling OBJECT-TYPE
    SYNTAX          INTEGER { yes(1), no(2) }
    MAX-ACCESS      read-write
    STATUS          current
    DESCRIPTION     
            "Used to enable or disable the B-channel availability signaling procedures"
    DEFVAL          { yes }
    ::= { sonusIsdnsgServiceGroupEntry 29 }

sonusIsdnsgServiceGroupVerboseTrace OBJECT-TYPE
    SYNTAX          INTEGER { off(1), on(2) }
    MAX-ACCESS      read-write
    STATUS          current
    DESCRIPTION     
            "Controls verbose mode in the logging of layer events to the trace event log file."
    DEFVAL          { on }
    ::= { sonusIsdnsgServiceGroupEntry 30 }

sonusIsdnsgServiceGroupCallingPartyNumberPresentation OBJECT-TYPE
    SYNTAX          INTEGER { yes(1), no(2) }
    MAX-ACCESS      read-write
    STATUS          current
    DESCRIPTION     
            "Used as Calling Party Number presentation indicator when none available in incoming SETUP."
    DEFVAL          { yes }
    ::= { sonusIsdnsgServiceGroupEntry 31 }

sonusIsdnsgServiceGroupDiscTreatmentProfileName OBJECT-TYPE
    SYNTAX          SonusNameReference
    MAX-ACCESS      read-write
    STATUS          current
    DESCRIPTION     
            "The disconnect treatment profile to be used for this service."
    ::= { sonusIsdnsgServiceGroupEntry 32 }

sonusIsdnsgServiceGroupTonePackageName OBJECT-TYPE
    SYNTAX          SonusNameReference
    MAX-ACCESS      read-write
    STATUS          current
    DESCRIPTION     
            "The tone package to be used for this service."
    ::= { sonusIsdnsgServiceGroupEntry 33 }

sonusIsdnsgServiceGroupT302 OBJECT-TYPE
    SYNTAX          Integer32 (0..127)
    MAX-ACCESS      read-only
    STATUS          current
    DESCRIPTION     
            "This T302 of Q.931 timer is used for both user and network sides."
    DEFVAL          { 15 }
    ::= { sonusIsdnsgServiceGroupEntry 34 }

sonusIsdnsgServiceGroupT303 OBJECT-TYPE
    SYNTAX          Integer32 (0..127)
    MAX-ACCESS      read-only
    STATUS          current
    DESCRIPTION     
            "This T303 of Q.931 timer is used for both user and network sides."
    DEFVAL          { 4 }
    ::= { sonusIsdnsgServiceGroupEntry 35 }

sonusIsdnsgServiceGroupT304 OBJECT-TYPE
    SYNTAX          Integer32 (0..127)
    MAX-ACCESS      read-only
    STATUS          current
    DESCRIPTION     
            "This T304 of Q.931 timer is used for both user and network sides."
    DEFVAL          { 30 }
    ::= { sonusIsdnsgServiceGroupEntry 36 }

sonusIsdnsgServiceGroupT305 OBJECT-TYPE
    SYNTAX          Integer32 (0..127)
    MAX-ACCESS      read-only
    STATUS          current
    DESCRIPTION     
            "This T305 of Q.931 timer is used for both user and network sides."
    DEFVAL          { 30 }
    ::= { sonusIsdnsgServiceGroupEntry 37 }

sonusIsdnsgServiceGroupT306 OBJECT-TYPE
    SYNTAX          Integer32 (0..127)
    MAX-ACCESS      read-only
    STATUS          current
    DESCRIPTION     
            "This T306 of Q.931 timer is used for network side only."
    DEFVAL          { 30 }
    ::= { sonusIsdnsgServiceGroupEntry 38 }

sonusIsdnsgServiceGroupT308 OBJECT-TYPE
    SYNTAX          Integer32 (0..127)
    MAX-ACCESS      read-only
    STATUS          current
    DESCRIPTION     
            "This T308 of Q.931 timer is used for both user and network sides."
    DEFVAL          { 4 }
    ::= { sonusIsdnsgServiceGroupEntry 39 }

sonusIsdnsgServiceGroupT309 OBJECT-TYPE
    SYNTAX          Integer32 (0..127)
    MAX-ACCESS      read-only
    STATUS          current
    DESCRIPTION     
            "This T309 of Q.931 timer is used for both user and network sides."
    DEFVAL          { 90 }
    ::= { sonusIsdnsgServiceGroupEntry 40 }

sonusIsdnsgServiceGroupT310 OBJECT-TYPE
    SYNTAX          Integer32 (0..127)
    MAX-ACCESS      read-only
    STATUS          current
    DESCRIPTION     
            "This T310 of Q.931 timer is used for both user and network sides."
    DEFVAL          { 15 }
    ::= { sonusIsdnsgServiceGroupEntry 41 }

sonusIsdnsgServiceGroupT312 OBJECT-TYPE
    SYNTAX          Integer32 (0..127)
    MAX-ACCESS      read-only
    STATUS          current
    DESCRIPTION     
            "This T312 of Q.931 timer is used for network side only."
    DEFVAL          { 6 }
    ::= { sonusIsdnsgServiceGroupEntry 42 }

sonusIsdnsgServiceGroupT313 OBJECT-TYPE
    SYNTAX          Integer32 (0..127)
    MAX-ACCESS      read-only
    STATUS          current
    DESCRIPTION     
            "This T313 of Q.931 timer is used for user side only."
    DEFVAL          { 4 }
    ::= { sonusIsdnsgServiceGroupEntry 43 }

sonusIsdnsgServiceGroupT314 OBJECT-TYPE
    SYNTAX          Integer32 (0..127)
    MAX-ACCESS      read-only
    STATUS          current
    DESCRIPTION     
            "This T314 of Q.931 timer is used for both user and network sides"
    DEFVAL          { 4 }
    ::= { sonusIsdnsgServiceGroupEntry 44 }

sonusIsdnsgServiceGroupT318 OBJECT-TYPE
    SYNTAX          Integer32 (0..127)
    MAX-ACCESS      read-only
    STATUS          current
    DESCRIPTION     
            "This T318 of Q.931 timer is used for user side only."
    DEFVAL          { 4 }
    ::= { sonusIsdnsgServiceGroupEntry 45 }

sonusIsdnsgServiceGroupT319 OBJECT-TYPE
    SYNTAX          Integer32 (0..127)
    MAX-ACCESS      read-only
    STATUS          current
    DESCRIPTION     
            "This T319 of Q.931 timer is used for user side only."
    DEFVAL          { 4 }
    ::= { sonusIsdnsgServiceGroupEntry 46 }

sonusIsdnsgServiceGroupT322 OBJECT-TYPE
    SYNTAX          Integer32 (0..127)
    MAX-ACCESS      read-only
    STATUS          current
    DESCRIPTION     
            "This T322 of Q.931 timer is used for network side only."
    DEFVAL          { 4 }
    ::= { sonusIsdnsgServiceGroupEntry 47 }

sonusIsdnsgServiceGroupK OBJECT-TYPE
    SYNTAX          Integer32 (1..127)
    MAX-ACCESS      read-only
    STATUS          current
    DESCRIPTION     
            "The maximum number of outstanding I frames. This K of Q.921 parameter is used for both user and network sides."
    DEFVAL          { 7 }
    ::= { sonusIsdnsgServiceGroupEntry 48 }

sonusIsdnsgServiceGroupT200 OBJECT-TYPE
    SYNTAX          Integer32 (1..255)
    MAX-ACCESS      read-only
    STATUS          current
    DESCRIPTION     
            "This T200 of Q.921 timer is used for both user and network sides."
    DEFVAL          { 1 }
    ::= { sonusIsdnsgServiceGroupEntry 49 }

sonusIsdnsgServiceGroupT203 OBJECT-TYPE
    SYNTAX          Integer32 (0..255)
    MAX-ACCESS      read-only
    STATUS          current
    DESCRIPTION     
            "This T203 of Q.921 timer is used for both user and network sides."
    DEFVAL          { 0 }
    ::= { sonusIsdnsgServiceGroupEntry 50 }

sonusIsdnsgServiceGroupN200 OBJECT-TYPE
    SYNTAX          Integer32 (1..100)
    MAX-ACCESS      read-only
    STATUS          current
    DESCRIPTION     
            "The maximum number of retransmissions of a frame. This N200 of Q.921 parameter is used for both user and network sides."
    DEFVAL          { 3 }
    ::= { sonusIsdnsgServiceGroupEntry 51 }

sonusIsdnsgServiceGroupN201 OBJECT-TYPE
    SYNTAX          Integer32 (1..260)
    MAX-ACCESS      read-only
    STATUS          current
    DESCRIPTION     
            "The maximum number of octets in an information field. This N201 of Q.921 parameter is used for both user and network sides."
    DEFVAL          { 260 }
    ::= { sonusIsdnsgServiceGroupEntry 52 }

sonusIsdnsgServiceGroupBchannelInitialRestart OBJECT-TYPE
    SYNTAX          INTEGER { yes(1), no(2) }
    MAX-ACCESS      read-write
    STATUS          current
    DESCRIPTION     
            "Controls wether RESTARTs are used to initially bring channels into service"
    DEFVAL          { yes }
    ::= { sonusIsdnsgServiceGroupEntry 53 }

sonusIsdnsgServiceGroupIuaApplicationServer OBJECT-TYPE
    SYNTAX          SonusNameReference
    MAX-ACCESS      read-write
    STATUS          current
    DESCRIPTION     
            "IUA Application server to which this D-channel belongs to"
    ::= { sonusIsdnsgServiceGroupEntry 54 }

sonusIsdnsgServiceGroupIuaAutoDatalinkEstablish OBJECT-TYPE
    SYNTAX          INTEGER { yes(1), no(2) }
    MAX-ACCESS      read-write
    STATUS          current
    DESCRIPTION     
            "Controls automatic datalink establishment upon IUA application server activation"
    DEFVAL          { no }
    ::= { sonusIsdnsgServiceGroupEntry 55 }

sonusIsdnsgServiceGroupStatTable OBJECT-TYPE
    SYNTAX          SEQUENCE OF SonusIsdnsgServiceGroupStatEntry
    MAX-ACCESS      not-accessible
    STATUS          current
    DESCRIPTION     
            "This table contains status information about each ISDN service group
             in the GSX9000 Switch node."
    ::= { sonusIsdnServiceGroupMIBObjects 2 }

sonusIsdnsgServiceGroupStatEntry OBJECT-TYPE
    SYNTAX          SonusIsdnsgServiceGroupStatEntry
    MAX-ACCESS      not-accessible
    STATUS          current
    DESCRIPTION     
            "This table describes the status of the Service Groups that are configured
             as destinations ISDN nodes for the GSX9000 Switch node."
    INDEX           { sonusIsdnsgServiceGroupStatListIndex }
    ::= { sonusIsdnsgServiceGroupStatTable 1 }

SonusIsdnsgServiceGroupStatEntry ::=
    SEQUENCE {
        sonusIsdnsgServiceGroupStatListIndex    Integer32,
        sonusIsdnsgServiceGroupStatStatus INTEGER,
        sonusIsdnsgServiceGroupStatTgMode INTEGER,
        sonusIsdnsgServiceGroupStatNumBchConfigured           Integer32,
        sonusIsdnsgServiceGroupStatNumBchAvailable          Integer32,
        sonusIsdnsgServiceGroupStatInCallsActive        Counter32,
        sonusIsdnsgServiceGroupStatInCalls  Counter32,
        sonusIsdnsgServiceGroupStatInConnected      Counter32,
        sonusIsdnsgServiceGroupStatOutCallsActive         Counter32,
        sonusIsdnsgServiceGroupStatOutCalls   Counter32,
        sonusIsdnsgServiceGroupStatOutConnected       Counter32,
        sonusIsdnsgServiceGroupStatPrimaryDchannel          INTEGER,
        sonusIsdnsgServiceGroupStatPrimaryDchInPkts           Counter32,
        sonusIsdnsgServiceGroupStatPrimaryDchOutPkts            Counter32,
        sonusIsdnsgServiceGroupStatPrimaryDchInBytes            Counter32,
        sonusIsdnsgServiceGroupStatPrimaryDchOutBytes             Counter32,
        sonusIsdnsgServiceGroupStatBackupDchannel         INTEGER,
        sonusIsdnsgServiceGroupStatBackupDchInPkts          Counter32,
        sonusIsdnsgServiceGroupStatBackupDchOutPkts           Counter32,
        sonusIsdnsgServiceGroupStatBackupDchInBytes           Counter32,
        sonusIsdnsgServiceGroupStatBackupDchOutBytes            Counter32
    }

sonusIsdnsgServiceGroupStatListIndex OBJECT-TYPE
    SYNTAX          Integer32
    MAX-ACCESS      read-only
    STATUS          current
    DESCRIPTION     
            "The index of the ISDN Service Group."
    ::= { sonusIsdnsgServiceGroupStatEntry 1 }

sonusIsdnsgServiceGroupStatStatus OBJECT-TYPE
    SYNTAX          INTEGER { available(1), unavailable(2), dryup(3) }
    MAX-ACCESS      read-only
    STATUS          current
    DESCRIPTION     
            "The state of the ISDN Service Group."
    ::= { sonusIsdnsgServiceGroupStatEntry 2 }

sonusIsdnsgServiceGroupStatTgMode OBJECT-TYPE
    SYNTAX          INTEGER { inService(1), outOfService(2) }
    MAX-ACCESS      read-only
    STATUS          current
    DESCRIPTION     
            "The state of the Trunk Group that this ISDN Service Group belongs to."
    ::= { sonusIsdnsgServiceGroupStatEntry 3 }

sonusIsdnsgServiceGroupStatNumBchConfigured OBJECT-TYPE
    SYNTAX          Integer32
    MAX-ACCESS      read-only
    STATUS          current
    DESCRIPTION     
            "Number of Bchannels configured for this ISDN service group."
    ::= { sonusIsdnsgServiceGroupStatEntry 4 }

sonusIsdnsgServiceGroupStatNumBchAvailable OBJECT-TYPE
    SYNTAX          Integer32
    MAX-ACCESS      read-only
    STATUS          current
    DESCRIPTION     
            "Number of Bchannels available in this ISDN service group."
    ::= { sonusIsdnsgServiceGroupStatEntry 5 }

sonusIsdnsgServiceGroupStatInCallsActive OBJECT-TYPE
    SYNTAX          Counter32
    MAX-ACCESS      read-only
    STATUS          current
    DESCRIPTION     
            "Number of incoming active calls."
    ::= { sonusIsdnsgServiceGroupStatEntry 6 }

sonusIsdnsgServiceGroupStatInCalls OBJECT-TYPE
    SYNTAX          Counter32
    MAX-ACCESS      read-only
    STATUS          current
    DESCRIPTION     
            "Number of incoming call attemps."
    ::= { sonusIsdnsgServiceGroupStatEntry 7 }

sonusIsdnsgServiceGroupStatInConnected OBJECT-TYPE
    SYNTAX          Counter32
    MAX-ACCESS      read-only
    STATUS          current
    DESCRIPTION     
            "Number of incoming calls connected."
    ::= { sonusIsdnsgServiceGroupStatEntry 8 }

sonusIsdnsgServiceGroupStatOutCallsActive OBJECT-TYPE
    SYNTAX          Counter32
    MAX-ACCESS      read-only
    STATUS          current
    DESCRIPTION     
            "Number of outgoing active calls."
    ::= { sonusIsdnsgServiceGroupStatEntry 9 }

sonusIsdnsgServiceGroupStatOutCalls OBJECT-TYPE
    SYNTAX          Counter32
    MAX-ACCESS      read-only
    STATUS          current
    DESCRIPTION     
            "Number of outgoing call attemps."
    ::= { sonusIsdnsgServiceGroupStatEntry 10 }

sonusIsdnsgServiceGroupStatOutConnected OBJECT-TYPE
    SYNTAX          Counter32
    MAX-ACCESS      read-only
    STATUS          current
    DESCRIPTION     
            "Number of outgoing calls connected."
    ::= { sonusIsdnsgServiceGroupStatEntry 11 }

sonusIsdnsgServiceGroupStatPrimaryDchannel OBJECT-TYPE
    SYNTAX          INTEGER { inService(1), outOfService(2), 
                        manualOos(3), standby(4), maintenanceBusy(5), 
                        unEquipped(6), wait(7) }
    MAX-ACCESS      read-only
    STATUS          current
    DESCRIPTION     
            "The state of the Primary Dchannel of the ISDN Service Group."
    ::= { sonusIsdnsgServiceGroupStatEntry 12 }

sonusIsdnsgServiceGroupStatPrimaryDchInPkts OBJECT-TYPE
    SYNTAX          Counter32
    MAX-ACCESS      read-only
    STATUS          current
    DESCRIPTION     
            "Number of packets received on the primary D-channel."
    ::= { sonusIsdnsgServiceGroupStatEntry 13 }

sonusIsdnsgServiceGroupStatPrimaryDchOutPkts OBJECT-TYPE
    SYNTAX          Counter32
    MAX-ACCESS      read-only
    STATUS          current
    DESCRIPTION     
            "Number of packets sent on the primary D-channel."
    ::= { sonusIsdnsgServiceGroupStatEntry 14 }

sonusIsdnsgServiceGroupStatPrimaryDchInBytes OBJECT-TYPE
    SYNTAX          Counter32
    MAX-ACCESS      read-only
    STATUS          current
    DESCRIPTION     
            "Number of bytes received on the primary D-channel."
    ::= { sonusIsdnsgServiceGroupStatEntry 15 }

sonusIsdnsgServiceGroupStatPrimaryDchOutBytes OBJECT-TYPE
    SYNTAX          Counter32
    MAX-ACCESS      read-only
    STATUS          current
    DESCRIPTION     
            "Number of bytes sent on the primary D-channel."
    ::= { sonusIsdnsgServiceGroupStatEntry 16 }

sonusIsdnsgServiceGroupStatBackupDchannel OBJECT-TYPE
    SYNTAX          INTEGER { inService(1), outOfService(2), 
                        manualOos(3), standby(4), maintenanceBusy(5), 
                        unEquipped(6), wait(7) }
    MAX-ACCESS      read-only
    STATUS          current
    DESCRIPTION     
            "The state of the Backup Dchannel of the ISDN Service Group."
    ::= { sonusIsdnsgServiceGroupStatEntry 17 }

sonusIsdnsgServiceGroupStatBackupDchInPkts OBJECT-TYPE
    SYNTAX          Counter32
    MAX-ACCESS      read-only
    STATUS          current
    DESCRIPTION     
            "Number of packets received on the backup D-channel."
    ::= { sonusIsdnsgServiceGroupStatEntry 18 }

sonusIsdnsgServiceGroupStatBackupDchOutPkts OBJECT-TYPE
    SYNTAX          Counter32
    MAX-ACCESS      read-only
    STATUS          current
    DESCRIPTION     
            "Number of packets sent on the backup D-channel."
    ::= { sonusIsdnsgServiceGroupStatEntry 19 }

sonusIsdnsgServiceGroupStatBackupDchInBytes OBJECT-TYPE
    SYNTAX          Counter32
    MAX-ACCESS      read-only
    STATUS          current
    DESCRIPTION     
            "Number of bytes received on the backup D-channel."
    ::= { sonusIsdnsgServiceGroupStatEntry 20 }

sonusIsdnsgServiceGroupStatBackupDchOutBytes OBJECT-TYPE
    SYNTAX          Counter32
    MAX-ACCESS      read-only
    STATUS          current
    DESCRIPTION     
            "Number of bytes sent on the backup D-channel."
    ::= { sonusIsdnsgServiceGroupStatEntry 21 }

sonusIsdnsgProfile OBJECT IDENTIFIER
    ::= { sonusIsdnServiceGroupMIBObjects 3 }

sonusIsdnsgProfileNextIndex OBJECT-TYPE
    SYNTAX          Integer32
    MAX-ACCESS      read-only
    STATUS          current
    DESCRIPTION     
            "The next valid index to use when creating a new sonusIsdnsgProfileEntry"
    ::= { sonusIsdnsgProfile 1 }

sonusIsdnsgProfileTable OBJECT-TYPE
    SYNTAX          SEQUENCE OF SonusIsdnsgProfileEntry
    MAX-ACCESS      not-accessible
    STATUS          current
    DESCRIPTION     
            "This table contains ISDN Service Group Profiles."
    ::= { sonusIsdnsgProfile 2 }

sonusIsdnsgProfileEntry OBJECT-TYPE
    SYNTAX          SonusIsdnsgProfileEntry
    MAX-ACCESS      not-accessible
    STATUS          current
    DESCRIPTION     
            "This table describes the ISDN Service Groups profile."
    INDEX           { sonusIsdnsgProfileListIndex }
    ::= { sonusIsdnsgProfileTable 1 }

SonusIsdnsgProfileEntry ::=
    SEQUENCE {
        sonusIsdnsgProfileListIndex     Integer32,
        sonusIsdnsgProfileName          SonusName,
        sonusIsdnsgProfileTrunkGroup    SonusNameReference,
        sonusIsdnsgProfileHuntAlgorithm INTEGER,
        sonusIsdnsgProfileCost          Integer32,
        sonusIsdnsgProfileSwitchSide    INTEGER,
        sonusIsdnsgProfileSwitchType    INTEGER,
        sonusIsdnsgProfileSwitchProfile DisplayString,
        sonusIsdnsgProfileMode          SonusServiceState,
        sonusIsdnsgProfileAdminState    SonusAdminState,
        sonusIsdnsgProfileRowStatus     RowStatus,
        sonusIsdnsgProfileDefaultDirectoryNumber        DisplayString,
        sonusIsdnsgProfileCallingPartyNumberProvision             INTEGER,
        sonusIsdnsgProfileCallingPartyNumberDiscard           INTEGER,
        sonusIsdnsgProfileCallingPartyNumberDelivery            INTEGER,
        sonusIsdnsgProfileCallingPartySubAddressTransfer                INTEGER,
        sonusIsdnsgProfileCallingPartySubAddressDelivery                INTEGER,
        sonusIsdnsgProfileCallingPartyNumberPresentation                INTEGER
    }

sonusIsdnsgProfileListIndex OBJECT-TYPE
    SYNTAX          Integer32 (1..128)
    MAX-ACCESS      read-only
    STATUS          current
    DESCRIPTION     
            "The index of the ISDN Service Group entry."
    ::= { sonusIsdnsgProfileEntry 1 }

sonusIsdnsgProfileName OBJECT-TYPE
    SYNTAX          SonusName
    MAX-ACCESS      read-write
    STATUS          current
    DESCRIPTION     
            "The name of the ISDN Service Group."
    ::= { sonusIsdnsgProfileEntry 2 }

sonusIsdnsgProfileTrunkGroup OBJECT-TYPE
    SYNTAX          SonusNameReference
    MAX-ACCESS      read-write
    STATUS          current
    DESCRIPTION     
            "The Trunk Group, which the ISDN Service Group belongs to."
    ::= { sonusIsdnsgProfileEntry 3 }

sonusIsdnsgProfileHuntAlgorithm OBJECT-TYPE
    SYNTAX          INTEGER { lowlow(1), highhigh(2), circularforward(3), 
                        circularbackward(4) }
    MAX-ACCESS      read-write
    STATUS          current
    DESCRIPTION     
            "The hunting method used to select channels for calls destined
             to the Service Group destination."
    DEFVAL          { lowlow }
    ::= { sonusIsdnsgProfileEntry 4 }

sonusIsdnsgProfileCost OBJECT-TYPE
    SYNTAX          Integer32 (0..100)
    MAX-ACCESS      read-write
    STATUS          current
    DESCRIPTION     
            "The routing cost to the ISDN Service Group."
    DEFVAL          { 50 }
    ::= { sonusIsdnsgProfileEntry 5 }

sonusIsdnsgProfileSwitchSide OBJECT-TYPE
    SYNTAX          INTEGER { network(1), user(2), usersym(3) }
    MAX-ACCESS      read-write
    STATUS          deprecated
    DESCRIPTION     
            "The switch side the ISDN Service Group should act as.
             This MIB object has been replaced by the
             sonusIsdnsgSwitchProfileSwitchSide MIB object."
    DEFVAL          { network }
    ::= { sonusIsdnsgProfileEntry 6 }

sonusIsdnsgProfileSwitchType OBJECT-TYPE
    SYNTAX          INTEGER { ni2(1), dms250(2), dms100(3), 
                        lucent5ESS(4), lucent4ESS(5), euroIsdn(6), 
                        ins1500(7) }
    MAX-ACCESS      read-write
    STATUS          deprecated
    DESCRIPTION     
            "The network switch type where the ISDN Service Group resides.
             This MIB object has been replaced by the
             sonusIsdnsgSwitchProfileSwitchType MIB object."
    DEFVAL          { ni2 }
    ::= { sonusIsdnsgProfileEntry 7 }

sonusIsdnsgProfileSwitchProfile OBJECT-TYPE
    SYNTAX          DisplayString (SIZE(0..23))
    MAX-ACCESS      read-write
    STATUS          obsolete
    DESCRIPTION     
            "The ISDN Service Group switch profile name.
             This MIB object is a duplicate of the
             sonusIsdnsgServiceGroupSwitchProfileName."
    ::= { sonusIsdnsgProfileEntry 8 }

sonusIsdnsgProfileMode OBJECT-TYPE
    SYNTAX          SonusServiceState
    MAX-ACCESS      read-write
    STATUS          obsolete
    DESCRIPTION     
            "The mode of operation of channels in the ISDN Service Group.
             This MIB object is no longer applicable."
    DEFVAL          { inService }
    ::= { sonusIsdnsgProfileEntry 9 }

sonusIsdnsgProfileAdminState OBJECT-TYPE
    SYNTAX          SonusAdminState
    MAX-ACCESS      read-write
    STATUS          current
    DESCRIPTION     
            "The admin state of the ISDN Service Group."
    DEFVAL          { disabled }
    ::= { sonusIsdnsgProfileEntry 10 }

sonusIsdnsgProfileRowStatus OBJECT-TYPE
    SYNTAX          RowStatus
    MAX-ACCESS      read-write
    STATUS          current
    DESCRIPTION     
            ""
    ::= { sonusIsdnsgProfileEntry 11 }

sonusIsdnsgProfileDefaultDirectoryNumber OBJECT-TYPE
    SYNTAX          DisplayString (SIZE(0..30))
    MAX-ACCESS      read-write
    STATUS          current
    DESCRIPTION     
            "Default Directory number for the ISDN Service Profile."
    ::= { sonusIsdnsgProfileEntry 12 }

sonusIsdnsgProfileCallingPartyNumberProvision OBJECT-TYPE
    SYNTAX          INTEGER { necessary(1), notNecessary(2) }
    MAX-ACCESS      read-write
    STATUS          current
    DESCRIPTION     
            "Specifies wether the Calling Party Number is required in the incoming SETUP."
    DEFVAL          { necessary }
    ::= { sonusIsdnsgProfileEntry 13 }

sonusIsdnsgProfileCallingPartyNumberDiscard OBJECT-TYPE
    SYNTAX          INTEGER { yes(1), no(2) }
    MAX-ACCESS      read-write
    STATUS          current
    DESCRIPTION     
            "Controls discard of Calling Party Numbers not screened or that failed screening."
    DEFVAL          { no }
    ::= { sonusIsdnsgProfileEntry 14 }

sonusIsdnsgProfileCallingPartyNumberDelivery OBJECT-TYPE
    SYNTAX          INTEGER { yes(1), no(2) }
    MAX-ACCESS      read-write
    STATUS          current
    DESCRIPTION     
            "Controls the delivery of the Calling Party Number within outgoing SETUP messages"
    DEFVAL          { yes }
    ::= { sonusIsdnsgProfileEntry 15 }

sonusIsdnsgProfileCallingPartySubAddressTransfer OBJECT-TYPE
    SYNTAX          INTEGER { yes(1), no(2), conditional(3) }
    MAX-ACCESS      read-write
    STATUS          current
    DESCRIPTION     
            "Controls the transfer of the Calling Party Subaddress Information Element"
    DEFVAL          { yes }
    ::= { sonusIsdnsgProfileEntry 16 }

sonusIsdnsgProfileCallingPartySubAddressDelivery OBJECT-TYPE
    SYNTAX          INTEGER { yes(1), no(2), conditional(3) }
    MAX-ACCESS      read-write
    STATUS          current
    DESCRIPTION     
            "Controls the delivery of the Calling Party Subaddress Information Element to the CPE"
    DEFVAL          { yes }
    ::= { sonusIsdnsgProfileEntry 17 }

sonusIsdnsgProfileCallingPartyNumberPresentation OBJECT-TYPE
    SYNTAX          INTEGER { yes(1), no(2) }
    MAX-ACCESS      read-write
    STATUS          current
    DESCRIPTION     
            "Used as Calling Party Number presentation indicator when none available in incoming SETUP."
    DEFVAL          { yes }
    ::= { sonusIsdnsgProfileEntry 18 }

sonusIsdnsgInterfaceTable OBJECT-TYPE
    SYNTAX          SEQUENCE OF SonusIsdnsgInterfaceEntry
    MAX-ACCESS      not-accessible
    STATUS          current
    DESCRIPTION     
            "The Isdnsg Interface table describes the interfaces in the indexed service
             group. This table is unavailable if the sonusIsdnsgServiceGroupStatStatus
             object indicates that this service group is unavailable."
    ::= { sonusIsdnServiceGroupMIBObjects 4 }

sonusIsdnsgInterfaceEntry OBJECT-TYPE
    SYNTAX          SonusIsdnsgInterfaceEntry
    MAX-ACCESS      not-accessible
    STATUS          current
    DESCRIPTION     
            ""
    INDEX           { sonusIsdnsgInterfaceServiceListIndex, 
                      sonusIsdnsgInterfaceIdentifier }
    ::= { sonusIsdnsgInterfaceTable 1 }

SonusIsdnsgInterfaceEntry ::=
    SEQUENCE {
        sonusIsdnsgInterfaceServiceListIndex    Integer32,
        sonusIsdnsgInterfaceIdentifier  Integer32,
        sonusIsdnsgInterfacePortName    SonusNameReference,
        sonusIsdnsgInterfaceOperation   INTEGER,
        sonusIsdnsgInterfaceAdminState  SonusAdminState,
        sonusIsdnsgInterfaceRowStatus   RowStatus
    }

sonusIsdnsgInterfaceServiceListIndex OBJECT-TYPE
    SYNTAX          Integer32
    MAX-ACCESS      read-only
    STATUS          current
    DESCRIPTION     
            "The index of the ISDN Service Group interface is defined for."
    ::= { sonusIsdnsgInterfaceEntry 1 }

sonusIsdnsgInterfaceIdentifier OBJECT-TYPE
    SYNTAX          Integer32 (0..127)
    MAX-ACCESS      read-only
    STATUS          current
    DESCRIPTION     
            "The Q931 interface identifier of the interface."
    ::= { sonusIsdnsgInterfaceEntry 2 }

sonusIsdnsgInterfacePortName OBJECT-TYPE
    SYNTAX          SonusNameReference
    MAX-ACCESS      read-write
    STATUS          current
    DESCRIPTION     
            "The name of the port interface is on."
    ::= { sonusIsdnsgInterfaceEntry 3 }

sonusIsdnsgInterfaceOperation OBJECT-TYPE
    SYNTAX          INTEGER { restart(1) }
    MAX-ACCESS      read-write
    STATUS          current
    DESCRIPTION     
            "Apply operation to the ISDN Interface."
    ::= { sonusIsdnsgInterfaceEntry 4 }

sonusIsdnsgInterfaceAdminState OBJECT-TYPE
    SYNTAX          SonusAdminState
    MAX-ACCESS      read-write
    STATUS          current
    DESCRIPTION     
            "The admin state of the ISDN Interface."
    DEFVAL          { disabled }
    ::= { sonusIsdnsgInterfaceEntry 5 }

sonusIsdnsgInterfaceRowStatus OBJECT-TYPE
    SYNTAX          RowStatus
    MAX-ACCESS      read-write
    STATUS          current
    DESCRIPTION     
            ""
    ::= { sonusIsdnsgInterfaceEntry 6 }

sonusIsdnsgBchannelTable OBJECT-TYPE
    SYNTAX          SEQUENCE OF SonusIsdnsgBchannelEntry
    MAX-ACCESS      not-accessible
    STATUS          current
    DESCRIPTION     
            "The Isdnsg B-channel table describes the B-channels in the indexed ISDN
             interface. This table is unavailable if the sonusisdnsgServiceGroupStatStatus
             object indicates that this service group is unavailable."
    ::= { sonusIsdnServiceGroupMIBObjects 5 }

sonusIsdnsgBchannelEntry OBJECT-TYPE
    SYNTAX          SonusIsdnsgBchannelEntry
    MAX-ACCESS      not-accessible
    STATUS          current
    DESCRIPTION     
            ""
    INDEX           { sonusIsdnsgBchannelServiceListIndex, 
                      sonusIsdnsgBchannelInterfaceIdentifier, 
                      sonusIsdnsgBchannelNumber }
    ::= { sonusIsdnsgBchannelTable 1 }

SonusIsdnsgBchannelEntry ::=
    SEQUENCE {
        sonusIsdnsgBchannelServiceListIndex   Integer32,
        sonusIsdnsgBchannelInterfaceIdentifier      Integer32,
        sonusIsdnsgBchannelNumber       Integer32,
        sonusIsdnsgBchannelCircuitProfileName     SonusNameReference,
        sonusIsdnsgBchannelDirection    INTEGER,
        sonusIsdnsgBchannelOperation    INTEGER,
        sonusIsdnsgBchannelMode         INTEGER,
        sonusIsdnsgBchannelAction       INTEGER,
        sonusIsdnsgBchannelTimeout      Integer32,
        sonusIsdnsgBchannelAdminState   SonusAdminState
    }

sonusIsdnsgBchannelServiceListIndex OBJECT-TYPE
    SYNTAX          Integer32
    MAX-ACCESS      read-only
    STATUS          current
    DESCRIPTION     
            "The index of the ISDN Service Group of the ISDN B-channel."
    ::= { sonusIsdnsgBchannelEntry 1 }

sonusIsdnsgBchannelInterfaceIdentifier OBJECT-TYPE
    SYNTAX          Integer32 (0..127)
    MAX-ACCESS      read-only
    STATUS          current
    DESCRIPTION     
            "The Q931 interface identifier of the ISDN B-channel."
    ::= { sonusIsdnsgBchannelEntry 2 }

sonusIsdnsgBchannelNumber OBJECT-TYPE
    SYNTAX          Integer32 (1..32)
    MAX-ACCESS      read-only
    STATUS          current
    DESCRIPTION     
            "The channel number of the ISDN B-channel."
    ::= { sonusIsdnsgBchannelEntry 3 }

sonusIsdnsgBchannelCircuitProfileName OBJECT-TYPE
    SYNTAX          SonusNameReference
    MAX-ACCESS      read-write
    STATUS          current
    DESCRIPTION     
            "The circuit profile name assigned to the ISDN B-channel."
    ::= { sonusIsdnsgBchannelEntry 4 }

sonusIsdnsgBchannelDirection OBJECT-TYPE
    SYNTAX          INTEGER { twoWay(1), oneWayIn(2), oneWayOut(3) }
    MAX-ACCESS      read-write
    STATUS          current
    DESCRIPTION     
            "Identifies the direction of traffic to be allowed on the ISDN B-channel."
    ::= { sonusIsdnsgBchannelEntry 5 }

sonusIsdnsgBchannelOperation OBJECT-TYPE
    SYNTAX          INTEGER { restart(1) }
    MAX-ACCESS      read-write
    STATUS          current
    DESCRIPTION     
            "Apply an operation to the ISDN B-channel."
    ::= { sonusIsdnsgBchannelEntry 6 }

sonusIsdnsgBchannelMode OBJECT-TYPE
    SYNTAX          INTEGER { outOfService(1), maintenance(2), 
                        inService(3) }
    MAX-ACCESS      read-write
    STATUS          current
    DESCRIPTION     
            "The mode of operation of the ISDN B-channel."
    ::= { sonusIsdnsgBchannelEntry 7 }

sonusIsdnsgBchannelAction OBJECT-TYPE
    SYNTAX          INTEGER { dryUp(1), force(2) }
    MAX-ACCESS      read-write
    STATUS          current
    DESCRIPTION     
            "The action taken on the ISDN B-channel when sonusIsdnsgBchannelMode is set to 
             out of service. This object should only be set in conjunction with sonusIsdnsgBchannelMode."
    ::= { sonusIsdnsgBchannelEntry 8 }

sonusIsdnsgBchannelTimeout OBJECT-TYPE
    SYNTAX          Integer32 (1..1440)
    MAX-ACCESS      read-write
    STATUS          current
    DESCRIPTION     
            "The timeout value in minutes for dryup action on the ISDN B-channel.
             This object should only be set in conjunction with sonusIsdnsgBchannelAction."
    ::= { sonusIsdnsgBchannelEntry 9 }

sonusIsdnsgBchannelAdminState OBJECT-TYPE
    SYNTAX          SonusAdminState
    MAX-ACCESS      read-write
    STATUS          current
    DESCRIPTION     
            "The admin state of the ISDN B-channel."
    ::= { sonusIsdnsgBchannelEntry 10 }

sonusIsdnsgBchannelStatTable OBJECT-TYPE
    SYNTAX          SEQUENCE OF SonusIsdnsgBchannelStatEntry
    MAX-ACCESS      not-accessible
    STATUS          current
    DESCRIPTION     
            "The Isdnsg B-channel status table describes the status of the B-channels 
             in the indexed ISDN interface. This table is unavailable if the 
             sonusisdnsgServiceGroupStatStatus object indicates that this service group 
             is unavailable."
    ::= { sonusIsdnServiceGroupMIBObjects 6 }

sonusIsdnsgBchannelStatEntry OBJECT-TYPE
    SYNTAX          SonusIsdnsgBchannelStatEntry
    MAX-ACCESS      not-accessible
    STATUS          current
    DESCRIPTION     
            ""
    INDEX           { sonusIsdnsgBchannelStatServiceListIndex, 
                      sonusIsdnsgBchannelStatInterfaceIdentifier, 
                      sonusIsdnsgBchannelStatNumber }
    ::= { sonusIsdnsgBchannelStatTable 1 }

SonusIsdnsgBchannelStatEntry ::=
    SEQUENCE {
        sonusIsdnsgBchannelStatServiceListIndex       Integer32,
        sonusIsdnsgBchannelStatInterfaceIdentifier          Integer32,
        sonusIsdnsgBchannelStatNumber   Integer32,
        sonusIsdnsgBchannelStatUsage    INTEGER,
        sonusIsdnsgBchannelStatLocalMaint INTEGER,
        sonusIsdnsgBchannelStatLocalHw  INTEGER,
        sonusIsdnsgBchannelStatRemoteMaint  INTEGER
    }

sonusIsdnsgBchannelStatServiceListIndex OBJECT-TYPE
    SYNTAX          Integer32
    MAX-ACCESS      read-only
    STATUS          current
    DESCRIPTION     
            "The index of the ISDN Service Group of the ISDN B-channel."
    ::= { sonusIsdnsgBchannelStatEntry 1 }

sonusIsdnsgBchannelStatInterfaceIdentifier OBJECT-TYPE
    SYNTAX          Integer32 (0..127)
    MAX-ACCESS      read-only
    STATUS          current
    DESCRIPTION     
            "The Q931 interface identifier of the ISDN B-channel."
    ::= { sonusIsdnsgBchannelStatEntry 2 }

sonusIsdnsgBchannelStatNumber OBJECT-TYPE
    SYNTAX          Integer32 (1..32)
    MAX-ACCESS      read-only
    STATUS          current
    DESCRIPTION     
            "The channel number of the ISDN B-channel."
    ::= { sonusIsdnsgBchannelStatEntry 3 }

sonusIsdnsgBchannelStatUsage OBJECT-TYPE
    SYNTAX          INTEGER { unequipped(1), idle(2), inBusy(3), 
                        outBusy(4), transientSetup(5), 
                        transientRelease(6) }
    MAX-ACCESS      read-only
    STATUS          current
    DESCRIPTION     
            "The usage state of the ISDN B-channel."
    ::= { sonusIsdnsgBchannelStatEntry 4 }

sonusIsdnsgBchannelStatLocalMaint OBJECT-TYPE
    SYNTAX          INTEGER { inService(1), maintenance(2), 
                        outOfService(3), transientInService(4), 
                        transientMaintenance(5), 
                        transientOutOfService(6), dryup(7), 
                        notAvailable(8) }
    MAX-ACCESS      read-only
    STATUS          current
    DESCRIPTION     
            "The local maintenance state of the ISDN B-channel."
    ::= { sonusIsdnsgBchannelStatEntry 5 }

sonusIsdnsgBchannelStatLocalHw OBJECT-TYPE
    SYNTAX          INTEGER { inService(1), outOfService(2), 
                        transientInService(3), transientOutOfService(4), 
                        notAvailable(5) }
    MAX-ACCESS      read-only
    STATUS          current
    DESCRIPTION     
            "The local hardware state of the ISDN B-channel."
    ::= { sonusIsdnsgBchannelStatEntry 6 }

sonusIsdnsgBchannelStatRemoteMaint OBJECT-TYPE
    SYNTAX          INTEGER { inService(1), maintenance(2), 
                        outOfService(3), transientInService(4), 
                        transientMaintenance(5), 
                        transientOutOfService(6), notAvailable(7), 
                        restarting(8), restartError(9), 
                        autoOutOfService(10) }
    MAX-ACCESS      read-only
    STATUS          current
    DESCRIPTION     
            "The remote maintenance state of the ISDN B-channel."
    ::= { sonusIsdnsgBchannelStatEntry 7 }

sonusIsdnsgSwitchProfile OBJECT IDENTIFIER
    ::= { sonusIsdnServiceGroupMIBObjects 7 }

sonusIsdnsgSwitchProfileNextIndex OBJECT-TYPE
    SYNTAX          Integer32
    MAX-ACCESS      read-only
    STATUS          current
    DESCRIPTION     
            "The next valid index to use when creating a new sonusIsdnsgSwitchProfileEntry"
    ::= { sonusIsdnsgSwitchProfile 1 }

sonusIsdnsgSwitchProfileTable OBJECT-TYPE
    SYNTAX          SEQUENCE OF SonusIsdnsgSwitchProfileEntry
    MAX-ACCESS      not-accessible
    STATUS          current
    DESCRIPTION     
            "This table contains ISDN switch profile information."
    ::= { sonusIsdnsgSwitchProfile 2 }

sonusIsdnsgSwitchProfileEntry OBJECT-TYPE
    SYNTAX          SonusIsdnsgSwitchProfileEntry
    MAX-ACCESS      not-accessible
    STATUS          current
    DESCRIPTION     
            "This table describes the ISDN Switch Profile that are configured
             on the GSX9000."
    INDEX           { sonusIsdnsgSwitchProfileListIndex }
    ::= { sonusIsdnsgSwitchProfileTable 1 }

SonusIsdnsgSwitchProfileEntry ::=
    SEQUENCE {
        sonusIsdnsgSwitchProfileListIndex Integer32,
        sonusIsdnsgSwitchProfileName    SonusName,
        sonusIsdnsgSwitchProfileSwitchSide  INTEGER,
        sonusIsdnsgSwitchProfileSwitchType  INTEGER,
        sonusIsdnsgSwitchProfileBchannelAvailabilitySignaling                     INTEGER,
        sonusIsdnsgSwitchProfileT302    Integer32,
        sonusIsdnsgSwitchProfileT303    Integer32,
        sonusIsdnsgSwitchProfileT304    Integer32,
        sonusIsdnsgSwitchProfileT305    Integer32,
        sonusIsdnsgSwitchProfileT306    Integer32,
        sonusIsdnsgSwitchProfileT308    Integer32,
        sonusIsdnsgSwitchProfileT309    Integer32,
        sonusIsdnsgSwitchProfileT310    Integer32,
        sonusIsdnsgSwitchProfileT312    Integer32,
        sonusIsdnsgSwitchProfileT313    Integer32,
        sonusIsdnsgSwitchProfileT314    Integer32,
        sonusIsdnsgSwitchProfileT318    Integer32,
        sonusIsdnsgSwitchProfileT319    Integer32,
        sonusIsdnsgSwitchProfileT322    Integer32,
        sonusIsdnsgSwitchProfileK       Integer32,
        sonusIsdnsgSwitchProfileT200    Integer32,
        sonusIsdnsgSwitchProfileT203    Integer32,
        sonusIsdnsgSwitchProfileN200    Integer32,
        sonusIsdnsgSwitchProfileN201    Integer32,
        sonusIsdnsgSwitchProfileAdminState  SonusAdminState,
        sonusIsdnsgSwitchProfileRowStatus RowStatus,
        sonusIsdnsgSwitchProfileBchannelInitialRestart              INTEGER
    }

sonusIsdnsgSwitchProfileListIndex OBJECT-TYPE
    SYNTAX          Integer32 (1..128)
    MAX-ACCESS      read-only
    STATUS          current
    DESCRIPTION     
            "The index of the ISDN Switch Profile entry."
    ::= { sonusIsdnsgSwitchProfileEntry 1 }

sonusIsdnsgSwitchProfileName OBJECT-TYPE
    SYNTAX          SonusName
    MAX-ACCESS      read-write
    STATUS          current
    DESCRIPTION     
            "The name of the ISDN Switch Profile."
    ::= { sonusIsdnsgSwitchProfileEntry 2 }

sonusIsdnsgSwitchProfileSwitchSide OBJECT-TYPE
    SYNTAX          INTEGER { network(1), user(2) }
    MAX-ACCESS      read-write
    STATUS          current
    DESCRIPTION     
            "The switch side the ISDN Switch Profile should act as."
    DEFVAL          { network }
    ::= { sonusIsdnsgSwitchProfileEntry 3 }

sonusIsdnsgSwitchProfileSwitchType OBJECT-TYPE
    SYNTAX          INTEGER { ni2(1), dms250(2), dms100(3), 
                        lucent5ESS(4), lucent4ESS(5), euroIsdn(6), 
                        ins1500(7) }
    MAX-ACCESS      read-write
    STATUS          current
    DESCRIPTION     
            "The network switch type where the ISDN Switch Profile resides."
    DEFVAL          { ni2 }
    ::= { sonusIsdnsgSwitchProfileEntry 4 }

sonusIsdnsgSwitchProfileBchannelAvailabilitySignaling OBJECT-TYPE
    SYNTAX          INTEGER { yes(1), no(2) }
    MAX-ACCESS      read-write
    STATUS          current
    DESCRIPTION     
            "Used to enable or disable the B-channel availability signaling procedures."
    DEFVAL          { yes }
    ::= { sonusIsdnsgSwitchProfileEntry 5 }

sonusIsdnsgSwitchProfileT302 OBJECT-TYPE
    SYNTAX          Integer32 (0..127)
    MAX-ACCESS      read-write
    STATUS          current
    DESCRIPTION     
            "This T302 of Q.931 timer is used for both user and network sides."
    DEFVAL          { 15 }
    ::= { sonusIsdnsgSwitchProfileEntry 6 }

sonusIsdnsgSwitchProfileT303 OBJECT-TYPE
    SYNTAX          Integer32 (0..127)
    MAX-ACCESS      read-write
    STATUS          current
    DESCRIPTION     
            "This T303 of Q.931 timer is used for both user and network sides."
    DEFVAL          { 4 }
    ::= { sonusIsdnsgSwitchProfileEntry 7 }

sonusIsdnsgSwitchProfileT304 OBJECT-TYPE
    SYNTAX          Integer32 (0..127)
    MAX-ACCESS      read-write
    STATUS          current
    DESCRIPTION     
            "This T304 of Q.931 timer is used for both user and network sides."
    DEFVAL          { 30 }
    ::= { sonusIsdnsgSwitchProfileEntry 8 }

sonusIsdnsgSwitchProfileT305 OBJECT-TYPE
    SYNTAX          Integer32 (0..127)
    MAX-ACCESS      read-write
    STATUS          current
    DESCRIPTION     
            "This T305 of Q.931 timer is used for both user and network sides."
    DEFVAL          { 30 }
    ::= { sonusIsdnsgSwitchProfileEntry 9 }

sonusIsdnsgSwitchProfileT306 OBJECT-TYPE
    SYNTAX          Integer32 (0..127)
    MAX-ACCESS      read-write
    STATUS          current
    DESCRIPTION     
            "This T306 of Q.931 timer is used for network side only."
    DEFVAL          { 30 }
    ::= { sonusIsdnsgSwitchProfileEntry 10 }

sonusIsdnsgSwitchProfileT308 OBJECT-TYPE
    SYNTAX          Integer32 (0..127)
    MAX-ACCESS      read-write
    STATUS          current
    DESCRIPTION     
            "This T308 of Q.931 timer is used for both user and network sides."
    DEFVAL          { 4 }
    ::= { sonusIsdnsgSwitchProfileEntry 11 }

sonusIsdnsgSwitchProfileT309 OBJECT-TYPE
    SYNTAX          Integer32 (0..127)
    MAX-ACCESS      read-write
    STATUS          current
    DESCRIPTION     
            "This T309 of Q.931 timer is used for both user and network sides."
    DEFVAL          { 90 }
    ::= { sonusIsdnsgSwitchProfileEntry 12 }

sonusIsdnsgSwitchProfileT310 OBJECT-TYPE
    SYNTAX          Integer32 (0..127)
    MAX-ACCESS      read-write
    STATUS          current
    DESCRIPTION     
            "This T310 of Q.931 timer is used for both user and network sides."
    DEFVAL          { 15 }
    ::= { sonusIsdnsgSwitchProfileEntry 13 }

sonusIsdnsgSwitchProfileT312 OBJECT-TYPE
    SYNTAX          Integer32 (0..127)
    MAX-ACCESS      read-write
    STATUS          current
    DESCRIPTION     
            "This T312 of Q.931 timer is used for network side only."
    DEFVAL          { 6 }
    ::= { sonusIsdnsgSwitchProfileEntry 14 }

sonusIsdnsgSwitchProfileT313 OBJECT-TYPE
    SYNTAX          Integer32 (0..127)
    MAX-ACCESS      read-write
    STATUS          current
    DESCRIPTION     
            "This T313 of Q.931 timer is used for user side only."
    DEFVAL          { 4 }
    ::= { sonusIsdnsgSwitchProfileEntry 15 }

sonusIsdnsgSwitchProfileT314 OBJECT-TYPE
    SYNTAX          Integer32 (0..127)
    MAX-ACCESS      read-write
    STATUS          current
    DESCRIPTION     
            "This T314 of Q.931 timer is used for both user and network sides"
    DEFVAL          { 4 }
    ::= { sonusIsdnsgSwitchProfileEntry 16 }

sonusIsdnsgSwitchProfileT318 OBJECT-TYPE
    SYNTAX          Integer32 (0..127)
    MAX-ACCESS      read-write
    STATUS          current
    DESCRIPTION     
            "This T318 of Q.931 timer is used for user side only."
    DEFVAL          { 4 }
    ::= { sonusIsdnsgSwitchProfileEntry 17 }

sonusIsdnsgSwitchProfileT319 OBJECT-TYPE
    SYNTAX          Integer32 (0..127)
    MAX-ACCESS      read-write
    STATUS          current
    DESCRIPTION     
            "This T319 of Q.931 timer is used for user side only."
    DEFVAL          { 4 }
    ::= { sonusIsdnsgSwitchProfileEntry 18 }

sonusIsdnsgSwitchProfileT322 OBJECT-TYPE
    SYNTAX          Integer32 (0..127)
    MAX-ACCESS      read-write
    STATUS          current
    DESCRIPTION     
            "This T322 of Q.931 timer is used for network side only."
    DEFVAL          { 4 }
    ::= { sonusIsdnsgSwitchProfileEntry 19 }

sonusIsdnsgSwitchProfileK OBJECT-TYPE
    SYNTAX          Integer32 (1..127)
    MAX-ACCESS      read-write
    STATUS          current
    DESCRIPTION     
            "The maximum number of outstanding I frames. This K of Q.921 parameter is used for both user and network sides."
    DEFVAL          { 7 }
    ::= { sonusIsdnsgSwitchProfileEntry 20 }

sonusIsdnsgSwitchProfileT200 OBJECT-TYPE
    SYNTAX          Integer32 (1..255)
    MAX-ACCESS      read-write
    STATUS          current
    DESCRIPTION     
            "This T200 of Q.921 timer is used for both user and network sides."
    DEFVAL          { 1 }
    ::= { sonusIsdnsgSwitchProfileEntry 21 }

sonusIsdnsgSwitchProfileT203 OBJECT-TYPE
    SYNTAX          Integer32 (0..255)
    MAX-ACCESS      read-write
    STATUS          current
    DESCRIPTION     
            "This T203 of Q.921 timer is used for both user and network sides."
    DEFVAL          { 0 }
    ::= { sonusIsdnsgSwitchProfileEntry 22 }

sonusIsdnsgSwitchProfileN200 OBJECT-TYPE
    SYNTAX          Integer32 (1..100)
    MAX-ACCESS      read-write
    STATUS          current
    DESCRIPTION     
            "The maximum number of retransmissions of a frame. This N200 of Q.921 parameter is used for both user and network sides."
    DEFVAL          { 3 }
    ::= { sonusIsdnsgSwitchProfileEntry 23 }

sonusIsdnsgSwitchProfileN201 OBJECT-TYPE
    SYNTAX          Integer32 (1..260)
    MAX-ACCESS      read-write
    STATUS          current
    DESCRIPTION     
            "The maximum number of octets in an information field. This N201 of Q.921 parameter is used for both user and network sides."
    DEFVAL          { 260 }
    ::= { sonusIsdnsgSwitchProfileEntry 24 }

sonusIsdnsgSwitchProfileAdminState OBJECT-TYPE
    SYNTAX          SonusAdminState
    MAX-ACCESS      read-write
    STATUS          current
    DESCRIPTION     
            "The admin state of the ISDN Switch Profile."
    DEFVAL          { disabled }
    ::= { sonusIsdnsgSwitchProfileEntry 25 }

sonusIsdnsgSwitchProfileRowStatus OBJECT-TYPE
    SYNTAX          RowStatus
    MAX-ACCESS      read-write
    STATUS          current
    DESCRIPTION     
            "The row status of the ISDN Switch Profile."
    ::= { sonusIsdnsgSwitchProfileEntry 26 }

sonusIsdnsgSwitchProfileBchannelInitialRestart OBJECT-TYPE
    SYNTAX          INTEGER { yes(1), no(2) }
    MAX-ACCESS      read-write
    STATUS          current
    DESCRIPTION     
            "Controls wether RESTARTs are used to initially bring channels into service"
    DEFVAL          { yes }
    ::= { sonusIsdnsgSwitchProfileEntry 27 }

sonusIsdnServiceGroupMIBNotifications OBJECT IDENTIFIER
    ::= { sonusIsdnServiceGroupMIB 2 }

sonusIsdnServiceGroupMIBNotificationsPrefix OBJECT IDENTIFIER
    ::= { sonusIsdnServiceGroupMIBNotifications 0 }

sonusIsdnServiceGroupMIBNotificationsObjects OBJECT IDENTIFIER
    ::= { sonusIsdnServiceGroupMIBNotifications 1 }

sonusIsdnSvcGrpName OBJECT-TYPE
    SYNTAX          DisplayString (SIZE(0..23))
    MAX-ACCESS      read-only
    STATUS          current
    DESCRIPTION     
            "Name of the ISDN service group."
    ::= { sonusIsdnServiceGroupMIBNotificationsObjects 1 }

sonusIsdnInterfaceId OBJECT-TYPE
    SYNTAX          Integer32 (0..127)
    MAX-ACCESS      read-only
    STATUS          current
    DESCRIPTION     
            "The Q931 interface identifier of the ISDN interface."
    ::= { sonusIsdnServiceGroupMIBNotificationsObjects 2 }

sonusIsdnBchannelOffsets OBJECT-TYPE
    SYNTAX          BITS { bchOffset0(0), bchOffset1(1), bchOffset2(2), 
                        bchOffset3(3), bchOffset4(4), bchOffset5(5), 
                        bchOffset6(6), bchOffset7(7), bchOffset8(8), 
                        bchOffset9(9), bchOffset10(10), bchOffset11(11), 
                        bchOffset12(12), bchOffset13(13), 
                        bchOffset14(14), bchOffset15(15), 
                        bchOffset16(16), bchOffset17(17), 
                        bchOffset18(18), bchOffset19(19), 
                        bchOffset20(20), bchOffset21(21), 
                        bchOffset22(22), bchOffset23(23) }
    MAX-ACCESS      read-only
    STATUS          current
    DESCRIPTION     
            "B-channel maintenance status bitmap."
    ::= { sonusIsdnServiceGroupMIBNotificationsObjects 3 }

sonusIsdnSvcGrpInServiceNotification NOTIFICATION-TYPE
    OBJECTS         { sonusIsdnSvcGrpName, sonusEventDescription, 
                      sonusEventClass, sonusEventLevel }
    STATUS          current
    DESCRIPTION     
            "This trap indicates that the specified ISDN Service Group
             was placed in service."
    ::= { sonusIsdnServiceGroupMIBNotificationsPrefix 1 }

sonusIsdnSvcGrpOutOfServiceNotification NOTIFICATION-TYPE
    OBJECTS         { sonusIsdnSvcGrpName, sonusEventDescription, 
                      sonusEventClass, sonusEventLevel }
    STATUS          current
    DESCRIPTION     
            "This trap indicates that the specified ISDN Service Group
             was taken out of service."
    ::= { sonusIsdnServiceGroupMIBNotificationsPrefix 2 }

sonusIsdnBChannelInServiceNotification NOTIFICATION-TYPE
    OBJECTS         { sonusIsdnSvcGrpName, sonusIsdnInterfaceId, 
                      sonusIsdnBchannelOffsets, sonusEventDescription, 
                      sonusEventClass, sonusEventLevel }
    STATUS          current
    DESCRIPTION     
            "This trap indicates that the specified ISDN B Channels
             are placed in service."
    ::= { sonusIsdnServiceGroupMIBNotificationsPrefix 3 }

sonusIsdnBChannelOutOfServiceNotification NOTIFICATION-TYPE
    OBJECTS         { sonusIsdnSvcGrpName, sonusIsdnInterfaceId, 
                      sonusIsdnBchannelOffsets, sonusEventDescription, 
                      sonusEventClass, sonusEventLevel }
    STATUS          current
    DESCRIPTION     
            "This trap indicates that the specified ISDN B Channels
             are taken out of service."
    ::= { sonusIsdnServiceGroupMIBNotificationsPrefix 4 }

sonusIsdnPrimaryDChannelInServiceNotification NOTIFICATION-TYPE
    OBJECTS         { sonusIsdnSvcGrpName, sonusEventDescription, 
                      sonusEventClass, sonusEventLevel }
    STATUS          current
    DESCRIPTION     
            "This trap indicates that the Primary D Channel for the
             specified ISDN Service Group was placed in service."
    ::= { sonusIsdnServiceGroupMIBNotificationsPrefix 5 }

sonusIsdnPrimaryDChannelOutOfServiceNotification NOTIFICATION-TYPE
    OBJECTS         { sonusIsdnSvcGrpName, sonusEventDescription, 
                      sonusEventClass, sonusEventLevel }
    STATUS          current
    DESCRIPTION     
            "This trap indicates that the Primary D Channel for the
             specified ISDN Service Group was taken out of service."
    ::= { sonusIsdnServiceGroupMIBNotificationsPrefix 6 }

sonusIsdnBackupDChannelInServiceNotification NOTIFICATION-TYPE
    OBJECTS         { sonusIsdnSvcGrpName, sonusEventDescription, 
                      sonusEventClass, sonusEventLevel }
    STATUS          current
    DESCRIPTION     
            "This trap indicates that the Backup D Channel for the
             specified ISDN Service Group was placed in service."
    ::= { sonusIsdnServiceGroupMIBNotificationsPrefix 7 }

sonusIsdnBackupDChannelOutOfServiceNotification NOTIFICATION-TYPE
    OBJECTS         { sonusIsdnSvcGrpName, sonusEventDescription, 
                      sonusEventClass, sonusEventLevel }
    STATUS          current
    DESCRIPTION     
            "This trap indicates that the Backup D Channel for the
             specified ISDN Service Group was taken out of service."
    ::= { sonusIsdnServiceGroupMIBNotificationsPrefix 8 }

END -- end of module SONUS-ISDN-SERVICE-GROUP-MIB.
