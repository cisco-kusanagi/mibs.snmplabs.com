-- MIB created 5/06/99 21:06:16, by
--   SMIC (the next generation) version 1.6.29, November 22, 1994.

WAN-RESTORAL-REROUTE-MIB DEFINITIONS ::= BEGIN

-- From file: "ibmwrr.mi2"
-- Compile options "G A T M"

IMPORTS
    Counter32, Integer32, TimeTicks
            FROM SNMPv2-SMI
    OBJECT-TYPE
            FROM RFC-1212
    enterprises
            FROM RFC1155-SMI
    DisplayString
            FROM SNMPv2-TC;

ibmWanRestoralRerouteMIB OBJECT IDENTIFIER ::= { enterprises ibm(2) ibmProd(6) ibmIROC(119) ibmIROCrouting(4) 11 }
-- MODULE-IDENTITY
--  LastUpdated
--    9810021200Z
--  OrgName
--    IBM
--  ContactInfo
--    Susie Chen
--     IBM Corporation
--     800 Park Offices Drive
--     FBWA/664
--     P.O. Box 12195
--     Research Triangle Park, NC 27709, USA
--     Tel:    1 919 254 9543
--     E-mail: susiec@us.ibm.com
--  Descr
--    This MIB module contains MIB for WAN restoral and reroute
--     function.

ibmWanRestoral  OBJECT IDENTIFIER ::= { ibmWanRestoralRerouteMIB 1 }
ibmWanReroute   OBJECT IDENTIFIER ::= { ibmWanRestoralRerouteMIB 2 }

ibmWanRestoralTable OBJECT-TYPE
    SYNTAX SEQUENCE OF IbmWanRestoralEntry
    ACCESS not-accessible
    STATUS mandatory
    DESCRIPTION
        "A list of WAN Restoral table entries.  The number of entries
        should equal the current number of primary link for WAN Restoral.
        The table has a row for primary link.  Each row has information
        about the current status of that link."
    ::= { ibmWanRestoral 1 }

ibmWanRestoralEntry OBJECT-TYPE
    SYNTAX IbmWanRestoralEntry
    ACCESS not-accessible
    STATUS mandatory
    DESCRIPTION
        "A WAN Restoral table entry describing current status of the primary link.
         The table has a row for each primary link.
        
         Rows in this table can not be created or deleted via SNMP commands"
    INDEX { ibmwrsPriNetifIndex }
    ::= { ibmWanRestoralTable 1 }

IbmWanRestoralEntry ::= SEQUENCE {
    ibmwrsPriNetifIndex Integer32,
    ibmwrsSecNetifIndex Integer32,
    ibmwrsEnabled INTEGER,
    ibmwrsActive INTEGER,
    ibmwrsDuration TimeTicks,
    ibmwrsAttempts Counter32,
    ibmwrsActuals Counter32,
    ibmwrsFwdPkts Counter32
    }

ibmwrsPriNetifIndex OBJECT-TYPE
    SYNTAX Integer32
    ACCESS read-only
    STATUS mandatory
    DESCRIPTION
        "The interface index of the primary net interface.
         This is the same as mib-2 ifIndex for that interface."
    ::= { ibmWanRestoralEntry 1 }

ibmwrsSecNetifIndex OBJECT-TYPE
    SYNTAX Integer32
    ACCESS read-only
    STATUS mandatory
    DESCRIPTION
        "The interface index of the secondary net interface.
         This is the same as mib-2 ifIndex for that interface."
    ::= { ibmWanRestoralEntry 2 }

ibmwrsEnabled OBJECT-TYPE
    SYNTAX INTEGER {
        yes(1),
        no(2)
        }
    ACCESS read-only
    STATUS mandatory
    DESCRIPTION
        "The flag indicates that restoral of this primary interface is currently
         enabled."
    ::= { ibmWanRestoralEntry 3 }

ibmwrsActive OBJECT-TYPE
    SYNTAX INTEGER {
        yes(1),
        no(2)
        }
    ACCESS read-only
    STATUS mandatory
    DESCRIPTION
        "The flag indicates that restoral of this primary interface is currently
         active."
    ::= { ibmWanRestoralEntry 4 }

ibmwrsDuration OBJECT-TYPE
    SYNTAX TimeTicks
    ACCESS read-only
    STATUS mandatory
    DESCRIPTION
        "The value in 1/100s of a second indicating the current or most
         recent duration that the secondary net interface was up. The value
         is current if ibmwrsActive has a value of yes(1), otherwise it is the most
         recent restoral duration.
        
         If restoral has never been active, the value is 0"
    ::= { ibmWanRestoralEntry 5 }

ibmwrsAttempts OBJECT-TYPE
    SYNTAX Counter32
    ACCESS read-only
    STATUS mandatory
    DESCRIPTION
        "The number of times an attempt was made to restore the primary."
    ::= { ibmWanRestoralEntry 6 }

ibmwrsActuals OBJECT-TYPE
    SYNTAX Counter32
    ACCESS read-only
    STATUS mandatory
    DESCRIPTION
        "The number of times the primary was actually restored by the secondary."
    ::= { ibmWanRestoralEntry 7 }

ibmwrsFwdPkts OBJECT-TYPE
    SYNTAX Counter32
    ACCESS read-only
    STATUS mandatory
    DESCRIPTION
        "The number of packets forwarded during the current or most recent restoral."
    ::= { ibmWanRestoralEntry 8 }

ibmWanRerouteTable OBJECT-TYPE
    SYNTAX SEQUENCE OF IbmWanRerouteEntry
    ACCESS not-accessible
    STATUS mandatory
    DESCRIPTION
        "A list of WAN Reroute table entries.  The number of entries
        should equal the current number of primary link for WAN Reroute.
        The table has a row for primary link.  Each row has information
        about the current status of that link."
    ::= { ibmWanReroute 1 }

ibmWanRerouteEntry OBJECT-TYPE
    SYNTAX IbmWanRerouteEntry
    ACCESS not-accessible
    STATUS mandatory
    DESCRIPTION
        "A WAN Reroute table entry describing current status of the primary link.
         The table has a row for each primary link.
        
         Rows in this table can not be created or deleted via SNMP commands"
    INDEX { ibmwrrPriNetifIndex }
    ::= { ibmWanRerouteTable 1 }

IbmWanRerouteEntry ::= SEQUENCE {
    ibmwrrPriNetifIndex Integer32,
    ibmwrrAltNetifIndex Integer32,
    ibmwrrEnabled INTEGER,
    ibmwrrActive INTEGER,
    ibmwrrDuration TimeTicks,
    ibmwrrAttempts Counter32,
    ibmwrrActuals Counter32,
    ibmwrrOverflowEnabled INTEGER,
    ibmwrrOverflowActive INTEGER,
    ibmwrrOverflowDuration TimeTicks,
    ibmwrrOverflowAttempts Counter32,
    ibmwrrOverflowActuals Counter32
    }

ibmwrrPriNetifIndex OBJECT-TYPE
    SYNTAX Integer32
    ACCESS read-only
    STATUS mandatory
    DESCRIPTION
        "The interface index of the primary net interface.
         This is the same as mib-2 ifIndex for that interface."
    ::= { ibmWanRerouteEntry 1 }

ibmwrrAltNetifIndex OBJECT-TYPE
    SYNTAX Integer32
    ACCESS read-only
    STATUS mandatory
    DESCRIPTION
        "The interface index of the alternate net interface.
         This is the same as mib-2 ifIndex for that interface."
    ::= { ibmWanRerouteEntry 2 }

ibmwrrEnabled OBJECT-TYPE
    SYNTAX INTEGER {
        yes(1),
        no(2)
        }
    ACCESS read-only
    STATUS mandatory
    DESCRIPTION
        "The flag indicates that reroute of this primary interface is currently
         enabled."
    ::= { ibmWanRerouteEntry 3 }

ibmwrrActive OBJECT-TYPE
    SYNTAX INTEGER {
        yes(1),
        no(2)
        }
    ACCESS read-only
    STATUS mandatory
    DESCRIPTION
        "The flag indicates that reroute of this primary interface is currently
         active."
    ::= { ibmWanRerouteEntry 4 }

ibmwrrDuration OBJECT-TYPE
    SYNTAX TimeTicks
    ACCESS read-only
    STATUS mandatory
    DESCRIPTION
        "The value in 1/100s of a second indicating the current or most
         recent duration that the alternate net interface was up. The value
         is current if ibmwrrActive has a value of yes(1), otherwise it is the most
         recent reroute duration.
        
         If reroute has never been active, the value is 0"
    ::= { ibmWanRerouteEntry 5 }

ibmwrrAttempts OBJECT-TYPE
    SYNTAX Counter32
    ACCESS read-only
    STATUS mandatory
    DESCRIPTION
        "The number of times an attempt was made to reroute the primary."
    ::= { ibmWanRerouteEntry 6 }

ibmwrrActuals OBJECT-TYPE
    SYNTAX Counter32
    ACCESS read-only
    STATUS mandatory
    DESCRIPTION
        "The number of times the primary was actually rerouted by the secondary."
    ::= { ibmWanRerouteEntry 7 }

ibmwrrOverflowEnabled OBJECT-TYPE
    SYNTAX INTEGER {
        yes(1),
        no(2)
        }
    ACCESS read-only
    STATUS mandatory
    DESCRIPTION
        "The flag indicates that dial on overflow of this primary interface is currently
         enabled."
    ::= { ibmWanRerouteEntry 8 }

ibmwrrOverflowActive OBJECT-TYPE
    SYNTAX INTEGER {
        yes(1),
        no(2)
        }
    ACCESS read-only
    STATUS mandatory
    DESCRIPTION
        "The flag indicates that dial on overflow of this primary interface is currently
         active."
    ::= { ibmWanRerouteEntry 9 }

ibmwrrOverflowDuration OBJECT-TYPE
    SYNTAX TimeTicks
    ACCESS read-only
    STATUS mandatory
    DESCRIPTION
        "The value in 1/100s of a second indicating the current or most
         recent dial on overflow duration that the alternate net interface was up. The value
         is current if ibmwrrOverflowActive has a value of yes(1), otherwise it is the most
         recent dial on overflow duration.
        
         If dial on overflow has never been active, the value is 0"
    ::= { ibmWanRerouteEntry 10 }

ibmwrrOverflowAttempts OBJECT-TYPE
    SYNTAX Counter32
    ACCESS read-only
    STATUS mandatory
    DESCRIPTION
        "The number of times an attempt was made to use the alternate link
         after the primary threshhold was reached."
    ::= { ibmWanRerouteEntry 11 }

ibmwrrOverflowActuals OBJECT-TYPE
    SYNTAX Counter32
    ACCESS read-only
    STATUS mandatory
    DESCRIPTION
        "The number of times the alternate link was actually used for overflow
         traffic once the primary threshhold was reached."
    ::= { ibmWanRerouteEntry 12 }


END
