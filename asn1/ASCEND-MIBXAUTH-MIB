--			Ascend mibxauth MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBXAUTH-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibexternalAuthProfile  OBJECT IDENTIFIER ::= { configuration 142}
    mibradStatProfile  OBJECT IDENTIFIER ::= { configuration 141}
    mibradAcctCallLogProfile  OBJECT IDENTIFIER ::= { configuration 143}

	-- The mibexternalAuthProfile table
	--
	-- This table contains parameters for the mibexternalAuthProfile profile
	--

    mibexternalAuthProfileTable	OBJECT-TYPE
	SYNTAX		SEQUENCE OF MibexternalAuthProfileEntry
	ACCESS		not-accessible
	STATUS		mandatory
	DESCRIPTION	"A list of mibexternalAuthProfile profile entries."
	::= { mibexternalAuthProfile 1 }

    mibexternalAuthProfileEntry	OBJECT-TYPE
	SYNTAX		MibexternalAuthProfileEntry
	ACCESS		not-accessible
	STATUS		mandatory
	DESCRIPTION	"A mibexternalAuthProfile entry containing objects that
			 maps to the parameters of mibexternalAuthProfile profile."
	INDEX		{ externalAuthProfile-Index-o }
	::= { mibexternalAuthProfileTable 1 }

    MibexternalAuthProfileEntry ::=
	SEQUENCE {
	    externalAuthProfile-Index-o
		INTEGER,
	    externalAuthProfile-AuthType
		INTEGER,
	    externalAuthProfile-AcctType
		INTEGER,
	    externalAuthProfile-RadServEnable
		INTEGER,
	    externalAuthProfile-RadAuthClient-AuthHost1
		DisplayString,
	    externalAuthProfile-RadAuthClient-AuthHost2
		DisplayString,
	    externalAuthProfile-RadAuthClient-AuthHost3
		DisplayString,
	    externalAuthProfile-RadAuthClient-AuthPort
		INTEGER,
	    externalAuthProfile-RadAuthClient-AuthSrcPort
		INTEGER,
	    externalAuthProfile-RadAuthClient-AuthKey
		DisplayString,
	    externalAuthProfile-RadAuthClient-AuthPool
		INTEGER,
	    externalAuthProfile-RadAuthClient-AuthTimeout
		INTEGER,
	    externalAuthProfile-RadAuthClient-AuthRspRequired
		INTEGER,
	    externalAuthProfile-RadAuthClient-AuthIdFailReturnBusy
		INTEGER,
	    externalAuthProfile-RadAuthClient-AuthIdTimeoutReturnBusy
		INTEGER,
	    externalAuthProfile-RadAuthClient-AuthSessInterval
		INTEGER,
	    externalAuthProfile-RadAuthClient-AuthTSSecure
		INTEGER,
	    externalAuthProfile-RadAuthClient-AuthSend67
		INTEGER,
	    externalAuthProfile-RadAuthClient-AuthFrmAdrStart
		INTEGER,
	    externalAuthProfile-RadAuthClient-AuthBootHost
		IpAddress,
	    externalAuthProfile-RadAuthClient-AuthBootHost2
		IpAddress,
	    externalAuthProfile-RadAuthClient-AuthBootPort
		INTEGER,
	    externalAuthProfile-RadAuthClient-AuthResetTime
		INTEGER,
	    externalAuthProfile-RadAuthClient-AuthIdMaxRetryTime
		INTEGER,
	    externalAuthProfile-RadAuthClient-AuthRadiusCompat
		INTEGER,
	    externalAuthProfile-RadAuthClient-AuthKeepUserName
		INTEGER,
	    externalAuthProfile-RadAuthClient-AuthRealmDelimiters
		DisplayString,
	    externalAuthProfile-RadAuthClient-IdAuthPrefix
		DisplayString,
	    externalAuthProfile-RadAuthClient-AllowAuthConfigRqsts
		INTEGER,
	    externalAuthProfile-RadAuthClient-AuthReqDelimCount
		INTEGER,
	    externalAuthProfile-RadAuthClient-AuthReqStripSide
		INTEGER,
	    externalAuthProfile-RadAuthClient-AuthNetworkRouteServer
		INTEGER,
	    externalAuthProfile-RadAuthClient-IdAuthPrefixX25
		DisplayString,
	    externalAuthProfile-RadAuthClient-AllowUnencryptedTunnelPassword
		INTEGER,
	    externalAuthProfile-RadAuthClient-AuthCliUserDnis
		DisplayString,
	    externalAuthProfile-RadAuthClient-AllowNasPortTypeInCliUserAuth
		INTEGER,
	    externalAuthProfile-RadAcctClient-AcctHost1
		DisplayString,
	    externalAuthProfile-RadAcctClient-AcctHost2
		DisplayString,
	    externalAuthProfile-RadAcctClient-AcctHost3
		DisplayString,
	    externalAuthProfile-RadAcctClient-AcctPort
		INTEGER,
	    externalAuthProfile-RadAcctClient-AcctSrcPort
		INTEGER,
	    externalAuthProfile-RadAcctClient-AcctKey
		DisplayString,
	    externalAuthProfile-RadAcctClient-AcctTimeout
		INTEGER,
	    externalAuthProfile-RadAcctClient-AcctSessInterval
		INTEGER,
	    externalAuthProfile-RadAcctClient-AcctIdBase
		INTEGER,
	    externalAuthProfile-RadAcctClient-AcctResetTime
		INTEGER,
	    externalAuthProfile-RadAcctClient-AcctCheckpoint
		INTEGER,
	    externalAuthProfile-RadAcctClient-AcctCheckpointTimer
		INTEGER,
	    externalAuthProfile-RadAcctClient-AcctStopOnly
		INTEGER,
	    externalAuthProfile-RadAcctClient-AcctLimitRetry
		INTEGER,
	    externalAuthProfile-RadAcctClient-AcctDropStopOnAuthFail
		INTEGER,
	    externalAuthProfile-RadAcctClient-AcctRadiusCompat
		INTEGER,
	    externalAuthProfile-RadAcctClient-TunnelAccounting
		INTEGER,
	    externalAuthProfile-RadAcctClient-VoipAccounting
		INTEGER,
	    externalAuthProfile-RadAcctClient-AcctOnSwitchover
		INTEGER,
	    externalAuthProfile-RadAuthServer-AuthPort
		INTEGER,
	    externalAuthProfile-RadAuthServer-AuthSessionKey
		INTEGER,
	    externalAuthProfile-RadAuthServer-AuthAttributeType
		INTEGER,
	    externalAuthProfile-RadAuthServer-AuthRadiusCompat
		INTEGER,
	    externalAuthProfile-TacAuthClient-AuthServer1
		IpAddress,
	    externalAuthProfile-TacAuthClient-AuthServer2
		IpAddress,
	    externalAuthProfile-TacAuthClient-AuthServer3
		IpAddress,
	    externalAuthProfile-TacAuthClient-AuthPort
		INTEGER,
	    externalAuthProfile-TacAuthClient-AuthSrcPort
		INTEGER,
	    externalAuthProfile-TacAuthClient-AuthKey
		DisplayString,
	    externalAuthProfile-TacAuthClient-AuthTimeout
		INTEGER,
	    externalAuthProfile-TacplusAuthClient-AuthServer1
		IpAddress,
	    externalAuthProfile-TacplusAuthClient-AuthServer2
		IpAddress,
	    externalAuthProfile-TacplusAuthClient-AuthServer3
		IpAddress,
	    externalAuthProfile-TacplusAuthClient-AuthPort
		INTEGER,
	    externalAuthProfile-TacplusAuthClient-AuthSrcPort
		INTEGER,
	    externalAuthProfile-TacplusAuthClient-AuthKey
		DisplayString,
	    externalAuthProfile-TacplusAuthClient-AuthTimeoutTime
		INTEGER,
	    externalAuthProfile-TacplusAuthClient-AuthRetries
		INTEGER,
	    externalAuthProfile-TacplusAcctClient-AcctServer1
		IpAddress,
	    externalAuthProfile-TacplusAcctClient-AcctServer2
		IpAddress,
	    externalAuthProfile-TacplusAcctClient-AcctServer3
		IpAddress,
	    externalAuthProfile-TacplusAcctClient-AcctPort
		INTEGER,
	    externalAuthProfile-TacplusAcctClient-AcctSrcPort
		INTEGER,
	    externalAuthProfile-TacplusAcctClient-AcctKey
		DisplayString,
	    externalAuthProfile-SecureidAuthClient-AuthServer1
		IpAddress,
	    externalAuthProfile-SecureidAuthClient-AuthServer2
		IpAddress,
	    externalAuthProfile-SecureidAuthClient-AuthServer3
		IpAddress,
	    externalAuthProfile-SecureidAuthClient-AuthPort
		INTEGER,
	    externalAuthProfile-SecureidAuthClient-AuthTimeout
		INTEGER,
	    externalAuthProfile-SecureidAuthClient-AuthRetrycount
		INTEGER,
	    externalAuthProfile-SecureidAuthClient-AuthDes
		INTEGER,
	    externalAuthProfile-SecureidAuthClient-AuthNodeSecret
		DisplayString,
	    externalAuthProfile-PasswordProfile-Clid
		DisplayString,
	    externalAuthProfile-PasswordProfile-Dnis
		DisplayString,
	    externalAuthProfile-PasswordProfile-Banner
		DisplayString,
	    externalAuthProfile-PasswordProfile-InitBanner
		DisplayString,
	    externalAuthProfile-PasswordProfile-Pool
		DisplayString,
	    externalAuthProfile-PasswordProfile-Frdl
		DisplayString,
	    externalAuthProfile-PasswordProfile-Dialout
		DisplayString,
	    externalAuthProfile-PasswordProfile-DialoutRoutes
		DisplayString,
	    externalAuthProfile-PasswordProfile-DialoutIpxRoutes
		DisplayString,
	    externalAuthProfile-PasswordProfile-DialoutAtalkRoutes
		DisplayString,
	    externalAuthProfile-PasswordProfile-SourceAuth
		DisplayString,
	    externalAuthProfile-LocalProfilesFirst
		INTEGER,
	    externalAuthProfile-Noattr6UseTermsrv
		INTEGER,
	    externalAuthProfile-Clid
		DisplayString,
	    externalAuthProfile-Dnis
		DisplayString,
	    externalAuthProfile-CliUserAuth
		INTEGER,
	    externalAuthProfile-Action-o
		INTEGER
	}

    externalAuthProfile-Index-o	OBJECT-TYPE
	SYNTAX	INTEGER
	ACCESS	read-only
	STATUS	mandatory
	DESCRIPTION	""
	::= { mibexternalAuthProfileEntry 1 }

    externalAuthProfile-AuthType	OBJECT-TYPE
	SYNTAX	INTEGER {
		    none (1),
		    tACACS (2),
		    rADIUS (3),
		    rADIUS-LOGOUT (4),
		    sECURID (5),
		    tACACSPLUS (6),
		    dEFENDER (7)
		}
	ACCESS	read-write
	STATUS	mandatory
	DESCRIPTION	"The type of authentication to perform."
	::= { mibexternalAuthProfileEntry 2 }

    externalAuthProfile-AcctType	OBJECT-TYPE
	SYNTAX	INTEGER {
		    none (1),
		    radius (2),
		    tacacsplus (3)
		}
	ACCESS	read-write
	STATUS	mandatory
	DESCRIPTION	"The type of accounting to perform."
	::= { mibexternalAuthProfileEntry 3 }

    externalAuthProfile-RadServEnable	OBJECT-TYPE
	SYNTAX	INTEGER {
		    no (1),
		    yes (2)
		}
	ACCESS	read-write
	STATUS	mandatory
	DESCRIPTION	"Whether or not the on-board RADIUS server is enabled."
	::= { mibexternalAuthProfileEntry 4 }

    externalAuthProfile-RadAuthClient-AuthHost1	OBJECT-TYPE
	SYNTAX	DisplayString
	ACCESS	read-write
	STATUS	mandatory
	DESCRIPTION	"The IP address/hostname of the first RADIUS authentication server "
	::= { mibexternalAuthProfileEntry 104 }

    externalAuthProfile-RadAuthClient-AuthHost2	OBJECT-TYPE
	SYNTAX	DisplayString
	ACCESS	read-write
	STATUS	mandatory
	DESCRIPTION	"The IP address/hostname of the second RADIUS authentication server"
	::= { mibexternalAuthProfileEntry 105 }

    externalAuthProfile-RadAuthClient-AuthHost3	OBJECT-TYPE
	SYNTAX	DisplayString
	ACCESS	read-write
	STATUS	mandatory
	DESCRIPTION	"The IP address/hostname of the third RADIUS authentication server"
	::= { mibexternalAuthProfileEntry 106 }

    externalAuthProfile-RadAuthClient-AuthPort	OBJECT-TYPE
	SYNTAX	INTEGER
	ACCESS	read-write
	STATUS	mandatory
	DESCRIPTION	"The UDP destination port to use for RADIUS authentication."
	::= { mibexternalAuthProfileEntry 8 }

    externalAuthProfile-RadAuthClient-AuthSrcPort	OBJECT-TYPE
	SYNTAX	INTEGER
	ACCESS	read-write
	STATUS	mandatory
	DESCRIPTION	"The UDP source port to use for RADIUS authentication. If zero, the source port is selected from the non-privileged port range (1024-2000)."
	::= { mibexternalAuthProfileEntry 9 }

    externalAuthProfile-RadAuthClient-AuthKey	OBJECT-TYPE
	SYNTAX	DisplayString
	ACCESS	read-write
	STATUS	mandatory
	DESCRIPTION	"The RADIUS authentication access key shared with the RADIUS server."
	::= { mibexternalAuthProfileEntry 10 }

    externalAuthProfile-RadAuthClient-AuthPool	OBJECT-TYPE
	SYNTAX	INTEGER {
		    no (1),
		    yes (2)
		}
	ACCESS	read-write
	STATUS	mandatory
	DESCRIPTION	"If TRUE an IP address is allocated from the default pool and passed to the RADIUS server during RADIUS authentication. This address may be assigned to the dial-in user for the duration of the connection."
	::= { mibexternalAuthProfileEntry 11 }

    externalAuthProfile-RadAuthClient-AuthTimeout	OBJECT-TYPE
	SYNTAX	INTEGER
	ACCESS	read-write
	STATUS	mandatory
	DESCRIPTION	"Number of seconds between retries to the authentication host."
	::= { mibexternalAuthProfileEntry 12 }

    externalAuthProfile-RadAuthClient-AuthRspRequired	OBJECT-TYPE
	SYNTAX	INTEGER {
		    no (1),
		    yes (2)
		}
	ACCESS	read-write
	STATUS	mandatory
	DESCRIPTION	"When set to Yes, entry is allowed only if the authentication server responds with an authentication of the login information. When set to No, entry is also allowed if there is no response from the authentication server. This field is used only for CLID or DNIS authentication."
	::= { mibexternalAuthProfileEntry 13 }

    externalAuthProfile-RadAuthClient-AuthIdFailReturnBusy	OBJECT-TYPE
	SYNTAX	INTEGER {
		    no (1),
		    yes (2)
		}
	ACCESS	read-write
	STATUS	mandatory
	DESCRIPTION	"Return busy instead of normal call clearing when id authentication fails."
	::= { mibexternalAuthProfileEntry 14 }

    externalAuthProfile-RadAuthClient-AuthIdTimeoutReturnBusy	OBJECT-TYPE
	SYNTAX	INTEGER {
		    no (1),
		    yes (2)
		}
	ACCESS	read-write
	STATUS	mandatory
	DESCRIPTION	"Return busy instead of normal call clearing when external id authentication fails."
	::= { mibexternalAuthProfileEntry 15 }

    externalAuthProfile-RadAuthClient-AuthSessInterval	OBJECT-TYPE
	SYNTAX	INTEGER
	ACCESS	read-write
	STATUS	mandatory
	DESCRIPTION	"Send the number-of-sessions-per-Class Attribute to the authentication server every auth-sess-interval seconds."
	::= { mibexternalAuthProfileEntry 16 }

    externalAuthProfile-RadAuthClient-AuthTSSecure	OBJECT-TYPE
	SYNTAX	INTEGER {
		    no (1),
		    yes (2)
		}
	ACCESS	read-write
	STATUS	mandatory
	DESCRIPTION	"Allow access to terminal server when RADIUS Login-Host is not specify when authTSsecure is set no"
	::= { mibexternalAuthProfileEntry 17 }

    externalAuthProfile-RadAuthClient-AuthSend67	OBJECT-TYPE
	SYNTAX	INTEGER {
		    no (1),
		    yes (2)
		}
	ACCESS	read-write
	STATUS	mandatory
	DESCRIPTION	"If Yes, default attributes 6,7 of Radius and send them in the authentication request."
	::= { mibexternalAuthProfileEntry 18 }

    externalAuthProfile-RadAuthClient-AuthFrmAdrStart	OBJECT-TYPE
	SYNTAX	INTEGER {
		    no (1),
		    yes (2)
		}
	ACCESS	read-write
	STATUS	mandatory
	DESCRIPTION	"Set Yes to send a second Radius accounting start record when the Framed-Address is assigned. Default No for backward compatibility."
	::= { mibexternalAuthProfileEntry 19 }

    externalAuthProfile-RadAuthClient-AuthBootHost	OBJECT-TYPE
	SYNTAX	IpAddress
	ACCESS	read-write
	STATUS	mandatory
	DESCRIPTION	"The IP address of the authentication boot host."
	::= { mibexternalAuthProfileEntry 20 }

    externalAuthProfile-RadAuthClient-AuthBootHost2	OBJECT-TYPE
	SYNTAX	IpAddress
	ACCESS	read-write
	STATUS	mandatory
	DESCRIPTION	"The IP address of the secondary authentication boot host."
	::= { mibexternalAuthProfileEntry 21 }

    externalAuthProfile-RadAuthClient-AuthBootPort	OBJECT-TYPE
	SYNTAX	INTEGER
	ACCESS	read-write
	STATUS	mandatory
	DESCRIPTION	"The UDP port to use for RADIUS authentication."
	::= { mibexternalAuthProfileEntry 22 }

    externalAuthProfile-RadAuthClient-AuthResetTime	OBJECT-TYPE
	SYNTAX	INTEGER
	ACCESS	read-write
	STATUS	mandatory
	DESCRIPTION	"The time to reset to the primary server after it has failed."
	::= { mibexternalAuthProfileEntry 23 }

    externalAuthProfile-RadAuthClient-AuthIdMaxRetryTime	OBJECT-TYPE
	SYNTAX	INTEGER
	ACCESS	read-write
	STATUS	mandatory
	DESCRIPTION	"Maximum time limit to spend retrying RADIUS servers when in id authentication, a value of 0 sets the limit to the internal default value."
	::= { mibexternalAuthProfileEntry 24 }

    externalAuthProfile-RadAuthClient-AuthRadiusCompat	OBJECT-TYPE
	SYNTAX	INTEGER {
		    oldAscend (1),
		    vendorSpecific (2),
		    n-16BitVendorSpecific (3)
		}
	ACCESS	read-write
	STATUS	mandatory
	DESCRIPTION	"Authentication RADIUS compatibility mode."
	::= { mibexternalAuthProfileEntry 25 }

    externalAuthProfile-RadAuthClient-AuthKeepUserName	OBJECT-TYPE
	SYNTAX	INTEGER {
		    changeName (1),
		    keepName (2),
		    keepRealmName (3)
		}
	ACCESS	read-write
	STATUS	mandatory
	DESCRIPTION	"Action if the Access-Accept packet from Radius server contains a User-Name attribute."
	::= { mibexternalAuthProfileEntry 26 }

    externalAuthProfile-RadAuthClient-AuthRealmDelimiters	OBJECT-TYPE
	SYNTAX	DisplayString
	ACCESS	read-write
	STATUS	mandatory
	DESCRIPTION	"Characters that delimit a realm and user name (used only if auth-keep-user-name=keep-realm-name or radius-delim_count>0)"
	::= { mibexternalAuthProfileEntry 27 }

    externalAuthProfile-RadAuthClient-IdAuthPrefix	OBJECT-TYPE
	SYNTAX	DisplayString
	ACCESS	read-write
	STATUS	mandatory
	DESCRIPTION	"A short text string prepended to the username portion of a CLID or DNIS authentication request."
	::= { mibexternalAuthProfileEntry 28 }

    externalAuthProfile-RadAuthClient-AllowAuthConfigRqsts	OBJECT-TYPE
	SYNTAX	INTEGER {
		    no (1),
		    yes (2)
		}
	ACCESS	read-write
	STATUS	mandatory
	DESCRIPTION	"Set Yes to send External Config Requests. Default is set to Yes."
	::= { mibexternalAuthProfileEntry 29 }

    externalAuthProfile-RadAuthClient-AuthReqDelimCount	OBJECT-TYPE
	SYNTAX	INTEGER
	ACCESS	read-write
	STATUS	mandatory
	DESCRIPTION	"Number of delimiters to strip from a username in Radius Auth request."
	::= { mibexternalAuthProfileEntry 30 }

    externalAuthProfile-RadAuthClient-AuthReqStripSide	OBJECT-TYPE
	SYNTAX	INTEGER {
		    none (1),
		    left (2),
		    right (3)
		}
	ACCESS	read-write
	STATUS	mandatory
	DESCRIPTION	"Side to strip chars from a username in a Radius Auth request if delim-count is > 0."
	::= { mibexternalAuthProfileEntry 31 }

    externalAuthProfile-RadAuthClient-AuthNetworkRouteServer	OBJECT-TYPE
	SYNTAX	INTEGER {
		    no (1),
		    yes (2)
		}
	ACCESS	read-write
	STATUS	mandatory
	DESCRIPTION	"Determines whether Radius server supports multiple profiles with the same user-name. Otherwise destination IP address is appended to user-name."
	::= { mibexternalAuthProfileEntry 98 }

    externalAuthProfile-RadAuthClient-IdAuthPrefixX25	OBJECT-TYPE
	SYNTAX	DisplayString
	ACCESS	read-write
	STATUS	mandatory
	DESCRIPTION	"A short text string prepended to the username portion of a DNIS authentication request for X25 calls."
	::= { mibexternalAuthProfileEntry 99 }

    externalAuthProfile-RadAuthClient-AllowUnencryptedTunnelPassword	OBJECT-TYPE
	SYNTAX	INTEGER {
		    no (1),
		    yes (2)
		}
	ACCESS	read-write
	STATUS	mandatory
	DESCRIPTION	"When set to 'YES', unencrypted as well as encrypted Tunnel-Password, from RADIUS, is accepted. When set to 'NO' only encrypted Tunnel-Password, from RADIUS, is accepted. But as per RFC 2868 the Tunnel-Password MUST be encrypted by RADIUS before sending out."
	::= { mibexternalAuthProfileEntry 101 }

    externalAuthProfile-RadAuthClient-AuthCliUserDnis	OBJECT-TYPE
	SYNTAX	DisplayString
	ACCESS	read-write
	STATUS	mandatory
	DESCRIPTION	"Pseudo DNIS number for CLI users. If set, this number is sent to RADIUS as DNIS. If not set, DNIS is not sent to RADIUS."
	::= { mibexternalAuthProfileEntry 102 }

    externalAuthProfile-RadAuthClient-AllowNasPortTypeInCliUserAuth	OBJECT-TYPE
	SYNTAX	INTEGER {
		    no (1),
		    yes (2)
		}
	ACCESS	read-write
	STATUS	mandatory
	DESCRIPTION	"When set to 'NO', NAS_Port_Type attribute is NOT sent in the RADIUS authentication request packet while authenticating CLI users. Default is set to Yes."
	::= { mibexternalAuthProfileEntry 103 }

    externalAuthProfile-RadAcctClient-AcctHost1	OBJECT-TYPE
	SYNTAX	DisplayString
	ACCESS	read-write
	STATUS	mandatory
	DESCRIPTION	"The IP address/hostname of the first RADIUS accounting server."
	::= { mibexternalAuthProfileEntry 107 }

    externalAuthProfile-RadAcctClient-AcctHost2	OBJECT-TYPE
	SYNTAX	DisplayString
	ACCESS	read-write
	STATUS	mandatory
	DESCRIPTION	"The IP address/hostname of the second RADIUS accounting server."
	::= { mibexternalAuthProfileEntry 108 }

    externalAuthProfile-RadAcctClient-AcctHost3	OBJECT-TYPE
	SYNTAX	DisplayString
	ACCESS	read-write
	STATUS	mandatory
	DESCRIPTION	"The IP address/hostname of the third RADIUS accounting server."
	::= { mibexternalAuthProfileEntry 109 }

    externalAuthProfile-RadAcctClient-AcctPort	OBJECT-TYPE
	SYNTAX	INTEGER
	ACCESS	read-write
	STATUS	mandatory
	DESCRIPTION	"The UDP destination port to use for RADIUS accounting."
	::= { mibexternalAuthProfileEntry 35 }

    externalAuthProfile-RadAcctClient-AcctSrcPort	OBJECT-TYPE
	SYNTAX	INTEGER
	ACCESS	read-write
	STATUS	mandatory
	DESCRIPTION	"The UDP source port to use for RADIUS accounting. If zero, the source port is selected from the non-privileged port range (1024-2000)."
	::= { mibexternalAuthProfileEntry 36 }

    externalAuthProfile-RadAcctClient-AcctKey	OBJECT-TYPE
	SYNTAX	DisplayString
	ACCESS	read-write
	STATUS	mandatory
	DESCRIPTION	"The RADIUS accounting access key shared with the RADIUS server."
	::= { mibexternalAuthProfileEntry 37 }

    externalAuthProfile-RadAcctClient-AcctTimeout	OBJECT-TYPE
	SYNTAX	INTEGER
	ACCESS	read-write
	STATUS	mandatory
	DESCRIPTION	"Number of seconds to wait for a response to previous accounting request."
	::= { mibexternalAuthProfileEntry 38 }

    externalAuthProfile-RadAcctClient-AcctSessInterval	OBJECT-TYPE
	SYNTAX	INTEGER
	ACCESS	read-write
	STATUS	mandatory
	DESCRIPTION	"Send the number-of-sessions-per-Class Attribute to the accounting server every acct-sess-interval seconds."
	::= { mibexternalAuthProfileEntry 39 }

    externalAuthProfile-RadAcctClient-AcctIdBase	OBJECT-TYPE
	SYNTAX	INTEGER {
		    acctBase10 (1),
		    acctBase16 (2)
		}
	ACCESS	read-write
	STATUS	mandatory
	DESCRIPTION	"The base value to use in reporting Account ID."
	::= { mibexternalAuthProfileEntry 40 }

    externalAuthProfile-RadAcctClient-AcctResetTime	OBJECT-TYPE
	SYNTAX	INTEGER
	ACCESS	read-write
	STATUS	mandatory
	DESCRIPTION	"The elapsed time to reset to the primary server, after failing to reach the primary server."
	::= { mibexternalAuthProfileEntry 41 }

    externalAuthProfile-RadAcctClient-AcctCheckpoint	OBJECT-TYPE
	SYNTAX	INTEGER
	ACCESS	read-write
	STATUS	mandatory
	DESCRIPTION	"Interval at which to send checkpoint packets to the daemon in minutes."
	::= { mibexternalAuthProfileEntry 42 }

    externalAuthProfile-RadAcctClient-AcctCheckpointTimer	OBJECT-TYPE
	SYNTAX	INTEGER {
		    perSession (1),
		    allSessions (2)
		}
	ACCESS	read-write
	STATUS	mandatory
	DESCRIPTION	"Sets the scope of the checkpoint timer to individual sessions or all-sessions."
	::= { mibexternalAuthProfileEntry 43 }

    externalAuthProfile-RadAcctClient-AcctStopOnly	OBJECT-TYPE
	SYNTAX	INTEGER {
		    no (1),
		    yes (2)
		}
	ACCESS	read-write
	STATUS	mandatory
	DESCRIPTION	"Send to RADIUS Accounting Stop packets that have username=0. These are caused by connections that are dropped before authentication is done."
	::= { mibexternalAuthProfileEntry 44 }

    externalAuthProfile-RadAcctClient-AcctLimitRetry	OBJECT-TYPE
	SYNTAX	INTEGER
	ACCESS	read-write
	STATUS	mandatory
	DESCRIPTION	"Number of retries before removing RADIUS Acct packet. 0 means leave on retry list until maximum retry entries are exceeded."
	::= { mibexternalAuthProfileEntry 45 }

    externalAuthProfile-RadAcctClient-AcctDropStopOnAuthFail	OBJECT-TYPE
	SYNTAX	INTEGER {
		    no (1),
		    yes (2)
		}
	ACCESS	read-write
	STATUS	mandatory
	DESCRIPTION	"If Yes, do not send RADIUS Accounting Stop/Checkpoint packets for users that failed authentication."
	::= { mibexternalAuthProfileEntry 46 }

    externalAuthProfile-RadAcctClient-AcctRadiusCompat	OBJECT-TYPE
	SYNTAX	INTEGER {
		    oldAscend (1),
		    vendorSpecific (2),
		    n-16BitVendorSpecific (3)
		}
	ACCESS	read-write
	STATUS	mandatory
	DESCRIPTION	"Accounting RADIUS compatibility mode."
	::= { mibexternalAuthProfileEntry 47 }

    externalAuthProfile-RadAcctClient-TunnelAccounting	OBJECT-TYPE
	SYNTAX	INTEGER {
		    no (1),
		    yes (2)
		}
	ACCESS	read-write
	STATUS	mandatory
	DESCRIPTION	"Perform RFC2867 Radius Tunnel Accounting ( L2F, L2TP )."
	::= { mibexternalAuthProfileEntry 48 }

    externalAuthProfile-RadAcctClient-VoipAccounting	OBJECT-TYPE
	SYNTAX	INTEGER {
		    no (1),
		    yes (2)
		}
	ACCESS	read-write
	STATUS	mandatory
	DESCRIPTION	"To Enable/Disable radius accounting for VOIP calls."
	::= { mibexternalAuthProfileEntry 110 }

    externalAuthProfile-RadAcctClient-AcctOnSwitchover	OBJECT-TYPE
	SYNTAX	INTEGER {
		    no (1),
		    yes (2)
		}
	ACCESS	read-write
	STATUS	mandatory
	DESCRIPTION	"Determines whether Accounting-on packet with event Ascend-Controller-Switchover should be sent or not during switchover when syncing is enabled."
	::= { mibexternalAuthProfileEntry 111 }

    externalAuthProfile-RadAuthServer-AuthPort	OBJECT-TYPE
	SYNTAX	INTEGER
	ACCESS	read-write
	STATUS	mandatory
	DESCRIPTION	"The UDP port to use for the on-board RADIUS server."
	::= { mibexternalAuthProfileEntry 49 }

    externalAuthProfile-RadAuthServer-AuthSessionKey	OBJECT-TYPE
	SYNTAX	INTEGER {
		    no (1),
		    yes (2)
		}
	ACCESS	read-write
	STATUS	mandatory
	DESCRIPTION	"Enables Session key assignments."
	::= { mibexternalAuthProfileEntry 50 }

    externalAuthProfile-RadAuthServer-AuthAttributeType	OBJECT-TYPE
	SYNTAX	INTEGER {
		    radServAttrAny (1),
		    radServAttrKey (2),
		    radServAttrAll (3)
		}
	ACCESS	read-write
	STATUS	mandatory
	DESCRIPTION	"The type of attributes required for session matching."
	::= { mibexternalAuthProfileEntry 51 }

    externalAuthProfile-RadAuthServer-AuthRadiusCompat	OBJECT-TYPE
	SYNTAX	INTEGER {
		    oldAscend (1),
		    vendorSpecific (2),
		    n-16BitVendorSpecific (3)
		}
	ACCESS	read-write
	STATUS	mandatory
	DESCRIPTION	"RADIUS server RADIUS compatibility mode."
	::= { mibexternalAuthProfileEntry 52 }

    externalAuthProfile-TacAuthClient-AuthServer1	OBJECT-TYPE
	SYNTAX	IpAddress
	ACCESS	read-write
	STATUS	mandatory
	DESCRIPTION	"The IP address of the first TACACS authentication server."
	::= { mibexternalAuthProfileEntry 53 }

    externalAuthProfile-TacAuthClient-AuthServer2	OBJECT-TYPE
	SYNTAX	IpAddress
	ACCESS	read-write
	STATUS	mandatory
	DESCRIPTION	"The IP address of the second TACACS authentication server."
	::= { mibexternalAuthProfileEntry 54 }

    externalAuthProfile-TacAuthClient-AuthServer3	OBJECT-TYPE
	SYNTAX	IpAddress
	ACCESS	read-write
	STATUS	mandatory
	DESCRIPTION	"The IP address of the third TACACS authentication server."
	::= { mibexternalAuthProfileEntry 55 }

    externalAuthProfile-TacAuthClient-AuthPort	OBJECT-TYPE
	SYNTAX	INTEGER
	ACCESS	read-write
	STATUS	mandatory
	DESCRIPTION	"The UDP port to use for TACACS authentication."
	::= { mibexternalAuthProfileEntry 56 }

    externalAuthProfile-TacAuthClient-AuthSrcPort	OBJECT-TYPE
	SYNTAX	INTEGER
	ACCESS	read-write
	STATUS	mandatory
	DESCRIPTION	"The UDP source port to use for TACACS authentication. If zero, the source port is selected from the non-privileged port range (1024-2000)."
	::= { mibexternalAuthProfileEntry 57 }

    externalAuthProfile-TacAuthClient-AuthKey	OBJECT-TYPE
	SYNTAX	DisplayString
	ACCESS	read-write
	STATUS	mandatory
	DESCRIPTION	"The RADIUS authentication access key shared with the RADIUS server."
	::= { mibexternalAuthProfileEntry 58 }

    externalAuthProfile-TacAuthClient-AuthTimeout	OBJECT-TYPE
	SYNTAX	INTEGER
	ACCESS	read-write
	STATUS	mandatory
	DESCRIPTION	"Number of seconds between retries to the authentication host."
	::= { mibexternalAuthProfileEntry 59 }

    externalAuthProfile-TacplusAuthClient-AuthServer1	OBJECT-TYPE
	SYNTAX	IpAddress
	ACCESS	read-write
	STATUS	mandatory
	DESCRIPTION	"The IP address of the first TACACS+ authentication server."
	::= { mibexternalAuthProfileEntry 60 }

    externalAuthProfile-TacplusAuthClient-AuthServer2	OBJECT-TYPE
	SYNTAX	IpAddress
	ACCESS	read-write
	STATUS	mandatory
	DESCRIPTION	"The IP address of the second TACACS+ authentication server."
	::= { mibexternalAuthProfileEntry 61 }

    externalAuthProfile-TacplusAuthClient-AuthServer3	OBJECT-TYPE
	SYNTAX	IpAddress
	ACCESS	read-write
	STATUS	mandatory
	DESCRIPTION	"The IP address of the third TACACS+ authentication server."
	::= { mibexternalAuthProfileEntry 62 }

    externalAuthProfile-TacplusAuthClient-AuthPort	OBJECT-TYPE
	SYNTAX	INTEGER
	ACCESS	read-write
	STATUS	mandatory
	DESCRIPTION	"The TCP destination port to use for TACACS+ authentication."
	::= { mibexternalAuthProfileEntry 63 }

    externalAuthProfile-TacplusAuthClient-AuthSrcPort	OBJECT-TYPE
	SYNTAX	INTEGER
	ACCESS	read-write
	STATUS	mandatory
	DESCRIPTION	"The TCP source port to use for TACACS+ authentication. If zero, the source port is selected from the non-privileged port range (1024-2000)."
	::= { mibexternalAuthProfileEntry 64 }

    externalAuthProfile-TacplusAuthClient-AuthKey	OBJECT-TYPE
	SYNTAX	DisplayString
	ACCESS	read-write
	STATUS	mandatory
	DESCRIPTION	"The Tacacs+ authentication access key shared with the TACACS+ server."
	::= { mibexternalAuthProfileEntry 65 }

    externalAuthProfile-TacplusAuthClient-AuthTimeoutTime	OBJECT-TYPE
	SYNTAX	INTEGER
	ACCESS	read-write
	STATUS	mandatory
	DESCRIPTION	"The time to reset to the primary server after it has failed."
	::= { mibexternalAuthProfileEntry 66 }

    externalAuthProfile-TacplusAuthClient-AuthRetries	OBJECT-TYPE
	SYNTAX	INTEGER
	ACCESS	read-write
	STATUS	mandatory
	DESCRIPTION	"The number of times to retry the auth hosts before giving up."
	::= { mibexternalAuthProfileEntry 67 }

    externalAuthProfile-TacplusAcctClient-AcctServer1	OBJECT-TYPE
	SYNTAX	IpAddress
	ACCESS	read-write
	STATUS	mandatory
	DESCRIPTION	"The IP address of the first TACACS+ accounting server."
	::= { mibexternalAuthProfileEntry 68 }

    externalAuthProfile-TacplusAcctClient-AcctServer2	OBJECT-TYPE
	SYNTAX	IpAddress
	ACCESS	read-write
	STATUS	mandatory
	DESCRIPTION	"The IP address of the second TACACS+ accounting server."
	::= { mibexternalAuthProfileEntry 69 }

    externalAuthProfile-TacplusAcctClient-AcctServer3	OBJECT-TYPE
	SYNTAX	IpAddress
	ACCESS	read-write
	STATUS	mandatory
	DESCRIPTION	"The IP address of the third TACACS+ accounting server."
	::= { mibexternalAuthProfileEntry 70 }

    externalAuthProfile-TacplusAcctClient-AcctPort	OBJECT-TYPE
	SYNTAX	INTEGER
	ACCESS	read-write
	STATUS	mandatory
	DESCRIPTION	"The TCP destination port to use for TACACS+ accounting."
	::= { mibexternalAuthProfileEntry 71 }

    externalAuthProfile-TacplusAcctClient-AcctSrcPort	OBJECT-TYPE
	SYNTAX	INTEGER
	ACCESS	read-write
	STATUS	mandatory
	DESCRIPTION	"The TCP source port to use for TACACS+ accounting. If zero, the source port is selected from the non-privileged port range (1024-2000)."
	::= { mibexternalAuthProfileEntry 72 }

    externalAuthProfile-TacplusAcctClient-AcctKey	OBJECT-TYPE
	SYNTAX	DisplayString
	ACCESS	read-write
	STATUS	mandatory
	DESCRIPTION	"The TACACS+ accounting access key shared with the TACACS+ server."
	::= { mibexternalAuthProfileEntry 73 }

    externalAuthProfile-SecureidAuthClient-AuthServer1	OBJECT-TYPE
	SYNTAX	IpAddress
	ACCESS	read-write
	STATUS	mandatory
	DESCRIPTION	"The IP address of the first authentication server."
	::= { mibexternalAuthProfileEntry 74 }

    externalAuthProfile-SecureidAuthClient-AuthServer2	OBJECT-TYPE
	SYNTAX	IpAddress
	ACCESS	read-write
	STATUS	mandatory
	DESCRIPTION	"The IP address of the second authentication server."
	::= { mibexternalAuthProfileEntry 75 }

    externalAuthProfile-SecureidAuthClient-AuthServer3	OBJECT-TYPE
	SYNTAX	IpAddress
	ACCESS	read-write
	STATUS	mandatory
	DESCRIPTION	"The IP address of the third authentication server."
	::= { mibexternalAuthProfileEntry 76 }

    externalAuthProfile-SecureidAuthClient-AuthPort	OBJECT-TYPE
	SYNTAX	INTEGER
	ACCESS	read-write
	STATUS	mandatory
	DESCRIPTION	"The UDP destination port to use for authentication."
	::= { mibexternalAuthProfileEntry 77 }

    externalAuthProfile-SecureidAuthClient-AuthTimeout	OBJECT-TYPE
	SYNTAX	INTEGER
	ACCESS	read-write
	STATUS	mandatory
	DESCRIPTION	"Number of seconds between retries to the authentication host."
	::= { mibexternalAuthProfileEntry 78 }

    externalAuthProfile-SecureidAuthClient-AuthRetrycount	OBJECT-TYPE
	SYNTAX	INTEGER
	ACCESS	read-write
	STATUS	mandatory
	DESCRIPTION	"Number of times to retry an authentication attempt."
	::= { mibexternalAuthProfileEntry 79 }

    externalAuthProfile-SecureidAuthClient-AuthDes	OBJECT-TYPE
	SYNTAX	INTEGER {
		    no (1),
		    yes (2)
		}
	ACCESS	read-write
	STATUS	mandatory
	DESCRIPTION	"Use DES encryption instead of native encryption."
	::= { mibexternalAuthProfileEntry 80 }

    externalAuthProfile-SecureidAuthClient-AuthNodeSecret	OBJECT-TYPE
	SYNTAX	DisplayString
	ACCESS	read-write
	STATUS	mandatory
	DESCRIPTION	"node secret assigned to this router, hexadecimal notation."
	::= { mibexternalAuthProfileEntry 81 }

    externalAuthProfile-PasswordProfile-Clid	OBJECT-TYPE
	SYNTAX	DisplayString
	ACCESS	read-write
	STATUS	mandatory
	DESCRIPTION	"This is the password for the CLID pseudo user."
	::= { mibexternalAuthProfileEntry 82 }

    externalAuthProfile-PasswordProfile-Dnis	OBJECT-TYPE
	SYNTAX	DisplayString
	ACCESS	read-write
	STATUS	mandatory
	DESCRIPTION	"This is the password for the DNIS pseudo user."
	::= { mibexternalAuthProfileEntry 83 }

    externalAuthProfile-PasswordProfile-Banner	OBJECT-TYPE
	SYNTAX	DisplayString
	ACCESS	read-write
	STATUS	mandatory
	DESCRIPTION	"This is the password for the Banner pseudo user."
	::= { mibexternalAuthProfileEntry 84 }

    externalAuthProfile-PasswordProfile-InitBanner	OBJECT-TYPE
	SYNTAX	DisplayString
	ACCESS	read-write
	STATUS	mandatory
	DESCRIPTION	"Authenticate DNIS using this password."
	::= { mibexternalAuthProfileEntry 85 }

    externalAuthProfile-PasswordProfile-Pool	OBJECT-TYPE
	SYNTAX	DisplayString
	ACCESS	read-write
	STATUS	mandatory
	DESCRIPTION	"This is the password for the POOLs pseudo user."
	::= { mibexternalAuthProfileEntry 86 }

    externalAuthProfile-PasswordProfile-Frdl	OBJECT-TYPE
	SYNTAX	DisplayString
	ACCESS	read-write
	STATUS	mandatory
	DESCRIPTION	"This is the password for the Frame Relay pseudo user."
	::= { mibexternalAuthProfileEntry 87 }

    externalAuthProfile-PasswordProfile-Dialout	OBJECT-TYPE
	SYNTAX	DisplayString
	ACCESS	read-write
	STATUS	mandatory
	DESCRIPTION	"This is the password for the Dialout pseudo user."
	::= { mibexternalAuthProfileEntry 88 }

    externalAuthProfile-PasswordProfile-DialoutRoutes	OBJECT-TYPE
	SYNTAX	DisplayString
	ACCESS	read-write
	STATUS	mandatory
	DESCRIPTION	"This is the password for the Dialout Routes pseudo user."
	::= { mibexternalAuthProfileEntry 89 }

    externalAuthProfile-PasswordProfile-DialoutIpxRoutes	OBJECT-TYPE
	SYNTAX	DisplayString
	ACCESS	read-write
	STATUS	mandatory
	DESCRIPTION	"This is the password for the Dialout IPX pseudo user."
	::= { mibexternalAuthProfileEntry 90 }

    externalAuthProfile-PasswordProfile-DialoutAtalkRoutes	OBJECT-TYPE
	SYNTAX	DisplayString
	ACCESS	read-write
	STATUS	mandatory
	DESCRIPTION	"This is the password for the Dialout Appletalk pseudo user."
	::= { mibexternalAuthProfileEntry 91 }

    externalAuthProfile-PasswordProfile-SourceAuth	OBJECT-TYPE
	SYNTAX	DisplayString
	ACCESS	read-write
	STATUS	mandatory
	DESCRIPTION	"This is the password for the Source Auth pseudo user."
	::= { mibexternalAuthProfileEntry 92 }

    externalAuthProfile-LocalProfilesFirst	OBJECT-TYPE
	SYNTAX	INTEGER {
		    lpfNo (1),
		    lpfYes (2),
		    lpfRno (3)
		}
	ACCESS	read-write
	STATUS	mandatory
	DESCRIPTION	"Authenticate using local profiles first."
	::= { mibexternalAuthProfileEntry 93 }

    externalAuthProfile-Noattr6UseTermsrv	OBJECT-TYPE
	SYNTAX	INTEGER {
		    no (1),
		    yes (2)
		}
	ACCESS	read-write
	STATUS	mandatory
	DESCRIPTION	"Using terminal server if attribute 6 is missing from RADIUS authentication."
	::= { mibexternalAuthProfileEntry 94 }

    externalAuthProfile-Clid	OBJECT-TYPE
	SYNTAX	DisplayString
	ACCESS	read-write
	STATUS	mandatory
	DESCRIPTION	"Authenticate CLID using this password."
	::= { mibexternalAuthProfileEntry 95 }

    externalAuthProfile-Dnis	OBJECT-TYPE
	SYNTAX	DisplayString
	ACCESS	read-write
	STATUS	mandatory
	DESCRIPTION	"Authenticate DNIS using this password."
	::= { mibexternalAuthProfileEntry 96 }

    externalAuthProfile-CliUserAuth	OBJECT-TYPE
	SYNTAX	INTEGER {
		    localOnly (1),
		    localThenExternal (2),
		    externalOnly (3),
		    externalThenLocal (4),
		    externalThenLocalIfTimeout (5)
		}
	ACCESS	read-write
	STATUS	mandatory
	DESCRIPTION	"Authenticate the user Locally or Externally in the sequence specified by this filed."
	::= { mibexternalAuthProfileEntry 100 }

    externalAuthProfile-Action-o	OBJECT-TYPE
	SYNTAX	INTEGER {
		    noAction (1),
		    createProfile (2),
		    deleteProfile (3)
		}
	ACCESS	read-write
	STATUS	mandatory
	DESCRIPTION	""
	::= { mibexternalAuthProfileEntry 97 }


	-- The mibexternalAuthProfile__rad_auth_server__auth_key table
	--
	-- This table contains parameters for the mibexternalAuthProfile__rad_auth_server__auth_key profile
	--

    mibexternalAuthProfile-RadAuthServer-AuthKeyTable	OBJECT-TYPE
	SYNTAX		SEQUENCE OF MibexternalAuthProfile-RadAuthServer-AuthKeyEntry
	ACCESS		not-accessible
	STATUS		mandatory
	DESCRIPTION	"A list of mibexternalAuthProfile__rad_auth_server__auth_key profile entries."
	::= { mibexternalAuthProfile 2 }

    mibexternalAuthProfile-RadAuthServer-AuthKeyEntry	OBJECT-TYPE
	SYNTAX		MibexternalAuthProfile-RadAuthServer-AuthKeyEntry
	ACCESS		not-accessible
	STATUS		mandatory
	DESCRIPTION	"A mibexternalAuthProfile__rad_auth_server__auth_key entry containing objects that
			 maps to the parameters of mibexternalAuthProfile__rad_auth_server__auth_key profile."
	INDEX		{ externalAuthProfile-RadAuthServer-AuthKey-Index-o, externalAuthProfile-RadAuthServer-AuthKey-Index1-o }
	::= { mibexternalAuthProfile-RadAuthServer-AuthKeyTable 1 }

    MibexternalAuthProfile-RadAuthServer-AuthKeyEntry ::=
	SEQUENCE {
	    externalAuthProfile-RadAuthServer-AuthKey-Index-o
		INTEGER,
	    externalAuthProfile-RadAuthServer-AuthKey-Index1-o
		INTEGER,
	    externalAuthProfile-RadAuthServer-AuthKey
		DisplayString
	}

    externalAuthProfile-RadAuthServer-AuthKey-Index-o	OBJECT-TYPE
	SYNTAX	INTEGER
	ACCESS	read-only
	STATUS	mandatory
	DESCRIPTION	""
	::= { mibexternalAuthProfile-RadAuthServer-AuthKeyEntry 1 }

    externalAuthProfile-RadAuthServer-AuthKey-Index1-o	OBJECT-TYPE
	SYNTAX	INTEGER
	ACCESS	read-only
	STATUS	mandatory
	DESCRIPTION	""
	::= { mibexternalAuthProfile-RadAuthServer-AuthKeyEntry 2 }

    externalAuthProfile-RadAuthServer-AuthKey	OBJECT-TYPE
	SYNTAX	DisplayString
	ACCESS	read-write
	STATUS	mandatory
	DESCRIPTION	"The on-board RADIUS server key, shared with the RADIUS clients."
	::= { mibexternalAuthProfile-RadAuthServer-AuthKeyEntry 3 }


	-- The mibexternalAuthProfile__rad_auth_server__auth_netmask table
	--
	-- This table contains parameters for the mibexternalAuthProfile__rad_auth_server__auth_netmask profile
	--

    mibexternalAuthProfile-RadAuthServer-AuthNetmaskTable	OBJECT-TYPE
	SYNTAX		SEQUENCE OF MibexternalAuthProfile-RadAuthServer-AuthNetmaskEntry
	ACCESS		not-accessible
	STATUS		mandatory
	DESCRIPTION	"A list of mibexternalAuthProfile__rad_auth_server__auth_netmask profile entries."
	::= { mibexternalAuthProfile 3 }

    mibexternalAuthProfile-RadAuthServer-AuthNetmaskEntry	OBJECT-TYPE
	SYNTAX		MibexternalAuthProfile-RadAuthServer-AuthNetmaskEntry
	ACCESS		not-accessible
	STATUS		mandatory
	DESCRIPTION	"A mibexternalAuthProfile__rad_auth_server__auth_netmask entry containing objects that
			 maps to the parameters of mibexternalAuthProfile__rad_auth_server__auth_netmask profile."
	INDEX		{ externalAuthProfile-RadAuthServer-AuthNetmask-Index-o, externalAuthProfile-RadAuthServer-AuthNetmask-Index1-o }
	::= { mibexternalAuthProfile-RadAuthServer-AuthNetmaskTable 1 }

    MibexternalAuthProfile-RadAuthServer-AuthNetmaskEntry ::=
	SEQUENCE {
	    externalAuthProfile-RadAuthServer-AuthNetmask-Index-o
		INTEGER,
	    externalAuthProfile-RadAuthServer-AuthNetmask-Index1-o
		INTEGER,
	    externalAuthProfile-RadAuthServer-AuthNetmask
		IpAddress
	}

    externalAuthProfile-RadAuthServer-AuthNetmask-Index-o	OBJECT-TYPE
	SYNTAX	INTEGER
	ACCESS	read-only
	STATUS	mandatory
	DESCRIPTION	""
	::= { mibexternalAuthProfile-RadAuthServer-AuthNetmaskEntry 1 }

    externalAuthProfile-RadAuthServer-AuthNetmask-Index1-o	OBJECT-TYPE
	SYNTAX	INTEGER
	ACCESS	read-only
	STATUS	mandatory
	DESCRIPTION	""
	::= { mibexternalAuthProfile-RadAuthServer-AuthNetmaskEntry 2 }

    externalAuthProfile-RadAuthServer-AuthNetmask	OBJECT-TYPE
	SYNTAX	IpAddress
	ACCESS	read-write
	STATUS	mandatory
	DESCRIPTION	"The IP netmask of the RADIUS clients."
	::= { mibexternalAuthProfile-RadAuthServer-AuthNetmaskEntry 3 }


	-- The mibexternalAuthProfile__rad_auth_server__auth_client table
	--
	-- This table contains parameters for the mibexternalAuthProfile__rad_auth_server__auth_client profile
	--

    mibexternalAuthProfile-RadAuthServer-AuthClientTable	OBJECT-TYPE
	SYNTAX		SEQUENCE OF MibexternalAuthProfile-RadAuthServer-AuthClientEntry
	ACCESS		not-accessible
	STATUS		mandatory
	DESCRIPTION	"A list of mibexternalAuthProfile__rad_auth_server__auth_client profile entries."
	::= { mibexternalAuthProfile 4 }

    mibexternalAuthProfile-RadAuthServer-AuthClientEntry	OBJECT-TYPE
	SYNTAX		MibexternalAuthProfile-RadAuthServer-AuthClientEntry
	ACCESS		not-accessible
	STATUS		mandatory
	DESCRIPTION	"A mibexternalAuthProfile__rad_auth_server__auth_client entry containing objects that
			 maps to the parameters of mibexternalAuthProfile__rad_auth_server__auth_client profile."
	INDEX		{ externalAuthProfile-RadAuthServer-AuthClient-Index-o, externalAuthProfile-RadAuthServer-AuthClient-Index1-o }
	::= { mibexternalAuthProfile-RadAuthServer-AuthClientTable 1 }

    MibexternalAuthProfile-RadAuthServer-AuthClientEntry ::=
	SEQUENCE {
	    externalAuthProfile-RadAuthServer-AuthClient-Index-o
		INTEGER,
	    externalAuthProfile-RadAuthServer-AuthClient-Index1-o
		INTEGER,
	    externalAuthProfile-RadAuthServer-AuthClient
		IpAddress
	}

    externalAuthProfile-RadAuthServer-AuthClient-Index-o	OBJECT-TYPE
	SYNTAX	INTEGER
	ACCESS	read-only
	STATUS	mandatory
	DESCRIPTION	""
	::= { mibexternalAuthProfile-RadAuthServer-AuthClientEntry 1 }

    externalAuthProfile-RadAuthServer-AuthClient-Index1-o	OBJECT-TYPE
	SYNTAX	INTEGER
	ACCESS	read-only
	STATUS	mandatory
	DESCRIPTION	""
	::= { mibexternalAuthProfile-RadAuthServer-AuthClientEntry 2 }

    externalAuthProfile-RadAuthServer-AuthClient	OBJECT-TYPE
	SYNTAX	IpAddress
	ACCESS	read-write
	STATUS	mandatory
	DESCRIPTION	"The IP address of the RADIUS clients."
	::= { mibexternalAuthProfile-RadAuthServer-AuthClientEntry 3 }


	-- The mibradStatProfile table
	--
	-- This table contains parameters for the mibradStatProfile profile
	--

    mibradStatProfileTable	OBJECT-TYPE
	SYNTAX		SEQUENCE OF MibradStatProfileEntry
	ACCESS		not-accessible
	STATUS		mandatory
	DESCRIPTION	"A list of mibradStatProfile profile entries."
	::= { mibradStatProfile 1 }

    mibradStatProfileEntry	OBJECT-TYPE
	SYNTAX		MibradStatProfileEntry
	ACCESS		not-accessible
	STATUS		mandatory
	DESCRIPTION	"A mibradStatProfile entry containing objects that
			 maps to the parameters of mibradStatProfile profile."
	INDEX		{ radStatProfile-Index-o }
	::= { mibradStatProfileTable 1 }

    MibradStatProfileEntry ::=
	SEQUENCE {
	    radStatProfile-Index-o
		INTEGER,
	    radStatProfile-CurrentAuthServer
		INTEGER,
	    radStatProfile-CurrentAcctServer
		INTEGER,
	    radStatProfile-Action-o
		INTEGER
	}

    radStatProfile-Index-o	OBJECT-TYPE
	SYNTAX	INTEGER
	ACCESS	read-only
	STATUS	mandatory
	DESCRIPTION	""
	::= { mibradStatProfileEntry 1 }

    radStatProfile-CurrentAuthServer	OBJECT-TYPE
	SYNTAX	INTEGER
	ACCESS	read-only
	STATUS	mandatory
	DESCRIPTION	"The index of the current RADIUS authentication server."
	::= { mibradStatProfileEntry 2 }

    radStatProfile-CurrentAcctServer	OBJECT-TYPE
	SYNTAX	INTEGER
	ACCESS	read-only
	STATUS	mandatory
	DESCRIPTION	"The index of the current RADIUS accounting server."
	::= { mibradStatProfileEntry 3 }

    radStatProfile-Action-o	OBJECT-TYPE
	SYNTAX	INTEGER {
		    noAction (1),
		    createProfile (2),
		    deleteProfile (3)
		}
	ACCESS	read-write
	STATUS	mandatory
	DESCRIPTION	""
	::= { mibradStatProfileEntry 4 }


	-- The mibradAcctCallLogProfile table
	--
	-- This table contains parameters for the mibradAcctCallLogProfile profile
	--

    mibradAcctCallLogProfileTable	OBJECT-TYPE
	SYNTAX		SEQUENCE OF MibradAcctCallLogProfileEntry
	ACCESS		not-accessible
	STATUS		mandatory
	DESCRIPTION	"A list of mibradAcctCallLogProfile profile entries."
	::= { mibradAcctCallLogProfile 1 }

    mibradAcctCallLogProfileEntry	OBJECT-TYPE
	SYNTAX		MibradAcctCallLogProfileEntry
	ACCESS		not-accessible
	STATUS		mandatory
	DESCRIPTION	"A mibradAcctCallLogProfile entry containing objects that
			 maps to the parameters of mibradAcctCallLogProfile profile."
	INDEX		{ radAcctCallLogProfile-Index-o }
	::= { mibradAcctCallLogProfileTable 1 }

    MibradAcctCallLogProfileEntry ::=
	SEQUENCE {
	    radAcctCallLogProfile-Index-o
		INTEGER,
	    radAcctCallLogProfile-CallLogEnable
		INTEGER,
	    radAcctCallLogProfile-CallLogHost1
		IpAddress,
	    radAcctCallLogProfile-CallLogHost2
		IpAddress,
	    radAcctCallLogProfile-CallLogHost3
		IpAddress,
	    radAcctCallLogProfile-CallLogPort
		INTEGER,
	    radAcctCallLogProfile-CallLogKey
		DisplayString,
	    radAcctCallLogProfile-CallLogTimeout
		INTEGER,
	    radAcctCallLogProfile-CallLogIdBase
		INTEGER,
	    radAcctCallLogProfile-CallLogResetTime
		INTEGER,
	    radAcctCallLogProfile-CallLogStopOnly
		INTEGER,
	    radAcctCallLogProfile-CallLogLimitRetry
		INTEGER,
	    radAcctCallLogProfile-CallLogServerIndex
		INTEGER,
	    radAcctCallLogProfile-CallLogRadiusCompat
		INTEGER,
	    radAcctCallLogProfile-CallLogMultiPacket
		INTEGER,
	    radAcctCallLogProfile-CallLogStreamPeriod
		INTEGER,
	    radAcctCallLogProfile-CallLogConnectionPacketsEnable
		INTEGER,
	    radAcctCallLogProfile-CallLogCsmModemDiag
		INTEGER,
	    radAcctCallLogProfile-VoipCallLogging
		INTEGER,
	    radAcctCallLogProfile-CallLogSwitchover
		INTEGER,
	    radAcctCallLogProfile-Action-o
		INTEGER
	}

    radAcctCallLogProfile-Index-o	OBJECT-TYPE
	SYNTAX	INTEGER
	ACCESS	read-only
	STATUS	mandatory
	DESCRIPTION	""
	::= { mibradAcctCallLogProfileEntry 1 }

    radAcctCallLogProfile-CallLogEnable	OBJECT-TYPE
	SYNTAX	INTEGER {
		    no (1),
		    yes (2)
		}
	ACCESS	read-write
	STATUS	mandatory
	DESCRIPTION	"Enable call log support."
	::= { mibradAcctCallLogProfileEntry 2 }

    radAcctCallLogProfile-CallLogHost1	OBJECT-TYPE
	SYNTAX	IpAddress
	ACCESS	read-write
	STATUS	mandatory
	DESCRIPTION	"The IP address of the first (RADIUS_ACCT) call log host."
	::= { mibradAcctCallLogProfileEntry 3 }

    radAcctCallLogProfile-CallLogHost2	OBJECT-TYPE
	SYNTAX	IpAddress
	ACCESS	read-write
	STATUS	mandatory
	DESCRIPTION	"The IP address of the second (RADIUS_ACCT) call log host."
	::= { mibradAcctCallLogProfileEntry 4 }

    radAcctCallLogProfile-CallLogHost3	OBJECT-TYPE
	SYNTAX	IpAddress
	ACCESS	read-write
	STATUS	mandatory
	DESCRIPTION	"The IP address of the third (RADIUS_ACCT) call log host."
	::= { mibradAcctCallLogProfileEntry 5 }

    radAcctCallLogProfile-CallLogPort	OBJECT-TYPE
	SYNTAX	INTEGER
	ACCESS	read-write
	STATUS	mandatory
	DESCRIPTION	"The UDP port to use for (RADIUS_ACCT) call log accounting."
	::= { mibradAcctCallLogProfileEntry 6 }

    radAcctCallLogProfile-CallLogKey	OBJECT-TYPE
	SYNTAX	DisplayString
	ACCESS	read-write
	STATUS	mandatory
	DESCRIPTION	"The (RADIUS_ACCT) call log accounting key."
	::= { mibradAcctCallLogProfileEntry 7 }

    radAcctCallLogProfile-CallLogTimeout	OBJECT-TYPE
	SYNTAX	INTEGER
	ACCESS	read-write
	STATUS	mandatory
	DESCRIPTION	"Number of seconds to wait for a response to previous call log accounting request."
	::= { mibradAcctCallLogProfileEntry 8 }

    radAcctCallLogProfile-CallLogIdBase	OBJECT-TYPE
	SYNTAX	INTEGER {
		    acctBase10 (1),
		    acctBase16 (2)
		}
	ACCESS	read-write
	STATUS	mandatory
	DESCRIPTION	"The Base to use in reporting Account ID."
	::= { mibradAcctCallLogProfileEntry 9 }

    radAcctCallLogProfile-CallLogResetTime	OBJECT-TYPE
	SYNTAX	INTEGER
	ACCESS	read-write
	STATUS	mandatory
	DESCRIPTION	"The timer to reset to the primary server(host-1) after current host is changed to host-2 or host-3. Value is in seconds. If value is 0, no timer is run."
	::= { mibradAcctCallLogProfileEntry 10 }

    radAcctCallLogProfile-CallLogStopOnly	OBJECT-TYPE
	SYNTAX	INTEGER {
		    no (1),
		    yes (2)
		}
	ACCESS	read-write
	STATUS	mandatory
	DESCRIPTION	"Send call log Stop packets that have username=0. These are caused by connections that are dropped before authentication is done."
	::= { mibradAcctCallLogProfileEntry 11 }

    radAcctCallLogProfile-CallLogLimitRetry	OBJECT-TYPE
	SYNTAX	INTEGER
	ACCESS	read-write
	STATUS	mandatory
	DESCRIPTION	"Number of retries before removing call log packet. 0 means leave on retry list until maximum retry entries are exceeded."
	::= { mibradAcctCallLogProfileEntry 12 }

    radAcctCallLogProfile-CallLogServerIndex	OBJECT-TYPE
	SYNTAX	INTEGER {
		    host1 (1),
		    host2 (2),
		    host3 (3)
		}
	ACCESS	read-write
	STATUS	mandatory
	DESCRIPTION	"The currently active call Logging server Index. The default factory setting is host-1."
	::= { mibradAcctCallLogProfileEntry 14 }

    radAcctCallLogProfile-CallLogRadiusCompat	OBJECT-TYPE
	SYNTAX	INTEGER {
		    vendorSpecific (1),
		    n-16BitVendorSpecific (2)
		}
	ACCESS	read-write
	STATUS	mandatory
	DESCRIPTION	"Call Logging RADIUS compatibility mode."
	::= { mibradAcctCallLogProfileEntry 13 }

    radAcctCallLogProfile-CallLogMultiPacket	OBJECT-TYPE
	SYNTAX	INTEGER {
		    no (1),
		    yes (2)
		}
	ACCESS	read-write
	STATUS	mandatory
	DESCRIPTION	"Call Logging MultiPacket Enable."
	::= { mibradAcctCallLogProfileEntry 15 }

    radAcctCallLogProfile-CallLogStreamPeriod	OBJECT-TYPE
	SYNTAX	INTEGER
	ACCESS	read-write
	STATUS	mandatory
	DESCRIPTION	"Number of minutes between snapshots for stream pkts."
	::= { mibradAcctCallLogProfileEntry 16 }

    radAcctCallLogProfile-CallLogConnectionPacketsEnable	OBJECT-TYPE
	SYNTAX	INTEGER {
		    no (1),
		    yes (2)
		}
	ACCESS	read-write
	STATUS	mandatory
	DESCRIPTION	"Enable/Disable call logging START/STOP pkts when connection comes up or goes down. This is opposed to line statistics call logging which is always enabled."
	::= { mibradAcctCallLogProfileEntry 17 }

    radAcctCallLogProfile-CallLogCsmModemDiag	OBJECT-TYPE
	SYNTAX	INTEGER {
		    no (1),
		    yes (2)
		}
	ACCESS	read-write
	STATUS	mandatory
	DESCRIPTION	"Enable CSM Modem diagnostics in Call Logging"
	::= { mibradAcctCallLogProfileEntry 18 }

    radAcctCallLogProfile-VoipCallLogging	OBJECT-TYPE
	SYNTAX	INTEGER {
		    no (1),
		    yes (2)
		}
	ACCESS	read-write
	STATUS	mandatory
	DESCRIPTION	"To Enable/Disable call logging for VOIP calls."
	::= { mibradAcctCallLogProfileEntry 20 }

    radAcctCallLogProfile-CallLogSwitchover	OBJECT-TYPE
	SYNTAX	INTEGER {
		    no (1),
		    yes (2)
		}
	ACCESS	read-write
	STATUS	mandatory
	DESCRIPTION	"Determines whether Accounting-on packet with event Ascend-Control-Module-Switchover should be sent or not during switchover when syncing is enabled."
	::= { mibradAcctCallLogProfileEntry 21 }

    radAcctCallLogProfile-Action-o	OBJECT-TYPE
	SYNTAX	INTEGER {
		    noAction (1),
		    createProfile (2),
		    deleteProfile (3)
		}
	ACCESS	read-write
	STATUS	mandatory
	DESCRIPTION	""
	::= { mibradAcctCallLogProfileEntry 19 }

END
