-- Avidia DSLAM SUBTENDING MIB
-- $Revision:   1.6  $
-- $Date:   Jul 07 2000 15:05:24  $

-- Copyright 2000 PairGain Technologies, Inc.  All Rights
-- Reserved.  Reproduction of this document is authorized on
-- condition that the foregoing copyright notice is included.
-- This PairGain SNMP Management Information Base Specification
-- (Specification) embodies PairGain's confidential and
-- proprietary intellectual property.  PairGain retains all
-- title and ownership in the Specification, including any
-- revisions.
--
-- It is PairGain's intent to encourage the widespread use of
-- this Specification in connection with the management of
-- PairGain products. PairGain grants vendors, end-users,
-- and other interested parties a non-exclusive license to
-- use this Specification in connection with the management
-- of PairGain products.
--
-- This Specification is supplied "AS IS," and PairGain makes
-- no warranty, either expressed or implied, as to the use,
-- operation, condition, or performance of the Specification.
--
-- Revision History
--------------------------------------------------------------
-- Date     Ver     Programmer  Description
--------------------------------------------------------------
-- 04/03/00 1.1     ebe       Initial Release
-- 06/21/00 1.2     ebe       Changes suggested in review
--        OBJECT-TYPE,
--        MODULE-IDENTITY,
--        IpAddress,
--        NOTIFICATION-TYPE,
--        Integer32
--                FROM SNMPv2-SMI


AVIDIA-SUBTEND-MIB DEFINITIONS ::= BEGIN

IMPORTS
        OBJECT-TYPE,
        MODULE-IDENTITY,
        IpAddress,
        NOTIFICATION-TYPE,
        Integer32
                FROM SNMPv2-SMI
    RowStatus
        FROM SNMPv2-TC
    InterfaceIndex
        FROM IF-MIB
    pgainDSLAM
        FROM PAIRGAIN-COMMON-HD-MIB;
 
avSubtendMIB MODULE-IDENTITY
        LAST-UPDATED    "0006210000Z"
        ORGANIZATION    "Pairgain Technologies Inc."
        CONTACT-INFO    "Ashok Singh
                         Pairgain Technologies Inc
                         14402 Franklin Avenue
                         Tustin, CA 92780"
        DESCRIPTION     "The module defines MIB for Avidia subtending"
        ::= {pgainDSLAM 14}


avSubtendInterfaces     OBJECT IDENTIFIER ::= { avSubtendMIB 1 }

--
-- avSubtendInterfaces group
-- 

--
-- The Pairgain Subtend Table
--

avSubtendIfTable OBJECT-TYPE
        SYNTAX  SEQUENCE OF AvSubtendIfEntry
        MAX-ACCESS  not-accessible
        STATUS  mandatory
        DESCRIPTION
                "A table that contains subtended interface information in 
        Avidia"
        ::= { avSubtendInterfaces 1 }

avSubtendIfEntry OBJECT-TYPE
        SYNTAX  AvSubtendIfEntry
        MAX-ACCESS  not-accessible
        STATUS  mandatory
        DESCRIPTION
                "Entry in avSubtendIfTable that contains port database 
        information for a subtended interface"

        INDEX { avSubtendIndex }
        ::= { avSubtendIfTable 1 }

AvSubtendIfEntry ::=
        SEQUENCE {
                avSubtendIndex                         INTEGER,
                avSubtendIfRowStatus                   RowStatus,
                avSubtendIfIndex                       InterfaceIndex,
                avSubtendIfVpi                         INTEGER,
                avSubtendIfVci                         INTEGER,
                avSubtendIfSourceIpAddress             IpAddress,
                avSubtendIfDestinationIpAddress        IpAddress,
                avSubtendIfSubnetMask                  IpAddress,
                avSubtendIfParentIfIndex               InterfaceIndex,
                avSubtendIfParentIpAddress             IpAddress,
                avSubtendIfAdminStatus                 INTEGER,
                avSubtendIfOperStatus                  INTEGER
        }

avSubtendIndex OBJECT-TYPE
        SYNTAX  INTEGER
        MAX-ACCESS  read-only
        STATUS  mandatory
        DESCRIPTION
                 "This is the index for the avSubtendIfTable. 
                  The index is generated by the agent implementation and
                  is available by querying avSubtendIndexNext"
        ::= { avSubtendIfEntry 1 }

avSubtendIfRowStatus OBJECT-TYPE
        SYNTAX      RowStatus
        MAX-ACCESS      read-write
        STATUS          mandatory
        DESCRIPTION 
            "This specifies the status of a row in the avSubtendIfTable.
             This allows table entries to be created and deleted."

        ::= { avSubtendIfEntry 2 }

avSubtendIfIndex OBJECT-TYPE
        SYNTAX  InterfaceIndex
        MAX-ACCESS  read-write
        STATUS  mandatory
        DESCRIPTION
                "This specifies the IfIndex which is computed from 
                Slot number and Port Number for the subtending entry"

        ::= { avSubtendIfEntry 3 }

avSubtendIfVpi OBJECT-TYPE
        SYNTAX  INTEGER
        MAX-ACCESS  read-write
        STATUS  mandatory
        DESCRIPTION
                 "This specifies the VPI for the subtending entry"
        ::= { avSubtendIfEntry 4 }

avSubtendIfVci OBJECT-TYPE
        SYNTAX  INTEGER
        MAX-ACCESS  read-write
        STATUS  mandatory
        DESCRIPTION
                "This specifies the VCI for the subtending entry"
        ::= { avSubtendIfEntry 5 }

avSubtendIfSourceIpAddress OBJECT-TYPE
    SYNTAX  IpAddress
        MAX-ACCESS  read-write
        STATUS  mandatory
    DESCRIPTION
                "This specifies the source IP address for the subtending entry"
        ::= { avSubtendIfEntry 6 }

avSubtendIfDestinationIpAddress OBJECT-TYPE
        SYNTAX  IpAddress
        MAX-ACCESS  read-write
        STATUS  mandatory
        DESCRIPTION
                "This specifies the destination IP address for the subtending
                 entry"
        ::= { avSubtendIfEntry 7 }

avSubtendIfSubnetMask OBJECT-TYPE
        SYNTAX  IpAddress
        MAX-ACCESS  read-write
        STATUS  mandatory
        DESCRIPTION
                "This specifies the IP subnet mask for the subtending entry"
        ::= { avSubtendIfEntry 8 }

avSubtendIfParentIfIndex OBJECT-TYPE
        SYNTAX  InterfaceIndex
        MAX-ACCESS  read-write
        STATUS  mandatory
        DESCRIPTION
                "This specifies the IfIndex for the parent.
                This is calculated from the slot and port number of the
                parent"
        DEFVAL { 0 }
        ::= { avSubtendIfEntry 9 }

avSubtendIfParentIpAddress OBJECT-TYPE
        SYNTAX  IpAddress
        MAX-ACCESS  read-write
        STATUS  mandatory
        DESCRIPTION
                "This specifies the parent IP address for the subtending
                 entry"
        ::= { avSubtendIfEntry 10 }

avSubtendIfAdminStatus OBJECT-TYPE
       SYNTAX  INTEGER {
                   up(1),       -- ready to pass packets
                   down(2),
                   testing(3)   -- in some test mode
               }
       MAX-ACCESS  read-write
       STATUS      mandatory
       DESCRIPTION
               "The desired state of the interface.  The testing(3)
               state indicates that no operational packets can be
               passed.  When a managed system initializes, all
               interfaces start with ifAdminStatus in the down(2)
               state.  As a result of either explicit management
               action or per configuration information retained by
               the managed system, ifAdminStatus is then changed to
               either the up(1) or testing(3) states (or remains in
               the down(2) state)."
       ::= { avSubtendIfEntry 11 }

avSubtendIfOperStatus OBJECT-TYPE
       SYNTAX  INTEGER {
                   up(1),       -- ready to pass packets
                   down(2),
                   testing(3),  -- in some test mode
                   unknown(4),  -- status can not be determined
                                -- for some reason.
                   dormant(5)
               }
       MAX-ACCESS  read-only
       STATUS      mandatory
       DESCRIPTION
               "The current operational state of the interface.  The
               testing(3) state indicates that no operational packets
               can be passed.  If ifAdminStatus is down(2) then
               ifOperStatus should be down(2).  If ifAdminStatus is
               changed to up(1) then ifOperStatus should change to
               up(1) if the interface is ready to transmit and
               receive network traffic; it should change to
               dormant(5) if the interface is waiting for external
               actions (such as a serial line waiting for an
               incomming connection); it should remain in the down(2)
               state if and only if there is a fault that prevents if
               from going to the up(1) state."
       ::= { avSubtendIfEntry 12 }

     --
     -- The following object may be used in conjunction with
     -- the avSubtendIfTable for the creation of
     -- new table entries.
     --

avSubtendIndexNext  OBJECT-TYPE
          SYNTAX         INTEGER (1..512)
          MAX-ACCESS     read-only
          STATUS         mandatory
          DESCRIPTION
           "This object contains an appropriate value to
            be used for avSubtendIndex when
            creating entries in the avSubtendIfTable.
            The value 0 indicates that no unassigned
            entries are available. To obtain the
            avSubtendIndex value for a new
            entry, the manager issues a management
            protocol retrieval operation to obtain the
            current value of this object."

        ::= { avSubtendInterfaces 2 }
END
