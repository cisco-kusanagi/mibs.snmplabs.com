SALIX-SYSTEM-MIB DEFINITIONS ::= BEGIN

IMPORTS
         MODULE-COMPLIANCE, OBJECT-GROUP     FROM SNMPv2-CONF
   
         OBJECT-TYPE, Unsigned32, Integer32,
         MODULE-IDENTITY, NOTIFICATION-TYPE  FROM SNMPv2-SMI  
         
         DisplayString                       FROM SNMPv2-TC
         
         InterfaceIndex, ifOperStatus        FROM IF-MIB
         
         PhysicalIndex, entPhysicalIndex, 
         entPhysicalClass, entPhysicalContainedIn,
         entPhysicalParentRelPos             FROM ENTITY-MIB
                  
         TruthValue                          FROM ATM-FORUM-TC-MIB
         
         atmfM4TcAdaptorEntry, 
         atmfM4EquipHolderEntry,
         atmfM4PlugInUnitEntry, 
         atmfM4CellProtoHistIndex,
         atmfM4TrapAlarmSeverity,
         atmfM4PlugInUnitAvailStatus         FROM ATM-FORUM-M4-MIB

         salixGeneric                        FROM SALIX-MIB;
         

salixSystemMIB MODULE-IDENTITY
     LAST-UPDATED "9810130000Z"
     ORGANIZATION "SALIX Technologies"
     CONTACT-INFO "904 Wind River Lane
                   Suite 101
                   Gaithersburg, MD  20878
                   (301)-417-0017"
     DESCRIPTION  "The MIB describing System Objects 
                   for SALIX products.  These objects include error
                   reporting objects, and other system information objects"
     ::= { salixGeneric 3 }   
     
   salixSystemMIBObjects OBJECT IDENTIFIER ::= { salixSystemMIB 1 }
   salixSystemMIBTraps   OBJECT IDENTIFIER ::= { salixSystemMIB 2 }
   salixSystemMIBCompliance OBJECT IDENTIFIER ::= { salixSystemMIB 3 }           
   salixSystemMIBTrapPrefix   OBJECT IDENTIFIER ::= { salixSystemMIBTraps 0 }   
   
   salixSystemSync OBJECT IDENTIFIER ::= { salixSystemMIBObjects 5 }
   salixSystemHsf  OBJECT IDENTIFIER ::= { salixSystemMIBObjects 6 }
   salixSystemRsc  OBJECT IDENTIFIER ::= { salixSystemMIBObjects 7 }

  -- Error reporting variables
  
  -- The following three variables provide a way of reporting SNMP errors        
  -- to the management station.  The SNMP agent keeps track three variables
  -- for each set request (last error number, last error message, and the 
  -- last Oid that was set and caused the error).  This information is based 
  -- on the incoming ipaddress and port, so there is only one instance
  -- available for each source.  The SNMP agent is responsible for correlating 
  -- the error reporting variables to the source Network Management System 
  -- (NMS) so that an NMS will only see errors that are a result of its 
  -- own set request.  If there is no errors available for this source, no 
  -- value is returned.

  salixSysLastLogErrorNumber OBJECT-TYPE
	    SYNTAX	   Unsigned32
	    MAX-ACCESS	read-only
	    STATUS	current
	    DESCRIPTION
		      "The error number that is associate with the last set request."
       ::= { salixSystemMIBObjects 1 }

  salixSysLastLogErrorMessage OBJECT-TYPE
	    SYNTAX	DisplayString (SIZE (0..255))
	    MAX-ACCESS	read-only
	    STATUS	current  
	    DESCRIPTION
		      "The error message that describes the error associated with the 
		       last set request."
       ::= { salixSystemMIBObjects 2 }

  salixSysLastLogErrorOid OBJECT-TYPE
	    SYNTAX	OBJECT IDENTIFIER
	    MAX-ACCESS	read-only
	    STATUS	current
	    DESCRIPTION
		      "The last set request OID that produced an error."
       ::= { salixSystemMIBObjects 3 }

  salixSysTemperature OBJECT-TYPE
	    SYNTAX	Integer32
	    MAX-ACCESS	read-only
	    STATUS	deprecated
	    DESCRIPTION
		      "The temperature in degrees Celsius inside the  chassis."
       ::= { salixSystemMIBObjects 4 }

  salixSysLoginMessage OBJECT-TYPE
	    SYNTAX	OCTET STRING (SIZE (0..768))
	    MAX-ACCESS	read-write
	    STATUS	current  
	    DESCRIPTION
		      "The message is displayed every time a user logs into the
		       CLI.  It may be used to display legal warnings."
       ::= { salixSystemMIBObjects 8 }

       
  -- SALIX System Sync Objects

  salixSysSyncTimingMode OBJECT-TYPE
       SYNTAX     INTEGER { internal(1), line(2), external(3) }
       MAX-ACCESS read-write
       STATUS     current
       DESCRIPTION
            "An identification of the source from which timing is derived by
             the working sync module.  Possible values are:

             internal(1) - the internal oscillator on the sync module will be
                           used as the master clock for system synchronization.
             line(2)     - the sync module is synchronizing with the receive
                           line timing from a signal received by an LIU.
             external(3) - an external timing interface will be used as the 
                           master clock for system sychronization."           
                           
       DEFVAL { internal }
       ::= { salixSystemSync 1 }

  salixSysSyncPrimaryRef OBJECT-TYPE
       SYNTAX     InterfaceIndex
       MAX-ACCESS read-write
       STATUS     current
       DESCRIPTION
            "The interface index of the primary reference line from which
             the sync module can derive timing.  If the 
             'salixSysSyncTimingMode' is set to 'line' then this interface 
             index should identify a physical line termination point.
             If the 'salixSysSyncTimingMode' is set to 'external' then this 
             interface index should identify a external timing interface."
       ::= { salixSystemSync 2 }

  salixSysSyncSecondaryRef OBJECT-TYPE
       SYNTAX     InterfaceIndex
       MAX-ACCESS read-write
       STATUS     current
       DESCRIPTION
            "The interface index of the secondary reference line from which
             the sync module can derive timing.  If the 
             'salixSysSyncTimingMode' is set to 'line' then this interface 
             index should identify a physical line termination point.
             If the 'salixSysSyncTimingMode' is set to 'external' then this 
             interface index should identify an external timing interface.
       
             The secondary reference line is only used if the 
             salixSysSyncTimingMode is set to 'line' or 'external' and the
             primary reference line identified by 'salixSysSyncPrimaryRef'
             has an oper status of 'down'."
       ::= { salixSystemSync 3 }

  salixSysSyncRevertiveSwitch OBJECT-TYPE
       SYNTAX     TruthValue
       MAX-ACCESS read-write
       STATUS     current
       DESCRIPTION
            "Indication of whether or not the active interface for deriving 
             timing should revert to the interface defined by the primary 
             reference line 'salixSysSyncPrimaryRef' if the primary
             becomes available after a failure is cleared.  This object is
             only valid if the 'salixSysSyncTimingMode' is configured as 
             'line' or 'external'.

             true(1)  - reference switching is revertive
             false(2) - reference switching is non-revertive"
       DEFVAL { false }
       ::= { salixSystemSync 4 }

  salixSysSyncClockMode OBJECT-TYPE
       SYNTAX     INTEGER { freeRun(1),
                            normal(2),
                            holdover(3),
                            fastStart(4)
                          }
       MAX-ACCESS read-only
       STATUS     current
       DESCRIPTION
            "Indication of the clock mode of the 'working' sync module.

             freeRun(1)  - mode in which the clock is synchronized to the
                           module's internal oscillator.
             normal(2)   - mode in which the clock is synchronized to an
                           external reference.
             holdover(3) - mode in which the clock, after having been
                           synchronized to an external reference, loses that
                           reference and all other external references.
             fastStart(4) - mode in which the clock is in the process of
                           synchronizing to a reference."
       ::= { salixSystemSync 5 }

  salixSysSyncConfiguredActiveRef OBJECT-TYPE
       SYNTAX     INTEGER { primary(1), secondary(2) }
       MAX-ACCESS read-write
       STATUS     current
       DESCRIPTION
            "The configured active reference line from which the sync module
             should deriving its timing.  This object is relevant if the
             'salixSysSyncTimingMode' is set to 'line' or 'external'.  
             Writing a value that is different from its current value will 
             force the Sync module to switch to using the specified managed
             object as the active reference line as indicated below:

             primary(1)    -  The salixSysSyncPrimaryRef is the active
                              reference line
             secondary(2)  -  The salixSysSyncSecondaryRef is the active
                              reference line"
       ::= { salixSystemSync 6 }

  salixSysSyncAutoRefSwitch OBJECT-TYPE
       SYNTAX     TruthValue
       MAX-ACCESS read-write
       STATUS     current
       DESCRIPTION
            "Indication of automatic reference switching being enabled or
             disabled.

             true(1)  - Auto reference switching is enabled
             false(2) - Auto reference switching is disabled"
       DEFVAL { true }
       ::= { salixSystemSync 7 }

  salixSysSyncFreeRunAlarm OBJECT-TYPE
       SYNTAX  TruthValue
       MAX-ACCESS      read-write
       STATUS     current
       DESCRIPTION
            "Indication of alarm associated with free-run mode being
             enabled or disabled.

             true(1)  - Alarm is enabled
             false(2) - Alarm is disabled"
       DEFVAL { true }
       ::= { salixSystemSync 8 }

  salixSysSyncWorking OBJECT-TYPE
       SYNTAX     PhysicalIndex
       MAX-ACCESS read-write
       STATUS     current
       DESCRIPTION
            "The entPhysicalIndex of the sync module plug-in unit that is
             providing the system synchronizaton signal.  Writing a new value
             to this object, a value not equal to the current value, will:

             - update the salixSysSyncProtect object with the current value
               of the salixSysSyncWorking object and

             - activate the specified sync module to start providing the
               system synchronization signal.

             A value of 0 indicates that there are no operational or not
             installed sync modules in the system.  Writing zero, an invalid
             index, or the current value to this object will have no effect.

             If the working sync module fails, the system will automatically
             switch to the sync module specified in the salixSysSyncProtect
             object."
       ::= { salixSystemSync 9 }

  salixSysSyncProtect OBJECT-TYPE
       SYNTAX     PhysicalIndex
       MAX-ACCESS read-only
       STATUS     current
       DESCRIPTION
            "The entPhysicalIndex of the sync module plug-in unit
             that is protecting or on standby to the working sync module.
             A value of 0 indicates that there is no redundant sync module
             available or provisioned as a protect module."
       ::= { salixSystemSync 10 }

  salixSysSyncPrimaryRefState OBJECT-TYPE
       SYNTAX     INTEGER { unknown(0),
                            valid(1),
                            lossOfSignalError(2),
                            frequencyOffsetError(3)
                          }
       MAX-ACCESS read-only
       STATUS     current
       DESCRIPTION
            "This variable indicates the state of the primary reference
             line termination point to be used as a timing 
             source by the sync module.  This object is relevant if the 
             salixSysSyncTimingMode is set to 'line' and the 
             salixSysSyncPrimaryRef is configured.
             
             unknown(0)           - the state of the line has not been 
                                    determined. 
             valid(1)             - the line is operating within the 
                                    frequency specification.
             lossOfSignalError    - loss of signal was detected from the
                                    line and has failed the health check.
             frequencyOffsetError - frequency errors were detected from
                                    the line and has failed the health check"
                                    
       ::= { salixSystemSync 11 }

  salixSysSyncSecondaryRefState OBJECT-TYPE
       SYNTAX     INTEGER { unknown(0),
                            valid(1),
                            lossOfSignalError(2),
                            frequencyOffsetError(3)
                          }
       MAX-ACCESS read-only
       STATUS     current
       DESCRIPTION
            "This variable indicates the state of the secondary reference
             line termination point to be used as a timing 
             source by the sync module.  This object is relevant if the 
             'salixSysSyncTimingMode' is set to 'line' and the 
             'salixSysSyncPrimaryRef' is configured.
             
             unknown(0)           - the state of the line has not been 
                                    determined. 
             valid(1)             - the line is operating within 
                                    frequency specification.
             lossOfSignalError    - loss of signal was detected from the
                                    line and has failed the health check.
             frequencyOffsetError - frequency errors were detected from
                                    the line and has failed the health check"
                                    
       ::= { salixSystemSync 12 }

  salixSysSyncCurrentActiveRef OBJECT-TYPE
       SYNTAX     INTEGER { primary(1), secondary(2) }
       MAX-ACCESS read-only
       STATUS     current
       DESCRIPTION
            "Indication of the active reference line from which the sync
             module is deriving its timing.  This object is relevant if the
             salixSysSyncTimingMode is set to 'line' or 'external'.  The 
             value of this variable can differ from the 
             'salixSysSyncConfiguredActiveRef' if the sync module determines
             an error condition with the 'salixSysSyncConfiguredActiveRef' and
             has switched to using another line as the active reference.

             primary(1)    -  The salixSysSyncPrimaryRef is the current
                              active reference line
             secondary(2)  -  The salixSysSyncSecondaryRef is the current
                              active reference line"
       ::= { salixSystemSync 13 }

  salixSysSyncForcedState OBJECT-TYPE
       SYNTAX     INTEGER { none(0),
                            revertiveSwitchInhibit(1),
                            autoReferenceSwitchInhbit(2)
                          }
       MAX-ACCESS read-only
       STATUS     current
       DESCRIPTION
            "This variable indicates the state of the sync module with
             regard to switching between the configured active reference, 
             the value of the 'salixSysSyncConfiguredActiveRef' variable, and  
             the alternate active reference.  The alternate active 
             reference is identified by the 'salixSysSyncPrimaryRef' or
             'salixSysSyncSecondaryRef' that is not configured as the
             'salixSysSyncConfiguredActiveRef'.
             
             none(0) - the sync module is in a state where it is free
                       to switch between the configured active reference
                       the alternate active reference.
                                          
             revertiveSwitchInhibit - the state of the sync module after 
                       switching from the 'salixSysSyncConfiguredActiveRef'
                       to the 'salixSysSyncCurrentActiveRef' when the 
                       'salixSysSyncRevertiveSwitch' is configured as 'false'.
                       In this state the sync module will not revert back
                       to using the 'salixSysSyncConfiguredActiveRef' unless
                       the 'salixSysSyncCurrentActiveRef' has failed and the 
                       state of the active reference defined by the 
                       'salixSysSyncConfiguredActiveRef' variable is 'valid'.
                       
             autoReferenceSwitchInhibit - the state of the sync module when
                       the 'salixSysSyncAutoReferenceSwitch' variable is 
                       configured as 'false'. In this state the sync module 
                       will not switch to using the alternate active reference
                       unless the 'salixSysSyncCurrentActiveRef' has failed and
                       the state of the alternate active reference is 'valid'."
       ::= { salixSystemSync 14 }

  -- SALIX System Hybrid Switch Fabric (HSF) Objects
       
  salixSysHsfWorking OBJECT-TYPE
       SYNTAX     PhysicalIndex
       MAX-ACCESS read-write
       STATUS     current
       DESCRIPTION
            "The PhysicalIndex of the Hybrid Switch Fabric (HSF) module
             plug-in unit that is performing switching in the SALIX.
             Writing a new value to this variable will:

             - update the salixHsfProtect object with the current
               value of the salixHsfWorking object and

             - activate the specified HSF module to start performing
               ATM and TDM switching in the system.

               A value of 0 indicates that there is no operational switch
               fabric installed. Writing zero, an invalid index,
               or the current value to this object will have no effect.

               If the working HSF module fails, the system will automatically
               switch to the HSF module specified in the salixHsfProtect object."
       ::= { salixSystemHsf 1 }       
       
  salixSysHsfProtect OBJECT-TYPE
       SYNTAX     PhysicalIndex
       MAX-ACCESS read-only
       STATUS     current
       DESCRIPTION
            "The entPhysicalIndex of the Hybrid Switch Fabric (HSF) module
             plug-in unit that is protecting or on standby to the working
             HSF module, salixHSFWorking.  A value of 0 indicates that there
             are no operational or no additional HSF modules present for
             redundancy."
       ::= { salixSystemHsf 2 }    
       
  -- SALIX System Redundant Shelf Controller (RSC) Objects
       
  salixSysRscWorking OBJECT-TYPE
       SYNTAX     PhysicalIndex
       MAX-ACCESS read-write
       STATUS     current
       DESCRIPTION
            "The PhysicalIndex of the Redundant Shelf Controller (RSC) module
             plug-in unit that is performing shelf controller operations
             in the product (ie. talking with media controller, handling
             SNMP requests).  Writing a new value to this variable will:

             - update the salixSysRscProtect object with the current
               value of the salixSysRscWorking object and

             - activate the specified RSC module to start performing
               shelf controller operations in the system.

               A value of 0 indicates that there is no operational shelf 
               controller installed. Writing zero, an invalid index,
               or the current value to this object will have no effect.

               If the working RSC module fails, the system will automatically
               switch to the RSC module specified in the salixRscProtect object."
       ::= { salixSystemRsc 1 }       
       
  salixSysRscProtect OBJECT-TYPE
       SYNTAX     PhysicalIndex
       MAX-ACCESS read-only
       STATUS     current
       DESCRIPTION
            "The entPhysicalIndex of the Redundant Shelf Controller (RSC) module
             plug-in unit that is protecting or on standby to the working
             RSC module, salixRscWorking.  A value of 0 indicates that there
             are no operational or no additional RSC modules present for
             redundancy."
       ::= { salixSystemRsc 2 }        
       
 -- Notifications
 
salixSysSyncRefLineAlarm NOTIFICATION-TYPE
     OBJECTS   { entPhysicalContainedIn,
                 entPhysicalParentRelPos,
                 entPhysicalClass,
                 ifOperStatus,
                 atmfM4TrapAlarmSeverity }
     STATUS    current
     DESCRIPTION
          "Indicates that the Sync plug-in unit associated with the
           specified physical entity detected an error condition with
           the interface configured as a reference.
           The default alarm severity for this alarm is 'minor'."

     ::= { salixSystemMIBTrapPrefix 1 }

salixSysSyncInvalidRefLineAlarm NOTIFICATION-TYPE
     OBJECTS   { entPhysicalContainedIn,
                 entPhysicalParentRelPos,
                 entPhysicalClass,
                 salixSysSyncPrimaryRef,
                 salixSysSyncSecondaryRef,
                 atmfM4TrapAlarmSeverity }
     STATUS    current
     DESCRIPTION
          "Indicates that the Sync plug-in unit associated with the
           specified physical entity does not have a valid primary
           or secondary reference line for deriving timing.  The
           default alarm severity for this alarm is 'major'."
     ::= { salixSystemMIBTrapPrefix 2 }
     
salixSysSyncClockModeAlarm NOTIFICATION-TYPE
     OBJECTS   { atmfM4PlugInUnitAvailStatus,
                 salixSysSyncClockMode,
                 salixSysSyncWorking,                 
                 atmfM4TrapAlarmSeverity }
     STATUS    current
     DESCRIPTION
          "Indicates that the clock mode of the working or protect
           Sync plug-in unit associated with the specified physical 
           entity, 'atmfM4PlugInUnitAvailStatus', changed to or from
           'normal'.  The default alarm severity for this alarm is 
           'major'."
     ::= { salixSystemMIBTrapPrefix 3 }
  
salixSysSyncClockModeStateChange NOTIFICATION-TYPE
     OBJECTS   { atmfM4PlugInUnitAvailStatus,
                 salixSysSyncClockMode,
                 salixSysSyncWorking }                 
     STATUS    current
     DESCRIPTION
          "Indicates that the clock mode of the working or protect
           Sync plug-in unit associated with the specified physical
           entity, 'atmfM4PlugInUnitAvailStatus', changed."
     ::= { salixSystemMIBTrapPrefix 4 }
     
salixSysFileSystemUnavailable NOTIFICATION-TYPE
     OBJECTS   { atmfM4TrapAlarmSeverity }                 
     STATUS    current
     DESCRIPTION
          "Indicates the System Filesystem is no longer available.  This can indicate
           the loss of connectivity to the NFS server, or loss of the hard disk in systems
           with a physical disk"
     ::= { salixSystemMIBTrapPrefix 5 }
   
-- Conformance Statements

salixSystemGroups      OBJECT IDENTIFIER  ::= { salixSystemMIBCompliance 1 }
salixSystemCompliances OBJECT IDENTIFIER  ::= { salixSystemMIBCompliance 2 }

   salixSystemGroup OBJECT-GROUP
      OBJECTS {
         salixSysLastLogErrorNumber,
         salixSysLastLogErrorMessage,
         salixSysLastLogErrorOid
      }
      STATUS         current
      DESCRIPTION    "Salix Error Objects Group"
      ::= { salixSystemGroups 1}

-- Compliance Statements

salixSystemCompliance MODULE-COMPLIANCE
     STATUS       current
     DESCRIPTION
                  "The basic implementation requirements for the SALIX-ERROR-MIB."
     MODULE       -- This module
     MANDATORY-GROUPS { salixSystemGroup }
     ::= { salixSystemCompliances 1 }

END
