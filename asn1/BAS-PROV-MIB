BAS-PROV-MIB DEFINITIONS ::= BEGIN

IMPORTS
	MODULE-IDENTITY, OBJECT-TYPE,
        IpAddress,
	Integer32						FROM SNMPv2-SMI
	basProvInfo                                                  FROM BAS-MIB;
	
basProvInfoMib MODULE-IDENTITY
	LAST-UPDATED "9901180900Z"
	ORGANIZATION "Broadband Access Systems"
	CONTACT-INFO
		" Tech Support
		  Broadband Access Systems
		  201 Forest Street
		  Marlboro, MA  01752
		  U.S.A.
		  
		  508-485-8200
		  support@basystems.com"
	DESCRIPTION
		"This MIB module defines the Provisioning Mib
		 for a Broadband Access System Chassis."
	::= { basProvInfo 1 }

basProvObjects	OBJECT IDENTIFIER ::= { basProvInfoMib 1 }

basProvServerId OBJECT-TYPE
    SYNTAX      Integer32
    MAX-ACCESS  read-write
    STATUS      current
    DESCRIPTION
        "The Provisioning Server unique Id"
    ::= { basProvObjects 1 }

basProvInfoLdapServerIpAddr OBJECT-TYPE
    SYNTAX      IpAddress
    MAX-ACCESS  read-write
    STATUS      current
    DESCRIPTION
        "The LDAP Server IP Address to access the
	 provisioning server database"
    ::= { basProvObjects 2 }

basProvInfoLdapServerPort OBJECT-TYPE
    SYNTAX      INTEGER(0..65535)
    MAX-ACCESS  read-write
    STATUS      current
    DESCRIPTION
        "The LDAP Server Port to access the
	 provisioning server database"
    ::= { basProvObjects 3 }

basProvInfoLdapServerUserName OBJECT-TYPE
    SYNTAX      OCTET STRING (SIZE(0..255))
    MAX-ACCESS  read-write
    STATUS      current
    DESCRIPTION
        "The LDAP Server username to access the
	 provisioning server database"
    ::= { basProvObjects 4 }

basProvInfoLdapServerPassword OBJECT-TYPE
    SYNTAX      OCTET STRING (SIZE(0..255))
    MAX-ACCESS  read-write
    STATUS      current
    DESCRIPTION
        "The LDAP Server Password to access the
	 provisioning server database"
    ::= { basProvObjects 5 }

--
-- ----------------------------------------------------------------------
--
-- End
--
-- ----------------------------------------------------------------------
--

END
