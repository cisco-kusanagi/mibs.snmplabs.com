BAS-ACCESS-MIB DEFINITIONS ::= BEGIN

IMPORTS
    MODULE-IDENTITY, OBJECT-TYPE, IpAddress, Integer32  FROM SNMPv2-SMI
    DisplayString, RowStatus                            FROM SNMPv2-TC
    basAccessControl, BasChassisId, BasSlotId, 
    BasInterfaceId, BasLogicalPortId                    FROM BAS-MIB;

basAccessMIB MODULE-IDENTITY
    LAST-UPDATED "9812080000Z"
    ORGANIZATION "Broadband Access Systems, Inc."
    CONTACT-INFO
        " Tech Support
          Broadband Access Systems, Inc.
          201 Forest Street
          Marlborough, MA 01752
          USA

          508-485-8200
          support@basystems.com"
    DESCRIPTION
        "This MIB module defines the configuration MIB objects
         for Broadband Access Systems, Inc. Network Management
         access control."
    ::= { basAccessControl 1 }

--*****************************************************************************
--* basAccessTable
--*****************************************************************************

basAccessTable OBJECT-TYPE
    SYNTAX      SEQUENCE OF BasAccessEntry
    MAX-ACCESS  not-accessible
    STATUS      current
    DESCRIPTION
        ""
    ::= { basAccessMIB 1 }

basAccessEntry OBJECT-TYPE
    SYNTAX      BasAccessEntry
    MAX-ACCESS  not-accessible
    STATUS      current
    DESCRIPTION
      ""
    INDEX       { basAccessChassis, basAccessSlot,
                  basAccessInterface, basAccessLPort,
                  basAccessIndex }
    ::= {basAccessTable 1 }

BasAccessEntry ::= 
    SEQUENCE {
        basAccessChassis            BasChassisId,
        basAccessSlot               BasSlotId,
        basAccessInterface          BasInterfaceId,
        basAccessLPort              BasLogicalPortId,
        basAccessIndex              Integer32,
        basAccessCommName           OCTET STRING,
        basAccessIpAddress          IpAddress,
        basAccessProfile            INTEGER,
        basAccessStatus             RowStatus
    }

basAccessChassis OBJECT-TYPE
    SYNTAX      BasChassisId
    MAX-ACCESS  not-accessible
    STATUS      current
    DESCRIPTION
        "The BAS Chassis ID of this card."
    ::= { basAccessEntry 1 }

basAccessSlot OBJECT-TYPE
    SYNTAX      BasSlotId
    MAX-ACCESS  not-accessible
    STATUS      current
    DESCRIPTION
        "The BAS Slot ID of this card."
    ::= { basAccessEntry 2 }

basAccessInterface OBJECT-TYPE
    SYNTAX      BasInterfaceId
    MAX-ACCESS  not-accessible
    STATUS      current
    DESCRIPTION
        "The BAS interface ID of this card."
    ::= { basAccessEntry 3 }

basAccessLPort OBJECT-TYPE
    SYNTAX      BasLogicalPortId
    MAX-ACCESS  not-accessible
    STATUS      current
    DESCRIPTION
        "The BAS logical port ID of this card."
    ::= { basAccessEntry 4 }

basAccessIndex OBJECT-TYPE
    SYNTAX      Integer32
    MAX-ACCESS  not-accessible
    STATUS      current
    DESCRIPTION
        ""
    ::= { basAccessEntry 5 }

basAccessCommName OBJECT-TYPE
    SYNTAX      OCTET STRING (SIZE(0..255))
    MAX-ACCESS  read-create
    STATUS      current
    DESCRIPTION
        "An assigned SNMP community name. The SNMP entity may have more
    than one community names with either read/write or read-only priviledge."
    ::= { basAccessEntry 6 }

basAccessIpAddress OBJECT-TYPE
    SYNTAX      IpAddress
    MAX-ACCESS  read-create
    STATUS      current
    DESCRIPTION
        "The Ip address of the management application that is
    authorized to communicate with the SNMP entity. An Ip address of
    0.0.0.0 allows any management application with a valid community
    and/or profile to connect to the SNMP entity. "
    ::= { basAccessEntry 7 }

basAccessProfile OBJECT-TYPE
    SYNTAX      INTEGER(1..2)
    MAX-ACCESS  read-create
    STATUS      current
    DESCRIPTION
        "The Profile associated with the community name. Each request
    PDU will have a profile in addition to the community name. The
    profile is specified as:
    '1' read-only
    '2' read/write"
    ::= { basAccessEntry 8 }

basAccessStatus OBJECT-TYPE
    SYNTAX      RowStatus
    MAX-ACCESS  read-create
    STATUS      current
    DESCRIPTION
        "This mib object allows row creation to take place in the
    profile table."
    ::= { basAccessEntry 9 }

END
