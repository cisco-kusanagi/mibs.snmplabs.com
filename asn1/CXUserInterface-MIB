CXUserInterface-MIB DEFINITIONS ::= BEGIN

IMPORTS 
	OBJECT-TYPE 		FROM RFC-1212
	DisplayString		FROM RFC1213-MIB
	cxUserInterface		FROM CXProduct-SMI;


uiPassword OBJECT-TYPE
	SYNTAX	DisplayString (SIZE (6..16))
	ACCESS	write-only
	STATUS	mandatory
	DESCRIPTION
"Determines the password the system requires to allow users to gain access 
to the console port. You must enter this password when you are using a TTY 
terminal or a PC running a TTY terminal emulation program to configure the 
console port.

Range of Values: from 6 to 16 alphanumeric characters. You can use any 
combination of letters and numbers, however you cannot use blank spaces. 
Use a dash or underscore as a delimiter.

Default Value: Supervisor

Configuration Changed: operative"

	DEFVAL { "Supervisor" }
	::= { cxUserInterface 1 }


uiTimeOut OBJECT-TYPE
	SYNTAX	INTEGER (10..65535)
	ACCESS	read-write
	STATUS	mandatory
	DESCRIPTION
"Determines the length of time, in seconds, the console port can remain 
inactive before the system logs out the user. Once the timer expires, the 
user needs to log in again to regain access to the console port.

Range of Values: a maximum of five digits between 10 and 65535.

Default Value: 600

Configuration Changed: operative"

	DEFVAL  { 300 }
	::= { cxUserInterface 2 }


END
