WSD-MIB DEFINITIONS ::= BEGIN

-- Title:      WSD specific MIB
--             This Private MIB supports WSD products
-- Version:    7.30
-- Date:       2/11/2001
-- By:         WMA (WSD MIB Authority)
-- E-mail:     US:            support@radware.com
--             International: support_int@radware.com
--
IMPORTS
       NetworkAddress,
       IpAddress,
       Counter,
       Gauge,
       enterprises
              FROM RFC1155-SMI
      OBJECT-TYPE
              FROM RFC-1212
       DisplayString,
       PhysAddress,
       ipAddrEntry
              FROM RFC1213-MIB
       TRAP-TYPE
                    FROM RFC-1215
	rsServerDispatcher,
        rsNWSD,
        rndErrorDesc,
        rndErrorSeverity,
        rsWSDThresholdWarnings
                    FROM RADWARE-MIB;

    TruthValue ::= INTEGER {
         true (1),
         false (2)
        }
    RowStatus ::= INTEGER {
        active(1),
        notInService(2),
        notReady(3),
        createAndGo(4),
        createAndWait(5),
        destroy(6)
        }
    NetNumber ::=  OCTET STRING (SIZE(4))

-- Some MIB compilers require that the following 7 lines which define the path
-- to RND MIB are commented out:

-- mib            OBJECT IDENTIFIER ::= { mgmt 1  }
-- directory      OBJECT IDENTIFIER ::= { internet 1  }
-- experimental   OBJECT IDENTIFIER ::= { internet 3  }
-- private        OBJECT IDENTIFIER ::= { internet 4  }
-- enterprises    OBJECT IDENTIFIER ::= { private 1  }

rsWSDApplicationServersTable OBJECT-TYPE
    SYNTAX SEQUENCE OF RsWSDApplicationServerEntry
    ACCESS not-accessible
    STATUS mandatory
    DESCRIPTION
      "Table containing the list of application servers to which the
      clients requested are dispatched."
    ::=  {rsServerDispatcher 11}

rsWSDApplicationServerEntry OBJECT-TYPE
    SYNTAX RsWSDApplicationServerEntry
    ACCESS not-accessible
    STATUS  mandatory
    DESCRIPTION
       " The row definition for this table."
   INDEX { rsWSDAddr,
           rsWSDServerAddr }
    ::=  {rsWSDApplicationServersTable 1}

RsWSDApplicationServerEntry ::= SEQUENCE {
  rsWSDAddr                           IpAddress,
  rsWSDServerAddr                     IpAddress,
  rsWSDServerName                     DisplayString,
  rsWSDServerOperStatus               INTEGER,
  rsWSDServerWeight                   INTEGER,
  rsWSDServerAttachedUsersNumber      INTEGER,
  rsWSDServerPeakLoad                 INTEGER,
  rsWSDServerFramesRate               INTEGER,
  rsWSDServerFramesLoad               Counter,
  rsWSDServerStatus                   INTEGER,
  rsWSDServerOperMode                 INTEGER,
  rsWSDMultiplexedServerPort          INTEGER,
  rsWSDServerType                     INTEGER,
  rsWSDServerConnectionLimit          INTEGER,
  rsWSDServerAdminStatus              INTEGER,
  rsWSDServerBandWidth                INTEGER,
  rsWSDServerCckID                    INTEGER,
  rsWSDServerRedirectTo               DisplayString,
  rsWSDServerClientNATStatus          INTEGER
  }

rsWSDAddr OBJECT-TYPE
    SYNTAX  IpAddress
    ACCESS  read-only
    STATUS  mandatory
    DESCRIPTION
     "WSD Virtual IP address"
 ::=  {rsWSDApplicationServerEntry 1}

rsWSDServerAddr  OBJECT-TYPE
    SYNTAX  IpAddress
    ACCESS  read-only
    STATUS  mandatory
    DESCRIPTION
     "Application  IP address"
 ::=  {rsWSDApplicationServerEntry 2 }

rsWSDServerName  OBJECT-TYPE
    SYNTAX DisplayString (SIZE(1..30))
    ACCESS  read-write
    STATUS  mandatory
    DESCRIPTION
      "The name assigned by the user to the server."
 ::=  {rsWSDApplicationServerEntry 3}

rsWSDServerOperStatus OBJECT-TYPE
    SYNTAX INTEGER {
      active(1),
      notInService(2),
      noNewSessions(3)
    }
    ACCESS  read-only
    STATUS  mandatory
    DESCRIPTION
      "Operational status of application on  server.
       active        - server is active
       notInService  - server is or will become inactive. Existing sessions
                       will be redirected to other servers.
       noNewSessions - server will receive no new sessions. Existing sessions
                       are allowed to complete."
 ::=  {rsWSDApplicationServerEntry 4 }

rsWSDServerWeight OBJECT-TYPE
    SYNTAX  INTEGER  (1..10)
    ACCESS  read-write
    STATUS  mandatory
    DESCRIPTION
      "A numerical weight assigned by the user in order to impose some
       priority mechanism on the server dispatchers considerations of which
       server to choose for attaching a client ."
 ::=  {rsWSDApplicationServerEntry 5}

rsWSDServerAttachedUsersNumber OBJECT-TYPE
    SYNTAX  INTEGER
    ACCESS  read-only
    STATUS  mandatory
    DESCRIPTION
      "Number of currently active users attached to this server."
    ::=  {rsWSDApplicationServerEntry 6 }

rsWSDServerPeakLoad OBJECT-TYPE
    SYNTAX  INTEGER
    ACCESS  read-only
    STATUS  mandatory
    DESCRIPTION
      "Maximal number of frames per second dispatched to server
       since last reset."
    ::=  {rsWSDApplicationServerEntry 7}

rsWSDServerFramesRate OBJECT-TYPE
    SYNTAX  INTEGER
    ACCESS  read-only
    STATUS  mandatory
    DESCRIPTION
      "Number of frames per second dispatched to server."
    ::=  {rsWSDApplicationServerEntry 8}

rsWSDServerFramesLoad OBJECT-TYPE
    SYNTAX  Counter
    ACCESS  read-only
    STATUS  mandatory
    DESCRIPTION
      "Number of frames per second dispatched to server."
    ::=  {rsWSDApplicationServerEntry 9}

rsWSDServerStatus OBJECT-TYPE
    SYNTAX INTEGER {
        active(1),
        notInService(2),
        notReady(3),
        createAndGo(4),
        createAndWait(5),
        destroy(6) }
    ACCESS  read-write
    STATUS  mandatory
    DESCRIPTION
      "Administative status of appliaction on  server."
    ::=  {rsWSDApplicationServerEntry 10}

rsWSDServerOperMode OBJECT-TYPE
    SYNTAX INTEGER { regular(1), backup(2)}
    ACCESS  read-write
    STATUS  mandatory
    DESCRIPTION
      "This variable indicate the status of the server,
      the WSD will not send any messages to a backup server
      unless all other server are down  status.
      In case of more then one backup server, the WSD will decide  to which
      backup server to send the massages acordinf to rsWSDWeight."
    ::=  { rsWSDApplicationServerEntry 11}

rsWSDMultiplexedServerPort OBJECT-TYPE
    SYNTAX INTEGER (0..65535)
    ACCESS  read-write
    STATUS  mandatory
    DESCRIPTION
       "The port on which this server listens to the multiplexed port
        of its farm. Port 0 - no multiplexing on this server"
--  DEFVAL {0}
    ::= { rsWSDApplicationServerEntry 12 }

rsWSDServerType OBJECT-TYPE
    SYNTAX INTEGER { 
      regular(1), 
      distributed(2), 
      remote(3), 
      loopback(4),
      localFarm(5)
    }
    ACCESS  read-write
    STATUS  mandatory
    DESCRIPTION
       "This variable indicates the server's type. Regular type servers
        have no other connection to the network except this WSD. Distributed
        type servers are remote WSDs. A remote type server is a server cpnnected
        to the network at a different entry point."
--  DEFVAL {regular}
    ::= { rsWSDApplicationServerEntry 13 }

rsWSDServerConnectionLimit OBJECT-TYPE
    SYNTAX INTEGER
    ACCESS  read-write
    STATUS  mandatory
    DESCRIPTION
      "The maximal number of client sessions which can be opened on this sever."
-- DEFVAL {0}
    ::= { rsWSDApplicationServerEntry 14 }

rsWSDServerAdminStatus OBJECT-TYPE
    SYNTAX INTEGER {
      enable(1),
      disable(2),
      shutdown(3)
          }
    ACCESS  read-write
    STATUS  mandatory
    DESCRIPTION
      "Administrative status of application on server.
       enable -   activates the server.
                  The rsWSDServerOperStatus will change to active.
       disable -  stops the server.
                  The rsWSDServerOperStatus will change to notInService.
       shutdown - gracefully shuts down the server.
                  The rsWSDServerOperStatus will change to noNewSessions."

 ::=  {rsWSDApplicationServerEntry 15 }

rsWSDServerBandWidth OBJECT-TYPE
    SYNTAX  INTEGER
    ACCESS  read-write
    STATUS  mandatory
    DESCRIPTION
      "Band width for server."
--  DEFVAL {0x7fffffff}
    ::=  {rsWSDApplicationServerEntry 16}

rsWSDServerCckID OBJECT-TYPE
    SYNTAX  INTEGER
    ACCESS  read-write
    STATUS  mandatory
    DESCRIPTION
      "Connectivity check module identifier."
    ::=  {rsWSDApplicationServerEntry 17}

rsWSDServerRedirectTo OBJECT-TYPE
    SYNTAX  DisplayString (SIZE(0..80))
    ACCESS  read-write
    STATUS  mandatory
    DESCRIPTION
      "String to be used by HTTP redirection."
    ::=  {rsWSDApplicationServerEntry 18}

rsWSDServerClientNATStatus OBJECT-TYPE
    SYNTAX INTEGER {
      enable(1),
      disable(2)
    }
    ACCESS  read-write
    STATUS  mandatory
    DESCRIPTION
      "enable or disable the NAT client feature for this server
       Default value is disable"
    DEFVAL { 2 }
 ::=  {rsWSDApplicationServerEntry 19 }


rsWSDdummy1 OBJECT-TYPE
    SYNTAX INTEGER
    ACCESS  read-only
    STATUS  mandatory
    DESCRIPTION
       " Dummy variable for stopping getnext."
    ::=  {rsWSDApplicationServersTable 2}

rsWSDFarmTable OBJECT-TYPE
   SYNTAX SEQUENCE OF RsWSDFarmEntry
   ACCESS not-accessible
   STATUS mandatory
   DESCRIPTION
          "In this table the WSD  version 2 saves the general parameters per
           server farme IP Addr."
   ::= {rsServerDispatcher 13}

rsWSDFarmEntry OBJECT-TYPE
    SYNTAX RsWSDFarmEntry
    ACCESS not-accessible
    STATUS  mandatory
    DESCRIPTION
       " The row definition for this table."
   INDEX  {rsWSDFarmAddress}
   ::= {rsWSDFarmTable 1}


RsWSDFarmEntry  ::= SEQUENCE {
  rsWSDFarmAddress                       IpAddress,
  rsWSDFarmName                          DisplayString,
  rsWSDAdminStatus                       INTEGER,
  rsWSDClientsLifeTime                   INTEGER,
  rsWSDDispatchMethod                    INTEGER,
  rsWSDCheckConnectivityStatus           INTEGER,
  rsWSDCheckConnectivityMethod           INTEGER,
  rsWSDCheckConnectivityInterval         INTEGER,
  rsWSDCheckConnectivityRetries          INTEGER,
  rsWSDClientsConnectDenials             Counter,
  rsWSDFarmStatus                        INTEGER,
  rsWSDMultiplexedFarmPort               INTEGER,
  rsWSDFarmDistThreshold                 INTEGER,
  rsWSDFarmTrafficThreshold              INTEGER,
  rsWSDFarmRedirectionMode               INTEGER,
  rsNsdFarmRegister                      INTEGER,
  rsWSDFarmMode                          INTEGER,
  rsWSDExtendedConnectivityCheckInterval INTEGER,
  rsWSDConnectivityCheckUrl              DisplayString,
  rsWSDFarmClientMode                    INTEGER,
  rsWSDDNSRedir2ndMode                   INTEGER,
  rsWSDFarmHttpRedirectionMode           INTEGER,
  rsWSDFarmOperStatus                    INTEGER,
  rsWSDFarmBandWidth                     INTEGER,
  rsWSDFarmCookieKey                     DisplayString,
   rsWSDConnCheckUserName            DisplayString,
  rsWSDConnCheckPassword              DisplayString
 }

rsWSDFarmAddress OBJECT-TYPE
    SYNTAX IpAddress
    ACCESS  read-only
    STATUS  mandatory
    DESCRIPTION
      "The IP Address of the WEB farm."
    ::= {rsWSDFarmEntry 1}

rsWSDFarmName OBJECT-TYPE
    SYNTAX DisplayString (SIZE(1..50))
    ACCESS  read-write
    STATUS  mandatory
    DESCRIPTION
      "The name assigned by the user to this WEB farm."
    ::= {rsWSDFarmEntry 2}

rsWSDAdminStatus  OBJECT-TYPE
    SYNTAX INTEGER {
      enable(1),
      disable(2)
   }
    ACCESS  read-write
    STATUS  mandatory
    DESCRIPTION
      "Enable/Disable server dispatcher."
    ::=  {rsWSDFarmEntry 3}

rsWSDClientsLifeTime OBJECT-TYPE
    SYNTAX  INTEGER
    ACCESS  read-write
    STATUS  mandatory
    DESCRIPTION
      "Maximal period of time in seconds a non-active client is kept
      in the clients table."
--  DEFVAL  { 60 }
    ::=  {rsWSDFarmEntry 4}

  rsWSDDispatchMethod OBJECT-TYPE
    SYNTAX INTEGER {
      cyclic(1),
      leastTraffic(2),
      leastUsersNumber(3),
      leastTrafficLocal(4),
      leastUsersNumberLocal(5),
      nt-1(6),
      nt-2(7),
      private-1(8),
      private-2(9),
      weightedCyclic(10),
      static(11)
   }
    ACCESS  read-write
    STATUS  mandatory
    DESCRIPTION
      "Type of dispatching required."
    ::=  {rsWSDFarmEntry 5}

  rsWSDCheckConnectivityStatus OBJECT-TYPE
    SYNTAX INTEGER {
		ping(1),
		disable(2),
            http(3),
		tcp(4),
		udp(5)
   }
    ACCESS  read-write
    STATUS  mandatory
    DESCRIPTION
     	 "Connectivity check method."
--  DEFVAL  { 1 }
    ::=  {rsWSDFarmEntry 6}

  rsWSDCheckConnectivityMethod OBJECT-TYPE
    SYNTAX INTEGER
    ACCESS  read-write
    STATUS  mandatory
    DESCRIPTION
     	 "Application port for TCP or UDP connectivity check."
--  DEFVAL  { 80 }
    ::=  {rsWSDFarmEntry 7}

  rsWSDCheckConnectivityInterval OBJECT-TYPE
    SYNTAX  INTEGER  (1..3600)
    ACCESS  read-write
    STATUS  mandatory
    DESCRIPTION
      "Polling interval in seconds for servers polling."
--  DEFVAL  { 10 }
    ::=  {rsWSDFarmEntry 8}

  rsWSDCheckConnectivityRetries OBJECT-TYPE
    SYNTAX  INTEGER  (1..20)
    ACCESS  read-write
    STATUS  mandatory
    DESCRIPTION
      "This variable indicate the Minimal number of unsuccessful polling
       attempts before considering a server disconnected."
--  DEFVAL  { 5 }
    ::=  {rsWSDFarmEntry 9}

  rsWSDClientsConnectDenials OBJECT-TYPE
    SYNTAX Counter
    ACCESS  read-only
    STATUS  mandatory
    DESCRIPTION
      "This variable indicate the Number of connection requests from clients
       that were denied by the the server dispatcher."
    ::=  {rsWSDFarmEntry 10}

  rsWSDFarmStatus OBJECT-TYPE
      SYNTAX INTEGER {
        active(1),
        notInService(2),
        notReady(3),
        createAndGo(4),
        createAndWait(5),
        destroy(6) }
    ACCESS  read-write
    STATUS  mandatory
    DESCRIPTION
      "This variable indicate the Administative status of this entry.
       Use for delete an entry in this table."
  ::=  {rsWSDFarmEntry 11}

  rsWSDMultiplexedFarmPort OBJECT-TYPE
    SYNTAX INTEGER (0..65535)
    ACCESS  read-write
    STATUS  mandatory
    DESCRIPTION
       "The port on this farm's virtual IP for which port
        multiplexing is enabled. Port 0 - multiplexing is disabled"
--  DEFVAL {0}
    ::= { rsWSDFarmEntry 12 }

rsWSDFarmDistThreshold OBJECT-TYPE
    SYNTAX INTEGER
    ACCESS  read-write
    STATUS  mandatory
    DESCRIPTION
       "This variable indicates the treshold above which the WSD starts
       distributing traffic to distributed WSDs. The significance of this
       parameter varies according to the load balancing algorithm chosen."
--  DEFVAL {1000}
    ::= { rsWSDFarmEntry 13 }

rsWSDFarmTrafficThreshold  OBJECT-TYPE
    SYNTAX INTEGER
    ACCESS  read-write
    STATUS  mandatory
    DESCRIPTION
       "This variable indicates the treshold above which the WSD signals
       to all the distributed WSDs not to send traffic to it."
--  DEFVAL {5000}
    ::= { rsWSDFarmEntry 14 }

rsWSDFarmRedirectionMode  OBJECT-TYPE
    SYNTAX INTEGER { httpRedirection(1),
                     triangleRedirection(2),
                     noRedirection(3),
                     httpAndTriangleRedirection(4),
                     dnsRedirection(5),
                     dnsReevaluationRedirection(6)}
    ACCESS  read-write
    STATUS  mandatory
    DESCRIPTION
       "This variable indicates if redirection is enabled and if enable
        which redirection mode is established (http, triangle or dns redirection).
        If redirection is disabled (i.e. -noRedirection), HTTP traffic is
        handled as all other traffic."
--      DEFVAL {enable}
    ::= { rsWSDFarmEntry 15 }


rsNsdFarmRegister  OBJECT-TYPE
    SYNTAX INTEGER {
        enable(1),
        disable(2)
    }
    ACCESS  read-write
    STATUS  mandatory
    DESCRIPTION
        "Enable/Disable farm's registration in the WINS server."
--  DEFVAL  {1}
    ::=  {rsWSDFarmEntry 16}

rsWSDFarmMode OBJECT-TYPE
    SYNTAX INTEGER {
           regular(1),
           backup(2)
    }
    ACCESS  read-write
    STATUS  mandatory
    DESCRIPTION
        "This variable indicate the mode of this farm weather
         its my farm or farm of my main WSD which this
         WSD make redundancy"
--  DEFVAL { 1 }
    ::= { rsWSDFarmEntry 17 }

rsWSDExtendedConnectivityCheckInterval OBJECT-TYPE
    SYNTAX  INTEGER
    ACCESS  read-write
    STATUS  mandatory
    DESCRIPTION
        "The frequency at which an extended http check will be sent if
         rsWSDCheckConnectivityMethod is equal to 2. After this number of
         normal http checks a extended http check will be performed."
--  DEFVAL  { 10 }
    ::=  {rsWSDFarmEntry 18}

rsWSDConnectivityCheckUrl OBJECT-TYPE
    SYNTAX DisplayString (SIZE(0..80))
    ACCESS  read-write
    STATUS  mandatory
    DESCRIPTION
        "The absolute path of the web page to be requested in the extended
         connectivity check. Example: ~smith/home.html    "
--  DEFVAL  ( "" )
    ::= {rsWSDFarmEntry 19}

rsWSDFarmClientMode  OBJECT-TYPE
    SYNTAX INTEGER {
      regular(1),
      entryPerSession(2),
      serverPerSession(3),
      removeEntryAtSessionEnd(4),
      removeEntryAtSessionEndForServerPerSession(5)
   }
    ACCESS  read-write
    STATUS  mandatory
    DESCRIPTION
      "Client mode for this farm. How a single client's sessions are handled in the client table.
       Regular: all sessions to the same server, differentiated by destination port.
       EntryPerSession: all sessions to the same server, differentiated by both ports.
       ServerPerSession: new server selected for every session.
       RemoveEntry: extends EntryPerSession by removing terminated TCP sessions.
       RemoveServerPerSession: extends ServerPerSession to remove terminated TCP sessions."
    DEFVAL  { 1 }
    ::=  {rsWSDFarmEntry 20}

rsWSDDNSRedir2ndMode  OBJECT-TYPE
    SYNTAX INTEGER {
      httpAndTriangle(1),
      http(2),
      triangulation(3),
      dnsOnly(4)
   }
    ACCESS  read-write
    STATUS  mandatory
    DESCRIPTION
      "Secondary choice to be used with DNS redirection, in case that a client tries to connect to the
        virtual IP although it can not receive local service."
    DEFVAL  { 1 }
    ::=  {rsWSDFarmEntry 21}

rsWSDFarmHttpRedirectionMode OBJECT-TYPE
    SYNTAX INTEGER {
       ipMode (1),
       nameMode (2)
     }
    ACCESS  read-write
    STATUS  mandatory
    DESCRIPTION
      "Http redirection mode : IP address redirection mode or URL address redirection mode."
--  DEFVAL { 1 }
    ::= {rsWSDFarmEntry 22}

rsWSDFarmOperStatus OBJECT-TYPE
    SYNTAX INTEGER {
        active(1),
        notInService(2)
      }
    ACCESS  read-only
    STATUS  mandatory
    DESCRIPTION
      "Farm status. Active - farm is active. NotInService - service is not
       available."
    ::= {rsWSDFarmEntry 23}

rsWSDFarmBandWidth OBJECT-TYPE
    SYNTAX INTEGER
    ACCESS  read-write
    STATUS  mandatory
    DESCRIPTION
      "Band width for farm."
--  DEFVAL   {0x7fffffff}
    ::= {rsWSDFarmEntry 24}


rsWSDFarmCookieKey OBJECT-TYPE
   SYNTAX DisplayString (SIZE(0..63))
   ACCESS  read-write
   STATUS  mandatory
   DESCRIPTION
     "String representing the cookie key to look for. A value
      also indicates that the farm does cookie-based load
      balancing."
   ::= {rsWSDFarmEntry 25}

rsWSDConnCheckUserName OBJECT-TYPE
   SYNTAX DisplayString (SIZE(0..20))
   ACCESS  read-write
   STATUS  mandatory
   DESCRIPTION
     "Username used for extended connectivity checks."
   ::= {rsWSDFarmEntry 26}

rsWSDConnCheckPassword OBJECT-TYPE
   SYNTAX DisplayString (SIZE(0..20))
   ACCESS  read-write
   STATUS  mandatory
   DESCRIPTION
     "Password used for extended connectivity checks."
   ::= {rsWSDFarmEntry 27}


rsWSDdummy3 OBJECT-TYPE
    SYNTAX INTEGER
    ACCESS  read-only
    STATUS  mandatory
    DESCRIPTION
       " Dummy variable for stopping getnext."
    ::=  {rsWSDFarmTable 2}

rsWSDClientsTable OBJECT-TYPE
    SYNTAX SEQUENCE OF RsWSDClientEntry
    ACCESS not-accessible
    STATUS  mandatory
    DESCRIPTION
      "Table containing the list of clients currently attached to a server."
    ::=  {rsServerDispatcher 14}

rsWSDClientEntry OBJECT-TYPE
    SYNTAX RsWSDClientEntry
    ACCESS not-accessible
    STATUS  mandatory
    DESCRIPTION
       " The row definition for this table."
   INDEX { rsWSDFarmAddr, rsWSDClientAddr }
    ::=  {rsWSDClientsTable 1}

RsWSDClientEntry ::= SEQUENCE {
  rsWSDFarmAddr                  IpAddress,
  rsWSDClientAddr                IpAddress,
  rsWSDAttachedServerAddr        IpAddress,
  rsWSDClientLastActivityTime    INTEGER,
  rsWSDClientAttachmentTime      INTEGER,
  rsWSDClientType                INTEGER,
  rsWSDClientStatus              RowStatus
  }

rsWSDFarmAddr OBJECT-TYPE
    SYNTAX  IpAddress
    ACCESS  read-only
    STATUS  mandatory
    DESCRIPTION
     "IP Address of the WEB farm the client trough which the client connected."
    ::=  {rsWSDClientEntry 1}

rsWSDClientAddr  OBJECT-TYPE
    SYNTAX  IpAddress
    ACCESS  read-only
    STATUS  mandatory
    DESCRIPTION
      "Client IP Address."
    ::=  {rsWSDClientEntry 2}

rsWSDAttachedServerAddr OBJECT-TYPE
    SYNTAX  IpAddress
    ACCESS  read-write
    STATUS  mandatory
    DESCRIPTION
      "IP Address of server currently serving this client."
    ::=  {rsWSDClientEntry 3 }

rsWSDClientLastActivityTime  OBJECT-TYPE
    SYNTAX  INTEGER
    ACCESS  read-only
    STATUS  mandatory
    DESCRIPTION
      "Indicates when the last frame from the client was dispatched.
       Measured in seconds since device re-initialization."
    ::=  {rsWSDClientEntry 4}

rsWSDClientAttachmentTime OBJECT-TYPE
    SYNTAX  INTEGER
    ACCESS  read-only
    STATUS  mandatory
    DESCRIPTION
      "Indicates when the client was attached.
       Measured in seconds since device re-initialization."
    ::=  {rsWSDClientEntry 5}

rsWSDClientType OBJECT-TYPE
    SYNTAX INTEGER {
                    dynamic(1),
                    static(2),
             		    nat(3),
                    clientnat(4)
                    }
    ACCESS  read-write
    STATUS  mandatory
    DESCRIPTION
              "This variable indicates the administrative type of this entry."
    ::=  { rsWSDClientEntry 6}

rsWSDClientStatus OBJECT-TYPE
    SYNTAX  RowStatus
    ACCESS  read-write
    STATUS  mandatory
    DESCRIPTION
       "This variable indicates the administrative status of this entry.
        Used to delete an entry of this table."
    ::=  { rsWSDClientEntry 7}

rsWSDdummy4 OBJECT-TYPE
    SYNTAX INTEGER
    ACCESS  read-only
    STATUS  mandatory
    DESCRIPTION
       " Dummy variable for stopping getnext."
    ::=  {rsWSDClientsTable 2}

rsWSDLoadReportTable OBJECT-TYPE
   SYNTAX SEQUENCE OF RsWSDLoadReportEntry
   ACCESS not-accessible
   STATUS mandatory
   DESCRIPTION
      ""
   ::= {rsServerDispatcher 17}

rsWSDLoadReportEntry  OBJECT-TYPE
   SYNTAX RsWSDLoadReportEntry
   ACCESS not-accessible
   STATUS mandatory
   DESCRIPTION
      "The row definition for this table."
   INDEX {rsWSDReportFarmAddress, rsWSDReportDstFarmAddress, rsWSDReportLclSuperFarmAddr}
   ::= {rsWSDLoadReportTable  1 }

RsWSDLoadReportEntry ::= SEQUENCE {
        rsWSDReportFarmAddress      IpAddress,
        rsWSDReportDstFarmAddress   IpAddress,
        rsWSDReportLclSuperFarmAddr IpAddress,
        rsWSDReportDstIpAddress     IpAddress,
        rsWSDReportMapFarmAddress   IpAddress,
        rsWSDReportStatus           RowStatus,
        rsWSDReportRdnDstIpAddr     IpAddress,
        rsWSDReportDstSuperFarmAddr IpAddress
   }

rsWSDReportFarmAddress  OBJECT-TYPE
   SYNTAX IpAddress
   ACCESS read-only
   STATUS mandatory
   DESCRIPTION
      "The farm IP address."
   ::=  {rsWSDLoadReportEntry 1}

rsWSDReportDstFarmAddress OBJECT-TYPE
   SYNTAX IpAddress
   ACCESS read-only
   STATUS mandatory
   DESCRIPTION
      "The farm IP address in the remote system which corresponding
       rsWSDReportFarmAddress."
   ::=  {rsWSDLoadReportEntry 2}

rsWSDReportLclSuperFarmAddr OBJECT-TYPE
   SYNTAX IpAddress
   ACCESS read-write
   STATUS mandatory
   DESCRIPTION
      "The Superfarm IP address in the local system"
-- DEFVAL   { 0.0.0.0 }
   ::=  {rsWSDLoadReportEntry 3}

rsWSDReportDstIpAddress OBJECT-TYPE
   SYNTAX IpAddress
   ACCESS read-write
   STATUS mandatory
   DESCRIPTION
      "The IP address of the remote system which should receive the load
       report."
   ::=  {rsWSDLoadReportEntry 4}

rsWSDReportMapFarmAddress OBJECT-TYPE
   SYNTAX IpAddress
   ACCESS read-write
   STATUS mandatory
   DESCRIPTION
      "The virtual address to which the request should be mapped when a
       distributed unit redirects traffic using the triangulation method."
--     DEFVAL   { 0.0.0.0 }
   ::=  {rsWSDLoadReportEntry 5}

rsWSDReportStatus OBJECT-TYPE
   SYNTAX  RowStatus
   ACCESS read-write
   STATUS mandatory
   DESCRIPTION
      ""
   ::=  {rsWSDLoadReportEntry 6}

rsWSDReportRdnDstIpAddr OBJECT-TYPE
   SYNTAX IpAddress
   ACCESS read-write
   STATUS mandatory
   DESCRIPTION
      "The IP address of the redundant remote system which should receive the
      load report."
--     DEFVAL   { 0.0.0.0 }
   ::=  {rsWSDLoadReportEntry 7}

rsWSDReportDstSuperFarmAddr OBJECT-TYPE
   SYNTAX IpAddress
   ACCESS read-write
   STATUS mandatory
   DESCRIPTION
      "The Superfarm IP address in the remote system"
-- DEFVAL   { 0.0.0.0 }
   ::=  {rsWSDLoadReportEntry 8}

rsWSDdummy6 OBJECT-TYPE
    SYNTAX INTEGER
    ACCESS  read-only
    STATUS  mandatory
    DESCRIPTION
       " Dummy variable for stopping getnext."
    ::=  {rsWSDLoadReportTable 2}

rsWSDFarmMappingTable OBJECT-TYPE
   SYNTAX SEQUENCE OF RsWSDFarmMappingEntry
   ACCESS not-accessible
   STATUS mandatory
   DESCRIPTION
      ""
   ::= {rsServerDispatcher 18}

rsWSDFarmMappingEntry  OBJECT-TYPE
   SYNTAX RsWSDFarmMappingEntry
   ACCESS not-accessible
   STATUS mandatory
   DESCRIPTION
      "The row definition for this table."
   INDEX {rsWSDMappingAddress}
   ::= {rsWSDFarmMappingTable  1 }

RsWSDFarmMappingEntry ::= SEQUENCE {
        rsWSDMappingAddress     IpAddress,
        rsWSDMappingFarmAddress IpAddress,
        rsWSDOriginalAddress    IpAddress,
        rsWSDMappingAdminStatus INTEGER,
        rsWSDMappingStatus      RowStatus
   }

rsWSDMappingAddress  OBJECT-TYPE
   SYNTAX IpAddress
   ACCESS read-only
   STATUS mandatory
   DESCRIPTION
      "The sub-virtual address of the farm. A distributed WSD directs the clients
       to this address."
   ::=  {rsWSDFarmMappingEntry 1}

rsWSDMappingFarmAddress OBJECT-TYPE
   SYNTAX IpAddress
   ACCESS read-write
   STATUS mandatory
   DESCRIPTION
      "The local virtual address of the farm. A couple of sub virtual addresses
       can belong to the same farm address. The local servers are defined per farm
       address."
   ::=  {rsWSDFarmMappingEntry 2}

rsWSDOriginalAddress OBJECT-TYPE
   SYNTAX IpAddress
   ACCESS read-write
   STATUS mandatory
   DESCRIPTION
      "The original IP address. This address replaces the server IP address when
       responding to the client. This IP address is the virtual IP address which the
       customer approached."
   ::=  {rsWSDFarmMappingEntry 3}

rsWSDMappingAdminStatus OBJECT-TYPE
   SYNTAX INTEGER {enable(1), disable(2)}
   ACCESS read-write
   STATUS mandatory
   DESCRIPTION
      "Indicates/controls the sub virtual address mapping enabling."
   ::=  {rsWSDFarmMappingEntry 4}

rsWSDMappingStatus OBJECT-TYPE
   SYNTAX RowStatus
-- SYNTAX INTEGER
   ACCESS read-write
   STATUS mandatory
   DESCRIPTION
      "Row control."
   ::=  {rsWSDFarmMappingEntry 5}

rsWSDdummy7 OBJECT-TYPE
    SYNTAX INTEGER
    ACCESS  read-only
    STATUS  mandatory
    DESCRIPTION
       " Dummy variable for stopping getnext."
    ::=  {rsWSDFarmMappingTable 2}

rsWSDLoadReportInterval OBJECT-TYPE
    SYNTAX INTEGER
    ACCESS  read-write
    STATUS  mandatory
    DESCRIPTION
        "The interval in seconds between two load reports."
--     DEFVAL   { 10 }
    ::=  {rsServerDispatcher 24}

rsWSDLoadReportTimeout OBJECT-TYPE
    SYNTAX INTEGER
    ACCESS  read-write
    STATUS  mandatory
    DESCRIPTION
        "The timeout in seconds between two load report messages."
--     DEFVAL   { 25 }
    ::=  {rsServerDispatcher 25}

rsWSDPortFarmTable OBJECT-TYPE
   SYNTAX SEQUENCE OF RsWSDPortFarmEntry
   ACCESS not-accessible
   STATUS mandatory
   DESCRIPTION
       "A table for managing the farm decision according to the incoming port."
   ::= {rsServerDispatcher 30}

rsWSDPortFarmEntry OBJECT-TYPE
   SYNTAX RsWSDPortFarmEntry
   ACCESS not-accessible
   STATUS  mandatory
   DESCRIPTION
       " The row definition for this table."
   INDEX  {rsWSDPortMainAddress, rsWSDPortNumber}
   ::= {rsWSDPortFarmTable 1}

RsWSDPortFarmEntry  ::= SEQUENCE {
      rsWSDPortMainAddress  IpAddress,
      rsWSDPortNumber       INTEGER,
      rsWSDPortFarmAddress  IpAddress,
      rsWSDPortFarmStatus   RowStatus,
      rsWSDPortFarmHeader   DisplayString
  }

rsWSDPortMainAddress OBJECT-TYPE
   SYNTAX IpAddress
   ACCESS  read-only
   STATUS  mandatory
   DESCRIPTION
       "The Main IP address given by clients."
   ::= {rsWSDPortFarmEntry 1}

rsWSDPortNumber OBJECT-TYPE
   SYNTAX INTEGER
   ACCESS  read-only
   STATUS  mandatory
   DESCRIPTION
       "The port number which defines the virtual farm."
   ::= {rsWSDPortFarmEntry 2}

rsWSDPortFarmAddress OBJECT-TYPE
   SYNTAX IpAddress
   ACCESS  read-write
   STATUS  mandatory
   DESCRIPTION
       "The IP Address to use for the port."
   ::= {rsWSDPortFarmEntry 3}

rsWSDPortFarmStatus OBJECT-TYPE
   SYNTAX  RowStatus
   ACCESS  read-write
   STATUS  mandatory
   DESCRIPTION
       "The  status of this entry."
   ::= {rsWSDPortFarmEntry 4}

rsWSDPortFarmHeader OBJECT-TYPE
   SYNTAX  DisplayString (SIZE(0..62))
   ACCESS  read-write
   STATUS  mandatory
   DESCRIPTION
       "HTTP Header field for token parsing."
   ::= {rsWSDPortFarmEntry 5}

rsWSDdummy10 OBJECT-TYPE
    SYNTAX INTEGER
    ACCESS  read-only
    STATUS  mandatory
    DESCRIPTION
       " Dummy variable for stopping getnext."
    ::=  {rsWSDPortFarmTable 2}

rsWSDProximity  OBJECT IDENTIFIER ::= { rsServerDispatcher 32 }

rsWSDStaticProximityTable OBJECT-TYPE
   SYNTAX SEQUENCE OF RsWSDStaticProximityEntry
   ACCESS not-accessible
   STATUS mandatory
   DESCRIPTION
          "In this table the WSD saves the static proximity ranges per server farm IP Address"
   ::= {rsWSDProximity 1}


rsWSDStaticProximityEntry OBJECT-TYPE
    SYNTAX RsWSDStaticProximityEntry
    ACCESS not-accessible
    STATUS  mandatory
    DESCRIPTION
       " The row definition for this table."
   INDEX  {rsWSDStaticProximityFarmAddress, rsWSDStaticProximityRangeFrom }
   ::= {rsWSDStaticProximityTable 1}


RsWSDStaticProximityEntry  ::= SEQUENCE {
  rsWSDStaticProximityFarmAddress               IpAddress,
  rsWSDStaticProximityRangeFrom                 IpAddress,
  rsWSDStaticProximityRangeTo                   IpAddress,
  rsWSDStaticProximityStatus                    INTEGER,
  rsWSDStaticProximityServer1                   IpAddress,
  rsWSDStaticProximityServer2                   IpAddress,
  rsWSDStaticProximityServer3                   IpAddress
  }

rsWSDStaticProximityFarmAddress OBJECT-TYPE
    SYNTAX IpAddress
    ACCESS  read-only
    STATUS  mandatory
    DESCRIPTION
      "The IP Address of the WEB farm."
    ::= {rsWSDStaticProximityEntry 1}

rsWSDStaticProximityRangeFrom OBJECT-TYPE
    SYNTAX IpAddress
    ACCESS  read-only
    STATUS  mandatory
    DESCRIPTION
      "The IP Address of the low boundary of the interval."
    ::= {rsWSDStaticProximityEntry 2}

rsWSDStaticProximityRangeTo OBJECT-TYPE
    SYNTAX IpAddress
    ACCESS  read-write
    STATUS  mandatory
    DESCRIPTION
      "The IP Address of the high boundary of the interval."
    ::= {rsWSDStaticProximityEntry 3}

rsWSDStaticProximityStatus OBJECT-TYPE
      SYNTAX INTEGER {
        active(1),
        notInService(2),
        notReady(3),
        createAndGo(4),
        createAndWait(5),
        destroy(6) }
    ACCESS  read-write
    STATUS  mandatory
    DESCRIPTION
      "This variable indicate the Administative status of this entry.
       Use for delete an entry in this table."
  ::= {rsWSDStaticProximityEntry 4}

rsWSDStaticProximityServer1 OBJECT-TYPE
    SYNTAX IpAddress
    ACCESS  read-write
    STATUS  mandatory
    DESCRIPTION
"The first priority server that this range of clients will be redirected to"
    ::= {rsWSDStaticProximityEntry 5}

rsWSDStaticProximityServer2 OBJECT-TYPE
    SYNTAX IpAddress
    ACCESS  read-write
    STATUS  mandatory
    DESCRIPTION
"The second priority server that this range of clients will be redirected to"
       ::= {rsWSDStaticProximityEntry 6}

rsWSDStaticProximityServer3 OBJECT-TYPE
    SYNTAX IpAddress
    ACCESS  read-write
    STATUS  mandatory
    DESCRIPTION
" The third priority server that this range of clients will be redirected to "
    ::= {rsWSDStaticProximityEntry 7}

rsWSDProximityOperationMode  OBJECT-TYPE
   SYNTAX INTEGER {
        noProximity(1),
        staticProximity(2),
	fullProximity(3)
   }
   ACCESS  read-write
   STATUS  mandatory
   DESCRIPTION
       "Allow proximity operation, and choose between operating only static proximity or dynamic proximity as well "
-- DEFVAL { 1 }
   ::=  {rsWSDProximity 2}

rsWSDProximityMainDNS OBJECT-TYPE
SYNTAX IpAddress
    ACCESS  read-write
    STATUS  mandatory
    DESCRIPTION
        "The IP Address of the main DNS to be ignored in the proximity operation"
    ::= { rsWSDProximity 3}

rsWSDProximityBackupDNS OBJECT-TYPE
SYNTAX IpAddress
    ACCESS  read-write
    STATUS  mandatory
    DESCRIPTION
        "The IP Address of the backup DNS to be ignored in the proximity operation"
    ::= { rsWSDProximity 4}

rsWSDProximityAgingPeriod OBJECT-TYPE
    SYNTAX INTEGER
    ACCESS  read-write
    STATUS  mandatory
    DESCRIPTION
        "The time in hours after which an old dynamic entry is invalid."
--     DEFVAL   { 48 }
    ::=  { rsWSDProximity 5}

rsWSDProximityClientMode  OBJECT-TYPE
   SYNTAX INTEGER {
        enable(1),
        disable(2)
   }
   ACCESS  read-write
   STATUS  mandatory
   DESCRIPTION
       "Enable or disable the proximity operation of the distributed WSD"
-- DEFVAL { 2 }
   ::=  {rsWSDProximity 6}

rsWSDProximityRetries  OBJECT-TYPE
   SYNTAX INTEGER (1..5)
   ACCESS  read-write
   STATUS  mandatory
   DESCRIPTION
       "The number of tries for checking the client distance"
-- DEFVAL { 2 }
   ::=  {rsWSDProximity 7}

rsWSDProximityTimeout  OBJECT-TYPE
   SYNTAX INTEGER (1..10)
   ACCESS  read-write
   STATUS  mandatory
   DESCRIPTION
       "The timeout between proximity checks"
-- DEFVAL { 5 }
   ::=  {rsWSDProximity 8}

rsWSDProximityTuning OBJECT IDENTIFIER ::= { rsWSDProximity 9}

rsWSDMaxDynEntries OBJECT-TYPE
    SYNTAX INTEGER
    ACCESS  read-only
    STATUS  mandatory
    DESCRIPTION
      "Maximal number of entries in the dynamic proximity table."
    ::=  { rsWSDProximityTuning 1 }

rsWSDMaxDynEntriesAfterReset OBJECT-TYPE
    SYNTAX INTEGER
    ACCESS  read-write
    STATUS  mandatory
    DESCRIPTION
      "Future maximal number of entries in the dynamic proximity table."
    ::=  { rsWSDProximityTuning 2 }


rsWSDPrxBasicCheckMethod  OBJECT-TYPE
   SYNTAX INTEGER {
        enable(1),
        disable(2)
   }
   ACCESS  read-write
   STATUS  mandatory
   DESCRIPTION
       "Enable or disable basic proximity check (ICMP)"
-- DEFVAL { 1 }
   ::=  {rsWSDProximity 10}

rsWSDPrxAdvancedCheckMethod  OBJECT-TYPE
   SYNTAX INTEGER {
        enable(1),
        disable(2)
   }
   ACCESS  read-write
   STATUS  mandatory
   DESCRIPTION
       "Enable or disable advanced proximity check (UDP)"
-- DEFVAL { 1 }
   ::=  {rsWSDProximity 11}

rsWSDPrxApplIndpndCheckMethod  OBJECT-TYPE
   SYNTAX INTEGER {
        enable(1),
        disable(2)
   }
   ACCESS  read-write
   STATUS  mandatory
   DESCRIPTION
       "Enable or disable application independent proximity check (TCP to port 80)"
-- DEFVAL { 1 }
   ::=  {rsWSDProximity 12}

rsWSDPrxApplAwareCheckMethod  OBJECT-TYPE
   SYNTAX INTEGER {
        enable(1),
        disable(2)
   }
   ACCESS  read-write
   STATUS  mandatory
   DESCRIPTION
       "Enable or disable application aware proximity check (TCP)"
-- DEFVAL { 1 }
   ::=  {rsWSDProximity 13}

rsNWSDProximity  OBJECT IDENTIFIER ::= { rsNWSD 1 }

rsWSDProximityHopsWeight  OBJECT-TYPE
   SYNTAX INTEGER (1..100)
   ACCESS  read-write
   STATUS  mandatory
   DESCRIPTION
       "The weight given to the clients hops distance in the dispatching decision"
-- DEFVAL { 50 }
   ::=  {rsNWSDProximity 1}

rsWSDProximityLatencyWeight  OBJECT-TYPE
   SYNTAX INTEGER (1..100)
   ACCESS  read-write
   STATUS  mandatory
   DESCRIPTION
       "The weight given to the clients latency in the dispatching decision"
-- DEFVAL { 50 }
   ::=  {rsNWSDProximity 2}

rsWSDProximityLoadWeight  OBJECT-TYPE
   SYNTAX INTEGER (1..100)
   ACCESS  read-write
   STATUS  mandatory
   DESCRIPTION
       "The weight given to the site load in the dispatching decision"
-- DEFVAL { 50 }
   ::=  {rsNWSDProximity 3}

rsWSDProximityMirrorPercentage  OBJECT-TYPE
   SYNTAX INTEGER (1..100)
   ACCESS  read-write
   STATUS  mandatory
   DESCRIPTION
       "The percent of the proximity table to back up"
-- DEFVAL { 100 }
   ::=  {rsNWSDProximity 4}

rsWSDProximityMirrorPollingTime  OBJECT-TYPE
   SYNTAX INTEGER
   ACCESS  read-write
   STATUS  mandatory
   DESCRIPTION
       "The polling time of the proximity mirror messages"
-- DEFVAL { 10 }
   ::=  {rsNWSDProximity 5}

rsWSDDNSttl  OBJECT-TYPE
   SYNTAX INTEGER
   ACCESS  read-write
   STATUS  mandatory
   DESCRIPTION
        "TTL for DNS replies."
-- DEFVAL { 0 }
   ::=  {rsNWSD 2}

rsWSDURLSuperFarmTable OBJECT-TYPE
   SYNTAX SEQUENCE OF RsWSDURLSuperFarmEntry
   ACCESS not-accessible
   STATUS mandatory
   DESCRIPTION
       "A table for managing the farm decision according to the incoming URL."
   ::= {rsNWSD 3}

rsWSDURLSuperFarmEntry OBJECT-TYPE
   SYNTAX RsWSDURLSuperFarmEntry
   ACCESS not-accessible
   STATUS mandatory
   DESCRIPTION
       " The row definition for this table."
   INDEX  {rsWSDURL}
   ::= {rsWSDURLSuperFarmTable 1}

RsWSDURLSuperFarmEntry  ::= SEQUENCE {
  rsWSDURLFarmAddress IpAddress,
  rsWSDURL            DisplayString,
  rsWSDURLStatus      RowStatus
}

rsWSDURLFarmAddress OBJECT-TYPE
    	SYNTAX IpAddress
    	ACCESS read-write
   	STATUS mandatory
   	DESCRIPTION
     	 "IP address of the farm to use with the URL."
	::=  {rsWSDURLSuperFarmEntry 1}

rsWSDURL  OBJECT-TYPE
        SYNTAX DisplayString (SIZE (1..63))
    	ACCESS read-write
   	STATUS mandatory
   	DESCRIPTION
     	 "The URL representing the farm."
	::=  {rsWSDURLSuperFarmEntry 2}

rsWSDURLStatus OBJECT-TYPE
    	SYNTAX RowStatus
    	ACCESS read-write
   	STATUS mandatory
   	DESCRIPTION
     	 "Row status for the URL."
	::=  {rsWSDURLSuperFarmEntry 3}


rsWSDMainVirtualDNS OBJECT-TYPE
    	SYNTAX IpAddress
    	ACCESS read-write
   	STATUS mandatory
   	DESCRIPTION
     	 "Main DNS virtual IP address."
	::=  {rsNWSD 4}

rsWSDBackupVirtualDNS OBJECT-TYPE
    	SYNTAX IpAddress
    	ACCESS read-write
   	STATUS mandatory
   	DESCRIPTION
     	 "Backup WSD virtual DNS IP address."
	::=  {rsNWSD 5}

rsWSDProximityMirrorProtocolMode OBJECT-TYPE
    SYNTAX  INTEGER {
      enable(1),
      disable(2)
    }
    ACCESS  read-write
    STATUS  mandatory
    DESCRIPTION
      "Enable/Disable of the mirror protocol mode."
        ::=  {rsNWSD 7}

rsWSDTwoDNSAnswers OBJECT-TYPE
 SYNTAX  INTEGER {
   enable(1),
   disable(2)
 }
 ACCESS  read-write
 STATUS  mandatory
 DESCRIPTION
   "Enable/Disable two answers to DNS queries."
     ::=  {rsNWSD 10}

rsWSDStatisticsDstIpAddr OBJECT-TYPE
    SYNTAX  IpAddress
    ACCESS  read-write
    STATUS  mandatory
    DESCRIPTION
      "Statistics Destination Ip Address"
        ::=  {rsNWSD 11}

rsWSDStatisticsReportingMode OBJECT-TYPE
    SYNTAX  INTEGER {
      full(1),
      disable(2),
      general(3),
      health(4)
    }
    ACCESS  read-write
    STATUS  mandatory
    DESCRIPTION
      "Statistics Reporting Mode: reporting enable / disable, full statistics
      report or partial"
        ::=  {rsNWSD 12}

rsWSDGeneralStatisticsPollingTime OBJECT-TYPE
    SYNTAX  INTEGER
    ACCESS  read-write
    STATUS  mandatory
    DESCRIPTION
      "Reporting polling time for general statistics"
        ::=  {rsNWSD 13}

rsWSDHealthStatisticsPollingTime OBJECT-TYPE
    SYNTAX  INTEGER
    ACCESS  read-write
    STATUS  mandatory
    DESCRIPTION
      "Reporting polling time for health statistics"
        ::=  {rsNWSD 14}

rsWSDAcceptableHTTPCodesTable OBJECT-TYPE
   SYNTAX SEQUENCE OF RsWSDAcceptableHTTPCodeEntry
   ACCESS not-accessible
   STATUS mandatory
   DESCRIPTION
       "A table for managing the acceptable HTTP codes received by extended
        connectivity check."
   ::= {rsNWSD 15}

rsWSDAcceptableHTTPCodeEntry OBJECT-TYPE
   SYNTAX RsWSDAcceptableHTTPCodeEntry
   ACCESS not-accessible
   STATUS mandatory
   DESCRIPTION
       " The row definition for this table."
   INDEX  {rsWSDAcceptableHTTPCodeFarm, rsWSDAcceptableHTTPCode}
   ::= {rsWSDAcceptableHTTPCodesTable 1}

RsWSDAcceptableHTTPCodeEntry ::= SEQUENCE {
  rsWSDAcceptableHTTPCodeFarm     IpAddress,
  rsWSDAcceptableHTTPCode         INTEGER,
  rsWSDAcceptableHTTPCodeStatus   RowStatus
}

rsWSDAcceptableHTTPCodeFarm OBJECT-TYPE
  SYNTAX IpAddress
  ACCESS read-write
  STATUS mandatory
  DESCRIPTION
     "IP address of the farm where the code is defined."
  ::=  {rsWSDAcceptableHTTPCodeEntry 1}

rsWSDAcceptableHTTPCode  OBJECT-TYPE
  SYNTAX INTEGER
  ACCESS read-write
  STATUS mandatory
  DESCRIPTION
     "The HTTP code acceptable in that farm."
  ::=  {rsWSDAcceptableHTTPCodeEntry 2}

rsWSDAcceptableHTTPCodeStatus OBJECT-TYPE
  SYNTAX RowStatus
  ACCESS read-write
  STATUS mandatory
  DESCRIPTION
    "Row status for the code."
  ::=  {rsWSDAcceptableHTTPCodeEntry 3}

rsWSDTotalNumberOfClients OBJECT-TYPE
  SYNTAX OCTET STRING (SIZE(8))
  ACCESS read-only
  STATUS mandatory
  DESCRIPTION
    "Total number of clients per device."
   ::= {rsNWSD 16}

rsWSDCurrentNumberOfClients OBJECT-TYPE
  SYNTAX INTEGER
  ACCESS read-only
  STATUS mandatory
  DESCRIPTION
    "Current number of clients per device."
   ::= {rsNWSD 17}

rsWSDFramesLoadInBytes OBJECT-TYPE
  SYNTAX OCTET STRING (SIZE(8))
  ACCESS read-only
  STATUS mandatory
  DESCRIPTION
    "Frames load in bytes per device."
   ::= {rsNWSD 18}

rsWSDRedundancyFailed OBJECT-TYPE
  SYNTAX INTEGER
  ACCESS read-only
  STATUS mandatory
  DESCRIPTION
    "Redundancy failed flag."
   ::= {rsNWSD 19}

rsWSDRedundancyTakeOver OBJECT-TYPE
  SYNTAX INTEGER
  ACCESS read-only
  STATUS mandatory
  DESCRIPTION
    "Redundancy take over flag."
   ::= {rsNWSD 20}

rsWSDDynamicProximityTableFilledUp OBJECT-TYPE
  SYNTAX INTEGER
  ACCESS read-only
  STATUS mandatory
  DESCRIPTION
    "Proximity table filled up flag."
   ::= {rsNWSD 21}

rsWSDClientTableFilledUp OBJECT-TYPE
  SYNTAX INTEGER
  ACCESS read-only
  STATUS mandatory
  DESCRIPTION
    "Client table filled up flag."
   ::= {rsNWSD 22}

rsWSDSSFTable OBJECT-TYPE
   SYNTAX SEQUENCE OF RsWSDSSFEntry
   ACCESS not-accessible
   STATUS mandatory
   DESCRIPTION
          "The table that contains general parameters for secondary servers."
   ::= {rsNWSD 23}

rsWSDSSFEntry OBJECT-TYPE
    SYNTAX RsWSDSSFEntry
    ACCESS not-accessible
    STATUS  mandatory
    DESCRIPTION
       " The row definition for the SSF table."
   INDEX  {rsWSDSSFName}
   ::= {rsWSDSSFTable 1}

RsWSDSSFEntry  ::= SEQUENCE {
  rsWSDSSFName                 DisplayString,
  rsWSDSSFStatus               INTEGER,
  rsWSDSSFCheckMethod          INTEGER,
  rsWSDSSFCheckInterval        INTEGER,
  rsWSDSSFCheckRetries         INTEGER,
  rsWSDSSFCheckPort            INTEGER,
  rsWSDSSFCheckCommunity       DisplayString,
  rsWSDSSFMode                 INTEGER,
  rsWSDSSFOperStatus           INTEGER,
  rsWSDSSFId                   INTEGER
}

rsWSDSSFName OBJECT-TYPE
    SYNTAX DisplayString (SIZE(1..20))
    ACCESS  read-write
    STATUS  mandatory
    DESCRIPTION
      "The name assigned by the user to this SSF."
    ::= {rsWSDSSFEntry 1}

rsWSDSSFStatus OBJECT-TYPE
      SYNTAX INTEGER {
        active(1),
        notInService(2),
        notReady(3),
        createAndGo(4),
        createAndWait(5),
        destroy(6) }
    ACCESS  read-write
    STATUS  mandatory
    DESCRIPTION
      "Administrative status of this entry. "
  ::=  {rsWSDSSFEntry 2}

rsWSDSSFCheckMethod OBJECT-TYPE
    SYNTAX INTEGER {
         disable(1),
         ping(2),
         tcp(3),
         oAS(4),
         oDB(5)
      }
    ACCESS  read-write
    STATUS  mandatory
    DESCRIPTION
     	 "Connectivity check method for the SSF."
    DEFVAL  { 2 }
    ::=  {rsWSDSSFEntry 3}

rsWSDSSFCheckInterval OBJECT-TYPE
    SYNTAX  INTEGER  (1..3600)
    ACCESS  read-write
    STATUS  mandatory
    DESCRIPTION
      "Polling interval in seconds for the secondary servers."
   DEFVAL  { 10 }
    ::=  {rsWSDSSFEntry 4}

rsWSDSSFCheckRetries OBJECT-TYPE
    SYNTAX  INTEGER  (1..20)
    ACCESS  read-write
    STATUS  mandatory
    DESCRIPTION
      "Minimum number of unsuccessful polling attempts before a server is
deemed
      disconnected."
    DEFVAL  { 5 }
    ::=  {rsWSDSSFEntry 5}

rsWSDSSFCheckPort OBJECT-TYPE
    SYNTAX INTEGER
    ACCESS  read-write
    STATUS  mandatory
    DESCRIPTION
     	 "Application port for TCP secondary server connectivity check."
    DEFVAL  { 80 }
    ::=  {rsWSDSSFEntry 6}

rsWSDSSFCheckCommunity OBJECT-TYPE
    SYNTAX DisplayString (SIZE(1..20))
    ACCESS  read-write
    STATUS  mandatory
    DESCRIPTION
        "The SNMP community to use in special secondary server polling."
    DEFVAL  { "public" }
    ::= {rsWSDSSFEntry 7}

rsWSDSSFMode  OBJECT-TYPE
    SYNTAX INTEGER {
      inclusive(1),
      singleFailure(2)
    }
    ACCESS  read-write
    STATUS  mandatory
    DESCRIPTION
      "Operation mode for SSF in case of failure. Either fail farm/server
        when all secondary servers
       fail (inclusive mode), or fail them when just one secondary server
        fails (single failure)."
    DEFVAL { 1 }
    ::=  {rsWSDSSFEntry 8}

rsWSDSSFOperStatus OBJECT-TYPE
   SYNTAX INTEGER {
       active(1),
       notInService(2)
     }
   ACCESS read-only
   STATUS  mandatory
    DESCRIPTION
      "Secondary server farm status. Active - farm is active.
       NotInService - one or more servers are not responding."
  ::=  { rsWSDSSFEntry 9}

rsWSDSSFId OBJECT-TYPE
   SYNTAX INTEGER
   ACCESS read-write
   STATUS  mandatory
    DESCRIPTION
      "The Id is used an alternate key to the SSF table"
  ::=  { rsWSDSSFEntry 10}

rsWSDSecondaryServerTable OBJECT-TYPE
   SYNTAX SEQUENCE OF RsWSDSecondaryServerEntry
   ACCESS not-accessible
   STATUS mandatory
   DESCRIPTION
          "The table that contains specific parameters for secondary servers."
   ::= {rsNWSD 24}

rsWSDSecondaryServerEntry OBJECT-TYPE
    SYNTAX RsWSDSecondaryServerEntry
    ACCESS not-accessible
    STATUS  mandatory
    DESCRIPTION
       "The row definition for the secondary server table."
   INDEX  {rsWSDSecondaryServerSSFName, rsWSDSecondaryServerAddr}
   ::= {rsWSDSecondaryServerTable 1}

RsWSDSecondaryServerEntry ::= SEQUENCE {
  rsWSDSecondaryServerSSFName           DisplayString,
  rsWSDSecondaryServerAddr              IpAddress,
  rsWSDSecondaryServerStatus            INTEGER,
  rsWSDSecondaryServerOperStatus        INTEGER,
  rsWSDSecondaryServerId                INTEGER
}

rsWSDSecondaryServerSSFName OBJECT-TYPE
    SYNTAX DisplayString (SIZE(1..20))
    ACCESS  read-write
    STATUS  mandatory
    DESCRIPTION
      "The name of the SSF of which the secondary server is a member."
    ::= {rsWSDSecondaryServerEntry 1}

rsWSDSecondaryServerAddr  OBJECT-TYPE
    SYNTAX  IpAddress
    ACCESS  read-write
    STATUS  mandatory
    DESCRIPTION
     "Secondary Server IP address."
 ::=  {rsWSDSecondaryServerEntry 2}

rsWSDSecondaryServerStatus OBJECT-TYPE
      SYNTAX INTEGER {
        active(1),
        notInService(2),
        notReady(3),
        createAndGo(4),
        createAndWait(5),
        destroy(6) }
    ACCESS  read-write
    STATUS  mandatory
    DESCRIPTION
      "Administrative status of this entry. "
  ::=  {rsWSDSecondaryServerEntry 3}

rsWSDSecondaryServerOperStatus OBJECT-TYPE
      SYNTAX INTEGER {
        active(1),
        notInService(2)
      }
    ACCESS  read-only
    STATUS  mandatory
    DESCRIPTION
      "Secondary server status. Active - server is active. NotInService -
server is not responding."
  ::=  {rsWSDSecondaryServerEntry 4}

rsWSDSecondaryServerId OBJECT-TYPE
    SYNTAX INTEGER
    ACCESS  read-write
    STATUS  mandatory
    DESCRIPTION
      "The Id serves as an alternate key to the SSF table"
  ::=  {rsWSDSecondaryServerEntry 5}

rsWSDSSFFarmTable OBJECT-TYPE
   SYNTAX SEQUENCE OF RsWSDSSFFarmEntry
   ACCESS not-accessible
   STATUS mandatory
   DESCRIPTION
          "The table that is used to configure farms in SSF."
   ::= {rsNWSD 25}

rsWSDSSFFarmEntry OBJECT-TYPE
    SYNTAX RsWSDSSFFarmEntry
    ACCESS not-accessible
    STATUS  mandatory
    DESCRIPTION
       "The row definition for the farm-SSF table."
   INDEX  {rsWSDSSFFarmSSFName, rsWSDSSFFarmAddr}
   ::= {rsWSDSSFFarmTable 1}

RsWSDSSFFarmEntry ::= SEQUENCE {
  rsWSDSSFFarmSSFName                       DisplayString,
  rsWSDSSFFarmAddr                          IpAddress,
  rsWSDSSFFarmStatus                        INTEGER,
  rsWSDSSFFarmId                            INTEGER
}

rsWSDSSFFarmSSFName OBJECT-TYPE
    SYNTAX DisplayString (SIZE(1..20))
    ACCESS  read-write
    STATUS  mandatory
    DESCRIPTION
      "The name of the SSF to which the farm is attached."
    ::= {rsWSDSSFFarmEntry 1}

rsWSDSSFFarmAddr  OBJECT-TYPE
    SYNTAX  IpAddress
    ACCESS  read-write
    STATUS  mandatory
    DESCRIPTION
     "Attached farm IP address."
 ::=  {rsWSDSSFFarmEntry 2}

rsWSDSSFFarmStatus OBJECT-TYPE
      SYNTAX INTEGER {
        active(1),
        notInService(2),
        notReady(3),
        createAndGo(4),
        createAndWait(5),
        destroy(6) }
    ACCESS  read-write
    STATUS  mandatory
    DESCRIPTION
      "Administrative status of this entry. "
  ::=  {rsWSDSSFFarmEntry 3}

rsWSDSSFFarmId OBJECT-TYPE
    SYNTAX INTEGER
    ACCESS  read-write
    STATUS  mandatory
    DESCRIPTION
      "The Id is an alternate key to the SSF table"
  ::=  {rsWSDSSFFarmEntry 4}

rsWSDClientGroupingMask OBJECT-TYPE
   SYNTAX IpAddress
   ACCESS read-write
   STATUS mandatory
   DESCRIPTION
           "Client IP address mask."
   ::=  {rsNWSD 26}

rsWSDSSFServerTable OBJECT-TYPE
   SYNTAX SEQUENCE OF RsWSDSSFServerEntry
   ACCESS not-accessible
   STATUS mandatory
   DESCRIPTION
          "The table that is used to configure servers in SSF."
   ::= {rsNWSD 27}

rsWSDSSFServerEntry OBJECT-TYPE
    SYNTAX RsWSDSSFServerEntry
    ACCESS not-accessible
    STATUS  mandatory
    DESCRIPTION
       "The row definition for the server-SSF table."
   INDEX  {rsWSDSSFServerSSFName,
                 rsWSDSSFServerFarmAddr,
                 rsWSDSSFServerSrvrAddr}
   ::= {rsWSDSSFServerTable 1}

RsWSDSSFServerEntry ::= SEQUENCE {
  rsWSDSSFServerSSFName                DisplayString,
  rsWSDSSFServerFarmAddr               IpAddress,
  rsWSDSSFServerSrvrAddr               IpAddress,
  rsWSDSSFServerStatus                 INTEGER,
  rsWSDSSFServerId                     INTEGER
}

rsWSDSSFServerSSFName OBJECT-TYPE
    SYNTAX DisplayString (SIZE(1..20))
    ACCESS  read-write
    STATUS  mandatory
    DESCRIPTION
      "The name of the SSF to which the server is attached."
    ::= {rsWSDSSFServerEntry 1}

rsWSDSSFServerFarmAddr  OBJECT-TYPE
    SYNTAX  IpAddress
    ACCESS  read-write
    STATUS  mandatory
    DESCRIPTION
     "Attached server's farm IP address."
 ::=  {rsWSDSSFServerEntry 2}

rsWSDSSFServerSrvrAddr  OBJECT-TYPE
    SYNTAX  IpAddress
    ACCESS  read-write
    STATUS  mandatory
    DESCRIPTION
     "Attached server's IP address."
 ::=  {rsWSDSSFServerEntry 3}

rsWSDSSFServerStatus OBJECT-TYPE
      SYNTAX INTEGER {
        active(1),
        notInService(2),
        notReady(3),
        createAndGo(4),
        createAndWait(5),
        destroy(6) }
    ACCESS  read-write
    STATUS  mandatory
    DESCRIPTION
      "Administrative status of this entry. "
  ::=  {rsWSDSSFServerEntry 4}

rsWSDSSFServerId OBJECT-TYPE
    SYNTAX INTEGER
    ACCESS  read-write
    STATUS  mandatory
    DESCRIPTION
      "The Id is an alternate key to the SSF table"
  ::=  {rsWSDSSFServerEntry 5}

rsWSDHTTPContentCheckTable OBJECT-TYPE
   SYNTAX SEQUENCE OF RsWSDHTTPContentCheckEntry
   ACCESS not-accessible
   STATUS mandatory
   DESCRIPTION
       "A table for managing the strings that the WSD looks for in HTTP responses (to extended
        connectivity checks)."
   ::= {rsNWSD 28}

rsWSDHTTPContentCheckEntry OBJECT-TYPE
   SYNTAX RsWSDHTTPContentCheckEntry
   ACCESS not-accessible
   STATUS mandatory
   DESCRIPTION
       " The row definition for this table."
   INDEX  {rsWSDHTTPContentCheckFarm}
   ::= {rsWSDHTTPContentCheckTable 1}

RsWSDHTTPContentCheckEntry ::= SEQUENCE {
  rsWSDHTTPContentCheckFarm    IpAddress,
  rsWSDHTTPContentCheckString   DisplayString,
  rsWSDHTTPContentCheckMode    INTEGER,
  rsWSDHTTPContentCheckStatus     RowStatus
}

rsWSDHTTPContentCheckFarm OBJECT-TYPE
  SYNTAX IpAddress
  ACCESS read-write
  STATUS mandatory
  DESCRIPTION
     "IP address of the farm where the extended check is made."
  ::=  {rsWSDHTTPContentCheckEntry 1}

rsWSDHTTPContentCheckString OBJECT-TYPE
    SYNTAX DisplayString (SIZE(1..64))
    ACCESS  read-write
    STATUS  mandatory
    DESCRIPTION
      "The string to look for in the HTTP response."
    ::= {rsWSDHTTPContentCheckEntry 2}

rsWSDHTTPContentCheckMode OBJECT-TYPE
      SYNTAX INTEGER {
        stringExists(1),
        stringIsAbsent(2)}
    ACCESS  read-write
    STATUS  mandatory
    DESCRIPTION
      "Type of checks - should the check be that the string exists or that it is absent."
    DEFVAL  { 1 }
  ::=  {rsWSDHTTPContentCheckEntry 3}

rsWSDHTTPContentCheckStatus OBJECT-TYPE
  SYNTAX RowStatus
  ACCESS read-write
  STATUS mandatory
  DESCRIPTION
    "Row status for the string."
  ::=  {rsWSDHTTPContentCheckEntry 4}

rsNWSDStats  OBJECT IDENTIFIER ::= { rsNWSD 29 }

rsWSDTotalDNSReqCounter OBJECT-TYPE
    SYNTAX  OCTET STRING (SIZE(8))
    ACCESS  read-only
    STATUS  mandatory
    DESCRIPTION
    "Total DNS requests counter."
    ::= {rsNWSDStats 1}

rsWSDAnsweredDNSReqCounter OBJECT-TYPE
    SYNTAX  OCTET STRING (SIZE(8))
    ACCESS  read-only
    STATUS  mandatory
    DESCRIPTION
    "Answered DNS requests counter."
    ::= {rsNWSDStats 2}

rsWSDBadDNSReqCounter OBJECT-TYPE
    SYNTAX  OCTET STRING (SIZE(8))
    ACCESS  read-only
    STATUS  mandatory
    DESCRIPTION
    "Bad DNS requests counter."
    ::= {rsNWSDStats 3}

rsWSDTotalDNSReqLastSecCounter OBJECT-TYPE
    SYNTAX INTEGER
    ACCESS read-only
    STATUS mandatory
    DESCRIPTION
    "Total DNS requests last second counter."
    ::=  {rsNWSDStats 4}

rsWSDAnsweredDNSReqLastSecCounter OBJECT-TYPE
    SYNTAX INTEGER
    ACCESS read-only
    STATUS mandatory
    DESCRIPTION
    "Answered DNS requests last second counter."
    ::=  {rsNWSDStats 5}

rsWSDBadDNSReqLastSecCounter OBJECT-TYPE
    SYNTAX INTEGER
    ACCESS read-only
    STATUS mandatory
    DESCRIPTION
    "Bad DNS requests last second counter."
    ::=  {rsNWSDStats 6}


rsNWSDFarmStatisticsTable OBJECT-TYPE
    SYNTAX SEQUENCE OF RsNWSDFarmStatisticsEntry
    ACCESS not-accessible
    STATUS mandatory
    DESCRIPTION
      "Table containing the Farm statistics values."
    ::=  {rsNWSDStats 7}

rsNWSDFarmStatisticsEntry OBJECT-TYPE
    SYNTAX RsNWSDFarmStatisticsEntry
    ACCESS not-accessible
    STATUS  mandatory
    DESCRIPTION
       " The row definition for this table."
   INDEX { rsNWSDFarmStatisticsAddress }
    ::=  {rsNWSDFarmStatisticsTable 1}

RsNWSDFarmStatisticsEntry ::= SEQUENCE {
  rsNWSDFarmStatisticsAddress					IpAddress,
  rsNWSDFarmStatisticsAttachedUsersNumber			INTEGER,
  rsNWSDFarmStatisticsTotalAttachedUsersNumber			OCTET STRING,
  rsNWSDFarmStatisticsPeakLoad					INTEGER,
  rsNWSDFarmStatisticsFramesLoad				OCTET STRING,
  rsNWSDFarmStatisticsFramesRate				INTEGER,
  rsNWSDFarmStatisticsFramesLoadInBytes				OCTET STRING,
  rsNWSDFarmStatisticsFramesRateInBytes				Counter,
  rsNWSDFarmStatisticsBackupServerUsed				INTEGER,
  rsNWSDFarmStatisticsDistThresholdReached			INTEGER,
  rsNWSDFarmStatisticsCapacityThresholdReached			INTEGER,
  rsNWSDFarmStatisticsTotalDNSReqCounter			Counter,
  rsNWSDFarmStatisticsTotalDNSReqLastSecCounter			Counter,
  rsNWSDFarmStatisticsLocalyAnsweredDNSReqCounter		Counter,
  rsNWSDFarmStatisticsLocalyAnsweredDNSReqLastSecCounter	Counter,
  rsNWSDFarmStatisticsRedirectedDNSReqCounter			Counter,
  rsNWSDFarmStatisticsRedirectedDNSReqLastSecCounter	  	Counter,
  rsNWSDFarmStatisticsTotalHTTPSessionsCounter                 OCTET STRING,
  rsNWSDFarmStatisticsTotalHTTPSessionsLastSecCounter          Counter,
  rsNWSDFarmStatisticsLocalHTTPSessionsCounter                 OCTET STRING,
  rsNWSDFarmStatisticsLocalHTTPSessionsLastSecCounter          Counter,
  rsNWSDFarmStatisticsRedirectedHTTPSessionsCounter            OCTET STRING,
  rsNWSDFarmStatisticsRedirectedHTTPSessionsLastSecCounter     Counter,
  rsNWSDFarmStatisticsTotalTriangSessionsCounter               OCTET STRING,
  rsNWSDFarmStatisticsTotalTriangSessionsLastSecCounter        Counter,
  rsNWSDFarmStatisticsLocalTriangSessionsCounter               OCTET STRING,
  rsNWSDFarmStatisticsLocalTriangSessionsLastSecCounter        Counter,
  rsNWSDFarmStatisticsRedirectedTriangSessionsCounter          OCTET STRING,
  rsNWSDFarmStatisticsRedirectedTriangSessionsLastSecCounter   Counter
  }

rsNWSDFarmStatisticsAddress OBJECT-TYPE
    SYNTAX IpAddress
    ACCESS  read-only
    STATUS  mandatory
    DESCRIPTION
      "The IP Address of the farm."
    ::= {rsNWSDFarmStatisticsEntry 1}

rsNWSDFarmStatisticsAttachedUsersNumber OBJECT-TYPE
    SYNTAX  INTEGER
    ACCESS  read-only
    STATUS  mandatory
    DESCRIPTION
      "Farm current connected users number."
    ::= {rsNWSDFarmStatisticsEntry 2}

rsNWSDFarmStatisticsTotalAttachedUsersNumber OBJECT-TYPE
    SYNTAX  OCTET STRING (SIZE(8))
    ACCESS  read-only
    STATUS  mandatory
    DESCRIPTION
      "Farm total users number since last reset of the device."
    ::= {rsNWSDFarmStatisticsEntry 3}

rsNWSDFarmStatisticsPeakLoad OBJECT-TYPE
    SYNTAX  INTEGER
    ACCESS  read-only
    STATUS  mandatory
    DESCRIPTION
      "Farm peak load of packets per second."
    ::= {rsNWSDFarmStatisticsEntry 4}

rsNWSDFarmStatisticsFramesLoad OBJECT-TYPE
    SYNTAX  OCTET STRING (SIZE(8))
    ACCESS  read-only
    STATUS  mandatory
    DESCRIPTION
      "Farm total number of frames handled by the device."
    ::= {rsNWSDFarmStatisticsEntry 5}

rsNWSDFarmStatisticsFramesRate OBJECT-TYPE
    SYNTAX  INTEGER
    ACCESS  read-only
    STATUS  mandatory
    DESCRIPTION
      "Farm frames rate in the last minute."
    ::= {rsNWSDFarmStatisticsEntry 6}

rsNWSDFarmStatisticsFramesLoadInBytes OBJECT-TYPE
    SYNTAX  OCTET STRING (SIZE(8))
    ACCESS  read-only
    STATUS  mandatory
    DESCRIPTION
      "Bytes load per second."
    ::=  {rsNWSDFarmStatisticsEntry 7}

rsNWSDFarmStatisticsFramesRateInBytes OBJECT-TYPE
    SYNTAX  Counter
    ACCESS  read-only
    STATUS  mandatory
    DESCRIPTION
      "Bytes load rate per second."
    ::=  {rsNWSDFarmStatisticsEntry 8}

rsNWSDFarmStatisticsBackupServerUsed OBJECT-TYPE
    SYNTAX  INTEGER
    ACCESS  read-only
    STATUS  mandatory
    DESCRIPTION
      "Backup server used flag. It shows true if the
       backup server was used in the last reporting period"
    ::= {rsNWSDFarmStatisticsEntry 9}

rsNWSDFarmStatisticsDistThresholdReached OBJECT-TYPE
    SYNTAX  INTEGER
    ACCESS  read-only
    STATUS  mandatory
    DESCRIPTION
      "Distribution threshold reached flag. It shows true if the
       distribution threshold was reached in the last reporting period"
    ::= {rsNWSDFarmStatisticsEntry 10}

rsNWSDFarmStatisticsCapacityThresholdReached OBJECT-TYPE
    SYNTAX  INTEGER
    ACCESS  read-only
    STATUS  mandatory
    DESCRIPTION
      "Capacity threshold reached flag. It shows true if the
       capacity threshold was reached in the last reporting period"
    ::= {rsNWSDFarmStatisticsEntry 11}

rsNWSDFarmStatisticsTotalDNSReqCounter OBJECT-TYPE
    SYNTAX  Counter
    ACCESS  read-only
    STATUS  mandatory
    DESCRIPTION
    "Total number of DNS requests which arrived for this Farm."
    ::= {rsNWSDFarmStatisticsEntry 12}

rsNWSDFarmStatisticsTotalDNSReqLastSecCounter OBJECT-TYPE
    SYNTAX  Counter
    ACCESS  read-only
    STATUS  mandatory
    DESCRIPTION
    "Total number of DNS requests which arrived
	 for this Farm during the last second."
    ::= {rsNWSDFarmStatisticsEntry 13}

rsNWSDFarmStatisticsLocalyAnsweredDNSReqCounter OBJECT-TYPE
    SYNTAX  Counter
    ACCESS  read-only
    STATUS  mandatory
    DESCRIPTION
    "The number of DNS Requests which arrived for this
	 farm and were answered by the local farm."
    ::= {rsNWSDFarmStatisticsEntry 14}

rsNWSDFarmStatisticsLocalyAnsweredDNSReqLastSecCounter OBJECT-TYPE
    SYNTAX  Counter
    ACCESS  read-only
    STATUS  mandatory
    DESCRIPTION
    "The number of DNS Requests which arrived during the last second
	 for this farm and were answered by the local farm."
    ::= {rsNWSDFarmStatisticsEntry 15}

rsNWSDFarmStatisticsRedirectedDNSReqCounter OBJECT-TYPE
    SYNTAX  Counter
    ACCESS  read-only
    STATUS  mandatory
    DESCRIPTION
    "The number of DNS Requests which arrived for this
	 farm and were redirecteded to remote/distributed servers."
    ::= {rsNWSDFarmStatisticsEntry 16}

rsNWSDFarmStatisticsRedirectedDNSReqLastSecCounter OBJECT-TYPE
    SYNTAX  Counter
    ACCESS  read-only
    STATUS  mandatory
    DESCRIPTION
    "The number of DNS Requests which arrived during the last second
	 for this farm and were redirecteded to remote/distributed servers."
    ::= {rsNWSDFarmStatisticsEntry 17}

rsNWSDFarmStatisticsTotalHTTPSessionsCounter OBJECT-TYPE
    SYNTAX  OCTET STRING (SIZE(8))
    ACCESS  read-only
    STATUS  mandatory
    DESCRIPTION
    "Total number of HTTP sessions which arrived for this Farm."
    ::= {rsNWSDFarmStatisticsEntry 18}

rsNWSDFarmStatisticsTotalHTTPSessionsLastSecCounter OBJECT-TYPE
    SYNTAX  Counter
    ACCESS  read-only
    STATUS  mandatory
    DESCRIPTION
    "Total number of HTTP sessions which arrived
  	 for this Farm during the last second."
    ::= {rsNWSDFarmStatisticsEntry 19}

rsNWSDFarmStatisticsLocalHTTPSessionsCounter OBJECT-TYPE
    SYNTAX  OCTET STRING (SIZE(8))
    ACCESS  read-only
    STATUS  mandatory
    DESCRIPTION
    "The number of HTTP sessions which arrived for this
	   farm and were directed to a local server."
    ::= {rsNWSDFarmStatisticsEntry 20}

rsNWSDFarmStatisticsLocalHTTPSessionsLastSecCounter OBJECT-TYPE
    SYNTAX  Counter
    ACCESS  read-only
    STATUS  mandatory
    DESCRIPTION
    "The number of HTTP sessions which arrived during the
	   last second for this farm and were directed to a local server."
    ::= {rsNWSDFarmStatisticsEntry 21}

rsNWSDFarmStatisticsRedirectedHTTPSessionsCounter OBJECT-TYPE
    SYNTAX  OCTET STRING (SIZE(8))
    ACCESS  read-only
    STATUS  mandatory
    DESCRIPTION
    "The number of HTTP sessions which arrived for this
	   farm and were redirecteded to remote/distributed servers."
    ::= {rsNWSDFarmStatisticsEntry 22}

rsNWSDFarmStatisticsRedirectedHTTPSessionsLastSecCounter OBJECT-TYPE
    SYNTAX  Counter
    ACCESS  read-only
    STATUS  mandatory
    DESCRIPTION
    "The number of HTTP sessions which arrived during the last second
	   for this farm and were redirecteded to remote/distributed servers."
    ::= {rsNWSDFarmStatisticsEntry 23}


rsNWSDFarmStatisticsTotalTriangSessionsCounter OBJECT-TYPE
    SYNTAX  OCTET STRING (SIZE(8))
    ACCESS  read-only
    STATUS  mandatory
    DESCRIPTION
    "Total number of Tringulation sessions for this Farm."
    ::= {rsNWSDFarmStatisticsEntry 24}

rsNWSDFarmStatisticsTotalTriangSessionsLastSecCounter OBJECT-TYPE
    SYNTAX  Counter
    ACCESS  read-only
    STATUS  mandatory
    DESCRIPTION
    "Total number of Tringulation sessions which arrived
	   for this Farm during the last second."
    ::= {rsNWSDFarmStatisticsEntry 25}

rsNWSDFarmStatisticsLocalTriangSessionsCounter OBJECT-TYPE
    SYNTAX  OCTET STRING (SIZE(8))
    ACCESS  read-only
    STATUS  mandatory
    DESCRIPTION
    "The number of Tringulation sessions which arrived for this
	   farm and were answered by the a local server."
    ::= {rsNWSDFarmStatisticsEntry 26}

rsNWSDFarmStatisticsLocalTriangSessionsLastSecCounter OBJECT-TYPE
    SYNTAX  Counter
    ACCESS  read-only
    STATUS  mandatory
    DESCRIPTION
    "The number of Tringulation sessions which arrived during the
	   last second for this farm and were answered by a local server."
    ::= {rsNWSDFarmStatisticsEntry 27}

rsNWSDFarmStatisticsRedirectedTriangSessionsCounter OBJECT-TYPE
    SYNTAX  OCTET STRING (SIZE(8))
    ACCESS  read-only
    STATUS  mandatory
    DESCRIPTION
    "The number of sessions which were redirecteded by triangulation
     to distributed servers."
    ::= {rsNWSDFarmStatisticsEntry 28}

rsNWSDFarmStatisticsRedirectedTriangSessionsLastSecCounter OBJECT-TYPE
    SYNTAX  Counter
    ACCESS  read-only
    STATUS  mandatory
    DESCRIPTION
    "The number of sessions which were redirecteded by triangulation
	   during the last second to distributed servers."
    ::= {rsNWSDFarmStatisticsEntry 29}


rsNWSDServerStatisticsTable OBJECT-TYPE
    SYNTAX SEQUENCE OF RsNWSDServerStatisticsEntry
    ACCESS not-accessible
    STATUS mandatory
    DESCRIPTION
      "Table containing the Server statistics values."
    ::=  {rsNWSDStats 8}

rsNWSDServerStatisticsEntry OBJECT-TYPE
    SYNTAX RsNWSDServerStatisticsEntry
    ACCESS not-accessible
    STATUS  mandatory
    DESCRIPTION
       " The row definition for this table."
   INDEX { rsNWSDServerStatisticsFarmAddr,
           rsNWSDServerStatisticsServerAddr }
    ::=  {rsNWSDServerStatisticsTable 1}

RsNWSDServerStatisticsEntry ::= SEQUENCE {
  rsNWSDServerStatisticsFarmAddr                     IpAddress,
  rsNWSDServerStatisticsServerAddr                   IpAddress,
  rsNWSDServerStatisticsAttachedUsersNumber          INTEGER,
  rsNWSDServerStatisticsPeakLoad                     INTEGER,
  rsNWSDServerStatisticsFramesRate                   INTEGER,
  rsNWSDServerStatisticsFramesLoad                   OCTET STRING,
  rsNWSDServerStatisticsTotalAttachedUsersNumber     OCTET STRING,
  rsNWSDServerStatisticsFramesLoadInBytes            OCTET STRING,
  rsNWSDServerStatisticsFramesRateInBytes            Counter,
  rsNWSDServerStatisticsConnectivityCheckFailed      INTEGER,
  rsNWSDServerStatisticsConnectionLimitReached       INTEGER,
  rsNWSDServerStatisticsAnsweredDNSReqCounter        Counter,
  rsNWSDServerStatisticsAnsweredDNSReqLastSecCounter Counter,
  rsNWSDServerStatisticsRedirectedHTTPSessions                  OCTET STRING,
  rsNWSDServerStatisticsRedirectedHTTPSessionsLastSecCounter    Counter,
  rsNWSDServerStatisticsRedirectedTriangSessions                OCTET STRING,
  rsNWSDServerStatisticsRedirectedTriangSessionsLastSecCount    Counter
  }

rsNWSDServerStatisticsFarmAddr OBJECT-TYPE
    SYNTAX  IpAddress
    ACCESS  read-only
    STATUS  mandatory
    DESCRIPTION
     "WSD Virtual IP address (Farm addr)"
	::=  {rsNWSDServerStatisticsEntry 1}

rsNWSDServerStatisticsServerAddr  OBJECT-TYPE
    SYNTAX  IpAddress
    ACCESS  read-only
    STATUS  mandatory
    DESCRIPTION
     "Server  IP address"
	::=  {rsNWSDServerStatisticsEntry 2 }

rsNWSDServerStatisticsAttachedUsersNumber OBJECT-TYPE
    SYNTAX  INTEGER
    ACCESS  read-only
    STATUS  mandatory
    DESCRIPTION
      "Number of currently active users attached to this server."
    ::=  {rsNWSDServerStatisticsEntry 3 }

rsNWSDServerStatisticsPeakLoad OBJECT-TYPE
    SYNTAX  INTEGER
    ACCESS  read-only
    STATUS  mandatory
    DESCRIPTION
      "Maximal number of frames per second dispatched to server
       since last reset."
    ::=  {rsNWSDServerStatisticsEntry 4}

rsNWSDServerStatisticsFramesRate OBJECT-TYPE
    SYNTAX  INTEGER
    ACCESS  read-only
    STATUS  mandatory
    DESCRIPTION
      "Number of frames per second dispatched to server."
    ::=  {rsNWSDServerStatisticsEntry 5}

rsNWSDServerStatisticsFramesLoad OBJECT-TYPE
    SYNTAX  OCTET STRING (SIZE(8))
    ACCESS  read-only
    STATUS  mandatory
    DESCRIPTION
      "Number of frames dispatched to server."
    ::=  {rsNWSDServerStatisticsEntry 6 }

rsNWSDServerStatisticsTotalAttachedUsersNumber OBJECT-TYPE
    SYNTAX  OCTET STRING (SIZE(8))
    ACCESS  read-only
    STATUS  mandatory
    DESCRIPTION
      "Total number of users ever attached to this server."
    ::=  {rsNWSDServerStatisticsEntry 7 }

rsNWSDServerStatisticsFramesLoadInBytes OBJECT-TYPE
    SYNTAX  OCTET STRING (SIZE(8))
    ACCESS  read-only
    STATUS  mandatory
    DESCRIPTION
      "Bytes load per second dispatched to server."
    ::=  {rsNWSDServerStatisticsEntry 8 }

rsNWSDServerStatisticsFramesRateInBytes OBJECT-TYPE
    SYNTAX  Counter
    ACCESS  read-only
    STATUS  mandatory
    DESCRIPTION
      "Bytes Rate dispatched to server."
    ::=  {rsNWSDServerStatisticsEntry 9}

rsNWSDServerStatisticsConnectivityCheckFailed OBJECT-TYPE
    SYNTAX  INTEGER
    ACCESS  read-only
    STATUS  mandatory
    DESCRIPTION
      "Connectivity check failed flag. It shows true if the
        checks of this server failed in the last reporting period"
    ::=  {rsNWSDServerStatisticsEntry 10}

rsNWSDServerStatisticsConnectionLimitReached OBJECT-TYPE
    SYNTAX  INTEGER
    ACCESS  read-only
    STATUS  mandatory
    DESCRIPTION
      "Connection limit reached flag. It shows true if the
       connection limit was reached in the last reporting period"
    ::=  {rsNWSDServerStatisticsEntry 11}

rsNWSDServerStatisticsAnsweredDNSReqCounter OBJECT-TYPE
    SYNTAX  Counter
    ACCESS  read-only
    STATUS  mandatory
    DESCRIPTION
    "Number of DNS requests answered by this Server."
    ::=  {rsNWSDServerStatisticsEntry 12}

rsNWSDServerStatisticsAnsweredDNSReqLastSecCounter OBJECT-TYPE
    SYNTAX  Counter
    ACCESS  read-only
    STATUS  mandatory
    DESCRIPTION
    "Number of DNS requests answered by this Server during the last second."
    ::=  {rsNWSDServerStatisticsEntry 13}
rsNWSDServerStatisticsRedirectedHTTPSessions OBJECT-TYPE
    SYNTAX  OCTET STRING (SIZE(8))
    ACCESS  read-only
    STATUS  mandatory
    DESCRIPTION
    "Number of HTTP sessions redirected to this Server."
    ::=  {rsNWSDServerStatisticsEntry 14}

rsNWSDServerStatisticsRedirectedHTTPSessionsLastSecCounter OBJECT-TYPE
    SYNTAX  Counter
    ACCESS  read-only
    STATUS  mandatory
    DESCRIPTION
    "Number of HTTP sessions redirected to this Server during the last second."
    ::=  {rsNWSDServerStatisticsEntry 15}

rsNWSDServerStatisticsRedirectedTriangSessions OBJECT-TYPE
    SYNTAX  OCTET STRING (SIZE(8))
    ACCESS  read-only
    STATUS  mandatory
    DESCRIPTION
    "Number of sessions triangulated to this site."
    ::=  {rsNWSDServerStatisticsEntry 16}

rsNWSDServerStatisticsRedirectedTriangSessionsLastSecCount OBJECT-TYPE
    SYNTAX  Counter
    ACCESS  read-only
    STATUS  mandatory
    DESCRIPTION
    "Number of sessions triangulated to this site during the last second."
    ::=  {rsNWSDServerStatisticsEntry 17}


rsWSDCookieTable OBJECT-TYPE
   SYNTAX SEQUENCE OF RsWSDCookieTableEntry
   ACCESS not-accessible
   STATUS mandatory
   DESCRIPTION
       "A table for managing cookie information."
   ::= {rsNWSD 30}

rsWSDCookieTableEntry OBJECT-TYPE
   SYNTAX RsWSDCookieTableEntry
   ACCESS not-accessible
   STATUS mandatory
   DESCRIPTION
       " The row definition for this table."
   INDEX  {rsWSDCookieFarm, rsWSDCookieValue}
   ::= {rsWSDCookieTable 1}

RsWSDCookieTableEntry ::= SEQUENCE {
  rsWSDCookieFarm    IpAddress,
  rsWSDCookieValue   DisplayString,
  rsWSDCookieServer  IpAddress,
  rsWSDCookieStatus  RowStatus
}

rsWSDCookieFarm OBJECT-TYPE
  SYNTAX IpAddress
  ACCESS read-write
  STATUS mandatory
  DESCRIPTION
     "IP address of the cookie farm."
  ::=  {rsWSDCookieTableEntry 1}

rsWSDCookieValue OBJECT-TYPE
    SYNTAX DisplayString (SIZE(1..63))
    ACCESS  read-write
    STATUS  mandatory
    DESCRIPTION
      "The cookie value that identifies the server."
    ::= {rsWSDCookieTableEntry 2}

rsWSDCookieServer OBJECT-TYPE
  SYNTAX IpAddress
  ACCESS read-write
  STATUS mandatory
  DESCRIPTION
     "IP address of the server identified by the cookie."
  ::=  {rsWSDCookieTableEntry 3}

rsWSDCookieStatus OBJECT-TYPE
  SYNTAX RowStatus
  ACCESS read-write
  STATUS mandatory
  DESCRIPTION
    "Row status for the cookie."
  ::=  {rsWSDCookieTableEntry 4}

rsWSDTrackUDPSessionsMode OBJECT-TYPE
    SYNTAX  INTEGER {
      enable(1),
      disable(2)
    }
    ACCESS  read-write
    STATUS  mandatory
    DESCRIPTION
      "Enable/Disable tracking of UDP sessions. When disabled, such sessions are not inserted into the client table."
    DEFVAL { 1 }
        ::=  {rsNWSD 31}

rsWSDTrackSSLIDinSelectServerMode OBJECT-TYPE
    SYNTAX  INTEGER {
      enable(1),
      disable(2)
    }
    ACCESS  read-write
    STATUS  mandatory
    DESCRIPTION
      "Enable/Disable tracking of SSL session IDs in Select Server mode. When disabled (default), SSL sessions
       are treated as if New Entry mode is used."
--  DEFVAL { 2 }
        ::=  {rsNWSD 32}

rsWSDTuning OBJECT IDENTIFIER ::= { rsNWSD 33}

rsWSDMaxURLEntriesTuning OBJECT IDENTIFIER ::= { rsWSDTuning 1}

rsWSDMaxURLEntries OBJECT-TYPE
    SYNTAX INTEGER
    ACCESS  read-only
    STATUS  mandatory
    DESCRIPTION
      "Maximal number of entries in the URL table."
    ::=  { rsWSDMaxURLEntriesTuning 1 }

rsWSDMaxURLEntriesAfterReset OBJECT-TYPE
    SYNTAX INTEGER
    ACCESS  read-write
    STATUS  mandatory
    DESCRIPTION
      "Future maximal number of entries in the URL table."
    ::=  { rsWSDMaxURLEntriesTuning 2 }

rsWSDMaxRequestEntriesTuning OBJECT IDENTIFIER ::= { rsWSDTuning 2}

rsWSDMaxRequestEntries OBJECT-TYPE
    SYNTAX INTEGER
    ACCESS  read-only
    STATUS  mandatory
    DESCRIPTION
      "Maximal number of entries in the request table."
    ::=  { rsWSDMaxRequestEntriesTuning 1 }

rsWSDMaxRequestEntriesAfterReset OBJECT-TYPE
    SYNTAX INTEGER
    ACCESS  read-write
    STATUS  mandatory
    DESCRIPTION
      "Future maximal number of entries in the request table."
    ::=  { rsWSDMaxRequestEntriesTuning 2 }

rsWSDMaxSSLEntriesTuning OBJECT IDENTIFIER ::= { rsWSDTuning 3}

rsWSDMaxSSLEntries OBJECT-TYPE
    SYNTAX INTEGER
    ACCESS  read-only
    STATUS  mandatory
    DESCRIPTION
      "Maximal number of entries in the SSL table."
    ::=  { rsWSDMaxSSLEntriesTuning 1 }

rsWSDMaxSSLEntriesAfterReset OBJECT-TYPE
    SYNTAX INTEGER
    ACCESS  read-write
    STATUS  mandatory
    DESCRIPTION
      "Future maximal number of entries in the SSL table."
    ::=  { rsWSDMaxSSLEntriesTuning 2 }


rsWSDTweaks OBJECT IDENTIFIER ::= { rsNWSD 34}

rsWSDMaintainURLSFPersistency OBJECT-TYPE
    SYNTAX INTEGER {
      enable(1),
      disable(2)
    }
    ACCESS  read-write
    STATUS  mandatory
    DESCRIPTION
      "maintain HTTP persistency in URL SuperFarm sessions. enable -
      persistency is maintained, disable - persistency is broken."
--  DEFVAL  { 2 }
    ::=  { rsWSDTweaks 1 }

rsWSDAllowAnyAppPortForCookies OBJECT-TYPE
    SYNTAX INTEGER {
      enable(1),
      disable(2)
    }
    ACCESS  read-write
    STATUS  mandatory
    DESCRIPTION
      "enable - allow cookies handling on any application port. disable -
      cookie mechanism works for port 80 only."
--  DEFVAL  { 2 }
    ::=  { rsWSDTweaks 2 }

rsWSDSrcPortInClientHash OBJECT-TYPE
    SYNTAX INTEGER {
      enable(1),
      disable(2)
    }
    ACCESS  read-write
    STATUS  mandatory
    DESCRIPTION
      "enable - client's source port is used in client table hashing, disable
      - only client IP is used."
--  DEFVAL  { 2 }
    ::=  { rsWSDTweaks 3 }

rsWSDUserDefinedTimeoutAfterTCPFailure OBJECT-TYPE
    SYNTAX INTEGER {
      enable(1),
      disable(2)
    }
    ACCESS  read-write
    STATUS  mandatory
    DESCRIPTION
      "enable - use user defined timeout between failed TCP checks, disable -
      use 0.5 seconds delay between checks."
--  DEFVAL  { 2 }
    ::=  { rsWSDTweaks 4 }

rsWSDNoSlashAfterGET OBJECT-TYPE
    SYNTAX INTEGER {
      enable(1),
      disable(2)
    }
    ACCESS  read-write
    STATUS  mandatory
    DESCRIPTION
      "enable - no slash is used when trying to read a HTTP page on the server
      (for syntax that includes a host name), disable - request is with a
      slash (for syntax that does not include a host name)."
--  DEFVAL  { 2 }
    ::=  { rsWSDTweaks 5 }

rsWSDTimeoutForSYN OBJECT-TYPE
    SYNTAX INTEGER  (0..10)
    ACCESS  read-write
    STATUS  mandatory
    DESCRIPTION
      "The initial aging time that a client entry will use when a SYN packet
      arrives. 0 means use the regular aging time."
--  DEFVAL  { 5 }
    ::=  { rsWSDTweaks 6 }

rsWSDSpecificNATAddress OBJECT-TYPE
    SYNTAX IpAddress
    ACCESS  read-write
    STATUS  mandatory
    DESCRIPTION
      "Use this (farm) address as the one used for all NAT sessions."
    ::=  { rsWSDTweaks 7 }

rsWSDExtendedCheckHostMode OBJECT-TYPE
    SYNTAX INTEGER {
      ipMode(1),
      nameMode(2)
    }
    ACCESS  read-write
    STATUS  mandatory
    DESCRIPTION
      "How the host in the extended HTTP check appears. Can be the server IP
      or the farm name."
    DEFVAL  { 1 }
    ::=  { rsWSDTweaks 8 }

rsWSDExtendedLRPSecurity OBJECT-TYPE
    SYNTAX INTEGER {
      enable(1),
      disable(2)
    }
    ACCESS  read-write
    STATUS  mandatory
    DESCRIPTION
      "When extended LRP security is enabled, the map address supplied by a distributed
       WSD must be in the same subnet as it's farm."
    DEFVAL  { 1 }
    ::=  { rsWSDTweaks 9 }

rsWSDURLCookies OBJECT-TYPE
    SYNTAX INTEGER {
      enable(1),
      disable(2)
    }
    ACCESS  read-write
    STATUS  mandatory
    DESCRIPTION
      "When enabled, cookie parsing is performed on URL parameters, rather than the 
       cookie header."
    DEFVAL  { 2 }
    ::=  { rsWSDTweaks 10 }

rsWSDURLTableLookupPrecedence OBJECT-TYPE
    SYNTAX INTEGER {
      url(1),
      fileType(2)
    }
    ACCESS  read-write
    STATUS  mandatory
    DESCRIPTION
      "This parameter sets the lookup precedence of the URL table. URL means look for URL first, 
       fileType means look for file type match first."
    DEFVAL  { 1 }
    ::=  { rsWSDTweaks 11 }

--
-- wsd specific threshold warnings
--

rsWSDClientTableSizeThresh OBJECT-TYPE
    SYNTAX INTEGER (0..100)
    ACCESS  read-write
    STATUS  mandatory
    DESCRIPTION
       "This variable defines at what percentage of the maximum allowed value of the
        client table size the Threshold Warning Trap should be dispatched. Default = 80, DISABLE = 0"
--  DEFVAL {80}
    ::= { rsWSDThresholdWarnings 3 }

rsWSDLogicServConnectLimitThresh OBJECT-TYPE
    SYNTAX INTEGER (0..100)
    ACCESS  read-write
    STATUS  mandatory
    DESCRIPTION
       "This variable defines at what percentage of the maximum allowed value of the
        Logical Server Connections Limit the Threshold Warning
        Trap should be dispatched. Default = 90,  DISABLE = 0"
--  DEFVAL {90 }
    ::= { rsWSDThresholdWarnings 4 }

rsWSDPhysServConnectLimitThresh OBJECT-TYPE
    SYNTAX INTEGER (0..100)
    ACCESS  read-write
    STATUS  mandatory
    DESCRIPTION
       "This variable defines at what percentage of the maximum allowed value of the
        Physical Server Connections Limit the Threshold Warning Trap should
        be dispatched. Default = 90, DISABLE = 0"
--  DEFVAL {90}
    ::= { rsWSDThresholdWarnings 5 }

rsWSDFarmCapacityLimitThresh OBJECT-TYPE
    SYNTAX INTEGER (0..100)
    ACCESS  read-write
    STATUS  mandatory
    DESCRIPTION
       "This variable defines at what percentage of the Farm Capacity Limit the
        Threshold Warning Trap should be dispatched. Default = 90, DISABLE = 0"
--  DEFVAL {90}
    ::= { rsWSDThresholdWarnings 6 }

rsWSDServBandwidthLimitThresh OBJECT-TYPE
    SYNTAX INTEGER (0..100)
    ACCESS  read-write
    STATUS  mandatory
    DESCRIPTION
       "This variable defines at what percentage of the Server Bandwidth Limit the
        Threshold Warning Trap should be dispatched. Default = 90, DISABLE = 0"
--  DEFVAL {90}
    ::= { rsWSDThresholdWarnings 7 }

rsWSDFarmBandwidthLimitThresh OBJECT-TYPE
    SYNTAX INTEGER (0..100)
    ACCESS  read-write
    STATUS  mandatory
    DESCRIPTION
       "This variable defines at what percentage of the Farm Bandwidth Limit the
        Threshold Warning Trap should be dispatched. Default = 90, DISABLE = 0 "
--  DEFVAL {90}
    ::= { rsWSDThresholdWarnings 8 }

--
-- extended farm table
--

rsWSDExtendedFarmTable OBJECT-TYPE
   SYNTAX SEQUENCE OF RsWSDExtendedFarmEntry
   ACCESS not-accessible
   STATUS mandatory
   DESCRIPTION
          "In this table the WSD  version 2 saves the general parameters per
           server farme IP Addr."
   ::= {rsNWSD 35}

rsWSDExtendedFarmEntry OBJECT-TYPE
    SYNTAX RsWSDExtendedFarmEntry
    ACCESS not-accessible
    STATUS  mandatory
    DESCRIPTION
       " The row definition for this table."
   INDEX  {rsWSDExtendedFarmAddress}
   ::= {rsWSDExtendedFarmTable 1}


RsWSDExtendedFarmEntry  ::= SEQUENCE {
  rsWSDExtendedFarmAddress      IpAddress,
  rsWSDExtendedFarmHttpsType    INTEGER,
  rsWSDConnCheckSecret          DisplayString,
  rsWSDOverLoadStatus           INTEGER,
  rsWSDFarmURLCookies           INTEGER,
  rsWSDExtendedFarmNATRangeIPFrom IpAddress
 }

rsWSDExtendedFarmAddress OBJECT-TYPE
    SYNTAX IpAddress
    ACCESS  read-only
    STATUS  mandatory
    DESCRIPTION
      "The IP Address of the WEB farm."
    ::= {rsWSDExtendedFarmEntry 1}

rsWSDExtendedFarmHttpsType OBJECT-TYPE
    SYNTAX INTEGER {
      regular(1),
      httpsonly(2)
   }
    ACCESS  read-write
    STATUS  mandatory
    DESCRIPTION
      " regular - means that this server applies all requests
        httpsonly - applies only HTTPS requests"
    ::=  {rsWSDExtendedFarmEntry 2}

rsWSDConnCheckSecret OBJECT-TYPE
   SYNTAX DisplayString (SIZE(0..20))
   ACCESS  read-write
   STATUS  mandatory
   DESCRIPTION
     "Secret used for radius connectivity checks."
   ::= {rsWSDExtendedFarmEntry 3}

rsWSDOverLoadStatus OBJECT-TYPE
   SYNTAX INTEGER {
        enable(1),
        disable(2)
   }
   ACCESS  read-write
   STATUS  mandatory
   DESCRIPTION
       "Enable or disable to open more clients session to a server even though
        its connection limit is reached"
-- DEFVAL { 2 }
   ::=  {rsWSDExtendedFarmEntry 4}

rsWSDFarmURLCookies OBJECT-TYPE
   SYNTAX INTEGER {
        enable(1),
        disable(2)
   }
   ACCESS  read-write
   STATUS  mandatory
   DESCRIPTION
       "Set cookie search in URL per farm (not just globally)."
   DEFVAL { 2 }
   ::=  {rsWSDExtendedFarmEntry 5}

rsWSDExtendedFarmNATRangeIPFrom OBJECT-TYPE
 SYNTAX IpAddress
    ACCESS  read-write
    STATUS  mandatory
    DESCRIPTION
 "choose beginning of existing range interval from NAT IP range table "
    ::=  {rsWSDExtendedFarmEntry 6}

rsWSDNHRTable OBJECT-TYPE
   SYNTAX SEQUENCE OF RsWSDNHREntry
   ACCESS not-accessible
   STATUS mandatory
   DESCRIPTION
          "In this table the WSD holds the Next Hop Routers to be used as Default Routers."
   ::= {rsNWSD 36}

rsWSDNHREntry OBJECT-TYPE
    SYNTAX RsWSDNHREntry
    ACCESS not-accessible
    STATUS mandatory
    DESCRIPTION
       " The row definition for NHR table."
   INDEX  {rsWSDNHRNHRIP}
   ::= {rsWSDNHRTable 1}

RsWSDNHREntry  ::= SEQUENCE {
        rsWSDNHRNHRIP                   IpAddress,
        rsWSDNHRDestinationMAC          PhysAddress,
        rsWSDNHRSourceMAC               PhysAddress,
        rsWSDNHRPhysicalPortNumber      INTEGER,
        rsWSDNHRAdminStatus             INTEGER,
        rsWSDNHROperStatus              INTEGER,
        rsWSDNHRPathHealthCheckIP       IpAddress,
        rsWSDNHRCheckMethod             INTEGER,
        rsWSDNHRCheckInterval           INTEGER,
        rsWSDNRHCheckRetries            INTEGER,
        rsWSDNHRRowStatus               RowStatus,
        rsWSDNHRTag                     INTEGER
}

rsWSDNHRNHRIP OBJECT-TYPE
    SYNTAX IpAddress
    ACCESS  read-only
    STATUS  mandatory
    DESCRIPTION
      "NHR's IP address."
   ::= { rsWSDNHREntry 1}

rsWSDNHRDestinationMAC OBJECT-TYPE
    SYNTAX PhysAddress
    ACCESS  read-only
    STATUS  mandatory
    DESCRIPTION
      "The router's MAC address."
   ::= { rsWSDNHREntry 2}

rsWSDNHRSourceMAC OBJECT-TYPE
    SYNTAX PhysAddress
    ACCESS  read-only
    STATUS  mandatory
    DESCRIPTION
      "WDS port's MAC address."
   ::= { rsWSDNHREntry 3}

rsWSDNHRPhysicalPortNumber OBJECT-TYPE
    SYNTAX INTEGER
    ACCESS  read-only
    STATUS  mandatory
    DESCRIPTION
      "WSD port's physical number."
   ::= { rsWSDNHREntry 4}


rsWSDNHRAdminStatus OBJECT-TYPE
    SYNTAX INTEGER {
	enable(1),
	disable(2) }
    ACCESS  read-write
    STATUS  mandatory
    DESCRIPTION
      "Forces the administrative state of the router."
    DEFVAL {1}
   ::= { rsWSDNHREntry 5}

rsWSDNHROperStatus OBJECT-TYPE
    SYNTAX INTEGER {
	active(1),
	notInService(2) }
    ACCESS  read-only
    STATUS  mandatory
    DESCRIPTION
      "The availability status of the router."
   ::= { rsWSDNHREntry 6}

rsWSDNHRPathHealthCheckIP OBJECT-TYPE
    SYNTAX IpAddress
    ACCESS  read-write
    STATUS  mandatory
    DESCRIPTION
      "The IP address of a network entity to check through the router - in order to check it's functionality."
   ::= { rsWSDNHREntry 7}

rsWSDNHRCheckMethod OBJECT-TYPE
    SYNTAX INTEGER {
	ping(1),
	disable(2) }
    ACCESS  read-write
    STATUS  mandatory
    DESCRIPTION
      "The test method."
    DEFVAL {2}
   ::= { rsWSDNHREntry 8}

rsWSDNHRCheckInterval OBJECT-TYPE
    SYNTAX INTEGER (1..3600)
    ACCESS  read-write
    STATUS  mandatory
    DESCRIPTION
      "The period of time between checks in seconds."
    DEFVAL {10}
   ::= { rsWSDNHREntry 9}

rsWSDNRHCheckRetries OBJECT-TYPE
    SYNTAX INTEGER (0..10)
    ACCESS  read-write
    STATUS  mandatory
    DESCRIPTION
      "The number of times a test will fail until Operational Status will be updated."
    DEFVAL {3}
   ::= { rsWSDNHREntry 10}

rsWSDNHRRowStatus OBJECT-TYPE
   SYNTAX RowStatus
   ACCESS read-write
   STATUS mandatory
   DESCRIPTION
      "Row status for the current row."
   ::=  { rsWSDNHREntry 11}

rsWSDNHRTag OBJECT-TYPE
    SYNTAX INTEGER
    ACCESS  read-write
    STATUS  mandatory
    DESCRIPTION
      "NHR's tag - matching the destination MAC."
   ::= { rsWSDNHREntry 12}


rsWSDVIPNHRTable OBJECT-TYPE
   SYNTAX SEQUENCE OF RsWSDVIPNHREntry
   ACCESS not-accessible
   STATUS mandatory
   DESCRIPTION
          "The table that contains WSD associations of Virtual IPs to the Next Hop Routers,
          planned be used as Default and Backup Routers."
   ::= { rsNWSD 37 }

rsWSDVIPNHREntry OBJECT-TYPE
    SYNTAX RsWSDVIPNHREntry
    ACCESS not-accessible
    STATUS mandatory
    DESCRIPTION
       " The row definition for VIR-NHR table."
   INDEX  {rsWSDVIPNHRVIP}
   ::= {rsWSDVIPNHRTable 1}

RsWSDVIPNHREntry  ::= SEQUENCE {
  rsWSDVIPNHRVIP                  IpAddress,
  rsWSDVIPNHRNHRIP                IpAddress,
  rsWSDVIPNHRBackupNHRIP          IpAddress,
  rsWSDVIPNHRNoRouteAction        INTEGER,
  rsWSDVIPNHRRowStatus            RowStatus,
  rsWSDVIPNHRNHRWeight            INTEGER,
  rsWSDVIPNHRBackupWeight         INTEGER,
  rsWSDVIPNHRAdminLoadSharing     INTEGER
}

rsWSDVIPNHRVIP OBJECT-TYPE
    SYNTAX IpAddress
    ACCESS read-only
    STATUS mandatory
    DESCRIPTION
      "The virtual IP of the farm\superfarm."
  ::= {rsWSDVIPNHREntry 1}


rsWSDVIPNHRNHRIP OBJECT-TYPE
    SYNTAX IpAddress
    ACCESS read-write
    STATUS mandatory
    DESCRIPTION
      "The IP of Next Hop Router."
  ::= {rsWSDVIPNHREntry 2}


rsWSDVIPNHRBackupNHRIP OBJECT-TYPE
    SYNTAX IpAddress
    ACCESS read-write
    STATUS mandatory
    DESCRIPTION
      "The IP of the Backup to Next Hop Router."
  ::= {rsWSDVIPNHREntry 3}

rsWSDVIPNHRNoRouteAction OBJECT-TYPE
    SYNTAX INTEGER {
    discard(1),
    useFFT(2) }
    ACCESS read-write
    STATUS mandatory
    DESCRIPTION
      "The action taken when NHR and Backup NHR are unavailable."
    DEFVAL  { 2 }
  ::= {rsWSDVIPNHREntry 4}

rsWSDVIPNHRRowStatus OBJECT-TYPE
   SYNTAX RowStatus
   ACCESS read-write
   STATUS mandatory
   DESCRIPTION
      "Row status for the current row."
   ::=  {rsWSDVIPNHREntry 5}

rsWSDVIPNHRNHRWeight OBJECT-TYPE
    SYNTAX INTEGER (1..100)
    ACCESS read-write
    STATUS mandatory
    DESCRIPTION
      "The NHR's weight."
    DEFVAL  { 1 }
  ::= {rsWSDVIPNHREntry 6}

rsWSDVIPNHRBackupWeight OBJECT-TYPE
    SYNTAX INTEGER (1..100)
    ACCESS read-write
    STATUS mandatory
    DESCRIPTION
      "The backup NHR's weight."
    DEFVAL  { 1 }
  ::= {rsWSDVIPNHREntry 7}

rsWSDVIPNHRAdminLoadSharing OBJECT-TYPE
    SYNTAX INTEGER {
    enable(1),
    disable(2) }
    ACCESS read-write
    STATUS mandatory
    DESCRIPTION
      "Enable/Disable NHR Load Sharing for this VIPNHR."
    DEFVAL  { 2 }
  ::= {rsWSDVIPNHREntry 8}


rsWSDTokenTable OBJECT-TYPE
   SYNTAX SEQUENCE OF RsWSDTokenTableEntry
   ACCESS not-accessible
   STATUS mandatory
   DESCRIPTION
       "A table for managing HTTP token information."
   ::= {rsNWSD 38}

rsWSDTokenTableEntry OBJECT-TYPE
   SYNTAX RsWSDTokenTableEntry
   ACCESS not-accessible
   STATUS mandatory
   DESCRIPTION
       " The row definition for this table."
   INDEX  { rsWSDToken }
   ::= {rsWSDTokenTable 1}

RsWSDTokenTableEntry ::= SEQUENCE {
  rsWSDToken         DisplayString,
  rsWSDTokenFarmMap  IpAddress,
  rsWSDTokenFarm     IpAddress,
  rsWSDTokenDefault  INTEGER,
  rsWSDTokenStatus   RowStatus
}

rsWSDToken OBJECT-TYPE
    SYNTAX DisplayString (SIZE(1..63))
    ACCESS  read-write
    STATUS  mandatory
    DESCRIPTION
      "The token value that identifies the farm."
    ::= {rsWSDTokenTableEntry 1}

rsWSDTokenFarmMap OBJECT-TYPE
  SYNTAX IpAddress
  ACCESS read-write
  STATUS mandatory
  DESCRIPTION
     "IP address of the superfarm in which the token farm is defined."
  ::=  {rsWSDTokenTableEntry 2}

rsWSDTokenFarm OBJECT-TYPE
  SYNTAX IpAddress
  ACCESS read-write
  STATUS mandatory
  DESCRIPTION
     "IP address of the farm for which the token is defined."
  ::=  {rsWSDTokenTableEntry 3}

rsWSDTokenDefault OBJECT-TYPE
  SYNTAX INTEGER {
    notDefault(1),
    noToken(2),
    noHeaderField(3),
    alwaysDefault(4)
  }
  ACCESS read-write
  STATUS mandatory
  DESCRIPTION
     "Indication whether this farm is the default one. noToken indicates that the farm
      should be used as default when no matching token was found. noHeaderField indicates
      that the farm should be used when no matching header field was found, and 
      alwaysDefault indicates that this farm should be used in either case."
  ::=  {rsWSDTokenTableEntry 4}

rsWSDTokenStatus OBJECT-TYPE
  SYNTAX RowStatus
  ACCESS read-write
  STATUS mandatory
  DESCRIPTION
    "Row status for the token entry."
  ::=  {rsWSDTokenTableEntry 5}


rsWSDVirtualDNSTable OBJECT-TYPE
   SYNTAX SEQUENCE OF RsWSDVirtualDNSTableEntry
   ACCESS not-accessible
   STATUS mandatory
   DESCRIPTION
       "A table for managing virtual DNS addresses."
   ::= {rsNWSD 39}

rsWSDVirtualDNSTableEntry OBJECT-TYPE
   SYNTAX RsWSDVirtualDNSTableEntry
   ACCESS not-accessible
   STATUS mandatory
   DESCRIPTION
       " The row definition for this table."
   INDEX  { rsWSDVirtualDNSAddress }
   ::= {rsWSDVirtualDNSTable 1}

RsWSDVirtualDNSTableEntry ::= SEQUENCE {
  rsWSDVirtualDNSAddress    IpAddress,
  rsWSDVirtualDNSRedunType  INTEGER,
  rsWSDVirtualDNSStatus     RowStatus
}

rsWSDVirtualDNSAddress OBJECT-TYPE
  SYNTAX IpAddress
  ACCESS read-only
  STATUS mandatory
  DESCRIPTION
     "The virtual DNS address."
  ::=  {rsWSDVirtualDNSTableEntry 1}

rsWSDVirtualDNSRedunType OBJECT-TYPE
  SYNTAX INTEGER {
    active(1),
    backup(2)
  }
  ACCESS read-write
  STATUS mandatory
  DESCRIPTION
     "A virtual DNS address can be either active or backup. Backup addresses are the active addresses
      on a backed-up unit."
-- DEFVAL { active }
  ::=  {rsWSDVirtualDNSTableEntry 2}

rsWSDVirtualDNSStatus OBJECT-TYPE
  SYNTAX RowStatus
  ACCESS read-write
  STATUS mandatory
  DESCRIPTION
    "Row status for the virtual dns entry."
  ::=  {rsWSDVirtualDNSTableEntry 3}

rsWSDClientNAT  OBJECT IDENTIFIER ::= { rsNWSD 40 }

rsWSDClientNATRangeTable OBJECT-TYPE
   SYNTAX SEQUENCE OF RsWSDClientNATRangeIPEntry
   ACCESS not-accessible
   STATUS mandatory
   DESCRIPTION
          "In this table the WSD saves the client's IP ranges "
   ::= {rsWSDClientNAT 1}


rsWSDClientNATRangeIPEntry OBJECT-TYPE
    SYNTAX RsWSDClientNATRangeIPEntry
    ACCESS not-accessible
    STATUS  mandatory
    DESCRIPTION
       " The row definition for this table."
   INDEX  { rsWSDClientNATRangeIPFrom }
   ::= {rsWSDClientNATRangeTable 1}

RsWSDClientNATRangeIPEntry  ::= SEQUENCE {
  rsWSDClientNATRangeIPFrom             IpAddress,
  rsWSDClientNATRangeIPTo                 IpAddress,
  rsWSDClientNATRangeIPStatus            RowStatus
}

rsWSDClientNATRangeIPFrom OBJECT-TYPE
    SYNTAX IpAddress
    ACCESS  read-only
    STATUS  mandatory
    DESCRIPTION
      "The IP Address of the low boundary of the interval."
    ::= {rsWSDClientNATRangeIPEntry 1}

rsWSDClientNATRangeIPTo OBJECT-TYPE
    SYNTAX IpAddress
    ACCESS  read-write
    STATUS  mandatory
    DESCRIPTION
      "The IP Address of the high boundary of the interval."
    ::= {rsWSDClientNATRangeIPEntry 2}

rsWSDClientNATRangeIPStatus OBJECT-TYPE
   SYNTAX  RowStatus
   ACCESS  read-write
   STATUS  mandatory
   DESCRIPTION
       "The  status of this entry."
   ::= {rsWSDClientNATRangeIPEntry 3}

rsWSDNATRangeTable OBJECT-TYPE
   SYNTAX SEQUENCE OF RsWSDNATRangeIPEntry
   ACCESS not-accessible
   STATUS mandatory
   DESCRIPTION
          "In this table the WSD saves the NAT's IP ranges "
   ::= {rsWSDClientNAT 2}

rsWSDNATRangeIPEntry OBJECT-TYPE
    SYNTAX RsWSDNATRangeIPEntry
    ACCESS not-accessible
    STATUS  mandatory
    DESCRIPTION
       " The row definition for this table."
   INDEX  { rsWSDNATRangeIPFrom }
   ::= {rsWSDNATRangeTable 1}

RsWSDNATRangeIPEntry ::= SEQUENCE {
  rsWSDNATRangeIPFrom             IpAddress,
  rsWSDNATRangeIPTo               IpAddress,
  rsWSDNATRangeStatus             RowStatus
}

rsWSDNATRangeIPFrom OBJECT-TYPE
    SYNTAX IpAddress
    ACCESS  read-only
    STATUS  mandatory
    DESCRIPTION
      "The IP Address of the low boundary of the interval."
    ::= {rsWSDNATRangeIPEntry 1}

rsWSDNATRangeIPTo OBJECT-TYPE
    SYNTAX IpAddress
    ACCESS  read-write
    STATUS  mandatory
    DESCRIPTION
      "The IP Address of the high boundary of the interval."
    ::= {rsWSDNATRangeIPEntry 2}

rsWSDNATRangeStatus OBJECT-TYPE
 SYNTAX  RowStatus
   ACCESS  read-write
   STATUS  mandatory
   DESCRIPTION
       "The  status of this entry."
  ::= {rsWSDNATRangeIPEntry 3}

rsWSDClientNATStatus  OBJECT-TYPE
   SYNTAX INTEGER {
        enable(1),
        disable(2)
   }
   ACCESS  read-write
   STATUS  mandatory
   DESCRIPTION
       "Enable or disable the NAT client feature in WSD"
   DEFVAL { 2 }
   ::=  {rsWSDClientNAT 3 }


rsWSDSessionChaining  OBJECT-TYPE
   SYNTAX INTEGER {
        enable(1),
        disable(2)
   }
   ACCESS  read-write
   STATUS  mandatory
   DESCRIPTION
       "Enable or disable session chaining."
   DEFVAL { 1 }
   ::=  {rsNWSD 41 }



-- Application-specific traps for WSD
-- Each enterprise-specific trap has two bound variables describing the exact nature of
-- the trap. rndErrorDesc provides a detailed description of the problem, including the
-- related interface number, board number or any other applicable variable.
-- rndErrorSeverity describes the severity of this problem.

-- Trap template
-- -------------
--    TRAP-TYPE
--       ENTERPRISE  rsServerDispatcher
--       VARIABLES   { rndErrorDesc, rndErrorSeverity }
--       DESCRIPTION
--             ""
--       ::=
-- -------------

rsWSDTWTClientTableSize TRAP-TYPE
         ENTERPRISE rsNWSD
         VARIABLES { rndErrorDesc, rndErrorSeverity }
         DESCRIPTION
             "This informational trap is sent when client table threshold is
             reached."
     ::=  1

rsWSDTWTLogicServConnectLimit TRAP-TYPE
         ENTERPRISE rsNWSD
         VARIABLES { rndErrorDesc, rndErrorSeverity }
         DESCRIPTION
             "This informational trap is sent when a logical server connection
             limit threshold is reached."
     ::=  2

rsWSDTWTPhyServConnectLimit TRAP-TYPE
         ENTERPRISE rsNWSD
         VARIABLES { rndErrorDesc, rndErrorSeverity }
         DESCRIPTION
             "This informational trap is sent when a physical serevr
             connection limit threshold is reached."
     ::=  3

rsWSDTWTFarmCapacityLimit TRAP-TYPE
         ENTERPRISE rsNWSD
         VARIABLES { rndErrorDesc, rndErrorSeverity }
         DESCRIPTION
             "This informational trap is sent when a farm capacity limit
             threshold is reached."
     ::=  4

rsWSDTWTServBandwidthLimit TRAP-TYPE
         ENTERPRISE rsNWSD
         VARIABLES { rndErrorDesc, rndErrorSeverity }
         DESCRIPTION
             "This informational trap is sent when a server's bandwidth limit
             threshold is reached."
     ::=  5

rsWSDTWTFarmBandwidthLimit TRAP-TYPE
         ENTERPRISE rsNWSD
         VARIABLES { rndErrorDesc, rndErrorSeverity }
         DESCRIPTION
             "This informational trap is sent when a farm's bandwidth limit
             threshold is reached."
     ::=  6

   END
