--
-- OptiView Family Generic Module for Fluke Networks
--
-- Textual conventions, variables and event definitions common 
-- across entire OptiView Family products are defined here.
--

    FNET-OPTIVIEW-GENERIC-MIB DEFINITIONS ::= BEGIN

        IMPORTS
            DisplayString          FROM RFC1213-MIB
            OBJECT-TYPE              FROM RFC-1212
            TRAP-TYPE              FROM RFC-1215
            fnetOptiViewGeneric   FROM FNET-GLOBAL-REG;

        -- Textual Conventions

        OvTrapSeverity ::= INTEGER
            { inform(1),
              warning(2),
              minor(3),
              major(4),
              critical(5)
            }

        OvTrapStatus ::= INTEGER
            { discovered(1),
              resolved(2)
            }

        -- Variable Definitions

        ovStdTraps OBJECT IDENTIFIER
            -- Sub-tree to define standard trap variables
            ::= { fnetOptiViewGeneric 1 }

            ovTrapAgentSysName OBJECT-TYPE
                SYNTAX DisplayString (SIZE (0..255))
                ACCESS not-accessible
                STATUS mandatory
                DESCRIPTION
                    "The System Group name or best name of the agent
                    that generated the trap."
                ::= { ovStdTraps 1 }

            ovTrapSeverity OBJECT-TYPE
                SYNTAX OvTrapSeverity 
                ACCESS not-accessible
                STATUS mandatory
                DESCRIPTION
                    "Alarm severity information delivered with the trap.
                    Values are critical, major, minor, warning and
                    informational."
                ::= { ovStdTraps 2 }

            ovTrapStatus OBJECT-TYPE
                SYNTAX OvTrapStatus
                ACCESS not-accessible
                STATUS mandatory
                DESCRIPTION
                    "Status of the problem being reported.  Values are
                    discovered and resolved."
                ::= { ovStdTraps 3 }

            ovTrapDescription OBJECT-TYPE
                SYNTAX DisplayString (SIZE (0..255))
                ACCESS not-accessible
                STATUS mandatory
                DESCRIPTION
                    "The alarm description.  Probably the same string
                    as what is shown in the problem log."
                ::= { ovStdTraps 4 }

            ovTrapOffenderName OBJECT-TYPE
                SYNTAX DisplayString (SIZE (0..255))
                ACCESS not-accessible
                STATUS mandatory 
                DESCRIPTION
                    "The best name (MAC, IP, DNS or SNMP) of the host
                    that the alarm message is associated to."
                ::= { ovStdTraps 5 }

            ovTrapOffenderNetAddr OBJECT-TYPE
                SYNTAX DisplayString (SIZE (0..255))
                ACCESS not-accessible
                STATUS mandatory
                DESCRIPTION
                    "The network address (IP, IPX, NETBIOS DOMAIN) of
                    the host that the alarm message is associated to."
                ::= { ovStdTraps 6 }

            ovTrapOffenderPhyAddr OBJECT-TYPE
                SYNTAX DisplayString (SIZE (0..255))
                ACCESS not-accessible
                STATUS mandatory
                DESCRIPTION
                    "The MAC address of the host that the alarm message
                    is associated to."
                ::= { ovStdTraps 7 }

            ovTrapOffenderSubId OBJECT-TYPE
                SYNTAX INTEGER
                ACCESS not-accessible
                STATUS optional
                DESCRIPTION
                    "A secondary key to identify the problem instance.
                    This is used when more than one problem of the
                    SAME type can occur on the SAME offender.
                    
                    For example, some problems occur on a particular
                    interface of an offender host. In this case, an
                    NMS station can use the offender information along with 
                    this SubId to track the problem.
                    
                    The identifier is arbitrary and managed by the agent."

                ::= { ovStdTraps 8 }

        --
        -- Common Trap Definitions
        --
        -- Trap definitions common to multiple OptiView products are
        -- defined in this section.  The following specific trap values
        -- have been assigned:
        --
        --   1..9999      OptiView Common Traps
        --   10000..10999 OptiView Console
        --   11000..11999 OptiView INA/WGA
        --   12000..12999 OptiView WAN Fiber/Copper
        --

        ovProbDupIp TRAP-TYPE
            ENTERPRISE  fnetOptiViewGeneric
            VARIABLES { ovTrapAgentSysName, ovTrapSeverity,
                        ovTrapStatus, ovTrapDescription,
                        ovTrapOffenderName, ovTrapOffenderNetAddr,
                        ovTrapOffenderPhyAddr }
            DESCRIPTION
                "The SNMP trap that is generated when a duplicate IP
                is detected and generates an event that is configured
                for sending SNMP traps."
            ::= 1

        probBadMask TRAP-TYPE
            ENTERPRISE  fnetOptiViewGeneric
            VARIABLES { ovTrapAgentSysName, ovTrapSeverity,
                        ovTrapStatus, ovTrapDescription,
                        ovTrapOffenderName, ovTrapOffenderNetAddr }
            DESCRIPTION
                "Incorrect subnet mask."
            ::= 2
        
        ovProbBadDefRouter TRAP-TYPE
            ENTERPRISE  fnetOptiViewGeneric
            VARIABLES { ovTrapAgentSysName, ovTrapSeverity,
                        ovTrapStatus, ovTrapDescription,
                        ovTrapOffenderName, ovTrapOffenderNetAddr }
            DESCRIPTION
                "Default router not responding."
            ::= 3

        probLoneIp TRAP-TYPE
            ENTERPRISE  fnetOptiViewGeneric
            VARIABLES { ovTrapAgentSysName, ovTrapSeverity,
                        ovTrapStatus, ovTrapDescription,
                        ovTrapOffenderName, ovTrapOffenderNetAddr }
            DESCRIPTION
                "Lone ranger IP subnet."
            ::= 4
        
        probLoneNbDomain TRAP-TYPE
            ENTERPRISE  fnetOptiViewGeneric
            VARIABLES { ovTrapAgentSysName, ovTrapSeverity,
                        ovTrapStatus, ovTrapDescription,
                        ovTrapOffenderName, ovTrapOffenderNetAddr }
            DESCRIPTION
                "Lone ranger NetBIOS domain."
            ::= 5
        
        probLoneIpxNet TRAP-TYPE
            ENTERPRISE  fnetOptiViewGeneric
            VARIABLES { ovTrapAgentSysName, ovTrapSeverity,
                        ovTrapStatus, ovTrapDescription,
                        ovTrapOffenderName, ovTrapOffenderNetAddr }
            DESCRIPTION
                "Lone ranger IPX network."
            ::= 6
        
        probLoneIpxType TRAP-TYPE
            ENTERPRISE  fnetOptiViewGeneric
            VARIABLES { ovTrapAgentSysName, ovTrapSeverity,
                        ovTrapStatus, ovTrapDescription,
                        ovTrapOffenderName, ovTrapOffenderNetAddr }
            DESCRIPTION
                "Lone ranger IPX encaps for a network."
            ::= 7
        
        probKeyDevNoResp TRAP-TYPE
            ENTERPRISE  fnetOptiViewGeneric
            VARIABLES { ovTrapAgentSysName, ovTrapSeverity,
                        ovTrapStatus, ovTrapDescription,
                        ovTrapOffenderName, ovTrapOffenderNetAddr }
            DESCRIPTION
                "Key Device not responding."
            ::= 8 

        probReboot TRAP-TYPE
            ENTERPRISE  fnetOptiViewGeneric
            VARIABLES { ovTrapAgentSysName, ovTrapSeverity,
                        ovTrapStatus, ovTrapDescription,
                        ovTrapOffenderName, ovTrapOffenderNetAddr }
            DESCRIPTION
                "ThisOptiview has powered on or rebooted.
                  (ovTrapSeverity = inform)"
            ::= 9 

        probRerunTest TRAP-TYPE
            ENTERPRISE  fnetOptiViewGeneric
            VARIABLES { ovTrapAgentSysName, ovTrapSeverity,
                        ovTrapStatus, ovTrapDescription,
                        ovTrapOffenderName, ovTrapOffenderNetAddr }
            DESCRIPTION
                "A user has cleared historical data and started
                 a new test. (ovTrapSeverity = inform)"
            ::= 10 
        
    END
