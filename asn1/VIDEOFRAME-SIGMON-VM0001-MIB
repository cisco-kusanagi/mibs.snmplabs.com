VIDEOFRAME-SIGMON-VM0001-MIB DEFINITIONS ::= BEGIN

	--  Relationship to Other MIBs
	--
	--
	--  The objects defined in this MIB are located under the
	--  private.enterprises subtree as shown below:
	--
	--               iso(1).org(3).dod(6).internet(1)
	--                            |
	--                         private(4)
	--                            |
	--                       enterprises(1)
	--                            |
	--                       videoframe(4596)
	--                            |
	--                      vfProducts(4)
	--							  |
	--						vfSigmonFrame(2)
	--							  |
	--					  vfSigmonFrameModules(1)
	--							  |
	--					   vm0001AnalogAudio(1)
	--                                 
	--
	--  References
	--
	--  [1]  RFC 1902.  McCloghrie, K., and M. Rose, "Structure 
	--       of Management Information for Version 2 of the Simple
	--       Network Management Protocol (SNMPv2)".  
	--       January, 1996.
	--
	--  [2]  RFC 1903.  McCloghrie, K., and M. Rose, "Textual
	--       Conventions for Version 2 of the Simple Network
	--       Management Protocol (SNMPv2)".  
	--       January, 1996.
	--
	--  [3]  RFC 1904.  McCloghrie, K., and M. Rose, "Conformance
	--       Statements for Version 2 of the Simple Network
	--       Management Protocol (SNMPv2)".  
	--       January, 1996.
	--
	--  [4]  RFC 1907.  McCloghrie, K., and M. Rose, "Management 
	--       Information Base for Version 2 of the Simple Network
	--       Management Protocol (SNMPv2)".  
	--       January, 1996.
	--
	--	[5]  Perkins, David and McGinnis, Evan; "Understanding SNMP
	--		 MIBs".  Prentice Hall, ISBN 0-13-437708-7, 1997.
	--
	--
	--  Object Synopsis
	--  
	--
	--  All objects within this MIB are prefixed with the OBJECT
	--  IDENTIFIER "p", where "p" is:
	--
	--  iso(1).org(3).dod(6).internet(1).private(4).enterprises(1).
	--          videoframe(4596).vfProducts(4).vfSigmonFrame(2).
	--			vfSigmonFrameModuleTypes(1)
	--	
	--  or, 1.3.6.1.4.1.4596.4.2.1
	--
	--
	--  Object Name                               Object Id         
	--  --------------------------------          --------------
	--
	--	vm0001AnalogAudio							p.1
	--		vm0001Table								p.1.1
	--		vm0001TableEntry						p.1.1.1
	--			vm0001SlotNumber					p.1.1.1.1.m		m = slot #
	--			vm0001Active						p.1.1.1.2.m
	--			vm0001FirmwareRev					p.1.1.1.3.m
	--			vm0001Locate						p.1.1.1.4.m
	--		vm0001SignalTable						p.1.2
	--		vm0001SignalEntry						p.1.2.1
	--			vm0001SignalSlotNumber				p.1.2.1.1.m.n	m = slot #, n = signal #
	--			vm0001SignalNumber					p.1.2.1.2.m.n
	--			vm0001SignalName					p.1.2.1.3.m.n
	--			vm0001SignalDescription				p.1.2.1.4.m.n
	--			vm0001CurrentAplRaw					p.1.2.1.5.m.n
	--			vm0001ZerodBCalibrationSet			p.1.2.1.6.m.n
	--			vm0001ZerodBCalibrationValue		p.1.2.1.7.m.n
	--			vm0001AplHighThreshold				p.1.2.1.8.m.n
	--			vm0001AplHighDuration				p.1.2.1.9.m.n
	--			vm0001AplHighAlarmState				p.1.2.1.10.m.n
	--			vm0001AplHighAlarmAck				p.1.2.1.11.m.n
	--			vm0001AplHighTrapEnable				p.1.2.1.12.m.n
	--			vm0001AplLowThreshold				p.1.2.1.13.m.n
	--			vm0001AplLowDuration				p.1.2.1.14.m.n
	--			vm0001AplLowAlarmState				p.1.2.1.15.m.n
	--			vm0001AplLowAlarmAck				p.1.2.1.16.m.n
	--			vm0001AplLowTrapEnable				p.1.2.1.17.m.n
	--			vm0001PeakThreshold					p.1.2.1.18.m.n
	--			vm0001PeakPeriod					p.1.2.1.19.m.n
	--			vm0001PeakAlarmState				p.1.2.1.20.m.n
	--			vm0001PeakAlarmAck					p.1.2.1.21.m.n
	--			vm0001PeakTrapEnable				p.1.2.1.22.m.n
	--		vm0001StereoPairTable                   p.1.3
	--		vm0001StereoPairEntry					p.1.3.1 
	--			vm0001StereoPairSlotNumber			p.1.3.1.1.m.n	m = slot #, n = stereo pair #
	--			vm0001StereoPairNumber				p.1.3.1.2.m.n
	--			vm0001StereoPairName				p.1.3.1.3.m.n
	--			vm0001StereoPairDescription			p.1.3.1.4.m.n
	--			vm0001MonoFilter					p.1.3.1.5.m.n
	--			vm0001MonoDuration					p.1.3.1.6.m.n
	--			vm0001MonoAlarmState				p.1.3.1.7.m.n
	--			vm0001MonoAlarmAck					p.1.3.1.8.m.n
	--			vm0001MonoTrapEnable				p.1.3.1.9.m.n
	--			vm0001StereoOutOfPhaseFilter		p.1.3.1.10.m.n
	--			vm0001StereoOutOfPhaseDuration		p.1.3.1.11.m.n
	--			vm0001StereoOutOfPhaseAlarmState	p.1.3.1.12.m.n
	--			vm0001StereoOutOfPhaseAlarmAck		p.1.3.1.13.m.n
	--		vm0001AnalogAudioEvents					p.1.4
	--			vm0001AnalogAudioEventsV2				p.1.4.0
	--				analogAudioAPLHighAlarm				p.1.4.0.1
	--				analogAudioAPLLowAlarm				p.1.4.0.2
	--				analogAudioPeakAlarm				p.1.4.0.3
	--				analogAudioMonoAlarm				p.1.4.0.4
	--				analogAudioStereoOutOfPhaseAlarm	p.1.4.0.5
	--    

	IMPORTS
		OBJECT-TYPE FROM RFC1155-SMI
		MODULE-IDENTITY, OBJECT-IDENTITY, NOTIFICATION-TYPE,
		Integer32, IpAddress
			FROM SNMPv2-SMI
		DisplayString, RowStatus
			FROM SNMPv2-TC
		MODULE-COMPLIANCE, OBJECT-GROUP
			FROM SNMPv2-CONF
		vfMIBModules
			FROM VIDEOFRAME-REGISTRATIONS-MIB
		vfBoxId
			FROM VIDEOFRAME-GENERIC-MIB
		vfSigmonFrameModuleTypes, vfProductsVF200Reg, vfFrameSlotNumber
			FROM VIDEOFRAME-SIGMON-MIB;

	videoframeSigmonVm0001MIB MODULE-IDENTITY
		LAST-UPDATED "0108300000Z"
		ORGANIZATION "Videoframe Systems"
		CONTACT-INFO
			"Videoframe Systems
			P.O. Box 1991,
			Grass Valley, CA 95945, USA.

			+1 (530) 477-2000

			http://www.videoframesystems.com"
	DESCRIPTION
		"This MIB describes the device specific objects of the VM0001
		Analog Audio Monitoring module, and augments MIB-2, VF-GENERIC,
		and VF-SIGMON in the identification of this Videoframe Systems
		managed device.

		This module will be extended or modified as required.

		Videoframe Systems reserves the right to
		make changes in specification and other 
		information contained in this document without 
		prior notice. The reader should consult Videoframe Systems
		to determine whether any such changes have been made.

		In no event shall Videoframe Systems be 
		liable for any incidental, indirect, special, 
		or consequential damages whatsoever (including 
		but not limited to lost profits) arising out of 
		or related to this document or the information 
		contained in it.

		Videoframe Systems grants vendors, end users, 
		and other interested parties a non-exclusive 
		license to use this specification in connection 
		with the management of Videoframe Systems products.

		Copyright 2001 Videoframe, Inc."
	REVISION      "0108300000Z"
	DESCRIPTION
		"First release."
	::= { vfMIBModules 4 }

	--
	-- VM0001 product registration. vfProductsVF200Reg is from
	-- vf-sigmon
	--

vfProductsVM0001Reg OBJECT-IDENTITY
		STATUS	current
		DESCRIPTION
			"Videoframe VM0001 Analog Audio Monitoring Module."
		::= { vfProductsVF200Reg 1 }

	--
	--  The VM0001 MIB top-level groups
	--

	-- root of this MIB module
vm0001AnalogAudio		OBJECT IDENTIFIER ::= { vfSigmonFrameModuleTypes 1 }

	--
	-- Other signal monitoring modules, whose management information is defined in
	-- other MIB modules.
	--
	--		vm0002AnalogVideo		OBJECT IDENTIFIER ::= { vfSigmonFrameModuleTypes 2 }
	--		vm0003AESEBUAudio		OBJECT IDENTIFIER ::= { vfSigmonFrameModuleTypes 3 }
	--		vm0004SDIVideo			OBJECT IDENTIFIER ::= { vfSigmonFrameModuleTypes 4 }
	--		vm0005SerialIO			OBJECT IDENTIFIER ::= { vfSigmonFrameModuleTypes 5 }
	--		vm0006GPIInterface		OBJECT IDENTIFIER ::= { vfSigmonFrameModuleTypes 6 }
	--		vm0007TransferSwitch	OBJECT IDENTIFIER ::= { vfSigmonFrameModuleTypes 7 }
	--		vm0008CPU				OBJECT IDENTIFIER ::= { vfSigmonFrameModuleTypes 8 }
	--		vm0009DTMFTransceiver	OBJECT IDENTIFIER ::= { vfSigmonFrameModuleTypes 9 }
	--		vm0010GPOInterface		OBJECT IDENTIFIER ::= { vfSigmonFrameModuleTypes 10 }
	--		vm0011GPIOInterface		OBJECT IDENTIFIER ::= { vfSigmonFrameModuleTypes 11 }
	--

vm0001Table	OBJECT-TYPE
	SYNTAX	SEQUENCE OF Vm0001Entry
	MAX-ACCESS	not-accessible
	STATUS	current
	DESCRIPTION
		"Each row contains information about one VM0001 Analog Audio
		 module in the managed VF200 frame."

	::=	{ vm0001AnalogAudio 1}


vm0001Entry	OBJECT-TYPE
	SYNTAX	Vm0001Entry
    MAX-ACCESS not-accessible
    STATUS     current
    DESCRIPTION
        "An Analog Audio module entry."
	INDEX { vfFrameSlotNumber }
    ::= { vm0001Table 1 } 
		
Vm0001Entry   ::= 
    SEQUENCE	{
		vm0001SlotNumber	INTEGER,
		vm0001Active		INTEGER,
		vm0001FirmwareRev	DisplayString,
		vm0001Locate		INTEGER
				}	

vm0001SlotNumber OBJECT-TYPE
		SYNTAX	INTEGER (1..12)				
		MAX-ACCESS	read-only
		STATUS		current
		DESCRIPTION
			"The slot that this entry represents."
	::= { vm0001Entry 1 }

vm0001Active OBJECT-TYPE
		SYNTAX	INTEGER
					{
						active(1),
						inactive(2)
					}				
		MAX-ACCESS	read-only
		STATUS		current
		DESCRIPTION
			"Indicates whether this entry is active (this module is in
			 this slot)."
	::= { vm0001Entry 2 }

vm0001FirmwareRev OBJECT-TYPE
		SYNTAX		DisplayString (SIZE(0..20))
		MAX-ACCESS	read-only
		STATUS		current
		DESCRIPTION
			"The revision level of the firmware on 
			this module."
	::= { vm0001Entry 3 }

vm0001Locate OBJECT-TYPE
		SYNTAX	INTEGER
					{
						flash(1),
						off(2)
					}				
		MAX-ACCESS	read-write
		STATUS		current
		DESCRIPTION
			"Controls the locate indicator on the module and indicates its
			 current state.  Set to flash (1) to cause the locate LED on the
			 front of the module to begin flashing.  Set to off to stop flashing."
	::= { vm0001Entry 4 }

vm0001SignalTable	OBJECT-TYPE
	SYNTAX	SEQUENCE OF Vm0001SignalEntry
	MAX-ACCESS	not-accessible
	STATUS	current
	DESCRIPTION
		"Each row contains information about one channel of one VM0001 Analog Audio
		 module in the managed VF200 frame."

	::=	{ vm0001AnalogAudio 2}


vm0001SignalEntry	OBJECT-TYPE
	SYNTAX	Vm0001SignalEntry
    MAX-ACCESS not-accessible
    STATUS     current
    DESCRIPTION
        "An Analog Audio module channel entry."
	INDEX { vfFrameSlotNumber, vm0001SignalNumber }
    ::= { vm0001SignalTable 1 } 
		
Vm0001SignalEntry   ::= 
    SEQUENCE	{
		vm0001SignalSlotNumber			INTEGER,
		vm0001SignalNumber				INTEGER,
		vm0001SignalName				DisplayString,
		vm0001SignalDescription			DisplayString,
   		vm0001CurrentAplRaw				INTEGER,
		vm0001ZerodBCalibrationSet		INTEGER,
		vm0001ZerodBCalibrationValue	INTEGER,
		vm0001AplHighThreshold			INTEGER,
		vm0001AplHighDuration			INTEGER,
		vm0001AplHighAlarmState			INTEGER,
		vm0001AplHighAlarmAck			INTEGER,
		vm0001AplHighTrapEnable			INTEGER,
		vm0001AplLowThreshold			INTEGER,
		vm0001AplLowDuration			INTEGER,
		vm0001AplLowAlarmState			INTEGER,
		vm0001AplLowAlarmAck			INTEGER,
		vm0001AplLowTrapEnable			INTEGER,
		vm0001PeakThreshold				INTEGER,
		vm0001PeakPeriod				INTEGER,
		vm0001PeakAlarmState			INTEGER,
		vm0001PeakAlarmAck				INTEGER,
		vm0001PeakTrapEnable			INTEGER
		}

vm0001SignalSlotNumber OBJECT-TYPE
		SYNTAX	INTEGER (1..12)				
		MAX-ACCESS	read-only
		STATUS		current
		DESCRIPTION
			"The frame slot number that this entry represents."
	::= { vm0001SignalEntry 1 }

vm0001SignalNumber OBJECT-TYPE
		SYNTAX		INTEGER(1..4)
		MAX-ACCESS	read-only
		STATUS		current
		DESCRIPTION
			"The channel within the module to which this signal is connected."
	::= { vm0001SignalEntry 2 }

vm0001SignalName OBJECT-TYPE
		SYNTAX		DisplayString (SIZE(0..20))
		MAX-ACCESS	read-write
		STATUS		current
		DESCRIPTION
			"The name of the signal connected to this channel."
	::= { vm0001SignalEntry 3 }

vm0001SignalDescription OBJECT-TYPE
		SYNTAX		DisplayString (SIZE(0..120))
		MAX-ACCESS	read-write
		STATUS		current
		DESCRIPTION
			"Descriptive identification of the signal connected to this channel."
	::= { vm0001SignalEntry 4 }

vm0001CurrentAplRaw	OBJECT-TYPE
		SYNTAX	INTEGER(0..131071)
		MAX-ACCESS	read-only
		STATUS		current
		DESCRIPTION
			"The current average amplitude value on this channel,
			 in raw sample units."
	::= { vm0001SignalEntry 5 }
			  
vm0001ZerodBCalibrationSet	OBJECT-TYPE
		SYNTAX	INTEGER
			{
				ready(1),
				go(2),
				notReady(3)
			}
		MAX-ACCESS	read-write
		STATUS		current
		DESCRIPTION
			"Set to 'go' (2) to set the value of the 0 dB channel
			 calibration to the current average amplitude value on
			 this channel."
	::= { vm0001SignalEntry 6 }
			  
vm0001ZerodBCalibrationValue	OBJECT-TYPE
		SYNTAX	INTEGER(0..131071)
		MAX-ACCESS	read-only
		STATUS		current
		DESCRIPTION
			"The current raw sample amplitude value used as the 0 dB
			 reference on this channel."
	::= { vm0001SignalEntry 7 }
			  
vm0001AplHighThreshold OBJECT-TYPE
		SYNTAX	INTEGER(-80..30)				
		MAX-ACCESS	read-write
		STATUS		current
		DESCRIPTION
			"The high APL alarm threshold for this
			channel, in dB."
	::= { vm0001SignalEntry 8 }

vm0001AplHighDuration OBJECT-TYPE
		SYNTAX	INTEGER(0..2147483647)				
		MAX-ACCESS	read-write
		STATUS		current
		DESCRIPTION
			"The high APL duration, in milliseconds, at which to alarm, for
			this channel."
	::= { vm0001SignalEntry 9 }

vm0001AplHighAlarmState	OBJECT-TYPE
		SYNTAX	INTEGER
				{
					ready(1),
					triggered(2)
				}
		MAX-ACCESS	read-only
		STATUS		current
		DESCRIPTION
			"The current state of the high APL alarm for this
			channel."
	::= { vm0001SignalEntry 10 }

vm0001AplHighAlarmAck	OBJECT-TYPE
		SYNTAX	INTEGER
				{
					idle(1),
					unacknowledged(2),
					acknowledge(3)
				}
		MAX-ACCESS	read-write
		STATUS		current
		DESCRIPTION
			"Set to acknowledge (3) to acknowledge a triggered high APL alarm for
			this channel."
	::= { vm0001SignalEntry 11 }

vm0001AplHighTrapEnable OBJECT-TYPE
		SYNTAX	INTEGER
					{
						enabled(1),
						disabled(2)
					}				
		MAX-ACCESS	read-write
		STATUS		current
		DESCRIPTION
			"Set to enabled (1) to enable the high APL alarm trap for
			this channel."
	::= { vm0001SignalEntry 12 }

vm0001AplLowThreshold OBJECT-TYPE
		SYNTAX	INTEGER(-80..30)				
		MAX-ACCESS	read-write
		STATUS		current
		DESCRIPTION
			"The low APL alarm threshold for this channel, in dB."
	::= { vm0001SignalEntry 13 }

vm0001AplLowDuration OBJECT-TYPE
		SYNTAX	INTEGER(0..2147483647)				
		MAX-ACCESS	read-write
		STATUS		current
		DESCRIPTION
			"The low APL duration, in milliseconds, at which to alarm, for
			this channel."
	::= { vm0001SignalEntry 14 }

vm0001AplLowAlarmState	OBJECT-TYPE
		SYNTAX	INTEGER
				{
					ready(1),
					triggered(2)
				}
		MAX-ACCESS	read-only
		STATUS		current
		DESCRIPTION
			"The current state of the low APL alarm for
			this channel."
	::= { vm0001SignalEntry 15 }

vm0001AplLowAlarmAck	OBJECT-TYPE
		SYNTAX	INTEGER
				{
					idle(1),
					unacknowledged(2),
					acknowledge(3)
				}
		MAX-ACCESS	read-write
		STATUS		current
		DESCRIPTION
			"Set to acknowledge (3) to acknowledge a triggered low APL alarm for
			this channel."
	::= { vm0001SignalEntry 16 }

vm0001AplLowTrapEnable OBJECT-TYPE
		SYNTAX	INTEGER				
					{
						enabled(1),
						disabled(2)
					}				
		MAX-ACCESS	read-write
		STATUS		current
		DESCRIPTION
			"Set to enabled (1) to enable the low APL alarm trap for
			this channel."
	::= { vm0001SignalEntry 17 }

vm0001PeakThreshold	OBJECT-TYPE
		SYNTAX	INTEGER(-80..30)
		MAX-ACCESS	read-write
		STATUS		current
		DESCRIPTION
			"The peak level above which to alarm."
	::= { vm0001SignalEntry 18 }

vm0001PeakPeriod	OBJECT-TYPE
		SYNTAX	INTEGER(0..2147483647)				
		MAX-ACCESS	read-write
		STATUS		current
		DESCRIPTION
			"The period, in milliseconds, over which the peak value
			 is accumulated for this channel."
	::= { vm0001SignalEntry 19 }

vm0001PeakAlarmState	OBJECT-TYPE
		SYNTAX	INTEGER
				{
					ready(1),
					triggered(2)
				}
		MAX-ACCESS	read-only
		STATUS		current
		DESCRIPTION
			"The current state of the peak-threshold-exceeded alarm for
			this channel."
	::= { vm0001SignalEntry 20 }

vm0001PeakAlarmAck	OBJECT-TYPE
		SYNTAX	INTEGER
				{
					idle(1),
					unacknowledged(2),
					acknowledge(3)
				}
		MAX-ACCESS	read-write
		STATUS		current
		DESCRIPTION
			"Set to acknowledge (3) to acknowledge a triggered peak alarm for
			this channel."
	::= { vm0001SignalEntry 21 }

vm0001PeakTrapEnable	OBJECT-TYPE
		SYNTAX	INTEGER
				{
					enabled(1),
					disabled(2)
				}
		MAX-ACCESS	read-write
		STATUS		current
		DESCRIPTION
			"Set to enabled (1) to enable the peak alarm trap for
			this channel."
	::= { vm0001SignalEntry 22 }

vm0001StereoPairTable	OBJECT-TYPE
	SYNTAX	SEQUENCE OF Vm0001StereoPairEntry
	MAX-ACCESS	not-accessible
	STATUS	current
	DESCRIPTION
		"Each row contains information about one stereo pair on
		 one VM0001 Analog Audio module in the managed VF200 frame."

	::=	{ vm0001AnalogAudio 3 }


vm0001StereoPairEntry	OBJECT-TYPE
	SYNTAX	Vm0001StereoPairEntry
    MAX-ACCESS not-accessible
    STATUS     current
    DESCRIPTION
        "An Analog Audio module channel entry."
	INDEX { vm0001StereoPairSlotNumber, vm0001StereoPairNumber }
    ::= { vm0001StereoPairTable 1 } 
		
Vm0001StereoPairEntry   ::= 
    SEQUENCE	{
		vm0001StereoPairSlotNumber			INTEGER,
		vm0001StereoPairNumber				DisplayString,
		vm0001StereoPairName				DisplayString,
		vm0001StereoPairDescription			DisplayString,
		vm0001MonoFilter					INTEGER,
		vm0001MonoDuration					Integer32,
		vm0001MonoAlarmState				INTEGER,
		vm0001MonoAlarmAck					INTEGER,
		vm0001MonoTrapEnable				INTEGER,
		vm0001StereoOutOfPhaseFilter		INTEGER,
		vm0001StereoOutOfPhaseDuration		Integer32,
		vm0001StereoOutOfPhaseAlarmState	INTEGER,
		vm0001StereoOutOfPhaseAlarmAck		INTEGER
				}

vm0001StereoPairSlotNumber OBJECT-TYPE
		SYNTAX	INTEGER (1..12)				
		MAX-ACCESS	read-only
		STATUS		current
		DESCRIPTION
			"The slot that this entry represents."
	::= { vm0001StereoPairEntry 1 }

vm0001StereoPairNumber OBJECT-TYPE
		SYNTAX		DisplayString (SIZE(0..20))
		MAX-ACCESS	read-write
		STATUS		current
		DESCRIPTION
			"The channel within the module to which this signal is connected."
	::= { vm0001StereoPairEntry 2 }

vm0001StereoPairName OBJECT-TYPE
		SYNTAX		DisplayString (SIZE(0..20))
		MAX-ACCESS	read-write
		STATUS		current
		DESCRIPTION
			"The name of the signal connected to this channel."
	::= { vm0001StereoPairEntry 3 }

vm0001StereoPairDescription OBJECT-TYPE
		SYNTAX		DisplayString (SIZE(0..120))
		MAX-ACCESS	read-write
		STATUS		current
		DESCRIPTION
			"Descriptive identifier of the signal connected to this channel."
	::= { vm0001StereoPairEntry 4 }

vm0001MonoFilter	OBJECT-TYPE
		SYNTAX	INTEGER(1..8)
		MAX-ACCESS	read-write
		STATUS		current
		DESCRIPTION
			"The filter type currently selected for the mono alarm for
			this stereo pair."
	::= { vm0001StereoPairEntry 5 }

vm0001MonoDuration	OBJECT-TYPE
		SYNTAX	Integer32
		MAX-ACCESS	read-write
		STATUS		current
		DESCRIPTION
			"The mono duration, in milliseconds, at which to alarm, for
			this stereo pair."
	::= { vm0001StereoPairEntry 6 }

vm0001MonoAlarmState	OBJECT-TYPE
		SYNTAX	INTEGER
				{
					ready(1),
					triggered(2)
				}
		MAX-ACCESS	read-write
		STATUS		current
		DESCRIPTION
			"The current state of the mono alarm for
			this stereo pair."
	::= { vm0001StereoPairEntry 7 }

vm0001MonoAlarmAck	OBJECT-TYPE
		SYNTAX	INTEGER
				{
					idle(1),
					unacknowledged(2),
					acknowledge(3)
			}
		MAX-ACCESS	read-write
		STATUS		current
		DESCRIPTION
			"Set to acknowledge (3) to acknowledge a triggered mono alarm for
			this stereo pair."
	::= { vm0001StereoPairEntry 8 }

vm0001MonoTrapEnable	OBJECT-TYPE
		SYNTAX	INTEGER
				{
					enabled(1),
					disabled(2)
				}
		MAX-ACCESS	read-write
		STATUS		current
		DESCRIPTION
			"Set to enabled (1) to enable the high APL alarm trap for
			this stereo pair."
	::= { vm0001StereoPairEntry 9 }

vm0001StereoOutOfPhaseFilter	OBJECT-TYPE
		SYNTAX	INTEGER(1..8)
		MAX-ACCESS	read-write
		STATUS		current
		DESCRIPTION
			"The filter type currently selected for the stereo out of
			 phase alarm for this stereo pair."
	::= { vm0001StereoPairEntry 10 }

vm0001StereoOutOfPhaseDuration	OBJECT-TYPE
		SYNTAX	Integer32
		MAX-ACCESS	read-write
		STATUS		current
		DESCRIPTION
			"The stereo out of phase duration, in milliseconds, at which
			 to alarm, for this stereo pair."
	::= { vm0001StereoPairEntry 11 }

vm0001StereoOutOfPhaseAlarmState	OBJECT-TYPE
		SYNTAX	INTEGER
				{
					ready(1),
					triggered(2)
				}
		MAX-ACCESS	read-only
		STATUS		current
		DESCRIPTION
			"The current state of the stereo out of phase alarm for
			this stereo pair."
	::= { vm0001StereoPairEntry 12 }

vm0001StereoOutOfPhaseAlarmAck	OBJECT-TYPE
		SYNTAX	INTEGER
				{
					idle(1),
					unacknowledged(2),
					acknowledge(3)
				}
		MAX-ACCESS	read-write
		STATUS		current
		DESCRIPTION
			"Set to acknowledge (3) to acknowledge a triggered stereo
			 out of phase alarm for this stereo pair."
	::= { vm0001StereoPairEntry 13 }

	--
	-- VM0001 Events
	--

vm0001AnalogAudioEvents		OBJECT IDENTIFIER ::= { vm0001AnalogAudio 4 }
vm0001AnalogAudioEventsV2	OBJECT IDENTIFIER ::= { vm0001AnalogAudioEvents 0 }

analogAudioAPLHighAlarm	NOTIFICATION-TYPE
		OBJECTS
			{
				vfBoxId,
				vm0001SlotNumber,
				vm0001SignalNumber,
				vm0001SignalName,
				vm0001SignalDescription
			}
		STATUS	current
		DESCRIPTION
			"An Analog Audio APL high alarm was triggered."
		::= { vm0001AnalogAudioEventsV2 1 }

analogAudioAPLLowAlarm	NOTIFICATION-TYPE
		OBJECTS
			{
				vfBoxId,
				vm0001SlotNumber,
				vm0001SignalNumber,
				vm0001SignalName,
				vm0001SignalDescription
			}
		STATUS	current
		DESCRIPTION
			"An Analog Audio APL low alarm was triggered."
		::= { vm0001AnalogAudioEventsV2 2 }

analogAudioPeakAlarm	NOTIFICATION-TYPE
		OBJECTS
			{
				vfBoxId,
				vm0001SlotNumber,
				vm0001SignalNumber,
				vm0001SignalName,
				vm0001SignalDescription
			}
		STATUS	current
		DESCRIPTION
			"An Analog Audio peak threshold exceeded alarm was triggered."
		::= { vm0001AnalogAudioEventsV2 3 }

analogAudioMonoAlarm	NOTIFICATION-TYPE
		OBJECTS
			{
				vfBoxId,
				vm0001StereoPairSlotNumber,
				vm0001StereoPairNumber,
				vm0001StereoPairName,
				vm0001StereoPairDescription
			}
		STATUS	current
		DESCRIPTION
			"An Analog Audio mono alarm was triggered."
		::= { vm0001AnalogAudioEventsV2 4 }

analogAudioStereoOutOfPhaseAlarm	NOTIFICATION-TYPE
		OBJECTS
			{
				vfBoxId,
				vm0001StereoPairSlotNumber,
				vm0001StereoPairNumber,
				vm0001StereoPairName,
				vm0001StereoPairDescription
			}
		STATUS	current
		DESCRIPTION
			"An Analog Audio stereo out of phase alarm was triggered."
		::= { vm0001AnalogAudioEventsV2 5 }


END
