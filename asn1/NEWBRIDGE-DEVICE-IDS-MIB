--------------------------------------------------------------------------------
-- file: NewbridgeDeviceIds.mib
--
-- contents:
--	This file contains the number assignments for the Newbridge MIB 
--      Device IDs
--
-- history:
--	NA  / 96.07.10 / M. Paquette / Creation
--	NA  / 96.10.10 / M. Paquette / add nncXcellys
--	NA  / 96.10.24 / M. Paquette / add nncCampusSwitch
--
--      ***** WARNING **** Numbers in this file are allocated by Numbers Admin!
--	***** This file may not be changed by anyone but Numbers Admin *****
--
-- %%history-start%%
-- 1999.06.15 jayanthi P.285550: Checking in new MIB module from regional as 
--   it contains device Ids now. 
-- %%history-end%%
--
-- Copyright 1996 Newbridge Networks Corporation.  All Rights Reserved
--------------------------------------------------------------------------------
NEWBRIDGE-DEVICE-IDS-MIB	DEFINITIONS ::= BEGIN
	
	IMPORTS	
		nncDeviceIDs
			FROM NNCGNI0001-SMI;
		
--
-- Device IDs
--
	nncStandalone  		 OBJECT IDENTIFIER ::= { nncDeviceIDs 1  }
        nnc8230        		 OBJECT IDENTIFIER ::= { nncStandalone 1 }
        nnc3604        		 OBJECT IDENTIFIER ::= { nncStandalone 2 }
        nnc8231        		 OBJECT IDENTIFIER ::= { nncStandalone 3 }
        nnc8251        		 OBJECT IDENTIFIER ::= { nncStandalone 4 }
        nnc3601        		 OBJECT IDENTIFIER ::= { nncStandalone 5 }
        nncWGS      		 OBJECT IDENTIFIER ::= { nncStandalone 6 }
        nncYRidge   		 OBJECT IDENTIFIER ::= { nncStandalone 7 }
        nncSystemManager	 OBJECT IDENTIFIER ::= { nncStandalone 8 }
        nncRouteServer 		 OBJECT IDENTIFIER ::= { nncStandalone 9 }
        nnc36170    		 OBJECT IDENTIFIER ::= { nncStandalone 10 }
        nnc36150    		 OBJECT IDENTIFIER ::= { nncStandalone 11 }
        nncNicSbus		 OBJECT IDENTIFIER ::= { nncStandalone 12 }
        nncNicIr5x		 OBJECT IDENTIFIER ::= { nncStandalone 13 }
        nnc48020		 OBJECT IDENTIFIER ::= { nncStandalone 14 }
        nncBRidge		 OBJECT IDENTIFIER ::= { nncStandalone 15 }
        nncELSU			 OBJECT IDENTIFIER ::= { nncStandalone 16 }
        nncTRLSU		 OBJECT IDENTIFIER ::= { nncStandalone 17 }
        nnc3620			 OBJECT IDENTIFIER ::= { nncStandalone 18 }
        nnc3624			 OBJECT IDENTIFIER ::= { nncStandalone 19 }
        nncOrangeRi		 OBJECT IDENTIFIER ::= { nncStandalone 20 }
        nncRedRidge		 OBJECT IDENTIFIER ::= { nncStandalone 21 }
        nnc38010		 OBJECT IDENTIFIER ::= { nncStandalone 22 }
        nncNicPci		 OBJECT IDENTIFIER ::= { nncStandalone 23 }
        nnc10BFLRid		 OBJECT IDENTIFIER ::= { nncStandalone 24 }
        nncXcellys		 OBJECT IDENTIFIER ::= { nncStandalone 25 }
        nncCampusSwitch		 OBJECT IDENTIFIER ::= { nncStandalone 26 }

        nncIntegral    		 OBJECT IDENTIFIER ::= { nncDeviceIDs 2 }
        nncITB         		 OBJECT IDENTIFIER ::= { nncIntegral 1  }
		
END
