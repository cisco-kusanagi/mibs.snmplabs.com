-- 
-- Copyright 1999 by Fore Systems, Inc. 
-- Converted to SMIv2 rfc 2578,2579,2580 - STD 58
--
-- Copyright 1996 by Fore Systems, Inc.  All rights reserved.

-- This file contains definitions for management information for extensions to
-- the Bridge MIB (RFC-1493) needed for products produced by FORE Systems, Inc.

--------------------------------------------------------------------------------

FORE-BRIDGE-MIB DEFINITIONS ::= BEGIN

IMPORTS
	OBJECT-TYPE,
	MODULE-IDENTITY,
        Counter32, Integer32    FROM SNMPv2-SMI
        DisplayString           FROM SNMPv2-TC
	BridgeId		FROM BRIDGE-MIB
	preDot1qVlanMIB         FROM Fore-Common-MIB;


foreBridgeExtensions MODULE-IDENTITY
        LAST-UPDATED         "9911050000Z"
        ORGANIZATION         "FORE"
        CONTACT-INFO         
             "      Postal:   FORE Systems Inc.
                              1000 FORE Drive
                              Warrendale, PA 15086-7502
                    Tel:      +1 724 742 6900
                    Email:    nm_mibs@fore.com
                    Web:      http://www.fore.com"
        DESCRIPTION "Fore ASX ethernet bridge mib extensions."
::= { preDot1qVlanMIB 2 }

--------------------------------------------------------------------------------


bridgeDataSource OBJECT-TYPE
	SYNTAX  DisplayString (SIZE (0..20))
	MAX-ACCESS  read-write
	STATUS  current
	DESCRIPTION
	    "This object specifies the name of the bridge that is currently
	     visable via SNMP accesses to the Bridge MIB (RFC-1493).  If
	     there is no bridge of that name, then accesses to objects in the
		Bridge MIB will return noSuchName errors.  The factory default
		value for this object is 'default'"
	::= { foreBridgeExtensions 1 }

bridgeNumberOfEntities OBJECT-TYPE
       SYNTAX  Integer32
       MAX-ACCESS  read-only
	STATUS  current
	DESCRIPTION
		"This object specifies the number of logical bridges in the
		system."
	::= { foreBridgeExtensions 2 }

bridgeStpAtmPortTable OBJECT-TYPE
	  SYNTAX  SEQUENCE OF BridgeStpAtmPortEntry
	  MAX-ACCESS  not-accessible
	  STATUS  current
	  DESCRIPTION
		"A table that contains atm port-specific information
		 for the Spanning Tree Protocol."
	  ::= { foreBridgeExtensions 3 }

bridgeStpAtmPortEntry OBJECT-TYPE
	 SYNTAX  BridgeStpAtmPortEntry
	 MAX-ACCESS  not-accessible
	 STATUS  current
	 DESCRIPTION
	       "A list of information maintained by every atm port
	       about the Spanning Tree Protocol state for that port."
	 INDEX   { bridgeStpAtmPort }
	 ::= { bridgeStpAtmPortTable 1 }

BridgeStpAtmPortEntry ::=
	 SEQUENCE {
	     bridgeStpAtmPort
		 DisplayString,
	     bridgeStpAtmPortPriority
		 Integer32,
	     bridgeStpAtmPortState
		 INTEGER,
	     bridgeStpAtmPortEnable
		 INTEGER,
	     bridgeStpAtmPortPathCost
		 Integer32,
	     bridgeStpAtmPortDesignatedRoot
		 BridgeId,
	     bridgeStpAtmPortDesignatedCost
		 Integer32,
	     bridgeStpAtmPortDesignatedBridge
		 BridgeId,
	     bridgeStpAtmPortDesignatedPort
		 OCTET STRING,
	     bridgeStpAtmPortForwardTransitions
		 Counter32
	 }

bridgeStpAtmPort OBJECT-TYPE
	 SYNTAX  DisplayString (SIZE (1..35))
	 MAX-ACCESS  read-only
	 STATUS  current
	 DESCRIPTION
	       "The port number of the port for which this entry
	       contains Spanning Tree Protocol management
	       information."
	 ::= { bridgeStpAtmPortEntry 1 }

bridgeStpAtmPortPriority OBJECT-TYPE
	 SYNTAX  Integer32 (0..255)
	 MAX-ACCESS  read-write
	 STATUS  current
	 DESCRIPTION
	       "The value of the priority field which is
	       contained in the first (in network byte order)
	       octet of the (2 octet long) Port ID.  The other
	       octet of the Port ID is given by the value of
	       bridgeStpAtmPort."
	 ::= { bridgeStpAtmPortEntry 2 }

bridgeStpAtmPortState OBJECT-TYPE
	 SYNTAX  INTEGER {
		     disabled(1),
		     blocking(2),
		     listening(3),
		     learning(4),
		     forwarding(5),
		     broken(6)
		 }
	 MAX-ACCESS  read-only
	 STATUS  current
	 DESCRIPTION
	       "The port's current state as defined by
		application of the Spanning Tree Protocol.  This
		state controls what action a port takes on
		reception of a frame."
	 ::= { bridgeStpAtmPortEntry 3 }

bridgeStpAtmPortEnable OBJECT-TYPE
	 SYNTAX  INTEGER {
		     enabled(1),
		     disabled(2)
		 }
	 MAX-ACCESS  read-write
	 STATUS  current
	 DESCRIPTION
	       "The enabled/disabled status of the port."
	 ::= { bridgeStpAtmPortEntry 4 }


bridgeStpAtmPortPathCost OBJECT-TYPE
	 SYNTAX  Integer32 (1..65535)
	 MAX-ACCESS  read-write
	 STATUS  current
	 DESCRIPTION
	       "The contribution of this port to the path cost of
	       paths towards the spanning tree root which include
	       this port."
	 ::= { bridgeStpAtmPortEntry 5 }

bridgeStpAtmPortDesignatedRoot OBJECT-TYPE
	 SYNTAX  BridgeId
	 MAX-ACCESS  read-only
	 STATUS  current
	 DESCRIPTION
	       "The unique Bridge Identifier of the Bridge
	       recorded as the Root in the Configuration BPDUs
	       transmitted by the Designated Bridge for the
	       segment to which the port is attached."
	 ::= { bridgeStpAtmPortEntry 6 }

bridgeStpAtmPortDesignatedCost OBJECT-TYPE
	 SYNTAX  Integer32 (1..65535)
	 MAX-ACCESS  read-only
	 STATUS  current
	 DESCRIPTION
	       "The path cost of the Designated Port of the
	       segment connected to this port.  This value is
	       compared to the Root Path Cost field in received
	       bridge PDUs."
	 ::= { bridgeStpAtmPortEntry 7 }

bridgeStpAtmPortDesignatedBridge OBJECT-TYPE
	 SYNTAX  BridgeId
	 MAX-ACCESS  read-only
	 STATUS  current
	 DESCRIPTION
	       "The Bridge Identifier of the bridge which this
	       port considers to be the Designated Bridge for
	       this port's segment."
	 ::= { bridgeStpAtmPortEntry 8 }

bridgeStpAtmPortDesignatedPort OBJECT-TYPE
	 SYNTAX  OCTET STRING (SIZE (2))
	 MAX-ACCESS  read-only
	 STATUS  current
	 DESCRIPTION
	       "The Port Identifier of the port on the Designated
	       Bridge for this port's segment."
	 ::= { bridgeStpAtmPortEntry 9 }

bridgeStpAtmPortForwardTransitions OBJECT-TYPE
	 SYNTAX  Counter32
	 MAX-ACCESS  read-only
	 STATUS  current
	 DESCRIPTION
	       "The number of times this port has transitioned
	       from the Learning state to the Forwarding state."
	 ::= { bridgeStpAtmPortEntry 10 }

bridgeStpEnable OBJECT-TYPE
	 SYNTAX  INTEGER {
		     enabled(1),
		     disabled(2)
		 }
	 MAX-ACCESS  read-write
	 STATUS  current
	 DESCRIPTION
	       "The enabled/disabled status of the bridge."
	 ::= { foreBridgeExtensions 4 }

END
