-- 
-- Copyright 1999 by Fore Systems, Inc. 
-- Converted to SMIv2 rfc 2578,2579,2580 - STD 58
--
-- Copyright 1995 by Fore Systems, Inc.
--
-- This file contains definitions for management information for Fore Systems
-- physical assemblies.  It is general in nature in order to accomodate all
-- of the current hardware products as well as any future products in the 
-- forseeable future, or until an industry standard MIB is adopted.
------------------------------------------------------------------------------

Fore-FileXfr-MIB DEFINITIONS ::= BEGIN

   IMPORTS
      Integer32,
      IpAddress,
      OBJECT-TYPE,
      MODULE-IDENTITY                   FROM SNMPv2-SMI
      DisplayString,
      TestAndIncr			FROM SNMPv2-TC
      fileXfr, EntryStatus		FROM Fore-Common-MIB;

foreFileXfrModule  MODULE-IDENTITY
	LAST-UPDATED	"9512071530-0500"
	ORGANIZATION	"FORE"
	CONTACT-INFO	"
		Postal:	FORE Systems Inc.
			1000 FORE Drive
			Warrendale, PA 15086-7502
		Tel:	+1 724 742 6900
		Email:	nm_mibs@fore.com
		Web:	http://www.fore.com"
	DESCRIPTION
             "This MIB module defines the FORE Systems generic
             file transfer information.  It provides for a file
             transfer table.  Each table entry contains the
             information necessary for a device to complete
             a file transfer.  Each table entry also contains
             information as to the status of the file transfer."
	::= { fileXfr 1 }

--------------------------------------------------------------------
-- The file transfer group

fXfrGroup OBJECT IDENTIFIER ::= { fileXfr 2 }

fXfrNextIndex OBJECT-TYPE
	SYNTAX	TestAndIncr
	MAX-ACCESS	read-write
	STATUS	current
	DESCRIPTION
		"The index of the next free row in the fXfrTable."
	::= { fXfrGroup 1}

fXfrTable OBJECT-TYPE
	SYNTAX	SEQUENCE OF FXfrEntry
	MAX-ACCESS	not-accessible
	STATUS	current
	DESCRIPTION
		"A table of pending and completed file transfers."
	::= { fXfrGroup 2 }

fXfrEntry OBJECT-TYPE
	SYNTAX	FXfrEntry
	MAX-ACCESS	not-accessible
	STATUS	current
	DESCRIPTION
                "A table entry containing information on a pending
                or completed file transfer."
	INDEX	{ fXfrIndex }
	::= { fXfrTable 1 }

FXfrEntry ::=
	SEQUENCE {
		fXfrIndex			Integer32,
		fXfrRemoteFileUrl		DisplayString,
		fXfrLocalFile			DisplayString,
		fXfrDirection			INTEGER,
		fXfrEntryStatus			EntryStatus,
		fXfrStatus			INTEGER,
		fXfrStatusText			DisplayString,
		fXfrOwnerIpAddress		IpAddress,
		fXfrOwnerSignature		DisplayString,
		fXfrTransferType		INTEGER,
		fXfrUserId			DisplayString,
		fXfrPassword			DisplayString
	}
		
fXfrIndex OBJECT-TYPE
        SYNTAX  Integer32
        MAX-ACCESS  read-only
        STATUS  current
        DESCRIPTION
		"The index of the file transfer."
        ::= { fXfrEntry 1 }

fXfrRemoteFileUrl OBJECT-TYPE
        SYNTAX  DisplayString
        MAX-ACCESS  read-create
        STATUS  current
        DESCRIPTION
		"This is the URL of the file to operate on.  The URL
		is taken from the snmp agents point of view.  The URL is
		in the form: <service>://<ip-address>[:port]/<filename>
		This includes the service (such as tftp), the server to 
		contact, the port on that server to use, and the file on
		that server that is to be operated on.  This definition
		does not specify the local filename.  That name is 
		specified in fXfrKnownFiles and fXfrLocalFilename."
        ::= { fXfrEntry 2 }

fXfrLocalFile OBJECT-TYPE
         SYNTAX  DisplayString
         MAX-ACCESS  read-create
         STATUS  current
         DESCRIPTION 
                "The name of the local file to use in the GET/PUT
                operations.  This can either be a full pathname or
                a device specific description of the local file.
                Some examples of descriptions specific to an ASX
                are switchCDB, lecsConfig, and switchUpgrade.
                As of FT5.2 additionally supported are netmodUpgradeA,
                netmodUpgradeB,netmodUpgradeC,netmodUpgradeD"
         ::= { fXfrEntry 3 }

fXfrDirection OBJECT-TYPE
         SYNTAX  INTEGER {
                    get(1),
                    put(2)
                 }
         MAX-ACCESS  read-create
         STATUS  current
         DESCRIPTION 
                 "Indication of the file transfer operation.
                  A 'get' will retrieve the file from the machine
                  specified in fXfrRemoteFileUrl.  A 'put' will
                  send the file to the machine specified in
                  fXfrRemoteFileUrl."
         ::= { fXfrEntry 4 }

fXfrEntryStatus OBJECT-TYPE
        SYNTAX  EntryStatus
        MAX-ACCESS  read-create
        STATUS  current
        DESCRIPTION
                "The status of this table entry."
        ::= { fXfrEntry 5 }

fXfrStatus OBJECT-TYPE
        SYNTAX  INTEGER {
                        idle(1),
			go(2),
			inQueue(3),
                        inProgress(4),
                        succeeded(5),
                        failed(6),
			busy(7)
                }
         MAX-ACCESS  read-create
         STATUS  current
         DESCRIPTION 
		"The current status of this file transfer.  Is idle when
		the row becomes valid.  To start the file transfer set this
		to go.  InQueue signifies that the file transfer is waiting
		for resources before it begins but it will begin 
		automatically.  Busy signifies that the file transfer
		could not begin due to a resource allocation problem.  The
		manager must try to restart the file transfer by setting
		this entry to go."
         ::= { fXfrEntry 6 }

fXfrStatusText OBJECT-TYPE
        SYNTAX  DisplayString
        MAX-ACCESS  read-only
        STATUS current
        DESCRIPTION
		"A message describing the status of this file transfer.  
		This must exists when the status is succeeded or failed.
		This can optionally exists when the status is inQueue,
		inProgress, or busy."
        ::= { fXfrEntry 7 }

fXfrOwnerIpAddress OBJECT-TYPE
        SYNTAX  IpAddress
        MAX-ACCESS  read-only
        STATUS  current
        DESCRIPTION
                "Ip address of the entity that requested this 
                 file transfer."
        ::= { fXfrEntry 8 }


fXfrOwnerSignature OBJECT-TYPE
        SYNTAX  DisplayString
        MAX-ACCESS  read-create
        STATUS  current
        DESCRIPTION
                "Signature of the owner of this file transfer.  This is
                supplied by the management station."
        ::= { fXfrEntry 9 }

fXfrTransferType OBJECT-TYPE
        SYNTAX  INTEGER {
                        binary(1),
                        ascii(2)
                }
        MAX-ACCESS  read-create
        STATUS  current
        DESCRIPTION
                "The type of transfer requested.  A binary transfer will
                perform no translations while an ascii transfer will 
                set the representation type to network ASCII."
        ::= { fXfrEntry 10 }

fXfrUserId OBJECT-TYPE
        SYNTAX DisplayString
        MAX-ACCESS  read-create
        STATUS  current
        DESCRIPTION
                "The login name on the remote host for FTP." 
        ::= { fXfrEntry 11 }

fXfrPassword OBJECT-TYPE
        SYNTAX DisplayString
        MAX-ACCESS  read-create
        STATUS  current
        DESCRIPTION
                "The password associated with the login name on the 
		 remote host for FTP.

		 Note this object is write-only and reading it will
		 result in implementation-specific results."
        ::= { fXfrEntry 12 }

END
