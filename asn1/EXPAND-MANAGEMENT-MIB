--
-- EXPAND-MANAGEMENT-MIB.my
-- MIB generated by MG-SOFT Visual MIB Builder Version 3.0 Build 253
-- Sunday, June 16, 2002 at 17:30:49
--

-- 
-- Expand Networks. Management.
-- Product Line MIB Version 1.0.8

	EXPAND-MANAGEMENT-MIB DEFINITIONS ::= BEGIN
 
		IMPORTS
			management			
				FROM EXPAND-NETWORKS-SMI			
			OBJECT-TYPE			
				FROM RFC-1212;
	
	
--
-- Node definitions
--
	
		-- 1.1
		log OBJECT IDENTIFIER ::= { management 1 }
		
		-- 1.1.1
		events OBJECT IDENTIFIER ::= { log 1 }
		
		-- 1.1.1.1
		general OBJECT IDENTIFIER ::= { events 1 }
		
		-- 1.1.1.1.1
		severity OBJECT-TYPE
			SYNTAX INTEGER {
					deb(1),
					info(2),
					audit(3),
					warning(4),		
					error(5),	
					fatal(6),
					max-severity(7),
					beta(8),
					overide(9) 
					}	
					

			ACCESS read-only
			STATUS mandatory
			DESCRIPTION
				"Severity of the logged event."
			::= { general 1 }
		
		-- 1.1.1.1.2
		message OBJECT-TYPE
			SYNTAX OCTET STRING
			ACCESS read-only
			STATUS mandatory
			DESCRIPTION
				"Content of the logged event."
			::= { general 2 }
		
	
	END

--
-- EXPAND-MANAGEMENT-MIB.my
--
