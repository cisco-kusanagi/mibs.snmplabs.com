TERAWAVE-teraSonet-MIB DEFINITIONS ::= BEGIN
        -- Created by sml2mib compiler 
        IMPORTS

 enterprises,  OBJECT-TYPE,  Counter,  Gauge,  TimeTicks
        FROM RFC1155-SMI
	Gauge32 FROM SNMPv2-SMI;

terawave OBJECT IDENTIFIER ::=  { enterprises 4513 }

teraSonetGroup OBJECT IDENTIFIER ::=  { terawave 10 }

     -- teraSonetMediumTable

teraSonetMediumTable OBJECT-TYPE
     SYNTAX SEQUENCE OF TeraSonetMediumTableEntryType
     ACCESS not-accessible
     STATUS mandatory
     DESCRIPTION
          " table teraSonetMediumTable"
     ::= { teraSonetGroup 1 }

teraSonetMediumTableEntry OBJECT-TYPE
          SYNTAX TeraSonetMediumTableEntryType
          ACCESS not-accessible
          STATUS mandatory
          DESCRIPTION
               " table entry teraSonetMediumTableEntry "
          INDEX {                   ifIndex }
     ::= { teraSonetMediumTable 1 }

TeraSonetMediumTableEntryType ::= SEQUENCE {
          teraSonetMode   
             INTEGER,
          teraSonetStm1Mapping   
             INTEGER,
          teraSonetSDThreshold   
             INTEGER (5..9),
          teraSonetSFThreshold   
             INTEGER (3..5),
          teraSonetMediumTotalTimeElapsed   
             INTEGER (1..86400),
          teraSonetMediumValidTotalIntervals   
             INTEGER (0..7),
          teraSonetMediumInvalidTotalIntervals   
             INTEGER (0..7)
}

teraSonetMode OBJECT-TYPE
          SYNTAX INTEGER
                  {
                  sts1STM0(1),
                  sts3STM1(2),
                  sts3cSTM1(3),
                  sts12STM4(4),
                  sts12cSTM4(5),
                  sts48cSTM16(6)
                  }
          ACCESS read-only
          STATUS mandatory
          DESCRIPTION
               ""
          ::= { teraSonetMediumTableEntry 1 }

teraSonetStm1Mapping OBJECT-TYPE
          SYNTAX INTEGER
                  {
                  none(0),
                  au3(1),
                  au4(2)
                  }
          ACCESS read-write
          STATUS mandatory
          DESCRIPTION
               ""
          ::= { teraSonetMediumTableEntry 2 }

teraSonetSDThreshold OBJECT-TYPE
          SYNTAX INTEGER (5..9)
          ACCESS read-write
          STATUS mandatory
          DESCRIPTION
               ""
          ::= { teraSonetMediumTableEntry 3 }

teraSonetSFThreshold OBJECT-TYPE
          SYNTAX INTEGER (3..5)
          ACCESS read-write
          STATUS mandatory
          DESCRIPTION
               ""
          ::= { teraSonetMediumTableEntry 4 }

teraSonetMediumTotalTimeElapsed OBJECT-TYPE
          SYNTAX INTEGER (1..86400)
          ACCESS read-only
          STATUS mandatory
          DESCRIPTION
               ""
          ::= { teraSonetMediumTableEntry 5 }

teraSonetMediumValidTotalIntervals OBJECT-TYPE
          SYNTAX INTEGER (0..7)
          ACCESS read-only
          STATUS mandatory
          DESCRIPTION
               ""
          ::= { teraSonetMediumTableEntry 6 }

teraSonetMediumInvalidTotalIntervals OBJECT-TYPE
          SYNTAX INTEGER (0..7)
          ACCESS read-only
          STATUS mandatory
          DESCRIPTION
               ""
          ::= { teraSonetMediumTableEntry 7 }

     -- teraSonetSectionTable

teraSonetSectionTable OBJECT-TYPE
     SYNTAX SEQUENCE OF TeraSonetSectionTableEntryType
     ACCESS not-accessible
     STATUS mandatory
     DESCRIPTION
          " table teraSonetSectionTable"
     ::= { teraSonetGroup 2 }

teraSonetSectionTableEntry OBJECT-TYPE
          SYNTAX TeraSonetSectionTableEntryType
          ACCESS not-accessible
          STATUS mandatory
          DESCRIPTION
               " table entry teraSonetSectionTableEntry "
          INDEX {                   ifIndex }
     ::= { teraSonetSectionTable 1 }

TeraSonetSectionTableEntryType ::= SEQUENCE {
          teraSonetSectionTraceLenTx   
             INTEGER,
          teraSonetSectionTraceTx   
             OCTET STRING,
          teraSonetSectionTraceLenRx   
             INTEGER,
          teraSonetSectionTraceRx   
             OCTET STRING
}

teraSonetSectionTraceLenTx OBJECT-TYPE
          SYNTAX INTEGER
                  {
                  number-16(1),
                  number-64(2)
                  }
          ACCESS read-write
          STATUS mandatory
          DESCRIPTION
               ""
          ::= { teraSonetSectionTableEntry 1 }

teraSonetSectionTraceTx OBJECT-TYPE
          SYNTAX OCTET STRING
          ACCESS read-write
          STATUS mandatory
          DESCRIPTION
               ""
          ::= { teraSonetSectionTableEntry 2 }

teraSonetSectionTraceLenRx OBJECT-TYPE
          SYNTAX INTEGER
                  {
                  number-16(1),
                  number-64(2)
                  }
          ACCESS read-only
          STATUS mandatory
          DESCRIPTION
               ""
          ::= { teraSonetSectionTableEntry 3 }

teraSonetSectionTraceRx OBJECT-TYPE
          SYNTAX OCTET STRING
          ACCESS read-only
          STATUS mandatory
          DESCRIPTION
               ""
          ::= { teraSonetSectionTableEntry 4 }

     -- teraSonetPathOverheadTable

teraSonetPathOverheadTable OBJECT-TYPE
     SYNTAX SEQUENCE OF TeraSonetPathOverheadTableEntryType
     ACCESS not-accessible
     STATUS mandatory
     DESCRIPTION
          " table teraSonetPathOverheadTable"
     ::= { teraSonetGroup 3 }

teraSonetPathOverheadTableEntry OBJECT-TYPE
          SYNTAX TeraSonetPathOverheadTableEntryType
          ACCESS not-accessible
          STATUS mandatory
          DESCRIPTION
               " table entry teraSonetPathOverheadTableEntry "
          INDEX {                   ifIndex }
     ::= { teraSonetPathOverheadTable 1 }

TeraSonetPathOverheadTableEntryType ::= SEQUENCE {
          teraSonetPathSigLabelTx   
             INTEGER (0..255),
          teraSonetPathTraceLenTx   
             INTEGER,
          teraSonetPathTraceTx   
             OCTET STRING,
          teraSonetPathSigLabelRx   
             INTEGER (0..255),
          teraSonetPathTraceLenRx   
             INTEGER,
          teraSonetPathTraceRx   
             OCTET STRING
}

teraSonetPathSigLabelTx OBJECT-TYPE
          SYNTAX INTEGER (0..255)
          ACCESS read-write
          STATUS mandatory
          DESCRIPTION
               ""
          ::= { teraSonetPathOverheadTableEntry 1 }

teraSonetPathTraceLenTx OBJECT-TYPE
          SYNTAX INTEGER
                  {
                  number-16(1),
                  number-64(2)
                  }
          ACCESS read-write
          STATUS mandatory
          DESCRIPTION
               ""
          ::= { teraSonetPathOverheadTableEntry 2 }

teraSonetPathTraceTx OBJECT-TYPE
          SYNTAX OCTET STRING
          ACCESS read-write
          STATUS mandatory
          DESCRIPTION
               ""
          ::= { teraSonetPathOverheadTableEntry 3 }

teraSonetPathSigLabelRx OBJECT-TYPE
          SYNTAX INTEGER (0..255)
          ACCESS read-only
          STATUS mandatory
          DESCRIPTION
               ""
          ::= { teraSonetPathOverheadTableEntry 4 }

teraSonetPathTraceLenRx OBJECT-TYPE
          SYNTAX INTEGER
                  {
                  number-16(1),
                  number-64(2)
                  }
          ACCESS read-only
          STATUS mandatory
          DESCRIPTION
               ""
          ::= { teraSonetPathOverheadTableEntry 5 }

teraSonetPathTraceRx OBJECT-TYPE
          SYNTAX OCTET STRING
          ACCESS read-only
          STATUS mandatory
          DESCRIPTION
               ""
          ::= { teraSonetPathOverheadTableEntry 6 }

     -- teraSonetMapperConfigTable

teraSonetMapperConfigTable OBJECT-TYPE
     SYNTAX SEQUENCE OF TeraSonetMapperConfigTableEntryType
     ACCESS not-accessible
     STATUS mandatory
     DESCRIPTION
          " table teraSonetMapperConfigTable"
     ::= { teraSonetGroup 4 }

teraSonetMapperConfigTableEntry OBJECT-TYPE
          SYNTAX TeraSonetMapperConfigTableEntryType
          ACCESS not-accessible
          STATUS mandatory
          DESCRIPTION
               " table entry teraSonetMapperConfigTableEntry "
          INDEX {                   ifIndex }
     ::= { teraSonetMapperConfigTable 1 }

TeraSonetMapperConfigTableEntryType ::= SEQUENCE {
          teraSonetMapperType   
             INTEGER,
          teraSonetMapperLoopbackConfig   
             INTEGER (1..6)
}

teraSonetMapperType OBJECT-TYPE
          SYNTAX INTEGER
                  {
                  none(0),
                  ds3(1),
                  vc12(2),
                  vt1-5(3)
                  }
          ACCESS read-write
          STATUS mandatory
          DESCRIPTION
               ""
          ::= { teraSonetMapperConfigTableEntry 1 }

teraSonetMapperLoopbackConfig OBJECT-TYPE
          SYNTAX INTEGER (1..6)
          ACCESS read-write
          STATUS mandatory
          DESCRIPTION
               ""
          ::= { teraSonetMapperConfigTableEntry 2 }

     -- teraSonetPathIdTable

teraSonetPathIdTable OBJECT-TYPE
     SYNTAX SEQUENCE OF TeraSonetPathIdTableEntryType
     ACCESS not-accessible
     STATUS mandatory
     DESCRIPTION
          " table teraSonetPathIdTable"
     ::= { teraSonetGroup 5 }

teraSonetPathIdTableEntry OBJECT-TYPE
          SYNTAX TeraSonetPathIdTableEntryType
          ACCESS not-accessible
          STATUS mandatory
          DESCRIPTION
               " table entry teraSonetPathIdTableEntry "
          INDEX {                   ifIndex,                  teraSonetPathIdSTS1 }
     ::= { teraSonetPathIdTable 1 }

TeraSonetPathIdTableEntryType ::= SEQUENCE {
          teraSonetPathIdSTS1   
             INTEGER (1..12),
          teraSonetPathIdIfIndex   
             INTEGER (1..65535)
}

teraSonetPathIdSTS1 OBJECT-TYPE
          SYNTAX INTEGER (1..12)
          ACCESS read-only
          STATUS mandatory
          DESCRIPTION
               ""
          ::= { teraSonetPathIdTableEntry 1 }

teraSonetPathIdIfIndex OBJECT-TYPE
          SYNTAX INTEGER (1..65535)
          ACCESS read-only
          STATUS mandatory
          DESCRIPTION
               ""
          ::= { teraSonetPathIdTableEntry 2 }

     -- teraSonetVTIdTable

teraSonetVTIdTable OBJECT-TYPE
     SYNTAX SEQUENCE OF TeraSonetVTIdTableEntryType
     ACCESS not-accessible
     STATUS mandatory
     DESCRIPTION
          " table teraSonetVTIdTable"
     ::= { teraSonetGroup 6 }

teraSonetVTIdTableEntry OBJECT-TYPE
          SYNTAX TeraSonetVTIdTableEntryType
          ACCESS not-accessible
          STATUS mandatory
          DESCRIPTION
               " table entry teraSonetVTIdTableEntry "
          INDEX {                   ifIndex,                  teraSonetVTIdSTS1,                  teraSonetVTIdVTG,                  teraSonetVTIdVT }
     ::= { teraSonetVTIdTable 1 }

TeraSonetVTIdTableEntryType ::= SEQUENCE {
          teraSonetVTIdSTS1   
             INTEGER (1..12),
          teraSonetVTIdVTG   
             INTEGER (1..7),
          teraSonetVTIdVT   
             INTEGER (1..4),
          teraSonetVTIdIfIndex   
             INTEGER (1..65535)
}

teraSonetVTIdSTS1 OBJECT-TYPE
          SYNTAX INTEGER (1..12)
          ACCESS read-write
          STATUS mandatory
          DESCRIPTION
               ""
          ::= { teraSonetVTIdTableEntry 1 }

teraSonetVTIdVTG OBJECT-TYPE
          SYNTAX INTEGER (1..7)
          ACCESS read-write
          STATUS mandatory
          DESCRIPTION
               ""
          ::= { teraSonetVTIdTableEntry 2 }

teraSonetVTIdVT OBJECT-TYPE
          SYNTAX INTEGER (1..4)
          ACCESS read-write
          STATUS mandatory
          DESCRIPTION
               ""
          ::= { teraSonetVTIdTableEntry 3 }

teraSonetVTIdIfIndex OBJECT-TYPE
          SYNTAX INTEGER (1..65535)
          ACCESS read-only
          STATUS mandatory
          DESCRIPTION
               ""
          ::= { teraSonetVTIdTableEntry 4 }

     -- teraSonetSectionCurrTotalTable

teraSonetSectionCurrTotalTable OBJECT-TYPE
     SYNTAX SEQUENCE OF TeraSonetSectionCurrTotalTableEntryType
     ACCESS not-accessible
     STATUS mandatory
     DESCRIPTION
          " table teraSonetSectionCurrTotalTable"
     ::= { teraSonetGroup 7 }

teraSonetSectionCurrTotalTableEntry OBJECT-TYPE
          SYNTAX TeraSonetSectionCurrTotalTableEntryType
          ACCESS not-accessible
          STATUS mandatory
          DESCRIPTION
               " table entry teraSonetSectionCurrTotalTableEntry "
          INDEX {                   ifIndex }
     ::= { teraSonetSectionCurrTotalTable 1 }

TeraSonetSectionCurrTotalTableEntryType ::= SEQUENCE {
          teraSonetSectionCurrTotalStatus   
             INTEGER (1..6),
          teraSonetSectionCurrTotalESs   
             Gauge32,
          teraSonetSectionCurrTotalSESs   
             Gauge32,
          teraSonetSectionCurrTotalSEFSs   
             Gauge32,
          teraSonetSectionCurrTotalCVs   
             Gauge32,
          teraSonetTotalPerfStat   
             INTEGER
}

teraSonetSectionCurrTotalStatus OBJECT-TYPE
          SYNTAX INTEGER (1..6)
          ACCESS read-only
          STATUS mandatory
          DESCRIPTION
               ""
          ::= { teraSonetSectionCurrTotalTableEntry 1 }

teraSonetSectionCurrTotalESs OBJECT-TYPE
          SYNTAX Gauge32
          ACCESS read-only
          STATUS mandatory
          DESCRIPTION
               ""
          ::= { teraSonetSectionCurrTotalTableEntry 2 }

teraSonetSectionCurrTotalSESs OBJECT-TYPE
          SYNTAX Gauge32
          ACCESS read-only
          STATUS mandatory
          DESCRIPTION
               ""
          ::= { teraSonetSectionCurrTotalTableEntry 3 }

teraSonetSectionCurrTotalSEFSs OBJECT-TYPE
          SYNTAX Gauge32
          ACCESS read-only
          STATUS mandatory
          DESCRIPTION
               ""
          ::= { teraSonetSectionCurrTotalTableEntry 4 }

teraSonetSectionCurrTotalCVs OBJECT-TYPE
          SYNTAX Gauge32
          ACCESS read-only
          STATUS mandatory
          DESCRIPTION
               ""
          ::= { teraSonetSectionCurrTotalTableEntry 5 }

teraSonetTotalPerfStat OBJECT-TYPE
          SYNTAX INTEGER
                  {
                  ok(1),
                  clear(2)
                  }
          ACCESS read-write
          STATUS mandatory
          DESCRIPTION
               ""
          ::= { teraSonetSectionCurrTotalTableEntry 6 }

     -- teraSonetSectionTotalTable

teraSonetSectionTotalTable OBJECT-TYPE
     SYNTAX SEQUENCE OF TeraSonetSectionTotalTableEntryType
     ACCESS not-accessible
     STATUS mandatory
     DESCRIPTION
          " table teraSonetSectionTotalTable"
     ::= { teraSonetGroup 8 }

teraSonetSectionTotalTableEntry OBJECT-TYPE
          SYNTAX TeraSonetSectionTotalTableEntryType
          ACCESS not-accessible
          STATUS mandatory
          DESCRIPTION
               " table entry teraSonetSectionTotalTableEntry "
          INDEX {                   ifIndex,                  teraSonetSectionTotalNumber }
     ::= { teraSonetSectionTotalTable 1 }

TeraSonetSectionTotalTableEntryType ::= SEQUENCE {
          teraSonetSectionTotalNumber   
             INTEGER (1..7),
          teraSonetSectionTotalESs   
             Gauge32,
          teraSonetSectionTotalSESs   
             Gauge32,
          teraSonetSectionTotalSEFSs   
             Gauge32,
          teraSonetSectionTotalCVs   
             Gauge32,
          teraSonetSectionTotalValidData   
             INTEGER
}

teraSonetSectionTotalNumber OBJECT-TYPE
          SYNTAX INTEGER (1..7)
          ACCESS read-only
          STATUS mandatory
          DESCRIPTION
               ""
          ::= { teraSonetSectionTotalTableEntry 1 }

teraSonetSectionTotalESs OBJECT-TYPE
          SYNTAX Gauge32
          ACCESS read-only
          STATUS mandatory
          DESCRIPTION
               ""
          ::= { teraSonetSectionTotalTableEntry 2 }

teraSonetSectionTotalSESs OBJECT-TYPE
          SYNTAX Gauge32
          ACCESS read-only
          STATUS mandatory
          DESCRIPTION
               ""
          ::= { teraSonetSectionTotalTableEntry 3 }

teraSonetSectionTotalSEFSs OBJECT-TYPE
          SYNTAX Gauge32
          ACCESS read-only
          STATUS mandatory
          DESCRIPTION
               ""
          ::= { teraSonetSectionTotalTableEntry 4 }

teraSonetSectionTotalCVs OBJECT-TYPE
          SYNTAX Gauge32
          ACCESS read-only
          STATUS mandatory
          DESCRIPTION
               ""
          ::= { teraSonetSectionTotalTableEntry 5 }

teraSonetSectionTotalValidData OBJECT-TYPE
          SYNTAX INTEGER
          ACCESS read-only
          STATUS mandatory
          DESCRIPTION
               ""
          ::= { teraSonetSectionTotalTableEntry 6 }

     -- teraSonetLineCurrTotalTable

teraSonetLineCurrTotalTable OBJECT-TYPE
     SYNTAX SEQUENCE OF TeraSonetLineCurrTotalTableEntryType
     ACCESS not-accessible
     STATUS mandatory
     DESCRIPTION
          " table teraSonetLineCurrTotalTable"
     ::= { teraSonetGroup 9 }

teraSonetLineCurrTotalTableEntry OBJECT-TYPE
          SYNTAX TeraSonetLineCurrTotalTableEntryType
          ACCESS not-accessible
          STATUS mandatory
          DESCRIPTION
               " table entry teraSonetLineCurrTotalTableEntry "
          INDEX {                   ifIndex }
     ::= { teraSonetLineCurrTotalTable 1 }

TeraSonetLineCurrTotalTableEntryType ::= SEQUENCE {
          teraSonetLineCurrTotalStatus   
             INTEGER (1..6),
          teraSonetLineCurrTotalESs   
             Gauge32,
          teraSonetLineCurrTotalSESs   
             Gauge32,
          teraSonetLineCurrTotalCVs   
             Gauge32,
          teraSonetLineCurrTotalUASs   
             Gauge32
}

teraSonetLineCurrTotalStatus OBJECT-TYPE
          SYNTAX INTEGER (1..6)
          ACCESS read-only
          STATUS mandatory
          DESCRIPTION
               ""
          ::= { teraSonetLineCurrTotalTableEntry 1 }

teraSonetLineCurrTotalESs OBJECT-TYPE
          SYNTAX Gauge32
          ACCESS read-only
          STATUS mandatory
          DESCRIPTION
               ""
          ::= { teraSonetLineCurrTotalTableEntry 2 }

teraSonetLineCurrTotalSESs OBJECT-TYPE
          SYNTAX Gauge32
          ACCESS read-only
          STATUS mandatory
          DESCRIPTION
               ""
          ::= { teraSonetLineCurrTotalTableEntry 3 }

teraSonetLineCurrTotalCVs OBJECT-TYPE
          SYNTAX Gauge32
          ACCESS read-only
          STATUS mandatory
          DESCRIPTION
               ""
          ::= { teraSonetLineCurrTotalTableEntry 4 }

teraSonetLineCurrTotalUASs OBJECT-TYPE
          SYNTAX Gauge32
          ACCESS read-only
          STATUS mandatory
          DESCRIPTION
               ""
          ::= { teraSonetLineCurrTotalTableEntry 5 }

     -- teraSonetLineTotalTable

teraSonetLineTotalTable OBJECT-TYPE
     SYNTAX SEQUENCE OF TeraSonetLineTotalTableEntryType
     ACCESS not-accessible
     STATUS mandatory
     DESCRIPTION
          " table teraSonetLineTotalTable"
     ::= { teraSonetGroup 10 }

teraSonetLineTotalTableEntry OBJECT-TYPE
          SYNTAX TeraSonetLineTotalTableEntryType
          ACCESS not-accessible
          STATUS mandatory
          DESCRIPTION
               " table entry teraSonetLineTotalTableEntry "
          INDEX {                   ifIndex,                  teraSonetLineTotalNumber }
     ::= { teraSonetLineTotalTable 1 }

TeraSonetLineTotalTableEntryType ::= SEQUENCE {
          teraSonetLineTotalNumber   
             INTEGER (1..7),
          teraSonetLineTotalESs   
             Gauge32,
          teraSonetLineTotalSESs   
             Gauge32,
          teraSonetLineTotalCVs   
             Gauge32,
          teraSonetLineTotalUASs   
             Gauge32,
          teraSonetLineTotalValidData   
             INTEGER
}

teraSonetLineTotalNumber OBJECT-TYPE
          SYNTAX INTEGER (1..7)
          ACCESS read-only
          STATUS mandatory
          DESCRIPTION
               ""
          ::= { teraSonetLineTotalTableEntry 1 }

teraSonetLineTotalESs OBJECT-TYPE
          SYNTAX Gauge32
          ACCESS read-only
          STATUS mandatory
          DESCRIPTION
               ""
          ::= { teraSonetLineTotalTableEntry 2 }

teraSonetLineTotalSESs OBJECT-TYPE
          SYNTAX Gauge32
          ACCESS read-only
          STATUS mandatory
          DESCRIPTION
               ""
          ::= { teraSonetLineTotalTableEntry 3 }

teraSonetLineTotalCVs OBJECT-TYPE
          SYNTAX Gauge32
          ACCESS read-only
          STATUS mandatory
          DESCRIPTION
               ""
          ::= { teraSonetLineTotalTableEntry 4 }

teraSonetLineTotalUASs OBJECT-TYPE
          SYNTAX Gauge32
          ACCESS read-only
          STATUS mandatory
          DESCRIPTION
               ""
          ::= { teraSonetLineTotalTableEntry 5 }

teraSonetLineTotalValidData OBJECT-TYPE
          SYNTAX INTEGER
          ACCESS read-only
          STATUS mandatory
          DESCRIPTION
               ""
          ::= { teraSonetLineTotalTableEntry 6 }

     -- teraSonetFarEndLineCurrTotalTable

teraSonetFarEndLineCurrTotalTable OBJECT-TYPE
     SYNTAX SEQUENCE OF TeraSonetFarEndLineCurrTotalTableEntryType
     ACCESS not-accessible
     STATUS mandatory
     DESCRIPTION
          " table teraSonetFarEndLineCurrTotalTable"
     ::= { teraSonetGroup 11 }

teraSonetFarEndLineCurrTotalTableEntry OBJECT-TYPE
          SYNTAX TeraSonetFarEndLineCurrTotalTableEntryType
          ACCESS not-accessible
          STATUS mandatory
          DESCRIPTION
               " table entry teraSonetFarEndLineCurrTotalTableEntry "
          INDEX {                   ifIndex }
     ::= { teraSonetFarEndLineCurrTotalTable 1 }

TeraSonetFarEndLineCurrTotalTableEntryType ::= SEQUENCE {
          teraSonetFarEndLineCurrTotalESs   
             Gauge32,
          teraSonetFarEndLineCurrTotalSESs   
             Gauge32,
          teraSonetFarEndLineCurrTotalCVs   
             Gauge32,
          teraSonetFarEndLineCurrTotalUASs   
             Gauge32
}

teraSonetFarEndLineCurrTotalESs OBJECT-TYPE
          SYNTAX Gauge32
          ACCESS read-only
          STATUS mandatory
          DESCRIPTION
               ""
          ::= { teraSonetFarEndLineCurrTotalTableEntry 1 }

teraSonetFarEndLineCurrTotalSESs OBJECT-TYPE
          SYNTAX Gauge32
          ACCESS read-only
          STATUS mandatory
          DESCRIPTION
               ""
          ::= { teraSonetFarEndLineCurrTotalTableEntry 2 }

teraSonetFarEndLineCurrTotalCVs OBJECT-TYPE
          SYNTAX Gauge32
          ACCESS read-only
          STATUS mandatory
          DESCRIPTION
               ""
          ::= { teraSonetFarEndLineCurrTotalTableEntry 3 }

teraSonetFarEndLineCurrTotalUASs OBJECT-TYPE
          SYNTAX Gauge32
          ACCESS read-only
          STATUS mandatory
          DESCRIPTION
               ""
          ::= { teraSonetFarEndLineCurrTotalTableEntry 4 }

     -- teraSonetFarEndLineTotalTable

teraSonetFarEndLineTotalTable OBJECT-TYPE
     SYNTAX SEQUENCE OF TeraSonetFarEndLineTotalTableEntryType
     ACCESS not-accessible
     STATUS mandatory
     DESCRIPTION
          " table teraSonetFarEndLineTotalTable"
     ::= { teraSonetGroup 12 }

teraSonetFarEndLineTotalTableEntry OBJECT-TYPE
          SYNTAX TeraSonetFarEndLineTotalTableEntryType
          ACCESS not-accessible
          STATUS mandatory
          DESCRIPTION
               " table entry teraSonetFarEndLineTotalTableEntry "
          INDEX {                   ifIndex,                  teraSonetFarEndLineTotalNumber }
     ::= { teraSonetFarEndLineTotalTable 1 }

TeraSonetFarEndLineTotalTableEntryType ::= SEQUENCE {
          teraSonetFarEndLineTotalNumber   
             INTEGER (1..7),
          teraSonetFarEndLineTotalESs   
             Gauge32,
          teraSonetFarEndLineTotalSESs   
             Gauge32,
          teraSonetFarEndLineTotalCVs   
             Gauge32,
          teraSonetFarEndLineTotalUASs   
             Gauge32,
          teraSonetFarEndLineTotalValidData   
             INTEGER
}

teraSonetFarEndLineTotalNumber OBJECT-TYPE
          SYNTAX INTEGER (1..7)
          ACCESS read-only
          STATUS mandatory
          DESCRIPTION
               ""
          ::= { teraSonetFarEndLineTotalTableEntry 1 }

teraSonetFarEndLineTotalESs OBJECT-TYPE
          SYNTAX Gauge32
          ACCESS read-only
          STATUS mandatory
          DESCRIPTION
               ""
          ::= { teraSonetFarEndLineTotalTableEntry 2 }

teraSonetFarEndLineTotalSESs OBJECT-TYPE
          SYNTAX Gauge32
          ACCESS read-only
          STATUS mandatory
          DESCRIPTION
               ""
          ::= { teraSonetFarEndLineTotalTableEntry 3 }

teraSonetFarEndLineTotalCVs OBJECT-TYPE
          SYNTAX Gauge32
          ACCESS read-only
          STATUS mandatory
          DESCRIPTION
               ""
          ::= { teraSonetFarEndLineTotalTableEntry 4 }

teraSonetFarEndLineTotalUASs OBJECT-TYPE
          SYNTAX Gauge32
          ACCESS read-only
          STATUS mandatory
          DESCRIPTION
               ""
          ::= { teraSonetFarEndLineTotalTableEntry 5 }

teraSonetFarEndLineTotalValidData OBJECT-TYPE
          SYNTAX INTEGER
          ACCESS read-only
          STATUS mandatory
          DESCRIPTION
               ""
          ::= { teraSonetFarEndLineTotalTableEntry 6 }

     -- teraSonetPathCurrTotalTable

teraSonetPathCurrTotalTable OBJECT-TYPE
     SYNTAX SEQUENCE OF TeraSonetPathCurrTotalTableEntryType
     ACCESS not-accessible
     STATUS mandatory
     DESCRIPTION
          " table teraSonetPathCurrTotalTable"
     ::= { teraSonetGroup 13 }

teraSonetPathCurrTotalTableEntry OBJECT-TYPE
          SYNTAX TeraSonetPathCurrTotalTableEntryType
          ACCESS not-accessible
          STATUS mandatory
          DESCRIPTION
               " table entry teraSonetPathCurrTotalTableEntry "
          INDEX {                   ifIndex }
     ::= { teraSonetPathCurrTotalTable 1 }

TeraSonetPathCurrTotalTableEntryType ::= SEQUENCE {
          teraSonetPathCurrTotalWidth   
             INTEGER,
          teraSonetPathCurrTotalStatus   
             INTEGER (1..62),
          teraSonetPathCurrTotalESs   
             Gauge32,
          teraSonetPathCurrTotalSESs   
             Gauge32,
          teraSonetPathCurrTotalCVs   
             Gauge32,
          teraSonetPathCurrTotalUASs   
             Gauge32
}

teraSonetPathCurrTotalWidth OBJECT-TYPE
          SYNTAX INTEGER
                  {
                  sts1(1),
                  sts3cSTM1(2),
                  sts12cSTM4(3),
                  sts48cSTM16(5)
                  }
          ACCESS read-only
          STATUS mandatory
          DESCRIPTION
               ""
          ::= { teraSonetPathCurrTotalTableEntry 1 }

teraSonetPathCurrTotalStatus OBJECT-TYPE
          SYNTAX INTEGER (1..62)
          ACCESS read-only
          STATUS mandatory
          DESCRIPTION
               ""
          ::= { teraSonetPathCurrTotalTableEntry 2 }

teraSonetPathCurrTotalESs OBJECT-TYPE
          SYNTAX Gauge32
          ACCESS read-only
          STATUS mandatory
          DESCRIPTION
               ""
          ::= { teraSonetPathCurrTotalTableEntry 3 }

teraSonetPathCurrTotalSESs OBJECT-TYPE
          SYNTAX Gauge32
          ACCESS read-only
          STATUS mandatory
          DESCRIPTION
               ""
          ::= { teraSonetPathCurrTotalTableEntry 4 }

teraSonetPathCurrTotalCVs OBJECT-TYPE
          SYNTAX Gauge32
          ACCESS read-only
          STATUS mandatory
          DESCRIPTION
               ""
          ::= { teraSonetPathCurrTotalTableEntry 5 }

teraSonetPathCurrTotalUASs OBJECT-TYPE
          SYNTAX Gauge32
          ACCESS read-only
          STATUS mandatory
          DESCRIPTION
               ""
          ::= { teraSonetPathCurrTotalTableEntry 6 }

     -- teraSonetPathTotalTable

teraSonetPathTotalTable OBJECT-TYPE
     SYNTAX SEQUENCE OF TeraSonetPathTotalTableEntryType
     ACCESS not-accessible
     STATUS mandatory
     DESCRIPTION
          " table teraSonetPathTotalTable"
     ::= { teraSonetGroup 14 }

teraSonetPathTotalTableEntry OBJECT-TYPE
          SYNTAX TeraSonetPathTotalTableEntryType
          ACCESS not-accessible
          STATUS mandatory
          DESCRIPTION
               " table entry teraSonetPathTotalTableEntry "
          INDEX {                   ifIndex,                  teraSonetPathTotalNumber }
     ::= { teraSonetPathTotalTable 1 }

TeraSonetPathTotalTableEntryType ::= SEQUENCE {
          teraSonetPathTotalNumber   
             INTEGER (1..7),
          teraSonetPathTotalESs   
             Gauge32,
          teraSonetPathTotalSESs   
             Gauge32,
          teraSonetPathTotalCVs   
             Gauge32,
          teraSonetPathTotalUASs   
             Gauge32,
          teraSonetPathTotalValidData   
             INTEGER
}

teraSonetPathTotalNumber OBJECT-TYPE
          SYNTAX INTEGER (1..7)
          ACCESS read-only
          STATUS mandatory
          DESCRIPTION
               ""
          ::= { teraSonetPathTotalTableEntry 1 }

teraSonetPathTotalESs OBJECT-TYPE
          SYNTAX Gauge32
          ACCESS read-only
          STATUS mandatory
          DESCRIPTION
               ""
          ::= { teraSonetPathTotalTableEntry 2 }

teraSonetPathTotalSESs OBJECT-TYPE
          SYNTAX Gauge32
          ACCESS read-only
          STATUS mandatory
          DESCRIPTION
               ""
          ::= { teraSonetPathTotalTableEntry 3 }

teraSonetPathTotalCVs OBJECT-TYPE
          SYNTAX Gauge32
          ACCESS read-only
          STATUS mandatory
          DESCRIPTION
               ""
          ::= { teraSonetPathTotalTableEntry 4 }

teraSonetPathTotalUASs OBJECT-TYPE
          SYNTAX Gauge32
          ACCESS read-only
          STATUS mandatory
          DESCRIPTION
               ""
          ::= { teraSonetPathTotalTableEntry 5 }

teraSonetPathTotalValidData OBJECT-TYPE
          SYNTAX INTEGER
          ACCESS read-only
          STATUS mandatory
          DESCRIPTION
               ""
          ::= { teraSonetPathTotalTableEntry 6 }

     -- teraSonetFarEndPathCurrTotalTable

teraSonetFarEndPathCurrTotalTable OBJECT-TYPE
     SYNTAX SEQUENCE OF TeraSonetFarEndPathCurrTotalTableEntryType
     ACCESS not-accessible
     STATUS mandatory
     DESCRIPTION
          " table teraSonetFarEndPathCurrTotalTable"
     ::= { teraSonetGroup 15 }

teraSonetFarEndPathCurrTotalTableEntry OBJECT-TYPE
          SYNTAX TeraSonetFarEndPathCurrTotalTableEntryType
          ACCESS not-accessible
          STATUS mandatory
          DESCRIPTION
               " table entry teraSonetFarEndPathCurrTotalTableEntry "
          INDEX {                   ifIndex }
     ::= { teraSonetFarEndPathCurrTotalTable 1 }

TeraSonetFarEndPathCurrTotalTableEntryType ::= SEQUENCE {
          teraSonetFarEndPathCurrTotalESs   
             Gauge32,
          teraSonetFarEndPathCurrTotalSESs   
             Gauge32,
          teraSonetFarEndPathCurrTotalCVs   
             Gauge32,
          teraSonetFarEndPathCurrTotalUASs   
             Gauge32
}

teraSonetFarEndPathCurrTotalESs OBJECT-TYPE
          SYNTAX Gauge32
          ACCESS read-only
          STATUS mandatory
          DESCRIPTION
               ""
          ::= { teraSonetFarEndPathCurrTotalTableEntry 1 }

teraSonetFarEndPathCurrTotalSESs OBJECT-TYPE
          SYNTAX Gauge32
          ACCESS read-only
          STATUS mandatory
          DESCRIPTION
               ""
          ::= { teraSonetFarEndPathCurrTotalTableEntry 2 }

teraSonetFarEndPathCurrTotalCVs OBJECT-TYPE
          SYNTAX Gauge32
          ACCESS read-only
          STATUS mandatory
          DESCRIPTION
               ""
          ::= { teraSonetFarEndPathCurrTotalTableEntry 3 }

teraSonetFarEndPathCurrTotalUASs OBJECT-TYPE
          SYNTAX Gauge32
          ACCESS read-only
          STATUS mandatory
          DESCRIPTION
               ""
          ::= { teraSonetFarEndPathCurrTotalTableEntry 4 }

     -- teraSonetFarEndPathTotalTable

teraSonetFarEndPathTotalTable OBJECT-TYPE
     SYNTAX SEQUENCE OF TeraSonetFarEndPathTotalTableEntryType
     ACCESS not-accessible
     STATUS mandatory
     DESCRIPTION
          " table teraSonetFarEndPathTotalTable"
     ::= { teraSonetGroup 16 }

teraSonetFarEndPathTotalTableEntry OBJECT-TYPE
          SYNTAX TeraSonetFarEndPathTotalTableEntryType
          ACCESS not-accessible
          STATUS mandatory
          DESCRIPTION
               " table entry teraSonetFarEndPathTotalTableEntry "
          INDEX {                   ifIndex,                  teraSonetFarEndPathTotalNumber }
     ::= { teraSonetFarEndPathTotalTable 1 }

TeraSonetFarEndPathTotalTableEntryType ::= SEQUENCE {
          teraSonetFarEndPathTotalNumber   
             INTEGER (1..7),
          teraSonetFarEndPathTotalESs   
             Gauge32,
          teraSonetFarEndPathTotalSESs   
             Gauge32,
          teraSonetFarEndPathTotalCVs   
             Gauge32,
          teraSonetFarEndPathTotalUASs   
             Gauge32,
          teraSonetFarEndPathTotalValidData   
             INTEGER
}

teraSonetFarEndPathTotalNumber OBJECT-TYPE
          SYNTAX INTEGER (1..7)
          ACCESS read-only
          STATUS mandatory
          DESCRIPTION
               ""
          ::= { teraSonetFarEndPathTotalTableEntry 1 }

teraSonetFarEndPathTotalESs OBJECT-TYPE
          SYNTAX Gauge32
          ACCESS read-only
          STATUS mandatory
          DESCRIPTION
               ""
          ::= { teraSonetFarEndPathTotalTableEntry 2 }

teraSonetFarEndPathTotalSESs OBJECT-TYPE
          SYNTAX Gauge32
          ACCESS read-only
          STATUS mandatory
          DESCRIPTION
               ""
          ::= { teraSonetFarEndPathTotalTableEntry 3 }

teraSonetFarEndPathTotalCVs OBJECT-TYPE
          SYNTAX Gauge32
          ACCESS read-only
          STATUS mandatory
          DESCRIPTION
               ""
          ::= { teraSonetFarEndPathTotalTableEntry 4 }

teraSonetFarEndPathTotalUASs OBJECT-TYPE
          SYNTAX Gauge32
          ACCESS read-only
          STATUS mandatory
          DESCRIPTION
               ""
          ::= { teraSonetFarEndPathTotalTableEntry 5 }

teraSonetFarEndPathTotalValidData OBJECT-TYPE
          SYNTAX INTEGER
          ACCESS read-only
          STATUS mandatory
          DESCRIPTION
               ""
          ::= { teraSonetFarEndPathTotalTableEntry 6 }

     -- teraSonetVTCurrTotalTable

teraSonetVTCurrTotalTable OBJECT-TYPE
     SYNTAX SEQUENCE OF TeraSonetVTCurrTotalTableEntryType
     ACCESS not-accessible
     STATUS mandatory
     DESCRIPTION
          " table teraSonetVTCurrTotalTable"
     ::= { teraSonetGroup 17 }

teraSonetVTCurrTotalTableEntry OBJECT-TYPE
          SYNTAX TeraSonetVTCurrTotalTableEntryType
          ACCESS not-accessible
          STATUS mandatory
          DESCRIPTION
               " table entry teraSonetVTCurrTotalTableEntry "
          INDEX {                   ifIndex }
     ::= { teraSonetVTCurrTotalTable 1 }

TeraSonetVTCurrTotalTableEntryType ::= SEQUENCE {
          teraSonetVTCurrTotalWidth   
             INTEGER,
          teraSonetVTCurrTotalStatus   
             INTEGER (1..126),
          teraSonetVTCurrTotalESs   
             Gauge32,
          teraSonetVTCurrTotalSESs   
             Gauge32,
          teraSonetVTCurrTotalCVs   
             Gauge32,
          teraSonetVTCurrTotalUASs   
             Gauge32,
          teraSonetVTCurrTotalPerfStat   
             INTEGER
}

teraSonetVTCurrTotalWidth OBJECT-TYPE
          SYNTAX INTEGER
                  {
                  vtWidth15VC11(1),
                  vtWidth2VC12(2)
                  }
          ACCESS read-only
          STATUS mandatory
          DESCRIPTION
               ""
          ::= { teraSonetVTCurrTotalTableEntry 1 }

teraSonetVTCurrTotalStatus OBJECT-TYPE
          SYNTAX INTEGER (1..126)
          ACCESS read-only
          STATUS mandatory
          DESCRIPTION
               ""
          ::= { teraSonetVTCurrTotalTableEntry 2 }

teraSonetVTCurrTotalESs OBJECT-TYPE
          SYNTAX Gauge32
          ACCESS read-only
          STATUS mandatory
          DESCRIPTION
               ""
          ::= { teraSonetVTCurrTotalTableEntry 3 }

teraSonetVTCurrTotalSESs OBJECT-TYPE
          SYNTAX Gauge32
          ACCESS read-only
          STATUS mandatory
          DESCRIPTION
               ""
          ::= { teraSonetVTCurrTotalTableEntry 4 }

teraSonetVTCurrTotalCVs OBJECT-TYPE
          SYNTAX Gauge32
          ACCESS read-only
          STATUS mandatory
          DESCRIPTION
               ""
          ::= { teraSonetVTCurrTotalTableEntry 5 }

teraSonetVTCurrTotalUASs OBJECT-TYPE
          SYNTAX Gauge32
          ACCESS read-only
          STATUS mandatory
          DESCRIPTION
               ""
          ::= { teraSonetVTCurrTotalTableEntry 6 }

teraSonetVTCurrTotalPerfStat OBJECT-TYPE
          SYNTAX INTEGER
                  {
                  ok(1),
                  clear(2),
                  clrall(3)
                  }
          ACCESS read-write
          STATUS mandatory
          DESCRIPTION
               ""
          ::= { teraSonetVTCurrTotalTableEntry 7 }

     -- teraSonetVTTotalTable

teraSonetVTTotalTable OBJECT-TYPE
     SYNTAX SEQUENCE OF TeraSonetVTTotalTableEntryType
     ACCESS not-accessible
     STATUS mandatory
     DESCRIPTION
          " table teraSonetVTTotalTable"
     ::= { teraSonetGroup 18 }

teraSonetVTTotalTableEntry OBJECT-TYPE
          SYNTAX TeraSonetVTTotalTableEntryType
          ACCESS not-accessible
          STATUS mandatory
          DESCRIPTION
               " table entry teraSonetVTTotalTableEntry "
          INDEX {                   ifIndex,                  teraSonetVTTotalNumber }
     ::= { teraSonetVTTotalTable 1 }

TeraSonetVTTotalTableEntryType ::= SEQUENCE {
          teraSonetVTTotalNumber   
             INTEGER (1..7),
          teraSonetVTTotalESs   
             Gauge32,
          teraSonetVTTotalSESs   
             Gauge32,
          teraSonetVTTotalCVs   
             Gauge32,
          teraSonetVTTotalUASs   
             Gauge32,
          teraSonetVTTotalValidData   
             INTEGER
}

teraSonetVTTotalNumber OBJECT-TYPE
          SYNTAX INTEGER (1..7)
          ACCESS read-only
          STATUS mandatory
          DESCRIPTION
               ""
          ::= { teraSonetVTTotalTableEntry 1 }

teraSonetVTTotalESs OBJECT-TYPE
          SYNTAX Gauge32
          ACCESS read-only
          STATUS mandatory
          DESCRIPTION
               ""
          ::= { teraSonetVTTotalTableEntry 2 }

teraSonetVTTotalSESs OBJECT-TYPE
          SYNTAX Gauge32
          ACCESS read-only
          STATUS mandatory
          DESCRIPTION
               ""
          ::= { teraSonetVTTotalTableEntry 3 }

teraSonetVTTotalCVs OBJECT-TYPE
          SYNTAX Gauge32
          ACCESS read-only
          STATUS mandatory
          DESCRIPTION
               ""
          ::= { teraSonetVTTotalTableEntry 4 }

teraSonetVTTotalUASs OBJECT-TYPE
          SYNTAX Gauge32
          ACCESS read-only
          STATUS mandatory
          DESCRIPTION
               ""
          ::= { teraSonetVTTotalTableEntry 5 }

teraSonetVTTotalValidData OBJECT-TYPE
          SYNTAX INTEGER
          ACCESS read-only
          STATUS mandatory
          DESCRIPTION
               ""
          ::= { teraSonetVTTotalTableEntry 6 }

     -- teraSonetFarEndVTCurrTotalTable

teraSonetFarEndVTCurrTotalTable OBJECT-TYPE
     SYNTAX SEQUENCE OF TeraSonetFarEndVTCurrTotalTableEntryType
     ACCESS not-accessible
     STATUS mandatory
     DESCRIPTION
          " table teraSonetFarEndVTCurrTotalTable"
     ::= { teraSonetGroup 19 }

teraSonetFarEndVTCurrTotalTableEntry OBJECT-TYPE
          SYNTAX TeraSonetFarEndVTCurrTotalTableEntryType
          ACCESS not-accessible
          STATUS mandatory
          DESCRIPTION
               " table entry teraSonetFarEndVTCurrTotalTableEntry "
          INDEX {                   ifIndex }
     ::= { teraSonetFarEndVTCurrTotalTable 1 }

TeraSonetFarEndVTCurrTotalTableEntryType ::= SEQUENCE {
          teraSonetFarEndVTCurrTotalESs   
             Gauge32,
          teraSonetFarEndVTCurrTotalSES   
             Gauge32,
          teraSonetFarEndVTCurrTotalCVs   
             Gauge32,
          teraSonetFarEndVTCurrTotalUASs   
             Gauge32
}

teraSonetFarEndVTCurrTotalESs OBJECT-TYPE
          SYNTAX Gauge32
          ACCESS read-only
          STATUS mandatory
          DESCRIPTION
               ""
          ::= { teraSonetFarEndVTCurrTotalTableEntry 1 }

teraSonetFarEndVTCurrTotalSES OBJECT-TYPE
          SYNTAX Gauge32
          ACCESS read-only
          STATUS mandatory
          DESCRIPTION
               ""
          ::= { teraSonetFarEndVTCurrTotalTableEntry 2 }

teraSonetFarEndVTCurrTotalCVs OBJECT-TYPE
          SYNTAX Gauge32
          ACCESS read-only
          STATUS mandatory
          DESCRIPTION
               ""
          ::= { teraSonetFarEndVTCurrTotalTableEntry 3 }

teraSonetFarEndVTCurrTotalUASs OBJECT-TYPE
          SYNTAX Gauge32
          ACCESS read-only
          STATUS mandatory
          DESCRIPTION
               ""
          ::= { teraSonetFarEndVTCurrTotalTableEntry 4 }

     -- teraSonetFarEndVTTotalTable

teraSonetFarEndVTTotalTable OBJECT-TYPE
     SYNTAX SEQUENCE OF TeraSonetFarEndVTTotalTableEntryType
     ACCESS not-accessible
     STATUS mandatory
     DESCRIPTION
          " table teraSonetFarEndVTTotalTable"
     ::= { teraSonetGroup 20 }

teraSonetFarEndVTTotalTableEntry OBJECT-TYPE
          SYNTAX TeraSonetFarEndVTTotalTableEntryType
          ACCESS not-accessible
          STATUS mandatory
          DESCRIPTION
               " table entry teraSonetFarEndVTTotalTableEntry "
          INDEX {                   ifIndex,                  teraSonetFarEndVTTotalNumber }
     ::= { teraSonetFarEndVTTotalTable 1 }

TeraSonetFarEndVTTotalTableEntryType ::= SEQUENCE {
          teraSonetFarEndVTTotalNumber   
             INTEGER (1..96),
          teraSonetFarEndVTTotalESs   
             Gauge32,
          teraSonetFarEndVTTotalSESs   
             Gauge32,
          teraSonetFarEndVTTotalCVs   
             Gauge32,
          teraSonetFarEndVTTotalUASs   
             Gauge32,
          teraSonetFarEndVTTotalValidData   
             INTEGER
}

teraSonetFarEndVTTotalNumber OBJECT-TYPE
          SYNTAX INTEGER (1..96)
          ACCESS read-only
          STATUS mandatory
          DESCRIPTION
               ""
          ::= { teraSonetFarEndVTTotalTableEntry 1 }

teraSonetFarEndVTTotalESs OBJECT-TYPE
          SYNTAX Gauge32
          ACCESS read-only
          STATUS mandatory
          DESCRIPTION
               ""
          ::= { teraSonetFarEndVTTotalTableEntry 2 }

teraSonetFarEndVTTotalSESs OBJECT-TYPE
          SYNTAX Gauge32
          ACCESS read-only
          STATUS mandatory
          DESCRIPTION
               ""
          ::= { teraSonetFarEndVTTotalTableEntry 3 }

teraSonetFarEndVTTotalCVs OBJECT-TYPE
          SYNTAX Gauge32
          ACCESS read-only
          STATUS mandatory
          DESCRIPTION
               ""
          ::= { teraSonetFarEndVTTotalTableEntry 4 }

teraSonetFarEndVTTotalUASs OBJECT-TYPE
          SYNTAX Gauge32
          ACCESS read-only
          STATUS mandatory
          DESCRIPTION
               ""
          ::= { teraSonetFarEndVTTotalTableEntry 5 }

teraSonetFarEndVTTotalValidData OBJECT-TYPE
          SYNTAX INTEGER
          ACCESS read-only
          STATUS mandatory
          DESCRIPTION
               ""
          ::= { teraSonetFarEndVTTotalTableEntry 6 }

     -- teraSonetVTConfigTable

teraSonetVTConfigTable OBJECT-TYPE
     SYNTAX SEQUENCE OF TeraSonetVTConfigTableEntryType
     ACCESS not-accessible
     STATUS mandatory
     DESCRIPTION
          " table teraSonetVTConfigTable"
     ::= { teraSonetGroup 21 }

teraSonetVTConfigTableEntry OBJECT-TYPE
          SYNTAX TeraSonetVTConfigTableEntryType
          ACCESS not-accessible
          STATUS mandatory
          DESCRIPTION
               " table entry teraSonetVTConfigTableEntry "
          INDEX {                   ifIndex }
     ::= { teraSonetVTConfigTable 1 }

TeraSonetVTConfigTableEntryType ::= SEQUENCE {
          teraSonetVTConfigERDIEnable   
             INTEGER,
          teraSonetVTLoopbackConfig   
             INTEGER
}

teraSonetVTConfigERDIEnable OBJECT-TYPE
          SYNTAX INTEGER
                  {
                  enable(1),
                  disable(2)
                  }
          ACCESS read-write
          STATUS mandatory
          DESCRIPTION
               ""
          ::= { teraSonetVTConfigTableEntry 1 }

teraSonetVTLoopbackConfig OBJECT-TYPE
          SYNTAX INTEGER
                  {
                  noLoop(1),
                  lineLoop(2),
                  diagLoop(3)
                  }
          ACCESS read-write
          STATUS mandatory
          DESCRIPTION
               ""
          ::= { teraSonetVTConfigTableEntry 2 }

END
