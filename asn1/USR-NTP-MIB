USR-NTP-MIB DEFINITIONS ::= BEGIN
        IMPORTS
          OBJECT-TYPE, MODULE-IDENTITY, Integer32, OBJECT-IDENTITY,
          Counter32, IpAddress, NOTIFICATION-TYPE
                FROM SNMPv2-SMI
          DisplayString
                FROM SNMPv2-TC
          MODULE-COMPLIANCE,
          OBJECT-GROUP
                FROM SNMPv2-CONF
          common, UsrConfigStatus, UsrDisplayString
                FROM USR-DEFINITIONS-MIB;
usrNTPMib MODULE-IDENTITY
    LAST-UPDATED        "200208231640Z"
    ORGANIZATION        "CommWorks Corporation"
    CONTACT-INFO        "Customer Support"
    DESCRIPTION
     "This MIB Module defines the CommWorks private interface
      to the Simple Network Time Protocol client process.
      The process can be configured with up to two alternate servers,
      a primary server and a secondary server. The primary server is
      always contacted first, the secondary server is contacted after
      all retransmissions to the primary failed have failed.
      The implementation is based on RFC 2030, using unicast mode
      only.
      Note that all the writable objects include a 'DEFVAL'
      clause. The clause is intended to be used as a reference only,
      in case an agent has no previously saved configuration.
      Typically, at start-up, an agent will load data saved from a
      previous session - thus 'DEFVAL' is used mainly for new
      systems."
--   REVISION   "200208231640Z"
--   DESCRIPTION "Clarified usage and labels for usrNTPEnable."
--   REVISION   "200202211500Z"
--   DESCRIPTION "Convert traps to SNMPv2"
    ::= { common 34 }
usrNTPObjects OBJECT IDENTIFIER ::= { usrNTPMib 1 }
usrNTPTraps   OBJECT IDENTIFIER ::= { usrNTPMib 3 }
-- Begin managed object definitions here...
usrNTPPrimaryServer OBJECT-TYPE
    SYNTAX      DisplayString (SIZE (0..132))
    MAX-ACCESS  read-write
    STATUS      current
    DESCRIPTION
     "The IP address or host name of the primary NTP server that the
      module will query for time synchronization.
      An empty string means that no primary server is defined."
    DEFVAL { "" }
    --CONFIGURABLE
    ::= { usrNTPObjects 1 }     
usrNTPSecondaryServer OBJECT-TYPE
    SYNTAX      DisplayString (SIZE (0..132))
    MAX-ACCESS  read-write
    STATUS      current
    DESCRIPTION
     "The IP address or host name of the secondary NTP server that the
      module will query for time synchronization whenever the primary
      server is unavailable.
      An empty string means that no secondary server is defined."
    DEFVAL { "" }
    --CONFIGURABLE
    ::= { usrNTPObjects 2 }
usrNTPPollingInterval OBJECT-TYPE
    SYNTAX      Integer32 (64..16284)
    UNITS       "seconds"
    MAX-ACCESS  read-write
    STATUS      current
    DESCRIPTION
     "The polling interval used by the NTP process to gather time
      synchronization information. In seconds.
      The range available is 64 seconds to 1024 seconds. The default is 600
      seconds (10 minutes)."
    REFERENCE "RFC 1305 (NTPv3)."
    DEFVAL { 600 }
    --CONFIGURABLE
    ::= { usrNTPObjects 3 }
usrNTPMaxRetransmits OBJECT-TYPE
    SYNTAX      Integer32 (1..200)
    MAX-ACCESS  read-write
    STATUS      current
    DESCRIPTION 
     "The maximum number of times a request will be retransmitted to a
      given server before the server is considered unavailable. The range
      allowed is 1 to 200 times. The default is 5 times."
    DEFVAL { 5 }
    --CONFIGURABLE
    ::= { usrNTPObjects 4 }
usrNTPTimeOut OBJECT-TYPE
    SYNTAX      Integer32 (1..60)
    UNITS       "seconds"
    MAX-ACCESS  read-write
    STATUS      current
    DESCRIPTION
     "The number of seconds since a request has been sent to a server,
      after which period the request is considered timed-out.
      The range for this is 1 second to 1 minute. The default is 10
      seconds."
    DEFVAL { 10 }
    --CONFIGURABLE
    ::= { usrNTPObjects 5 }
usrNTPEnable OBJECT-TYPE
    SYNTAX      INTEGER {
                    enabled(1),
                    disabled(2)
                    }
    MAX-ACCESS  read-write
    STATUS      current
    DESCRIPTION
     "This object enables or disables NTP synchronization in a
      system. Default is disabled."
    DEFVAL { disabled }
    --CONFIGURABLE
    ::= { usrNTPObjects 6 }
usrNTPProtocolVersion OBJECT-TYPE
    SYNTAX INTEGER {
        ntpV3(3),
        ntpV4(4)
      }
    MAX-ACCESS  read-write
    STATUS      current
    DESCRIPTION
     "The protocol version that the NTP client will use when sending NTP
      client requests to a server."
    DEFVAL { ntpV3 }
    --CONFIGURABLE
    ::= { usrNTPObjects 7 }
usrNTPCfmFileName OBJECT-TYPE
    SYNTAX      DisplayString (SIZE (1..32))
    MAX-ACCESS  read-only
    STATUS      current
    DESCRIPTION
     "The name of the configuration file currently in use."
    DEFVAL { "@file://Ntp.cfg" }
    ::= { usrNTPObjects 8 }
usrNTPCfmSaveFlag OBJECT-TYPE
    SYNTAX      UsrConfigStatus
    MAX-ACCESS  read-write
    STATUS      current
    DESCRIPTION
     "Setting the value of this object to `save' causes the values of the
     NTP Group to be written out to the current config file, which
     is stored in the usrNTPCfmFileName object. While the new
     ConfigFile is being written, the NTP process will set the value
     of this flag set to `saving''. Any attempts to set the value while it
     is  not `normal' (i.e. the file is currently being written to the
     ConfigFile) will result in a badValue error being returned. Setting
     the value to `normal' will result in no action."
    ::= { usrNTPObjects 9 }
usrNTPModuleVersion OBJECT-TYPE
    SYNTAX      DisplayString
    MAX-ACCESS  read-only
    STATUS      current
    DESCRIPTION
     "The current software version of the NTP module."
    ::= { usrNTPObjects 10 }
usrNTPLastGoodServer OBJECT-TYPE
    SYNTAX      DisplayString
    MAX-ACCESS  read-only
    STATUS      current
    DESCRIPTION
     "The symbolic host name of the last server from which
      time synchronization information was received (if there was a numeric
      address defined, this will be a numeric address in dot notation)."
    ::= { usrNTPObjects 11 }
usrNTPRcvdDatagrams OBJECT-TYPE
    SYNTAX      Counter32
    MAX-ACCESS  read-only
    STATUS      current
    DESCRIPTION
     "Number of datagrams received at the port on which NTP is listening to."
    ::= { usrNTPObjects 12 }
usrNTPRcvdTooShorts OBJECT-TYPE
    SYNTAX      Counter32
    MAX-ACCESS  read-only
    STATUS      current
    DESCRIPTION
     "Number of datagrams received which were too short for NTP version
      four."
    ::= { usrNTPObjects 13 }
usrNTPRcvdBadVersions OBJECT-TYPE
    SYNTAX      Counter32
    MAX-ACCESS  read-only
    STATUS      current
    DESCRIPTION
     "Number of datagrams received with a wrong NTP version."
    ::= { usrNTPObjects 14 }
usrNTPRcvdRequests OBJECT-TYPE
    SYNTAX      Counter32
    MAX-ACCESS  read-only
    STATUS      current
    DESCRIPTION
     "Number of NTP requests received."
    ::= { usrNTPObjects 15 }
usrNTPRcvdReplies OBJECT-TYPE
    SYNTAX      Counter32
    MAX-ACCESS  read-only
    STATUS      current
    DESCRIPTION
     "Number of NTP replies received."
    ::= { usrNTPObjects 16 }
usrNTPRcvdUnsuportedModes OBJECT-TYPE
    SYNTAX      Counter32
    MAX-ACCESS  read-only
    STATUS      current
    DESCRIPTION
     "Number of NTP datagrams received which had a mode value not supported
      by this entity."
    ::= { usrNTPObjects 17 }
usrNTPSentRequests OBJECT-TYPE
    SYNTAX      Counter32
    MAX-ACCESS  read-only
    STATUS      current
    DESCRIPTION
     "Number of NTP requests sent."
    ::= { usrNTPObjects 18 }
usrNTPSentReplies OBJECT-TYPE
    SYNTAX      Counter32
    MAX-ACCESS  read-only
    STATUS      current
    DESCRIPTION
     "Number of NTP replies sent since the system was last rebooted."
    ::= { usrNTPObjects 19 }
usrNTPSentRexmits OBJECT-TYPE
    SYNTAX      Counter32
    MAX-ACCESS  read-only
    STATUS      current
    DESCRIPTION
     "Number of NTP requests that were retransmitted due to lack of a timely
      reply."
    ::= { usrNTPObjects 20 }
usrNTPSendErrors OBJECT-TYPE
    SYNTAX      Counter32
    MAX-ACCESS  read-only
    STATUS      current
    DESCRIPTION
     "Number of NTP requests that could not be sent due to internal errors."
    ::= { usrNTPObjects 21 }
usrNTPDnsErrors OBJECT-TYPE
    SYNTAX      Counter32
    MAX-ACCESS  read-only
    STATUS      current
    DESCRIPTION
     "Number of times an error was returned by DNS when processing a name
      resolution request from the NTP module."
    ::= { usrNTPObjects 22 }
usrNTPServerTimeouts OBJECT-TYPE
    SYNTAX      Counter32
    MAX-ACCESS  read-only
    STATUS      current
    DESCRIPTION
     "Number of times a server was considered unavailable after requests
      were sent to it a maximum number of retransmissions without a reply."
    ::= { usrNTPObjects 23 }
usrNTPAllocErrors OBJECT-TYPE
    SYNTAX      Counter32
    MAX-ACCESS  read-only
    STATUS      current
    DESCRIPTION
     "Number of times an operation could not be performed due to a failure
      to allocate memory resources."
    ::= { usrNTPObjects 24 }
usrNTPResolvedIPAddress OBJECT-TYPE
    SYNTAX      IpAddress
    MAX-ACCESS  read-only
    STATUS      current
    DESCRIPTION
     "The IP address resolved from the 'current' server with which
      synchronization is being attempted.
      If there is no resolution, or there is no current server defined, this
      object returns zero."
    ::= { usrNTPObjects 25 }
usrNTPLastRcvdLeapIndicator OBJECT-TYPE
    SYNTAX      Integer32 (0..3)
    MAX-ACCESS  read-only
    STATUS      current
    DESCRIPTION
     "The value of the last received Leap Indicator field."
    REFERENCE "RFC 2030 (NTPv4)."
    ::= { usrNTPObjects 26 }
usrNTPLastRcvdMode OBJECT-TYPE
    SYNTAX      Integer32 (0..7)
    MAX-ACCESS  read-only
    STATUS      current
    DESCRIPTION
     "The value of the last received Mode field."
    REFERENCE "RFC 2030 (NTPv4)."
    ::= { usrNTPObjects 27 }
usrNTPLastRcvdStratum OBJECT-TYPE
    SYNTAX      Integer32 (0..255)
    MAX-ACCESS  read-only
    STATUS      current
    DESCRIPTION
     "The value of the last received Stratum field."
    REFERENCE "RFC 2030 (NTPv4)."
    ::= { usrNTPObjects 28 }
usrNTPLastRcvdPoll OBJECT-TYPE
    SYNTAX      Integer32 (0..255)
    MAX-ACCESS  read-only
    STATUS      current
    DESCRIPTION
     "The value of the last received Poll field."
    REFERENCE "RFC 2030 (NTPv4)."
    ::= { usrNTPObjects 29 }
usrNTPLastRcvdPrecision OBJECT-TYPE
    SYNTAX      Integer32 (-127..127)
    MAX-ACCESS  read-only
    STATUS      current
    DESCRIPTION
     "The value of the last received Precision field."
    REFERENCE "RFC 2030 (NTPv4)."
    ::= { usrNTPObjects 30 }
usrNTPLastRcvdRootDelay OBJECT-TYPE
    SYNTAX      Integer32
    MAX-ACCESS  read-only
    STATUS      current
    DESCRIPTION
     "The value of the last received Root Delay field."
    REFERENCE "RFC 2030 (NTPv4)."
    ::= { usrNTPObjects 31 }
usrNTPLastRcvdRootDispersion OBJECT-TYPE
    SYNTAX      Integer32
    MAX-ACCESS  read-only
    STATUS      current
    DESCRIPTION
     "The value of the last received Root Dispersion field."
    REFERENCE "RFC 2030 (NTPv4)."
    ::= { usrNTPObjects 32 }
usrNTPLastRcvdReferenceIdentifier OBJECT-TYPE
    SYNTAX      Integer32
    MAX-ACCESS  read-only
    STATUS      current
    DESCRIPTION
     "The value of the last received Reference Identifier field."
    REFERENCE "RFC 2030 (NTPv4)."
    ::= { usrNTPObjects 33 }
usrNTPLastRcvdReferenceTimestampHigh OBJECT-TYPE
    SYNTAX      Integer32
    MAX-ACCESS  read-only
    STATUS      current
    DESCRIPTION
     "The value of the last received Reference Timestamp field (high octets)."
    REFERENCE "RFC 2030 (NTPv4)."
    ::= { usrNTPObjects 34 }
usrNTPLastRcvdReferenceTimestampLow OBJECT-TYPE
    SYNTAX      Integer32
    MAX-ACCESS  read-only
    STATUS      current
    DESCRIPTION
     "The value of the last received Reference Timestamp field (low octets)."
    REFERENCE "RFC 2030 (NTPv4)."
    ::= { usrNTPObjects 35 }
usrNTPLastRcvdOriginateTimestampHigh OBJECT-TYPE
    SYNTAX      Integer32
    MAX-ACCESS  read-only
    STATUS      current
    DESCRIPTION
     "The value of the last received Originate Timestamp field (high octets)."
    REFERENCE "RFC 2030 (NTPv4)."
    ::= { usrNTPObjects 36 }
usrNTPLastRcvdOriginateTimestampLow OBJECT-TYPE
    SYNTAX      Integer32
    MAX-ACCESS  read-only
    STATUS      current
    DESCRIPTION
     "The value of the last received Originate Timestamp field (low octets)."
    REFERENCE "RFC 2030 (NTPv4)."
    ::= { usrNTPObjects 37 }
usrNTPLastRcvdReceiveTimestampHigh OBJECT-TYPE
    SYNTAX      Integer32
    MAX-ACCESS  read-only
    STATUS      current
    DESCRIPTION
     "The value of the last received Receive Timestamp field (high octets)."
    REFERENCE "RFC 2030 (NTPv4)."
    ::= { usrNTPObjects 38 }
usrNTPLastRcvdReceiveTimestampLow OBJECT-TYPE
    SYNTAX      Integer32
    MAX-ACCESS  read-only
    STATUS      current
    DESCRIPTION
     "The value of the last received Receive Timestamp field (low octets)."
    REFERENCE "RFC 2030 (NTPv4)."
    ::= { usrNTPObjects 39 }
usrNTPLastRcvdTransmitTimestampHigh OBJECT-TYPE
    SYNTAX      Integer32
    MAX-ACCESS  read-only
    STATUS      current
    DESCRIPTION
     "The value of the last received Transmit Timestamp field (high octets)."
    REFERENCE "RFC 2030 (NTPv4)."
    ::= { usrNTPObjects 40 }
usrNTPLastRcvdTransmitTimestampLow OBJECT-TYPE
    SYNTAX      Integer32
    MAX-ACCESS  read-only
    STATUS      current
    DESCRIPTION
     "The value of the last received Transmit Timestamp field (low octets)."
    REFERENCE "RFC 2030 (NTPv4)."
    ::= { usrNTPObjects 41 }
usrNTPTimeZone OBJECT-TYPE
    SYNTAX      UsrDisplayString
    MAX-ACCESS  read-write
    STATUS      current
    DESCRIPTION
      "Timezone variables; should be one of the following,
    Egypt, Libya, PRC, ROC, Hongkong, Iran, Israel, Japan, ROK, Singapore,
    Australia/Tasmania, Australia/Queensland, Australia/North,
    Australia/West, Australia/South, Australia/Victoria, Australia/NSW,
    Australia/Yancowinna, Australia/LHI, NZ, GMT, GMT-12, GMT-11, GMT-10,
    GMT-9, GMT-8, GMT-7, GMT-6, GMT-5, GMT-4, GMT-3, GMT-2, GMT-1, GMT+1,
    GMT+2, GMT+3, GMT+4, GMT+5, GMT+6, GMT+7, GMT+8, GMT+9, GMT+10, GMT+11,
    GMT+12, GMT+13, UTC, Universal, Greenwich, Zulu, GMT-0, GMT+0, GB-Eire,
    WET, Iceland, MET, EET, Turkey, W-SU, CET, Factory, US/Eastern, 
    US/Central, US/Mountain, US/Pacific, US/Alaska, US/East-Indiana, 
    US/Arizona, US/Michigan, US/Samoa, US/Aleutian, US/Hawaii, 
    Canada/Newfoundland, Canada/Atlantic, Canada/Eastern, Canada/Central,
    Canada/East-Saskatchewan, Canada/Mountain, Canada/Pacific, Canada/Yukon,
    Mexico/BajaNorte, Mexico/BajaSur, Mexico/General, Cuba, Navajo, Jamaica,
    Brazil/East, Brazil/West, Brazil/Acre, Brazil/DeNoronha, 
    Chile/Continental, Chile/EasterIsland."
    --CONFIGURABLE
    ::= { usrNTPObjects 42 }
--
-- conformance information
--
usrNTPConformance OBJECT IDENTIFIER ::= { usrNTPMib 2 }
usrNTPCompliances OBJECT IDENTIFIER ::= { usrNTPConformance 1 }
usrNTPGroups      OBJECT IDENTIFIER ::= { usrNTPConformance 2 }
usrNTPCompliance MODULE-COMPLIANCE
    STATUS        current
    DESCRIPTION
     "The compliance statement for entities which implement
      the MIB."
    MODULE    -- this module
    MANDATORY-GROUPS {
      usrNTPGroup
    }
    ::= { usrNTPCompliances 1 }
-- units of conformance
usrNTPGroup OBJECT-GROUP
    OBJECTS {
      usrNTPPrimaryServer,
      usrNTPSecondaryServer,
      usrNTPPollingInterval,
      usrNTPMaxRetransmits,
      usrNTPTimeOut,
      usrNTPEnable,
      usrNTPProtocolVersion,
      usrNTPCfmFileName,
      usrNTPCfmSaveFlag,
      usrNTPModuleVersion,
      usrNTPLastGoodServer,
      usrNTPRcvdDatagrams,
      usrNTPRcvdTooShorts,
      usrNTPRcvdBadVersions,
      usrNTPRcvdRequests,
      usrNTPRcvdReplies,
      usrNTPRcvdUnsuportedModes,
      usrNTPSentRequests,
      usrNTPSentReplies,
      usrNTPSentRexmits,
      usrNTPSendErrors,
      usrNTPDnsErrors,
      usrNTPServerTimeouts,
      usrNTPAllocErrors,
      usrNTPResolvedIPAddress,
      usrNTPLastRcvdLeapIndicator,
      usrNTPLastRcvdMode,
      usrNTPLastRcvdStratum,
      usrNTPLastRcvdPoll,
      usrNTPLastRcvdPrecision,
      usrNTPLastRcvdRootDelay,
      usrNTPLastRcvdRootDispersion,
      usrNTPLastRcvdReferenceIdentifier,
      usrNTPLastRcvdReferenceTimestampHigh,
      usrNTPLastRcvdReferenceTimestampLow,
      usrNTPLastRcvdOriginateTimestampHigh,
      usrNTPLastRcvdOriginateTimestampLow,
      usrNTPLastRcvdReceiveTimestampHigh,
      usrNTPLastRcvdReceiveTimestampLow,
      usrNTPLastRcvdTransmitTimestampHigh,
      usrNTPLastRcvdTransmitTimestampLow
    }
    STATUS        current
    DESCRIPTION
     "All objects in this MIB."
    ::= { usrNTPGroups 1 }
-- Time Zone name  table definition      
    usrNTPTimeZoneTable OBJECT-TYPE
    SYNTAX SEQUENCE OF TimeZoneEntry 
    MAX-ACCESS  not-accessible  
    STATUS  current
    DESCRIPTION
        ""
    ::= { usrNTPObjects 43 }
    timeZoneEntry    OBJECT-TYPE
    SYNTAX  TimeZoneEntry
    MAX-ACCESS  not-accessible
    STATUS  current
    DESCRIPTION
        ""
    INDEX   { usrNTPIndex  }
    ::= { usrNTPTimeZoneTable 1 }
    TimeZoneEntry ::=
    SEQUENCE {
   	usrNTPIndex 
		Integer32,
    usrNTPNextTimeZone
        DisplayString
	}
    usrNTPIndex OBJECT-TYPE
    SYNTAX  Integer32
    MAX-ACCESS  not-accessible
    STATUS  current
    DESCRIPTION
        "The key field"
    ::= { timeZoneEntry 1 }
    usrNTPNextTimeZone    OBJECT-TYPE
    SYNTAX  DisplayString
    MAX-ACCESS  read-only
    STATUS  current
    DESCRIPTION 
        "Time zone list name"
    ::= { timeZoneEntry 2 }
    usrNTPTrapsV2 OBJECT-IDENTITY
    STATUS  current
    DESCRIPTION
        "Events for NTP"
    ::= { usrNTPTraps 0 }
    usrNTPServerFailure NOTIFICATION-TYPE
        OBJECTS  {
                  usrNTPPrimaryServer,
                  usrNTPSecondaryServer
                  }
        STATUS  current
        DESCRIPTION     "This trap is generated for NTP Server
                        connectivity failure."
        --#TYPE    "Alarm"
        --#SUMMARY "NTP Server %d or %d Failure"
        --#ARGUMENTS { 0 1 }
        --#SEVERITY MAJOR
        --#STATE    OPERATIONAL
        --#PROBABLECAUSE "networkError"
    ::= { usrNTPTrapsV2 1 }
END     -- End of USR-NTP-MIB DEFINITIONS
-- ************************************************************************
--
--    usr_slip.mib - The CommWorks SLIP MIB module
--
-- Author:         <sanil>
--
