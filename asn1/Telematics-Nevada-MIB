Telematics-Nevada-MIB DEFINITIONS ::= BEGIN
--
--  MIB for Nevada software release 4.x
--
--  Last Updated: March 02,2000
--

               IMPORTS
                    enterprises, Counter, Gauge, TimeTicks
                                  FROM RFC1155-SMI
                    DisplayString FROM RFC1213-MIB
                    OBJECT-TYPE   FROM RFC-1212
                    TRAP-TYPE     FROM RFC-1215;



telematics              OBJECT IDENTIFIER ::= {enterprises 230}
tmxNevada               OBJECT IDENTIFIER ::= {telematics 5}

nevadaSystem            OBJECT IDENTIFIER ::= {tmxNevada 1}
nevadaModels            OBJECT IDENTIFIER ::= {tmxNevada 2}
nevadaFrameRelay        OBJECT IDENTIFIER ::= {tmxNevada 5}
nevadaIti               OBJECT IDENTIFIER ::= {tmxNevada 6}
nevadaSync              OBJECT IDENTIFIER ::= {tmxNevada 7}
nevadaX25               OBJECT IDENTIFIER ::= {tmxNevada 10}
nevadaIsdn              OBJECT IDENTIFIER ::= {tmxNevada 11}
nevadaPpp               OBJECT IDENTIFIER ::= {tmxNevada 12}
nevadaElx               OBJECT IDENTIFIER ::= {tmxNevada 15}
nevadaIp                OBJECT IDENTIFIER ::= {tmxNevada 16}
nevadaTcp               OBJECT IDENTIFIER ::= {tmxNevada 17}
nevadaFtp               OBJECT IDENTIFIER ::= {tmxNevada 18}
nevadaTelnet            OBJECT IDENTIFIER ::= {tmxNevada 20}
nevadaRadius            OBJECT IDENTIFIER ::= {tmxNevada 40}
nevadaSnmp              OBJECT IDENTIFIER ::= {tmxNevada 45}
nevadaApacs             OBJECT IDENTIFIER ::= {tmxNevada 50}
nevadaR2                OBJECT IDENTIFIER ::= {tmxNevada 55}
nevadaRb                OBJECT IDENTIFIER ::= {tmxNevada 58}
nevadaTraps             OBJECT IDENTIFIER ::= {tmxNevada 64}
nevadaAdmin             OBJECT IDENTIFIER ::= {tmxNevada 65}
nevadaPos               OBJECT IDENTIFIER ::= {tmxNevada 66}
nevadaL2tp		OBJECT IDENTIFIER ::= {tmxNevada 70}


--
-- Nevada Types
--
NvPortName ::= 
    DisplayString (SIZE(0..10))
NvPoolName   ::= DisplayString (SIZE(0..10))
NvNetAddress ::= DisplayString (SIZE(0..16))
NvVisaType   ::= INTEGER {
                undef(1),    --  (+1)
                fxd1(2),     --
                fxd2(3),     --
                fxd3(4),     --
                fxd4(5),     --
                fxd5(6),     --
                fxd6(7),     --
                fxd7(8),     --
                fxd8(9),     --
                fxd9(10),    --
                fxd10(11),     --
                fxd11(12),     --
                fxd12(13),     --
                fxd13(14),     --
                fxd14(15),     --
                fxd15(16),     --
                fxd16(17),     --
                fxd17(18),     --
                fxd18(19),     --
                fxd19(20),     --
                fxd20(21),     --
                fxd21(22),     --
                fxd22(23),     --
                fxd23(24),     --
                fxd24(25),     --
                fxd25(26),     --
                fxd26(27),     --
                fxd27(28),     --
                fxd28(29),     --
                fxd29(30),     --
                fxd30(31),     --
                fxd31(32),     --
                fxd32(33),     --
                varfs(102)     --
		}
NvIsoType    ::= INTEGER {
                unused(1),     --  (+1)
                fxb1(2),     --
                fxb2(3),     --
                fxb3(4),     --
                fxb4(5),     --
                fxb5(6),     --
                fxb6(7),     --
                fxb7(8),     --
                fxb8(9),     --
                fxb9(10),     --
                fxb10(11),     --
                fxb11(12),     --
                fxb12(13),     --
                fxb13(14),     --
                fxb14(15),     --
                fxb15(16),     --
                fxb16(17),     --
                fxb17(18),     --
                fxb18(19),     --
                fxb19(20),     --
                fxb20(21),     --
                fxb21(22),     --
                fxb22(23),     --
                fxb23(24),     --
                fxb24(25),     --
                fxb25(26),     --
                fxb26(27),     --
                fxb27(28),     --
                fxb28(29),     --
                fxb29(30),     --
                fxb30(31),     --
                fxb31(32),     --
                fxb32(33),     --
                fxb33(34),     --
                fxb34(35),     --
                fxb35(36),     --
                fxb36(37),     --
                fxb37(38),     --
                fxb38(39),     --
                fxb39(40),     --
                fxb40(41),     --
                fxb41(42),     --
                fxb42(43),     --
                fxn1(102),     --
                fxn2(103),     --
                fxn3(104),     --
                fxn4(105),     --
                fxn5(106),     --
                fxn6(107),     --
                fxn7(108),     --
                fxn8(109),     --
                fxn9(110),     --
                fxn10(111),     --
                fxn11(112),     --
                fxn12(113),     --
                fxn13(114),     --
                fxn14(115),     --
                fxn15(116),     --
                fxn16(117),     --
                fxn17(118),     --
                fxn18(119),     --
                fxn19(120),     --
                fxn20(121),     --
                fxn21(122),     --
                fxn22(123),     --
                fxn23(124),     --
                fxn24(125),     --
                fxn25(126),     --
                fxn26(127),     --
                fxn27(128),     --
                fxn28(129),     --
                fxn29(130),     --
                fxn30(131),     --
                fxn31(132),     --
                fxn32(133),     --
                fxn33(134),     --
                fxn34(135),     --
                fxn35(136),     --
                fxn36(137),     --
                fxn37(138),     --
                fxn38(139),     --
                fxn39(140),     --
                fxn40(141),     --
                fxn41(142),     --
                fxn42(143),     --
                llbyte(202),    --
                lllbyte(204),     --
                llnibble(222),     --
                lllnibble(224)      --
		}

--
--      nodestat file
--
nvNodestat      OBJECT IDENTIFIER ::= {nevadaSystem 1}

nvNodestatTotalbufs OBJECT-TYPE
     SYNTAX   INTEGER
     ACCESS   read-only
     STATUS   mandatory
     DESCRIPTION
        "total number of buffers in system
         - these buffers are freed at startup time to be allocated
         as needed. Statistic is zeroed at startup time."
     ::= {nvNodestat 1 }

nvNodestatCurminbufs OBJECT-TYPE
     SYNTAX   INTEGER
     ACCESS   read-only
     STATUS   mandatory
     DESCRIPTION
        "minimum number of buffers available in last 15 minute cycle
        Statistic is zeroed at startup time."
     ::= {nvNodestat 2 }

nvNodestatCurmincpu OBJECT-TYPE
     SYNTAX   INTEGER
     ACCESS   read-only
     STATUS   mandatory
     DESCRIPTION
        "cpu availablity -minimum percentage of CPU available in last 15
        minute cycle. Statistic is zeroed at startup time."
     ::= {nvNodestat 3 }

nvNodestatCurtime OBJECT-TYPE
     SYNTAX   Gauge
     ACCESS   read-only
     STATUS   mandatory
     DESCRIPTION
        "current time
        number of minutes into current time
         - is set to 0 at start of current cycle
         - is incremented every minute
         - when incremented to 15 then cycle is over and curminbuf
         and curmincpu are calculated and curtime is set back to 0
        Statistic is zeroed at startup time."
     ::= {nvNodestat 4 }

nvNodestatFreebufs OBJECT-TYPE
     SYNTAX   INTEGER
     ACCESS   read-only
     STATUS   mandatory
     DESCRIPTION
        "number of available buffers at last check
         - check is done every 3 seconds
         Statistic is zeroed at startup time."
     ::= {nvNodestat 6 }

nvNodestatFreecpu OBJECT-TYPE
     SYNTAX   Gauge
     ACCESS   read-only
     STATUS   mandatory
     DESCRIPTION
        "percentage of CPU available at last check
         - check is done every 3 seconds
        Statistic is zeroed at startup time."
     ::= {nvNodestat 7 }

nvNodestatMaxcpu OBJECT-TYPE
     SYNTAX   INTEGER
     ACCESS   read-only
     STATUS   mandatory
     DESCRIPTION
        "maximum CPU availablity
         maximum count of idle CPU cycles per 16 milliseconds
         - percentages of CPU availability are calculated relative
         to this number (freecpu,curmincpu,mincpu)
        Statistic is zeroed at startup time."
     ::= {nvNodestat 8 }

nvNodestatMinbufs OBJECT-TYPE
     SYNTAX   INTEGER
     ACCESS   read-only
     STATUS   mandatory
     DESCRIPTION
        "minimum number of buffers
         minimum number of available buffers ever recorded
         Statistic is zeroed at startup time."
     ::= {nvNodestat 10 }

nvNodestatMincpu OBJECT-TYPE
     SYNTAX   INTEGER
     ACCESS   read-only
     STATUS   mandatory
     DESCRIPTION
        "cpu availablity
         minimum percentage of CPU available ever recorded
         Statistic is zeroed at startup time."
     ::= {nvNodestat 11 }

nvNodestatRxavgpps OBJECT-TYPE
     SYNTAX   INTEGER
     ACCESS   read-only
     STATUS   mandatory
     DESCRIPTION
        "average rx packets per second
         average packets per second received during last 15 minute cycle
         Statistic is zeroed at startup time."
     ::= {nvNodestat 12 }

nvNodestatRxcurpps OBJECT-TYPE
     SYNTAX   INTEGER
     ACCESS   read-only
     STATUS   mandatory
     DESCRIPTION
        "current rx packets per second
         packets per second received during last 3 second cycle
         Statistic is zeroed at startup time"
     ::= {nvNodestat 13 }

nvNodestatTxavgpps OBJECT-TYPE
     SYNTAX   INTEGER
     ACCESS   read-only
     STATUS   mandatory
     DESCRIPTION
        "average tx packets per second
         average packets per second transmitted during last 15 minute cycle
         Statistic is zeroed at startup time."
     ::= {nvNodestat 14 }

nvNodestatTxcurpps OBJECT-TYPE
     SYNTAX   INTEGER
     ACCESS   read-only
     STATUS   mandatory
     DESCRIPTION
        "current tx packets per second
         packets per second transmitted during last 3 second cycle
         Statistic is zeroed at startup time."
     ::= {nvNodestat 15 }

nvNodestatX25call OBJECT-TYPE
     SYNTAX   INTEGER
     ACCESS   read-only
     STATUS   mandatory
     DESCRIPTION
        "Actual number of lcns allocated."
     ::= {nvNodestat 16}

nvNodestatChgreqid OBJECT-TYPE
     SYNTAX   INTEGER
     ACCESS   read-only
     STATUS   mandatory
     DESCRIPTION
        "Change Request ID
         Confirmation management change request ID."
     ::= {nvNodestat 17}

nvNodestatCurclk OBJECT-TYPE
     SYNTAX   DisplayString (SIZE (0..10))
     ACCESS   read-only
     STATUS   mandatory
     DESCRIPTION
        "Indicates the current clock source."
     ::= {nvNodestat 18}

nvNodestatClkfails OBJECT-TYPE
     SYNTAX   INTEGER
     ACCESS   read-only
     STATUS   mandatory
     DESCRIPTION
        "Number of times clock failure has been detected."
     ::= {nvNodestat 19}

nvNodestatDtreset OBJECT-TYPE
     SYNTAX   DisplayString (SIZE (0..20))
     ACCESS   read-only
     STATUS   mandatory
     DESCRIPTION
        "date & time statistics last reset"
      ::= { nvNodestat 20 }

nvNodestatNumcalls OBJECT-TYPE		 --AF
      SYNTAX   INTEGER			 --AF
      ACCESS   read-only			 --AF
      STATUS   mandatory			 --AF
      DESCRIPTION			 --AF
         "Number of succesful modem calls received by ITI."
      ::= {nvNodestat 21}		 --AF
 

--
-- nodeconf
--

nvNodeconf OBJECT IDENTIFIER ::= { nevadaSystem 2}

nvNodeconfMaxRec OBJECT-TYPE
     SYNTAX   INTEGER
     ACCESS   read-only
     STATUS   mandatory
     DESCRIPTION
        "total number of records allowed in database file."
     ::= {nvNodeconf 1}

nvNodeconfNumRec OBJECT-TYPE
     SYNTAX   INTEGER
     ACCESS   read-only
     STATUS   mandatory
     DESCRIPTION
        "number of records in use."
     ::= {nvNodeconf 2}

nvNodeconfTable OBJECT-TYPE
      SYNTAX   SEQUENCE OF NvNodeconfEntry
      ACCESS   not-accessible
      STATUS   mandatory
      DESCRIPTION
               "nodeconf file."
      ::= { nvNodeconf 3 }

nvNodeconfEntry OBJECT-TYPE
      SYNTAX   NvNodeconfEntry
      ACCESS   not-accessible
      STATUS   mandatory
      DESCRIPTION
               "nodeconf record."
      INDEX { nvNodeconfIndex }
      ::= { nvNodeconfTable 1 }

NvNodeconfEntry ::=
      SEQUENCE {
      nvNodeconfIndex
            INTEGER,
      nvNodeconfPartnum
            DisplayString,
      nvNodeconfDbversion
            DisplayString,
      nvNodeconfSwdate
            DisplayString,
      nvNodeconfSwversion
            DisplayString,
      nvNodeconfCalarms
            INTEGER,
      nvNodeconfStartup
            INTEGER,
      nvNodeconfSwtype
            INTEGER,
      nvNodeconfX25call
            INTEGER,
      nvNodeconfAcctrec
            INTEGER,
      nvNodeconfAlarmrec
            INTEGER,
      nvNodeconfBusyout
            INTEGER,
      nvNodeconfRate1
            INTEGER,
      nvNodeconfRate2
            INTEGER,
      nvNodeconfRate3
            INTEGER,
      nvNodeconfRate4
            INTEGER,
      nvNodeconfNodeid
            INTEGER,
      nvNodeconfExstat
            INTEGER,
      nvNodeconfRsttimer
            INTEGER,
      nvNodeconfChgreqid
            INTEGER,
      nvNodeconfClksrc1
            DisplayString,
      nvNodeconfClksrc2
            DisplayString,
      nvNodeconfClksrc3
            DisplayString,
      nvNodeconfDsprfail
            INTEGER,
      nvNodeconfFrmrfail
            INTEGER,
      nvNodeconfQdlifail
            INTEGER
                }

nvNodeconfIndex OBJECT-TYPE
     SYNTAX   INTEGER
     ACCESS   read-only
     STATUS   mandatory
     DESCRIPTION
        "Index of nodeconf record"
      ::= { nvNodeconfEntry 1 }

nvNodeconfPartnum OBJECT-TYPE
     SYNTAX   DisplayString (SIZE (0..19))
     ACCESS   read-only
     STATUS   mandatory
     DESCRIPTION
"Part Number -partnum- This is the part number of the software
Format:  AAAAAA-BBB-C-DDEEFF AAAAAA = Concatenated product code ie.
 a 4 link,8 channel switching PAD which has the code 2604-8 becomes
 260408  BBB = Customer/feature code  C = Medium  DD = Major version number. A new set of
 documentation is generated for each  major version  EE = Database version number
 FF = Software version number Parameter is set during factory configuration."
     ::= { nvNodeconfEntry 2 }

nvNodeconfDbversion OBJECT-TYPE
     SYNTAX   DisplayString (SIZE (0..4))
     ACCESS   read-only
     STATUS   mandatory
     DESCRIPTION
"Database Version (dbversion)
 Major and minor database release numbers Eg 0300
Similar usage as for software revision number
Parameter is set during factory configuration."
     ::= { nvNodeconfEntry 3 }

nvNodeconfSwdate OBJECT-TYPE
     SYNTAX   DisplayString (SIZE (0..7))
     ACCESS   read-only
     STATUS   mandatory
     DESCRIPTION
"Software Creation Date (swdate)
Parameter is set during factory configuration."
     ::= { nvNodeconfEntry 7 }

nvNodeconfSwversion OBJECT-TYPE
     SYNTAX   DisplayString (SIZE (0..4))
     ACCESS   read-only
     STATUS   mandatory
     DESCRIPTION
"Software Version (swversion)
Major and minor software release numbers
 Eg. 0601
Parameter is set during factory configuration."
     ::= { nvNodeconfEntry 8 }

nvNodeconfCalarms OBJECT-TYPE
     SYNTAX   INTEGER (0..500)
     ACCESS   read-write
     STATUS   mandatory
     DESCRIPTION
"Max Custom Alarm Records (calarms)
This field indicates the total num of custom alarm entries
per box.
 DO NOT USE HUB-RESERVE3 OR TAKE ANY SPACE AWAY FROM IT TO USE
 FOR A NEW FIELD. IT IS THE SECRET HIDING PLACE WHERE THE HARDWARE
 CONFIGURATION IS STORED FOR USE IN DETECTING HARDWARE CHANGES WHEN
 REBOOTING.
Default value is 0."
     ::= { nvNodeconfEntry 10 }

nvNodeconfStartup OBJECT-TYPE
     SYNTAX   INTEGER
     ACCESS   read-write
     STATUS   mandatory
     DESCRIPTION
"SD Script to automatically start after aprox. 10 seconds system boot"
     ::= { nvNodeconfEntry 11 }


nvNodeconfSwtype OBJECT-TYPE
     SYNTAX   INTEGER {
                sview(1),     -- smartnet (+1)
                inf(2),     -- acp
                inf2(3)      -- acp with sview billing records
                }
     ACCESS   read-write
     STATUS   mandatory
     DESCRIPTION
"INF or SmartView Type (swtype)
sview for old std billing
Default value is sview (0+1)."
     ::= { nvNodeconfEntry 12 }

nvNodeconfX25call OBJECT-TYPE
     SYNTAX   INTEGER (1..25000)
     ACCESS   read-write
     STATUS   mandatory
     DESCRIPTION
"X.25 Call (nvX25call)
This field indicates the total num of lcn per box
Default value is 257."
     ::= { nvNodeconfEntry 14 }

nvNodeconfAcctrec OBJECT-TYPE
     SYNTAX   INTEGER (0..65535)
     ACCESS   read-write
     STATUS   mandatory
     DESCRIPTION
"Max Accounting Records (acctrec)
This indicates the maximum number of accounting records that
will be held in memory. When this number is reached,
additional records will be discarded.
Default value is 100."
     ::= { nvNodeconfEntry 16 }

nvNodeconfAlarmrec OBJECT-TYPE
     SYNTAX   INTEGER (0..65535)
     ACCESS   read-write
     STATUS   mandatory
     DESCRIPTION
"Max Alarm Records (alarmrec)
This indicates the maximum number of alarm records buffered
Default value is 50."
     ::= { nvNodeconfEntry 17 }

nvNodeconfBusyout OBJECT-TYPE
     SYNTAX   INTEGER (0..65535)
     ACCESS   read-write
     STATUS   mandatory
     DESCRIPTION
"used to busy out ITI ports when X25 links
go down "
     ::= { nvNodeconfEntry 21 }

nvNodeconfRate1 OBJECT-TYPE
     SYNTAX   INTEGER (0..65535)
     ACCESS   read-write
     STATUS   mandatory
     DESCRIPTION
"Rate For Time Zone 1 (rate1)
"
     ::= { nvNodeconfEntry 22 }

nvNodeconfRate2 OBJECT-TYPE
     SYNTAX   INTEGER (0..65535)
     ACCESS   read-write
     STATUS   mandatory
     DESCRIPTION
"Rate For Time Zone 2 (rate2)
"
     ::= { nvNodeconfEntry 23 }

nvNodeconfRate3 OBJECT-TYPE
     SYNTAX   INTEGER (0..65535)
     ACCESS   read-write
     STATUS   mandatory
     DESCRIPTION
"Rate For Time Zone 3 (rate3)
"
     ::= { nvNodeconfEntry 24 }

nvNodeconfRate4 OBJECT-TYPE
     SYNTAX   INTEGER (0..65535)
     ACCESS   read-write
     STATUS   mandatory
     DESCRIPTION
"Rate For Time Zone 4 (rate4)
"
     ::= { nvNodeconfEntry 25 }

nvNodeconfNodeid OBJECT-TYPE
     SYNTAX   INTEGER (1..65535)
     ACCESS   read-write
     STATUS   mandatory
     DESCRIPTION
"Node Identifier (nodeid)
This field is used by the Network Bus component to identify
this node within a private network,and must be unique within
that domain.
Default value is 1000."
     ::= { nvNodeconfEntry 27 }

nvNodeconfExstat OBJECT-TYPE
     SYNTAX   INTEGER {
                disable(1),     -- no enhx25stat (+1)
                link(2),     -- level 2 only
                x25(3)      -- level 2 and 3
                }
     ACCESS   read-write
     STATUS   mandatory
     DESCRIPTION
"enhanced x25 stat (exstat)
"
     ::= { nvNodeconfEntry 28 }

nvNodeconfRsttimer OBJECT-TYPE
     SYNTAX   INTEGER (0..255)
     ACCESS   read-write
     STATUS   mandatory
     DESCRIPTION
"Restart timer for OMS
Default value is 0."
     ::= { nvNodeconfEntry 29 }

nvNodeconfChgreqid OBJECT-TYPE
     SYNTAX   INTEGER
     ACCESS   read-write
     STATUS   mandatory
     DESCRIPTION
"Change Request Id
"
     ::= { nvNodeconfEntry 30 }

nvNodeconfClksrc1 OBJECT-TYPE
     SYNTAX   DisplayString (SIZE (0..10))
     ACCESS   read-write
     STATUS   mandatory
     DESCRIPTION
"Primary clock source to synchronize TDM connects.
"
     ::= { nvNodeconfEntry 31 }

nvNodeconfClksrc2 OBJECT-TYPE
     SYNTAX   DisplayString (SIZE (0..10))
     ACCESS   read-write
     STATUS   mandatory
     DESCRIPTION
"Primary clock source to synchronize TDM connects.
"
     ::= { nvNodeconfEntry 32 }

nvNodeconfClksrc3 OBJECT-TYPE
     SYNTAX   DisplayString (SIZE (0..10))
     ACCESS   read-write
     STATUS   mandatory
     DESCRIPTION
"Primary clock source to synchronize TDM connects.
"
     ::= { nvNodeconfEntry 33 }

     
nvNodeconfDsprfail OBJECT-TYPE
     SYNTAX   INTEGER (0..255)
     ACCESS   read-write
     STATUS   mandatory
     DESCRIPTION
"dspr failure threshold
"
     ::= { nvNodeconfEntry 34 }

nvNodeconfFrmrfail OBJECT-TYPE
     SYNTAX   INTEGER (0..255)
     ACCESS   read-write
     STATUS   mandatory
     DESCRIPTION
"frmr failure threshold
"
     ::= { nvNodeconfEntry 35 }

nvNodeconfQdlifail OBJECT-TYPE
     SYNTAX   INTEGER (0..255)
     ACCESS   read-write
     STATUS   mandatory
     DESCRIPTION
"Qdli failure threshold
"
     ::= { nvNodeconfEntry 36 }

--
--      acctstat file
--
nvAcctstat OBJECT IDENTIFIER ::= {nevadaSystem 3}

nvAcctstatMaxRec OBJECT-TYPE
     SYNTAX   INTEGER
     ACCESS   read-only
     STATUS   mandatory
     DESCRIPTION
        "total number of records in file."
     ::= {nvAcctstat 1}

nvAcctstatNumRec OBJECT-TYPE
     SYNTAX   INTEGER
     ACCESS   read-only
     STATUS   mandatory
     DESCRIPTION
        "number of records in use."
     ::= {nvAcctstat 2}

nvAcctstatTable OBJECT-TYPE
      SYNTAX   SEQUENCE OF NvAcctstatEntry
      ACCESS   not-accessible
      STATUS   mandatory
      DESCRIPTION
               "acctstat file."
      ::= {nvAcctstat 3}

nvAcctstatEntry OBJECT-TYPE
      SYNTAX   NvAcctstatEntry
      ACCESS   not-accessible
      STATUS   mandatory
      DESCRIPTION
               "acctstat record, indexed by record number"
      INDEX {nvAcctstatRecord}
      ::= {nvAcctstatTable 1 }

NvAcctstatEntry ::=
      SEQUENCE {
      nvAcctstatComponent
            DisplayString,
      nvAcctstatCallid
            INTEGER,
      nvAcctstatRecord
            INTEGER,
      nvAcctstatCalled
            DisplayString,
      nvAcctstatCalling
            DisplayString,
      nvAcctstatRecorg
            INTEGER,
      nvAcctstatSegsize
            INTEGER,
      nvAcctstatInfofunc
            INTEGER,
      nvAcctstatDay
            INTEGER,
      nvAcctstatMinute
            INTEGER,
      nvAcctstatSecond
            INTEGER,
      nvAcctstatTxpaks
            Counter,
      nvAcctstat64ktxpaks
            Counter,
      nvAcctstatRxpaks
            Counter,
      nvAcctstat64krxpaks
            Counter,
      nvAcctstatTxchars
            Counter,
      nvAcctstat64ktxchars
            Counter,
      nvAcctstatRxchars
            Counter,
      nvAcctstat64krxchars
            Counter,
      nvAcctstatTxsegs
            Counter,
      nvAcctstat64ktxsegs
            Counter,
      nvAcctstatRxsegs
            Counter,
      nvAcctstat64krxsegs
            Counter,
      nvAcctstatAbstime
            INTEGER,
      nvAcctstatDtreset
	    DisplayString
               }

nvAcctstatComponent OBJECT-TYPE
     SYNTAX   DisplayString (SIZE (0..10))
     ACCESS   read-only
     STATUS   mandatory
     DESCRIPTION
        " name of component
         This is the name of component accumulating the statistics."
     ::= {nvAcctstatEntry 1 }

nvAcctstatRecord OBJECT-TYPE
     SYNTAX   INTEGER
     ACCESS   read-only
     STATUS   mandatory
     DESCRIPTION
        "record ID
         This is the internal number of the accounting record."
     ::= {nvAcctstatEntry 2}

nvAcctstatCalled OBJECT-TYPE
     SYNTAX   DisplayString (SIZE (0..8))
     ACCESS   read-only
     STATUS   mandatory
     DESCRIPTION
        "Called address (from bcd)"
     ::= {nvAcctstatEntry 3 }

nvAcctstatCalling OBJECT-TYPE
     SYNTAX   DisplayString (SIZE (0..8))
     ACCESS   read-only
     STATUS   mandatory
     DESCRIPTION
        "Calling address (from bcd)."
     ::= {nvAcctstatEntry 4 }

nvAcctstatRecorg OBJECT-TYPE
     SYNTAX   INTEGER {
                        iti(1),         -- (+1)
                        x25(2)
                        }
     ACCESS   read-only
     STATUS   mandatory
     DESCRIPTION
        " call origin: 1=iti/lserv 2=x25 ."
     ::= {nvAcctstatEntry 5 }

nvAcctstatSegsize OBJECT-TYPE
     SYNTAX   INTEGER (1..32767)
     ACCESS   read-only
     STATUS   mandatory
     DESCRIPTION
        "segment size
         This is the segment size of this port that generates accounting.
         Statistic is zeroed at startup time."
     ::= {nvAcctstatEntry 6 }

nvAcctstatDay OBJECT-TYPE
     SYNTAX   INTEGER
     ACCESS   read-only
     STATUS   mandatory
     DESCRIPTION
        " date of call establishment (internal)
         Statistic is zeroed at startup time."
     ::= {nvAcctstatEntry 7 }

nvAcctstatMinute OBJECT-TYPE
     SYNTAX   INTEGER
     ACCESS   read-only
     STATUS   mandatory
     DESCRIPTION
        " time of call establishment
         Statistic is zeroed at startup time."
     ::= {nvAcctstatEntry 8 }

nvAcctstatSecond OBJECT-TYPE
     SYNTAX   INTEGER
     ACCESS   read-only
     STATUS   mandatory
     DESCRIPTION
        "time of call establishment
         Statistic is zeroed at startup time."
     ::= {nvAcctstatEntry 9 }

nvAcctstatTxpaks OBJECT-TYPE
     SYNTAX   Counter
     ACCESS   read-only
     STATUS   mandatory
     DESCRIPTION
        "number transmitted packets
         Statistic is zeroed at startup time."
     ::= {nvAcctstatEntry 10 }

nvAcctstat64ktxpaks OBJECT-TYPE
     SYNTAX   Counter
     ACCESS   read-only
     STATUS   mandatory
     DESCRIPTION
        "1000 transmitted packets
         Statistic is zeroed at startup time."
     ::= {nvAcctstatEntry 11 }

nvAcctstatRxpaks OBJECT-TYPE
     SYNTAX   Counter
     ACCESS   read-only
     STATUS   mandatory
     DESCRIPTION
        "number received packets
         Statistic is zeroed at startup time."
     ::= {nvAcctstatEntry 12 }

nvAcctstat64krxpaks OBJECT-TYPE
     SYNTAX   Counter
     ACCESS   read-only
     STATUS   mandatory
     DESCRIPTION
        "1000 received packets
         Statistic is zeroed at startup time."
     ::= {nvAcctstatEntry 13 }

nvAcctstatTxchars OBJECT-TYPE
     SYNTAX   Counter
     ACCESS   read-only
     STATUS   mandatory
     DESCRIPTION
        "number transmitted characters
         Statistic is zeroed at startup time."
     ::= {nvAcctstatEntry 14 }

nvAcctstat64ktxchars OBJECT-TYPE
     SYNTAX   Counter
     ACCESS   read-only
     STATUS   mandatory
     DESCRIPTION
        "1000 transmitted characters
         Statistic is zeroed at startup time."
     ::= {nvAcctstatEntry 15 }

nvAcctstatRxchars OBJECT-TYPE
     SYNTAX   Counter
     ACCESS   read-only
     STATUS   mandatory
     DESCRIPTION
        "number received characters
         Statistic is zeroed at startup time."
     ::= {nvAcctstatEntry 16 }

nvAcctstat64krxchars OBJECT-TYPE
     SYNTAX   Counter
     ACCESS   read-only
     STATUS   mandatory
     DESCRIPTION
        "1000 received characters
         Statistic is zeroed at startup time."
     ::= {nvAcctstatEntry 17 }

nvAcctstatTxsegs OBJECT-TYPE
     SYNTAX   Counter
     ACCESS   read-only
     STATUS   mandatory
     DESCRIPTION
        "number transmitted segments
         Statistic is zeroed at startup time."
     ::= {nvAcctstatEntry 18 }

nvAcctstat64ktxsegs OBJECT-TYPE
     SYNTAX   Counter
     ACCESS   read-only
     STATUS   mandatory
     DESCRIPTION
        "1000 transmitted segments
         Statistic is zeroed at startup time."
     ::= {nvAcctstatEntry 19 }

nvAcctstatRxsegs OBJECT-TYPE
     SYNTAX   Counter
     ACCESS   read-only
     STATUS   mandatory
     DESCRIPTION
        " number received segments
         Statistic is zeroed at startup time."
     ::= {nvAcctstatEntry 20 }

nvAcctstat64krxsegs OBJECT-TYPE
     SYNTAX   Counter
     ACCESS   read-only
     STATUS   mandatory
     DESCRIPTION
        " 1000 received segments
         Statistic is zeroed at startup time."
     ::= {nvAcctstatEntry 21 }

nvAcctstatAbstime OBJECT-TYPE
     SYNTAX   INTEGER
     ACCESS   read-only
     STATUS   mandatory
     DESCRIPTION
        "starting absolute time
         Statistic is zeroed at startup time."
     ::= {nvAcctstatEntry 22 }

nvAcctstatDtreset OBJECT-TYPE
     SYNTAX   DisplayString (SIZE (0..20))
     ACCESS   read-only
     STATUS   mandatory
     DESCRIPTION
        "date & time statistics last reset"
      ::= { nvAcctstatEntry 23 }

nvAcctstatCallid OBJECT-TYPE
     SYNTAX   INTEGER
     ACCESS   read-only
     STATUS   mandatory
     DESCRIPTION
        "Ptr to internal structure that starts accounting"
     ::= {nvAcctstatEntry 24 }
     
nvAcctstatInfofunc OBJECT-TYPE
     SYNTAX   INTEGER
     ACCESS   read-only
     STATUS   mandatory
     DESCRIPTION
     "Information function ptr provided by accounting entity"
     ::= {nvAcctstatEntry 25 }
--
--  FILE ACCTOPER
--
nvAcctoper OBJECT IDENTIFIER ::= { nevadaSystem 4}

nvAcctoperMaxRec OBJECT-TYPE
     SYNTAX   INTEGER
     ACCESS   read-only
     STATUS   mandatory
     DESCRIPTION
        "total number of records allowed in database file."
     ::= {nvAcctoper 1}

nvAcctoperNumRec OBJECT-TYPE
     SYNTAX   INTEGER
     ACCESS   read-only
     STATUS   mandatory
     DESCRIPTION
        "number of records in use."
     ::= {nvAcctoper 2}

nvAcctoperTable OBJECT-TYPE
      SYNTAX   SEQUENCE OF NvAcctoperEntry
      ACCESS   not-accessible
      STATUS   mandatory
      DESCRIPTION
               "acctoper file."
      ::= { nvAcctoper 3 }

nvAcctoperEntry OBJECT-TYPE
      SYNTAX   NvAcctoperEntry
      ACCESS   not-accessible
      STATUS   mandatory
      DESCRIPTION
               "acctoper record."
      INDEX { nvAcctoperIndex }
      ::= { nvAcctoperTable 1 }

NvAcctoperEntry ::=
      SEQUENCE {
      nvAcctoperIndex
            INTEGER,
      nvAcctoperComponent
            DisplayString,
      nvAcctoperEnable
            INTEGER,
      nvAcctoperSegsize
            INTEGER
               }

nvAcctoperIndex OBJECT-TYPE
     SYNTAX   INTEGER
     ACCESS   read-only
     STATUS   mandatory
     DESCRIPTION
        "Index of acctoper record"
     ::= { nvAcctoperEntry 1 }

nvAcctoperComponent OBJECT-TYPE
     SYNTAX   DisplayString (SIZE (0..10))
     ACCESS   read-only
     STATUS   mandatory
     DESCRIPTION
"service component
This is the name of the component that uses the
accounting service. An example of this is NET1,ITI,etc.
Parameter is set during factory configuration."
     ::= { nvAcctoperEntry 2 }     

nvAcctoperEnable OBJECT-TYPE SYNTAX   INTEGER {
                false(1),     -- disable (+1)
                true(2)       -- enable  (+1)
                }
     ACCESS   read-write
     STATUS   mandatory
     DESCRIPTION
"enable/disable
This field is used to enable the accounting function.
Default value is true (1+1)."
     ::= { nvAcctoperEntry 3 }

nvAcctoperSegsize OBJECT-TYPE
     SYNTAX   INTEGER (1..32767)
     ACCESS   read-write
     STATUS   mandatory
     DESCRIPTION
"segment size
This field defines the size of a segment. A
segment is usually a portion of a packet (ie. 64 bytes)
as is more representative in actual
accounting of resource utilization. The
possible values range from one to the largest
possible packet size.
Default value is 64."
     ::= { nvAcctoperEntry 4 }

--
--      modemstat file
--
nvModemstat OBJECT IDENTIFIER ::= {nevadaSystem 5}

nvModemstatMaxRec OBJECT-TYPE
     SYNTAX   INTEGER
     ACCESS   read-only
     STATUS   mandatory
     DESCRIPTION
        "total number of records allowed in database file."
     ::= {nvModemstat 1}

nvModemstatNumRec OBJECT-TYPE
     SYNTAX   INTEGER
     ACCESS   read-only
     STATUS   mandatory
     DESCRIPTION
        "number of records in use."
     ::= {nvModemstat 2}

nvModemstatTable OBJECT-TYPE
      SYNTAX   SEQUENCE OF NvModemstatEntry
      ACCESS   not-accessible
      STATUS   mandatory
      DESCRIPTION
               "modemstat file."
      ::= {nvModemstat 3}

nvModemstatEntry OBJECT-TYPE
      SYNTAX   NvModemstatEntry
      ACCESS   not-accessible
      STATUS   mandatory
      DESCRIPTION
               "modemstat record."
      INDEX {nvModemstatIndex}
      ::= {nvModemstatTable 1 }

NvModemstatEntry ::= SEQUENCE {
      nvModemstatIndex
            INTEGER,
      nvModemstatName
            DisplayString,
      nvModemstatState
            INTEGER,
      nvModemstatRate
            INTEGER,
      nvModemstatType
            INTEGER,
      nvModemstatEctype
            INTEGER,
      nvModemstatDctype
            INTEGER,
      nvModemstatMode
            INTEGER,
      nvModemstatRxparity
            INTEGER,
      nvModemstatTxparity
            INTEGER,
      nvModemstatAccms
            DisplayString,
      nvModemstatMse
            INTEGER,
      nvModemstatRcvlvl
            INTEGER,
      nvModemstatRetrain
            INTEGER,
      nvModemstatRenego
            INTEGER,
      nvModemstatSelftest
            INTEGER,
      nvModemstatFirmver
            DisplayString,
      nvModemstatModel
            DisplayString,
      nvModemstatRxpclear
            INTEGER,
      nvModemstatDsp
            DisplayString,
      nvModemstatDtreset
            DisplayString
               }

nvModemstatIndex OBJECT-TYPE
     SYNTAX   INTEGER
     ACCESS   read-only
     STATUS   mandatory
     DESCRIPTION
        "Index of Modemstat record"
     ::= {nvModemstatEntry 1}

nvModemstatName OBJECT-TYPE
     SYNTAX   DisplayString (SIZE (0..11))
     ACCESS   read-only
     STATUS   mandatory
     DESCRIPTION
        "digital modem status name."
     ::= {nvModemstatEntry 2 }

nvModemstatState OBJECT-TYPE
     SYNTAX   INTEGER {
                idle(1),                -- (+1)
                hshake(2),
                ecdc(3),
                connected(4),
                retraining(5),
                renegotiating(6),
                clearDown(7)
                }
     ACCESS   read-only
     STATUS   mandatory
     DESCRIPTION
        "Current state"
     ::= {nvModemstatEntry 3 }

nvModemstatRate OBJECT-TYPE
     SYNTAX   INTEGER {
                idle(1),                -- (+1)
                t1200R75(2),
                t75R1200(3),
                v300(4),
                v600(5),
                v1200(6),
                v2400(7),
                v4800(8),
                v7200(9),
                v9600NT(10),
                v9600(11),
                v12000(12),
                v14400(13),
                v16800(14),
                v19200(15),
		v21600(16),
                v24000(17),
		v26400(18),
                v28800(19),
		v31200(20),
		v33600(21),
		v32000(22),
		v34000(23),
		v36000(24),
		v38000(25),
		v40000(26),
		v42000(27),
		v44000(28),
		v46000(29),
		v48000(30),
		v50000(31),
		v52000(32),
		v54000(33),
		v56000(34),
		v58000(35),
		v60000(36),
		vv28000(37),
		v29333(38),
		v30667(39),
		vv32000(40),
		v33333(41),
		v34667(42),
		vv36000(43),
		v37333(44),
		v38667(45),
		vv40000(46),
		v41333(47),
		v42667(48),
		vv44000(49),
		v45333(50),
		v46667(51),
		vv48000(52),
		v49333(53),
		v50667(54),
		vv52000(55),
		v53333(56),
		v54667(57),
		vv56000(58),
		v57333(59),
		v58667(60),
		vv60000(61)
                }
     ACCESS   read-only
     STATUS   mandatory
     DESCRIPTION
        "modem rate in bps."
     ::= {nvModemstatEntry 4 }

nvModemstatType OBJECT-TYPE
     SYNTAX   INTEGER {
                idle(1),        -- (+1)
                v34(2),
                v32bis(3),
                v32(4),
                v22bis(5),
                v22(6),
                v21(7),
                bell212(9),
                unknown(10),
                bell103(11),
                v23(12),
                v27(13),
                v29(14),
                v33(15),
                v17(16),
		v34bis(17),
		vpcm(18),
                v110(21)
                }
     ACCESS   read-only
     STATUS   mandatory
     DESCRIPTION
        "modem modulation scheme."
     ::= {nvModemstatEntry 5 }

nvModemstatEctype OBJECT-TYPE
     SYNTAX   INTEGER {
                idle(1),                -- (+1)
                v42ErrorCorrection(2),
                mnpErrorCorrection(3)
                }
     ACCESS   read-only
     STATUS   mandatory
     DESCRIPTION
        "modem error correction status"
     ::= {nvModemstatEntry 6 }

nvModemstatDctype OBJECT-TYPE
     SYNTAX   INTEGER {
                idle(1),        -- (+1)
                on(2),
                off(3)
                }
     ACCESS   read-only
     STATUS   mandatory
     DESCRIPTION
        " modem data compression status."
     ::= {nvModemstatEntry 7 }

nvModemstatMode OBJECT-TYPE
     SYNTAX   INTEGER {
                predetection(2),        -- (+1)
                sync(3),
                async(4)
                }
     ACCESS   read-only
     STATUS   mandatory
     DESCRIPTION
        "synchronous or asynchronous."
     ::= {nvModemstatEntry 8 }

nvModemstatRxparity OBJECT-TYPE
     SYNTAX   INTEGER {
                even(2),        -- (+1)
                odd(3),
                mark(4),
                space(5),
                none(6),
                clear(7)
                }
     ACCESS   read-only
     STATUS   mandatory
     DESCRIPTION
        "receive parity setting."
     ::= {nvModemstatEntry 9 }

nvModemstatTxparity OBJECT-TYPE
     SYNTAX   INTEGER {
                even(2),        -- (+1)
                odd(3),
                mark(4),
                space(5),
                none(6),
                clear(7)
                }
     ACCESS   read-only
     STATUS   mandatory
     DESCRIPTION
        "transmit parity setting."
     ::= {nvModemstatEntry 10 }

nvModemstatAccms OBJECT-TYPE
     SYNTAX   DisplayString (SIZE(0..17))
     ACCESS   read-only
     STATUS   mandatory
     DESCRIPTION
        "for async to sync PPP, shows asy char
         control maps."
     ::= {nvModemstatEntry 11 }

nvModemstatMse OBJECT-TYPE
     SYNTAX   INTEGER (0..65535)
     ACCESS   read-only
     STATUS   mandatory
     DESCRIPTION
        "modem noise level (mean squared err)."
     ::= {nvModemstatEntry 12 }

nvModemstatRcvlvl OBJECT-TYPE
     SYNTAX   INTEGER (0..255)
     ACCESS   read-only
     STATUS   mandatory
     DESCRIPTION
        "Modem receive level."
     ::= {nvModemstatEntry 13 }

nvModemstatRetrain OBJECT-TYPE
     SYNTAX   INTEGER (0..65535)
     ACCESS   read-only
     STATUS   mandatory
     DESCRIPTION
        "Number retrains this call."
     ::= {nvModemstatEntry 14 }

nvModemstatRenego OBJECT-TYPE
     SYNTAX   INTEGER (0..65535)
     ACCESS   read-only
     STATUS   mandatory
     DESCRIPTION
        "Number renegotiations this call."
     ::= {nvModemstatEntry 15 }

nvModemstatSelftest OBJECT-TYPE
     SYNTAX   INTEGER {
                passed(2),
                dspFailed(3),
                sramFailed(4),
                sramAndDspFailed(5)
                }
     ACCESS   read-only
     STATUS   mandatory
     DESCRIPTION
        "soft init selftest result."
     ::= {nvModemstatEntry 16 }

nvModemstatFirmver OBJECT-TYPE
     SYNTAX   DisplayString (SIZE(0..10))
     ACCESS   read-only
     STATUS   mandatory
     DESCRIPTION
        "Firmware version number"
     ::= {nvModemstatEntry 17 }

nvModemstatModel OBJECT-TYPE
     SYNTAX   DisplayString (SIZE(0..10))
     ACCESS   read-only
     STATUS   mandatory
     DESCRIPTION
        "DSP microcode product code."
     ::= {nvModemstatEntry 18 }

nvModemstatRxpclear OBJECT-TYPE
     SYNTAX   INTEGER {
		yes(2),
		no(3)
		}
     ACCESS   read-only
     STATUS   mandatory
     DESCRIPTION
"Modem clear rx parity (rxpclear)
 bit."
     ::= { nvModemstatEntry 19 }

nvModemstatDsp OBJECT-TYPE
     SYNTAX   DisplayString (SIZE(0..11))
     ACCESS   read-only
     STATUS   mandatory
     DESCRIPTION
        "the name of the DSP allocated."
     ::= {nvModemstatEntry 20 }

nvModemstatDtreset OBJECT-TYPE
     SYNTAX   DisplayString (SIZE (0..20))
     ACCESS   read-only
     STATUS   mandatory
     DESCRIPTION
        "date & time statistics last reset"
      ::= { nvModemstatEntry 21 }

--
--      modemconf
--
nvModemconf OBJECT IDENTIFIER ::= {nevadaSystem 6}

nvModemconfMaxRec OBJECT-TYPE
     SYNTAX   INTEGER
     ACCESS   read-only
     STATUS   mandatory
     DESCRIPTION
        "total number of records allowed in database file."
     ::= {nvModemconf 1}

nvModemconfNumRec OBJECT-TYPE
     SYNTAX   INTEGER
     ACCESS   read-only
     STATUS   mandatory
     DESCRIPTION
        "number of records in use."
     ::= {nvModemconf 2}

nvModemconfTable OBJECT-TYPE
      SYNTAX   SEQUENCE OF NvModemconfEntry
      ACCESS   not-accessible
      STATUS   mandatory
      DESCRIPTION
               "modemconf file."
      ::= { nvModemconf 3 }

nvModemconfEntry OBJECT-TYPE
      SYNTAX   NvModemconfEntry
      ACCESS   not-accessible
      STATUS   mandatory
      DESCRIPTION
               "modemconf record."
      INDEX { nvModemconfIndex }
      ::= { nvModemconfTable 1 }

NvModemconfEntry ::=
      SEQUENCE {
      nvModemconfIndex
            INTEGER,
      nvModemconfName
            DisplayString,
      nvModemconfProfilename
            DisplayString,
      nvModemconfEnable
            INTEGER,
      nvModemconfStatus
            INTEGER
                }

nvModemconfIndex OBJECT-TYPE
     SYNTAX   INTEGER
     ACCESS   read-only
     STATUS   mandatory
     DESCRIPTION
        "Index of modemconf record"
      ::= { nvModemconfEntry 1 }

nvModemconfName OBJECT-TYPE
     SYNTAX   DisplayString (SIZE (0..11))
     ACCESS   read-only
     STATUS   mandatory
     DESCRIPTION
"Digital modem resource config name (name)
Parameter is set during factory configuration."
     ::= { nvModemconfEntry 2 }

nvModemconfProfilename OBJECT-TYPE
     SYNTAX   DisplayString (SIZE (0..11))
     ACCESS   read-write
     STATUS   mandatory
     DESCRIPTION
"Digital modemprof name that it is associated with"
     ::= { nvModemconfEntry 4 }

nvModemconfEnable OBJECT-TYPE
     SYNTAX   INTEGER {
                yes(2),         -- (+1)
                no(3)
                }
     ACCESS   read-write
     STATUS   mandatory
     DESCRIPTION "Enabled or not."
     ::= { nvModemconfEntry 5 }


nvModemconfStatus OBJECT-TYPE
     SYNTAX   INTEGER {
                valid(1),
                invalid(2)
                }
     ACCESS   read-write
     STATUS   mandatory
     DESCRIPTION
"Operation status. Add the record to the table (valid) or delete
the record from the table (invalid)."
     ::= { nvModemconfEntry 20 }


-- This file is used to define names and passwords of individuals
-- authorized to use the system management facilities.
-- There is one record for each authorized user.
--  add-action symuser-encode
--  mod-action symuser-encode

nvSymuser OBJECT IDENTIFIER ::= { nevadaSystem 7 }

nvSymuserMaxRec OBJECT-TYPE
     SYNTAX   INTEGER
     ACCESS   read-only
     STATUS   mandatory
     DESCRIPTION
        "total number of records allowed in database file."
     ::= {nvSymuser 1}

nvSymuserNumRec OBJECT-TYPE
     SYNTAX   INTEGER
     ACCESS   read-only
     STATUS   mandatory
     DESCRIPTION
        "number of records in use."
     ::= {nvSymuser 2}

nvSymuserTable OBJECT-TYPE
      SYNTAX   SEQUENCE OF NvSymuserEntry
      ACCESS   not-accessible
      STATUS   mandatory
      DESCRIPTION
               "symuser file."
      ::= { nvSymuser 3 }

nvSymuserEntry OBJECT-TYPE
      SYNTAX   NvSymuserEntry
      ACCESS   not-accessible
      STATUS   mandatory
      DESCRIPTION
               "symuser record."
      INDEX { nvSymuserIndex }
      ::= { nvSymuserTable 1 }

NvSymuserEntry ::=
      SEQUENCE {
      nvSymuserIndex
            INTEGER,
      nvSymuserUsername
            DisplayString,
      nvSymuserPassword
            DisplayString,
      nvSymuserStatus
            INTEGER
                }

nvSymuserIndex OBJECT-TYPE
     SYNTAX   INTEGER
     ACCESS   read-only
     STATUS   mandatory
     DESCRIPTION
        "Index of symuser record"
      ::= { nvSymuserEntry 1 }

nvSymuserUsername OBJECT-TYPE
     SYNTAX   DisplayString (SIZE (0..16))
     ACCESS   read-write
     STATUS   mandatory
     DESCRIPTION
"User Name (username)
Name of user allowed to use system management functions.
The System Manager Interface attempts to match
the call user data
field of an incoming call
against the entries in this file.
If no match is found,
the call is cleared.
"
     ::= { nvSymuserEntry 2 }

nvSymuserPassword OBJECT-TYPE
     SYNTAX   DisplayString (SIZE (0..16))
     ACCESS   read-write
     STATUS   mandatory
     DESCRIPTION
"User Password (password)
User password. After a user name is matched,the user is asked
to enter their assigned password.
If it is not entered correctly,the call is cleared.
"
     ::= { nvSymuserEntry 3 }

nvSymuserStatus OBJECT-TYPE
     SYNTAX   INTEGER {
                valid(1),
                invalid(2)
                }
     ACCESS   read-write
     STATUS   mandatory
     DESCRIPTION
"Operation status. Add the record to the table (valid) or delete
the record from the table (invalid)."
     ::= { nvSymuserEntry 5 }

nvNmsuser OBJECT IDENTIFIER ::= { nevadaSystem 8 }

nvNmsuserMaxRec OBJECT-TYPE
     SYNTAX   INTEGER
     ACCESS   read-only
     STATUS   mandatory
     DESCRIPTION
        "total number of records allowed in database file."
     ::= {nvNmsuser 1}

nvNmsuserNumRec OBJECT-TYPE
     SYNTAX   INTEGER
     ACCESS   read-only
     STATUS   mandatory
     DESCRIPTION
        "number of records in use."
     ::= {nvNmsuser 2}

nvNmsuserTable OBJECT-TYPE
      SYNTAX   SEQUENCE OF NvNmsuserEntry
      ACCESS   not-accessible
      STATUS   mandatory
      DESCRIPTION
               "nmsuser file."
      ::= { nvNmsuser 3 }

nvNmsuserEntry OBJECT-TYPE
      SYNTAX   NvNmsuserEntry
      ACCESS   not-accessible
      STATUS   mandatory
      DESCRIPTION
               "nmsuser record."
      INDEX { nvNmsuserIndex }
      ::= { nvNmsuserTable 1 }

NvNmsuserEntry ::=
      SEQUENCE {
      nvNmsuserIndex
            INTEGER,
      nvNmsuserCalladdr
            DisplayString,
      nvNmsuserCalldata
            DisplayString,
      nvNmsuserPassword
            DisplayString,
      nvNmsuserPsiz
            INTEGER,
      nvNmsuserWsiz
            INTEGER,
      nvNmsuserRpoacode
            INTEGER,
      nvNmsuserOchrg
            INTEGER,
      nvNmsuserCug
            INTEGER,
      nvNmsuserTput
            INTEGER,
      nvNmsuserNmsid
            DisplayString,
      nvNmsuserStatus
	    INTEGER
                }

nvNmsuserIndex OBJECT-TYPE
     SYNTAX   INTEGER
     ACCESS   read-only
     STATUS   mandatory
     DESCRIPTION
        "Index of nmsuser record"
      ::= { nvNmsuserEntry 1 }

nvNmsuserCalladdr OBJECT-TYPE
     SYNTAX   DisplayString (SIZE (0..16))
     ACCESS   read-write
     STATUS   mandatory
     DESCRIPTION
"NMS X.121 Address (calladdr)

"
     ::= { nvNmsuserEntry 2 }

nvNmsuserCalldata OBJECT-TYPE
     SYNTAX   DisplayString (SIZE (0..14))
     ACCESS   read-write
     STATUS   mandatory
     DESCRIPTION
"NMS Userdata (calldata)

Default value is 0."
     ::= { nvNmsuserEntry 3 }

nvNmsuserPassword OBJECT-TYPE
     SYNTAX   DisplayString (SIZE (0..16))
     ACCESS   read-write
     STATUS   mandatory
     DESCRIPTION
"NMS Component Password (password)

Default value is 0."
     ::= { nvNmsuserEntry 4 }

nvNmsuserPsiz OBJECT-TYPE
     SYNTAX   INTEGER {
                b16(5),     --  (+1)
                b32(6),     --
                b64(7),     --
                b128(8),     --
                b256(9),     --
                b512(10),     --
                b1024(11)      --
                }
     ACCESS   read-write
     STATUS   mandatory
     DESCRIPTION
"Packet Size (psiz)

Default value is 7+1."
     ::= { nvNmsuserEntry 5 }

nvNmsuserWsiz OBJECT-TYPE
     SYNTAX   INTEGER (1..127)
     ACCESS   read-write
     STATUS   mandatory
     DESCRIPTION
"Window Size (wsiz)

Default value is 2."
     ::= { nvNmsuserEntry 6 }

nvNmsuserRpoacode OBJECT-TYPE
     SYNTAX   INTEGER (0..65535)
     ACCESS   read-write
     STATUS   mandatory
     DESCRIPTION
"RPOA Code (rpoacode)

Default value is 0."
     ::= { nvNmsuserEntry 7 }

nvNmsuserOchrg OBJECT-TYPE
     SYNTAX   INTEGER {
                oall(2),     -- (+1)
                onorm(3),     --
                orev(4)      --
                }
     ACCESS   read-write
     STATUS   mandatory
     DESCRIPTION
"Outgoing Charging Restriction (ochrg)

Default value is 1+1."
     ::= { nvNmsuserEntry 8 }

nvNmsuserCug OBJECT-TYPE
     SYNTAX   INTEGER (0..65535)
     ACCESS   read-write
     STATUS   mandatory
     DESCRIPTION
"Closed User Group Id (cug)

Default value is 0."
     ::= { nvNmsuserEntry 9 }

nvNmsuserTput OBJECT-TYPE
     SYNTAX   INTEGER {
                bps75(4),     -- (+1)
                bps150(5),     --
                bps300(6),     --
                bps600(7),     --
                bps1200(8),     --
                bps2400(9),     --
                bps4800(10),     --
                bps9600(11)      --
                }
     ACCESS   read-write
     STATUS   mandatory
     DESCRIPTION
"Throughput Class (tput)

Default value is 10+1."
     ::= { nvNmsuserEntry 10 }

nvNmsuserNmsid OBJECT-TYPE
     SYNTAX   DisplayString (SIZE (0..4))
     ACCESS   read-write
     STATUS   mandatory
     DESCRIPTION
"NMS Identification (nmsid) "
     ::= { nvNmsuserEntry 11 }

nvNmsuserStatus OBJECT-TYPE
     SYNTAX   INTEGER {
                valid(1),
                invalid(2)
                }
     ACCESS   read-write
     STATUS   mandatory
     DESCRIPTION
"Operation status. Add the record to the table (valid) or delete
the record from the table (invalid)."
     ::= { nvNmsuserEntry 12 }

-- File contains information that is used by the network router
-- to map network-addresses to destination node id's.
--
-- This information identifies the location of an addressed
-- network entity.
--
-- The network address and user data stored in the NETMAP file
-- are patterns that allow the following options:
--  1. xxxxxx - arbitrary alpha/numeric data (numeric for address)
--  2. *xxx - match exactly the last 3 characters,allow any
-- number of preceeding characters (0 or more).
--  3. xxx* - match exactly the first three characters,any number of
-- trailing ones (0 or more).
--  4. * - match anything.
--  5. xx%xx - match exactly the first two characters,an arbitrary
-- third character,and exactly the last two characters.
--
-- The best match is defined as the field with the most number of
-- exact matches with the stored patterns. This means that * is the
-- last to be matched (catch all).
--
-- In mapping,the best match of the network address is taken first,
-- and within this,the best match for user data.

nvNetmap OBJECT IDENTIFIER ::= { nevadaSystem 9 }

nvNetmapMaxRec OBJECT-TYPE
     SYNTAX   INTEGER
     ACCESS   read-only
     STATUS   mandatory
     DESCRIPTION
        "total number of records allowed in database file."
     ::= {nvNetmap 1}

nvNetmapNumRec OBJECT-TYPE
     SYNTAX   INTEGER
     ACCESS   read-only
     STATUS   mandatory
     DESCRIPTION
        "number of records in use."
     ::= {nvNetmap 2}

nvNetmapTable OBJECT-TYPE
      SYNTAX   SEQUENCE OF NvNetmapEntry
      ACCESS   not-accessible
      STATUS   mandatory
      DESCRIPTION
               "netmap file."
      ::= { nvNetmap 3 }

nvNetmapEntry OBJECT-TYPE
      SYNTAX   NvNetmapEntry
      ACCESS   not-accessible
      STATUS   mandatory
      DESCRIPTION
               "netmap record."
      INDEX { nvNetmapIndex }
      ::= { nvNetmapTable 1 }

NvNetmapEntry ::=
      SEQUENCE {
      nvNetmapIndex
            INTEGER,
      nvNetmapNetaddr
            DisplayString,
      nvNetmapUserdata
            DisplayString,
      nvNetmapNodeid
            INTEGER,
      nvNetmapStatus
            INTEGER
               }

nvNetmapIndex OBJECT-TYPE
     SYNTAX   INTEGER
     ACCESS   read-only
     STATUS   mandatory
     DESCRIPTION
        "Index of netmap record"
      ::= { nvNetmapEntry 1 }

nvNetmapNetaddr OBJECT-TYPE
     SYNTAX   DisplayString (SIZE (0..16))
     ACCESS   read-write
     STATUS   mandatory
     DESCRIPTION
"Network X.121 Address (netaddr)
This field contains the network address
pattern that is matched against the the
network address field in a 'call request'.
"
     ::= { nvNetmapEntry 2 }

nvNetmapUserdata OBJECT-TYPE
     SYNTAX   DisplayString (SIZE (0..14))
     ACCESS   read-write
     STATUS   mandatory
     DESCRIPTION
"User Data (userdata)
This field contains the call user data
pattern that is matched against the call user
data field in a 'call request'.
"
     ::= { nvNetmapEntry 3 }

nvNetmapNodeid OBJECT-TYPE
     SYNTAX   INTEGER (0..65535)
     ACCESS   read-write
     STATUS   mandatory
     DESCRIPTION
"Node Identifier (nodeid)
This parameter is the identifier of the entity
providing the service for a
matched network address and user data.
"
     ::= { nvNetmapEntry 4 }

nvNetmapStatus OBJECT-TYPE
     SYNTAX   INTEGER {
                valid(1),
                invalid(2)
                }
     ACCESS   read-write
     STATUS   mandatory
     DESCRIPTION
"Operation status. Add the record to the table (valid) or delete
the record from the table (invalid)."
     ::= { nvNetmapEntry 5 }


-- File used by the network router to decide how to get to a
-- desired location. This location is obtained from the NETMAP file.

nvNetroute OBJECT IDENTIFIER ::= { nevadaSystem 10 }

nvNetrouteMaxRec OBJECT-TYPE
     SYNTAX   INTEGER
     ACCESS   read-only
     STATUS   mandatory
     DESCRIPTION
        "total number of records allowed in database file."
     ::= {nvNetroute 1}

nvNetrouteNumRec OBJECT-TYPE
     SYNTAX   INTEGER
     ACCESS   read-only
     STATUS   mandatory
     DESCRIPTION
        "number of records in use."
     ::= {nvNetroute 2}

nvNetrouteTable OBJECT-TYPE
      SYNTAX   SEQUENCE OF NvNetrouteEntry
      ACCESS   not-accessible
      STATUS   mandatory
      DESCRIPTION
               "netroute file."
      ::= { nvNetroute 3 }

nvNetrouteEntry OBJECT-TYPE
      SYNTAX   NvNetrouteEntry
      ACCESS   not-accessible
      STATUS   mandatory
      DESCRIPTION
               "netroute record."
      INDEX { nvNetrouteIndex }
      ::= { nvNetrouteTable 1 }

NvNetrouteEntry ::=
      SEQUENCE {
      nvNetrouteIndex
            INTEGER,
      nvNetrouteNodeid
            INTEGER,
      nvNetrouteService
            DisplayString,
      nvNetroutePrio
            INTEGER,
      nvNetrouteStatus
            INTEGER
                }

nvNetrouteIndex OBJECT-TYPE
     SYNTAX   INTEGER
     ACCESS   read-only
     STATUS   mandatory
     DESCRIPTION
        "Index of netroute record"
      ::= { nvNetrouteEntry 1 }

nvNetrouteNodeid OBJECT-TYPE
     SYNTAX   INTEGER (0..65535)
     ACCESS   read-write
     STATUS   mandatory
     DESCRIPTION
"Node Identifier (nodeid)
This parameter is an identifier of destination node.
This value was located in NETMAP.
"
     ::= { nvNetrouteEntry 2 }

nvNetrouteService OBJECT-TYPE
     SYNTAX   DisplayString (SIZE (0..10))
     ACCESS   read-write
     STATUS   mandatory
     DESCRIPTION
"Service Component (service)
This parameter is an index into component table
of component providing the service.
"
     ::= { nvNetrouteEntry 3 }

nvNetroutePrio OBJECT-TYPE
     SYNTAX   INTEGER (0..255)
     ACCESS   read-write
     STATUS   mandatory
     DESCRIPTION
"Route Priority (prio)
This parameter represents the user-assigned
priority of the route.
The router searches this file for the highest priority route that
will allow more connections.

If the highest priority route is unavailable,the next highest
is tried until all possibilities are exhausted and the call
is cleared.
Default value is 100."
     ::= { nvNetrouteEntry 4 }

nvNetrouteStatus OBJECT-TYPE
     SYNTAX   INTEGER {
                valid(1),
                invalid(2)
                }
     ACCESS   read-write
     STATUS   mandatory
     DESCRIPTION
"Operation status. Add the record to the table (valid) or delete
the record from the table (invalid)."
     ::= { nvNetrouteEntry 5 }

-- This file describes all the PVCs in this network that "originate"
-- or "terminate"
-- within this node. PVCs are implemented within the network as
-- switched virtual circuits from the "A" end to the "B" end. The
-- "A" end is responsible for initiating the connection.

nvNetpvc OBJECT IDENTIFIER ::= { nevadaSystem 11 }

nvNetpvcMaxRec OBJECT-TYPE
     SYNTAX   INTEGER
     ACCESS   read-only
     STATUS   mandatory
     DESCRIPTION
        "total number of records allowed in database file."
     ::= {nvNetpvc 1}

nvNetpvcNumRec OBJECT-TYPE
     SYNTAX   INTEGER
     ACCESS   read-only
     STATUS   mandatory
     DESCRIPTION
        "number of records in use."
     ::= {nvNetpvc 2}

nvNetpvcTable OBJECT-TYPE
      SYNTAX   SEQUENCE OF NvNetpvcEntry
      ACCESS   not-accessible
      STATUS   mandatory
      DESCRIPTION
               "netpvc file."
      ::= { nvNetpvc 3 }

nvNetpvcEntry OBJECT-TYPE
      SYNTAX   NvNetpvcEntry
      ACCESS   not-accessible
      STATUS   mandatory
      DESCRIPTION
               "netpvc record."
      INDEX { nvNetpvcIndex }
      ::= { nvNetpvcTable 1 }

NvNetpvcEntry ::=
      SEQUENCE {
      nvNetpvcIndex
            INTEGER,
      nvNetpvcService
            DisplayString,
      nvNetpvcPvcid
            INTEGER,
      nvNetpvcPvccode
            INTEGER,
      nvNetpvcPvcend
            INTEGER,
      nvNetpvcStatus
            INTEGER
                }

nvNetpvcIndex OBJECT-TYPE
     SYNTAX   INTEGER
     ACCESS   read-only
     STATUS   mandatory
     DESCRIPTION
        "Index of netpvc record"
      ::= { nvNetpvcEntry 1 }

nvNetpvcService OBJECT-TYPE
     SYNTAX   DisplayString (SIZE (0..10))
     ACCESS   read-write
     STATUS   mandatory
     DESCRIPTION
"Service Component (service)
COMPID and PVCID together uniquely identify one end of
a PVC,and make up the key to this file when searching
for an 'A' end.
"
     ::= { nvNetpvcEntry 2 }

nvNetpvcPvcid OBJECT-TYPE
     SYNTAX   INTEGER (0..65535)
     ACCESS   read-write
     STATUS   mandatory
     DESCRIPTION
"Local PVC Identifier (pvcid)
"
     ::= { nvNetpvcEntry 3 }

nvNetpvcPvccode OBJECT-TYPE
     SYNTAX   INTEGER (0..65535)
     ACCESS   read-write
     STATUS   mandatory
     DESCRIPTION
"Global PVC Identifier (pvccode)
PVCCODE uniquely identifies a PVC,and is used as the key
to this file when searching for a 'B' end.
"
     ::= { nvNetpvcEntry 4 }

nvNetpvcPvcend OBJECT-TYPE
     SYNTAX   INTEGER {
                originatingEnd(2),     -- originating end (+1)
                terminatingEnd(3),     -- terminating end
                symmetricEnd(4)      -- symmetric end
                }
     ACCESS   read-write
     STATUS   mandatory
     DESCRIPTION
"PVC End (pvcend)
Default value is 2+1."
     ::= { nvNetpvcEntry 5 }

nvNetpvcStatus OBJECT-TYPE
     SYNTAX   INTEGER {
                valid(1),
                invalid(2)
                }
     ACCESS   read-write
     STATUS   mandatory
     DESCRIPTION
"Operation status. Add the record to the table (valid) or
delete the record from the table (invalid)."
     ::= { nvNetpvcEntry 6 }

-- File contains information that is used by the network router
-- to map PVC identifiers to destination node id's.
--
-- This information identifies the location of an addressed
-- network entity.

nvNetpvcmap OBJECT IDENTIFIER ::= { nevadaSystem 12 }

nvNetpvcmapMaxRec OBJECT-TYPE
     SYNTAX   INTEGER
     ACCESS   read-only
     STATUS   mandatory
     DESCRIPTION
        "total number of records allowed in database file."
     ::= {nvNetpvcmap 1}

nvNetpvcmapNumRec OBJECT-TYPE
     SYNTAX   INTEGER
     ACCESS   read-only
     STATUS   mandatory
     DESCRIPTION
        "number of records in use."
     ::= {nvNetpvcmap 2}

nvNetpvcmapTable OBJECT-TYPE
      SYNTAX   SEQUENCE OF NvNetpvcmapEntry
      ACCESS   not-accessible
      STATUS   mandatory
      DESCRIPTION
               "netpvcmap file."
      ::= { nvNetpvcmap 3 }

nvNetpvcmapEntry OBJECT-TYPE
      SYNTAX   NvNetpvcmapEntry
      ACCESS   not-accessible
      STATUS   mandatory
      DESCRIPTION
               "netpvcmap record."
      INDEX { nvNetpvcmapIndex }
      ::= { nvNetpvcmapTable 1 }

NvNetpvcmapEntry ::=
      SEQUENCE {
      nvNetpvcmapIndex
            INTEGER,
      nvNetpvcmapPvccode
            INTEGER,
      nvNetpvcmapNodeid
            INTEGER,
      nvNetpvcmapStatus
	    INTEGER
                }

nvNetpvcmapIndex OBJECT-TYPE
     SYNTAX   INTEGER
     ACCESS   read-only
     STATUS   mandatory
     DESCRIPTION
        "Index of netpvcmap record"
      ::= { nvNetpvcmapEntry 1 }

nvNetpvcmapPvccode OBJECT-TYPE
     SYNTAX   INTEGER (0..65535)
     ACCESS   read-write
     STATUS   mandatory
     DESCRIPTION
"Global PVC Identifier (pvccode)
"
     ::= { nvNetpvcmapEntry 2 }

nvNetpvcmapNodeid OBJECT-TYPE
     SYNTAX   INTEGER (0..65535)
     ACCESS   read-write
     STATUS   mandatory
     DESCRIPTION
"Node Identifier (nodeid)
This parameter is the identifier of the entity
providing 'B' end of a PVC within our network.
"
     ::= { nvNetpvcmapEntry 3 }

nvNetpvcmapStatus OBJECT-TYPE
     SYNTAX   INTEGER {
		valid(1),
		invalid(2)
		}
     ACCESS   read-write
     STATUS   mandatory
     DESCRIPTION
"Operation status. Add the record to the table (valid) or
delete the record from the table (invalid)."
     ::= { nvNetpvcmapEntry 10 }

--
-- netcon
--
nvNetcon OBJECT IDENTIFIER ::= {nevadaSystem 13}

nvNetconMaxRec OBJECT-TYPE
     SYNTAX   INTEGER
     ACCESS   read-only
     STATUS   mandatory
     DESCRIPTION
        "total number of records allowed in database file."
     ::= {nvNetcon 1}

nvNetconNumRec OBJECT-TYPE
     SYNTAX   INTEGER
     ACCESS   read-only
     STATUS   mandatory
     DESCRIPTION
        "number of records in use."
     ::= {nvNetcon 2}

nvNetconTable OBJECT-TYPE
      SYNTAX   SEQUENCE OF NvNetconEntry
      ACCESS   not-accessible
      STATUS   mandatory
      DESCRIPTION
               "netcon file."
      ::= {nvNetcon 3}

nvNetconEntry OBJECT-TYPE
      SYNTAX   NvNetconEntry
      ACCESS   not-accessible
      STATUS   mandatory
      DESCRIPTION
               "netcon record, indexed by record number"
      INDEX {nvNetconIndex}
      ::= {nvNetconTable 1 }

NvNetconEntry ::=
      SEQUENCE {
       nvNetconIndex
            INTEGER,
      nvNetconSrccompid
            DisplayString,
      nvNetconDstcompid
            DisplayString,
      nvNetconCallingad
            DisplayString,
      nvNetconCalledad
            DisplayString,
      nvNetconConstate
            INTEGER,
      nvNetconConid
	    DisplayString,
      nvNetconSrcid
	    DisplayString,
      nvNetconDstid
	    DisplayString
               }

nvNetconIndex OBJECT-TYPE
     SYNTAX   INTEGER
     ACCESS   read-only
     STATUS   mandatory
     DESCRIPTION
        "Index of netcon record"
     ::= {nvNetconEntry 1}

nvNetconSrccompid OBJECT-TYPE
     SYNTAX   DisplayString (SIZE (0..10))
     ACCESS   read-only
     STATUS   mandatory
     DESCRIPTION
        "source component id
         Originating component of the connection. "
     ::= {nvNetconEntry 2 }

nvNetconDstcompid OBJECT-TYPE
     SYNTAX   DisplayString (SIZE (0..10))
     ACCESS   read-only
     STATUS   mandatory
     DESCRIPTION
        "destination component id
         Receiving component of the connection. "
     ::= {nvNetconEntry 3}

nvNetconCallingad OBJECT-TYPE
     SYNTAX   DisplayString (SIZE (0..15))
     ACCESS   read-only
     STATUS   mandatory
     DESCRIPTION
        "calling network address (from bcd)
         The calling network address."
     ::= {nvNetconEntry 4 }

nvNetconCalledad OBJECT-TYPE
     SYNTAX   DisplayString (SIZE (0..15))
     ACCESS   read-only
     STATUS   mandatory
     DESCRIPTION
        "called network address (from bcd)
         The called network address."
     ::= {nvNetconEntry 5 }

nvNetconConstate OBJECT-TYPE
     SYNTAX   INTEGER {
                initial(2),             -- (+1)
                awaitingResponse(3),
                dataTransfer(5),
                disconnected(9)
                }
     ACCESS   read-only
     STATUS   mandatory
     DESCRIPTION
        "connection state
         The actual state of this connection.
         Initial status is 1."
     ::= {nvNetconEntry 6 }

nvNetconConid OBJECT-TYPE
     SYNTAX   DisplayString (SIZE (0..10))
     ACCESS   read-only
     STATUS   mandatory
     DESCRIPTION
        "Internal Network connection identifier."
     ::= {nvNetconEntry 7 }

nvNetconSrcid OBJECT-TYPE
     SYNTAX   DisplayString (SIZE (0..10))
     ACCESS   read-only
     STATUS   mandatory
     DESCRIPTION
        "Internal Source identifier."
     ::= {nvNetconEntry 8 }

nvNetconDstid OBJECT-TYPE
     SYNTAX   DisplayString (SIZE (0..10))
     ACCESS   read-only
     STATUS   mandatory
     DESCRIPTION
        "Internal Destination identifier."
     ::= {nvNetconEntry 9 }

--
--      routemap file
--
nvRoutemap OBJECT IDENTIFIER ::= { nevadaSystem 14}

nvRoutemapMaxRec OBJECT-TYPE
     SYNTAX   INTEGER
     ACCESS   read-only
     STATUS   mandatory
     DESCRIPTION
        "total number of records allowed in database file."
     ::= {nvRoutemap 1}

nvRoutemapNumRec OBJECT-TYPE
     SYNTAX   INTEGER
     ACCESS   read-only
     STATUS   mandatory
     DESCRIPTION
        "number of records in use."
     ::= {nvRoutemap 2}

nvRoutemapTable OBJECT-TYPE
      SYNTAX   SEQUENCE OF NvRoutemapEntry
      ACCESS   not-accessible
      STATUS   mandatory
      DESCRIPTION
               "routemap file."
      ::= { nvRoutemap 3 }

nvRoutemapEntry OBJECT-TYPE
      SYNTAX   NvRoutemapEntry
      ACCESS   not-accessible
      STATUS   mandatory
      DESCRIPTION
               "routemap record."
      INDEX { nvRoutemapIndex }
      ::= { nvRoutemapTable 1 }

NvRoutemapEntry ::=
      SEQUENCE {
      nvRoutemapIndex
            INTEGER,
      nvRoutemapAddrstr
            DisplayString,
      nvRoutemapAddrtype
            INTEGER,
      nvRoutemapNetaddr
            DisplayString,
      nvRoutemapUserdata
            DisplayString,
      nvRoutemapStatus
            INTEGER
               }

nvRoutemapIndex OBJECT-TYPE
     SYNTAX   INTEGER
     ACCESS   read-only
     STATUS   mandatory
     DESCRIPTION
        "Index of routemap record"
      ::= { nvRoutemapEntry 1 }

nvRoutemapAddrstr OBJECT-TYPE
     SYNTAX   DisplayString (SIZE (0..64))
     ACCESS   read-write
     STATUS   mandatory
     DESCRIPTION
        "Address string to be translated (addrstr)."
     ::= { nvRoutemapEntry 2 }

nvRoutemapAddrtype OBJECT-TYPE
     SYNTAX   INTEGER {
                callednum(2),           -- (+1)
                calledsub(3),
                any(9)
                }
     ACCESS   read-write
     STATUS   mandatory
     DESCRIPTION
        "How to interpret addrstr (addrtype)."
     ::= { nvRoutemapEntry 3 }

nvRoutemapNetaddr OBJECT-TYPE
     SYNTAX   DisplayString (SIZE (0..15))
     ACCESS   read-write
     STATUS   mandatory
     DESCRIPTION
        "Netaddr yielded by match with addrstr."
     ::= { nvRoutemapEntry 4 }

nvRoutemapUserdata OBJECT-TYPE
     SYNTAX   DisplayString (SIZE (0..14))
     ACCESS   read-write
     STATUS   mandatory
     DESCRIPTION
        "Userdata yielded by match with addrstr."
     ::= { nvRoutemapEntry 5 }


nvRoutemapStatus OBJECT-TYPE
     SYNTAX   INTEGER {
                valid(1),
                invalid(2)
                }
     ACCESS   read-write
     STATUS   mandatory
     DESCRIPTION
"Operation status. Add the record to the table (valid) or delete
the record from the table (invalid)."
     ::= { nvRoutemapEntry 6 }


-- File contains one record used to uniquely identify a HUB,
-- and to carry miscellaneous configuration information.

--
--      mediastat file
--
nvMediastat     OBJECT IDENTIFIER ::= {nevadaSystem 15}

nvMediastatMaxRec OBJECT-TYPE
     SYNTAX   INTEGER
     ACCESS   read-only
     STATUS   mandatory
     DESCRIPTION
        "total number of records allowed in database file."
     ::= {nvMediastat 1}

nvMediastatNumRec OBJECT-TYPE
     SYNTAX   INTEGER
     ACCESS   read-only
     STATUS   mandatory
     DESCRIPTION
        "number of records in use."
     ::= {nvMediastat 2}

nvMediastatTable OBJECT-TYPE
      SYNTAX   SEQUENCE OF NvMediastatEntry
      ACCESS   not-accessible
      STATUS   mandatory
      DESCRIPTION
         "Mediastat file."
      ::= { nvMediastat 3 }

nvMediastatEntry OBJECT-TYPE
      SYNTAX   NvMediastatEntry
      ACCESS   not-accessible
      STATUS   mandatory
      DESCRIPTION
               "Mediastat record."
      INDEX { nvMediastatIndex }
      ::= { nvMediastatTable 1 }


NvMediastatEntry ::=
      SEQUENCE {
           nvMediastatIndex
               INTEGER,
           nvMediastatOrigimage
               INTEGER,
           nvMediastatImage
               INTEGER,
           nvMediastatDebug
               INTEGER,
           nvMediastatImagechg
               INTEGER,
           nvMediastatDump
               INTEGER,
           nvMediastatImage1db
               DisplayString,
           nvMediastatImage1sw
               DisplayString,
           nvMediastatImage2db
               DisplayString,
           nvMediastatImage2sw
               DisplayString,
           nvMediastatMediasize
               INTEGER
                }

nvMediastatIndex OBJECT-TYPE
     SYNTAX   INTEGER
     ACCESS   read-only
     STATUS   mandatory
     DESCRIPTION
        "Index of mediastat record"
      ::= { nvMediastatEntry 1 }


nvMediastatOrigimage OBJECT-TYPE
     SYNTAX   INTEGER {
                image1(1),              -- (+1)
                image2(401)
                }
     ACCESS   read-only
     STATUS   mandatory
     DESCRIPTION
        "original boot image."
     ::= {nvMediastatEntry 2 }

nvMediastatImage OBJECT-TYPE
     SYNTAX   INTEGER {
                image1(1),              -- (+1)
                image2(401)
                }
     ACCESS   read-write
     STATUS   mandatory
     DESCRIPTION
        "current boot image."
     ::= {nvMediastatEntry  3 }

nvMediastatDebug OBJECT-TYPE
     SYNTAX   INTEGER {
                disable(1),             -- (+1)
                enable(2)
                }
     ACCESS   read-write
     STATUS   mandatory
     DESCRIPTION
        "debug flag."
     ::= {nvMediastatEntry  4 }

nvMediastatImagechg OBJECT-TYPE
     SYNTAX   INTEGER {
                disable(1),             -- (+1)
                enable(2)
                }
     ACCESS   read-write
     STATUS   mandatory
     DESCRIPTION
        "auto image change."
     ::= {nvMediastatEntry  5 }

nvMediastatDump OBJECT-TYPE
     SYNTAX   INTEGER {
                disable(1),             -- (+1)
                enable(2)
                }
     ACCESS   read-write
     STATUS   mandatory
     DESCRIPTION
        "dump flag."
     ::= {nvMediastatEntry  6 }

nvMediastatImage1db OBJECT-TYPE
     SYNTAX   DisplayString (SIZE(0..4))
     ACCESS   read-only
     STATUS   mandatory
     DESCRIPTION
        "side0 database version."
     ::= {nvMediastatEntry  7 }

nvMediastatImage1sw OBJECT-TYPE
     SYNTAX   DisplayString (SIZE(0..4))
     ACCESS   read-only
     STATUS   mandatory
     DESCRIPTION
        "side0 software version."
     ::= {nvMediastatEntry  8 }

nvMediastatImage2db OBJECT-TYPE
     SYNTAX   DisplayString (SIZE(0..4))
     ACCESS   read-only
     STATUS   mandatory
     DESCRIPTION
        "side1 database version."
     ::= {nvMediastatEntry  9 }

nvMediastatImage2sw OBJECT-TYPE
     SYNTAX   DisplayString (SIZE(0..4))
     ACCESS   read-only
     STATUS   mandatory
     DESCRIPTION
        "side1 software version."
     ::= {nvMediastatEntry  10 }

nvMediastatMediasize OBJECT-TYPE
     SYNTAX   INTEGER {
                absent(1),              -- (+1)
                v2MB(3),
                v4MB(5),
                v6MB(7),
                v8MB(9),
                v10MB(11),
                v12MB(13),
                v14MB(15),
                v16MB(17),
                v18MB(19),
                v20MB(21),
                v32MB(33)
                }
     ACCESS   read-only
     STATUS   mandatory
     DESCRIPTION
        "storage medium size."
     ::= {nvMediastatEntry  11 }

--
-- Backhaul instance table definition
--

        nvTnnlconf OBJECT IDENTIFIER ::= { nevadaSystem 16 }

        nvTnnlconfMaxRec OBJECT-TYPE
           SYNTAX   INTEGER
           ACCESS   read-only
           STATUS   mandatory
           DESCRIPTION
                "total number of records allowed in database file."
           ::= {nvTnnlconf 1}

        nvTnnlconfNumRec OBJECT-TYPE
           SYNTAX   INTEGER
           ACCESS   read-only
           STATUS   mandatory
           DESCRIPTION
                "number of records in use."
           ::= {nvTnnlconf 2}

        nvTnnlconfTable OBJECT-TYPE
           SYNTAX SEQUENCE OF NvTnnlconfEntry
           ACCESS not-accessible
           STATUS mandatory
           DESCRIPTION
                "Backhaul instance table definition."
           ::= { nvTnnlconf 3 }

        nvTnnlconfEntry OBJECT-TYPE
           SYNTAX NvTnnlconfEntry
           ACCESS not-accessible
           STATUS mandatory
           DESCRIPTION
                "A tunnel table entry containing objects which
                configure a tunnel protocol."
           INDEX { nvTnnlconfIndex }
           ::= { nvTnnlconfTable 1 }

        NvTnnlconfEntry ::=
           SEQUENCE {
                nvTnnlconfIndex
                   INTEGER,
                nvTnnlconfPortname
                   DisplayString,
                nvTnnlconfRsrcpool
                   DisplayString,
                nvTnnlconfLineprot
                   INTEGER,
                nvTnnlconfProt
                   INTEGER,
                nvTnnlconfRtmethod
                   INTEGER,
                nvTnnlconfNetaddr
                   DisplayString,
                nvTnnlconfUserdata
                   DisplayString,
                nvTnnlconfStatus
                   INTEGER
           }

        nvTnnlconfIndex OBJECT-TYPE
           SYNTAX INTEGER
           ACCESS read-only
           STATUS mandatory
           DESCRIPTION
                "Backhaul configuration entry index number."
           ::= { nvTnnlconfEntry 1 }

        nvTnnlconfPortname OBJECT-TYPE
           SYNTAX DisplayString (SIZE(0..10))
           ACCESS read-write
           STATUS mandatory
           DESCRIPTION
                "Port name (portname)"
           ::= { nvTnnlconfEntry 2 }

        nvTnnlconfRsrcpool OBJECT-TYPE
           SYNTAX DisplayString (SIZE(0..10))
           ACCESS read-write
           STATUS mandatory
           DESCRIPTION
                "Resource pool name."
           ::= { nvTnnlconfEntry 3 }

        -- 4 is reserved

        nvTnnlconfLineprot OBJECT-TYPE
           SYNTAX INTEGER {
               dontcare(2),  -- Dont know or care what protocol is on line (+1)
               rfc1662(3)    -- RFC1662 PPP in HDLC-like Framing
           }
           ACCESS read-write
           STATUS mandatory
           DESCRIPTION
                "Backhaul line protocol."
           ::= { nvTnnlconfEntry 5 }

        nvTnnlconfProt OBJECT-TYPE
           SYNTAX INTEGER {
               transparent(2),  -- Transparent encapsulation (+1)
               rfc1598(3)       -- RFC1598 PPP in X25
           }
           ACCESS read-write
           STATUS mandatory
           DESCRIPTION
                "Backhaul line protocol."
           ::= { nvTnnlconfEntry 6 }

        nvTnnlconfRtmethod OBJECT-TYPE
           SYNTAX INTEGER {
               useconfig(2),   -- Route to netaddr/userdata in this record (+1)
               usecallednm(3), -- Route on ISDN called party number
               usecalledsb(4)  -- Route on ISDN called party subaddress
           }
           ACCESS read-write
           STATUS mandatory
           DESCRIPTION
                "Backhaul routing protocol."
           ::= { nvTnnlconfEntry 7 }

        -- 8 is reserved

        nvTnnlconfNetaddr OBJECT-TYPE
           SYNTAX DisplayString (SIZE(0..16))
           ACCESS read-write
           STATUS mandatory
           DESCRIPTION
                "Backhaul network address when rtmethod is useconfig."
           ::= { nvTnnlconfEntry 9 }

        nvTnnlconfUserdata OBJECT-TYPE
           SYNTAX DisplayString (SIZE(0..20))
           ACCESS read-write
           STATUS mandatory
           DESCRIPTION
                "Backhaul configuration user data."
           ::= { nvTnnlconfEntry 10 }

        nvTnnlconfStatus OBJECT-TYPE
           SYNTAX   INTEGER {
                        valid(1),
                        invalid(2)
                        }
           ACCESS   read-write
           STATUS   mandatory
           DESCRIPTION
                 "Operation status. Add the record to the table (valid) or
                 delete the record from the table (invalid)."
           ::= { nvTnnlconfEntry 11 }

-- Backhaul instance status table definition

        nvTnnlstat OBJECT IDENTIFIER ::= { nevadaSystem 17 }

        nvTnnlstatfMaxRec OBJECT-TYPE
           SYNTAX   INTEGER
           ACCESS   read-only
           STATUS   mandatory
           DESCRIPTION
                "total number of records allowed in database file."
           ::= {nvTnnlstat 1}

        nvTnnlstatNumRec OBJECT-TYPE
           SYNTAX   INTEGER
           ACCESS   read-only
           STATUS   mandatory
           DESCRIPTION
                "number of records in use."
           ::= {nvTnnlstat 2}

        nvTnnlstatTable OBJECT-TYPE
           SYNTAX SEQUENCE OF NvTnnlstatEntry
           ACCESS not-accessible
           STATUS mandatory
           DESCRIPTION
                "Backhaul instance status table definition."
           ::= { nvTnnlstat 3 }

        nvTnnlstatEntry OBJECT-TYPE
           SYNTAX NvTnnlstatEntry
           ACCESS not-accessible
           STATUS mandatory
           DESCRIPTION
                "A tunnel status table entry containing fields which
                store tunnel status information."
           INDEX { nvTnnlstatIndex }
           ::= { nvTnnlstatTable 1 }

        NvTnnlstatEntry ::=
           SEQUENCE {
                nvTnnlstatIndex
                        INTEGER,
                nvTnnlstatPortname
                        DisplayString, 
                nvTnnlstatRsrcpool
                        DisplayString,
                nvTnnlstatConnstat
                        INTEGER,
                nvTnnlstatRtstring
                        DisplayString,
                nvTnnlstatNetaddr
                        DisplayString,
                nvTnnlstatUserdata
                        DisplayString,
                nvTnnlstatCallatts
                        Counter,
                nvTnnlstatCallattfs
                        Counter,
                nvTnnlstatInframes
                        Counter,
                nvTnnlstatOutframes
                        Counter,
		nvTnnlstatDtreset
			DisplayString
           }

        nvTnnlstatIndex OBJECT-TYPE
           SYNTAX INTEGER
           ACCESS read-only
           STATUS mandatory
           DESCRIPTION
                "Backhaul status entry index number."
           ::= { nvTnnlstatEntry 1 }

        nvTnnlstatPortname OBJECT-TYPE
           SYNTAX DisplayString (SIZE(0..10)) 
           ACCESS read-only
           STATUS mandatory
           DESCRIPTION
                "Port on which this Backhaul status entry is applied."
           ::= { nvTnnlstatEntry 2 }

        nvTnnlstatRsrcpool OBJECT-TYPE
           SYNTAX DisplayString (SIZE(0..10))
           ACCESS read-only
           STATUS mandatory
           DESCRIPTION
                "Resource pool on which this Backhaul status entry
                is applied."
           ::= { nvTnnlstatEntry 3 }

        nvTnnlstatConnstat OBJECT-TYPE
           SYNTAX INTEGER {
               tunnelnocb(2),    -- Couldnt get control block for Tunnel. (+1)
               tunnelnoport(3),  -- Tunnel has no connected port. Must reboot.
               tunnelinactive(4), -- Tunnel instance currently idle
               tunnelcalling(5), -- Tunnel currently establishing tunnel path
               tunnelactive(6) -- Tunnel tunnel path established
           }
           ACCESS read-only
           STATUS mandatory
           DESCRIPTION
                "Current connection status."
           ::= { nvTnnlstatEntry 4 }

        nvTnnlstatRtstring OBJECT-TYPE
           SYNTAX DisplayString (SIZE(0..64))
           ACCESS read-only
           STATUS mandatory
           DESCRIPTION
                "String upon which routing was based."
           ::= { nvTnnlstatEntry 5 }

        nvTnnlstatNetaddr OBJECT-TYPE
           SYNTAX DisplayString (SIZE(0..16))
           ACCESS read-only
           STATUS mandatory
           DESCRIPTION
                "Network address to which call was routed."
           ::= { nvTnnlstatEntry 6 }

        nvTnnlstatUserdata OBJECT-TYPE
           SYNTAX DisplayString (SIZE(0..13))
           ACCESS read-only
           STATUS mandatory
           DESCRIPTION
                "User data to which call was routed."
           ::= { nvTnnlstatEntry 7 }

        -- 8 is reserved

        nvTnnlstatCallatts OBJECT-TYPE
           SYNTAX Counter
           ACCESS read-only
           STATUS mandatory
           DESCRIPTION
                "No of attempts to place current call."
           ::= { nvTnnlstatEntry 9 }

        nvTnnlstatCallattfs OBJECT-TYPE
           SYNTAX Counter
           ACCESS read-only
           STATUS mandatory
           DESCRIPTION
                "No of failed attempts to place current call."
           ::= { nvTnnlstatEntry 10 }

        nvTnnlstatInframes OBJECT-TYPE
           SYNTAX Counter
           ACCESS read-only
           STATUS mandatory
           DESCRIPTION
                "No of frames switched from line to tunnel route."
           ::= { nvTnnlstatEntry 11 }

        nvTnnlstatOutframes OBJECT-TYPE
           SYNTAX Counter
           ACCESS read-only
           STATUS mandatory
           DESCRIPTION
                "No of frames switched from tunnel route to line."
           ::= { nvTnnlstatEntry 12 }

	nvTnnlstatDtreset OBJECT-TYPE
	   SYNTAX   DisplayString (SIZE (0..20))
	   ACCESS   read-only
	   STATUS   mandatory
	   DESCRIPTION
		"date & time statistics last reset"
	   ::= { nvTnnlstatEntry 13 }

-- DLI configuration table definition

        nvCDLITable OBJECT-TYPE
           SYNTAX SEQUENCE OF NvCDLIEntry
           ACCESS not-accessible
           STATUS mandatory
           DESCRIPTION
                "DLI configuration table definition.The actual database
                contains 17 tables, if a DLI card is plugged in
                one of the slot then the data table matched the
                slot will become active, otherwise the record is
                not active. This table combines 17 tables into one
                MIB table which uses two table instances: slot
                and port."
           ::= { nevadaSystem 18 }

        nvCDLIEntry OBJECT-TYPE
           SYNTAX NvCDLIEntry
           ACCESS not-accessible
           STATUS mandatory
           DESCRIPTION
                "DLI configuration record."
           INDEX { nvCDLISlotIndex,nvCDLIPortIndex }
           ::= { nvCDLITable 1 }

        NvCDLIEntry ::=
           SEQUENCE {
                nvCDLISlotIndex
                        INTEGER,
                nvCDLIPortIndex
                        INTEGER,
                nvCDLIName
                        DisplayString,
                nvCDLIFormat
                        INTEGER,
                nvCDLICode
                        INTEGER,
                nvCDLIFdl
                        INTEGER,
                nvCDLISignaling
                        INTEGER,
                nvCDLILineimp
                        INTEGER,
                nvCDLIEnable
                        INTEGER,
                nvCDLICsudsu
                        INTEGER,
                nvCDLIAtten
                        INTEGER,
                nvCDLIGain
                        INTEGER,
                nvCDLIDataInver
                        INTEGER
           }

        nvCDLISlotIndex OBJECT-TYPE
           SYNTAX INTEGER (1..17)
           ACCESS read-only
           STATUS mandatory
           DESCRIPTION
                "CDLI slot index number."
           ::= { nvCDLIEntry 1 }

        nvCDLIPortIndex OBJECT-TYPE
           SYNTAX INTEGER (1..4)
           ACCESS read-only
           STATUS mandatory
           DESCRIPTION
                "CDLI card port index number."
           ::= { nvCDLIEntry 2 }

        nvCDLIName OBJECT-TYPE
           SYNTAX DisplayString (SIZE(0..10))
           ACCESS read-only
           STATUS mandatory
           DESCRIPTION
                "The name of the DLI card port such as CDLI1_I2."
           ::= { nvCDLIEntry 3 }

        nvCDLIFormat OBJECT-TYPE
           SYNTAX INTEGER {
                d4sf(1),  -- D4 Superframe (+1)
                d4esf(2), -- D4 Extended Superframe
                pcm30(3), -- PCM-30
                crc4(4)   -- CRC4 Multi Frame
           }
           ACCESS read-write
           STATUS mandatory
           DESCRIPTION
                "Frame format."
           ::= { nvCDLIEntry 4 }

        nvCDLICode OBJECT-TYPE
           SYNTAX INTEGER {
                ami(1),  -- Alternated Mark Inversion (+1)
                b8zs(2), -- Binary 8 zero subsitution
                hdb3(3)  -- HDB3
           }
           ACCESS read-write
           STATUS mandatory
           DESCRIPTION
                "Code format."
           ::= { nvCDLIEntry 5 }

        nvCDLIFdl OBJECT-TYPE
           SYNTAX INTEGER {
                none(1), -- No Facilites Data Link  (+1)
                att(2), -- AT&T 54016 Format
                ansi(3)  -- ANSI T1.403
           }
           ACCESS read-write
           STATUS mandatory
           DESCRIPTION
                "Facilities data link format."
           ::= { nvCDLIEntry 6 }

        nvCDLISignaling OBJECT-TYPE
           SYNTAX INTEGER {
                ccs(1), -- CCS time slot 16 for E1 time slot 24 for T1 (+1)
		rbs(2) -- Robbed bit signaling for T1
           }
           ACCESS read-write
           STATUS mandatory
           DESCRIPTION
                "Signal type."
           ::= { nvCDLIEntry 7 }

        nvCDLILineimp OBJECT-TYPE
           SYNTAX INTEGER {
                ohm-120(1), -- E1 120 OHM  (+1)
                ohm-75(2),  -- E1 75 OHM
                ohm-100(3)  -- T1 100 OHM
           }
           ACCESS read-write
           STATUS mandatory
           DESCRIPTION
                "Line impedance."
           ::= { nvCDLIEntry 8 }

        nvCDLIEnable OBJECT-TYPE
           SYNTAX INTEGER {
                yes(1), -- Enable yes  (+1)
                no(2)   -- Enable no
           }
           ACCESS read-write
           STATUS mandatory
           DESCRIPTION
                "Port enable."
           ::= { nvCDLIEntry 9 }
           
        nvCDLICsudsu OBJECT-TYPE
           SYNTAX INTEGER {
                yes(1), -- Enable yes  (+1)
                no(2)   -- Enable no
           }
           ACCESS read-write
           STATUS mandatory
           DESCRIPTION
                "csudsu enabled or not."
           ::= { nvCDLIEntry 10 }

        nvCDLIAtten OBJECT-TYPE
           SYNTAX INTEGER {
		t130(1),  --           0,      T1 3 DB
		t124(2),   --          1,      T1 2.4 DB
		t118(3),    --         2,      T1 1.8 DB
		t112(4),     --        3,      T1 1.2 DB
		t16(5),       --       4,      T1 .6  DB
		t10(6),         --     5,      T1 0   DB
		t1neg75(7),     --     6,      T1 -7.5 DB
		t1neg150(8),     --    7,      T1 -15 DB
		t1neg225(9)      --   8,      T1 -22.5 DB
           }
           ACCESS read-write
           STATUS mandatory
           DESCRIPTION
                "Attenuation of the line ."
           ::= { nvCDLIEntry 11 }

        nvCDLIGain OBJECT-TYPE
           SYNTAX INTEGER {
		g12db(1),   --        0,      12 DB
		g26db(2),   --        1,      26 DB
		g36db(3),   --        2,      36 DB
		g43db(4)    --       3,      43 DB
           }
           ACCESS read-write
           STATUS mandatory
           DESCRIPTION
                "Gain of the receiver."
           ::= { nvCDLIEntry 12 }

        nvCDLIDataInver OBJECT-TYPE
           SYNTAX INTEGER {
                yes(1), -- Enable yes  (+1)
                no(2)   -- Enable no
           }
           ACCESS read-write
           STATUS mandatory
           DESCRIPTION
                "Data inversion enabled or not."
           ::= { nvCDLIEntry 13 }

--
-- sdlix - DLI statistics table definition
--
        nvSDLITable OBJECT-TYPE
           SYNTAX SEQUENCE OF NvSDLIEntry
           ACCESS not-accessible
           STATUS mandatory
           DESCRIPTION
                "DLI statistics table definition.The actual database
                contains 17 tables, if a DLI card is plugged in
                one of the slot then the data table matched the
                slot will become active, otherwise the record is
                not active. This table combines 17 tables into one
                MIB table which uses two table instances: slot
                and port."
           ::= { nevadaSystem 19 }

        nvSDLIEntry OBJECT-TYPE
           SYNTAX NvSDLIEntry
           ACCESS not-accessible
           STATUS mandatory
           DESCRIPTION
                "DLI statistics record."
           INDEX { nvSDLISlotIndex,nvSDLIPortIndex }
           ::= { nvSDLITable 1 }

        NvSDLIEntry ::=
           SEQUENCE {
                nvSDLISlotIndex
                        INTEGER,
                nvSDLIPortIndex
                        INTEGER,
                nvSDLISdlinm
                        DisplayString,
                nvSDLIDlitype
                        DisplayString,
                nvSDLICurstate
                        INTEGER,
                nvSDLIRedcnts
                        Counter,
                nvSDLIYelcnts
                        Counter,
                nvSDLIBlucnts
                        Counter,
                nvSDLIErrcnt
                        Counter,
		nvSDLITxundrun         --pkg 84
		        Counter,       --AF  	
		nvSDLIRxfrmslp         --AF
		        Counter,        --AF            
		nvSDLIDtreset
			DisplayString
           }

        nvSDLISlotIndex OBJECT-TYPE
           SYNTAX INTEGER (1..17)
           ACCESS read-only
           STATUS mandatory
           DESCRIPTION
                "SDLI slot index number."
           ::= { nvSDLIEntry 1 }

        nvSDLIPortIndex OBJECT-TYPE
           SYNTAX INTEGER (1..4)
           ACCESS read-only
           STATUS mandatory
           DESCRIPTION
                "SDLI card port index number."
           ::= { nvSDLIEntry 2 }

        nvSDLISdlinm OBJECT-TYPE
           SYNTAX DisplayString (SIZE(0..10))
           ACCESS read-only
           STATUS mandatory
           DESCRIPTION
                "SDLI entry name such as SDLI1_I2."
           ::= { nvSDLIEntry 3 }

        nvSDLIDlitype OBJECT-TYPE
           SYNTAX DisplayString (SIZE(0..3))
           ACCESS read-only
           STATUS mandatory
           DESCRIPTION
                "SDLI card port type such as E1 or T1."
           ::= { nvSDLIEntry 4 }

        nvSDLICurstate OBJECT-TYPE
           SYNTAX INTEGER {
                ok(1),       -- DLI Up (+1)
                unknwn(2),   -- DLI Unknown State
                down(3),     -- DLI Down
                red(4),      -- DLI Red Alarm State
                blue(5),     -- DLI Blue Alarm State
                yell(6),     -- DLI Yellow Alarm State
                mLine(7),    -- DLI Line Maintenance Mode
                mPay(8),     -- DLI Payload Maintenance Mode
                busyAIS(9)   -- DLI Busied out sending AIS
           }
           ACCESS read-only
           STATUS mandatory
           DESCRIPTION
                "SDLI card port current device state."
           ::= { nvSDLIEntry 5 }

        nvSDLIRedcnts OBJECT-TYPE
           SYNTAX Counter
           ACCESS read-only
           STATUS mandatory
           DESCRIPTION
                "SDLI card port red alarm count."
           ::= { nvSDLIEntry 6 }

        nvSDLIYelcnts OBJECT-TYPE
           SYNTAX Counter
           ACCESS read-only
           STATUS mandatory
           DESCRIPTION
                "SDLI card port yellow alarm count."
           ::= { nvSDLIEntry 7 }

        nvSDLIBlucnts OBJECT-TYPE
           SYNTAX Counter
           ACCESS read-only
           STATUS mandatory
           DESCRIPTION
                "SDLI card port blue alarm count."
           ::= { nvSDLIEntry 8 }

        nvSDLIErrcnt OBJECT-TYPE
           SYNTAX Counter
           ACCESS read-only
           STATUS mandatory
           DESCRIPTION
                "SDLI card port crc alarm count."
           ::= { nvSDLIEntry 9 }

        nvSDLITxundrun OBJECT-TYPE            --pkg 84
           SYNTAX Counter		      --AF
           ACCESS read-only		      --AF
           STATUS mandatory		      --AF
           DESCRIPTION			      --AF
                "TX underrun count."          --pkg 84
           ::= { nvSDLIEntry 10 }             --AF 

        nvSDLIRxfrmslp OBJECT-TYPE            --AF
           SYNTAX Counter		      --AF
           ACCESS read-only		      --AF
           STATUS mandatory		      --AF
           DESCRIPTION			      --AF
                "RX Slip count."              --AF
           ::= { nvSDLIEntry 11 }             --AF 

	nvSDLIDtreset OBJECT-TYPE
	   SYNTAX   DisplayString (SIZE (0..20))
	   ACCESS   read-only
	   STATUS   mandatory
	   DESCRIPTION
		"date & time statistics last reset"
	   ::= { nvSDLIEntry 12 }

-- Usage group configuration table

        nvUgconf OBJECT IDENTIFIER ::= { nevadaSystem 20 }

        nvUgconfMaxRec OBJECT-TYPE
           SYNTAX   INTEGER
           ACCESS   read-only
           STATUS   mandatory
           DESCRIPTION
                "total number of records allowed in database file."
           ::= {nvUgconf 1}

        nvUgconfNumRec OBJECT-TYPE
           SYNTAX   INTEGER
           ACCESS   read-only
           STATUS   mandatory
           DESCRIPTION
                "number of records in use."
           ::= {nvUgconf 2}

        nvUgconfTable OBJECT-TYPE
           SYNTAX SEQUENCE OF NvUgconfEntry
           ACCESS not-accessible
           STATUS mandatory
           DESCRIPTION
                " Device usage group configuration table."
           ::= { nvUgconf 3 }

        nvUgconfEntry OBJECT-TYPE
           SYNTAX NvUgconfEntry
           ACCESS not-accessible
           STATUS mandatory
           DESCRIPTION
                "Device usage group configuration record."
           INDEX { nvUgconfIndex }
           ::= { nvUgconfTable 1 }

        NvUgconfEntry ::=
           SEQUENCE {
                nvUgconfIndex
                        INTEGER,
                nvUgconfName
                        DisplayString,
                nvUgconfPool
                        DisplayString,
                nvUgconfNumrsrvd
                        INTEGER,
                nvUgconfThreshld
                        INTEGER,
                nvUgconfMaxbw
                        INTEGER,
                nvUgconfStatus
                        INTEGER
           }

        nvUgconfIndex OBJECT-TYPE
           SYNTAX INTEGER
           ACCESS read-only
           STATUS mandatory
           DESCRIPTION
                "Usage group entry index number."
           ::= { nvUgconfEntry 1 }

        -- 2 is reserved

        -- 3 is reserved

        -- 4 is reserved

        nvUgconfName OBJECT-TYPE
           SYNTAX DisplayString (SIZE(0..10))
           ACCESS read-write
           STATUS mandatory
           DESCRIPTION
                "Usage group entry name."
           ::= { nvUgconfEntry 5 }

        -- 6 is reserved

        -- 7 is reserved

        nvUgconfPool OBJECT-TYPE
           SYNTAX DisplayString (SIZE(0..10))
           ACCESS read-write
           STATUS mandatory
           DESCRIPTION
                "Usage group entry resource pool name."
           ::= { nvUgconfEntry 8 }

        -- 9 is reserved

        -- 10 is reserved

        nvUgconfNumrsrvd OBJECT-TYPE
           SYNTAX INTEGER
           ACCESS read-write
           STATUS mandatory
           DESCRIPTION
                "Number of devices reserved for this entry."
           ::= { nvUgconfEntry 11 }

        -- 12 is reserved

        -- 13 is reserved

        nvUgconfThreshld OBJECT-TYPE
           SYNTAX INTEGER
           ACCESS read-write
           STATUS mandatory
           DESCRIPTION
                "Allocation of disallowance thrreshold for this entry."
           ::= { nvUgconfEntry 14 }

        -- 15 is reserved

        -- 16 is reserved

        nvUgconfMaxbw OBJECT-TYPE
           SYNTAX INTEGER
           ACCESS read-write
           STATUS mandatory
           DESCRIPTION
                "Maximum bandwidth allocated to this entry."
           ::= { nvUgconfEntry 17 }

        -- 18 is reserved

        -- 19 is reserved

        nvUgconfStatus OBJECT-TYPE
           SYNTAX   INTEGER {
                        valid(1),
                        invalid(2)
                        }
           ACCESS   read-write
           STATUS   mandatory
           DESCRIPTION
           "Operation status. Add the record to the table (valid) or
           delete the record from the table (invalid)."
           ::= { nvUgconfEntry 20 }

-- Usage group configuration table

        nvUgstat OBJECT IDENTIFIER ::= { nevadaSystem 21 }

        nvUgstatMaxRec OBJECT-TYPE
           SYNTAX   INTEGER
           ACCESS   read-only
           STATUS   mandatory
           DESCRIPTION
                "total number of records allowed in database file."
           ::= {nvUgstat 1}

        nvUgstatNumRec OBJECT-TYPE
           SYNTAX   INTEGER
           ACCESS   read-only
           STATUS   mandatory
           DESCRIPTION
                "number of records in use."
           ::= {nvUgstat 2}

        nvUgstatTable OBJECT-TYPE
           SYNTAX SEQUENCE OF NvUgstatEntry
           ACCESS not-accessible
           STATUS mandatory
           DESCRIPTION
                " Device usage group statistics table."
           ::= { nvUgstat 3 }

        nvUgstatEntry OBJECT-TYPE
           SYNTAX NvUgstatEntry
           ACCESS not-accessible
           STATUS mandatory
           DESCRIPTION
                "Device usage group statistics record."
           INDEX { nvUgstatIndex }
           ::= { nvUgstatTable 1 }

        NvUgstatEntry ::=
           SEQUENCE {
                nvUgstatIndex
                        INTEGER,
                nvUgstatName
                        DisplayString,
                nvUgstatPool
                        DisplayString,
                nvUgstatNumused
                        INTEGER,
                nvUgstatBwused
                        INTEGER,
                nvUgstatBwrejs
                        Counter,
                nvUgstatUnavrejs
                        Counter,
                nvUgstatThresrejs
                        Counter,
		nvUgstatDtreset
			DisplayString
           }

        nvUgstatIndex OBJECT-TYPE
           SYNTAX INTEGER
           ACCESS read-only
           STATUS mandatory
           DESCRIPTION
                "Usage group statistics entry index number."
           ::= { nvUgstatEntry 1 }

        nvUgstatName OBJECT-TYPE
           SYNTAX DisplayString (SIZE(0..10))
           ACCESS read-only
           STATUS mandatory
           DESCRIPTION
                "Usage group statistics entry name."
           ::= { nvUgstatEntry 2 }

        nvUgstatPool OBJECT-TYPE
           SYNTAX DisplayString (SIZE(0..10))
           ACCESS read-only
           STATUS mandatory
           DESCRIPTION
                "Usage group statistics entry resource pool name."
           ::= { nvUgstatEntry 3 }

        nvUgstatNumused OBJECT-TYPE
           SYNTAX INTEGER
           ACCESS read-only
           STATUS mandatory
           DESCRIPTION
                "Number of devices allocated to this group."
           ::= { nvUgstatEntry 4 }

        nvUgstatBwused OBJECT-TYPE
           SYNTAX INTEGER
           ACCESS read-only
           STATUS mandatory
           DESCRIPTION
                "Amount of bandwidth allocated to this group."
           ::= { nvUgstatEntry 5 }

        nvUgstatBwrejs OBJECT-TYPE
           SYNTAX Counter
           ACCESS read-only
           STATUS mandatory
           DESCRIPTION
                "Rejections to this group due to bandwidth restrain."
           ::= { nvUgstatEntry 6 }

        nvUgstatUnavrejs OBJECT-TYPE
           SYNTAX Counter
           ACCESS read-only
           STATUS mandatory
           DESCRIPTION
                "Rejections to this group due to device unavailability."
           ::= { nvUgstatEntry 7 }

        nvUgstatThresrejs OBJECT-TYPE
           SYNTAX Counter
           ACCESS read-only
           STATUS mandatory
           DESCRIPTION
                "Rejections to this group due to threshold restriction."
           ::= { nvUgstatEntry 8 }

	nvUgstatDtreset OBJECT-TYPE
	   SYNTAX   DisplayString (SIZE (0..20))
	   ACCESS   read-only
	   STATUS   mandatory
	   DESCRIPTION
		"date & time statistics last reset"
	   ::= { nvUgstatEntry 9 }

-- Device pool registry statistics table

        nvDrstat OBJECT IDENTIFIER ::= { nevadaSystem 22 }

        nvDrstatMaxRec OBJECT-TYPE
           SYNTAX   INTEGER
           ACCESS   read-only
           STATUS   mandatory
           DESCRIPTION
                "total number of records allowed in database file."
           ::= {nvDrstat 1}

        nvDrstatNumRec OBJECT-TYPE
           SYNTAX   INTEGER
           ACCESS   read-only
           STATUS   mandatory
           DESCRIPTION
                "number of records in use."
           ::= {nvDrstat 2}

        nvDrstatTable OBJECT-TYPE
           SYNTAX SEQUENCE OF NvDrstatEntry
           ACCESS not-accessible
           STATUS mandatory
           DESCRIPTION
                " Device pool registry statistics."
           ::= { nvDrstat 3 }

        nvDrstatEntry OBJECT-TYPE
           SYNTAX NvDrstatEntry
           ACCESS not-accessible
           STATUS mandatory
           DESCRIPTION
                "Device pool registry statistics record."
           INDEX { nvDrstatIndex }
           ::= { nvDrstatTable 1 }

        NvDrstatEntry ::=
           SEQUENCE {
                nvDrstatIndex
                        INTEGER,
                nvDrstatName
                        DisplayString,
                nvDrstatClass
                        INTEGER,
                nvDrstatNumdev
                        INTEGER,
                nvDrstatNumrsrvd
                        INTEGER,
                nvDrstatNumavail
                        INTEGER,
                nvDrstatNumused
                        INTEGER,
                nvDrstatMaxused
                        INTEGER,
		nvDrstatDtreset
			DisplayString
           }

        nvDrstatIndex OBJECT-TYPE
           SYNTAX INTEGER
           ACCESS read-only
           STATUS mandatory
           DESCRIPTION
                "Device pool registry statistics entry index number."
           ::= { nvDrstatEntry 1 }

        nvDrstatName OBJECT-TYPE
           SYNTAX DisplayString (SIZE(0..10))
           ACCESS read-only
           STATUS mandatory
           DESCRIPTION
                "Device pool registry statistics entry name."
           ::= { nvDrstatEntry 2 }

        nvDrstatClass OBJECT-TYPE
           SYNTAX INTEGER {
                port(1),
                dsp(2)
           }
           ACCESS read-only
           STATUS mandatory
           DESCRIPTION
                "Device class of this pool."
           ::= { nvDrstatEntry 3 }

        nvDrstatNumdev OBJECT-TYPE
           SYNTAX INTEGER
           ACCESS read-only
           STATUS mandatory
           DESCRIPTION
                "Number of devices registered to this pool."
           ::= { nvDrstatEntry 4 }

        nvDrstatNumrsrvd OBJECT-TYPE
           SYNTAX INTEGER
           ACCESS read-only
           STATUS mandatory
           DESCRIPTION
                "Number of devices reserved to this pool."
           ::= { nvDrstatEntry 5 }

        nvDrstatNumavail OBJECT-TYPE
           SYNTAX INTEGER
           ACCESS read-only
           STATUS mandatory
           DESCRIPTION
                "Number of devices available for allocation."
           ::= { nvDrstatEntry 6 }

        nvDrstatNumused OBJECT-TYPE
           SYNTAX INTEGER
           ACCESS read-only
           STATUS mandatory
           DESCRIPTION
                "Number of devices presently allocated for use."
           ::= { nvDrstatEntry 7 }

        nvDrstatMaxused OBJECT-TYPE
           SYNTAX INTEGER
           ACCESS read-only
           STATUS mandatory
           DESCRIPTION
                "Maximum number of numused since last box reset."
           ::= { nvDrstatEntry 8 }

	nvDrstatDtreset OBJECT-TYPE
	   SYNTAX   DisplayString (SIZE (0..20))
	   ACCESS   read-only
	   STATUS   mandatory
	   DESCRIPTION
                 "date & time statistics last reset"
           ::= { nvDrstatEntry 9 }


-- Framer card configuration table definition

        nvCFRMRTable OBJECT-TYPE
           SYNTAX SEQUENCE OF NvCFRMREntry
           ACCESS not-accessible
           STATUS mandatory
           DESCRIPTION
                "Framer card configuration table definition. The actual
                framer card database has 17 tables. Each table uses name
                convention: CFRMR plus slot number. Each framer card has
                two static WAN ports and 128 smart ports. This table will
                combine 17 databases into one table. In order to support
                the actual framer card configuration, this table requires
                two instances: slot and port number."
           ::= { nevadaSystem 23 }

        nvCFRMREntry OBJECT-TYPE
           SYNTAX NvCFRMREntry
           ACCESS not-accessible
           STATUS mandatory
           DESCRIPTION
                "Framer card configuration record definition. The total
                record number is 17. If there is a framer card plugged in
                one of the slot, then the corresponding framer record is
                active. Otherwise the record is not active."
           INDEX { nvCFRMRSlotIndex,nvCFRMRPortIndex }
           ::= { nvCFRMRTable 1 }

        NvCFRMREntry ::=
           SEQUENCE {
                nvCFRMRSlotIndex
                        INTEGER,
                nvCFRMRPortIndex
                        INTEGER,
                nvCFRMRName
                        DisplayString, 
                nvCFRMRRate
                        INTEGER,
                nvCFRMREIAtype
                        INTEGER,
                nvCFRMRClkmode
                        INTEGER,
                nvCFRMRDebounce
                        INTEGER,
                nvCFRMREnable
                        INTEGER
           }

        nvCFRMRSlotIndex OBJECT-TYPE
           SYNTAX INTEGER
           ACCESS read-only
           STATUS mandatory
           DESCRIPTION
                "Framer card slot number."
           ::= { nvCFRMREntry 1 }

        nvCFRMRPortIndex OBJECT-TYPE
           SYNTAX INTEGER
           ACCESS read-only
           STATUS mandatory
           DESCRIPTION
                "For static port, the index number is from 1 to 2.
                For smart port type, the index number is from 3 to 130."
           ::= { nvCFRMREntry 2 }

        nvCFRMRName OBJECT-TYPE
           SYNTAX DisplayString (SIZE(0..10))
           ACCESS read-only
           STATUS mandatory
           DESCRIPTION
                "The name of a framer card port."
           ::= { nvCFRMREntry 3 }

        -- 4 is reserved

        -- 5 is reserved

        -- 6 is reserved

        nvCFRMRRate OBJECT-TYPE
           SYNTAX INTEGER {
                undef(1),   -- undefined so far (+1)
                v64K(2),     -- 64 Kbps
                v128K(3),    -- 128 Kbps
                v192K(4),    -- 192 Kbps
                v256K(5),    -- 256 Kbps
                v320K(6),    -- 192 Kbps
                v384K(7),    -- 192 Kbps
                v448K(8),    -- 192 Kbps
                v512K(9),    -- 512 Kbps
                v576K(10),   -- 192 Kbps
                v640K(11),   -- 512 Kbps
                v704K(12),   -- 192 Kbps
                v768K(13),   -- 512 Kbps
                v832K(14),   -- 192 Kbps
                v896K(15),   -- 512 Kbps
                v960K(16),   -- 192 Kbps
                v1024K(17),  -- 512 Kbps
                v1088K(18),  -- 512 Kbps
                v1152K(19),  -- 512 Kbps
                v1216K(20),  -- 512 Kbps
                v1280K(21),  -- 512 Kbps
                v1344K(22),  -- 512 Kbps
                v1408K(23),  -- 512 Kbps
                v1472K(24),  -- 512 Kbps
                v1536K(25),  -- 512 Kbps
                v1600K(26),  -- 512 Kbps
                v1664K(27),  -- 512 Kbps
                v1728K(28),  -- 512 Kbps
                v1792K(29),  -- 512 Kbps
                v1856K(30),  -- 512 Kbps
                v1920K(31),  -- 512 Kbps
                v1984K(32),  -- 512 Kbps
                v2048K(33)   -- 2048 Kbps
           }
           ACCESS read-write
           STATUS mandatory
           DESCRIPTION
                "Framer card port baud rate."
           ::= { nvCFRMREntry 7 }

        -- 8 is reserved

        -- 9 is reserved

        nvCFRMREIAtype OBJECT-TYPE
           SYNTAX INTEGER {
                v3wire(1),   -- 3-wire EIA (+1)
                vx21bis(2)   -- X21bis EIA
           }
           ACCESS read-write
           STATUS mandatory
           DESCRIPTION
                "Port interface type."
           ::= { nvCFRMREntry 10 }

        -- 11 is reserved

        -- 12 is reserved

        nvCFRMRClkmode OBJECT-TYPE
           SYNTAX INTEGER {
                insync(1),   -- Nevada provides clock (+1)
                exsync(2)    -- Attached device provides clock
           }
           ACCESS read-write
           STATUS mandatory
           DESCRIPTION
                "Port clock mode."
           ::= { nvCFRMREntry 13 }

        -- 14 is reserved

        -- 15 is reserved

        nvCFRMRDebounce OBJECT-TYPE
           SYNTAX INTEGER (1..255)
           ACCESS read-write
           STATUS mandatory
           DESCRIPTION
                "WAN port eia debounce interval."
           ::= { nvCFRMREntry 16 }

        -- 17 is reserved

        -- 18 is reserved


        nvCFRMREnable OBJECT-TYPE
           SYNTAX INTEGER {
                no(1),    -- (+1)
                yes(2)    --
           }
           ACCESS read-write
           STATUS mandatory
           DESCRIPTION
                "Enable or disable port."
           ::= { nvCFRMREntry 19 }

        -- 20 is reserved

        -- 21 is reserved

-- Framer card statistics table definition

        nvSFRMRTable OBJECT-TYPE
           SYNTAX SEQUENCE OF NvSFRMREntry
           ACCESS not-accessible
           STATUS mandatory
           DESCRIPTION
                "Framer card statistics table definition. The actual
                framer card database has 17 tables. Each table uses name
                convention: SFRMR plus slot number. Each framer card has
                two static WAN ports and 128 smart ports. This table will
                combine 17 databases into one table. In order to support
                the actual framer card configuration, this table requires
                two instances: slot and port number."
           ::= { nevadaSystem 24 }

        nvSFRMREntry OBJECT-TYPE
           SYNTAX NvSFRMREntry
           ACCESS not-accessible
           STATUS mandatory
           DESCRIPTION
                "Framer card statistics record definition. The total
                record number is 17. If there is a framer card plugged in
                one of the slot, then the corresponding framer record is
                active. Otherwise the record is not active."
           INDEX { nvSFRMRSlotIndex,nvSFRMRPortIndex }
           ::= { nvSFRMRTable 1 }

        NvSFRMREntry ::=
           SEQUENCE {
                nvSFRMRSlotIndex
                        INTEGER,
                nvSFRMRPortIndex
                        INTEGER,
                nvSFRMRName
                        DisplayString,
                nvSFRMRMode
                        INTEGER,
                nvSFRMRState
                        INTEGER,
                nvSFRMRRate
                        INTEGER,
                nvSFRMRCid
                        DisplayString,



                nvSFRMRRxoff
                        INTEGER,
                nvSFRMRTxoff
                        INTEGER,
                nvSFRMRNrxoff
                        INTEGER,
                nvSFRMRNtxoff
                        INTEGER,

                nvSFRMRLostfrms
                        Counter,

                nvSFRMRFerrs
                        INTEGER,
                nvSFRMRPerrs
                        INTEGER,


                nvSFRMRRxovrs
                        Counter,
                nvSFRMRCrcerrs
                        Counter,
                nvSFRMRRxaborts
                        Counter,
		nvSFRMRDtreset
			DisplayString
           }

        nvSFRMRSlotIndex OBJECT-TYPE
           SYNTAX INTEGER
           ACCESS read-only
           STATUS mandatory
           DESCRIPTION
                "Framer card slot number."
           ::= { nvSFRMREntry 1 }

        nvSFRMRPortIndex OBJECT-TYPE
           SYNTAX INTEGER
           ACCESS read-only
           STATUS mandatory
           DESCRIPTION
                "For static port, the index number is from 1 to 2.
                For smart port type, the index number is from 3 to 130."
           ::= { nvSFRMREntry 2 }

        nvSFRMRName OBJECT-TYPE
           SYNTAX DisplayString (SIZE(0..10))
           ACCESS read-only
           STATUS mandatory
           DESCRIPTION
                "The name of a framer card port."
           ::= { nvSFRMREntry 3 }

        nvSFRMRMode OBJECT-TYPE
           SYNTAX INTEGER {
                absent(1),     -- hardwwre not present in box  (+1)
                dead(2),       -- out of service
                broken(3),     -- broken
                async(4),      -- asynchronous mode
                sync(5)        -- synchronous mode
           }
           ACCESS read-only
           STATUS mandatory
           DESCRIPTION
                "The operation mode."
           ::= { nvSFRMREntry 4 }

        nvSFRMRState OBJECT-TYPE
           SYNTAX INTEGER {
                free(1),    -- not claimed (+1)
                down(2),    -- not operating
                setup(3),   -- waiting for modem signal
                up(4),      -- operating
                test(5)     -- loop test being performed
           }
           ACCESS read-only
           STATUS mandatory
           DESCRIPTION
                "The operation state."
           ::= { nvSFRMREntry 5 }

        nvSFRMRRate OBJECT-TYPE
           SYNTAX INTEGER {
                undef(1),   -- undefined so far (+1)
                v64K(2),     -- 64 Kbps
                v128K(3),    -- 128 Kbps
                v192K(4),    -- 192 Kbps
                v256K(5),    -- 256 Kbps
                v320K(6),    -- 192 Kbps
                v384K(7),    -- 192 Kbps
                v448K(8),    -- 192 Kbps
                v512K(9),    -- 512 Kbps
                v576K(10),   -- 192 Kbps
                v640K(11),   -- 512 Kbps
                v704K(12),   -- 192 Kbps
                v768K(13),   -- 512 Kbps
                v832K(14),   -- 192 Kbps
                v896K(15),   -- 512 Kbps
                v960K(16),   -- 192 Kbps
                v1024K(17),  -- 512 Kbps
                v1088K(18),  -- 512 Kbps
                v1152K(19),  -- 512 Kbps
                v1216K(20),  -- 512 Kbps
                v1280K(21),  -- 512 Kbps
                v1344K(22),  -- 512 Kbps
                v1408K(23),  -- 512 Kbps
                v1472K(24),  -- 512 Kbps
                v1536K(25),  -- 512 Kbps
                v1600K(26),  -- 512 Kbps
                v1664K(27),  -- 512 Kbps
                v1728K(28),  -- 512 Kbps
                v1792K(29),  -- 512 Kbps
                v1856K(30),  -- 512 Kbps
                v1920K(31),  -- 512 Kbps
                v1984K(32),  -- 512 Kbps
                v2048K(33)   -- 2048 Kbps
           }
           ACCESS read-only
           STATUS mandatory
           DESCRIPTION
                "Framer card port baud rate."
           ::= { nvSFRMREntry 6 }

        nvSFRMRCid OBJECT-TYPE
           SYNTAX DisplayString
           ACCESS read-only
           STATUS mandatory
           DESCRIPTION
                "Circuit ID of Munich ports."
           ::= { nvSFRMREntry 7 }

        nvSFRMRRxoff OBJECT-TYPE
           SYNTAX INTEGER
           ACCESS read-only
           STATUS mandatory
           DESCRIPTION
                "RXOFF"
           ::= { nvSFRMREntry 8 }

        nvSFRMRTxoff OBJECT-TYPE
           SYNTAX INTEGER
           ACCESS read-only
           STATUS mandatory
           DESCRIPTION
                "TXOFF"
           ::= { nvSFRMREntry 9 }

        nvSFRMRNrxoff OBJECT-TYPE
           SYNTAX INTEGER
           ACCESS read-only
           STATUS mandatory
           DESCRIPTION
                "RNRXOFF"
           ::= { nvSFRMREntry 10 }

        nvSFRMRNtxoff OBJECT-TYPE
           SYNTAX INTEGER
           ACCESS read-only
           STATUS mandatory
           DESCRIPTION
                "RNTXOFF"
           ::= { nvSFRMREntry 11 }

        nvSFRMRLostfrms OBJECT-TYPE
           SYNTAX Counter
           ACCESS read-only
           STATUS mandatory
           DESCRIPTION
                "Number of lost frames."
           ::= { nvSFRMREntry 12 }

        nvSFRMRFerrs OBJECT-TYPE
           SYNTAX INTEGER
           ACCESS read-only
           STATUS mandatory
           DESCRIPTION
                "FERRS"
           ::= { nvSFRMREntry 13 }

        nvSFRMRPerrs OBJECT-TYPE
           SYNTAX INTEGER
           ACCESS read-only
           STATUS mandatory
           DESCRIPTION
                "PERRS"
           ::= { nvSFRMREntry 14 }

        nvSFRMRRxovrs OBJECT-TYPE
           SYNTAX Counter
           ACCESS read-only
           STATUS mandatory
           DESCRIPTION
                "Number of receive overruns frames."
           ::= { nvSFRMREntry 15 }

        nvSFRMRCrcerrs OBJECT-TYPE
           SYNTAX Counter
           ACCESS read-only
           STATUS mandatory
           DESCRIPTION
                "Number of CRC errors."
           ::= { nvSFRMREntry 16 }

        nvSFRMRRxaborts OBJECT-TYPE
           SYNTAX Counter
           ACCESS read-only
           STATUS mandatory
           DESCRIPTION
                "Number of receive aborte frames."
           ::= { nvSFRMREntry 17 }

	nvSFRMRDtreset OBJECT-TYPE
	   SYNTAX   DisplayString (SIZE (0..20))
	   ACCESS   read-only
	   STATUS   mandatory
	   DESCRIPTION
		"date & time statistics last reset"
	   ::= { nvSFRMREntry 18 }

--
-- slot statistics table definition
--
        nvSlotstat OBJECT IDENTIFIER ::= { nevadaSystem 25 }

        nvSlotstatMaxRec OBJECT-TYPE
           SYNTAX   INTEGER
           ACCESS   read-only
           STATUS   mandatory
           DESCRIPTION
                "total number of records allowed in database file."
           ::= {nvSlotstat 1}

        nvSlotstatNumRec OBJECT-TYPE
           SYNTAX   INTEGER
           ACCESS   read-only
           STATUS   mandatory
           DESCRIPTION
                "number of records in use."
           ::= {nvSlotstat 2}

        nvSlotstatTable OBJECT-TYPE
           SYNTAX SEQUENCE OF NvSlotstatEntry
           ACCESS not-accessible
           STATUS mandatory
           DESCRIPTION
                "Slot statistics table definition."
           ::= { nvSlotstat 3 }

        nvSlotstatEntry OBJECT-TYPE
           SYNTAX NvSlotstatEntry
           ACCESS not-accessible
           STATUS mandatory
           DESCRIPTION
                "Nevada product is a 17 slot chassis. Each slot can be
                plugged in a communication card module. The module can
                be a Host Packet, Framer or DLI card module. The system
                can have only one Host Module and up to two Framer card
                module. This table contains statistics information for
                each slot."
           INDEX { nvSlotstatIndex }
           ::= { nvSlotstatTable 1 }

        NvSlotstatEntry ::=
           SEQUENCE {
                nvSlotstatIndex
                        INTEGER,
                nvSlotstatName
                        DisplayString,
                nvSlotstatCardType
                        INTEGER,
                nvSlotstatIotype
                        INTEGER,
                nvSlotstatCpu
                        INTEGER,
                nvSlotstatRam
                        DisplayString,
                nvSlotstatStatus
                        DisplayString,
		nvSlotstatCardid
			DisplayString,
		nvSlotstatHwRevision
			DisplayString,
		nvSlotstatCatPartnum
			DisplayString,
		nvSlotstatSrNumber
			DisplayString,
		nvSlotstatProdChkDate
			DisplayString
           }

        nvSlotstatIndex OBJECT-TYPE
           SYNTAX INTEGER (1..17)
           ACCESS read-only
           STATUS mandatory
           DESCRIPTION
                "Slot index number."
           ::= { nvSlotstatEntry 1 }

        nvSlotstatName OBJECT-TYPE
           SYNTAX DisplayString (SIZE(0..7))
           ACCESS read-only
           STATUS mandatory
           DESCRIPTION
                "Slot name."
           ::= { nvSlotstatEntry 2 }

        nvSlotstatCardType OBJECT-TYPE
           SYNTAX INTEGER {
                empty    (1),   -- empty  (+1)
                dliE1    (2),   -- Digital Line Interface card
                dliT1    (3),   -- Digital Line Interface card
                framer   (4),  -- FRAMER card
                dsp      (5),     -- Digital Signal Processor Card
                phost    (6),   -- Packet Host
                qpsPower (7), -- Power Supply
		framer2  (8),  -- FRAMER card type II
                qDE1     (9),   -- DLI, access bus compatible
                qDT1     (10),  -- DLI card, access bus compatible
                oDLI     (11),  -- ODLI T1 (CSU), access bus compatible
                fRMR     (12),  -- Framer1++ card, access bus compatible
                ps       (13),  -- Power Supply, access bus compatible
		none     (51),  --  no i/o card
                pHOSTIO  (52),  --  standard p1acket host i/o card
                fRMRIO   (53),  --  standard framer card i/o card
                e1IO     (55),  -- standard qdli-e1 i/o card
                t1IO     (56),  -- standard qdli-t1 i/o card
                pOWERIO  (57),  -- power entry module i/o card
                v11EXT   (58),  -- V11 EXT  type framer I/O card
                v11INT   (59),  -- V11 INT type framer I/O card
                v35      (60),  -- V35 type framer I/O card
                v24V35   (61),  -- V24V35 type framer I/O card
                v24      (62),  -- V24 type framer I/O card
                qDE1IO   (63),  -- QDLI E1 type I/O card
                qDT1IO   (64),  -- QDLI T1 type I/O card
                oDIO     (65),  -- ODLI T1 (CSU) type I/O card
                pEM      (66),  -- POWER ENTRY MODULE
                pHIOM    (67)   -- PH/CPUM I/O
           }
           ACCESS read-only
           STATUS mandatory
           DESCRIPTION
                "Slot card type."
           ::= { nvSlotstatEntry 3 }

        nvSlotstatIotype OBJECT-TYPE
           SYNTAX INTEGER {
		empty    (1),    -- empty
                none    (51),    -- no i/o card (+1)
                phostIo (52),    -- standard packet host i/o card
                frmrIo  (53),    -- standard framer card i/o card
                e1Io    (54),    -- standard qdli-e1 i/o card
                t1Io    (56),    -- standard qdli-t1 i/o card
                powerIo (57),    -- Power Supply
                v11ext  (58),    -- V11 EXT  type framer I/O card
                v11int  (59),    -- V11 INT type framer I/O card
                v35     (60),    -- V35 type framer I/O card
                v24v35  (61),    -- V24V35 type framer I/O card
                v24     (62),    -- V24 type framer I/O card
                qDE1IO  (63),    -- QDLI E1 type I/O card
                qDT1IO  (64),    -- QDLI T1 type I/O card
                oDIO    (65),    -- ODLI T1 (CSU) type I/O card
                pEM     (66),    -- POWER ENTRY MODULE
                pHIOM   (67)     -- PH/CPUM I/O
           }
           ACCESS read-only
           STATUS mandatory
           DESCRIPTION
                "Slot IO type."
           ::= { nvSlotstatEntry 4 }

        nvSlotstatCpu OBJECT-TYPE
           SYNTAX INTEGER {
                notapp(1),   -- not applicable to this type of card  (+1)
                p5-100(2),   -- standard cpu for packet host
                i960JF(3),   -- standard cpu for framer card
                adsp2181(4)  -- standard cpu for DLI card
           }
           ACCESS read-only
           STATUS mandatory
           DESCRIPTION
                "Slot IO type."
           ::= { nvSlotstatEntry 5 }

        -- 6 is reserved

        nvSlotstatRam OBJECT-TYPE
           SYNTAX DisplayString (SIZE(0..8))
           ACCESS read-only
           STATUS mandatory
           DESCRIPTION
                "Amount of RAM on card."
           ::= { nvSlotstatEntry 6 }

        nvSlotstatStatus OBJECT-TYPE
           SYNTAX INTEGER {
                good(1),         -- Card is working
                failure(2),      -- Card is failing
                notPowered(3),   -- Power Supply -48 volts not supplied
                notapplicable(4) -- not applicable, status only pertains to power supply and Framer
                          }
           ACCESS read-only
           STATUS mandatory
           DESCRIPTION
                "Status of card as given by bats.
		good(1),         -- Card is working
                failure(2),      -- Card is failing
                notPowered(3),   -- Power Supply -48 volts not supplied
                notapplicable(4) -- not applicable
                "
           ::= { nvSlotstatEntry 7 }

        nvSlotstatCardid OBJECT-TYPE
           SYNTAX DisplayString (SIZE(0..12))
           ACCESS read-only
           STATUS mandatory
           DESCRIPTION
                "Card id from eeprom."
           ::= { nvSlotstatEntry 8 }

        nvSlotstatHwRevision OBJECT-TYPE
           SYNTAX DisplayString (SIZE(0..4))
           ACCESS read-only
           STATUS mandatory
           DESCRIPTION
                "Hardware Revision of the board."
           ::= { nvSlotstatEntry 9 }

        nvSlotstatCatPartnum OBJECT-TYPE
           SYNTAX DisplayString (SIZE(0..16))
           ACCESS read-only
           STATUS mandatory
           DESCRIPTION
                "Catalog part number."
           ::= { nvSlotstatEntry 10 }

        nvSlotstatSrNumber OBJECT-TYPE
           SYNTAX DisplayString (SIZE(0..11))
           ACCESS read-only
           STATUS mandatory
           DESCRIPTION
                "Serial Number."
           ::= { nvSlotstatEntry 11 }

        nvSlotstatProdChkDate OBJECT-TYPE
           SYNTAX DisplayString (SIZE(0..11))
           ACCESS read-only
           STATUS mandatory
           DESCRIPTION
                "Production Check Date."
           ::= { nvSlotstatEntry 12 }

--
-- DSP configuration table definition
--
        nvCDSPTable OBJECT-TYPE
           SYNTAX SEQUENCE OF NvCDSPEntry
           ACCESS not-accessible
           STATUS mandatory
           DESCRIPTION
                "DSP configuration table definition.The actual database
                contains 17 tables, if a DSP card is plugged in
                one of the slot then the data table matched the
                slot will become active, otherwise the record is
                not active. This table combines 17 tables into one
                MIB table which uses two table instances: slot
                and port."
           ::= { nevadaSystem 26 }

        nvCDSPEntry OBJECT-TYPE
           SYNTAX NvCDSPEntry
           ACCESS not-accessible
           STATUS mandatory
           DESCRIPTION
                "DLI configuration record."
           INDEX { nvCDSPSlotIndex,nvCDSPPortIndex }
           ::= { nvCDSPTable 1 }

        NvCDSPEntry ::=
           SEQUENCE {
                nvCDSPSlotIndex
                        INTEGER,
                nvCDSPPortIndex
                        INTEGER,
                nvCDSPName
                        DisplayString,
                nvCDSPEnable
                        INTEGER,
                nvCDSPNumfaicon
                        INTEGER,
                nvCDSPNumload
                        INTEGER

           }

        nvCDSPSlotIndex OBJECT-TYPE
           SYNTAX INTEGER (1..17)
           ACCESS read-only
           STATUS mandatory
           DESCRIPTION
                "CDSP slot number."
           ::= { nvCDSPEntry 1 }

        nvCDSPPortIndex OBJECT-TYPE
           SYNTAX INTEGER
           ACCESS read-only
           STATUS mandatory
           DESCRIPTION
                "CDSP port number."
           ::= { nvCDSPEntry 2 }

        nvCDSPName OBJECT-TYPE
           SYNTAX DisplayString (SIZE(0..10))
           ACCESS read-only
           STATUS mandatory
           DESCRIPTION
                "CDSP port name."
           ::= { nvCDSPEntry 3 }

        -- 4 is reserved

        -- 5 is reserved

        -- 6 is reserved

        -- 7 is reserved

        nvCDSPEnable OBJECT-TYPE
           SYNTAX INTEGER {
                yes(2),     -- enabled  (+1)
                slowno(3),  -- disabled gracefully
                fastno(4)   -- disabled fast
           }
           ACCESS read-write
           STATUS mandatory
           DESCRIPTION
                "CDSP port enable control."
           ::= { nvCDSPEntry 8 }

        nvCDSPNumfaicon OBJECT-TYPE
           SYNTAX INTEGER
           ACCESS read-write
           STATUS mandatory
           DESCRIPTION
                "CDSP num of consecutive hand shakes failed."
           ::= { nvCDSPEntry 9 }

        nvCDSPNumload OBJECT-TYPE
           SYNTAX INTEGER
           ACCESS read-write
           STATUS mandatory
           DESCRIPTION
                "CDSP num of times redownload failed."
           ::= { nvCDSPEntry 10 }

        -- 11 is reserved

        -- 12 is reserved

-- DSP statistics table definition

        nvSDSPTable OBJECT-TYPE
           SYNTAX SEQUENCE OF NvSDSPEntry
           ACCESS not-accessible
           STATUS mandatory
           DESCRIPTION
                "DSP statistics table definition.The actual database
                contains 17 tables, if a DSP card is plugged in
                one of the slot then the data table matched the
                slot will become active, otherwise the record is
                not active. This table combines 17 tables into one
                MIB table which uses two table instances: slot
                and port."
           ::= { nevadaSystem 27 }

        nvSDSPEntry OBJECT-TYPE
           SYNTAX NvSDSPEntry
           ACCESS not-accessible
           STATUS mandatory
           DESCRIPTION
                "DLI configuration record."
           INDEX { nvSDSPSlotIndex,nvSDSPPortIndex }
           ::= { nvSDSPTable 1 }

        NvSDSPEntry ::=
           SEQUENCE {
                nvSDSPSlotIndex
                        INTEGER,
                nvSDSPPortIndex
                        INTEGER,
                nvSDSPName
                        DisplayString,
                nvSDSPState
                        INTEGER,
                nvSDSPNumfaicon
                        INTEGER,
                nvSDSPNumload
                        INTEGER,
                nvSDSPFailcaus
                        INTEGER,
      		nvSDSPNumcalls        --AF
            		Counter,		 --AF
      		nvSDSPNumfnegs        --AF
            		Counter,		 --AF
		nvSDSPDtreset
			DisplayString,
		nvSDSPNumIncom
			Counter,
		nvSDSPNumOutgo
			Counter,
		nvSDSPNumIfailneg
			Counter,
		nvSDSPNumOfailneg
			Counter,
		nvSDSPEvent1
			Counter,
		nvSDSPEvent2
			Counter,
		nvSDSPEvent3
			Counter,
		nvSDSPEvent4
			Counter,
		nvSDSPEvent5
			Counter,
		nvSDSPEvent6
			Counter,
		nvSDSPEvent7
			Counter,
		nvSDSPEvent8
			Counter,
		nvSDSPEvent9
			Counter,
		nvSDSPEvent10
			Counter,
		nvSDSPEvent11
			Counter,
		nvSDSPEvent12
			Counter
           }

        nvSDSPSlotIndex OBJECT-TYPE
           SYNTAX INTEGER (1..17)
           ACCESS read-only
           STATUS mandatory
           DESCRIPTION
                "SDSP slot number."
           ::= { nvSDSPEntry 1 }

        nvSDSPPortIndex OBJECT-TYPE
           SYNTAX INTEGER
           ACCESS read-only
           STATUS mandatory
           DESCRIPTION
                "SDSP port number."
           ::= { nvSDSPEntry 2 }

        nvSDSPName OBJECT-TYPE
           SYNTAX DisplayString (SIZE(0..10))
           ACCESS read-only
           STATUS mandatory
           DESCRIPTION
                "SDSP port name."
           ::= { nvSDSPEntry 3 }

        nvSDSPState OBJECT-TYPE
           SYNTAX INTEGER {
                idle(2),   -- DSP is ready to connect (+1)
                busy(3),   -- DSP has at least 1 active SCSA channel
                dead(4),   -- DSP marked DEAD by software
                asleep(5), -- DSP marked ASLEEP by configurator
                dwld(6)    -- DSP download not finished

           }
           ACCESS read-only
           STATUS mandatory
           DESCRIPTION
                "CDSP port state."
           ::= { nvSDSPEntry 4 }
                   nvSDSPNumfaicon OBJECT-TYPE
           SYNTAX INTEGER
           ACCESS read-only
           STATUS mandatory
           DESCRIPTION
                "number of consecutive handshake failures."
           ::= { nvSDSPEntry 5 }

        nvSDSPNumload OBJECT-TYPE
           SYNTAX INTEGER
           ACCESS read-only
           STATUS mandatory
           DESCRIPTION
                "number of redownload attempts failed."
           ::= { nvSDSPEntry 6 }

        nvSDSPFailcaus OBJECT-TYPE
           SYNTAX INTEGER {
                healthy(2),    -- DSP has not failed yet (+1)
                dwldFail(3),
		portUpFail(4),
		handshkeAbort(5),
		handshkeTimeout(6),
		llHandAbort(7),
		llHandTimeout(8),
		llHandHsAbo(9),
                cmdTimeout(10),
		monRegTimeout(11),
		clrDownTimeout(12),
		chCreErrNoReload(13),
		chCreErrReload(14),
		userDown(15),
		handModify(16),
                userReset(17),
		notUsable(18)
           }
           ACCESS read-only
           STATUS mandatory
           DESCRIPTION
                "SDSP port state."
           ::= { nvSDSPEntry 7 }

nvSDSPNumcalls OBJECT-TYPE                 --AF
     SYNTAX   INTEGER				--AF
     ACCESS   read-only				--AF
     STATUS   mandatory				--AF
     DESCRIPTION				--AF
      "Number of calls processed on this DSP."  --AF 
     ::= {nvSDSPEntry 8 }                 --AF 

nvSDSPNumfnegs OBJECT-TYPE                 --AF
     SYNTAX   INTEGER				--AF
     ACCESS   read-only				--AF
     STATUS   mandatory				--AF
     DESCRIPTION				--AF
  "Number of calls faild prior to negotiation start." --AF 
     ::= {nvSDSPEntry 9 }                 --AF 

nvSDSPDtreset OBJECT-TYPE
     SYNTAX   DisplayString (SIZE (0..20))
     ACCESS   read-only
     STATUS   mandatory
     DESCRIPTION
	"date & time statistics last reset"
     ::= { nvSDSPEntry 10 }

nvSDSPNumIncom OBJECT-TYPE
     SYNTAX   Counter
     ACCESS   read-only
     STATUS   mandatory
     DESCRIPTION
        "Total number of INcoming calls made to this DSP."
     ::= { nvSDSPEntry 11 }

nvSDSPNumOutgo OBJECT-TYPE
     SYNTAX   Counter
     ACCESS   read-only
     STATUS   mandatory
     DESCRIPTION
        "Total number of OUTgoing calls made to this DSP."
     ::= { nvSDSPEntry 12 }

nvSDSPNumIfailneg OBJECT-TYPE
     SYNTAX   Counter
     ACCESS   read-only
     STATUS   mandatory
     DESCRIPTION
        "Total number of failed negotiations INcoming."
     ::= { nvSDSPEntry 13 }

nvSDSPNumOfailneg OBJECT-TYPE
     SYNTAX   Counter
     ACCESS   read-only
     STATUS   mandatory
     DESCRIPTION
        "Total number of failed negotiations OUTgoing."
     ::= { nvSDSPEntry 14 }

nvSDSPEvent1 OBJECT-TYPE
     SYNTAX   Counter
     ACCESS   read-only
     STATUS   mandatory
     DESCRIPTION
        "DMOD- primary modem hs ended in abort condition."
     ::= { nvSDSPEntry 15 }

nvSDSPEvent2 OBJECT-TYPE 
     SYNTAX   Counter 
     ACCESS   read-only 
     STATUS   mandatory
     DESCRIPTION 
        "DMOD- primary modem hs ended in timeout condition."
     ::= { nvSDSPEntry 16 }

nvSDSPEvent3 OBJECT-TYPE 
     SYNTAX   Counter 
     ACCESS   read-only 
     STATUS   mandatory
     DESCRIPTION 
        "DMOD- Link layer modem hs ended in abort condition."
     ::= { nvSDSPEntry 17 }

nvSDSPEvent4 OBJECT-TYPE 
     SYNTAX   Counter 
     ACCESS   read-only 
     STATUS   mandatory
     DESCRIPTION 
        "DMOD- Link layer modem hs ende in timeout condition."
     ::= { nvSDSPEntry 18 }

nvSDSPEvent5 OBJECT-TYPE 
     SYNTAX   Counter 
     ACCESS   read-only 
     STATUS   mandatory
     DESCRIPTION 
        "DMOD- Link layer modem hs ended in primary hs aborted condition."
     ::= { nvSDSPEntry 19 }

nvSDSPEvent6 OBJECT-TYPE
     SYNTAX   Counter
     ACCESS   read-only 
     STATUS   mandatory
     DESCRIPTION 
        "DMOD- Command Response Timeout error."
     ::= { nvSDSPEntry 20 }

nvSDSPEvent7 OBJECT-TYPE
     SYNTAX   Counter 
     ACCESS   read-only 
     STATUS   mandatory
     DESCRIPTION 
        "DMOD- Cleardown procedure ended in timeout condition."
     ::= { nvSDSPEntry 21 }

nvSDSPEvent8 OBJECT-TYPE 
     SYNTAX   Counter 
     ACCESS   read-only 
     STATUS   mandatory
     DESCRIPTION 
        "DMOD- Moniter Register timeout error."
     ::= { nvSDSPEntry 22 }

nvSDSPEvent9 OBJECT-TYPE 
     SYNTAX   Counter 
     ACCESS   read-only 
     STATUS   mandatory
     DESCRIPTION 
        "DMOD- Port Up failure
		No SABM from DSP to start the session."
     ::= { nvSDSPEntry 23 }

nvSDSPEvent10 OBJECT-TYPE 
     SYNTAX   Counter 
     ACCESS   read-only 
     STATUS   mandatory
     DESCRIPTION 
        "DMOD- CHCRERR - with DSP Fail logic optioned."
     ::= { nvSDSPEntry 24 }

nvSDSPEvent11 OBJECT-TYPE 
     SYNTAX   Counter 
     ACCESS   read-only 
     STATUS   mandatory
     DESCRIPTION 
        "DMOD- CHCRERR - with DSP Fail logic not optioned."
     ::= { nvSDSPEntry 25 }

nvSDSPEvent12 OBJECT-TYPE 
     SYNTAX   Counter 
     ACCESS   read-only 
     STATUS   mandatory
     DESCRIPTION 
        "DMOD- modify action in SDSPx caused numfaicon
		threshold to be reached."
     ::= { nvSDSPEntry 26 }

--
--      croute file
--
        nvCroute OBJECT IDENTIFIER ::= { nevadaSystem 28 }

        nvCrouteMaxRec OBJECT-TYPE
           SYNTAX   INTEGER
           ACCESS   read-only
           STATUS   mandatory
           DESCRIPTION
                "total number of records allowed in database file."
           ::= {nvCroute 1}

        nvCrouteNumRec OBJECT-TYPE
           SYNTAX   INTEGER
           ACCESS   read-only
           STATUS   mandatory
           DESCRIPTION
                "number of records in use."
           ::= {nvCroute 2}

        nvCrouteTable OBJECT-TYPE
           SYNTAX SEQUENCE OF NvCrouteEntry
           ACCESS not-accessible
           STATUS mandatory
           DESCRIPTION
                "Circuit routing table."
           ::= { nvCroute 3 }

        nvCrouteEntry OBJECT-TYPE
           SYNTAX NvCrouteEntry
           ACCESS not-accessible
           STATUS mandatory
           DESCRIPTION
                "Circuit routing table record."
           INDEX { nvCrouteIndex }
           ::= { nvCrouteTable 1 }

        NvCrouteEntry ::=
           SEQUENCE {
                nvCrouteIndex
                        INTEGER,
                nvCrouteAddr
                        DisplayString,
                nvCrouteRouting
                        INTEGER,
                nvCrouteType
                        INTEGER,
                nvCrouteVol1prot
                        INTEGER,
                nvCrouteVol1mode
                        INTEGER,
                nvCrouteBw
                        INTEGER,
                nvCrouteRcscp1
                        DisplayString,
                nvCrouteRcscp2
                        DisplayString,
		nvCrouteDialmapid
			INTEGER,
		nvCrouteReserve1
			DisplayString,
		nvCrouteDirection
		        INTEGER,
                nvCrouteChoice
                        INTEGER,
                nvCrouteStatus
                        INTEGER
			}

        nvCrouteIndex OBJECT-TYPE
           SYNTAX INTEGER
           ACCESS read-only
           STATUS mandatory
           DESCRIPTION
                "Index of croute record."
           ::= { nvCrouteEntry 1 }

        nvCrouteAddr OBJECT-TYPE
           SYNTAX DisplayString
           ACCESS read-write
           STATUS mandatory
           DESCRIPTION
                "Address."
           ::= { nvCrouteEntry 10 }

        nvCrouteRouting OBJECT-TYPE
           SYNTAX INTEGER {
               noroute(1),     -- (+1)    
               callednum(2),   
               callngnum(3),   
               calledsub(4),   
               callngsub(5)   
           }
           ACCESS read-write
           STATUS mandatory
           DESCRIPTION
                "routing new var."
           ::= { nvCrouteEntry 11 }

        nvCrouteType OBJECT-TYPE
           SYNTAX INTEGER {
               switched(2),      -- switched circuit (+1)
               pernament(3)      -- pernament circuit
           }
           ACCESS read-write
           STATUS mandatory
           DESCRIPTION
                "circuit type."
           ::= { nvCrouteEntry 13 }

        nvCrouteVol1prot OBJECT-TYPE
           SYNTAX INTEGER {
                noprot(1),   --  no layer1 protocol specified
                dcprot(2),     --  dont care about layer1 protocol
                g711a(3),      --  layer1 protocol is G-711 A-law
                g711mu(4),     --  layer1 protocol is G-711 MU-law
                g711(5),       --  layer1 protocol is G-711 A- or MU-law
                v110(6),       --  layer1 protocol is V-110
                v120(7)        --  layer1 protocol is V-120
           }
           ACCESS read-write
           STATUS mandatory
           DESCRIPTION
                "Protocol Specified."
           ::= { nvCrouteEntry 15 }


        nvCrouteVol1mode OBJECT-TYPE
           SYNTAX INTEGER {
                nomode(1),    --AF no data mode specified
                dcmode(2),      --AF dont care about data mode
                sync(3),      -- data mode is async
                async(4)      -- data mode is sync
           }

           ACCESS read-write
           STATUS mandatory
           DESCRIPTION
                "Data mode."
           ::= { nvCrouteEntry 17 }


        nvCrouteBw OBJECT-TYPE
           SYNTAX INTEGER
           ACCESS read-write
           STATUS mandatory
           DESCRIPTION
                ""
           ::= { nvCrouteEntry 19 }

        nvCrouteRcscp1 OBJECT-TYPE
           SYNTAX DisplayString (SIZE(0..12))
           ACCESS read-write
           STATUS mandatory
           DESCRIPTION
                "rcscp1."
           ::= { nvCrouteEntry 22 }

        nvCrouteRcscp2 OBJECT-TYPE
           SYNTAX DisplayString (SIZE(0..12))
           ACCESS read-write
           STATUS mandatory
           DESCRIPTION
                "rcscp1."
           ::= { nvCrouteEntry 25 }

	nvCrouteDialmapid OBJECT-TYPE
	   SYNTAX   INTEGER (0..65535)
	   ACCESS   read-write
	   STATUS   mandatory
	   DESCRIPTION
		"Record id of dialmap record to use."
	   ::= { nvCrouteEntry 27 }

        nvCrouteReserve1 OBJECT-TYPE
           SYNTAX DisplayString (SIZE(0..2))
           ACCESS read-only
           STATUS obsolete
           DESCRIPTION
                "OBSOLETE - removed field."
           ::= { nvCrouteEntry 28 }

	nvCrouteDirection OBJECT-TYPE
           SYNTAX INTEGER {
                incoming(1),  --CROUTE for incoming calls     
                outgoing(2),  --CROUTE for outgoing calls     
                unspec  (3)   --CROUTE for all calls          
           	}
           ACCESS read-write
           STATUS mandatory
           DESCRIPTION
                "Direction record is for."
	    ::= { nvCrouteEntry 29 }

        nvCrouteChoice OBJECT-TYPE
           SYNTAX   INTEGER {
                        first(1),
                        second(2),
                        third(3),
                        fourth(4)
                        }
           ACCESS   read-write
           STATUS   mandatory
           DESCRIPTION
           "A priority value.  Used to specify which record gets
           precedence if two records have the same addr."
           ::= { nvCrouteEntry 30 }

        nvCrouteStatus OBJECT-TYPE
           SYNTAX   INTEGER {
                        valid(1),
                        invalid(2)
                        }
           ACCESS   read-write
           STATUS   mandatory
           DESCRIPTION
           "Operation status. Add the record to the table (valid) or
           delete the record from the table (invalid)."
           ::= { nvCrouteEntry 31 }

--
--      crcstat file
--
        nvCrcstat OBJECT IDENTIFIER ::= { nevadaSystem 29 }

        nvCrcstatMaxRec OBJECT-TYPE
           SYNTAX   INTEGER
           ACCESS   read-only
           STATUS   mandatory
           DESCRIPTION
                "total number of records allowed in database file."
           ::= {nvCrcstat 1}

        nvCrcstatNumRec OBJECT-TYPE
           SYNTAX   INTEGER
           ACCESS   read-only
           STATUS   mandatory
           DESCRIPTION
                "number of records in use."
           ::= {nvCrcstat 2}

        nvCrcstatTable OBJECT-TYPE
           SYNTAX SEQUENCE OF NvCrcstatEntry
           ACCESS not-accessible
           STATUS mandatory
           DESCRIPTION
                "Circuit connection status table."
           ::= { nvCrcstat 3 }

        nvCrcstatEntry OBJECT-TYPE
           SYNTAX NvCrcstatEntry
           ACCESS not-accessible
           STATUS mandatory
           DESCRIPTION
                "crcstat record indexed by record number."
           INDEX { nvCrcstatIndex }
           ::= { nvCrcstatTable 1 }

        NvCrcstatEntry ::=
           SEQUENCE {
                nvCrcstatIndex
                        INTEGER,
                nvCrcstatCid
                        INTEGER,
                nvCrcstatState
                        INTEGER,
                nvCrcstatCallednum          --AF
                        DisplayString,	    --AF
		nvCrcstatCallngnum          --AF
		        DisplayString,	    --AF
		nvCrcstatCalledsub          --AF
		        DisplayString,	    --AF
		nvCrcstatCallngsub          --AF
		        DisplayString,	    --AF
                nvCrcstatRcsc0
                        DisplayString,
                nvCrcstatDevice0
                        DisplayString,
                nvCrcstatRcsc1
                        DisplayString,
                nvCrcstatDevice1
                        DisplayString,
                nvCrcstatRcsc2
                        DisplayString,
                nvCrcstatDevice2
                        DisplayString,
                nvCrcstatReserve1
                        DisplayString,
                nvCrcstatReserve2
                        DisplayString,
		nvCrcstatL1prot            --AF
		        INTEGER,	   --AF
		nvCrcstatL1mode            --AF
		        INTEGER,	   --AF
		nvCrcstatCroute            --AF
		        INTEGER,	   --AF
		nvCrcstatRouting           --AF
		        INTEGER,		   --AF
                nvCrcstatBw
                        INTEGER,
		nvCrcstatDirection
			INTEGER
                }

        nvCrcstatIndex OBJECT-TYPE
           SYNTAX INTEGER
           ACCESS read-only
           STATUS mandatory
           DESCRIPTION
                "Index of crcstat record."
           ::= { nvCrcstatEntry 1 }

        nvCrcstatCid OBJECT-TYPE
           SYNTAX INTEGER
           ACCESS read-only
           STATUS mandatory
           DESCRIPTION
                "circuit connection identifier."
           ::= { nvCrcstatEntry 2 }

        nvCrcstatState OBJECT-TYPE
           SYNTAX INTEGER {
                pending(1),      -- pending (+1)
                connecting(2),
                connected(3),
                clearing(4),
                hung(5)
           }
           ACCESS read-only
           STATUS mandatory
           DESCRIPTION
                "circuit connection state."
           ::= { nvCrcstatEntry 3 }

        nvCrcstatCallednum OBJECT-TYPE        --AF
           SYNTAX DisplayString (SIZE(0..32)) --AF
           ACCESS read-only
           STATUS mandatory		      --AF
           DESCRIPTION			      --AF
                "called party address."	      --AF
           ::= { nvCrcstatEntry 4 }	      --AF

        nvCrcstatBw OBJECT-TYPE
           SYNTAX INTEGER
           ACCESS read-only
           STATUS mandatory
           DESCRIPTION
                "bandwidth of permanent circuit."
           ::= { nvCrcstatEntry 5 }

        nvCrcstatRcsc0 OBJECT-TYPE
           SYNTAX DisplayString (SIZE(0..24))
           ACCESS read-only
           STATUS mandatory
           DESCRIPTION
                "resource info 0."
           ::= { nvCrcstatEntry 6 }

        nvCrcstatDevice0 OBJECT-TYPE
           SYNTAX DisplayString (SIZE(0..12))
           ACCESS read-only
           STATUS mandatory
           DESCRIPTION
                "device info 0."
           ::= { nvCrcstatEntry 7 }

        nvCrcstatRcsc1 OBJECT-TYPE
           SYNTAX DisplayString (SIZE(0..24))
           ACCESS read-only
           STATUS mandatory
           DESCRIPTION
                "resource info 1."
           ::= { nvCrcstatEntry 8 }

        nvCrcstatDevice1 OBJECT-TYPE
           SYNTAX DisplayString (SIZE(0..12))
           ACCESS read-only
           STATUS mandatory
           DESCRIPTION
                "device info 1."
           ::= { nvCrcstatEntry 9 }

        nvCrcstatRcsc2 OBJECT-TYPE
           SYNTAX DisplayString (SIZE(0..24))
           ACCESS read-only
           STATUS mandatory
           DESCRIPTION
                "resource info 2."
           ::= { nvCrcstatEntry 10 }

        nvCrcstatDevice2 OBJECT-TYPE
           SYNTAX DisplayString (SIZE(0..12))
           ACCESS read-only
           STATUS mandatory
           DESCRIPTION
                "device info 2."
           ::= { nvCrcstatEntry 11 }

        nvCrcstatReserve1 OBJECT-TYPE
           SYNTAX DisplayString (SIZE(0..2))
           ACCESS read-only
           STATUS obsolete
           DESCRIPTION
                "OBSOLETE - removed field."
           ::= { nvCrcstatEntry 12 }
 
        nvCrcstatReserve2 OBJECT-TYPE
           SYNTAX DisplayString (SIZE(0..2))
           ACCESS read-only
           STATUS obsolete
           DESCRIPTION
                "OBSOLETE - removed field."
           ::= { nvCrcstatEntry 13 }

        nvCrcstatCallngnum OBJECT-TYPE         --AF 
           SYNTAX DisplayString (SIZE(0..32))  --AF
           ACCESS read-only		       --AF
           STATUS mandatory		       --AF
           DESCRIPTION			       --AF
                "calling party address."       --AF
           ::= { nvCrcstatEntry 14 }	       --AF

        nvCrcstatCalledsub OBJECT-TYPE	       --AF
           SYNTAX DisplayString (SIZE(0..32))  --AF
           ACCESS read-only		       --AF
           STATUS mandatory		       --AF
           DESCRIPTION			       --AF
                "called party subaddress."     --AF
           ::= { nvCrcstatEntry 15 }	       --AF

        nvCrcstatCallngsub OBJECT-TYPE	       --AF
           SYNTAX DisplayString (SIZE(0..32))  --AF
           ACCESS read-only		       --AF
           STATUS mandatory		       --AF
           DESCRIPTION			       --AF
                "calling party subaddress."    --AF
           ::= { nvCrcstatEntry 16 }	       --AF
	   
        nvCrcstatL1prot OBJECT-TYPE	       --AF
           SYNTAX INTEGER {		       --AF
                noprot(1),		       --AF (+1)
                dcprot(2),		       --AF
                g711A(3),		       --AF
                g711MU(4),		       --AF
                g711(5),		       --AF
		v110(6),		       --AF
		v120(7)		               --AF
           }				       --AF
           ACCESS read-only		       --AF
           STATUS mandatory		       --AF
           DESCRIPTION			       --AF
                "L1prot."		       --AF
           ::= { nvCrcstatEntry 17 }	       --AF
	   
        nvCrcstatL1mode OBJECT-TYPE	       --AF
           SYNTAX INTEGER {		       --AF
                nomode(1),	               --AF (+1) no data mode specified
                dcmode(2),	               --AF dont care about data mode
                sync(3),                       --AF data in sync mode
                async(4)                       --AF data in async mode
           }				       --AF
           ACCESS read-only		       --AF
           STATUS mandatory		       --AF
           DESCRIPTION			       --AF
                "Layer 1 data mode."	       --AF
           ::= { nvCrcstatEntry 18 }	       --AF

        nvCrcstatCroute OBJECT-TYPE	       --AF
           SYNTAX INTEGER		       --AF
           ACCESS read-only		       --AF
           STATUS mandatory		       --AF
           DESCRIPTION			       --AF
                "Croute record id used."       --AF
           ::= { nvCrcstatEntry 19 }	       --AF
	   
        nvCrcstatRouting OBJECT-TYPE	       --AF
           SYNTAX INTEGER {		       --AF
                noroute(1),                    --AF (+1) routing not done
                callednum(2),                  --AF  route on called address
                callngnum(3),                  --AF route on calling address
                calledsub(4),                  --AF route on called sub address
                callngsub(5)                   --AF route on calling sub address
           }				       --AF
           ACCESS read-only		       --AF
           STATUS mandatory		       --AF
           DESCRIPTION			       --AF
                "Routing method."	       --AF
           ::= { nvCrcstatEntry 20 }	       --AF

        nvCrcstatDirection OBJECT-TYPE
           SYNTAX INTEGER {
                incoming(1),  --CROUTE for incoming calls
                outgoing(2),  --CROUTE for outgoing calls
                unspec  (3)   --CROUTE for all calls
                }
           ACCESS read-only
           STATUS mandatory
           DESCRIPTION
                "Direction call was in."
            ::= { nvCrcstatEntry 21 }

--
--      crfstat file
--
        nvCrfstat OBJECT IDENTIFIER ::= { nevadaSystem 30 }

        nvCrfstatMaxRec OBJECT-TYPE
           SYNTAX   INTEGER
           ACCESS   read-only
           STATUS   mandatory
           DESCRIPTION
                "total number of records allowed in database file."
           ::= {nvCrfstat 1}

        nvCrfstatNumRec OBJECT-TYPE
           SYNTAX   INTEGER
           ACCESS   read-only
           STATUS   mandatory
           DESCRIPTION
                "number of records in use."
           ::= {nvCrfstat 2}

        nvCrfstatTable OBJECT-TYPE
           SYNTAX SEQUENCE OF NvCrfstatEntry
           ACCESS not-accessible
           STATUS mandatory
           DESCRIPTION
                "Circuit failure status table."
           ::= { nvCrfstat 3 }

        nvCrfstatEntry OBJECT-TYPE
           SYNTAX NvCrfstatEntry
           ACCESS not-accessible
           STATUS mandatory
           DESCRIPTION
                "crfstat record indexed by record number."
           INDEX { nvCrfstatIndex }
           ::= { nvCrfstatTable 1 }

        NvCrfstatEntry ::=
           SEQUENCE {
                nvCrfstatIndex
                        INTEGER,
                nvCrfstatCid
                        INTEGER,
                nvCrfstatCallednum          --AF
                        DisplayString,	    --AF
		nvCrfstatCallngnum          --AF
		        DisplayString,	    --AF
		nvCrfstatCalledsub          --AF
		        DisplayString,	    --AF
		nvCrfstatCallngsub          --AF
		        DisplayString,	    --AF
		nvCrfstatL1prot             --AF
		        INTEGER,	    --AF
		nvCrfstatL1mode             --AF
		        INTEGER,	    --AF
		nvCrfstatCroute             --AF
		        INTEGER,	    --AF
		nvCrfstatRouting            --AF
		        INTEGER,	    --AF
                nvCrfstatAddr               --AF
		        DisplayString,	    --AF
		nvCrfstatCause              --AF
		        INTEGER,	    --AF
                nvCrfstatRcsc0
                        DisplayString,
                nvCrfstatRcsc1
                        DisplayString,
                nvCrfstatRcsc2
                        DisplayString,
		nvCrfstatReserve1
			DisplayString,
		nvCrfstatDirection
			INTEGER
                }

        nvCrfstatIndex OBJECT-TYPE
           SYNTAX INTEGER
           ACCESS read-only
           STATUS mandatory
           DESCRIPTION
                "Index of crfstat record."
           ::= { nvCrfstatEntry 1 }

        nvCrfstatCid OBJECT-TYPE
           SYNTAX INTEGER
           ACCESS read-only
           STATUS mandatory
           DESCRIPTION
                "circuit connection identifier."
           ::= { nvCrfstatEntry 2 }

        nvCrfstatCallednum OBJECT-TYPE	       --AF
           SYNTAX DisplayString (SIZE(0..32))  --AF
           ACCESS read-only		       --AF
           STATUS mandatory		       --AF
           DESCRIPTION			       --AF
                "called party address."	       --AF
           ::= { nvCrfstatEntry 3 }	       --AF

        nvCrfstatCallngnum OBJECT-TYPE		 --AF
           SYNTAX DisplayString (SIZE(0..32))	 --AF
           ACCESS read-only			 --AF
           STATUS mandatory			 --AF
           DESCRIPTION				 --AF
                "calling party address."	 --AF
           ::= { nvCrfstatEntry 4 }		 --AF

        nvCrfstatCalledsub OBJECT-TYPE		 --AF
           SYNTAX DisplayString (SIZE(0..32))	 --AF
           ACCESS read-only			 --AF
           STATUS mandatory			 --AF
           DESCRIPTION				 --AF
                "called party subaddress."	 --AF
           ::= { nvCrfstatEntry 5 }		 --AF

        nvCrfstatCallngsub OBJECT-TYPE		 --AF
           SYNTAX DisplayString (SIZE(0..32))	 --AF
           ACCESS read-only			 --AF
           STATUS mandatory			 --AF
           DESCRIPTION				 --AF
                "calling party subaddress."	 --AF
           ::= { nvCrfstatEntry 6 }		 --AF
	   
        nvCrfstatL1prot OBJECT-TYPE		 --AF
           SYNTAX INTEGER {			 --AF
                noprot(1),			 --AF
                dcprot(2),			 --AF
                g711A(3),			 --AF
                g711MU(4),			 --AF
                g711(5),			 --AF
		v110(6),			 --AF
		v120(7)				 --AF
           }					 --AF
           ACCESS read-only			 --AF
           STATUS mandatory			 --AF
           DESCRIPTION				 --AF
                "L1prot."			 --AF
           ::= { nvCrfstatEntry 7 }		 --AF
	   
        nvCrfstatL1mode OBJECT-TYPE		 --AF
           SYNTAX INTEGER {			 --AF
                nomode(1),	                 --AF (+1) no data mode specified
                dcprot(2),	                 --AF dont care about data mode
                sync(3),	                 --AF data in sync mode
                async(4)                         --AF data in async mode
           }					 --AF
           ACCESS read-only			 --AF
           STATUS mandatory			 --AF
           DESCRIPTION				 --AF
                "Layer 1 data mode."		 --AF
           ::= { nvCrfstatEntry 8 }		 --AF

        nvCrfstatCroute OBJECT-TYPE		 --AF
           SYNTAX INTEGER			 --AF
           ACCESS read-only			 --AF
           STATUS mandatory			 --AF
           DESCRIPTION				 --AF
                "Croute record id used."	 --AF
           ::= { nvCrfstatEntry 9 }		 --AF
	   
        nvCrfstatRouting OBJECT-TYPE		 --AF
           SYNTAX INTEGER {			 --AF
                noroute(1),                      --AF routing not done
                callednum(2),                    --AF route on called address
                callngnum(3),                    --AF route on calling address
                calledsub(4),                    --AF route on called sub address
                callngsub(5)                     --AF route on calling sub address
           }					 --AF
           ACCESS read-only			 --AF
           STATUS mandatory			 --AF
           DESCRIPTION				 --AF
                "Routing method."		 --AF
           ::= { nvCrfstatEntry 10 }		 --AF

        nvCrfstatAddr OBJECT-TYPE	       --AF
           SYNTAX DisplayString (SIZE(0..32))  --AF
           ACCESS read-only		       --AF
           STATUS mandatory		       --AF
           DESCRIPTION			       --AF
                " address."                    --AF
           ::= { nvCrfstatEntry 11 }	       --AF

        nvCrfstatCause OBJECT-TYPE
           SYNTAX INTEGER {
                crfNoRoute(2),          -- failure cause code (+1)
                crfTsAllocFail(3),
                crfRcscAllocFail(4),
                crfConAbort(5),
                crfConFail(6),
                dvNoGroup(7),
                dvBwRej(8),
                dvThrshRej(9),
                dvUnavail(10),
                frBwUnavail(11),
                portNoConn(12),
                scsaStuck(13),
		psReject(14),
		psChCrErr(15),
		dvNoPool(16),
		dvBadClass(17),
		dspHwUnavail(18),
		dspBadResrc(19),
		dspNoSetupI(20),
		dspRoRoNone(21),
		dspChCRspTO(22),
		dspChCRNoHw(23),
		dspChCrSyEr(24),
		dspChCrBitF(25),
		dspChCrDwlF(26),
		dspMsgNotPS(27),
		r2NoDspTs(28),
		r2ChCrErr(29),
		srcAborted(30),
		crfRsrcBusy(31),
		dspmFullLts(32),
		sigChCrErr(33),
		busy(34),
		noAnswer(35),
		tsUnavail(36),
		noDialtone(37),
		causeUnspecified(38)
                }
           ACCESS read-only
           STATUS mandatory
           DESCRIPTION
                "circuit connection failure cause."
           ::= { nvCrfstatEntry 12 }

        nvCrfstatRcsc0 OBJECT-TYPE
           SYNTAX DisplayString (SIZE(0..24))
           ACCESS read-only
           STATUS mandatory
           DESCRIPTION
                "resource info 0."
           ::= { nvCrfstatEntry 13 }

        nvCrfstatRcsc1 OBJECT-TYPE
           SYNTAX DisplayString (SIZE(0..24))
           ACCESS read-only
           STATUS mandatory
           DESCRIPTION
                "resource info 1."
           ::= { nvCrfstatEntry 14 }

        nvCrfstatRcsc2 OBJECT-TYPE
           SYNTAX DisplayString (SIZE(0..24))
           ACCESS read-only
           STATUS mandatory
           DESCRIPTION
                "resource info 2."
           ::= { nvCrfstatEntry 15 }

        nvCrfstatReserve1 OBJECT-TYPE
           SYNTAX DisplayString (SIZE(0..2))
           ACCESS read-only
           STATUS obsolete
           DESCRIPTION
                "OBSOLETE - removed field."
           ::= { nvCrfstatEntry 16 }

	nvCrfstatDirection OBJECT-TYPE
           SYNTAX INTEGER {
                incoming(1),  --CROUTE for incoming calls
                outgoing(2),  --CROUTE for outgoing calls
                unspec  (3)   --CROUTE for all calls
                }
           ACCESS read-only
           STATUS mandatory
           DESCRIPTION
                "Direction record is for."
            ::= { nvCrfstatEntry 18 }

--
--      rrstat file
--
        nvRrstat OBJECT IDENTIFIER ::= { nevadaSystem 31 }

        nvRrstatMaxRec OBJECT-TYPE
           SYNTAX   INTEGER
           ACCESS   read-only
           STATUS   mandatory
           DESCRIPTION
                "total number of records allowed in database file."
           ::= {nvRrstat 1}

        nvRrstatNumRec OBJECT-TYPE
           SYNTAX   INTEGER
           ACCESS   read-only
           STATUS   mandatory
           DESCRIPTION
                "number of records in use."
           ::= {nvRrstat 2}

        nvRrstatTable OBJECT-TYPE
           SYNTAX SEQUENCE OF NvRrstatEntry
           ACCESS not-accessible
           STATUS mandatory
           DESCRIPTION
                "resouce registry (system registry) status table."
           ::= { nvRrstat 3 }

        nvRrstatEntry OBJECT-TYPE
           SYNTAX NvRrstatEntry
           ACCESS not-accessible
           STATUS mandatory
           DESCRIPTION
                "rrstat record indexed by record number."
           INDEX { nvRrstatIndex }
           ::= { nvRrstatTable 1 }

        NvRrstatEntry ::=
           SEQUENCE {
                nvRrstatIndex
                        INTEGER,
                nvRrstatPoolname
                        DisplayString,
                nvRrstatClass
                        INTEGER,
                nvRrstatNumbers
                        Counter,
                nvRrstatConns
                        Counter,
                nvRrstatMaxcalls
                        Counter,
                nvRrstatNumIcalls
                        Counter,
                nvRrstatNumOcalls
                        Counter,
                nvRrstatNumcalls
                        Counter,
                nvRrstatAvgtime
                        Counter,
	 	nvRrstatDtreset
			DisplayString
                }

        nvRrstatIndex OBJECT-TYPE
           SYNTAX INTEGER
           ACCESS read-only
           STATUS mandatory
           DESCRIPTION
                "Index of rrstat record."
           ::= { nvRrstatEntry 1 }

        nvRrstatPoolname OBJECT-TYPE
           SYNTAX DisplayString
           ACCESS read-only
           STATUS mandatory
           DESCRIPTION
                "resource pool name."
           ::= { nvRrstatEntry 2 }

        nvRrstatClass OBJECT-TYPE
           SYNTAX INTEGER {
                protocolStack(2),       -- protocol stack (+1)
                digitalModem(3),
                priCall(4),
                priDc(5)
                }
           ACCESS read-only
           STATUS mandatory
           DESCRIPTION
                "resource pool class."
           ::= { nvRrstatEntry 3 }

        nvRrstatNumbers OBJECT-TYPE
           SYNTAX Counter
           ACCESS read-only
           STATUS mandatory
           DESCRIPTION
                "number of resources."
           ::= { nvRrstatEntry 4 }

        nvRrstatConns OBJECT-TYPE
           SYNTAX Counter
           ACCESS read-only
           STATUS mandatory
           DESCRIPTION
                "number of connected resources."
           ::= { nvRrstatEntry 5 }
           
        nvRrstatMaxcalls OBJECT-TYPE
           SYNTAX Counter
           ACCESS read-only
           STATUS mandatory
           DESCRIPTION
           "Maximum number of connected resources."
           ::= { nvRrstatEntry 6 }
           
        nvRrstatNumIcalls OBJECT-TYPE
           SYNTAX Counter
           ACCESS read-only
           STATUS mandatory
           DESCRIPTION
           "Total number of incoming calls processed."
           ::= { nvRrstatEntry 7 }
           
        nvRrstatNumOcalls OBJECT-TYPE
           SYNTAX Counter
           ACCESS read-only
           STATUS mandatory
           DESCRIPTION
           "Total number of outgoing calls processed."
           ::= { nvRrstatEntry 8 }
           
        nvRrstatNumcalls OBJECT-TYPE
           SYNTAX Counter
           ACCESS read-only
           STATUS mandatory
           DESCRIPTION
           "Total number of calls processed."
           ::= { nvRrstatEntry 9 } 
           
        nvRrstatAvgtime OBJECT-TYPE
           SYNTAX Counter
           ACCESS read-only
           STATUS mandatory
           DESCRIPTION
           "Average length of call in seconds."
           ::= { nvRrstatEntry 10 }

	nvRrstatDtreset OBJECT-TYPE
	   SYNTAX   DisplayString (SIZE (0..20))
	   ACCESS   read-only
	   STATUS   mandatory
	   DESCRIPTION
	   "date & time statistics last reset"
	   ::= { nvRrstatEntry 15 }

--
--      modemprof
--
nvModemprof OBJECT IDENTIFIER ::= {nevadaSystem 32}

nvModemprofMaxRec OBJECT-TYPE
     SYNTAX   INTEGER
     ACCESS   read-only
     STATUS   mandatory
     DESCRIPTION
        "total number of records allowed in database file."
     ::= {nvModemprof 1}

nvModemprofNumRec OBJECT-TYPE
     SYNTAX   INTEGER
     ACCESS   read-only
     STATUS   mandatory
     DESCRIPTION
        "number of records in use."
     ::= {nvModemprof 2}

nvModemprofTable OBJECT-TYPE
      SYNTAX   SEQUENCE OF NvModemprofEntry
      ACCESS   not-accessible
      STATUS   mandatory
      DESCRIPTION
               "modemconf file."
      ::= { nvModemprof 3 }

nvModemprofEntry OBJECT-TYPE
      SYNTAX   NvModemprofEntry
      ACCESS   not-accessible
      STATUS   mandatory
      DESCRIPTION
               "modemconf record."
      INDEX { nvModemprofIndex }
      ::= { nvModemprofTable 1 }

NvModemprofEntry ::=
      SEQUENCE {
      nvModemprofIndex
            INTEGER,
      nvModemprofName
            DisplayString,
      nvModemprofRsrcpool
            DisplayString,
      nvModemprofDspname
            DisplayString,
      nvModemprofType
            INTEGER,
      nvModemprofEc
            INTEGER,
      nvModemprofDc
            INTEGER,
      nvModemprofMode
            INTEGER,
      nvModemprofCmpdtype
            INTEGER,
      nvModemprofTxlvl
            INTEGER,
      nvModemprofRxthresh
            INTEGER,
      nvModemprofAnston
            INTEGER,
      nvModemprofAnstondur
            INTEGER,
      nvModemprofBildly
            INTEGER,
      nvModemprofStatus
            INTEGER,
      nvModemprofFalbckchr
	    INTEGER
            }


nvModemprofIndex OBJECT-TYPE
     SYNTAX   INTEGER
     ACCESS   read-only
     STATUS   mandatory
     DESCRIPTION
        "Index of modemconf record"
      ::= { nvModemprofEntry 1 }

nvModemprofName OBJECT-TYPE
     SYNTAX   DisplayString (SIZE (0..11))
     ACCESS   read-write
     STATUS   mandatory
     DESCRIPTION
"Modem Prof resource config name (name)"
     ::= { nvModemprofEntry 2 }

nvModemprofRsrcpool OBJECT-TYPE
     SYNTAX   DisplayString (SIZE (0..11))
     ACCESS   read-write
     STATUS   mandatory
     DESCRIPTION
"Resource pool name."
     ::= { nvModemprofEntry 5 }

nvModemprofDspname OBJECT-TYPE
     SYNTAX   DisplayString (SIZE (0..11))
     ACCESS   read-write
     STATUS   mandatory
     DESCRIPTION
"Device usage group name."
     ::= { nvModemprofEntry 6 }

nvModemprofType OBJECT-TYPE
     SYNTAX   INTEGER {
                modauto(1),   -- V.34 by any other name
                v34(2),       -- V.34 (19200,16800)  (+1)
                v32bis(3),    -- V.32bis (14400,12000,9600,7200,4800)
                v32(4),       -- V.32 (9600,4800,2400)
                v23t75r12(5), -- V.23t75r12 (tx7500/r1200)
                v23t12r75(6), -- V.23t12r75 (tx1200/r7500)
                v22bis(7),    -- V.22bis (2400)
                v22(8),       -- V.22 (1200)
                v21(9),       -- V.21 (0-300)
                b212a(10),    -- Bell 212A (1200)
                b103(11),     -- Bell 103 (0-300)
                pautob(12),   -- Auto Mode, incl Fastconn, Bell Answer Tone
                pautoc(13),   -- Auto Mode, incl Fastconn, CCITT Answer Tone
		v34bis(14),   -- v.34bis (33,600 and 31,200)
		vpcm(15),     -- V.PCM (k56) 60,000 down to 32,000 in increments of 2k
                v21rev(16),   -- Reverse Training - V.21 up thru V.22bis => automode starting at 300.
                v110mod(21),
                v110b600(22),
                v110b1200(23),
                v110b2400(24),
                v110b4800(25),
                v110b7200(26),
                v110b9600(27),
                v110b12000(28),
                v110b14400(29),
                v110b19200(30),
                v110b48000(31),
                v110b56000(32)
                }
     ACCESS   read-write
     STATUS   mandatory
     DESCRIPTION
"Modem modulation scheme (type)
Default value is 3."
     ::= { nvModemprofEntry 7 }

nvModemprofEc OBJECT-TYPE
     SYNTAX   INTEGER {
                disable(1),     -- disable all error correction (+1)
                v42ec(2),       -- V.42 error correction
                mNPec(3),       -- MNP Microcom Networking Protocol err correction
                eitherec(4),    -- try v42,then try MNP,then disconnect
                autoec(5)       -- try v42,then try MNP,then connect with no ec
                }
     ACCESS   read-write
     STATUS   mandatory
     DESCRIPTION
"Modem error correction option."
     ::= { nvModemprofEntry 8 }

nvModemprofDc OBJECT-TYPE
     SYNTAX   INTEGER {
                disable(1),     -- disable data compression (+1)
                enable(2)       -- enable data compression
                }
     ACCESS   read-write
     STATUS   mandatory
     DESCRIPTION
"Modem data compression option."
     ::= { nvModemprofEntry 9 }

nvModemprofMode OBJECT-TYPE
     SYNTAX   INTEGER {
                sync(3),        -- synchronous data configured (+1)
                async(4),       -- async data configured
                auto(8)         -- will decide at call start
                }
     ACCESS   read-write
     STATUS   mandatory
     DESCRIPTION
"Modem sync / async option."
     ::= { nvModemprofEntry 10 }

nvModemprofCmpdtype OBJECT-TYPE
     SYNTAX   INTEGER {
                mulaw(2),       -- mu law (+1)
                alaw(3),        -- a law
                nocmpdt(4)      -- field no applicable as for V.110
                }
     ACCESS   read-write
     STATUS   mandatory
     DESCRIPTION
"Modem companding type."
     ::= { nvModemprofEntry 13 }

nvModemprofTxlvl OBJECT-TYPE
     SYNTAX   INTEGER (0..15)
     ACCESS   read-write
     STATUS   mandatory
     DESCRIPTION
"Transmit level (txlvl)
Default value is 13."
     ::= { nvModemprofEntry 14 }

nvModemprofRxthresh OBJECT-TYPE
     SYNTAX   INTEGER (0..255)
     ACCESS   read-write
     STATUS   mandatory
     DESCRIPTION
"Modem receive threshold (rxthresh)
Default value is 38."
     ::= { nvModemprofEntry 15 }


nvModemprofAnston OBJECT-TYPE
     SYNTAX   INTEGER {
                yes(2),
                no(3)
                }
     ACCESS   read-write
     STATUS   mandatory
     DESCRIPTION
"Modem generate answer (anston)
tone."
     ::= { nvModemprofEntry 17 }

nvModemprofAnstondur OBJECT-TYPE
     SYNTAX   INTEGER (0..100)
     ACCESS   read-write
     STATUS   mandatory
     DESCRIPTION
"Mode answer tone (anstondur)
duration."
     ::= { nvModemprofEntry 18 }

nvModemprofBildly OBJECT-TYPE
     SYNTAX   INTEGER (0..100)
     ACCESS   read-write
     STATUS   mandatory
     DESCRIPTION
"Modem wait to send answer (bildly)
tone."
     ::= { nvModemprofEntry 19 }

nvModemprofStatus OBJECT-TYPE
     SYNTAX   INTEGER {
                valid(1),
                invalid(2)
                }
     ACCESS   read-write
     STATUS   mandatory
     DESCRIPTION
"Operation status. Add the record to the table (valid) or delete
the record from the table (invalid)."
     ::= { nvModemprofEntry 20 }

nvModemprofFalbckchr OBJECT-TYPE
     SYNTAX   INTEGER (0..80)
     ACCESS   read-write
     STATUS   mandatory
     DESCRIPTION
"modem autorel fallback char."
     ::= { nvModemprofEntry 21 }


nvIfStackInfo OBJECT IDENTIFIER ::= {nevadaSystem 33}

nvIfStackInfoNumRec OBJECT-TYPE
     SYNTAX   INTEGER
     ACCESS   read-only
     STATUS   mandatory
     DESCRIPTION
        "number of records in use."
     ::= {nvIfStackInfo 1}

nvIfStackInfoTable OBJECT-TYPE
      SYNTAX   SEQUENCE OF NvIfStackInfoEntry
      ACCESS   not-accessible
      STATUS   mandatory
      DESCRIPTION
               "modemconf file."
      ::= { nvIfStackInfo 2 }

nvIfStackInfoEntry OBJECT-TYPE
      SYNTAX   NvIfStackInfoEntry
      ACCESS   not-accessible
      STATUS   mandatory
      DESCRIPTION
               "IfStackInfo record."
      INDEX { nvIfStackInfoHigherLI, nvIfStackInfoLowerLI }
      ::= { nvIfStackInfoTable 1 }

NvIfStackInfoEntry ::=
      SEQUENCE {
      nvIfStackInfoHigherLI
            INTEGER,
      nvIfStackInfoLowerLI
            INTEGER,
      nvIfStackInfoStatus
            INTEGER,
      nvIfStackInfoRid
            INTEGER
                }

nvIfStackInfoHigherLI OBJECT-TYPE
     SYNTAX   INTEGER
     ACCESS   read-only
     STATUS   mandatory
     DESCRIPTION
        "highre layer interface number."
     ::= {nvIfStackInfoEntry 1}

nvIfStackInfoLowerLI OBJECT-TYPE
     SYNTAX   INTEGER
     ACCESS   read-only
     STATUS   mandatory
     DESCRIPTION
        "Lower layer interface number."
     ::= {nvIfStackInfoEntry 2}

nvIfStackInfoStatus OBJECT-TYPE
     SYNTAX   INTEGER
     ACCESS   read-only
     STATUS   mandatory
     DESCRIPTION
        "Status of the entry."
     ::= {nvIfStackInfoEntry 3}

nvIfStackInfoRid OBJECT-TYPE
     SYNTAX   INTEGER
     ACCESS   read-only
     STATUS   mandatory
     DESCRIPTION
        "Record ID to get info on this"
     ::= {nvIfStackInfoEntry 4}

--
--      dialmap file
--
nvDialmap OBJECT IDENTIFIER ::= { nevadaSystem 34 }
 
        nvDialmapMaxRec OBJECT-TYPE                         
           SYNTAX   INTEGER
           ACCESS   read-only
           STATUS   mandatory
           DESCRIPTION
                "total number of records allowed in database file."
           ::= {nvDialmap 1}

        nvDialmapNumRec OBJECT-TYPE
           SYNTAX   INTEGER (0..255)
           ACCESS   read-only
           STATUS   mandatory
           DESCRIPTION
                "number of records in use."
           ::= {nvDialmap 2}

        nvDialmapTable OBJECT-TYPE
           SYNTAX SEQUENCE OF NvDialmapEntry
           ACCESS not-accessible
           STATUS mandatory
           DESCRIPTION
                "Dialmap table."
           ::= { nvDialmap 3 }
 
        nvDialmapEntry OBJECT-TYPE
           SYNTAX NvDialmapEntry
           ACCESS not-accessible
           STATUS mandatory
           DESCRIPTION
                "Dialmap table record."
           INDEX { nvDialmapIndex }
           ::= { nvDialmapTable 1 }
 
        NvDialmapEntry ::=
           SEQUENCE {
                nvDialmapIndex
                        INTEGER,
		nvDialmapNumdelete
			INTEGER,
		nvDialmapAddprefix
			DisplayString,
		nvDialmapStatus
			INTEGER
			}

        nvDialmapIndex OBJECT-TYPE
           SYNTAX INTEGER
           ACCESS read-only
           STATUS mandatory
           DESCRIPTION
                "Index of dialmap record."
           ::= { nvDialmapEntry 1 }

	nvDialmapNumdelete OBJECT-TYPE
	   SYNTAX INTEGER (0..255)
	   ACCESS read-write
	   STATUS mandatory
	   DESCRIPTION
		"Number of digits to delete."
	   ::= { nvDialmapEntry 2}

        nvDialmapAddprefix OBJECT-TYPE
           SYNTAX DisplayString (SIZE (0..9))
           ACCESS read-write
           STATUS mandatory
           DESCRIPTION
                "Digits to add after digits deleted."
           ::= { nvDialmapEntry 3 }

        nvDialmapStatus OBJECT-TYPE
           SYNTAX   INTEGER {
                        valid(1),
                        invalid(2)
                        }
           ACCESS   read-write
           STATUS   mandatory
           DESCRIPTION
           "Operation status. Add the record to the table (valid) or
           delete the record from the table (invalid)."
           ::= { nvDialmapEntry 10 }

--
--	dspmalloc file
--
nvDspmalloc OBJECT IDENTIFIER ::= { nevadaSystem 35 }
 
        nvDspmallocMaxRec OBJECT-TYPE
           SYNTAX   INTEGER
           ACCESS   read-only
           STATUS   mandatory
           DESCRIPTION
                "total number of records allowed in database file."
           ::= {nvDspmalloc 1}
 
        nvDspmallocNumRec OBJECT-TYPE
           SYNTAX   INTEGER
           ACCESS   read-only
           STATUS   mandatory
           DESCRIPTION
                "number of records in use."
           ::= {nvDspmalloc 2}
 
        nvDspmallocTable OBJECT-TYPE
           SYNTAX SEQUENCE OF NvDspmallocEntry
           ACCESS not-accessible
           STATUS mandatory
           DESCRIPTION
                "Dspmalloc table."
           ::= { nvDspmalloc 3 }
 
        nvDspmallocEntry OBJECT-TYPE
           SYNTAX NvDspmallocEntry
           ACCESS not-accessible
           STATUS mandatory
           DESCRIPTION
                "Dspmalloc table record."
           INDEX { nvDspmallocIndex }
           ::= { nvDspmallocTable 1 }
 
        NvDspmallocEntry ::=
           SEQUENCE {
                nvDspmallocIndex
                        INTEGER,
		nvDspmallocDsptype
			INTEGER,
		nvDspmallocWeight
			INTEGER,
		nvDspmallocStatus
			INTEGER
		}

	nvDspmallocIndex OBJECT-TYPE
	     SYNTAX   INTEGER
	     ACCESS   read-only
	     STATUS   mandatory
	     DESCRIPTION
		"Index of dspmalloc record"
	     ::= { nvDspmallocEntry 1 }

        nvDspmallocDsptype OBJECT-TYPE 
             SYNTAX   INTEGER {
			kfModem(2),
			v90Modem(3)
			}
             ACCESS   read-only 
             STATUS   mandatory 
             DESCRIPTION 
                "Type of DSP - kflex or V.90."
             ::= { nvDspmallocEntry 2 }

        nvDspmallocWeight OBJECT-TYPE 
             SYNTAX   INTEGER 
             ACCESS   read-write 
             STATUS   mandatory 
             DESCRIPTION 
                "Allocation proportion."
             ::= { nvDspmallocEntry 3 }

	nvDspmallocStatus OBJECT-TYPE
	     SYNTAX   INTEGER {
			valid(1),
			invalid(2)
			}
	     ACCESS   read-write
	     STATUS   mandatory
	     DESCRIPTION
		"Operation status. Add the record to the table (valid) or
		 delete the record from the table (invalid)."
	     ::= { nvDspmallocEntry 10 }

--
--	dialstat file
--
nvDialstat OBJECT IDENTIFIER ::= { nevadaSystem 36 }

        nvDialstatMaxRec OBJECT-TYPE
           SYNTAX   INTEGER
           ACCESS   read-only
           STATUS   mandatory
           DESCRIPTION
                "total number of records allowed in database file."
           ::= {nvDialstat 1}

        nvDialstatNumRec OBJECT-TYPE
           SYNTAX   INTEGER
           ACCESS   read-only
           STATUS   mandatory
           DESCRIPTION
                "number of records in use."
           ::= {nvDialstat 2}

        nvDialstatTable OBJECT-TYPE
           SYNTAX SEQUENCE OF NvDialstatEntry
           ACCESS not-accessible
           STATUS mandatory
           DESCRIPTION
                "Dialstat table."
           ::= { nvDialstat 3 }

	nvDialstatEntry OBJECT-TYPE
           SYNTAX NvDialstatEntry
           ACCESS not-accessible
           STATUS mandatory
           DESCRIPTION
                "Dialstat table record."
           INDEX { nvDialstatIndex }
           ::= { nvDialstatTable 1 }

	NvDialstatEntry ::=
           SEQUENCE {
                nvDialstatIndex
                        INTEGER,
		nvDialstatRcscpool
			DisplayString,
		nvDialstatNcurrent
			INTEGER,
		nvDialstatNcalling
			INTEGER,
		nvDialstatTrace
			INTEGER,
		nvDialstatLastAddr
			DisplayString,
		nvDialstatLastCause
			INTEGER,
		nvDialstatLastDiag
			INTEGER,
		nvDialstatLastResponse
			DisplayString,
		nvDialstatNdialout
			Counter,
		nvDialstatNattempt
			Counter,
		nvDialstatNsucceed
			Counter,
		nvDialstatNfail
			Counter,
		nvDialstatNcircfail
			Counter,
		nvDialstatNcmderror
			Counter,
		nvDialstatNdialtone
			Counter,
		nvDialstatNbusy
			Counter,
		nvDialstatNnoRoute
			Counter,
		nvDialstatNnoModem
			Counter,
		nvDialstatNnoInput
			Counter,
		nvDialstatNinvnum
			Counter,
		nvDialstatNnoAnswer
			Counter,
		nvDialstatNmnegfail
			Counter,
		nvDialstatNconnfail
			Counter,
		nvDialstatNmiscfail
			Counter,
		nvDialstatMaxcall
			Counter,
		nvDialstatAdSucctim
			INTEGER,
		nvDialstatAdFailtim
			INTEGER,
		nvDialstatNabredial
			Counter
		}

	nvDialstatIndex OBJECT-TYPE
	    SYNTAX   INTEGER
	    ACCESS   read-only
	    STATUS   mandatory
	    DESCRIPTION
		"Index of Dialstat record"
	    ::= {nvDialstatEntry 1 }

	nvDialstatRcscpool OBJECT-TYPE
	    SYNTAX   DisplayString (SIZE (0..14))
	    ACCESS   read-only
	    STATUS   mandatory
	    DESCRIPTION
		"Resource Name."
	    ::= { nvDialstatEntry 2 }

        nvDialstatNcurrent OBJECT-TYPE
            SYNTAX   INTEGER (0..65535)
            ACCESS   read-only
            STATUS   mandatory
            DESCRIPTION
                "Number of dial-out Sessions currently occuring."
            ::= {nvDialstatEntry 3 }

        nvDialstatNcalling OBJECT-TYPE
            SYNTAX   INTEGER (0..65535)
            ACCESS   read-only
            STATUS   mandatory
            DESCRIPTION
                "Number of call attempts currently occuring."
            ::= {nvDialstatEntry 4 }

        nvDialstatTrace OBJECT-TYPE
            SYNTAX   INTEGER {
			no(1),
			yes(2),
			busy(4)
			}
            ACCESS   read-only
            STATUS   mandatory
            DESCRIPTION
                "Is trace enabled?"
            ::= {nvDialstatEntry 5 }

        nvDialstatLastAddr OBJECT-TYPE
            SYNTAX   DisplayString (SIZE (0..20))
            ACCESS   read-only
            STATUS   mandatory
            DESCRIPTION
                "Last Called Number."
            ::= { nvDialstatEntry 6 }

        nvDialstatLastCause OBJECT-TYPE
            SYNTAX   INTEGER
            ACCESS   read-only
            STATUS   mandatory
            DESCRIPTION
                "Last ISDN cause code."
            ::= {nvDialstatEntry 7 }

        nvDialstatLastDiag OBJECT-TYPE
            SYNTAX   INTEGER
            ACCESS   read-only
            STATUS   mandatory
            DESCRIPTION
                "Last X.25 diagnostic."
            ::= {nvDialstatEntry 8 }

        nvDialstatLastResponse OBJECT-TYPE
            SYNTAX   DisplayString (SIZE (0..9))
            ACCESS   read-only
            STATUS   mandatory
            DESCRIPTION
                "Last Response."
            ::= { nvDialstatEntry 9 }

        nvDialstatNdialout OBJECT-TYPE
            SYNTAX   Counter
            ACCESS   read-only
            STATUS   mandatory 
            DESCRIPTION  
                "Number of dial-out sessions."
            ::= {nvDialstatEntry 10 }

        nvDialstatNattempt OBJECT-TYPE
            SYNTAX   Counter
            ACCESS   read-only
            STATUS   mandatory
            DESCRIPTION    
                "Number of call attempts.
			(May be multiple attempts per dialout request)."
            ::= {nvDialstatEntry 11 }
 
        nvDialstatNsucceed OBJECT-TYPE
            SYNTAX   Counter
            ACCESS   read-only
            STATUS   mandatory
            DESCRIPTION    
                "Number of successful dial-out attempts."
            ::= {nvDialstatEntry 12 }
 
        nvDialstatNfail OBJECT-TYPE
            SYNTAX   Counter
            ACCESS   read-only
            STATUS   mandatory
            DESCRIPTION    
                "Number of failed dial-out attempts."
            ::= {nvDialstatEntry 13 }
 
        nvDialstatNcircfail OBJECT-TYPE
            SYNTAX   Counter
            ACCESS   read-only
            STATUS   mandatory
            DESCRIPTION    
                "Number of times circuit creation failed immediately."
            ::= {nvDialstatEntry 14 }
 
        nvDialstatNcmderror OBJECT-TYPE
            SYNTAX   Counter
            ACCESS   read-only
            STATUS   mandatory
            DESCRIPTION    
                "Number of fails due to error in dialout string command."
            ::= {nvDialstatEntry 15 }
 
        nvDialstatNdialtone OBJECT-TYPE
            SYNTAX   Counter
            ACCESS   read-only
            STATUS   mandatory
            DESCRIPTION    
                "Number of fails due to no dialtone."
            ::= {nvDialstatEntry 16 }
 
        nvDialstatNbusy OBJECT-TYPE
            SYNTAX   Counter
            ACCESS   read-only
            STATUS   mandatory
            DESCRIPTION    
                "Number of fails due to remote busy."
            ::= {nvDialstatEntry 17 }

        nvDialstatNnoRoute OBJECT-TYPE
            SYNTAX   Counter
            ACCESS   read-only
            STATUS   mandatory
            DESCRIPTION    
                "Number of fails due to routing error."
            ::= {nvDialstatEntry 18 }
 
        nvDialstatNnoModem OBJECT-TYPE
            SYNTAX   Counter
            ACCESS   read-only
            STATUS   mandatory
            DESCRIPTION    
                "Number of Fails because no modem was available."
            ::= {nvDialstatEntry 19 }
 
        nvDialstatNnoInput OBJECT-TYPE
            SYNTAX   Counter
            ACCESS   read-only
            STATUS   mandatory
            DESCRIPTION    
                "Number of fails because of no user input
		  within time limit."
            ::= {nvDialstatEntry 20 }
 
        nvDialstatNinvnum OBJECT-TYPE
            SYNTAX   Counter
            ACCESS   read-only
            STATUS   mandatory
            DESCRIPTION    
                "Number of fails because invalid user input received."
            ::= {nvDialstatEntry 21 }
 
        nvDialstatNnoAnswer OBJECT-TYPE
            SYNTAX   Counter
            ACCESS   read-only
            STATUS   mandatory
            DESCRIPTION    
                "Number of fails due to no answer."
            ::= {nvDialstatEntry 22 }
 
        nvDialstatNmnegfail OBJECT-TYPE
            SYNTAX   Counter
            ACCESS   read-only
            STATUS   mandatory
            DESCRIPTION    
                "Number of failed modem negotiation."
            ::= {nvDialstatEntry 23 }
 
        nvDialstatNconnfail OBJECT-TYPE
            SYNTAX   Counter
            ACCESS   read-only
            STATUS   mandatory
            DESCRIPTION    
                "Number of fails after ISDN connection for reasons
		 other than modem negotiation failure."
            ::= {nvDialstatEntry 24 }
 
        nvDialstatNmiscfail OBJECT-TYPE
            SYNTAX   Counter
            ACCESS   read-only
            STATUS   mandatory
            DESCRIPTION    
                "Number of miscellaneous failures not counted elsewhere."
            ::= {nvDialstatEntry 25 }
 
        nvDialstatMaxcall OBJECT-TYPE
            SYNTAX   Counter
            ACCESS   read-only
            STATUS   mandatory
            DESCRIPTION
                "Maximum number concurrently calling."
            ::= {nvDialstatEntry 26 }

        nvDialstatAdSucctim OBJECT-TYPE
            SYNTAX   INTEGER
            ACCESS   read-only
            STATUS   mandatory
            DESCRIPTION
                "Average time for dial-out for successful dial-out request,
			in units of tenths of a second."
            ::= {nvDialstatEntry 27 }

        nvDialstatAdFailtim OBJECT-TYPE
            SYNTAX   INTEGER
            ACCESS   read-only
            STATUS   mandatory
            DESCRIPTION
                "Average time for dial-out for filaed cases,
			in units of tenths of a second."
            ::= {nvDialstatEntry 28 }
         nvDialstatNabredial  OBJECT-TYPE
            SYNTAX   Counter
            ACCESS   read-only
            STATUS   mandatory
            DESCRIPTION    
                " number of aborted redials, JATE redial restriction."
            ::= {nvDialstatEntry 29 }
	    

--
--	frmrstat 
-- 
        nvFrmrstatTable OBJECT-TYPE
           SYNTAX SEQUENCE OF NvFrmrstatEntry
           ACCESS not-accessible
           STATUS mandatory
           DESCRIPTION
                "Framer card statistics table definition. The actual
                framer card database has 17 tables. Each table uses name
                convention: frmrstat plus slot number. This table will
                combine 17 databases into one table. In order to support
                the actual framer card configuration, this table requires
                the slot number"
           ::= { nevadaSystem 37 }
 
        nvFrmrstatEntry OBJECT-TYPE
           SYNTAX NvFrmrstatEntry
           ACCESS not-accessible
           STATUS mandatory
           DESCRIPTION
                "Framer card statistics record definition. The total
                record number is 17. If there is a framer card plugged in
                one of the slot, then the corresponding framer record is
                active. Otherwise the record is not active."
           INDEX { nvFrmrstatSlotIndex }
           ::= { nvFrmrstatTable 1 } 

        NvFrmrstatEntry ::=
           SEQUENCE {
                nvFrmrstatSlotIndex
                        INTEGER,
		nvFrmrstatState
			INTEGER,
		nvFrmrstatFailCause
			INTEGER,
		nvFrmrstatResetTime
			DisplayString,
                nvFrmrstatNumFailures
			INTEGER,
                nvFrmrstatNumReloads
			INTEGER,
		nvFrmrstatTotalCalls
			INTEGER,
                nvFrmrstatCallsPresent
			INTEGER,
                nvFrmrstatNumPortUp
			INTEGER,
		nvFrmrstatNumFailUp
			INTEGER,
                nvFrmrstatNumTxFrames
			INTEGER,
                nvFrmrstatNumRxFrames
			INTEGER,
                nvFrmrstatNumTxBytes
			INTEGER,
                nvFrmrstatNumRxBytes
			INTEGER
		}

        nvFrmrstatSlotIndex OBJECT-TYPE
           SYNTAX INTEGER
           ACCESS read-only
           STATUS mandatory
           DESCRIPTION
                "Framer card slot number."
           ::= { nvFrmrstatEntry 1 }

        nvFrmrstatState OBJECT-TYPE
           SYNTAX INTEGER {
			free(1),
			dead(2),
			dying(3),
			up(4),
			download(6)
		}
           ACCESS read-only
           STATUS mandatory
           DESCRIPTION
                "State of framer card."
           ::= { nvFrmrstatEntry 2 }

        nvFrmrstatFailCause OBJECT-TYPE 
           SYNTAX INTEGER { 
                        none(1), 
                        softfail(2),
                        hardfail(3), 
                        download(6) 
                } 
           ACCESS read-only
           STATUS mandatory
           DESCRIPTION    
                "Reason for last failure."
           ::= { nvFrmrstatEntry 3 }

        nvFrmrstatResetTime OBJECT-TYPE
           SYNTAX DisplayString (SIZE(0..20))
           ACCESS read-only
           STATUS mandatory
           DESCRIPTION
                "Date and Time of last framer card reset."
           ::= { nvFrmrstatEntry 4 }

        nvFrmrstatNumFailures OBJECT-TYPE
           SYNTAX INTEGER
           ACCESS read-only
           STATUS mandatory
           DESCRIPTION
                "Number of download attempts."
           ::= { nvFrmrstatEntry 5 }

        nvFrmrstatNumReloads OBJECT-TYPE
           SYNTAX INTEGER
           ACCESS read-only
           STATUS mandatory
           DESCRIPTION
                "Number of successful reloads."
           ::= { nvFrmrstatEntry 6 }

        nvFrmrstatTotalCalls OBJECT-TYPE
           SYNTAX INTEGER
           ACCESS read-only
           STATUS mandatory
           DESCRIPTION
                "number of smartport calls made."
           ::= { nvFrmrstatEntry 7 }

        nvFrmrstatCallsPresent OBJECT-TYPE
           SYNTAX INTEGER
           ACCESS read-only
           STATUS mandatory
           DESCRIPTION
                "number of calls currently up."
           ::= { nvFrmrstatEntry 8 }

        nvFrmrstatNumPortUp OBJECT-TYPE
           SYNTAX INTEGER
           ACCESS read-only
           STATUS mandatory
           DESCRIPTION
                "number of successful port ups."
           ::= { nvFrmrstatEntry 9 }

        nvFrmrstatNumFailUp OBJECT-TYPE
           SYNTAX INTEGER
           ACCESS read-only
           STATUS mandatory
           DESCRIPTION
                "number of failed port ups."
           ::= { nvFrmrstatEntry 10 }

        nvFrmrstatNumTxFrames OBJECT-TYPE
           SYNTAX INTEGER
           ACCESS read-only
           STATUS mandatory
           DESCRIPTION
                "number of frames transmitted."
           ::= { nvFrmrstatEntry 11 }

        nvFrmrstatNumRxFrames OBJECT-TYPE
           SYNTAX INTEGER
           ACCESS read-only
           STATUS mandatory
           DESCRIPTION
                "number of frames received."
           ::= { nvFrmrstatEntry 12 }

        nvFrmrstatNumTxBytes OBJECT-TYPE
           SYNTAX INTEGER
           ACCESS read-only
           STATUS mandatory
           DESCRIPTION
                "Number of bytes transmitted."
           ::= { nvFrmrstatEntry 13 }

        nvFrmrstatNumRxBytes OBJECT-TYPE
           SYNTAX INTEGER
           ACCESS read-only
           STATUS mandatory
           DESCRIPTION
                "number of bytes received."
           ::= { nvFrmrstatEntry 14 }

--
--      Models / Platform types
--
nvNas  OBJECT IDENTIFIER ::= {nevadaModels 1}



--
--      frstat file
--
nvFrstat        OBJECT IDENTIFIER ::= {nevadaFrameRelay 1}

nvFrstatCurtime OBJECT-TYPE
     SYNTAX   Gauge
     ACCESS   read-only
     STATUS   mandatory
     DESCRIPTION
        "Minutes into current 15-minute cycle
         Statistic is zeroed at startup time."
     ::= {nvFrstat 1 }

nvFrstatTxcurfps OBJECT-TYPE
     SYNTAX   Gauge
     ACCESS   read-only
     STATUS   mandatory
     DESCRIPTION
        "Current snapshot of Tx Frames/Second
         Statistic is zeroed at startup time."
     ::= {nvFrstat 2 }

nvFrstatTxavgfps OBJECT-TYPE
     SYNTAX   Gauge
     ACCESS   read-only
     STATUS   mandatory
     DESCRIPTION
        "Average Tx Frames/Second for 15-minute cycle
         Statistic is zeroed at startup time."
     ::= {nvFrstat 3 }

nvFrstatRxcurfps OBJECT-TYPE
     SYNTAX   Gauge
     ACCESS   read-only
     STATUS   mandatory
     DESCRIPTION
        " Current snapshot of Rx Frames/Second
         Statistic is zeroed at startup time."
     ::= {nvFrstat 4 }

nvFrstatRxavgfps OBJECT-TYPE
     SYNTAX   Gauge
     ACCESS   read-only
     STATUS   mandatory
     DESCRIPTION
        "Average Rx Frames/Second for 15-minute cycle
         Statistic is zeroed at startup time."
     ::= {nvFrstat 5 }

nvFrstatMtxcurfps OBJECT-TYPE
     SYNTAX   Gauge
     ACCESS   read-only
     STATUS   mandatory
     DESCRIPTION
        "Current snapshot of mapped Tx Frames/Second
         Statistic is zeroed at startup time."
     ::= {nvFrstat 6 }

nvFrstatMtxavgfps OBJECT-TYPE
     SYNTAX   Gauge
     ACCESS   read-only
     STATUS   mandatory
     DESCRIPTION
        "Average mapped Tx Frames/Second for 15-minute cycle
         Statistic is zeroed at startup time."
     ::= {nvFrstat 7 }

nvFrstatMrxcurfps OBJECT-TYPE
     SYNTAX   Gauge
     ACCESS   read-only
     STATUS   mandatory
     DESCRIPTION
        "Current snapshot of mapped Rx Frames/Second
         Statistic is zeroed at startup time."
     ::= {nvFrstat 8 }

nvFrstatMrxavgfps OBJECT-TYPE
     SYNTAX   Gauge
     ACCESS   read-only
     STATUS   mandatory
     DESCRIPTION
        "Average mapped Rx Frames/Second for 15-minute cycle
         Statistic is zeroed at startup time."
     ::= {nvFrstat 9 }

nvFrstatDtreset OBJECT-TYPE
     SYNTAX   DisplayString (SIZE (0..20))
     ACCESS   read-only
     STATUS   mandatory
     DESCRIPTION
        "date & time statistics last reset"
      ::= { nvFrstat 10 }

--
--      fristat
--
nvFristat OBJECT IDENTIFIER ::= {nevadaFrameRelay 2}

nvFristatMaxRec OBJECT-TYPE
      SYNTAX   INTEGER
      ACCESS   read-only
      STATUS   mandatory
      DESCRIPTION
                "total number of records allowed in database file."
      ::= {nvFristat 1}

nvFristatNumRec OBJECT-TYPE
      SYNTAX   INTEGER
      ACCESS   read-only
      STATUS   mandatory
      DESCRIPTION
                "number of records in use."
      ::= {nvFristat 2}

nvFristatTable OBJECT-TYPE
      SYNTAX   SEQUENCE OF NvFristatEntry
      ACCESS   not-accessible
      STATUS   mandatory
      DESCRIPTION
               "fristat file."
      ::= {nvFristat 3}

nvFristatEntry OBJECT-TYPE
      SYNTAX   NvFristatEntry
      ACCESS   not-accessible
      STATUS   mandatory
      DESCRIPTION
               "fristat record."
      INDEX    {nvFristatIndex}
      ::= {nvFristatTable 1 }

NvFristatEntry ::=
      SEQUENCE {
      nvFristatIndex
            INTEGER,
      nvFristatPort
            DisplayString,
      nvFristatOperstate
            INTEGER,
      nvFristatLmistate
            INTEGER,
      nvFristatCurseq
            INTEGER,
      nvFristatRcvseq
            INTEGER,
      nvFristatErrorcounts
            Counter,
      nvFristatRxexceszes
            Counter,
      nvFristatRxbaddlcis
            Counter,
      nvFristatDtreset
            DisplayString
               }

nvFristatIndex OBJECT-TYPE
     SYNTAX   INTEGER
     ACCESS   read-only
     STATUS   mandatory
     DESCRIPTION
        "Index of Fristat record"
     ::= {nvFristatEntry 1 }

nvFristatPort OBJECT-TYPE
     SYNTAX   DisplayString (SIZE (0..11))
     ACCESS   read-only
     STATUS   mandatory
     DESCRIPTION
        " Physical Port"
     ::= {nvFristatEntry 2 }

nvFristatOperstate OBJECT-TYPE
     SYNTAX   INTEGER {
                unconnected(1),         -- (+1)
                badFriConfig(2),
                idle(3),
                setup(4),
                active(5)
                }
     ACCESS   read-only
     STATUS   mandatory
     DESCRIPTION
        "FRI Operational state
         Initial status is 0+1."
     ::= {nvFristatEntry 3 }

nvFristatLmistate OBJECT-TYPE
     SYNTAX   INTEGER {
                inactive(1),            -- (+1)
                normal(2),
                error(3)
                }
     ACCESS   read-only
     STATUS   mandatory
     DESCRIPTION
        "LMI Operational state
         Initial status is 0+1."
     ::= {nvFristatEntry 4 }

nvFristatCurseq OBJECT-TYPE
     SYNTAX   INTEGER
     ACCESS   read-only
     STATUS   mandatory
     DESCRIPTION
        "Transmitted LMI sequence number"
     ::= {nvFristatEntry 5 }

nvFristatRcvseq OBJECT-TYPE
     SYNTAX   INTEGER
     ACCESS   read-only
     STATUS   mandatory
     DESCRIPTION
        "Received LMI sequence number"
     ::= {nvFristatEntry 6 }

nvFristatErrorcounts OBJECT-TYPE
     SYNTAX   Counter
     ACCESS   read-only
     STATUS   mandatory
     DESCRIPTION
        "LMI errors during recorded history
         Statistic is zeroed at startup time."
     ::= {nvFristatEntry 7 }

nvFristatRxexceszes OBJECT-TYPE
     SYNTAX   Counter
     ACCESS   read-only
     STATUS   mandatory
     DESCRIPTION
        "Too Large Incoming Frames
         Statistic is zeroed at startup time."
     ::= {nvFristatEntry 8 }

nvFristatRxbaddlcis OBJECT-TYPE
     SYNTAX   Counter
     ACCESS   read-only
     STATUS   mandatory
     DESCRIPTION
        "Invalid dlci Incoming Frames
         Statistic is zeroed at startup time."
     ::= {nvFristatEntry 9 }

nvFristatDtreset OBJECT-TYPE
     SYNTAX   DisplayString (SIZE (0..20))
     ACCESS   read-only
     STATUS   mandatory
     DESCRIPTION
        "date & time statistics last reset"
      ::= { nvFristatEntry 10 }

--
--      frvcstat file
--
nvFrvcstat OBJECT IDENTIFIER ::= {nevadaFrameRelay 3}

nvFrvcstatMaxRec OBJECT-TYPE
      SYNTAX   INTEGER
      ACCESS   read-only
      STATUS   mandatory
      DESCRIPTION
                "total number of records allowed in database file."
      ::= {nvFrvcstat 1}

nvFrvcstatNumRec OBJECT-TYPE
      SYNTAX   INTEGER
      ACCESS   read-only
      STATUS   mandatory
      DESCRIPTION
                "number of records in use."
      ::= {nvFrvcstat 2}

nvFrvcstatTable OBJECT-TYPE
      SYNTAX   SEQUENCE OF NvFrvcstatEntry
      ACCESS   not-accessible
      STATUS   mandatory
      DESCRIPTION
               "frvcstat file."
      ::= {nvFrvcstat 3}

nvFrvcstatEntry OBJECT-TYPE
      SYNTAX   NvFrvcstatEntry
      ACCESS   not-accessible
      STATUS   mandatory
      DESCRIPTION
               "frvcstat record."
      INDEX {nvFrvcstatIndex}
      ::= {nvFrvcstatTable 1 }

NvFrvcstatEntry ::=
      SEQUENCE {
      nvFrvcstatIndex
            INTEGER,
      nvFrvcstatService
            DisplayString,
      nvFrvcstatServiceid
            DisplayString,
      nvFrvcstatFri
            INTEGER,
      nvFrvcstatDlci
            INTEGER,
      nvFrvcstatStatus
            INTEGER,
      nvFrvcstatTxcongstatus
            INTEGER,
      nvFrvcstatRxbufdepletion
            Gauge,
      nvFrvcstatOutputrate
            Gauge,
      nvFrvcstatInputrate
            Gauge,
      nvFrvcstatExcessdatas
            Counter,
      nvFrvcstatTxframes
            Counter,
      nvFrvcstatRxframes
            Counter,
      nvFrvcstatDrprxs
            Counter,
      nvFrvcstatDrprxdes
            Counter,
      nvFrvcstatDtreset
      	     DisplayString
               }

nvFrvcstatIndex OBJECT-TYPE
     SYNTAX   INTEGER
     ACCESS   read-only
     STATUS   mandatory
     DESCRIPTION
        "Index of Frvcstat"
     ::= {nvFrvcstatEntry 1 }

nvFrvcstatService OBJECT-TYPE
     SYNTAX   DisplayString (SIZE (0..10))
     ACCESS   read-only
     STATUS   mandatory
     DESCRIPTION
        "Connected Component ID  "
     ::= {nvFrvcstatEntry 2 }

nvFrvcstatServiceid OBJECT-TYPE
     SYNTAX   DisplayString (SIZE(0..32))
     ACCESS   read-only
     STATUS   mandatory
     DESCRIPTION
        "Service Instance."
     ::= {nvFrvcstatEntry 3 }

nvFrvcstatFri OBJECT-TYPE
     SYNTAX   INTEGER
     ACCESS   read-only
     STATUS   mandatory
     DESCRIPTION
        "FRI of this PVC (FRICONF recnum)"
     ::= {nvFrvcstatEntry 4 }

nvFrvcstatDlci OBJECT-TYPE
     SYNTAX   INTEGER
     ACCESS   read-only
     STATUS   mandatory
     DESCRIPTION
        "DLCI of this PVC"
     ::= {nvFrvcstatEntry 5 }

nvFrvcstatStatus OBJECT-TYPE
     SYNTAX   INTEGER {
                free(1),                -- (+1)
                badPvcConfig(2),
                disabled(3),
                badDLCI(4),
                operDisabled(5),
                friFull(6),
                noFri(7),
                friDown(8),
                friError(9),
                pvcInit(10),
                pvcDown(11),
                pvcUp(12),
                pvcInactive(13)
                }
     ACCESS   read-only
     STATUS   mandatory
     DESCRIPTION
        "PVC Operational State
         Initial status is 0+1."
     ::= {nvFrvcstatEntry 6 }

nvFrvcstatTxcongstatus OBJECT-TYPE
     SYNTAX   INTEGER {
                none(1),        -- (+1)
                low(2),
                medium(3),
                high(4)
                }
     ACCESS   read-only
     STATUS   mandatory
     DESCRIPTION
        "Transmit Congestion Status
         Initial status is 0+1."
     ::= {nvFrvcstatEntry 7 }

nvFrvcstatRxbufdepletion OBJECT-TYPE
     SYNTAX   Gauge
     ACCESS   read-only
     STATUS   mandatory
     DESCRIPTION
        "Receive Buffer Depletion
         Statistic is zeroed at startup time."
     ::= {nvFrvcstatEntry 8 }

nvFrvcstatOutputrate OBJECT-TYPE
     SYNTAX   Gauge
     ACCESS   read-only
     STATUS   mandatory
     DESCRIPTION
        "Output during last period (bytes)
         Statistic is zeroed at startup time."
     ::= {nvFrvcstatEntry 9 }

nvFrvcstatInputrate OBJECT-TYPE
     SYNTAX   Gauge
     ACCESS   read-only
     STATUS   mandatory
     DESCRIPTION
        "Input during last period (bytes)
         Statistic is zeroed at startup time."
     ::= {nvFrvcstatEntry 10 }

nvFrvcstatExcessdatas OBJECT-TYPE
     SYNTAX   Counter
     ACCESS   read-only
     STATUS   mandatory
     DESCRIPTION
        "Data over output limit
         Statistic is zeroed at startup time."
     ::= {nvFrvcstatEntry 11 }

nvFrvcstatTxframes OBJECT-TYPE
     SYNTAX   Counter
     ACCESS   read-only
     STATUS   mandatory
     DESCRIPTION
        "Transmitted Frame Counter
         Statistic is zeroed at startup time."
     ::= {nvFrvcstatEntry 12 }

nvFrvcstatRxframes OBJECT-TYPE
     SYNTAX   Counter
     ACCESS   read-only
     STATUS   mandatory
     DESCRIPTION
        "Received Frame Counter
         Statistic is zeroed at startup time."
     ::= {nvFrvcstatEntry 13 }

nvFrvcstatDrprxs OBJECT-TYPE
     SYNTAX   Counter
     ACCESS   read-only
     STATUS   mandatory
     DESCRIPTION
        "Received Frames Dropped
         Statistic is zeroed at startup time."
     ::= {nvFrvcstatEntry 14 }

nvFrvcstatDrprxdes OBJECT-TYPE
     SYNTAX   Counter
     ACCESS   read-only
     STATUS   mandatory
     DESCRIPTION
        "Received DE Frames Dropped
         Statistic is zeroed at startup time."
     ::= {nvFrvcstatEntry 15 }

nvFrvcstatDtreset OBJECT-TYPE
     SYNTAX   DisplayString (SIZE (0..20))
     ACCESS   read-only
     STATUS   mandatory
     DESCRIPTION
        "date & time statistics last reset"
      ::= { nvFrvcstatEntry 16 }


-- The records in this file configure Frame Relay Interfaces
-- There is one record per Frame Relay Interface

nvFriconf OBJECT IDENTIFIER ::= { nevadaFrameRelay 4 }

nvFriconfMaxRec OBJECT-TYPE
      SYNTAX   INTEGER
      ACCESS   read-only
      STATUS   mandatory
      DESCRIPTION
                "total number of records allowed in database file."
      ::= {nvFriconf 1}

nvFriconfNumRec OBJECT-TYPE
      SYNTAX   INTEGER
      ACCESS   read-only
      STATUS   mandatory
      DESCRIPTION
                "number of records in use."
      ::= {nvFriconf 2}

nvFriconfTable OBJECT-TYPE
      SYNTAX   SEQUENCE OF NvFriconfEntry
      ACCESS   not-accessible
      STATUS   mandatory
      DESCRIPTION
               "friconf file."
      ::= { nvFriconf 3 }

nvFriconfEntry OBJECT-TYPE
      SYNTAX   NvFriconfEntry
      ACCESS   not-accessible
      STATUS   mandatory
      DESCRIPTION
               "friconf record."
      INDEX { nvFriconfIndex }
      ::= { nvFriconfTable 1 }

NvFriconfEntry ::=
      SEQUENCE {
      nvFriconfIndex
            INTEGER,
      nvFriconfPort
            DisplayString,
      nvFriconfRsrcpool
            DisplayString,
      nvFriconfMaxfrmsz
            INTEGER,
      nvFriconfLmitype
            INTEGER,
      nvFriconfMode
            INTEGER,
      nvFriconfDlci
            INTEGER,
      nvFriconfnT1
            INTEGER,
      nvFriconfnT2
            INTEGER,
      nvFriconfnT3
            INTEGER,
      nvFriconfnN1
            INTEGER,
      nvFriconfnN2
            INTEGER,
      nvFriconfnN3
            INTEGER,
      nvFriconfnN4
            INTEGER,
      nvFriconfnP1
            INTEGER,
      nvFriconfStatus
            INTEGER
               }

nvFriconfIndex OBJECT-TYPE
     SYNTAX   INTEGER
     ACCESS   read-only
     STATUS   mandatory
     DESCRIPTION
        "Index of friconf record"
      ::= { nvFriconfEntry 1 }

nvFriconfPort OBJECT-TYPE
     SYNTAX   DisplayString (SIZE (0..11))
     ACCESS   read-write
     STATUS   mandatory
     DESCRIPTION
"Physical Port (port)
"
     ::= { nvFriconfEntry 2 }

nvFriconfRsrcpool OBJECT-TYPE
     SYNTAX   DisplayString (SIZE (0..11))
     ACCESS   read-write
     STATUS   mandatory
     DESCRIPTION
"Resource pool
"
     ::= { nvFriconfEntry 3 }

nvFriconfMaxfrmsz OBJECT-TYPE
     SYNTAX   INTEGER (0..65535)
     ACCESS   read-write
     STATUS   mandatory
     DESCRIPTION
"Maximum Frame Size (maxfrmsz)
Default value is 140."
     ::= { nvFriconfEntry 6 }

nvFriconfLmitype OBJECT-TYPE
     SYNTAX   INTEGER {
                nolmi(1),     -- No LMI (+1)
                go4(2),     -- Group of 4
                ansi(3),     -- ANSI LMI
                itu(4)      -- ITU (CCITT) LMI
                }
     ACCESS   read-write
     STATUS   mandatory
     DESCRIPTION
"Style of LMI operation (lmitype)
Default value is go4 (1+1)."
     ::= { nvFriconfEntry 8 }

nvFriconfMode OBJECT-TYPE
     SYNTAX   INTEGER {
                user(1),     -- User Side (+1)
                net(2)      -- Network Side
                }
     ACCESS   read-write
     STATUS   mandatory
     DESCRIPTION
"Mode of FRI Operation (mode)
Default value is  user (0+1)."
     ::= { nvFriconfEntry 9 }

nvFriconfDlci OBJECT-TYPE
     SYNTAX   INTEGER (0..1023)
     ACCESS   read-write
     STATUS   mandatory
     DESCRIPTION
"LMI's DLCI (dlci)
Default value is 1023."
     ::= { nvFriconfEntry 11 }

nvFriconfnT1 OBJECT-TYPE
     SYNTAX   INTEGER (5..30)
     ACCESS   read-write
     STATUS   mandatory
     DESCRIPTION
"LMI Polling Interval (nT1)
Default value is 10."
     ::= { nvFriconfEntry 12 }

nvFriconfnT2 OBJECT-TYPE
     SYNTAX   INTEGER (5..30)
     ACCESS   read-write
     STATUS   mandatory
     DESCRIPTION
"Max Time Between Polls (nT2)
Default value is 15."
     ::= { nvFriconfEntry 13 }

nvFriconfnT3 OBJECT-TYPE
     SYNTAX   INTEGER (5..30)
     ACCESS   read-write
     STATUS   mandatory
     DESCRIPTION
"Max Polls per nN4 (nT3)
Default value is 20."
     ::= { nvFriconfEntry 14 }

nvFriconfnN1 OBJECT-TYPE
     SYNTAX   INTEGER (1..255)
     ACCESS   read-write
     STATUS   mandatory
     DESCRIPTION
"LMI Full Status Poll Frequency (nN1)
Default value is 6."
     ::= { nvFriconfEntry 19 }

nvFriconfnN2 OBJECT-TYPE
     SYNTAX   INTEGER (1..10)
     ACCESS   read-write
     STATUS   mandatory
     DESCRIPTION
"LMI Error Threshold (nN2)
Default value is 2."
     ::= { nvFriconfEntry 20 }

nvFriconfnN3 OBJECT-TYPE
     SYNTAX   INTEGER (1..10)
     ACCESS   read-write
     STATUS   mandatory
     DESCRIPTION
"LMI Error History Length (nN3)
Default value is 4."
     ::= { nvFriconfEntry 21 }

nvFriconfnN4 OBJECT-TYPE
     SYNTAX   INTEGER
     ACCESS   read-only
     STATUS   mandatory
     DESCRIPTION
"Max Polls Within nT3 (nN4).
Default value is 5."
     ::= { nvFriconfEntry 22 }

nvFriconfnP1 OBJECT-TYPE
     SYNTAX   INTEGER (0..65535)
     ACCESS   read-write
     STATUS   mandatory
     DESCRIPTION
"Max PVCs allowed FRI (nP1)
Default value is 1."
     ::= { nvFriconfEntry 23 }

nvFriconfStatus OBJECT-TYPE
     SYNTAX   INTEGER {
                valid(1),
                invalid(2)
                }
     ACCESS   read-write
     STATUS   mandatory
     DESCRIPTION
           "Operation status. Add the record to the table (valid) or
           delete the record from the table (invalid)."
     ::= { nvFriconfEntry 29 }

-- The records in this file configure Frame Relay PVCs
-- There is one record per Frame Relay PVC

nvFrvcconf OBJECT IDENTIFIER ::= { nevadaFrameRelay 5 }

nvFrvcconfMaxRec OBJECT-TYPE
      SYNTAX   INTEGER
      ACCESS   read-only
      STATUS   mandatory
      DESCRIPTION
                "total number of records allowed in database file."
      ::= {nvFrvcconf 1}

nvFrvcconfNumRec OBJECT-TYPE
      SYNTAX   INTEGER
      ACCESS   read-only
      STATUS   mandatory
      DESCRIPTION
                "number of records in use."
      ::= {nvFrvcconf 2}

nvFrvcconfTable OBJECT-TYPE
      SYNTAX   SEQUENCE OF NvFrvcconfEntry
      ACCESS   not-accessible
      STATUS   mandatory
      DESCRIPTION
               "frvcconf file."
      ::= { nvFrvcconf 3 }

nvFrvcconfEntry OBJECT-TYPE
      SYNTAX   NvFrvcconfEntry
      ACCESS   not-accessible
      STATUS   mandatory
      DESCRIPTION
               "frvcconf record."
      INDEX { nvFrvcconfIndex }
      ::= { nvFrvcconfTable 1 }

NvFrvcconfEntry ::=
      SEQUENCE {
      nvFrvcconfIndex
            INTEGER,
      nvFrvcconfDlci
            INTEGER,
      nvFrvcconfFri
            INTEGER,
      nvFrvcconfMappedpvc
            INTEGER,
      nvFrvcconfEnable
            INTEGER,
      nvFrvcconfT
            INTEGER,
      nvFrvcconfBc
            INTEGER,
      nvFrvcconfBe
            INTEGER,
      nvFrvcconfN
            INTEGER,
      nvFrvcconfRxbufspac
            INTEGER,
      nvFrvcconfRxcgthres
            INTEGER,
      nvFrvcconfRxcgclear
            INTEGER,
      nvFrvcconfStatus
            INTEGER
               }

nvFrvcconfIndex OBJECT-TYPE
     SYNTAX   INTEGER
     ACCESS   read-only
     STATUS   mandatory
     DESCRIPTION
        "Index of frvcconf record"
      ::= { nvFrvcconfEntry 1 }

nvFrvcconfDlci OBJECT-TYPE
     SYNTAX   INTEGER (0..1023)
     ACCESS   read-write
     STATUS   mandatory
     DESCRIPTION
"DLCI of this PVC (dlci)
"
     ::= { nvFrvcconfEntry 2 }

nvFrvcconfFri OBJECT-TYPE
     SYNTAX   INTEGER (0..255)
     ACCESS   read-write
     STATUS   mandatory
     DESCRIPTION
"FRI of this PVC (fri)
"
     ::= { nvFrvcconfEntry 6 }

nvFrvcconfMappedpvc OBJECT-TYPE
     SYNTAX   INTEGER (0..65535)
     ACCESS   read-write
     STATUS   mandatory
     DESCRIPTION
"Recnum of Mapped PVC (mappedpvc)
"
     ::= { nvFrvcconfEntry 8 }

nvFrvcconfEnable OBJECT-TYPE
     SYNTAX   INTEGER {
                no(1),     -- Not Enabled (+1)
                yes(2)      -- Enabled
                }
     ACCESS   read-write
     STATUS   mandatory
     DESCRIPTION
"Is this PVC enabled? (enable)
Default value is yse (1+1)."
     ::= { nvFrvcconfEntry 11 }

nvFrvcconfT OBJECT-TYPE
     SYNTAX   INTEGER (0..65535)
     ACCESS   read-write
     STATUS   mandatory
     DESCRIPTION
"Rate Monitoring Period (t)
"
     ::= { nvFrvcconfEntry 12 }

nvFrvcconfBc OBJECT-TYPE
     SYNTAX   INTEGER (0..65535)
     ACCESS   read-write
     STATUS   mandatory
     DESCRIPTION
"Committed Burst Size (bc)
"
     ::= { nvFrvcconfEntry 15 }

nvFrvcconfBe OBJECT-TYPE
     SYNTAX   INTEGER (0..65535)
     ACCESS   read-write
     STATUS   mandatory
     DESCRIPTION
"Excess Burst Size (be)
"
     ::= { nvFrvcconfEntry 16 }

nvFrvcconfN OBJECT-TYPE
     SYNTAX   INTEGER (0..65535)
     ACCESS   read-write
     STATUS   mandatory
     DESCRIPTION
"Incoming BECN Threshold (n)
"
     ::= { nvFrvcconfEntry 17 }

nvFrvcconfRxbufspac OBJECT-TYPE
     SYNTAX   INTEGER (1..9400)
     ACCESS   read-write
     STATUS   mandatory
     DESCRIPTION
"Receive Buffer Space (rxbufspac)
Default value is 1."
     ::= { nvFrvcconfEntry 20 }

nvFrvcconfRxcgthres OBJECT-TYPE
     SYNTAX   INTEGER (0..100)
     ACCESS   read-write
     STATUS   mandatory
     DESCRIPTION
"Rcv Congestion Thrshld (rxcgthres)
"
     ::= { nvFrvcconfEntry 21 }

nvFrvcconfRxcgclear OBJECT-TYPE
     SYNTAX   INTEGER (0..100)
     ACCESS   read-write
     STATUS   mandatory
     DESCRIPTION
"Rcv Cong. Clear Thrshld (rxcgclear)."
     ::= { nvFrvcconfEntry 22 }

nvFrvcconfStatus OBJECT-TYPE
     SYNTAX   INTEGER {
                valid(1),
                invalid(2)
                }
     ACCESS   read-write
     STATUS   mandatory
     DESCRIPTION
           "Operation status. Add the record to the table (valid) or
           delete the record from the table (invalid)."
     ::= { nvFrvcconfEntry 27 }

--
--      iticstat file
--
nvIticstat OBJECT IDENTIFIER    ::= {nevadaIti 1}

nvIticstatMaxRec OBJECT-TYPE
      SYNTAX   INTEGER
      ACCESS   read-only
      STATUS   mandatory
      DESCRIPTION
                "total number of records allowed in database file."
      ::= {nvIticstat 1}

nvIticstatNumRec OBJECT-TYPE
      SYNTAX   INTEGER
      ACCESS   read-only
      STATUS   mandatory
      DESCRIPTION
                "number of records in use."
      ::= {nvIticstat 2}

nvIticstatTable OBJECT-TYPE
      SYNTAX   SEQUENCE OF NvIticstatEntry
      ACCESS   not-accessible
      STATUS   mandatory
      DESCRIPTION
               "iticstat file."
      ::= {nvIticstat 3}

nvIticstatEntry OBJECT-TYPE
      SYNTAX   NvIticstatEntry
      ACCESS   not-accessible
      STATUS   mandatory
      DESCRIPTION
               "iticstat record."
      INDEX {nvIticstatIndex}
      ::= {nvIticstatTable 1 }

NvIticstatEntry ::=
      SEQUENCE {
      nvIticstatIndex
            INTEGER,
      nvIticstatClassname
            DisplayString,
      nvIticstatNnccs
            Counter,
      nvIticstatNnfails
            Counter,
      nvIticstatNpassfails
            Counter,
      nvIticstatCurcalls
            Counter,
      nvIticstatAvgtime		   --AF
            Counter,		   --AF
      nvIticstatMaxcalls
            Counter,
      nvIticstatNumcalls
            INTEGER,
      nvIticstatDtreset
            DisplayString,
      nvIticstatTcalls
            Counter,
      nvIticstatN300bd
            Counter,
      nvIticstatN1200bd
            Counter,
      nvIticstatN2400bd
            Counter,
      nvIticstatN9600bd
            Counter,
      nvIticstatN14400bd
            Counter,
      nvIticstatN28800bd
            Counter,
      nvIticstatFailneg
            Counter,
      nvIticstatTrmdscdat
            Counter,
      nvIticstatLoscarsu
            Counter,
      nvIticstatLoscarcip
            Counter,
      nvIticstatLoscardat
            Counter,
      nvIticstatTrmdscsu
            Counter,
      nvIticstatTrmdsccip
            Counter,
      nvIticstatNcurIncom
            Counter,
      nvIticstatNcurOutgo
            Counter,
      nvIticstatMaxIncom
            Counter,
      nvIticstatMaxOutgo
            Counter,
      nvIticstatNumIncom
            Counter,
      nvIticstatNumOutgo
            Counter,
      nvIticstatNncr
	    Counter
               }

nvIticstatIndex OBJECT-TYPE
     SYNTAX   INTEGER
     ACCESS   read-only
     STATUS   mandatory
     DESCRIPTION
        "Index of iticstat record"
     ::= {nvIticstatEntry 1 }

nvIticstatClassname OBJECT-TYPE
     SYNTAX   DisplayString (SIZE (0..10))
     ACCESS   read-only
     STATUS   mandatory
     DESCRIPTION
        "Name of class.
         This field identifies which class the statistics in this record
         pertain to."
     ::= {nvIticstatEntry 2 }

nvIticstatNnccs OBJECT-TYPE
     SYNTAX   Counter
     ACCESS   read-only
     STATUS   mandatory
     DESCRIPTION
        "number of network connection commands.
         Total number of network originated calls to this class.
         Statistic is zeroed at startup time."
     ::= {nvIticstatEntry 3 }

nvIticstatNnfails OBJECT-TYPE
     SYNTAX   Counter
     ACCESS   read-only
     STATUS   mandatory
     DESCRIPTION
        "number of network connection failures.
         Total number of network connection commands that failed.
         Statistic is zeroed at startup time."
     ::= {nvIticstatEntry 4 }

nvIticstatNpassfails OBJECT-TYPE
     SYNTAX   Counter
     ACCESS   read-only
     STATUS   mandatory
     DESCRIPTION
        "number of password failures.
         Total number of password failures for this class.
         Statistic is zeroed at startup time."
     ::= {nvIticstatEntry 5 }

nvIticstatCurcalls OBJECT-TYPE                          --AF
     SYNTAX   Counter					--AF
     ACCESS   read-only					--AF
     STATUS   mandatory					--AF
     DESCRIPTION					--AF
        "Current number of calls."			--AF
     ::={nvIticstatEntry 6}				--AF
     							--AF
nvIticstatAvgtime OBJECT-TYPE				--AF
     SYNTAX   Counter					--AF
     ACCESS   read-only					--AF
     STATUS   mandatory					--AF
     DESCRIPTION					--AF
        "Average number of seconds per call."		--AF
     ::={nvIticstatEntry 7}				--AF
							--AF
nvIticstatMaxcalls OBJECT-TYPE				--AF
     SYNTAX   Counter					--AF
     ACCESS   read-only					--AF
     STATUS   mandatory					--AF
     DESCRIPTION					--AF
        "Maximum concurrent calls."			--AF
     ::={nvIticstatEntry 8}				--AF
							--AF
nvIticstatNumcalls OBJECT-TYPE
     SYNTAX   INTEGER
     ACCESS   read-only
     STATUS   mandatory
     DESCRIPTION
        "Total number of successful modem connctions."
     ::={nvIticstatEntry 9}

nvIticstatDtreset OBJECT-TYPE
     SYNTAX   DisplayString (SIZE (0..20))
     ACCESS   read-only
     STATUS   mandatory
     DESCRIPTION
        "date & time statistics last reset"
      ::= { nvIticstatEntry 10 }

nvIticstatTcalls OBJECT-TYPE
     SYNTAX   Counter   
     ACCESS   read-only
     STATUS   mandatory
     DESCRIPTION
        "Total number of hostcalls."
     ::={nvIticstatEntry 11 }

nvIticstatN300bd OBJECT-TYPE
     SYNTAX   Counter   
     ACCESS   read-only
     STATUS   mandatory
     DESCRIPTION
        "300 up to 1200 baud calls received."
     ::={nvIticstatEntry 12}

nvIticstatN1200bd OBJECT-TYPE
     SYNTAX   Counter   
     ACCESS   read-only
     STATUS   mandatory
     DESCRIPTION
        "1200 up to 2400 baud calls received."
     ::={nvIticstatEntry 13}

nvIticstatN2400bd OBJECT-TYPE
     SYNTAX   Counter   
     ACCESS   read-only
     STATUS   mandatory
     DESCRIPTION
        "2400 up to 9600 baud calls received."
     ::={nvIticstatEntry 14}

nvIticstatN9600bd OBJECT-TYPE
     SYNTAX   Counter   
     ACCESS   read-only
     STATUS   mandatory
     DESCRIPTION
        "9600 up to 14400 baud calls received."
     ::={nvIticstatEntry 15 }

nvIticstatN14400bd OBJECT-TYPE
     SYNTAX   Counter   
     ACCESS   read-only
     STATUS   mandatory
     DESCRIPTION
        "14400 up to 28800 baud calls received."
     ::={nvIticstatEntry 16 }

nvIticstatN28800bd OBJECT-TYPE
     SYNTAX   Counter   
     ACCESS   read-only
     STATUS   mandatory
     DESCRIPTION
        "28800 baud calls and above received."
     ::={nvIticstatEntry 17}

nvIticstatFailneg OBJECT-TYPE
     SYNTAX   Counter   
     ACCESS   read-only
     STATUS   mandatory
     DESCRIPTION
        "Calls disconnected during modem negotiation."
     ::={nvIticstatEntry 18}

nvIticstatTrmdscdat OBJECT-TYPE
     SYNTAX   Counter   
     ACCESS   read-only
     STATUS   mandatory
     DESCRIPTION
        "Calls disconnected by terminal during data transfer."
     ::={nvIticstatEntry 19}

nvIticstatLoscarsu OBJECT-TYPE
     SYNTAX   Counter   
     ACCESS   read-only
     STATUS   mandatory
     DESCRIPTION
        "Calls disconnected during setup phase."
     ::={nvIticstatEntry 20}

nvIticstatLoscarcip OBJECT-TYPE
     SYNTAX   Counter   
     ACCESS   read-only
     STATUS   mandatory
     DESCRIPTION
        "Calls disconnected during connection phase."
     ::={nvIticstatEntry 21}

nvIticstatLoscardat OBJECT-TYPE
     SYNTAX   Counter   
     ACCESS   read-only
     STATUS   mandatory
     DESCRIPTION
        "Calls disconnected during data transfer."
     ::={nvIticstatEntry 22}

nvIticstatTrmdscsu OBJECT-TYPE
     SYNTAX   Counter   
     ACCESS   read-only
     STATUS   mandatory
     DESCRIPTION
        "Calls disconnected by terminal during setup."
     ::={nvIticstatEntry 23}

nvIticstatTrmdsccip OBJECT-TYPE
     SYNTAX   Counter   
     ACCESS   read-only
     STATUS   mandatory
     DESCRIPTION
        "Calls disconnected by terminal during modem negotiation."
     ::={nvIticstatEntry 24}

nvIticstatNcurIncom OBJECT-TYPE
     SYNTAX   Counter
     ACCESS   read-only
     STATUS   mandatory
     DESCRIPTION
        "Number of Current Incoming Calls."
     ::={nvIticstatEntry 25}

nvIticstatNcurOutgo OBJECT-TYPE 
     SYNTAX   Counter 
     ACCESS   read-only 
     STATUS   mandatory 
     DESCRIPTION 
        "Number of Current Outgoing Calls."
     ::={nvIticstatEntry 26} 
 
nvIticstatMaxIncom OBJECT-TYPE 
     SYNTAX   Counter 
     ACCESS   read-only 
     STATUS   mandatory 
     DESCRIPTION 
        "Maximum number of Incoming Calls."
     ::={nvIticstatEntry 27} 
 
nvIticstatMaxOutgo OBJECT-TYPE 
     SYNTAX   Counter 
     ACCESS   read-only 
     STATUS   mandatory 
     DESCRIPTION 
        "Maximum number of Outgoing Calls."
     ::={nvIticstatEntry 28} 
 
nvIticstatNumIncom OBJECT-TYPE 
     SYNTAX   Counter 
     ACCESS   read-only 
     STATUS   mandatory 
     DESCRIPTION 
        "Number of Successful Incoming Calls."
     ::={nvIticstatEntry 29} 
 
nvIticstatNumOutgo OBJECT-TYPE 
     SYNTAX   Counter 
     ACCESS   read-only 
     STATUS   mandatory 
     DESCRIPTION 
        "Number of Successful Outgoing Calls."
     ::={nvIticstatEntry 30} 

nvIticstatNncr OBJECT-TYPE
     SYNTAX   Counter
     ACCESS   read-only
     STATUS   mandatory
     DESCRIPTION
        "number of network connection commands.
         Count of virtual circuits initiated from ITI port."
     ::= {nvIticstatEntry 31 }
 
--
--      itipstat file
--
nvItipstat OBJECT IDENTIFIER    ::= {nevadaIti 2}

nvItipstatMaxRec OBJECT-TYPE
      SYNTAX   INTEGER
      ACCESS   read-only
      STATUS   mandatory
      DESCRIPTION
                "total number of records allowed in database file."
      ::= {nvItipstat 1}

nvItipstatNumRec OBJECT-TYPE
      SYNTAX   INTEGER
      ACCESS   read-only
      STATUS   mandatory
      DESCRIPTION
                "number of records in use."
      ::= {nvItipstat 2}

nvItipstatTable OBJECT-TYPE
      SYNTAX   SEQUENCE OF NvItipstatEntry
      ACCESS   not-accessible
      STATUS   mandatory
      DESCRIPTION
               "itipstat file."
      ::= {nvItipstat 3}

nvItipstatEntry OBJECT-TYPE
      SYNTAX   NvItipstatEntry
      ACCESS   not-accessible
      STATUS   mandatory
      DESCRIPTION
               "itipstat record."
      INDEX {nvItipstatIndex}
      ::= {nvItipstatTable 1 }

NvItipstatEntry ::=
      SEQUENCE {
      nvItipstatIndex
            INTEGER,
      nvItipstatPortname
            DisplayString,
      nvItipstatReserve1
            DisplayString,
      nvItipstatAcct
            DisplayString,
      nvItipstatClassname
            DisplayString,
      nvItipstatSrcadr
            DisplayString,
      nvItipstatDstadr
            DisplayString,
      nvItipstatTxPsze
            INTEGER,
      nvItipstatRxPsze
            INTEGER,
      nvItipstatTxWsze
            INTEGER,
      nvItipstatRxWsze
            INTEGER,
      nvItipstatTxTput
            INTEGER,
      nvItipstatRxTput
            INTEGER,
      nvItipstatCugtype
            INTEGER,
      nvItipstatCug
            INTEGER,
      nvItipstatRpoa
            INTEGER,
      nvItipstatRevf
            INTEGER,
      nvItipstatPrio
            INTEGER,
      nvItipstatFast
            INTEGER,
      nvItipstatPvc
            INTEGER,
      nvItipstatNdcode
            INTEGER,
      nvItipstatNddiag
            INTEGER,
      nvItipstatNdorigin
            INTEGER,
      nvItipstatNrcode
            INTEGER,
      nvItipstatNrdiag
            INTEGER,
      nvItipstatOrg
            INTEGER,
      nvItipstatState
            INTEGER,
      nvItipstatUserdata
            DisplayString,
      nvItipstatUsername
            DisplayString,
      nvItipstatX28type
            INTEGER,
      nvItipstatX3type
            INTEGER,
      nvItipstatReservet
            DisplayString,
      nvItipstatNtccs
            Counter,
      nvItipstatNnccs
            Counter,
      nvItipstatNnfails
            Counter,
      nvItipstatNtxpaks
            Counter,
      nvItipstatNrxpaks
            Counter,
      nvItipstatNtxresets
            Counter,
      nvItipstatNrxresets
            Counter,
      nvItipstatNctxpaks
            Counter,
      nvItipstatNcrxpaks
            Counter,
      nvItipstatNctxresets
            Counter,
      nvItipstatNcrxresets
            Counter,
      nvItipstatNinputs
            Counter,
      nvItipstatNoutputs
            Counter,
      nvItipstatParam
            DisplayString,
      nvItipstatPreparam
            DisplayString,
      nvItipstatDtreset
            DisplayString,
      nvItipstatId
	    DisplayString,
      nvItipstatNtconn
	    Counter,
      nvItipstatNtdc
	    Counter,
      nvItipstatNncr
	    Counter,
      nvItipstatNtimeout
	    Counter
        }

nvItipstatIndex OBJECT-TYPE
     SYNTAX   INTEGER
     ACCESS   read-only
     STATUS   mandatory
     DESCRIPTION
        "Index of itipstat"
     ::= {nvItipstatEntry 1 }

nvItipstatPortname OBJECT-TYPE
     SYNTAX   DisplayString (SIZE (0..4))
     ACCESS   read-only
     STATUS   mandatory
     DESCRIPTION
        "Name of port.
         This field identifies which port the statistics in this record pertain
         to."
     ::= {nvItipstatEntry 2 }

nvItipstatReserve1 OBJECT-TYPE
     SYNTAX   DisplayString (SIZE (0..2))
     ACCESS   read-only
     STATUS   obsolete
     DESCRIPTION
        "OBSOLETE - removed field."
     ::= {nvItipstatEntry 3 }

nvItipstatAcct OBJECT-TYPE
     SYNTAX   DisplayString (SIZE (0..10))
     ACCESS   read-only
     STATUS   mandatory
     DESCRIPTION
        "accounting id."
     ::= {nvItipstatEntry 4 }

nvItipstatClassname OBJECT-TYPE
     SYNTAX   DisplayString (SIZE (0..10))
     ACCESS   read-only
     STATUS   mandatory
     DESCRIPTION
        "iti class: Current user class using this port.
         NOTE: Order of the following fields corresponds to subset of NSCC structure.
          The code uses block copies for these fields and assumes the above
          condition is always true."
     ::= {nvItipstatEntry 5 }

nvItipstatSrcadr OBJECT-TYPE
     SYNTAX   DisplayString (SIZE (0..16))
     ACCESS   read-only
     STATUS   mandatory
     DESCRIPTION
        "source address: Source network address."
     ::= {nvItipstatEntry 6 }

nvItipstatDstadr OBJECT-TYPE
     SYNTAX   DisplayString (SIZE (0..16))
     ACCESS   read-only
     STATUS   mandatory
     DESCRIPTION
        "destination address: Destination network address."
     ::= {nvItipstatEntry 7 }

nvItipstatTxPsze OBJECT-TYPE
     SYNTAX   INTEGER   {
                        pktUndefined(1),        -- (+1)
                        pkt16(5),
                        pkt32(6),
                        pkt64(7),
                        pkt128(8),
                        pkt256(9),
                        pkt512(10),
                        pkt1024(11),
                        pkt2048(12),
                        pkt4096(13)
                        }
     ACCESS   read-only
     STATUS   mandatory
     DESCRIPTION
        "packet size: Transmit Packet size used. "
     ::= {nvItipstatEntry 8 }

nvItipstatRxPsze OBJECT-TYPE
     SYNTAX   INTEGER   {
                        pktUndefined(1),        -- (+1)
                        pkt16(5),
                        pkt32(6),
                        pkt64(7),
                        pkt128(8),
                        pkt256(9),
                        pkt512(10),
                        pkt1024(11),
                        pkt2048(12),
                        pkt4096(13)
                        }
     ACCESS   read-only
     STATUS   mandatory
     DESCRIPTION
        "packet size: Receive Packet size used. "
     ::= {nvItipstatEntry 9 }

nvItipstatTxWsze OBJECT-TYPE
     SYNTAX   INTEGER (0..128)
     ACCESS   read-only
     STATUS   mandatory
     DESCRIPTION
        "window size: transmit Window size used."
     ::= {nvItipstatEntry 10 }

nvItipstatRxWsze OBJECT-TYPE
     SYNTAX   INTEGER (0..127)
     ACCESS   read-only
     STATUS   mandatory
     DESCRIPTION
        "window size: receive Window size used."
     ::= {nvItipstatEntry 11 }

nvItipstatTxTput OBJECT-TYPE
     SYNTAX   INTEGER   {
                        tcUndefined(1),         -- (+1)
                        tc75(4),
                        tc150(5),
                        tc300(6),
                        tc600(7),
                        tc1200(8),
                        tc2400(9),
                        tc4800(10),
                        tc9600(11),
                        tc19200(12),
                        tc48000(13)
                        }
     ACCESS   read-only
     STATUS   mandatory
     DESCRIPTION
        "throughput class: transmit Throughput class used. "
     ::= {nvItipstatEntry 12 }

nvItipstatRxTput OBJECT-TYPE
     SYNTAX   INTEGER   {
                        tcUndefined(1),         -- (+1)
                        tc75(4),
                        tc150(5),
                        tc300(6),
                        tc600(7),
                        tc1200(8),
                        tc2400(9),
                        tc4800(10),
                        tc9600(11),
                        tc19200(12),
                        tc48000(13)
                        }
     ACCESS   read-only
     STATUS   mandatory
     DESCRIPTION
        "throughput class: receive Throughput class used. "
     ::= {nvItipstatEntry 13 }

nvItipstatCugtype OBJECT-TYPE
     SYNTAX   INTEGER {
                noCug(1),               -- (+1)
                cug(2),
                cugWithOutgoingAccess(3),
                bilateralCug(4)
                }
     ACCESS   read-only
     STATUS   mandatory
     DESCRIPTION
        "cug type: Type of closed user group call."
     ::= {nvItipstatEntry 14 }

nvItipstatCug OBJECT-TYPE
     SYNTAX   INTEGER
     ACCESS   read-only
     STATUS   mandatory
     DESCRIPTION
        "cug: Closed group identifier. Valid only if previous flag is true."
     ::= {nvItipstatEntry 15 }

nvItipstatRpoa OBJECT-TYPE
     SYNTAX   INTEGER
     ACCESS   read-only
     STATUS   mandatory
     DESCRIPTION
        "rpoa: DNIC"
     ::= {nvItipstatEntry 16 }

nvItipstatRevf OBJECT-TYPE
     SYNTAX   INTEGER {
                false(1),          -- (+1)
                true(2),
                busied(3), 
                notapp(4)
                }
     ACCESS   read-only
     STATUS   mandatory
     DESCRIPTION
        "reverse charging: Flag indicating if reverse charging is being used."
     ::= {nvItipstatEntry 17 }

nvItipstatPrio OBJECT-TYPE
     SYNTAX   INTEGER {
                false(1),          -- (+1)
                true(2),
		busied(3),
		notapp(4)
                }
     ACCESS   read-only
     STATUS   mandatory
     DESCRIPTION
        "priority call: Flag indicating if priority calling is beng used."
     ::= {nvItipstatEntry 18 }

nvItipstatFast OBJECT-TYPE
     SYNTAX   INTEGER {
                noFastSelect(1),        -- (+1)
                fastSelect(2),
                fastSelectRestricted(3)
                }
     ACCESS   read-only
     STATUS   mandatory
     DESCRIPTION
        "fast select: Type of fast select."
     ::= {nvItipstatEntry 19 }

nvItipstatPvc OBJECT-TYPE
     SYNTAX   INTEGER
     ACCESS   read-only
     STATUS   mandatory
     DESCRIPTION
        "pvc code: Permanent Virtual Circuit Code."
     ::= {nvItipstatEntry 20 }

nvItipstatNdcode OBJECT-TYPE
     SYNTAX   INTEGER
     ACCESS   read-only
     STATUS   mandatory
     DESCRIPTION
        "network disconnect code.
         Value of the last network disconnnect code."
     ::= {nvItipstatEntry 21 }

nvItipstatNddiag OBJECT-TYPE
     SYNTAX   INTEGER
     ACCESS   read-only
     STATUS   mandatory
     DESCRIPTION
        "network diag code: Value of the last network diagnostic code."
     ::= {nvItipstatEntry 22 }

nvItipstatNdorigin OBJECT-TYPE
     SYNTAX   INTEGER
     ACCESS   read-only
     STATUS   mandatory
     DESCRIPTION
        "disconnect origin: Whether disconnect was local or remote directive."
     ::= {nvItipstatEntry 23 }

nvItipstatNrcode OBJECT-TYPE
     SYNTAX   INTEGER
     ACCESS   read-only
     STATUS   mandatory
     DESCRIPTION
        "network reset code: Value of the last network reset code."
     ::= {nvItipstatEntry 24 }

nvItipstatNrdiag OBJECT-TYPE
     SYNTAX   INTEGER
     ACCESS   read-only
     STATUS   mandatory
     DESCRIPTION
        "network reset diag: Value of the last network reset diagnostic code."
     ::= {nvItipstatEntry 25 }

nvItipstatOrg OBJECT-TYPE
     SYNTAX   INTEGER {
                false(1),          -- (+1)
                true(2),
                busied(3), 
                notapp(4)
                }
     ACCESS   read-only
     STATUS   mandatory
     DESCRIPTION
        "call originator.
         Flag indicating who originated the call in progress."
     ::= {nvItipstatEntry 26 }

nvItipstatState OBJECT-TYPE
     SYNTAX   INTEGER {
                idle(2),                -- (+1)
                awaitingCommand(3),
                awaitingSelection(4),
                awaitingUserid(5),
                awaitingPassword(6),
                dataTransfer(8),
                invitationToClear(9),
                padCommandAfterEscape(10),
                padCommand(11),
                awaitingTerminalConnectResponse(12),
                awaitingFastSelectUserData(13),
                loopback(14),
                awaitingDiscBeforeCallBack(15),
                awaitingCallBack(16),
                awaitingDialoutUserInput(17),
                unused2(18),
                unused3(19),
                unused4(20),
                unused5(21),
                loginServicesControlMode(22),
                callReselection(23),
                scanLoginString(24),
                waitOutputDoneBeforeIdel(25),
                dlspcWaitCallClearFromDUI(26),
                escFromConnInProgress(27),
                waitRadiusResponseToMsg(28),
                waitUserInputForRadChallenge(29),
                connectingWaitForModemTrain(30)
                }
     ACCESS   read-only
     STATUS   mandatory
     DESCRIPTION
        "iti internal state: Internal state of the ITI interface."
     ::= {nvItipstatEntry 27 }

nvItipstatUserdata OBJECT-TYPE
     SYNTAX   DisplayString (SIZE (0..128))
     ACCESS   read-only
     STATUS   mandatory
     DESCRIPTION
        "user data: User specified user data."
     ::= {nvItipstatEntry 28 }

nvItipstatUsername OBJECT-TYPE
     SYNTAX   DisplayString (SIZE (0..10))
     ACCESS   read-only
     STATUS   mandatory
     DESCRIPTION
        "iti class: Current user using this port."
     ::= {nvItipstatEntry 29 }

nvItipstatX28type OBJECT-TYPE
     SYNTAX   INTEGER {
		undefined(1),
                pci(2),                 -- (+1)
                ccitt1976(3),
                ccitt1980(4),
                ccitt1984(5),
                telenet(6),
                datapac(7),
                micom(8),
                dynapac(9),
                telepac(10),
                amdahl(11),
                telematics(12),
                hughes(13),
                otc(14),
		consat(15),
		dlspc(16),
		pos(17),
                dcall(18),
                pacnet(19)
                }
     ACCESS   read-only
     STATUS   mandatory
     DESCRIPTION
        "command standard."
     ::= {nvItipstatEntry 30 }

nvItipstatX3type OBJECT-TYPE
     SYNTAX   INTEGER {
	        undefined(1),
                pci(2),                 -- (+1)
                ccitt1976(3),
                ccitt1980(4),
                ccitt1984(5),
                telenet(6),
                datapac(7),
                micom(8),
                dynapac(9),
                telepac(10),
                amdahl(11),
                telematics(12),
                hughes(13),
                otc(14),
		consat(15),
		dlspc(16),
		pos(17),
                dcall(18),
                pacnet(19)
                }
     ACCESS   read-only
     STATUS   mandatory
     DESCRIPTION
        "parameter standard: Current X.3 parameter standard being used."
     ::= {nvItipstatEntry 31 }

nvItipstatReservet      OBJECT-TYPE
     SYNTAX   DisplayString (SIZE (0..2))
     ACCESS   read-only
     STATUS   mandatory
     DESCRIPTION
        "OBSOLETE - removed field."
     ::= {nvItipstatEntry 32 }

nvItipstatNtccs OBJECT-TYPE
     SYNTAX   Counter
     ACCESS   read-only
     STATUS   mandatory
     DESCRIPTION
        "number of term connection commands.
         Count of service requests received from the terminal.
         Statistic is zeroed at startup time."
     ::= {nvItipstatEntry 33 }

nvItipstatNnccs OBJECT-TYPE
     SYNTAX   Counter
     ACCESS   read-only
     STATUS   mandatory
     DESCRIPTION
        "number of network connection cmds.
         Count of service requests received from the network.
         Statistic is zeroed at startup time."
     ::= {nvItipstatEntry 34 }

nvItipstatNnfails OBJECT-TYPE
     SYNTAX   Counter
     ACCESS   read-only
     STATUS   mandatory
     DESCRIPTION
        "number of network connection fails.
         Count of network call failures.
         Statistic is zeroed at startup time."
     ::= {nvItipstatEntry 35 }

nvItipstatNtxpaks OBJECT-TYPE
     SYNTAX   Counter
     ACCESS   read-only
     STATUS   mandatory
     DESCRIPTION
        "number of transmitted packets (to network).
         Number of packets sent on the network.
         Statistic is zeroed at startup time."
     ::= {nvItipstatEntry  36 }

nvItipstatNrxpaks OBJECT-TYPE
     SYNTAX   Counter
     ACCESS   read-only
     STATUS   mandatory
     DESCRIPTION
        "number of received packets (from network).
         Number of packets received from the network.
         Statistic is zeroed at startup time."
     ::= {nvItipstatEntry 37 }

nvItipstatNtxresets OBJECT-TYPE
     SYNTAX   Counter
     ACCESS   read-only
     STATUS   mandatory
     DESCRIPTION
        "number of transmitted resets.
         Number of resets originated.
         Statistic is zeroed at startup time."
     ::= {nvItipstatEntry 38 }

nvItipstatNrxresets OBJECT-TYPE
     SYNTAX   Counter
     ACCESS   read-only
     STATUS   mandatory
     DESCRIPTION
        "number of received resets.
         Number of resets received from network.
         Statistic is zeroed at startup time."
     ::= {nvItipstatEntry 39 }

nvItipstatNctxpaks OBJECT-TYPE
     SYNTAX   Counter
     ACCESS   read-only
     STATUS   mandatory
     DESCRIPTION
        "number of current transmitted packets (to network).
         Number of packets send over the network during current terminal
         session. Statistic is zeroed at startup time."
     ::= {nvItipstatEntry 40 }

nvItipstatNcrxpaks OBJECT-TYPE
     SYNTAX   Counter
     ACCESS   read-only
     STATUS   mandatory
     DESCRIPTION
        "number of current received packets (from network).
         Number of packets received from the network during current terminal
         session.
         Statistic is zeroed at startup time."
     ::= {nvItipstatEntry 41 }

nvItipstatNctxresets OBJECT-TYPE
     SYNTAX   Counter
     ACCESS   read-only
     STATUS   mandatory
     DESCRIPTION
        "number of current transmitted resets.
         Number of resets originated during current terminal session.
         Statistic is zeroed at startup time."
     ::= {nvItipstatEntry 42 }

nvItipstatNcrxresets OBJECT-TYPE
     SYNTAX   Counter
     ACCESS   read-only
     STATUS   mandatory
     DESCRIPTION
        "number of current received resets.
         Number of resets received during current terminal session.
         Statistic is zeroed at startup time."
     ::= {nvItipstatEntry 43 }

nvItipstatNinputs OBJECT-TYPE
     SYNTAX   Counter
     ACCESS   read-only
     STATUS   mandatory
     DESCRIPTION
        "number of input characters.
         Statistic is zeroed at startup time."
     ::= {nvItipstatEntry 44 }

nvItipstatNoutputs OBJECT-TYPE
     SYNTAX   Counter
     ACCESS   read-only
     STATUS   mandatory
     DESCRIPTION
        "number of output characters.
         Statistic is zeroed at startup time."
     ::= {nvItipstatEntry 45 }

nvItipstatParam OBJECT-TYPE
     SYNTAX   DisplayString (SIZE (0..140))
     ACCESS   read-only
     STATUS   mandatory
     DESCRIPTION 
"Copy of the current settings of the X.3 parameters (EX standard)
 for this port. This byte array must contain at least P_MAX + 1 bytes.
"
     ::= {nvItipstatEntry 46 }
 
nvItipstatPreparam OBJECT-TYPE
     SYNTAX   DisplayString (SIZE (0..140))
     ACCESS   read-only
     STATUS   mandatory
     DESCRIPTION
" Copy of X.3 parameters that were in effect before the current
  call (if any) was made. These values are restored (back to param)
  after the call is cleared.
"
     ::= {nvItipstatEntry 47 }

nvItipstatDtreset OBJECT-TYPE
     SYNTAX   DisplayString (SIZE (0..20))
     ACCESS   read-only
     STATUS   mandatory
     DESCRIPTION
        "date & time statistics last reset"
      ::= { nvItipstatEntry 48 }

nvItipstatId OBJECT-TYPE
     SYNTAX   DisplayString (SIZE (0..10))
     ACCESS   read-only
     STATUS   mandatory
     DESCRIPTION
        "Address of ITI control block."
     ::= {nvItipstatEntry 49 }

nvItipstatNtconn OBJECT-TYPE
     SYNTAX   Counter
     ACCESS   read-only
     STATUS   mandatory
     DESCRIPTION
        "Number of terminal connections.
         Number of times modem successfully trained."
     ::= {nvItipstatEntry 50 }

nvItipstatNtdc OBJECT-TYPE
     SYNTAX   Counter
     ACCESS   read-only
     STATUS   mandatory
     DESCRIPTION
        "Number of terminal disconnect commands.
	  Number of time terminal disconnected."
     ::= {nvItipstatEntry 51 }

nvItipstatNncr OBJECT-TYPE
     SYNTAX   Counter
     ACCESS   read-only
     STATUS   mandatory
     DESCRIPTION
        "Number of network connection responses.
	  Count of virtual circuits initiated from ITI port."
     ::= {nvItipstatEntry 52 }

nvItipstatNtimeout OBJECT-TYPE
     SYNTAX   Counter
     ACCESS   read-only
     STATUS   mandatory
     DESCRIPTION
        "Number of disconnects caused by ITI timeout."
     ::= {nvItipstatEntry 53 }

--
--      itiustat file
--
nvItiustat OBJECT IDENTIFIER    ::= {nevadaIti 5}

nvItiustatMaxRec OBJECT-TYPE
      SYNTAX   INTEGER
      ACCESS   read-only
      STATUS   mandatory
      DESCRIPTION
                "total number of records allowed in database file."
      ::= {nvItiustat 1}

nvItiustatNumRec OBJECT-TYPE
      SYNTAX   INTEGER
      ACCESS   read-only
      STATUS   mandatory
      DESCRIPTION
                "number of records in use."
      ::= {nvItiustat 2}

nvItiustatTable OBJECT-TYPE
      SYNTAX   SEQUENCE OF NvItiustatEntry
      ACCESS   not-accessible
      STATUS   mandatory
      DESCRIPTION
        "itiustat file."
      ::= {nvItiustat 3}

nvItiustatEntry OBJECT-TYPE
      SYNTAX   NvItiustatEntry
      ACCESS   not-accessible
      STATUS   mandatory
      DESCRIPTION
        "itiustat record."
      INDEX {nvItiustatIndex}
      ::= {nvItiustatTable 1 }

NvItiustatEntry ::=
      SEQUENCE {
      nvItiustatIndex
            INTEGER,
      nvItiustatUsername
            DisplayString,
      nvItiustatNcalls
            Counter,
      nvItiustatNpassfails
            Counter,
      nvItiustatNcallbacks
            Counter,
      nvItiustatDuration
            TimeTicks,
      nvItiustatNtxpaks
            Counter,
      nvItiustatNrxpaks
            Counter,
      nvItiustatDtreset
            DisplayString
               }

nvItiustatIndex OBJECT-TYPE
     SYNTAX   INTEGER
     ACCESS   read-only
     STATUS   mandatory
     DESCRIPTION
        "Index of itiustat record"
     ::= {nvItiustatEntry 1 }

nvItiustatUsername OBJECT-TYPE
     SYNTAX   DisplayString (SIZE (1..10))
     ACCESS   read-only
     STATUS   mandatory
     DESCRIPTION
        "Name of user.
         This field identifies which user the statistics in this record pertain
         to."
     ::= {nvItiustatEntry 2 }

nvItiustatNcalls OBJECT-TYPE
     SYNTAX   Counter
     ACCESS   read-only
     STATUS   mandatory
     DESCRIPTION
        "number of calls made.
         Total number of calls initiated by user
         Statistic is zeroed at startup time."
     ::= {nvItiustatEntry 3 }

nvItiustatNpassfails OBJECT-TYPE
     SYNTAX   Counter
     ACCESS   read-only
     STATUS   mandatory
     DESCRIPTION
        "number of password failures.
         Total number of password failures.
         Statistic is zeroed at startup time."
     ::= {nvItiustatEntry 4 }

nvItiustatNcallbacks OBJECT-TYPE
     SYNTAX   Counter
     ACCESS   read-only
     STATUS   mandatory
     DESCRIPTION
        "number of callbacks.
         Total number of callbacks to this user.
         Statistic is zeroed at startup time."
     ::= {nvItiustatEntry 5 }

nvItiustatDuration OBJECT-TYPE
     SYNTAX   TimeTicks
     ACCESS   read-only
     STATUS   mandatory
     DESCRIPTION
        "length of time used by user.
         Total number of minutes of time (*100*60).
         Statistic is zeroed at startup time."
     ::= {nvItiustatEntry 6 }

nvItiustatNtxpaks OBJECT-TYPE
     SYNTAX   Counter
     ACCESS   read-only
     STATUS   mandatory
     DESCRIPTION
        "number of transmitted packets (to network).
         Total number packets sent by this user over the network.
         Statistic is zeroed at startup time."
     ::= {nvItiustatEntry 7 }

nvItiustatNrxpaks OBJECT-TYPE
     SYNTAX   Counter
     ACCESS   read-only
     STATUS   mandatory
     DESCRIPTION
        "number of received packets (from network).
         Total number packets received by this user over the network.
         Statistic is zeroed at startup time."
     ::= {nvItiustatEntry 8 }

nvItiustatDtreset OBJECT-TYPE
     SYNTAX   DisplayString (SIZE (0..20))
     ACCESS   read-only
     STATUS   mandatory
     DESCRIPTION
        "date & time statistics last reset"
      ::= { nvItiustatEntry 9 }

--
--      dlspcstat file
--
nvDlspcstat     OBJECT IDENTIFIER ::= {nevadaIti 6}

nvDlspcstatMaxRec OBJECT-TYPE
      SYNTAX   INTEGER
      ACCESS   read-only
      STATUS   mandatory
      DESCRIPTION
                "total number of records allowed in database file."
      ::= {nvDlspcstat 1}

nvDlspcstatNumRec OBJECT-TYPE
      SYNTAX   INTEGER
      ACCESS   read-only
      STATUS   mandatory
      DESCRIPTION
                "number of records in use."
      ::= {nvDlspcstat 2}

nvDlspcstatTable OBJECT-TYPE
      SYNTAX   SEQUENCE OF NvDlspcstatEntry
      ACCESS   not-accessible
      STATUS   mandatory
      DESCRIPTION
               "dlspcstat file."
      ::= {nvDlspcstat 3}

nvDlspcstatEntry OBJECT-TYPE
      SYNTAX   NvDlspcstatEntry
      ACCESS   not-accessible
      STATUS   mandatory
      DESCRIPTION
               "dlspcstat record."
      INDEX   {nvDlspcstatIndex}
      ::= {nvDlspcstatTable 1 }

NvDlspcstatEntry ::=
      SEQUENCE {
        nvDlspcstatIndex
                INTEGER,
        nvDlspcstatNports
                INTEGER,
        nvDlspcstatNidle
                INTEGER
     }
nvDlspcstatIndex OBJECT-TYPE
     SYNTAX   INTEGER
     ACCESS   read-only
     STATUS   mandatory
     DESCRIPTION
        "Number of dial records."
     ::= {nvDlspcstatEntry 1 }

nvDlspcstatNports OBJECT-TYPE
     SYNTAX   INTEGER
     ACCESS   read-only
     STATUS   mandatory
     DESCRIPTION
        "Number of dial ports."
     ::= {nvDlspcstatEntry 2 }

nvDlspcstatNidle OBJECT-TYPE
     SYNTAX   INTEGER
     ACCESS   read-only
     STATUS   mandatory
     DESCRIPTION
        "Number of idle dial ports."
     ::= {nvDlspcstatEntry 3 }
--
--      Duistat file
--
nvDuistat OBJECT IDENTIFIER ::= {nevadaIti 7}

nvDuistatMaxRec OBJECT-TYPE
      SYNTAX   INTEGER
      ACCESS   read-only
      STATUS   mandatory
      DESCRIPTION
                "total number of records allowed in database file."
      ::= {nvDuistat 1}

nvDuistatNumRec OBJECT-TYPE
      SYNTAX   INTEGER
      ACCESS   read-only
      STATUS   mandatory
      DESCRIPTION
                "number of records in use."
      ::= {nvDuistat 2}

nvDuistatTable OBJECT-TYPE
      SYNTAX   SEQUENCE OF NvDuistatEntry
      ACCESS   not-accessible
      STATUS   mandatory
      DESCRIPTION
          "duistat file statistics."
      ::= {nvDuistat 3}

nvDuistatEntry OBJECT-TYPE
      SYNTAX   NvDuistatEntry
      ACCESS   not-accessible
      STATUS   mandatory
      DESCRIPTION
        "Duistat record."
      INDEX {nvDuistatIndex}
      ::= {nvDuistatTable 1 }

NvDuistatEntry ::=
      SEQUENCE {
      nvDuistatIndex
            INTEGER,
      nvDuistatType
            INTEGER,
      nvDuistatNua
            DisplayString,
      nvDuistatState
            INTEGER,
      nvDuistatLink
            INTEGER,
      nvDuistatLcn
            INTEGER,
      nvDuistatLastcause
            INTEGER,
      nvDuistatLastdiag
            INTEGER,
      nvDuistatNmnxtcall
            INTEGER,
      nvDuistatNretries
            Counter,
      nvDuistatNrejects
            Counter,
      nvDuistatNaccepts
            Counter,
      nvDuistatNinvmsgs
            Counter,
      nvDuistatNunxmsgs
            Counter,
      nvDuistatDtreset
	    DisplayString
               }

nvDuistatIndex OBJECT-TYPE
     SYNTAX   INTEGER
     ACCESS   read-only
     STATUS   mandatory
     DESCRIPTION
        "index"
     ::= {nvDuistatEntry 1 }

nvDuistatType OBJECT-TYPE
     SYNTAX   INTEGER {
                primary(1),     -- (+1)
                alternate(2)
                }
     ACCESS   read-only
     STATUS   mandatory
     DESCRIPTION
        "Type of DUI Circuit."
     ::= {nvDuistatEntry 2 }

nvDuistatNua OBJECT-TYPE
     SYNTAX   DisplayString (SIZE(0..16))
     ACCESS   read-only
     STATUS   mandatory
     DESCRIPTION
        "Last address used."
     ::= {nvDuistatEntry 3 }

nvDuistatState OBJECT-TYPE
     SYNTAX   INTEGER {
                down(1),        -- (+1)
                up(2),
                calling(3)
                }
     ACCESS   read-only
     STATUS   mandatory
     DESCRIPTION
        "State of DUI Circuit."
     ::= {nvDuistatEntry 4 }

nvDuistatLink OBJECT-TYPE
     SYNTAX   INTEGER (0..255)
     ACCESS   read-only
     STATUS   mandatory
     DESCRIPTION
        "Link carrying virual circuit."
     ::= {nvDuistatEntry 5 }

nvDuistatLcn OBJECT-TYPE
     SYNTAX   INTEGER (0..65535)
     ACCESS   read-only
     STATUS   mandatory
     DESCRIPTION
        "LCN of virual circuit."
     ::= {nvDuistatEntry 6 }

nvDuistatLastcause OBJECT-TYPE
     SYNTAX   INTEGER (0..255)
     ACCESS   read-only
     STATUS   mandatory
     DESCRIPTION
        "Last clear cause code."
     ::= {nvDuistatEntry 7 }

nvDuistatLastdiag OBJECT-TYPE
     SYNTAX   INTEGER (0..255)
     ACCESS   read-only
     STATUS   mandatory
     DESCRIPTION
        "Last clear diagnostic."
     ::= {nvDuistatEntry 8 }

nvDuistatNmnxtcall OBJECT-TYPE
     SYNTAX   INTEGER (0..65535)
     ACCESS   read-only
     STATUS   mandatory
     DESCRIPTION
        "Number of minutes until next call."
     ::= {nvDuistatEntry 9 }

nvDuistatNretries OBJECT-TYPE
     SYNTAX   Counter
     ACCESS   read-only
     STATUS   mandatory
     DESCRIPTION
        "Number of retries."
     ::= {nvDuistatEntry 10 }

nvDuistatNrejects OBJECT-TYPE
     SYNTAX   Counter
     ACCESS   read-only
     STATUS   mandatory
     DESCRIPTION
        "Number of rejects."
     ::= {nvDuistatEntry 11 }

nvDuistatNaccepts OBJECT-TYPE
     SYNTAX   Counter
     ACCESS   read-only
     STATUS   mandatory
     DESCRIPTION
        "Number of accepts."
     ::= {nvDuistatEntry 12 }

nvDuistatNinvmsgs OBJECT-TYPE
     SYNTAX   Counter
     ACCESS   read-only
     STATUS   mandatory
     DESCRIPTION
        "Number of invalid DUI messages received."
     ::= {nvDuistatEntry 13 }

nvDuistatNunxmsgs OBJECT-TYPE
     SYNTAX   Counter
     ACCESS   read-only
     STATUS   mandatory
     DESCRIPTION
        "Number of unexpected DUI messages received."
     ::= {nvDuistatEntry 14 }

nvDuistatDtreset OBJECT-TYPE
     SYNTAX   DisplayString (SIZE (0..20))
     ACCESS   read-only
     STATUS   mandatory
     DESCRIPTION
        "date & time statistics last reset"
      ::= { nvDuistatEntry 15 }



nvItiport OBJECT IDENTIFIER ::= { nevadaIti 16 }

nvItiportMaxRec OBJECT-TYPE
      SYNTAX   INTEGER
      ACCESS   read-only
      STATUS   mandatory
      DESCRIPTION
                "total number of records allowed in database file."
      ::= {nvItiport 1}

nvItiportNumRec OBJECT-TYPE
      SYNTAX   INTEGER
      ACCESS   read-only
      STATUS   mandatory
      DESCRIPTION
                "number of records in use."
      ::= {nvItiport 2}

nvItiportTable OBJECT-TYPE
      SYNTAX   SEQUENCE OF NvItiportEntry
      ACCESS   not-accessible
      STATUS   mandatory
      DESCRIPTION
               "itiport file."
      ::= { nvItiport 3 }

nvItiportEntry OBJECT-TYPE
      SYNTAX   NvItiportEntry
      ACCESS   not-accessible
      STATUS   mandatory
      DESCRIPTION
               "itiport record."
      INDEX { nvItiportIndex }
      ::= { nvItiportTable 1 }

NvItiportEntry ::=
      SEQUENCE {
      nvItiportIndex
            INTEGER,
      nvItiportName
            DisplayString,
      nvItiportEnable
            INTEGER,
      nvItiportIticlass
            DisplayString,
      nvItiportFclevel
            INTEGER,
      nvItiportMinbspace
            INTEGER,
      nvItiportMaxbspace
            INTEGER,
      nvItiportMode            --AF
            INTEGER, 	       --AF
      nvItiportRsrcpool
            DisplayString,
      nvItiportPortname
            DisplayString,
      nvItiportTimer0
            INTEGER,
      nvItiportTimer1
            INTEGER,
      nvItiportTimer2
            INTEGER
               }

nvItiportIndex OBJECT-TYPE
     SYNTAX   INTEGER
     ACCESS   read-only
     STATUS   mandatory
     DESCRIPTION
        "Index of itiport file."
     ::= {nvItiportEntry 1 }

nvItiportName OBJECT-TYPE
     SYNTAX   DisplayString
     ACCESS   read-only
     STATUS   mandatory
     DESCRIPTION
        "Name of ITI instance."
     ::= {nvItiportEntry 2 }

nvItiportEnable OBJECT-TYPE
     SYNTAX   INTEGER {
                no(1),      -- no (+1)
                yes(2)     -- yes
                }
     ACCESS   read-write
     STATUS   mandatory
     DESCRIPTION
        "ndicates whether port is enabled."
     ::= {nvItiportEntry 3 }

nvItiportIticlass OBJECT-TYPE
     SYNTAX   DisplayString  (SIZE (0..10))
     ACCESS   read-write
     STATUS   mandatory
     DESCRIPTION
        "Class of Service associated with ITI port."
     ::= {nvItiportEntry 5 }

nvItiportRsrcpool OBJECT-TYPE
     SYNTAX   DisplayString  (SIZE (0..10))
     ACCESS   read-write
     STATUS   mandatory
     DESCRIPTION
        "Name of Resource Pool."
     ::= {nvItiportEntry 6 }

nvItiportPortname OBJECT-TYPE
     SYNTAX   DisplayString  (SIZE (0..10))
     ACCESS   read-write
     STATUS   mandatory
     DESCRIPTION
        "Name of physical port or Device Usage Group."
     ::= {nvItiportEntry 7 }

nvItiportTimer1 OBJECT-TYPE
     SYNTAX   INTEGER (0..255)
     ACCESS   read-write
     STATUS   mandatory
     DESCRIPTION
           "TID timeout."
     ::= { nvItiportEntry 8 }

nvItiportMinbspace OBJECT-TYPE
     SYNTAX   INTEGER (2000..20000)
     ACCESS   read-write
     STATUS   mandatory
     DESCRIPTION
           "Modem Train timer."
     ::= { nvItiportEntry 9 }
     	             
nvItiportMaxbspace OBJECT-TYPE
     SYNTAX   INTEGER (5000..50000)
     ACCESS   read-write
     STATUS   mandatory
     DESCRIPTION
           "Maximum preallocated buffer space."
     ::= { nvItiportEntry 10 }

nvItiportFclevel OBJECT-TYPE
     SYNTAX   INTEGER (500..5000)
     ACCESS   read-write
     STATUS   mandatory
     DESCRIPTION
           "Buffer space left which causes flow control."
     ::= { nvItiportEntry 11 }

nvItiportMode   OBJECT-TYPE           --AF
     SYNTAX   INTEGER{                --AF
                m8N1(1),               --AF +1 
		m7E1(2),               --AF
		m7O1(3),               --AF
		m7M1(4),               --AF
		m7S1(5),               --AF
		m8G1(7),               --AF
		mAP1(8)                --AF                 
		}                     --AF
     ACCESS   read-write	      --AF
     STATUS   mandatory		      --AF
     DESCRIPTION		      --AF
	   "Port mode"		      --AF
     ::= { nvItiportEntry 12 }        --AF
	   
nvItiportTimer0 OBJECT-TYPE
     SYNTAX   INTEGER (0..255)
     ACCESS   read-write
     STATUS   mandatory
     DESCRIPTION
           "TID timeout."
     ::= { nvItiportEntry 13 }

nvItiportTimer2 OBJECT-TYPE
     SYNTAX   INTEGER (0..255)
     ACCESS   read-write
     STATUS   mandatory
     DESCRIPTION
           "TID timeout."
     ::= { nvItiportEntry 14 }

--
--      Dportstat file
--
nvDportstat OBJECT IDENTIFIER ::= {nevadaIti 8}

nvDportstatMaxRec OBJECT-TYPE
      SYNTAX   INTEGER
      ACCESS   read-only
      STATUS   mandatory
      DESCRIPTION
                "total number of records allowed in database file."
      ::= {nvDportstat 1}

nvDportstatNumRec OBJECT-TYPE
      SYNTAX   INTEGER
      ACCESS   read-only
      STATUS   mandatory
      DESCRIPTION
                "number of records in use."
      ::= {nvDportstat 2}

nvDportstatTable OBJECT-TYPE
      SYNTAX   SEQUENCE OF NvDportstatEntry
      ACCESS   not-accessible
      STATUS   mandatory
      DESCRIPTION
          "Dportstat file statistics."
      ::= {nvDportstat 3}

nvDportstatEntry OBJECT-TYPE
      SYNTAX   NvDportstatEntry
      ACCESS   not-accessible
      STATUS   mandatory
      DESCRIPTION
        "Dportstat record."
      INDEX {nvDportstatIndex}
      ::= {nvDportstatTable 1 }

NvDportstatEntry ::=
      SEQUENCE {
      nvDportstatIndex
            INTEGER,
      nvDportstatPortname
            DisplayString,
      nvDportstatSetstate
            INTEGER,
      nvDportstatIntfstate
            INTEGER,
      nvDportstatChstate
            INTEGER,
      nvDportstatDuihost
            INTEGER,
      nvDportstatDuistatus
            INTEGER,
      nvDportstatPorttype
            INTEGER,
--AF      nvDportstatDcd
--AF            INTEGER,
--AF      nvDportstatCts
--AF            INTEGER,
      nvDportstatCli
            DisplayString,
      nvDportstatResetdate
            DisplayString,
      nvDportstatUptime
            TimeTicks,
      nvDportstatDowntime
            TimeTicks,
      nvDportstatSessions
            Counter,
      nvDportstatIncalls
            Counter,
      nvDportstatOutcalls
            Counter,
      nvDportstatDtreset
            DisplayString
               }

nvDportstatIndex OBJECT-TYPE
     SYNTAX   INTEGER
     ACCESS   read-only
     STATUS   mandatory
     DESCRIPTION
        "a. index"
     ::= {nvDportstatEntry 1 }

nvDportstatPortname OBJECT-TYPE
     SYNTAX   DisplayString (SIZE(0..6))           --AF used to be (0..4)
     ACCESS   read-only
     STATUS   mandatory
     DESCRIPTION
        "Port name"
     ::= {nvDportstatEntry 2 }

nvDportstatSetstate OBJECT-TYPE
     SYNTAX   INTEGER {
                offline(1),     -- (+1)
                online(2),
                locked(3)
                }
     ACCESS   read-only
     STATUS   mandatory
     DESCRIPTION
        "State the port was last set to"
     ::= {nvDportstatEntry 3 }

nvDportstatIntfstate OBJECT-TYPE
     SYNTAX   INTEGER {
                false(1),       -- (+1)
                true(2),
                busied(3),
                notApplicable(4)
                }
     ACCESS   read-only
     STATUS   mandatory
     DESCRIPTION
        "Physical port state"
     ::= {nvDportstatEntry 4 }

nvDportstatChstate OBJECT-TYPE
     SYNTAX   INTEGER {
                idle(1),                -- (+1)
                connectedDuiHost(2),
                connectingUserSelectedHost(3),
                escapedFromConnectionInProgress(4),
                connectedUserSelectedHost(5),
                escapedDataState(6),
                portDisabled(7)
                }
     ACCESS   read-only
     STATUS   mandatory
     DESCRIPTION
        "Channel state"
     ::= {nvDportstatEntry 5 }

nvDportstatDuihost OBJECT-TYPE
     SYNTAX   INTEGER {
                primary(1),             -- (+1)
                alternate(2)
                }
     ACCESS   read-only
     STATUS   mandatory
     DESCRIPTION
        "Type of DUI host"
     ::= {nvDportstatEntry 6 }

nvDportstatDuistatus OBJECT-TYPE
     SYNTAX   INTEGER {
                ok(1),                  -- (+1)
                failed(2)
                }
     ACCESS   read-only
     STATUS   mandatory
     DESCRIPTION
        "Status of DUI port"
     ::= {nvDportstatEntry 7 }

nvDportstatPorttype OBJECT-TYPE
     SYNTAX   INTEGER {
                publicSwitched(2),      -- (+1)
                directConnect(3),
                passwordProtectedDirect(4)
                }
     ACCESS   read-only
     STATUS   mandatory
     DESCRIPTION
        "Type of port"
     ::= {nvDportstatEntry 8 }

--AF nvDportstatDcd OBJECT-TYPE
--AF     SYNTAX   INTEGER (0..255)
--AF     ACCESS   read-only
--AF     STATUS   mandatory
--AF     DESCRIPTION
--AF        "Debounced DCD state"
--AF     ::= {nvDportstatEntry 9 }

--AF  nvDportstatCts OBJECT-TYPE
--AF     SYNTAX   INTEGER (0..255)
--AF     ACCESS   read-only
--AF     STATUS   mandatory
--AF     DESCRIPTION
--AF        "Debounced CTS state"
--AF     ::= {nvDportstatEntry 10 }

nvDportstatCli OBJECT-TYPE
     SYNTAX   DisplayString (SIZE(0..16))
     ACCESS   read-only
     STATUS   mandatory
     DESCRIPTION
        "Calling line identifier"
     ::= {nvDportstatEntry 11 }

nvDportstatResetdate OBJECT-TYPE
     SYNTAX   DisplayString (SIZE(0..20))
     ACCESS   read-only
     STATUS   mandatory
     DESCRIPTION
        "Date when statistics were last reset"
     ::= {nvDportstatEntry 12 }

nvDportstatUptime OBJECT-TYPE
     SYNTAX   TimeTicks
     ACCESS   read-only
     STATUS   mandatory
     DESCRIPTION
        "Number of minutes port active"
     ::= {nvDportstatEntry 13 }

nvDportstatDowntime OBJECT-TYPE
     SYNTAX   TimeTicks
     ACCESS   read-only
     STATUS   mandatory
     DESCRIPTION
        "Number of minutes port idle"
     ::= {nvDportstatEntry 14 }

nvDportstatSessions OBJECT-TYPE
     SYNTAX   Counter
     ACCESS   read-only
     STATUS   mandatory
     DESCRIPTION
        "Number of sessions"
     ::= {nvDportstatEntry 15}

nvDportstatIncalls OBJECT-TYPE
     SYNTAX   Counter
     ACCESS   read-only
     STATUS   mandatory
     DESCRIPTION
        "Number of incoming calls"
     ::= {nvDportstatEntry 16 }

nvDportstatOutcalls OBJECT-TYPE
     SYNTAX   Counter
     ACCESS   read-only
     STATUS   mandatory
     DESCRIPTION
        "Number of outgoing calls"
     ::= {nvDportstatEntry 17 }

nvDportstatDtreset OBJECT-TYPE
     SYNTAX   DisplayString (SIZE (0..20))
     ACCESS   read-only
     STATUS   mandatory
     DESCRIPTION
        "date & time statistics last reset"
      ::= { nvDportstatEntry 18 }

-- ITI sessions are all associated with "users".
-- An ITI "user" may represent an individual,a group of individuals,
-- or a service such as a host computer port.
--
-- This file contains information about ITI "users".
-- This information provides for security (passwords),call restrictions,
-- closed user groups,etc.
-- There is one entry per defined user.
--
--  =login,6,login required
--  =plogin,7,login of privileged user

nvIticlass OBJECT IDENTIFIER ::= { nevadaIti 9 }

nvIticlassMaxRec OBJECT-TYPE
      SYNTAX   INTEGER
      ACCESS   read-only
      STATUS   mandatory
      DESCRIPTION
                "total number of records allowed in database file."
      ::= {nvIticlass 1}

nvIticlassNumRec OBJECT-TYPE
      SYNTAX   INTEGER
      ACCESS   read-only
      STATUS   mandatory
      DESCRIPTION
                "number of records in use."
      ::= {nvIticlass 2}

nvIticlassTable OBJECT-TYPE
      SYNTAX   SEQUENCE OF NvIticlassEntry
      ACCESS   not-accessible
      STATUS   mandatory
      DESCRIPTION
               "iticlass file."
      ::= { nvIticlass 3 }

nvIticlassEntry OBJECT-TYPE
      SYNTAX   NvIticlassEntry
      ACCESS   not-accessible
      STATUS   mandatory
      DESCRIPTION
               "iticlass record."
      INDEX { nvIticlassIndex }
      ::= { nvIticlassTable 1 }

NvIticlassEntry ::=
      SEQUENCE {
      nvIticlassIndex
            INTEGER,
      nvIticlassClassname
            DisplayString,
      nvIticlassAcctsigl
            INTEGER,
      nvIticlassActonloss
            INTEGER,
      nvIticlassBannerid
            INTEGER,
      nvIticlassBreaksgnl
            INTEGER,
      nvIticlassCalmethod
            INTEGER,
      nvIticlassClasmsgid
            INTEGER,
      nvIticlassClaspaswd
            DisplayString,
      nvIticlassCmdtimout
            INTEGER,
      nvIticlassCug
            INTEGER,
      nvIticlassDatacmd
            INTEGER,
      nvIticlassDefwsze
            INTEGER,
      nvIticlassDefpsze
            INTEGER,
      nvIticlassDevtype
            INTEGER,
      nvIticlassExitcmd
            INTEGER,
      nvIticlassFastsel
            INTEGER,
      nvIticlassIchrg
            INTEGER,
      nvIticlassInactivty
            INTEGER,
      nvIticlassIncbar
            INTEGER,
      nvIticlassInitcmd
            INTEGER,
      nvIticlassMaskstrng
            INTEGER,
      nvIticlassMaxpsze
            INTEGER,
      nvIticlassMaxwsze
            INTEGER,
      nvIticlassOchrg
            INTEGER,
      nvIticlassOutbar
            INTEGER,
      nvIticlassPrefixid
            INTEGER,
      nvIticlassProfile
            DisplayString,
      nvIticlassPromptid
            INTEGER,
      nvIticlassPvcid
            INTEGER,
      nvIticlassRejectid
            INTEGER,
      nvIticlassRpoacode
            INTEGER,
      nvIticlassRpoatype
            INTEGER,
      nvIticlassSecurity
            INTEGER,
      nvIticlassTermtype
            INTEGER,
      nvIticlassX28type
            INTEGER,
      nvIticlassX3type
            INTEGER,
      nvIticlassXoffin
            INTEGER,
      nvIticlassXoffout
            INTEGER,
      nvIticlassXonin
            INTEGER,
      nvIticlassXonout
            INTEGER,
      nvIticlassTidprompt
            INTEGER,
      nvIticlassStatus
            INTEGER,
      nvIticlassEscchar
            INTEGER,
      nvIticlassInvclrcmd
            INTEGER,
      nvIticlassX29mskstr
            INTEGER,
      nvIticlassDroptimer
            INTEGER,
      nvIticlassClasmode         --AF
            INTEGER,             --AF
      nvIticlassDialout
            INTEGER,
      nvIticlassCallingid        --AF
            INTEGER,
      nvIticlassAcctng
            INTEGER,
      nvIticlassInvclrtim
            INTEGER,
      nvIticlassComfac
	    INTEGER
                }

nvIticlassIndex OBJECT-TYPE
     SYNTAX   INTEGER
     ACCESS   read-only
     STATUS   mandatory
     DESCRIPTION
        "Index of iticlass record"
      ::= { nvIticlassEntry 1 }

nvIticlassClassname OBJECT-TYPE
     SYNTAX   DisplayString (SIZE (0..10))
     ACCESS   read-write
     STATUS   mandatory
     DESCRIPTION
"Class Name (classname)
This field contains a user's name.

If a default user id is not specified in the PORT record,
ITI will ask the user to enter a User Name.
The entered value is matched against the records in this file.
"
     ::= { nvIticlassEntry 2 }

nvIticlassAcctsigl OBJECT-TYPE
     SYNTAX   INTEGER {
                none(2),     -- No accounting (+1)
                demand(3),     -- Accounting on demand
                on(4),     -- Accounting always on
                dmand1(5),     -- Accounting on demand (packets+segments in ones)
                on1(6)      -- Accounting always on (packets+segments in ones)
                }
     ACCESS   read-write
     STATUS   mandatory
     DESCRIPTION
"Accounting Service Signal (acctsigl)
Default value is 2+1."
     ::= { nvIticlassEntry 3 }

nvIticlassActonloss OBJECT-TYPE
     SYNTAX   INTEGER {
                ignore(2),     -- ignore data loss (+1)
                clear(3),     -- clear call
                reset(4),      -- reset the virtual call
		discon(5)
                }
     ACCESS   read-write
     STATUS   mandatory
     DESCRIPTION
"Action on Data Loss (actonloss)
Default value is 1+1."
     ::= { nvIticlassEntry 4 }

nvIticlassBannerid OBJECT-TYPE
     SYNTAX   INTEGER (0..65535)
     ACCESS   read-write
     STATUS   mandatory
     DESCRIPTION
"Connect Banner Identification (bannerid)
This parameter indicates the herald
message that is to be send to the port upon activation.

This value is an index into string storage.
Default value is 0."
     ::= { nvIticlassEntry 5 }

nvIticlassBreaksgnl OBJECT-TYPE
     SYNTAX   INTEGER (0..65535)
     ACCESS   read-write
     STATUS   mandatory
     DESCRIPTION
"BREAK Character Signal Id (breaksgnl)
"
     ::= { nvIticlassEntry 6 }

nvIticlassCalmethod OBJECT-TYPE
     SYNTAX   INTEGER {
                norm(2),     -- Normal (+1)
                abrv(3),     -- abbreviated only
                direct(4),     -- hot line only
                pvc(5),         -- permanent virtual circuit
                teleneta(6),    -- allow abbreviated address feature of telenet
                special(7),     -- same as telenet,but dnic from iticonf
                telenb(8),      -- same as special,but mnemonic facility added,PDS 846
                telenc(9),      -- same as telenc,but abbrev calls only,PDS 846
                login(10),      --
                pad(11),
		telkom(12)         --
                }
     ACCESS   read-write
     STATUS   mandatory
     DESCRIPTION
"Allowed Calling Method (calmethod)
Parameter to control the restriction of outgoing call methods.
Default value is 1+1."
     ::= { nvIticlassEntry 7 }

nvIticlassClasmsgid OBJECT-TYPE
     SYNTAX   INTEGER (0..65535)
     ACCESS   read-write
     STATUS   mandatory
     DESCRIPTION
"Class Info Message Id (clasmsgid)
This parameter controls the facility that is used to send a greeting
message to users successfully connecting to the PAD.

A terminal port will send the message to the terminal while
a host port will send it across the virtual call to the
user.

The value is an index into string storage.
If the specified string contains the two consecutive characters '%s'
then the first occurance of those two characters will be replaced
by a string naming the port. This may be usefull when a user
wishes to know exactly what the remote destination port is
when the destination port is a member of a hunt group.
Default value is 0."
     ::= { nvIticlassEntry 8 }

nvIticlassClaspaswd OBJECT-TYPE
     SYNTAX   DisplayString (SIZE (0..10))
     ACCESS   read-write
     STATUS   mandatory
     DESCRIPTION
"Class Password (claspaswd)
This field contains the password associated with this
user.

When a userid and password are prompted for then the values supplied
by the user must match the USERNAME and PASSWORD fields of one of
the records in the nvIticlass file. If no match is made then access is
denied.

If this field is NULL then only the user's name is required and the
supplied password is not checked.
"
     ::= { nvIticlassEntry 9 }

nvIticlassCmdtimout OBJECT-TYPE
     SYNTAX   INTEGER (0..500)
     ACCESS   read-write
     STATUS   mandatory
     DESCRIPTION
"X.28 Command Timeout (cmdtimout)
Timeout value (in seconds) when waiting for user to enter a command.
If the value is zero,the command timeout facility is disabled.
Default value is 60."
     ::= { nvIticlassEntry 10 }

nvIticlassCug OBJECT-TYPE
     SYNTAX   INTEGER (0..65535)
     ACCESS   read-write
     STATUS   mandatory
     DESCRIPTION
"Closed User Group Identifier (cug)
Default value is 0."
     ::= { nvIticlassEntry 11 }

nvIticlassDatacmd OBJECT-TYPE
     SYNTAX   INTEGER (0..65535)
     ACCESS   read-write
     STATUS   mandatory
     DESCRIPTION
"Data Command (datacmd)
Default value is 0."
     ::= { nvIticlassEntry 12 }

nvIticlassDefwsze OBJECT-TYPE
     SYNTAX   INTEGER (1..15)
     ACCESS   read-write
     STATUS   mandatory
     DESCRIPTION
"Default Window Size (defwsze)
This field specifies the window size to be used when transmitting
packets. It is the maximum number packets that can be transmitted
before an acknowledgement is received.
Default value is 2."
     ::= { nvIticlassEntry 13 }

nvIticlassDefpsze OBJECT-TYPE
     SYNTAX   INTEGER {
                b16(5),     -- 16 bytes (+1)
                b32(6),     -- 32 bytes
                b64(7),     -- 64 bytes
                b128(8),     -- 128 bytes
                b256(9),     -- 256 bytes
                b512(10),     -- 512 bytes
                b1024(11)     -- 1024 bytes
                }
     ACCESS   read-write
     STATUS   mandatory
     DESCRIPTION
"Default Packet Size (defpsze)
This field specifies which packet size to use when packetizing
data to be sent accross a virtual circuit.
Default value is 7+1."
     ::= { nvIticlassEntry 14 }

nvIticlassDevtype OBJECT-TYPE
     SYNTAX   INTEGER {
                term(2),     -- terminal interface (+1)
                host(3)      -- host interface
                }
     ACCESS   read-write
     STATUS   mandatory
     DESCRIPTION
"Device Type (devtype)
This field is used to control ITI actions depending upon whether
the port is
connected to a host or terminal.
For example,a terminal interface will recognize Break,while
a host interface may have to generate one.
Default value is 1+1."
     ::= { nvIticlassEntry 15 }

nvIticlassExitcmd OBJECT-TYPE
     SYNTAX   INTEGER (0..65535)
     ACCESS   read-write
     STATUS   mandatory
     DESCRIPTION
"Exit Command (exitcmd)
Default value is 0."
     ::= { nvIticlassEntry 16 }

nvIticlassFastsel OBJECT-TYPE
     SYNTAX   INTEGER {
                none(2),     -- No fast selects allowed,in or out (+1)
                inallow(3),     -- incomming fast select allowed
                outallow(4),     -- outgoing fast select allowed
                allowed(5)      -- allowed for both incomming and outgoing
                }
     ACCESS   read-write
     STATUS   mandatory
     DESCRIPTION
"Fast Select Calling (fastsel)
This field determines whether fast select calls may be placed
or received
Default value is 4+1."
     ::= { nvIticlassEntry 17 }

nvIticlassIchrg OBJECT-TYPE
     SYNTAX   INTEGER {
                iall(2),     -- accept normal and reverse (+1)
                inorm(3),     -- accept normal
                irev(4)      -- accept reverse charging
                }
     ACCESS   read-write
     STATUS   mandatory
     DESCRIPTION
"Incoming Charging Restriction (ichrg)
This field controls the incoming charging options
allowed for this session.

Normally used on a host interface.
Default value is 1+1."
     ::= { nvIticlassEntry 18 }

nvIticlassInactivty OBJECT-TYPE
     SYNTAX   INTEGER (0..255)
     ACCESS   read-write
     STATUS   mandatory
     DESCRIPTION
"Data Mode Inactivity Timeout (inactivty)
Timeout value (in minutes) when waiting for data transfer
after call has been connected.
If set to zero then no timeout occurs.
Default value is 0."
     ::= { nvIticlassEntry 19 }

nvIticlassIncbar OBJECT-TYPE
     SYNTAX   INTEGER {
                inbar(2),     -- bar incoming calls
                inallow(3),     -- allow incoming calls (+1)
                inx28(4)      -- incoming calls accepted in X28 mode
                }
     ACCESS   read-write
     STATUS   mandatory
     DESCRIPTION
"Incoming Call Restriction (incbar)
This field is used to bar specified incoming calls.

Normally used on a host interface.
Default value is 2+1."
     ::= { nvIticlassEntry 20 }

nvIticlassInitcmd OBJECT-TYPE
     SYNTAX   INTEGER (0..65535)
     ACCESS   read-write
     STATUS   mandatory
     DESCRIPTION
"Initial Automatic Command Id (initcmd)
Default value is 0."
     ::= { nvIticlassEntry 21 }

nvIticlassMaskstrng OBJECT-TYPE
     SYNTAX   INTEGER (0..65535)
     ACCESS   read-write
     STATUS   mandatory
     DESCRIPTION
"string containing echo mask sequence
Default value is 0.
string MUST be defined BEFORE it can 
be referenced in this field."
     ::= { nvIticlassEntry 22 }

nvIticlassMaxpsze OBJECT-TYPE
     SYNTAX   INTEGER {
                b16(5),     -- 16 bytes (+1)
                b32(6),     -- 32 bytes
                b64(7),     -- 64 bytes
                b128(8),     -- 128 bytes
                b256(9),     -- 256 bytes
                b512(10),     -- 512 bytes
                b1024(11)      -- 1024 bytes
                }
     ACCESS   read-write
     STATUS   mandatory
     DESCRIPTION
"Maximum Packet Size (maxpsze)
This field specifies which packet size to use when packetizing
data to be sent accross a virtual circuit.
Default value is 7+1."
     ::= { nvIticlassEntry 23 }

nvIticlassMaxwsze OBJECT-TYPE
     SYNTAX   INTEGER (1..15)
     ACCESS   read-write
     STATUS   mandatory
     DESCRIPTION
"Maximum Window Size (maxwsze)
This field specifies the window size to be used when transmitting
packets. It is the maximum number packets that can be transmitted
before an acknowledgement is received.
Default value is 2."
     ::= { nvIticlassEntry 24 }

nvIticlassOchrg OBJECT-TYPE
     SYNTAX   INTEGER {
                oall(2),     -- normal and reverse charging are allowed (+1)
                onorm(3),     -- normal charging only
                orev(4)      -- reverse charging only
                }
     ACCESS   read-write
     STATUS   mandatory
     DESCRIPTION
"Outgoing Charging Restriction (ochrg)
This field controls the outgoing charging options permitted
during this session.

Normally used on a terminal interface.
Default value is 1+1."
     ::= { nvIticlassEntry 25 }

nvIticlassOutbar OBJECT-TYPE
     SYNTAX   INTEGER {
                outone(2),      -- allow only one outgoing call per physical connection
                outbar(3),     -- bar outgoing calls
                outallow(4)     -- allow outgoing calls (+1)
                }
     ACCESS   read-write
     STATUS   mandatory
     DESCRIPTION
"Outgoing Call Restriction (outbar)
This field is used to bar specified outgoing calls.

Normally used on a terminal interface.
Default value is 3+1."
     ::= { nvIticlassEntry 26 }

nvIticlassPrefixid OBJECT-TYPE
     SYNTAX   INTEGER (0..65535)
     ACCESS   read-write
     STATUS   mandatory
     DESCRIPTION
"Service Signal Prefix Id (prefixid)
This parameter indicates the prefix string
that is prefixed to all replies from ITI.

This value is an index into string storage.
Default value is 0."
     ::= { nvIticlassEntry 27 }

nvIticlassProfile OBJECT-TYPE
     SYNTAX   DisplayString (SIZE (0..10))
     ACCESS   read-write
     STATUS   mandatory
     DESCRIPTION
"Initial X.3 Parameter Profile (profile)
This field specifies which X.3 parameter profile is to
be used for the session. The terminal parameter table is
initialized with the specified values.
Users are free to change their own parameters.

Whenever a session is terminated,via a timeout,a broken connection
or a cleared call,the X.3 profile is reloaded for the user when
the Network Processor is next accessed.

This facility is used by both terminal and host interfaces to set
up initial parameters.

This field is an index into the ITIPROF file.
"
     ::= { nvIticlassEntry 28 }

nvIticlassPromptid OBJECT-TYPE
     SYNTAX   INTEGER (0..65535)
     ACCESS   read-write
     STATUS   mandatory
     DESCRIPTION
"X.28 Prompt Identification (promptid)
This parameter indicates the prompt to be used
to solicit a user response.

This value is an index into string storage.
Default value is 0."
     ::= { nvIticlassEntry 29 }

nvIticlassPvcid OBJECT-TYPE
     SYNTAX   INTEGER (0..65535)
     ACCESS   read-write
     STATUS   mandatory
     DESCRIPTION
"PVC Identifier (pvcid)
This field is used to select a network provided permanent
virtual circuit for the session.
"
     ::= { nvIticlassEntry 30 }

nvIticlassRejectid OBJECT-TYPE
     SYNTAX   INTEGER (0..65535)
     ACCESS   read-write
     STATUS   mandatory
     DESCRIPTION
"Reject Service Message Id (rejectid)
This field controls the facility that is used to send a service
refusal message to the user and to disconnect the call.
An example of use would be on a host pad when the host is
down.

A terminal port will send the message to the terminal and clear the
physical connection.

A host port will send the message across the virtual call to the user,
and follow it by an invitation to clear.

The value is an index into string storage.
Default value is 0."
     ::= { nvIticlassEntry 31 }

nvIticlassRpoacode OBJECT-TYPE
     SYNTAX   INTEGER (0..65535)
     ACCESS   read-write
     STATUS   mandatory
     DESCRIPTION
"RPOA Code (rpoacode)
Default value is 0."
     ::= { nvIticlassEntry 32 }

nvIticlassRpoatype OBJECT-TYPE
     SYNTAX   INTEGER {
                none(2),     -- No RPOA allowed (+1)
                file(3),     -- restricted to choices from RPOA file
                restrict(4)      -- restricted to RPOA in rpoacode field
                }
     ACCESS   read-write
     STATUS   mandatory
     DESCRIPTION
"RPOA Type (rpoatype)
Default value is 2+1."
     ::= { nvIticlassEntry 33 }

nvIticlassSecurity OBJECT-TYPE
     SYNTAX   INTEGER {
                none(2),     -- no security (+1)
                class(3),     -- class password required
                user(4),     -- user password required
                callback(5),     -- user password plus disconnect followed by dial back
                nui(6),      -- NUI facility required for each call
                radius(7),      -- use RADIUS to authenticate
                usrnui(8)       -- lookup NUI in ITIUSER file for ROSNET, PDS 21096
                }
     ACCESS   read-write
     STATUS   mandatory
     DESCRIPTION
"Access Method (security)
Default value is 1+1."
     ::= { nvIticlassEntry 34 }

nvIticlassTermtype OBJECT-TYPE
     SYNTAX   INTEGER {
                normal(2),      -- normal (+1)
		apacs(3),
		cdapacs(4),
		cdx28(5),
		epapacs(6)
                }
     ACCESS   read-write
     STATUS   mandatory
     DESCRIPTION
"Terminal Type (termtype)
Default value is 1+1."
     ::= { nvIticlassEntry 35 }

nvIticlassX28type OBJECT-TYPE
     SYNTAX   INTEGER {
                 pci(2),         -- (+1)
                 c76(3),         -- (+1)
                 c80(4),         -- (+1)
                 c84(5),         -- (+1)
                 telenet(6),     -- (+1)
                 datapac(7),     -- (+1)
                 micom(8),       -- (+1)
                 dynapac(9),     -- (+1)
                 telepac(10),    -- (+1)
                 amdahl(11),     -- (+1)
                 telematics(12), -- (+1)
                 hughes(13),     -- (+1)
                 otc(14),        -- (+1)
                 consat(15),     -- (+1)
                 dlspc (16),     -- (+1)
                 pos(17),
		 dcall(18),
		 pacnet(19)
                 }
     ACCESS   read-write
     STATUS   mandatory
     DESCRIPTION "X.28 Command Set (x28type) Default value is 1+1."
     ::= { nvIticlassEntry 36 }

nvIticlassX3type OBJECT-TYPE
     SYNTAX   INTEGER {
                pci(2),                 -- (+1)
                ccitt1976(3),
                ccitt1980(4),
                ccitt1984(5),
                telenet(6),
                datapac(7),
                micom(8),
                dynapac(9),
                telepac(10),
                amdahl(11),
                telematics(12),
                hughes(13),
                otc(14),
                consat(15),          --AF
                dlspc(16),           --AF
                pos(17),
		dcall(18),
		pacnet(19)
                }
     ACCESS   read-write
     STATUS   mandatory
     DESCRIPTION
"X.3 Parameter Profile Type (x3type)
Many implementations of X.3 may be found in today's public data
networks. A parameter on one network may mean something different
on another one. Or the allowable values may be different.

This field selects which parameter standard is to be used in
the X.28 (user interface) and X.29 (remote computer) interfaces.

It is important that a user know and conform to the parameter
standard being used by a remote PAD. Otherwise commands sent from
the remote PAD to set local parameters may not be interpreted
properly.
Default value is 1+1."
     ::= { nvIticlassEntry 37 }

nvIticlassXoffin OBJECT-TYPE
     SYNTAX   INTEGER (0..255)
     ACCESS   read-write
     STATUS   mandatory
     DESCRIPTION
"Input XOFF Character (xoffin)
Second user selectable XOFF charcter.
This character functions in an input only capacity and is not
output by the PAD as an XOFF chaacter.
Default value is 19."
     ::= { nvIticlassEntry 38 }

nvIticlassXoffout OBJECT-TYPE
     SYNTAX   INTEGER (0..255)
     ACCESS   read-write
     STATUS   mandatory
     DESCRIPTION
"Output XOFF Character (xoffout)
User selectable XOFF character.
Default value is 19."
     ::= { nvIticlassEntry 39 }

nvIticlassXonin OBJECT-TYPE
     SYNTAX   INTEGER (0..255)
     ACCESS   read-write
     STATUS   mandatory
     DESCRIPTION
"Input XON Character (xonin)
Second user selectable XON charcter.
This character functions in an input only capacity and is not
output by the PAD as an XON character.
Default value is 17."
     ::= { nvIticlassEntry 40 }

nvIticlassXonout OBJECT-TYPE
     SYNTAX   INTEGER (0..255)
     ACCESS   read-write
     STATUS   mandatory
     DESCRIPTION
"Output XON Character (xonout)
User selectable XON character.
Default value is 17."
     ::= { nvIticlassEntry 41 }

nvIticlassTidprompt OBJECT-TYPE
     SYNTAX   INTEGER (0..65535)
     ACCESS   read-write
     STATUS   mandatory
     DESCRIPTION
""
     ::= { nvIticlassEntry 42 }

nvIticlassStatus OBJECT-TYPE
     SYNTAX   INTEGER {
                valid(1),
                invalid(2)
                }
     ACCESS   read-write
     STATUS   mandatory
     DESCRIPTION
           "Operation status. Add the record to the table (valid) or
           delete the record from the table (invalid)."
     ::= { nvIticlassEntry 43 }

nvIticlassEscchar OBJECT-TYPE
     SYNTAX   INTEGER  (0..255)
     ACCESS   read-write
     STATUS   mandatory
     DESCRIPTION
"escape character use default is 0."
     ::= { nvIticlassEntry 44 }

nvIticlassInvclrcmd OBJECT-TYPE
     SYNTAX   INTEGER (0..65535)
     ACCESS   read-write
     STATUS   mandatory
     DESCRIPTION
"clear  Command (initcmd)
Default value is 0."
     ::= { nvIticlassEntry 45 }

nvIticlassX29mskstr OBJECT-TYPE
     SYNTAX   INTEGER (0..65535)
     ACCESS   read-write
     STATUS   mandatory
     DESCRIPTION
""
     ::= { nvIticlassEntry 46 }

nvIticlassDroptimer OBJECT-TYPE
     SYNTAX   INTEGER (0..255)
     ACCESS   read-write
     STATUS   mandatory
     DESCRIPTION
" length of time before disconnecting a call
  default 0"
     ::= { nvIticlassEntry 47 }

nvIticlassClasmode     OBJECT-TYPE               --AF
     SYNTAX   INTEGER {                          --AF
                m8N1(1),                                 --AF
                m7E1(2),                                 --AF
                m7O1(3),                                 --AF
                m7M1(4),                                 --AF
                m7S1(5),                                 --AF
                m8G1(7),                                 --AF
                mAP1(8),                                 --AF
                unused(16)                       --AF
                }                                --AF
     ACCESS   read-write                         --AF
     STATUS   mandatory                          --AF
     DESCRIPTION                                 --AF
           "Padding."                            --AF
     ::= { nvIticlassEntry 48 }                  --AF

nvIticlassDialout  OBJECT-TYPE
     SYNTAX   INTEGER (0..65535)
     ACCESS   read-write
     STATUS   mandatory
     DESCRIPTION
" dial-out string"
     ::= { nvIticlassEntry 49 }

nvIticlassCallingid     OBJECT-TYPE              --AF 
     SYNTAX   INTEGER {                          --AF 
                none(2),                         --AF 
                userdata(3)                      --AF
                }                                --AF 
     ACCESS   read-write                         --AF 
     STATUS   mandatory                          --AF 
     DESCRIPTION                                 --AF 
  "What to do with call id."                     --AF 
     ::= { nvIticlassEntry 50 }                  --AF 

nvIticlassAcctng OBJECT-TYPE
     SYNTAX   INTEGER {
                noacct(1),
                usage(2),
                billng(3),
                both(4)
                }
     ACCESS   read-write
     STATUS   mandatory
     DESCRIPTION
     "Accounting"
     ::= { nvIticlassEntry 51 }

nvIticlassInvclrtim OBJECT-TYPE
     SYNTAX   INTEGER(0..255)
     ACCESS   read-write
     STATUS   mandatory
     DESCRIPTION
     "Timeout for Invitation to Clear"
     ::= { nvIticlassEntry 52 }

nvIticlassComfac OBJECT-TYPE
     SYNTAX   INTEGER {
		lcfac(1),
		ucfac(2),
		lcnofac(3),
		ucnofac(4)
		}
     ACCESS   read-write
     STATUS   mandatory
     DESCRIPTION
	"Lower or Upper case service signals.
	 lcfac = lower case with fac
	 ucfac = upper case with fac
	 lcnofac = lower case with no fac
	 ucnofac = upper case no fac."
     ::= { nvIticlassEntry 53 }

-- File contains pre-defined commands for users.
--
--  An ITI user may use the "dir" command to display these pre-defined
-- commands.

nvIticmd OBJECT IDENTIFIER ::= { nevadaIti 10 }

nvIticmdMaxRec OBJECT-TYPE
      SYNTAX   INTEGER
      ACCESS   read-only
      STATUS   mandatory
      DESCRIPTION
                "total number of records allowed in database file."
      ::= {nvIticmd 1}

nvIticmdNumRec OBJECT-TYPE
      SYNTAX   INTEGER
      ACCESS   read-only
      STATUS   mandatory
      DESCRIPTION
                "number of records in use."
      ::= {nvIticmd 2}

nvIticmdTable OBJECT-TYPE
      SYNTAX   SEQUENCE OF NvIticmdEntry
      ACCESS   not-accessible
      STATUS   mandatory
      DESCRIPTION
               "iticmd file."
      ::= { nvIticmd 3 }

nvIticmdEntry OBJECT-TYPE
      SYNTAX   NvIticmdEntry
      ACCESS   not-accessible
      STATUS   mandatory
      DESCRIPTION
               "iticmd record."
      INDEX { nvIticmdIndex }
      ::= { nvIticmdTable 1 }

NvIticmdEntry ::=
      SEQUENCE {
      nvIticmdIndex
            INTEGER,
      nvIticmdCommand
            DisplayString,
      nvIticmdClass
            DisplayString,
      nvIticmdStringid
            INTEGER,
      nvIticmdStatus
            INTEGER
                }

nvIticmdIndex OBJECT-TYPE
     SYNTAX   INTEGER
     ACCESS   read-only
     STATUS   mandatory
     DESCRIPTION
        "Index of iticmd record"
      ::= { nvIticmdEntry 1 }

nvIticmdCommand OBJECT-TYPE
     SYNTAX   DisplayString (SIZE (0..10))
     ACCESS   read-write
     STATUS   mandatory
     DESCRIPTION
"Command Mnemonic (command)
Command name,this string is entered by the user and is matched
against entries in this file. If successful,the matched string is
taken as user input and processed.
"
     ::= { nvIticmdEntry 2 }

nvIticmdClass OBJECT-TYPE
     SYNTAX   DisplayString (SIZE (0..10))
     ACCESS   read-write
     STATUS   mandatory
     DESCRIPTION
"Class of Service (class)
Name of class that owns command.
"
     ::= { nvIticmdEntry 3 }

nvIticmdStringid OBJECT-TYPE
     SYNTAX   INTEGER (0..65535)
     ACCESS   read-write
     STATUS   mandatory
     DESCRIPTION
"Full Command Name Id (stringid)
Index into string storage for replacement value.
"
     ::= { nvIticmdEntry 4 }

nvIticmdStatus OBJECT-TYPE
     SYNTAX   INTEGER {
                valid(1),
                invalid(2)
                }
     ACCESS   read-write
     STATUS   mandatory
     DESCRIPTION
" "
     ::= { nvIticmdEntry 5 }


nvIticonf OBJECT IDENTIFIER ::= { nevadaIti 11 }

nvIticonfMaxRec OBJECT-TYPE
      SYNTAX   INTEGER
      ACCESS   read-only
      STATUS   mandatory
      DESCRIPTION
                "total number of records allowed in database file."
      ::= {nvIticonf 1}

nvIticonfNumRec OBJECT-TYPE
      SYNTAX   INTEGER
      ACCESS   read-only
      STATUS   mandatory
      DESCRIPTION
                "number of records in use."
      ::= {nvIticonf 2}

nvIticonfTable OBJECT-TYPE
      SYNTAX   SEQUENCE OF NvIticonfEntry
      ACCESS   not-accessible
      STATUS   mandatory
      DESCRIPTION
               "iticonf file."
      ::= { nvIticonf 3 }

nvIticonfEntry OBJECT-TYPE
      SYNTAX   NvIticonfEntry
      ACCESS   not-accessible
      STATUS   mandatory
      DESCRIPTION
               "iticonf record."
      INDEX { nvIticonfIndex }
      ::= { nvIticonfTable 1 }

NvIticonfEntry ::=
      SEQUENCE {
      nvIticonfIndex
            INTEGER,
      nvIticonfNumcopy
            INTEGER,
      nvIticonfBroadcast
            INTEGER,
      nvIticonfItiswitch
            INTEGER,
      nvIticonfPadaddr
            DisplayString,
      nvIticonfDnic
            INTEGER,
      nvIticonfConfigstr
            INTEGER,
      nvIticonfValserver
            INTEGER,
      nvIticonfV120p11
            INTEGER
                }

nvIticonfIndex OBJECT-TYPE
     SYNTAX   INTEGER
     ACCESS   read-only
     STATUS   mandatory
     DESCRIPTION
        "Index of iticonf record"
      ::= { nvIticonfEntry 1 }

nvIticonfNumcopy OBJECT-TYPE
     SYNTAX   INTEGER (0..32)
     ACCESS   read-write
     STATUS   mandatory
     DESCRIPTION
"Number of Simultaneous Copies (numcopy)
This field specifies how many ITI ports may be copying network
data at one time.
Default value is 4."
     ::= { nvIticonfEntry 2 }

nvIticonfBroadcast OBJECT-TYPE
     SYNTAX   INTEGER (0..65535)
     ACCESS   read-write
     STATUS   mandatory
     DESCRIPTION
"Broadcast Message Id (broadcast)
This field identifies a string which is to be broadcast to a
port following a service request but before security checking.
Replacing the nvIticonf record will cause the message to be
broadcast to all active iti ports that have service signals enabled.
"
     ::= { nvIticonfEntry 3 }

nvIticonfItiswitch OBJECT-TYPE
     SYNTAX   INTEGER {
                no(1),      -- no
                yes(2)     -- yes (+1)
                }
     ACCESS   read-write
     STATUS   mandatory
     DESCRIPTION
"ITI Switch (itiswitch)
This field will be used to tell NBUS whether outgoing calls
can be looped back (ITI to ITI calls allowed)
Default value is ysr (1+1)."
     ::= { nvIticonfEntry 4 }

nvIticonfPadaddr OBJECT-TYPE
     SYNTAX   DisplayString (SIZE (0..6))
     ACCESS   read-write
     STATUS   mandatory
     DESCRIPTION
"PAD Address Field (padaddr)
"
     ::= { nvIticonfEntry 5 }

nvIticonfDnic OBJECT-TYPE
     SYNTAX   INTEGER (1000..9999)
     ACCESS   read-write
     STATUS   mandatory
     DESCRIPTION
"Data Network Identification Code (dnic)
DNIC number when calmethod=special in nvIticlass file.
"
     ::= { nvIticonfEntry 6 }

nvIticonfConfigstr OBJECT-TYPE
     SYNTAX   INTEGER (0..65535)
     ACCESS   read-write
     STATUS   mandatory
     DESCRIPTION
"CONSAT facility mapping string."
     ::= { nvIticonfEntry 7 }

nvIticonfValserver OBJECT-TYPE
     SYNTAX   INTEGER (0..65535)
     ACCESS   read-write
     STATUS   mandatory
     DESCRIPTION
"address of validation server
Default value is 0."
     ::= { nvIticonfEntry 8 }
     
nvIticonfV120p11 OBJECT-TYPE
     SYNTAX   INTEGER{
                 k64k(1),
		 urate(2)
		 }
     ACCESS   read-write
     STATUS   mandatory
     DESCRIPTION
           " 64k   1,      p11 for v.120 set for 64000                   
	     urate 2,      p11 for v.120 from user rate in ISDN"
     ::= { nvIticonfEntry 10 }

-- This file contains information that is used by ITI
-- to map network-addresses and call user data to
-- local ITI "users". These normally represent hunt-groups.
--
-- The network address and user data stored in the itihunt file
-- are patterns that allow the following options:
--  1. xxxxxx - arbitrary alpha/numeric data (numeric for address)
--  2. *xxx - match exactly the last 3 characters,allow any
-- number of preceeding characters (0 or more).
--  3. xxxx* - match exactly the first four characters,any number of
-- trailing ones (0 or more).
--  4. * - match any thing.
--  5. xx%xx - match exactly the first two characters,arbitrary
-- third character,and exact last two characters.
--
-- The best match is defined as the field with the most number of
-- exact matches with the stored patterns. This means that * is the
-- last to be matched (catch all).
--
-- In mapping,the best match of the network address is taken first,
-- and within this,the best match for user data.

nvItimap OBJECT IDENTIFIER ::= { nevadaIti 12 }

nvItimapMaxRec OBJECT-TYPE
      SYNTAX   INTEGER
      ACCESS   read-only
      STATUS   mandatory
      DESCRIPTION
                "total number of records allowed in database file."
      ::= {nvItimap 1}

nvItimapNumRec OBJECT-TYPE
      SYNTAX   INTEGER
      ACCESS   read-only
      STATUS   mandatory
      DESCRIPTION
                "number of records in use."
      ::= {nvItimap 2}

nvItimapTable OBJECT-TYPE
      SYNTAX   SEQUENCE OF NvItimapEntry
      ACCESS   not-accessible
      STATUS   mandatory
      DESCRIPTION
               "itimap file."
      ::= { nvItimap 3 }

nvItimapEntry OBJECT-TYPE
      SYNTAX   NvItimapEntry
      ACCESS   not-accessible
      STATUS   mandatory
      DESCRIPTION
               "itimap record."
      INDEX { nvItimapIndex }
      ::= { nvItimapTable 1 }

NvItimapEntry ::=
      SEQUENCE {
      nvItimapIndex
            INTEGER,
      nvItimapNetaddr
            DisplayString,
      nvItimapUserdata
            DisplayString,
      nvItimapClass
            DisplayString,
      nvItimapStatus
	    INTEGER
                }

nvItimapIndex OBJECT-TYPE
     SYNTAX   INTEGER
     ACCESS   read-only
     STATUS   mandatory
     DESCRIPTION
        "Index of itimap record"
      ::= { nvItimapEntry 1 }

nvItimapNetaddr OBJECT-TYPE
     SYNTAX   DisplayString (SIZE (0..16))
     ACCESS   read-write
     STATUS   mandatory
     DESCRIPTION
"Network X.121 Address (netaddr)
This field contains the pattern against which the incoming network
address is matched.
"
     ::= { nvItimapEntry 2 }

nvItimapUserdata OBJECT-TYPE
     SYNTAX   DisplayString (SIZE (0..16))
     ACCESS   read-write
     STATUS   mandatory
     DESCRIPTION
"User Data (userdata)
This field contains the pattern against which the associated call
user data is matched.
"
     ::= { nvItimapEntry 3 }

nvItimapClass OBJECT-TYPE
     SYNTAX   DisplayString (SIZE (0..10))
     ACCESS   read-write
     STATUS   mandatory
     DESCRIPTION
"Class of Port Assignment (class)
This field indicates which ITI 'user' is
associated with the network address and call user data.
If the PORT field in this record is NULL then the actual
port is located by processing the itihunt file.
"
     ::= { nvItimapEntry 4 }

nvItimapStatus OBJECT-TYPE
     SYNTAX   INTEGER {
                valid(1),
                invalid(2)
                }
     ACCESS   read-write
     STATUS   mandatory
     DESCRIPTION
           "Operation status. Add the record to the table (valid) or
           delete the record from the table (invalid)."
     ::= { nvItimapEntry 5 }

--
--  The following parameters are taken from CCITT Recommendation X.3: Packet
-- Assembly/Disassembly (PAD) Facility in a Public Data Network. In supporting
-- a particular user port,the operation of a PAD is controlled by the current
-- X.3 parameters,set or selected for that port. When initializing a session
-- between the PAD and a terminal or a host,
-- the initial value of each PAD parameter is set according to a pre-configured
-- profile. The terminal user may subsequently alter the parameters.
--
--  The ITI "prof" command will search this file using a profile name as
-- a key.

nvItiprof OBJECT IDENTIFIER ::= { nevadaIti 13 }

nvItiprofMaxRec OBJECT-TYPE
      SYNTAX   INTEGER
      ACCESS   read-only
      STATUS   mandatory
      DESCRIPTION
                "total number of records allowed in database file."
      ::= {nvItiprof 1}

nvItiprofNumRec OBJECT-TYPE
      SYNTAX   INTEGER
      ACCESS   read-only
      STATUS   mandatory
      DESCRIPTION
                "number of records in use."
      ::= {nvItiprof 2}

nvItiprofTable OBJECT-TYPE
      SYNTAX   SEQUENCE OF NvItiprofEntry
      ACCESS   not-accessible
      STATUS   mandatory
      DESCRIPTION
               "itiprof file."
      ::= { nvItiprof 3 }

nvItiprofEntry OBJECT-TYPE
      SYNTAX   NvItiprofEntry
      ACCESS   not-accessible
      STATUS   mandatory
      DESCRIPTION
               "itiprof record."
      INDEX { nvItiprofIndex }
      ::= { nvItiprofTable 1 }

NvItiprofEntry ::=
      SEQUENCE {
      nvItiprofIndex
            INTEGER,
      nvItiprofName
            DisplayString,
      nvItiprofP1
            INTEGER,
      nvItiprofP2
            INTEGER,
      nvItiprofP3
            INTEGER,
      nvItiprofP4
            INTEGER,
      nvItiprofP5
            INTEGER,
      nvItiprofP6
            INTEGER,
      nvItiprofP7
            INTEGER,
      nvItiprofP8
            INTEGER,
      nvItiprofP9
            INTEGER,
      nvItiprofP10
            INTEGER,
      nvItiprofP11
            INTEGER,
      nvItiprofP12
            INTEGER,
      nvItiprofP13
            INTEGER,
      nvItiprofP14
            INTEGER,
      nvItiprofP15
            INTEGER,
      nvItiprofP16
            INTEGER,
      nvItiprofP17
            INTEGER,
      nvItiprofP18
            INTEGER,
      nvItiprofP19
            INTEGER,
      nvItiprofP20
            INTEGER,
      nvItiprofP21
            INTEGER,
      nvItiprofP22
            INTEGER,
      nvItiprofP23
            INTEGER,
      nvItiprofP24
            INTEGER,
      nvItiprofP25
            INTEGER,
      nvItiprofP26
            INTEGER,
      nvItiprofP27
            INTEGER,
      nvItiprofP28
            INTEGER,
      nvItiprofP29
            INTEGER,
      nvItiprofP30
            INTEGER,
      nvItiprofP31
            INTEGER,
      nvItiprofP32
            INTEGER,
      nvItiprofP33
            INTEGER,
      nvItiprofP34
            INTEGER,
      nvItiprofP35
            INTEGER,
      nvItiprofStatus
	    INTEGER
                }

nvItiprofIndex OBJECT-TYPE
     SYNTAX   INTEGER
     ACCESS   read-only
     STATUS   mandatory
     DESCRIPTION
        "Index of itiprof record"
      ::= { nvItiprofEntry 1 }

nvItiprofName OBJECT-TYPE
     SYNTAX   DisplayString (SIZE (0..10))
     ACCESS   read-write
     STATUS   mandatory
     DESCRIPTION
"Profile Name (name)
Name of profile. Used by ITI 'prof' command to locate
specified record.
"
     ::= { nvItiprofEntry 2 }

nvItiprofP1 OBJECT-TYPE
     SYNTAX   INTEGER (0..255)
     ACCESS   read-write
     STATUS   mandatory
     DESCRIPTION
"PAD Recall Character (p1)
This parameter indicates whether or not the
transmission of a DLE character (ASCII value of 16.) from
the terminal to the PAD is recognized as an escape from the data
transfer state. If so,transmission of DLE will cause the
virtual call to be suspended,
allowing the terminal user to send commands to the PAD.
 (0) = No escape allowed
 (1) = Escape allowed
Default value is 1."
     ::= { nvItiprofEntry 3 }

nvItiprofP2 OBJECT-TYPE
     SYNTAX   INTEGER (0..255)
     ACCESS   read-write
     STATUS   mandatory
     DESCRIPTION
"Echo Enable/Disable (p2)
This parameter indicates to the PAD whether or not
the terminal input data is to be echoed.
If so,characters typed in from the terminal keyboard will be
transmitted back to the terminal as well as being interpreted by
the PAD. Transmission costs can be reduced by having the PAD echo
characters rather than having a remote host doing the echoing.
 (0) = No echo
 (1) = Echo
Default value is 1."
     ::= { nvItiprofEntry 4 }

nvItiprofP3 OBJECT-TYPE
     SYNTAX   INTEGER (0..255)
     ACCESS   read-write
     STATUS   mandatory
     DESCRIPTION
"Packet Forwarding Characters (p3)
This parameter indicates to the PAD the set of terminal generated
characters that will cause data to be forwarded to the
destination. When a data forwarding signal is received then all
buffered data is assembled into a packet and sent to the destination.
 (0) = No signals
 (2) = CR
 (6) = CR,ESC,BEL,ENQ,ACK
 (18) = CR,EOT,ETX
 (126) = all control characters (ASCII values from 1. to 31.) and DEL
Default value is 2."
     ::= { nvItiprofEntry 5 }

nvItiprofP4 OBJECT-TYPE
     SYNTAX   INTEGER (0..255)
     ACCESS   read-write
     STATUS   mandatory
     DESCRIPTION
"Forwarding Idle Timer (p4)
This parameter indicates to the PAD whether data forwarding is to be
based on timeouts.
If so,then the value of the parameter specifies the time limit
imposed on the buffering of data characters.
Each received data character will reset the timer until eventually
a pause in the character stream will allow the timer to expire
and all buffered data will be forwarded.
 (0) = No timer
 (1-255) = Indicates the value of the delay in twentieths of a second.
Default value is 0."
     ::= { nvItiprofEntry 6 }

nvItiprofP5 OBJECT-TYPE
     SYNTAX   INTEGER (0..255)
     ACCESS   read-write
     STATUS   mandatory
     DESCRIPTION
"Device Flow Control (p5)
This parameter indicates whether the terminal will respond to flow
control. If so,then this will allow the PAD to stop
(by sending an XOFF character) and start (by sending an XON character)
transmission from the terminal so that the PAD can pace the terminal.

Flow control using modem signals is not supported.
 (0) = No auxiliary device control
 (1) = xon/xoff flow control (data transfer)
Default value is 1."
     ::= { nvItiprofEntry 7 }

nvItiprofP6 OBJECT-TYPE
     SYNTAX   INTEGER (0..255)
     ACCESS   read-write
     STATUS   mandatory
     DESCRIPTION
"Service Signal Control (p6)
This parameter indicates to the PAD whether or not
network generated messages are to be transmitted to the terminal.
 (0) = No messages sent
 (1) = Send service messages
 (4) = Send prompts only
Default value is 5."
     ::= { nvItiprofEntry 8 }

nvItiprofP7 OBJECT-TYPE
     SYNTAX   INTEGER (0..255)
     ACCESS   read-write
     STATUS   mandatory
     DESCRIPTION
"Device BREAK Action (p7)
This parameter is used to indicate how the PAD should process a BREAK
signal that is received from the terminal while the terminal is in
data transfer state.
 (0) = Nothing
 (1) = Send interrupt
 (2) = Send reset
 (8) = Escape from data state
 (21) = Discard output,send interrupt and indication of break
Default value is 21."
     ::= { nvItiprofEntry 9 }

nvItiprofP8 OBJECT-TYPE
     SYNTAX   INTEGER (0..255)
     ACCESS   read-write
     STATUS   mandatory
     DESCRIPTION
"Output Discard (p8)
This parameter is used in conjunction with Parameter 7. Depending
upon the BREAK procedure selected,this parameter may be set by
the PAD when the terminal user requests that terminal data be
discarded. This parameter must then be reset by the destination
to allow normal delivery. The PAD will discard all packets
destined for the terminal from the time the PAD sets this
parameter (ie. BREAK) and the time the parameter is reset by the
destination. This feature can be used,for example,to allow users to
terminate lengthy outputs to terminals by pressing BREAK.
 (0) = Normal delivery
 (1) = Discard output
Default value is 0."
     ::= { nvItiprofEntry 10 }

nvItiprofP9 OBJECT-TYPE
     SYNTAX   INTEGER (0..255)
     ACCESS   read-write
     STATUS   mandatory
     DESCRIPTION
"Carriage Return Padding (p9)
This parameter specifies the number of padding characters to be
inserted by the PAD following a carriage return transmitted to the
terminal. This would allow mechanical actions
(such as type-ball returns) to be completed before
more data is to be output.
 (0) = No padding
 (1-255) = Number of pads to be inserted
Default value is 4."
     ::= { nvItiprofEntry 11 }

nvItiprofP10 OBJECT-TYPE
     SYNTAX   INTEGER (0..255)
     ACCESS   read-write
     STATUS   mandatory
     DESCRIPTION
"Line Length (p10)
This parameter indicates the maximum number of printable characters
that can be displayed on the terminal before the PAD must be sent a
format effector (ie. CR LF). This causes data to be output on the
next line on the terminal.
 (0) = No line folding
 (1-255) = Number of characters per line
Default value is 80."
     ::= { nvItiprofEntry 12 }

nvItiprofP11 OBJECT-TYPE
     SYNTAX   INTEGER (0..255)
     ACCESS   read-write
     STATUS   mandatory
     DESCRIPTION
"Transmission Speed (Read Only) (p11)
This parameter is set by the PAD as the result of transmission speed
detection if the terminal access is an autobaud port. When a port
with fixed speed is used,this parameter is set during PAD
configuration,based on the pre-configured value.
 (0) = 110 bps
 (1) = 134.5 bps
 (2) = 300 bps
 (3) = 1200 bps
 (4) = 600 bps
 (5) = 75 bps
 (6) = 150 bps
 (7) = 1800 bps
 (8) = 200 bps
 (9) = 100 bps
 (10) = 50 bps
 (11) = 75/1200
 (12) = 2400
 (13) = 4800
 (14) = 9600
"
     ::= { nvItiprofEntry 13 }

nvItiprofP12 OBJECT-TYPE
     SYNTAX   INTEGER (0..255)
     ACCESS   read-write
     STATUS   mandatory
     DESCRIPTION
"PAD Flow Control (p12)
This parameter enables the terminal to indicate to the PAD that the
terminal cannot receive any more data. When this parameter is set
to 1,the terminal user can request that the PAD stop sending data
by transmitting a DC3 character. The PAD then suspends transmission
of data until a DC1 character is received. This feature allows a
display terminal user to indicate when the PAD should suspend the
scrolling of terminal output,so that it can be viewed. Then the
output can be restarted.
 (0) = No flow control
 (1) = Flow control
Default value is 1."
     ::= { nvItiprofEntry 14 }

nvItiprofP13 OBJECT-TYPE
     SYNTAX   INTEGER (0..255)
     ACCESS   read-write
     STATUS   mandatory
     DESCRIPTION
"Line Feed Insertion (p13)
This parameter specifies when the PAD should insert Linefeed upon
receipt of carriage return from the terminal or destination. As the
parameter value is bit-encoded,any combination is permissible.
 (0) = No linefeed insertion
 (1) = Insert after carriage return to terminal
 (2) = Insert in data stream after carriage return from terminal
 (4) = Insert linefeed after echo of carriage return to terminal
Default value is 4."
     ::= { nvItiprofEntry 15 }

nvItiprofP14 OBJECT-TYPE
     SYNTAX   INTEGER (0..255)
     ACCESS   read-write
     STATUS   mandatory
     DESCRIPTION
"Line Feed Padding (p14)
This parameter provides for the automatic insertion by the PAD of
padding characters or time delays after occurrence of a linefeed
character.
 (0) = No padding
 (1-255) = Padding after linefeed
Default value is 0."
     ::= { nvItiprofEntry 16 }

nvItiprofP15 OBJECT-TYPE
     SYNTAX   INTEGER (0..255)
     ACCESS   read-write
     STATUS   mandatory
     DESCRIPTION
"Editing Enable/Disable (p15)
This parameter sets character delete,line delete,and line display
actions in the data transfer state. Editing is always available in
the command state.
 (0) = No editing
 (1) = Editing enabled (data state)
Default value is 1."
     ::= { nvItiprofEntry 17 }

nvItiprofP16 OBJECT-TYPE
     SYNTAX   INTEGER (0..255)
     ACCESS   read-write
     STATUS   mandatory
     DESCRIPTION
"Character Delete Character (p16)
This parameter specifies the ASCII character to be used as
a 'character delete' character for local editing by the PAD.
 (0) = No delete character
Default value is 8."
     ::= { nvItiprofEntry 18 }

nvItiprofP17 OBJECT-TYPE
     SYNTAX   INTEGER (0..255)
     ACCESS   read-write
     STATUS   mandatory
     DESCRIPTION
"Line Delete Character (p17)
This parameter specifies the ASCII character to be used as a 'line delete'
character for local editing by the PAD.
 (0) = No line delete
Default value is 24."
     ::= { nvItiprofEntry 19 }

nvItiprofP18 OBJECT-TYPE
     SYNTAX   INTEGER (0..255)
     ACCESS   read-write
     STATUS   mandatory
     DESCRIPTION
"Line Display Character (p18)
This parameter specifies the ASCII character to be used as a 'line redisplay'
character for local editing by the PAD.
 (0) = No line redisplay.
Default value is 18."
     ::= { nvItiprofEntry 20 }

nvItiprofP19 OBJECT-TYPE
     SYNTAX   INTEGER (0..255)
     ACCESS   read-write
     STATUS   mandatory
     DESCRIPTION
"Service Signal Editing (p19)
 (0) = None
 (1) = Printing terminal edit
 (2) = CRT terminal editing
Default value is 2."
     ::= { nvItiprofEntry 21 }

nvItiprofP20 OBJECT-TYPE
     SYNTAX   INTEGER (0..255)
     ACCESS   read-write
     STATUS   mandatory
     DESCRIPTION
"Echo Mask (p20)
This parameter specifies which characters are not echoed to the
device (when p2 is set to 1).
 (0) = No mask (echo all)
 (1) = No echo CR
 (2) = No echo LF
 (4) = No echo VT,HT,FF
 (8) = No echo BEL,BS
 (16) = No echo ESC,ENQ
 (32) = No echo ACK,NAK,STX,SOH,EOT,ETX,ETB
 (64) = No echo of parameters 16,17,18
 (128) = No echo of control characters not named above
Default value is 6."
     ::= { nvItiprofEntry 22 }

nvItiprofP21 OBJECT-TYPE
     SYNTAX   INTEGER (0..255)
     ACCESS   read-write
     STATUS   mandatory
     DESCRIPTION
"Parity Treatment (p21)
This parameter specifies whether or not the PAD should detect,check and
generate parity.
 (0) = No parity detection or generation
 (1) = Parity checking and PAD handles any parity errors
 (2) = Parity generation,PAD sets the parity bit for each ASCII
character.
Default value is 3."
     ::= { nvItiprofEntry 23 }

nvItiprofP22 OBJECT-TYPE
     SYNTAX   INTEGER (0..255)
     ACCESS   read-write
     STATUS   mandatory
     DESCRIPTION
"Page Wait (p22)
This parameter specifies the number of lines (line-feeds) that will be
sent to the attached device before output is halted.
Output is subsequently resumed after an XON character or any
packetizing character is received from the device.
 (0) = No page wait enabled
 (1-255) = Number of lines output before page wait condition
Default value is 23."
     ::= { nvItiprofEntry 24 }

nvItiprofP23 OBJECT-TYPE
     SYNTAX   INTEGER (0..255)
     ACCESS   read-write
     STATUS   mandatory
     DESCRIPTION
"First Extra Forwarding Character (p23)
This parameter allow the definition of an additional data forwarding signal.
This signal is in addition to those specified by parameters 3 and 4.
 (0) = No extra character
 (1-127) = ASCII code of character
Default value is 0."
     ::= { nvItiprofEntry 25 }

nvItiprofP24 OBJECT-TYPE
     SYNTAX   INTEGER (0..255)
     ACCESS   read-write
     STATUS   mandatory
     DESCRIPTION
"Second Extra Forwarding Character (p24)
This parameter allows the definition of an additional data forwarding signal.
This signal is in addition to those characters specified by parameter 3 and 4.
 (0) = No extra character
 (1-127) = ASCII code of character
Default value is 0."
     ::= { nvItiprofEntry 26 }

nvItiprofP25 OBJECT-TYPE
     SYNTAX   INTEGER (0..255)
     ACCESS   read-write
     STATUS   mandatory
     DESCRIPTION
"Output Pending Timer (p25)
This parameter specifies the length of time,if any,that terminal output
will be blocked by terminal input.
 (0) = No output pending timer. That is,output is not blocked by input
(such as in half-duplex transmission).
 (1-255) = Delay in seconds
Default value is 1."
     ::= { nvItiprofEntry 27 }

nvItiprofP26 OBJECT-TYPE
     SYNTAX   INTEGER (0..255)
     ACCESS   read-write
     STATUS   mandatory
     DESCRIPTION
"Interval Timer (p26)
Maximum time,in 1/20 seconds,between transmission of packets.
Default value is 0."
     ::= { nvItiprofEntry 28 }

nvItiprofP27 OBJECT-TYPE
     SYNTAX   INTEGER (0..255)
     ACCESS   read-write
     STATUS   mandatory
     DESCRIPTION
"Horizontal Tab Padding (p27)
Number of nulls to output after a TAB.
Default value is 0."
     ::= { nvItiprofEntry 29 }

nvItiprofP28 OBJECT-TYPE
     SYNTAX   INTEGER (0..255)
     ACCESS   read-write
     STATUS   mandatory
     DESCRIPTION
"XON Character to PAD (p28)
Default value is 0."
     ::= { nvItiprofEntry 30 }

nvItiprofP29 OBJECT-TYPE
     SYNTAX   INTEGER (0..255)
     ACCESS   read-write
     STATUS   mandatory
     DESCRIPTION
"XOFF Character to PAD (p29)
Default value is 0."
     ::= { nvItiprofEntry 31 }

nvItiprofP30 OBJECT-TYPE
     SYNTAX   INTEGER (0..255)
     ACCESS   read-write
     STATUS   mandatory
     DESCRIPTION
"XON Character to Device (p30)
Default value is 0."
     ::= { nvItiprofEntry 32 }

nvItiprofP31 OBJECT-TYPE
     SYNTAX   INTEGER (0..255)
     ACCESS   read-write
     STATUS   mandatory
     DESCRIPTION
"XOFF Character to Device (p31)
Default value is 0."
     ::= { nvItiprofEntry 33 }

nvItiprofP32 OBJECT-TYPE
     SYNTAX   INTEGER (0..255)
     ACCESS   read-write
     STATUS   mandatory
     DESCRIPTION
"Packet Forward on Character Count (p32)
Default value is 0."
     ::= { nvItiprofEntry 34 }

nvItiprofP33 OBJECT-TYPE
     SYNTAX   INTEGER (0..255)
     ACCESS   read-write
     STATUS   mandatory
     DESCRIPTION
"CONSAT parameter 101 (TAB echo)
Default value is 0."
     ::= { nvItiprofEntry 35 }

nvItiprofP34 OBJECT-TYPE
     SYNTAX   INTEGER (0..255)
     ACCESS   read-write
     STATUS   mandatory
     DESCRIPTION
"CONSAT parameter 102 (TAB expansion)
Default value is 0."
     ::= { nvItiprofEntry 36 }

nvItiprofP35 OBJECT-TYPE
     SYNTAX   INTEGER (0..255)
     ACCESS   read-write
     STATUS   mandatory
     DESCRIPTION
"CONSAT parameter 103 (BREAK key)
Default value is 0."
     ::= { nvItiprofEntry 37 }

nvItiprofStatus OBJECT-TYPE
     SYNTAX   INTEGER {
                valid(1),
                invalid(2)
                }
     ACCESS   read-write
     STATUS   mandatory
     DESCRIPTION
           "Operation status. Add the record to the table (valid) or
           delete the record from the table (invalid)."
     ::= { nvItiprofEntry 38 }
--
--
nvItirpoa OBJECT IDENTIFIER ::= { nevadaIti 14 }

nvItirpoaMaxRec OBJECT-TYPE
      SYNTAX   INTEGER
      ACCESS   read-only
      STATUS   mandatory
      DESCRIPTION
                "total number of records allowed in database file."
      ::= {nvItirpoa 1}

nvItirpoaNumRec OBJECT-TYPE
      SYNTAX   INTEGER
      ACCESS   read-only
      STATUS   mandatory
      DESCRIPTION
                "number of records in use."
      ::= {nvItirpoa 2}

nvItirpoaTable OBJECT-TYPE
      SYNTAX   SEQUENCE OF NvItirpoaEntry
      ACCESS   not-accessible
      STATUS   mandatory
      DESCRIPTION
               "itirpoa file."
      ::= { nvItirpoa 3 }

nvItirpoaEntry OBJECT-TYPE
      SYNTAX   NvItirpoaEntry
      ACCESS   not-accessible
      STATUS   mandatory
      DESCRIPTION
               "itirpoa record."
      INDEX { nvItirpoaIndex }
      ::= { nvItirpoaTable 1 }

NvItirpoaEntry ::=
      SEQUENCE {
      nvItirpoaIndex
            INTEGER,
      nvItirpoaCode
            INTEGER,
      nvItirpoaCarrier
            DisplayString,
      nvItirpoaStatus
	    INTEGER
                }

nvItirpoaIndex OBJECT-TYPE
     SYNTAX   INTEGER
     ACCESS   read-only
     STATUS   mandatory
     DESCRIPTION
        "Index of itirpoa record"
      ::= { nvItirpoaEntry 1 }

nvItirpoaCode OBJECT-TYPE
     SYNTAX   INTEGER (0..65535)
     ACCESS   read-write
     STATUS   mandatory
     DESCRIPTION
"RPOA Code (code)
"
     ::= { nvItirpoaEntry 2 }

nvItirpoaCarrier OBJECT-TYPE
     SYNTAX   DisplayString (SIZE (0..10))
     ACCESS   read-write
     STATUS   mandatory
     DESCRIPTION
"RPOA Name (carrier)
"
     ::= { nvItirpoaEntry 3 }

nvItirpoaStatus OBJECT-TYPE
     SYNTAX   INTEGER {
                valid(1),
                invalid(2)
                }
     ACCESS   read-write
     STATUS   mandatory
     DESCRIPTION
           "Operation status. Add the record to the table (valid) or
           delete the record from the table (invalid)."
     ::= { nvItirpoaEntry 4 }


nvItiuser OBJECT IDENTIFIER ::= { nevadaIti 15 }

nvItiuserMaxRec OBJECT-TYPE
      SYNTAX   INTEGER
      ACCESS   read-only
      STATUS   mandatory
      DESCRIPTION
                "total number of records allowed in database file."
      ::= {nvItiuser 1}

nvItiuserNumRec OBJECT-TYPE
      SYNTAX   INTEGER
      ACCESS   read-only
      STATUS   mandatory
      DESCRIPTION
                "number of records in use."
      ::= {nvItiuser 2}

nvItiuserTable OBJECT-TYPE
      SYNTAX   SEQUENCE OF NvItiuserEntry
      ACCESS   not-accessible
      STATUS   mandatory
      DESCRIPTION
               "itiprof file."
      ::= { nvItiuser 3 }

nvItiuserEntry OBJECT-TYPE
      SYNTAX   NvItiuserEntry
      ACCESS   not-accessible
      STATUS   mandatory
      DESCRIPTION
               "itiuser record."
      INDEX { nvItiuserIndex }
      ::= { nvItiuserTable 1 }

NvItiuserEntry ::=
      SEQUENCE {
      nvItiuserIndex
            INTEGER,
      nvItiuserUsername
            DisplayString,
      nvItiuserCallback
            INTEGER,
      nvItiuserClrestrct
            INTEGER,
      nvItiuserInitcmd
            INTEGER,
      nvItiuserUserclass
            DisplayString,
      nvItiuserUserpaswd
            DisplayString,
      nvItiuserNumber
            DisplayString,
      nvItiuserStatus
            INTEGER
                }

nvItiuserIndex OBJECT-TYPE
     SYNTAX   INTEGER
     ACCESS   read-only
     STATUS   mandatory
     DESCRIPTION
        "Index of itiuser record"
      ::= { nvItiuserEntry 1 }

nvItiuserUsername OBJECT-TYPE
     SYNTAX   DisplayString (SIZE (0..10))
     ACCESS   read-write
     STATUS   mandatory
     DESCRIPTION
"User Name (username)
"
     ::= { nvItiuserEntry 2 }

nvItiuserCallback OBJECT-TYPE
     SYNTAX   INTEGER (0..65535)
     ACCESS   read-write
     STATUS   mandatory
     DESCRIPTION
"User Callback Number Id (callback)
Default value is 0."
     ::= { nvItiuserEntry 3 }

nvItiuserClrestrct OBJECT-TYPE
     SYNTAX   INTEGER {
                ignore(2),     -- no security (+1)
                select(3),     -- class password required
                restrict(4)      -- user password required
                }
     ACCESS   read-write
     STATUS   mandatory
     DESCRIPTION
"Class Restriction (clrestrct)
Default value is 1+1."
     ::= { nvItiuserEntry 4 }

nvItiuserInitcmd OBJECT-TYPE
     SYNTAX   INTEGER (0..65535)
     ACCESS   read-write
     STATUS   mandatory
     DESCRIPTION
"Initial Automatic Command Id (initcmd)
Default value is 0."
     ::= { nvItiuserEntry 5 }

nvItiuserUserclass OBJECT-TYPE
     SYNTAX   DisplayString (SIZE (0..10))
     ACCESS   read-write
     STATUS   mandatory
     DESCRIPTION
"Class Assignment (userclass)
"
     ::= { nvItiuserEntry 6 }

nvItiuserUserpaswd OBJECT-TYPE
     SYNTAX   DisplayString (SIZE (0..10))
     ACCESS   read-write
     STATUS   mandatory
     DESCRIPTION
"User Password (userpaswd)
"
     ::= { nvItiuserEntry 7 }

nvItiuserStatus OBJECT-TYPE
     SYNTAX   INTEGER {
                valid(1),
                invalid(2)
                }
     ACCESS   read-write
     STATUS   mandatory
     DESCRIPTION
           "Operation status. Add the record to the table (valid) or
           delete the record from the table (invalid)."
     ::= { nvItiuserEntry 8 }
     
nvItiuserNumber OBJECT-TYPE
     SYNTAX   DisplayString (SIZE (0..16))
     ACCESS   read-write
     STATUS   mandatory
     DESCRIPTION
     "Call back number"
     ::= { nvItiuserEntry 9 }
     
--
-- duiconf
--
nvDuiconf OBJECT IDENTIFIER ::= { nevadaIti 17 }

nvDuiconfMaxRec OBJECT-TYPE
      SYNTAX   INTEGER
      ACCESS   read-only
      STATUS   mandatory
      DESCRIPTION
                "total number of records allowed in database file."
      ::= {nvDuiconf 1}

nvDuiconfNumRec OBJECT-TYPE
      SYNTAX   INTEGER
      ACCESS   read-only
      STATUS   mandatory
      DESCRIPTION
                "number of records in use."
      ::= {nvDuiconf 2}

nvDuiconfTable OBJECT-TYPE
      SYNTAX   SEQUENCE OF NvDuiconfEntry
      ACCESS   not-accessible
      STATUS   mandatory
      DESCRIPTION
               "duiconf file."
      ::= { nvDuiconf 3 }

nvDuiconfEntry OBJECT-TYPE
      SYNTAX   NvDuiconfEntry
      ACCESS   not-accessible
      STATUS   mandatory
      DESCRIPTION
               "duiconf record."
      INDEX { nvDuiconfIndex }
      ::= { nvDuiconfTable 1 }

NvDuiconfEntry ::=
      SEQUENCE {
      nvDuiconfIndex
            INTEGER,
      nvDuiconfType
            INTEGER,
      nvDuiconfNua
            DisplayString,
      nvDuiconfCalling
            DisplayString,
      nvDuiconfFirsttry
            INTEGER,
      nvDuiconfRetrytime
            INTEGER,
      nvDuiconfRetryinc
            INTEGER,
      nvDuiconfStatus
            INTEGER
               }

nvDuiconfIndex OBJECT-TYPE
     SYNTAX   INTEGER
     ACCESS   read-only
     STATUS   mandatory
     DESCRIPTION
        "index"
     ::= {nvDuiconfEntry 1 }

nvDuiconfType OBJECT-TYPE
     SYNTAX   INTEGER {
                primary(1),     -- (+1)
                alternate(2)
                }
     ACCESS   read-only
     STATUS   mandatory
     DESCRIPTION
        "Type of DUI Circuit."
     ::= {nvDuiconfEntry 2 }

nvDuiconfNua OBJECT-TYPE
     SYNTAX   DisplayString (SIZE(0..16))
     ACCESS   read-write
     STATUS   mandatory
     DESCRIPTION
        "X.121 address of DUI host."
     ::= {nvDuiconfEntry 3 }

nvDuiconfCalling OBJECT-TYPE
     SYNTAX   DisplayString (SIZE(0..16))
     ACCESS   read-write
     STATUS   mandatory
     DESCRIPTION
        "calling address."
     ::= {nvDuiconfEntry 4 }

nvDuiconfFirsttry OBJECT-TYPE
     SYNTAX   INTEGER
     ACCESS   read-write
     STATUS   mandatory
     DESCRIPTION
        "num seconds til first try."
     ::= {nvDuiconfEntry 5 }

nvDuiconfRetrytime OBJECT-TYPE
     SYNTAX   INTEGER
     ACCESS   read-write
     STATUS   mandatory
     DESCRIPTION
        "num seconds for retry."
     ::= {nvDuiconfEntry 6 }

nvDuiconfRetryinc OBJECT-TYPE
     SYNTAX   INTEGER
     ACCESS   read-write
     STATUS   mandatory
     DESCRIPTION
        "retry time increment (in seconds)."
     ::= {nvDuiconfEntry 7 }

nvDuiconfStatus OBJECT-TYPE
     SYNTAX   INTEGER {
                valid(1),
                invalid(2)
                }
     ACCESS   read-write
     STATUS   mandatory
     DESCRIPTION
           "Operation status. Add the record to the table (valid) or
           delete the record from the table (invalid)."
     ::= { nvDuiconfEntry 9 }

--
--      dlspcconf
--

nvDlspcconf OBJECT IDENTIFIER ::= {nevadaIti 18}

nvDlspcconfMaxRec OBJECT-TYPE
      SYNTAX   INTEGER
      ACCESS   read-only
      STATUS   mandatory
      DESCRIPTION
                "total number of records allowed in database file."
      ::= {nvDlspcconf 1}

nvDlspcconfNumRec OBJECT-TYPE
      SYNTAX   INTEGER
      ACCESS   read-only
      STATUS   mandatory
      DESCRIPTION
                "number of records in use."
      ::= {nvDlspcconf 2}

nvDlspcconfTable OBJECT-TYPE
      SYNTAX   SEQUENCE OF NvDlspcconfEntry
      ACCESS   not-accessible
      STATUS   mandatory
      DESCRIPTION
               "dlspcconf file."
      ::= {nvDlspcconf 3}

nvDlspcconfEntry OBJECT-TYPE
      SYNTAX   NvDlspcconfEntry
      ACCESS   not-accessible
      STATUS   mandatory
      DESCRIPTION
               "dlspcconf record."
      INDEX   {nvDlspcconfIndex}
      ::= {nvDlspcconfTable 1 }

NvDlspcconfEntry ::=
      SEQUENCE {
        nvDlspcconfIndex
                INTEGER,
        nvDlspcconfNodename
                DisplayString,
        nvDlspcconfSitename
                DisplayString,
        nvDlspcconfHelpphone
                DisplayString,
        nvDlspcconfAbortmsg
                INTEGER,
        nvDlspcconfPidtable
                INTEGER,
        nvDlspcconfPortalarm
                INTEGER,
        nvDlspcconfStatus
                INTEGER
     }

nvDlspcconfIndex OBJECT-TYPE
     SYNTAX   INTEGER
     ACCESS   read-only
     STATUS   mandatory
     DESCRIPTION
        "Dlspcconf file record number."
     ::= {nvDlspcconfEntry 1 }

nvDlspcconfNodename OBJECT-TYPE
     SYNTAX   DisplayString  (SIZE(0..16))
     ACCESS   read-write
     STATUS   mandatory
     DESCRIPTION
        "name of node."
     ::= {nvDlspcconfEntry 2 }

nvDlspcconfSitename OBJECT-TYPE
     SYNTAX   DisplayString  (SIZE(0..30))
     ACCESS   read-write
     STATUS   mandatory
     DESCRIPTION
        "name of site."
     ::= {nvDlspcconfEntry 3 }

nvDlspcconfHelpphone OBJECT-TYPE
     SYNTAX   DisplayString  (SIZE(0..16))
     ACCESS   read-write
     STATUS   mandatory
     DESCRIPTION
        "phone number part of help message."
     ::= {nvDlspcconfEntry 4 }

nvDlspcconfAbortmsg OBJECT-TYPE
     SYNTAX   INTEGER
     ACCESS   read-write
     STATUS   mandatory
     DESCRIPTION
        "message if session cannot be resumed."
     ::= {nvDlspcconfEntry 5 }

nvDlspcconfPidtable OBJECT-TYPE
     SYNTAX   INTEGER
     ACCESS   read-write
     STATUS   mandatory
     DESCRIPTION
        "to map X.3 P11 into protocol id."
     ::= {nvDlspcconfEntry 6 }

nvDlspcconfPortalarm OBJECT-TYPE
     SYNTAX   INTEGER
     ACCESS   read-write
     STATUS   mandatory
     DESCRIPTION
        "number of idle ports to cause alarm."
     ::= {nvDlspcconfEntry 7 }

nvDlspcconfStatus OBJECT-TYPE
     SYNTAX   INTEGER {
                valid(1),
                invalid(2)
     }
     ACCESS   read-write
     STATUS   mandatory
     DESCRIPTION
           "Operation status. Add the record to the table (valid) or
           delete the record from the table (invalid)."
     ::= { nvDlspcconfEntry 8 }

--
--      dlstat file
--
nvDlstat OBJECT IDENTIFIER ::= {nevadaSync 1}

nvDlstatMaxRec OBJECT-TYPE
      SYNTAX   INTEGER
      ACCESS   read-only
      STATUS   mandatory
      DESCRIPTION
                "total number of records allowed in database file."
      ::= {nvDlstat 1}

nvDlstatNumRec OBJECT-TYPE
      SYNTAX   INTEGER
      ACCESS   read-only
      STATUS   mandatory
      DESCRIPTION
                "number of records in use."
      ::= {nvDlstat 2}

nvDlstatTable OBJECT-TYPE
      SYNTAX   SEQUENCE OF NvDlstatEntry
      ACCESS   not-accessible
      STATUS   mandatory
      DESCRIPTION
               "dlstat file."
      ::= {nvDlstat 3}

nvDlstatEntry OBJECT-TYPE
      SYNTAX   NvDlstatEntry
      ACCESS   not-accessible
      STATUS   mandatory
      DESCRIPTION
               "dlstat record."
      INDEX {nvDlstatIndex}
      ::= {nvDlstatTable 1 }

NvDlstatEntry ::=
      SEQUENCE {
      nvDlstatIndex
            INTEGER,
      nvDlstatLinkname
            INTEGER,
      nvDlstatApp
            INTEGER,
      nvDlstatLfrmr
            INTEGER,
      nvDlstatLreset
            INTEGER,
      nvDlstatMstate
            INTEGER,
      nvDlstatProtocol
            INTEGER,
      nvDlstatPstate
            INTEGER,
      nvDlstatSstate
            INTEGER,
      nvDlstatAbtfrxs
            Counter,
      nvDlstatAlarms
            Counter,
      nvDlstatFrmrrxs
            Counter,
      nvDlstatFrmrtxs
            Counter,
      nvDlstatIfrxs
            Counter,
      nvDlstatIftxs
            Counter,
      nvDlstatRejrxs
            Counter,
      nvDlstatRejtxs
            Counter,
      nvDlstatRnrrxs
            Counter,
      nvDlstatRnrtxs
            Counter,
      nvDlstatRrrxs
            Counter,
      nvDlstatRrtxs
            Counter,
      nvDlstatRxdds
            Counter,
      nvDlstatTouts
            Counter,
      nvDlstatTretrys
            Counter,
      nvDlstatDtreset
            DisplayString
               }

nvDlstatIndex OBJECT-TYPE
     SYNTAX   INTEGER
     ACCESS   read-only
     STATUS   mandatory
     DESCRIPTION
        "Index of dlstat"
     ::= {nvDlstatEntry 1 }

nvDlstatLinkname OBJECT-TYPE
     SYNTAX   INTEGER {
                nolink(1),              -- (+1)
                link1(2),
                link2(3),
                link3(4),
                link4(5),
                link5(6),
                link6(7),
                link7(8),
                link8(9),
                link9(10),
                link10(11),
                link11(12),
                link12(13),
                link13(14),
                link14(15),
                link15(16),
                link16(17),
                link17(18),
                link18(19),
                link19(20),
                link20(21),
                link21(22),
                link22(23),
                link23(24),
                link24(25),
                link25(26),
                link26(27),
                link27(28),
                link28(29),
                link29(30),
                link30(31),
                link31(32),
                link32(33),
                link33(34),
                link34(35),
                link35(36),
                link36(37),
                link37(38),
                link38(39),
                link39(40),
                link40(41),
                link41(42),
                link42(43),
                link43(44),
                link44(45),
                link45(46),
                link46(47),
                link47(48),
                link48(49),
                link49(50),
                link50(51),
                link51(52),
                link52(53),
                link53(54),
                link54(55),
                link55(56),
                link56(57),
                link57(58),
                link58(59),
                link59(60),
                link60(61),
                link61(62),
                link62(63),
                link63(64),
                link64(65),
                link65(66),
                link66(67),
                link67(68),
                link68(69),
                link69(70),
                link70(71),
                link71(72),
                link72(73),
                link73(74),
                link74(75),
                link75(76),
                link76(77),
                link77(78),
                link78(79),
                link79(80),
                link80(81),
                link81(82),
                link82(83),
                link83(84),
                link84(85),
                link85(86),
                link86(87),
                link87(88),
                link88(89),
                link89(90),
                link90(91),
                link91(92),
                link92(93),
                link93(94),
                link94(95),
                link95(96),
                link96(97),
                link97(98),
                link98(99),
                link99(100),
                link100(101),
                link101(102),
                link102(103),
                link103(104),
                link104(105),
                link105(106),
                link106(107),
                link107(108),
                link108(109),
                link109(110),
                link110(111),
                link111(112),
                link112(113),
                link113(114),
                link114(115),
                link115(116),
                link116(117),
                link117(118),
                link118(119),
                link119(120),
                link120(121),
                link121(122),
                link122(123),
                link123(124),
                link124(125),
                link125(126),
                link126(127),
                link127(128),
                link128(129),
                link129(130),
                link130(131),
                link131(132),
                link132(133),
                link133(134),
                link134(135),
                link135(136),
                link136(137),
                link137(138),
                link138(139),
                link139(140),
                link140(141),
                link141(142),
                link142(143),
                link143(144),
                link144(145),
                link145(146),
                link146(147),
                link147(148),
                link148(149),
                link149(150),
                link150(151),
                link151(152),
                link152(153),
                link153(154),
                link154(155),
                link155(156),
                link156(157),
                link157(158),
                link158(159),
                link159(160),
                link160(161),
                link161(162),
                link162(163),
                link163(164),
                link164(165),
                link165(166),
                link166(167),
                link167(168),
                link168(169),
                link169(170),
                link170(171),
                link171(172),
                link172(173),
                link173(174),
                link174(175),
                link175(176),
                link176(177),
                link177(178),
                link178(179),
                link179(180),
                link180(181),
                link181(182),
                link182(183),
                link183(184),
                link184(185),
                link185(186),
                link186(187),
                link187(188),
                link188(189),
                link189(190),
                link190(191),
                link191(192),
                link192(193),
                link193(194),
                link194(195),
                link195(196),
                link196(197),
                link197(198),
                link198(199),
                link199(200),
                link200(201),
                link201(202),
                link202(203),
                link203(204),
                link204(205),
                link205(206),
                link206(207),
                link207(208),
                link208(209),
                link209(210),
                link210(211),
                link211(212),
                link212(213),
                link213(214),
                link214(215),
                link215(216),
                link216(217),
                link217(218),
                link218(219),
                link219(220),
                link220(221),
                link221(222),
                link222(223),
                link223(224),
                link224(225),
                link225(226),
                link226(227),
                link227(228),
                link228(229),
                link229(230),
                link230(231),
                link231(232),
                link232(233),
                link233(234),
                link234(235),
                link235(236),
                link236(237),
                link237(238),
                link238(239),
                link239(240),
                link240(241),
                link241(242),
                link242(243),
                link243(244),
                link244(245),
                link245(246),
                link246(247),
                link247(248),
                link248(249),
                link249(250),
                link250(251),
                link251(252),
                link252(253),
                link253(254),
                link254(255),
                link255(256),
                link256(257),
                link257(258),
                link258(259),
                link259(260),
                link260(261),
                link261(262),
                link262(263),
                link263(264),
                link264(265),
                link265(266),
                link266(267),
                link267(268),
                link268(269),
                link269(270),
                link270(271),
                link271(272),
                link272(273),
                link273(274),
                link274(275),
                link275(276),
                link276(277),
                link277(278),
                link278(279),
                link279(280),
                link280(281),
                link281(282),
                link282(283),
                link283(284),
                link284(285),
                link285(286),
                link286(287),
                link287(288),
                link288(289),
                link289(290),
                link290(291),
                link291(292),
                link292(293),
                link293(294),
                link294(295),
                link295(296),
                link296(297),
                link297(298),
                link298(299),
                link299(300),
                link300(301),
                link301(302),
                link302(303),
                link303(304),
                link304(305),
                link305(306),
                link306(307),
                link307(308),
                link308(309),
                link309(310),
                link310(311),
                link311(312),
                link312(313),
                link313(314),
                link314(315),
                link315(316),
                link316(317),
                link317(318),
                link318(319),
                link319(320),
                link320(321),
                link321(322),
                link322(323),
                link323(324),
                link324(325),
                link325(326),
                link326(327),
                link327(328),
                link328(329),
                link329(330),
                link330(331),
                link331(332),
                link332(333),
                link333(334),
                link334(335),
                link335(336),
                link336(337),
                link337(338),
                link338(339),
                link339(340),
                link340(341),
                link341(342),
                link342(343),
                link343(344),
                link344(345),
                link345(346),
                link346(347),
                link347(348),
                link348(349),
                link349(350),
                link350(351),
                link351(352),
                link352(353),
                link353(354),
                link354(355),
                link355(356),
                link356(357),
                link357(358),
                link358(359),
                link359(360),
                link360(361),
                link361(362),
                link362(363),
                link363(364),
                link364(365),
                link365(366),
                link366(367),
                link367(368),
                link368(369),
                link369(370),
                link370(371),
                link371(372),
                link372(373),
                link373(374),
                link374(375),
                link375(376),
                link376(377),
                link377(378),
                link378(379),
                link379(380),
                link380(381),
                link381(382),
                link382(383),
                link383(384),
                link384(385),
                link385(386),
                link386(387),
                link387(388),
                link388(389),
                link389(390),
                link390(391),
                link391(392),
                link392(393),
                link393(394),
                link394(395),
                link395(396),
                link396(397),
                link397(398),
                link398(399),
                link399(400),
                link400(401),
                link401(402),
                link402(403),
                link403(404),
                link404(405),
                link405(406),
                link406(407),
                link407(408),
                link408(409),
                link409(410),
                link410(411),
                link411(412),
                link412(413),
                link413(414),
                link414(415),
                link415(416),
                link416(417),
                link417(418),
                link418(419),
                link419(420),
                link420(421),
                link421(422),
                link422(423),
                link423(424),
                link424(425),
                link425(426),
                link426(427),
                link427(428),
                link428(429)
 }
     ACCESS   read-only
     STATUS   mandatory
     DESCRIPTION
        "name of link being used
         Initial status is 0+1."
     ::= {nvDlstatEntry 2 }

nvDlstatApp OBJECT-TYPE
     SYNTAX   INTEGER {
                dte(1),                 -- (+1)
                dce(2),
                primarySdlcStation(3),
                secondarySdlcStation(4),
                idle(5)
                }
     ACCESS   read-only
     STATUS   mandatory
     DESCRIPTION
        "link appearence
         Initial status is 0+1."
     ::= {nvDlstatEntry 3 }

nvDlstatLfrmr OBJECT-TYPE
     SYNTAX   INTEGER {
                none(1),                -- (+1)
                badNR(17),
                overrun(33),
                undefinedControlField(122),
                badSUFrame(193)
                }
     ACCESS   read-only
     STATUS   mandatory
     DESCRIPTION
        "reason code from last FRMR received
         Initial status is 0+1."
     ::= {nvDlstatEntry 4 }

nvDlstatLreset OBJECT-TYPE
     SYNTAX   INTEGER {
                none(1),                -- (+1)
                badCommandFrame(2),
                badResponseFrame(4),
                receiverOverrun(5),
                badNR(9),
                networkDisconnect(10),
                driverDisconnect(11),
                unsolicitedFinal(12),
                frmr(13),
                unexpectedUA(14),
                remoteTimeout(15),
                sabm(16),
                sarm(17),
                disc(18),
                dm(19),
                snrm(20)
                }
     ACCESS   read-only
     STATUS   mandatory
     DESCRIPTION
        "reason for last link reset
         Initial status is 0+1."
     ::= {nvDlstatEntry 5 }

nvDlstatMstate OBJECT-TYPE
     SYNTAX   INTEGER {
                disabled(1),            -- (+1)
                down(2),
                startingDriver(3),
                discSent(4),
                sabmSent(5),
                sarmSetup(6),
                frmrSent(7),
                sabmReset(8),
                up(9),
                clearing(10),
                dm(11),
                nu(12),
                sabmAwaitingRrAFterCr(13),
                badCmdAwaitingRrToSendFrmr(14),
                frmrAwaitingRrToEnterRs(15),
                discAwaitingRrToEnterSs(16),
                awaitingIdleDriverToSendDn(17),
                awaitingIdleDriverToResend(18),
                waitingToSendDisc(19),
                waitingToSendSnrm(20),
                disconnectMode(21),
                waitingToSendXid(22),
                sentXid(23),
                multipleSnrm(24)
                }
     ACCESS   read-only
     STATUS   mandatory
     DESCRIPTION
        "main state of link
         Initial status is 0+1."
     ::= {nvDlstatEntry 6 }

nvDlstatProtocol OBJECT-TYPE
     SYNTAX   INTEGER {
                unconfigured(1),        -- (+1)
                lap(2),
                lapb(4),
                lapbExtended(8),
                austrianPTT(12),
                pss(16),
                sdlc(17),
                sdlcExtended(49)
                }
     ACCESS   read-only
     STATUS   mandatory
     DESCRIPTION
        "link procedure selected
         Initial status is 3+1."
     ::= {nvDlstatEntry 7 }

nvDlstatPstate OBJECT-TYPE
     SYNTAX   INTEGER {
                disabled(1),            -- (+1)
                down(2),
                normalReceiveMode(3),
                remoteBusy(4),
                remoteTimedOut(5)
                }
     ACCESS   read-only
     STATUS   mandatory
     DESCRIPTION
        "a. primary UP state
         Initial status is 1+1."
     ::= {nvDlstatEntry 8 }

nvDlstatSstate OBJECT-TYPE
        --% ALIAS "Secondary State"
     SYNTAX   INTEGER {
                disabled(1),            -- (+1)
                down(2),
                normalTransmit(3),
                localBusy(4),
                rejectFrameSent(5)
                }
     ACCESS   read-only
     STATUS   mandatory
     DESCRIPTION
        "Secondary UP state .  Initial status is 1+1."
     ::= {nvDlstatEntry 9 }

nvDlstatAbtfrxs OBJECT-TYPE
     SYNTAX   Counter
     ACCESS   read-only
     STATUS   mandatory
     DESCRIPTION
        "a. Number of aborted frames received
         Statistic is zeroed at startup time."
     ::= {nvDlstatEntry 10 }

nvDlstatAlarms OBJECT-TYPE
     SYNTAX   Counter
     ACCESS   read-only
     STATUS   mandatory
     DESCRIPTION
        "Number of alarms.
         Statistic is zeroed at startup time."
     ::= {nvDlstatEntry 11 }

nvDlstatFrmrrxs OBJECT-TYPE
     SYNTAX   Counter
     ACCESS   read-only
     STATUS   mandatory
     DESCRIPTION
        "a. Number of frame-reject frames received
         Statistic is zeroed at startup time."
     ::= {nvDlstatEntry 12 }

nvDlstatFrmrtxs OBJECT-TYPE
     SYNTAX   Counter
     ACCESS   read-only
     STATUS   mandatory
     DESCRIPTION
        "Number of frame-reject frames transmitted.
         Statistic is zeroed at startup time."
     ::= {nvDlstatEntry 13 }

nvDlstatIfrxs OBJECT-TYPE
     SYNTAX   Counter
     ACCESS   read-only
     STATUS   mandatory
     DESCRIPTION
        "Number of I-frames received.
         Statistic is zeroed at startup time."
     ::= {nvDlstatEntry 14 }

nvDlstatIftxs OBJECT-TYPE
     SYNTAX   Counter
     ACCESS   read-only
     STATUS   mandatory
     DESCRIPTION
        "Number of I-frames transmitted.
         Statistic is zeroed at startup time."
     ::= {nvDlstatEntry 15 }

nvDlstatRejrxs OBJECT-TYPE
     SYNTAX   Counter
     ACCESS   read-only
     STATUS   mandatory
     DESCRIPTION
        "Number of REJ-frames received.
         Statistic is zeroed at startup time."
     ::= {nvDlstatEntry 16 }

nvDlstatRejtxs OBJECT-TYPE
     SYNTAX   Counter
     ACCESS   read-only
     STATUS   mandatory
     DESCRIPTION
        "Number of REJ-frames transmitted.
         Statistic is zeroed at startup time."
     ::= {nvDlstatEntry 17 }

nvDlstatRnrrxs OBJECT-TYPE
     SYNTAX   Counter
     ACCESS   read-only
     STATUS   mandatory
     DESCRIPTION
        "Number of RNR-frames received.
         Statistic is zeroed at startup time."
     ::= {nvDlstatEntry 18 }

nvDlstatRnrtxs OBJECT-TYPE
     SYNTAX   Counter
     ACCESS   read-only
     STATUS   mandatory
     DESCRIPTION
         "Number of RNR-frames transmitted.
         Statistic is zeroed at startup time."
     ::= {nvDlstatEntry 19 }

nvDlstatRrrxs OBJECT-TYPE
     SYNTAX   Counter
     ACCESS   read-only
     STATUS   mandatory
     DESCRIPTION
        "Number of RR-frames received.
         Statistic is zeroed at startup time."
     ::= {nvDlstatEntry 20 }

nvDlstatRrtxs OBJECT-TYPE
     SYNTAX   Counter
     ACCESS   read-only
     STATUS   mandatory
     DESCRIPTION
        "Number of RR-frames transmitted.
         Statistic is zeroed at startup time."
     ::= {nvDlstatEntry 21 }

nvDlstatRxdds OBJECT-TYPE
     SYNTAX   Counter
     ACCESS   read-only
     STATUS   mandatory
     DESCRIPTION
        "Number of receive device-driver errors.
         Statistic is zeroed at startup time."
     ::= {nvDlstatEntry 22 }

nvDlstatTouts OBJECT-TYPE
     SYNTAX   Counter
     ACCESS   read-only
     STATUS   mandatory
     DESCRIPTION
        "Number of link resets due to remote timeouts.
         Statistic is zeroed at startup time."
     ::= {nvDlstatEntry 23 }

nvDlstatTretrys OBJECT-TYPE
     SYNTAX   Counter
     ACCESS   read-only
     STATUS   mandatory
     DESCRIPTION
        "Number of retries due to remote timeouts.
         Statistic is zeroed at startup time."
     ::= {nvDlstatEntry 24 }

nvDlstatDtreset OBJECT-TYPE
     SYNTAX   DisplayString (SIZE (0..20))
     ACCESS   read-only
     STATUS   mandatory
     DESCRIPTION
        "date & time statistics last reset"
      ::= {nvDlstatEntry 25 }

--
--      linkstat file
--
nvLinkstat OBJECT IDENTIFIER ::= {nevadaSync 2}

nvLinkstatMaxRec OBJECT-TYPE
      SYNTAX   INTEGER
      ACCESS   read-only
      STATUS   mandatory
      DESCRIPTION
                "total number of records allowed in database file."
      ::= {nvLinkstat 1}

nvLinkstatNumRec OBJECT-TYPE
      SYNTAX   INTEGER
      ACCESS   read-only
      STATUS   mandatory
      DESCRIPTION
                "number of records in use."
      ::= {nvLinkstat 2}

nvLinkstatTable OBJECT-TYPE
      SYNTAX   SEQUENCE OF NvLinkstatEntry
      ACCESS   not-accessible
      STATUS   mandatory
      DESCRIPTION
               "linkstat file."
      ::= {nvLinkstat 3}

nvLinkstatEntry OBJECT-TYPE
      SYNTAX   NvLinkstatEntry
      ACCESS   not-accessible
      STATUS   mandatory
      DESCRIPTION
         "linkstat record."
      INDEX     {nvLinkstatIndex}
      ::= {nvLinkstatTable 1 }

NvLinkstatEntry ::=
      SEQUENCE {
      nvLinkstatIndex
            INTEGER,
      nvLinkstatPort
            DisplayString,
      nvLinkstatApp
            INTEGER,
      nvLinkstatFstate
            INTEGER,
      nvLinkstatLfrmr
            INTEGER,
      nvLinkstatLreset
            INTEGER,
      nvLinkstatN1
            INTEGER,
      nvLinkstatProtocol
            INTEGER,
      nvLinkstatAbtfrxs
            Counter,
      nvLinkstatAlarms
            Counter,
      nvLinkstatFrmrrxs
            Counter,
      nvLinkstatFrmrtxs
            Counter,
      nvLinkstatIfrxs
            Counter,
      nvLinkstatIftxs
            Counter,
      nvLinkstatRejrxs
            Counter,
      nvLinkstatRejtxs
            Counter,
      nvLinkstatRnrrxs
            Counter,
      nvLinkstatRnrtxs
            Counter,
      nvLinkstatRrrxs
            Counter,
      nvLinkstatRrtxs
            Counter,
      nvLinkstatRxdds
            Counter,
      nvLinkstatTouts
            Counter,
      nvLinkstatTretrys
            Counter,
      nvLinkstatTchartxs
            Counter,
      nvLinkstatTcharrxs
            Counter,
      nvLinkstatDtreset
            DisplayString,
      nvLinkstatNlinkup
	    Counter
               }

nvLinkstatIndex OBJECT-TYPE
     SYNTAX   INTEGER
     ACCESS   read-only
     STATUS   mandatory
     DESCRIPTION
        "Index of linkstat record"
     ::= {nvLinkstatEntry 1 }
--
nvLinkstatPort OBJECT-TYPE
     SYNTAX   DisplayString (SIZE (1..11))
     ACCESS   read-only
     STATUS   mandatory
     DESCRIPTION
        "name of port being used
         Initial status is 0."
     ::= {nvLinkstatEntry 2 }

nvLinkstatApp OBJECT-TYPE
     SYNTAX   INTEGER {
                dte(1),                         -- (+1)
                dce(2),
                primarySDLCStation(3),
                secondarySDLCStation(4),
                idle(5)
                }
     ACCESS   read-only
     STATUS   mandatory
     DESCRIPTION
        "link appearence Initial status is 0+1."
     ::= {nvLinkstatEntry 3 }

nvLinkstatFstate OBJECT-TYPE
     SYNTAX   INTEGER {
                disabled(1),            -- (+1)
                down(2),
                startingDriver(3),
                up(4)
                }
     ACCESS   read-only
     STATUS   mandatory
     DESCRIPTION
        "main state of FLTE FSM
         Initial status is 0+1."
     ::= {nvLinkstatEntry 4 }

nvLinkstatLfrmr OBJECT-TYPE
     SYNTAX   INTEGER {
                none(1),                        -- (+1)
                badNR(17),
                overrun(33),
                undefinedControlField(129),
                badSUFrame(193)
                }
     ACCESS   read-only
     STATUS   mandatory
     DESCRIPTION
        "reason code from last FRMR received
         Initial status is 0+1."
     ::= {nvLinkstatEntry 5 }

nvLinkstatLreset OBJECT-TYPE
     SYNTAX   INTEGER {
                none(1),                -- (+1)
                illegalCommand(2),
                illegalResponse(4),
                receiverOverrun(5),
                illegalNr(9),
                networkDisconnect(10),
                driverDisconnect(11),
                unsolicitedFinal(12),
                frmrOrCmdr(13),
                unexpectedUa(14),
                remoteTimedOut(15),
                sabm(16),
                sarm(17),
                disconnect(18),
                dm(19),
                snrm(20)
                }
     ACCESS   read-only
     STATUS   mandatory
     DESCRIPTION
        "reason for last link reset
         Initial status is 0+1."
     ::= {nvLinkstatEntry 6 }

nvLinkstatN1 OBJECT-TYPE
     SYNTAX   INTEGER
     ACCESS   read-only
     STATUS   mandatory
     DESCRIPTION
        " actual n1 used (in bits)
         Initial status is 0."
     ::= {nvLinkstatEntry 7 }

nvLinkstatProtocol OBJECT-TYPE
     SYNTAX   INTEGER {
                unconfigured(1),        -- (+1)
                lap(2),
                lapb(4),
                lapbExtended(8),
                austrianPTT(12),
                pss(16),
                sdlc(17),
                sdlcExtended(49)
                }
     ACCESS   read-only
     STATUS   mandatory
     DESCRIPTION
        "link procedure selected
         Initial status is 3+1."
    ::= {nvLinkstatEntry 8 }

nvLinkstatAbtfrxs OBJECT-TYPE
     SYNTAX   Counter
     ACCESS   read-only
     STATUS   mandatory
     DESCRIPTION
        "Number of aborted frames received.
         Statistic is zeroed at startup time."
     ::= {nvLinkstatEntry 9 }

nvLinkstatAlarms OBJECT-TYPE
     SYNTAX   Counter
     ACCESS   read-only
     STATUS   mandatory
     DESCRIPTION
        "Number of alarms.
         Statistic is zeroed at startup time."
     ::= {nvLinkstatEntry 10 }

nvLinkstatFrmrrxs OBJECT-TYPE
     SYNTAX   Counter
     ACCESS   read-only
     STATUS   mandatory
     DESCRIPTION
        "Number of frame-reject frames received.
         Statistic is zeroed at startup time."
     ::= {nvLinkstatEntry 11 }

nvLinkstatFrmrtxs OBJECT-TYPE
     SYNTAX   Counter
     ACCESS   read-only
     STATUS   mandatory
     DESCRIPTION
        "Number of frame-reject frames transmitted.
         Statistic is zeroed at startup time."
     ::= {nvLinkstatEntry 12 }

nvLinkstatIfrxs OBJECT-TYPE
     SYNTAX   Counter
     ACCESS   read-only
     STATUS   mandatory
     DESCRIPTION
        "Number of I-frames received.
         Statistic is zeroed at startup time."
     ::= {nvLinkstatEntry 13 }

nvLinkstatIftxs OBJECT-TYPE
     SYNTAX   Counter
     ACCESS   read-only
     STATUS   mandatory
     DESCRIPTION
        "Number of I-frames transmitted.
         Statistic is zeroed at startup time."
     ::= {nvLinkstatEntry 14 }

nvLinkstatRejrxs OBJECT-TYPE
     SYNTAX   Counter
     ACCESS   read-only
     STATUS   mandatory
     DESCRIPTION
        "Number of REJ-frames received.
         Statistic is zeroed at startup time."
     ::= {nvLinkstatEntry 15 }

nvLinkstatRejtxs OBJECT-TYPE
     SYNTAX   Counter
     ACCESS   read-only
     STATUS   mandatory
     DESCRIPTION
        "Number of REJ-frames transmitted.
         Statistic is zeroed at startup time."
     ::= {nvLinkstatEntry 16 }

nvLinkstatRnrrxs OBJECT-TYPE
     SYNTAX   Counter
     ACCESS   read-only
     STATUS   mandatory
     DESCRIPTION
        "Number of RNR-frames received.
         Statistic is zeroed at startup time."
     ::= {nvLinkstatEntry 17 }

nvLinkstatRnrtxs OBJECT-TYPE
     SYNTAX   Counter
     ACCESS   read-only
     STATUS   mandatory
     DESCRIPTION
        "Number of RNR-frames transmitted.
         Statistic is zeroed at startup time."
     ::= {nvLinkstatEntry 18 }

nvLinkstatRrrxs OBJECT-TYPE
     SYNTAX   Counter
     ACCESS   read-only
     STATUS   mandatory
     DESCRIPTION
        "Number of RR-frames received.
         Statistic is zeroed at startup time."
     ::= {nvLinkstatEntry 19 }

nvLinkstatRrtxs OBJECT-TYPE
     SYNTAX   Counter
     ACCESS   read-only
     STATUS   mandatory
     DESCRIPTION
        "Number of RR-frames transmitted.
         Statistic is zeroed at startup time."
     ::= {nvLinkstatEntry 20 }

nvLinkstatRxdds OBJECT-TYPE
     SYNTAX   Counter
     ACCESS   read-only
     STATUS   mandatory
     DESCRIPTION
        "Number of receive device-driver errors.
         Statistic is zeroed at startup time."
     ::= {nvLinkstatEntry 21 }

nvLinkstatTouts OBJECT-TYPE
     SYNTAX   Counter
     ACCESS   read-only
     STATUS   mandatory
     DESCRIPTION
        "Number of link resets due to remote timeouts.
         Statistic is zeroed at startup time."
     ::= {nvLinkstatEntry 22 }

nvLinkstatTretrys OBJECT-TYPE
     SYNTAX   Counter
     ACCESS   read-only
     STATUS   mandatory
     DESCRIPTION
        "Number of retries due to remote timeouts.
         Statistic is zeroed at startup time."
     ::= {nvLinkstatEntry 23 }

nvLinkstatTchartxs OBJECT-TYPE
     SYNTAX   Counter
     ACCESS   read-only
     STATUS   mandatory
     DESCRIPTION
        "Number of characters sent.
         Statistic is zeroed at startup time."
     ::= {nvLinkstatEntry 24 }

nvLinkstatTcharrxs OBJECT-TYPE
     SYNTAX   Counter
     ACCESS   read-only
     STATUS   mandatory
     DESCRIPTION
        "Number of characters received.
         Statistic is zeroed at startup time."
     ::= {nvLinkstatEntry 25 }

nvLinkstatDtreset OBJECT-TYPE
     SYNTAX   DisplayString (SIZE (0..20))
     ACCESS   read-only
     STATUS   mandatory
     DESCRIPTION
        "date & time statistics last reset"
      ::= {nvLinkstatEntry 26 }

nvLinkstatNlinkup OBJECT-TYPE
     SYNTAX   Counter
     ACCESS   read-only
     STATUS   mandatory
     DESCRIPTION
        "Number of times link came up."
     ::= {nvLinkstatEntry 27 }


nvDlconf OBJECT IDENTIFIER ::= { nevadaSync 3 }

nvDlconfMaxRec OBJECT-TYPE
      SYNTAX   INTEGER
      ACCESS   read-only
      STATUS   mandatory
      DESCRIPTION
                "total number of records allowed in database file."
      ::= {nvDlconf 1}

nvDlconfNumRec OBJECT-TYPE
      SYNTAX   INTEGER
      ACCESS   read-only
      STATUS   mandatory
      DESCRIPTION
                "number of records in use."
      ::= {nvDlconf 2}

nvDlconfTable OBJECT-TYPE
      SYNTAX   SEQUENCE OF NvDlconfEntry
      ACCESS   not-accessible
      STATUS   mandatory
      DESCRIPTION
               "dlconf file."
      ::= { nvDlconf 3 }

nvDlconfEntry OBJECT-TYPE
      SYNTAX   NvDlconfEntry
      ACCESS   not-accessible
      STATUS   mandatory
      DESCRIPTION
               "dlconf record."
      INDEX { nvDlconfDlnumber }
      ::= { nvDlconfTable 1 }

NvDlconfEntry ::=
      SEQUENCE {
      nvDlconfDlnumber
            INTEGER,
      nvDlconfLinkname
            INTEGER,
      nvDlconfPuaddr
            DisplayString
               }

nvDlconfDlnumber OBJECT-TYPE
     SYNTAX   INTEGER (1..428)
     ACCESS   read-only
     STATUS   mandatory
     DESCRIPTION
"Data Link Record (dlnumber)
 Number of the DL,ie,record id# in DLCONF file.
Parameter is set during factory configuration."
     ::= { nvDlconfEntry 2 }

nvDlconfLinkname OBJECT-TYPE
     SYNTAX   INTEGER {
                nolink(1),     -- unassigned (+1)
                link1(2),     --
                link2(3),     --
                link3(4),     --
                link4(5),     --
                link5(6),     --
                link6(7),     --
                link7(8),     --
                link8(9),     --
                link9(10),     --
                link10(11),     --
                link11(12),     --
                link12(13),     --
                link13(14),     --
                link14(15),     --
                link15(16),     --
                link16(17),     --
                link17(18),     --
                link18(19),     --
                link19(20),     --
                link20(21),     --
                link21(22),     --
                link22(23),     --
                link23(24),     --
                link24(25),     --
                link25(26),     --
                link26(27),     --
                link27(28),     --
                link28(29),     --
                link29(30),     --
                link30(31),     --
                link31(32),     --
                link32(33),     --
                link33(34),     --
                link34(35),     --
                link35(36),     --
                link36(37),     --
                link37(38),     --
                link38(39),     --
                link39(40),     --
                link40(41),     --
                link41(42),     --
                link42(43),     --
                link43(44),     --
                link44(45),     --
                link45(46),     --
                link46(47),     --
                link47(48),     --
                link48(49),     --
                link49(50),     --
                link50(51),     --
                link51(52),     --
                link52(53),     --
                link53(54),     --
                link54(55),     --
                link55(56),     --
                link56(57),     --
                link57(58),     --
                link58(59),     --
                link59(60),     --
                link60(61),     --
                link61(62),     --
                link62(63),     --
                link63(64),     --
                link64(65),     --
                link65(66),     --
                link66(67),     --
                link67(68),     --
                link68(69),     --
                link69(70),     --
                link70(71),     --
                link71(72),     --
                link72(73),     --
                link73(74),     --
                link74(75),     --
                link75(76),     --
                link76(77),     --
                link77(78),     --
                link78(79),     --
                link79(80),     --
                link80(81),     --
                link81(82),     --
                link82(83),     --
                link83(84),     --
                link84(85),     --
                link85(86),     --
                link86(87),     --
                link87(88),     --
                link88(89),     --
                link89(90),     --
                link90(91),     --
                link91(92),     --
                link92(93),     --
                link93(94),     --
                link94(95),     --
                link95(96),     --
                link96(97),     --
                link97(98),     --
                link98(99),     --
                link99(100),     --
                link100(101),     --
                link101(102),     --
                link102(103),     --
                link103(104),     --
                link104(105),     --
                link105(106),     --
                link106(107),     --
                link107(108),     --
                link108(109),     --
                link109(110),     --
                link110(111),     --
                link111(112),     --
                link112(113),     --
                link113(114),     --
                link114(115),     --
                link115(116),     --
                link116(117),     --
                link117(118),     --
                link118(119),     --
                link119(120),     --
                link120(121),     --
                link121(122),     --
                link122(123),     --
                link123(124),     --
                link124(125),     --
                link125(126),     --
                link126(127),     --
                link127(128),     --
                link128(129),     --
                link129(130),     --
                link130(131),     --
                link131(132),     --
                link132(133),     --
                link133(134),     --
                link134(135),     --
                link135(136),     --
                link136(137),     --
                link137(138),     --
                link138(139),     --
                link139(140),     --
                link140(141),     --
                link141(142),     --
                link142(143),     --
                link143(144),     --
                link144(145),     --
                link145(146),     --
                link146(147),     --
                link147(148),     --
                link148(149),     --
                link149(150),     --
                link150(151),     --
                link151(152),     --
                link152(153),     --
                link153(154),     --
                link154(155),     --
                link155(156),     --
                link156(157),     --
                link157(158),     --
                link158(159),     --
                link159(160),     --
                link160(161),     --
                link161(162),     --
                link162(163),     --
                link163(164),     --
                link164(165),     --
                link165(166),     --
                link166(167),     --
                link167(168),     --
                link168(169),     --
                link169(170),     --
                link170(171),     --
                link171(172),     --
                link172(173),     --
                link173(174),     --
                link174(175),     --
                link175(176),     --
                link176(177),     --
                link177(178),     --
                link178(179),     --
                link179(180),     --
                link180(181),     --
                link181(182),     --
                link182(183),     --
                link183(184),     --
                link184(185),     --
                link185(186),     --
                link186(187),     --
                link187(188),     --
                link188(189),     --
                link189(190),     --
                link190(191),     --
                link191(192),     --
                link192(193),     --
                link193(194),     --
                link194(195),     --
                link195(196),     --
                link196(197),     --
                link197(198),     --
                link198(199),     --
                link199(200),     --
                link200(201),     --
                link201(202),     --
                link202(203),     --
                link203(204),     --
                link204(205),     --
                link205(206),     --
                link206(207),     --
                link207(208),     --
                link208(209),     --
                link209(210),     --
                link210(211),     --
                link211(212),     --
                link212(213),     --
                link213(214),     --
                link214(215),     --
                link215(216),     --
                link216(217),     --
                link217(218),     --
                link218(219),     --
                link219(220),     --
                link220(221),     --
                link221(222),     --
                link222(223),     --
                link223(224),     --
                link224(225),     --
                link225(226),     --
                link226(227),     --
                link227(228),     --
                link228(229),     --
                link229(230),     --
                link230(231),     --
                link231(232),     --
                link232(233),     --
                link233(234),     --
                link234(235),     --
                link235(236),     --
                link236(237),     --
                link237(238),     --
                link238(239),     --
                link239(240),     --
                link240(241),     --
                link241(242),     --
                link242(243),     --
                link243(244),     --
                link244(245),     --
                link245(246),     --
                link246(247),     --
                link247(248),     --
                link248(249),     --
                link249(250),     --
                link250(251),     --
                link251(252),     --
                link252(253),     --
                link253(254),     --
                link254(255),     --
                link255(256),     --
                link256(257),     --
                link257(258),     --
                link258(259),     --
                link259(260),     --
                link260(261),     --
                link261(262),     --
                link262(263),     --
                link263(264),     --
                link264(265),     --
                link265(266),     --
                link266(267),     --
                link267(268),     --
                link268(269),     --
                link269(270),     --
                link270(271),     --
                link271(272),     --
                link272(273),     --
                link273(274),     --
                link274(275),     --
                link275(276),     --
                link276(277),     --
                link277(278),     --
                link278(279),     --
                link279(280),     --
                link280(281),     --
                link281(282),     --
                link282(283),     --
                link283(284),     --
                link284(285),     --
                link285(286),     --
                link286(287),     --
                link287(288),     --
                link288(289),     --
                link289(290),     --
                link290(291),     --
                link291(292),     --
                link292(293),     --
                link293(294),     --
                link294(295),     --
                link295(296),     --
                link296(297),     --
                link297(298),     --
                link298(299),     --
                link299(300),     --
                link300(301),     --
                link301(302),     --
                link302(303),     --
                link303(304),     --
                link304(305),     --
                link305(306),     --
                link306(307),     --
                link307(308),     --
                link308(309),     --
                link309(310),     --
                link310(311),     --
                link311(312),     --
                link312(313),     --
                link313(314),     --
                link314(315),     --
                link315(316),     --
                link316(317),     --
                link317(318),     --
                link318(319),     --
                link319(320),     --
                link320(321),     --
                link321(322),     --
                link322(323),     --
                link323(324),     --
                link324(325),     --
                link325(326),     --
                link326(327),     --
                link327(328),     --
                link328(329),     --
                link329(330),     --
                link330(331),     --
                link331(332),     --
                link332(333),     --
                link333(334),     --
                link334(335),     --
                link335(336),     --
                link336(337),     --
                link337(338),     --
                link338(339),     --
                link339(340),     --
                link340(341),     --
                link341(342),     --
                link342(343),     --
                link343(344),     --
                link344(345),     --
                link345(346),     --
                link346(347),     --
                link347(348),     --
                link348(349),     --
                link349(350),     --
                link350(351),     --
                link351(352),     --
                link352(353),     --
                link353(354),     --
                link354(355),     --
                link355(356),     --
                link356(357),     --
                link357(358),     --
                link358(359),     --
                link359(360),     --
                link360(361),     --
                link361(362),     --
                link362(363),     --
                link363(364),     --
                link364(365),     --
                link365(366),     --
                link366(367),     --
                link367(368),     --
                link368(369),     --
                link369(370),     --
                link370(371),     --
                link371(372),     --
                link372(373),     --
                link373(374),     --
                link374(375),     --
                link375(376),     --
                link376(377),     --
                link377(378),     --
                link378(379),     --
                link379(380),     --
                link380(381),     --
                link381(382),     --
                link382(383),     --
                link383(384),     --
                link384(385),     --
                link385(386),     --
                link386(387),     --
                link387(388),     --
                link388(389),     --
                link389(390),     --
                link390(391),     --
                link391(392),     --
                link392(393),     --
                link393(394),     --
                link394(395),     --
                link395(396),     --
                link396(397),     --
                link397(398),     --
                link398(399),     --
                link399(400),     --
                link400(401),     --
                link401(402),     --
                link402(403),     --
                link403(404),     --
                link404(405),     --
                link405(406),     --
                link406(407),     --
                link407(408),     --
                link408(409),     --
                link409(410),     --
                link410(411),     --
                link411(412),     --
                link412(413),     --
                link413(414),     --
                link414(415),     --
                link415(416),     --
                link416(417),     --
                link417(418),     --
                link418(419),     --
                link419(420),     --
                link420(421),     --
                link421(422),     --
                link422(423),     --
                link423(424),     --
                link424(425),     --
                link425(426),     --
                link426(427),     --
                link427(428),     --
                link428(429)     --
                }
     ACCESS   read-write
     STATUS   mandatory
     DESCRIPTION
"Link Name (linkname)
"
     ::= { nvDlconfEntry 3 }

nvDlconfPuaddr OBJECT-TYPE
     SYNTAX   DisplayString (SIZE (0..2))
     ACCESS   read-write
     STATUS   mandatory
     DESCRIPTION
"Polling Address (puaddr)
Default value is 0."
     ::= { nvDlconfEntry 4 }

-- The records in this file configure instances of the Synchronous Link link
-- component. There is one record per instance of the link component.
--
-- This type should be identical to the 'lapp' type in ls.pd.
--
--
--  In lapbd.dd there are mask defines for this type.
--  -Vtlapb is 0x01 and indicates LAP/LAPB/PSS.
--  -Vtsdlc is 0x10 and indicates SLDCP/SDLCS.
--  They enable determining the type (SDLC or LAPB) of protocol.
--

nvLinkconf OBJECT IDENTIFIER ::= { nevadaSync 4 }

nvLinkconfMaxRec OBJECT-TYPE
      SYNTAX   INTEGER
      ACCESS   read-only
      STATUS   mandatory
      DESCRIPTION
                "total number of records allowed in database file."
      ::= {nvLinkconf 1}

nvLinkconfNumRec OBJECT-TYPE
      SYNTAX   INTEGER
      ACCESS   read-only
      STATUS   mandatory
      DESCRIPTION
                "number of records in use."
      ::= {nvLinkconf 2}

nvLinkconfTable OBJECT-TYPE
      SYNTAX   SEQUENCE OF NvLinkconfEntry
      ACCESS   not-accessible
      STATUS   mandatory
      DESCRIPTION
               "linkconf file."
      ::= { nvLinkconf 3 }

nvLinkconfEntry OBJECT-TYPE
      SYNTAX   NvLinkconfEntry
      ACCESS   not-accessible
      STATUS   mandatory
      DESCRIPTION
               "linkconf record."
      INDEX { nvLinkconfIndex }
      ::= { nvLinkconfTable 1 }

NvLinkconfEntry ::=
      SEQUENCE {
      nvLinkconfIndex
            INTEGER,
      nvLinkconfLinkname
            INTEGER,
      nvLinkconfPortname
            DisplayString,
      nvLinkconfRsrcpool
            DisplayString,
      nvLinkconfProtocol
            INTEGER,
      nvLinkconfWsze
            INTEGER,
      nvLinkconfHostinact
            INTEGER,
      nvLinkconfN2
            INTEGER,
      nvLinkconfPollthres
            INTEGER,
      nvLinkconfT1
            INTEGER,
      nvLinkconfT2
            INTEGER,
      nvLinkconfT3
            INTEGER,
      nvLinkconfAckthresh
            INTEGER,
      nvLinkconfDialout
            INTEGER,
      nvLinkconfWaitframe
	    INTEGER
                }

nvLinkconfIndex OBJECT-TYPE
     SYNTAX   INTEGER
     ACCESS   read-only
     STATUS   mandatory
     DESCRIPTION
        "Index of linkconf record"
      ::= { nvLinkconfEntry 1 }

nvLinkconfLinkname OBJECT-TYPE
     SYNTAX   INTEGER {
                nolink(1),     -- unassigned (+1)
                link1(2),     --
                link2(3),     --
                link3(4),     --
                link4(5),     --
                link5(6),     --
                link6(7),     --
                link7(8),     --
                link8(9),     --
                link9(10),     --
                link10(11),     --
                link11(12),     --
                link12(13),     --
                link13(14),     --
                link14(15),     --
                link15(16),     --
                link16(17),     --
                link17(18),     --
                link18(19),     --
                link19(20),     --
                link20(21),     --
                link21(22),     --
                link22(23),     --
                link23(24),     --
                link24(25),     --
                link25(26),     --
                link26(27),     --
                link27(28),     --
                link28(29),     --
                link29(30),     --
                link30(31),     --
                link31(32),     --
                link32(33),     --
                link33(34),     --
                link34(35),     --
                link35(36),     --
                link36(37),     --
                link37(38),     --
                link38(39),     --
                link39(40),     --
                link40(41),     --
                link41(42),     --
                link42(43),     --
                link43(44),     --
                link44(45),     --
                link45(46),     --
                link46(47),     --
                link47(48),     --
                link48(49),     --
                link49(50),     --
                link50(51),     --
                link51(52),     --
                link52(53),     --
                link53(54),     --
                link54(55),     --
                link55(56),     --
                link56(57),     --
                link57(58),     --
                link58(59),     --
                link59(60),     --
                link60(61),     --
                link61(62),     --
                link62(63),     --
                link63(64),     --
                link64(65),     --
                link65(66),     --
                link66(67),     --
                link67(68),     --
                link68(69),     --
                link69(70),     --
                link70(71),     --
                link71(72),     --
                link72(73),     --
                link73(74),     --
                link74(75),     --
                link75(76),     --
                link76(77),     --
                link77(78),     --
                link78(79),     --
                link79(80),     --
                link80(81),     --
                link81(82),     --
                link82(83),     --
                link83(84),     --
                link84(85),     --
                link85(86),     --
                link86(87),     --
                link87(88),     --
                link88(89),     --
                link89(90),     --
                link90(91),     --
                link91(92),     --
                link92(93),     --
                link93(94),     --
                link94(95),     --
                link95(96),     --
                link96(97),     --
                link97(98),     --
                link98(99),     --
                link99(100),     --
                link100(101),     --
                link101(102),     --
                link102(103),     --
                link103(104),     --
                link104(105),     --
                link105(106),     --
                link106(107),     --
                link107(108),     --
                link108(109),     --
                link109(110),     --
                link110(111),     --
                link111(112),     --
                link112(113),     --
                link113(114),     --
                link114(115),     --
                link115(116),     --
                link116(117),     --
                link117(118),     --
                link118(119),     --
                link119(120),     --
                link120(121),     --
                link121(122),     --
                link122(123),     --
                link123(124),     --
                link124(125),     --
                link125(126),     --
                link126(127),     --
                link127(128),     --
                link128(129),     --
                link129(130),     --
                link130(131),     --
                link131(132),     --
                link132(133),     --
                link133(134),     --
                link134(135),     --
                link135(136),     --
                link136(137),     --
                link137(138),     --
                link138(139),     --
                link139(140),     --
                link140(141),     --
                link141(142),     --
                link142(143),     --
                link143(144),     --
                link144(145),     --
                link145(146),     --
                link146(147),     --
                link147(148),     --
                link148(149),     --
                link149(150),     --
                link150(151),     --
                link151(152),     --
                link152(153),     --
                link153(154),     --
                link154(155),     --
                link155(156),     --
                link156(157),     --
                link157(158),     --
                link158(159),     --
                link159(160),     --
                link160(161),     --
                link161(162),     --
                link162(163),     --
                link163(164),     --
                link164(165),     --
                link165(166),     --
                link166(167),     --
                link167(168),     --
                link168(169),     --
                link169(170),     --
                link170(171),     --
                link171(172),     --
                link172(173),     --
                link173(174),     --
                link174(175),     --
                link175(176),     --
                link176(177),     --
                link177(178),     --
                link178(179),     --
                link179(180),     --
                link180(181),     --
                link181(182),     --
                link182(183),     --
                link183(184),     --
                link184(185),     --
                link185(186),     --
                link186(187),     --
                link187(188),     --
                link188(189),     --
                link189(190),     --
                link190(191),     --
                link191(192),     --
                link192(193),     --
                link193(194),     --
                link194(195),     --
                link195(196),     --
                link196(197),     --
                link197(198),     --
                link198(199),     --
                link199(200),     --
                link200(201),     --
                link201(202),     --
                link202(203),     --
                link203(204),     --
                link204(205),     --
                link205(206),     --
                link206(207),     --
                link207(208),     --
                link208(209),     --
                link209(210),     --
                link210(211),     --
                link211(212),     --
                link212(213),     --
                link213(214),     --
                link214(215),     --
                link215(216),     --
                link216(217),     --
                link217(218),     --
                link218(219),     --
                link219(220),     --
                link220(221),     --
                link221(222),     --
                link222(223),     --
                link223(224),     --
                link224(225),     --
                link225(226),     --
                link226(227),     --
                link227(228),     --
                link228(229),     --
                link229(230),     --
                link230(231),     --
                link231(232),     --
                link232(233),     --
                link233(234),     --
                link234(235),     --
                link235(236),     --
                link236(237),     --
                link237(238),     --
                link238(239),     --
                link239(240),     --
                link240(241),     --
                link241(242),     --
                link242(243),     --
                link243(244),     --
                link244(245),     --
                link245(246),     --
                link246(247),     --
                link247(248),     --
                link248(249),     --
                link249(250),     --
                link250(251),     --
                link251(252),     --
                link252(253),     --
                link253(254),     --
                link254(255),     --
                link255(256),     --
                link256(257),     --
                link257(258),     --
                link258(259),     --
                link259(260),     --
                link260(261),     --
                link261(262),     --
                link262(263),     --
                link263(264),     --
                link264(265),     --
                link265(266),     --
                link266(267),     --
                link267(268),     --
                link268(269),     --
                link269(270),     --
                link270(271),     --
                link271(272),     --
                link272(273),     --
                link273(274),     --
                link274(275),     --
                link275(276),     --
                link276(277),     --
                link277(278),     --
                link278(279),     --
                link279(280),     --
                link280(281),     --
                link281(282),     --
                link282(283),     --
                link283(284),     --
                link284(285),     --
                link285(286),     --
                link286(287),     --
                link287(288),     --
                link288(289),     --
                link289(290),     --
                link290(291),     --
                link291(292),     --
                link292(293),     --
                link293(294),     --
                link294(295),     --
                link295(296),     --
                link296(297),     --
                link297(298),     --
                link298(299),     --
                link299(300),     --
                link300(301),     --
                link301(302),     --
                link302(303),     --
                link303(304),     --
                link304(305),     --
                link305(306),     --
                link306(307),     --
                link307(308),     --
                link308(309),     --
                link309(310),     --
                link310(311),     --
                link311(312),     --
                link312(313),     --
                link313(314),     --
                link314(315),     --
                link315(316),     --
                link316(317),     --
                link317(318),     --
                link318(319),     --
                link319(320),     --
                link320(321),     --
                link321(322),     --
                link322(323),     --
                link323(324),     --
                link324(325),     --
                link325(326),     --
                link326(327),     --
                link327(328),     --
                link328(329),     --
                link329(330),     --
                link330(331),     --
                link331(332),     --
                link332(333),     --
                link333(334),     --
                link334(335),     --
                link335(336),     --
                link336(337),     --
                link337(338),     --
                link338(339),     --
                link339(340),     --
                link340(341),     --
                link341(342),     --
                link342(343),     --
                link343(344),     --
                link344(345),     --
                link345(346),     --
                link346(347),     --
                link347(348),     --
                link348(349),     --
                link349(350),     --
                link350(351),     --
                link351(352),     --
                link352(353),     --
                link353(354),     --
                link354(355),     --
                link355(356),     --
                link356(357),     --
                link357(358),     --
                link358(359),     --
                link359(360),     --
                link360(361),     --
                link361(362),     --
                link362(363),     --
                link363(364),     --
                link364(365),     --
                link365(366),     --
                link366(367),     --
                link367(368),     --
                link368(369),     --
                link369(370),     --
                link370(371),     --
                link371(372),     --
                link372(373),     --
                link373(374),     --
                link374(375),     --
                link375(376),     --
                link376(377),     --
                link377(378),     --
                link378(379),     --
                link379(380),     --
                link380(381),     --
                link381(382),     --
                link382(383),     --
                link383(384),     --
                link384(385),     --
                link385(386),     --
                link386(387),     --
                link387(388),     --
                link388(389),     --
                link389(390),     --
                link390(391),     --
                link391(392),     --
                link392(393),     --
                link393(394),     --
                link394(395),     --
                link395(396),     --
                link396(397),     --
                link397(398),     --
                link398(399),     --
                link399(400),     --
                link400(401),     --
                link401(402),     --
                link402(403),     --
                link403(404),     --
                link404(405),     --
                link405(406),     --
                link406(407),     --
                link407(408),     --
                link408(409),     --
                link409(410),     --
                link410(411),     --
                link411(412),     --
                link412(413),     --
                link413(414),     --
                link414(415),     --
                link415(416),     --
                link416(417),     --
                link417(418),     --
                link418(419),     --
                link419(420),     --
                link420(421),     --
                link421(422),     --
                link422(423),     --
                link423(424),     --
                link424(425),     --
                link425(426),     --
                link426(427),     --
                link427(428),     --
                link428(429)     --
                }
     ACCESS   read-only
     STATUS   mandatory
     DESCRIPTION
"Link Name (linkname)
Link name and number (ie,'Link1')
Parameter is set during factory configuration."
     ::= { nvLinkconfEntry 2 }

nvLinkconfPortname OBJECT-TYPE
     SYNTAX   DisplayString (SIZE (0..11))
     ACCESS   read-write
     STATUS   mandatory
     DESCRIPTION
"Port to serve this link."
     ::= { nvLinkconfEntry 3 }

nvLinkconfRsrcpool OBJECT-TYPE
     SYNTAX   DisplayString (SIZE (0..11))
     ACCESS   read-write
     STATUS   mandatory
     DESCRIPTION
"Resource Pool Name."
     ::= { nvLinkconfEntry 4 }

nvLinkconfProtocol OBJECT-TYPE
     SYNTAX   INTEGER {
                lap(2),     -- 0x01 LAP procedure (+1)
                lapb(4),     -- 0x03 LAPB procedure
                lapbe(8),     -- 0x07 LAPB procedure with extended frame sequencing
                aust(12),     -- 0x0b austrian PTT
                pss(16),     -- 0x0f PSS (U.K.) special procedure
                sdlc(17),     -- 0x10 SDLC
                sdlce(49)      -- 0x30 SDLC with extended frame sequencing
                }
     ACCESS   read-write
     STATUS   mandatory
     DESCRIPTION
"Link-Level Protocol (protocol)
This field defines the Synchronous Link link procedure
that is to be followed.
Default value is 3+1."
     ::= { nvLinkconfEntry 5 }

nvLinkconfWsze OBJECT-TYPE
     SYNTAX   INTEGER (1..15)
     ACCESS   read-write
     STATUS   mandatory
     DESCRIPTION
"Link-Level Window Size (wsze)
Option to select window size to be used.
 Between 1 and 7 for modulo 8.
 Between 1 and 127 for modulo 127.
Default value is 7."
     ::= { nvLinkconfEntry 6 }

nvLinkconfHostinact OBJECT-TYPE
     SYNTAX   INTEGER (0..3600)
     ACCESS   read-write
     STATUS   mandatory
     DESCRIPTION
"SDLC Host Inactivity Timer (hostinact)
SDLC secondary station maximum wait without host contact.
Default value is 600."
     ::= { nvLinkconfEntry 9 }

nvLinkconfN2 OBJECT-TYPE
     SYNTAX   INTEGER (0..255)
     ACCESS   read-write
     STATUS   mandatory
     DESCRIPTION
"Number of Retransmissions (n2)
Maximum number of times a data frame will be retransmitted,
before resetting the link.
Default value is 10."
     ::= { nvLinkconfEntry 11 }

nvLinkconfPollthres OBJECT-TYPE
     SYNTAX   INTEGER (0..100)
     ACCESS   read-write
     STATUS   mandatory
     DESCRIPTION
"SDLC Poll Threshold (pollthres)
Default value is 20."
     ::= { nvLinkconfEntry 12 }

nvLinkconfT1 OBJECT-TYPE
     SYNTAX   INTEGER (0..300)
     ACCESS   read-write
     STATUS   mandatory
     DESCRIPTION
"Timer Recovery Timer (t1)
Timer for maximum wait for acknowledgment. When timer expires,
timeout recovery is attempted.
Default value is 5."
     ::= { nvLinkconfEntry 13 }

nvLinkconfT2 OBJECT-TYPE
     SYNTAX   INTEGER (0..300)
     ACCESS   read-write
     STATUS   mandatory
     DESCRIPTION
"Acknowledgement Timer (t2)
LAPB maximum amount of time before acknowledgement.
Default value is 0."
     ::= { nvLinkconfEntry 14 }

nvLinkconfT3 OBJECT-TYPE
     SYNTAX   INTEGER (0..300)
     ACCESS   read-write
     STATUS   mandatory
     DESCRIPTION
"Link Watchdog Timer (t3)
LAPB maximum amount of link idle time before a probe is done.
Default value is 15."
     ::= { nvLinkconfEntry 15 }

nvLinkconfAckthresh OBJECT-TYPE
     SYNTAX   INTEGER (0..65535)
     ACCESS   read-write
     STATUS   mandatory
     DESCRIPTION
"Acknowledgement Threshold (ackthresh)
"
     ::= { nvLinkconfEntry 16 }

nvLinkconfDialout OBJECT-TYPE
     SYNTAX   INTEGER (0..65535)
     ACCESS   read-write
     STATUS   mandatory
     DESCRIPTION
"dialout command string id"
     ::= { nvLinkconfEntry 18}

nvLinkconfWaitframe OBJECT-TYPE
     SYNTAX   INTEGER (0..255)
     ACCESS   read-write
     STATUS   mandatory
     DESCRIPTION
"Number of T1 periods to wait for frame upon startup."
     ::= { nvLinkconfEntry 19}

--
--      x25stat file
--
nvX25stat OBJECT IDENTIFIER ::= { nevadaX25 1}

nvX25statMaxRec OBJECT-TYPE
      SYNTAX   INTEGER
      ACCESS   read-only
      STATUS   mandatory
      DESCRIPTION
                "total number of records allowed in database file."
      ::= {nvX25stat 1}

nvX25statNumRec OBJECT-TYPE
      SYNTAX   INTEGER
      ACCESS   read-only
      STATUS   mandatory
      DESCRIPTION
                "number of records in use."
      ::= {nvX25stat 2}

nvX25statTable OBJECT-TYPE
      SYNTAX   SEQUENCE OF NvX25statEntry
      ACCESS   not-accessible
      STATUS   mandatory
      DESCRIPTION
               "x25stat file."
      ::= {nvX25stat 3}

nvX25statEntry OBJECT-TYPE
      SYNTAX   NvX25statEntry
      ACCESS   not-accessible
      STATUS   mandatory
      DESCRIPTION
               "x25stat record."
      INDEX   {nvX25statIndex}
      ::= {nvX25statTable 1 }

NvX25statEntry ::=
      SEQUENCE {
      nvX25statIndex
            DisplayString,
      nvX25statNetname
            DisplayString,
      nvX25statCode
            INTEGER,
      nvX25statDiag
            INTEGER,
      nvX25statIfstate
            INTEGER,
      nvX25statCallcur
            INTEGER,
      nvX25statOpen
            INTEGER,
      nvX25statUp
            INTEGER,
      nvX25statLinkup
            INTEGER,
      nvX25statNtxcalls
            Counter,
      nvX25statNrxcalls
            Counter,
      nvX25statNtxcallcs
            Counter,
      nvX25statNrxcallcs
            Counter,
      nvX25statNtxclrs
            Counter,
      nvX25statNrxclrs
            Counter,
      nvX25statNtxclrcs
            Counter,
      nvX25statNrxclrcs
            Counter,
      nvX25statNtxres
            Counter,
      nvX25statNrxres
            Counter,
      nvX25statNtxints
            Counter,
      nvX25statNrxints
            Counter,
      nvX25statNtxrrs
            Counter,
      nvX25statNrxrrs
            Counter,
      nvX25statNtxrnrs
            Counter,
      nvX25statNrxrnrs
            Counter,
      nvX25statNtxpaks
            Counter,
      nvX25statNrxpaks
            Counter,
      nvX25statNtxsegs
            Counter,
      nvX25statNrxsegs
            Counter,
      nvX25statNtxchars
            Counter,
      nvX25statNrxchars
            Counter,
      nvX25statMaxvc
            INTEGER,
      nvX25statDtreset
            DisplayString
               }

nvX25statIndex OBJECT-TYPE
        SYNTAX  INTEGER
        ACCESS  read-only
        STATUS  mandatory
        DESCRIPTION
        "Index of x25stat record"
        ::= {nvX25statEntry 1 }

nvX25statNetname OBJECT-TYPE
     SYNTAX   DisplayString (SIZE (0..10))
     ACCESS   read-only
     STATUS   mandatory
     DESCRIPTION
        "x25stat: network interface name."
     ::= {nvX25statEntry 2 }

nvX25statCode OBJECT-TYPE
     SYNTAX   INTEGER {
                dteOriginated(2),
                numberBusy(3),
                outOfOrder(4),
                remoteDteOperational(5),
                remoteProcedureError(6),
                localProcedureError(7),
                reverseChargeNotSubscribed(8),
                incompatibleDestination(9),
                fastSelectNotSubscribed(10),
                invalidFacilityRequest(11),
                accessBarred(12),
                networkCongestion(13),
                networkOperational(14),
                notObtainable(15),
                rpoaOutOfOrder(16),
                shipAbsent(17),
                networkOutOfOrder(18)
                }
     ACCESS   read-only
     STATUS   mandatory
     DESCRIPTION
        "last clear or reset code.
         Initial status is 1+1."
     ::= {nvX25statEntry 3 }

nvX25statDiag OBJECT-TYPE
     SYNTAX   INTEGER
     ACCESS   read-only
     STATUS   mandatory
     DESCRIPTION
        "last diagnostic code.
         Initial status is 0."
     ::= {nvX25statEntry 4 }

nvX25statIfstate OBJECT-TYPE
     SYNTAX   INTEGER {
                r1Down(1),                -- (+1)
                r2Startup(2),
                r3Restart(3),
                r4Up(4),
                r5Disconnected(5)
                }
     ACCESS   read-only
     STATUS   mandatory
     DESCRIPTION
        "network state.
         Current state of network interface.
         Initial status is 0+1."
     ::= {nvX25statEntry 5 }

nvX25statCallcur OBJECT-TYPE
     SYNTAX   INTEGER
     ACCESS   read-only
     STATUS   mandatory
     DESCRIPTION
     "Number of X25 calls currently active."
     ::= { nvX25statEntry 6}
     
nvX25statOpen OBJECT-TYPE
     SYNTAX   INTEGER {
                no(1),                  -- (+1)
                yes(2)
                }
     ACCESS   read-only
     STATUS   mandatory
     DESCRIPTION
        "network open?
         Initial status is 0+1."
     ::= {nvX25statEntry 7 }

nvX25statUp OBJECT-TYPE
     SYNTAX   INTEGER {
                no(1),                  -- (+1)
                yes(2)
                }
     ACCESS   read-only
     STATUS   mandatory
     DESCRIPTION
        "network up?
         Initial status is 0+1."
     ::= {nvX25statEntry 8 }

nvX25statNtxcalls OBJECT-TYPE
     SYNTAX   Counter
     ACCESS   read-only
     STATUS   mandatory
     DESCRIPTION
        "number of call requests sent.
         Statistic is zeroed at startup time."
     ::= {nvX25statEntry 9 }

nvX25statNrxcalls OBJECT-TYPE
     SYNTAX   Counter
     ACCESS   read-only
     STATUS   mandatory
     DESCRIPTION
        "number of call requests received.
         Statistic is zeroed at startup time."
     ::= {nvX25statEntry 10 }

nvX25statNtxcallcs OBJECT-TYPE
     SYNTAX   Counter
     ACCESS   read-only
     STATUS   mandatory
     DESCRIPTION
        "number of call confs sent.
         Statistic is zeroed at startup time."
     ::= {nvX25statEntry 11 }

nvX25statNrxcallcs OBJECT-TYPE
     SYNTAX   Counter
     ACCESS   read-only
     STATUS   mandatory
     DESCRIPTION
        "number of call confs received.
         Statistic is zeroed at startup time."
     ::= {nvX25statEntry 12 }

nvX25statNtxclrs OBJECT-TYPE
     SYNTAX   Counter
     ACCESS   read-only
     STATUS   mandatory
     DESCRIPTION
        "number of clear requests sent.
         Statistic is zeroed at startup time."
     ::= {nvX25statEntry 13 }

nvX25statNrxclrs OBJECT-TYPE
     SYNTAX   Counter
     ACCESS   read-only
     STATUS   mandatory
     DESCRIPTION
        "number of clear requests received.
         Statistic is zeroed at startup time."
     ::= {nvX25statEntry 14 }

nvX25statNtxclrcs OBJECT-TYPE
     SYNTAX   Counter
     ACCESS   read-only
     STATUS   mandatory
     DESCRIPTION
        "number of clear confs sent.
         Statistic is zeroed at startup time."
     ::= {nvX25statEntry 15 }

nvX25statNrxclrcs OBJECT-TYPE
     SYNTAX   Counter
     ACCESS   read-only
     STATUS   mandatory
     DESCRIPTION
        "number of clear confs received.
         Statistic is zeroed at startup time."
     ::= {nvX25statEntry 16 }

nvX25statNtxres OBJECT-TYPE
     SYNTAX   Counter
     ACCESS   read-only
     STATUS   mandatory
     DESCRIPTION
        "number of reset requests send.
         Statistic is zeroed at startup time."
     ::= {nvX25statEntry 17 }

nvX25statNrxres OBJECT-TYPE
     SYNTAX   Counter
     ACCESS   read-only
     STATUS   mandatory
     DESCRIPTION
        "number of reset requests received.
         Statistic is zeroed at startup time."
     ::= {nvX25statEntry 18 }

nvX25statNtxints OBJECT-TYPE
     SYNTAX   Counter
     ACCESS   read-only
     STATUS   mandatory
     DESCRIPTION
        "number of int requests send.
         Statistic is zeroed at startup time."
     ::= {nvX25statEntry 19 }

nvX25statNrxints OBJECT-TYPE
     SYNTAX   Counter
     ACCESS   read-only
     STATUS   mandatory
     DESCRIPTION
        "number of int requests received.
         Statistic is zeroed at startup time."
     ::= {nvX25statEntry 20 }

nvX25statNtxrrs OBJECT-TYPE
     SYNTAX   Counter
     ACCESS   read-only
     STATUS   mandatory
     DESCRIPTION
        "number of receiver readys send.
         Statistic is zeroed at startup time."
     ::= {nvX25statEntry 21 }

nvX25statNrxrrs OBJECT-TYPE
     SYNTAX   Counter
     ACCESS   read-only
     STATUS   mandatory
     DESCRIPTION
        "number of receiver readys received.
         Statistic is zeroed at startup time."
     ::= {nvX25statEntry 22 }

nvX25statNtxrnrs OBJECT-TYPE
     SYNTAX   Counter
     ACCESS   read-only
     STATUS   mandatory
     DESCRIPTION
        "number of receiver not readys send.
         Statistic is zeroed at startup time."
     ::= {nvX25statEntry 23 }

nvX25statNrxrnrs OBJECT-TYPE
     SYNTAX   Counter
     ACCESS   read-only
     STATUS   mandatory
     DESCRIPTION
        "number of receiver not readys received.
         Statistic is zeroed at startup time."
     ::= {nvX25statEntry 24 }

nvX25statNtxpaks OBJECT-TYPE
     SYNTAX   Counter
     ACCESS   read-only
     STATUS   mandatory
     DESCRIPTION
        "number of data packets sent.
         Statistic is zeroed at startup time."
     ::= {nvX25statEntry 25 }

nvX25statNrxpaks OBJECT-TYPE
     SYNTAX   Counter
     ACCESS   read-only
     STATUS   mandatory
     DESCRIPTION
        "number of data packets received.
         Statistic is zeroed at startup time."
     ::= {nvX25statEntry 26 }

nvX25statNtxsegs OBJECT-TYPE
     SYNTAX   Counter
     ACCESS   read-only
     STATUS   mandatory
     DESCRIPTION
        "number of data segments sent.
         Statistic is zeroed at startup time."
     ::= {nvX25statEntry 27 }

nvX25statNrxsegs OBJECT-TYPE
     SYNTAX   Counter
     ACCESS   read-only
     STATUS   mandatory
     DESCRIPTION
        "number of data segments received.
         Statistic is zeroed at startup time."

     ::= {nvX25statEntry 28 }

nvX25statNtxchars  OBJECT-TYPE
     SYNTAX   Counter
     ACCESS   read-only
     STATUS   mandatory
     DESCRIPTION
        "number of data chars sent.
         Statistic is zeroed at startup time."
     ::= {nvX25statEntry 29 }

nvX25statNrxchars OBJECT-TYPE
     SYNTAX   Counter
     ACCESS   read-only
     STATUS   mandatory
     DESCRIPTION
        "number of data chars received.
         Statistic is zeroed at startup time."
     ::= {nvX25statEntry 30 }

nvX25statMaxvc OBJECT-TYPE
     SYNTAX   INTEGER
     ACCESS   read-only
     STATUS   mandatory
     DESCRIPTION
        "maximum connections.
         Statistic is zeroed at startup time."
     ::= {nvX25statEntry 31 }


nvX25statDtreset OBJECT-TYPE
     SYNTAX   DisplayString (SIZE (0..20))
     ACCESS   read-only
     STATUS   mandatory
     DESCRIPTION
       	"date & time statistics last reset"
     ::= {nvX25statEntry 32 }
     
nvX25statLinkup OBJECT-TYPE
     SYNTAX   INTEGER
     ACCESS   read-only
     STATUS   mandatory
     DESCRIPTION
     "Link (level2) uptime in seconds."
     ::= { nvX25statEntry 33 }

-- This file contains information about each virtual call
-- that is in progress. There is one record for each virtual
-- call in progress.

nvX25call OBJECT IDENTIFIER ::= { nevadaX25 2 }

nvX25callMaxRec OBJECT-TYPE
      SYNTAX   INTEGER
      ACCESS   read-only
      STATUS   mandatory
      DESCRIPTION
                "total number of records allowed in database file."
      ::= {nvX25call 1}

nvX25callNumRec OBJECT-TYPE
      SYNTAX   INTEGER
      ACCESS   read-only
      STATUS   mandatory
      DESCRIPTION
                "number of records in use."
      ::= {nvX25call 2}

nvX25callTable OBJECT-TYPE
      SYNTAX   SEQUENCE OF NvX25callEntry
      ACCESS   not-accessible
      STATUS   mandatory
      DESCRIPTION
               "x25call file."
      ::= { nvX25call 3 }

nvX25callEntry OBJECT-TYPE
      SYNTAX   NvX25callEntry
      ACCESS   not-accessible
      STATUS   mandatory
      DESCRIPTION
               "x25call record."
      INDEX { nvX25callIndex }
      ::= { nvX25callTable 1 }

NvX25callEntry ::=
      SEQUENCE {
      nvX25callIndex
            INTEGER,
      nvX25callNetname
            DisplayString,
      nvX25callChanstate
            INTEGER,
      nvX25callChantype
            INTEGER,
      nvX25callCode
            INTEGER,
      nvX25callDiag
            INTEGER,
      nvX25callExpack
            INTEGER,
      nvX25callLcn
            INTEGER,
      nvX25callRxpsze
            INTEGER,
      nvX25callRxwsze
            INTEGER,
      nvX25callRxtput
            INTEGER,
      nvX25callNr
            INTEGER,
      nvX25callNrunak
            INTEGER,
      nvX25callNs
            INTEGER,
      nvX25callNsunak
            INTEGER,
      nvX25callNunakpac
           INTEGER,
      nvX25callTxpsze
            INTEGER,
      nvX25callTxwsze
            INTEGER,
      nvX25callTxtput
            INTEGER,
      nvX25callNrxints
            Counter,
      nvX25callNrxpaks
            Counter,
      nvX25callNrxres
            Counter,
      nvX25callNrxrnrs
            Counter,
      nvX25callNrxrrs
            Counter,
      nvX25callNrxsegs
            Counter,
      nvX25callNtxints
            Counter,
      nvX25callNtxpaks
            Counter,
      nvX25callNtxsegs
            Counter,
      nvX25callNtxres
            Counter,
      nvX25callNtxrrs
            Counter,
      nvX25callDtreset
            DisplayString
               }

nvX25callIndex OBJECT-TYPE
     SYNTAX   INTEGER
     ACCESS   read-only
     STATUS   mandatory
     DESCRIPTION
        "Index of x25call record"
      ::= { nvX25callEntry 1 }

nvX25callNetname OBJECT-TYPE
     SYNTAX   DisplayString (SIZE (0..10))
     ACCESS   read-only
     STATUS   mandatory
     DESCRIPTION
"network interface name (as defined in the X25conf record)
"
     ::= { nvX25callEntry 2 }

nvX25callChanstate OBJECT-TYPE
     SYNTAX   INTEGER {
                p1(1),     -- ready (+1)
                p1r(2),     -- ready RESET
                p2(3),     -- local waiting
                p3(4),     -- remote waiting
                p3r(5),     -- remote waiting RESET
                d1i1(6),     -- normal
                d1i2(7),     -- remote interrupted
                d1i3(8),     -- local interrupted
                d1i4(9),     -- both interrupted
                d2(10),     -- remote reset
                d3(11),     -- local reset
                d4(12),     -- error reset I
                d5(13),     -- error reset II
                d6(14),     -- error reset III
                d7(15),     -- error reset IV
                p5C(16),     -- DCE call collision
                p5T(17),     -- DTE call collision
                p6(18),     -- local clearing
                p6r(19),     -- PVC clearing
                p2r(20),     -- wait for PVC response
                p7r(21)      -- data received causing PVC establishment
                }
     ACCESS   read-only
     STATUS   mandatory
     DESCRIPTION
"logical channel state
Initial status is p1 (0+1)."
     ::= { nvX25callEntry 3 }

nvX25callChantype OBJECT-TYPE
     SYNTAX   INTEGER {
                incoming(2),     -- Incoming (+1)
                outgoing(3),     -- Outgoing
                twoway(4),     -- Two-way
                permanent(5)      -- Permanent
                }
     ACCESS   read-only
     STATUS   mandatory
     DESCRIPTION
"logical channel type
Initial status is 3+1."
     ::= { nvX25callEntry 4 }

nvX25callCode OBJECT-TYPE
     SYNTAX   INTEGER {
                c-dte(2),     -- DTE originated (+1)
                c-bsy(3),     -- number busy
                c-ooo(4),     -- out of order
                c-rdo(5),     -- remote DTE operational
                c-rpe(6),     -- remote procedure error
                c-lpe(7),     -- local procedure error
                c-rns(8),     -- reverse charging acceptance not subscribed
                c-id(9),     -- incompatible destination
                c-fns(10),     -- fast select not subscribed
                c-ifr(11),     -- invalid facility request
                c-ab(12),     -- access barred
                c-nc(13),     -- network congestion
                c-no(14),     -- network operational
                c-nob(15),     -- not obtainable
                c-roo(16),     -- RPOA out of order
                c-sa(17),     -- ship absent
                c-noo(18)      -- network out of order
                }
     ACCESS   read-only
     STATUS   mandatory
     DESCRIPTION
"last clear or reset code
Initial status is 1+1."
     ::= { nvX25callEntry 5 }

nvX25callDiag OBJECT-TYPE
     SYNTAX   INTEGER (0..255)
     ACCESS   read-only
     STATUS   mandatory
     DESCRIPTION
"last diagnostic code
Initial status is 0."
     ::= { nvX25callEntry 6 }

nvX25callExpack OBJECT-TYPE
     SYNTAX   INTEGER (0..255)
     ACCESS   read-only
     STATUS   mandatory
     DESCRIPTION
"number of ACKs expected
This field indicates the number of message acknowlegements
that are expected from the Network User and is used for flow
control within the node.
Initial status is 0."
     ::= { nvX25callEntry 7 }

nvX25callLcn OBJECT-TYPE
     SYNTAX   INTEGER (0..4095)
     ACCESS   read-only
     STATUS   mandatory
     DESCRIPTION
"logical channel number assigned to this call
"
     ::= { nvX25callEntry 8 }

nvX25callRxpsze OBJECT-TYPE
     SYNTAX   INTEGER {
                b16(5),     -- 16 bytes (+1)
                b32(6),     -- 32 bytes
                b64(7),     -- 64 bytes
                b128(8),     -- 128 bytes
                b256(9),     -- 256 bytes
                b512(10),     -- 512 bytes
                b1024(11),     -- 1024 bytes
                b2048(12),     -- 2048 bytes
                b4096(13)      -- 4096 bytes
                }
     ACCESS   read-only
     STATUS   mandatory
     DESCRIPTION
"receive packet size
This field indicates the largest packet that will be
received across the interface. If flow-control negotiation
is in effect,this is the value that was agreed.
Initial status is 7+1."
     ::= { nvX25callEntry 9 }

nvX25callRxwsze OBJECT-TYPE
     SYNTAX   INTEGER (1..15)
     ACCESS   read-only
     STATUS   mandatory
     DESCRIPTION
"receive window
This field indicates the packet-level receive
window size being used.
If flow-control negotiation
is in effect,this is the value that was agreed.
Initial status is 2."
     ::= { nvX25callEntry 10 }

nvX25callRxtput OBJECT-TYPE
     SYNTAX   INTEGER {
                bps75(4),     -- 75 bps (+1)
                bps150(5),     -- 150 bps
                bps300(6),     -- 300 bps
                bps600(7),     -- 600 bps
                bps1200(8),     -- 1200 bps
                bps2400(9),     -- 2400 bps
                bps4800(10),     -- 4800 bps
                bps9600(11),     -- 9600 bps
                bps19200(12),     -- 19200 bps
                bps48000(13)      -- 48000 bps
                }
     ACCESS   read-only
     STATUS   mandatory
     DESCRIPTION
"receive throughput class
This field indicates the receive throughtput class that is
being used. If throughput-class negotiation
is in effect,this is the value that was agreed.
Initial status is 7+1."
     ::= { nvX25callEntry 11 }

nvX25callNr OBJECT-TYPE
     SYNTAX   INTEGER (0..127)
     ACCESS   read-only
     STATUS   mandatory
     DESCRIPTION
"N(R) state variable
This field indicates the sequence number of the next packet
expected to be received on this logical channel.
Initial status is 0."
     ::= { nvX25callEntry 12 }

nvX25callNrunak OBJECT-TYPE
     SYNTAX   INTEGER (0..127)
     ACCESS   read-only
     STATUS   mandatory
     DESCRIPTION
"next N(R) to acknowlege
This field indicates the sequence number of the packet
that will next be acknowledged as received on this channel.
 By delaying acknowledgements of received packets,flow
control of the sender is achieved.
Initial status is 0."
     ::= { nvX25callEntry 13 }

nvX25callNs OBJECT-TYPE
     SYNTAX   INTEGER (0..127)
     ACCESS   read-only
     STATUS   mandatory
     DESCRIPTION
"N(S) state variable
This field indicates the sequence number of the next
data packet to be sent on this logical channel.
Initial status is 0."
     ::= { nvX25callEntry 14 }

nvX25callNsunak OBJECT-TYPE
     SYNTAX   INTEGER (0..127)
     ACCESS   read-only
     STATUS   mandatory
     DESCRIPTION
"N(S) to be acknowledged
This field indicates the sequence number of the data
packet that
is to be acknowledged next by the receiver.
Initial status is 0."
     ::= { nvX25callEntry 15 }

nvX25callNunakpac OBJECT-TYPE
     SYNTAX   INTEGER (0..255)
     ACCESS   read-only
     STATUS   mandatory
     DESCRIPTION
"number of unacknowledged data packets transmitted
This field indicates the number of data packets that have been
sent but that are not yet acknowledged by the receiver.
Initial status is 0."
     ::= { nvX25callEntry 16 }

nvX25callTxpsze OBJECT-TYPE
     SYNTAX   INTEGER {
                b16(5),     -- 16 bytes (+1)
                b32(6),     -- 32 bytes
                b64(7),     -- 64 bytes
                b128(8),     -- 128 bytes
                b256(9),     -- 256 bytes
                b512(10),     -- 512 bytes
                b1024(11),     -- 1024 bytes
                b2048(12),     -- 2048 bytes
                b4096(13)      -- 4096 bytes
                }
     ACCESS   read-only
     STATUS   mandatory
     DESCRIPTION
"transmit packet size
This field indicates the largest packet that will be
transmitted across the interface. If flow-control negotiation
is in effect,this is the value that was agreed.
Initial status is 7+1."
     ::= { nvX25callEntry 17 }

nvX25callTxwsze OBJECT-TYPE
     SYNTAX   INTEGER (1..15)
     ACCESS   read-only
     STATUS   mandatory
     DESCRIPTION
"transmit window
This field indicates the packet-level transmit
window size being used.
If flow-control negotiation
is in effect,this is the value that was agreed.
Initial status is 2."
     ::= { nvX25callEntry 18 }

nvX25callTxtput OBJECT-TYPE
     SYNTAX   INTEGER {
                bps75(4),     -- 75 bps (+1)
                bps150(5),     -- 150 bps
                bps300(6),     -- 300 bps
                bps600(7),     -- 600 bps
                bps1200(8),     -- 1200 bps
                bps2400(9),     -- 2400 bps
                bps4800(10),     -- 4800 bps
                bps9600(11),     -- 9600 bps
                bps19200(12),     -- 19200 bps
                bps48000(13)      -- 48000 bps
                }
     ACCESS   read-only
     STATUS   mandatory
     DESCRIPTION
"transmit throughput class
This field indicates the transmit throughtput class that is
being used. If throughput-class negotiation
is in effect,this is the value that was agreed.
Initial status is 7+1."
     ::= { nvX25callEntry 19 }

nvX25callNrxints OBJECT-TYPE
     SYNTAX   Counter
     ACCESS   read-only
     STATUS   mandatory
     DESCRIPTION
"number of INTERRUPTs received
Statistic is zeroed at startup time."
     ::= { nvX25callEntry 20 }

nvX25callNrxpaks OBJECT-TYPE
     SYNTAX   Counter
     ACCESS   read-only
     STATUS   mandatory
     DESCRIPTION
"number of packets received
Statistic is zeroed at startup time."
     ::= { nvX25callEntry 21 }

nvX25callNrxres OBJECT-TYPE
     SYNTAX   Counter
     ACCESS   read-only
     STATUS   mandatory
     DESCRIPTION
"number of RESET REQUESTs received
Statistic is zeroed at startup time."
     ::= { nvX25callEntry 22 }

nvX25callNrxrnrs OBJECT-TYPE
     SYNTAX   Counter
     ACCESS   read-only
     STATUS   mandatory
     DESCRIPTION
"number of RNRs received
Statistic is zeroed at startup time."
     ::= { nvX25callEntry 23 }

nvX25callNrxrrs OBJECT-TYPE
     SYNTAX   Counter
     ACCESS   read-only
     STATUS   mandatory
     DESCRIPTION
"number of RRs received
Statistic is zeroed at startup time."
     ::= { nvX25callEntry 24 }

nvX25callNrxsegs OBJECT-TYPE
     SYNTAX   Counter
     ACCESS   read-only
     STATUS   mandatory
     DESCRIPTION
"number of segments received
Statistic is zeroed at startup time."
     ::= { nvX25callEntry 25 }

nvX25callNtxints OBJECT-TYPE
     SYNTAX   Counter
     ACCESS   read-only
     STATUS   mandatory
     DESCRIPTION
"number of INTERRUPTs sent
Statistic is zeroed at startup time."
     ::= { nvX25callEntry 26 }

nvX25callNtxpaks OBJECT-TYPE
     SYNTAX   Counter
     ACCESS   read-only
     STATUS   mandatory
     DESCRIPTION
"number of packets sent
Statistic is zeroed at startup time."
     ::= { nvX25callEntry 27 }

nvX25callNtxsegs OBJECT-TYPE
     SYNTAX   Counter
     ACCESS   read-only
     STATUS   mandatory
     DESCRIPTION
"number of segments sent
Statistic is zeroed at startup time."
     ::= { nvX25callEntry 28 }

nvX25callNtxres OBJECT-TYPE
     SYNTAX   Counter
     ACCESS   read-only
     STATUS   mandatory
     DESCRIPTION
"number of RESET REQUESTs sent
Statistic is zeroed at startup time."
     ::= { nvX25callEntry 29 }

nvX25callNtxrrs OBJECT-TYPE
     SYNTAX   Counter
     ACCESS   read-only
     STATUS   mandatory
     DESCRIPTION
"number of RRs sent
.note
RNRs are not transmitted by the X.25 interface component.
.end note
Statistic is zeroed at startup time."
     ::= { nvX25callEntry 30 }

nvX25callDtreset OBJECT-TYPE
     SYNTAX   DisplayString (SIZE (0..20))
     ACCESS   read-only
     STATUS   mandatory
     DESCRIPTION
       	"date & time statistics last reset"
     ::= { nvX25callEntry 31 }

-- The records in this file
-- configure instances of X.25 network interfaces. There
-- is one record per instance of an X.25 network interface.

nvX25conf OBJECT IDENTIFIER ::= { nevadaX25 3 }

nvX25confMaxRec OBJECT-TYPE
      SYNTAX   INTEGER
      ACCESS   read-only
      STATUS   mandatory
      DESCRIPTION
                "total number of records allowed in database file."
      ::= {nvX25conf 1}

nvX25confNumRec OBJECT-TYPE
      SYNTAX   INTEGER
      ACCESS   read-only
      STATUS   mandatory
      DESCRIPTION
                "number of records in use."
      ::= {nvX25conf 2}

nvX25confTable OBJECT-TYPE
      SYNTAX   SEQUENCE OF NvX25confEntry
      ACCESS   not-accessible
      STATUS   mandatory
      DESCRIPTION
               "x25conf file."
      ::= { nvX25conf 3 }

nvX25confEntry OBJECT-TYPE
      SYNTAX   NvX25confEntry
      ACCESS   not-accessible
      STATUS   mandatory
      DESCRIPTION
               "x25conf record."
      INDEX { nvX25confIndex }
      ::= { nvX25confTable 1 }

NvX25confEntry ::=
      SEQUENCE {
      nvX25confIndex
            INTEGER,
      nvX25confNetname
            DisplayString,
      nvX25confApp
            INTEGER,
      nvX25confAutostart
            INTEGER,
      nvX25confDlnumber
            INTEGER,
      nvX25confLic
            INTEGER,
      nvX25confLoc
            INTEGER,
      nvX25confLpc
            INTEGER,
      nvX25confLtc
            INTEGER,
      nvX25confNic
            INTEGER,
      nvX25confNoc
            INTEGER,
      nvX25confNpc
            INTEGER,
      nvX25confNtc
            INTEGER,
      nvX25confAcktimer
            INTEGER,
      nvX25confAckthresh
            INTEGER,
      nvX25confNuireq
            INTEGER,
      nvX25confCugformat
            INTEGER,
      nvX25confDbmod
            INTEGER,
      nvX25confDefpsze
            INTEGER,
      nvX25confDefwsze
            INTEGER,
      nvX25confDeftput
            INTEGER,
      nvX25confDiagsupr
            INTEGER,
      nvX25confDirection
            INTEGER,
      nvX25confFlowneg
            INTEGER,
      nvX25confFstacc
            INTEGER,
      nvX25confUpdncmd
            INTEGER,
      nvX25confMaxpsze
            INTEGER,
      nvX25confMaxwsze
            INTEGER,
      nvX25confNetaddr
            DisplayString,
      nvX25confNettype
            INTEGER,
      nvX25confNetvrsion
            INTEGER,
      nvX25confPktbuf
            INTEGER,
      nvX25confStndbytim
            INTEGER,
      nvX25confRevacc
            INTEGER,
      nvX25confThruneg
            INTEGER,
      nvX25confTx0
            INTEGER,
      nvX25confTx1
            INTEGER,
      nvX25confTx2
            INTEGER,
      nvX25confTx3
            INTEGER,
      nvX25confXtend
            INTEGER,
      nvX25confNuirtg
            INTEGER,
      nvX25confIsdnaddr
	    INTEGER
                }

nvX25confIndex OBJECT-TYPE
     SYNTAX   INTEGER
     ACCESS   read-only
     STATUS   mandatory
     DESCRIPTION
        "Index of x25conf record"
      ::= { nvX25confEntry 1 }

nvX25confNetname OBJECT-TYPE
     SYNTAX   DisplayString (SIZE (0..10))
     ACCESS   read-only
     STATUS   mandatory
     DESCRIPTION
"Network Interface Name (netname)
This field names an instance of the X.25 network interface.
The name is used to identify the status records belonging to,and commands
destined for,a particular instance of an X.25 network interface.
Parameter is set during factory configuration."
     ::= { nvX25confEntry 2 }

nvX25confApp OBJECT-TYPE
     SYNTAX   INTEGER {
                dte(2),     -- X.25 DTE (+1)
                dce(3),     -- X.25 DCE
                trunkx(17),     -- internodal trunk STE-X
                trunky(33)      -- internodal trunk STE-Y
                }
     ACCESS   read-write
     STATUS   mandatory
     DESCRIPTION
"Logical Interface Appearance (app)
This field defines whether the component implements an X.25
interface,or an internal network trunk interface.
In addition,it specifies the appearance of the interface.
Default value is 1+1."
     ::= { nvX25confEntry 3 }

nvX25confAutostart OBJECT-TYPE
     SYNTAX   INTEGER {
                disable(1),  -- (+1)network interface remains inactive after processor start-up
                enable(2),   -- network interface attempts to establish a connection after processor start-up
                stndby(3),   -- network interface establishes a connection when required
                v32(4),      -- V.32 Modem Management
                dialin(5),    -- dial in X.25 access concentrator
                bidir(6)        -- allow bidirectional call on isdn port
                }
     ACCESS   read-write
     STATUS   mandatory
     DESCRIPTION
"Auto X.25 Connection Startup (autostart)
Default value is enable (1+1)."
     ::= { nvX25confEntry 4 }

nvX25confDlnumber OBJECT-TYPE
     SYNTAX   INTEGER (0..254)
     ACCESS   read-write
     STATUS   mandatory
     DESCRIPTION
"Data Link Record (dlnumber)
This field tells which of the DLCONF records in the
SL component should be used by this net.
Default value is 0."
     ::= { nvX25confEntry 5 }

nvX25confLic OBJECT-TYPE
     SYNTAX   INTEGER (0..4095)
     ACCESS   read-write
     STATUS   mandatory
     DESCRIPTION
"Lowest Incoming SVC (lic)
This field defines the lowest logical channel number (LCN)
that is reserved for incoming calls.
The range of logical channels from LIC to LIC+NIC-1 is
reserved for incoming calls only.
Default value is 1."
     ::= { nvX25confEntry 6 }

nvX25confLoc OBJECT-TYPE
     SYNTAX   INTEGER (0..4095)
     ACCESS   read-write
     STATUS   mandatory
     DESCRIPTION
"Lowest Outgoing SVC (loc)
This field defines the lowest logical channel number (LCN)
that is reserved for outgoing calls.
The range of logical channels from LOC to LOC+NOC-1 is
reserved for outgoing calls.
Default value is 1."
     ::= { nvX25confEntry 7 }

nvX25confLpc OBJECT-TYPE
     SYNTAX   INTEGER (0..4095)
     ACCESS   read-write
     STATUS   mandatory
     DESCRIPTION
"Lowest PVC (lpc)
This field describes the lowest logical channel number (LCN)
in the range reserved for permanent virtual circuits (PVCs).
Each of the channels should also be described in the X25PVC
file,although if they are not they will be treated as PVC
'B' ends.
Default value is 1."
     ::= { nvX25confEntry 8 }

nvX25confLtc OBJECT-TYPE
     SYNTAX   INTEGER (0..4095)
     ACCESS   read-write
     STATUS   mandatory
     DESCRIPTION
"Lowest Two-Way SVC (ltc)
This field defines the lowest logical channel number (LCN)
that may be used for both incoming calls and outgoing calls.
The range of logical channels from LTC to LTC+NTC-1 is
available for incoming and outgoing calls.
Default value is 1."
     ::= { nvX25confEntry 9 }

nvX25confNic OBJECT-TYPE
     SYNTAX   INTEGER (0..4095)
     ACCESS   read-write
     STATUS   mandatory
     DESCRIPTION
"Number of Incoming SVCs (nic)
Default value is 0."
     ::= { nvX25confEntry 10 }

nvX25confNoc OBJECT-TYPE
     SYNTAX   INTEGER (0..4095)
     ACCESS   read-write
     STATUS   mandatory
     DESCRIPTION
"Number of Outgoing SVCs (noc)
Default value is 0."
     ::= { nvX25confEntry 11 }

nvX25confNpc OBJECT-TYPE
     SYNTAX   INTEGER (0..4095)
     ACCESS   read-write
     STATUS   mandatory
     DESCRIPTION
"Number of PVCs (npc)
Default value is 0."
     ::= { nvX25confEntry 12 }

nvX25confNtc OBJECT-TYPE
     SYNTAX   INTEGER (0..4095)
     ACCESS   read-write
     STATUS   mandatory
     DESCRIPTION
"Number of Two-Way SVCs (ntc)
.nfl index
.nfl capitalize
.note
The four ranges
(LPC to LPC+NPC-1; LIC to LIC+NIC-1; LTC to LTC+NTC-1 ;and LOC to LOC+NOC-1)
must not overlap. Futhermore,to avoid channel assignments collisions
between DTEs and DCEs,it is recommended that the ranges be assigned thus:
.br;For DTEs: LIC to LIC+NIC-1 < LTC to LTC+NTC-1 < LOC to LOC+NOC-1
.br;For DCEs: LIC to LIC+NIC-1 > LTC to LTC+NTC-1 > LOC to LOC+NOC-1
.end note
.fl index
.fl capitalize
Default value is 28."
     ::= { nvX25confEntry 13 }

nvX25confAcktimer OBJECT-TYPE
     SYNTAX   INTEGER (0..100)
     ACCESS   read-write
     STATUS   mandatory
     DESCRIPTION
"Packet Acknowledgement Timer (acktimer)
 defines if t2 procedure is going to be used or not,and
 if it is going to be used what t2 time period will be in
 one tenths of a second. When t2 is zero,procedure to
 delay acknowledgement will not be performed.
Default value is 0."
     ::= { nvX25confEntry 14 }

nvX25confAckthresh OBJECT-TYPE
     SYNTAX   INTEGER (0..15)
     ACCESS   read-write
     STATUS   mandatory
     DESCRIPTION
"Acknowledgement Threshold (ackthresh)
 acknowledgement threshold is used to acknowledge received
 data when certain number of data packets received,even if
 t2 timer has not expired. It is used only if t2 procedure
 is active,ie acktime is greater than zero.
Default value is 0."
     ::= { nvX25confEntry 15 }

nvX25confNuireq OBJECT-TYPE
     SYNTAX   INTEGER {
                no(1),     -- (+1)disable option
                yes(2)      -- enable option
                }
     ACCESS   read-write
     STATUS   mandatory
     DESCRIPTION
" NUI required
"
     ::= { nvX25confEntry 16 }

nvX25confCugformat OBJECT-TYPE
     SYNTAX   INTEGER {
                basic(1)      -- basic format (+1)
                }
     ACCESS   read-write
     STATUS   mandatory
     DESCRIPTION
"Closed User Group Format (cugformat)
This field indicates the format of closed user groups to which
this interface subscribes. If the type is basic,the
two digit format of the CUG facility request is used. If
the type is extend the four digit format is used.
Default value is basic (0+1)."
     ::= { nvX25confEntry 17 }

nvX25confDbmod OBJECT-TYPE
     SYNTAX   INTEGER {
                no(1),     -- (+1)disable option
                yes(2)      -- enable option
                }
     ACCESS   read-write
     STATUS   mandatory
     DESCRIPTION
"D-Bit Modification (dbmod)
This field enables d bit modification,where all data packets
received from the link are assumed to have their delivery
confirmation bit set,and all data packets transmitted have
it reset. This is only present to cater to older network
implementations that do not support delivery confirmation.
Default value is 0."
     ::= { nvX25confEntry 18 }

nvX25confDefpsze OBJECT-TYPE
     SYNTAX   INTEGER {
                b16(5),     -- 16 bytes (+1)
                b32(6),     -- 32 bytes
                b64(7),     -- 64 bytes
                b128(8),     -- 128 bytes
                b256(9),     -- 256 bytes
                b512(10),     -- 512 bytes
                b1024(11),     -- 1024 bytes
                b2048(12),     -- 2048 bytes
                b4096(13)      -- 4096 bytes
                }
     ACCESS   read-write
     STATUS   mandatory
     DESCRIPTION
"Default Packet Size (defpsze)
This value sets the maximum packet size that can be
transferred across the interface if packet size negotiation
is disabled (flowneg = no/wsz) or is not requested.

If flow control parameter negotiation is enabled
(flowneg = yes/psz),
this value is used as a starting point and may be negotiated,
with the network,
up to the value of maxpsze or down to the minimum value of 16.

Values for packet size requested by components (eg ITI)
are preferentially used if flow
control negotiation is enabled (flowneg = yes/psz) AND if the
requested values are between maxpsze and 16; in all other
cases defpsze is used.
Default value is 7+1."
     ::= { nvX25confEntry 19 }

nvX25confDefwsze OBJECT-TYPE
     SYNTAX   INTEGER (1..15)
     ACCESS   read-write
     STATUS   mandatory
     DESCRIPTION
"Default Window Size (defwsze)
This field sets the default value for the packet-level
window size to be used
when transferring packets if flow-control negotiation is
disabled (flowneg = no/psz) or is not requested.
 If flow control parameter
negotiation is enabled (flowneg=yes/wsz) then this value is
used as a starting point and may be negotiated up to the
maximum value set by maxwsze or down to a minimum value of 1.

If this field is set to a value greater than 7,the
interface must be configured for extended packet numbering
(xtend = yes).

Values for window size requested by components (eg ITI)
are preferentially used if flow
control negotiation is enabled (flowneg = yes/wsz) AND if the
requested values are between maxwsze and 1; in all other
cases defwsze is used.
Default value is 2."
     ::= { nvX25confEntry 20 }

nvX25confDeftput OBJECT-TYPE
     SYNTAX   INTEGER {
                bps75(4),     -- 75 bps (+1)
                bps150(5),     -- 150 bps
                bps300(6),     -- 300 bps
                bps600(7),     -- 600 bps
                bps1200(8),     -- 1200 bps
                bps2400(9),     -- 2400 bps
                bps4800(10),     -- 4800 bps
                bps9600(11),     -- 9600 bps
                bps19200(12),     -- 19200 bps
                bps48000(13)      -- 48000 bps
                }
     ACCESS   read-write
     STATUS   mandatory
     DESCRIPTION
"Default Throughput Class (deftput)
This field sets the initial value to be used for the
throughput class for the virtual call if throughput-class
negotiation is disabled (thruneg = no) or is not requested.

If throughput-class negotiation is enabled (thruneg = yes),
this value is used as a starting point and may be negotiated,
with the network,downwards.

Values for throughputclass negotiation
requested by components (eg ITI)
are preferentially used if throughput-class
negotiation is enabled (thruneg = yes) AND if the
requested values are less than deftput; in all other
cases deftput is used.

.note;Although CCITT defines throughput classes in terms of
a guaranteed data-rate,throughput classes are only
implemented to the extent of arranging that packets of a
higher throughput-class are serviced before those of a lower
class.
.end note
Default value is 10+1."
     ::= { nvX25confEntry 21 }

nvX25confDiagsupr OBJECT-TYPE
     SYNTAX   INTEGER {
                no(1),     -- disable option (+1)
                yes(2)      -- enable option
                }
     ACCESS   read-write
     STATUS   mandatory
     DESCRIPTION
"Diagnostic Packet Suppression (diagsupr)
This field suppresses or enables the emission of DIAG
diagnostic packets on some network protocol violations.
Default value is no (0+1)."
     ::= { nvX25confEntry 22 }

nvX25confDirection OBJECT-TYPE
     SYNTAX   INTEGER {
                incoming(2),     -- incoming only (+1)
                outgoing(3),     -- outgoing only
                twoway(4)      -- incoming and outgoing
                }
     ACCESS   read-write
     STATUS   mandatory
     DESCRIPTION
"Call Direction Allowed (direction)
This field indicates whether incoming and outgoing calls may be
made over this interface.
Default value is 3+1."
     ::= { nvX25confEntry 23 }

nvX25confFlowneg OBJECT-TYPE
     SYNTAX   INTEGER {
                no(1),     -- disable packet size and window size negotiation (+1)
                yes(2),     -- enable both packet and window sizes negotiation
                psn(3),     -- enable packet size negotiation only
                wsn(4)      -- enable window size negotiation only
                }
     ACCESS   read-write
     STATUS   mandatory
     DESCRIPTION
"Flow Control Negotiation (flowneg)
This field enables or disables negotiation of the flow control
parameters,window size and packet size.
Default value is no (0+1)."
     ::= { nvX25confEntry 24 }

nvX25confFstacc OBJECT-TYPE
     SYNTAX   INTEGER {
                no(1),     -- disable option (+1)
                yes(2)      -- enable option
                }
     ACCESS   read-write
     STATUS   mandatory
     DESCRIPTION
"Fast Select Acceptance (fstacc)
This field defines whether fast-select call requests
are accepted.
Default value is no (0+1)."
     ::= { nvX25confEntry 25 }

nvX25confUpdncmd OBJECT-TYPE
     SYNTAX   INTEGER (0..65535)
     ACCESS   read-write
     STATUS   mandatory
     DESCRIPTION
"Link Up/Down Command
This field is the string id of a script like command that
may bring other links up or down when this link goes up or
down
 format: netup-cmds>netdown-cmds
 netup-cmds: >netx.up/down...
 netdown-cmds: netx.up/down...
 example: >netw.up>netx.down>>nety.up>netz.down
Default value is 0."
     ::= { nvX25confEntry 26 }

nvX25confMaxpsze OBJECT-TYPE
     SYNTAX   INTEGER {
                b16(5),     -- 16 bytes (+1)
                b32(6),     -- 32 bytes
                b64(7),     -- 64 bytes
                b128(8),     -- 128 bytes
                b256(9),     -- 256 bytes
                b512(10),     -- 512 bytes
                b1024(11),     -- 1024 bytes
                b2048(12),     -- 2048 bytes
                b4096(13)      -- 4096 bytes
                }
     ACCESS   read-write
     STATUS   mandatory
     DESCRIPTION
"Maximum Packet Size (maxpsze)
This value is the maximum acceptable value for the
largest packet that can be sent across the interface.
It is used as an upper-bound in packet size negotiation.
Default value is 7+1."
     ::= { nvX25confEntry 27 }

nvX25confMaxwsze OBJECT-TYPE
     SYNTAX   INTEGER (1..15)
     ACCESS   read-write
     STATUS   mandatory
     DESCRIPTION
"Maximum Window Size (maxwsze)
This field sets the maximum acceptable value for the
packet-level window size to be used
when transferring packets. It is used as a upper-bound
in window size negotiation.

If this field is set to a value greater than 7,the
interface must be configured for extended packet numbering
(xtend = yes).
Default value is 2."
     ::= { nvX25confEntry 28 }

nvX25confNetaddr OBJECT-TYPE
     SYNTAX   DisplayString (SIZE (0..16))
     ACCESS   read-write
     STATUS   mandatory
     DESCRIPTION
"Calling Network Address (netaddr)
If this field is not empty,the contents will be supplied as
the calling network address in all call request packets
transmitted,overriding anything supplied by the network user.
"
     ::= { nvX25confEntry 29 }

nvX25confNettype OBJECT-TYPE
     SYNTAX   INTEGER {
                ccitt(1),     -- pure CCITT X.25 (+1)
                datapac(2),     -- Canadian Datapac
                transpac(3),     -- French Transpac
                upss(4),      -- Unextended PSS
                transb(6)       -- French Transpac with truncated address
                }
     ACCESS   read-write
     STATUS   mandatory
     DESCRIPTION
"X.25 Network Type (nettype)
This field indicates the local variety of X.25 network and
is primarily used to show how to interpret non-X.25 facilities
of the local network.If nettype = unknown,non-X.25
facilities are passed transparently through a switch
and ignored by a PAD.
Default value is ccitt (0+1)."
     ::= { nvX25confEntry 30 }

nvX25confNetvrsion OBJECT-TYPE
     SYNTAX   INTEGER {
                v1976(77),     -- original version (+1)
                v1980(81),     -- first revision
                v1984(85)      -- second revision
                }
     ACCESS   read-write
     STATUS   mandatory
     DESCRIPTION
"Network Version (netvrsion)
This field indicates which version of the X.25 recommendation
to which the network interface should adhere.
Default value is 80."
     ::= { nvX25confEntry 31 }

nvX25confPktbuf OBJECT-TYPE
     SYNTAX   INTEGER (0..15)
     ACCESS   read-write
     STATUS   mandatory
     DESCRIPTION
"Packet Buffer for Unbalance Window
For unbalanced window enhancement,FRR will be generated
when the number of unacknowledged transmitted packets reaches
the value of the PKTBUF field.
Default value is 0."
     ::= { nvX25confEntry 32 }

nvX25confStndbytim OBJECT-TYPE
     SYNTAX   INTEGER (0..255)
     ACCESS   read-write
     STATUS   mandatory
     DESCRIPTION
"Standby Timer (stndbytim)
How many seconds the box will wait before dropping
dialout connection when there is no vc connected.
Default value is 30."
     ::= { nvX25confEntry 33 }

nvX25confRevacc OBJECT-TYPE
     SYNTAX   INTEGER {
                no(1),     -- disable option (+1)
                yes(2)      -- enable option  (+1)
                }
     ACCESS   read-write
     STATUS   mandatory
     DESCRIPTION
"Reverse Charging Acceptance (revacc)
In an X.25 DTE configuration,this field defines whether
an incoming call indicating reverse charging is passed up to
the Network Bus or rejected immediately.
 In an X.25 DCE configuration,it indicates whether a reverse
charging call to the DTE should be passed through or cleared.
 In X.75 configurations this field has no significance.
Default value is yes (1+1)."
     ::= { nvX25confEntry 34 }

nvX25confThruneg OBJECT-TYPE
     SYNTAX   INTEGER {
                no(1),     -- (+1)disable option
                yes(2)      -- enable option
                }
     ACCESS   read-write
     STATUS   mandatory
     DESCRIPTION
"Throughput Class Negotiation (thruneg)
This field enables or disables negotiation of throughput classes.
Default value is (0+1)."
     ::= { nvX25confEntry 35 }

nvX25confTx0 OBJECT-TYPE
     SYNTAX   INTEGER (0..255)
     ACCESS   read-write
     STATUS   mandatory
     DESCRIPTION
"Restart Request Timer (tx0)
This field defines the value,in seconds,for
restart indication timer#(T10 - DCE appearance)
restart request timer####(T20 - DTE appearance)

Recommended values are:
T10 - 60s
T20 - 180s
Default value is 180."
     ::= { nvX25confEntry 36 }

nvX25confTx1 OBJECT-TYPE
     SYNTAX   INTEGER (0..255)
     ACCESS   read-write
     STATUS   mandatory
     DESCRIPTION
"Call Request Timer (tx1)
This field defines the value,in seconds,for
- incoming call timer######(T11 - DCE appearance)
- call request timer#######(T21 - DTE appearance)

Recommended values are:
T11 - 180s
T21 - 200s
Default value is 200."
     ::= { nvX25confEntry 37 }

nvX25confTx2 OBJECT-TYPE
     SYNTAX   INTEGER (0..255)
     ACCESS   read-write
     STATUS   mandatory
     DESCRIPTION
"Reset Request Timer (tx2)
This field defines the value,in seconds,for
- reset indication timer###(T12 - DCE appearance)
- reset request timer######(T22 - DTE appearance)

Recommended values are:
T12 - 60s
T22 - 180s
Default value is 180."
     ::= { nvX25confEntry 38 }

nvX25confTx3 OBJECT-TYPE
     SYNTAX   INTEGER (0..255)
     ACCESS   read-write
     STATUS   mandatory
     DESCRIPTION
"Clear Request Timer (tx3)
This field defines the value,in seconds,for
- clear indication timer###(T13 - DCE appearance)
- clear request timer######(T23 - DTE appearance)

Recommended values are:
T13 - 60s
T23 - 180s
Default value is 180."
     ::= { nvX25confEntry 39 }

nvX25confXtend OBJECT-TYPE
     SYNTAX   INTEGER {
                no(1),     -- disable option (+1)
                yes(2)      -- enable option (+1)
                }
     ACCESS   read-write
     STATUS   mandatory
     DESCRIPTION
"Extended Packet Numbering (xtend)
This field allows the extended packet
sequencing format (modulo 128) to be used.
If this option is not selected,packet sequencing is
modulo 8.
Default value is no (0+1)."
     ::= { nvX25confEntry 40 }

nvX25confNuirtg OBJECT-TYPE
     SYNTAX   INTEGER {
                no(1),     -- (+1)disable option
                yes(2)      -- enable option
                }
     ACCESS   read-write
     STATUS   mandatory
     DESCRIPTION 
"If this field is set to yes,route is based on NUI using x25nuimap entries.
"
     ::= { nvX25confEntry 42 }

nvX25confIsdnaddr OBJECT-TYPE
     SYNTAX   INTEGER {
		no(1),
		yes(2)
		}
     ACCESS   read-write
     STATUS   mandatory
     DESCRIPTION
	"Get calling address from ISDN?
	Default value is no (0+1)."
     ::= { nvX25confEntry 43 }

-- The records in this file
-- If the x25conf nuirtg field is set to Yes, then this
-- file specifies the mapping between the NUI facility and
-- the called address.

nvX25nuimap OBJECT IDENTIFIER ::= { nevadaX25 4 }

nvX25nuimapMaxRec OBJECT-TYPE
      SYNTAX   INTEGER
      ACCESS   read-only
      STATUS   mandatory
      DESCRIPTION
                "total number of records allowed in database file."
      ::= {nvX25nuimap 1}

nvX25nuimapNumRec OBJECT-TYPE
      SYNTAX   INTEGER
      ACCESS   read-only
      STATUS   mandatory
      DESCRIPTION
                "number of records in use."
      ::= {nvX25nuimap 2}

nvX25nuimapTable OBJECT-TYPE
      SYNTAX   SEQUENCE OF NvX25nuimapEntry
      ACCESS   not-accessible
      STATUS   mandatory
      DESCRIPTION
               "x25nuimap file."
      ::= { nvX25nuimap 3 }

nvX25nuimapEntry OBJECT-TYPE
      SYNTAX   NvX25nuimapEntry
      ACCESS   not-accessible
      STATUS   mandatory
      DESCRIPTION
               "x25nuimap record."
      INDEX { nvX25nuimapIndex }
      ::= { nvX25nuimapTable 1 }

NvX25nuimapEntry ::=
      SEQUENCE {
      nvX25nuimapIndex
            INTEGER,
      nvX25nuimapNui
            DisplayString,
      nvX25nuimapCalled
            DisplayString,
      nvX25nuimapStatus
            INTEGER
		}

nvX25nuimapIndex OBJECT-TYPE
     SYNTAX   INTEGER
     ACCESS   read-only
     STATUS   mandatory
     DESCRIPTION
        "Index of x25nuimap record"
      ::= { nvX25nuimapEntry 1 }

nvX25nuimapNui OBJECT-TYPE
     SYNTAX   DisplayString  (SIZE(0..58))
     ACCESS   read-write
     STATUS   mandatory
     DESCRIPTION

" NUI value to match
"
     ::= { nvX25nuimapEntry 2 }

nvX25nuimapCalled OBJECT-TYPE

     SYNTAX   DisplayString  (SIZE(0..16))
     ACCESS   read-write
     STATUS   mandatory
     DESCRIPTION

" Called Network Address
"
     ::= { nvX25nuimapEntry 3 }


nvX25nuimapStatus OBJECT-TYPE
     SYNTAX   INTEGER {
                valid(1),
                invalid(2)
                }
     ACCESS   read-write
     STATUS   mandatory
     DESCRIPTION
           "Operation status. Add the record to the table (valid) or
           delete the record from the table (invalid)."
     ::= { nvX25nuimapEntry 4 }

--
--	xbillconf filw
--

nvXbillconf OBJECT IDENTIFIER ::= { nevadaX25 5 }

nvXbillconfMaxRec OBJECT-TYPE
      SYNTAX   INTEGER
      ACCESS   read-only
      STATUS   mandatory
      DESCRIPTION
	"total number of records allowed in database file."
      ::= {nvXbillconf 1}

nvXbillconfNumRec OBJECT-TYPE
      SYNTAX   INTEGER
      ACCESS   read-only
      STATUS   mandatory
      DESCRIPTION
                "number of records in use."
      ::= {nvXbillconf 2}
 
nvXbillconfTable OBJECT-TYPE
      SYNTAX   SEQUENCE OF NvXbillconfEntry
      ACCESS   not-accessible
      STATUS   mandatory
      DESCRIPTION
               "xbillconf file."
      ::= {nvXbillconf 3}

nvXbillconfEntry OBJECT-TYPE
      SYNTAX   NvXbillconfEntry
      ACCESS   not-accessible
      STATUS   mandatory
      DESCRIPTION
               "xbillconf record, indexed by record number"
      INDEX {nvXbillconfIndex}
      ::= {nvXbillconfTable 1 }
 
NvXbillconfEntry ::=
      SEQUENCE {
        nvXbillconfIndex
                INTEGER,
	nvXbillconfEnable
		INTEGER,
	nvXbillconfSegsize
		INTEGER,
	nvXbillconfBilltime
		INTEGER
	}

nvXbillconfIndex OBJECT-TYPE
     SYNTAX   INTEGER
     ACCESS   read-only
     STATUS   mandatory
     DESCRIPTION
        "Index of xbillconf record."
     ::= {nvXbillconfEntry 1 }
 
nvXbillconfEnable OBJECT-TYPE
     SYNTAX   INTEGER {
		false(1),
		true(2)
		}
     ACCESS   read-write
     STATUS   mandatory
     DESCRIPTION
	"Enable/Disable xbillstat accounting."
     ::= { nvXbillconfEntry 2 }

nvXbillconfSegsize OBJECT-TYPE 
     SYNTAX   INTEGER (0..32767)
     ACCESS   read-write 
     STATUS   mandatory 
     DESCRIPTION 
        "Segment size."
     ::= { nvXbillconfEntry 3 }

nvXbillconfBilltime OBJECT-TYPE 
     SYNTAX   INTEGER
     ACCESS   read-write 
     STATUS   mandatory 
     DESCRIPTION 
        "Time xbillstat records will remain open for."
     ::= { nvXbillconfEntry 4 }

--
--	xnuaset file
--

nvXnuaset OBJECT IDENTIFIER ::= { nevadaX25 6}
 
nvXnuasetMaxRec OBJECT-TYPE
      SYNTAX   INTEGER
      ACCESS   read-only
      STATUS   mandatory
      DESCRIPTION
                "total number of records allowed in database file."
      ::= {nvXnuaset 1}

nvXnuasetNumRec OBJECT-TYPE
      SYNTAX   INTEGER
      ACCESS   read-only
      STATUS   mandatory
      DESCRIPTION
                "number of records in use."
      ::= {nvXnuaset 2}
 
nvXnuasetTable OBJECT-TYPE
      SYNTAX   SEQUENCE OF NvXnuasetEntry
      ACCESS   not-accessible
      STATUS   mandatory
      DESCRIPTION
               "xnuaset file."
      ::= {nvXnuaset 3}
 
nvXnuasetEntry OBJECT-TYPE
      SYNTAX   NvXnuasetEntry
      ACCESS   not-accessible
      STATUS   mandatory
      DESCRIPTION
               "xnuaset record, indexed by record number"
      INDEX {nvXnuasetIndex}
      ::= {nvXnuasetTable 1 }
 
NvXnuasetEntry ::=
      SEQUENCE {
        nvXnuasetIndex
                INTEGER,
	nvXnuasetSetname
		DisplayString,
	nvXnuasetNua1
		DisplayString,
	nvXnuasetNua2
		DisplayString,
	nvXnuasetNua3
		DisplayString,
	nvXnuasetStatus
		INTEGER
	}

nvXnuasetIndex OBJECT-TYPE
     SYNTAX   INTEGER
     ACCESS   read-only
     STATUS   mandatory
     DESCRIPTION
        "Index of xnuaset record."
     ::= {nvXnuasetEntry 1 }

nvXnuasetSetname OBJECT-TYPE
     SYNTAX   DisplayString (SIZE (0..8))
     ACCESS   read-write
     STATUS   mandatory
     DESCRIPTION
	"Nuaset name"
     ::={ nvXnuasetEntry 2}

nvXnuasetNua1 OBJECT-TYPE
     SYNTAX   DisplayString (SIZE (0..16))
     ACCESS   read-write 
     STATUS   mandatory
     DESCRIPTION 
        "Nua1."
     ::={ nvXnuasetEntry 3}
 
nvXnuasetNua2 OBJECT-TYPE
     SYNTAX   DisplayString (SIZE (0..16))
     ACCESS   read-write 
     STATUS   mandatory
     DESCRIPTION 
        "Nua2."
     ::={ nvXnuasetEntry 4}
 
nvXnuasetNua3 OBJECT-TYPE
     SYNTAX   DisplayString (SIZE (0..16))
     ACCESS   read-write 
     STATUS   mandatory
     DESCRIPTION 
        "Nua3."
     ::={ nvXnuasetEntry 5}
 
nvXnuasetStatus OBJECT-TYPE
     SYNTAX   INTEGER {
                valid(1),
                invalid(2)
                }
     ACCESS   read-write
     STATUS   mandatory
     DESCRIPTION
           "Operation status. Add the record to the table (valid) or
           delete the record from the table (invalid)."
     ::= { nvXnuasetEntry 10 }

--
--	xbillstat file
--

nvXbillstat OBJECT IDENTIFIER ::= { nevadaX25 7 }

nvXbillstatMaxRec OBJECT-TYPE
      SYNTAX   INTEGER
      ACCESS   read-only
      STATUS   mandatory
      DESCRIPTION
                "total number of records allowed in database file."
      ::= {nvXbillstat 1}
 
nvXbillstatNumRec OBJECT-TYPE
      SYNTAX   INTEGER
      ACCESS   read-only
      STATUS   mandatory
      DESCRIPTION
                "number of records in use."
      ::= {nvXbillstat 2}
 
nvXbillstatTable OBJECT-TYPE
      SYNTAX   SEQUENCE OF NvXbillstatEntry
      ACCESS   not-accessible
      STATUS   mandatory
      DESCRIPTION
               "xbillstat file."
      ::= {nvXbillstat 3}
        
nvXbillstatEntry OBJECT-TYPE
      SYNTAX   NvXbillstatEntry
      ACCESS   not-accessible
      STATUS   mandatory
      DESCRIPTION
               "xbillstat record, indexed by record number"
      INDEX {nvXbillstatIndex}
      ::= {nvXbillstatTable 1 }
        
NvXbillstatEntry ::=
      SEQUENCE {
        nvXbillstatIndex
                INTEGER,
	nvXbillstatNodeid
		INTEGER,
	nvXbillstatDate
		DisplayString,
	nvXbillstatTime
		DisplayString,
	nvXbillstatNuaset
		DisplayString,
	nvXbillstatDatarate
		DisplayString,
	nvXbillstatTxseg
		Counter,
	nvXbillstatRxseg
		Counter,
	nvXbillstatRxcallc
		Counter,
	nvXbillstatHostclr
		Counter,
	nvXbillstatNetclr
		Counter,
	nvXbillstatTxpak
		Counter,
	nvXbillstatRxpak
		Counter,
	nvXbillstatLess5
		Counter,
	nvXbillstat5to10
		Counter,
	nvXbillstat10to15
		Counter,
	nvXbillstat15to20
		Counter,
	nvXbillstatGrtr20
		Counter,
	nvXbillstatClosed
		INTEGER
	}

nvXbillstatIndex OBJECT-TYPE
     SYNTAX   INTEGER
     ACCESS   read-only
     STATUS   mandatory
     DESCRIPTION
        "Index of xbillstat record."
     ::= { nvXbillstatEntry 1 }
 
nvXbillstatNodeid OBJECT-TYPE
     SYNTAX   INTEGER 
     ACCESS   read-only 
     STATUS   mandatory
     DESCRIPTION
	"Node Identifier"
     ::= { nvXbillstatEntry 2 }

nvXbillstatDate OBJECT-TYPE
     SYNTAX   DisplayString (SIZE (0..6))
     ACCESS   read-only 
     STATUS   mandatory 
     DESCRIPTION 
        "Date of Record Generation."
     ::= { nvXbillstatEntry 3 }

nvXbillstatTime OBJECT-TYPE 
     SYNTAX   DisplayString (SIZE (0..8))
     ACCESS   read-only  
     STATUS   mandatory  
     DESCRIPTION  
        "Time of Record Generation."
     ::= { nvXbillstatEntry 4 }

nvXbillstatNuaset OBJECT-TYPE 
     SYNTAX   DisplayString (SIZE (0..8))
     ACCESS   read-only  
     STATUS   mandatory  
     DESCRIPTION  
        "Nuaset used to generate this record."
     ::= { nvXbillstatEntry 5 }

nvXbillstatDatarate OBJECT-TYPE 
     SYNTAX   DisplayString (SIZE (0..12))
     ACCESS   read-only  
     STATUS   mandatory  
     DESCRIPTION  
        "ISDN speed"
     ::= { nvXbillstatEntry 6 }

nvXbillstatTxseg OBJECT-TYPE
     SYNTAX   Counter
     ACCESS   read-only
     STATUS   mandatory
     DESCRIPTION
        "Number of transmitted X.25 segments."
     ::= { nvXbillstatEntry 7 }

nvXbillstatRxseg OBJECT-TYPE
     SYNTAX   Counter 
     ACCESS   read-only 
     STATUS   mandatory 
     DESCRIPTION
        "Number of received X.25 segments."
     ::= { nvXbillstatEntry 8 } 
 
nvXbillstatRxcallc OBJECT-TYPE
     SYNTAX   Counter 
     ACCESS   read-only 
     STATUS   mandatory 
     DESCRIPTION
        "Number of X.25 Calls Accepted by the Host."
     ::= { nvXbillstatEntry 9 } 
 
nvXbillstatHostclr OBJECT-TYPE
     SYNTAX   Counter 
     ACCESS   read-only 
     STATUS   mandatory 
     DESCRIPTION
        "Number of X.25 Calls Cleared by the Host."
     ::= { nvXbillstatEntry 10 } 
 
nvXbillstatNetclr OBJECT-TYPE
     SYNTAX   Counter 
     ACCESS   read-only 
     STATUS   mandatory 
     DESCRIPTION
        "Number of X.25 Calls Cleared by the Network."
     ::= { nvXbillstatEntry 11 } 
 
nvXbillstatTxpak OBJECT-TYPE
     SYNTAX   Counter 
     ACCESS   read-only 
     STATUS   mandatory 
     DESCRIPTION
        "Number of Transmitted X.25 packets."
     ::= { nvXbillstatEntry 12 } 
 
nvXbillstatRxpak OBJECT-TYPE
     SYNTAX   Counter 
     ACCESS   read-only 
     STATUS   mandatory 
     DESCRIPTION
        "Number of X.25 packets received."
     ::= { nvXbillstatEntry 13 } 
 
nvXbillstatLess5 OBJECT-TYPE
     SYNTAX   Counter 
     ACCESS   read-only 
     STATUS   mandatory 
     DESCRIPTION
        "Number of ISDN calls less that 5 secs."
     ::= { nvXbillstatEntry 14 } 
 
nvXbillstat5to10 OBJECT-TYPE
     SYNTAX   Counter 
     ACCESS   read-only 
     STATUS   mandatory 
     DESCRIPTION
        "Number of ISDN calls from 5 to 10 secs."
     ::= { nvXbillstatEntry 15 } 
 
nvXbillstat10to15 OBJECT-TYPE
     SYNTAX   Counter 
     ACCESS   read-only 
     STATUS   mandatory 
     DESCRIPTION
        "Number of ISDN calls from 10 to 15 secs."
     ::= { nvXbillstatEntry 16 } 

nvXbillstat15to20 OBJECT-TYPE
     SYNTAX   Counter 
     ACCESS   read-only 
     STATUS   mandatory 
     DESCRIPTION
        "Number of ISDN calls from 15 to 20 secs."
     ::= { nvXbillstatEntry 17 } 
 
nvXbillstatGrtr20 OBJECT-TYPE
     SYNTAX   Counter 
     ACCESS   read-only 
     STATUS   mandatory 
     DESCRIPTION
        "Number of ISDN calls greater than 20 secs."
     ::= { nvXbillstatEntry 18 } 
 
nvXbillstatClosed OBJECT-TYPE
     SYNTAX   INTEGER {
		open(1),
		closed(2)
		}
     ACCESS   read-only
     STATUS   mandatory
     DESCRIPTION
	"Record open or closed."
     ::= { nvXbillstatEntry 19 } 

--
--      priconf file
--

nvPriconf OBJECT IDENTIFIER ::= {nevadaIsdn 1}

nvPriconfMaxRec OBJECT-TYPE
      SYNTAX   INTEGER
      ACCESS   read-only
      STATUS   mandatory
      DESCRIPTION
                "total number of records allowed in database file."
      ::= {nvPriconf 1}

nvPriconfNumRec OBJECT-TYPE
      SYNTAX   INTEGER
      ACCESS   read-only
      STATUS   mandatory
      DESCRIPTION
                "number of records in use."
      ::= {nvPriconf 2}

nvPriconfTable OBJECT-TYPE
      SYNTAX   SEQUENCE OF NvPriconfEntry
      ACCESS   not-accessible
      STATUS   mandatory
      DESCRIPTION
               "priconf file."
      ::= {nvPriconf 3}

nvPriconfEntry OBJECT-TYPE
      SYNTAX   NvPriconfEntry
      ACCESS   not-accessible
      STATUS   mandatory
      DESCRIPTION
               "priconf record, indexed by record number"
      INDEX {nvPriconfIndex}
      ::= {nvPriconfTable 1 }

NvPriconfEntry ::=
      SEQUENCE {
        nvPriconfIndex
                INTEGER,
        nvPriconfPriname
                INTEGER,
        nvPriconfSwitch
                INTEGER,
        nvPriconfDsltype
                INTEGER,
        nvPriconfRouting
                INTEGER,
        nvPriconfDliname
                DisplayString,
        nvPriconfRsrcpool
                DisplayString,
        nvPriconfStatus
                INTEGER,
	nvPriconfBusyout           --AF
	        INTEGER,           --AF
        nvPriconfEstlink           --AF
                INTEGER,           --AF
        nvPriconfDlirst            --AF
                INTEGER,           --AF
        nvPriconfDchrst            --AF
                INTEGER,           --AF 
	nvPriconfNfasdch          --SF 
                INTEGER,
	nvPriconfNfasif
		INTEGER,
	nvPriconfNfasgrp          --SF 
                INTEGER,
	nvPriconfTsshift          --SF 
                INTEGER,                   
	nvPriconfX25diags	--LB
		INTEGER,
	nvPriconfNumbtype
		INTEGER,
	nvPriconfNumbplan
		INTEGER,
	nvPriconfModemcap
		INTEGER,
	nvPriconfL1prot
		INTEGER,
	nvPriconfStandby
		INTEGER
        }

nvPriconfIndex OBJECT-TYPE
     SYNTAX   INTEGER
     ACCESS   read-only
     STATUS   mandatory
     DESCRIPTION
        "Index of priconf record."
     ::= {nvPriconfEntry 1 }

nvPriconfPriname OBJECT-TYPE
     SYNTAX   INTEGER {
                none(1),        -- (+1)
                pri1(2),
                pri2(3),
                pri3(4),
                pri4(5),
                pri5(6),
                pri6(7),
                pri7(8),
                pri8(9)
                }
     ACCESS   read-only
     STATUS   mandatory
     DESCRIPTION
        "PRI name."
     ::= {nvPriconfEntry 2 }

nvPriconfSwitch OBJECT-TYPE
     SYNTAX   INTEGER {
                none(1),        -- (+1)
                att4ess(17),
                att5ess(18),
                dms100(20),
		ntt(22),
                v1tr6(24),
                net5(27),
                vn3(33)
                }
     ACCESS   read-write
     STATUS   mandatory
     DESCRIPTION
        "Switch type."
     ::= {nvPriconfEntry 3 }

nvPriconfDsltype OBJECT-TYPE
     SYNTAX   INTEGER {
                switched(1)     -- (+1)
                }
     ACCESS   read-write
     STATUS   mandatory
     DESCRIPTION
        "DSL type."
     ::= {nvPriconfEntry 4 }

nvPriconfRouting OBJECT-TYPE
     SYNTAX   INTEGER {
                caladr(1),      -- use called address (+1)
                subadr(2)       -- use sub address in the packet
                }
     ACCESS   read-write
     STATUS   mandatory
     DESCRIPTION
        "Routing address."
     ::= {nvPriconfEntry 5 }

nvPriconfDliname OBJECT-TYPE
     SYNTAX   DisplayString (SIZE (0..10))
     ACCESS   read-write
     STATUS   mandatory
     DESCRIPTION
        "DLI name."
     ::= {nvPriconfEntry 6}

nvPriconfRsrcpool OBJECT-TYPE
     SYNTAX   DisplayString (SIZE (0..10))
     ACCESS   read-write
     STATUS   mandatory
     DESCRIPTION
        "B channel pool name."
     ::= {nvPriconfEntry 7}

nvPriconfStatus OBJECT-TYPE
     SYNTAX   INTEGER {
                valid(1),
                invalid(2)
                }
     ACCESS   read-write
     STATUS   mandatory
     DESCRIPTION
           "Operation status. Add the record to the table (valid) or
           delete the record from the table (invalid)."
     ::= { nvPriconfEntry 9 }

nvPriconfBusyout OBJECT-TYPE           --AF
     SYNTAX   INTEGER{		       --AF
               	 disable(1),           --AF
		 enable(2)             --AF
		 }                     --AF
     ACCESS   read-write	       --AF
     STATUS   mandatory		       --AF
     DESCRIPTION		       --AF
        "specifies whether new calls should be rejected."
     ::= {nvPriconfEntry 10}	       --AF
     
nvPriconfEstlink OBJECT-TYPE           --AF
     SYNTAX   INTEGER{		       --AF
               	 disable(1),           --AF
		 enable(2)             --AF
		 }                     --AF
     ACCESS   read-write	       --AF
     STATUS   mandatory		       --AF
     DESCRIPTION		       --AF
        "Added T1/E1 L1/L2 recovery"   --AF
     ::= {nvPriconfEntry 11}	       --AF

nvPriconfDlirst OBJECT-TYPE            --AF
     SYNTAX   INTEGER{		       --AF
               	 disable(1),           --AF
		 enable(2)             --AF
		 }                     --AF
     ACCESS   read-write	       --AF
     STATUS   mandatory		       --AF
     DESCRIPTION		       --AF
        "Added T1/E1 L1/L2 recovery"   --AF
     ::= {nvPriconfEntry 12}	       --AF

nvPriconfDchrst OBJECT-TYPE            --AF
     SYNTAX   INTEGER{		       --AF
               	 disable(1),           --AF
		 enable(2)             --AF
		 }                     --AF
     ACCESS   read-write	       --AF
     STATUS   mandatory		       --AF
     DESCRIPTION		       --AF
        "Added T1/E1 L1/L2 recovery"   --AF
     ::= {nvPriconfEntry 13}	       --AF
     
nvPriconfNfasdch  OBJECT-TYPE
     SYNTAX   INTEGER {
		none(1),     --No NFAS interface configured  
		primary(2),  --Primary NFAS interface        
		backup(3)    --Secondary NFAS interface      
                }
     ACCESS   read-write    	
     STATUS   mandatory
     DESCRIPTION 
       "NFAS type primary or backup
        1-  No NFAS interface configured 
        2-  Primary NFAS interface       
        3-  Secondary NFAS interface     
       "
     ::= {nvPriconfEntry 14}	       

nvPriconfNfasif  OBJECT-TYPE
     SYNTAX   INTEGER (0..9)
     ACCESS   read-write
     STATUS   mandatory
     DESCRIPTION
	"NFAS Interface numbers"
     ::= { nvPriconfEntry 15 }

nvPriconfNfasgrp  OBJECT-TYPE
     SYNTAX   INTEGER (0..4) 
     ACCESS   read-write    	
     STATUS   mandatory
     DESCRIPTION 
       "NFAS group numbers"  
     ::= {nvPriconfEntry 16}
     
nvPriconfTsshift OBJECT-TYPE
     SYNTAX   INTEGER {
		disable(1),
		enable(2)
                }
     ACCESS   read-write    	
     STATUS   mandatory
     DESCRIPTION 
     " Run T1 timeslot format on E1 lines"         
     ::= {nvPriconfEntry 17}

nvPriconfX25diags OBJECT-TYPE
     SYNTAX   INTEGER (0..65535)
     ACCESS   read-write
     STATUS   mandatory
     DESCRIPTION
     "String defining X.25 diagnostic lookup table"
     ::= {nvPriconfEntry 18}

nvPriconfNumbtype OBJECT-TYPE
     SYNTAX   INTEGER {
		unknown(2),
		internat(3),
		national(4),
		netspec(5),
		subscrib(6),
		abbrev(8)
		}
     ACCESS   read-write
     STATUS   mandatory
     DESCRIPTION
     "Type of Number."
     ::= {nvPriconfEntry 19}

nvPriconfNumbplan OBJECT-TYPE
     SYNTAX   INTEGER {
		unknown(2),
		isdn(3),
		data(5),
		telex(6),
		natstand(10),
		private(11)
		}
     ACCESS   read-write
     STATUS   mandatory
     DESCRIPTION
     "Numbering plan."
     ::= {nvPriconfEntry 20}

nvPriconfModemcap OBJECT-TYPE
     SYNTAX   INTEGER {
                speech(1),
                audio3k(2),
                audio7k(3)
                }
     ACCESS   read-write
     STATUS   mandatory
     DESCRIPTION
     "Speech or audio(3.1 or 7 kHz)."
     ::= {nvPriconfEntry 21}

nvPriconfL1prot OBJECT-TYPE
     SYNTAX   INTEGER {
                disable(1),
                enable(2)
                }
     ACCESS   read-write
     STATUS   mandatory
     DESCRIPTION
     "L1 protocol enabled."
     ::= {nvPriconfEntry 22}

nvPriconfStandby OBJECT-TYPE
     SYNTAX   INTEGER {
                disable(1),
                enable(2)
                }
     ACCESS   read-write
     STATUS   mandatory
     DESCRIPTION
     "standby enabled."
     ::= {nvPriconfEntry 23}

--
--      pristat file
--
nvPristat OBJECT IDENTIFIER ::= {nevadaIsdn 2}

nvPristatMaxRec OBJECT-TYPE
      SYNTAX   INTEGER
      ACCESS   read-only
      STATUS   mandatory
      DESCRIPTION
                "total number of records allowed in database file."
      ::= {nvPristat 1}

nvPristatNumRec OBJECT-TYPE
      SYNTAX   INTEGER
      ACCESS   read-only
      STATUS   mandatory
      DESCRIPTION
                "number of records in use."
      ::= {nvPristat 2}

nvPristatTable OBJECT-TYPE
      SYNTAX   SEQUENCE OF NvPristatEntry
      ACCESS   not-accessible
      STATUS   mandatory
      DESCRIPTION
               "pristat file."
      ::= {nvPristat 3}

nvPristatEntry OBJECT-TYPE
      SYNTAX   NvPristatEntry
      ACCESS   not-accessible
      STATUS   mandatory
      DESCRIPTION
               "pristat record, indexed by record number"
      INDEX {nvPristatIndex}
      ::= {nvPristatTable 1 }

NvPristatEntry ::=
      SEQUENCE {
        nvPristatIndex
                INTEGER,
        nvPristatPriname
                INTEGER,
        nvPristatStatus
                INTEGER,
        nvPristatCallrecvs
                Counter,
        nvPristatCallaceps
                Counter,
        nvPristatCallrejs
                Counter,
        nvPristatCallinrels
                Counter,
        nvPristatCalloutrels
                Counter,
        nvPristatEstreq         --AF
                Counter,	--AF
        nvPristatDlirst         --AF
                Counter,	--AF
        nvPristatDchrst         --AF
                Counter,	--AF
        nvPristatCallcur        --AF
                Counter,        --AF
        nvPristatDchanup        --AF
                Counter,        --AF
        nvPristatDtreset
                DisplayString,
	nvPristatNcurincom
                Counter,
        nvPristatNcuroutgo
                Counter,
	nvPristatNrxsetup
		Counter,
	nvPristatMaxrsetup
		Counter,
	nvPristatNrxsetupa
		Counter,
	nvPristatNtxconn
		Counter,
	nvPristatNtxbusy
		Counter,
	nvPristatNtxsetup
		Counter,
	nvPristatMaxtsetup
		Counter,
	nvPristatNtxsetupa
		Counter,
	nvPristatNrxconn
		Counter,
	nvPristatNrxbusy
		Counter,
	nvPristatNnoanswer
		Counter,
	nvPristatMaxincom
		Counter,
	nvPristatMaxoutgo
		Counter,
	nvPristatCallsent
		Counter,
	nvPristatCallconn
		Counter,
	nvPristatCallfail
		Counter
        }

nvPristatIndex OBJECT-TYPE
     SYNTAX   INTEGER
     ACCESS   read-only
     STATUS   mandatory
     DESCRIPTION
        "Index of pristat record."
     ::= {nvPristatEntry 1 }

nvPristatPriname OBJECT-TYPE
     SYNTAX   INTEGER {
                none(1),        -- (+1)
                pri1(2),
                pri2(3),
                pri3(4),
                pri4(5),
                pri5(6),
                pri6(7),
                pri7(8),
                pri8(9)
                }
     ACCESS   read-only
     STATUS   mandatory
     DESCRIPTION
        "PRI name."
     ::= {nvPristatEntry 2 }

nvPristatStatus OBJECT-TYPE
     SYNTAX   INTEGER {
                down(1),        -- interface down (+1)
                up(2)           -- interface up
                }
     ACCESS   read-only
     STATUS   mandatory
     DESCRIPTION
        "interface status."
     ::= {nvPristatEntry 3 }

nvPristatCallrecvs OBJECT-TYPE
     SYNTAX   Counter
     ACCESS   read-only
     STATUS   mandatory
     DESCRIPTION
        "number of calls received."
     ::= {nvPristatEntry 4 }

nvPristatCallaceps OBJECT-TYPE
     SYNTAX   Counter
     ACCESS   read-only
     STATUS   mandatory
     DESCRIPTION
        "number of incoming connections."
     ::= {nvPristatEntry 5 }

nvPristatCallrejs OBJECT-TYPE
     SYNTAX   Counter
     ACCESS   read-only
     STATUS   mandatory
     DESCRIPTION
        "number of incoming calls rejected."
     ::= {nvPristatEntry 6 }

nvPristatCallinrels OBJECT-TYPE
     SYNTAX   Counter
     ACCESS   read-only
     STATUS   mandatory
     DESCRIPTION
        "number of inside released connections."
     ::= {nvPristatEntry 7 }

nvPristatCalloutrels OBJECT-TYPE
     SYNTAX   Counter
     ACCESS   read-only
     STATUS   mandatory
     DESCRIPTION
        "number of outside released connections."
     ::= {nvPristatEntry 8 }

nvPristatEstreq OBJECT-TYPE                            --AF
     SYNTAX   Counter				       --AF
     ACCESS   read-only				       --AF
     STATUS   mandatory				       --AF
     DESCRIPTION				       --AF
        "Number of established requests."              --AF
     ::= {nvPristatEntry 9 }			       --AF
     
nvPristatDlirst OBJECT-TYPE                            --AF
     SYNTAX   Counter				       --AF
     ACCESS   read-only				       --AF
     STATUS   mandatory				       --AF
     DESCRIPTION				       --AF
        "Number of dli chip resets."                   --AF
     ::= {nvPristatEntry 10 }			       --AF

nvPristatDchrst OBJECT-TYPE                            --AF
     SYNTAX   Counter				       --AF
     ACCESS   read-only				       --AF
     STATUS   mandatory				       --AF
     DESCRIPTION				       --AF
        "Number of d-channel resets."                  --AF
     ::= {nvPristatEntry 11 }			       --AF

nvPristatCallcur OBJECT-TYPE                           --AF
     SYNTAX   Counter				       --AF
     ACCESS   read-only				       --AF
     STATUS   mandatory				       --AF
     DESCRIPTION				       --AF
        "Number of current calls."                     --AF
     ::= {nvPristatEntry 12 }			       --AF

nvPristatDchanup OBJECT-TYPE                           --AF
     SYNTAX   Counter				       --AF
     ACCESS   read-only				       --AF
     STATUS   mandatory				       --AF
     DESCRIPTION				       --AF
        "Number in seconds d channel comes up."        --AF
     ::= {nvPristatEntry 13 }			       --AF

nvPristatDtreset OBJECT-TYPE
     SYNTAX   DisplayString (SIZE (0..20))
     ACCESS   read-only
     STATUS   mandatory
     DESCRIPTION
        "date & time statistics last reset"
      ::= {nvPristatEntry 14 }

nvPristatNcurincom OBJECT-TYPE
     SYNTAX   Counter
     ACCESS   read-only
     STATUS   mandatory
     DESCRIPTION
        "Current Number of simulataneous incoming calls." 
     ::= {nvPristatEntry 15 }

nvPristatNcuroutgo OBJECT-TYPE
     SYNTAX   Counter 
     ACCESS   read-only
     STATUS   mandatory
     DESCRIPTION
        "Current Number of simulataneous outgoing calls." 
     ::= {nvPristatEntry 16 }

nvPristatNrxsetup OBJECT-TYPE
     SYNTAX   Counter 
     ACCESS   read-only
     STATUS   mandatory
     DESCRIPTION
        "Number of SETUP messages received."
     ::= {nvPristatEntry 17 }

nvPristatMaxrsetup OBJECT-TYPE
     SYNTAX   Counter 
     ACCESS   read-only
     STATUS   mandatory
     DESCRIPTION
        "Max number of outstanding SETUP messages for dial-in."
     ::= {nvPristatEntry 18 }

nvPristatNrxsetupa OBJECT-TYPE
     SYNTAX   Counter 
     ACCESS   read-only
     STATUS   mandatory
     DESCRIPTION
        "Number of aborted rx SETUP messages."
     ::= {nvPristatEntry 19 }

nvPristatNtxconn OBJECT-TYPE
     SYNTAX   Counter 
     ACCESS   read-only
     STATUS   mandatory
     DESCRIPTION
        "Number of CONNECT messages set for dial-in."
     ::= {nvPristatEntry 20 }

nvPristatNtxbusy OBJECT-TYPE
     SYNTAX   Counter 
     ACCESS   read-only
     STATUS   mandatory
     DESCRIPTION
        "Number of dial-in fail due to busy."
     ::= {nvPristatEntry 21 }

nvPristatNtxsetup OBJECT-TYPE
     SYNTAX   Counter 
     ACCESS   read-only
     STATUS   mandatory
     DESCRIPTION
        "Number of SEUTP messages sent for dial-out."
     ::= {nvPristatEntry 22 }

nvPristatMaxtsetup OBJECT-TYPE
     SYNTAX   Counter 
     ACCESS   read-only
     STATUS   mandatory
     DESCRIPTION
        "Max number of outstanding tx SETUP messages."
     ::= {nvPristatEntry 23 }

nvPristatNtxsetupa OBJECT-TYPE
     SYNTAX   Counter 
     ACCESS   read-only
     STATUS   mandatory
     DESCRIPTION
        "Number of aborted tx SETUP messages."
     ::= {nvPristatEntry 24 }

nvPristatNrxconn OBJECT-TYPE
     SYNTAX   Counter 
     ACCESS   read-only
     STATUS   mandatory
     DESCRIPTION
        "Number of CONNECT recieved for dial-in."
     ::= {nvPristatEntry 25 }

nvPristatNrxbusy OBJECT-TYPE
     SYNTAX   Counter 
     ACCESS   read-only
     STATUS   mandatory
     DESCRIPTION
        "Number of dial-out fails due to busy."
     ::= {nvPristatEntry 26 }

nvPristatNnoanswer OBJECT-TYPE
     SYNTAX   Counter 
     ACCESS   read-only
     STATUS   mandatory
     DESCRIPTION
        "Number of fail no answer for dialout."
     ::= {nvPristatEntry 27 }

nvPristatMaxincom OBJECT-TYPE
     SYNTAX   Counter 
     ACCESS   read-only
     STATUS   mandatory
     DESCRIPTION
        "Maximum number of simultaneous incoming calls."
     ::= {nvPristatEntry 28 }

nvPristatMaxoutgo OBJECT-TYPE
     SYNTAX   Counter 
     ACCESS   read-only
     STATUS   mandatory
     DESCRIPTION
        "Maximum number of simultaneous outgoing calls."
     ::= {nvPristatEntry 29 }

nvPristatCallsent OBJECT-TYPE 
     SYNTAX   Counter 
     ACCESS   read-only 
     STATUS   mandatory 
     DESCRIPTION
        "Number of outgoing calls sent." 
     ::= {nvPristatEntry 30 }

nvPristatCallconn OBJECT-TYPE
     SYNTAX   Counter
     ACCESS   read-only
     STATUS   mandatory
     DESCRIPTION
	"Number of outgoing calls connected."
     ::= {nvPristatEntry 31 }

nvPristatCallfail OBJECT-TYPE 
     SYNTAX   Counter 
     ACCESS   read-only 
     STATUS   mandatory 
     DESCRIPTION
        "Number of outgoing calls failed."
     ::= {nvPristatEntry 32 }


--
--      pricstat file
--
nvPricstat OBJECT IDENTIFIER ::= {nevadaIsdn 3}

nvPricstatMaxRec OBJECT-TYPE
      SYNTAX   INTEGER
      ACCESS   read-only
      STATUS   mandatory
      DESCRIPTION
                "total number of records allowed in database file."
      ::= {nvPricstat 1}

nvPricstatNumRec OBJECT-TYPE
      SYNTAX   INTEGER
      ACCESS   read-only
      STATUS   mandatory
      DESCRIPTION
                "number of records in use."
      ::= {nvPricstat 2}

nvPricstatTable OBJECT-TYPE
      SYNTAX   SEQUENCE OF NvPricstatEntry
      ACCESS   not-accessible
      STATUS   mandatory
      DESCRIPTION
               "pricstat file."
      ::= {nvPricstat 3}

nvPricstatEntry OBJECT-TYPE
      SYNTAX   NvPricstatEntry
      ACCESS   not-accessible
      STATUS   mandatory
      DESCRIPTION
               "pricstat record, indexed by record number"
      INDEX {nvPricstatIndex}
      ::= {nvPricstatTable 1 }

NvPricstatEntry ::=
      SEQUENCE {
        nvPricstatIndex
                INTEGER,
        nvPricstatSeqno
                INTEGER,
        nvPricstatCallid
                DisplayString,
        nvPricstatRate
                DisplayString,
        nvPricstatState
                INTEGER,
        nvPricstatPriname
                INTEGER,
        nvPricstatCalldir
                INTEGER,
        nvPricstatContype
                INTEGER,
        nvPricstatL1prot
                INTEGER,
        nvPricstatCallingno
                DisplayString,
        nvPricstatCalledno
                DisplayString,
        nvPricstatBchanl
                DisplayString
        }

nvPricstatIndex OBJECT-TYPE
     SYNTAX   INTEGER
     ACCESS   read-only
     STATUS   mandatory
     DESCRIPTION
        "Index of pricstat record."
     ::= {nvPricstatEntry 1}

nvPricstatSeqno OBJECT-TYPE
     SYNTAX   INTEGER
     ACCESS   read-only
     STATUS   mandatory
     DESCRIPTION
        "sequence number."
     ::= {nvPricstatEntry 2}

nvPricstatCallid OBJECT-TYPE
     SYNTAX   DisplayString (SIZE(0..10))
     ACCESS   read-only
     STATUS   mandatory
     DESCRIPTION
        "Call ID number."
     ::= {nvPricstatEntry 3}

nvPricstatRate OBJECT-TYPE
     SYNTAX   DisplayString
     ACCESS   read-only
     STATUS   mandatory
     DESCRIPTION
        "data rate used."
     ::= {nvPricstatEntry 4}

nvPricstatState OBJECT-TYPE
     SYNTAX   INTEGER {
                disc(1),        -- not connected nor ready for connection (+1)
                idle(2),        -- not connected but ready for connection
                waiting(3),     -- connecting
                active(4),      -- connected
                clearing(5)     -- disconnecting
                }
     ACCESS   read-only
     STATUS   mandatory
     DESCRIPTION
        "channel state."
     ::= {nvPricstatEntry 5}

nvPricstatPriname OBJECT-TYPE
     SYNTAX   INTEGER {
                none(1),        -- (+1)
                pri1(2),
                pri2(3),
                pri3(4),
                pri4(5),
                pri5(6),
                pri6(7),
                pri7(8),
                pri8(9)
                }
     ACCESS   read-only
     STATUS   mandatory
     DESCRIPTION
        "PRI interface name."
     ::= {nvPricstatEntry 6}

nvPricstatCalldir OBJECT-TYPE
     SYNTAX   INTEGER {
                none(1),        -- no call (+1)
                out(2),         -- outgoing call
                in(3)           -- incoming call
                }
     ACCESS   read-only
     STATUS   mandatory
     DESCRIPTION
        "call direction."
     ::= {nvPricstatEntry 7}

nvPricstatContype OBJECT-TYPE
     SYNTAX   INTEGER {
                audio(1),       -- audio connection (+1)
                data(9),        -- data connection
                video(25),      -- video connection
                noType(256)     -- no connection type (actual db value)
                }
     ACCESS   read-only
     STATUS   mandatory
     DESCRIPTION
        "connectuon type."
     ::= {nvPricstatEntry 8}

nvPricstatL1prot OBJECT-TYPE
     SYNTAX   INTEGER {
                none(1),        -- no protocol (+1)
                v110(2),        -- v1.10 protocol
 		g711-M(3),      --AF
 		g711-A(4),      --AF
 		g712(5),        --AF
 		h221(6),        --AF
 		nON-CCITT(8),   --AF
                v120(9),         -- v1.20 protocol
 		x31(10)         --AF
                }
     ACCESS   read-only
     STATUS   mandatory
     DESCRIPTION
        "layer 1 protocol."
     ::= {nvPricstatEntry 9}

nvPricstatCallingno OBJECT-TYPE
     SYNTAX   DisplayString (SIZE(0..20))
     ACCESS   read-only
     STATUS   mandatory
     DESCRIPTION
        "Calling number."
     ::= {nvPricstatEntry 10}

nvPricstatCalledno OBJECT-TYPE
     SYNTAX   DisplayString (SIZE(0..20))
     ACCESS   read-only
     STATUS   mandatory
     DESCRIPTION
        "Called number."
     ::= {nvPricstatEntry 11}

nvPricstatBchanl OBJECT-TYPE
     SYNTAX   DisplayString (SIZE(0..8))
     ACCESS   read-only
     STATUS   mandatory
     DESCRIPTION
        "B channel used."
     ::= {nvPricstatEntry 12}

--
--      pridstat file
--
nvPridstat OBJECT IDENTIFIER ::= {nevadaIsdn 4}

nvPridstatMaxRec OBJECT-TYPE
      SYNTAX   INTEGER
      ACCESS   read-only
      STATUS   mandatory
      DESCRIPTION
                "total number of records allowed in database file."
      ::= {nvPridstat 1}

nvPridstatNumRec OBJECT-TYPE
      SYNTAX   INTEGER
      ACCESS   read-only
      STATUS   mandatory
      DESCRIPTION
                "number of records in use."
      ::= {nvPridstat 2}

nvPridstatTable OBJECT-TYPE
      SYNTAX   SEQUENCE OF NvPridstatEntry
      ACCESS   not-accessible
      STATUS   mandatory
      DESCRIPTION
               "pridstat file."
      ::= {nvPridstat 3}

nvPridstatEntry OBJECT-TYPE
      SYNTAX   NvPridstatEntry
      ACCESS   not-accessible
      STATUS   mandatory
      DESCRIPTION
               "pridstat record, indexed by record number"
      INDEX {nvPridstatIndex}
      ::= {nvPridstatTable 1 }

NvPridstatEntry ::=
      SEQUENCE {
        nvPridstatIndex
                INTEGER,
        nvPridstatPriname
                INTEGER,
        nvPridstatEventno
                INTEGER,
        nvPridstatProtlayer
                INTEGER,
        nvPridstatTime
                INTEGER,
        nvPridstatDate
                INTEGER
        }

nvPridstatIndex OBJECT-TYPE
     SYNTAX   INTEGER
     ACCESS   read-only
     STATUS   mandatory
     DESCRIPTION
        "Index of pridstat record."
     ::= {nvPridstatEntry 1}

nvPridstatPriname OBJECT-TYPE
     SYNTAX   INTEGER {
                none(1),        -- (+1)
                pri1(2),
                pri2(3),
                pri3(4),
                pri4(5),
                pri5(6),
                pri6(7),
                pri7(8),
                pri8(9)
                }
     ACCESS   read-only
     STATUS   mandatory
     DESCRIPTION
        "PRI interface name."
     ::= {nvPridstatEntry 2}

nvPridstatEventno OBJECT-TYPE
     SYNTAX   INTEGER { -- from p_prihost.h Debug Cause Log
		channelMissing(114),
		outcallEstablished(115),
		noTimeslotInfoRcvd(116),
		channelNotFound(117),
		invalidEvent(118),
		unknownEvent(119),
		noChannelAvail(120),
		directoryNumMismatch(121),
		originatorNumMismatch(122),
		mandatoryInfoElemMissing(123),
		calledNumBusy(124),
		callingNumBusy(125),
		incallEstablished(126),
		dchannelConnect(127),
		channelCollision(128),
		noTimeslotAvailable(129),
		reassignTimeslots(130),
		undefinedString(255),
		undefinedEvent(253)
		}
     ACCESS   read-only
     STATUS   mandatory
     DESCRIPTION
        "event number."
     ::= {nvPridstatEntry 3}

nvPridstatProtlayer OBJECT-TYPE
     SYNTAX   INTEGER {
                lapd(1),        -- (+1)
                l3err(2),
                l3caus(3),
                l3call(4),
                ckRtr(5)
                }
     ACCESS   read-only
     STATUS   mandatory
     DESCRIPTION
        "layer where event occurred."
     ::= {nvPridstatEntry 4}

nvPridstatTime OBJECT-TYPE
     SYNTAX   INTEGER
     ACCESS   read-only
     STATUS   mandatory
     DESCRIPTION
        "time when event occurred."
     ::= {nvPridstatEntry 5}

nvPridstatDate OBJECT-TYPE
     SYNTAX   INTEGER
     ACCESS   read-only
     STATUS   mandatory
     DESCRIPTION
        "date where event occurred."
     ::= {nvPridstatEntry 6}

--
--	pricuconf file
--
nvPricuconf OBJECT IDENTIFIER	::= { nevadaIsdn 5 }

nvPricuconfMaxRec OBJECT-TYPE
      SYNTAX   INTEGER
      ACCESS   read-only
      STATUS   mandatory
      DESCRIPTION
                "total number of records allowed in database file."
      ::= {nvPricuconf 1}
 
nvPricuconfNumRec OBJECT-TYPE
      SYNTAX   INTEGER
      ACCESS   read-only
      STATUS   mandatory
      DESCRIPTION
                "number of records in use."
      ::= {nvPricuconf 2}

nvPricuconfTable OBJECT-TYPE
      SYNTAX   SEQUENCE OF NvPricuconfEntry
      ACCESS   not-accessible
      STATUS   mandatory
      DESCRIPTION
               "pricuconf file."
      ::= {nvPricuconf 3}
 
nvPricuconfEntry OBJECT-TYPE
      SYNTAX   NvPricuconfEntry
      ACCESS   not-accessible
      STATUS   mandatory
      DESCRIPTION
               "pricuconf record, indexed by record number"
      INDEX {nvPricuconfIndex}
      ::= {nvPricuconfTable 1 }
 
NvPricuconfEntry ::=
      SEQUENCE {
        nvPricuconfIndex
                INTEGER,
        nvPricuconfThresh1
                INTEGER,
        nvPricuconfThresh2
                INTEGER,
        nvPricuconfThresh3
                INTEGER,
        nvPricuconfThresh4
                INTEGER,
        nvPricuconfInterval
                INTEGER,
	nvPricuconfStatus
		INTEGER
	}

nvPricuconfIndex OBJECT-TYPE
     SYNTAX   INTEGER
     ACCESS   read-only
     STATUS   mandatory
     DESCRIPTION
        "Index of pricuconf record."
     ::= {nvPricuconfEntry 1 }

nvPricuconfThresh1 OBJECT-TYPE
     SYNTAX   INTEGER (0..30)
     ACCESS   read-write
     STATUS   mandatory
     DESCRIPTION
        "Threshold."
     ::= {nvPricuconfEntry 2 }

nvPricuconfThresh2 OBJECT-TYPE
     SYNTAX   INTEGER (31..60)
     ACCESS   read-write
     STATUS   mandatory
     DESCRIPTION
        "Threshold."
     ::= {nvPricuconfEntry 3 }

nvPricuconfThresh3 OBJECT-TYPE
     SYNTAX   INTEGER (61..90)
     ACCESS   read-write
     STATUS   mandatory
     DESCRIPTION
        "Threshold."
     ::= {nvPricuconfEntry 4 }

nvPricuconfThresh4 OBJECT-TYPE
     SYNTAX   INTEGER (91..120)
     ACCESS   read-write
     STATUS   mandatory
     DESCRIPTION
        "Threshold."
     ::= {nvPricuconfEntry 5 }

nvPricuconfInterval OBJECT-TYPE
     SYNTAX   INTEGER (5..60)
     ACCESS   read-write
     STATUS   mandatory
     DESCRIPTION
        "Time period."
     ::= {nvPricuconfEntry 6 }

nvPricuconfStatus OBJECT-TYPE
     SYNTAX   INTEGER {
                valid(1),
                invalid(2)
                }
     ACCESS   read-write
     STATUS   mandatory
     DESCRIPTION
           "Operation status. Add the record to the table (valid) or
           delete the record from the table (invalid)."
     ::= { nvPricuconfEntry 7 }

--
--      pricustat file
--
nvPricustat OBJECT IDENTIFIER   ::= { nevadaIsdn 6 }

nvPricustatMaxRec OBJECT-TYPE
      SYNTAX   INTEGER
      ACCESS   read-only
      STATUS   mandatory
      DESCRIPTION
                "total number of records allowed in database file."
      ::= {nvPricustat 1}

nvPricustatNumRec OBJECT-TYPE
      SYNTAX   INTEGER
      ACCESS   read-only
      STATUS   mandatory
      DESCRIPTION
                "number of records in use."
      ::= {nvPricustat 2}

nvPricustatTable OBJECT-TYPE
      SYNTAX   SEQUENCE OF NvPricustatEntry
      ACCESS   not-accessible
      STATUS   mandatory
      DESCRIPTION
               "pricustat file."
      ::= {nvPricustat 3}
 

nvPricustatEntry OBJECT-TYPE
      SYNTAX   NvPricustatEntry
      ACCESS   not-accessible
      STATUS   mandatory
      DESCRIPTION
               "pricustat record, indexed by record number"
      INDEX {nvPricustatIndex}
      ::= {nvPricustatTable 1 }

NvPricustatEntry ::=            
      SEQUENCE {
        nvPricustatIndex
                INTEGER,
        nvPricustatThresh1
                INTEGER,
	nvPricustatCounter1
                INTEGER,
        nvPricustatThresh2
                INTEGER,
	nvPricustatCounter2
                INTEGER,
        nvPricustatThresh3
                INTEGER,
	nvPricustatCounter3
                INTEGER,
        nvPricustatThresh4
                INTEGER,
	nvPricustatCounter4
                INTEGER,
	nvPricustatResettime
		DisplayString
	}

nvPricustatIndex OBJECT-TYPE
     SYNTAX   INTEGER
     ACCESS   read-only
     STATUS   mandatory
     DESCRIPTION
        "Index of pricustat record."
     ::= {nvPricustatEntry 1 }

nvPricustatThresh1 OBJECT-TYPE
     SYNTAX   INTEGER
     ACCESS   read-only
     STATUS   mandatory
     DESCRIPTION
        "Number of calls received."
     ::= {nvPricustatEntry 2 }

nvPricustatCounter1 OBJECT-TYPE
     SYNTAX   INTEGER
     ACCESS   read-only
     STATUS   mandatory
     DESCRIPTION
        "Number of calls received."
     ::= {nvPricustatEntry 3 }

nvPricustatThresh2 OBJECT-TYPE
     SYNTAX   INTEGER
     ACCESS   read-only
     STATUS   mandatory
     DESCRIPTION
        "Number of incoming connections."
     ::= {nvPricustatEntry 4 }

nvPricustatCounter2 OBJECT-TYPE
     SYNTAX   INTEGER
     ACCESS   read-only
     STATUS   mandatory
     DESCRIPTION
        "Number of incoming connections."
     ::= {nvPricustatEntry 5 }

nvPricustatThresh3 OBJECT-TYPE
     SYNTAX   INTEGER
     ACCESS   read-only
     STATUS   mandatory
     DESCRIPTION
        "Number of incoming calls rejected."
     ::= {nvPricustatEntry 6 }

nvPricustatCounter3 OBJECT-TYPE
     SYNTAX   INTEGER
     ACCESS   read-only
     STATUS   mandatory
     DESCRIPTION
        "Number of incoming calls rejected."
     ::= {nvPricustatEntry 7 }

nvPricustatThresh4 OBJECT-TYPE
     SYNTAX   INTEGER
     ACCESS   read-only
     STATUS   mandatory
     DESCRIPTION
        "Number of inside released connections."
     ::= {nvPricustatEntry 8 }

nvPricustatCounter4 OBJECT-TYPE
     SYNTAX   INTEGER
     ACCESS   read-only
     STATUS   mandatory
     DESCRIPTION
        "Number of inside released connections."
     ::= {nvPricustatEntry 9 }

nvPricustatResettime OBJECT-TYPE
     SYNTAX   DisplayString (SIZE(0..48))
     ACCESS   read-only
     STATUS   mandatory
     DESCRIPTION
        "Calling number."
     ::= {nvPricustatEntry 10 }
--
--   Nevada PPP files
--
nvPppstat OBJECT IDENTIFIER     ::= { nevadaPpp 1 }

nvPppstatMaxRec OBJECT-TYPE
      SYNTAX   INTEGER
      ACCESS   read-only
      STATUS   mandatory
      DESCRIPTION
                "total number of records allowed in database file."
      ::= {nvPppstat 1}

nvPppstatNumRec OBJECT-TYPE
      SYNTAX   INTEGER
      ACCESS   read-only
      STATUS   mandatory
      DESCRIPTION
                "number of records in use."
      ::= {nvPppstat 2}

nvPppstatTable OBJECT-TYPE
      SYNTAX   SEQUENCE OF NvPppstatEntry
      ACCESS   not-accessible
      STATUS   mandatory
      DESCRIPTION
               "pppstat file."
      ::= { nvPppstat 3 }

nvPppstatEntry OBJECT-TYPE
      SYNTAX   NvPppstatEntry
      ACCESS   not-accessible
      STATUS   mandatory
      DESCRIPTION
               "pppstat record."
      INDEX { nvPppstatIndex }
      ::= { nvPppstatTable 1 }

NvPppstatEntry ::=
      SEQUENCE {
      nvPppstatIndex
            INTEGER,
      nvPppstatName
            DisplayString,
      nvPppstatPppAdminS
            INTEGER,
      nvPppstatLcpOperS
            INTEGER,
      nvPppstatIpcpOperS
            INTEGER,
      nvPppstatInOctets
            Counter,
      nvPppstatInPkts
            Counter,
      nvPppstatInDiscard
            Counter,
      nvPppstatInError
            Counter,
      nvPppstatInEch
            Counter,
      nvPppstatInEchRp
            Counter,
      nvPppstatInDiscRq
            Counter,
      nvPppstatUnKnwnPr
            Counter,
      nvPppstatOutOctets
            Counter,
      nvPppstatOutPkts
            Counter,
      nvPppstatOutDiscrd
            Counter,
      nvPppstatOutErrors
            Counter,
      nvPppstatOutEch
            Counter,
      nvPppstatOutEchRp
            Counter,
      nvPppstatOutDiscRq
            Counter,
      nvPppstatCcpOperS	      --AF
            INTEGER, 	      --AF
      nvPppstatComprot        --AF
            INTEGER,          --AF 
      nvPppstatUserName	      --AF
            DisplayString,    --AF
      nvPppstatIpAddr	      --AF
            DisplayString,    --AF
      nvPppstatBundleId	      --AF
            INTEGER,	      --AF
      nvPppstatIpcp	      --AF
            INTEGER,          --AF
      nvPppstatMultilink      --AF
            INTEGER,          --AF
      nvPppstatTnnlState      --AF
            INTEGER,          --AF
      nvPppstatTnnlId         --AF
            INTEGER,          --AF
      nvPppstatCallId         --AF
            INTEGER,          --AF
      nvPppstatOutCmPcnt      --AF
            Counter,          --AF
      nvPppstatInCmPcnt       --AF
            Counter,          --AF
      nvPppstatOutExpnds      --AF
            Counter,          --AF
      nvPppstatDtreset
            DisplayString,
      nvPppstatRealm
	    DisplayString
               }

nvPppstatIndex OBJECT-TYPE
     SYNTAX   INTEGER
     ACCESS   read-only
     STATUS   mandatory
     DESCRIPTION
        "Index of pppstat record"
      ::= { nvPppstatEntry 1 }

nvPppstatName OBJECT-TYPE
     SYNTAX   DisplayString (SIZE (0..5))
     ACCESS   read-only
     STATUS   mandatory
     DESCRIPTION
"statistics Name (name)
statistics name and number (ie,'ps1')
"
     ::= { nvPppstatEntry 2 }

nvPppstatPppAdminS OBJECT-TYPE
     SYNTAX   INTEGER {
                down(1),     -- protocol status is down (+1)
                up(2)      -- protocol status is up
                }
     ACCESS   read-only
     STATUS   mandatory
     DESCRIPTION
"ppp admin status (pppAdminS)
lcp link Admin Status down/up.
"
     ::= { nvPppstatEntry 3 }

nvPppstatLcpOperS OBJECT-TYPE
     SYNTAX   INTEGER {
                down(1),     -- protocol status is down (+1)
                up(2)      -- protocol status is up
                }
     ACCESS   read-only
     STATUS   mandatory
     DESCRIPTION
"lcp operation status (lcpOperS)
lcp link Admin Status down/up.
"
     ::= { nvPppstatEntry 4 } 

nvPppstatIpcpOperS OBJECT-TYPE
     SYNTAX   INTEGER {
                down(1),     -- protocol status is down (+1)
                up(2)      -- protocol status is up
                }
     ACCESS   read-only
     STATUS   mandatory
     DESCRIPTION
"ipcp operation status (ipcpOperS)
ipcp link status down/up.
"
     ::= { nvPppstatEntry 5 }

nvPppstatInOctets OBJECT-TYPE
     SYNTAX   Counter
     ACCESS   read-only
     STATUS   mandatory
     DESCRIPTION
"Octets received (InOctets)
The number of good data bytes received
Statistic is zeroed at startup time."
     ::= { nvPppstatEntry 6 }
	  
nvPppstatInPkts OBJECT-TYPE
     SYNTAX   Counter
     ACCESS   read-only
     STATUS   mandatory
     DESCRIPTION
"good packets received (InPkts)
The number of good received frames
Statistic is zeroed at startup time."
     ::= { nvPppstatEntry 7 }

nvPppstatInDiscard OBJECT-TYPE
     SYNTAX   Counter
     ACCESS   read-only
     STATUS   mandatory
     DESCRIPTION
"discarded good packets (InDiscard)
The total number of good frames dicarded due to lack of buffers
Statistic is zeroed at startup time."
     ::= { nvPppstatEntry 8 }

nvPppstatInError OBJECT-TYPE
     SYNTAX   Counter
     ACCESS   read-only
     STATUS   mandatory
     DESCRIPTION
"Bad packets received (InError)
The total number of frames received due to crc,format etc.
Statistic is zeroed at startup time."
     ::= { nvPppstatEntry 9 }

nvPppstatInEch OBJECT-TYPE
     SYNTAX   Counter
     ACCESS   read-only
     STATUS   mandatory
     DESCRIPTION
"received echo requests (InEch)
The number of echo request packets recieved.
Statistic is zeroed at startup time."
     ::= { nvPppstatEntry 10 }

nvPppstatInEchRp OBJECT-TYPE
     SYNTAX   Counter
     ACCESS   read-only
     STATUS   mandatory
     DESCRIPTION
"echo reply received (InEchRp)
The num of packets Rxed due to the echo-req sent (software loopback)
Statistic is zeroed at startup time."
     ::= { nvPppstatEntry 11 }

nvPppstatInDiscRq OBJECT-TYPE
     SYNTAX   Counter
     ACCESS   read-only
     STATUS   mandatory
     DESCRIPTION
"discard requests Rxed (InDiscRq)
The number of discard request packets received.
Statistic is zeroed at startup time."
     ::= { nvPppstatEntry 12 }

nvPppstatUnKnwnPr OBJECT-TYPE
     SYNTAX   Counter
     ACCESS   read-only
     STATUS   mandatory
     DESCRIPTION
"rxed Unknown protocol (UnKnwnPr)
The number of link quality reports received on this PPP link
Statistic is zeroed at startup time."
     ::= { nvPppstatEntry 13 }

nvPppstatOutOctets OBJECT-TYPE
     SYNTAX   Counter
     ACCESS   read-only
     STATUS   mandatory
     DESCRIPTION
"Octets transmitted (OutOctets)
The number of bytes transmitted on the ppp link.
Statistic is zeroed at startup time."
     ::= { nvPppstatEntry 14 }

nvPppstatOutPkts OBJECT-TYPE
     SYNTAX   Counter
     ACCESS   read-only
     STATUS   mandatory
     DESCRIPTION
"Packets transmitted (OutPkts)
The number of pakets transmitted on the PPP link.
Statistic is zeroed at startup time."
     ::= { nvPppstatEntry 15 }

nvPppstatOutDiscrd OBJECT-TYPE
     SYNTAX   Counter
     ACCESS   read-only
     STATUS   mandatory
     DESCRIPTION
"output errors (OutDiscrd)
The number of outbound pkts droped due to lack of buffers.
Statistic is zeroed at startup time."
     ::= { nvPppstatEntry 16 }

nvPppstatOutErrors OBJECT-TYPE
     SYNTAX   Counter
     ACCESS   read-only
     STATUS   mandatory
     DESCRIPTION
"output errors (OutErrors)
The number of outbound pkts could not be txed due to errors.
Statistic is zeroed at startup time."
     ::= { nvPppstatEntry 17 }

nvPppstatOutEch OBJECT-TYPE
     SYNTAX   Counter
     ACCESS   read-only
     STATUS   mandatory
     DESCRIPTION
"echo request pkts transmitted (OutEch)
The number of lcp echo request packets transmitted
Statistic is zeroed at startup time."
     ::= { nvPppstatEntry 18 }

nvPppstatOutEchRp OBJECT-TYPE
     SYNTAX   Counter
     ACCESS   read-only
     STATUS   mandatory
     DESCRIPTION
"echo reply transmitted (OutEchRp)
The num of echo reply packets Txed due to the echo-req
Statistic is zeroed at startup time."
     ::= { nvPppstatEntry 19 }

nvPppstatOutDiscRq OBJECT-TYPE
     SYNTAX   Counter
     ACCESS   read-only
     STATUS   mandatory
     DESCRIPTION
"discard requests Txed (OutDiscRq)
The number of discard request packets received.
Statistic is zeroed at startup time."
     ::= { nvPppstatEntry 20 }

nvPppstatUserName OBJECT-TYPE
     SYNTAX   DisplayString (SIZE (0..64))
     ACCESS   read-only
     STATUS   mandatory
     DESCRIPTION
"authenticated username of remote user (username)."
     ::= { nvPppstatEntry 21 }

nvPppstatIpAddr OBJECT-TYPE
     SYNTAX   DisplayString (SIZE (0..16))
     ACCESS   read-only
     STATUS   mandatory
     DESCRIPTION
"IP address in use on this PPP link (ipaddr)."
     ::= { nvPppstatEntry 22 }

nvPppstatBundleId OBJECT-TYPE
     SYNTAX   INTEGER
     ACCESS   read-only
     STATUS   mandatory
     DESCRIPTION
"Bundle identifier (mpstat record id) of multilink PPP
bundle in which this link is being used if nvPppstatMultilink is
yes (bundleid)."
     ::= { nvPppstatEntry 23 }

nvPppstatIpcp OBJECT-TYPE
     SYNTAX   INTEGER
     ACCESS   read-only
     STATUS   mandatory
     DESCRIPTION
"ipcp record number used for this link."
     ::= { nvPppstatEntry 24 }

nvPppstatMultilink OBJECT-TYPE
     SYNTAX INTEGER {
         no(1), -- not used in a multilink bundle
         yes(2) -- used in a multilink bundle
	 }
     ACCESS   read-only
     STATUS   mandatory
     DESCRIPTION
"Set to yes if this LCP is in use in a multilink bundle."
     ::= { nvPppstatEntry 25 }

nvPppstatCcpOperS OBJECT-TYPE       --AF 
     SYNTAX INTEGER {	            --AF
         down(1),                   --AF (+1) protocol status is down
         up(2)                      --AF      protocol status is up
	 }		            --AF
     ACCESS   read-only		    --AF
     STATUS   mandatory		    --AF
     DESCRIPTION		    --AF
"ccp Operation status."		    --AF
     ::= { nvPppstatEntry 26 }	    --AF
     
nvPppstatComprot OBJECT-TYPE        --AF
     SYNTAX   INTEGER {		    --AF
            none(1),                --AF (+1) no compession
            stacopt4(2),            --AF stac LZS enhanced mode
	    stacopt3(3),            --AF stac LZS sequence numbers
	    mppc(4)                 --AF Microsoft point to point compression 
	    }			    --AF
     ACCESS   read-write	    --AF
     STATUS   mandatory		    --AF
     DESCRIPTION		    --AF
"Compression protocol in use."	    --AF
     ::= { nvPppstatEntry 27 }	    --AF

nvPppstatTnnlState OBJECT-TYPE      --AF 
     SYNTAX INTEGER {	            --AF
         none(1),                   --AF (+1) session is not being tunneled
         l2tpwt(2),                 --AF      waiting for an l2tp session to be established
         l2tpcn(3)                  --AF      l2tp session has been established  	 
	 }		            --AF
     ACCESS   read-only		    --AF
     STATUS   mandatory		    --AF
     DESCRIPTION		    --AF
"State of a tunneled session."	    --AF
     ::= { nvPppstatEntry 28 }	    --AF

nvPppstatTnnlId OBJECT-TYPE         --AF 
     SYNTAX INTEGER                 --AF
     ACCESS   read-only             --AF
     STATUS   mandatory	            --AF
     DESCRIPTION	            --AF
"Tunnel ID assosiated with the tunneled session."	    --AF
     ::= { nvPppstatEntry 29 }      --AF

nvPppstatCallId OBJECT-TYPE        --AF 
     SYNTAX INTEGER                 --AF
     ACCESS   read-only             --AF
     STATUS   mandatory	            --AF
     DESCRIPTION	            --AF
"Call ID assosiated with the tunneled session."	    --AF
     ::= { nvPppstatEntry 30 }      --AF

nvPppstatOutCmPcnt OBJECT-TYPE      --AF
     SYNTAX   Counter		    --AF
     ACCESS   read-only		    --AF
     STATUS   mandatory		    --AF
     DESCRIPTION		    --AF
"Percent compression on tx."        --AF
     ::= { nvPppstatEntry 31 }	    --AF

nvPppstatInCmPcnt OBJECT-TYPE       --AF
     SYNTAX   Counter		    --AF
     ACCESS   read-only		    --AF
     STATUS   mandatory		    --AF
     DESCRIPTION		    --AF
"Percent compression on rx."        --AF
     ::= { nvPppstatEntry 32 }	    --AF

nvPppstatOutExpnds OBJECT-TYPE      --AF
     SYNTAX   Counter		    --AF
     ACCESS   read-only		    --AF
     STATUS   mandatory		    --AF
     DESCRIPTION		    --AF
"Number of packets expanded by compression."        --AF
     ::= { nvPppstatEntry 33 }	    --AF

nvPppstatDtreset OBJECT-TYPE
     SYNTAX   DisplayString (SIZE (0..20))
     ACCESS   read-only
     STATUS   mandatory
     DESCRIPTION
        "date & time statistics last reset"
      ::= { nvPppstatEntry 34 }

nvPppstatRealm OBJECT-TYPE
     SYNTAX   DisplayString (SIZE (0..64))
     ACCESS   read-only
     STATUS   mandatory
     DESCRIPTION
        "First 64 characters of the realm if parsing NAI."
      ::= { nvPppstatEntry 35 }

--
--      lcpconf file
--
nvLcpconf OBJECT IDENTIFIER ::= { nevadaPpp 2 }

nvLcpconfMaxRec OBJECT-TYPE
      SYNTAX   INTEGER
      ACCESS   read-only
      STATUS   mandatory
      DESCRIPTION
                "total number of records allowed in database file."
      ::= {nvLcpconf 1}

nvLcpconfNumRec OBJECT-TYPE
      SYNTAX   INTEGER
      ACCESS   read-only
      STATUS   mandatory
      DESCRIPTION
                "number of records in use."
      ::= {nvLcpconf 2}

nvLcpconfTable OBJECT-TYPE
      SYNTAX   SEQUENCE OF NvLcpconfEntry
      ACCESS   not-accessible
      STATUS   mandatory
      DESCRIPTION
               "lcpconf file."
      ::= { nvLcpconf 3 }

nvLcpconfEntry OBJECT-TYPE
      SYNTAX   NvLcpconfEntry
      ACCESS   not-accessible
      STATUS   mandatory
      DESCRIPTION
               "lcpconf record."
      INDEX { nvLcpconfIndex }
      ::= { nvLcpconfTable 1 }

NvLcpconfEntry ::=
      SEQUENCE {
      nvLcpconfIndex
            INTEGER,
      nvLcpconfPort
            DisplayString,
      nvLcpconfRsrcpool
            DisplayString,
      nvLcpconfItiudata
            DisplayString,
      nvLcpconfAccm
            DisplayString,
      nvLcpconfMode
            INTEGER,
      nvLcpconfPfc
            INTEGER,
      nvLcpconfAcfc
            INTEGER,
      nvLcpconfRestartim
            INTEGER,
      nvLcpconfMaxterm
            INTEGER,
      nvLcpconfMaxcfg
            INTEGER,
      nvLcpconfMaxnak
            INTEGER,
      nvLcpconfInactivty
            INTEGER,
      nvLcpconfAuth
            INTEGER,
      nvLcpconfSecurtmr
            INTEGER,
      nvLcpconfChalint
            INTEGER,
      nvLcpconfMultilink
            INTEGER,
      nvLcpconfpppTrapEn
            INTEGER,
      nvLcpconfComprot1	    --AF
            INTEGER, 	    --AF
      nvLcpconfComprot2	    --AF
            INTEGER, 	    --AF
      nvLcpconfUsrdelim	    --LB
	    DisplayString,  --LB
      nvLcpconfNaifwd
	    INTEGER,
      nvLcpconfTxmaxbuf    --SF
            INTEGER,       --SF
      nvLcpconfStatus
            INTEGER
                }

nvLcpconfIndex OBJECT-TYPE
     SYNTAX   INTEGER
     ACCESS   read-only
     STATUS   mandatory
     DESCRIPTION
        "Index of lcpconf record"
      ::= { nvLcpconfEntry 1 }

nvLcpconfPort OBJECT-TYPE
     SYNTAX   DisplayString (SIZE (0..11))
     ACCESS   read-write
     STATUS   mandatory
     DESCRIPTION
"Link Name (port).  "
     ::= { nvLcpconfEntry 2 }

nvLcpconfRsrcpool OBJECT-TYPE
     SYNTAX   DisplayString (SIZE (0..11))
     ACCESS   read-write
     STATUS   mandatory
     DESCRIPTION
"Resource Poolname.  "
     ::= { nvLcpconfEntry 3 }

nvLcpconfItiudata OBJECT-TYPE
     SYNTAX   DisplayString (SIZE (0..20))
     ACCESS   read-write
     STATUS   mandatory
     DESCRIPTION
"iti user data (itiudata)
"
     ::= { nvLcpconfEntry 4 }

nvLcpconfAccm OBJECT-TYPE
     SYNTAX   DisplayString (SIZE (0..8))
     ACCESS   read-write
     STATUS   mandatory
     DESCRIPTION
"Async. Control Char Map (accm)
"
     ::= { nvLcpconfEntry 5 }

nvLcpconfMode OBJECT-TYPE
     SYNTAX   INTEGER {
                sync(1),      -- syncchronous (+1)
                async(2),     -- asynchronous
                tpp(3),
                x25(4)
                }
     ACCESS   read-write
     STATUS   mandatory
     DESCRIPTION
"interface type (mode)
Default value is psync (0+1)."
     ::= { nvLcpconfEntry 6 }

nvLcpconfPfc OBJECT-TYPE
     SYNTAX   INTEGER {
                no(1),      -- no
                yes(2)     -- yes (+1)
                }
     ACCESS   read-write
     STATUS   mandatory
     DESCRIPTION
"protocol field compression (pfc)
Default value is yes (1+1)."
     ::= { nvLcpconfEntry 7 }

nvLcpconfAcfc OBJECT-TYPE
     SYNTAX   INTEGER {
                no(1),      -- no
                yes(2)     -- yes (+1)
                }
     ACCESS   read-write
     STATUS   mandatory
     DESCRIPTION
"addr. ctrl fields comp. (acfc)
Default value is yes (1+1)."
     ::= { nvLcpconfEntry 8 }

nvLcpconfRestartim OBJECT-TYPE
     SYNTAX   INTEGER (0..255)
     ACCESS   read-write
     STATUS   mandatory
     DESCRIPTION
"lcp reqests restart (restartim)
Default value is 3."
     ::= { nvLcpconfEntry 9 }

nvLcpconfMaxterm OBJECT-TYPE
     SYNTAX   INTEGER (0..255)
     ACCESS   read-write
     STATUS   mandatory
     DESCRIPTION
"terminate request count (maxterm)
Default value is 2."
     ::= { nvLcpconfEntry 10 }

nvLcpconfMaxcfg OBJECT-TYPE
     SYNTAX   INTEGER (0..255)
     ACCESS   read-write
     STATUS   mandatory
     DESCRIPTION
"configure request count (maxcfg)
Default value is 10."
     ::= { nvLcpconfEntry 11 }

nvLcpconfMaxnak OBJECT-TYPE
     SYNTAX   INTEGER (0..255)
     ACCESS   read-write
     STATUS   mandatory
     DESCRIPTION
"config-Nak send (maxnak)
Default value is 10."
     ::= { nvLcpconfEntry 12 }

nvLcpconfInactivty OBJECT-TYPE
     SYNTAX   INTEGER (0..255)
     ACCESS   read-write
     STATUS   mandatory
     DESCRIPTION
"nbus call inact timer (inactivty)
Default value is 0."
     ::= { nvLcpconfEntry 13 }

nvLcpconfAuth OBJECT-TYPE
     SYNTAX   INTEGER {
                none(1),        -- (+1)
                pap(2),
                chap(3),
                either(4),
		telno(5),
		prxypap(6), 
		prxychap(7),
		prxyeith(8)
                }
     ACCESS   read-write
     STATUS   mandatory
     DESCRIPTION
"ppp authentication.
        none,      1,    Disable authentication
	pap,       2,    Password Authentication Protocol
	chap,      3,    Challenge Handshake Authentication Protocol
	either,    4,    First use CHAP, then try PAP
	telno,     5,    Telephone Number Authentication
	prxypap,   6,    Proxy PAP partial authentication
	prxychap,  7,    Proxy CHAP partial authentication
	prxyeith,  8    Proxy PAP or CHAP partial authentication 
"
     ::= { nvLcpconfEntry 14 }

nvLcpconfSecurtmr OBJECT-TYPE
     SYNTAX   INTEGER (0..255)
     ACCESS   read-write
     STATUS   mandatory
     DESCRIPTION
"security timer."
     ::= { nvLcpconfEntry 15 }

nvLcpconfChalint OBJECT-TYPE
     SYNTAX   INTEGER (0..255)
     ACCESS   read-write
     STATUS   mandatory
     DESCRIPTION
"rechallenge interval."
     ::= { nvLcpconfEntry 16 }

nvLcpconfMultilink OBJECT-TYPE
     SYNTAX   INTEGER {
            no(1), -- not available for use in a multilink bundle
            yes(2) -- may be used in a multilink bundle
	    }
     ACCESS   read-write
     STATUS   mandatory
     DESCRIPTION
"If yes this LCP is available for use in a multilink bundle."
     ::= { nvLcpconfEntry 17 }

nvLcpconfpppTrapEn OBJECT-TYPE
     SYNTAX   INTEGER {
            no(1), -- traps not sent for PPP events
            yes(2) -- traps sent for PPP events
	    }
     ACCESS   read-write
     STATUS   mandatory
     DESCRIPTION
"If yes then trap generation is enabled for LCP state changes and
other PPP events."
     ::= { nvLcpconfEntry 18 }

nvLcpconfComprot1 OBJECT-TYPE   --AF
     SYNTAX   INTEGER {		--AF
            none(1),            --AF (+1) no compession
            stacopt4(2),        --AF stac LZS enhanced mode
	    stacopt3(3),        --AF stac LZS sequence numbers
	    mppc(4)             --AF Microsoft point to point compression 
	    }			--AF
     ACCESS   read-write	--AF
     STATUS   mandatory		--AF
     DESCRIPTION		--AF
"First choice for compression."	--AF
     ::= { nvLcpconfEntry 19 }	--AF

nvLcpconfComprot2 OBJECT-TYPE	--AF
     SYNTAX   INTEGER {		--AF
            none(1),            --AF (+1) no compession
            stacopt4(2),        --AF stac LZS enhanced mode
	    stacopt3(3),        --AF stac LZS sequence numbers
	    mppc(4)             --AF Microsoft point to point compression 
	    }			--AF
     ACCESS   read-write	--AF
     STATUS   mandatory		--AF
     DESCRIPTION		--AF
"Second choice for compression."--AF
     ::= { nvLcpconfEntry 20 }	--AF

nvLcpconfUsrdelim OBJECT-TYPE
     SYNTAX   DisplayString (SIZE (0..4))
     ACCESS   read-write
     STATUS   mandatory
     DESCRIPTION
	"Delimiter for NAI parsing"
     ::= { nvLcpconfEntry 21 }

nvLcpconfNaifwd OBJECT-TYPE
     SYNTAX   INTEGER {
		useronly(1),
		fullnai(2)
		}
     ACCESS   read-write
     STATUS   mandatory
     DESCRIPTION
	"Forward full NAI or only username"
     ::= { nvLcpconfEntry 22 }
     
nvLcpconfTxmaxbuf   OBJECT-TYPE
     SYNTAX   INTEGER(50..500)
     ACCESS   read-write
     STATUS   mandatory
     DESCRIPTION
           "transmit buffering"
     ::= { nvLcpconfEntry 23 }

nvLcpconfStatus OBJECT-TYPE
     SYNTAX   INTEGER {
                valid(1),
                invalid(2)
                }
     ACCESS   read-write
     STATUS   mandatory
     DESCRIPTION
           "Operation status. Add the record to the table (valid) or
           delete the record from the table (invalid)."
     ::= { nvLcpconfEntry 26 }



--
--      MPCONF
--
nvMpconf OBJECT IDENTIFIER     ::= { nevadaPpp 3 }

nvMpconfMaxRec OBJECT-TYPE
      SYNTAX   INTEGER
      ACCESS   read-only
      STATUS   mandatory
      DESCRIPTION
                "total number of records allowed in database file."
      ::= {nvMpconf 1}

nvMpconfNumRec OBJECT-TYPE
      SYNTAX   INTEGER
      ACCESS   read-only
      STATUS   mandatory
      DESCRIPTION
                "number of records in use."
      ::= {nvMpconf 2}

nvMpconfTable OBJECT-TYPE
      SYNTAX   SEQUENCE OF NvMpconfEntry
      ACCESS   not-accessible
      STATUS   mandatory
      DESCRIPTION
               "mpconf file."
      ::= { nvMpconf 3 }

nvMpconfEntry OBJECT-TYPE
      SYNTAX   NvMpconfEntry
      ACCESS   not-accessible
      STATUS   mandatory
      DESCRIPTION
               "mpconf record."
      INDEX { nvMpconfIndex }
      ::= { nvMpconfTable 1 }

NvMpconfEntry ::=
      SEQUENCE {
      nvMpconfIndex
            INTEGER,
      nvMpconfProfile
            DisplayString,
      nvMpconfAdminS
            INTEGER,
      nvMpconfTrapEnable
            INTEGER,
      nvMpconfLnkLimit
            INTEGER,
      nvMpconfTxFrag
            INTEGER,
      nvMpconfTxFragMin
            INTEGER,
      nvMpconfTxShortSeq
            INTEGER,
      nvMpconfComprot1		 --AF
            INTEGER, 		 --AF
      nvMpconfComprot2		 --AF
            INTEGER, 		 --AF
      nvMpconfComptype           --AF
            INTEGER,             --AF  
      nvMpconfStatus
            INTEGER
        }

nvMpconfIndex OBJECT-TYPE
     SYNTAX   INTEGER
     ACCESS   read-only
     STATUS   mandatory
     DESCRIPTION
      "Index of Mpconf record."
        ::= { nvMpconfEntry 1 }

nvMpconfProfile OBJECT-TYPE
     SYNTAX   DisplayString (SIZE (0..20))
     ACCESS   read-write
     STATUS   mandatory
     DESCRIPTION
      "Must match lcp record itiudata (async ppp) or rsrcpool (sync ppp) field for
       multilink to operate on the lcp."
     ::= { nvMpconfEntry 2 }


nvMpconfAdminS OBJECT-TYPE
     SYNTAX   INTEGER {
                      enable(1),      -- +1 enable multilink, default
                      disable(2)      -- +1 disable multilink
                      }
     ACCESS   read-write
     STATUS   mandatory
     DESCRIPTION
                "If set to enable no multilink sessions can be started
                 from LCP records which match the nvMpconfProfile of this record."
     ::= { nvMpconfEntry 3 }

nvMpconfTrapEnable OBJECT-TYPE
     SYNTAX   INTEGER {
                no(1),      -- +1 disable multilink traps, default
                yes(2)      -- +1 enable multilink traps
                }
     ACCESS   read-write
     STATUS   mandatory
     DESCRIPTION
        "If set to yes Nevada enterprise traps will be generated for
        certain events occuring relative to multilink bundles.  For example,
        when a new link joins a multilink bundle.  No traps for multilink
        are generated if set to no."
     ::= { nvMpconfEntry 4 }

nvMpconfLnkLimit OBJECT-TYPE
     SYNTAX   INTEGER (2..16)
     ACCESS   read-write
     STATUS   mandatory
     DESCRIPTION
         "The maximum number of links permitted in multilink bundles
         created from this mpconf record."
     ::= { nvMpconfEntry 5 }

nvMpconfTxFrag OBJECT-TYPE
     SYNTAX   INTEGER {
                        no(1), -- +1 no fragmentation
                        yes(2) -- +1 fragment, default
                  }
     ACCESS   read-write
     STATUS   mandatory
     DESCRIPTION
         "When set to yes PPP datagrams larger than nvMpconfTxFragMin bytes
         will be fragmented before transmission on the links in the bundle."
     ::= { nvMpconfEntry 6 }

nvMpconfTxFragMin OBJECT-TYPE
     SYNTAX   INTEGER (256..1500)
     ACCESS   read-write
     STATUS   mandatory
     DESCRIPTION
          "PPP datagrams smaller than mvMpconfTxFragMin bytes will not be fragmented
           before transmission regardless of the setting of nvMpconfTxFrag."
     ::= { nvMpconfEntry 7 }

nvMpconfTxShortSeq OBJECT-TYPE
     SYNTAX   INTEGER {
               no(1), -- +1 attempt to negotiate short sequence numbers
               yes(2) -- +1 do not allow negotiation of short sequence numbers, default
            }
     ACCESS   read-write
     STATUS   mandatory
     DESCRIPTION
          "When set to yes the Nevada will attempt to negotiate the short sequence
           number option on multilink bundles created from this record.  When
           set to no the Nevada will reject attempts to negotiate short sequence
           numbers."
     ::= { nvMpconfEntry 8 }

nvMpconfComprot1 OBJECT-TYPE   --AF
     SYNTAX   INTEGER {		--AF
            none(1),            --AF (+1) no compession
            stacopt4(2),        --AF stac LZS enhanced mode
	    stacopt3(3),        --AF stac LZS sequence numbers
	    mppc(4),            --AF Microsoft point to point compression 
            stacopt0(5),        --No history, no sequence Number
            any(6)              --any supported protocol will do
	    }			--AF
     ACCESS   read-write	--AF
     STATUS   mandatory		--AF
     DESCRIPTION		--AF
"First choice for compression."	--AF
     ::= { nvMpconfEntry 9 }	--AF

nvMpconfComprot2 OBJECT-TYPE	--AF
     SYNTAX   INTEGER {		--AF
            none(1),            --AF (+1) no compession
            stacopt4(2),        --AF stac LZS enhanced mode
	    stacopt3(3),        --AF stac LZS sequence numbers
	    mppc(4),            --AF Microsoft point to point compression 
            stacopt0(5),        -- No history, no sequence number
            any(6)              -- any supported protocol will do
	    }			--AF
     ACCESS   read-write	--AF
     STATUS   mandatory		--AF
     DESCRIPTION		--AF
"Second choice for compression."--AF
     ::= { nvMpconfEntry 10 }	--AF

nvMpconfComptype OBJECT-TYPE	--AF
     SYNTAX   INTEGER {		--AF
            bundle(1),          --AF (+1) use multilink bundle compression
            lnkbylnk(2)         --AF stac use link by link compression
	    }			--AF
     ACCESS   read-write	--AF
     STATUS   mandatory		--AF
     DESCRIPTION		--AF
"Second choice for compression."--AF
     ::= { nvMpconfEntry 11 }	--AF

nvMpconfStatus OBJECT-TYPE
     SYNTAX   INTEGER {
                valid(1),
                invalid(2)
                }
     ACCESS   read-write
     STATUS   mandatory
     DESCRIPTION
           "Operation status. Add the record to the table (valid) or
           delete the record from the table (invalid)."
     ::= { nvMpconfEntry 24 }

--
--   MPSTAT
--


nvMpstatPart1 OBJECT IDENTIFIER     ::= { nevadaPpp 4 }

nvMpstatPart1MaxRec OBJECT-TYPE
      SYNTAX   INTEGER
      ACCESS   read-only
      STATUS   mandatory
      DESCRIPTION
                "total number of records allowed in database file."
      ::= {nvMpstatPart1 1}

nvMpstatPart1NumRec OBJECT-TYPE
      SYNTAX   INTEGER
      ACCESS   read-only
      STATUS   mandatory
      DESCRIPTION
                "number of records in use."
      ::= {nvMpstatPart1 2}

nvMpstatPart1Table OBJECT-TYPE
      SYNTAX   SEQUENCE OF NvMpstatPart1Entry
      ACCESS   not-accessible
      STATUS   mandatory
      DESCRIPTION
               "mpstatPart1 file."
      ::= { nvMpstatPart1 3 }

nvMpstatPart1Entry OBJECT-TYPE
      SYNTAX   NvMpstatPart1Entry
      ACCESS   not-accessible
      STATUS   mandatory
      DESCRIPTION
               "mpstatPart1 record."
      INDEX { nvMpstatPart1Index }
      ::= { nvMpstatPart1Table 1 }

NvMpstatPart1Entry ::=
      SEQUENCE {
      nvMpstatPart1Index
           INTEGER,
      nvMpstatPart1UserName
           DisplayString,
      nvMpstatPart1IpcpOperS
           INTEGER,
      nvMpstatPart1Ipcp
           INTEGER,
      nvMpstatPart1IpAddress
           DisplayString,
      nvMpstatPart1Profile
           DisplayString,
     nvMpstatPart1RmtClass
          INTEGER,
     nvMpstatPart1RmtDisc
          DisplayString,
     nvMpstatPart1LocClass
          INTEGER,
     nvMpstatPart1LocDisc
          DisplayString,
     nvMpstatPart1RmtMRRU
          INTEGER,
     nvMpstatPart1LocMRRU
          INTEGER,
     nvMpstatPart1RmtSeqS
          INTEGER,
     nvMpstatPart1LocSeqS
          INTEGER,
     nvMpstatPart1Link1
          DisplayString,
      nvMpstatPart1Link2
            DisplayString,
      nvMpstatPart1Link3
            DisplayString,
      nvMpstatPart1Link4
            DisplayString,
      nvMpstatPart1Link5
            DisplayString,
      nvMpstatPart1Link6
            DisplayString,
      nvMpstatPart1Link7
            DisplayString,
      nvMpstatPart1Link8
            DisplayString,
      nvMpstatPart1Link9
            DisplayString,
      nvMpstatPart1Link10
            DisplayString,
      nvMpstatPart1Link11
            DisplayString,
      nvMpstatPart1Link12
            DisplayString,
      nvMpstatPart1Link13
            DisplayString,
      nvMpstatPart1Link14
            DisplayString,
      nvMpstatPart1Link15
            DisplayString,
      nvMpstatPart1Link16
            DisplayString
      }

nvMpstatPart1Index OBJECT-TYPE
     SYNTAX   INTEGER
     ACCESS   read-only
     STATUS   mandatory
     DESCRIPTION
"Index of MpstatPart1 record"
      ::= { nvMpstatPart1Entry 1 }

nvMpstatPart1UserName OBJECT-TYPE
     SYNTAX   DisplayString (SIZE (0..64))
     ACCESS   read-only
     STATUS   mandatory
     DESCRIPTION
"Authenticated name of remote peer."
     ::= { nvMpstatPart1Entry 2 }

nvMpstatPart1IpcpOperS OBJECT-TYPE
     SYNTAX   INTEGER {
                down(1),   -- protocol status is down (+1)
                up(2)      -- protocol status is up
                }
     ACCESS   read-only
     STATUS   mandatory
     DESCRIPTION
"Ipcp operation status (ipcpOperS)- IPCP protocol up or not."
     ::= { nvMpstatPart1Entry 3 }

nvMpstatPart1Ipcp OBJECT-TYPE
     SYNTAX   INTEGER
     ACCESS   read-only
     STATUS   mandatory
     DESCRIPTION
"ipcpconf file record number in use for this multilink bundle (ipcp)."
     ::= { nvMpstatPart1Entry 4 }

nvMpstatPart1IpAddress OBJECT-TYPE
     SYNTAX DisplayString (SIZE (0..16))
     ACCESS   read-only
     STATUS   mandatory
     DESCRIPTION
"IP address in use on this multilink bundle (ipaddr)."
     ::= { nvMpstatPart1Entry 5 }

nvMpstatPart1Profile OBJECT-TYPE
     SYNTAX DisplayString (SIZE(0..20))
     ACCESS   read-only
     STATUS   mandatory
     DESCRIPTION
"nvMpconfProfile value of nvMpconfTable entry (mpconf record) used
to create this multilink bundle (profile)."
     ::= { nvMpstatPart1Entry 6 }

nvMpstatPart1RmtClass OBJECT-TYPE
     SYNTAX INTEGER {
                null(1),     --   NULL class
                local(2),    --   Locally assigned address
                ipaddr(3),   --   IP address from ipconf
                global(4),   --   ieee 802.1 globally assigned
                magicnum(5), --   magic number block
                dirnum(6)    --   public switched network directory number
            }
     ACCESS   read-only
     STATUS   mandatory
     DESCRIPTION
"Class of endpoint discriminator in use on remote (peer) end of
 multilink bundle (rmtClass)."
     ::= { nvMpstatPart1Entry 7 }

nvMpstatPart1RmtDisc OBJECT-TYPE
     SYNTAX DisplayString (SIZE(0..44))
     ACCESS   read-only
     STATUS   mandatory
     DESCRIPTION
"Value of endpoint discriminator in use on remote (peer) end of
multilink bundle (rmtDisc)."
     ::= { nvMpstatPart1Entry 8 }

nvMpstatPart1LocClass OBJECT-TYPE
     SYNTAX INTEGER {
                null(1),     --   NULL class
                local(2),    --   Locally assigned address
                ipaddr(3),   --   IP address from ipconf
                global(4),   --   ieee 802.1 globally assigned
                magicnum(5), --   magic number block
                dirnum(6)    --   public switched network directory number
            }
     ACCESS   read-only
     STATUS   mandatory
     DESCRIPTION
"Class of endpoint discriminator in use on local (Nevada) end of
multilink bundle (locClass)."
     ::= { nvMpstatPart1Entry 9 }

nvMpstatPart1LocDisc OBJECT-TYPE
     SYNTAX DisplayString (SIZE(0..44))
     ACCESS   read-only
     STATUS   mandatory
     DESCRIPTION
"Value of endpoint discriminator in use on local (Nevada) end of
multilink bundle (rmtDisc)."
     ::= { nvMpstatPart1Entry 10 }

nvMpstatPart1RmtMRRU OBJECT-TYPE
     SYNTAX      INTEGER
     ACCESS   read-only
     STATUS   mandatory
     DESCRIPTION
"Value for the Maximum Reassembled Receive Unit negotiated for remote (peer)
end of multilink bundle (rmtMRRU)."
     ::= { nvMpstatPart1Entry 11 }

nvMpstatPart1LocMRRU OBJECT-TYPE
     SYNTAX      INTEGER
     ACCESS   read-only
     STATUS   mandatory
     DESCRIPTION
"Value for the Maximum Reassembled Receive Unit negotiated for local (Nevada)
end of multilink bundle (locMRRU)."
     ::= { nvMpstatPart1Entry 12 }

nvMpstatPart1RmtSeqS OBJECT-TYPE
     SYNTAX      INTEGER {
            short(1), --  short sequence numbers in use
            long(2)  --  long sequence numbers in use
	    }
     ACCESS   read-only
     STATUS   mandatory
     DESCRIPTION
"Indicates whether short or long sequence numbers are in use for multilink
datagrams transmitted to the peer by the Nevada (rmtSeq)."
     ::= { nvMpstatPart1Entry 13 }

nvMpstatPart1LocSeqS OBJECT-TYPE
     SYNTAX      INTEGER {
            short(1), --  short sequence numbers in use
            long(2)  --  long sequence numbers in use
	    }
     ACCESS   read-only
     STATUS   mandatory
     DESCRIPTION
"Indicates whether short or long sequence numbers are in use for multilink
datagrams received by the Nevada (locSeq)."
     ::= { nvMpstatPart1Entry 14 }

nvMpstatPart1Link1 OBJECT-TYPE
     SYNTAX      DisplayString (SIZE(0..8))
     ACCESS   read-only
     STATUS   mandatory
     DESCRIPTION
"The LCP record number corresponding to nth link in the multilink bundle (link n)."
     ::= { nvMpstatPart1Entry 15 }

nvMpstatPart1Link2 OBJECT-TYPE
     SYNTAX      DisplayString (SIZE(0..8))
     ACCESS   read-only
     STATUS   mandatory
     DESCRIPTION
"The LCP record number corresponding to nth link in the multilink bundle (link n)."
     ::= { nvMpstatPart1Entry 16 }

nvMpstatPart1Link3 OBJECT-TYPE
     SYNTAX      DisplayString (SIZE(0..8))
     ACCESS   read-only
     STATUS   mandatory
     DESCRIPTION
"The LCP record number corresponding to nth link in the multilink bundle (link n)."
     ::= { nvMpstatPart1Entry 17 }

nvMpstatPart1Link4 OBJECT-TYPE
     SYNTAX      DisplayString (SIZE(0..8))
     ACCESS   read-only
     STATUS   mandatory
     DESCRIPTION
"The LCP record number corresponding to nth link in the multilink bundle (link n)."
     ::= { nvMpstatPart1Entry 18 }

nvMpstatPart1Link5 OBJECT-TYPE
     SYNTAX      DisplayString (SIZE(0..8))
     ACCESS   read-only
     STATUS   mandatory
     DESCRIPTION
"The LCP record number corresponding to nth link in the multilink bundle (link n)."
     ::= { nvMpstatPart1Entry 19 }

nvMpstatPart1Link6 OBJECT-TYPE
     SYNTAX      DisplayString (SIZE(0..8))
     ACCESS   read-only
     STATUS   mandatory
     DESCRIPTION
"The LCP record number corresponding to nth link in the multilink bundle (link n)."
     ::= { nvMpstatPart1Entry 20 }

nvMpstatPart1Link7 OBJECT-TYPE
     SYNTAX      DisplayString (SIZE(0..8))
     ACCESS   read-only
     STATUS   mandatory
     DESCRIPTION
"The LCP record number corresponding to nth link in the multilink bundle (link n)."
     ::= { nvMpstatPart1Entry 21 }

nvMpstatPart1Link8 OBJECT-TYPE
     SYNTAX      DisplayString (SIZE(0..8))
     ACCESS   read-only
     STATUS   mandatory
     DESCRIPTION
"The LCP record number corresponding to nth link in the multilink bundle (link n)."
     ::= { nvMpstatPart1Entry 22 }

nvMpstatPart1Link9 OBJECT-TYPE
     SYNTAX      DisplayString (SIZE(0..8))
     ACCESS   read-only
     STATUS   mandatory
     DESCRIPTION
"The LCP record number corresponding to nth link in the multilink bundle (link n)."
     ::= { nvMpstatPart1Entry 23 }

nvMpstatPart1Link10 OBJECT-TYPE
     SYNTAX      DisplayString (SIZE(0..8))
     ACCESS   read-only
     STATUS   mandatory
     DESCRIPTION
"The LCP record number corresponding to nth link in the multilink bundle (link n)."
     ::= { nvMpstatPart1Entry 24 }

nvMpstatPart1Link11 OBJECT-TYPE
     SYNTAX      DisplayString (SIZE(0..8))
     ACCESS   read-only
     STATUS   mandatory
     DESCRIPTION
"The LCP record number corresponding to nth link in the multilink bundle (link n)."
     ::= { nvMpstatPart1Entry 25 }

nvMpstatPart1Link12 OBJECT-TYPE
     SYNTAX      DisplayString (SIZE(0..8))
     ACCESS   read-only
     STATUS   mandatory
     DESCRIPTION
"The LCP record number corresponding to nth link in the multilink bundle (link n)."
     ::= { nvMpstatPart1Entry 26 }

nvMpstatPart1Link13 OBJECT-TYPE
     SYNTAX      DisplayString (SIZE (0..8))
     ACCESS   read-only
     STATUS   mandatory
     DESCRIPTION
"The LCP record number corresponding to nth link in the multilink bundle (link n)."
     ::= { nvMpstatPart1Entry 27 }

nvMpstatPart1Link14 OBJECT-TYPE
     SYNTAX      DisplayString (SIZE(0..8))
     ACCESS   read-only
     STATUS   mandatory
     DESCRIPTION
"The LCP record number corresponding to nth link in the multilink bundle (link n)."
     ::= { nvMpstatPart1Entry 28 }

nvMpstatPart1Link15 OBJECT-TYPE
     SYNTAX      DisplayString (SIZE(0..8))
     ACCESS   read-only
     STATUS   mandatory
     DESCRIPTION
"The LCP record number corresponding to nth link in the multilink bundle (link n)."
     ::= { nvMpstatPart1Entry 29 }

nvMpstatPart1Link16 OBJECT-TYPE
     SYNTAX      DisplayString (SIZE(0..8))
     ACCESS   read-only
     STATUS   mandatory
     DESCRIPTION
"The LCP record number corresponding to nth link in the multilink bundle (link n)."
     ::= { nvMpstatPart1Entry 30 }



nvMpstatPart2 OBJECT IDENTIFIER     ::= { nevadaPpp 5 }

nvMpstatPart2MaxRec OBJECT-TYPE
      SYNTAX   INTEGER
      ACCESS   read-only
      STATUS   mandatory
      DESCRIPTION
                "total number of records allowed in database file."
      ::= {nvMpstatPart2 1}

nvMpstatPart2NumRec OBJECT-TYPE
      SYNTAX   INTEGER
      ACCESS   read-only
      STATUS   mandatory
      DESCRIPTION
                "number of records in use."
      ::= {nvMpstatPart2 2}

nvMpstatPart2Table OBJECT-TYPE
      SYNTAX   SEQUENCE OF NvMpstatPart2Entry
      ACCESS   not-accessible
      STATUS   mandatory
      DESCRIPTION
               "mpstatPart2 file."
      ::= { nvMpstatPart2 3 }

nvMpstatPart2Entry OBJECT-TYPE
      SYNTAX   NvMpstatPart2Entry
      ACCESS   not-accessible
      STATUS   mandatory
      DESCRIPTION
               "mpstatPart2 record."
      INDEX { nvMpstatPart2Index }
      ::= { nvMpstatPart2Table 1 }

NvMpstatPart2Entry ::=
      SEQUENCE {
      nvMpstatPart2Index
           INTEGER,
      nvMpstatPart2InOctets
            Counter,
      nvMpstatPart2InPkts
            Counter,
      nvMpstatPart2InBfrags
            Counter,
      nvMpstatPart2InEfrags
            Counter,
      nvMpstatPart2InMfrags
            Counter,
      nvMpstatPart2InRsmErr
            Counter,
      nvMpstatPart2InDiscrd
            Counter,
      nvMpstatPart2InErrors
            Counter,
      nvMpstatPart2InEch
            Counter,
      nvMpstatPart2InEchRp
            Counter,
      nvMpstatPart2InDiscRq
            Counter,
      nvMpstatPart2UnKnwnPr
            Counter,
      nvMpstatPart2OutOctets
            Counter,
      nvMpstatPart2OutPkts
            Counter,
      nvMpstatPart2OutBfrags
            Counter,
      nvMpstatPart2OutEfrags
            Counter,
      nvMpstatPart2OutMfrags
            Counter,
      nvMpstatPart2OutDiscrd
            Counter,
      nvMpstatPart2OutErrors
            Counter,
      nvMpstatPart2OutEch
            Counter,
      nvMpstatPart2OutEchRp
            Counter,
      nvMpstatPart2OutDiscRq
            Counter,
      nvMpstatPart2OutCmPcnt              --AF
            Counter,                 --AF
      nvMpstatPart2InCmPcnt               --AF
            Counter,                 --AF
      nvMpstatPart2OutExpnds              --AF
            Counter,                 --AF
      nvMpstatPart2Dtreset
            DisplayString                   	    	    
      }

nvMpstatPart2Index OBJECT-TYPE
     SYNTAX   INTEGER
     ACCESS   read-only
     STATUS   mandatory
     DESCRIPTION
"Index of MpstatPart2 record"
      ::= { nvMpstatPart2Entry 1 }

nvMpstatPart2InOctets OBJECT-TYPE
     SYNTAX   Counter
     ACCESS   read-only
     STATUS   mandatory
     DESCRIPTION
"Octets received (InOctets)
The number of good data bytes received
Statistic is zeroed at startup time."
     ::= { nvMpstatPart2Entry 2 }

nvMpstatPart2InPkts OBJECT-TYPE
     SYNTAX   Counter
     ACCESS   read-only
     STATUS   mandatory
     DESCRIPTION
"good packets received (InPkts)
The number of good received frames
Statistic is zeroed at startup time."
     ::= { nvMpstatPart2Entry 3 }

nvMpstatPart2InBfrags OBJECT-TYPE
     SYNTAX   Counter
     ACCESS   read-only
     STATUS   mandatory
     DESCRIPTION
"The number of good received multilink frames with the
B bit set in the multilink header (beginning fragment).
Statistic is zeroed at startup time."
     ::= { nvMpstatPart2Entry 4 }

nvMpstatPart2InEfrags OBJECT-TYPE
     SYNTAX   Counter
     ACCESS   read-only
     STATUS   mandatory
     DESCRIPTION
"The number of good received multilink frames with the
E bit set in the multilink header (ending fragment) .
Statistic is zeroed at startup time."
     ::= { nvMpstatPart2Entry 5 }

nvMpstatPart2InMfrags OBJECT-TYPE
     SYNTAX   Counter
     ACCESS   read-only
     STATUS   mandatory
     DESCRIPTION
"The number of good received multilink frames with neither
the B nor the E bit set in the multilink header (middle fragment).
Statistic is zeroed at startup time."
     ::= { nvMpstatPart2Entry 6 }

nvMpstatPart2InRsmErr OBJECT-TYPE
     SYNTAX   Counter
     ACCESS   read-only
     STATUS   mandatory
     DESCRIPTION
"number of times the multilink receive algorithm detected
 one or more lost PPP datagrams (InRsmErr).
 Statistic is zeroed at startup time."
     ::= { nvMpstatPart2Entry 7 }

nvMpstatPart2InDiscrd OBJECT-TYPE
     SYNTAX   Counter
     ACCESS   read-only
     STATUS   mandatory
     DESCRIPTION
"discarded good packets (InDiscrd)
The total number of good frames dicarded due to lack of buffers
Statistic is zeroed at startup time."
     ::= { nvMpstatPart2Entry 8 }

nvMpstatPart2InErrors OBJECT-TYPE
     SYNTAX   Counter
     ACCESS   read-only
     STATUS   mandatory
     DESCRIPTION
"Bad packets received (InError)
The total number of frames received with errors due to crc,format etc.
Statistic is zeroed at startup time."
     ::= { nvMpstatPart2Entry 9 }

nvMpstatPart2InEch OBJECT-TYPE
     SYNTAX   Counter
     ACCESS   read-only
     STATUS   mandatory
     DESCRIPTION
"received echo requests (InEch)
The number of echo request packets recieved.
Statistic is zeroed at startup time."
     ::= { nvMpstatPart2Entry 10 }

nvMpstatPart2InEchRp OBJECT-TYPE
     SYNTAX   Counter
     ACCESS   read-only
     STATUS   mandatory
     DESCRIPTION
"echo reply received (InEchRp)
The num of packets Rxed due to the echo-req sent (software loopback)
Statistic is zeroed at startup time."
     ::= { nvMpstatPart2Entry 11 }

nvMpstatPart2InDiscRq OBJECT-TYPE
     SYNTAX   Counter
     ACCESS   read-only
     STATUS   mandatory
     DESCRIPTION
"discard requests Rxed (InDiscRq)
The number of discard request packets received.
Statistic is zeroed at startup time."
     ::= { nvMpstatPart2Entry 12 }

nvMpstatPart2UnKnwnPr OBJECT-TYPE
     SYNTAX   Counter
     ACCESS   read-only
     STATUS   mandatory
     DESCRIPTION
"rxed Unknown protocol (UnKnwnPr)
The number of link quality reports received on this PPP link
Statistic is zeroed at startup time."
     ::= { nvMpstatPart2Entry 13 }

nvMpstatPart2OutOctets OBJECT-TYPE
     SYNTAX   Counter
     ACCESS   read-only
     STATUS   mandatory
     DESCRIPTION
"Octets transmitted (OutOctets)
The number of bytes transmitted on the ppp link.
Statistic is zeroed at startup time."
     ::= { nvMpstatPart2Entry 14 }

nvMpstatPart2OutPkts OBJECT-TYPE
     SYNTAX   Counter
     ACCESS   read-only
     STATUS   mandatory
     DESCRIPTION
"Packets transmitted (OutPkts)
The number of pakets transmitted on the PPP link.
Statistic is zeroed at startup time."
     ::= { nvMpstatPart2Entry 15 }

nvMpstatPart2OutBfrags OBJECT-TYPE
     SYNTAX   Counter
     ACCESS   read-only
     STATUS   mandatory
     DESCRIPTION
"The number of multilink frames transmitted with the
B bit set in the multilink header (beginning fragment).
Statistic is zeroed at startup time."
     ::= { nvMpstatPart2Entry 16 }

nvMpstatPart2OutEfrags OBJECT-TYPE
     SYNTAX   Counter
     ACCESS   read-only
     STATUS   mandatory
     DESCRIPTION
"The number of multilink frames transmitted with the
E bit set in the multilink header (ending fragment) .
Statistic is zeroed at startup time."
     ::= { nvMpstatPart2Entry 17 }

nvMpstatPart2OutMfrags OBJECT-TYPE
     SYNTAX   Counter
     ACCESS   read-only
     STATUS   mandatory
     DESCRIPTION
"The number of multilink frames transmitted with neither
the B nor the E bit set in the multilink header (middle fragment).
Statistic is zeroed at startup time."
     ::= { nvMpstatPart2Entry 18 }

nvMpstatPart2OutDiscrd OBJECT-TYPE
     SYNTAX   Counter
     ACCESS   read-only
     STATUS   mandatory
     DESCRIPTION
"output errors (OutDiscrd)
The number of outbound pkts droped due to lack of buffers.
Statistic is zeroed at startup time."
     ::= { nvMpstatPart2Entry 19 }

nvMpstatPart2OutErrors OBJECT-TYPE
     SYNTAX   Counter
     ACCESS   read-only
     STATUS   mandatory
     DESCRIPTION
"output errors (OutErrors)
The number of outbound pkts could not be txed due to errors.
Statistic is zeroed at startup time."
     ::= { nvMpstatPart2Entry 20 }

nvMpstatPart2OutEch OBJECT-TYPE
     SYNTAX   Counter
     ACCESS   read-only
     STATUS   mandatory
     DESCRIPTION
"echo request pkts transmitted (OutEch)
The number of lcp echo request packets transmitted
Statistic is zeroed at startup time."
     ::= { nvMpstatPart2Entry 21 }

nvMpstatPart2OutEchRp OBJECT-TYPE
     SYNTAX   Counter
     ACCESS   read-only
     STATUS   mandatory
     DESCRIPTION
"echo reply transmitted (OutEchRp)
The num of echo reply packets Txed due to the echo-req
Statistic is zeroed at startup time."
     ::= { nvMpstatPart2Entry 22 }

nvMpstatPart2OutDiscRq OBJECT-TYPE
     SYNTAX   Counter
     ACCESS   read-only
     STATUS   mandatory
     DESCRIPTION
"discard requests Txed (OutDiscRq)
The number of discard request packets received.
Statistic is zeroed at startup time."
     ::= { nvMpstatPart2Entry 23 }

nvMpstatPart2OutCmPcnt OBJECT-TYPE      --AF
     SYNTAX   Counter		    --AF
     ACCESS   read-only		    --AF
     STATUS   mandatory		    --AF
     DESCRIPTION		    --AF
"Percent compression on tx."        --AF
     ::= { nvMpstatPart2Entry 24 }	    --AF

nvMpstatPart2InCmPcnt OBJECT-TYPE       --AF
     SYNTAX   Counter		    --AF
     ACCESS   read-only		    --AF
     STATUS   mandatory		    --AF
     DESCRIPTION		    --AF
"Percent compression on rx."        --AF
     ::= { nvMpstatPart2Entry 25 }	    --AF

nvMpstatPart2OutExpnds OBJECT-TYPE      --AF
     SYNTAX   Counter		    --AF
     ACCESS   read-only		    --AF
     STATUS   mandatory		    --AF
     DESCRIPTION		    --AF
"Number of packets expanded by compression."        --AF
     ::= { nvMpstatPart2Entry 26 }	    --AF

nvMpstatPart2Dtreset OBJECT-TYPE
     SYNTAX   DisplayString (SIZE (0..20))
     ACCESS   read-only
     STATUS   mandatory
     DESCRIPTION
        "date & time statistics last reset"
      ::= { nvMpstatPart2Entry 27 }

--
--      elxstat file
--
nvElxstat OBJECT IDENTIFIER ::= { nevadaElx 1 }

nvElxstatMaxRec OBJECT-TYPE
      SYNTAX   INTEGER
      ACCESS   read-only
      STATUS   mandatory
      DESCRIPTION
                "total number of records allowed in database file."
      ::= {nvElxstat 1}

nvElxstatNumRec OBJECT-TYPE
      SYNTAX   INTEGER
      ACCESS   read-only
      STATUS   mandatory
      DESCRIPTION
                "number of records in use."
      ::= {nvElxstat 2}

nvElxstatTable OBJECT-TYPE
      SYNTAX   SEQUENCE OF NvElxstatEntry
      ACCESS   not-accessible
      STATUS   mandatory
      DESCRIPTION
               "elxstat file."
      ::= { nvElxstat 3 }

nvElxstatEntry OBJECT-TYPE
      SYNTAX   NvElxstatEntry
      ACCESS   not-accessible
      STATUS   mandatory
      DESCRIPTION
               "elxstat record."
      INDEX { nvElxstatIndex }
      ::= { nvElxstatTable 1 }

NvElxstatEntry ::=
      SEQUENCE {
      nvElxstatIndex
            INTEGER,
      nvElxstatPhysAddr
            DisplayString,
      nvElxstatAdminStat
            INTEGER,
      nvElxstatOperStat
            INTEGER,
      nvElxstatInOctets
            Counter,
      nvElxstatInUcasts
            Counter,
      nvElxstatInNUcasts
            Counter,
      nvElxstatInDiscards
            Counter,
      nvElxstatInErrors
            Counter,
      nvElxstatUnKnwnPrs
            Counter,
      nvElxstatOutOctets
            Counter,
      nvElxstatOutUcasts
            Counter,
      nvElxstatOutNUcasts
            Counter,
      nvElxstatOutDiscrds
            Counter,
      nvElxstatOutErrors
            Counter,
      nvElxstatDtreset
            DisplayString
               }

nvElxstatIndex OBJECT-TYPE
     SYNTAX   INTEGER
     ACCESS   read-only
     STATUS   mandatory
     DESCRIPTION
        "Index of elxstat record"
      ::= { nvElxstatEntry 1 }

nvElxstatPhysAddr OBJECT-TYPE
     SYNTAX   DisplayString (SIZE (0..12))
     ACCESS   read-only
     STATUS   mandatory
     DESCRIPTION
"Ethernet Physical Address (PhysAddr)
This field contains the Ethernet address as configured at the
factory.
"
     ::= { nvElxstatEntry 2 }

nvElxstatAdminStat OBJECT-TYPE
     SYNTAX   INTEGER {
                up(2),     -- up (+1)
                down(3)      -- down
                }
     ACCESS   read-only
     STATUS   mandatory
     DESCRIPTION
"Desired Interface state (AdminStat)
The desired state of the interface. This field reflects the
desired state of the interface as determined by the enable
field of the ELXCONF file,as well as the ELX.UP and ELX.DOWN
commands.
"
     ::= { nvElxstatEntry 3 }

nvElxstatOperStat OBJECT-TYPE
     SYNTAX   INTEGER {
                up(2),     -- up (+1)
                down(3)      -- down
                }
     ACCESS   read-only
     STATUS   mandatory
     DESCRIPTION
"Current Interface state (OperStat)
The current operational state of the Ethernet interface. This
is determined by the AdminStat and whether or not any transmit
faults were detected.
"
     ::= { nvElxstatEntry 4 }

nvElxstatInOctets OBJECT-TYPE
     SYNTAX   Counter
     ACCESS   read-only
     STATUS   mandatory
     DESCRIPTION
"Octets received on the interface (InOctets)
The total number of octets received on the interface,
including framing characters.
Statistic is zeroed at startup time."
     ::= { nvElxstatEntry 5 }

nvElxstatInUcasts OBJECT-TYPE
     SYNTAX   Counter
     ACCESS   read-only
     STATUS   mandatory
     DESCRIPTION
"Unicast packets delivered (InUcast)
The number of subnetwork unicast packets delivered to a
higher layer protocol.
Statistic is zeroed at startup time."
     ::= { nvElxstatEntry 6 }

nvElxstatInNUcasts OBJECT-TYPE
     SYNTAX   Counter
     ACCESS   read-only
     STATUS   mandatory
     DESCRIPTION
"Non unicast packets delivered (InNUcast)
The number of non unicast,i.e.,subnetwork broadcast or
subnetwork multicast,packets delivered to a higher layer
protocol.
Statistic is zeroed at startup time."
     ::= { nvElxstatEntry 7 }

nvElxstatInDiscards OBJECT-TYPE
     SYNTAX   Counter
     ACCESS   read-only
     STATUS   mandatory
     DESCRIPTION
"Discarded input packets (InDiscard)
The number of inbound packets which were chosen to be
discarded even though no errors had been detected to
prevent their being deliverable to a higher layer
protocol. One possible reason for discarding such a
packet could be to free up buffer space.
Statistic is zeroed at startup time."
     ::= { nvElxstatEntry 8 }

nvElxstatInErrors OBJECT-TYPE
     SYNTAX   Counter
     ACCESS   read-only
     STATUS   mandatory
     DESCRIPTION
"Error input packets (InError)
The number of inbound packets that contained errors
preventing them from being deliverable to a higher
layer protocol.
Statistic is zeroed at startup time."
     ::= { nvElxstatEntry 9 }

nvElxstatUnKnwnPrs OBJECT-TYPE
     SYNTAX   Counter
     ACCESS   read-only
     STATUS   mandatory
     DESCRIPTION
"Unknown protocol packets discarded (UnKnwnPr)
The number of packets received via the interface which
were discarded because of an unknown or unsupported
protocol.
Statistic is zeroed at startup time."
     ::= { nvElxstatEntry 10 }

nvElxstatOutOctets OBJECT-TYPE
     SYNTAX   Counter
     ACCESS   read-only
     STATUS   mandatory
     DESCRIPTION
"Octets transmitted from the interface (OutOctets)
The total number of octets transmitted out the
interface,including framing characters.
Statistic is zeroed at startup time."
     ::= { nvElxstatEntry 11 }

nvElxstatOutUcasts OBJECT-TYPE
     SYNTAX   Counter
     ACCESS   read-only
     STATUS   mandatory
     DESCRIPTION
"Unicast packets transmitted (OutUcast)
The total number of packets that higher level protocols
requested be transmitted to a subnetwork unicast address,
including those that were discarded or not sent.
Statistic is zeroed at startup time."
     ::= { nvElxstatEntry 12 }

nvElxstatOutNUcasts OBJECT-TYPE
     SYNTAX   Counter
     ACCESS   read-only
     STATUS   mandatory
     DESCRIPTION
"Non unicast packets transmitted (OutNUcast)
The total number of packets that highel level protocols
requested be transmitted to a non unicast,i.e.,a
subnetwork broadcast or subnetwork multicast,address,
including those that were discarded or not sent.
Statistic is zeroed at startup time."
     ::= { nvElxstatEntry 13 }

nvElxstatOutDiscrds OBJECT-TYPE
     SYNTAX   Counter
     ACCESS   read-only
     STATUS   mandatory
     DESCRIPTION
"Discarded output packets (OutDiscrd)
The number of outbound packets which were chosen to be
discarded even though no errors had been detected to
prevent their being transmitted. One possible reason for
discarding such a packet could be to free up buffer
space.
Statistic is zeroed at startup time."
     ::= { nvElxstatEntry 14 }

nvElxstatOutErrors OBJECT-TYPE
     SYNTAX   Counter
     ACCESS   read-only
     STATUS   mandatory
     DESCRIPTION
"Error output packets (OutErrors)
The number of outbound packets that could not be
transmitted because of errors.
Statistic is zeroed at startup time."
     ::= { nvElxstatEntry 15 }

nvElxstatDtreset OBJECT-TYPE
     SYNTAX   DisplayString (SIZE (0..20))
     ACCESS   read-only
     STATUS   mandatory
     DESCRIPTION
        "date & time statistics last reset"
      ::= { nvElxstatEntry 16 }

--
--      elxconf file
--
nvElxconf OBJECT IDENTIFIER ::= { nevadaElx 2 }

nvElxconfMaxRec OBJECT-TYPE
      SYNTAX   INTEGER
      ACCESS   read-only
      STATUS   mandatory
      DESCRIPTION
                "total number of records allowed in database file."
      ::= {nvElxconf 1}

nvElxconfNumRec OBJECT-TYPE
      SYNTAX   INTEGER
      ACCESS   read-only
      STATUS   mandatory
      DESCRIPTION
                "number of records in use."
      ::= {nvElxconf 2}
        
nvElxconfTable OBJECT-TYPE
      SYNTAX   SEQUENCE OF NvElxconfEntry
      ACCESS   not-accessible
      STATUS   mandatory
      DESCRIPTION
               "elxconf file."
      ::= { nvElxconf 3 }

nvElxconfEntry OBJECT-TYPE
      SYNTAX   NvElxconfEntry
      ACCESS   not-accessible
      STATUS   mandatory
      DESCRIPTION
               "elxconf record."
      INDEX { nvElxconfIndex }
      ::= { nvElxconfTable 1 }
        
NvElxconfEntry ::=
      SEQUENCE {
      nvElxconfIndex
            INTEGER,
      nvElxconfEnable
            INTEGER,
      nvElxconfInactivty
            INTEGER
               }

nvElxconfIndex OBJECT-TYPE
     SYNTAX   INTEGER
     ACCESS   read-only
     STATUS   mandatory
     DESCRIPTION
        "Index of elxconf record"
      ::= { nvElxconfEntry 1 }

nvElxconfEnable OBJECT-TYPE
     SYNTAX   INTEGER {
                no(1),      -- no
                yes(2)     -- yes (+1)
                }
     ACCESS   read-write
     STATUS   mandatory
     DESCRIPTION
"Ethernet interface enabled (enable)
This field indicates whether or not the Ethernet interface should
be enabled. Note that disabling the interface does not disable
IP. IP may still route between its other networks,such as X.25
and Frame Relay.
Default value is yes (1+1)."
     ::= { nvElxconfEntry 2 }

nvElxconfInactivty OBJECT-TYPE
     SYNTAX   INTEGER (0..255)
     ACCESS   read-write
     STATUS   mandatory
     DESCRIPTION
"Inactivity test frame timer (inactivty)
When this time in minutes has been exceeded with no activity on the
Ethernet,a frame will be transmitted in order to check for transmit
faults.
Default value is 0."
     ::= { nvElxconfEntry 3 }

--
-- ipconf
--

nvIpconf OBJECT IDENTIFIER ::= { nevadaIp 1}

nvIpconfMaxRec OBJECT-TYPE
      SYNTAX   INTEGER
      ACCESS   read-only
      STATUS   mandatory
      DESCRIPTION
                "total number of records allowed in database file."
      ::= {nvIpconf 1}

nvIpconfNumRec OBJECT-TYPE
      SYNTAX   INTEGER
      ACCESS   read-only
      STATUS   mandatory
      DESCRIPTION
                "number of records in use."
      ::= {nvIpconf 2}

nvIpconfTable OBJECT-TYPE
      SYNTAX   SEQUENCE OF NvIpconfEntry
      ACCESS   not-accessible
      STATUS   mandatory
      DESCRIPTION
               "ipconf file."
      ::= { nvIpconf 3 }

nvIpconfEntry OBJECT-TYPE
      SYNTAX   NvIpconfEntry
      ACCESS   not-accessible
      STATUS   mandatory
      DESCRIPTION
               "ipconf record."
      INDEX { nvIpconfIndex }
      ::= { nvIpconfTable 1 }

NvIpconfEntry ::=
      SEQUENCE {
      nvIpconfIndex
            INTEGER,
      nvIpconfIpaddr
            DisplayString,
      nvIpconfMask
            DisplayString,
      nvIpconfBcastaddr
            DisplayString,
      nvIpconfMtu
            INTEGER,
      nvIpconfEncap
            INTEGER,
      nvIpconfRoutprot
            INTEGER,
      nvIpconfStatus
            INTEGER
               }

nvIpconfIndex OBJECT-TYPE
     SYNTAX   INTEGER
     ACCESS   read-only
     STATUS   mandatory
     DESCRIPTION
        "Index of ipconf record"
      ::= { nvIpconfEntry 1 }

nvIpconfIpaddr OBJECT-TYPE
     SYNTAX   DisplayString (SIZE (0..16))
     ACCESS   read-write
     STATUS   mandatory
     DESCRIPTION
"IP address of local LAN (ipaddr)
This field is a 15 byte character string in IP dotted address format.
"
     ::= { nvIpconfEntry 7 }

nvIpconfMask OBJECT-TYPE
     SYNTAX   DisplayString (SIZE (0..16))
     ACCESS   read-write
     STATUS   mandatory
     DESCRIPTION
"IP network mask (mask)
This field is a 15 byte character string in IP dotted address format.
"
     ::= { nvIpconfEntry 8 }

nvIpconfBcastaddr OBJECT-TYPE
     SYNTAX   DisplayString (SIZE (0..16))
     ACCESS   read-write
     STATUS   mandatory
     DESCRIPTION
"Outgoing broadcast IP address (bcastaddr)
This field is a 15 byte character string in IP dotted address format.
"
     ::= { nvIpconfEntry 9 }

nvIpconfMtu OBJECT-TYPE
     SYNTAX   INTEGER (64..1500)
     ACCESS   read-write
     STATUS   mandatory
     DESCRIPTION
"Maximum frame length on this interface (mtu)
Default value is 1500."
     ::= { nvIpconfEntry 10 }

nvIpconfEncap OBJECT-TYPE
     SYNTAX   INTEGER {
                v2(1),     -- Ethernet Version 2 encapsulation (+1)
                snap(2)      -- SNAP encapsulation
                }
     ACCESS   read-write
     STATUS   mandatory
     DESCRIPTION
"Encapsulation type
Default value is v2 (0+1)."
     ::= { nvIpconfEntry 11 }

nvIpconfRoutprot OBJECT-TYPE
     SYNTAX   INTEGER {
                none(1),      -- none
                rip(9)     -- rip,must agree with ip-rtsprot definition  (+1)
                }
     ACCESS   read-write
     STATUS   mandatory
     DESCRIPTION
"IP routing protocol (routprot)."
     ::= { nvIpconfEntry 12 }

nvIpconfStatus OBJECT-TYPE
     SYNTAX   INTEGER {
                valid(1),
                invalid(2)
                }
     ACCESS   read-write
     STATUS   mandatory
     DESCRIPTION
           "Operation status. Add the record to the table (valid) or
           delete the record from the table (invalid)."
     ::= { nvIpconfEntry 17 }

--
--      ipstat file
--
nvIpstat OBJECT IDENTIFIER ::= { nevadaIp 2}

nvIpstatMaxRec OBJECT-TYPE
      SYNTAX   INTEGER
      ACCESS   read-only
      STATUS   mandatory
      DESCRIPTION
                "total number of records allowed in database file."
      ::= {nvIpstat 1}

nvIpstatNumRec OBJECT-TYPE
      SYNTAX   INTEGER
      ACCESS   read-only
      STATUS   mandatory
      DESCRIPTION
                "number of records in use."
      ::= {nvIpstat 2}

nvIpstatTable OBJECT-TYPE
      SYNTAX   SEQUENCE OF NvIpstatEntry
      ACCESS   not-accessible
      STATUS   mandatory
      DESCRIPTION
               "ipstat file."
      ::= { nvIpstat 3 }

nvIpstatEntry OBJECT-TYPE
      SYNTAX   NvIpstatEntry
      ACCESS   not-accessible
      STATUS   mandatory
      DESCRIPTION
               "ipstat record."
      INDEX { nvIpstatIndex }
      ::= { nvIpstatTable 1 }

NvIpstatEntry ::=
      SEQUENCE {
      nvIpstatIndex
            INTEGER,
      nvIpstatInRxs
            Counter,
      nvIpstatInHdrErrs
            Counter,
      nvIpstatInAdrErrs
            Counter,
      nvIpstatForwDatas
            Counter,
      nvIpstatUnKnwnPrs
            Counter,
      nvIpstatInDiscrds
            Counter,
      nvIpstatInDlvrs
            Counter,
      nvIpstatOutRqsts
            Counter,
      nvIpstatOutDiscrds
            Counter,
      nvIpstatOutNoRts
            Counter,
      nvIpstatReasmRqds
            Counter,
      nvIpstatReasmOKs
            Counter,
      nvIpstatReasmFails
            Counter,
      nvIpstatFragOKs
            Counter,
      nvIpstatFragFails
            Counter,
      nvIpstatFragCrs
            Counter,
      nvIpstatDtreset
            DisplayString
               }

nvIpstatIndex OBJECT-TYPE
     SYNTAX   INTEGER
     ACCESS   read-only
     STATUS   mandatory
     DESCRIPTION
        "Index of ipstat record"
      ::= { nvIpstatEntry 1 }

nvIpstatInRxs OBJECT-TYPE
     SYNTAX   Counter
     ACCESS   read-only
     STATUS   mandatory
     DESCRIPTION
"Input datagrams received (InRx)
The total number of input datagrams received from
interfaces,including those received in error.
Statistic is zeroed at startup time."
     ::= { nvIpstatEntry 2 }

nvIpstatInHdrErrs OBJECT-TYPE
     SYNTAX   Counter
     ACCESS   read-only
     STATUS   mandatory
     DESCRIPTION
"Input datagrams with header errors (InHdrErr)
The number of input datagrams discarded due to
errors in their IP headers,including bad
checksums,version number mismatch,other format
errors,time-to-live exceeded,errors discovered
in processing their IP options,etc.
Statistic is zeroed at startup time."
     ::= { nvIpstatEntry 3 }

nvIpstatInAdrErrs OBJECT-TYPE
     SYNTAX   Counter
     ACCESS   read-only
     STATUS   mandatory
     DESCRIPTION
"Input datagrams with address errors (InAdrErr)
The number of input datagrams discarded because
the IP address in their IP header's destination
field was not a valid address to be received at
this entity. This count includes invalid
addresses (e.g.,0.0.0.0) and addresses of
unsupported Classes (e.g.,Class E). For entities
which are not IP Gateways and therefore do not
forward datagrams,this counter includes datagrams
discarded because the destination address was not
a local address.
Statistic is zeroed at startup time."
     ::= { nvIpstatEntry 4 }

nvIpstatForwDatas OBJECT-TYPE
     SYNTAX   Counter
     ACCESS   read-only
     STATUS   mandatory
     DESCRIPTION
"Input datagrams forwarded (ForwData)
The number of input datagrams for which this
entity was not their final IP destination,as a
result of which an attempt was made to find a
route to forward them to that final destination.
In entities which do not act as IP Gateways,this
counter will include only those packets which were
Source-Routed via this entity,and the Source-
Route option processing was successful.
Statistic is zeroed at startup time."
     ::= { nvIpstatEntry 5 }

nvIpstatUnKnwnPrs OBJECT-TYPE
     SYNTAX   Counter
     ACCESS   read-only
     STATUS   mandatory
     DESCRIPTION
"Input datagrams with protocol errors (UnKnwnPr)
The number of locally-addressed datagrams
received successfully but discarded because of an
unknown or unsupported protocol.
Statistic is zeroed at startup time."
     ::= { nvIpstatEntry 6 }

nvIpstatInDiscrds OBJECT-TYPE
     SYNTAX   Counter
     ACCESS   read-only
     STATUS   mandatory
     DESCRIPTION
"Input datagrams with buffer errors (InDiscrd)
The number of input IP datagrams for which no
problems were encountered to prevent their
continued processing,but which were discarded
(e.g.,for lack of buffer space). Note that this
counter does not include any datagrams discarded
while waiting re-assembly.
Statistic is zeroed at startup time."
     ::= { nvIpstatEntry 7 }

nvIpstatInDlvrs OBJECT-TYPE
     SYNTAX   Counter
     ACCESS   read-only
     STATUS   mandatory
     DESCRIPTION
"Input datagrams delivered (InDlvrs)
The total number of input datagrams successfully
delivered to IP user-protocols (including ICMP).
Statistic is zeroed at startup time."
     ::= { nvIpstatEntry 8 }

nvIpstatOutRqsts OBJECT-TYPE
     SYNTAX   Counter
     ACCESS   read-only
     STATUS   mandatory
     DESCRIPTION
"Local datagrams created (OutRqst)
The total number of IP datagrams which local IP
user protocols (including ICMP) supplied to IP in
requests for transmission. Note that this counter
does not include any datagrams counted in ForwData.
Statistic is zeroed at startup time."
     ::= { nvIpstatEntry 9 }

nvIpstatOutDiscrds OBJECT-TYPE
     SYNTAX   Counter
     ACCESS   read-only
     STATUS   mandatory
     DESCRIPTION
"Output datagrams with buffer errors (OutDiscrd)
The number of output IP datagrams for which no
problem was encountered to prevent their
transmission to their destination,but which were
discarded (e.g.,for lack of buffer space). Note
that this counter would include datagrams counted
in ForwData if any such packets met this
(discretionary) discard criterion.
Statistic is zeroed at startup time."
     ::= { nvIpstatEntry 10 }

nvIpstatOutNoRts OBJECT-TYPE
     SYNTAX   Counter
     ACCESS   read-only
     STATUS   mandatory
     DESCRIPTION
"Output datagrams with address errors (OutNoRts)
The number of IP datagrams discarded because no
route could be found to transmit them to their
destination. Note that this counter includes any
packets counted in ForwData which meet this
`no-route' criterion. Note that this includes any
datagrams which a host cannot route because all of
its default gateways are down.
Statistic is zeroed at startup time."
     ::= { nvIpstatEntry 11 }

nvIpstatReasmRqds OBJECT-TYPE
     SYNTAX   Counter
     ACCESS   read-only
     STATUS   mandatory
     DESCRIPTION
"Received IP fragments (ReasmRqd)
The number of IP fragments received which needed
to be reassembled at this entity.
Statistic is zeroed at startup time."
     ::= { nvIpstatEntry 12 }

nvIpstatReasmOKs OBJECT-TYPE
     SYNTAX   Counter
     ACCESS   read-only
     STATUS   mandatory
     DESCRIPTION
"Datagrams successfully reassembled (ReasmOK)
The number of IP datagrams successfully reassembled.
Statistic is zeroed at startup time."
     ::= { nvIpstatEntry 13 }

nvIpstatReasmFails OBJECT-TYPE
     SYNTAX   Counter
     ACCESS   read-only
     STATUS   mandatory
     DESCRIPTION
"Datagram reassembly failures (ReasmFail)
The number of errors detected by the IP re-assembly algorithm
(for whatever reason: timed out,errors,etc). Note that this
is not necessarily a count of discarded IP fragments since some
algorithms (notably the algorithm in RFC 815) can loose track
of the number of fragments by combining them as they are received.
Statistic is zeroed at startup time."
     ::= { nvIpstatEntry 14 }

nvIpstatFragOKs OBJECT-TYPE
     SYNTAX   Counter
     ACCESS   read-only
     STATUS   mandatory
     DESCRIPTION
"Datagrams successfully fragmented (FragOK)
The number of IP datagrams that have been
successfully fragmented at this entity.
Statistic is zeroed at startup time."
     ::= { nvIpstatEntry 15 }

nvIpstatFragFails OBJECT-TYPE
     SYNTAX   Counter
     ACCESS   read-only
     STATUS   mandatory
     DESCRIPTION
"Datagrams with fragmentation errors (FragFail)
The number of IP datagrams that have been
discarded because they needed to be fragmented at
this entity but could not be,e.g.,because their
Don't Fragment flag was set.
Statistic is zeroed at startup time."
     ::= { nvIpstatEntry 16 }

nvIpstatFragCrs OBJECT-TYPE
     SYNTAX   Counter
     ACCESS   read-only
     STATUS   mandatory
     DESCRIPTION
"Fragments created (FragCr)
The number of IP datagram fragments that have
been generated as a result of fragmentation at
this entity.
Statistic is zeroed at startup time."
     ::= { nvIpstatEntry 17 }

nvIpstatDtreset OBJECT-TYPE
     SYNTAX   DisplayString (SIZE (0..20))
     ACCESS   read-only
     STATUS   mandatory
     DESCRIPTION
        "date & time statistics last reset"
      ::= { nvIpstatEntry 18 }

--
-- ipwanmap
--
nvIpwanmap OBJECT IDENTIFIER ::= { nevadaIp 3}

nvIpwanmapMaxRec OBJECT-TYPE
      SYNTAX   INTEGER
      ACCESS   read-only
      STATUS   mandatory
      DESCRIPTION
                "total number of records allowed in database file."
      ::= {nvIpwanmap 1}

nvIpwanmapNumRec OBJECT-TYPE
      SYNTAX   INTEGER
      ACCESS   read-only
      STATUS   mandatory
      DESCRIPTION
                "number of records in use."
      ::= {nvIpwanmap 2}

nvIpwanmapTable OBJECT-TYPE
      SYNTAX   SEQUENCE OF NvIpwanmapEntry
      ACCESS   not-accessible
      STATUS   mandatory
      DESCRIPTION
               "ipwanmap file."
      ::= { nvIpwanmap 3 }

nvIpwanmapEntry OBJECT-TYPE
      SYNTAX   NvIpwanmapEntry
      ACCESS   not-accessible
      STATUS   mandatory
      DESCRIPTION
               "ipwanmap record."
      INDEX { nvIpwanmapIndex }
      ::= { nvIpwanmapTable 1 }

NvIpwanmapEntry ::=
      SEQUENCE {
      nvIpwanmapIndex
            INTEGER,
      nvIpwanmapIpaddr
            DisplayString,
      nvIpwanmapMask
            DisplayString,
      nvIpwanmapBcastcntl
            INTEGER,
      nvIpwanmapMtu
            INTEGER,
      nvIpwanmapMetric
            INTEGER,
      nvIpwanmapInactivty
            INTEGER,
      nvIpwanmapNetaddr
            DisplayString,
      nvIpwanmapUserdat
            DisplayString,
      nvIpwanmapRevacc
            INTEGER,
      nvIpwanmapRevcall
            INTEGER,
      nvIpwanmapTput
            INTEGER,
      nvIpwanmapPsize
            INTEGER,
      nvIpwanmapWsize
            INTEGER,
      nvIpwanmapCugtype
            INTEGER,
      nvIpwanmapCug
            INTEGER,
      nvIpwanmapRpoa
            INTEGER,
      nvIpwanmapPvcid
            INTEGER,
      nvIpwanmapFrpvc
            INTEGER,
      nvIpwanmapNetprot
            INTEGER,
      nvIpwanmapIpcp
            INTEGER,
      nvIpwanmapIdnum
            INTEGER,
      nvIpwanmapStatus
            INTEGER
                }

nvIpwanmapIndex OBJECT-TYPE
     SYNTAX   INTEGER
     ACCESS   read-only
     STATUS   mandatory
     DESCRIPTION
        "Index of ipwanmap record"
      ::= { nvIpwanmapEntry 1 }

nvIpwanmapIpaddr OBJECT-TYPE
     SYNTAX   DisplayString (SIZE (0..16))
     ACCESS   read-write
     STATUS   mandatory
     DESCRIPTION
"IP address of local LAN (ipaddr)
This field is a 15 byte character string in IP dotted address format.
"
     ::= { nvIpwanmapEntry 7 }

nvIpwanmapMask OBJECT-TYPE
     SYNTAX   DisplayString (SIZE (0..16))
     ACCESS   read-write
     STATUS   mandatory
     DESCRIPTION
"IP network mask (mask)
This field is a 15 byte character string in IP dotted address format.
"
     ::= { nvIpwanmapEntry 8 }

nvIpwanmapBcastcntl OBJECT-TYPE
     SYNTAX   INTEGER {
                no(1),      -- no
                yes(2)     -- yes (+1)
                }
     ACCESS   read-write
     STATUS   mandatory
     DESCRIPTION
"Send internally generated broadcasts (broadcast)
This field is a 15 byte character string in IP dotted address format.
"
     ::= { nvIpwanmapEntry 9 }

nvIpwanmapMtu OBJECT-TYPE
     SYNTAX   INTEGER (64..1600)
     ACCESS   read-write
     STATUS   mandatory
     DESCRIPTION
"Maximum frame length on this interface (mtu)
Default value is 1500."
     ::= { nvIpwanmapEntry 10 }

nvIpwanmapMetric OBJECT-TYPE
     SYNTAX   INTEGER (1..15)
     ACCESS   read-write
     STATUS   mandatory
     DESCRIPTION
"Cost of route (metric)
Default value is 1."
     ::= { nvIpwanmapEntry 11 }

nvIpwanmapInactivty OBJECT-TYPE
     SYNTAX   INTEGER (0..255)
     ACCESS   read-write
     STATUS   mandatory
     DESCRIPTION
"Inactivity timer (inactivty)."
     ::= { nvIpwanmapEntry 12 }

nvIpwanmapNetaddr OBJECT-TYPE
     SYNTAX   DisplayString (SIZE (0..16))
     ACCESS   read-write
     STATUS   mandatory
     DESCRIPTION
"Called address (netaddr)."
     ::= { nvIpwanmapEntry 13 }

nvIpwanmapUserdat OBJECT-TYPE
     SYNTAX   DisplayString (SIZE (0..20))
     ACCESS   read-write
     STATUS   mandatory
     DESCRIPTION
"User data (userdat) "
     ::= { nvIpwanmapEntry 14 }

nvIpwanmapRevacc OBJECT-TYPE
     SYNTAX   INTEGER {
                no(1),      -- no
                yes(2)     -- yes (+1)
                }
     ACCESS   read-write
     STATUS   mandatory
     DESCRIPTION
"Reverse charging accepted? (revacc)
Default value is no (0+1)."
     ::= { nvIpwanmapEntry 15 }

nvIpwanmapRevcall OBJECT-TYPE
     SYNTAX   INTEGER {
                no(1),      -- no
                yes(2)     -- yes (+1)
                }
     ACCESS   read-write
     STATUS   mandatory
     DESCRIPTION
"Reverse charging flag (revacc)
Default value is no (0+1)."
     ::= { nvIpwanmapEntry 16 }

nvIpwanmapTput OBJECT-TYPE
        SYNTAX   INTEGER {
                link(1),     -- link default (+1)
                bps75(4),     -- 75 bps
                bps150(5),     -- 150 bps
                bps300(6),     -- 300 bps
                bps600(7),     -- 600 bps
                bps1200(8),     -- 1200 bps
                bps2400(9),     -- 2400 bps
                bps4800(10),     -- 4800 bps
                bps9600(11),     -- 9600 bps
                bps19200(12),     -- 19200 bps
                bps48000(13)      -- 48000 bps
                }
     ACCESS   read-write
     STATUS   mandatory
     DESCRIPTION
"Throughput (tput)
Default value is link (0+1)."
     ::= { nvIpwanmapEntry 17 }

nvIpwanmapPsize OBJECT-TYPE
     SYNTAX   INTEGER {
                b16(5),     -- 16 bytes (+1)
                b32(6),     -- 32 bytes
                b64(7),     -- 64 bytes
                b128(8),     -- 128 bytes
                b256(9),     -- 256 bytes
                b512(10),     -- 512 bytes
                b1024(11),     -- 1024 bytes
                b2048(12),     -- 2048 bytes
                b4096(13)      -- 4096 bytes
                }
     ACCESS   read-write
     STATUS   mandatory
     DESCRIPTION
"Max packet size (psize)
Default value is 8+1."
     ::= { nvIpwanmapEntry 18 }

nvIpwanmapWsize OBJECT-TYPE
     SYNTAX   INTEGER (0..15)
     ACCESS   read-write
     STATUS   mandatory
     DESCRIPTION
"Max window size (wsize)
Default value is 0."
     ::= { nvIpwanmapEntry 19 }

nvIpwanmapCugtype OBJECT-TYPE
     SYNTAX   INTEGER {
                nocug(1),     -- No closed user group (+1)
                cug(2),     -- Closed user group
                cugog(3),     -- Closed user group with outgoing access
                bcug(4),     -- Bilateral closed user group
                bcugog(5)      -- Bilateral closed user group with outgoing access
                }
     ACCESS   read-write
     STATUS   mandatory
     DESCRIPTION
"Closed user group type (cugtype)
Default value is nocug (0+1)."
     ::= { nvIpwanmapEntry 20 }

nvIpwanmapCug OBJECT-TYPE
     SYNTAX   INTEGER (0..65535)
     ACCESS   read-write
     STATUS   mandatory
     DESCRIPTION
"Closed user group number (cug)
Default value is 0."
     ::= { nvIpwanmapEntry 21 }

nvIpwanmapRpoa OBJECT-TYPE
     SYNTAX   INTEGER (0..65535)
     ACCESS   read-write
     STATUS   mandatory
     DESCRIPTION
"RPOA number (rpoa)
Default value is 0."
     ::= { nvIpwanmapEntry 22 }

nvIpwanmapPvcid OBJECT-TYPE
     SYNTAX   INTEGER (0..65535)
     ACCESS   read-write
     STATUS   mandatory
     DESCRIPTION
"PVC ID - zero if SVC (pvcid)
Default value is 0."
     ::= { nvIpwanmapEntry 23 }

nvIpwanmapFrpvc OBJECT-TYPE
     SYNTAX   INTEGER (0..65535)
     ACCESS   read-write
     STATUS   mandatory
     DESCRIPTION
"Frame Relay PVC record (frpvc)
Default value is 0."
     ::= { nvIpwanmapEntry 24 }

nvIpwanmapNetprot OBJECT-TYPE
     SYNTAX   INTEGER {
                x25(1),     -- x25 network protocol (+1)
                slip(2),     -- slip network protocol
                frelay(3),     -- frame relay network protocol
                ppp(4)      -- ppp network protocol
                }
     ACCESS   read-write
     STATUS   mandatory
     DESCRIPTION
"Network protocol (netprot)
Default value is x25 (0+1)."
     ::= { nvIpwanmapEntry 25 }

nvIpwanmapIpcp OBJECT-TYPE
     SYNTAX   INTEGER (0..255)
     ACCESS   read-write
     STATUS   mandatory
     DESCRIPTION
"IPCPCONF record number (ipcp)
Default value is 0."
     ::= { nvIpwanmapEntry 26 }

nvIpwanmapIdnum OBJECT-TYPE
     SYNTAX   INTEGER (0..255)
     ACCESS   read-write
     STATUS   mandatory
     DESCRIPTION
"PDS 974 stringid of calling addr
Default value is 0."
     ::= { nvIpwanmapEntry 27 }

nvIpwanmapStatus OBJECT-TYPE
     SYNTAX   INTEGER {
                valid(1),
                invalid(2)
                }
     ACCESS   read-write
     STATUS   mandatory
     DESCRIPTION
           "Operation status. Add the record to the table (valid) or
           delete the record from the table (invalid)."
     ::= { nvIpwanmapEntry 36 }

nvIproute OBJECT IDENTIFIER ::= { nevadaIp 4 }

nvIprouteMaxRec OBJECT-TYPE
      SYNTAX   INTEGER
      ACCESS   read-only
      STATUS   mandatory
      DESCRIPTION
                "total number of records allowed in database file."
      ::= {nvIproute 1}

nvIprouteNumRec OBJECT-TYPE
      SYNTAX   INTEGER
      ACCESS   read-only
      STATUS   mandatory
      DESCRIPTION
                "number of records in use."
      ::= {nvIproute 2}

nvIprouteTable OBJECT-TYPE
      SYNTAX   SEQUENCE OF NvIprouteEntry
      ACCESS   not-accessible
      STATUS   mandatory
      DESCRIPTION
               "iproute file."
      ::= { nvIproute 3 }

nvIprouteEntry OBJECT-TYPE
      SYNTAX   NvIprouteEntry
      ACCESS   not-accessible
      STATUS   mandatory
      DESCRIPTION
               "iproute record."
      INDEX { nvIprouteIndex }
      ::= { nvIprouteTable 1 }

NvIprouteEntry ::=
      SEQUENCE {
      nvIprouteIndex
            INTEGER,
      nvIprouteIpaddr
            DisplayString,
      nvIprouteMask
            DisplayString,
      nvIprouteNexthop
            DisplayString,
      nvIprouteMetric
            INTEGER,
      nvIprouteStatus
            INTEGER
               }

nvIprouteIndex OBJECT-TYPE
     SYNTAX   INTEGER
     ACCESS   read-only
     STATUS   mandatory
     DESCRIPTION
        "Index of iproute record"
      ::= { nvIprouteEntry 1 }

nvIprouteIpaddr OBJECT-TYPE
     SYNTAX   DisplayString (SIZE (0..16))
     ACCESS   read-write
     STATUS   mandatory
     DESCRIPTION
"IP destination address (ipaddr)
This field is a 15 byte character string in IP dotted address format.
"
     ::= { nvIprouteEntry 3 }

nvIprouteMask OBJECT-TYPE
     SYNTAX   DisplayString (SIZE (0..16))
     ACCESS   read-write
     STATUS   mandatory
     DESCRIPTION
"IP destination mask (ipmask)
This field is a 15 byte character string in IP dotted address format.
"
     ::= { nvIprouteEntry 4 }

nvIprouteNexthop OBJECT-TYPE
     SYNTAX   DisplayString (SIZE (0..16))
     ACCESS   read-write
     STATUS   mandatory
     DESCRIPTION
"Next hop IP address (nexthop)
This field is a 15 byte character string in IP dotted address format.
"
     ::= { nvIprouteEntry 5 }

nvIprouteMetric OBJECT-TYPE
     SYNTAX   INTEGER (1..15)
     ACCESS   read-write
     STATUS   mandatory
     DESCRIPTION
"Cost of route (metric)
Default value is 1."
     ::= { nvIprouteEntry 6 }

nvIprouteStatus OBJECT-TYPE
     SYNTAX   INTEGER {
                valid(1),
                invalid(2)
                }
     ACCESS   read-write
     STATUS   mandatory
     DESCRIPTION
           "Operation status. Add the record to the table (valid) or
           delete the record from the table (invalid)."
     ::= { nvIprouteEntry 12 }



nvIprtstat OBJECT IDENTIFIER ::= { nevadaIp 5}

nvIprtstatMaxRec OBJECT-TYPE
      SYNTAX   INTEGER
      ACCESS   read-only
      STATUS   mandatory
      DESCRIPTION
                "total number of records allowed in database file."
      ::= {nvIprtstat 1}

nvIprtstatNumRec OBJECT-TYPE
      SYNTAX   INTEGER
      ACCESS   read-only
      STATUS   mandatory
      DESCRIPTION
                "number of records in use."
      ::= {nvIprtstat 2}

nvIprtstatTable OBJECT-TYPE
      SYNTAX   SEQUENCE OF NvIprtstatEntry
      ACCESS   not-accessible
      STATUS   mandatory
      DESCRIPTION
               "iprtstat file."
      ::= { nvIprtstat 3 }

nvIprtstatEntry OBJECT-TYPE
      SYNTAX   NvIprtstatEntry
      ACCESS   not-accessible
      STATUS   mandatory
      DESCRIPTION
               "iprtstat record."
      INDEX { nvIprtstatIndex }
      ::= { nvIprtstatTable 1 }

NvIprtstatEntry ::=
      SEQUENCE {
      nvIprtstatIndex
            INTEGER,
      nvIprtstatDest
            DisplayString,
      nvIprtstatInterface
            INTEGER,
      nvIprtstatMetric
            INTEGER,
      nvIprtstatNextHop
            DisplayString,
      nvIprtstatType
            INTEGER,
      nvIprtstatProto
            INTEGER
               }

nvIprtstatIndex OBJECT-TYPE
     SYNTAX   INTEGER
     ACCESS   read-only
     STATUS   mandatory
     DESCRIPTION
        "Index of iprtstat record"
      ::= { nvIprtstatEntry 1 }

nvIprtstatDest OBJECT-TYPE
     SYNTAX   DisplayString (SIZE (0..16))
     ACCESS   read-only
     STATUS   mandatory
     DESCRIPTION
"Destination address of this route (Dest)
"
     ::= { nvIprtstatEntry 2 }

nvIprtstatInterface OBJECT-TYPE
     SYNTAX   INTEGER {
                x25(1),     -- x.25 interface (+1)
                slip(2),     -- slip network interface
                frelay(3),     -- frame relay interface
                ppp(4),     -- ppp network inteface
                ether(5)      -- ethernet interface
                }
     ACCESS   read-only
     STATUS   mandatory
     DESCRIPTION
"Interface for route (Interface)
"
     ::= { nvIprtstatEntry 3 }

nvIprtstatMetric OBJECT-TYPE
     SYNTAX   INTEGER
     ACCESS   read-only
     STATUS   mandatory
     DESCRIPTION
"The routing metric for this route (Metric)
"
     ::= { nvIprtstatEntry 4 }

nvIprtstatNextHop OBJECT-TYPE
     SYNTAX   DisplayString (SIZE (0..16))
     ACCESS   read-only
     STATUS   mandatory
     DESCRIPTION
"The address of the next hop (NextHop)
"
     ::= { nvIprtstatEntry 5 }

nvIprtstatType OBJECT-TYPE
     SYNTAX   INTEGER {
                other(2),     -- none of the following (+1)
                invald(3),     -- an invalidated route
                direct(4),     -- route to directly connected network
                remote(5)      -- route to non-local network
                }
     ACCESS   read-only
     STATUS   mandatory
     DESCRIPTION
"The type of route (Type)
"
     ::= { nvIprtstatEntry 6 }

nvIprtstatProto OBJECT-TYPE
     SYNTAX   INTEGER {
                local(3),     -- manually configured entries (+1)
                icmp(5),     -- icmp redirect
                rip(9),      -- rip
                rad(17)      -- rad
                }
     ACCESS   read-only
     STATUS   mandatory
     DESCRIPTION
"The mechanism via which this route was learned (Proto)
"
     ::= { nvIprtstatEntry 7 }
--
--      icmpstat file
--
nvIcmpstat OBJECT IDENTIFIER ::= { nevadaIp 6}

nvIcmpstatMaxRec OBJECT-TYPE
      SYNTAX   INTEGER
      ACCESS   read-only
      STATUS   mandatory
      DESCRIPTION
                "total number of records allowed in database file."
      ::= {nvIcmpstat 1}

nvIcmpstatNumRec OBJECT-TYPE
      SYNTAX   INTEGER
      ACCESS   read-only
      STATUS   mandatory
      DESCRIPTION
                "number of records in use."
      ::= {nvIcmpstat 2}

nvIcmpstatTable OBJECT-TYPE
      SYNTAX   SEQUENCE OF NvIcmpstatEntry
      ACCESS   not-accessible
      STATUS   mandatory
      DESCRIPTION
               "icmpstat file."
      ::= { nvIcmpstat 3 }

nvIcmpstatEntry OBJECT-TYPE
      SYNTAX   NvIcmpstatEntry
      ACCESS   not-accessible
      STATUS   mandatory
      DESCRIPTION
               "icmpstat record."
      INDEX { nvIcmpstatIndex }
      ::= { nvIcmpstatTable 1 }

NvIcmpstatEntry ::=
      SEQUENCE {
      nvIcmpstatIndex
            INTEGER,
      nvIcmpstatInMsgs
            Counter,
      nvIcmpstatInErrs
            Counter,
      nvIcmpstatInDstUnrs
            Counter,
      nvIcmpstatInTmExcds
            Counter,
      nvIcmpstatInPrmPrbs
            Counter,
      nvIcmpstatInSrcQus
            Counter,
      nvIcmpstatInRdrcts
            Counter,
      nvIcmpstatInEchs
            Counter,
      nvIcmpstatInEchRps
            Counter,
      nvIcmpstatInTmSts
            Counter,
      nvIcmpstatInTmStRps
            Counter,
      nvIcmpstatInAdMs
            Counter,
      nvIcmpstatInAdMsRps
            Counter,
      nvIcmpstatOutMsgs
            Counter,
      nvIcmpstatOutErrs
            Counter,
      nvIcmpstatOutDstUnrs
            Counter,
      nvIcmpstatOutTmExcds
            Counter,
      nvIcmpstatOutPrmPrbs
            Counter,
      nvIcmpstatOutSrcQus
            Counter,
      nvIcmpstatOutRdrcts
            Counter,
      nvIcmpstatOutEchs
            Counter,
      nvIcmpstatOutEchRps
            Counter,
      nvIcmpstatOutTmSts
            Counter,
      nvIcmpstatOutTmStRps
            Counter,
      nvIcmpstatOutAdMs
            Counter,
      nvIcmpstatOutAdMsRps
            Counter,
      nvIcmpstatDtreset
            DisplayString
               }

nvIcmpstatIndex OBJECT-TYPE
     SYNTAX   INTEGER
     ACCESS   read-only
     STATUS   mandatory
     DESCRIPTION
        "Index of icmpstat record"
      ::= { nvIcmpstatEntry 1 }

nvIcmpstatInMsgs OBJECT-TYPE
     SYNTAX   Counter
     ACCESS   read-only
     STATUS   mandatory
     DESCRIPTION
"Input messages received (InMsgs)
The total number of ICMP messages which the
entity received. Note that this counter includes
all those counted by InErrs.
Statistic is zeroed at startup time."
     ::= { nvIcmpstatEntry 2 }

nvIcmpstatInErrs OBJECT-TYPE
     SYNTAX   Counter
     ACCESS   read-only
     STATUS   mandatory
     DESCRIPTION
"Input errors received (InErrs)
The number of ICMP messages which the entity
received but determined as having ICMP-specific
errors (bad ICMP checksums,bad length,etc.).
Statistic is zeroed at startup time."
     ::= { nvIcmpstatEntry 3 }

nvIcmpstatInDstUnrs OBJECT-TYPE
     SYNTAX   Counter
     ACCESS   read-only
     STATUS   mandatory
     DESCRIPTION
"Destination Unreachable messages recieved (InDstUnr)
The number of ICMP Destination Unreachable
messages received.
Statistic is zeroed at startup time."
     ::= { nvIcmpstatEntry 4 }

nvIcmpstatInTmExcds OBJECT-TYPE
     SYNTAX   Counter
     ACCESS   read-only
     STATUS   mandatory
     DESCRIPTION
"Time Exceeded messages received (InTmExcd)
The number of ICMP Time Exceeded messages
received.
Statistic is zeroed at startup time."
     ::= { nvIcmpstatEntry 5 }

nvIcmpstatInPrmPrbs OBJECT-TYPE
     SYNTAX   Counter
     ACCESS   read-only
     STATUS   mandatory
     DESCRIPTION
"Parameter Problem messages received (InPrmPrb)
The number of ICMP Parameter Problem messages
received.
Statistic is zeroed at startup time."
     ::= { nvIcmpstatEntry 6 }

nvIcmpstatInSrcQus OBJECT-TYPE
     SYNTAX   Counter
     ACCESS   read-only
     STATUS   mandatory
     DESCRIPTION
"Source Quench messages received (InSrcQu)
The number of ICMP Source Quench messages
received.
Statistic is zeroed at startup time."
     ::= { nvIcmpstatEntry 7 }

nvIcmpstatInRdrcts OBJECT-TYPE
     SYNTAX   Counter
     ACCESS   read-only
     STATUS   mandatory
     DESCRIPTION
"Redirect messages received (InRdrct)
The number of ICMP Redirect messages received.
Statistic is zeroed at startup time."
     ::= { nvIcmpstatEntry 8 }

nvIcmpstatInEchs OBJECT-TYPE
     SYNTAX   Counter
     ACCESS   read-only
     STATUS   mandatory
     DESCRIPTION
"Echo Request messages received (InEch)
The number of ICMP Echo (request) messages
received.
Statistic is zeroed at startup time."
     ::= { nvIcmpstatEntry 9 }

nvIcmpstatInEchRps OBJECT-TYPE
     SYNTAX   Counter
     ACCESS   read-only
     STATUS   mandatory
     DESCRIPTION
"Echo Reply messages received (InEchRp)
The number of ICMP Echo Reply messages received.
Statistic is zeroed at startup time."
     ::= { nvIcmpstatEntry 10 }

nvIcmpstatInTmSts OBJECT-TYPE
     SYNTAX   Counter
     ACCESS   read-only
     STATUS   mandatory
     DESCRIPTION
"Timestamp Request messages received (InTmSt)
The number of ICMP Timestamp (request) messages
received.
Statistic is zeroed at startup time."
     ::= { nvIcmpstatEntry 11 }

nvIcmpstatInTmStRps OBJECT-TYPE
     SYNTAX   Counter
     ACCESS   read-only
     STATUS   mandatory
     DESCRIPTION
"Timestamp Reply messages received (InTmStRp)
The number of ICMP Timestamp Reply messages
received.
Statistic is zeroed at startup time."
     ::= { nvIcmpstatEntry 12 }

nvIcmpstatInAdMs OBJECT-TYPE
     SYNTAX   Counter
     ACCESS   read-only
     STATUS   mandatory
     DESCRIPTION
"Address Mask Request messages received (InAdMs)
The number of ICMP Address Mask Request messages
received.
Statistic is zeroed at startup time."
     ::= { nvIcmpstatEntry 13 }

nvIcmpstatInAdMsRps OBJECT-TYPE
     SYNTAX   Counter
     ACCESS   read-only
     STATUS   mandatory
     DESCRIPTION
"Address Mask Reply messages received (InAdMsRp)
The number of ICMP Address Mask Reply messages
received.
Statistic is zeroed at startup time."
     ::= { nvIcmpstatEntry 14 }

nvIcmpstatOutMsgs OBJECT-TYPE
     SYNTAX   Counter
     ACCESS   read-only
     STATUS   mandatory
     DESCRIPTION
"Output messages attempted (OutMsgs)
The total number of ICMP messages which this
entity attempted to send. Note that this counter
includes all those counted by OutErrs.
Statistic is zeroed at startup time."
     ::= { nvIcmpstatEntry 15 }

nvIcmpstatOutErrs OBJECT-TYPE
     SYNTAX   Counter
     ACCESS   read-only
     STATUS   mandatory
     DESCRIPTION
"Output messages not sent (OutErrs)
The number of ICMP messages which this entity did
not send due to problems discovered within ICMP
such as lack of buffers. This value should not
include errors discovered outside the ICMP layer
such as the inability of IP to route the resultant
datagram. In some implementations there may be no
types of errors which contribute to this counter's
value.
Statistic is zeroed at startup time."
     ::= { nvIcmpstatEntry 16 }

nvIcmpstatOutDstUnrs OBJECT-TYPE
     SYNTAX   Counter
     ACCESS   read-only
     STATUS   mandatory
     DESCRIPTION
"Destination Unreachable messages sent (OutDstUnr)
The number of ICMP Destination Unreachable
messages sent.
Statistic is zeroed at startup time."
     ::= { nvIcmpstatEntry 17 }

nvIcmpstatOutTmExcds OBJECT-TYPE
     SYNTAX   Counter
     ACCESS   read-only
     STATUS   mandatory
     DESCRIPTION
"Time Exceeded messages sent (OutTmExcd)
The number of ICMP Time Exceeded messages sent.
Statistic is zeroed at startup time."
     ::= { nvIcmpstatEntry 18 }

nvIcmpstatOutPrmPrbs OBJECT-TYPE
     SYNTAX   Counter
     ACCESS   read-only
     STATUS   mandatory
     DESCRIPTION
"Parameter Problem messages sent (OutPrmPrb)
The number of ICMP Parameter Problem messages
sent.
Statistic is zeroed at startup time."
     ::= { nvIcmpstatEntry 19 }

nvIcmpstatOutSrcQus OBJECT-TYPE
     SYNTAX   Counter
     ACCESS   read-only
     STATUS   mandatory
     DESCRIPTION
"Source Quench messages sent (OutSrcQu)
The number of ICMP Source Quench messages sent.
Statistic is zeroed at startup time."
     ::= { nvIcmpstatEntry 20 }

nvIcmpstatOutRdrcts OBJECT-TYPE
     SYNTAX   Counter
     ACCESS   read-only
     STATUS   mandatory
     DESCRIPTION
"Redirect messages sent (OutRdrct)
The number of ICMP Redirect messages sent. For a
host,this object will always be zero,since hosts
do not send redirects.
Statistic is zeroed at startup time."
     ::= { nvIcmpstatEntry 21 }

nvIcmpstatOutEchs OBJECT-TYPE
     SYNTAX   Counter
     ACCESS   read-only
     STATUS   mandatory
     DESCRIPTION
"Echo Request messages sent (OutEch)
The number of ICMP Echo (request) messages sent.
Statistic is zeroed at startup time."
     ::= { nvIcmpstatEntry 22 }

nvIcmpstatOutEchRps OBJECT-TYPE
     SYNTAX   Counter
     ACCESS   read-only
     STATUS   mandatory
     DESCRIPTION
"Echo Reply messages sent (OutEchRp)
The number of ICMP Echo Reply messages sent.
Statistic is zeroed at startup time."
     ::= { nvIcmpstatEntry 23 }

nvIcmpstatOutTmSts OBJECT-TYPE
     SYNTAX   Counter
     ACCESS   read-only
     STATUS   mandatory
     DESCRIPTION
"Timestamp Request meessages sent (OutTmSt)
The number of ICMP Timestamp (request) messages
sent.
Statistic is zeroed at startup time."
     ::= { nvIcmpstatEntry 24 }

nvIcmpstatOutTmStRps OBJECT-TYPE
     SYNTAX   Counter
     ACCESS   read-only
     STATUS   mandatory
     DESCRIPTION
"Timestamp Reply messages sent (OutTmStRp)
The number of ICMP Timestamp Reply messages
sent.
Statistic is zeroed at startup time."
     ::= { nvIcmpstatEntry 25 }

nvIcmpstatOutAdMs OBJECT-TYPE
     SYNTAX   Counter
     ACCESS   read-only
     STATUS   mandatory
     DESCRIPTION
"Address Mask Request messages sent (OutAdMs)
The number of ICMP Address Mask Request messages
sent.
Statistic is zeroed at startup time."
     ::= { nvIcmpstatEntry 26 }

nvIcmpstatOutAdMsRps OBJECT-TYPE
     SYNTAX   Counter
     ACCESS   read-only
     STATUS   mandatory
     DESCRIPTION
"Address Mask Reply messages sent (OutAdMsRp)
The number of ICMP Address Mask Reply messages
sent.
Statistic is zeroed at startup time."
     ::= { nvIcmpstatEntry 27 }

nvIcmpstatDtreset OBJECT-TYPE
     SYNTAX   DisplayString (SIZE (0..20))
     ACCESS   read-only
     STATUS   mandatory
     DESCRIPTION
        "date & time statistics last reset"
      ::= { nvIcmpstatEntry 28 }

--
-- iptrunk
--
nvIptrunk OBJECT IDENTIFIER ::= { nevadaIp 7 }

nvIptrunkMaxRec OBJECT-TYPE
      SYNTAX   INTEGER
      ACCESS   read-only
      STATUS   mandatory
      DESCRIPTION
                "total number of records allowed in database file."
      ::= {nvIptrunk 1}

nvIptrunkNumRec OBJECT-TYPE
      SYNTAX   INTEGER
      ACCESS   read-only
      STATUS   mandatory
      DESCRIPTION
                "number of records in use."
      ::= {nvIptrunk 2}

nvIptrunkTable OBJECT-TYPE
      SYNTAX   SEQUENCE OF NvIptrunkEntry
      ACCESS   not-accessible
      STATUS   mandatory
      DESCRIPTION
               "iptrunk file."
      ::= { nvIptrunk 3 }

nvIptrunkEntry OBJECT-TYPE
      SYNTAX   NvIptrunkEntry
      ACCESS   not-accessible
      STATUS   mandatory
      DESCRIPTION
               "iptrunk record."
      INDEX { nvIptrunkIndex }
      ::= { nvIptrunkTable 1 }

NvIptrunkEntry ::=
      SEQUENCE {
      nvIptrunkIndex
            INTEGER,
      nvIptrunkIpaddr
            DisplayString,
      nvIptrunkDstiptrnk
            INTEGER,
      nvIptrunkStatus
            INTEGER
               }

nvIptrunkIndex OBJECT-TYPE
     SYNTAX   INTEGER
     ACCESS   read-only
     STATUS   mandatory
     DESCRIPTION
        "Index of iptrunk record"
      ::= { nvIptrunkEntry 1 }

nvIptrunkIpaddr OBJECT-TYPE
     SYNTAX   DisplayString (SIZE (0..16))
     ACCESS   read-write
     STATUS   mandatory
     DESCRIPTION
"IP destination address (ipaddr)
This field is a 15 byte character string in IP dotted address format.
"
     ::= { nvIptrunkEntry 3 }

nvIptrunkDstiptrnk OBJECT-TYPE
     SYNTAX   INTEGER (0..255)
     ACCESS   read-write
     STATUS   mandatory
     DESCRIPTION
"destenation lapb link (Dstiptrnk)
Default value is 0."
     ::= { nvIptrunkEntry 5 }

nvIptrunkStatus OBJECT-TYPE
     SYNTAX   INTEGER {
                valid(1),
                invalid(2)
                }
     ACCESS   read-write
     STATUS   mandatory
     DESCRIPTION
           "Operation status. Add the record to the table (valid) or
           delete the record from the table (invalid)."
     ::= { nvIptrunkEntry 9 }


--
--      ipcpconf
--
nvIpcpconf OBJECT IDENTIFIER ::= { nevadaIp 8 }

nvIpcpconfMaxRec OBJECT-TYPE
      SYNTAX   INTEGER
      ACCESS   read-only
      STATUS   mandatory
      DESCRIPTION
                "total number of records allowed in database file."
      ::= {nvIpcpconf 1}

nvIpcpconfNumRec OBJECT-TYPE
      SYNTAX   INTEGER
      ACCESS   read-only
      STATUS   mandatory
      DESCRIPTION
                "number of records in use."
      ::= {nvIpcpconf 2}

nvIpcpconfTable OBJECT-TYPE
      SYNTAX   SEQUENCE OF NvIpcpconfEntry
      ACCESS   not-accessible
      STATUS   mandatory
      DESCRIPTION
               "ipcpconf file."
      ::= { nvIpcpconf 3 }

nvIpcpconfEntry OBJECT-TYPE
      SYNTAX   NvIpcpconfEntry
      ACCESS   not-accessible
      STATUS   mandatory
      DESCRIPTION
               "ipcpconf record."
      INDEX { nvIpcpconfIndex }
      ::= { nvIpcpconfTable 1 }

NvIpcpconfEntry ::=
      SEQUENCE {
      nvIpcpconfIndex
            INTEGER,
      nvIpcpconfLcp
            INTEGER,
      nvIpcpconfCompress
            INTEGER,
      nvIpcpconfTest
            INTEGER,
      nvIpcpconfProfile
            DisplayString,
      nvIpcpconfDnsadd1
            DisplayString,
      nvIpcpconfDnsadd2
            DisplayString,
      nvIpcpconfNbnsadd1
            DisplayString,
      nvIpcpconfNbnsadd2
            DisplayString,
      nvIpcpconfStatus
            INTEGER
               }

nvIpcpconfIndex OBJECT-TYPE
     SYNTAX   INTEGER
     ACCESS   read-only
     STATUS   mandatory
     DESCRIPTION
"Index of Ipcpconf record."
     ::= { nvIpcpconfEntry 1 }

nvIpcpconfLcp OBJECT-TYPE
     SYNTAX   INTEGER (0..255)
     ACCESS   read-write
     STATUS   mandatory
     DESCRIPTION
"link control proto rec-num (lcp)
"
     ::= { nvIpcpconfEntry 2 }

nvIpcpconfCompress OBJECT-TYPE
     SYNTAX   INTEGER {
                none(1)                -- (+1)
                }
     ACCESS   read-write
     STATUS   mandatory
     DESCRIPTION
"compress flag."
     ::= { nvIpcpconfEntry 3 }

nvIpcpconfTest OBJECT-TYPE
     SYNTAX   INTEGER {
                no(1),          -- (+1)
                yes(2)
                }
     ACCESS   read-write
     STATUS   mandatory
     DESCRIPTION
"test mode."
     ::= { nvIpcpconfEntry 4 }


nvIpcpconfProfile OBJECT-TYPE
     SYNTAX   DisplayString (SIZE (0..20))
     ACCESS   read-write
     STATUS   mandatory
     DESCRIPTION
        "Ipcp Profile Name"
     ::= { nvIpcpconfEntry 5 }
     
nvIpcpconfDnsadd1 OBJECT-TYPE
     SYNTAX   DisplayString (SIZE (0..16))
     ACCESS   read-write
     STATUS   mandatory
     DESCRIPTION
     "IP address of primary DNS server"
     ::= { nvIpcpconfEntry  7}

nvIpcpconfDnsadd2 OBJECT-TYPE
     SYNTAX   DisplayString (SIZE (0..16))
     ACCESS   read-write
     STATUS   mandatory
     DESCRIPTION
     "IP address of secondary DNS server"
     ::= { nvIpcpconfEntry  8}

nvIpcpconfNbnsadd1 OBJECT-TYPE
     SYNTAX   DisplayString (SIZE (0..16))
     ACCESS   read-write
     STATUS   mandatory
     DESCRIPTION
     "IP address of primary NBNS server"
     ::= { nvIpcpconfEntry  9}

nvIpcpconfNbnsadd2  OBJECT-TYPE
     SYNTAX   DisplayString (SIZE (0..16))
     ACCESS   read-write
     STATUS   mandatory
     DESCRIPTION
     "IP address of secondary NBNS server"
     ::= { nvIpcpconfEntry  10}

nvIpcpconfStatus OBJECT-TYPE
     SYNTAX   INTEGER {
                valid(1),
                invalid(2)
                }
     ACCESS   read-write
     STATUS   mandatory
     DESCRIPTION
           "Operation status. Add the record to the table (valid) or
           delete the record from the table (invalid)."
     ::= { nvIpcpconfEntry 12 }


--
--
--      tcpstat file
--

nvTcpstat OBJECT IDENTIFIER ::= { nevadaTcp 1 }

nvTcpstatMaxRec OBJECT-TYPE
      SYNTAX   INTEGER
      ACCESS   read-only
      STATUS   mandatory
      DESCRIPTION
                "total number of records allowed in database file."
      ::= {nvTcpstat 1}

nvTcpstatNumRec OBJECT-TYPE
      SYNTAX   INTEGER
      ACCESS   read-only
      STATUS   mandatory
      DESCRIPTION
                "number of records in use."
      ::= {nvTcpstat 2}

nvTcpstatTable OBJECT-TYPE
      SYNTAX   SEQUENCE OF NvTcpstatEntry
      ACCESS   not-accessible
      STATUS   mandatory
      DESCRIPTION
               "tcpstat file."
      ::= {nvTcpstat 3}

nvTcpstatEntry OBJECT-TYPE
      SYNTAX   NvTcpstatEntry
      ACCESS   not-accessible
      STATUS   mandatory
      DESCRIPTION
               "tcpstat record, indexed by record number"
      INDEX {nvTcpstatIndex}
      ::= {nvTcpstatTable 1 }

NvTcpstatEntry ::=
      SEQUENCE {
        nvTcpstatIndex
                INTEGER,
        nvTcpstatConnattempts
                Counter,
        nvTcpstatAccepts
                Counter,
        nvTcpstatConnects
                Counter,
        nvTcpstatDrops
                Counter,
        nvTcpstatConndrops
                Counter,
        nvTcpstatCloseds
                Counter,
        nvTcpstatSegstimeds
                Counter,
        nvTcpstatRttupdateds
                Counter,
        nvTcpstatDelacks
                Counter,
        nvTcpstatTimeoutdrops
                Counter,
        nvTcpstatRexmttimeos
                Counter,
        nvTcpstatPersisttimeos
                Counter,
        nvTcpstatKeeptimeos
                Counter,
        nvTcpstatKeepprobes
                Counter,
        nvTcpstatKeepdrops
                Counter,
        nvTcpstatSndtotals
                Counter,
        nvTcpstatSndpacks
                Counter,
        nvTcpstatSndbytes
                Counter,
        nvTcpstatSndrexmitpacks
                Counter,
        nvTcpstatSndrexmitbytes
                Counter,
        nvTcpstatSndacks
                Counter,
        nvTcpstatSndprobes
                Counter,
        nvTcpstatSndurgs
                Counter,
        nvTcpstatSndwinups
                Counter,
        nvTcpstatSndctrls
                Counter,
        nvTcpstatRcvtotals
                Counter,
        nvTcpstatRcvpacks
                Counter,
        nvTcpstatRcvbytes
                Counter,
        nvTcpstatRcvbadsums
                Counter,
        nvTcpstatRcvbadoffs
                Counter,
        nvTcpstatRcvshorts
                Counter,
        nvTcpstatRcvduppacks
                Counter,
        nvTcpstatRcvdupbytes
                Counter,
        nvTcpstatRcvpartduppacks
                Counter,
        nvTcpstatRcvpartdupbytes
                Counter,
        nvTcpstatRcvoopacks
                Counter,
        nvTcpstatRcvoobytes
                Counter,
        nvTcpstatRcvpackafterwins
                Counter,
        nvTcpstatRcvbyteafterwins
                Counter,
        nvTcpstatRcvaftercloses
                Counter,
        nvTcpstatRcvwinprobes
                Counter,
        nvTcpstatRcvdupacks
                Counter,
        nvTcpstatRcvacktoomuchs
                Counter,
        nvTcpstatRcvackpacks
                Counter,
        nvTcpstatRcvackbytes
                Counter,
        nvTcpstatRcvwinupds
                Counter,
        nvTcpstatDtreset
		DisplayString
                }

nvTcpstatIndex OBJECT-TYPE
     SYNTAX   INTEGER
     ACCESS   read-only
     STATUS   mandatory
     DESCRIPTION
        "Index of tcpstat record"
     ::= {nvTcpstatEntry 1}

nvTcpstatConnattempts OBJECT-TYPE
     SYNTAX   Counter
     ACCESS   read-only
     STATUS   mandatory
     DESCRIPTION
        "connection attempts made."
     ::= {nvTcpstatEntry 2}

nvTcpstatAccepts OBJECT-TYPE
     SYNTAX   Counter
     ACCESS   read-only
     STATUS   mandatory
     DESCRIPTION
        "connections accepted."
     ::= {nvTcpstatEntry 3}

nvTcpstatConnects OBJECT-TYPE
     SYNTAX   Counter
     ACCESS   read-only
     STATUS   mandatory
     DESCRIPTION
        "connections established."
     ::= {nvTcpstatEntry 4}

nvTcpstatDrops OBJECT-TYPE
     SYNTAX   Counter
     ACCESS   read-only
     STATUS   mandatory
     DESCRIPTION
        "connections dropped."
     ::= {nvTcpstatEntry 5}

nvTcpstatConndrops OBJECT-TYPE
     SYNTAX   Counter
     ACCESS   read-only
     STATUS   mandatory
     DESCRIPTION
        "embryonic conns dropped."
     ::= {nvTcpstatEntry 6}

nvTcpstatCloseds OBJECT-TYPE
     SYNTAX   Counter
     ACCESS   read-only
     STATUS   mandatory
     DESCRIPTION
        "conn closed inlc drops."
     ::= {nvTcpstatEntry 7}

nvTcpstatSegstimeds OBJECT-TYPE
     SYNTAX   Counter
     ACCESS   read-only
     STATUS   mandatory
     DESCRIPTION
        "segs where tried to get rt."
     ::= {nvTcpstatEntry 8}

nvTcpstatRttupdateds OBJECT-TYPE
     SYNTAX   Counter
     ACCESS   read-only
     STATUS   mandatory
     DESCRIPTION
        "times succeeded."
     ::= {nvTcpstatEntry 9}

nvTcpstatDelacks OBJECT-TYPE
     SYNTAX   Counter
     ACCESS   read-only
     STATUS   mandatory
     DESCRIPTION
        "delayed acls sent."
     ::= {nvTcpstatEntry 10}

nvTcpstatTimeoutdrops OBJECT-TYPE
     SYNTAX   Counter
     ACCESS   read-only
     STATUS   mandatory
     DESCRIPTION
        "conn dropped in rxmt timeout."
     ::= {nvTcpstatEntry 11}

nvTcpstatRexmttimeos OBJECT-TYPE
     SYNTAX   Counter
     ACCESS   read-only
     STATUS   mandatory
     DESCRIPTION
        "retransmit timeouts."
     ::= {nvTcpstatEntry 12}

nvTcpstatPersisttimeos OBJECT-TYPE
     SYNTAX   Counter
     ACCESS   read-only
     STATUS   mandatory
     DESCRIPTION
        "persist timeouts."
     ::= {nvTcpstatEntry 13}

nvTcpstatKeeptimeos OBJECT-TYPE
     SYNTAX   Counter
     ACCESS   read-only
     STATUS   mandatory
     DESCRIPTION
        "keepalive timeouts."
     ::= {nvTcpstatEntry 14}

nvTcpstatKeepprobes OBJECT-TYPE
     SYNTAX   Counter
     ACCESS   read-only
     STATUS   mandatory
     DESCRIPTION
        "keepalive probes sent."
     ::= {nvTcpstatEntry 15}

nvTcpstatKeepdrops OBJECT-TYPE
     SYNTAX   Counter
     ACCESS   read-only
     STATUS   mandatory
     DESCRIPTION
        "connections dropped in keep alive."
     ::= {nvTcpstatEntry 16}

nvTcpstatSndtotals OBJECT-TYPE
     SYNTAX   Counter
     ACCESS   read-only
     STATUS   mandatory
     DESCRIPTION
        "total packets sent."
     ::= {nvTcpstatEntry 17}

nvTcpstatSndpacks OBJECT-TYPE
     SYNTAX   Counter
     ACCESS   read-only
     STATUS   mandatory
     DESCRIPTION
        "data packets sent."
     ::= {nvTcpstatEntry 18}

nvTcpstatSndbytes OBJECT-TYPE
     SYNTAX   Counter
     ACCESS   read-only
     STATUS   mandatory
     DESCRIPTION
        "data bytes sent."
     ::= {nvTcpstatEntry 19}

nvTcpstatSndrexmitpacks OBJECT-TYPE
     SYNTAX   Counter
     ACCESS   read-only
     STATUS   mandatory
     DESCRIPTION
        "data packetes retransmitted."
     ::= {nvTcpstatEntry 20}

nvTcpstatSndrexmitbytes OBJECT-TYPE
     SYNTAX   Counter
     ACCESS   read-only
     STATUS   mandatory
     DESCRIPTION
        "data bytes retransmitted."
     ::= {nvTcpstatEntry 21}

nvTcpstatSndacks OBJECT-TYPE
     SYNTAX   Counter
     ACCESS   read-only
     STATUS   mandatory
     DESCRIPTION
        "ack only packets sent."
     ::= {nvTcpstatEntry 22}

nvTcpstatSndprobes OBJECT-TYPE
     SYNTAX   Counter
     ACCESS   read-only
     STATUS   mandatory
     DESCRIPTION
        "window probes sent."
     ::= {nvTcpstatEntry 23}

nvTcpstatSndurgs OBJECT-TYPE
     SYNTAX   Counter
     ACCESS   read-only
     STATUS   mandatory
     DESCRIPTION
        "packets sent with urg only."
     ::= {nvTcpstatEntry 24}

nvTcpstatSndwinups OBJECT-TYPE
     SYNTAX   Counter
     ACCESS   read-only
     STATUS   mandatory
     DESCRIPTION
        "window update only packets."
     ::= {nvTcpstatEntry 25}

nvTcpstatSndctrls OBJECT-TYPE
     SYNTAX   Counter
     ACCESS   read-only
     STATUS   mandatory
     DESCRIPTION
        "control SYN|FIN|RST packets."
     ::= {nvTcpstatEntry 26}

nvTcpstatRcvtotals OBJECT-TYPE
     SYNTAX   Counter
     ACCESS   read-only
     STATUS   mandatory
     DESCRIPTION
        "total packets rcvd."
     ::= {nvTcpstatEntry 27}

nvTcpstatRcvpacks OBJECT-TYPE
     SYNTAX   Counter
     ACCESS   read-only
     STATUS   mandatory
     DESCRIPTION
        "packets rcvd in sequence."
     ::= {nvTcpstatEntry 28}

nvTcpstatRcvbytes OBJECT-TYPE
     SYNTAX   Counter
     ACCESS   read-only
     STATUS   mandatory
     DESCRIPTION
        "bytes rcvd in sequence."
     ::= {nvTcpstatEntry 29}

nvTcpstatRcvbadsums OBJECT-TYPE
     SYNTAX   Counter
     ACCESS   read-only
     STATUS   mandatory
     DESCRIPTION
        "packets rcvd with cksum errors."
     ::= {nvTcpstatEntry 30}

nvTcpstatRcvbadoffs OBJECT-TYPE
     SYNTAX   Counter
     ACCESS   read-only
     STATUS   mandatory
     DESCRIPTION
        "packets rcvd with bad offset."
     ::= {nvTcpstatEntry 31}

nvTcpstatRcvshorts OBJECT-TYPE
     SYNTAX   Counter
     ACCESS   read-only
     STATUS   mandatory
     DESCRIPTION
        "packets rcvd too short."
     ::= {nvTcpstatEntry 32}

nvTcpstatRcvduppacks OBJECT-TYPE
     SYNTAX   Counter
     ACCESS   read-only
     STATUS   mandatory
     DESCRIPTION
        "dup only packets rcvd."
     ::= {nvTcpstatEntry 33}

nvTcpstatRcvdupbytes OBJECT-TYPE
     SYNTAX   Counter
     ACCESS   read-only
     STATUS   mandatory
     DESCRIPTION
        "dup only bytes rcvd."
     ::= {nvTcpstatEntry 34}

nvTcpstatRcvpartduppacks OBJECT-TYPE
     SYNTAX   Counter
     ACCESS   read-only
     STATUS   mandatory
     DESCRIPTION
        "packets with some dup data."
     ::= {nvTcpstatEntry 35}

nvTcpstatRcvpartdupbytes OBJECT-TYPE
     SYNTAX   Counter
     ACCESS   read-only
     STATUS   mandatory
     DESCRIPTION
        "dup bytes in part dup packets."
     ::= {nvTcpstatEntry 36}

nvTcpstatRcvoopacks OBJECT-TYPE
     SYNTAX   Counter
     ACCESS   read-only
     STATUS   mandatory
     DESCRIPTION
        "out of order packets rcvd."
     ::= {nvTcpstatEntry 37}

nvTcpstatRcvoobytes OBJECT-TYPE
     SYNTAX   Counter
     ACCESS   read-only
     STATUS   mandatory
     DESCRIPTION
        "out of order bytes rcvd."
     ::= {nvTcpstatEntry 38}

nvTcpstatRcvpackafterwins OBJECT-TYPE
     SYNTAX   Counter
     ACCESS   read-only
     STATUS   mandatory
     DESCRIPTION
        "packets rcvd after window."
     ::= {nvTcpstatEntry 39}

nvTcpstatRcvbyteafterwins OBJECT-TYPE
     SYNTAX   Counter
     ACCESS   read-only
     STATUS   mandatory
     DESCRIPTION
        "bytes rcvd after window."
     ::= {nvTcpstatEntry 40}

nvTcpstatRcvaftercloses OBJECT-TYPE
     SYNTAX   Counter
     ACCESS   read-only
     STATUS   mandatory
     DESCRIPTION
        "packets rcvd after close."
     ::= {nvTcpstatEntry 41}

nvTcpstatRcvwinprobes OBJECT-TYPE
     SYNTAX   Counter
     ACCESS   read-only
     STATUS   mandatory
     DESCRIPTION
        "rcvd window probe packets."
     ::= {nvTcpstatEntry 42}

nvTcpstatRcvdupacks OBJECT-TYPE
     SYNTAX   Counter
     ACCESS   read-only
     STATUS   mandatory
     DESCRIPTION
        "rcvd duplicate acks."
     ::= {nvTcpstatEntry 43}

nvTcpstatRcvacktoomuchs OBJECT-TYPE
     SYNTAX   Counter
     ACCESS   read-only
     STATUS   mandatory
     DESCRIPTION
        "rcvd acks for unsent data."
     ::= {nvTcpstatEntry 44}

nvTcpstatRcvackpacks OBJECT-TYPE
     SYNTAX   Counter
     ACCESS   read-only
     STATUS   mandatory
     DESCRIPTION
        "rcvd ack packets."
     ::= {nvTcpstatEntry 45}

nvTcpstatRcvackbytes OBJECT-TYPE
     SYNTAX   Counter
     ACCESS   read-only
     STATUS   mandatory
     DESCRIPTION
        "bytes acked by rcvd acks."
     ::= {nvTcpstatEntry 46}

nvTcpstatRcvwinupds OBJECT-TYPE
     SYNTAX   Counter
     ACCESS   read-only
     STATUS   mandatory
     DESCRIPTION
        "rcvd window update pkts."
     ::= {nvTcpstatEntry 47}

nvTcpstatDtreset OBJECT-TYPE
     SYNTAX   DisplayString (SIZE (0..20))
     ACCESS   read-only
     STATUS   mandatory
     DESCRIPTION
       	"date & time statistics last reset"
     ::= { nvTcpstatEntry 48 }

--
--      tcpcnstat file
--

nvTcpcnstat OBJECT IDENTIFIER ::= { nevadaTcp 2 }

nvTcpcnstatMaxRec OBJECT-TYPE
      SYNTAX   INTEGER
      ACCESS   read-only
      STATUS   mandatory
      DESCRIPTION
                "total number of records allowed in database file."
      ::= {nvTcpcnstat 1}

nvTcpcnstatNumRec OBJECT-TYPE
      SYNTAX   INTEGER
      ACCESS   read-only
      STATUS   mandatory
      DESCRIPTION
                "number of records in use."
      ::= {nvTcpcnstat 2}

nvTcpcnstatTable OBJECT-TYPE
      SYNTAX   SEQUENCE OF NvTcpcnstatEntry
      ACCESS   not-accessible
      STATUS   mandatory
      DESCRIPTION
               "tcpcnstat file."
      ::= {nvTcpcnstat 3}

nvTcpcnstatEntry OBJECT-TYPE
      SYNTAX   NvTcpcnstatEntry
      ACCESS   not-accessible
      STATUS   mandatory
      DESCRIPTION
               "tcpcnstat record, indexed by record number"
      INDEX {nvTcpcnstatIndex}
      ::= {nvTcpcnstatTable 1 }

NvTcpcnstatEntry ::=
      SEQUENCE {
        nvTcpcnstatIndex
                INTEGER,
        nvTcpcnstatState
                INTEGER,
        nvTcpcnstatLocaladdr
                DisplayString,
        nvTcpcnstatLocalport
                INTEGER,
        nvTcpcnstatRemaddr
                DisplayString,
        nvTcpcnstatRemport
                INTEGER,
	nvTcpcnstatDtreset
		DisplayString
                }

nvTcpcnstatIndex OBJECT-TYPE
     SYNTAX   INTEGER
     ACCESS   read-only
     STATUS   mandatory
     DESCRIPTION
        "Index of tcpcnstat record"
     ::= {nvTcpcnstatEntry 1}

nvTcpcnstatState OBJECT-TYPE
     SYNTAX   INTEGER {
                null(1),        -- (+1)
                closed(2),
                listen(3),
                syncsent(4),
                syncrcv(5),
                established(6),
                wait1(7),
                wait2(8),
                closewait(9),
                lastack(10),
                closing(11),
                timewait(12)
                }
     ACCESS   read-only
     STATUS   mandatory
     DESCRIPTION
        "Connection state."
     ::= {nvTcpcnstatEntry 2}

nvTcpcnstatLocaladdr OBJECT-TYPE
     SYNTAX   DisplayString (SIZE (0..16))
     ACCESS   read-only
     STATUS   mandatory
     DESCRIPTION
        "Local host address."
     ::= {nvTcpcnstatEntry 3}

nvTcpcnstatLocalport OBJECT-TYPE
     SYNTAX   INTEGER
     ACCESS   read-only
     STATUS   mandatory
     DESCRIPTION
        "Local port."
     ::= {nvTcpcnstatEntry 4}

nvTcpcnstatRemaddr OBJECT-TYPE
     SYNTAX   DisplayString (SIZE (0..16))
     ACCESS   read-only
     STATUS   mandatory
     DESCRIPTION
        "Remote host address."
     ::= {nvTcpcnstatEntry 5}

nvTcpcnstatRemport OBJECT-TYPE
     SYNTAX   INTEGER
     ACCESS   read-only
     STATUS   mandatory
     DESCRIPTION
        "Remote port."
     ::= {nvTcpcnstatEntry 6}

nvTcpcnstatDtreset OBJECT-TYPE
     SYNTAX   DisplayString (SIZE (0..20))
     ACCESS   read-only
     STATUS   mandatory
     DESCRIPTION
       	"date & time statistics last reset"
     ::= { nvTcpcnstatEntry 7 }

--
--      tcprstat file
--

nvTcprstat OBJECT IDENTIFIER ::= { nevadaTcp 3 }

nvTcprstatMaxRec OBJECT-TYPE
      SYNTAX   INTEGER
      ACCESS   read-only
      STATUS   mandatory
      DESCRIPTION
                "total number of records allowed in database file."
      ::= {nvTcprstat 1}

nvTcprstatNumRec OBJECT-TYPE
      SYNTAX   INTEGER
      ACCESS   read-only
      STATUS   mandatory
      DESCRIPTION
                "number of records in use."
      ::= {nvTcprstat 2}

nvTcprstatTable OBJECT-TYPE
      SYNTAX   SEQUENCE OF NvTcprstatEntry
      ACCESS   not-accessible
      STATUS   mandatory
      DESCRIPTION
               "tcprstat file."
      ::= {nvTcprstat 3}

nvTcprstatEntry OBJECT-TYPE
      SYNTAX   NvTcprstatEntry
      ACCESS   not-accessible
      STATUS   mandatory
      DESCRIPTION
               "tcprstat record, indexed by record number"
      INDEX {nvTcprstatIndex}
      ::= {nvTcprstatTable 1 }

NvTcprstatEntry ::=
      SEQUENCE {
        nvTcprstatIndex
                INTEGER,
        nvTcprstatInport
                INTEGER,
        nvTcprstatOutport
                INTEGER,
        nvTcprstatService
                DisplayString,
	nvTcprstatDtreset
		DisplayString
        }

nvTcprstatIndex OBJECT-TYPE
     SYNTAX   INTEGER
     ACCESS   read-only
     STATUS   mandatory
     DESCRIPTION
        "Index of tcprstat record"
     ::= {nvTcprstatEntry 1}

nvTcprstatInport OBJECT-TYPE
     SYNTAX   INTEGER
     ACCESS   read-only
     STATUS   mandatory
     DESCRIPTION
        "Port number to check for traffic from IP."
     ::= {nvTcprstatEntry 2}

nvTcprstatOutport OBJECT-TYPE
     SYNTAX   INTEGER
     ACCESS   read-only
     STATUS   mandatory
     DESCRIPTION
        "Port number to route call to if inport match."
     ::= {nvTcprstatEntry 3}

nvTcprstatService OBJECT-TYPE
     SYNTAX   DisplayString (SIZE (0..10))
     ACCESS   read-only
     STATUS   mandatory
     DESCRIPTION
        "component using the port number."
     ::= {nvTcprstatEntry 4}

nvTcprstatDtreset OBJECT-TYPE
     SYNTAX   DisplayString (SIZE (0..20))
     ACCESS   read-only
     STATUS   mandatory
     DESCRIPTION
       	"date & time statistics last reset"
     ::= { nvTcprstatEntry 5 }


---
--- Tslotconf file 
---

nvTslotconf OBJECT IDENTIFIER ::= { nevadaTcp 6 }    --AF

nvTslotconfMaxRec OBJECT-TYPE                        --AF
      SYNTAX   INTEGER				     --AF
      ACCESS   read-only			     --AF
      STATUS   mandatory			     --AF
      DESCRIPTION				     --AF
                "total number of records allowed in database file."
      ::= {nvTslotconf 1}                            --AF

nvTslotconfNumRec OBJECT-TYPE                        --AF
      SYNTAX   INTEGER				     --AF
      ACCESS   read-only			     --AF
      STATUS   mandatory			     --AF
      DESCRIPTION				     --AF
                "number of records in use."	     --AF
      ::= {nvTslotconf 2}                            --AF 

nvTslotconfTable OBJECT-TYPE                         --AF
      SYNTAX   SEQUENCE OF NvTslotconfEntry          --AF
      ACCESS   not-accessible			     --AF
      STATUS   mandatory			     --AF
      DESCRIPTION				     --AF
               "tslotconf file."                     --AF 
      ::= {nvTslotconf 3}                            --AF

nvTslotconfEntry OBJECT-TYPE			     --AF
      SYNTAX   NvTslotconfEntry                      --AF
      ACCESS   not-accessible			     --AF
      STATUS   mandatory			     --AF
      DESCRIPTION				     --AF
               "tslotconf record, indexed by record number"
      INDEX {nvTslotconfIndex}                       --AF 
      ::= {nvTslotconfTable 1 }                      --AF 

NvTslotconfEntry ::=                                 --AF
      SEQUENCE {				     --AF
        nvTslotconfIndex
                INTEGER,
        nvTslotconfName                              --AF
                DisplayString,                       --AF
        nvTslotconfOrigans                           --AF
                INTEGER,                             --AF
        nvTslotconfTcpprof                           --AF
                DisplayString,                       --AF
	nvTslotconfReserve1
		DisplayString,
	nvTslotconfReserve2
		DisplayString,
        nvTslotconfMaxrxbuf
                INTEGER,
        nvTslotconfEnable
                INTEGER,
        nvTslotconfStatus
                INTEGER,
	nvTslotconfVersion
		INTEGER,
        nvTslotconfPeertsid
                INTEGER,
        nvTslotconfPeeripadr
                DisplayString
        }

nvTslotconfIndex OBJECT-TYPE                         --AF
     SYNTAX   INTEGER				     --AF
     ACCESS   read-only				     --AF
     STATUS   mandatory				     --AF
     DESCRIPTION				     --AF
        "Index of tslotconf record"                  --AF
     ::= {nvTslotconfEntry 1}			     --AF

nvTslotconfName OBJECT-TYPE                          --AF 
     SYNTAX   DisplayString (SIZE (0..6))	     --AF
     ACCESS   read-only			     	--AF
     STATUS   mandatory				     --AF
     DESCRIPTION				     --AF
"Name of TSLOT instance."                            --AF 
     ::= { nvTslotconfEntry 2 }			     --AF
     
nvTslotconfOrigans OBJECT-TYPE                       --AF
     SYNTAX   INTEGER{				     --AF
                 originate(2),                       --AF +1
		 answer(3)                           --AF
		 }                                   --AF 
     ACCESS   read-write				     --AF
     STATUS   mandatory				     --AF
     DESCRIPTION				     --AF
        "Originate or answer."                       --AF
     ::= {nvTslotconfEntry 3}			     --AF
     
nvTslotconfTcpprof OBJECT-TYPE                      --AF 
     SYNTAX   DisplayString (SIZE (0..8))	     --AF
     ACCESS   read-write			     --AF
     STATUS   mandatory				     --AF
     DESCRIPTION				     --AF
"TCP profile name."                      	     --AF
     ::= { nvTslotconfEntry 4 }                      --AF

nvTslotconfReserve1 OBJECT-TYPE
     SYNTAX   DisplayString (SIZE (0..2))
     ACCESS   read-only
     STATUS   mandatory
     DESCRIPTION
	"OBSOLETE - removed field."
     ::= { nvTslotconfEntry 5 }

nvTslotconfReserve2 OBJECT-TYPE
     SYNTAX   DisplayString (SIZE (0..2))
     ACCESS   read-write
     STATUS   mandatory
     DESCRIPTION
	"OBSOLETE - removed field."
     ::= { nvTslotconfEntry 6 }

nvTslotconfMaxrxbuf OBJECT-TYPE
     SYNTAX   INTEGER (1..9400)
     ACCESS   read-write
     STATUS   mandatory
     DESCRIPTION
        "Maximum receive buffer space."
     ::= {nvTslotconfEntry 7}

nvTslotconfEnable OBJECT-TYPE                        --AF
     SYNTAX   INTEGER{				     --AF
                 yes(2),                            --AF +1
		 no(3)                               --AF
		 }                                   --AF 
     ACCESS   read-write				     --AF
     STATUS   mandatory				     --AF
     DESCRIPTION				     --AF
        "Is this TSLOT enabled."                     --AF
     ::= {nvTslotconfEntry 8}			     --AF
     
nvTslotconfStatus OBJECT-TYPE                        --AF
     SYNTAX   INTEGER {				     --AF
                valid(1),			     --AF
                invalid(2)			     --AF
                }				     --AF
     ACCESS   read-write			     --AF
     STATUS   mandatory				     --AF
     DESCRIPTION				     --AF
           "Operation status. Add the record to the table (valid) or
           delete the record from the table (invalid)."
     ::= { nvTslotconfEntry 9 }                      --AF

nvTslotconfVersion OBJECT-TYPE
     SYNTAX   INTEGER {
                ver0(2),
                ver1(3)
                }
     ACCESS   read-write
     STATUS   mandatory
     DESCRIPTION
	"TSLOT version number to behave as."
     ::= { nvTslotconfEntry 10 }

nvTslotconfPeertsid OBJECT-TYPE
     SYNTAX   INTEGER
     ACCESS   read-write
     STATUS   mandatory
     DESCRIPTION
	"TSLOT ID on destination side.
	Only used if origans = originate."
     ::= { nvTslotconfEntry 11 }
     
 nvTslotconfPeeripadr OBJECT-TYPE
     SYNTAX   DisplayString (SIZE (0..16))
     ACCESS   read-write
     STATUS   mandatory
     DESCRIPTION
	"IP address if destination machine.
	Only used if origans = originate."
     ::= { nvTslotconfEntry 12 }

---AF
--- Tslotstat file
---AF
	
nvTslotstat OBJECT IDENTIFIER ::= { nevadaTcp 7 }    --AF

nvTslotstatMaxRec OBJECT-TYPE                        --AF
      SYNTAX   INTEGER				     --AF
      ACCESS   read-only			     --AF
      STATUS   mandatory			     --AF
      DESCRIPTION				     --AF
                "total number of records allowed in database file."
      ::= {nvTslotstat 1}                            --AF

nvTslotstatNumRec OBJECT-TYPE                        --AF
      SYNTAX   INTEGER				     --AF
      ACCESS   read-only			     --AF
      STATUS   mandatory			     --AF
      DESCRIPTION				     --AF
                "number of records in use."	     --AF
      ::= {nvTslotstat 2}                            --AF 

nvTslotstatTable OBJECT-TYPE                         --AF
      SYNTAX   SEQUENCE OF NvTslotstatEntry          --AF
      ACCESS   not-accessible			     --AF
      STATUS   mandatory			     --AF
      DESCRIPTION				     --AF
               "tslotstat file."                     --AF 
      ::= {nvTslotstat 3}                            --AF

nvTslotstatEntry OBJECT-TYPE			     --AF
      SYNTAX   NvTslotstatEntry                      --AF
      ACCESS   not-accessible			     --AF
      STATUS   mandatory			     --AF
      DESCRIPTION				     --AF
               "tslotstat record, indexed by record number"
      INDEX {nvTslotstatIndex}                       --AF 
      ::= {nvTslotstatTable 1 }                      --AF 

NvTslotstatEntry ::=                                 --AF
      SEQUENCE {				     --AF
        nvTslotstatIndex                             --AF
                INTEGER,			     --AF
        nvTslotstatName                              --AF
                DisplayString,                       --AF
        nvTslotstatService                           --AF
                INTEGER,                             --AF
        nvTslotstatServiceid                         --AF
                DisplayString,                       --AF
        nvTslotstatOpstate                           --AF
                INTEGER,                             --AF
        nvTslotstatRemipaddr                         --AF
                DisplayString,                       --AF
        nvTslotstatRemtsid                           --AF
                INTEGER,                             --AF
        nvTslotstatTcpcn                             --AF
                INTEGER,                             --AF
        nvTslotstatNumcon                            --AF
                INTEGER,                             --AF
        nvTslotstatNumfailcn                         --AF
                INTEGER,                             --AF
        nvTslotstatTotrxfrm                          --AF
                INTEGER,                             --AF
        nvTslotstatTottxfrm                          --AF
                INTEGER,                             --AF
        nvTslotstatCurtxfrm                          --AF
                INTEGER,                             --AF
        nvTslotstatCurrxfrm                          --AF
                INTEGER,                             --AF
        nvTslotstatCurdrprx                          --AF
                INTEGER,                             --AF
	nvTslotstatDtreset
		DisplayString                              
        }

nvTslotstatIndex OBJECT-TYPE                         --AF
     SYNTAX   INTEGER				     --AF
     ACCESS   read-only				     --AF
     STATUS   mandatory				     --AF
     DESCRIPTION				     --AF
        "Index of tslotconf record"                  --AF
     ::= {nvTslotstatEntry 1}			     --AF

nvTslotstatName OBJECT-TYPE                          --AF 
     SYNTAX   DisplayString (SIZE (0..6))	     --AF
     ACCESS   read-only			     --AF
     STATUS   mandatory				     --AF
     DESCRIPTION				     --AF
"Name of TSLOT instance."                            --AF 
     ::= { nvTslotstatEntry 2 }			     --AF
     
nvTslotstatService OBJECT-TYPE                       --AF
     SYNTAX   INTEGER				     --AF
     ACCESS   read-only				     --AF
     STATUS   mandatory				     --AF
     DESCRIPTION				     --AF
        "Connected component id."                    --AF
     ::= {nvTslotstatEntry 3}			     --AF
     
 nvTslotstatServiceid OBJECT-TYPE                    --AF 
     SYNTAX   DisplayString (SIZE (0..8))	     --AF
     ACCESS   read-only			     --AF
     STATUS   mandatory				     --AF
     DESCRIPTION				     --AF
"Service instance name."                      	     --AF
     ::= { nvTslotstatEntry 4 }                      --AF
     
nvTslotstatOpstate OBJECT-TYPE                       --AF
     SYNTAX   INTEGER{				     --AF
                disabled(1),                         --AF
		idle(2),			     --AF
		conreq(3),			     --AF
		conwait(4),			     --AF
		conn(5)				     --AF
		}				     --AF
     ACCESS   read-only				     --AF
     STATUS   mandatory				     --AF
     DESCRIPTION				     --AF
        "TSLOT instance operational state."          --AF
     ::= {nvTslotstatEntry 5}			     --AF
     
 nvTslotstatRemipaddr OBJECT-TYPE                    --AF 
     SYNTAX   DisplayString (SIZE (0..16))	     --AF
     ACCESS   read-only			     --AF
     STATUS   mandatory				     --AF
     DESCRIPTION				     --AF
"Remote machine IP address.              	     
This field is a 15 byte character string in IP dotted address format.
"
     ::= { nvTslotstatEntry 6 }

nvTslotstatRemtsid OBJECT-TYPE                       --AF
     SYNTAX   INTEGER				     --AF
     ACCESS   read-only				     --AF
     STATUS   mandatory				     --AF
     DESCRIPTION				     --AF
        "TSLOT ID on remote machine."                --AF
     ::= {nvTslotstatEntry 7}			     --AF

nvTslotstatTcpcn OBJECT-TYPE                         --AF
     SYNTAX   INTEGER				     --AF
     ACCESS   read-only				     --AF
     STATUS   mandatory				     --AF
     DESCRIPTION				     --AF
        "TCPCNSTAT file record number."              --AF
     ::= {nvTslotstatEntry 8}			     --AF

nvTslotstatNumcon OBJECT-TYPE                        --AF
     SYNTAX   INTEGER				     --AF
     ACCESS   read-only				     --AF
     STATUS   mandatory				     --AF
     DESCRIPTION				     --AF
        "Number of TCP connections."                 --AF
     ::= {nvTslotstatEntry 9}			     --AF

nvTslotstatNumfailcn OBJECT-TYPE                     --AF
     SYNTAX   INTEGER				     --AF
     ACCESS   read-only				     --AF
     STATUS   mandatory				     --AF
     DESCRIPTION				     --AF
   "Number of failed attempts at TCP connection."    --AF
     ::= {nvTslotstatEntry 10}			     --AF
     
nvTslotstatTotrxfrm OBJECT-TYPE                      --AF
     SYNTAX   INTEGER				     --AF
     ACCESS   read-only				     --AF
     STATUS   mandatory				     --AF
     DESCRIPTION				     --AF
   "Total number of received frames."                --AF
     ::= {nvTslotstatEntry 11}			     --AF
     
nvTslotstatTottxfrm OBJECT-TYPE                      --AF
     SYNTAX   INTEGER				     --AF
     ACCESS   read-only				     --AF
     STATUS   mandatory				     --AF
     DESCRIPTION				     --AF
   "Total number of transmitted frames."             --AF
     ::= {nvTslotstatEntry 12}			     --AF
     
nvTslotstatCurtxfrm OBJECT-TYPE                      --AF
     SYNTAX   INTEGER				     --AF
     ACCESS   read-only				     --AF
     STATUS   mandatory				     --AF
     DESCRIPTION				     --AF
"Total number of transmitted frames on current TCP connection."             --AF
     ::= {nvTslotstatEntry 13}			     --AF
     
nvTslotstatCurrxfrm OBJECT-TYPE                      --AF
     SYNTAX   INTEGER				     --AF
     ACCESS   read-only				     --AF
     STATUS   mandatory				     --AF
     DESCRIPTION				     --AF
   "Total number of received frames on current TCP connection."             --AF
     ::= {nvTslotstatEntry 14}			     --AF
     
nvTslotstatCurdrprx OBJECT-TYPE                      --AF
     SYNTAX   INTEGER 				     --AF
     ACCESS   read-only			     --AF
     STATUS   mandatory				     --AF
     DESCRIPTION				     --AF
       "Number of dropped frames due to ins buffer space."   --AF
     ::= { nvTslotstatEntry 15 }                     --AF

nvTslotstatDtreset OBJECT-TYPE
     SYNTAX   DisplayString (SIZE (0..20))
     ACCESS   read-only
     STATUS   mandatory
     DESCRIPTION
       	"date & time statistics last reset"
     ::= { nvTslotstatEntry 16 }


---AF
--- Tcpprof file
---AF
	
nvTcpprof OBJECT IDENTIFIER ::= { nevadaTcp 8 }      --AF

nvTcpprofMaxRec OBJECT-TYPE                          --AF
      SYNTAX   INTEGER				     --AF
      ACCESS   read-only			     --AF
      STATUS   mandatory			     --AF
      DESCRIPTION				     --AF
                "total number of records allowed in database file."
      ::= {nvTcpprof 1}                              --AF

nvTcpprofNumRec OBJECT-TYPE                          --AF
      SYNTAX   INTEGER				     --AF
      ACCESS   read-only			     --AF
      STATUS   mandatory			     --AF
      DESCRIPTION				     --AF
                "number of records in use."	     --AF
      ::= {nvTcpprof 2}                              --AF 

nvTcpprofTable OBJECT-TYPE                           --AF
      SYNTAX   SEQUENCE OF NvTcpprofEntry            --AF
      ACCESS   not-accessible			     --AF
      STATUS   mandatory			     --AF
      DESCRIPTION				     --AF
               "tcpprof file."                       --AF 
      ::= {nvTcpprof 3}                              --AF

nvTcpprofEntry OBJECT-TYPE			     --AF
      SYNTAX   NvTcpprofEntry                        --AF
      ACCESS   not-accessible			     --AF
      STATUS   mandatory			     --AF
      DESCRIPTION				     --AF
               "tcpprof record, indexed by record number"
      INDEX {nvTcpprofIndex}                         --AF 
      ::= {nvTcpprofTable 1 }                        --AF 

NvTcpprofEntry ::=                                   --AF
      SEQUENCE {				     --AF
        nvTcpprofIndex                               --AF
                INTEGER,			     --AF
        nvTcpprofProfname                            --AF
                DisplayString,                       --AF
        nvTcpprofKeepidle                            --AF
                INTEGER,                             --AF
        nvTcpprofKeepprbs                            --AF
                DisplayString,                       --AF
        nvTcpprofKeepintvl                           --AF
                INTEGER,                             --AF
        nvTcpprofStatus                              --AF
                INTEGER                              --AF
        }

nvTcpprofIndex OBJECT-TYPE                           --AF
     SYNTAX   INTEGER				     --AF
     ACCESS   read-only				     --AF
     STATUS   mandatory				     --AF
     DESCRIPTION				     --AF
        "Index of tslotconf record"                  --AF
     ::= {nvTcpprofEntry 1}			     --AF

nvTcpprofProfname OBJECT-TYPE                        --AF 
     SYNTAX   DisplayString (SIZE (0..8))	     --AF
     ACCESS   read-write			     --AF
     STATUS   mandatory				     --AF
     DESCRIPTION				     --AF
      "Nmae of TCP profile."                         --AF 
     ::= { nvTcpprofEntry 2 }			     --AF
     
nvTcpprofKeepidle OBJECT-TYPE                        --AF
     SYNTAX   INTEGER				     --AF
     ACCESS   read-write				     --AF
     STATUS   mandatory				     --AF
     DESCRIPTION				     --AF
  "Idle time in seconds before keepalive probe."     --AF
     ::= {nvTcpprofEntry 3}			     --AF
     
 nvTcpprofKeepprbs OBJECT-TYPE                       --AF 
     SYNTAX   INTEGER                    	     --AF
     ACCESS   read-write			     --AF
     STATUS   mandatory				     --AF
     DESCRIPTION				     --AF
   "Number of unanswered probes before reset."       --AF
     ::= { nvTcpprofEntry 4 }                        --AF
     
nvTcpprofKeepintvl OBJECT-TYPE                       --AF
     SYNTAX   INTEGER				     --AF
     ACCESS   read-write				     --AF
     STATUS   mandatory				     --AF
     DESCRIPTION				     --AF
  "Interval in seconds between keppalive probes."    --AF
     ::= {nvTcpprofEntry 5}			     --AF
     
nvTcpprofStatus OBJECT-TYPE                        --AF
     SYNTAX   INTEGER {				     --AF
                valid(1),			     --AF
                invalid(2)			     --AF
                }				     --AF
     ACCESS   read-write			     --AF
     STATUS   mandatory				     --AF
     DESCRIPTION				     --AF
           "Operation status. Add the record to the table (valid) or
           delete the record from the table (invalid)."
     ::= { nvTcpprofEntry 6 }                      --AF


--
--      nsock file
--

nvNsockconf OBJECT IDENTIFIER ::= { nevadaTcp 4 }

nvNsockconfMaxRec OBJECT-TYPE
      SYNTAX   INTEGER
      ACCESS   read-only
      STATUS   mandatory
      DESCRIPTION
                "total number of records allowed in database file."
      ::= {nvNsockconf 1}

nvNsockconfNumRec OBJECT-TYPE
      SYNTAX   INTEGER
      ACCESS   read-only
      STATUS   mandatory
      DESCRIPTION
                "number of records in use."
      ::= {nvNsockconf 2}

nvNsockconfTable OBJECT-TYPE
      SYNTAX   SEQUENCE OF NvNsockconfEntry
      ACCESS   not-accessible
      STATUS   mandatory
      DESCRIPTION
               "tcpstat file."
      ::= {nvNsockconf 3}

nvNsockconfEntry OBJECT-TYPE
      SYNTAX   NvNsockconfEntry
      ACCESS   not-accessible
      STATUS   mandatory
      DESCRIPTION
               "tcpstat record, indexed by record number"
      INDEX {nvNsockconfIndex}
      ::= {nvNsockconfTable 1 }

NvNsockconfEntry ::=
      SEQUENCE {
        nvNsockconfIndex
                INTEGER,
        nvNsockconfMaxconn
                INTEGER,
        nvNsockconfStatus
                INTEGER,
	nvNsockconfDefport
		INTEGER
	}

nvNsockconfIndex OBJECT-TYPE
     SYNTAX   INTEGER
     ACCESS   read-only
     STATUS   mandatory
     DESCRIPTION
        "Index of nsockconf record"
     ::= {nvNsockconfEntry 1}

nvNsockconfMaxconn OBJECT-TYPE
     SYNTAX   INTEGER
     ACCESS   read-write
     STATUS   mandatory
     DESCRIPTION
        "Maximum number of connections."
     ::= {nvNsockconfEntry 2}

nvNsockconfStatus OBJECT-TYPE
     SYNTAX   INTEGER {
                enable(1),
                disable(2)
                }
     ACCESS   read-write
     STATUS   mandatory
     DESCRIPTION
        "nsockconf record"
     ::= {nvNsockconfEntry 3}

nvNsockconfDefport OBJECT-TYPE
     SYNTAX   INTEGER
     ACCESS   read-write
     STATUS   mandatory
     DESCRIPTION
        "default TCP port."
     ::= {nvNsockconfEntry 4}


nvNsockmap OBJECT IDENTIFIER ::= { nevadaTcp 5 }

nvNsockmapMaxRec OBJECT-TYPE
      SYNTAX   INTEGER
      ACCESS   read-only
      STATUS   mandatory
      DESCRIPTION
                "total number of records allowed in database file."
      ::= {nvNsockmap 1}

nvNsockmapNumRec OBJECT-TYPE
      SYNTAX   INTEGER
      ACCESS   read-only
      STATUS   mandatory
      DESCRIPTION
                "number of records in use."
      ::= {nvNsockmap 2}

nvNsockmapTable OBJECT-TYPE
      SYNTAX   SEQUENCE OF NvNsockmapEntry
      ACCESS   not-accessible
      STATUS   mandatory
      DESCRIPTION
               "tcpstat file."
      ::= {nvNsockmap 3}

nvNsockmapEntry OBJECT-TYPE
      SYNTAX   NvNsockmapEntry
      ACCESS   not-accessible
      STATUS   mandatory
      DESCRIPTION
               "tcpstat record, indexed by record number"
      INDEX {nvNsockmapIndex}
      ::= {nvNsockmapTable 1 }

NvNsockmapEntry ::=
      SEQUENCE {
        nvNsockmapIndex
		INTEGER,
	nvNsockmapOrigin
		INTEGER,
	nvNsockmapService
		INTEGER,
	nvNsockmapMaxsessn
		INTEGER,
	nvNsockmapNbusport
		INTEGER,
	nvNsockmapNetaddr
		DisplayString,
	nvNsockmapUserdata
		DisplayString,
	nvNsockmapTcpport
		INTEGER,
	nvNsockmapIpaddr
		DisplayString,
	nvNsockmapTcpmsglen
		INTEGER,
	nvNsockmapStatus
		INTEGER
	}

nvNsockmapIndex OBJECT-TYPE
     SYNTAX   INTEGER
     ACCESS   read-only
     STATUS   mandatory
     DESCRIPTION
        "Index of nsockconf record"
     ::= {nvNsockmapEntry 1}

nvNsockmapOrigin OBJECT-TYPE
     SYNTAX   INTEGER {
              tcp(1),
              nbus(2)
              }
     ACCESS   read-write
     STATUS   mandatory
     DESCRIPTION
        "nsockconf record"
     ::= {nvNsockmapEntry 2}

nvNsockmapService OBJECT-TYPE
     SYNTAX   INTEGER {
              any(1),
              telnet(2),
              pos(3),
              x25(4)
              }
     ACCESS   read-write
     STATUS   mandatory
     DESCRIPTION
        "nsockconf record"
     ::= {nvNsockmapEntry 3}

nvNsockmapMaxsessn OBJECT-TYPE
     SYNTAX   INTEGER 
     ACCESS   read-write
     STATUS   mandatory
     DESCRIPTION
        "nsockconf record"
     ::= {nvNsockmapEntry 4}

nvNsockmapNbusport OBJECT-TYPE
     SYNTAX   INTEGER 
     ACCESS   read-write
     STATUS   mandatory
     DESCRIPTION
        "nsockconf record"
     ::= {nvNsockmapEntry 5}

nvNsockmapNetaddr OBJECT-TYPE
     SYNTAX   DisplayString (SIZE (0..16))
     ACCESS   read-write
     STATUS   mandatory
     DESCRIPTION
        "nsockconf record"
     ::= {nvNsockmapEntry 6}

nvNsockmapUserdata OBJECT-TYPE
     SYNTAX   DisplayString (SIZE (0..20))
     ACCESS   read-write
     STATUS   mandatory
     DESCRIPTION
        "nsockconf record"
     ::= {nvNsockmapEntry 7}

nvNsockmapTcpport OBJECT-TYPE
     SYNTAX   INTEGER 
     ACCESS   read-write
     STATUS   mandatory
     DESCRIPTION
        "nsockconf record"
     ::= {nvNsockmapEntry 8}

nvNsockmapIpaddr OBJECT-TYPE
     SYNTAX   DisplayString (SIZE (0..16))
     ACCESS   read-write
     STATUS   mandatory
     DESCRIPTION
        "nsockconf record"
     ::= {nvNsockmapEntry 9}

nvNsockmapTcpmsglen   OBJECT-TYPE
     SYNTAX   INTEGER {
		none  (1),
		vap   (2),
		bin2  (3),
		bin3  (4),
		bin4  (5)
                }
     ACCESS   read-write
     STATUS   mandatory
     DESCRIPTION
        " type of header for tcp message "
     ::= {nvNsockmapEntry 11}

nvNsockmapStatus OBJECT-TYPE
     SYNTAX   INTEGER {
                valid(1),
                invalid(2)
                }
     ACCESS   read-write
     STATUS   mandatory
     DESCRIPTION
        "nsockconf record"
     ::= {nvNsockmapEntry 10}

--
--      ftpconf file
--

nvFtpconf OBJECT IDENTIFIER ::= { nevadaFtp 1 }

nvFtpconfMaxRec OBJECT-TYPE
      SYNTAX   INTEGER
      ACCESS   read-only
      STATUS   mandatory
      DESCRIPTION
                "total number of records allowed in database file."
      ::= {nvFtpconf 1}

nvFtpconfNumRec OBJECT-TYPE
      SYNTAX   INTEGER
      ACCESS   read-only
      STATUS   mandatory
      DESCRIPTION
                "number of records in use."
      ::= {nvFtpconf 2}

nvFtpconfTable OBJECT-TYPE
      SYNTAX   SEQUENCE OF NvFtpconfEntry
      ACCESS   not-accessible
      STATUS   mandatory
      DESCRIPTION
               "ftpconf file."
      ::= {nvFtpconf 3}

nvFtpconfEntry OBJECT-TYPE
      SYNTAX   NvFtpconfEntry
      ACCESS   not-accessible
      STATUS   mandatory
      DESCRIPTION
               "ftpconf record, indexed by record number"
      INDEX {nvFtpconfIndex}
      ::= {nvFtpconfTable 1 }

NvFtpconfEntry ::=
      SEQUENCE {
        nvFtpconfIndex
                INTEGER,
        nvFtpconfReqaddr
                DisplayString,
        nvFtpconfUsername
                DisplayString,
        nvFtpconfPassword
                DisplayString,
        nvFtpconfTimeout
                INTEGER,
        nvFtpconfStatus
                INTEGER
                }

nvFtpconfIndex OBJECT-TYPE
     SYNTAX   INTEGER
     ACCESS   read-only
     STATUS   mandatory
     DESCRIPTION
        "Index of ftpconf record"
     ::= {nvFtpconfEntry 1}

nvFtpconfReqaddr OBJECT-TYPE
     SYNTAX   DisplayString (SIZE (0..16))
     ACCESS   read-write
     STATUS   mandatory
     DESCRIPTION
        "FTPD remote client IP address."
     ::= {nvFtpconfEntry 2}

nvFtpconfUsername OBJECT-TYPE
     SYNTAX   DisplayString (SIZE (0..16))
     ACCESS   read-write
     STATUS   mandatory
     DESCRIPTION
        "FTPD username."
     ::= {nvFtpconfEntry 3}

nvFtpconfPassword OBJECT-TYPE
     SYNTAX   DisplayString (SIZE (0..16))
     ACCESS   read-write
     STATUS   mandatory
     DESCRIPTION
        "FTPD user password."
     ::= {nvFtpconfEntry 4}

nvFtpconfTimeout OBJECT-TYPE
     SYNTAX   INTEGER
     ACCESS   read-write
     STATUS   mandatory
     DESCRIPTION
        "FTPD user inactivity timer."
     ::= {nvFtpconfEntry 5}

nvFtpconfStatus OBJECT-TYPE
     SYNTAX   INTEGER {
                valid(1),
                invalid(2)
                }
     ACCESS   read-write
     STATUS   mandatory
     DESCRIPTION
"Operation status. Add the record to the table (valid) or delete
the record from the table (invalid).
Reqaddr MUST be set to a valid value before 
adding new record (setting Status to valid)."
     ::= { nvFtpconfEntry 10 }

--
--
--      ftpstat file
--

nvFtpstat OBJECT IDENTIFIER ::= { nevadaFtp 2 }

nvFtpstatIndex OBJECT-TYPE
     SYNTAX   INTEGER
     ACCESS   read-only
     STATUS   mandatory
     DESCRIPTION
        "Index of ftpconf record"
     ::= {nvFtpstat 1}

nvFtpstatServaddr OBJECT-TYPE
     SYNTAX   DisplayString (SIZE (0..16))
     ACCESS   read-only
     STATUS   mandatory
     DESCRIPTION
        "server FTP host IP address."
     ::= {nvFtpstat 2}

nvFtpstatNumreqs OBJECT-TYPE
     SYNTAX   Counter
     ACCESS   read-only
     STATUS   mandatory
     DESCRIPTION
        "number of connection requested."
     ::= {nvFtpstat 3}

nvFtpstatConnects OBJECT-TYPE
     SYNTAX   Counter
     ACCESS   read-only
     STATUS   mandatory
     DESCRIPTION
        "number of successful connections."
     ::= {nvFtpstat 4}

nvFtpstatConnfails OBJECT-TYPE
     SYNTAX   Counter
     ACCESS   read-only
     STATUS   mandatory
     DESCRIPTION
        "number of connect request failures."
     ::= {nvFtpstat 5}

nvFtpstatTotalfirvs OBJECT-TYPE
     SYNTAX   Counter
     ACCESS   read-only
     STATUS   mandatory
     DESCRIPTION
        "number of files server received."
     ::= {nvFtpstat 6}

nvFtpstatTotalfisds OBJECT-TYPE
     SYNTAX   Counter
     ACCESS   read-only
     STATUS   mandatory
     DESCRIPTION
        "number of files server sent."
     ::= {nvFtpstat 7}

nvFtpstatTotalkbyrvs OBJECT-TYPE
     SYNTAX   Counter
     ACCESS   read-only
     STATUS   mandatory
     DESCRIPTION
        "number of Kbytes server received."
     ::= {nvFtpstat 8}

nvFtpstatTotalkbysds OBJECT-TYPE
     SYNTAX   Counter
     ACCESS   read-only
     STATUS   mandatory
     DESCRIPTION
        "number of Kbytes server sent."
     ::= {nvFtpstat 9}

nvFtpstatClientaddr OBJECT-TYPE
     SYNTAX   DisplayString (SIZE (0..16))
     ACCESS   read-only
     STATUS   mandatory
     DESCRIPTION
        "client FTP host IP address."
     ::= {nvFtpstat 10}

nvFtpstatCurrstat OBJECT-TYPE
     SYNTAX   INTEGER {
                closed(1),      -- (+1)
                copen(2),
                bothopen(3)
                }
     ACCESS   read-only
     STATUS   mandatory
     DESCRIPTION
        "current FTPD status."
     ::= {nvFtpstat 11}

nvFtpstatCommstat OBJECT-TYPE
     SYNTAX   INTEGER {
                none(1),        -- (+1)
                cmdok(2),
                cmdfail(3),
                cmderr(4)
                }
     ACCESS   read-only
     STATUS   mandatory
     DESCRIPTION
        "last command status."
     ::= {nvFtpstat 12}

nvFtpstatTotalsucs OBJECT-TYPE
     SYNTAX   Counter
     ACCESS   read-only
     STATUS   mandatory
     DESCRIPTION
        "total number of commands executed successfully."
     ::= {nvFtpstat 13}

nvFtpstatTotalfals OBJECT-TYPE
     SYNTAX   Counter
     ACCESS   read-only
     STATUS   mandatory
     DESCRIPTION
        "total number of commands executed with failure."
     ::= {nvFtpstat 14}

nvFtpstatTotalerrs OBJECT-TYPE
     SYNTAX   Counter
     ACCESS   read-only
     STATUS   mandatory
     DESCRIPTION
        "total number of unsupported commands."
     ::= {nvFtpstat 15}

nvFtpstatCurrfirecs OBJECT-TYPE
     SYNTAX   Counter
     ACCESS   read-only
     STATUS   mandatory
     DESCRIPTION
        "total number of files current user received."
     ::= {nvFtpstat 16}

nvFtpstatCurrfisnds OBJECT-TYPE
     SYNTAX   Counter
     ACCESS   read-only
     STATUS   mandatory
     DESCRIPTION
        "total number of files current user sent."
     ::= {nvFtpstat 17}

nvFtpstatCurrkbyrvs OBJECT-TYPE
     SYNTAX   Counter
     ACCESS   read-only
     STATUS   mandatory
     DESCRIPTION
        "total number of Kbytes current user server sent."
     ::= {nvFtpstat 18}

nvFtpstatCurrkbysds OBJECT-TYPE
     SYNTAX   Counter
     ACCESS   read-only
     STATUS   mandatory
     DESCRIPTION
        "total number of Kbytes current user server received."
     ::= {nvFtpstat 19}

nvFtpstatDtreset OBJECT-TYPE
     SYNTAX   DisplayString (SIZE (0..20))
     ACCESS   read-only
     STATUS   mandatory
     DESCRIPTION
        "date & time statistics last reset"
      ::= {nvFtpstat 20 }



--
--  Tnconf
--

nvTnconf OBJECT IDENTIFIER ::= { nevadaTelnet 1 }

nvTnconfMaxRec OBJECT-TYPE
      SYNTAX   INTEGER
      ACCESS   read-only
      STATUS   mandatory
      DESCRIPTION
                "total number of records allowed in database file."
      ::= { nvTnconf 1}

nvTnconfNumRec OBJECT-TYPE
      SYNTAX   INTEGER
      ACCESS   read-only
      STATUS   mandatory
      DESCRIPTION
                "number of records in use."
      ::= { nvTnconf 2}

nvTnconfTable OBJECT-TYPE
      SYNTAX   SEQUENCE OF NvTnconfEntry
      ACCESS   not-accessible
      STATUS   mandatory
      DESCRIPTION
               "Nevada Telnet config file."
      ::= { nvTnconf 3 }

nvTnconfEntry OBJECT-TYPE
      SYNTAX   NvTnconfEntry
      ACCESS   not-accessible
      STATUS   mandatory
      DESCRIPTION
               "Nevada node Telnet record."
      INDEX { nvTnconfIndex }
      ::= { nvTnconfTable 1 }

NvTnconfEntry ::=
      SEQUENCE {
      nvTnconfIndex
            INTEGER,
      nvTnconfNumSess
            INTEGER,
      nvTnconfDeftnclass
            DisplayString,
      nvTnconfDefiticlass
            DisplayString,
      nvTnconfDefminbspace
            INTEGER,
      nvTnconfDefmaxbspace
            INTEGER
                }

nvTnconfIndex OBJECT-TYPE
                SYNTAX   INTEGER
                ACCESS  read-only
                STATUS  mandatory
                DESCRIPTION
                    "Index of Telenet conf record"
                ::= { nvTnconfEntry 1 }

nvTnconfNumSess OBJECT-TYPE
                SYNTAX   INTEGER (0..65535)
                ACCESS   read-only
                STATUS   mandatory
                DESCRIPTION
                    "number of simultaneous sessions"
                ::= { nvTnconfEntry 2 }

nvTnconfDeftnclass OBJECT-TYPE
                SYNTAX   DisplayString (SIZE (0..10))
                ACCESS   read-write
                STATUS   mandatory
                DESCRIPTION
                     "Default telnet class"
                ::= { nvTnconfEntry 3 }

nvTnconfDefiticlass OBJECT-TYPE
                SYNTAX   DisplayString (SIZE (0..10))
                ACCESS   read-write
                STATUS   mandatory
                DESCRIPTION
                     "Default iti class"
                ::= { nvTnconfEntry 4 }
nvTnconfDefminbspace OBJECT-TYPE
                SYNTAX   INTEGER (0..65535)
                ACCESS   read-write
                STATUS   mandatory
                DESCRIPTION
                    "number of simultaneous sessions"
                ::= { nvTnconfEntry 5 }
 nvTnconfDefmaxbspace OBJECT-TYPE
                SYNTAX   INTEGER (0..65535)
                ACCESS   read-write
                STATUS   mandatory
                DESCRIPTION
                    "number of simultaneous sessions"
                ::= { nvTnconfEntry 6 }

--
-- tnclass
--

nvTnclass OBJECT IDENTIFIER ::= { nevadaTelnet 2 }

nvTnclassMaxRec OBJECT-TYPE
      SYNTAX   INTEGER
      ACCESS   read-only
      STATUS   mandatory
      DESCRIPTION
                "total number of records allowed in database file."
      ::= { nvTnclass 1}

nvTnclassNumRec OBJECT-TYPE
      SYNTAX   INTEGER
      ACCESS   read-only
      STATUS   mandatory
      DESCRIPTION
                "number of records in use."
      ::= { nvTnclass 2}

nvTnclassTable OBJECT-TYPE
      SYNTAX   SEQUENCE OF NvTnclassEntry
      ACCESS   not-accessible
      STATUS   mandatory
      DESCRIPTION
               "Nevada Telnet class file."
      ::= { nvTnclass 3 }

nvTnclassEntry OBJECT-TYPE
      SYNTAX   NvTnclassEntry
      ACCESS   not-accessible
      STATUS   mandatory
      DESCRIPTION
               "Nevada node Telnet record."
      INDEX { nvTnclassIndex }
      ::= { nvTnclassTable 1 }


NvTnclassEntry ::=
      SEQUENCE {
      nvTnclassIndex
            INTEGER,
      nvTnclassClassname
            DisplayString,
      nvTnclassAobreak
            INTEGER,
      nvTnclassIpcmd
            INTEGER,
      nvTnclassGoahead
            INTEGER,
      nvTnclassStatus
            INTEGER
                }

nvTnclassIndex OBJECT-TYPE
                SYNTAX   INTEGER
                ACCESS  read-only
                STATUS  mandatory
                DESCRIPTION
                    "Index of Telenet class record"
                ::= { nvTnclassEntry 1 }


nvTnclassClassname OBJECT-TYPE
                SYNTAX   DisplayString (SIZE (0..10))
                ACCESS   read-write
                STATUS   mandatory
                DESCRIPTION
                     "Telnet classname"
                ::= { nvTnclassEntry 2 }

nvTnclassAobreak OBJECT-TYPE
                SYNTAX   INTEGER {
                        no(1),
                        yes(2)
                        }
                ACCESS   read-write
                STATUS   mandatory
                DESCRIPTION
                     "Telnet abort cmd issues break"
                ::= { nvTnclassEntry 4 }

nvTnclassIpcmd OBJECT-TYPE
                SYNTAX   INTEGER {
                        no(1),
                        yes(2)
                        }
                ACCESS   read-write
                STATUS   mandatory
                DESCRIPTION
                     "Telnet interrupt process cmd"
                ::= { nvTnclassEntry 5 }

nvTnclassGoahead OBJECT-TYPE
                SYNTAX   INTEGER {
                        send(1),
                        suppress(2)
                        }
                ACCESS   read-write
                STATUS   mandatory
                DESCRIPTION
                     "Telnet suppress/send Go Ahead cmd"
                ::= { nvTnclassEntry 7 }

nvTnclassStatus OBJECT-TYPE
     SYNTAX   INTEGER {
                valid(1),
                invalid(2)
                }
     ACCESS   read-write
     STATUS   mandatory
     DESCRIPTION
"Operation status of the record. Use valid to add
record to database file and invalid to delete
record from database file."
      ::= { nvTnclassEntry 9 }


--
-- tnmap
--
nvTnmap OBJECT IDENTIFIER ::= { nevadaTelnet 3 }

nvTnmapMaxRec OBJECT-TYPE
      SYNTAX   INTEGER
      ACCESS   read-only
      STATUS   mandatory
      DESCRIPTION
                "total number of records allowed in database file."
      ::= { nvTnmap 1}

nvTnmapNumRec OBJECT-TYPE
      SYNTAX   INTEGER
      ACCESS   read-only
      STATUS   mandatory
      DESCRIPTION
                "number of records in use."
      ::= { nvTnmap 2}

nvTnmapTable OBJECT-TYPE
      SYNTAX   SEQUENCE OF NvTnmapEntry
      ACCESS   not-accessible
      STATUS   mandatory
      DESCRIPTION
               "Nevada Telnet map file."
      ::= { nvTnmap 3 }

nvTnmapEntry OBJECT-TYPE
      SYNTAX   NvTnmapEntry
      ACCESS   not-accessible
      STATUS   mandatory
      DESCRIPTION
               "Nevada node Telnet map record."
      INDEX { nvTnmapIndex }
      ::= { nvTnmapTable 1 }


NvTnmapEntry ::=
      SEQUENCE {
      nvTnmapIndex
            INTEGER,
      nvTnmapPortnum
            INTEGER,
      nvTnmapTnclass
            DisplayString,
      nvTnmapIticlass
            DisplayString,
      nvTnmapStatus
            INTEGER
                }

nvTnmapIndex OBJECT-TYPE
                SYNTAX   INTEGER
                ACCESS  read-only
                STATUS  mandatory
                DESCRIPTION
                    "Index of Telenet map record"
                ::= { nvTnmapEntry 1 }

nvTnmapPortnum OBJECT-TYPE
                SYNTAX   INTEGER (0..65535)
                ACCESS   read-write
                STATUS   mandatory
                DESCRIPTION
                     "Telnet portnumber"
                ::= { nvTnmapEntry 2 }

nvTnmapTnclass OBJECT-TYPE
                SYNTAX   DisplayString (SIZE (0..10))
                ACCESS   read-write
                STATUS   mandatory
                DESCRIPTION
                     "Telnet classname"
                ::= { nvTnmapEntry 3 }

nvTnmapIticlass OBJECT-TYPE
                SYNTAX   DisplayString (SIZE (0..10))
                ACCESS   read-write
                STATUS   mandatory
                DESCRIPTION
                     "Telnet iti classname"
                ::= { nvTnmapEntry 4 }

nvTnmapStatus OBJECT-TYPE
     SYNTAX   INTEGER {
                valid(1),
                invalid(2)
                }
     ACCESS   read-write
     STATUS   mandatory
     DESCRIPTION
"Operation status of the record. Use valid to add
record to database file and invalid to delete
record from database file."
      ::= { nvTnmapEntry 5 }
--
-- tnstat
--

nvTnstat OBJECT IDENTIFIER ::= { nevadaTelnet 4 }

nvTnstatMaxRec OBJECT-TYPE
      SYNTAX   INTEGER
      ACCESS   read-only
      STATUS   mandatory
      DESCRIPTION
                "total number of records allowed in database file."
      ::= { nvTnstat 1}

nvTnstatNumRec OBJECT-TYPE
      SYNTAX   INTEGER
      ACCESS   read-only
      STATUS   mandatory
      DESCRIPTION
                "number of records in use."
      ::= { nvTnstat 2}

nvTnstatTable OBJECT-TYPE
      SYNTAX   SEQUENCE OF NvTnstatEntry
      ACCESS   not-accessible
      STATUS   mandatory
      DESCRIPTION
               "Nevada Telnet stat file."
      ::= { nvTnstat 3 }

nvTnstatEntry OBJECT-TYPE
      SYNTAX   NvTnstatEntry
      ACCESS   not-accessible
      STATUS   mandatory
      DESCRIPTION
               "Nevada node Telnet stat record."
      INDEX { nvTnstatIndex }
      ::= { nvTnstatTable 1 }


NvTnstatEntry ::=
      SEQUENCE {
      nvTnstatIndex
            INTEGER,
      nvTnstatPortnum
            INTEGER,
      nvTnstatStatus
            INTEGER,
      nvTnstatMode
            INTEGER,
      nvTnstatLastCmd
            DisplayString,
      nvTnstatOptions
            DisplayString,
      nvTnstatClientAddr
	    DisplayString
                }

nvTnstatIndex OBJECT-TYPE
                SYNTAX   INTEGER
                ACCESS  read-only
                STATUS  mandatory
                DESCRIPTION
                    "Index of Telenet stat record"
                ::= { nvTnstatEntry 1 }

nvTnstatPortnum OBJECT-TYPE
                SYNTAX   INTEGER
                ACCESS   read-only
                STATUS   mandatory
                DESCRIPTION
                     "Telnet portnumber in use"
                ::= { nvTnstatEntry 2 }

nvTnstatStatus OBJECT-TYPE
                SYNTAX   INTEGER {
                        disconnected(1),
                        connecting(2),
			connected(3)
                        }
                ACCESS   read-only
                STATUS   mandatory
                DESCRIPTION
                     "Telnet call status"
                ::= { nvTnstatEntry 3 }

nvTnstatMode OBJECT-TYPE
                SYNTAX   INTEGER {
                        normal(1),
                        linemode(2),
                        binary(3)
                        }
                ACCESS   read-only
                STATUS   mandatory
                DESCRIPTION
                     "Telnet mode in use"
                ::= { nvTnstatEntry 4 }

nvTnstatLastCmd OBJECT-TYPE
                SYNTAX   DisplayString (SIZE (0..20))
                ACCESS   read-only
                STATUS   mandatory
                DESCRIPTION
                     "Telnet last cmd received"
                ::= { nvTnstatEntry 5 }

nvTnstatOptions OBJECT-TYPE
                SYNTAX   DisplayString (SIZE (0..40))
                ACCESS   read-only
                STATUS   mandatory
                DESCRIPTION
                     "Telnet active options"
                ::= { nvTnstatEntry 6 }

nvTnstatClientAddr OBJECT-TYPE
                SYNTAX   DisplayString (SIZE (0..20))
                ACCESS   read-only
                STATUS   mandatory
                DESCRIPTION
                     "Address of the Client."
                ::= { nvTnstatEntry 7 }

--
-- tncconf
--
nvTncconf OBJECT IDENTIFIER ::= { nevadaTelnet 5 }

nvTncconfMaxRec OBJECT-TYPE
      SYNTAX   INTEGER
      ACCESS   read-only
      STATUS   mandatory
      DESCRIPTION
		"total number of records allowed in database file."
      ::= { nvTncconf 1}

nvTncconfNumRec OBJECT-TYPE
      SYNTAX   INTEGER
      ACCESS   read-only
      STATUS   mandatory
      DESCRIPTION
		"number of records in use."
      ::= { nvTncconf 2}

nvTncconfTable OBJECT-TYPE
      SYNTAX   SEQUENCE OF NvTncconfEntry
      ACCESS   not-accessible
      STATUS   mandatory
      DESCRIPTION
               "Nevada Telnet cconf file."
      ::= { nvTncconf 3 }

nvTncconfEntry OBJECT-TYPE
      SYNTAX   NvTncconfEntry
      ACCESS   not-accessible
      STATUS   mandatory
      DESCRIPTION
               "nevada node Tncconf record."
      INDEX { nvTncconfIndex }
      ::= { nvTncconfTable 1 }

      NvTncconfEntry ::=
      SEQUENCE {
      nvTncconfIndex
            INTEGER,
      nvTncconfNumSess
            INTEGER,
      nvTncconfX3parms
            INTEGER,
      nvTncconfSetact
            INTEGER,
      nvTncconfIdletim
            INTEGER,
      nvTncconfEscape
            INTEGER,
      nvTncconfEcho
            INTEGER,
      nvTncconfInterrupt
            INTEGER,
      nvTncconfQuit
            INTEGER,
      nvTncconfFout
            INTEGER,
      nvTncconfErase
            INTEGER,
      nvTncconfKill
            INTEGER,
      nvTncconfAyt
            INTEGER,
      nvTncconfSuspend
            INTEGER,
      nvTncconfDnsaddr
            DisplayString,
      nvTncconfStatus
            INTEGER
                }

nvTncconfIndex OBJECT-TYPE
		SYNTAX   INTEGER
		ACCESS	read-only
		STATUS	mandatory
		DESCRIPTION
		    "Index of Telnet Client record"
		::= { nvTncconfEntry 1 }

nvTncconfNumSess  OBJECT-TYPE
		SYNTAX   INTEGER
		ACCESS	read-only
		STATUS	mandatory
		DESCRIPTION
		    "number of simultaneous sessions (numSess)"
		::= { nvTncconfEntry 2 }

nvTncconfX3parms OBJECT-TYPE
		SYNTAX   INTEGER (0..255)
		ACCESS	read-write
		STATUS	mandatory
		DESCRIPTION
		    "string of X.3 params to send at start (x3parms)"
		::= { nvTncconfEntry 3 }

nvTncconfSetact  OBJECT-TYPE
     	SYNTAX   INTEGER {
                yes(2),
                no(1)
                }
		ACCESS	read-write
		STATUS	mandatory
		DESCRIPTION
		    "allow user to perform set actions (setact)"
		::= { nvTncconfEntry 4 }

nvTncconfIdletim OBJECT-TYPE
		SYNTAX   INTEGER (0..255)
		ACCESS	read-write
		STATUS	mandatory
		DESCRIPTION
		    "forwarding timer used in character at a time (idletim)"
		::= { nvTncconfEntry 5 }

nvTncconfEscape  OBJECT-TYPE
		SYNTAX   INTEGER (0..255)
		ACCESS	read-write
		STATUS	mandatory
		DESCRIPTION
		    "decimal number of character to use for escape (escape)"
		::= { nvTncconfEntry 6 }

nvTncconfEcho    OBJECT-TYPE
		SYNTAX   INTEGER (0..255)
		ACCESS	read-write
		STATUS	mandatory
		DESCRIPTION
		    "decimal number of character to use for echo (echo)"
		::= { nvTncconfEntry 7 }

nvTncconfInterrupt OBJECT-TYPE
		SYNTAX   INTEGER (0..255)
		ACCESS	read-write
		STATUS	mandatory
		DESCRIPTION
		    "decimal number of character to use for interrupt (interrupt)"
		::= { nvTncconfEntry 8 }

nvTncconfQuit    OBJECT-TYPE
		SYNTAX   INTEGER (0..255)
		ACCESS	read-write
		STATUS	mandatory
		DESCRIPTION
		    "decimal number of character to use for quit (quit)"
		::= { nvTncconfEntry 9 }

nvTncconfFout    OBJECT-TYPE
		SYNTAX   INTEGER (0..255)
		ACCESS	read-write
		STATUS	mandatory
		DESCRIPTION
		"decimal number of character to use for flushoutput (fout)"
		::= { nvTncconfEntry 10 }

nvTncconfErase   OBJECT-TYPE
		SYNTAX   INTEGER (0..255)
		ACCESS	read-write
		STATUS	mandatory
		DESCRIPTION
		    "decimal number of character to use for erase (erase)"
		::= { nvTncconfEntry 11 }

nvTncconfKill    OBJECT-TYPE
		SYNTAX   INTEGER (0..255)
		ACCESS	read-write
		STATUS	mandatory
		DESCRIPTION
		    "decimal number of character to use for kill (kill)"
		::= { nvTncconfEntry 12 }

nvTncconfAyt     OBJECT-TYPE
		SYNTAX   INTEGER (0..255)
		ACCESS	read-write
		STATUS	mandatory
		DESCRIPTION
		    "decimal number of character to use for ayt (ayt)"
		::= { nvTncconfEntry 13 }

nvTncconfSuspend OBJECT-TYPE
		SYNTAX   INTEGER (0..255)
		ACCESS	read-write
		STATUS	mandatory
		DESCRIPTION
		    "decimal number of character to use for suspend (suspend)"
		::= { nvTncconfEntry 14 }

nvTncconfDnsaddr OBJECT-TYPE
      		SYNTAX   DisplayString (SIZE (0..16))
		ACCESS	read-write
		STATUS	mandatory
		DESCRIPTION
		    " Dnsaddr"
		::= { nvTncconfEntry 15 }

nvTncconfStatus OBJECT-TYPE
     SYNTAX   INTEGER {
                      valid(1),
                      invalid(2)
		      }
     ACCESS   read-write
     STATUS   mandatory
     DESCRIPTION
"Operation status of the record. Use valid to add
record to database file and invalid to delete
record from database file."
      ::= { nvTncconfEntry 16 }
 
--
-- tncmap
--
nvTncmap OBJECT IDENTIFIER ::= { nevadaTelnet 6 } 

nvTncmapMaxRec OBJECT-TYPE
      SYNTAX   INTEGER
      ACCESS   read-only
      STATUS   mandatory
      DESCRIPTION
		"total number of records allowed in database file."
      ::= { nvTncmap 1}

nvTncmapNumRec OBJECT-TYPE
      SYNTAX   INTEGER
      ACCESS   read-only
      STATUS   mandatory
      DESCRIPTION
		"number of records in use."
      ::= { nvTncmap 2}

nvTncmapTable OBJECT-TYPE
      SYNTAX   SEQUENCE OF NvTncmapEntry
      ACCESS   not-accessible
      STATUS   mandatory
      DESCRIPTION
               "Nevada Telnet cstat file."
      ::= { nvTncmap 3 }

nvTncmapEntry OBJECT-TYPE
      SYNTAX   NvTncmapEntry
      ACCESS   not-accessible
      STATUS   mandatory
      DESCRIPTION
               "Nevada node Telnet cstat record."
      INDEX { nvTncmapIndex }
      ::= { nvTncmapTable 1 }

NvTncmapEntry ::=
      SEQUENCE {
      nvTncmapIndex
            INTEGER,
      nvTncmapNetad
            DisplayString,
      nvTncmapUsdata
            DisplayString,
      nvTncmapIpaddr
            DisplayString,
      nvTncmapTcppn
            DisplayString,
      nvTncmapX3parms
            INTEGER,
      nvTncmapMode
            INTEGER,
      nvTncmapSecure
            INTEGER,
      nvTncmapStatus
            INTEGER
	}

nvTncmapIndex OBJECT-TYPE
		SYNTAX   INTEGER
		ACCESS	read-only
		STATUS	mandatory
		DESCRIPTION
		    "Index of Telnet Client map record"
		::= { nvTncmapEntry 1 }

nvTncmapNetad OBJECT-TYPE
      		SYNTAX   DisplayString(SIZE (0..16))
		ACCESS	read-write
		STATUS	mandatory
		DESCRIPTION
		    " "
		::= { nvTncmapEntry 2 }

nvTncmapUsdata OBJECT-TYPE
      		SYNTAX   DisplayString (SIZE (0..16))
		ACCESS	read-write
		STATUS	mandatory
		DESCRIPTION
		    " "
		::= { nvTncmapEntry 3 }


nvTncmapIpaddr OBJECT-TYPE
      		SYNTAX   DisplayString (SIZE (0..16))
		ACCESS	read-write
		STATUS	mandatory
		DESCRIPTION
		    " "
		::= { nvTncmapEntry 4 }

nvTncmapTcppn OBJECT-TYPE
      		SYNTAX   DisplayString (SIZE (0..8))
		ACCESS	read-write
		STATUS	mandatory
		DESCRIPTION
		    " "
		::= { nvTncmapEntry 5 }

nvTncmapX3parms OBJECT-TYPE
      		SYNTAX   INTEGER (0..255)
		ACCESS	read-write
		STATUS	mandatory
		DESCRIPTION
		    " "
		::= { nvTncmapEntry 6 }

nvTncmapMode OBJECT-TYPE
     SYNTAX   INTEGER {
                asci(1),
                binary(2)
                }
		ACCESS	read-write
		STATUS	mandatory
		DESCRIPTION
		    " "
		::= { nvTncmapEntry 7 }

nvTncmapSecure OBJECT-TYPE
     SYNTAX   INTEGER {
                no(1),
                yes(2)
                      }
		ACCESS	read-write
		STATUS	mandatory
		DESCRIPTION
		    " security opreation enabled"
		::= { nvTncmapEntry 9 }

nvTncmapStatus OBJECT-TYPE
     SYNTAX   INTEGER {
                valid(1),
                invalid(2)
                }
		ACCESS	read-write
		STATUS	mandatory
		DESCRIPTION
		    " "
		::= { nvTncmapEntry 8 }


--
-- tncstat
--
nvTncstat OBJECT IDENTIFIER ::= { nevadaTelnet 7 } 

nvTncstatMaxRec OBJECT-TYPE
      SYNTAX   INTEGER
      ACCESS   read-only
      STATUS   mandatory
      DESCRIPTION
		"total number of records allowed in database file."
      ::= { nvTncstat 1}

nvTncstatNumRec OBJECT-TYPE
      SYNTAX   INTEGER
      ACCESS   read-only
      STATUS   mandatory
      DESCRIPTION
		"number of records in use."
      ::= { nvTncstat 2}

nvTncstatTable OBJECT-TYPE
      SYNTAX   SEQUENCE OF NvTncstatEntry
      ACCESS   not-accessible
      STATUS   mandatory
      DESCRIPTION
               "Nevada Telnet cstat file."
      ::= { nvTncstat 3 }

nvTncstatEntry OBJECT-TYPE
      SYNTAX   NvTncstatEntry
      ACCESS   not-accessible
      STATUS   mandatory
      DESCRIPTION
               "Nevada node Telnet cstat record."
      INDEX { nvTncstatIndex }
      ::= { nvTncstatTable 1 }

NvTncstatEntry ::=
      SEQUENCE {
      nvTncstatIndex
            INTEGER,
      nvTncstatSessnum
            INTEGER,
      nvTncstatStatus
            INTEGER,
      nvTncstatDnsidx
            INTEGER,
      nvTncstatCalladdr
            DisplayString,
      nvTncstatCalldata
            DisplayString,
      nvTncstatIpaddr
            DisplayString,
      nvTncstatPortnum
            INTEGER,
      nvTncstatMode
            INTEGER,
      nvTncstatX29err
            INTEGER
	    }


nvTncstatIndex OBJECT-TYPE
		SYNTAX   INTEGER
		ACCESS	read-only
		STATUS	mandatory
		DESCRIPTION
		    "Index of Telnet Client stat record"
		::= { nvTncstatEntry 1 }


nvTncstatSessnum OBJECT-TYPE
      SYNTAX   INTEGER
      ACCESS   read-only
      STATUS   mandatory
      DESCRIPTION
		"the number of the session"
      ::= { nvTncstatEntry  2}

nvTncstatStatus OBJECT-TYPE
     SYNTAX   INTEGER {
                discon(1),
                cnectg(2),
		cnetctd(3),
		cmd(4)
                }
      ACCESS   read-only
      STATUS   mandatory
      DESCRIPTION
		"Call status "
      ::= { nvTncstatEntry  3}

nvTncstatDnsidx OBJECT-TYPE
     SYNTAX   INTEGER
      ACCESS   read-only
      STATUS   mandatory
      DESCRIPTION
		"dnsindex  "
      ::= { nvTncstatEntry  4}

nvTncstatCalladdr OBJECT-TYPE
      SYNTAX   DisplayString (SIZE (0..16))
      ACCESS   read-only
      STATUS   mandatory
      DESCRIPTION
		"x121 address calling TELNET Client"
      ::= { nvTncstatEntry  5}

nvTncstatCalldata OBJECT-TYPE
      SYNTAX   DisplayString (SIZE (0..16))
      ACCESS   read-only
      STATUS   mandatory
      DESCRIPTION
		"call user data"
      ::= { nvTncstatEntry  6}

nvTncstatIpaddr OBJECT-TYPE
      SYNTAX   DisplayString (SIZE (0..16))
      ACCESS   read-only
      STATUS   mandatory
      DESCRIPTION
		"ip address connected to"
      ::= { nvTncstatEntry  7}

nvTncstatPortnum OBJECT-TYPE
      SYNTAX   INTEGER
      ACCESS   read-only
      STATUS   mandatory
      DESCRIPTION
		"Port number connected to"
      ::= { nvTncstatEntry  8}

nvTncstatMode OBJECT-TYPE
     SYNTAX   INTEGER {
                normal(1),
                linemode(2),
		binary(3)
                }
      ACCESS   read-only
      STATUS   mandatory
      DESCRIPTION
		"mode in use"
      ::= { nvTncstatEntry  9}

nvTncstatX29err OBJECT-TYPE
      SYNTAX   INTEGER
      ACCESS   read-only
      STATUS   mandatory
      DESCRIPTION
		"last X29 error rcvd from 3XPAD"
      ::= { nvTncstatEntry  10}



--
--      radconf file
--

nvRadconf OBJECT IDENTIFIER ::= { nevadaRadius 1 }

nvRadconfMaxRec OBJECT-TYPE
      SYNTAX   INTEGER
      ACCESS   read-only
      STATUS   mandatory
      DESCRIPTION
                "total number of records allowed in database file."
      ::= {nvRadconf 1}

nvRadconfNumRec OBJECT-TYPE
      SYNTAX   INTEGER
      ACCESS   read-only
      STATUS   mandatory
      DESCRIPTION
                "number of records in use."
      ::= {nvRadconf 2}

nvRadconfTable OBJECT-TYPE
      SYNTAX   SEQUENCE OF NvRadconfEntry
      ACCESS   not-accessible
      STATUS   mandatory
      DESCRIPTION
               "radconf file."
      ::= {nvRadconf 3}

nvRadconfEntry OBJECT-TYPE
      SYNTAX   NvRadconfEntry
      ACCESS   not-accessible
      STATUS   mandatory
      DESCRIPTION
               "radconf record, indexed by record number"
      INDEX {nvRadconfIndex}
      ::= {nvRadconfTable 1 }

NvRadconfEntry ::=
      SEQUENCE {
        nvRadconfIndex
                INTEGER,
        nvRadconfName
                DisplayString,
        nvRadconfSecret
                DisplayString,
        nvRadconfN1
                INTEGER,
        nvRadconfT1
                INTEGER,
        nvRadconfAcct
                INTEGER,
        nvRadconfNumdigits
                INTEGER,
        nvRadconfAuth1
                DisplayString,
        nvRadconfAuth2
                DisplayString,
        nvRadconfAuth3
                DisplayString,
        nvRadconfAcct1
                DisplayString,
        nvRadconfAcct2
                DisplayString,
        nvRadconfAcct3
                DisplayString,
        nvRadconfAcctauth
                INTEGER,
        nvRadconfAuth1port          --AF
                INTEGER,	    --AF
        nvRadconfAuth2port          --AF
                 INTEGER,	    --AF
        nvRadconfAuth3port          --AF
                 INTEGER,	    --AF
        nvRadconfAcct1port          --AF
                 INTEGER,	    --AF
        nvRadconfAcct2port          --AF
                 INTEGER,	    --AF
        nvRadconfAcct3port          --AF
                 INTEGER,	    --AF
        nvRadconfAttrchk            --AF
                 INTEGER,	    --AF
        nvRadconfDnsatt1          
                 INTEGER, 
        nvRadconfDnsatt2
                 INTEGER, 
        nvRadconfNbnsatt1
                 INTEGER, 
        nvRadconfStatus
	 	 INTEGER,
        nvRadconfNbnsatt2
                 INTEGER 
                }

nvRadconfIndex OBJECT-TYPE
     SYNTAX   INTEGER
     ACCESS   read-only
     STATUS   mandatory
     DESCRIPTION
        "Index of radconf record"
     ::= {nvRadconfEntry 1}

nvRadconfName OBJECT-TYPE
     SYNTAX   DisplayString (SIZE (0..8))
     ACCESS   read-write
     STATUS   mandatory
     DESCRIPTION
        "Nevada name."
     ::= {nvRadconfEntry 2}

nvRadconfSecret OBJECT-TYPE
     SYNTAX   DisplayString (SIZE (0..16))
     ACCESS   read-write
     STATUS   mandatory
     DESCRIPTION
        "secret for accounting."
     ::= {nvRadconfEntry 3}

nvRadconfN1 OBJECT-TYPE
     SYNTAX   INTEGER (0..255)
     ACCESS   read-write
     STATUS   mandatory
     DESCRIPTION
        "retry counter."
     ::= {nvRadconfEntry 4}

nvRadconfT1 OBJECT-TYPE
     SYNTAX   INTEGER (0..255)
     ACCESS   read-write
     STATUS   mandatory
     DESCRIPTION
        "times between attempts."
     ::= {nvRadconfEntry 5}

nvRadconfAcct OBJECT-TYPE
     SYNTAX   INTEGER {
                disable(1),     -- (+1)
                adapt(2),
                enable(3)
                }
     ACCESS   read-write
     STATUS   mandatory
     DESCRIPTION
        "radius accounting."
     ::= {nvRadconfEntry 6}

nvRadconfNumdigits OBJECT-TYPE
     SYNTAX   INTEGER (0..255)
     ACCESS   read-write
     STATUS   mandatory
     DESCRIPTION
        "trailing port digits."
     ::= {nvRadconfEntry 7}

nvRadconfAuth1 OBJECT-TYPE
     SYNTAX   DisplayString (SIZE (0..16))
     ACCESS   read-write
     STATUS   mandatory
     DESCRIPTION
        "IP address primary auth server."
     ::= {nvRadconfEntry 8}

-- 9 is reserved

nvRadconfAuth2 OBJECT-TYPE
     SYNTAX   DisplayString (SIZE (0..16))
     ACCESS   read-write
     STATUS   mandatory
     DESCRIPTION
        "IP address secondary auth server."
     ::= {nvRadconfEntry 10}

-- 11 is reserved

nvRadconfAuth3 OBJECT-TYPE
     SYNTAX   DisplayString (SIZE (0..16))
     ACCESS   read-write
     STATUS   mandatory
     DESCRIPTION
        "IP address tertiary auth server."
     ::= {nvRadconfEntry 12}

-- 13 is reserved

nvRadconfAcct1 OBJECT-TYPE
     SYNTAX   DisplayString (SIZE (0..16))
     ACCESS   read-write
     STATUS   mandatory
     DESCRIPTION
        "IP address primary accounting."
     ::= {nvRadconfEntry 14 }

-- 15 is reserved

nvRadconfAcct2 OBJECT-TYPE
     SYNTAX   DisplayString (SIZE (0..16))
     ACCESS   read-write
     STATUS   mandatory
     DESCRIPTION
        "IP address secondary accounting."
     ::= {nvRadconfEntry 16 }

-- 17 is reserved

nvRadconfAcct3 OBJECT-TYPE
     SYNTAX   DisplayString (SIZE (0..16))
     ACCESS   read-write
     STATUS   mandatory
     DESCRIPTION
        "IP address tertiary accounting."
     ::= {nvRadconfEntry 18 }

-- 19 is reserved

nvRadconfAcctauth OBJECT-TYPE
     SYNTAX   INTEGER {
                secret(1),     -- (+1)
                zero(2)
                }
     ACCESS   read-write
     STATUS   mandatory
     DESCRIPTION
        "authorizarion encoding."
     ::= {nvRadconfEntry 20}

nvRadconfAuth1port     OBJECT-TYPE      --AF
      SYNTAX   INTEGER                   --AF 
      ACCESS   read-write                --AF
      STATUS   mandatory			--AF
      DESCRIPTION			--AF
         "authserver port1 ."		--AF
      ::= {nvRadconfEntry 21}            --AF
      
nvRadconfAuth2port     OBJECT-TYPE      --AF
      SYNTAX   INTEGER                   --AF 
      ACCESS   read-write                --AF
      STATUS   mandatory			--AF
      DESCRIPTION			--AF
         "authserver port2 ."		--AF
      ::= {nvRadconfEntry 22}            --AF

nvRadconfAuth3port     OBJECT-TYPE      --AF
      SYNTAX   INTEGER                   --AF 
      ACCESS   read-write                --AF
      STATUS   mandatory			--AF
      DESCRIPTION			--AF
         "authserver port3 ."		--AF
      ::= {nvRadconfEntry 23}            --AF
 
nvRadconfAcct1port     OBJECT-TYPE      --AF
      SYNTAX   INTEGER                   --AF 
      ACCESS   read-write                --AF
      STATUS   mandatory			--AF
      DESCRIPTION			--AF
         "account server port1 ."	--AF
      ::= {nvRadconfEntry 24}            --AF
 
nvRadconfAcct2port     OBJECT-TYPE      --AF
      SYNTAX   INTEGER                   --AF 
      ACCESS   read-write                --AF
      STATUS   mandatory			--AF
      DESCRIPTION			--AF
         "account server port2 ."	--AF
      ::= {nvRadconfEntry 25}            --AF
 
nvRadconfAcct3port     OBJECT-TYPE      --AF
      SYNTAX   INTEGER                   --AF 
      ACCESS   read-write                --AF
      STATUS   mandatory			--AF
      DESCRIPTION			--AF
         "account server port3 ."	--AF
      ::= {nvRadconfEntry 26}            --AF
 
nvRadconfAttrchk OBJECT-TYPE            --AF
      SYNTAX   INTEGER {			--AF
                 no(1),	         	--AF    
                 yes(2)          	--AF
                 }			--AF
      ACCESS   read-write		--AF
      STATUS   mandatory			--AF
      DESCRIPTION			--AF
 "Strict attribute checking."            --AF
      ::= { nvRadconfEntry 27 }

nvRadconfDnsatt1 OBJECT-TYPE          
      SYNTAX   INTEGER             
      ACCESS   read-write	      
      STATUS   mandatory	      
      DESCRIPTION		      
 " attribute code for primary DNS server"          
      ::= { nvRadconfEntry 28 }

nvRadconfDnsatt2 OBJECT-TYPE          
      SYNTAX   INTEGER             
      ACCESS   read-write	      
      STATUS   mandatory	      
      DESCRIPTION		      
 " attribute code for secondary DNS server"          
      ::= { nvRadconfEntry 29 }

nvRadconfNbnsatt1 OBJECT-TYPE          
      SYNTAX   INTEGER             
      ACCESS   read-write	      
      STATUS   mandatory	      
      DESCRIPTION		      
 " attribute code for primary NBNS server"          
      ::= { nvRadconfEntry 30}

nvRadconfStatus OBJECT-TYPE
     SYNTAX   INTEGER {
                valid(1),
                invalid(2)
                }
     ACCESS   read-write
     STATUS   mandatory
     DESCRIPTION
"Operation status. Add the record to the table (valid) or delete
the record from the table (invalid)."
     ::= { nvRadconfEntry 31 }

nvRadconfNbnsatt2 OBJECT-TYPE
      SYNTAX   INTEGER
      ACCESS   read-write
      STATUS   mandatory
      DESCRIPTION
 "attribute code for secondary NBNS server "
      ::= { nvRadconfEntry 32 }

--
--      raduser file
--

nvRaduser OBJECT IDENTIFIER ::= { nevadaRadius 2 }

nvRaduserMaxRec OBJECT-TYPE
      SYNTAX   INTEGER
      ACCESS   read-only
      STATUS   mandatory
      DESCRIPTION
                "total number of records allowed in database file."
      ::= {nvRaduser 1}

nvRaduserNumRec OBJECT-TYPE
      SYNTAX   INTEGER
      ACCESS   read-only
      STATUS   mandatory
      DESCRIPTION
                "number of records in use."
      ::= {nvRaduser 2}

nvRaduserTable OBJECT-TYPE
      SYNTAX   SEQUENCE OF NvRaduserEntry
      ACCESS   not-accessible
      STATUS   mandatory
      DESCRIPTION
               "raduser file."
      ::= {nvRaduser 3}

nvRaduserEntry OBJECT-TYPE
      SYNTAX   NvRaduserEntry
      ACCESS   not-accessible
      STATUS   mandatory
      DESCRIPTION
               "raduser record, indexed by record number"
      INDEX {nvRaduserIndex}
      ::= {nvRaduserTable 1 }

NvRaduserEntry ::=
      SEQUENCE {
        nvRaduserIndex
                INTEGER,
        nvRaduserUsername
                DisplayString,
        nvRaduserPasswd
                DisplayString,
        nvRaduserRespmsg
                INTEGER,
        nvRaduserStatus
                INTEGER
                }

nvRaduserIndex OBJECT-TYPE
     SYNTAX   INTEGER
     ACCESS   read-only
     STATUS   mandatory
     DESCRIPTION
        "Index of raduser record"
     ::= {nvRaduserEntry 1}

nvRaduserUsername OBJECT-TYPE
     SYNTAX   DisplayString (SIZE (0..16))
     ACCESS   read-write
     STATUS   mandatory
     DESCRIPTION
        "user name."
     ::= {nvRaduserEntry 2}

nvRaduserPasswd OBJECT-TYPE
     SYNTAX   DisplayString (SIZE (0..16))
     ACCESS   read-write
     STATUS   mandatory
     DESCRIPTION
        "user password."
     ::= {nvRaduserEntry 3}

nvRaduserRespmsg OBJECT-TYPE
     SYNTAX   INTEGER (0..65535)
     ACCESS   read-write
     STATUS   mandatory
     DESCRIPTION
        "stringid of response message."
     ::= {nvRaduserEntry 4}

-- 5 - 14 reserved.


nvRaduserStatus OBJECT-TYPE
     SYNTAX   INTEGER {
                valid(1),
                invalid(2)
                }
     ACCESS   read-write
     STATUS   mandatory
     DESCRIPTION
"Operation status. Add the record to the table (valid) or delete
the record from the table (invalid)."
     ::= { nvRaduserEntry 15 }

--
--      radcstat file
--

nvRadcstat OBJECT IDENTIFIER ::= { nevadaRadius 3 }

nvRadcstatMaxRec OBJECT-TYPE
      SYNTAX   INTEGER
      ACCESS   read-only
      STATUS   mandatory
      DESCRIPTION
                "total number of records allowed in database file."
      ::= {nvRadcstat 1}

nvRadcstatNumRec OBJECT-TYPE
      SYNTAX   INTEGER
      ACCESS   read-only
      STATUS   mandatory
      DESCRIPTION
                "number of records in use."
      ::= {nvRadcstat 2}

nvRadcstatTable OBJECT-TYPE
      SYNTAX   SEQUENCE OF NvRadcstatEntry
      ACCESS   not-accessible
      STATUS   mandatory
      DESCRIPTION
               "radcstat file."
      ::= {nvRadcstat 3}

nvRadcstatEntry OBJECT-TYPE
      SYNTAX   NvRadcstatEntry
      ACCESS   not-accessible
      STATUS   mandatory
      DESCRIPTION
               "radcstat record, indexed by record number"
      INDEX {nvRadcstatIndex}
      ::= {nvRadcstatTable 1 }

NvRadcstatEntry ::=
      SEQUENCE {
        nvRadcstatIndex
                INTEGER,
        nvRadcstatRadAdminS
                INTEGER,
        nvRadcstatRadcOperS
                INTEGER,
        nvRadcstatNAuths
                DisplayString,
        nvRadcstatNAuthLocl
                DisplayString,
        nvRadcstatNAuthLost
                DisplayString,
        nvRadcstatNAuthRtry
                DisplayString,
        nvRadcstatNAuth1Acc
                DisplayString,
        nvRadcstatNAuth1Rej
                DisplayString,
        nvRadcstatNAuth2Acc
                DisplayString,
        nvRadcstatNAuth2Rej
                DisplayString,
        nvRadcstatNAuth3Acc
                DisplayString,
        nvRadcstatNAuth3Rej
                DisplayString,
        nvRadcstatNAcct
                DisplayString,
        nvRadcstatNAcctLost
                DisplayString,
        nvRadcstatNAcctRtry
                DisplayString,
        nvRadcstatNAcct1
                DisplayString,
        nvRadcstatNAcct2
                DisplayString,
        nvRadcstatNAcct3
		DisplayString,
	nvRadcstatNSilent
		DisplayString,
	nvRadcstatDtreset
		DisplayString
                }

nvRadcstatIndex OBJECT-TYPE
     SYNTAX   INTEGER
     ACCESS   read-only
     STATUS   mandatory
     DESCRIPTION
        "Index of radcstat record"
     ::= {nvRadcstatEntry 1}

nvRadcstatRadAdminS OBJECT-TYPE
     SYNTAX   INTEGER {
                down(1),        -- (+1)
                up(2)
                }
     ACCESS   read-only
     STATUS   mandatory
     DESCRIPTION
        "radius admin status."
     ::= {nvRadcstatEntry 2}

nvRadcstatRadcOperS OBJECT-TYPE
     SYNTAX   INTEGER {
                down(1),        -- (+1)
                up(2)
                }
     ACCESS   read-only
     STATUS   mandatory
     DESCRIPTION
        "radius operation status."
     ::= {nvRadcstatEntry 3}

nvRadcstatNAuths OBJECT-TYPE
     SYNTAX   DisplayString (SIZE(0..12))
     ACCESS   read-only
     STATUS   mandatory
     DESCRIPTION
        "number of auth attempts."
     ::= {nvRadcstatEntry 4}

nvRadcstatNAuthLocl OBJECT-TYPE
     SYNTAX   DisplayString (SIZE(0..12))
     ACCESS   read-only
     STATUS   mandatory
     DESCRIPTION
        "number of local authorizations."
     ::= {nvRadcstatEntry 5}

nvRadcstatNAuthLost OBJECT-TYPE
     SYNTAX   DisplayString (SIZE(0..12))
     ACCESS   read-only
     STATUS   mandatory
     DESCRIPTION
        "number of authorization lost."
     ::= {nvRadcstatEntry 6}

nvRadcstatNAuthRtry OBJECT-TYPE
     SYNTAX   DisplayString (SIZE(0..12))
     ACCESS   read-only
     STATUS   mandatory
     DESCRIPTION
        "number of authentication retr."
     ::= {nvRadcstatEntry 7}

nvRadcstatNAuth1Acc OBJECT-TYPE
     SYNTAX   DisplayString (SIZE(0..12))
     ACCESS   read-only
     STATUS   mandatory
     DESCRIPTION
        "number of auth accepts by auth1."
     ::= {nvRadcstatEntry 8}

nvRadcstatNAuth1Rej OBJECT-TYPE
     SYNTAX   DisplayString (SIZE(0..12))
     ACCESS   read-only
     STATUS   mandatory
     DESCRIPTION
        "number of auth rejects by auth1."
     ::= {nvRadcstatEntry 9}

nvRadcstatNAuth2Acc OBJECT-TYPE
     SYNTAX   DisplayString (SIZE(0..12))
     ACCESS   read-only
     STATUS   mandatory
     DESCRIPTION
        "number of auth accepts by auth2."
     ::= {nvRadcstatEntry 10}

nvRadcstatNAuth2Rej OBJECT-TYPE
     SYNTAX   DisplayString (SIZE(0..12))
     ACCESS   read-only
     STATUS   mandatory
     DESCRIPTION
        "number of auth rejects by auth2."
     ::= {nvRadcstatEntry 11}

nvRadcstatNAuth3Acc OBJECT-TYPE
     SYNTAX   DisplayString (SIZE(0..12))
     ACCESS   read-only
     STATUS   mandatory
     DESCRIPTION
        "number of auth accepts by auth3."
     ::= {nvRadcstatEntry 12}

nvRadcstatNAuth3Rej OBJECT-TYPE
     SYNTAX   DisplayString (SIZE(0..12))
     ACCESS   read-only
     STATUS   mandatory
     DESCRIPTION
        "number of auth rejects by auth3."
     ::= {nvRadcstatEntry 13}

nvRadcstatNAcct OBJECT-TYPE
     SYNTAX   DisplayString (SIZE(0..12))
     ACCESS   read-only
     STATUS   mandatory
     DESCRIPTION
        "number of accounting msgs attempts."
     ::= {nvRadcstatEntry 14}

nvRadcstatNAcctLost OBJECT-TYPE
     SYNTAX   DisplayString (SIZE(0..12))
     ACCESS   read-only
     STATUS   mandatory
     DESCRIPTION
        "number of accounting records lost."
     ::= {nvRadcstatEntry 15}

nvRadcstatNAcctRtry OBJECT-TYPE
     SYNTAX   DisplayString (SIZE(0..12))
     ACCESS   read-only
     STATUS   mandatory
     DESCRIPTION
        "number of accounting msgs retry."
     ::= {nvRadcstatEntry 16}

nvRadcstatNAcct1 OBJECT-TYPE
     SYNTAX   DisplayString (SIZE(0..12))
     ACCESS   read-only
     STATUS   mandatory
     DESCRIPTION
        "number of accounting msgs acct1."
     ::= {nvRadcstatEntry 17}

nvRadcstatNAcct2 OBJECT-TYPE
     SYNTAX   DisplayString (SIZE(0..12))
     ACCESS   read-only
     STATUS   mandatory
     DESCRIPTION
        "number of accounting msgs acct2."
     ::= {nvRadcstatEntry 18}

nvRadcstatNAcct3 OBJECT-TYPE
     SYNTAX   DisplayString (SIZE(0..12))
     ACCESS   read-only
     STATUS   mandatory
     DESCRIPTION
        "number of accounting msgs acct3."
     ::= {nvRadcstatEntry 19}

nvRadcstatNSilent OBJECT-TYPE
     SYNTAX   DisplayString (SIZE(0..12))
     ACCESS   read-only
     STATUS   mandatory
     DESCRIPTION
        "num of silent discards"
     ::= {nvRadcstatEntry 20}

nvRadcstatDtreset OBJECT-TYPE
     SYNTAX   DisplayString (SIZE (0..20))
     ACCESS   read-only
     STATUS   mandatory
     DESCRIPTION
        "date & time statistics last reset"
      ::= { nvRadcstatEntry 21 }

--
--      radustat file
--

nvRadustat OBJECT IDENTIFIER ::= { nevadaRadius 4 }

nvRadustatMaxRec OBJECT-TYPE
      SYNTAX   INTEGER
      ACCESS   read-only
      STATUS   mandatory
      DESCRIPTION
                "total number of records allowed in database file."
      ::= {nvRadustat 1}

nvRadustatNumRec OBJECT-TYPE
      SYNTAX   INTEGER
      ACCESS   read-only
      STATUS   mandatory
      DESCRIPTION
                "number of records in use."
      ::= {nvRadustat 2}

nvRadustatTable OBJECT-TYPE
      SYNTAX   SEQUENCE OF NvRadustatEntry
      ACCESS   not-accessible
      STATUS   mandatory
      DESCRIPTION
               "radustat file."
      ::= {nvRadustat 3}

nvRadustatEntry OBJECT-TYPE
      SYNTAX   NvRadustatEntry
      ACCESS   not-accessible
      STATUS   mandatory
      DESCRIPTION
               "radustat record, indexed by record number"
      INDEX {nvRadustatIndex}
      ::= {nvRadustatTable 1 }

NvRadustatEntry ::=
      SEQUENCE {
        nvRadustatIndex
                INTEGER,
        nvRadustatRaduOperS
                INTEGER,
        nvRadustatSessionId
                DisplayString,
        nvRadustatUserId
                DisplayString,
        nvRadustatNasPort
                DisplayString,
        nvRadustatNasIpAddr
                DisplayString,
        nvRadustatFrmIpaddr
                DisplayString,
        nvRadustatFrmIpMask
                DisplayString,
        nvRadustatState
                DisplayString,
        nvRadustatClass
                DisplayString,
        nvRadustatSType
                INTEGER,
        nvRadustatFrmProto
                INTEGER,
        nvRadustatFrmRting
                INTEGER,
        nvRadustatSTime
                INTEGER,
        nvRadustatFrmMtu
                INTEGER,
        nvRadustatFrmRt
                INTEGER,
        nvRadustatSTimeout
                INTEGER,
        nvRadustatITimeout
                INTEGER,
        nvRadustatDFilter
                INTEGER,
        nvRadustatReqId
                DisplayString,
	nvRadustatDtreset
		DisplayString
                }

nvRadustatIndex OBJECT-TYPE
     SYNTAX   INTEGER
     ACCESS   read-only
     STATUS   mandatory
     DESCRIPTION
        "Index of radustat record"
     ::= {nvRadustatEntry 1}

nvRadustatRaduOperS OBJECT-TYPE
     SYNTAX   INTEGER {
                idle(1),                -- (+1)
                open(2),
                ready(3),
                waiting(4),
                active(5),
                astart(6),
                astop(7)
                }
     ACCESS   read-only
     STATUS   mandatory
     DESCRIPTION
        "User operation/session status."
     ::= { nvRadustatEntry 2 }

nvRadustatSessionId OBJECT-TYPE
     SYNTAX   DisplayString (SIZE (0..18))
     ACCESS   read-only
     STATUS   mandatory
     DESCRIPTION
        "accounting session-id name."
     ::= {nvRadustatEntry 3}

nvRadustatUserId OBJECT-TYPE
     SYNTAX   DisplayString (SIZE (0..64))
     ACCESS   read-only
     STATUS   mandatory
     DESCRIPTION
        "user/host name of requestor."
     ::= {nvRadustatEntry 4}

nvRadustatNasPort OBJECT-TYPE
     SYNTAX   DisplayString (SIZE (0..16))
     ACCESS   read-only
     STATUS   mandatory
     DESCRIPTION
        "Called address."
     ::= {nvRadustatEntry 5}

nvRadustatNasIpAddr OBJECT-TYPE
     SYNTAX   DisplayString (SIZE (0..16))
     ACCESS   read-only
     STATUS   mandatory
     DESCRIPTION
        "NAS IP address."
     ::= {nvRadustatEntry 6}

nvRadustatFrmIpaddr OBJECT-TYPE
     SYNTAX   DisplayString (SIZE (0..16))
     ACCESS   read-only
     STATUS   mandatory
     DESCRIPTION
        "Framed IP address."
     ::= {nvRadustatEntry 7}

nvRadustatFrmIpMask OBJECT-TYPE
     SYNTAX   DisplayString (SIZE (0..16))
     ACCESS   read-only
     STATUS   mandatory
     DESCRIPTION
        "Framed IP mask."
     ::= {nvRadustatEntry 8}

-- 9, 10, 11, 12 reserved

nvRadustatState OBJECT-TYPE
     SYNTAX   DisplayString (SIZE (0..64))
     ACCESS   read-only
     STATUS   mandatory
     DESCRIPTION
        "state."
     ::= {nvRadustatEntry 13}

nvRadustatClass OBJECT-TYPE
     SYNTAX   DisplayString (SIZE (0..64))
     ACCESS   read-only
     STATUS   mandatory
     DESCRIPTION
        "class."
     ::= {nvRadustatEntry 14}

nvRadustatSType OBJECT-TYPE
     SYNTAX   INTEGER {
                none(1),                -- (+1)
                login(2),
                framed(3),
                callBackLogin(4),
                callBackFramed(5),
                outboundUser(6),
                adminUser(7),
                execUser(8),
                authOnly(9)
                }
     ACCESS   read-only
     STATUS   mandatory
     DESCRIPTION "Service type."
     ::= { nvRadustatEntry 15 }

-- 16 reserved

nvRadustatFrmProto OBJECT-TYPE
     SYNTAX   INTEGER {
                notSet(1),              -- (+1)
                ppp(2),
                slip(3)
                }
     ACCESS   read-only
     STATUS   mandatory
     DESCRIPTION "Framed protocol type."
     ::= { nvRadustatEntry 17 }

nvRadustatFrmRting OBJECT-TYPE
     SYNTAX   INTEGER {
                none(1),                -- (+1)
                sendRtPkt(2),
                listenRtPkt(3),
                sendListen(4)
                }
     ACCESS   read-only
     STATUS   mandatory
     DESCRIPTION "Framed routing attribute type."
     ::= { nvRadustatEntry 18 }

nvRadustatSTime OBJECT-TYPE
     SYNTAX   INTEGER
     ACCESS   read-only
     STATUS   mandatory
     DESCRIPTION "Seconds the call was active."
     ::= { nvRadustatEntry 19 }

nvRadustatFrmMtu OBJECT-TYPE
     SYNTAX   INTEGER
     ACCESS   read-only
     STATUS   mandatory
     DESCRIPTION "Framed mtu."
     ::= { nvRadustatEntry 20 }

nvRadustatFrmRt OBJECT-TYPE
     SYNTAX   INTEGER
     ACCESS   read-only
     STATUS   mandatory
     DESCRIPTION "Framed route."
     ::= { nvRadustatEntry 21 }

nvRadustatSTimeout OBJECT-TYPE
     SYNTAX   INTEGER
     ACCESS   read-only
     STATUS   mandatory
     DESCRIPTION "Session timeout."
     ::= { nvRadustatEntry 22 }

nvRadustatITimeout OBJECT-TYPE
     SYNTAX   INTEGER
     ACCESS   read-only
     STATUS   mandatory
     DESCRIPTION "Idle timeout."
     ::= { nvRadustatEntry 23 }

nvRadustatDFilter OBJECT-TYPE
     SYNTAX   INTEGER
     ACCESS   read-only
     STATUS   mandatory
     DESCRIPTION "Data filters."
     ::= { nvRadustatEntry 24 }

nvRadustatReqId OBJECT-TYPE
     SYNTAX   DisplayString (SIZE(0..12))
     ACCESS   read-only
     STATUS   mandatory
     DESCRIPTION  "Request ID of outstanding radius msgs."
     ::= { nvRadustatEntry 25 }

nvRadustatDtreset OBJECT-TYPE
     SYNTAX   DisplayString (SIZE (0..20))
     ACCESS   read-only
     STATUS   mandatory
     DESCRIPTION
        "date & time statistics last reset"
      ::= { nvRadustatEntry 26 }

--
--       SNMP
--
--
--       snmpconf file
--
nvSnmpconf OBJECT IDENTIFIER ::= { nevadaSnmp 1 }
--
nvSnmpconfMaxRec OBJECT-TYPE
     SYNTAX   INTEGER
     ACCESS   read-only
     STATUS   mandatory
     DESCRIPTION
        "total number of records allowed in database file."
     ::= { nvSnmpconf 1 }

nvSnmpconfNumRec OBJECT-TYPE
     SYNTAX   INTEGER
     ACCESS   read-only
     STATUS   mandatory
     DESCRIPTION
        "number of records in use."
     ::= { nvSnmpconf 2 }

nvSnmpconfTable OBJECT-TYPE
      SYNTAX   SEQUENCE OF NvSnmpconfEntry
      ACCESS   not-accessible
      STATUS   mandatory
      DESCRIPTION
               "Snmpconf file."
      ::= { nvSnmpconf 3 }

nvSnmpconfEntry OBJECT-TYPE
      SYNTAX   NvSnmpconfEntry
      ACCESS   not-accessible
      STATUS   mandatory
      DESCRIPTION
               "Snmpconf record."
      INDEX { nvSnmpconfIndex }
      ::= { nvSnmpconfTable 1 }

NvSnmpconfEntry ::=
      SEQUENCE {
	nvSnmpconfIndex
		INTEGER,
        nvSnmpconflocation
                DisplayString,
        nvSnmpconfcontact
                DisplayString,
        nvSnmpconfsysname
                DisplayString,
        nvSnmpconfauthen
                INTEGER,
        nvSnmpconfstatus
                INTEGER
                }

nvSnmpconfIndex OBJECT-TYPE
     SYNTAX   INTEGER
     ACCESS   read-only
     STATUS   mandatory
     DESCRIPTION
        "Index of nvSnmpconf record"
      ::= { nvSnmpconfEntry 1 }


nvSnmpconflocation OBJECT-TYPE
     SYNTAX   DisplayString (SIZE (0..64))
     ACCESS   read-write
     STATUS   mandatory
     DESCRIPTION
        "Location "
      ::= { nvSnmpconfEntry 2 }

nvSnmpconfcontact OBJECT-TYPE
     SYNTAX   DisplayString (SIZE (0..64))
     ACCESS   read-write
     STATUS   mandatory
     DESCRIPTION
        "contact "
      ::= { nvSnmpconfEntry 3 }

nvSnmpconfsysname OBJECT-TYPE
     SYNTAX   DisplayString (SIZE (0..64))
     ACCESS   read-write
     STATUS   mandatory
     DESCRIPTION
        "sysname "
      ::= { nvSnmpconfEntry 4 }

nvSnmpconfauthen OBJECT-TYPE
     SYNTAX   INTEGER {
                yes(2),
                no(3)
                }
     ACCESS   read-write
     STATUS   mandatory
     DESCRIPTION
        "authentication trap yes(1)/no(2) "
      ::= { nvSnmpconfEntry 5 }

nvSnmpconfstatus OBJECT-TYPE
     SYNTAX   INTEGER {
                valid(1),
                invalid(2)
                }
     ACCESS   read-write
     STATUS   mandatory
     DESCRIPTION
"Operation status. Add the record to the table (valid) or delete
the record from the table (invalid)."
     ::= { nvSnmpconfEntry 6 }


--
--
--       snmpmgr file
--
nvSnmpmgr  OBJECT IDENTIFIER ::= { nevadaSnmp 2 }
--
nvSnmpmgrMaxRec OBJECT-TYPE
     SYNTAX   INTEGER
     ACCESS   read-only
     STATUS   mandatory
     DESCRIPTION
        "total number of records allowed in database file."
     ::= { nvSnmpmgr 1 }

nvSnmpmgrNumRec OBJECT-TYPE
     SYNTAX   INTEGER
     ACCESS   read-only
     STATUS   mandatory
     DESCRIPTION
        "number of records in use."
     ::= { nvSnmpmgr 2 }

nvSnmpmgrTable OBJECT-TYPE
      SYNTAX   SEQUENCE OF NvSnmpmgrEntry
      ACCESS   not-accessible
      STATUS   mandatory
      DESCRIPTION
               "Snmpmgr file."
      ::= { nvSnmpmgr 3 }

nvSnmpmgrEntry OBJECT-TYPE
      SYNTAX   NvSnmpmgrEntry
      ACCESS   not-accessible
      STATUS   mandatory
      DESCRIPTION
               "Snmpmgr record."
      INDEX { nvSnmpmgrIndex }
      ::= { nvSnmpmgrTable 1 }

NvSnmpmgrEntry ::=
      SEQUENCE {
	nvSnmpmgrIndex
		INTEGER,
	nvSnmpmgrIp
		DisplayString,
	nvSnmpmgrComm
		DisplayString,
	nvSnmpmgrAccPriv
		INTEGER,
	nvSnmpmgrSndTrap
		INTEGER,
	nvSnmpmgrstatus
		INTEGER

	}

nvSnmpmgrIndex OBJECT-TYPE
     SYNTAX   INTEGER
     ACCESS   read-only
     STATUS   mandatory
     DESCRIPTION
        "Index of nvSnmpmgr record"
      ::= { nvSnmpmgrEntry 1 }

nvSnmpmgrIp OBJECT-TYPE
     SYNTAX   DisplayString (SIZE (0..16))
     ACCESS   read-write
     STATUS   mandatory
     DESCRIPTION
        "IP address "
      ::= { nvSnmpmgrEntry 2 }

nvSnmpmgrComm OBJECT-TYPE
     SYNTAX   DisplayString (SIZE (0..64))
     ACCESS   read-write
     STATUS   mandatory
     DESCRIPTION
        "community "
      ::= { nvSnmpmgrEntry 3 }

nvSnmpmgrAccPriv OBJECT-TYPE
     SYNTAX   INTEGER {
                ro(1),
                rw(2),
                wo(3)
                }
     ACCESS   read-write
     STATUS   mandatory
     DESCRIPTION
        "Access priv "
      ::= { nvSnmpmgrEntry 4 }

nvSnmpmgrSndTrap OBJECT-TYPE
     SYNTAX   INTEGER {
                yes(1),
                no(2)
                }
     ACCESS   read-write
     STATUS   mandatory
     DESCRIPTION
        "Send trap  "
      ::= { nvSnmpmgrEntry 5 }

nvSnmpmgrstatus OBJECT-TYPE
     SYNTAX   INTEGER {
                valid(1),
                invalid(2)
                }
     ACCESS   read-write
     STATUS   mandatory
     DESCRIPTION
"Operation status. Add the record to the table (valid) or delete
the record from the table (invalid)."
     ::= { nvSnmpmgrEntry 6 }



--
--
--       snmpstat file
--
-- nvSnmpstat OBJECT IDENTIFIER ::= { nevadaSnmp 3 }
--

--
-- pos
--

nvPosprof OBJECT IDENTIFIER ::= { nevadaPos 1 }

nvPosprofMaxRec OBJECT-TYPE
      SYNTAX   INTEGER
      ACCESS   read-only
      STATUS   mandatory
      DESCRIPTION
		"total number of records allowed in database file."
      ::= { nvPosprof 1}

nvPosprofNumRec OBJECT-TYPE
      SYNTAX   INTEGER
      ACCESS   read-only
      STATUS   mandatory
      DESCRIPTION
		"number of records in use."
      ::= { nvPosprof 2}

nvPosprofTable OBJECT-TYPE
      SYNTAX   SEQUENCE OF NvPosprofEntry
      ACCESS   not-accessible
      STATUS   mandatory
      DESCRIPTION
               "NEvada node posprof file."
      ::= { nvPosprof 3 }

nvPosprofEntry OBJECT-TYPE
      SYNTAX   NvPosprofEntry
      ACCESS   not-accessible
      STATUS   mandatory
      DESCRIPTION
               "Nevada node posprof record."
      INDEX { nvPosprofIndex }
      ::= { nvPosprofTable 1 }

NvPosprofEntry ::=
      SEQUENCE {
      nvPosprofIndex
            INTEGER,
      nvPosprofName
            DisplayString,
      nvPosprofSize
            INTEGER,
      nvPosprofNumchan
            INTEGER,
      nvPosprofPermchan
            INTEGER,
      nvPosprofDirection
            INTEGER,
      nvPosprofProtocol
            INTEGER,
      nvPosprofAddrtype
            INTEGER,
      nvPosprofUserdata
            DisplayString,
      nvPosprofMode
            INTEGER,
      nvPosprofIdletime
            INTEGER,
      nvPosprofRouting
            INTEGER,
      nvPosprofTranslate
            INTEGER,
      nvPosprofTpduaddr
            DisplayString,
      nvPosprofEftrspto
            INTEGER,
      nvPosprofRetrytim
            INTEGER,
      nvPosprofNretry
            INTEGER,
      nvPosprofActsupl
            INTEGER,
      nvPosprofResptim
            INTEGER,
      nvPosprofPolltim
            INTEGER,
      nvPosprofPolladdr
            DisplayString,
      nvPosprofSkip
            INTEGER,
      nvPosprofTcpmsglen
            INTEGER,
      nvPosprofPortname
            DisplayString,
      nvPosprofRsrcpool
            DisplayString,
      nvPosprofStatus
            INTEGER
                }

nvPosprofIndex OBJECT-TYPE
     SYNTAX   INTEGER
     ACCESS   read-only
     STATUS   mandatory
     DESCRIPTION
	"Index of nevada posprof record"
      ::= { nvPosprofEntry 1 }

nvPosprofName OBJECT-TYPE
     SYNTAX   DisplayString (SIZE (0..16))
     ACCESS   read-write
     STATUS   mandatory
     DESCRIPTION
"Profile Name."
     ::= { nvPosprofEntry 2 }

nvPosprofSize OBJECT-TYPE
     SYNTAX   INTEGER {
                b128(1),     --  (+1)
                b256(2),     --
                b512(3),     --
                b1024(4),     --
                b2048(5),     --
                b4096(6)      --
		}
     ACCESS   read-write
     STATUS   mandatory
     DESCRIPTION
"max bytes per frame
Default value is 128 (0+1)."
     ::= { nvPosprofEntry 3 }

nvPosprofNumchan OBJECT-TYPE
     SYNTAX   INTEGER
     ACCESS   read-write
     STATUS   mandatory
     DESCRIPTION
"max number of channels
Default value is 1."
     ::= { nvPosprofEntry 4 }

-- reserved 5

nvPosprofPermchan OBJECT-TYPE
     SYNTAX   INTEGER
     ACCESS   read-write
     STATUS   mandatory
     DESCRIPTION
"min number of channels
"
     ::= { nvPosprofEntry 6 }

nvPosprofDirection OBJECT-TYPE
     SYNTAX   INTEGER {
                uplink(1),     -- this connection leads toward host (+1)
                dnlink(2),      -- this connection leads toward terminal
		nmslink(3)	-- used to forward nms messages
		}
     ACCESS   read-write
     STATUS   mandatory
     DESCRIPTION
"up or down?
Default value is dnlink (1+1)."
     ::= { nvPosprofEntry 7 }

nvPosprofProtocol OBJECT-TYPE
     SYNTAX   INTEGER {
                sdlc(1),     -- simple SDLC subset (+1)
                x25(2),     -- X.25 through nbus
                visa(3),     -- visa terminal protocol
                tcp(4),      -- TCP/IP through nbus
		spdh(5),
		dfono(6),
		dtfspc(7),
		dtfgen(8)
		}
     ACCESS   read-write
     STATUS   mandatory
     DESCRIPTION
	"protocol on port
		Default value is visa."
     ::= { nvPosprofEntry 8 }

nvPosprofAddrtype OBJECT-TYPE
     SYNTAX   INTEGER {
                none(1),     -- use no address headder (+1)
                tpdu(2),      -- use a TPDU to multiplex messages
		fast3(3),
		fast6(4)
		}
     ACCESS   read-write
     STATUS   mandatory
     DESCRIPTION
"address header
Default value is tpdu."
     ::= { nvPosprofEntry 9 }

nvPosprofUserdata OBJECT-TYPE
     SYNTAX   DisplayString (SIZE (0..12))
     ACCESS   read-write
     STATUS   mandatory
     DESCRIPTION
"call user data
"
     ::= { nvPosprofEntry 10 }

nvPosprofMode OBJECT-TYPE
     SYNTAX   INTEGER {
                m8n1(1),     -- use no address headder (+1)
                m7e1(2),      -- use a TPDU to multiplex messages
		m7o1(3),
		m7m1(4),
		m7s1(5)
		}
     ACCESS   read-write
     STATUS   mandatory
     DESCRIPTION
	"Mode of operation.
		Default is 7E1."
     ::= { nvPosprofEntry 11 }

nvPosprofIdletime OBJECT-TYPE
     SYNTAX   INTEGER
     ACCESS   read-write
     STATUS   mandatory
     DESCRIPTION
"max num secs channel can remain idle
"
     ::= { nvPosprofEntry 12 }

nvPosprofRouting OBJECT-TYPE
     SYNTAX   INTEGER {
                datartg(1),     -- route messages based upon their contents (+1)
                tpdurtg(2)      -- route based on the TPDU
		}
     ACCESS   read-write
     STATUS   mandatory
     DESCRIPTION
	"look at data or tpdu?
	Default value is tpdurtg (1+1)."
     ::= { nvPosprofEntry 13 }

nvPosprofTranslate OBJECT-TYPE
     SYNTAX   INTEGER {
		none(1),	-- no translation (+1)
		ascii(2),	-- ebcdic to ascii
		ebcdic(3),	-- ascii to ebcdic
		fastpos(4)	-- ascii to ebcdic (for Fastpos)
		}
     ACCESS   read-write
     STATUS   mandatory
     DESCRIPTION
	"message translation."
     ::= { nvPosprofEntry 14 }

nvPosprofTpduaddr OBJECT-TYPE
     SYNTAX   DisplayString (SIZE (0..4))
     ACCESS   read-write
     STATUS   mandatory
     DESCRIPTION
	"use this when tpdu not supplied (but required)."
     ::= { nvPosprofEntry 15 }

nvPosprofEftrspto OBJECT-TYPE
     SYNTAX   INTEGER
     ACCESS   read-write
     STATUS   mandatory
     DESCRIPTION
"number of seconds before addr table entry cleared
Default value is 300."
     ::= { nvPosprofEntry 16 }

nvPosprofRetrytim OBJECT-TYPE
     SYNTAX   INTEGER
     ACCESS   read-write
     STATUS   mandatory
     DESCRIPTION
"retry timer
Default value is 100."
     ::= { nvPosprofEntry 17 }

nvPosprofNretry OBJECT-TYPE
     SYNTAX   INTEGER
     ACCESS   read-write
     STATUS   mandatory
     DESCRIPTION
"max retry attempts
Default value is 3."
     ::= { nvPosprofEntry 18 }

nvPosprofActsupl OBJECT-TYPE
     SYNTAX   INTEGER {
		none(1),	-- 
		sndnak(2),	--
		reverse(3),	
		muzo(4),
		closelcn(5),
		fdr(6)
		}
     ACCESS   read-write
     STATUS   mandatory
     DESCRIPTION
	"Action after responce is sent to terminal."
     ::= { nvPosprofEntry 19 }

nvPosprofResptim OBJECT-TYPE
     SYNTAX   INTEGER
     ACCESS   read-write
     STATUS   mandatory
     DESCRIPTION
"host response timer
Default value is 100."
     ::= { nvPosprofEntry 20 }

nvPosprofPolltim OBJECT-TYPE
     SYNTAX   INTEGER
     ACCESS   read-write
     STATUS   mandatory
     DESCRIPTION
"poll timer
Default value is 5."
     ::= { nvPosprofEntry 21 }

nvPosprofPolladdr OBJECT-TYPE
     SYNTAX   DisplayString (SIZE (0..2))
     ACCESS   read-write
     STATUS   mandatory
     DESCRIPTION
"base poll address,hex
"
     ::= { nvPosprofEntry 22 }

nvPosprofSkip OBJECT-TYPE
     SYNTAX   INTEGER
     ACCESS   read-write
     STATUS   mandatory
     DESCRIPTION
"number of cycles to skip for non-func device
Default value is 4."
     ::= { nvPosprofEntry 23 }

nvPosprofTcpmsglen OBJECT-TYPE
     SYNTAX   INTEGER {
                none(1),     --  (+1)
		vap(2),
		bin2(3),
		bin3(4),
		bin4(5)
		}
     ACCESS   read-write
     STATUS   mandatory
     DESCRIPTION
	"TCP msg header format.
	Default value is bin4."
     ::= { nvPosprofEntry 24 }

nvPosprofPortname OBJECT-TYPE
     SYNTAX   DisplayString (SIZE (0..10))
     ACCESS   read-write
     STATUS   mandatory
     DESCRIPTION
	"Name of physical port or Device Usage Group."
     ::= { nvPosprofEntry 25 }

nvPosprofRsrcpool OBJECT-TYPE
     SYNTAX   DisplayString (SIZE (0..11))
     ACCESS   read-write
     STATUS   mandatory
     DESCRIPTION
	"Resource Pool Name."
     ::= { nvPosprofEntry 26 }

nvPosprofStatus OBJECT-TYPE
     SYNTAX   INTEGER {
                valid(1),
                invalid(2)
		}
     ACCESS   read-write
     STATUS   mandatory
     DESCRIPTION
"Operation status of the record. Use valid to add
record to database file and invalid to delete
record from database file."
     ::= { nvPosprofEntry 27 }


nvPosconf OBJECT IDENTIFIER ::= { nevadaPos 2 }

nvPosconfMaxRec OBJECT-TYPE
      SYNTAX   INTEGER
      ACCESS   read-only
      STATUS   mandatory
      DESCRIPTION
		"total number of records allowed in database file."
      ::= { nvPosconf 1}

nvPosconfNumRec OBJECT-TYPE
      SYNTAX   INTEGER
      ACCESS   read-only
      STATUS   mandatory
      DESCRIPTION
		"number of records in use."
      ::= { nvPosconf 2}

nvPosconfTable OBJECT-TYPE
      SYNTAX   SEQUENCE OF NvPosconfEntry
      ACCESS   not-accessible
      STATUS   mandatory
      DESCRIPTION
               "NEvada node posconf file."
      ::= { nvPosconf 3 }

nvPosconfEntry OBJECT-TYPE
      SYNTAX   NvPosconfEntry
      ACCESS   not-accessible
      STATUS   mandatory
      DESCRIPTION
               "Nevada node posprof record."
      INDEX { nvPosconfIndex }
      ::= { nvPosconfTable 1 }

NvPosconfEntry ::=
      SEQUENCE {
      nvPosconfIndex
            INTEGER,
      nvPosconfName
            DisplayString,
      nvPosconfEnable
	    INTEGER,
      nvPosconfProfile
            DisplayString,
      nvPosconfStatus
	    INTEGER
    	}

nvPosconfIndex OBJECT-TYPE
     SYNTAX   INTEGER
     ACCESS   read-only
     STATUS   mandatory
     DESCRIPTION
	"Index of nevada posconf record"
      ::= { nvPosconfEntry 1 }

nvPosconfName OBJECT-TYPE
     SYNTAX   DisplayString (SIZE (0..16))
     ACCESS   read-write
     STATUS   mandatory
     DESCRIPTION
"either POS# or X.121 Address."
     ::= { nvPosconfEntry 2 }

nvPosconfEnable OBJECT-TYPE
     SYNTAX   INTEGER {
                no(1),     --  (+1)
                yes(2)      --
		}
     ACCESS   read-write
     STATUS   mandatory
     DESCRIPTION
"Enabled or not."
     ::= { nvPosconfEntry 3 }

nvPosconfProfile OBJECT-TYPE
     SYNTAX   DisplayString (SIZE (0..16))
     ACCESS   read-write
     STATUS   mandatory
     DESCRIPTION
	"Name of profile (in posprof) being used."
     ::= { nvPosconfEntry 4 }

nvPosconfStatus OBJECT-TYPE
     SYNTAX   INTEGER {
                valid(1),
                invalid(2)
		}
     ACCESS   read-write
     STATUS   mandatory
     DESCRIPTION
"Operation status of the record. Use valid to add
record to database file and invalid to delete
record from database file."
      ::= { nvPosconfEntry 5 }


nvPosmsgmap OBJECT IDENTIFIER ::= { nevadaPos 3 }

nvPosmsgmapMaxRec OBJECT-TYPE
      SYNTAX   INTEGER
      ACCESS   read-only
      STATUS   mandatory
      DESCRIPTION
		"total number of records allowed in database file."
      ::= { nvPosmsgmap 1}

nvPosmsgmapNumRec OBJECT-TYPE
      SYNTAX   INTEGER
      ACCESS   read-only
      STATUS   mandatory
      DESCRIPTION
		"number of records in use."
      ::= { nvPosmsgmap 2}

nvPosmsgmapTable OBJECT-TYPE
      SYNTAX   SEQUENCE OF NvPosmsgmapEntry
      ACCESS   not-accessible
      STATUS   mandatory
      DESCRIPTION
               "Nevada node posmsgmap file."
      ::= { nvPosmsgmap 3 }

nvPosmsgmapEntry OBJECT-TYPE
      SYNTAX   NvPosmsgmapEntry
      ACCESS   not-accessible
      STATUS   mandatory
      DESCRIPTION
               "nevada node posmsgmap record."
      INDEX { nvPosmsgmapIndex }
      ::= { nvPosmsgmapTable 1 }

NvPosmsgmapEntry ::=
      SEQUENCE {
      nvPosmsgmapIndex
            INTEGER,
      nvPosmsgmapPattern
            INTEGER,
      nvPosmsgmapDest
            DisplayString,
      nvPosmsgmapStatus
            INTEGER
	}

nvPosmsgmapIndex OBJECT-TYPE
     SYNTAX   INTEGER
     ACCESS   read-only
     STATUS   mandatory
     DESCRIPTION
	"Index of nevada posmsgmap record"
      ::= { nvPosmsgmapEntry 1 }

nvPosmsgmapPattern OBJECT-TYPE
     SYNTAX   INTEGER (0..65535)
     ACCESS   read-write
     STATUS   mandatory
     DESCRIPTION
"pointer to pattern in string storage
"
     ::= { nvPosmsgmapEntry 2 }

nvPosmsgmapDest OBJECT-TYPE
     SYNTAX   DisplayString (SIZE (0..16))
     ACCESS   read-write
     STATUS   mandatory
     DESCRIPTION
"port/link or X.121 address
"
     ::= { nvPosmsgmapEntry 3 }

nvPosmsgmapStatus OBJECT-TYPE
     SYNTAX   INTEGER {
                valid(1),
                invalid(2)
		}
     ACCESS   read-write
     STATUS   mandatory
     DESCRIPTION
"Operation status of the record. Use valid to add
record to database file and invalid to delete
record from database file."
      ::= { nvPosmsgmapEntry 4 }


nvPosniimap OBJECT IDENTIFIER ::= { nevadaPos 4 }

nvPosniimapMaxRec OBJECT-TYPE
      SYNTAX   INTEGER
      ACCESS   read-only
      STATUS   mandatory
      DESCRIPTION
		"total number of records allowed in database file."
      ::= { nvPosniimap 1}

nvPosniimapNumRec OBJECT-TYPE
      SYNTAX   INTEGER
      ACCESS   read-only
      STATUS   mandatory
      DESCRIPTION
		"number of records in use."
      ::= { nvPosniimap 2}

nvPosniimapTable OBJECT-TYPE
      SYNTAX   SEQUENCE OF NvPosniimapEntry
      ACCESS   not-accessible
      STATUS   mandatory
      DESCRIPTION
               "nevada node posniimap file."
      ::= { nvPosniimap 3 }

nvPosniimapEntry OBJECT-TYPE
      SYNTAX   NvPosniimapEntry
      ACCESS   not-accessible
      STATUS   mandatory
      DESCRIPTION
               "Nevada node posniimap record."
      INDEX { nvPosniimapIndex }
      ::= { nvPosniimapTable 1 }

NvPosniimapEntry ::=
      SEQUENCE {
      nvPosniimapIndex
	    INTEGER,
      nvPosniimapTpduaddr
            DisplayString,
      nvPosniimapDest
            DisplayString,
      nvPosniimapStatus
            INTEGER
               }

nvPosniimapIndex OBJECT-TYPE
     SYNTAX   INTEGER
     ACCESS   read-only
     STATUS   mandatory
     DESCRIPTION
	"Index of nevada posniimap record"
      ::= { nvPosniimapEntry 1 }

nvPosniimapTpduaddr OBJECT-TYPE
     SYNTAX   DisplayString (SIZE (0..4))
     ACCESS   read-write
     STATUS   mandatory
     DESCRIPTION
"NII value to match
"
     ::= { nvPosniimapEntry 2 }

nvPosniimapDest OBJECT-TYPE
     SYNTAX   DisplayString (SIZE (0..16))
     ACCESS   read-write
     STATUS   mandatory
     DESCRIPTION
"port/link or X.121 address
"
     ::= { nvPosniimapEntry 3 }

nvPosniimapStatus OBJECT-TYPE
     SYNTAX   INTEGER {
                valid(1),
                invalid(2)
		}
     ACCESS   read-write
     STATUS   mandatory
     DESCRIPTION
"Operation status of the record. Use valid to add
record to database file and invalid to delete
record from database file."
      ::= { nvPosniimapEntry 4 }


nvPosnmsmap OBJECT IDENTIFIER ::= { nevadaPos 5 }

nvPosnmsmapMaxRec OBJECT-TYPE
      SYNTAX   INTEGER
      ACCESS   read-only
      STATUS   mandatory
      DESCRIPTION
		"total number of records allowed in database file."
      ::= { nvPosnmsmap 1}

nvPosnmsmapNumRec OBJECT-TYPE
      SYNTAX   INTEGER
      ACCESS   read-only
      STATUS   mandatory
      DESCRIPTION
		"number of records in use."
      ::= { nvPosnmsmap 2}

nvPosnmsmapTable OBJECT-TYPE
      SYNTAX   SEQUENCE OF NvPosnmsmapEntry
      ACCESS   not-accessible
      STATUS   mandatory
      DESCRIPTION
               "nevada node posnmsmap file."
      ::= { nvPosnmsmap 3 }

nvPosnmsmapEntry OBJECT-TYPE
      SYNTAX   NvPosnmsmapEntry
      ACCESS   not-accessible
      STATUS   mandatory
      DESCRIPTION
               "nevada node posnmsmap record."
      INDEX { nvPosnmsmapIndex }
      ::= { nvPosnmsmapTable 1 }

NvPosnmsmapEntry ::=
      SEQUENCE {
      nvPosnmsmapIndex
	    INTEGER,
      nvPosnmsmapNmsid
            DisplayString,
      nvPosnmsmapDest
            DisplayString,
      nvPosnmsmapStatus
            INTEGER
               }

nvPosnmsmapIndex OBJECT-TYPE
     SYNTAX   INTEGER
     ACCESS   read-only
     STATUS   mandatory
     DESCRIPTION
	"Index of nevada posnmsmap record"
      ::= { nvPosnmsmapEntry 1 }

nvPosnmsmapNmsid OBJECT-TYPE
     SYNTAX   DisplayString (SIZE (0..2))
     ACCESS   read-write
     STATUS   mandatory
     DESCRIPTION
"two digit hex NMS ID
"
     ::= { nvPosnmsmapEntry 2 }

nvPosnmsmapDest OBJECT-TYPE
     SYNTAX   DisplayString (SIZE (0..16))
     ACCESS   read-write
     STATUS   mandatory
     DESCRIPTION
"port/link or X.121 address
"
     ::= { nvPosnmsmapEntry 3 }

nvPosnmsmapStatus OBJECT-TYPE
     SYNTAX   INTEGER {
                valid(1),
                invalid(2)
		}
     ACCESS   read-write
     STATUS   mandatory
     DESCRIPTION
"Operation status of the record. Use valid to add
record to database file and invalid to delete
record from database file."
      ::= { nvPosnmsmapEntry 4 }


nvPosiso OBJECT IDENTIFIER ::= { nevadaPos 6 }

nvPosisoMaxRec OBJECT-TYPE
      SYNTAX   INTEGER
      ACCESS   read-only
      STATUS   mandatory
      DESCRIPTION
		"total number of records allowed in database file."
      ::= { nvPosiso 1}

nvPosisoNumRec OBJECT-TYPE
      SYNTAX   INTEGER
      ACCESS   read-only
      STATUS   mandatory
      DESCRIPTION
		"number of records in use."
      ::= { nvPosiso 2}

nvPosisoTable OBJECT-TYPE
      SYNTAX   SEQUENCE OF NvPosisoEntry
      ACCESS   not-accessible
      STATUS   mandatory
      DESCRIPTION
               "nevada node posiso file."
      ::= { nvPosiso 3 }

nvPosisoEntry OBJECT-TYPE
      SYNTAX   NvPosisoEntry
      ACCESS   not-accessible
      STATUS   mandatory
      DESCRIPTION
               "navada node posiso record."
      INDEX { nvPosisoIndex }
      ::= { nvPosisoTable 1 }

NvPosisoEntry ::=
      SEQUENCE {
      nvPosisoIndex
            INTEGER,
      nvPosisoName
            DisplayString,
      nvPosisoContrec
	    INTEGER,
      nvPosisoField2
            INTEGER,
      nvPosisoField3
            INTEGER,
      nvPosisoField4
            INTEGER,
      nvPosisoField5
            INTEGER,
      nvPosisoField6
            INTEGER,
      nvPosisoField7
            INTEGER,
      nvPosisoField8
            INTEGER,
      nvPosisoField9
            INTEGER,
      nvPosisoField10
            INTEGER,
      nvPosisoField11
            INTEGER,
      nvPosisoField12
            INTEGER,
      nvPosisoField13
            INTEGER,
      nvPosisoField14
            INTEGER,
      nvPosisoField15
            INTEGER,
      nvPosisoField16
            INTEGER,
      nvPosisoField17
            INTEGER,
      nvPosisoField18
            INTEGER,
      nvPosisoField19
            INTEGER,
      nvPosisoField20
            INTEGER,
      nvPosisoField21
            INTEGER,
      nvPosisoField22
            INTEGER,
      nvPosisoField23
            INTEGER,
      nvPosisoField24
            INTEGER,
      nvPosisoField25
            INTEGER,
      nvPosisoField26
            INTEGER,
      nvPosisoField27
            INTEGER,
      nvPosisoField28
            INTEGER,
      nvPosisoField29
            INTEGER,
      nvPosisoField30
            INTEGER,
      nvPosisoField31
            INTEGER,
      nvPosisoField32
            INTEGER,
      nvPosisoField33
            INTEGER,
      nvPosisoField34
            INTEGER,
      nvPosisoField35
            INTEGER,
      nvPosisoField36
            INTEGER,
      nvPosisoField37
            INTEGER,
      nvPosisoField38
            INTEGER,
      nvPosisoField39
            INTEGER,
      nvPosisoField40
            INTEGER,
      nvPosisoField41
            INTEGER,
      nvPosisoField42
            INTEGER,
      nvPosisoField43
            INTEGER,
      nvPosisoField44
            INTEGER,
      nvPosisoField45
            INTEGER,
      nvPosisoField46
            INTEGER,
      nvPosisoField47
            INTEGER,
      nvPosisoField48
            INTEGER,
      nvPosisoField49
            INTEGER,
      nvPosisoField50
            INTEGER,
      nvPosisoField51
            INTEGER,
      nvPosisoField52
            INTEGER,
      nvPosisoField53
            INTEGER,
      nvPosisoField54
            INTEGER,
      nvPosisoField55
            INTEGER,
      nvPosisoField56
            INTEGER,
      nvPosisoField57
            INTEGER,
      nvPosisoField58
            INTEGER,
      nvPosisoField59
            INTEGER,
      nvPosisoField60
            INTEGER,
      nvPosisoField61
            INTEGER,
      nvPosisoField62
            INTEGER,
      nvPosisoField63
            INTEGER,
      nvPosisoField64
            INTEGER,
      nvPosisoStatus
            INTEGER
                }

nvPosisoIndex OBJECT-TYPE
     SYNTAX   INTEGER
     ACCESS   read-only
     STATUS   mandatory
     DESCRIPTION
	"Index of Nevada posiso record"
      ::= { nvPosisoEntry 1 }

nvPosisoName OBJECT-TYPE
     SYNTAX   DisplayString (SIZE (0..16))
     ACCESS   read-write
     STATUS   mandatory
     DESCRIPTION
"used to identify record
"
     ::= { nvPosisoEntry 2 }

nvPosisoContrec OBJECT-TYPE
     SYNTAX   INTEGER (0..255)
     ACCESS   read-write
     STATUS   mandatory
     DESCRIPTION
"pointer to continuation record
Default value is 0."
     ::= { nvPosisoEntry 3 }

nvPosisoField2 OBJECT-TYPE
     SYNTAX   NvIsoType
     ACCESS   read-write
     STATUS   mandatory
     DESCRIPTION
"same as field1
"
     ::= { nvPosisoEntry 4 }

nvPosisoField3 OBJECT-TYPE
     SYNTAX   NvIsoType
     ACCESS   read-write
     STATUS   mandatory
     DESCRIPTION
"same as field1
"
     ::= { nvPosisoEntry 5 }

nvPosisoField4 OBJECT-TYPE
     SYNTAX   NvIsoType
     ACCESS   read-write
     STATUS   mandatory
     DESCRIPTION
"same as field1
"
     ::= { nvPosisoEntry 6 }

nvPosisoField5 OBJECT-TYPE
     SYNTAX   NvIsoType
     ACCESS   read-write
     STATUS   mandatory
     DESCRIPTION
"same as field1
"
     ::= { nvPosisoEntry 7 }

nvPosisoField6 OBJECT-TYPE
     SYNTAX   NvIsoType
     ACCESS   read-write
     STATUS   mandatory
     DESCRIPTION
"same as field1
"
     ::= { nvPosisoEntry 8 }

nvPosisoField7 OBJECT-TYPE
     SYNTAX   NvIsoType
     ACCESS   read-write
     STATUS   mandatory
     DESCRIPTION
"same as field1
"
     ::= { nvPosisoEntry 9 }

nvPosisoField8 OBJECT-TYPE
     SYNTAX   NvIsoType
     ACCESS   read-write
     STATUS   mandatory
     DESCRIPTION
"same as field1
"
     ::= { nvPosisoEntry 10 }

nvPosisoField9 OBJECT-TYPE
     SYNTAX   NvIsoType
     ACCESS   read-write
     STATUS   mandatory
     DESCRIPTION
"same as field1
"
     ::= { nvPosisoEntry 11 }

nvPosisoField10 OBJECT-TYPE
     SYNTAX   NvIsoType
     ACCESS   read-write
     STATUS   mandatory
     DESCRIPTION
"same as field1
"
     ::= { nvPosisoEntry 12 }

nvPosisoField11 OBJECT-TYPE
     SYNTAX   NvIsoType
     ACCESS   read-write
     STATUS   mandatory
     DESCRIPTION
"same as field1
"
     ::= { nvPosisoEntry 13 }

nvPosisoField12 OBJECT-TYPE
     SYNTAX   NvIsoType
     ACCESS   read-write
     STATUS   mandatory
     DESCRIPTION
"same as field1
"
     ::= { nvPosisoEntry 14 }

nvPosisoField13 OBJECT-TYPE
     SYNTAX   NvIsoType
     ACCESS   read-write
     STATUS   mandatory
     DESCRIPTION
"same as field1
"
     ::= { nvPosisoEntry 15 }

nvPosisoField14 OBJECT-TYPE
     SYNTAX   NvIsoType
     ACCESS   read-write
     STATUS   mandatory
     DESCRIPTION
"same as field1
"
     ::= { nvPosisoEntry 16 }

nvPosisoField15 OBJECT-TYPE
     SYNTAX   NvIsoType
     ACCESS   read-write
     STATUS   mandatory
     DESCRIPTION
"same as field1
"
     ::= { nvPosisoEntry 17 }

nvPosisoField16 OBJECT-TYPE
     SYNTAX   NvIsoType
     ACCESS   read-write
     STATUS   mandatory
     DESCRIPTION
"same as field1
"
     ::= { nvPosisoEntry 18 }

nvPosisoField17 OBJECT-TYPE
     SYNTAX   NvIsoType
     ACCESS   read-write
     STATUS   mandatory
     DESCRIPTION
"same as field1
"
     ::= { nvPosisoEntry 19 }

nvPosisoField18 OBJECT-TYPE
     SYNTAX   NvIsoType
     ACCESS   read-write
     STATUS   mandatory
     DESCRIPTION
"same as field1
"
     ::= { nvPosisoEntry 20 }

nvPosisoField19 OBJECT-TYPE
     SYNTAX   NvIsoType
     ACCESS   read-write
     STATUS   mandatory
     DESCRIPTION
"same as field1
"
     ::= { nvPosisoEntry 21 }

nvPosisoField20 OBJECT-TYPE
     SYNTAX   NvIsoType
     ACCESS   read-write
     STATUS   mandatory
     DESCRIPTION
"same as field1
"
     ::= { nvPosisoEntry 22 }

nvPosisoField21 OBJECT-TYPE
     SYNTAX   NvIsoType
     ACCESS   read-write
     STATUS   mandatory
     DESCRIPTION
"same as field1
"
     ::= { nvPosisoEntry 23 }

nvPosisoField22 OBJECT-TYPE
     SYNTAX   NvIsoType
     ACCESS   read-write
     STATUS   mandatory
     DESCRIPTION
"same as field1
"
     ::= { nvPosisoEntry 24 }

nvPosisoField23 OBJECT-TYPE
     SYNTAX   NvIsoType
     ACCESS   read-write
     STATUS   mandatory
     DESCRIPTION
"same as field1
"
     ::= { nvPosisoEntry 25 }

nvPosisoField24 OBJECT-TYPE
     SYNTAX   NvIsoType
     ACCESS   read-write
     STATUS   mandatory
     DESCRIPTION
"same as field1
"
     ::= { nvPosisoEntry 26 }

nvPosisoField25 OBJECT-TYPE
     SYNTAX   NvIsoType
     ACCESS   read-write
     STATUS   mandatory
     DESCRIPTION
"same as field1
"
     ::= { nvPosisoEntry 27 }

nvPosisoField26 OBJECT-TYPE
     SYNTAX   NvIsoType
     ACCESS   read-write
     STATUS   mandatory
     DESCRIPTION
"same as field1
"
     ::= { nvPosisoEntry 28 }

nvPosisoField27 OBJECT-TYPE
     SYNTAX   NvIsoType
     ACCESS   read-write
     STATUS   mandatory
     DESCRIPTION
"same as field1
"
     ::= { nvPosisoEntry 29 }

nvPosisoField28 OBJECT-TYPE
     SYNTAX   NvIsoType
     ACCESS   read-write
     STATUS   mandatory
     DESCRIPTION
"same as field1
"
     ::= { nvPosisoEntry 30 }

nvPosisoField29 OBJECT-TYPE
     SYNTAX   NvIsoType
     ACCESS   read-write
     STATUS   mandatory
     DESCRIPTION
"same as field1
"
     ::= { nvPosisoEntry 31 }

nvPosisoField30 OBJECT-TYPE
     SYNTAX   NvIsoType
     ACCESS   read-write
     STATUS   mandatory
     DESCRIPTION
"same as field1
"
     ::= { nvPosisoEntry 32 }

nvPosisoField31 OBJECT-TYPE
     SYNTAX   NvIsoType
     ACCESS   read-write
     STATUS   mandatory
     DESCRIPTION
"same as field1
"
     ::= { nvPosisoEntry 33 }

nvPosisoField32 OBJECT-TYPE
     SYNTAX   NvIsoType
     ACCESS   read-write
     STATUS   mandatory
     DESCRIPTION
"same as field1
"
     ::= { nvPosisoEntry 34 }

nvPosisoField33 OBJECT-TYPE
     SYNTAX   NvIsoType
     ACCESS   read-write
     STATUS   mandatory
     DESCRIPTION
"same as field1
"
     ::= { nvPosisoEntry 35 }

nvPosisoField34 OBJECT-TYPE
     SYNTAX   NvIsoType
     ACCESS   read-write
     STATUS   mandatory
     DESCRIPTION
"same as field1
"
     ::= { nvPosisoEntry 36 }

nvPosisoField35 OBJECT-TYPE
     SYNTAX   NvIsoType
     ACCESS   read-write
     STATUS   mandatory
     DESCRIPTION
"same as field1
"
     ::= { nvPosisoEntry 37 }

nvPosisoField36 OBJECT-TYPE
     SYNTAX   NvIsoType
     ACCESS   read-write
     STATUS   mandatory
     DESCRIPTION
"same as field1
"
     ::= { nvPosisoEntry 38 }

nvPosisoField37 OBJECT-TYPE
     SYNTAX   NvIsoType
     ACCESS   read-write
     STATUS   mandatory
     DESCRIPTION
"same as field1
"
     ::= { nvPosisoEntry 39 }

nvPosisoField38 OBJECT-TYPE
     SYNTAX   NvIsoType
     ACCESS   read-write
     STATUS   mandatory
     DESCRIPTION
"same as field1
"
     ::= { nvPosisoEntry 40 }

nvPosisoField39 OBJECT-TYPE
     SYNTAX   NvIsoType
     ACCESS   read-write
     STATUS   mandatory
     DESCRIPTION
"same as field1
"
     ::= { nvPosisoEntry 41 }

nvPosisoField40 OBJECT-TYPE
     SYNTAX   NvIsoType
     ACCESS   read-write
     STATUS   mandatory
     DESCRIPTION
"same as field1
"
     ::= { nvPosisoEntry 42 }

nvPosisoField41 OBJECT-TYPE
     SYNTAX   NvIsoType
     ACCESS   read-write
     STATUS   mandatory
     DESCRIPTION
"same as field1
"
     ::= { nvPosisoEntry 43 }

nvPosisoField42 OBJECT-TYPE
     SYNTAX   NvIsoType
     ACCESS   read-write
     STATUS   mandatory
     DESCRIPTION
"same as field1
"
     ::= { nvPosisoEntry 44 }

nvPosisoField43 OBJECT-TYPE
     SYNTAX   NvIsoType
     ACCESS   read-write
     STATUS   mandatory
     DESCRIPTION
"same as field1
"
     ::= { nvPosisoEntry 45 }

nvPosisoField44 OBJECT-TYPE
     SYNTAX   NvIsoType
     ACCESS   read-write
     STATUS   mandatory
     DESCRIPTION
"same as field1
"
     ::= { nvPosisoEntry 46 }

nvPosisoField45 OBJECT-TYPE
     SYNTAX   NvIsoType
     ACCESS   read-write
     STATUS   mandatory
     DESCRIPTION
"same as field1
"
     ::= { nvPosisoEntry 47 }

nvPosisoField46 OBJECT-TYPE
     SYNTAX   NvIsoType
     ACCESS   read-write
     STATUS   mandatory
     DESCRIPTION
"same as field1
"
     ::= { nvPosisoEntry 48 }

nvPosisoField47 OBJECT-TYPE
     SYNTAX   NvIsoType
     ACCESS   read-write
     STATUS   mandatory
     DESCRIPTION
"same as field1
"
     ::= { nvPosisoEntry 49 }

nvPosisoField48 OBJECT-TYPE
     SYNTAX   NvIsoType
     ACCESS   read-write
     STATUS   mandatory
     DESCRIPTION
"same as field1
"
     ::= { nvPosisoEntry 50 }

nvPosisoField49 OBJECT-TYPE
     SYNTAX   NvIsoType
     ACCESS   read-write
     STATUS   mandatory
     DESCRIPTION
"same as field1
"
     ::= { nvPosisoEntry 51 }

nvPosisoField50 OBJECT-TYPE
     SYNTAX   NvIsoType
     ACCESS   read-write
     STATUS   mandatory
     DESCRIPTION
"same as field1
"
     ::= { nvPosisoEntry 52 }

nvPosisoField51 OBJECT-TYPE
     SYNTAX   NvIsoType
     ACCESS   read-write
     STATUS   mandatory
     DESCRIPTION
"same as field1
"
     ::= { nvPosisoEntry 53 }

nvPosisoField52 OBJECT-TYPE
     SYNTAX   NvIsoType
     ACCESS   read-write
     STATUS   mandatory
     DESCRIPTION
"same as field1
"
     ::= { nvPosisoEntry 54 }

nvPosisoField53 OBJECT-TYPE
     SYNTAX   NvIsoType
     ACCESS   read-write
     STATUS   mandatory
     DESCRIPTION
"same as field1
"
     ::= { nvPosisoEntry 55 }

nvPosisoField54 OBJECT-TYPE
     SYNTAX   NvIsoType
     ACCESS   read-write
     STATUS   mandatory
     DESCRIPTION
"same as field1
"
     ::= { nvPosisoEntry 56 }

nvPosisoField55 OBJECT-TYPE
     SYNTAX   NvIsoType
     ACCESS   read-write
     STATUS   mandatory
     DESCRIPTION
"same as field1
"
     ::= { nvPosisoEntry 57 }

nvPosisoField56 OBJECT-TYPE
     SYNTAX   NvIsoType
     ACCESS   read-write
     STATUS   mandatory
     DESCRIPTION
"same as field1
"
     ::= { nvPosisoEntry 58 }

nvPosisoField57 OBJECT-TYPE
     SYNTAX   NvIsoType
     ACCESS   read-write
     STATUS   mandatory
     DESCRIPTION
"same as field1
"
     ::= { nvPosisoEntry 59 }

nvPosisoField58 OBJECT-TYPE
     SYNTAX   NvIsoType
     ACCESS   read-write
     STATUS   mandatory
     DESCRIPTION
"same as field1
"
     ::= { nvPosisoEntry 60 }

nvPosisoField59 OBJECT-TYPE
     SYNTAX   NvIsoType
     ACCESS   read-write
     STATUS   mandatory
     DESCRIPTION
"same as field1
"
     ::= { nvPosisoEntry 61 }

nvPosisoField60 OBJECT-TYPE
     SYNTAX   NvIsoType
     ACCESS   read-write
     STATUS   mandatory
     DESCRIPTION
"same as field1
"
     ::= { nvPosisoEntry 62 }

nvPosisoField61 OBJECT-TYPE
     SYNTAX   NvIsoType
     ACCESS   read-write
     STATUS   mandatory
     DESCRIPTION
"same as field1
"
     ::= { nvPosisoEntry 63 }

nvPosisoField62 OBJECT-TYPE
     SYNTAX   NvIsoType
     ACCESS   read-write
     STATUS   mandatory
     DESCRIPTION
"same as field1
"
     ::= { nvPosisoEntry 64 }

nvPosisoField63 OBJECT-TYPE
     SYNTAX   NvIsoType
     ACCESS   read-write
     STATUS   mandatory
     DESCRIPTION
"same as field1
"
     ::= { nvPosisoEntry 65 }

nvPosisoField64 OBJECT-TYPE
     SYNTAX   NvIsoType
     ACCESS   read-write
     STATUS   mandatory
     DESCRIPTION
"same as field1
"
     ::= { nvPosisoEntry 66 }

nvPosisoStatus OBJECT-TYPE
     SYNTAX   INTEGER {
                valid(1),
                invalid(2)
		}
     ACCESS   read-write
     STATUS   mandatory
     DESCRIPTION
"Operation status of the record. Use valid to add
record to database file and invalid to delete
record from database file."
      ::= { nvPosisoEntry 67 }


nvPosvisa OBJECT IDENTIFIER ::= { nevadaPos 7 }

nvPosvisaMaxRec OBJECT-TYPE
      SYNTAX   INTEGER
      ACCESS   read-only
      STATUS   mandatory
      DESCRIPTION
		"total number of records allowed in database file."
      ::= { nvPosvisa 1}

nvPosvisaNumRec OBJECT-TYPE
      SYNTAX   INTEGER
      ACCESS   read-only
      STATUS   mandatory
      DESCRIPTION
		"number of records in use."
      ::= { nvPosvisa 2}

nvPosvisaTable OBJECT-TYPE
      SYNTAX   SEQUENCE OF NvPosvisaEntry
      ACCESS   not-accessible
      STATUS   mandatory
      DESCRIPTION
               "Nevada node posvisa file."
      ::= { nvPosvisa 3 }

nvPosvisaEntry OBJECT-TYPE
      SYNTAX   NvPosvisaEntry
      ACCESS   not-accessible
      STATUS   mandatory
      DESCRIPTION
               "Nevada node posvisa record."
      INDEX { nvPosvisaIndex }
      ::= { nvPosvisaTable 1 }

NvPosvisaEntry ::=
      SEQUENCE {
      nvPosvisaIndex
            INTEGER,
      nvPosvisaName
            DisplayString,
      nvPosvisaField1
            INTEGER,
      nvPosvisaField2
            INTEGER,
      nvPosvisaField3
            INTEGER,
      nvPosvisaField4
            INTEGER,
      nvPosvisaField5
            INTEGER,
      nvPosvisaField6
            INTEGER,
      nvPosvisaField7
            INTEGER,
      nvPosvisaField8
            INTEGER,
      nvPosvisaField9
            INTEGER,
      nvPosvisaField10
            INTEGER,
      nvPosvisaField11
            INTEGER,
      nvPosvisaField12
            INTEGER,
      nvPosvisaField13
            INTEGER,
      nvPosvisaField14
            INTEGER,
      nvPosvisaField15
            INTEGER,
      nvPosvisaField16
            INTEGER,
      nvPosvisaField17
            INTEGER,
      nvPosvisaField18
            INTEGER,
      nvPosvisaField19
            INTEGER,
      nvPosvisaField20
            INTEGER,
      nvPosvisaStatus
            INTEGER
                }

nvPosvisaIndex OBJECT-TYPE
     SYNTAX   INTEGER
     ACCESS   read-only
     STATUS   mandatory
     DESCRIPTION
	"Index of Nevada posvisa record"
      ::= { nvPosvisaEntry 1 }

nvPosvisaName OBJECT-TYPE
     SYNTAX   DisplayString (SIZE (0..16))
     ACCESS   read-write
     STATUS   mandatory
     DESCRIPTION
"used to identify record
"
     ::= { nvPosvisaEntry 2 }

nvPosvisaField1 OBJECT-TYPE
     SYNTAX   NvVisaType
     ACCESS   read-write
     STATUS   mandatory
     DESCRIPTION
"description of a single field
"
     ::= { nvPosvisaEntry 3 }

nvPosvisaField2 OBJECT-TYPE
     SYNTAX   NvVisaType
     ACCESS   read-write
     STATUS   mandatory
     DESCRIPTION
"same as field1
"
     ::= { nvPosvisaEntry 4 }

nvPosvisaField3 OBJECT-TYPE
     SYNTAX   NvVisaType
     ACCESS   read-write
     STATUS   mandatory
     DESCRIPTION
"same as field1
"
     ::= { nvPosvisaEntry 5 }

nvPosvisaField4 OBJECT-TYPE
     SYNTAX   NvVisaType
     ACCESS   read-write
     STATUS   mandatory
     DESCRIPTION
"same as field1
"
     ::= { nvPosvisaEntry 6 }

nvPosvisaField5 OBJECT-TYPE
     SYNTAX   NvVisaType
     ACCESS   read-write
     STATUS   mandatory
     DESCRIPTION
"same as field1
"
     ::= { nvPosvisaEntry 7 }

nvPosvisaField6 OBJECT-TYPE
     SYNTAX   NvVisaType
     ACCESS   read-write
     STATUS   mandatory
     DESCRIPTION
"same as field1
"
     ::= { nvPosvisaEntry 8 }

nvPosvisaField7 OBJECT-TYPE
     SYNTAX   NvVisaType
     ACCESS   read-write
     STATUS   mandatory
     DESCRIPTION
"same as field1
"
     ::= { nvPosvisaEntry 9 }

nvPosvisaField8 OBJECT-TYPE
     SYNTAX   NvVisaType
     ACCESS   read-write
     STATUS   mandatory
     DESCRIPTION
"same as field1
"
     ::= { nvPosvisaEntry 10 }

nvPosvisaField9 OBJECT-TYPE
     SYNTAX   NvVisaType
     ACCESS   read-write
     STATUS   mandatory
     DESCRIPTION
"same as field1
"
     ::= { nvPosvisaEntry 11 }

nvPosvisaField10 OBJECT-TYPE
     SYNTAX   NvVisaType
     ACCESS   read-write
     STATUS   mandatory
     DESCRIPTION
"same as field1
"
     ::= { nvPosvisaEntry 12 }

nvPosvisaField11 OBJECT-TYPE
     SYNTAX   NvVisaType
     ACCESS   read-write
     STATUS   mandatory
     DESCRIPTION
"same as field1
"
     ::= { nvPosvisaEntry 13 }

nvPosvisaField12 OBJECT-TYPE
     SYNTAX   NvVisaType
     ACCESS   read-write
     STATUS   mandatory
     DESCRIPTION
"same as field1
"
     ::= { nvPosvisaEntry 14 }

nvPosvisaField13 OBJECT-TYPE
     SYNTAX   NvVisaType
     ACCESS   read-write
     STATUS   mandatory
     DESCRIPTION
"same as field1
"
     ::= { nvPosvisaEntry 15 }

nvPosvisaField14 OBJECT-TYPE
     SYNTAX   NvVisaType
     ACCESS   read-write
     STATUS   mandatory
     DESCRIPTION
"same as field1
"
     ::= { nvPosvisaEntry 16 }

nvPosvisaField15 OBJECT-TYPE
     SYNTAX   NvVisaType
     ACCESS   read-write
     STATUS   mandatory
     DESCRIPTION
"same as field1
"
     ::= { nvPosvisaEntry 17 }

nvPosvisaField16 OBJECT-TYPE
     SYNTAX   NvVisaType
     ACCESS   read-write
     STATUS   mandatory
     DESCRIPTION
"same as field1
"
     ::= { nvPosvisaEntry 18 }

nvPosvisaField17 OBJECT-TYPE
     SYNTAX   NvVisaType
     ACCESS   read-write
     STATUS   mandatory
     DESCRIPTION
"same as field1
"
     ::= { nvPosvisaEntry 19 }

nvPosvisaField18 OBJECT-TYPE
     SYNTAX   NvVisaType
     ACCESS   read-write
     STATUS   mandatory
     DESCRIPTION
"same as field1
"
     ::= { nvPosvisaEntry 20 }

nvPosvisaField19 OBJECT-TYPE
     SYNTAX   NvVisaType
     ACCESS   read-write
     STATUS   mandatory
     DESCRIPTION
"same as field1
"
     ::= { nvPosvisaEntry 21 }

nvPosvisaField20 OBJECT-TYPE
     SYNTAX   NvVisaType
     ACCESS   read-write
     STATUS   mandatory
     DESCRIPTION
"same as field1
"
     ::= { nvPosvisaEntry 22 }

nvPosvisaStatus OBJECT-TYPE
     SYNTAX   INTEGER {
                valid(1),
                invalid(2)
		}
     ACCESS   read-write
     STATUS   mandatory
     DESCRIPTION
"Operation status of the record. Use valid to add
record to database file and invalid to delete
record from database file."
      ::= { nvPosvisaEntry 23 }


nvPosstat OBJECT IDENTIFIER ::= { nevadaPos 8 }

nvPosstatMaxRec OBJECT-TYPE
      SYNTAX   INTEGER
      ACCESS   read-only
      STATUS   mandatory
      DESCRIPTION
		"total number of records allowed in database file."
      ::= { nvPosstat 1}

nvPosstatNumRec OBJECT-TYPE
      SYNTAX   INTEGER
      ACCESS   read-only
      STATUS   mandatory
      DESCRIPTION
		"number of records in use."
      ::= { nvPosstat 2}

nvPosstatTable OBJECT-TYPE
      SYNTAX   SEQUENCE OF NvPosstatEntry
      ACCESS   not-accessible
      STATUS   mandatory
      DESCRIPTION
               "Nevada node posstat file."
      ::= { nvPosstat 3 }

nvPosstatEntry OBJECT-TYPE
      SYNTAX   NvPosstatEntry
      ACCESS   not-accessible
      STATUS   mandatory
      DESCRIPTION
               "Nevada node posstat record."
      INDEX { nvPosstatIndex }
      ::= { nvPosstatTable 1 }


NvPosstatEntry ::=
      SEQUENCE {
     nvPosstatIndex
            INTEGER,
      nvPosstatName
            DisplayString,
      nvPosstatNactivchn
            INTEGER,
      nvPosstatProtocol
            INTEGER,
      nvPosstatNumcalls
            INTEGER,
      nvPosstatNfailcall
            INTEGER,
      nvPosstatNumimsgs
            INTEGER,
      nvPosstatNumomsgs
            INTEGER,
      nvPosstatEftreqs
            INTEGER,
      nvPosstatEftrsps
            INTEGER,
      nvPosstatNmsreqs
            INTEGER,
      nvPosstatNmsrsps
            INTEGER,
      nvPosstatNodatart
            INTEGER,
      nvPosstatNotpdurt
            INTEGER,
      nvPosstatInvrqtpdu
            INTEGER,
      nvPosstatNousdest
            INTEGER,
      nvPosstatQueued
            INTEGER,
      nvPosstatCommfail
            INTEGER,
      nvPosstatInvrstpdu
            INTEGER,
      nvPosstatDnlnkfail
            INTEGER,
      nvPosstatRspnomtch
            INTEGER,
      nvPosstatConnfail
            INTEGER,
      nvPosstatRsptimout
            INTEGER,
      nvPosstatNmsbaddst
            INTEGER,
      nvPosstatNmsbadhst
            INTEGER,
      nvPosstatNbadframes
            INTEGER,
      nvPosstatNtoolong
            INTEGER,
      nvPosstatDtreset
            DisplayString
                }

nvPosstatIndex OBJECT-TYPE
     SYNTAX   INTEGER
     ACCESS   read-only
     STATUS   mandatory
     DESCRIPTION
	"Index of Nevada posstat record"
      ::= { nvPosstatEntry 1 }

nvPosstatName OBJECT-TYPE
     SYNTAX   DisplayString (SIZE (0..16))
     ACCESS   read-only
     STATUS   mandatory
     DESCRIPTION
"port/link or X.121 address (matches posconf)
"
     ::= { nvPosstatEntry 2 }

nvPosstatNactivchn OBJECT-TYPE
     SYNTAX   INTEGER
     ACCESS   read-only
     STATUS   mandatory
     DESCRIPTION
"number of active channels
Initial status is 0."
     ::= { nvPosstatEntry 3 }

nvPosstatProtocol OBJECT-TYPE
     SYNTAX   INTEGER {
                sdlc(1),     -- simple SDLC subset (+1)
                x25(2),     -- X.25 through nbus
                visa(3),     -- visa terminal protocol
                tcp(4),      -- TCP/IP through nbus
		spdh(5),
		dfono(6),
		dtfspc(7),
		dtfgen(8)
		}
     ACCESS   read-only
     STATUS   mandatory
     DESCRIPTION
"protocol on port
"
     ::= { nvPosstatEntry 4 }

nvPosstatNumcalls OBJECT-TYPE
     SYNTAX   INTEGER
     ACCESS   read-only
     STATUS   mandatory
     DESCRIPTION
"number of calls
Statistic is zeroed at startup time."
     ::= { nvPosstatEntry 5 }

nvPosstatNfailcall OBJECT-TYPE
     SYNTAX   INTEGER
     ACCESS   read-only
     STATUS   mandatory
     DESCRIPTION
"number of failed calls
Statistic is zeroed at startup time."
     ::= { nvPosstatEntry 6 }

nvPosstatNumimsgs OBJECT-TYPE
     SYNTAX   INTEGER
     ACCESS   read-only
     STATUS   mandatory
     DESCRIPTION
"number of messages from device
Statistic is zeroed at startup time."
     ::= { nvPosstatEntry 7 }

nvPosstatNumomsgs OBJECT-TYPE
     SYNTAX   INTEGER
     ACCESS   read-only
     STATUS   mandatory
     DESCRIPTION
"number of messages to device
Statistic is zeroed at startup time."
     ::= { nvPosstatEntry 8 }

nvPosstatEftreqs OBJECT-TYPE
     SYNTAX   INTEGER
     ACCESS   read-only
     STATUS   mandatory
     DESCRIPTION
"number of EFT requests
Statistic is zeroed at startup time."
     ::= { nvPosstatEntry 9 }

nvPosstatEftrsps OBJECT-TYPE
     SYNTAX   INTEGER
     ACCESS   read-only
     STATUS   mandatory
     DESCRIPTION
"number of EFT responses
Statistic is zeroed at startup time."
     ::= { nvPosstatEntry 10 }

nvPosstatNmsreqs OBJECT-TYPE
     SYNTAX   INTEGER
     ACCESS   read-only
     STATUS   mandatory
     DESCRIPTION
"number of NMS requests
Statistic is zeroed at startup time."
     ::= { nvPosstatEntry 11 }

nvPosstatNmsrsps OBJECT-TYPE
     SYNTAX   INTEGER
     ACCESS   read-only
     STATUS   mandatory
     DESCRIPTION
"number of NMS responses
Statistic is zeroed at startup time."
     ::= { nvPosstatEntry 12 }

nvPosstatNodatart OBJECT-TYPE
     SYNTAX   INTEGER
     ACCESS   read-only
     STATUS   mandatory
     DESCRIPTION
"EFT reqs discarded becaues msg switch could find route
Statistic is zeroed at startup time."
     ::= { nvPosstatEntry 13 }

nvPosstatNotpdurt OBJECT-TYPE
     SYNTAX   INTEGER
     ACCESS   read-only
     STATUS   mandatory
     DESCRIPTION
"EFT reqs discarded because no match to posniimap entry
Statistic is zeroed at startup time."
     ::= { nvPosstatEntry 14 }

nvPosstatInvrqtpdu OBJECT-TYPE
     SYNTAX   INTEGER
     ACCESS   read-only
     STATUS   mandatory
     DESCRIPTION
"EFT reqs discarded because of bad TPDUs
Statistic is zeroed at startup time."
     ::= { nvPosstatEntry 15 }

nvPosstatNousdest OBJECT-TYPE
     SYNTAX   INTEGER
     ACCESS   read-only
     STATUS   mandatory
     DESCRIPTION
"EFT reqs discarded because destination couldn't be matched
Statistic is zeroed at startup time."
     ::= { nvPosstatEntry 16 }

nvPosstatQueued OBJECT-TYPE
     SYNTAX   INTEGER
     ACCESS   read-only
     STATUS   mandatory
     DESCRIPTION
"EFT reqs discarded because all dest channels or TDPU IDs in use
Statistic is zeroed at startup time."
     ::= { nvPosstatEntry 17 }

nvPosstatCommfail OBJECT-TYPE
     SYNTAX   INTEGER
     ACCESS   read-only
     STATUS   mandatory
     DESCRIPTION
"EFT reqs that couldn't be delivered due to comm failure
Statistic is zeroed at startup time."
     ::= { nvPosstatEntry 18 }

nvPosstatInvrstpdu OBJECT-TYPE
     SYNTAX   INTEGER
     ACCESS   read-only
     STATUS   mandatory
     DESCRIPTION
"EFT rsps discarded because they did not contain valid TPDUs
Statistic is zeroed at startup time."
     ::= { nvPosstatEntry 19 }

nvPosstatDnlnkfail OBJECT-TYPE
     SYNTAX   INTEGER
     ACCESS   read-only
     STATUS   mandatory
     DESCRIPTION
"EFT rsps discarded because they did not match any request
Statistic is zeroed at startup time."
     ::= { nvPosstatEntry 20 }

nvPosstatRspnomtch OBJECT-TYPE
     SYNTAX   INTEGER
     ACCESS   read-only
     STATUS   mandatory
     DESCRIPTION
"EFT rsps discarded because they did not match any request
Statistic is zeroed at startup time."
     ::= { nvPosstatEntry 21 }

nvPosstatConnfail OBJECT-TYPE
     SYNTAX   INTEGER
     ACCESS   read-only
     STATUS   mandatory
     DESCRIPTION
"EFT requests lost because of connection failures
Statistic is zeroed at startup time."
     ::= { nvPosstatEntry 22 }

nvPosstatRsptimout OBJECT-TYPE
     SYNTAX   INTEGER
     ACCESS   read-only
     STATUS   mandatory
     DESCRIPTION
"EFT rsps (map table entries) that were timed out (response lost)
Statistic is zeroed at startup time."
     ::= { nvPosstatEntry 23 }

nvPosstatNmsbaddst OBJECT-TYPE
     SYNTAX   INTEGER
     ACCESS   read-only
     STATUS   mandatory
     DESCRIPTION
"NMS reqs with bad destination addresses
Statistic is zeroed at startup time."
     ::= { nvPosstatEntry 24 }

nvPosstatNmsbadhst OBJECT-TYPE
     SYNTAX   INTEGER
     ACCESS   read-only
     STATUS   mandatory
     DESCRIPTION
"NMS reqs with bad source addresses (no matching host ID in posnmsmap file)
Statistic is zeroed at startup time."
     ::= { nvPosstatEntry 25 }

nvPosstatNbadframes OBJECT-TYPE
     SYNTAX   INTEGER
     ACCESS   read-only
     STATUS   mandatory
     DESCRIPTION
"NMS reqs with bad source addresses (no matching host ID in posnmsmap file)
Statistic is zeroed at startup time."
     ::= { nvPosstatEntry 26 }

nvPosstatNtoolong OBJECT-TYPE
     SYNTAX   INTEGER
     ACCESS   read-only
     STATUS   mandatory
     DESCRIPTION
"NMS reqs with bad source addresses (no matching host ID in posnmsmap file)
Statistic is zeroed at startup time."
     ::= { nvPosstatEntry 27 }

nvPosstatDtreset OBJECT-TYPE
     SYNTAX   DisplayString (SIZE (0..20))
     ACCESS   read-only
     STATUS   mandatory
     DESCRIPTION
        "date & time statistics last reset"
     ::= { nvPosstatEntry 28 }

--

--       APACS
--
--
--  apacsconf
--
nvApacsconf OBJECT IDENTIFIER ::= { nevadaApacs 1 }

nvApacsconfMaxRec OBJECT-TYPE
     SYNTAX   INTEGER
     ACCESS   read-only
     STATUS   mandatory
     DESCRIPTION
        "total number of records allowed in database file."
     ::= {nvApacsconf 1}

nvApacsconfNumRec OBJECT-TYPE
     SYNTAX   INTEGER
     ACCESS   read-only
     STATUS   mandatory
     DESCRIPTION
        "number of records in use."
     ::= {nvApacsconf 2}

nvApacsconfTable OBJECT-TYPE
      SYNTAX   SEQUENCE OF NvApacsconfEntry
      ACCESS   not-accessible
      STATUS   mandatory
      DESCRIPTION
               "Apacsconf file."
      ::= { nvApacsconf 3 }

nvApacsconfEntry OBJECT-TYPE
      SYNTAX   NvApacsconfEntry
      ACCESS   not-accessible
      STATUS   mandatory
      DESCRIPTION
               "Apacsconf record."
      INDEX { nvApacsconfIndex }
      ::= { nvApacsconfTable 1 }

NvApacsconfEntry ::=
      SEQUENCE {
	nvApacsconfIndex
		INTEGER,
	nvApacsconfNodename
		DisplayString,
	nvApacsconfSitename
		DisplayString,
	nvApacsconfHelpphone
		DisplayString,
	nvApacsconfReserve1
		DisplayString,
	nvApacsconfBillingT1
		INTEGER,
	nvApacsconfBillingT2
		INTEGER,
	nvApacsconfBillingT3
		INTEGER,
	nvApacsconfBillingT4
		INTEGER,
	nvApacsconfBillingT5
		INTEGER,
	nvApacsconfBillingT6
		INTEGER,
	nvApacsconfDlrtries
		INTEGER,
	nvApacsconfTimerA
		INTEGER,
	nvApacsconfTimerB
		INTEGER,
	nvApacsconfTimerC
		INTEGER,
	nvApacsconfDscdleeot
		INTEGER,
	nvApacsconfParerrall
		INTEGER,
        nvApacsconfStatus
                INTEGER
	}

nvApacsconfIndex OBJECT-TYPE
     SYNTAX   INTEGER
     ACCESS   read-only
     STATUS   mandatory
     DESCRIPTION
        "Index of Apacsconf record"
      ::= { nvApacsconfEntry 1 }

nvApacsconfNodename OBJECT-TYPE
     SYNTAX   DisplayString (SIZE (0..16))
     ACCESS   read-write
     STATUS   mandatory
     DESCRIPTION
        "For display purpose only Not used by Apacs software "
      ::= { nvApacsconfEntry 2 }

nvApacsconfSitename OBJECT-TYPE
     SYNTAX   DisplayString (SIZE (0..30))
     ACCESS   read-write
     STATUS   mandatory
     DESCRIPTION
        "For display purpose only Not used by Apacs software
         other than in generating alarms "
      ::= { nvApacsconfEntry 3 }

nvApacsconfHelpphone OBJECT-TYPE
     SYNTAX   DisplayString (SIZE (0..16))
     ACCESS   read-write
     STATUS   mandatory
     DESCRIPTION
        "For display purpose in INF help message.
         	Phone number of cardway help desk "
      ::= { nvApacsconfEntry 4 }

nvApacsconfReserve1 OBJECT-TYPE
     SYNTAX   DisplayString (SIZE (0..2))
     ACCESS   read-only
     STATUS   mandatory
     DESCRIPTION
         "OBSOLETE - removed field."
      ::= { nvApacsconfEntry 5 }

nvApacsconfBillingT1 OBJECT-TYPE
     SYNTAX   INTEGER
     ACCESS   read-write
     STATUS   mandatory
     DESCRIPTION
	" Call duration timer limit for billing ( in 100th secs )
	  Default value of 500  "
      ::= { nvApacsconfEntry 6 }

nvApacsconfBillingT2 OBJECT-TYPE
     SYNTAX   INTEGER
     ACCESS   read-write
     STATUS   mandatory
     DESCRIPTION
	" Call duration timer limit for billing ( in 100th secs )
	  Default value of 1000  "
      ::= { nvApacsconfEntry 7 }

nvApacsconfBillingT3 OBJECT-TYPE
     SYNTAX   INTEGER
     ACCESS   read-write
     STATUS   mandatory
     DESCRIPTION
	" Call duration timer limit for billing ( in 100th secs )
	  Default value of 1500  "
      ::= { nvApacsconfEntry 8 }

nvApacsconfBillingT4 OBJECT-TYPE
     SYNTAX   INTEGER
     ACCESS   read-write
     STATUS   mandatory
     DESCRIPTION
	" Call duration timer limit for billing ( in 100th secs )
	  Default value of 2000  "
      ::= { nvApacsconfEntry 9 }

nvApacsconfBillingT5 OBJECT-TYPE
     SYNTAX   INTEGER
     ACCESS   read-write
     STATUS   mandatory
     DESCRIPTION
	" Call duration timer limit for billing ( in 100th secs )
	  Default value of 3000  "
      ::= { nvApacsconfEntry 10 }

nvApacsconfBillingT6 OBJECT-TYPE
     SYNTAX   INTEGER
     ACCESS   read-write
     STATUS   mandatory
     DESCRIPTION
	" Call duration timer limit for billing ( in 100th secs )
	  Default value of 6000  "
      ::= { nvApacsconfEntry 11 }

nvApacsconfDlrtries OBJECT-TYPE
     SYNTAX   INTEGER (0..255)
     ACCESS   read-write
     STATUS   mandatory
     DESCRIPTION
	" number of retries to deliver data before disconnecting
	  Default value of 0 -- nevada retries 6 times by default"
      ::= { nvApacsconfEntry 13 }

nvApacsconfTimerA OBJECT-TYPE
     SYNTAX   INTEGER (0..255)
     ACCESS   read-write
     STATUS   mandatory
     DESCRIPTION
	"  time in sec,for timer A
	  Default value of 5 "
      ::= { nvApacsconfEntry 14 }

nvApacsconfTimerB OBJECT-TYPE
     SYNTAX   INTEGER (0..255)
     ACCESS   read-write
     STATUS   mandatory
     DESCRIPTION
	"  time in sec,for timer A
	  Default value of 10 "
      ::= { nvApacsconfEntry 15 }

nvApacsconfTimerC OBJECT-TYPE
     SYNTAX   INTEGER (0..255)
     ACCESS   read-write
     STATUS   mandatory
     DESCRIPTION
	"  time in sec,for timer A
	  Default value of 40 "
      ::= { nvApacsconfEntry 16 }

nvApacsconfDscdleeot  OBJECT-TYPE
     SYNTAX   INTEGER {
                no(1),
                yes(2)
                }
     ACCESS   read-write
     STATUS   mandatory
     DESCRIPTION
	" "
      ::= { nvApacsconfEntry 17 }

nvApacsconfParerrall  OBJECT-TYPE
     SYNTAX   INTEGER (0..255)
     ACCESS   read-write
     STATUS   mandatory
     DESCRIPTION
" "
      ::= { nvApacsconfEntry 18 }

nvApacsconfStatus OBJECT-TYPE
     SYNTAX   INTEGER {
                valid(1),
                invalid(2)
                }
     ACCESS   read-write
     STATUS   mandatory
     DESCRIPTION
"Operation status. Add the record to the table (valid) or delete
the record from the table (invalid)."
      ::= { nvApacsconfEntry 19 }

--
--  anuaconf
--
nvAnuaconf OBJECT IDENTIFIER ::= { nevadaApacs 2 }

nvAnuaconfMaxRec OBJECT-TYPE
     SYNTAX   INTEGER
     ACCESS   read-only
     STATUS   mandatory
     DESCRIPTION
        "total number of records allowed in database file."
     ::= {nvAnuaconf 1}

nvAnuaconfNumRec OBJECT-TYPE
     SYNTAX   INTEGER
     ACCESS   read-only
     STATUS   mandatory
     DESCRIPTION
        "number of records in use."
     ::= {nvAnuaconf 2}

nvAnuaconfTable OBJECT-TYPE
      SYNTAX   SEQUENCE OF NvAnuaconfEntry
      ACCESS   not-accessible
      STATUS   mandatory
      DESCRIPTION
               "Anuaconf file."
      ::= { nvAnuaconf 3 }

nvAnuaconfEntry OBJECT-TYPE
      SYNTAX   NvAnuaconfEntry
      ACCESS   not-accessible
      STATUS   mandatory
      DESCRIPTION
               "Anuaconf record."
      INDEX { nvAnuaconfIndex }
      ::= { nvAnuaconfTable 1 }

NvAnuaconfEntry ::=
      SEQUENCE {
	nvAnuaconfIndex
		INTEGER,
	nvAnuaconfLabel1
		DisplayString,
	nvAnuaconfReserve1
		DisplayString,
	nvAnuaconfNuaAddress
		DisplayString,
	nvAnuaconfAltLabel
		DisplayString,
	nvAnuaconfRsvrReverse
		INTEGER,
	nvAnuaconfRedirect
		INTEGER,
	nvAnuaconfRetries
		INTEGER,
	nvAnuaconfPreempt
		INTEGER,
	nvAnuaconfMaxpsze
		INTEGER,
	nvAnuaconfStrippar
		INTEGER,
        nvAnuaconfStatus
                INTEGER
	}


nvAnuaconfIndex OBJECT-TYPE
     SYNTAX   INTEGER
     ACCESS   read-only
     STATUS   mandatory
     DESCRIPTION
        "Index of Anuaconf record"
      ::= { nvAnuaconfEntry 1 }

nvAnuaconfLabel1 OBJECT-TYPE
     SYNTAX   DisplayString (SIZE (0..8))
     ACCESS   read-write
     STATUS   mandatory
     DESCRIPTION
        "Identifier to match alternate label in case of redirection  "
      ::= { nvAnuaconfEntry 2 }

nvAnuaconfReserve1 OBJECT-TYPE
     SYNTAX   DisplayString (SIZE (0..2))
     ACCESS   read-only
     STATUS   mandatory
     DESCRIPTION
        "OBSOLETE - removed field."
      ::= { nvAnuaconfEntry 3 }

nvAnuaconfNuaAddress OBJECT-TYPE
     SYNTAX   DisplayString (SIZE (0..16))
     ACCESS   read-write
     STATUS   mandatory
     DESCRIPTION
        "Null terminated ascii string, used ot match the address string
         received from the terminal and/or the x.121 address of the
	 x.25 call placed to the host "
      ::= { nvAnuaconfEntry 4 }

nvAnuaconfAltLabel OBJECT-TYPE
     SYNTAX   DisplayString (SIZE (0..8))
     ACCESS   read-write
     STATUS   mandatory
     DESCRIPTION
        " indicates the label1 of the anuaconf record to be used for redirection "
      ::= { nvAnuaconfEntry 5 }

nvAnuaconfRsvrReverse OBJECT-TYPE
     SYNTAX   INTEGER {
                no(1),
                yes(2)
                }
     ACCESS   read-write
     STATUS   mandatory
     DESCRIPTION
        " reverse charging indication
	  default value is no "
      ::= { nvAnuaconfEntry 6 }

nvAnuaconfRedirect OBJECT-TYPE
     SYNTAX   INTEGER {
                no(1),
                immed(2),
                fail(3)
                }
     ACCESS   read-write
     STATUS   mandatory
     DESCRIPTION
        " Condition for redirecting call
	  default value is no "
      ::= { nvAnuaconfEntry 7 }

nvAnuaconfRetries OBJECT-TYPE
     SYNTAX   INTEGER (0..20)
     ACCESS   read-write
     STATUS   mandatory
     DESCRIPTION
        " number of call retries
	  default value is 2 "
      ::= { nvAnuaconfEntry 8 }

nvAnuaconfPreempt OBJECT-TYPE
     SYNTAX   INTEGER {
                no(1),
                yes(2)
                }
     ACCESS   read-write
     STATUS   mandatory
     DESCRIPTION
        " Call preemption indication
	  default value is no "
      ::= { nvAnuaconfEntry 9 }


nvAnuaconfMaxpsze OBJECT-TYPE
     SYNTAX   INTEGER {
                psze-128(8),    -- enum size 128 bytes
                psze-256(9),
		psze-512(10),
		psze-1024(11),
		psze-2048(12),
		psze-4096(13)
                }
     ACCESS   read-write
     STATUS   mandatory
     DESCRIPTION
        " Maximum message size
	  default value is 256 "
      ::= { nvAnuaconfEntry 10 }


nvAnuaconfStrippar OBJECT-TYPE
     SYNTAX   INTEGER {
                no(1),
                yes(2)
                }
     ACCESS   read-write
     STATUS   mandatory
     DESCRIPTION
        " Strip parity bit ?
	  default value is no "
      ::= { nvAnuaconfEntry 11 }

nvAnuaconfStatus OBJECT-TYPE
     SYNTAX   INTEGER {
                valid(1),
                invalid(2)
                }
     ACCESS   read-write
     STATUS   mandatory
     DESCRIPTION
"Operation status. Add the record to the table (valid) or delete
the record from the table (invalid)."
      ::= { nvAnuaconfEntry 12 }


--
--  abillstat
--
nvAbillstat OBJECT IDENTIFIER ::= { nevadaApacs 3 }

nvAbillstatMaxRec OBJECT-TYPE
     SYNTAX   INTEGER
     ACCESS   read-only
     STATUS   mandatory
     DESCRIPTION
        "total number of records allowed in database file."
     ::= {nvAbillstat 1}

nvAbillstatNumRec OBJECT-TYPE
     SYNTAX   INTEGER
     ACCESS   read-only
     STATUS   mandatory
     DESCRIPTION
        "number of records in use."
     ::= {nvAbillstat 2}

nvAbillstatTable OBJECT-TYPE
      SYNTAX   SEQUENCE OF NvAbillstatEntry
      ACCESS   not-accessible
      STATUS   mandatory
      DESCRIPTION
               "Abillstat file."
      ::= { nvAbillstat 3 }

nvAbillstatEntry OBJECT-TYPE
      SYNTAX   NvAbillstatEntry
      ACCESS   not-accessible
      STATUS   mandatory
      DESCRIPTION
               "Abillstat record."
      INDEX { nvAbillstatIndex }
      ::= { nvAbillstatTable 1 }

NvAbillstatEntry ::=
      SEQUENCE {
	nvAbillstatIndex
		INTEGER,
	nvAbillstatNua
		DisplayString,
	nvAbillstatTbcalls
		INTEGER,
	nvAbillstatTbtime
		INTEGER,
	nvAbillstatTfail
		INTEGER,
	nvAbillstatTxbytes
		INTEGER,
	nvAbillstatRxbytes
		INTEGER,
	nvAbillstatB1call
		INTEGER,
	nvAbillstatB1time
		INTEGER,
	nvAbillstatB2call
		INTEGER,
	nvAbillstatB2time
		INTEGER,
	nvAbillstatB3call
		INTEGER,
	nvAbillstatB3time
		INTEGER,
	nvAbillstatB4call
		INTEGER,
	nvAbillstatB4time
		INTEGER,
	nvAbillstatB5call
		INTEGER,
	nvAbillstatB5time
		INTEGER,
	nvAbillstatB6call
		INTEGER,
	nvAbillstatB6time
		INTEGER,
	nvAbillstatB7call
		INTEGER,
	nvAbillstatB7time
		INTEGER,
		
	nvAbillstatPbcalls
		INTEGER,
	nvAbillstatPbtime
		INTEGER,
	nvAbillstatPfail
		INTEGER,
	nvAbillstatPtxbytes
		INTEGER,
	nvAbillstatPrxbytes
		INTEGER,
	nvAbillstatP1call
		INTEGER,
	nvAbillstatP1time
		INTEGER,
	nvAbillstatP2call
		INTEGER,
	nvAbillstatP2time
		INTEGER,
	nvAbillstatP3call
		INTEGER,
	nvAbillstatP3time
		INTEGER,
	nvAbillstatP4call
		INTEGER,
	nvAbillstatP4time
		INTEGER,
	nvAbillstatP5call
		INTEGER,
	nvAbillstatP5time
		INTEGER,
	nvAbillstatP6call
		INTEGER,
	nvAbillstatP6time
		INTEGER,
	nvAbillstatP7call
		INTEGER,
	nvAbillstatP7time
		INTEGER,
	nvAbillstatDtreset
		DisplayString
	}

nvAbillstatIndex OBJECT-TYPE
     SYNTAX   INTEGER
     ACCESS   read-only
     STATUS   mandatory
     DESCRIPTION
        "Index of Abillstat record"
      ::= { nvAbillstatEntry 1 }

nvAbillstatNua OBJECT-TYPE
     SYNTAX   DisplayString (SIZE (0..16))
     ACCESS   read-only
     STATUS   mandatory
     DESCRIPTION
        " Network User Address "
      ::= { nvAbillstatEntry 2 }

nvAbillstatTbcalls OBJECT-TYPE
     SYNTAX   INTEGER
     ACCESS   read-only
     STATUS   mandatory
     DESCRIPTION
        " Total number of calls to this nua "
      ::= { nvAbillstatEntry 3 }

nvAbillstatTbtime OBJECT-TYPE
     SYNTAX   INTEGER
     ACCESS   read-only
     STATUS   mandatory
     DESCRIPTION
        " Total time to this nua in 100th of second "
      ::= { nvAbillstatEntry 4 }

nvAbillstatTfail OBJECT-TYPE
     SYNTAX   INTEGER
     ACCESS   read-only
     STATUS   mandatory
     DESCRIPTION
        " Number of failed call request "
      ::= { nvAbillstatEntry 5 }

nvAbillstatTxbytes OBJECT-TYPE
     SYNTAX   INTEGER
     ACCESS   read-only
     STATUS   mandatory
     DESCRIPTION
        " Number of bytes of data Transmitted to this nua "
      ::= { nvAbillstatEntry 6 }

nvAbillstatRxbytes OBJECT-TYPE
     SYNTAX   INTEGER
     ACCESS   read-only
     STATUS   mandatory
     DESCRIPTION
        " Number of bytes of data received from this nua "
      ::= { nvAbillstatEntry 7 }

nvAbillstatB1call OBJECT-TYPE
     SYNTAX   INTEGER
     ACCESS   read-only
     STATUS   mandatory
     DESCRIPTION
        " Number of calls greater than call duration timer b1 "
      ::= { nvAbillstatEntry 8 }

nvAbillstatB1time OBJECT-TYPE
     SYNTAX   INTEGER
     ACCESS   read-only
     STATUS   mandatory
     DESCRIPTION
        " Total time for calls greater than timer b1 (100th of sec) "
      ::= { nvAbillstatEntry 9 }

nvAbillstatB2call OBJECT-TYPE
     SYNTAX   INTEGER
     ACCESS   read-only
     STATUS   mandatory
     DESCRIPTION
        " Number of calls greater than call duration timer b2 "
      ::= { nvAbillstatEntry 10 }

nvAbillstatB2time OBJECT-TYPE
     SYNTAX   INTEGER
     ACCESS   read-only
     STATUS   mandatory
     DESCRIPTION
        " Total time for calls greater than timer b2 (100th of sec) "
      ::= { nvAbillstatEntry 11 }

nvAbillstatB3call OBJECT-TYPE
     SYNTAX   INTEGER
     ACCESS   read-only
     STATUS   mandatory
     DESCRIPTION
        " Number of calls greater than call duration timer b3 "
      ::= { nvAbillstatEntry 12 }

nvAbillstatB3time OBJECT-TYPE
     SYNTAX   INTEGER
     ACCESS   read-only
     STATUS   mandatory
     DESCRIPTION
        " Total time for calls greater than timer b3 (100th of sec) "
      ::= { nvAbillstatEntry 13 }

nvAbillstatB4call OBJECT-TYPE
     SYNTAX   INTEGER
     ACCESS   read-only
     STATUS   mandatory
     DESCRIPTION
        " Number of calls greater than call duration timer b4 "
      ::= { nvAbillstatEntry 14 }

nvAbillstatB4time OBJECT-TYPE
     SYNTAX   INTEGER
     ACCESS   read-only
     STATUS   mandatory
     DESCRIPTION
        " Total time for calls greater than timer b4 (100th of sec) "
      ::= { nvAbillstatEntry 15 }

nvAbillstatB5call OBJECT-TYPE
     SYNTAX   INTEGER
     ACCESS   read-only
     STATUS   mandatory
     DESCRIPTION
        " Number of calls greater than call duration timer b5 "
      ::= { nvAbillstatEntry 16 }

nvAbillstatB5time OBJECT-TYPE
     SYNTAX   INTEGER
     ACCESS   read-only
     STATUS   mandatory
     DESCRIPTION
        " Total time for calls greater than timer b5 (100th of sec) "
      ::= { nvAbillstatEntry 17 }

nvAbillstatB6call OBJECT-TYPE
     SYNTAX   INTEGER
     ACCESS   read-only
     STATUS   mandatory
     DESCRIPTION
        " Number of calls greater than call duration timer b7 "
      ::= { nvAbillstatEntry 18 }

nvAbillstatB6time OBJECT-TYPE
     SYNTAX   INTEGER
     ACCESS   read-only
     STATUS   mandatory
     DESCRIPTION
        " Total time for calls greater than timer b6 (100th of sec) "
      ::= { nvAbillstatEntry 19 }

nvAbillstatB7call OBJECT-TYPE
     SYNTAX   INTEGER
     ACCESS   read-only
     STATUS   mandatory
     DESCRIPTION
        " Number of calls greater than call duration timer b7 "
      ::= { nvAbillstatEntry 20 }

nvAbillstatB7time OBJECT-TYPE
     SYNTAX   INTEGER
     ACCESS   read-only
     STATUS   mandatory
     DESCRIPTION
        " Total time for calls greater than timer b7 (100th of sec) "
      ::= { nvAbillstatEntry 21 }

nvAbillstatPbcalls OBJECT-TYPE
     SYNTAX   INTEGER
     ACCESS   read-only
     STATUS   mandatory
     DESCRIPTION
        " "
      ::= { nvAbillstatEntry 22 }

nvAbillstatPbtime OBJECT-TYPE
     SYNTAX   INTEGER
     ACCESS   read-only
     STATUS   mandatory
     DESCRIPTION
        " "
      ::= { nvAbillstatEntry 23 }

nvAbillstatPfail OBJECT-TYPE
     SYNTAX   INTEGER
     ACCESS   read-only
     STATUS   mandatory
     DESCRIPTION
        " "
      ::= { nvAbillstatEntry 24 }

nvAbillstatPtxbytes OBJECT-TYPE
     SYNTAX   INTEGER
     ACCESS   read-only
     STATUS   mandatory
     DESCRIPTION
        " "
      ::= { nvAbillstatEntry 25 }

nvAbillstatPrxbytes OBJECT-TYPE
     SYNTAX   INTEGER
     ACCESS   read-only
     STATUS   mandatory
     DESCRIPTION
        " "
      ::= { nvAbillstatEntry 26 }

nvAbillstatP1call OBJECT-TYPE
     SYNTAX   INTEGER
     ACCESS   read-only
     STATUS   mandatory
     DESCRIPTION
        " "
      ::= { nvAbillstatEntry 27 }

nvAbillstatP1time OBJECT-TYPE
     SYNTAX   INTEGER
     ACCESS   read-only
     STATUS   mandatory
     DESCRIPTION
        " "
      ::= { nvAbillstatEntry 28 }

nvAbillstatP2call OBJECT-TYPE
     SYNTAX   INTEGER
     ACCESS   read-only
     STATUS   mandatory
     DESCRIPTION
        " "
      ::= { nvAbillstatEntry 29 }

nvAbillstatP2time OBJECT-TYPE
     SYNTAX   INTEGER
     ACCESS   read-only
     STATUS   mandatory
     DESCRIPTION
        " "
      ::= { nvAbillstatEntry 30 }

nvAbillstatP3call OBJECT-TYPE
     SYNTAX   INTEGER
     ACCESS   read-only
     STATUS   mandatory
     DESCRIPTION
        " "
      ::= { nvAbillstatEntry 31 }

nvAbillstatP3time OBJECT-TYPE
     SYNTAX   INTEGER
     ACCESS   read-only
     STATUS   mandatory
     DESCRIPTION
        " "
      ::= { nvAbillstatEntry 32 }

nvAbillstatP4call OBJECT-TYPE
     SYNTAX   INTEGER
     ACCESS   read-only
     STATUS   mandatory
     DESCRIPTION
        " "
      ::= { nvAbillstatEntry 33 }

nvAbillstatP4time OBJECT-TYPE
     SYNTAX   INTEGER
     ACCESS   read-only
     STATUS   mandatory
     DESCRIPTION
        " "
      ::= { nvAbillstatEntry 34 }

nvAbillstatP5call OBJECT-TYPE
     SYNTAX   INTEGER
     ACCESS   read-only
     STATUS   mandatory
     DESCRIPTION
        " "
      ::= { nvAbillstatEntry 35 }

nvAbillstatP5time OBJECT-TYPE
     SYNTAX   INTEGER
     ACCESS   read-only
     STATUS   mandatory
     DESCRIPTION
        " "
      ::= { nvAbillstatEntry 36 }

nvAbillstatP6call OBJECT-TYPE
     SYNTAX   INTEGER
     ACCESS   read-only
     STATUS   mandatory
     DESCRIPTION
        " "
      ::= { nvAbillstatEntry 37 }

nvAbillstatP6time OBJECT-TYPE
     SYNTAX   INTEGER
     ACCESS   read-only
     STATUS   mandatory
     DESCRIPTION
        " "
      ::= { nvAbillstatEntry 38 }

nvAbillstatP7call OBJECT-TYPE
     SYNTAX   INTEGER
     ACCESS   read-only
     STATUS   mandatory
     DESCRIPTION
        " "
      ::= { nvAbillstatEntry 39 }

nvAbillstatP7time OBJECT-TYPE
     SYNTAX   INTEGER
     ACCESS   read-only
     STATUS   mandatory
     DESCRIPTION
        " "
      ::= { nvAbillstatEntry 40 }

nvAbillstatDtreset OBJECT-TYPE
     SYNTAX   DisplayString (SIZE (0..20))
     ACCESS   read-only
     STATUS   mandatory
     DESCRIPTION
        "date & time statistics last reset"
      ::= { nvAbillstatEntry 41 }

--
--  apmdmstat
--
nvApmdmstat OBJECT IDENTIFIER ::= { nevadaApacs 4 }

nvApmdmstatMaxRec OBJECT-TYPE
     SYNTAX   INTEGER
     ACCESS   read-only
     STATUS   mandatory
     DESCRIPTION
        "total number of records allowed in database file."
     ::= {nvApmdmstat 1}

nvApddmstatNumRec OBJECT-TYPE
     SYNTAX   INTEGER
     ACCESS   read-only
     STATUS   mandatory
     DESCRIPTION
        "number of records in use."
     ::= {nvApmdmstat 2}

nvApmdmstatTable OBJECT-TYPE
      SYNTAX   SEQUENCE OF NvApmdmstatEntry
      ACCESS   not-accessible
      STATUS   mandatory
      DESCRIPTION
               "Apmdmstat file."
      ::= { nvApmdmstat 3 }

nvApmdmstatEntry OBJECT-TYPE
      SYNTAX   NvApmdmstatEntry
      ACCESS   not-accessible
      STATUS   mandatory
      DESCRIPTION
               "Apmdmstat record."
      INDEX { nvApmdmstatIndex }
      ::= { nvApmdmstatTable 1 }

NvApmdmstatEntry ::=
      SEQUENCE {
	nvApmdmstatIndex
		INTEGER,
	nvApmdmstatSpeed
		INTEGER,
	nvApmdmstatTbcalls
		INTEGER,
	nvApmdmstatSuccess
		INTEGER,
	nvApmdmstatHostclr
		INTEGER,
	nvApmdmstatNwclr
		INTEGER,
	nvApmdmstatFltrain
		INTEGER,
	nvApmdmstatFlsess
		INTEGER,
	nvApmdmstatTxpkt
		INTEGER,
	nvApmdmstatRxpkt
		INTEGER,
	nvApmdmstatTxbytes
		INTEGER,
	nvApmdmstatRxbytes
		INTEGER,
	nvApmdmstatB1calls
		INTEGER,
	nvApmdmstatB2calls
		INTEGER,
	nvApmdmstatB3calls
		INTEGER,
	nvApmdmstatB4calls
		INTEGER,
	nvApmdmstatB5calls
		INTEGER,
	nvApmdmstatB6calls
		INTEGER,
	nvApmdmstatB7calls
		INTEGER,
	nvApmdmstatDtreset
		DisplayString
	}

nvApmdmstatIndex OBJECT-TYPE
     SYNTAX   INTEGER
     ACCESS   read-only
     STATUS   mandatory
     DESCRIPTION
        " Index -- db record "
      ::= { nvApmdmstatEntry 1 }

nvApmdmstatSpeed OBJECT-TYPE
     SYNTAX   INTEGER
     ACCESS   read-only
     STATUS   mandatory
     DESCRIPTION
        " Modem speed "
      ::= { nvApmdmstatEntry 2 }

nvApmdmstatTbcalls OBJECT-TYPE
     SYNTAX   INTEGER
     ACCESS   read-only
     STATUS   mandatory
     DESCRIPTION
        " Total Number of calls at this speed "
      ::= { nvApmdmstatEntry 3 }

nvApmdmstatSuccess OBJECT-TYPE
     SYNTAX   INTEGER
     ACCESS   read-only
     STATUS   mandatory
     DESCRIPTION
        " Number of successful connections "
      ::= { nvApmdmstatEntry 4 }

nvApmdmstatHostclr OBJECT-TYPE
     SYNTAX   INTEGER
     ACCESS   read-only
     STATUS   mandatory
     DESCRIPTION
        " Number of calls cleared by the Host "
      ::= { nvApmdmstatEntry 5 }

nvApmdmstatNwclr OBJECT-TYPE
     SYNTAX   INTEGER
     ACCESS   read-only
     STATUS   mandatory
     DESCRIPTION
        " Number of calls cleared by the network "
      ::= { nvApmdmstatEntry 6 }

nvApmdmstatFltrain OBJECT-TYPE
     SYNTAX   INTEGER
     ACCESS   read-only
     STATUS   mandatory
     DESCRIPTION
        " Number of calls that failed to train "
      ::= { nvApmdmstatEntry 7 }

nvApmdmstatFlsess OBJECT-TYPE
     SYNTAX   INTEGER
     ACCESS   read-only
     STATUS   mandatory
     DESCRIPTION
        " Number with no A-block "
      ::= { nvApmdmstatEntry 8 }

nvApmdmstatTxpkt OBJECT-TYPE
     SYNTAX   INTEGER
     ACCESS   read-only
     STATUS   mandatory
     DESCRIPTION
        " Number of x.25 packet  Tx "
      ::= { nvApmdmstatEntry 9 }

nvApmdmstatRxpkt OBJECT-TYPE
     SYNTAX   INTEGER
     ACCESS   read-only
     STATUS   mandatory
     DESCRIPTION
        " Number of x.25 packet  Rx "
      ::= { nvApmdmstatEntry 10 }

nvApmdmstatTxbytes OBJECT-TYPE
     SYNTAX   INTEGER
     ACCESS   read-only
     STATUS   mandatory
     DESCRIPTION
        " Number of x.25 bytes of data Tx "
      ::= { nvApmdmstatEntry 11 }

nvApmdmstatRxbytes OBJECT-TYPE
     SYNTAX   INTEGER
     ACCESS   read-only
     STATUS   mandatory
     DESCRIPTION
        " Number of x.25 bytes of data rx "
      ::= { nvApmdmstatEntry 12 }

nvApmdmstatB1calls OBJECT-TYPE
     SYNTAX   INTEGER
     ACCESS   read-only
     STATUS   mandatory
     DESCRIPTION
        " Number of calls greater than call duration timer b1 "
      ::= { nvApmdmstatEntry 13 }

nvApmdmstatB2calls OBJECT-TYPE
     SYNTAX   INTEGER
     ACCESS   read-only
     STATUS   mandatory
     DESCRIPTION
        " Number of calls greater than call duration timer b2 "
      ::= { nvApmdmstatEntry 14 }

nvApmdmstatB3calls OBJECT-TYPE
     SYNTAX   INTEGER
     ACCESS   read-only
     STATUS   mandatory
     DESCRIPTION
        " Number of calls greater than call duration timer b3 "
      ::= { nvApmdmstatEntry 15 }

nvApmdmstatB4calls OBJECT-TYPE
     SYNTAX   INTEGER
     ACCESS   read-only
     STATUS   mandatory
     DESCRIPTION
        " Number of calls greater than call duration timer b4 "
      ::= { nvApmdmstatEntry 16 }

nvApmdmstatB5calls OBJECT-TYPE
     SYNTAX   INTEGER
     ACCESS   read-only
     STATUS   mandatory
     DESCRIPTION
        " Number of calls greater than call duration timer b5 "
      ::= { nvApmdmstatEntry 17 }

nvApmdmstatB6calls OBJECT-TYPE
     SYNTAX   INTEGER
     ACCESS   read-only
     STATUS   mandatory
     DESCRIPTION
        " Number of calls greater than call duration timer b6 "
      ::= { nvApmdmstatEntry 18 }


nvApmdmstatB7calls OBJECT-TYPE
     SYNTAX   INTEGER
     ACCESS   read-only
     STATUS   mandatory
     DESCRIPTION
        " Number of calls greater than call duration timer b7 "
      ::= { nvApmdmstatEntry 19 }

nvApmdmstatDtreset OBJECT-TYPE
     SYNTAX   DisplayString (SIZE (0..20))
     ACCESS   read-only
     STATUS   mandatory
     DESCRIPTION
        "date & time statistics last reset"
      ::= { nvApmdmstatEntry 20 }

--
--
--  apacsstat
--
nvApacsstat OBJECT IDENTIFIER ::= { nevadaApacs 5 }

nvApacsstatMaxRec OBJECT-TYPE
     SYNTAX   INTEGER
     ACCESS   read-only
     STATUS   mandatory
     DESCRIPTION
        "total number of records allowed in database file."
     ::= {nvApacsstat 1}

nvApacsstatNumRec OBJECT-TYPE
     SYNTAX   INTEGER
     ACCESS   read-only
     STATUS   mandatory
     DESCRIPTION
        "number of records in use."
     ::= {nvApacsstat 2}

nvApacsstatTable OBJECT-TYPE
      SYNTAX   SEQUENCE OF NvApacsstatEntry
      ACCESS   not-accessible
      STATUS   mandatory
      DESCRIPTION
               "Apacsstat file."
      ::= { nvApacsstat 3 }

nvApacsstatEntry OBJECT-TYPE
      SYNTAX   NvApacsstatEntry
      ACCESS   not-accessible
      STATUS   mandatory
      DESCRIPTION
               "Apacsstat record."
      INDEX { nvApacsstatIndex }
      ::= { nvApacsstatTable 1 }

NvApacsstatEntry ::=
      SEQUENCE {
	nvApacsstatIndex
		INTEGER,
	nvApacsstatNidle
		INTEGER,
        nvApacsstatNxidle
		INTEGER,
        nvApacsstatCursimul
		INTEGER,
        nvApacsstatResetdate
		DisplayString,
        nvApacsstatTcalls
		INTEGER,
        nvApacsstatTxnaks
		INTEGER,
        nvApacsstatRxnaks
		INTEGER,
        nvApacsstatTxbytes
		INTEGER,
        nvApacsstatRxbytes
		INTEGER,
        nvApacsstatCallrcv
		INTEGER,
        nvApacsstatFailneg
		INTEGER,
        nvApacsstatNoadrblk
		INTEGER,
        nvApacsstatInvadrblk
		INTEGER,
        nvApacsstatNonuamtch
		INTEGER,
        nvApacsstatTrmdscsu
		INTEGER,
        nvApacsstatLoscarsu
		INTEGER,
        nvApacsstatParerrsu  -- NR 
		INTEGER,
        nvApacsstatGdadrblks
		INTEGER,
        nvApacsstatX25clrcip
		INTEGER,
        nvApacsstatActtmocip
		INTEGER,
        nvApacsstatTrmdsccip
		INTEGER,
        nvApacsstatLoscarcip
		INTEGER,
        nvApacsstatLrcerrcip
		INTEGER,
        nvApacsstatParerrcip  -- RN 
		INTEGER,
        nvApacsstatTmoerrcip
		INTEGER,
        nvApacsstatX25conns
		INTEGER,
        nvApacsstatX25clrdat
		INTEGER,
        nvApacsstatActtmodat
		INTEGER,
        nvApacsstatTrmdscdat
		INTEGER,
        nvApacsstatLoscardat
		INTEGER,
        nvApacsstatDscnoack
		INTEGER,
        nvApacsstatDscexcnak
		INTEGER,
        nvApacsstatLrcerrdat
		INTEGER,
        nvApacsstatParerrdat  -- RN
		INTEGER,
        nvApacsstatBdhostblk
		INTEGER,
        nvApacsstatTrmnodat
		INTEGER,
        nvApacsstatHostnodat
		INTEGER,
        nvApacsstatTrmnoack
		INTEGER,
        nvApacsstatRetrntmo
		INTEGER,
        nvApacsstatRetrnnak
		INTEGER,
        nvApacsstatTxenqs
		INTEGER,
        nvApacsstatDleeotsnt
		INTEGER,
        nvApacsstatDleeotrcv
		INTEGER,
        nvApacsstatUnxhstclr
		INTEGER,
        nvApacsstatNwadrblks
		INTEGER,
        nvApacsstatRjadrblks
		INTEGER,
        nvApacsstatNonuaentr
		INTEGER,
        nvApacsstatMaxsimul
		INTEGER,
        nvApacsstatN300bd
		INTEGER,
        nvApacsstatN1200bd
		INTEGER,
        nvApacsstatN2400bd
		INTEGER,
        nvApacsstatN9600bd
		INTEGER,
        nvApacsstatN14400bd
		INTEGER,
        nvApacsstatN28800bd
		INTEGER,
	nvApacsstatSimultime	      --AF
	        DisplayString, 	      --AF
	nvApacsstatDtreset
		DisplayString
	}

nvApacsstatIndex OBJECT-TYPE
     SYNTAX   INTEGER
     ACCESS   read-only
     STATUS   mandatory
     DESCRIPTION
        "Index "
      ::= { nvApacsstatEntry 1 }

nvApacsstatNidle OBJECT-TYPE
     SYNTAX   INTEGER
     ACCESS   read-only
     STATUS   mandatory
     DESCRIPTION
        "number of iti ports in idle state "
      ::= { nvApacsstatEntry 2 }

nvApacsstatNxidle OBJECT-TYPE
	SYNTAX   INTEGER
     ACCESS   read-only
     STATUS   mandatory
     DESCRIPTION
        ""
      ::= { nvApacsstatEntry 3 }

nvApacsstatCursimul OBJECT-TYPE
	SYNTAX   INTEGER
     ACCESS   read-only
     STATUS   mandatory
     DESCRIPTION
        ""
      ::= { nvApacsstatEntry 4 }

nvApacsstatResetdate OBJECT-TYPE
     SYNTAX   DisplayString (SIZE (0..32))
     ACCESS   read-only
     STATUS   mandatory
     DESCRIPTION
        ""
      ::= { nvApacsstatEntry 5 }

nvApacsstatTcalls OBJECT-TYPE
	SYNTAX   INTEGER
     ACCESS   read-only
     STATUS   mandatory
     DESCRIPTION
        ""
      ::= { nvApacsstatEntry 6 }

nvApacsstatTxnaks OBJECT-TYPE
	SYNTAX   INTEGER
     ACCESS   read-only
     STATUS   mandatory
     DESCRIPTION
        ""
      ::= { nvApacsstatEntry 7 }

nvApacsstatRxnaks OBJECT-TYPE
	SYNTAX   INTEGER
     ACCESS   read-only
     STATUS   mandatory
     DESCRIPTION
        ""
      ::= { nvApacsstatEntry 8 }

nvApacsstatTxbytes OBJECT-TYPE
	SYNTAX   INTEGER
     ACCESS   read-only
     STATUS   mandatory
     DESCRIPTION
        ""
      ::= { nvApacsstatEntry 9 }

nvApacsstatRxbytes OBJECT-TYPE
	SYNTAX   INTEGER
     ACCESS   read-only
     STATUS   mandatory
     DESCRIPTION
        ""
      ::= { nvApacsstatEntry 10 }

nvApacsstatCallrcv OBJECT-TYPE
	SYNTAX   INTEGER
     ACCESS   read-only
     STATUS   mandatory
     DESCRIPTION
        ""
      ::= { nvApacsstatEntry 11 }

nvApacsstatFailneg OBJECT-TYPE
	SYNTAX   INTEGER
     ACCESS   read-only
     STATUS   mandatory
     DESCRIPTION
        ""
      ::= { nvApacsstatEntry 12 }

nvApacsstatNoadrblk OBJECT-TYPE
	SYNTAX   INTEGER
     ACCESS   read-only
     STATUS   mandatory
     DESCRIPTION
        ""
      ::= { nvApacsstatEntry 13 }

nvApacsstatInvadrblk OBJECT-TYPE
	SYNTAX   INTEGER
     ACCESS   read-only
     STATUS   mandatory
     DESCRIPTION
        ""
      ::= { nvApacsstatEntry 14 }

nvApacsstatNonuamtch OBJECT-TYPE
	SYNTAX   INTEGER
     ACCESS   read-only
     STATUS   mandatory
     DESCRIPTION
        ""
      ::= { nvApacsstatEntry 15 }

nvApacsstatTrmdscsu OBJECT-TYPE
	SYNTAX   INTEGER
     ACCESS   read-only
     STATUS   mandatory
     DESCRIPTION
        ""
      ::= { nvApacsstatEntry 16 }

nvApacsstatLoscarsu OBJECT-TYPE
	SYNTAX   INTEGER
     ACCESS   read-only
     STATUS   mandatory
     DESCRIPTION
        ""
      ::= { nvApacsstatEntry 17 }

nvApacsstatGdadrblks OBJECT-TYPE
	SYNTAX   INTEGER
     ACCESS   read-only
     STATUS   mandatory
     DESCRIPTION
        ""
      ::= { nvApacsstatEntry 18 }

nvApacsstatX25clrcip OBJECT-TYPE
	SYNTAX   INTEGER
     ACCESS   read-only
     STATUS   mandatory
     DESCRIPTION
        ""
      ::= { nvApacsstatEntry 19 }

nvApacsstatActtmocip OBJECT-TYPE
	SYNTAX   INTEGER
     ACCESS   read-only
     STATUS   mandatory
     DESCRIPTION
        ""
      ::= { nvApacsstatEntry 20 }

nvApacsstatTrmdsccip OBJECT-TYPE
	SYNTAX   INTEGER
     ACCESS   read-only
     STATUS   mandatory
     DESCRIPTION
        ""
      ::= { nvApacsstatEntry 21 }

nvApacsstatLoscarcip OBJECT-TYPE
	SYNTAX   INTEGER
     ACCESS   read-only
     STATUS   mandatory
     DESCRIPTION
        ""
      ::= { nvApacsstatEntry 22 }

nvApacsstatLrcerrcip OBJECT-TYPE
	SYNTAX   INTEGER
     ACCESS   read-only
     STATUS   mandatory
     DESCRIPTION
        ""
      ::= { nvApacsstatEntry 23 }

nvApacsstatTmoerrcip OBJECT-TYPE
	SYNTAX   INTEGER
     ACCESS   read-only
     STATUS   mandatory
     DESCRIPTION
        ""
      ::= { nvApacsstatEntry 24 }

nvApacsstatX25conns OBJECT-TYPE
	SYNTAX   INTEGER
     ACCESS   read-only
     STATUS   mandatory
     DESCRIPTION
        ""
      ::= { nvApacsstatEntry 25 }

nvApacsstatX25clrdat OBJECT-TYPE
	SYNTAX   INTEGER
     ACCESS   read-only
     STATUS   mandatory
     DESCRIPTION
        ""
      ::= { nvApacsstatEntry 26 }

nvApacsstatActtmodat OBJECT-TYPE
	SYNTAX   INTEGER
     ACCESS   read-only
     STATUS   mandatory
     DESCRIPTION
        ""
      ::= { nvApacsstatEntry 27 }

nvApacsstatTrmdscdat OBJECT-TYPE
	SYNTAX   INTEGER
     ACCESS   read-only
     STATUS   mandatory
     DESCRIPTION
        ""
      ::= { nvApacsstatEntry 28 }

nvApacsstatLoscardat OBJECT-TYPE
	SYNTAX   INTEGER
     ACCESS   read-only
     STATUS   mandatory
     DESCRIPTION
        ""
      ::= { nvApacsstatEntry 29 }

nvApacsstatDscnoack OBJECT-TYPE
	SYNTAX   INTEGER
     ACCESS   read-only
     STATUS   mandatory
     DESCRIPTION
        ""
      ::= { nvApacsstatEntry 30 }

nvApacsstatDscexcnak OBJECT-TYPE
	SYNTAX   INTEGER
     ACCESS   read-only
     STATUS   mandatory
     DESCRIPTION
        ""
      ::= { nvApacsstatEntry 31 }

nvApacsstatLrcerrdat OBJECT-TYPE
	SYNTAX   INTEGER
     ACCESS   read-only
     STATUS   mandatory
     DESCRIPTION
        ""
      ::= { nvApacsstatEntry 32 }

nvApacsstatBdhostblk OBJECT-TYPE
	SYNTAX   INTEGER
     ACCESS   read-only
     STATUS   mandatory
     DESCRIPTION
        ""
      ::= { nvApacsstatEntry 33 }

nvApacsstatTrmnodat OBJECT-TYPE
	SYNTAX   INTEGER
     ACCESS   read-only
     STATUS   mandatory
     DESCRIPTION
        ""
      ::= { nvApacsstatEntry 34 }

nvApacsstatHostnodat OBJECT-TYPE
	SYNTAX   INTEGER
     ACCESS   read-only
     STATUS   mandatory
     DESCRIPTION
        ""
      ::= { nvApacsstatEntry 35 }

nvApacsstatTrmnoack OBJECT-TYPE
	SYNTAX   INTEGER
     ACCESS   read-only
     STATUS   mandatory
     DESCRIPTION
        ""
      ::= { nvApacsstatEntry 36 }

nvApacsstatRetrntmo OBJECT-TYPE
	SYNTAX   INTEGER
     ACCESS   read-only
     STATUS   mandatory
     DESCRIPTION
        ""
      ::= { nvApacsstatEntry 37 }

nvApacsstatRetrnnak OBJECT-TYPE
	SYNTAX   INTEGER
     ACCESS   read-only
     STATUS   mandatory
     DESCRIPTION
        ""
      ::= { nvApacsstatEntry 38 }

nvApacsstatTxenqs OBJECT-TYPE
	SYNTAX   INTEGER
     ACCESS   read-only
     STATUS   mandatory
     DESCRIPTION
        ""
      ::= { nvApacsstatEntry 39 }

nvApacsstatDleeotsnt OBJECT-TYPE
	SYNTAX   INTEGER
     ACCESS   read-only
     STATUS   mandatory
     DESCRIPTION
        ""
      ::= { nvApacsstatEntry 40 }

nvApacsstatDleeotrcv OBJECT-TYPE
	SYNTAX   INTEGER
     ACCESS   read-only
     STATUS   mandatory
     DESCRIPTION
        ""
      ::= { nvApacsstatEntry 41 }

nvApacsstatUnxhstclr OBJECT-TYPE
	SYNTAX   INTEGER
     ACCESS   read-only
     STATUS   mandatory
     DESCRIPTION
        ""
      ::= { nvApacsstatEntry 42 }

nvApacsstatNwadrblks OBJECT-TYPE
	SYNTAX   INTEGER
     ACCESS   read-only
     STATUS   mandatory
     DESCRIPTION
        ""
      ::= { nvApacsstatEntry 43 }

nvApacsstatRjadrblks OBJECT-TYPE
	SYNTAX   INTEGER
     ACCESS   read-only
     STATUS   mandatory
     DESCRIPTION
        ""
      ::= { nvApacsstatEntry 44 }

nvApacsstatNonuaentr OBJECT-TYPE
	SYNTAX   INTEGER
     ACCESS   read-only
     STATUS   mandatory
     DESCRIPTION
        ""
      ::= { nvApacsstatEntry 45 }

nvApacsstatMaxsimul OBJECT-TYPE
	SYNTAX   INTEGER
     ACCESS   read-only
     STATUS   mandatory
     DESCRIPTION
        ""
      ::= { nvApacsstatEntry 46 }

nvApacsstatN300bd OBJECT-TYPE
	SYNTAX   INTEGER
     ACCESS   read-only
     STATUS   mandatory
     DESCRIPTION
        ""
      ::= { nvApacsstatEntry 47 }

nvApacsstatN1200bd OBJECT-TYPE
	SYNTAX   INTEGER
     ACCESS   read-only
     STATUS   mandatory
     DESCRIPTION
        ""
      ::= { nvApacsstatEntry 48 }

nvApacsstatN2400bd OBJECT-TYPE
	SYNTAX   INTEGER
     ACCESS   read-only
     STATUS   mandatory
     DESCRIPTION
        ""
      ::= { nvApacsstatEntry 49 }

nvApacsstatN9600bd OBJECT-TYPE
	SYNTAX   INTEGER
     ACCESS   read-only
     STATUS   mandatory
     DESCRIPTION
        ""
      ::= { nvApacsstatEntry 50 }

nvApacsstatN14400bd OBJECT-TYPE
	SYNTAX   INTEGER
     ACCESS   read-only
     STATUS   mandatory
     DESCRIPTION
        ""
      ::= { nvApacsstatEntry 51 }

nvApacsstatN28800bd OBJECT-TYPE
	SYNTAX   INTEGER
     ACCESS   read-only
     STATUS   mandatory
     DESCRIPTION
        ""
      ::= { nvApacsstatEntry 52 }
      
nvApacsstatSimultime OBJECT-TYPE            --AF
     SYNTAX   DisplayString (SIZE (0..20))  --AF
     ACCESS   read-only			    --AF
     STATUS   mandatory			    --AF
     DESCRIPTION			    --AF
        "When maxsimul reached."	    --AF
      ::= { nvApacsstatEntry 53 }	    --AF

nvApacsstatParerrsu OBJECT-TYPE
	SYNTAX   INTEGER
     ACCESS   read-only
     STATUS   mandatory
     DESCRIPTION
        ""
      ::= { nvApacsstatEntry 54 }

nvApacsstatParerrcip OBJECT-TYPE
	SYNTAX   INTEGER
     ACCESS   read-only
     STATUS   mandatory
     DESCRIPTION
        ""
      ::= { nvApacsstatEntry 55 }

nvApacsstatParerrdat OBJECT-TYPE
	SYNTAX   INTEGER
     ACCESS   read-only
     STATUS   mandatory
     DESCRIPTION
        ""
      ::= { nvApacsstatEntry 56 }

nvApacsstatDtreset  OBJECT-TYPE
     SYNTAX    DisplayString(SIZE(0..20))
     ACCESS    read-only
     STATUS    mandatory
     DESCRIPTION
       "Date & Time statistics last reset."
      ::= { nvApacsstatEntry 57 }  
--
--  billconf
--
nvBillconf OBJECT IDENTIFIER ::= { nevadaApacs 6 }

nvBillconfMaxRec OBJECT-TYPE
     SYNTAX   INTEGER
     ACCESS   read-only
     STATUS   mandatory
     DESCRIPTION
        "total number of records allowed in database file."
     ::= {nvBillconf 1}

nvBillconfNumRec OBJECT-TYPE
     SYNTAX   INTEGER
     ACCESS   read-only
     STATUS   mandatory
     DESCRIPTION
        "number of records in use."
     ::= {nvBillconf 2}


nvBillconf1Table OBJECT-TYPE
      SYNTAX   SEQUENCE OF NvBillconf1Entry
      ACCESS   not-accessible
      STATUS   mandatory
      DESCRIPTION
               "Billconf file."
      ::= { nvBillconf 3 }

nvBillconf1Entry OBJECT-TYPE
      SYNTAX   NvBillconf1Entry
      ACCESS   not-accessible
      STATUS   mandatory
      DESCRIPTION
               "Billconf record."
      INDEX { nvBillconf1Index }
      ::= { nvBillconf1Table 1 }

NvBillconf1Entry ::=
      SEQUENCE {
	nvBillconf1Index
		INTEGER,
	nvBillconfEnable
		INTEGER,
	nvBillconfSegsize
		INTEGER,
	nvBillconfSet1
		INTEGER,
	nvBillconfSet1nua1
		DisplayString,
	nvBillconfSet1nua2
		DisplayString,
	nvBillconfSet1nua3
		DisplayString,
	nvBillconfSet2
		INTEGER,
	nvBillconfSet2nua1
		DisplayString,
	nvBillconfSet2nua2
		DisplayString,
	nvBillconfSet2nua3
		DisplayString,
	nvBillconfSet3
		INTEGER,
	nvBillconfSet3nua1
		DisplayString,
	nvBillconfSet3nua2
		DisplayString,
	nvBillconfSet3nua3
		DisplayString,
	nvBillconfSet4
		INTEGER,
	nvBillconfSet4nua1
		DisplayString,
	nvBillconfSet4nua2
		DisplayString,
	nvBillconfSet4nua3
		DisplayString,
	nvBillconfSet5
		INTEGER,
	nvBillconfSet5nua1
		DisplayString,
	nvBillconfSet5nua2
		DisplayString,
	nvBillconfSet5nua3
		DisplayString,
	nvBillconfSet6
		INTEGER,
	nvBillconfSet6nua1
		DisplayString,
	nvBillconfSet6nua2
		DisplayString,
	nvBillconfSet6nua3
		DisplayString
	}

nvBillconf1Index OBJECT-TYPE
     SYNTAX   INTEGER
     ACCESS   read-only
     STATUS   mandatory
     DESCRIPTION
        "Index of Billconf record"
      ::= { nvBillconf1Entry 1 }

nvBillconfEnable OBJECT-TYPE
     SYNTAX   INTEGER {
		false(1),
		true(2)
		}
     ACCESS   read-write
     STATUS   mandatory
     DESCRIPTION
        "Enable/Disable billstat accounting."
      ::= { nvBillconf1Entry 2 }

nvBillconfSegsize OBJECT-TYPE
     SYNTAX   INTEGER (1..32767)
     ACCESS   read-write
     STATUS   mandatory
     DESCRIPTION
        "Segment size."
      ::= { nvBillconf1Entry 3 }

nvBillconfSet1 OBJECT-TYPE
     SYNTAX   INTEGER (0..255)
     ACCESS   read-write
     STATUS   mandatory
     DESCRIPTION
        ""
      ::= { nvBillconf1Entry 4 }

nvBillconfSet1nua1 OBJECT-TYPE
     SYNTAX   DisplayString (SIZE(0..16))
     ACCESS   read-write
     STATUS   mandatory
     DESCRIPTION
        ""
      ::= { nvBillconf1Entry 5 }

nvBillconfSet1nua2 OBJECT-TYPE
     SYNTAX   DisplayString (SIZE(0..16))
     ACCESS   read-write
     STATUS   mandatory
     DESCRIPTION
        ""
      ::= { nvBillconf1Entry 6 }

nvBillconfSet1nua3 OBJECT-TYPE
     SYNTAX   DisplayString (SIZE(0..16))
     ACCESS   read-write
     STATUS   mandatory
     DESCRIPTION
        ""
      ::= { nvBillconf1Entry 7 }

nvBillconfSet2 OBJECT-TYPE
     SYNTAX   INTEGER (0..255)
     ACCESS   read-write
     STATUS   mandatory
     DESCRIPTION
        ""
      ::= { nvBillconf1Entry 8 }

nvBillconfSet2nua1 OBJECT-TYPE
     SYNTAX   DisplayString (SIZE(0..16))
     ACCESS   read-write
     STATUS   mandatory
     DESCRIPTION
        ""
      ::= { nvBillconf1Entry 9 }

nvBillconfSet2nua2 OBJECT-TYPE
     SYNTAX   DisplayString (SIZE(0..16))
     ACCESS   read-write
     STATUS   mandatory
     DESCRIPTION
        ""
      ::= { nvBillconf1Entry 10 }

nvBillconfSet2nua3 OBJECT-TYPE
     SYNTAX   DisplayString (SIZE(0..16))
     ACCESS   read-write
     STATUS   mandatory
     DESCRIPTION
        ""
      ::= { nvBillconf1Entry 11 }

nvBillconfSet3 OBJECT-TYPE
     SYNTAX   INTEGER (0..255)
     ACCESS   read-write
     STATUS   mandatory
     DESCRIPTION
        ""
      ::= { nvBillconf1Entry 12 }

nvBillconfSet3nua1 OBJECT-TYPE
     SYNTAX   DisplayString (SIZE(0..16))
     ACCESS   read-write
     STATUS   mandatory
     DESCRIPTION
        ""
      ::= { nvBillconf1Entry 13 }

nvBillconfSet3nua2 OBJECT-TYPE
     SYNTAX   DisplayString (SIZE(0..16))
     ACCESS   read-write
     STATUS   mandatory
     DESCRIPTION
        ""
      ::= { nvBillconf1Entry 14 }

nvBillconfSet3nua3 OBJECT-TYPE
     SYNTAX   DisplayString (SIZE(0..16))
     ACCESS   read-write
     STATUS   mandatory
     DESCRIPTION
        ""
      ::= { nvBillconf1Entry 15 }

nvBillconfSet4 OBJECT-TYPE
     SYNTAX   INTEGER (0..255)
     ACCESS   read-write
     STATUS   mandatory
     DESCRIPTION
        ""
      ::= { nvBillconf1Entry 16 }

nvBillconfSet4nua1 OBJECT-TYPE
     SYNTAX   DisplayString (SIZE(0..16))
     ACCESS   read-write
     STATUS   mandatory
     DESCRIPTION
        ""
      ::= { nvBillconf1Entry 17 }

nvBillconfSet4nua2 OBJECT-TYPE
     SYNTAX   DisplayString (SIZE(0..16))
     ACCESS   read-write
     STATUS   mandatory
     DESCRIPTION
        ""
      ::= { nvBillconf1Entry 18 }

nvBillconfSet4nua3 OBJECT-TYPE
     SYNTAX   DisplayString (SIZE(0..16))
     ACCESS   read-write
     STATUS   mandatory
     DESCRIPTION
        ""
      ::= { nvBillconf1Entry 19 }

nvBillconfSet5 OBJECT-TYPE
     SYNTAX   INTEGER (0..255)
     ACCESS   read-write
     STATUS   mandatory
     DESCRIPTION
        ""
      ::= { nvBillconf1Entry 20 }

nvBillconfSet5nua1 OBJECT-TYPE
     SYNTAX   DisplayString (SIZE(0..16))
     ACCESS   read-write
     STATUS   mandatory
     DESCRIPTION
        ""
      ::= { nvBillconf1Entry 21 }

nvBillconfSet5nua2 OBJECT-TYPE
     SYNTAX   DisplayString (SIZE(0..16))
     ACCESS   read-write
     STATUS   mandatory
     DESCRIPTION
        ""
      ::= { nvBillconf1Entry 22 }

nvBillconfSet5nua3 OBJECT-TYPE
     SYNTAX   DisplayString (SIZE(0..16))
     ACCESS   read-write
     STATUS   mandatory
     DESCRIPTION
        ""
      ::= { nvBillconf1Entry 23 }


nvBillconfSet6 OBJECT-TYPE
     SYNTAX   INTEGER (0..255)
     ACCESS   read-write
     STATUS   mandatory
     DESCRIPTION
        ""
      ::= { nvBillconf1Entry 24 }

nvBillconfSet6nua1 OBJECT-TYPE
     SYNTAX   DisplayString (SIZE(0..16))
     ACCESS   read-write
     STATUS   mandatory
     DESCRIPTION
        ""
      ::= { nvBillconf1Entry 25 }

nvBillconfSet6nua2 OBJECT-TYPE
     SYNTAX   DisplayString (SIZE(0..16))
     ACCESS   read-write
     STATUS   mandatory
     DESCRIPTION
        ""
      ::= { nvBillconf1Entry 26 }

nvBillconfSet6nua3 OBJECT-TYPE
     SYNTAX   DisplayString (SIZE(0..16))
     ACCESS   read-write
     STATUS   mandatory
     DESCRIPTION
        ""
      ::= { nvBillconf1Entry 27 }


nvBillconf2Table OBJECT-TYPE
      SYNTAX   SEQUENCE OF NvBillconf2Entry
      ACCESS   not-accessible
      STATUS   mandatory
      DESCRIPTION
               "Billconf file."
      ::= { nvBillconf 4 }

nvBillconf2Entry OBJECT-TYPE
      SYNTAX   NvBillconf2Entry
      ACCESS   not-accessible
      STATUS   mandatory
      DESCRIPTION
               "Billconf record."
      INDEX { nvBillconf2Index }
      ::= { nvBillconf2Table 1 }

NvBillconf2Entry ::=
      SEQUENCE {
	nvBillconf2Index
		INTEGER,
	nvBillconfSet7
		INTEGER,
	nvBillconfSet7nua1
		DisplayString,
	nvBillconfSet7nua2
		DisplayString,
	nvBillconfSet7nua3
		DisplayString,
	nvBillconfSet8
		INTEGER,
	nvBillconfSet8nua1
		DisplayString,
	nvBillconfSet8nua2
		DisplayString,
	nvBillconfSet8nua3
		DisplayString,
	nvBillconfSet9
		INTEGER,
	nvBillconfSet9nua1
		DisplayString,
	nvBillconfSet9nua2
		DisplayString,
	nvBillconfSet9nua3
		DisplayString,
	nvBillconfSet10
		INTEGER,
	nvBillconfSet10nua1
		DisplayString,
	nvBillconfSet10nua2
		DisplayString,
	nvBillconfSet10nua3
		DisplayString,
	nvBillconfSet11
		INTEGER,
	nvBillconfSet11nua1
		DisplayString,
	nvBillconfSet11nua2
		DisplayString,
	nvBillconfSet11nua3
		DisplayString,
	nvBillconfSet12
		INTEGER,
	nvBillconfSet12nua1
		DisplayString,
	nvBillconfSet12nua2
		DisplayString,
	nvBillconfSet12nua3
		DisplayString
	}

nvBillconf2Index OBJECT-TYPE
     SYNTAX   INTEGER
     ACCESS   read-only
     STATUS   mandatory
     DESCRIPTION
        "Index of Billconf record"
      ::= { nvBillconf2Entry 1 }

nvBillconfSet7 OBJECT-TYPE
     SYNTAX   INTEGER (0..255)
     ACCESS   read-write
     STATUS   mandatory
     DESCRIPTION
        ""
      ::= { nvBillconf2Entry 2 }

nvBillconfSet7nua1 OBJECT-TYPE
     SYNTAX   DisplayString (SIZE(0..16)) 
     ACCESS   read-write
     STATUS   mandatory
     DESCRIPTION
        ""
      ::= { nvBillconf2Entry 3 }

nvBillconfSet7nua2 OBJECT-TYPE
     SYNTAX   DisplayString (SIZE(0..16))
     ACCESS   read-write
     STATUS   mandatory
     DESCRIPTION
        ""
      ::= { nvBillconf2Entry 4 }

nvBillconfSet7nua3 OBJECT-TYPE
     SYNTAX   DisplayString (SIZE(0..16))
     ACCESS   read-write
     STATUS   mandatory
     DESCRIPTION
        ""
      ::= { nvBillconf2Entry 5 }

nvBillconfSet8 OBJECT-TYPE
     SYNTAX   INTEGER (0..255)
     ACCESS   read-write
     STATUS   mandatory
     DESCRIPTION
        ""
      ::= { nvBillconf2Entry 6 }

nvBillconfSet8nua1 OBJECT-TYPE
     SYNTAX   DisplayString (SIZE(0..16))
     ACCESS   read-write
     STATUS   mandatory
     DESCRIPTION
        ""
      ::= { nvBillconf2Entry 7 }

nvBillconfSet8nua2 OBJECT-TYPE
     SYNTAX   DisplayString (SIZE(0..16))
     ACCESS   read-write
     STATUS   mandatory
     DESCRIPTION
        ""
      ::= { nvBillconf2Entry 8 }

nvBillconfSet8nua3 OBJECT-TYPE
     SYNTAX   DisplayString (SIZE(0..16))
     ACCESS   read-write
     STATUS   mandatory
     DESCRIPTION
        ""
      ::= { nvBillconf2Entry 9 }

nvBillconfSet9 OBJECT-TYPE
     SYNTAX   INTEGER (0..255)
     ACCESS   read-write
     STATUS   mandatory
     DESCRIPTION
        ""
      ::= { nvBillconf2Entry 10 }

nvBillconfSet9nua1 OBJECT-TYPE
     SYNTAX   DisplayString (SIZE(0..16))
     ACCESS   read-write
     STATUS   mandatory
     DESCRIPTION
        ""
      ::= { nvBillconf2Entry 11 }

nvBillconfSet9nua2 OBJECT-TYPE
     SYNTAX   DisplayString (SIZE(0..16))
     ACCESS   read-write
     STATUS   mandatory
     DESCRIPTION
        ""
      ::= { nvBillconf2Entry 12 }

nvBillconfSet9nua3 OBJECT-TYPE
     SYNTAX   DisplayString (SIZE(0..16))
     ACCESS   read-write
     STATUS   mandatory
     DESCRIPTION
        ""
      ::= { nvBillconf2Entry 13 }

nvBillconfSet10 OBJECT-TYPE
     SYNTAX   INTEGER (0..255)
     ACCESS   read-write
     STATUS   mandatory
     DESCRIPTION
        ""
      ::= { nvBillconf2Entry 14 }

nvBillconfSet10nua1 OBJECT-TYPE
     SYNTAX   DisplayString (SIZE(0..16))
     ACCESS   read-write
     STATUS   mandatory
     DESCRIPTION
        ""
      ::= { nvBillconf2Entry 15 }

nvBillconfSet10nua2 OBJECT-TYPE
     SYNTAX   DisplayString (SIZE(0..16))
     ACCESS   read-write
     STATUS   mandatory
     DESCRIPTION
        ""
      ::= { nvBillconf2Entry 16 }

nvBillconfSet10nua3 OBJECT-TYPE
     SYNTAX   DisplayString (SIZE(0..16))
     ACCESS   read-write
     STATUS   mandatory
     DESCRIPTION
        ""
      ::= { nvBillconf2Entry 17 }


nvBillconfSet11 OBJECT-TYPE
     SYNTAX   INTEGER (0..255)
     ACCESS   read-write
     STATUS   mandatory
     DESCRIPTION
        ""
      ::= { nvBillconf2Entry 18 }

nvBillconfSet11nua1 OBJECT-TYPE
     SYNTAX   DisplayString (SIZE(0..16))
     ACCESS   read-write
     STATUS   mandatory
     DESCRIPTION
        ""
      ::= { nvBillconf2Entry 19 }

nvBillconfSet11nua2 OBJECT-TYPE
     SYNTAX   DisplayString (SIZE(0..16))
     ACCESS   read-write
     STATUS   mandatory
     DESCRIPTION
        ""
      ::= { nvBillconf2Entry 20 }

nvBillconfSet11nua3 OBJECT-TYPE
     SYNTAX   DisplayString (SIZE(0..16))
     ACCESS   read-write
     STATUS   mandatory
     DESCRIPTION
        ""
      ::= { nvBillconf2Entry 21 }

nvBillconfSet12 OBJECT-TYPE
     SYNTAX   INTEGER (0..255)
     ACCESS   read-write
     STATUS   mandatory
     DESCRIPTION
        ""
      ::= { nvBillconf2Entry 22 }

nvBillconfSet12nua1 OBJECT-TYPE
     SYNTAX   DisplayString (SIZE(0..16))
     ACCESS   read-write
     STATUS   mandatory
     DESCRIPTION
        ""
      ::= { nvBillconf2Entry 23 }

nvBillconfSet12nua2 OBJECT-TYPE
     SYNTAX   DisplayString (SIZE(0..16))
     ACCESS   read-write
     STATUS   mandatory
     DESCRIPTION
        ""
      ::= { nvBillconf2Entry 24 }

nvBillconfSet12nua3 OBJECT-TYPE
     SYNTAX   DisplayString (SIZE(0..16))
     ACCESS   read-write
     STATUS   mandatory
     DESCRIPTION
        ""
      ::= { nvBillconf2Entry 25 }

--
--
--  billstat
--
nvBillstat OBJECT IDENTIFIER ::= { nevadaApacs 7 }

nvBillstatMaxRec OBJECT-TYPE
     SYNTAX   INTEGER
     ACCESS   read-only
     STATUS   mandatory
     DESCRIPTION
        "total number of records allowed in database file."
     ::= {nvBillstat 1}

nvBillstatNumRec OBJECT-TYPE
     SYNTAX   INTEGER
     ACCESS   read-only
     STATUS   mandatory
     DESCRIPTION
        "number of records in use."
     ::= {nvBillstat 2}

nvBillstatTable OBJECT-TYPE
      SYNTAX   SEQUENCE OF NvBillstatEntry
      ACCESS   not-accessible
      STATUS   mandatory
      DESCRIPTION
               "Billstat file."
      ::= { nvBillstat 3 }

nvBillstatEntry OBJECT-TYPE
      SYNTAX   NvBillstatEntry
      ACCESS   not-accessible
      STATUS   mandatory
      DESCRIPTION
               "Billstat record."
      INDEX { nvBillstatIndex }
      ::= { nvBillstatTable 1 }

NvBillstatEntry ::=
      SEQUENCE {
	nvBillstatIndex
		INTEGER,
        nvBillstatNodeid
		INTEGER,
        nvBillstatDate
		DisplayString,
        nvBillstatTime
		DisplayString,
        nvBillstatNuaset
		INTEGER,
        nvBillstatN300bps
		INTEGER,
        nvBillstatN1200bps
		INTEGER,
        nvBillstatN2400bps
		INTEGER,
        nvBillstatNgrtr2400
		INTEGER,
        nvBillstatTxseg
		INTEGER,
        nvBillstatRxseg
		INTEGER,
        nvBillstatRxcallc
		INTEGER,
        nvBillstatHostclr
		INTEGER,
        nvBillstatNetclr
		INTEGER,
        nvBillstatTxpak
		INTEGER,
        nvBillstatRxpak
		INTEGER,
        nvBillstatLess5
		INTEGER,
        nvBillstat5to10
		INTEGER,
        nvBillstat10to15
		INTEGER,
        nvBillstat15to20
		INTEGER,
        nvBillstatGrtr20
		INTEGER,
	nvBillstatClosed
		INTEGER
	}

nvBillstatIndex OBJECT-TYPE
     SYNTAX   INTEGER
     ACCESS   read-only
     STATUS   mandatory
     DESCRIPTION
        "Index "
      ::= { nvBillstatEntry 1 }

nvBillstatNodeid  OBJECT-TYPE
	SYNTAX  INTEGER
     ACCESS   read-only
     STATUS   mandatory
     DESCRIPTION
        ""
      ::= { nvBillstatEntry 2 }

nvBillstatDate  OBJECT-TYPE
	SYNTAX  DisplayString (SIZE(0..6))
     ACCESS   read-only
     STATUS   mandatory
     DESCRIPTION
        ""
      ::= { nvBillstatEntry 3 }

nvBillstatTime  OBJECT-TYPE
	SYNTAX  DisplayString (SIZE(0..8))
     ACCESS   read-only
     STATUS   mandatory
     DESCRIPTION
        ""
      ::= { nvBillstatEntry 4 }

nvBillstatNuaset  OBJECT-TYPE
	SYNTAX  INTEGER
     ACCESS   read-only
     STATUS   mandatory
     DESCRIPTION
        ""
      ::= { nvBillstatEntry 5 }

nvBillstatN300bps  OBJECT-TYPE
	SYNTAX  INTEGER
     ACCESS   read-only
     STATUS   mandatory
     DESCRIPTION
        ""
      ::= { nvBillstatEntry 7 }

nvBillstatN1200bps  OBJECT-TYPE
	SYNTAX  INTEGER
     ACCESS   read-only
     STATUS   mandatory
     DESCRIPTION
        ""
      ::= { nvBillstatEntry 8 }

nvBillstatN2400bps  OBJECT-TYPE
	SYNTAX  INTEGER
     ACCESS   read-only
     STATUS   mandatory
     DESCRIPTION
        ""
      ::= { nvBillstatEntry 9 }

nvBillstatNgrtr2400  OBJECT-TYPE
	SYNTAX  INTEGER
     ACCESS   read-only
     STATUS   mandatory
     DESCRIPTION
        ""
      ::= { nvBillstatEntry 10 }

nvBillstatTxseg  OBJECT-TYPE
	SYNTAX  INTEGER
     ACCESS   read-only
     STATUS   mandatory
     DESCRIPTION
        ""
      ::= { nvBillstatEntry 11 }

nvBillstatRxseg  OBJECT-TYPE
	SYNTAX  INTEGER
     ACCESS   read-only
     STATUS   mandatory
     DESCRIPTION
        ""
      ::= { nvBillstatEntry 12 }

nvBillstatRxcallc  OBJECT-TYPE
	SYNTAX  INTEGER
     ACCESS   read-only
     STATUS   mandatory
     DESCRIPTION
        ""
      ::= { nvBillstatEntry 13 }

nvBillstatHostclr  OBJECT-TYPE
	SYNTAX  INTEGER
     ACCESS   read-only
     STATUS   mandatory
     DESCRIPTION
        ""
      ::= { nvBillstatEntry 14 }

nvBillstatNetclr  OBJECT-TYPE
	SYNTAX  INTEGER
     ACCESS   read-only
     STATUS   mandatory
     DESCRIPTION
        ""
      ::= { nvBillstatEntry 15 }

nvBillstatTxpak  OBJECT-TYPE
	SYNTAX  INTEGER
     ACCESS   read-only
     STATUS   mandatory
     DESCRIPTION
        ""
      ::= { nvBillstatEntry 16 }

nvBillstatRxpak  OBJECT-TYPE
	SYNTAX  INTEGER
     ACCESS   read-only
     STATUS   mandatory
     DESCRIPTION
        ""
      ::= { nvBillstatEntry 17 }

nvBillstatLess5  OBJECT-TYPE
	SYNTAX  INTEGER
     ACCESS   read-only
     STATUS   mandatory
     DESCRIPTION
        ""
      ::= { nvBillstatEntry 18 }

nvBillstat5to10  OBJECT-TYPE
	SYNTAX  INTEGER
     ACCESS   read-only
     STATUS   mandatory
     DESCRIPTION
        ""
      ::= { nvBillstatEntry 19 }

nvBillstat10to15  OBJECT-TYPE
	SYNTAX  INTEGER
     ACCESS   read-only
     STATUS   mandatory
     DESCRIPTION
        ""
      ::= { nvBillstatEntry 20 }

nvBillstat15to20  OBJECT-TYPE
	SYNTAX  INTEGER
     ACCESS   read-only
     STATUS   mandatory
     DESCRIPTION
        ""
      ::= { nvBillstatEntry 21 }

nvBillstatGrtr20  OBJECT-TYPE
	SYNTAX  INTEGER
     ACCESS   read-only
     STATUS   mandatory
     DESCRIPTION
        ""
      ::= { nvBillstatEntry 22 }

nvBillstatClosed OBJECT-TYPE
     SYNTAX   INTEGER {
		open(1),
		closed(2)
		}
     ACCESS   read-only
     STATUS   mandatory
     DESCRIPTION
	"Record closed or open."
     ::= { nvBillstatEntry 23 }


--
-- apfilter
--

nvApfilter    OBJECT IDENTIFIER ::= { nevadaApacs 8 }

nvApfilterMaxRec OBJECT-TYPE
     SYNTAX   INTEGER
     ACCESS   read-only
     STATUS   mandatory
     DESCRIPTION
        "total number of records allowed in database file."
     ::= {nvApfilter 1}

nvApfilterNumRec OBJECT-TYPE
     SYNTAX   INTEGER
     ACCESS   read-only
     STATUS   mandatory
     DESCRIPTION
        "number of records in use."
     ::= {nvApfilter 2}

nvApfilterTable OBJECT-TYPE
      SYNTAX   SEQUENCE OF NvApfilterEntry
      ACCESS   not-accessible
      STATUS   mandatory
      DESCRIPTION
               "Apfilter file."
      ::= { nvApfilter 3 }

nvApfilterEntry OBJECT-TYPE
      SYNTAX   NvApfilterEntry
      ACCESS   not-accessible
      STATUS   mandatory
      DESCRIPTION
               "Apfilter record."
      INDEX { nvApfilterIndex }
      ::= { nvApfilterTable 1 }

NvApfilterEntry ::=
      SEQUENCE {
      nvApfilterIndex
            INTEGER,
      nvApfilterCalled
            DisplayString,
      nvApfilterCalling
            DisplayString,
      nvApfilterAblock
            DisplayString,
      nvApfilterLabel1
            DisplayString,
      nvApfilterMerchid
            DisplayString,
      nvApfilterTermid
            DisplayString,
      nvApfilterFailcause
            INTEGER,
      nvApfilterThreshold
            INTEGER,
      nvApfilterStatus
            INTEGER
      }
      
nvApfilterIndex OBJECT-TYPE
     SYNTAX   INTEGER
     ACCESS   read-only
     STATUS   mandatory
     DESCRIPTION
        "Index of Apfilter record"
      ::= { nvApfilterEntry 1 }

nvApfilterCalled OBJECT-TYPE
     SYNTAX   DisplayString (SIZE (0..21))
     ACCESS   read-write
     STATUS   mandatory
     DESCRIPTION
     "Called Telephone Number."
     ::= { nvApfilterEntry 2 }
     
nvApfilterCalling OBJECT-TYPE
     SYNTAX   DisplayString (SIZE (0..21))
     ACCESS   read-write
     STATUS   mandatory
     DESCRIPTION
     "Calling Telephone Number."
     ::= { nvApfilterEntry 3 }
    
nvApfilterAblock OBJECT-TYPE
     SYNTAX   DisplayString (SIZE (0..16))
     ACCESS   read-write
     STATUS   mandatory
     DESCRIPTION
     "A Block."
     ::= { nvApfilterEntry 4 }
    
nvApfilterLabel1 OBJECT-TYPE
     SYNTAX   DisplayString (SIZE (0..8))
     ACCESS   read-write
     STATUS   mandatory
     DESCRIPTION
     "ANUACONF Label 1."
     ::= { nvApfilterEntry 5 }
    
nvApfilterMerchid OBJECT-TYPE
     SYNTAX   DisplayString (SIZE (0..15))
     ACCESS   read-write
     STATUS   mandatory
     DESCRIPTION
     "Merchant ID."
     ::= { nvApfilterEntry 6 }
    
nvApfilterTermid OBJECT-TYPE
     SYNTAX   DisplayString (SIZE (0..8))
     ACCESS   read-write
     STATUS   mandatory
     DESCRIPTION
     "Terminal ID."
     ::= { nvApfilterEntry 7 }

nvApfilterFailcause OBJECT-TYPE
     SYNTAX   INTEGER {
                any(1),
                none(2),
                failneg(3),
                noadrblk(4),
                invadrblk(5),
                nonuamtch(6),
                trmdscsu(7),
                loscarsu(8),
                parerrsu(9),
                x25clrcip(10),
                acttmocip(11),
                trmdsccip(12),
                loscarcip(13),
                lrcerrcip(14),
                parerrcip(15),
                tmoerrcip(16),
                x25clrdat(17),
                acttmodat(18),
                trmdscdat(19),
                loscardat(20),
                dscnoack(21),
                dscexcnak(22),
                lrcerrdat(23),
                parerrdat(24),
                bdhostblk(25)
                }
     ACCESS   read-write
     STATUS   mandatory
     DESCRIPTION
     "Failure Cause."
     ::= { nvApfilterEntry 8 }
     
nvApfilterThreshold OBJECT-TYPE
     SYNTAX   INTEGER (0..65535)
     ACCESS   read-write
     STATUS   mandatory
     DESCRIPTION
     "Number of records per minute for this filter."
     ::= { nvApfilterEntry 9}

nvApfilterStatus OBJECT-TYPE
     SYNTAX   INTEGER {
                valid(1),
                invalid(2)
                }
     ACCESS   read-write
     STATUS   mandatory
     DESCRIPTION
           "Operation status. Add the record to the table (valid) or
           delete the record from the table (invalid)."
     ::= { nvApfilterEntry 15 }

--
-- apfclstat
--

nvApfclstat    OBJECT IDENTIFIER ::= { nevadaApacs 9 }

nvApfclstatMaxRec OBJECT-TYPE
     SYNTAX   INTEGER
     ACCESS   read-only
     STATUS   mandatory
     DESCRIPTION
        "total number of records allowed in database file."
     ::= {nvApfclstat 1}

nvApfclstatNumRec OBJECT-TYPE
     SYNTAX   INTEGER
     ACCESS   read-only
     STATUS   mandatory
     DESCRIPTION
        "number of records in use."
     ::= {nvApfclstat 2}

nvApfclstatTable OBJECT-TYPE
      SYNTAX   SEQUENCE OF NvApfclstatEntry
      ACCESS   not-accessible
      STATUS   mandatory
      DESCRIPTION
               "Apfclstat file."
      ::= { nvApfclstat 3 }

nvApfclstatEntry OBJECT-TYPE
      SYNTAX   NvApfclstatEntry
      ACCESS   not-accessible
      STATUS   mandatory
      DESCRIPTION
               "Apfclstat record."
      INDEX { nvApfclstatIndex }
      ::= { nvApfclstatTable 1 }

NvApfclstatEntry ::=
      SEQUENCE {
      nvApfclstatIndex
            INTEGER,
      nvApfclstatDate
            DisplayString,
      nvApfclstatTime
            DisplayString,
      nvApfclstatCalling
            DisplayString,
      nvApfclstatCalled
            DisplayString,
      nvApfclstatAblock
            DisplayString,
      nvApfclstatNua
            DisplayString,
      nvApfclstatLabel1
            DisplayString,
      nvApfclstatMerchid
            DisplayString,
      nvApfclstatTermid
            DisplayString,
      nvApfclstatSpeed
            INTEGER,
      nvApfclstatTxbytes
            INTEGER,
      nvApfclstatRxbytes
            INTEGER,
      nvApfclstatIsdnclr
            INTEGER,
      nvApfclstatX25clr
            INTEGER,
      nvApfclstatDialind
            INTEGER,
      nvApfclstatTermtype
            DisplayString,
      nvApfclstatPstndur
            INTEGER,
      nvApfclstatX25dur
            INTEGER,
      nvApfclstatDspname
            DisplayString,
      nvApfclstatPriname
            INTEGER,
      nvApfclstatWanport
            DisplayString,
      nvApfclstatFailcause
            INTEGER,
      nvApfclstatFilter
            INTEGER
      }
      
nvApfclstatIndex OBJECT-TYPE
     SYNTAX   INTEGER
     ACCESS   read-only
     STATUS   mandatory
     DESCRIPTION
        "Index of Apfclstat record"
      ::= { nvApfclstatEntry 1 }
      
nvApfclstatDate OBJECT-TYPE
     SYNTAX   DisplayString (SIZE(0..10))
     ACCESS   read-only
     STATUS   mandatory
     DESCRIPTION
        "Date of Call Failure."
     ::= { nvApfclstatEntry 2}
     
nvApfclstatTime OBJECT-TYPE
     SYNTAX   DisplayString (SIZE(0..8))
     ACCESS   read-only
     STATUS   mandatory
     DESCRIPTION
        "Time of Call Failure."
     ::= { nvApfclstatEntry 3}
 
nvApfclstatCalling OBJECT-TYPE
     SYNTAX   DisplayString (SIZE(0..21))
     ACCESS   read-only
     STATUS   mandatory
     DESCRIPTION
        "Calling telephone number."
     ::= { nvApfclstatEntry 4}
 
nvApfclstatCalled OBJECT-TYPE
     SYNTAX   DisplayString (SIZE(0..21))
     ACCESS   read-only
     STATUS   mandatory
     DESCRIPTION
        "Called telephone number."
     ::= { nvApfclstatEntry 5}
 
nvApfclstatAblock OBJECT-TYPE
     SYNTAX   DisplayString (SIZE(0..16))
     ACCESS   read-only
     STATUS   mandatory
     DESCRIPTION
        "A-block received from terminal."
     ::= { nvApfclstatEntry 6}
 
nvApfclstatNua OBJECT-TYPE
     SYNTAX   DisplayString (SIZE(0..16))
     ACCESS   read-only
     STATUS   mandatory
     DESCRIPTION
        "NUA to which call was connected."
     ::= { nvApfclstatEntry 7}
 
nvApfclstatLabel1 OBJECT-TYPE
     SYNTAX   DisplayString (SIZE(0..8))
     ACCESS   read-only
     STATUS   mandatory
     DESCRIPTION
        "ANUACONF label1 used."
     ::= { nvApfclstatEntry 8}
 
nvApfclstatMerchid OBJECT-TYPE
     SYNTAX   DisplayString (SIZE(0..15))
     ACCESS   read-only
     STATUS   mandatory
     DESCRIPTION
        "Merchant ID from transaction."
     ::= { nvApfclstatEntry 9}
 
nvApfclstatTermid OBJECT-TYPE
     SYNTAX   DisplayString (SIZE(0..8))
     ACCESS   read-only
     STATUS   mandatory
     DESCRIPTION
        "Terminal ID from transaction."
     ::= { nvApfclstatEntry 10}
 
nvApfclstatSpeed OBJECT-TYPE
     SYNTAX   INTEGER (0..65535)
     ACCESS   read-only
     STATUS   mandatory
     DESCRIPTION
        "Speed of modem."
     ::= { nvApfclstatEntry 11 }
     
nvApfclstatTxbytes OBJECT-TYPE
     SYNTAX   INTEGER
     ACCESS   read-only
     STATUS   mandatory
     DESCRIPTION
        "Number of bytes sent."
     ::= { nvApfclstatEntry 12 }
     
nvApfclstatRxbytes OBJECT-TYPE
     SYNTAX   INTEGER
     ACCESS   read-only
     STATUS   mandatory
     DESCRIPTION
        "Number of bytes received."
     ::= { nvApfclstatEntry 13 }
     
nvApfclstatIsdnclr OBJECT-TYPE
     SYNTAX   INTEGER (0..255)
     ACCESS   read-only
     STATUS   mandatory
     DESCRIPTION
        "ISDN Clear codes."
     ::= { nvApfclstatEntry 14 }

nvApfclstatX25clr OBJECT-TYPE
     SYNTAX   INTEGER (0..255)
     ACCESS   read-only
     STATUS   mandatory
     DESCRIPTION
        "X25 Clear codes."
     ::= { nvApfclstatEntry 15 }
     
nvApfclstatDialind OBJECT-TYPE
     SYNTAX   INTEGER
     ACCESS   read-only
     STATUS   mandatory
     DESCRIPTION
        "Dial indicator from the transaction data."
     ::= { nvApfclstatEntry 16 }
     
nvApfclstatTermtype OBJECT-TYPE
     SYNTAX   DisplayString (SIZE(0..4))
     ACCESS   read-only
     STATUS   mandatory
     DESCRIPTION
        "Terminal type from the transaction data."
     ::= { nvApfclstatEntry 17 }

nvApfclstatPstndur OBJECT-TYPE
     SYNTAX   INTEGER (0..65535)
     ACCESS   read-only
     STATUS   mandatory
     DESCRIPTION
        "PSTN duration."
     ::= { nvApfclstatEntry 18}
     
nvApfclstatX25dur OBJECT-TYPE
     SYNTAX   INTEGER (0..65535)
     ACCESS   read-only
     STATUS   mandatory
     DESCRIPTION
        "X25 duration."
     ::= { nvApfclstatEntry 19}
     
nvApfclstatDspname OBJECT-TYPE
     SYNTAX   DisplayString (SIZE(0..11))
     ACCESS   read-only
     STATUS   mandatory
     DESCRIPTION
        "DSP Port Number."
     ::= { nvApfclstatEntry 20 }
     
nvApfclstatPriname OBJECT-TYPE
     SYNTAX   INTEGER {
                none(1),
                pri1(2),
                pri2(3),
                pri3(4),
                pri4(5),
                pri5(6),
                pri6(7),
                pri7(8),
                pri8(9)
                }
     ACCESS   read-only
     STATUS   mandatory
     DESCRIPTION
        "PRI link number."
     ::= { nvApfclstatEntry 21}
      
nvApfclstatWanport OBJECT-TYPE
     SYNTAX   DisplayString (SIZE(0..11))
     ACCESS   read-only
     STATUS   mandatory
     DESCRIPTION
        "X25 Port Number."
     ::= { nvApfclstatEntry 22 }
     

nvApfclstatFailcause OBJECT-TYPE
     SYNTAX   INTEGER {
                any(1),
                none(2),
                failneg(3),
                noadrblk(4),
                invadrblk(5),
                nonuamtch(6),
                trmdscsu(7),
                loscarsu(8),
                parerrsu(9),
                x25clrcip(10),
                acttmocip(11),
                trmdsccip(12),
                loscarcip(13),
                lrcerrcip(14),
                parerrcip(15),
                tmoerrcip(16),
                x25clrdat(17),
                acttmodat(18),
                trmdscdat(19),
                loscardat(20),
                dscnoack(21),
                dscexcnak(22),
                lrcerrdat(23),
                parerrdat(24),
                bdhostblk(25)
                }
     ACCESS   read-only
     STATUS   mandatory
     DESCRIPTION
        "Failure Cause."
     ::= { nvApfclstatEntry 23}

nvApfclstatFilter OBJECT-TYPE
     SYNTAX   INTEGER(0..255)
     ACCESS   read-only
     STATUS   mandatory
     DESCRIPTION
        "Filter number - not used in this file."
     ::= { nvApfclstatEntry 24}
     
--
-- apclstat
--

nvApclstat    OBJECT IDENTIFIER ::= { nevadaApacs 10 }

nvApclstatMaxRec OBJECT-TYPE
     SYNTAX   INTEGER
     ACCESS   read-only
     STATUS   mandatory
     DESCRIPTION
        "total number of records allowed in database file."
     ::= {nvApclstat 1}

nvApclstatNumRec OBJECT-TYPE
     SYNTAX   INTEGER
     ACCESS   read-only
     STATUS   mandatory
     DESCRIPTION
        "number of records in use."
     ::= {nvApclstat 2}

nvApclstatTable OBJECT-TYPE
      SYNTAX   SEQUENCE OF NvApclstatEntry
      ACCESS   not-accessible
      STATUS   mandatory
      DESCRIPTION
               "Apclstat file."
      ::= { nvApclstat 3 }

nvApclstatEntry OBJECT-TYPE
      SYNTAX   NvApclstatEntry
      ACCESS   not-accessible
      STATUS   mandatory
      DESCRIPTION
               "Apclstat record."
      INDEX { nvApclstatIndex }
      ::= { nvApclstatTable 1 }

NvApclstatEntry ::=
      SEQUENCE {
      nvApclstatIndex
            INTEGER,
      nvApclstatDate
            DisplayString,
      nvApclstatTime
            DisplayString,
      nvApclstatCalling
            DisplayString,
      nvApclstatCalled
            DisplayString,
      nvApclstatAblock
            DisplayString,
      nvApclstatNua
            DisplayString,
      nvApclstatLabel1
            DisplayString,
      nvApclstatMerchid
            DisplayString,
      nvApclstatTermid
            DisplayString,
      nvApclstatSpeed
            INTEGER,
      nvApclstatTxbytes
            INTEGER,
      nvApclstatRxbytes
            INTEGER,
      nvApclstatIsdnclr
            INTEGER,
      nvApclstatX25clr
            INTEGER,
      nvApclstatDialind
            INTEGER,
      nvApclstatTermtype
            DisplayString,
      nvApclstatPstndur
            INTEGER,
      nvApclstatX25dur
            INTEGER,
      nvApclstatDspname
            DisplayString,
      nvApclstatPriname
            INTEGER,
      nvApclstatWanport
            DisplayString,
      nvApclstatFailcause
            INTEGER,
      nvApclstatFilter
            INTEGER
      }
      
nvApclstatIndex OBJECT-TYPE
     SYNTAX   INTEGER
     ACCESS   read-only
     STATUS   mandatory
     DESCRIPTION
        "Index of Apclstat record"
      ::= { nvApclstatEntry 1 }
      
nvApclstatDate OBJECT-TYPE
     SYNTAX   DisplayString (SIZE(0..10))
     ACCESS   read-only
     STATUS   mandatory
     DESCRIPTION
        "Date of Call Failure."
     ::= { nvApclstatEntry 2}
     
nvApclstatTime OBJECT-TYPE
     SYNTAX   DisplayString (SIZE(0..8))
     ACCESS   read-only
     STATUS   mandatory
     DESCRIPTION
        "Time of Call Failure."
     ::= { nvApclstatEntry 3}
 
nvApclstatCalling OBJECT-TYPE
     SYNTAX   DisplayString (SIZE(0..21))
     ACCESS   read-only
     STATUS   mandatory
     DESCRIPTION
        "Calling telephone number."
     ::= { nvApclstatEntry 4}
 
nvApclstatCalled OBJECT-TYPE
     SYNTAX   DisplayString (SIZE(0..21))
     ACCESS   read-only
     STATUS   mandatory
     DESCRIPTION
        "Called telephone number."
     ::= { nvApclstatEntry 5}
 
nvApclstatAblock OBJECT-TYPE
     SYNTAX   DisplayString (SIZE(0..16))
     ACCESS   read-only
     STATUS   mandatory
     DESCRIPTION
        "A-block received from terminal."
     ::= { nvApclstatEntry 6}
 
nvApclstatNua OBJECT-TYPE
     SYNTAX   DisplayString (SIZE(0..16))
     ACCESS   read-only
     STATUS   mandatory
     DESCRIPTION
        "NUA to which call was connected."
     ::= { nvApclstatEntry 7}
 
nvApclstatLabel1 OBJECT-TYPE
     SYNTAX   DisplayString (SIZE(0..8))
     ACCESS   read-only
     STATUS   mandatory
     DESCRIPTION
        "ANUACONF label1 used."
     ::= { nvApclstatEntry 8}
 
nvApclstatMerchid OBJECT-TYPE
     SYNTAX   DisplayString (SIZE(0..15))
     ACCESS   read-only
     STATUS   mandatory
     DESCRIPTION
        "Merchant ID from transaction."
     ::= { nvApclstatEntry 9}
 
nvApclstatTermid OBJECT-TYPE
     SYNTAX   DisplayString (SIZE(0..8))
     ACCESS   read-only
     STATUS   mandatory
     DESCRIPTION
        "Terminal ID from transaction."
     ::= { nvApclstatEntry 10}
 
nvApclstatSpeed OBJECT-TYPE
     SYNTAX   INTEGER (0..65535)
     ACCESS   read-only
     STATUS   mandatory
     DESCRIPTION
        "Speed of modem."
     ::= { nvApclstatEntry 11 }
     
nvApclstatTxbytes OBJECT-TYPE
     SYNTAX   INTEGER
     ACCESS   read-only
     STATUS   mandatory
     DESCRIPTION
        "Number of bytes sent."
     ::= { nvApclstatEntry 12 }
     
nvApclstatRxbytes OBJECT-TYPE
     SYNTAX   INTEGER
     ACCESS   read-only
     STATUS   mandatory
     DESCRIPTION
        "Number of bytes received."
     ::= { nvApclstatEntry 13 }
     
nvApclstatIsdnclr OBJECT-TYPE
     SYNTAX   INTEGER (0..255)
     ACCESS   read-only
     STATUS   mandatory
     DESCRIPTION
        "ISDN Clear codes."
     ::= { nvApclstatEntry 14 }

nvApclstatX25clr OBJECT-TYPE
     SYNTAX   INTEGER (0..255)
     ACCESS   read-only
     STATUS   mandatory
     DESCRIPTION
        "X25 Clear codes."
     ::= { nvApclstatEntry 15 }
     
nvApclstatDialind OBJECT-TYPE
     SYNTAX   INTEGER
     ACCESS   read-only
     STATUS   mandatory
     DESCRIPTION
        "Dial indicator from the transaction data."
     ::= { nvApclstatEntry 16 }
     
nvApclstatTermtype OBJECT-TYPE
     SYNTAX   DisplayString (SIZE(0..4))
     ACCESS   read-only
     STATUS   mandatory
     DESCRIPTION
        "Terminal type from the transaction data."
     ::= { nvApclstatEntry 17 }

nvApclstatPstndur OBJECT-TYPE
     SYNTAX   INTEGER (0..65535)
     ACCESS   read-only
     STATUS   mandatory
     DESCRIPTION
        "PSTN duration."
     ::= { nvApclstatEntry 18}
     
nvApclstatX25dur OBJECT-TYPE
     SYNTAX   INTEGER (0..65535)
     ACCESS   read-only
     STATUS   mandatory
     DESCRIPTION
        "X25 duration."
     ::= { nvApclstatEntry 19}
     
nvApclstatDspname OBJECT-TYPE
     SYNTAX   DisplayString (SIZE(0..11))
     ACCESS   read-only
     STATUS   mandatory
     DESCRIPTION
        "DSP Port Number."
     ::= { nvApclstatEntry 20 }
     
nvApclstatPriname OBJECT-TYPE
     SYNTAX   INTEGER {
                none(1),
                pri1(2),
                pri2(3),
                pri3(4),
                pri4(5),
                pri5(6),
                pri6(7),
                pri7(8),
                pri8(9)
                }
     ACCESS   read-only
     STATUS   mandatory
     DESCRIPTION
        "PRI link number."
     ::= { nvApclstatEntry 21}
      
nvApclstatWanport OBJECT-TYPE
     SYNTAX   DisplayString (SIZE(0..11))
     ACCESS   read-only
     STATUS   mandatory
     DESCRIPTION
        "X25 Port Number."
     ::= { nvApclstatEntry 22 }
     

nvApclstatFailcause OBJECT-TYPE
     SYNTAX   INTEGER {
                any(1),
                none(2),
                failneg(3),
                noadrblk(4),
                invadrblk(5),
                nonuamtch(6),
                trmdscsu(7),
                loscarsu(8),
                parerrsu(9),
                x25clrcip(10),
                acttmocip(11),
                trmdsccip(12),
                loscarcip(13),
                lrcerrcip(14),
                parerrcip(15),
                tmoerrcip(16),
                x25clrdat(17),
                acttmodat(18),
                trmdscdat(19),
                loscardat(20),
                dscnoack(21),
                dscexcnak(22),
                lrcerrdat(23),
                parerrdat(24),
                bdhostblk(25)
                }
     ACCESS   read-only
     STATUS   mandatory
     DESCRIPTION
        "Failure Cause."
     ::= { nvApclstatEntry 23}

nvApclstatFilter OBJECT-TYPE
     SYNTAX   INTEGER(0..255)
     ACCESS   read-only
     STATUS   mandatory
     DESCRIPTION
        "Filter number used to produce this record."
     ::= { nvApclstatEntry 24}
 
--
--
--      R2 Signaling
--
--
--
-- r2prof
--

nvR2prof    OBJECT IDENTIFIER ::= { nevadaR2 1 }

nvR2profMaxRec OBJECT-TYPE
     SYNTAX   INTEGER
     ACCESS   read-only
     STATUS   mandatory
     DESCRIPTION
        "total number of records allowed in database file."
     ::= {nvR2prof 1}

nvR2profNumRec OBJECT-TYPE
     SYNTAX   INTEGER
     ACCESS   read-only
     STATUS   mandatory
     DESCRIPTION
        "number of records in use."
     ::= {nvR2prof 2}

nvR2profTable OBJECT-TYPE
      SYNTAX   SEQUENCE OF NvR2profEntry
      ACCESS   not-accessible
      STATUS   mandatory
      DESCRIPTION
               "R2prof file."
      ::= { nvR2prof 3 }

nvR2profEntry OBJECT-TYPE
      SYNTAX   NvR2profEntry
      ACCESS   not-accessible
      STATUS   mandatory
      DESCRIPTION
               "R2prof record."
      INDEX { nvR2profIndex }
      ::= { nvR2profTable 1 }

NvR2profEntry ::=
      SEQUENCE {
      nvR2profIndex
            INTEGER,
      nvR2profProfname
            DisplayString,
      nvR2profSuffix
            DisplayString,
      nvR2profcdBits    -- RN 04/28/98
            INTEGER,
      nvR2profClearback
            INTEGER,
      nvR2profForcerel
            INTEGER,
      nvR2profClearack
            INTEGER,
      nvR2profReanswer
            INTEGER,
      nvR2profMfmode
            INTEGER,
      nvR2profMfnextdig
            INTEGER,
      nvR2profMfrestart
            INTEGER,
      nvR2profMfcongstion
            INTEGER,
      nvR2profMfvacant
            INTEGER,
      nvR2profMfspeech
            INTEGER,
      nvR2profMfbusy
            INTEGER,
      nvR2profMfspchnc
            INTEGER,
      nvR2profMfgroupb
            INTEGER,
      nvR2profMfanumsch
            INTEGER,
      nvR2profMftimeout
            INTEGER,
      nvR2profStatus
            INTEGER,
      nvR2profAnswergrd
	    INTEGER,
      nvR2profClrfwdgrd
	    INTEGER,
      nvR2profMfabnrel
	    INTEGER,
      nvR2profIdlealmsk
	    INTEGER,
      nvR2profSeizalmsk
	    INTEGER,
      nvR2profSzakalmsk
	    INTEGER,
      nvR2profAnswalmsk
	    INTEGER,
      nvR2profClbkalmsk
	    INTEGER,
      nvR2profFcrlalmsk
	    INTEGER,
      nvR2profClfwalmsk
	    INTEGER,
      nvR2profBlckalmsk
	    INTEGER
                    }

nvR2profIndex OBJECT-TYPE
     SYNTAX   INTEGER
     ACCESS   read-only
     STATUS   mandatory
     DESCRIPTION
        "Index of R2prof record"
      ::= { nvR2profEntry 1 }

nvR2profProfname OBJECT-TYPE
     SYNTAX   DisplayString (SIZE (0..11))
     ACCESS   read-write
     STATUS   mandatory
     DESCRIPTION
     "Name of R2 flavor (profname)"
     ::= { nvR2profEntry 2 }

nvR2profSuffix OBJECT-TYPE
     SYNTAX   DisplayString (SIZE (0..4))
     ACCESS   read-write
     STATUS   mandatory
     DESCRIPTION
     "Abbreviation of R2 flavor (suffix)  "
     ::= { nvR2profEntry 3 }

nvR2profcdBits OBJECT-TYPE
     SYNTAX   INTEGER (0..3)
     ACCESS   read-write
     STATUS   mandatory
     DESCRIPTION
     " Support for CD bits (cdbits)
       Default value 2 "
     ::= { nvR2profEntry 4 }

nvR2profClearback OBJECT-TYPE
     SYNTAX   INTEGER
               {
               sup(6),     -- all values (+1)
               notsup(7)   -- all values (+1)
               }
     ACCESS   read-write
     STATUS   mandatory
     DESCRIPTION
     " Support for CLEAR_BACK (clearback)  "
     ::= { nvR2profEntry 5 }

nvR2profForcerel OBJECT-TYPE
     SYNTAX   INTEGER
               {
               sup(6),     -- all values (+1)
               notsup(7)   -- all values (+1)
               }
     ACCESS   read-write
     STATUS   mandatory
     DESCRIPTION
     " Support for Forced Release (forcerel)  "
     ::= { nvR2profEntry 6 }

nvR2profClearack OBJECT-TYPE
     SYNTAX   INTEGER
               {
               sup(6),     -- all values (+1)
               notsup(7)   -- all values (+1)
               }
     ACCESS   read-write
     STATUS   mandatory
     DESCRIPTION
     " Support for CLEAR_ACK (clearack)  "
     ::= { nvR2profEntry 7 }

nvR2profReanswer OBJECT-TYPE
     SYNTAX   INTEGER
               {
               sup(6),     -- all values (+1)
               notsup(7)   -- all values (+1)
               }
     ACCESS   read-write
     STATUS   mandatory
     DESCRIPTION
     " Support for Reanswer (reanswer)  "
     ::= { nvR2profEntry 8 }

nvR2profMfmode OBJECT-TYPE
     SYNTAX   INTEGER
               {
               compelled(24),               -- all values (+1)
               semicompel(25),              -- all values (+1)
               noncompel(26)                -- all values (+1)
               }
     ACCESS   read-write
     STATUS   mandatory
     DESCRIPTION
     "  MF scheme for in-band signaling (mfmode)  "
     ::= { nvR2profEntry 9 }

nvR2profMfnextdig OBJECT-TYPE
     SYNTAX   INTEGER
               {
               notapp(1),        -- all values (+1)
               a1    (32),       -- all values (+1)
               a2    (33),       -- all values (+1)
               a3    (34),       -- all values (+1)
               a4    (35),       -- all values (+1)
               a5    (36),       -- all values (+1)
               a6    (37),       -- all values (+1)
               a7    (38),       -- all values (+1)
               a8    (39),       -- all values (+1)
               a9    (40),       -- all values (+1)
               a10   (41),       -- all values (+1)
               a11   (42),       -- all values (+1)
               a12   (43),       -- all values (+1)
               a13   (44),       -- all values (+1)
               a14   (45),       -- all values (+1)
               a15   (46),       -- all values (+1)
               b1    (47),       -- all values (+1)
               b2    (48),       -- all values (+1)
               b3    (49),       -- all values (+1)
               b4    (50),       -- all values (+1)
               b5    (51),       -- all values (+1)
               b6    (52),       -- all values (+1)
               b7    (53),       -- all values (+1)
               b8    (54),       -- all values (+1)
               b9    (55),       -- all values (+1)
               b10   (56),       -- all values (+1)
               b11   (57),       -- all values (+1)
               b12   (58),       -- all values (+1)
               b13   (59),       -- all values (+1)
               b14   (60),       -- all values (+1)
               b15   (61)        -- all values (+1)
               }
     ACCESS   read-write
     STATUS   mandatory
     DESCRIPTION
     "       MF code for send next digit (mfnextdig)  "
     ::= { nvR2profEntry 10 }

nvR2profMfrestart OBJECT-TYPE
     SYNTAX   INTEGER
               {
               notapp(1),        -- all values (+1)
               a1    (32),       -- all values (+1)
               a2    (33),       -- all values (+1)
               a3    (34),       -- all values (+1)
               a4    (35),       -- all values (+1)
               a5    (36),       -- all values (+1)
               a6    (37),       -- all values (+1)
               a7    (38),       -- all values (+1)
               a8    (39),       -- all values (+1)
               a9    (40),       -- all values (+1)
               a10   (41),       -- all values (+1)
               a11   (42),       -- all values (+1)
               a12   (43),       -- all values (+1)
               a13   (44),       -- all values (+1)
               a14   (45),       -- all values (+1)
               a15   (46),       -- all values (+1)
               b1    (47),       -- all values (+1)
               b2    (48),       -- all values (+1)
               b3    (49),       -- all values (+1)
               b4    (50),       -- all values (+1)
               b5    (51),       -- all values (+1)
               b6    (52),       -- all values (+1)
               b7    (53),       -- all values (+1)
               b8    (54),       -- all values (+1)
               b9    (55),       -- all values (+1)
               b10   (56),       -- all values (+1)
               b11   (57),       -- all values (+1)
               b12   (58),       -- all values (+1)
               b13   (59),       -- all values (+1)
               b14   (60),       -- all values (+1)
               b15   (61)        -- all values (+1)
               }
     ACCESS   read-write
     STATUS   mandatory
     DESCRIPTION
     "       MF code for restart (mfrestart)  "
     ::= { nvR2profEntry 11}

nvR2profMfcongstion OBJECT-TYPE
     SYNTAX   INTEGER
               {
               notapp(1),        -- all values (+1)
               a1    (32),       -- all values (+1)
               a2    (33),       -- all values (+1)
               a3    (34),       -- all values (+1)
               a4    (35),       -- all values (+1)
               a5    (36),       -- all values (+1)
               a6    (37),       -- all values (+1)
               a7    (38),       -- all values (+1)
               a8    (39),       -- all values (+1)
               a9    (40),       -- all values (+1)
               a10   (41),       -- all values (+1)
               a11   (42),       -- all values (+1)
               a12   (43),       -- all values (+1)
               a13   (44),       -- all values (+1)
               a14   (45),       -- all values (+1)
               a15   (46),       -- all values (+1)
               b1    (47),       -- all values (+1)
               b2    (48),       -- all values (+1)
               b3    (49),       -- all values (+1)
               b4    (50),       -- all values (+1)
               b5    (51),       -- all values (+1)
               b6    (52),       -- all values (+1)
               b7    (53),       -- all values (+1)
               b8    (54),       -- all values (+1)
               b9    (55),       -- all values (+1)
               b10   (56),       -- all values (+1)
               b11   (57),       -- all values (+1)
               b12   (58),       -- all values (+1)
               b13   (59),       -- all values (+1)
               b14   (60),       -- all values (+1)
               b15   (61)        -- all values (+1)
               }
     ACCESS   read-write
     STATUS   mandatory
     DESCRIPTION
     "     MF code for eqpt congestion (mfcongestion)  "
     ::= { nvR2profEntry 12 }

nvR2profMfvacant OBJECT-TYPE
     SYNTAX   INTEGER
               {
               notapp(1),        -- all values (+1)
               a1    (32),       -- all values (+1)
               a2    (33),       -- all values (+1)
               a3    (34),       -- all values (+1)
               a4    (35),       -- all values (+1)
               a5    (36),       -- all values (+1)
               a6    (37),       -- all values (+1)
               a7    (38),       -- all values (+1)
               a8    (39),       -- all values (+1)
               a9    (40),       -- all values (+1)
               a10   (41),       -- all values (+1)
               a11   (42),       -- all values (+1)
               a12   (43),       -- all values (+1)
               a13   (44),       -- all values (+1)
               a14   (45),       -- all values (+1)
               a15   (46),       -- all values (+1)
               b1    (47),       -- all values (+1)
               b2    (48),       -- all values (+1)
               b3    (49),       -- all values (+1)
               b4    (50),       -- all values (+1)
               b5    (51),       -- all values (+1)
               b6    (52),       -- all values (+1)
               b7    (53),       -- all values (+1)
               b8    (54),       -- all values (+1)
               b9    (55),       -- all values (+1)
               b10   (56),       -- all values (+1)
               b11   (57),       -- all values (+1)
               b12   (58),       -- all values (+1)
               b13   (59),       -- all values (+1)
               b14   (60),       -- all values (+1)
               b15   (61)        -- all values (+1)
               }
     ACCESS   read-write
     STATUS   mandatory
     DESCRIPTION
     "        MF code for vacant number (mfvacant)  "
     ::= { nvR2profEntry 13 }

nvR2profMfspeech OBJECT-TYPE
     SYNTAX   INTEGER
               {
               notapp(1),        -- all values (+1)
               a1    (32),       -- all values (+1)
               a2    (33),       -- all values (+1)
               a3    (34),       -- all values (+1)
               a4    (35),       -- all values (+1)
               a5    (36),       -- all values (+1)
               a6    (37),       -- all values (+1)
               a7    (38),       -- all values (+1)
               a8    (39),       -- all values (+1)
               a9    (40),       -- all values (+1)
               a10   (41),       -- all values (+1)
               a11   (42),       -- all values (+1)
               a12   (43),       -- all values (+1)
               a13   (44),       -- all values (+1)
               a14   (45),       -- all values (+1)
               a15   (46),       -- all values (+1)
               b1    (47),       -- all values (+1)
               b2    (48),       -- all values (+1)
               b3    (49),       -- all values (+1)
               b4    (50),       -- all values (+1)
               b5    (51),       -- all values (+1)
               b6    (52),       -- all values (+1)
               b7    (53),       -- all values (+1)
               b8    (54),       -- all values (+1)
               b9    (55),       -- all values (+1)
               b10   (56),       -- all values (+1)
               b11   (57),       -- all values (+1)
               b12   (58),       -- all values (+1)
               b13   (59),       -- all values (+1)
               b14   (60),       -- all values (+1)
               b15   (61)        -- all values (+1)
               }
     ACCESS   read-write
     STATUS   mandatory
     DESCRIPTION
     "        MF code for set up speech charge (mfspeech)  "
     ::= { nvR2profEntry 14 }

nvR2profMfbusy OBJECT-TYPE
     SYNTAX   INTEGER
               {
               notapp(1),        -- all values (+1)
               a1    (32),       -- all values (+1)
               a2    (33),       -- all values (+1)
               a3    (34),       -- all values (+1)
               a4    (35),       -- all values (+1)
               a5    (36),       -- all values (+1)
               a6    (37),       -- all values (+1)
               a7    (38),       -- all values (+1)
               a8    (39),       -- all values (+1)
               a9    (40),       -- all values (+1)
               a10   (41),       -- all values (+1)
               a11   (42),       -- all values (+1)
               a12   (43),       -- all values (+1)
               a13   (44),       -- all values (+1)
               a14   (45),       -- all values (+1)
               a15   (46),       -- all values (+1)
               b1    (47),       -- all values (+1)
               b2    (48),       -- all values (+1)
               b3    (49),       -- all values (+1)
               b4    (50),       -- all values (+1)
               b5    (51),       -- all values (+1)
               b6    (52),       -- all values (+1)
               b7    (53),       -- all values (+1)
               b8    (54),       -- all values (+1)
               b9    (55),       -- all values (+1)
               b10   (56),       -- all values (+1)
               b11   (57),       -- all values (+1)
               b12   (58),       -- all values (+1)
               b13   (59),       -- all values (+1)
               b14   (60),       -- all values (+1)
               b15   (61)        -- all values (+1)
               }
     ACCESS   read-write
     STATUS   mandatory
     DESCRIPTION
     "  MF code for line busy (mfbusy)  "
     ::= { nvR2profEntry 15 }

nvR2profMfspchnc OBJECT-TYPE
     SYNTAX   INTEGER
               {
               notapp(1),        -- all values (+1)
               a1    (32),       -- all values (+1)
               a2    (33),       -- all values (+1)
               a3    (34),       -- all values (+1)
               a4    (35),       -- all values (+1)
               a5    (36),       -- all values (+1)
               a6    (37),       -- all values (+1)
               a7    (38),       -- all values (+1)
               a8    (39),       -- all values (+1)
               a9    (40),       -- all values (+1)
               a10   (41),       -- all values (+1)
               a11   (42),       -- all values (+1)
               a12   (43),       -- all values (+1)
               a13   (44),       -- all values (+1)
               a14   (45),       -- all values (+1)
               a15   (46),       -- all values (+1)
               b1    (47),       -- all values (+1)
               b2    (48),       -- all values (+1)
               b3    (49),       -- all values (+1)
               b4    (50),       -- all values (+1)
               b5    (51),       -- all values (+1)
               b6    (52),       -- all values (+1)
               b7    (53),       -- all values (+1)
               b8    (54),       -- all values (+1)
               b9    (55),       -- all values (+1)
               b10   (56),       -- all values (+1)
               b11   (57),       -- all values (+1)
               b12   (58),       -- all values (+1)
               b13   (59),       -- all values (+1)
               b14   (60),       -- all values (+1)
               b15   (61)        -- all values (+1)
               }
     ACCESS   read-write
     STATUS   mandatory
     DESCRIPTION
     "        MF code for free no charge (mfspchnc)  "
     ::= { nvR2profEntry 16 }

nvR2profMfgroupb OBJECT-TYPE
     SYNTAX   INTEGER
               {
               notapp(1),        -- all values (+1)
               a1    (32),       -- all values (+1)
               a2    (33),       -- all values (+1)
               a3    (34),       -- all values (+1)
               a4    (35),       -- all values (+1)
               a5    (36),       -- all values (+1)
               a6    (37),       -- all values (+1)
               a7    (38),       -- all values (+1)
               a8    (39),       -- all values (+1)
               a9    (40),       -- all values (+1)
               a10   (41),       -- all values (+1)
               a11   (42),       -- all values (+1)
               a12   (43),       -- all values (+1)
               a13   (44),       -- all values (+1)
               a14   (45),       -- all values (+1)
               a15   (46),       -- all values (+1)
               b1    (47),       -- all values (+1)
               b2    (48),       -- all values (+1)
               b3    (49),       -- all values (+1)
               b4    (50),       -- all values (+1)
               b5    (51),       -- all values (+1)
               b6    (52),       -- all values (+1)
               b7    (53),       -- all values (+1)
               b8    (54),       -- all values (+1)
               b9    (55),       -- all values (+1)
               b10   (56),       -- all values (+1)
               b11   (57),       -- all values (+1)
               b12   (58),       -- all values (+1)
               b13   (59),       -- all values (+1)
               b14   (60),       -- all values (+1)
               b15   (61)        -- all values (+1)
               }
     ACCESS   read-write
     STATUS   mandatory
     DESCRIPTION
     "        MF code for change to group B (mfgroupb)  "
     ::= { nvR2profEntry 17 }

nvR2profMfanumsch OBJECT-TYPE
     SYNTAX   INTEGER (0..3)
     ACCESS   read-write
     STATUS   mandatory
     DESCRIPTION
     " Trans prot type for calling number (mfanumsch)  "
     ::= { nvR2profEntry 18 }

nvR2profMftimeout OBJECT-TYPE
     SYNTAX   INTEGER
     ACCESS   read-write
     STATUS   mandatory
     DESCRIPTION
     "       Timeout for MF signaling (mftimeout)  "
     ::= { nvR2profEntry 19 }

nvR2profStatus OBJECT-TYPE
     SYNTAX   INTEGER {
                valid(1),
                invalid(2)
                }
     ACCESS   read-write
     STATUS   mandatory
     DESCRIPTION
"Operation status. Add the record to the table (valid) or delete
the record from the table (invalid)."
     ::= { nvR2profEntry 20 }

nvR2profAnswergrd OBJECT-TYPE
     SYNTAX   INTEGER
     ACCESS   read-write
     STATUS   mandatory
     DESCRIPTION
     "Minimal duration of answer signal in ms."
     ::= { nvR2profEntry 21 }

nvR2profClrfwdgrd OBJECT-TYPE
     SYNTAX   INTEGER
     ACCESS   read-write
     STATUS   mandatory
     DESCRIPTION
     "Minimal duration of clr fwd signal in ms."
     ::= { nvR2profEntry 22 }

nvR2profMfabnrel OBJECT-TYPE
     SYNTAX   INTEGER
               {
               notapp(1),        -- all values (+1)
               a1    (32),       -- all values (+1)
               a2    (33),       -- all values (+1)
               a3    (34),       -- all values (+1)
               a4    (35),       -- all values (+1)
               a5    (36),       -- all values (+1)
               a6    (37),       -- all values (+1)
               a7    (38),       -- all values (+1)
               a8    (39),       -- all values (+1)
               a9    (40),       -- all values (+1)
               a10   (41),       -- all values (+1)
               a11   (42),       -- all values (+1)
               a12   (43),       -- all values (+1)
               a13   (44),       -- all values (+1)
               a14   (45),       -- all values (+1)
               a15   (46),       -- all values (+1)
               b1    (47),       -- all values (+1)
               b2    (48),       -- all values (+1)
               b3    (49),       -- all values (+1)
               b4    (50),       -- all values (+1)
               b5    (51),       -- all values (+1)
               b6    (52),       -- all values (+1)
               b7    (53),       -- all values (+1)
               b8    (54),       -- all values (+1)
               b9    (55),       -- all values (+1)
               b10   (56),       -- all values (+1)
               b11   (57),       -- all values (+1)
               b12   (58),       -- all values (+1)
               b13   (59),       -- all values (+1)
               b14   (60),       -- all values (+1)
               b15   (61)        -- all values (+1)
               }
     ACCESS   read-write
     STATUS   mandatory
     DESCRIPTION
	"MF code for abnormal release of inband."
     ::= { nvR2profEntry 23 }

nvR2profIdlealmsk OBJECT-TYPE
     SYNTAX   INTEGER {
                yes(2),
                no(3)
                }
     ACCESS   read-write
     STATUS   mandatory
     DESCRIPTION
	"Mask alarms in IDLE state?"
     ::= { nvR2profEntry 24 }

nvR2profSeizalmsk OBJECT-TYPE 
     SYNTAX   INTEGER { 
                yes(2),
                no(3)
                } 
     ACCESS   read-write 
     STATUS   mandatory 
     DESCRIPTION 
        "Mask alarms in SEIZED state?"
     ::= { nvR2profEntry 25 }

nvR2profSzakalmsk OBJECT-TYPE 
     SYNTAX   INTEGER { 
                yes(2),
                no(3)
                } 
     ACCESS   read-write 
     STATUS   mandatory 
     DESCRIPTION 
        "Mask alarms in SEIZE ACK state?"
     ::= { nvR2profEntry 26 }

nvR2profAnswalmsk OBJECT-TYPE 
     SYNTAX   INTEGER { 
                yes(2),
                no(3)
                } 
     ACCESS   read-write 
     STATUS   mandatory 
     DESCRIPTION 
        "Mask alarms in ANSWERED state?"
     ::= { nvR2profEntry 27 }

nvR2profClbkalmsk OBJECT-TYPE 
     SYNTAX   INTEGER { 
                yes(2),
                no(3)
                } 
     ACCESS   read-write 
     STATUS   mandatory 
     DESCRIPTION 
        "Mask alarms in ANSWERED state?"
     ::= { nvR2profEntry 28 }

nvR2profFcrlalmsk OBJECT-TYPE 
     SYNTAX   INTEGER { 
                yes(2),
                no(3)
                } 
     ACCESS   read-write 
     STATUS   mandatory 
     DESCRIPTION 
        "Mask alarms in FORCE RELEASE state?"
     ::= { nvR2profEntry 29 }

nvR2profClfwalmsk OBJECT-TYPE 
     SYNTAX   INTEGER { 
                yes(2),
                no(3)
                } 
     ACCESS   read-write 
     STATUS   mandatory 
     DESCRIPTION 
        "Mask alarms in CLEAR FWD state?"
     ::= { nvR2profEntry 30 }

nvR2profBlckalmsk OBJECT-TYPE 
     SYNTAX   INTEGER { 
                yes(2),
                no(3)
                } 
     ACCESS   read-write 
     STATUS   mandatory 
     DESCRIPTION 
        "Mask alarms in BLOCKED state?"
     ::= { nvR2profEntry 31 }

--
--
-- r2syspar
--

nvR2syspar    OBJECT IDENTIFIER ::= { nevadaR2 2 }

nvR2sysparMaxRec OBJECT-TYPE
     SYNTAX   INTEGER
     ACCESS   read-only
     STATUS   mandatory
     DESCRIPTION
        "total number of records allowed in database file."
     ::= {nvR2syspar 1}

nvR2sysparNumRec OBJECT-TYPE
     SYNTAX   INTEGER
     ACCESS   read-only
     STATUS   mandatory
     DESCRIPTION
        "number of records in use."
     ::= {nvR2syspar 2}

nvR2sysparTable OBJECT-TYPE
      SYNTAX   SEQUENCE OF NvR2sysparEntry
      ACCESS   not-accessible
      STATUS   mandatory
      DESCRIPTION
               "R2syspar file."
      ::= { nvR2syspar 3 }

nvR2sysparEntry OBJECT-TYPE
      SYNTAX   NvR2sysparEntry
      ACCESS   not-accessible
      STATUS   mandatory
      DESCRIPTION
               "R2syspar record."
      INDEX { nvR2sysparIndex }
      ::= { nvR2sysparTable 1 }

NvR2sysparEntry ::=
      SEQUENCE {
      nvR2sysparIndex
            INTEGER,
      nvR2sysparProfname
            DisplayString,
      nvR2sysparMaxperdsp
            INTEGER,
      nvR2sysparAllocthrs
            INTEGER,
      nvR2sysparDeallthrs
            INTEGER,
      nvR2sysparStatint
            INTEGER,
      nvR2sysparAlarmint
            INTEGER,
      nvR2sysparLineway
            INTEGER,
     nvR2sysparMaxbnmlen
            INTEGER,
      nvR2sysparMinbnmlen
            INTEGER,
      nvR2sysparGetcalling
            INTEGER

               }

nvR2sysparIndex OBJECT-TYPE
     SYNTAX   INTEGER
     ACCESS   read-only
     STATUS   mandatory
     DESCRIPTION
        "Index of R2syspar record"
      ::= { nvR2sysparEntry 1 }

nvR2sysparProfname OBJECT-TYPE
     SYNTAX   DisplayString (SIZE (0..11))
     ACCESS   read-write
     STATUS   mandatory
     DESCRIPTION
     "Name of R2 flavor (profname)"
     ::= { nvR2sysparEntry 2 }

nvR2sysparMaxperdsp   OBJECT-TYPE
     SYNTAX   INTEGER (1..255)
     ACCESS   read-write
     STATUS   mandatory
     DESCRIPTION
     "Signaling channels allowed per R2DSP (maxperdsp)"
     ::= { nvR2sysparEntry 3 }

nvR2sysparAllocthrs   OBJECT-TYPE
     SYNTAX   INTEGER (0..255)
     ACCESS   read-write
     STATUS   mandatory
     DESCRIPTION
     " Allocation threshold for R2DSPs (allocthrs)  "
     ::= { nvR2sysparEntry 4 }

nvR2sysparDeallthrs OBJECT-TYPE
     SYNTAX   INTEGER (0..255)
     ACCESS   read-write
     STATUS   mandatory
     DESCRIPTION
     "Deallocation threshold for R2DSPs (deallthrs)"
     ::= { nvR2sysparEntry 5 }

nvR2sysparStatint OBJECT-TYPE
     SYNTAX   INTEGER
     ACCESS   read-write
     STATUS   mandatory
     DESCRIPTION
     "Health status message interval for R2DSPs (statint) "
     ::= { nvR2sysparEntry 6 }

nvR2sysparAlarmint   OBJECT-TYPE
     SYNTAX   INTEGER (0..255)
     ACCESS   read-write
     STATUS   mandatory
     DESCRIPTION
     "Debounce for line status changes (alarmint)"
     ::= { nvR2sysparEntry 7 }

nvR2sysparLineway  OBJECT-TYPE
     SYNTAX   INTEGER
                 {
                 inonly(104),         --   all values (+1)
		 inout(105)
                 }
     ACCESS   read-write
     STATUS   mandatory
     DESCRIPTION
     "Direction of allowed R2 calls (lineway) "
     ::= { nvR2sysparEntry 8 }

nvR2sysparMaxbnmlen	OBJECT-TYPE
     SYNTAX   INTEGER (0..24)
     ACCESS   read-write
     STATUS   mandatory
     DESCRIPTION
     "Maximum length of called number for incoming calls (maxbnmlen)
      default is zero  "
     ::= { nvR2sysparEntry 9 }

nvR2sysparMinbnmlen	OBJECT-TYPE
     SYNTAX   INTEGER (0..24)
     ACCESS   read-write
     STATUS   mandatory
     DESCRIPTION
     "Minimum length of called number for incoming calls (minbnmlen)
      Default value is zero  "
     ::= { nvR2sysparEntry 10 }

nvR2sysparGetcalling	OBJECT-TYPE
     SYNTAX   INTEGER {
                yes(2),
                no(3)
                }
     ACCESS   read-write
     STATUS   mandatory
     DESCRIPTION
     "Whether or not calling number is needed (getcallng)
      default is yes "
     ::= { nvR2sysparEntry 11 }



--
-- r2conf
--
nvR2conf    OBJECT IDENTIFIER ::= { nevadaR2 3 }

nvR2confMaxRec OBJECT-TYPE
     SYNTAX   INTEGER
     ACCESS   read-only
     STATUS   mandatory
     DESCRIPTION
        "total number of records allowed in database file."
     ::= {nvR2conf 1}

nvR2confNumRec OBJECT-TYPE
     SYNTAX   INTEGER
     ACCESS   read-only
     STATUS   mandatory
     DESCRIPTION
        "number of records in use."
     ::= {nvR2conf 2}

nvR2confTable OBJECT-TYPE
      SYNTAX   SEQUENCE OF NvR2confEntry
      ACCESS   not-accessible
      STATUS   mandatory
      DESCRIPTION
               "R2conf file."
      ::= { nvR2conf 3 }

nvR2confEntry OBJECT-TYPE
      SYNTAX   NvR2confEntry
      ACCESS   not-accessible
      STATUS   mandatory
      DESCRIPTION
               "R2conf record."
      INDEX { nvR2confIndex }
      ::= { nvR2confTable 1 }

NvR2confEntry ::=
      SEQUENCE {
      nvR2confIndex
            INTEGER,
      nvR2confDliname
            DisplayString,
      nvR2confStatus
	    INTEGER
               }

nvR2confIndex OBJECT-TYPE
     SYNTAX   INTEGER
     ACCESS   read-only
     STATUS   mandatory
     DESCRIPTION
        "Index of R2conf record"
      ::= { nvR2confEntry 1 }

nvR2confDliname OBJECT-TYPE
     SYNTAX   DisplayString (SIZE (0..11))
     ACCESS   read-write
     STATUS   mandatory
     DESCRIPTION
     "Name of DLI port (dliname)"
     ::= { nvR2confEntry 3 }

nvR2confStatus OBJECT-TYPE
     SYNTAX   INTEGER {
                valid(1),
                invalid(2)
                }
     ACCESS   read-write
     STATUS   mandatory
     DESCRIPTION
           "Operation status. Add the record to the table (valid) or
           delete the record from the table (invalid)."
     ::= { nvR2confEntry 4 }
--
--
--
-- r2pstat
--
--
nvR2pstat   OBJECT IDENTIFIER ::= { nevadaR2 4 }

nvR2pstatMaxRec OBJECT-TYPE
      SYNTAX   INTEGER
      ACCESS   read-only
      STATUS   mandatory
      DESCRIPTION
                "total number of records allowed in database file."
      ::= {nvR2pstat 1}

nvR2pstatNumRec OBJECT-TYPE
      SYNTAX   INTEGER
      ACCESS   read-only
      STATUS   mandatory
      DESCRIPTION
                "number of records in use."
      ::= {nvR2pstat 2}

nvR2pstatTable OBJECT-TYPE
      SYNTAX   SEQUENCE OF NvR2pstatEntry
      ACCESS   not-accessible
      STATUS   mandatory
      DESCRIPTION
               "R2pstat file."
      ::= { nvR2pstat 3 }

nvR2pstatEntry OBJECT-TYPE
      SYNTAX   NvR2pstatEntry
      ACCESS   not-accessible
      STATUS   mandatory
      DESCRIPTION
               "R2pstat record."
      INDEX { nvR2pstatIndex }
      ::= { nvR2pstatTable 1 }

NvR2pstatEntry ::=
      SEQUENCE {
      nvR2pstatIndex
            INTEGER,
      nvR2pstatDliname
            DisplayString,
      nvR2pstatPstat
            INTEGER,
      nvR2pstatTsstat
            DisplayString,
      nvR2pstatObr2dsp
            INTEGER,
      nvR2pstatObstat
            INTEGER,
      nvR2pstatLstatinfo
            INTEGER,
      nvR2pstatLinbadcnt
            Counter,
      nvR2pstatTsbadcnt
            Counter,
      nvR2pstatTotisigatt
            Counter,
      nvR2pstatToticalatt
            Counter,
      nvR2pstatToticalest
            Counter,
      nvR2pstatTotosigatt
            Counter,
      nvR2pstatTotocalatt
            Counter,
      nvR2pstatTotocalest
            Counter,
      nvR2pstatDtreset
            DisplayString,
      nvR2pstatFlavor
	    DisplayString
            }

nvR2pstatIndex OBJECT-TYPE
     SYNTAX   INTEGER
     ACCESS   read-only
     STATUS   mandatory
     DESCRIPTION
        "Index of R2pstat record"
      ::= { nvR2pstatEntry 1 }

nvR2pstatDliname     OBJECT-TYPE
      SYNTAX   DisplayString (SIZE (0..11))
      ACCESS   read-only
      STATUS   mandatory
      DESCRIPTION
      "Name of DLI port (dliname)"
      ::= { nvR2pstatEntry 2 }

nvR2pstatPstat       OBJECT-TYPE
      SYNTAX   INTEGER
             {
             unknown(2),    -- all values (+1)
             up(3),         -- all values (+1)
             disabled(4),   -- all values (+1)
             down(5)        -- all values (+1)
             }
      ACCESS   read-only
      STATUS   mandatory
      DESCRIPTION
      "Status of R2 port"
      ::= { nvR2pstatEntry 3 }

nvR2pstatTsstat      OBJECT-TYPE
      SYNTAX   DisplayString (SIZE (0..32))
      ACCESS   read-only
      STATUS   mandatory
      DESCRIPTION
      "Status of R2 port's timeslots.
	s : means timeslot for synchronization
	O : means out-of-band signaling
	- : means no info yet
	B : means blocked
	I : means idle
	M : means in-band signaling (MF)
	C : means call is up
	E : means timeslot is in abnormal state
	D : means port is down."
      ::= { nvR2pstatEntry 4 }

nvR2pstatObr2dsp     OBJECT-TYPE
      SYNTAX   INTEGER (0..255)
      ACCESS   read-only
      STATUS   mandatory
      DESCRIPTION
      "R2DSP which has this ports ob sig channel"
      ::= { nvR2pstatEntry 5 }

nvR2pstatObstat      OBJECT-TYPE
      SYNTAX   INTEGER
         {
         nocircuit(1),       -- all values (+1)
         obcircsetup(2),     -- all values (+1)
         obsigsetup(3),      -- all values (+1)
         obsigup(4),         -- all values (+1)
         obbad(5),           -- all values (+1)
         dspbad(6),          -- all values (+1)
         swerr(7)            -- all values (+1)
         }
      ACCESS   read-only
      STATUS   mandatory
      DESCRIPTION
      "status of the ob sig channel for this port"
      ::= { nvR2pstatEntry 6 }

nvR2pstatLstatinfo   OBJECT-TYPE
      SYNTAX   INTEGER
      ACCESS   read-only
      STATUS   mandatory
      DESCRIPTION
      "Information accompanying a LINE_STATUS message"
      ::= { nvR2pstatEntry 7 }

nvR2pstatLinbadcnt  OBJECT-TYPE
     SYNTAX   Counter
     ACCESS   read-only
     STATUS   mandatory
     DESCRIPTION
     " No. of line_status line_bad msg received"
      ::= { nvR2pstatEntry 8 }

nvR2pstatTsbadcnt   OBJECT-TYPE
     SYNTAX   Counter
     ACCESS   read-only
     STATUS   mandatory
     DESCRIPTION
     "No. of line_status line_bad msg received "
      ::= { nvR2pstatEntry 9 }

nvR2pstatTotisigatt OBJECT-TYPE
     SYNTAX   Counter
     ACCESS   read-only
     STATUS   mandatory
     DESCRIPTION
     "No. of incoming in-band channels created"
      ::= { nvR2pstatEntry 10 }

nvR2pstatToticalatt OBJECT-TYPE
     SYNTAX   Counter
     ACCESS   read-only
     STATUS   mandatory
     DESCRIPTION
     "No. of incoming R2 calls attempted"
      ::= { nvR2pstatEntry 11 }

nvR2pstatToticalest OBJECT-TYPE
     SYNTAX   Counter
     ACCESS   read-only
     STATUS   mandatory
     DESCRIPTION
     "No. of incoming R2 calls established"
      ::= { nvR2pstatEntry 12 }

nvR2pstatTotosigatt OBJECT-TYPE
     SYNTAX   Counter
     ACCESS   read-only
     STATUS   mandatory
     DESCRIPTION
     "No. of outgoing in-band channels created"
      ::= { nvR2pstatEntry 13 }

nvR2pstatTotocalatt  OBJECT-TYPE
     SYNTAX   Counter
     ACCESS   read-only
     STATUS   mandatory
     DESCRIPTION
     "No. of outgoing R2 calls attempted"
      ::= { nvR2pstatEntry 14 }

nvR2pstatTotocalest  OBJECT-TYPE
     SYNTAX   Counter
     ACCESS   read-only
     STATUS   mandatory
     DESCRIPTION
     "No. of outgoing R2 calls established"
      ::= { nvR2pstatEntry 15 }

nvR2pstatDtreset OBJECT-TYPE
     SYNTAX   DisplayString (SIZE (0..20))
     ACCESS   read-only
     STATUS   mandatory
     DESCRIPTION
        "date & time statistics last reset"
      ::= { nvR2pstatEntry 16 }

nvR2pstatFlavor OBJECT-TYPE
     SYNTAX   DisplayString (SIZE (0..4))
     ACCESS   read-only
     STATUS   mandatory
     DESCRIPTION
        "Abbreviation of R2 flavor."
      ::= { nvR2pstatEntry 17 }

--
-- r2dspstat
--
--
nvR2dspstat OBJECT IDENTIFIER ::= { nevadaR2 5 }


nvR2dspstatMaxRec OBJECT-TYPE
      SYNTAX   INTEGER
      ACCESS   read-only
      STATUS   mandatory
      DESCRIPTION
                "total number of records allowed in database file."
      ::= {nvR2dspstat 1}

nvR2dspstatNumRec OBJECT-TYPE
      SYNTAX   INTEGER
      ACCESS   read-only
      STATUS   mandatory
      DESCRIPTION
                "number of records in use."
      ::= {nvR2dspstat 2}

nvR2dspstatTable OBJECT-TYPE
      SYNTAX   SEQUENCE OF NvR2dspstatEntry
      ACCESS   not-accessible
      STATUS   mandatory
      DESCRIPTION
               "R2dspstat file."
      ::= { nvR2dspstat 3 }

nvR2dspstatEntry OBJECT-TYPE
      SYNTAX   NvR2dspstatEntry
      ACCESS   not-accessible
      STATUS   mandatory
      DESCRIPTION
               "R2dspstat record."
      INDEX { nvR2dspstatIndex }
      ::= { nvR2dspstatTable 1 }

NvR2dspstatEntry ::=
      SEQUENCE {
         nvR2dspstatIndex
             INTEGER,
         nvR2dspstatDevname
            DisplayString,
         nvR2dspstatStat
            INTEGER,
         nvR2dspstatNumobchn
            Counter,
         nvR2dspstatNumibchn
            Counter,
         nvR2dspstatUnusedchn
            Counter,
         nvR2dspstatTotobchn
            Counter,
         nvR2dspstatTotibchn
           Counter,
	 nvR2dspstatDtreset
		DisplayString,
	 nvR2dspstatFlavor
		DisplayString
            }

nvR2dspstatIndex OBJECT-TYPE
     SYNTAX   INTEGER
     ACCESS   read-only
     STATUS   mandatory
     DESCRIPTION
        "Index of R2dspstat record"
      ::= { nvR2dspstatEntry 1 }

nvR2dspstatDevname    OBJECT-TYPE
     SYNTAX   DisplayString (SIZE (0..11))
     ACCESS   read-only
     STATUS   mandatory
     DESCRIPTION
     "Name of DSP device used for this R2DSP"
      ::= { nvR2dspstatEntry 2 }

nvR2dspstatStat    OBJECT-TYPE
     SYNTAX   INTEGER
         {
          r2dspinit(1),   -- all values (+1)
          r2dspconfig(2), -- all values (+1)
          r2dspup(3),     -- all values (+1)
          r2dspdown(4),   -- all values (+1)
          r2dspfail(5),   -- all values (+1)
	  tsmalfunc(6)
         }
     ACCESS   read-only
     STATUS   mandatory
     DESCRIPTION
     "Health status of R2DSP"
      ::= { nvR2dspstatEntry 3 }

nvR2dspstatNumobchn    OBJECT-TYPE
     SYNTAX   Counter
     ACCESS   read-only
     STATUS   mandatory
     DESCRIPTION
     "Num of ob sig channels assigned to this R2DSP"
      ::= { nvR2dspstatEntry 4 }

nvR2dspstatNumibchn    OBJECT-TYPE
     SYNTAX   Counter
     ACCESS   read-only
     STATUS   mandatory
     DESCRIPTION
     "Num of ib channels assigned to this R2DSP"
      ::= { nvR2dspstatEntry 5 }

nvR2dspstatUnusedchn   OBJECT-TYPE
     SYNTAX   Counter
     ACCESS   read-only
     STATUS   mandatory
     DESCRIPTION
     "Num of avaialble timeslots on this R2DSP"
      ::= { nvR2dspstatEntry 6 }

nvR2dspstatTotobchn    OBJECT-TYPE
     SYNTAX   Counter
     ACCESS   read-only
     STATUS   mandatory
     DESCRIPTION
     "Cumulative total of ob channels assigned to this R2DSP"
      ::= { nvR2dspstatEntry 7 }

nvR2dspstatTotibchn    OBJECT-TYPE
     SYNTAX   Counter
     ACCESS   read-only
     STATUS   mandatory
     DESCRIPTION
     "Cumulative total of ib channels assigned to this R2DSP"
      ::= { nvR2dspstatEntry 8 }

nvR2dspstatDtreset OBJECT-TYPE
     SYNTAX   DisplayString (SIZE (0..20))
     ACCESS   read-only
     STATUS   mandatory
     DESCRIPTION
        "date & time statistics last reset"
      ::= { nvR2dspstatEntry 9 }

nvR2dspstatFlavor OBJECT-TYPE
     SYNTAX   DisplayString (SIZE (0..4))
     ACCESS   read-only
     STATUS   mandatory
     DESCRIPTION
        "Abbreviation of the R2 Flavor."
      ::= { nvR2dspstatEntry 10 }

--
-- r2cstat
--
--
nvR2cstat   OBJECT IDENTIFIER ::= { nevadaR2 6 }

nvR2cstatMaxRec OBJECT-TYPE
      SYNTAX   INTEGER
      ACCESS   read-only
      STATUS   mandatory
      DESCRIPTION
                "total number of records allowed in database file."
      ::= {nvR2cstat 1}

nvR2cstatNumRec OBJECT-TYPE
      SYNTAX   INTEGER
      ACCESS   read-only
      STATUS   mandatory
      DESCRIPTION
                "number of records in use."
      ::= {nvR2cstat 2}

nvR2cstatTable OBJECT-TYPE
      SYNTAX   SEQUENCE OF NvR2cstatEntry
      ACCESS   not-accessible
      STATUS   mandatory
      DESCRIPTION
               "R2cstat file."
      ::= { nvR2cstat 3 }

nvR2cstatEntry OBJECT-TYPE
      SYNTAX   NvR2cstatEntry
      ACCESS   not-accessible
      STATUS   mandatory
      DESCRIPTION
               "R2cstat record."
      INDEX { nvR2cstatIndex }
      ::= { nvR2cstatTable 1 }

NvR2cstatEntry ::=
      SEQUENCE {
          nvR2cstatIndex
            INTEGER,
          nvR2cstatR2port
            INTEGER,
          nvR2cstatTimeslot
            INTEGER,
          nvR2cstatIbr2dsp
            INTEGER,
          nvR2cstatCstat
            INTEGER,
          nvR2cstatDirection
            INTEGER,
          nvR2cstatReason
            INTEGER,
          nvR2cstatCallnum
            INTEGER,
          nvR2cstatCallednum
            DisplayString,
          nvR2cstatCallingnum
            DisplayString,
          nvR2cstatLanguage
            INTEGER,
          nvR2cstatEchosup
            INTEGER,
          nvR2cstatCparty
            INTEGER
               }

nvR2cstatIndex OBJECT-TYPE
     SYNTAX   INTEGER
     ACCESS   read-only
     STATUS   mandatory
     DESCRIPTION
        "Index of R2cstat record"
      ::= { nvR2cstatEntry 1 }

nvR2cstatR2port OBJECT-TYPE
     SYNTAX   INTEGER (0..255)
     ACCESS   read-only
     STATUS   mandatory
     DESCRIPTION
     " R2CONF record number of port carring timeslot of this call"
      ::= { nvR2cstatEntry 2 }

nvR2cstatTimeslot OBJECT-TYPE
     SYNTAX   INTEGER (0..255)
     ACCESS   read-only
     STATUS   mandatory
     DESCRIPTION
	"Timeslot number"
      ::= { nvR2cstatEntry 3 }

nvR2cstatIbr2dsp OBJECT-TYPE
     SYNTAX   INTEGER (0..255)
     ACCESS   read-only
     STATUS   mandatory
     DESCRIPTION
     "R2DSPSTAT recnum of R2DSP carrying this circuit"
      ::= { nvR2cstatEntry 4 }

nvR2cstatCstat OBJECT-TYPE
     SYNTAX   INTEGER
         {
	 ibnocircuit(1),
         ibcircsetup(2),   -- all values (+1)
         ibcircerr(3),     -- all values (+1)
	 ibcirfail(4),
	 ibdspmalf(5),
         nor2dspts(6),     -- all values (+1)
         ibdecode(7),      -- all values (+1)
         ibcomplete(8),    -- all values (+1)
         ibabnterm(9),     -- all values (+1)
	 ibconrej(10),
         rejected(11),      -- all values (+1)
         datacall(12),      -- all values (+1)
         cleared(13)       -- all values (+1)
         }
     ACCESS   read-only
     STATUS   mandatory
     DESCRIPTION
     " Current status of this timeslot"
      ::= { nvR2cstatEntry 5 }

nvR2cstatDirection OBJECT-TYPE
     SYNTAX   INTEGER
         {
         incoming(1),   -- all values (+1)
         outgoing(2)    -- all values (+1)
         }
     ACCESS   read-only
     STATUS   mandatory
     DESCRIPTION
     "                  incoming or outgoing call"
      ::= { nvR2cstatEntry 6 }

nvR2cstatReason OBJECT-TYPE
     SYNTAX   INTEGER (0..255)
     ACCESS   read-only
     STATUS   mandatory
     DESCRIPTION
     " For failed calls reason for the failure"
      ::= { nvR2cstatEntry 7 }

nvR2cstatCallnum OBJECT-TYPE
     SYNTAX   INTEGER
     ACCESS   read-only
     STATUS   mandatory
     DESCRIPTION
     "Sequence number of this call"
      ::= { nvR2cstatEntry 8 }

nvR2cstatCallednum  OBJECT-TYPE
     SYNTAX   DisplayString (SIZE (0..25))
     ACCESS   read-only
     STATUS   mandatory
     DESCRIPTION
     "             Called number"
      ::= { nvR2cstatEntry 9 }

nvR2cstatCallingnum OBJECT-TYPE
     SYNTAX   DisplayString (SIZE (0..25))
     ACCESS   read-only
     STATUS   mandatory
     DESCRIPTION
     "             Calling number"
      ::= { nvR2cstatEntry 10 }

nvR2cstatLanguage OBJECT-TYPE
     SYNTAX INTEGER
         {
         nolang(1),  -- all values (+1)
         discrim(2), -- all values (+1)
         french(3),  -- all values (+1)
         english(4), -- all values (+1)
         german(5),  -- all values (+1)
         russian(6), -- all values (+1)
         spanish(7), -- all values (+1)
         spare1(8),  -- all values (+1)
         spare2(9),  -- all values (+1)
         spare3(10),  -- all values (+1)
         spare4(11)  -- all values (+1)
         }
     ACCESS   read-only
     STATUS   mandatory
     DESCRIPTION
     "Language of call"
      ::= { nvR2cstatEntry 11 }

nvR2cstatEchosup OBJECT-TYPE
     SYNTAX INTEGER
         {
         noechosup(1),   -- all values (+1)
         echosnone(2),   -- all values (+1)
         echoshalf(3),   -- all values (+1)
         echosfull(4)    -- all values (+1)
         }
     ACCESS   read-only
     STATUS   mandatory
     DESCRIPTION
     "Echo suppressor"
      ::= { nvR2cstatEntry 12 }

nvR2cstatCparty  OBJECT-TYPE
     SYNTAX   INTEGER
         {
         nocparty    (1),    -- all values (+1)
         natsubpri   (2),    -- all values (+1)
         natsubnopri (3),    -- all values (+1)
         natmaint    (4),    -- all values (+1)
         spare       (5),    -- all values (+1)
         natmanop    (6),    -- all values (+1)
         natdata     (7),    -- all values (+1)
         intsubnopri (8),    -- all values (+1)
         intsubpri   (9),    -- all values (+1)
         intdata     (10),    -- all values (+1)
         intopftc    (11)    -- all values (+1)
         }
     ACCESS   read-only
     STATUS   mandatory
     DESCRIPTION
     "Type of calling party"
      ::= { nvR2cstatEntry 13 }

--
--
-- rbsyspar
--

nvRbsyspar    OBJECT IDENTIFIER ::= { nevadaRb 1 }

nvRbsysparMaxRec OBJECT-TYPE
     SYNTAX   INTEGER
     ACCESS   read-only
     STATUS   mandatory
     DESCRIPTION
        "total number of records allowed in database file."
     ::= {nvRbsyspar 1}

nvRbsysparNumRec OBJECT-TYPE
     SYNTAX   INTEGER
     ACCESS   read-only
     STATUS   mandatory
     DESCRIPTION
        "number of records in use."
     ::= {nvRbsyspar 2}

nvRbsysparTable OBJECT-TYPE
      SYNTAX   SEQUENCE OF NvRbsysparEntry
      ACCESS   not-accessible
      STATUS   mandatory
      DESCRIPTION
               "Rbsyspar file."
      ::= { nvRbsyspar 3 }

nvRbsysparEntry OBJECT-TYPE
      SYNTAX   NvRbsysparEntry
      ACCESS   not-accessible
      STATUS   mandatory
      DESCRIPTION
               "Rbsyspar record."
      INDEX { nvRbsysparIndex }
      ::= { nvRbsysparTable 1 }

NvRbsysparEntry ::=
      SEQUENCE {
      nvRbsysparIndex
            INTEGER,
      nvRbsysparMaxperdsp
            INTEGER,
      nvRbsysparAllocthrs
            INTEGER,
      nvRbsysparDeallthrs
            INTEGER,
      nvRbsysparStatint
            INTEGER,
      nvRbsysparAlarmint
            INTEGER,
      nvRbsysparMaxbnmlen
            INTEGER,
      nvRbsysparMinbnmlen
            INTEGER,
      nvRbsysparPollint
            INTEGER,
      nvRbsysparStatus
            INTEGER
               }

nvRbsysparIndex OBJECT-TYPE
     SYNTAX   INTEGER
     ACCESS   read-only
     STATUS   mandatory
     DESCRIPTION
        "Index of Rbsyspar record"
      ::= { nvRbsysparEntry 1 }

nvRbsysparMaxperdsp   OBJECT-TYPE
     SYNTAX   INTEGER (1..255)
     ACCESS   read-write
     STATUS   mandatory
     DESCRIPTION
     "Signaling channels allowed per RbDSP (maxperdsp)"
     ::= { nvRbsysparEntry 3 }

nvRbsysparAllocthrs   OBJECT-TYPE
     SYNTAX   INTEGER (0..255)
     ACCESS   read-write
     STATUS   mandatory
     DESCRIPTION
     " Allocation threshold for RbDSPs (allocthrs)  "
     ::= { nvRbsysparEntry 4 }

nvRbsysparDeallthrs OBJECT-TYPE
     SYNTAX   INTEGER (0..255)
     ACCESS   read-write
     STATUS   mandatory
     DESCRIPTION
     "Deallocation threshold for RbDSPs (deallthrs)"
     ::= { nvRbsysparEntry 5 }

nvRbsysparStatint OBJECT-TYPE
     SYNTAX   INTEGER
     ACCESS   read-write
     STATUS   mandatory
     DESCRIPTION
     "Health status message interval for RbDSPs (statint) "
     ::= { nvRbsysparEntry 6 }

nvRbsysparAlarmint   OBJECT-TYPE
     SYNTAX   INTEGER
     ACCESS   read-write
     STATUS   mandatory
     DESCRIPTION
     "Debounce for line status changes (alarmint)"
     ::= { nvRbsysparEntry 7 }

nvRbsysparMaxbnmlen	OBJECT-TYPE
     SYNTAX   INTEGER (0..24)
     ACCESS   read-write
     STATUS   mandatory
     DESCRIPTION
     "Maximum length of called number for incoming calls (maxbnmlen)
      default is zero  "
     ::= { nvRbsysparEntry 9 }

nvRbsysparMinbnmlen	OBJECT-TYPE
     SYNTAX   INTEGER (0..24)
     ACCESS   read-write
     STATUS   mandatory
     DESCRIPTION
     "Minimum length of called number for incoming calls (minbnmlen)
      Default value is zero  "
     ::= { nvRbsysparEntry 10 }

nvRbsysparPollint	OBJECT-TYPE
     SYNTAX   INTEGER 
     ACCESS   read-write
     STATUS   mandatory
     DESCRIPTION
     "Polling interval for RB pipes.
	default is 25 "
     ::= { nvRbsysparEntry 11 }


nvRbsysparStatus	OBJECT-TYPE
     SYNTAX   INTEGER {
                valid(1),
                invalid(2)
                }
     ACCESS   read-write
     STATUS   mandatory
     DESCRIPTION
"Operation status. Add the record to the table (valid) or delete
the record from the table (invalid)."
     ::= { nvRbsysparEntry 12 }

--
-- rbconf
--
nvRbconf    OBJECT IDENTIFIER ::= { nevadaRb 2 }

nvRbconfMaxRec OBJECT-TYPE
     SYNTAX   INTEGER
     ACCESS   read-only
     STATUS   mandatory
     DESCRIPTION
        "total number of records allowed in database file."
     ::= {nvRbconf 1}

nvRbconfNumRec OBJECT-TYPE
     SYNTAX   INTEGER
     ACCESS   read-only
     STATUS   mandatory
     DESCRIPTION
        "number of records in use."
     ::= {nvRbconf 2}

nvRbconfTable OBJECT-TYPE
      SYNTAX   SEQUENCE OF NvRbconfEntry
      ACCESS   not-accessible
      STATUS   mandatory
      DESCRIPTION
               "Rbconf file."
      ::= { nvRbconf 3 }

nvRbconfEntry OBJECT-TYPE
      SYNTAX   NvRbconfEntry
      ACCESS   not-accessible
      STATUS   mandatory
      DESCRIPTION
               "Rbconf record."
      INDEX { nvRbconfIndex }
      ::= { nvRbconfTable 1 }

NvRbconfEntry ::=
      SEQUENCE {
      nvRbconfIndex
            INTEGER,
      nvRbconfDliname
            DisplayString,
      nvRbconfProfname
            DisplayString,
      nvRbconfRtmethod
            INTEGER,
      nvRbconfStatus
	    INTEGER
               }

nvRbconfIndex OBJECT-TYPE
     SYNTAX   INTEGER
     ACCESS   read-only
     STATUS   mandatory
     DESCRIPTION
        "Index of Rbconf record"
      ::= { nvRbconfEntry 1 }

nvRbconfDliname OBJECT-TYPE
     SYNTAX   DisplayString (SIZE (0..11))
     ACCESS   read-write
     STATUS   mandatory
     DESCRIPTION
     "Name of DLI port (dliname)"
     ::= { nvRbconfEntry 3 }

nvRbconfProfname OBJECT-TYPE
     SYNTAX   DisplayString (SIZE (0..11))
     ACCESS   read-write
     STATUS   mandatory
     DESCRIPTION
     "Name of Prof"
     ::= { nvRbconfEntry 4 }

nvRbconfRtmethod OBJECT-TYPE
     SYNTAX   INTEGER {
                ibsig(16),
                direct(17)
                }
     ACCESS   read-write
     STATUS   mandatory
     DESCRIPTION
     "default 15"
     ::= { nvRbconfEntry 5 }

nvRbconfStatus OBJECT-TYPE
     SYNTAX   INTEGER {
                valid(1),
                invalid(2)
                }
     ACCESS   read-write
     STATUS   mandatory
     DESCRIPTION
           "Operation status. Add the record to the table (valid) or
           delete the record from the table (invalid)."
     ::= { nvRbconfEntry 6 }
--
--
--
-- rbpstat
--
--
nvRbpstat   OBJECT IDENTIFIER ::= { nevadaRb 3 }

nvRbpstatMaxRec OBJECT-TYPE
      SYNTAX   INTEGER
      ACCESS   read-only
      STATUS   mandatory
      DESCRIPTION
                "total number of records allowed in database file."
      ::= {nvRbpstat 1}

nvRbpstatNumRec OBJECT-TYPE
      SYNTAX   INTEGER
      ACCESS   read-only
      STATUS   mandatory
      DESCRIPTION
                "number of records in use."
      ::= {nvRbpstat 2}

nvRbpstatTable OBJECT-TYPE
      SYNTAX   SEQUENCE OF NvRbpstatEntry
      ACCESS   not-accessible
      STATUS   mandatory
      DESCRIPTION
               "Rbpstat file."
      ::= { nvRbpstat 3 }

nvRbpstatEntry OBJECT-TYPE
      SYNTAX   NvRbpstatEntry
      ACCESS   not-accessible
      STATUS   mandatory
      DESCRIPTION
               "Rbpstat record."
      INDEX { nvRbpstatIndex }
      ::= { nvRbpstatTable 1 }

NvRbpstatEntry ::=
      SEQUENCE {
      nvRbpstatIndex
            INTEGER,
      nvRbpstatDliname
            DisplayString,
      nvRbpstatFlavor
            DisplayString,
      nvRbpstatPstat
            INTEGER,
      nvRbpstatTsstat
            DisplayString,
      nvRbpstatRbsrbdsp
            INTEGER,
      nvRbpstatRbstat
            INTEGER,
      nvRbpstatLinbadcnt
            Counter,
      nvRbpstatTsbadcnt
            Counter,
      nvRbpstatTotisigatt
            Counter,
      nvRbpstatToticalatt
            Counter,
      nvRbpstatToticalest
            Counter,
      nvRbpstatTotosigatt
            Counter,
      nvRbpstatTotocalatt
            Counter,
      nvRbpstatTotocalest
            Counter,
      nvRbpstatDtreset
            DisplayString
            }

nvRbpstatIndex OBJECT-TYPE
     SYNTAX   INTEGER
     ACCESS   read-only
     STATUS   mandatory
     DESCRIPTION
        "Index of Rbpstat record"
      ::= { nvRbpstatEntry 1 }

nvRbpstatDliname     OBJECT-TYPE
      SYNTAX   DisplayString (SIZE (0..11))
      ACCESS   read-only
      STATUS   mandatory
      DESCRIPTION
      "Name of (dliname)"
      ::= { nvRbpstatEntry 2 }

nvRbpstatFlavor     OBJECT-TYPE
      SYNTAX   DisplayString (SIZE (0..4))
      ACCESS   read-only
      STATUS   mandatory
      DESCRIPTION
      "Name "
      ::= { nvRbpstatEntry 3 }

nvRbpstatPstat       OBJECT-TYPE
      SYNTAX   INTEGER
             {
             unknown(2),    -- all values (+1)
             up(3),         -- all values (+1)
             disabled(4),   -- all values (+1)
             down(5)        -- all values (+1)
             }
      ACCESS   read-only
      STATUS   mandatory
      DESCRIPTION
      "Status of Rb port"
      ::= { nvRbpstatEntry 4 }

nvRbpstatTsstat      OBJECT-TYPE
      SYNTAX   DisplayString (SIZE (0..25))
      ACCESS   read-only
      STATUS   mandatory
      DESCRIPTION
      "Status of Rb port's timeslots.
	s : means timeslot for synchronization
	O : means out-of-band signaling
	- : means no info yet
	B : means blocked
	I : means idle
	M : means in-band signaling (MF)
	C : means call is up
	E : means timeslot is in abnormal state
	D : means port is down."
      ::= { nvRbpstatEntry 5 }

nvRbpstatRbsrbdsp     OBJECT-TYPE
      SYNTAX   INTEGER (0..255)
      ACCESS   read-only
      STATUS   mandatory
      DESCRIPTION
      "RbsrbDSP which has this ports ob sig channel"
      ::= { nvRbpstatEntry 6 }

nvRbpstatRbstat      OBJECT-TYPE
      SYNTAX   INTEGER
         {
	 nopipe(1),
         rbsigsetup(3),
         rbsigup(4),
         rbbad(5),
         dspbad(6),
         swerr(7)
        }
      ACCESS   read-only
      STATUS   mandatory
      DESCRIPTION
      "status of the ob sig channel for this port"
      ::= { nvRbpstatEntry 7 }

nvRbpstatLstatinfo   OBJECT-TYPE
      SYNTAX   INTEGER
      ACCESS   read-only
      STATUS   mandatory
      DESCRIPTION
      "Information accompanying a LINE_STATUS message"
      ::= { nvRbpstatEntry 8 }

nvRbpstatLinbadcnt  OBJECT-TYPE
     SYNTAX   Counter
     ACCESS   read-only
     STATUS   mandatory
     DESCRIPTION
     " No. of line_status line_bad msg received"
      ::= { nvRbpstatEntry 9 }

nvRbpstatTsbadcnt   OBJECT-TYPE
     SYNTAX   Counter
     ACCESS   read-only
     STATUS   mandatory
     DESCRIPTION
     "No. of line_status line_bad msg received "
      ::= { nvRbpstatEntry 10 }

nvRbpstatTotisigatt OBJECT-TYPE
     SYNTAX   Counter
     ACCESS   read-only
     STATUS   mandatory
     DESCRIPTION
     "No. of incoming in-band channels created"
      ::= { nvRbpstatEntry 11 }

nvRbpstatToticalatt OBJECT-TYPE
     SYNTAX   Counter
     ACCESS   read-only
     STATUS   mandatory
     DESCRIPTION
     "No. of incoming Rb calls attempted"
      ::= { nvRbpstatEntry 12 }

nvRbpstatToticalest OBJECT-TYPE
     SYNTAX   Counter
     ACCESS   read-only
     STATUS   mandatory
     DESCRIPTION
     "No. of incoming Rb calls established"
      ::= { nvRbpstatEntry 13 }

nvRbpstatTotosigatt OBJECT-TYPE
     SYNTAX   Counter
     ACCESS   read-only
     STATUS   mandatory
     DESCRIPTION
     "No. of outgoing in-band channels created"
      ::= { nvRbpstatEntry 14 }

nvRbpstatTotocalatt  OBJECT-TYPE
     SYNTAX   Counter
     ACCESS   read-only
     STATUS   mandatory
     DESCRIPTION
     "No. of outgoing R2 calls attempted"
      ::= { nvRbpstatEntry 15 }

nvRbpstatTotocalest  OBJECT-TYPE
     SYNTAX   Counter
     ACCESS   read-only
     STATUS   mandatory
     DESCRIPTION
     "No. of outgoing Rb calls established"
      ::= { nvRbpstatEntry 16 }

nvRbpstatDtreset OBJECT-TYPE
     SYNTAX   DisplayString (SIZE (0..20))
     ACCESS   read-only
     STATUS   mandatory
     DESCRIPTION
        "date & time statistics last reset"
      ::= { nvRbpstatEntry 17 }

--
-- rbdspstat
--
--
nvRbdspstat OBJECT IDENTIFIER ::= { nevadaRb 4 }


nvRbdspstatMaxRec OBJECT-TYPE
      SYNTAX   INTEGER
      ACCESS   read-only
      STATUS   mandatory
      DESCRIPTION
                "total number of records allowed in database file."
      ::= {nvRbdspstat 1}

nvRbdspstatNumRec OBJECT-TYPE
      SYNTAX   INTEGER
      ACCESS   read-only
      STATUS   mandatory
      DESCRIPTION
                "number of records in use."
      ::= {nvRbdspstat 2}

nvRbdspstatTable OBJECT-TYPE
      SYNTAX   SEQUENCE OF NvRbdspstatEntry
      ACCESS   not-accessible
      STATUS   mandatory
      DESCRIPTION
               "Rbdspstat file."
      ::= { nvRbdspstat 3 }

nvRbdspstatEntry OBJECT-TYPE
      SYNTAX   NvRbdspstatEntry
      ACCESS   not-accessible
      STATUS   mandatory
      DESCRIPTION
               "Rbdspstat record."
      INDEX { nvRbdspstatIndex }
      ::= { nvRbdspstatTable 1 }

NvRbdspstatEntry ::=
      SEQUENCE {
         nvRbdspstatIndex
             INTEGER,
         nvRbdspstatDevname
            DisplayString,
         nvRbdspstatFlavor
            DisplayString,
         nvRbdspstatStat
            INTEGER,
         nvRbdspstatNumrbpipe
            Counter,
         nvRbdspstatNumibchn
            Counter,
         nvRbdspstatUnusedchn
            Counter,
         nvRbdspstatTotrbpipe
            Counter,
         nvRbdspstatTotibchn
            Counter,
	 nvRbdspstatDtreset
            DisplayString
            }

nvRbdspstatIndex OBJECT-TYPE
     SYNTAX   INTEGER
     ACCESS   read-only
     STATUS   mandatory
     DESCRIPTION
        "Index of Rbdspstat record"
      ::= { nvRbdspstatEntry 1 }

nvRbdspstatDevname    OBJECT-TYPE
     SYNTAX   DisplayString (SIZE (0..11))
     ACCESS   read-only
     STATUS   mandatory
     DESCRIPTION
     "Name of DSP device used for this RbDSP"
      ::= { nvRbdspstatEntry 2 }

nvRbdspstatFlavor    OBJECT-TYPE
     SYNTAX   DisplayString (SIZE (0..4))
     ACCESS   read-only
     STATUS   mandatory
     DESCRIPTION
     "flavor"
      ::= { nvRbdspstatEntry 3 }

nvRbdspstatStat    OBJECT-TYPE
     SYNTAX   INTEGER
         {
          rbdspinit(1),   -- all values (+1)
          rbdspconfig(2), -- all values (+1)
          rbdspup(3),     -- all values (+1)
          rbdspdown(4),   -- all values (+1)
          rbdspfail(5),   -- all values (+1)
	  tsmalfunc(6)
         }
     ACCESS   read-only
     STATUS   mandatory
     DESCRIPTION
     "Health status of RbDSP"
      ::= { nvRbdspstatEntry 4 }

nvRbdspstatNumrbpipe    OBJECT-TYPE
     SYNTAX   Counter
     ACCESS   read-only
     STATUS   mandatory
     DESCRIPTION
     "Num of rbpipe sig channels assigned to this RbDSP"
      ::= { nvRbdspstatEntry 5 }

nvRbdspstatNumibchn    OBJECT-TYPE
     SYNTAX   Counter
     ACCESS   read-only
     STATUS   mandatory
     DESCRIPTION
     "Num of ib channels assigned to this RbDSP"
      ::= { nvRbdspstatEntry 6 }

nvRbdspstatUnusedchn   OBJECT-TYPE
     SYNTAX   Counter
     ACCESS   read-only
     STATUS   mandatory
     DESCRIPTION
     "Num of avaialble timeslots on this RbDSP"
      ::= { nvRbdspstatEntry 7 }

nvRbdspstatTotrbpipe    OBJECT-TYPE
     SYNTAX   Counter
     ACCESS   read-only
     STATUS   mandatory
     DESCRIPTION
     "Cumulative total of rbpipe channels assigned to this RbDSP"
      ::= { nvRbdspstatEntry 8 }

nvRbdspstatTotibchn    OBJECT-TYPE
     SYNTAX   Counter
     ACCESS   read-only
     STATUS   mandatory
     DESCRIPTION
     "Cumulative total of ib channels assigned to this RbDSP"
      ::= { nvRbdspstatEntry 9 }

nvRbdspstatDtreset OBJECT-TYPE
     SYNTAX   DisplayString (SIZE (0..20))
     ACCESS   read-only
     STATUS   mandatory
     DESCRIPTION
        "date & time statistics last reset"
      ::= { nvRbdspstatEntry 10 }


--
-- rbcstat
--
--
nvRbcstat   OBJECT IDENTIFIER ::= { nevadaRb 5 }

nvRbcstatMaxRec OBJECT-TYPE
      SYNTAX   INTEGER
      ACCESS   read-only
      STATUS   mandatory
      DESCRIPTION
                "total number of records allowed in database file."
      ::= {nvRbcstat 1}

nvRbcstatNumRec OBJECT-TYPE
      SYNTAX   INTEGER
      ACCESS   read-only
      STATUS   mandatory
      DESCRIPTION
                "number of records in use."
      ::= {nvRbcstat 2}

nvRbcstatTable OBJECT-TYPE
      SYNTAX   SEQUENCE OF NvRbcstatEntry
      ACCESS   not-accessible
      STATUS   mandatory
      DESCRIPTION
               "Rbcstat file."
      ::= { nvRbcstat 3 }

nvRbcstatEntry OBJECT-TYPE
      SYNTAX   NvRbcstatEntry
      ACCESS   not-accessible
      STATUS   mandatory
      DESCRIPTION
               "Rbcstat record."
      INDEX { nvRbcstatIndex }
      ::= { nvRbcstatTable 1 }

NvRbcstatEntry ::=
      SEQUENCE {
          nvRbcstatIndex
            INTEGER,
          nvRbcstatRbport
            INTEGER,
          nvRbcstatTimeslot
            INTEGER,
          nvRbcstatIbrbdsp
            INTEGER,
          nvRbcstatCstat
            INTEGER,
          nvRbcstatDirection
            INTEGER,
          nvRbcstatReason
            INTEGER,
          nvRbcstatCallnum
            INTEGER,
          nvRbcstatCallednum
            DisplayString,
          nvRbcstatCallingnum
            DisplayString
               }

nvRbcstatIndex OBJECT-TYPE
     SYNTAX   INTEGER
     ACCESS   read-only
     STATUS   mandatory
     DESCRIPTION
        "Index of Rbcstat record"
      ::= { nvRbcstatEntry 1 }

nvRbcstatRbport OBJECT-TYPE
     SYNTAX   INTEGER (0..255)
     ACCESS   read-only
     STATUS   mandatory
     DESCRIPTION
     "RBCONF record number of port carring timeslot of this call"
      ::= { nvRbcstatEntry 2 }

nvRbcstatTimeslot OBJECT-TYPE
     SYNTAX   INTEGER (0..255)
     ACCESS   read-only
     STATUS   mandatory
     DESCRIPTION
     "Timeslot number"
      ::= { nvRbcstatEntry 3 }

nvRbcstatIbrbdsp OBJECT-TYPE
     SYNTAX   INTEGER
     ACCESS   read-only
     STATUS   mandatory
     DESCRIPTION
     "RBDSPSTAT recnum of RBDSP carrying this circuit"
      ::= { nvRbcstatEntry 4 }

nvRbcstatCstat OBJECT-TYPE
     SYNTAX   INTEGER
         {
	 ibnocircuit(1),
         ibcircsetup(2),   -- all values (+1)
         ibcircerr(3),     -- all values (+1)
	 ibcircfail(4),
	 ibdspmalf(5),
         norbdspts(6),     -- all values (+1)
         ibdecode(7),      -- all values (+1)
         ibcomplete(8),    -- all values (+1)
	 dirrouting(9),
         ibabnterm(10),     -- all values (+1)
	 ibconrej(11),
         rejected(12),      -- all values (+1)
         datacall(13),      -- all values (+1)
         cleared(14)       -- all values (+1)
         }
     ACCESS   read-only
     STATUS   mandatory
     DESCRIPTION
     " Current status of this timeslot"
      ::= { nvRbcstatEntry 5 }

nvRbcstatDirection OBJECT-TYPE
     SYNTAX   INTEGER
         {
         incoming(1),   -- all values (+1)
         outgoing(2)    -- all values (+1)
         }
     ACCESS   read-only
     STATUS   mandatory
     DESCRIPTION
     "                  incoming or outgoing call"
      ::= { nvRbcstatEntry 6 }

nvRbcstatReason OBJECT-TYPE
     SYNTAX   INTEGER (0..255)
     ACCESS   read-only
     STATUS   mandatory
     DESCRIPTION
     " For failed calls reason for the failure"
      ::= { nvRbcstatEntry 7 }

nvRbcstatCallnum OBJECT-TYPE
     SYNTAX   INTEGER
     ACCESS   read-only
     STATUS   mandatory
     DESCRIPTION
     "Sequence number of this call"
      ::= { nvRbcstatEntry 8 }

nvRbcstatCallednum  OBJECT-TYPE
     SYNTAX   DisplayString (SIZE (0..25))
     ACCESS   read-only
     STATUS   mandatory
     DESCRIPTION
     "             Called number"
      ::= { nvRbcstatEntry 9 }

nvRbcstatCallingnum OBJECT-TYPE
     SYNTAX   DisplayString (SIZE (0..25))
     ACCESS   read-only
     STATUS   mandatory
     DESCRIPTION
     "             Calling number"
      ::= { nvRbcstatEntry 10 }

--
--
-- rbprof
--

nvRbprof    OBJECT IDENTIFIER ::= { nevadaRb 6 }

nvRbprofMaxRec OBJECT-TYPE
     SYNTAX   INTEGER
     ACCESS   read-only
     STATUS   mandatory
     DESCRIPTION
        "total number of records allowed in database file."
     ::= {nvRbprof 1}

nvRbprofNumRec OBJECT-TYPE
     SYNTAX   INTEGER
     ACCESS   read-only
     STATUS   mandatory
     DESCRIPTION
        "number of records in use."
     ::= {nvRbprof 2}

nvRbprofTable OBJECT-TYPE
      SYNTAX   SEQUENCE OF NvRbprofEntry
      ACCESS   not-accessible
      STATUS   mandatory
      DESCRIPTION
               "Rbprof file."
      ::= { nvRbprof 3 }

nvRbprofEntry OBJECT-TYPE
      SYNTAX   NvRbprofEntry
      ACCESS   not-accessible
      STATUS   mandatory
      DESCRIPTION
               "Rbprof record."
      INDEX { nvRbprofIndex }
      ::= { nvRbprofTable 1 }

NvRbprofEntry ::=
      SEQUENCE {
      nvRbprofIndex
            INTEGER,
      nvRbprofProfname
            DisplayString,
      nvRbprofSuffix
            DisplayString,
      nvRbprofSigtype
            INTEGER,
      nvRbprofRlcf
            INTEGER,
      nvRbprofLcfo
            INTEGER,
      nvRbprofWinklen
            INTEGER,
      nvRbprofMfdelay
            INTEGER,
      nvRbprofDisconlen
            INTEGER,
      nvRbprofIbsigtype
            INTEGER,
      nvRbprofDtmftmout
            INTEGER,
      nvRbprofDtmfon
            INTEGER,
      nvRbprofDtmfoff
            INTEGER,
      nvRbprofStatus
            INTEGER
                    }

nvRbprofIndex OBJECT-TYPE
     SYNTAX   INTEGER
     ACCESS   read-only
     STATUS   mandatory
     DESCRIPTION
        "Index of Rbprof record"
      ::= { nvRbprofEntry 1 }

nvRbprofProfname OBJECT-TYPE
     SYNTAX   DisplayString (SIZE (0..11))
     ACCESS   read-write
     STATUS   mandatory
     DESCRIPTION
     "Name of RB flavor (profname)"
     ::= { nvRbprofEntry 2 }

nvRbprofSuffix OBJECT-TYPE
     SYNTAX   DisplayString (SIZE (0..4))
     ACCESS   read-write
     STATUS   mandatory
     DESCRIPTION
     "Abbreviation of RB flavor (suffix)  "
     ::= { nvRbprofEntry 3 }

nvRbprofSigtype OBJECT-TYPE
     SYNTAX   INTEGER
               {
               e-and-m(2),     -- all values (+1)
               loop(3),   -- all values (+1)
               ground(4)   -- all values (+1)
               }
     ACCESS   read-write
     STATUS   mandatory
     DESCRIPTION
     " Support for CD bits (cdbits)
       Default value 2 "
     ::= { nvRbprofEntry 4 }

nvRbprofRlcf OBJECT-TYPE
     SYNTAX   INTEGER
               {
               notapp(1),     -- all values (+1)
               yes(2),   -- all values (+1)
               no(3)   -- all values (+1)
               }
     ACCESS   read-write
     STATUS   mandatory
     DESCRIPTION
     " " 
     ::= { nvRbprofEntry 5 }

nvRbprofLcfo OBJECT-TYPE
     SYNTAX   INTEGER
               {
               notapp(1),     -- all values (+1)
               yes(2),   -- all values (+1)
               no(3)   -- all values (+1)
               }
     ACCESS   read-write
     STATUS   mandatory
     DESCRIPTION
     " "
     ::= { nvRbprofEntry 6 }

nvRbprofWinklen OBJECT-TYPE
     SYNTAX   INTEGER
     ACCESS   read-write
     STATUS   mandatory
     DESCRIPTION
     " Support for CLEAR_ACK (clearack)  "
     ::= { nvRbprofEntry 7 }

nvRbprofMfdelay OBJECT-TYPE
     SYNTAX   INTEGER
     ACCESS   read-write
     STATUS   mandatory
     DESCRIPTION
     "Duration in ms between wink and inband (mfdelay)."
     ::= { nvRbprofEntry 8 }

nvRbprofDisconlen OBJECT-TYPE
     SYNTAX   INTEGER
     ACCESS   read-write
     STATUS   mandatory
     DESCRIPTION
     "Duration of EM disconnection." 
     ::= { nvRbprofEntry 9 }

nvRbprofIbsigtype OBJECT-TYPE
     SYNTAX   INTEGER
               {
               dtmf(2)        -- all values (+1)
               }
     ACCESS   read-write
     STATUS   mandatory
     DESCRIPTION
     "Inband signaling protocol to use." 
     ::= { nvRbprofEntry 10 }

nvRbprofDtmftmout OBJECT-TYPE
     SYNTAX   INTEGER
     ACCESS   read-write
     STATUS   mandatory
     DESCRIPTION
     "DTMF signal timeout."
     ::= { nvRbprofEntry 11}

nvRbprofDtmfon OBJECT-TYPE
     SYNTAX   INTEGER (16..100)
     ACCESS   read-write
     STATUS   mandatory
     DESCRIPTION
     "DTMF signal ON time." 
     ::= { nvRbprofEntry 12 }

nvRbprofDtmfoff OBJECT-TYPE
     SYNTAX   INTEGER (16..100)
     ACCESS   read-write
     STATUS   mandatory
     DESCRIPTION
     "DTMF signal OFF time." 
     ::= { nvRbprofEntry 13 }

nvRbprofStatus OBJECT-TYPE
     SYNTAX   INTEGER {
                valid(1),
                invalid(2)
                }
     ACCESS   read-write
     STATUS   mandatory
     DESCRIPTION
"Operation status. Add the record to the table (valid) or delete
the record from the table (invalid)."
     ::= { nvRbprofEntry 14 }


--
--        l2tp
--
--
--      L2TPCONF
--

nvL2tpconf OBJECT IDENTIFIER     ::= { nevadaL2tp 1 }

nvL2tpconfMaxRec OBJECT-TYPE
      SYNTAX   INTEGER
      ACCESS   read-only
      STATUS   mandatory
      DESCRIPTION
                "total number of records allowed in database file."
      ::= {nvL2tpconf 1}

nvL2tpconfNumRec OBJECT-TYPE
      SYNTAX   INTEGER
      ACCESS   read-only
      STATUS   mandatory
      DESCRIPTION
                "number of records in use."
      ::= {nvL2tpconf 2}

nvL2tpconfTable OBJECT-TYPE
      SYNTAX   SEQUENCE OF NvL2tpconfEntry
      ACCESS   not-accessible
      STATUS   mandatory
      DESCRIPTION
               "l2tpconf file."
      ::= { nvL2tpconf 3 }

nvL2tpconfEntry OBJECT-TYPE
      SYNTAX   NvL2tpconfEntry
      ACCESS   not-accessible
      STATUS   mandatory
      DESCRIPTION
               "l2tpconf record."
      INDEX { nvL2tpconfIndex }
      ::= { nvL2tpconfTable 1 }

NvL2tpconfEntry ::=
      SEQUENCE {
      nvL2tpconfIndex
            INTEGER,
      nvL2tpconfAdminStat
            INTEGER,
      nvL2tpconfAckTimout 
            INTEGER,
      nvL2tpconfInactivty 
            INTEGER,
      nvL2tpconfRetrans
            INTEGER,
      nvL2tpconfIdle
            INTEGER,
      nvL2tpconfStatus
            INTEGER
        }

nvL2tpconfIndex OBJECT-TYPE
     SYNTAX   INTEGER
     ACCESS   read-only
     STATUS   mandatory
     DESCRIPTION
      "Index of L2tpconf record."
        ::= { nvL2tpconfEntry 1 }

nvL2tpconfAdminStat OBJECT-TYPE
     SYNTAX   INTEGER
              { 
              enabled (1),      
              disabled (2)
	      }
     ACCESS   read-write
     STATUS   mandatory
     DESCRIPTION
      "enable l2tp protocol stack."
     ::= { nvL2tpconfEntry 2 }

nvL2tpconfAckTimout OBJECT-TYPE
     SYNTAX   INTEGER
     ACCESS   read-write
     STATUS   mandatory
     DESCRIPTION
		"acknowlege timeout."
     ::= { nvL2tpconfEntry  3}
     
nvL2tpconfInactivty OBJECT-TYPE
     SYNTAX   INTEGER
     ACCESS   read-write
     STATUS   mandatory
     DESCRIPTION
                "Inactivty interval for hello msg."
     ::= { nvL2tpconfEntry  4}
     
nvL2tpconfRetrans OBJECT-TYPE
     SYNTAX   INTEGER
     ACCESS   read-write
     STATUS   mandatory
     DESCRIPTION
                "max retransmit before closing."
     ::= { nvL2tpconfEntry 5 }

nvL2tpconfIdle OBJECT-TYPE
     SYNTAX   INTEGER
     ACCESS   read-write
     STATUS   mandatory
     DESCRIPTION
                "max idle prior to closing tunnel"
     ::= { nvL2tpconfEntry  6}

nvL2tpconfStatus OBJECT-TYPE
     SYNTAX   INTEGER {
                valid(1),
                invalid(2)
                }
     ACCESS   read-write
     STATUS   mandatory
     DESCRIPTION
           "Operation status. Add the record to the table (valid) or
           delete the record from the table (invalid)."
     ::= { nvL2tpconfEntry 7 }


--
--        L2tpstat
--
nvL2tpstat   OBJECT IDENTIFIER ::= { nevadaL2tp 2 }

nvL2tpstatMaxRec OBJECT-TYPE
      SYNTAX   INTEGER
      ACCESS   read-only
      STATUS   mandatory
      DESCRIPTION
                "total number of records allowed in database file."
      ::= {nvL2tpstat 1}

nvL2tpstatNumRec OBJECT-TYPE
      SYNTAX   INTEGER
      ACCESS   read-only
      STATUS   mandatory
      DESCRIPTION
                "number of records in use."
      ::= {nvL2tpstat 2}

nvL2tpstatTable OBJECT-TYPE
      SYNTAX   SEQUENCE OF NvL2tpstatEntry
      ACCESS   not-accessible
      STATUS   mandatory
      DESCRIPTION
               "L2tpstat file."
      ::= { nvL2tpstat 3 }

nvL2tpstatEntry OBJECT-TYPE
      SYNTAX   NvL2tpstatEntry
      ACCESS   not-accessible
      STATUS   mandatory
      DESCRIPTION
               "L2tpstat record."
      INDEX { nvL2tpstatIndex }
      ::= { nvL2tpstatTable 1 }

NvL2tpstatEntry ::=
      SEQUENCE {
          nvL2tpstatIndex
            INTEGER,
	  nvL2tpstatProtVrsn
	    INTEGER,
          nvL2tpstatActivTnls
            INTEGER,
          nvL2tpstatActivSns
            INTEGER,
          nvL2tpstatMlfrmPkt
            INTEGER,
          nvL2tpstatCtrlRecv
            INTEGER,
          nvL2tpstatCtrlOofW
            INTEGER,
          nvL2tpstatCtrlOofS
            INTEGER,
          nvL2tpstatCtrlSend
            INTEGER,
          nvL2tpstatDataRecv
            INTEGER,
          nvL2tpstatDataSend
            INTEGER,
          nvL2tpstatTnlUnav	  
            INTEGER,
          nvL2tpstatSessUnav
            INTEGER,
	  nvL2tpstatDtreset
	    DisplayString
               }

nvL2tpstatIndex OBJECT-TYPE
     SYNTAX   INTEGER
     ACCESS   read-only
     STATUS   mandatory
     DESCRIPTION
        "Index of L2tpstat record"
      ::= { nvL2tpstatEntry 1 }

nvL2tpstatActivTnls OBJECT-TYPE
     SYNTAX   INTEGER
     ACCESS   read-only
     STATUS   mandatory
     DESCRIPTION
     "number of currently active tunnel"
      ::= { nvL2tpstatEntry 2 }

nvL2tpstatActivSns OBJECT-TYPE
     SYNTAX   INTEGER
     ACCESS   read-only
     STATUS   mandatory
     DESCRIPTION
     " number of currently active session"
      ::= { nvL2tpstatEntry 3 }

nvL2tpstatMlfrmPkt OBJECT-TYPE
     SYNTAX   INTEGER
     ACCESS   read-only
     STATUS   mandatory
     DESCRIPTION
"number of malformed packets received by l2tp"
      ::= { nvL2tpstatEntry 4 }

nvL2tpstatCtrlRecv OBJECT-TYPE
     SYNTAX   INTEGER
     ACCESS   read-only
     STATUS   mandatory
     DESCRIPTION
      "number of control packet received"
      ::= { nvL2tpstatEntry 5 }

nvL2tpstatCtrlOofW OBJECT-TYPE
     SYNTAX   INTEGER
     ACCESS   read-only
     STATUS   mandatory
     DESCRIPTION
     "number of control packet received outside of window"
      ::= { nvL2tpstatEntry 6 }

nvL2tpstatCtrlOofS OBJECT-TYPE
     SYNTAX   INTEGER
     ACCESS   read-only
     STATUS   mandatory
     DESCRIPTION
     "number of control packet received out of sequence"
      
      ::= { nvL2tpstatEntry 7 }

nvL2tpstatCtrlSend OBJECT-TYPE
     SYNTAX   INTEGER
     ACCESS   read-only
     STATUS   mandatory
     DESCRIPTION
     "number of control packet sent"
      ::= { nvL2tpstatEntry 8 }

nvL2tpstatDataRecv  OBJECT-TYPE
     SYNTAX   INTEGER
     ACCESS   read-only
     STATUS   mandatory
     DESCRIPTION
     " number of data packet received"
      ::= { nvL2tpstatEntry 9 }

nvL2tpstatDataSend OBJECT-TYPE
     SYNTAX   INTEGER
     ACCESS   read-only
     STATUS   mandatory
     DESCRIPTION
     "  number of data packet sent"
      ::= { nvL2tpstatEntry 10 }
      
nvL2tpstatTnlUnav OBJECT-TYPE
     SYNTAX   INTEGER
     ACCESS   read-only
     STATUS   mandatory
     DESCRIPTION
     "tunnels not created due to unavailable resources"
      ::= { nvL2tpstatEntry 11 }

nvL2tpstatSessUnav OBJECT-TYPE
     SYNTAX   INTEGER
     ACCESS   read-only
     STATUS   mandatory
     DESCRIPTION
     "number session not created due to unavailable resources"
      ::= { nvL2tpstatEntry 12 }

nvL2tpstatProtVrsn OBJECT-TYPE
     SYNTAX   INTEGER
     ACCESS   read-only
     STATUS   mandatory
     DESCRIPTION
     "l2tp protocol version number"
      ::= { nvL2tpstatEntry 13 }

nvL2tpstatDtreset OBJECT-TYPE
     SYNTAX   DisplayString (SIZE (0..20))
     ACCESS   read-only
     STATUS   mandatory
     DESCRIPTION
        "date & time statistics last reset"
      ::= { nvL2tpstatEntry 20 }

--
--        L2tptstat
--

nvL2tptstat   OBJECT IDENTIFIER ::= { nevadaL2tp 3 }

nvL2tptstatMaxRec OBJECT-TYPE
      SYNTAX   INTEGER
      ACCESS   read-only
      STATUS   mandatory
      DESCRIPTION
                "total number of records allowed in database file."
      ::= {nvL2tptstat 1}

nvL2tptstatNumRec OBJECT-TYPE
      SYNTAX   INTEGER
      ACCESS   read-only
      STATUS   mandatory
      DESCRIPTION
                "number of records in use."
      ::= {nvL2tptstat 2}

nvL2tptstatTable OBJECT-TYPE
      SYNTAX   SEQUENCE OF NvL2tptstatEntry
      ACCESS   not-accessible
      STATUS   mandatory
      DESCRIPTION
               "L2tptstat file."
      ::= { nvL2tptstat 3 }

nvL2tptstatEntry OBJECT-TYPE
      SYNTAX   NvL2tptstatEntry
      ACCESS   not-accessible
      STATUS   mandatory
      DESCRIPTION
               "L2tptstat record."
      INDEX { nvL2tptstatIndex }
      ::= { nvL2tptstatTable 1 }

NvL2tptstatEntry ::=
      SEQUENCE {
          nvL2tptstatIndex
            INTEGER,
          nvL2tptstatLocalTnID
            INTEGER,
          nvL2tptstatRemotTnID
            INTEGER,
	  nvL2tptstatLocalWSiz
            INTEGER,
	  nvL2tptstatRemotWSiz
	    INTEGER,
	  nvL2tptstatRmtIPaddr
            DisplayString,
	  nvL2tptstatRmtHstNme
            DisplayString,
	  nvL2tptstatTunlState
            INTEGER,
	  nvL2tptstatRecvCtrl
	    INTEGER,
	  nvL2tptstatRecvData
	    INTEGER,
	  nvL2tptstatSendCtrl
	    INTEGER,
	  nvL2tptstatSendData
	    INTEGER,
	  nvL2tptstatDtreset
	    DisplayString
               }

nvL2tptstatIndex OBJECT-TYPE
     SYNTAX   INTEGER
     ACCESS   read-only
     STATUS   mandatory
     DESCRIPTION
        "Index of L2tptstat record"
      ::= { nvL2tptstatEntry 1 }

nvL2tptstatLocalTnID  OBJECT-TYPE
     SYNTAX   INTEGER
     ACCESS   read-only
     STATUS   mandatory
     DESCRIPTION
     "Local Tunnel Id of the LAC "
      ::= { nvL2tptstatEntry 2 }

nvL2tptstatRemotTnID  OBJECT-TYPE
     SYNTAX   INTEGER
     ACCESS   read-only
     STATUS   mandatory
     DESCRIPTION
     " Local call id of the LNS"
      ::= { nvL2tptstatEntry 3 }

nvL2tptstatLocalWSiz OBJECT-TYPE
     SYNTAX   INTEGER
     ACCESS   read-only
     STATUS   mandatory
     DESCRIPTION
     "Remote Call Id of the LNS"
      ::= { nvL2tptstatEntry 4 }

nvL2tptstatRemotWSiz OBJECT-TYPE
     SYNTAX   INTEGER
     ACCESS   read-only
     STATUS   mandatory
     DESCRIPTION
      "Call Serial Number"
      ::= { nvL2tptstatEntry 5 }

nvL2tptstatRmtIPaddr OBJECT-TYPE
     SYNTAX   DisplayString (SIZE (0..16))
     ACCESS   read-only
     STATUS   mandatory
     DESCRIPTION
      "Local Window Size"
      ::= { nvL2tptstatEntry 6 }

nvL2tptstatRmtHstNme OBJECT-TYPE
     SYNTAX   DisplayString (SIZE (0..20))
     ACCESS   read-only
     STATUS   mandatory
     DESCRIPTION
       "PPP stat file record"
      ::= { nvL2tptstatEntry 7 }

nvL2tptstatTunlState OBJECT-TYPE
     SYNTAX   INTEGER{
	      null(1),      --  null state    
	      idle(2),      --  idle         
	      cnnting(3),   --  connecting   
	      estb(4),      --  established  
	      disconn(5)    --  disconnected 
	      }
     ACCESS   read-only
     STATUS   mandatory
     DESCRIPTION
     "Received Data Packets"
      ::= { nvL2tptstatEntry 8 }

nvL2tptstatRecvCtrl OBJECT-TYPE
     SYNTAX   INTEGER
     ACCESS   read-only
     STATUS   mandatory
     DESCRIPTION
	"Received Control Packets"
     ::= { nvL2tptstatEntry 9 }

nvL2tptstatRecvData OBJECT-TYPE
     SYNTAX   INTEGER
     ACCESS   read-only 
     STATUS   mandatory 
     DESCRIPTION
	"Received Data Packets"
     ::= { nvL2tptstatEntry 10 }

nvL2tptstatSendCtrl OBJECT-TYPE 
     SYNTAX   INTEGER
     ACCESS   read-only  
     STATUS   mandatory  
     DESCRIPTION 
        "Sent Control Packets"
     ::= { nvL2tptstatEntry 11 } 
 
nvL2tptstatSendData OBJECT-TYPE 
     SYNTAX   INTEGER
     ACCESS   read-only  
     STATUS   mandatory  
     DESCRIPTION 
        "Sent Data Packets" 
     ::= { nvL2tptstatEntry 12 } 

nvL2tptstatDtreset OBJECT-TYPE
     SYNTAX   DisplayString (SIZE (0..20))
     ACCESS   read-only
     STATUS   mandatory
     DESCRIPTION
        "date & time statistics last reset"
      ::= { nvL2tptstatEntry 20 }

--
--        L2tpsstat
--
 
nvL2tpsstat   OBJECT IDENTIFIER ::= { nevadaL2tp 4 }

nvL2tpsstatMaxRec OBJECT-TYPE
      SYNTAX   INTEGER
      ACCESS   read-only
      STATUS   mandatory
      DESCRIPTION
                "total number of records allowed in database file."
      ::= {nvL2tpsstat 1}

nvL2tpsstatNumRec OBJECT-TYPE
     SYNTAX   INTEGER
     ACCESS   read-only
     STATUS   mandatory
     DESCRIPTION
        "number of records in use."
     ::= {nvL2tpsstat 2}

nvL2tpsstatTable OBJECT-TYPE
      SYNTAX   SEQUENCE OF NvL2tpsstatEntry
      ACCESS   not-accessible
      STATUS   mandatory
      DESCRIPTION
               "l2tpsstat file."
      ::= {nvL2tpsstat 3}

nvL2tpsstatEntry OBJECT-TYPE
      SYNTAX   NvL2tpsstatEntry
      ACCESS   not-accessible
      STATUS   mandatory
      DESCRIPTION
               "l2tpsstat record."
      INDEX {nvL2tpsstatIndex}
      ::= {nvL2tpsstatTable 1 }

NvL2tpsstatEntry ::= SEQUENCE { 
      nvL2tpsstatIndex
          INTEGER,
      nvL2tpsstatTunnelID
	  INTEGER,
      nvL2tpsstatLclCallID
	  INTEGER,
      nvL2tpsstatRmtCallID
	  INTEGER,
      nvL2tpsstatCallSN
	  INTEGER,
      nvL2tpsstatState
	  INTEGER,
      nvL2tpsstatDeviceNum
	  INTEGER,
      nvL2tpsstatDataRecv
	  INTEGER,
      nvL2tpsstatDataSend
	  INTEGER,
      nvL2tpsstatDtreset
	  DisplayString
      }
 
nvL2tpsstatIndex OBJECT-TYPE
     SYNTAX   INTEGER
     ACCESS   read-only
     STATUS   mandatory
     DESCRIPTION
        "Index of L2tpsstat record"
     ::= {nvL2tpsstatEntry 1}

nvL2tpsstatTunnelID OBJECT-TYPE
     SYNTAX   INTEGER
     ACCESS   read-only
     STATUS   mandatory
     DESCRIPTION
        "Local Tunnel Id of the LAC."
     ::= {nvL2tpsstatEntry 2}

nvL2tpsstatLclCallID OBJECT-TYPE
     SYNTAX   INTEGER
     ACCESS   read-only
     STATUS   mandatory
     DESCRIPTION
        "Local Call Id of the LNS."
     ::= {nvL2tpsstatEntry 3}

nvL2tpsstatRmtCallID OBJECT-TYPE
     SYNTAX   INTEGER
     ACCESS   read-only
     STATUS   mandatory
     DESCRIPTION
        "Remote Call Id of the LNS."
     ::= {nvL2tpsstatEntry 4}

nvL2tpsstatCallSN OBJECT-TYPE
     SYNTAX   INTEGER
     ACCESS   read-only
     STATUS   mandatory
     DESCRIPTION
        "Call Serial Number."
     ::= {nvL2tpsstatEntry 5}

nvL2tpsstatState OBJECT-TYPE
     SYNTAX   INTEGER {
		null(1),
		idle(2),
		cnnting(3),
		estb(4),
		disconn(5)
		}
     ACCESS   read-only
     STATUS   mandatory
     DESCRIPTION
        "State."
     ::= {nvL2tpsstatEntry 6}

nvL2tpsstatDeviceNum OBJECT-TYPE
     SYNTAX   INTEGER
     ACCESS   read-only
     STATUS   mandatory
     DESCRIPTION
        "Device Number."
     ::= {nvL2tpsstatEntry 7}

nvL2tpsstatDataRecv OBJECT-TYPE
     SYNTAX   INTEGER
     ACCESS   read-only
     STATUS   mandatory
     DESCRIPTION
        "Received Data Packets."
     ::= {nvL2tpsstatEntry 8}

nvL2tpsstatDataSend OBJECT-TYPE
     SYNTAX   INTEGER
     ACCESS   read-only
     STATUS   mandatory
     DESCRIPTION
        "Sent Data Packets."
     ::= {nvL2tpsstatEntry 9}

nvL2tpsstatDtreset OBJECT-TYPE
     SYNTAX   DisplayString (SIZE (0..20))
     ACCESS   read-only
     STATUS   mandatory
     DESCRIPTION
        "date & time statistics last reset"
      ::= { nvL2tpsstatEntry 15 }
--
--
--
--
--      Nevada Generic Alarm/Trap Objects
--

nvTrapS0        OBJECT-TYPE
                SYNTAX  DisplayString  (SIZE (0..80))
                ACCESS  read-only
                STATUS  mandatory
                DESCRIPTION "S0: 0-80 character trap string"
                ::= {nevadaTraps 1}

nvTrapS1        OBJECT-TYPE
                SYNTAX  DisplayString  (SIZE (0..80))
                ACCESS  read-only
                STATUS  mandatory
                DESCRIPTION "S1: 0-80 character trap string"
                ::= {nevadaTraps 2}

nvTrapS2        OBJECT-TYPE
                SYNTAX  DisplayString  (SIZE (0..80))
                ACCESS  read-only
                STATUS  mandatory
                DESCRIPTION "S2: 0-80 character trap string"
                ::= {nevadaTraps 3}

nvTrapN0        OBJECT-TYPE
                SYNTAX  INTEGER
                ACCESS  read-only
                STATUS  mandatory
                DESCRIPTION "N0: numeric trap value"
                ::= {nevadaTraps 4}

nvTrapN1        OBJECT-TYPE
                SYNTAX  INTEGER
                ACCESS  read-only
                STATUS  mandatory
                DESCRIPTION "N1: numeric trap value"
                ::= {nevadaTraps 5}

nvTrapN2        OBJECT-TYPE
                SYNTAX  INTEGER
                ACCESS  read-only
                STATUS  mandatory
                DESCRIPTION "N2: numeric trap value"
                ::= {nevadaTraps 6}

--
--
--
--      Nevada  Alarm/Trap conf table
--
nvTrapconf   OBJECT IDENTIFIER ::= { nevadaTraps 7 }

nvTrapconfMaxRec OBJECT-TYPE
      SYNTAX   INTEGER
      ACCESS   read-only
      STATUS   mandatory
      DESCRIPTION
                "total number of traps that have been defined"
      ::= { nvTrapconf 1}

nvTrapconfNumRec OBJECT-TYPE
      SYNTAX   INTEGER
      ACCESS   read-only
      STATUS   mandatory
      DESCRIPTION
                "number of highest record in use."
      ::= { nvTrapconf 2}

nvTrapconfTable OBJECT-TYPE
      SYNTAX   SEQUENCE OF NvTrapconfEntry
      ACCESS   not-accessible
      STATUS   mandatory
      DESCRIPTION
               "Nevada Traps Lists"
      ::= { nvTrapconf 3 }

nvTrapconfEntry OBJECT-TYPE
      SYNTAX   NvTrapconfEntry
      ACCESS   not-accessible
      STATUS   mandatory
      DESCRIPTION
               "Nevada Trapconf definition."
      INDEX { nvTrapconfIndex }
      ::= { nvTrapconfTable 1 }

NvTrapconfEntry ::=
      SEQUENCE {
      nvTrapconfIndex
            INTEGER,
      nvTrapconfTrapId
            INTEGER,
      nvTrapconfDesc
            DisplayString,
      nvTrapconfStatus
            INTEGER
               }

nvTrapconfIndex OBJECT-TYPE
     SYNTAX   INTEGER
     ACCESS   read-only
     STATUS   mandatory
     DESCRIPTION
        "Index for traps.. for config purpose"
      ::= { nvTrapconfEntry 1 }

nvTrapconfTrapId OBJECT-TYPE
     SYNTAX   INTEGER
     ACCESS   read-only
     STATUS   mandatory
     DESCRIPTION
        "The assigned enterprise trap number"
      ::= { nvTrapconfEntry 2 }

nvTrapconfDesc OBJECT-TYPE
     SYNTAX   DisplayString (SIZE (0..256))
     ACCESS   read-write
     STATUS   mandatory
     DESCRIPTION
"The Description of the specific trap"
     ::= { nvTrapconfEntry 3 }

nvTrapconfStatus OBJECT-TYPE
     SYNTAX   INTEGER {
                enable(1),
                disable(2)
                }
     ACCESS   read-write
     STATUS   mandatory
     DESCRIPTION
"Operation status of the Trap. Use enable to generate
trap and disable otherwise."
      ::= { nvTrapconfEntry 4 }

--
--
--

nvReboot        OBJECT-TYPE
                SYNTAX  INTEGER {
                        ok (1),
                        reboot (2),
                        failed (3)
                        }
                ACCESS  read-write
                STATUS  mandatory
                DESCRIPTION
                      "Reboot Nevada."
                ::= {nevadaAdmin 1}

nvWriteConfig   OBJECT-TYPE
                SYNTAX  INTEGER {
                        write (1),
                        executing (2),
                        successful (3),
                        failed (4)
                        }
                ACCESS  read-write
                STATUS  mandatory
                DESCRIPTION
                      "Write Configuration -save-"
                ::= {nevadaAdmin 2}

nvDate          OBJECT-TYPE
                SYNTAX  DisplayString (SIZE (0..25))
                ACCESS  read-write
                STATUS  mandatory
                DESCRIPTION "Set Nevada date/time.  The Format is as follows
                        yyyy mm dd hh mm ss"
                ::= {nevadaAdmin 3}

nvWriteRoot     OBJECT-TYPE
                SYNTAX  INTEGER {
                        write (1),
                        executing (2),
                        successful (3),
                        failed (4)
                        }
                ACCESS  read-write
                STATUS  mandatory
                DESCRIPTION
                   "Write Mediastat file (root)"
                ::= {nevadaAdmin 4}

nvStartScript       OBJECT-TYPE
                SYNTAX  INTEGER
                ACCESS  read-write
                STATUS  mandatory
                DESCRIPTION
                     "Script Number to Start"
               ::= {nevadaAdmin 5}

--
-- Stringlists
--

nvString OBJECT IDENTIFIER ::= { nevadaAdmin 6 }

nvStringMaxRec OBJECT-TYPE
      SYNTAX   INTEGER
      ACCESS   read-only
      STATUS   mandatory
      DESCRIPTION
                "total number of records available for all strings allowed in database file."
      ::= { nvString 1}

nvStringNumRec OBJECT-TYPE
      SYNTAX   INTEGER
      ACCESS   read-only
      STATUS   mandatory
      DESCRIPTION
                "number of highest record in use."
      ::= { nvString 2}

nvStringTable OBJECT-TYPE
      SYNTAX   SEQUENCE OF NvStringEntry
      ACCESS   not-accessible
      STATUS   mandatory
      DESCRIPTION
               "Nevada String List file."
      ::= { nvString 3 }

nvStringEntry OBJECT-TYPE
      SYNTAX   NvStringEntry
      ACCESS   not-accessible
      STATUS   mandatory
      DESCRIPTION
               "Nevada String record."
      INDEX { nvStringIndex }
      ::= { nvStringTable 1 }

NvStringEntry ::=
      SEQUENCE {
      nvStringIndex
            INTEGER,
      nvStringData
            DisplayString,
      nvStringStatus
            INTEGER
               }

nvStringIndex OBJECT-TYPE
     SYNTAX   INTEGER
     ACCESS   read-only
     STATUS   mandatory
     DESCRIPTION
        "Index of Nevada String record"
      ::= { nvStringEntry 1 }

nvStringData OBJECT-TYPE
     SYNTAX   DisplayString (SIZE (0..256))
     ACCESS   read-write
     STATUS   mandatory
     DESCRIPTION
"The data in the specific string, size up to 256"
     ::= { nvStringEntry 2 }

nvStringStatus OBJECT-TYPE
     SYNTAX   INTEGER {
                valid(1),
                invalid(2)
                }
     ACCESS   read-write
     STATUS   mandatory
     DESCRIPTION
"Operation status of the record. Use valid to add
record to database file and invalid to delete
record from database file."
      ::= { nvStringEntry 3 }

--
--      Nevada Traps
--
--
--      ITI (async) traps
--
nvTrapDeviceConnected TRAP-TYPE
                ENTERPRISE nvNas
                VARIABLES {nvTrapS0, nvTrapS1}
                DESCRIPTION
"Probable Cause
  The port placed or accepted call with the attached device.

Probable Effect
  Nevada has a network connection

Recommended Action
  Network connection is now available for data transfer.
"
                ::= 4352

nvTrapDeviceDisconnected TRAP-TYPE
                ENTERPRISE nvNas
                VARIABLES {nvTrapS0, nvTrapS1}
                DESCRIPTION
"Probable Cause
  The port disconnected with the attached device.

Probable Effect
  Nevada does not have a network connection on the port.

Recommended Action
  Refer stat files itipstat, iticstat, itiustat & portstat.
"
                ::= 4353
nvTrapDuiportavail TRAP-TYPE
                ENTERPRISE nvNas
                VARIABLES {nvTrapS0, nvTrapS1}
                DESCRIPTION
"Probable Cause
    number of available ports at site

Probable Effect
    can place calls
    
Recommended Action
    place calls
"
                ::= 4354

nvTrapNoIdlePorts TRAP-TYPE
                ENTERPRISE nvNas
                DESCRIPTION
"Probable Cause
  All available ports are in use

Probable Effect
  No additional users will be able to call in.

Recommended Action
  Add more ports to the particular site.
"
                ::= 4355

nvTrapDatatimerexpird TRAP-TYPE
                ENTERPRISE nvNas
                VARIABLES {nvTrapS0, nvTrapS1}
                DESCRIPTION
"Probable Cause
     Data mode timer expired

Probable Effect
     
Recommended Action

"
                ::= 4359

nvTrapDUIDown TRAP-TYPE
                ENTERPRISE nvNas
                VARIABLES {nvTrapS0}
                DESCRIPTION
"Probable Cause
  Both DUI Circuits down.

Probable Effect
  Can not accept calls.

Recommended Action
"
                ::= 4365

nvTrapDatabaseUpPrimary TRAP-TYPE
                ENTERPRISE nvNas
                VARIABLES {nvTrapS0}
                DESCRIPTION
                "LSERVER: Database Up: primary NUA `S0`"
                ::= 4377

nvTrapDatabaseUpSecondary TRAP-TYPE
                ENTERPRISE nvNas
                VARIABLES {nvTrapS0}
                DESCRIPTION
                "LSERVER: Database Up: secondary NUA `S0`"
                ::= 4378
--
--      Nevada X.25 alarms
--

--
--      nevada X.25 alarms
--
nvTrapLinkNotReady TRAP-TYPE
                ENTERPRISE nvNas
                VARIABLES {nvTrapS0}
                DESCRIPTION
"Probable Cause
  X.25 detected that the link is down.
Probable Effect
  Data transfer over the specified link not possible
Recommended Action
  Correct the Physical connection and/or configuration
"
                ::= 4668

nvTrapLinkReady TRAP-TYPE
                ENTERPRISE nvNas
                VARIABLES {nvTrapS0}
                DESCRIPTION
"Probable Cause
  X.25 detected that the link has come up.

Probable Effect
  Data transfer over the specified link possible

Recommended Action
  New calls can now be established on this link
"
                ::= 4669

--
--      Nevada Node Alarms
--


nvTrapAlternateConfig   TRAP-TYPE
                ENTERPRISE nvNas
                VARIABLES {nvTrapN0}
                DESCRIPTION
                "Nevada running alternate config on side `n0`"
                ::= 5635
		
nvTrapDbautosave   TRAP-TYPE
                ENTERPRISE nvNas
                DESCRIPTION
                "data base auto save"
                ::= 5636

nvTrapDbCrcError        TRAP-TYPE
                ENTERPRISE nvNas
                DESCRIPTION
                "Nevada CRC error on database"
                ::= 5637
		
nvTrapDbsavecount   TRAP-TYPE
                ENTERPRISE nvNas
                DESCRIPTION
                "save count is zero"
                ::= 5638

nvTrapLocalDatabaseChanged TRAP-TYPE
                ENTERPRISE nvNas
                DESCRIPTION
                "Nevada local database has been changed"
                ::= 5639

nvTrapRateIncreasedToL1 TRAP-TYPE
                ENTERPRISE nvNas
                VARIABLES {nvTrapS0, nvTrapS1, nvTrapS2,
                        nvTrapN0}
                DESCRIPTION
                "Nevada statistics rate increased to level 1"
                ::= 5640

nvTrapRateIncreasedToL2 TRAP-TYPE
                ENTERPRISE nvNas
                VARIABLES {nvTrapS0, nvTrapS1, nvTrapS2,
                        nvTrapN0}
                DESCRIPTION
                "Nevada statistics rate increased to level 2"
                ::= 5641

nvTrapRateDecreasedBelowL1      TRAP-TYPE
                ENTERPRISE nvNas
                VARIABLES {nvTrapS0, nvTrapS1, nvTrapS2,
                        nvTrapN0}
                DESCRIPTION
                "Nevada statistics rate decrease to below level 1"
                ::= 5642

nvTrapRateDecreasedBelowL2      TRAP-TYPE
                ENTERPRISE nvNas
                VARIABLES {nvTrapS0, nvTrapS1, nvTrapS2,
                        nvTrapN0}
                DESCRIPTION
                "Nevada statistics rate decrease to below level 2"
                ::= 5643

nvTrapReachedStatus     TRAP-TYPE
                ENTERPRISE nvNas
                VARIABLES {nvTrapS0, nvTrapS1, nvTrapS2}
                DESCRIPTION
                "Nevada status value reached"
                ::= 5644

nvTrapLeftStatus        TRAP-TYPE
                ENTERPRISE nvNas
                VARIABLES {nvTrapS0, nvTrapS1, nvTrapS2}
                DESCRIPTION
                "Nevada status value no longer met"
                ::= 5645
--
--		NMS traps
--



--
--        Framer traps
--
nvTrapFramerfailaction  TRAP-TYPE
                ENTERPRISE nvNas
                VARIABLES {nvTrapS0, nvTrapS1}
                DESCRIPTION
"Probable Cause
   framer failed to do the required action
Probable Effect

Recommended Action

"
                ::= 5652

nvTrapFramerfailed  TRAP-TYPE
                ENTERPRISE nvNas
		VARIABLES {nvTrapS0,nvTrapN0}
                DESCRIPTION
"Probable Cause
   framer card in the indicated slot failed to do the requested action
Probable Effect
   no traffic will flow
Recommended Action
   check hardware and software configuration
"
                ::= 5653
--
--      Nevada Frame Relay Traps
--
nvTrapFrPortUp  TRAP-TYPE
                ENTERPRISE nvNas
                VARIABLES {nvTrapN0}
                DESCRIPTION
                 "Nevada Frame Relay Interface up ready"
                ::= 11520

nvTrapFrPortDown  TRAP-TYPE
                  ENTERPRISE nvNas
                  VARIABLES {nvTrapN0}
                  DESCRIPTION
                  "Nevada Frame Relay Interface down not-ready"
                 ::= 11521
nvTrapFrLMIError        TRAP-TYPE
                ENTERPRISE nvNas
                VARIABLES {nvItipstatPortname, nvTrapS0}
                DESCRIPTION
"Probable Cause
  The specified frame relay interface has detected LMI error.

Probable Effect
  Stops PVC traffic.

Recommended Action
  Wait for LMI to enter normal state to resume PVC traffic.
"
                ::= 11522

nvTrapFrLMINormal       TRAP-TYPE
                ENTERPRISE nvNas
                VARIABLES {nvItipstatPortname, nvTrapS0}
                DESCRIPTION
"Probable Cause
  The specified frame relay interface has found LMI in normal state.

Probable Effect
  Enables PVC traffic to resume.

Recommended Action
  The FRI is available for data transfer.
"
                ::= 11523

nvTrapFrAllDLCIsUp      TRAP-TYPE
                ENTERPRISE nvNas
                VARIABLES {nvItipstatPortname, nvTrapS0}
                DESCRIPTION
"Probable Cause
  All DLCIs on the FRI are functional.

Probable Effect
  All FRPVCs enter data transfer state.

Recommended Action
  All FRPVCs are available for data transfer.
"
                ::= 11524

nvTrapFrDLCIsDown       TRAP-TYPE
                ENTERPRISE nvNas
                VARIABLES {nvItipstatPortname, nvTrapS0}
                DESCRIPTION
"Probable Cause
  One or more DLCIs on the FRI not functional.

Probable Effect
  Data transfer will stop on the FRPVC that has gone down.

Recommended Action
  Refer stat files fristat, frvcstat and frstat.
"
                ::= 11525
--
--          ELX Traps
--
nvTrapElxUp     TRAP-TYPE
                ENTERPRISE nvNas
                VARIABLES {nvTrapS0}
                DESCRIPTION
"Probable Cause
  ELX has gone up.

Probable Effect
  Data can be exchanged

Recommended Action
 Pass data through
"
                 ::= 12032
nvTrapElxDown   TRAP-TYPE
                ENTERPRISE nvNas
                VARIABLES {nvTrapS0}
                DESCRIPTION
"Probable Cause
  ELX has gone down.
 
Probable Effect
  Data can not be exchanged
 
Recommended Action
 Correct configuration, cable connection or the hardware setup.
"
        ::= 12033
--
-- PPP Traps
--
nvTrapPppLcpUp TRAP-TYPE
                ENTERPRISE nvNas
		VARIABLES {nvTrapN0}
		DESCRIPTION
"Probable Cause
  The Link Control Protocol (LCP) has gone up.

Probable Effect
  The link is configured, tested and available for higher-level
  protocols such as IPCP (Internet Protocol Control Protocol).

Recommended Action
  The PPP link is now available for higher-level protocol such as IPCP.
"
		::= 14848

nvTrapPppLcpDown TRAP-TYPE
                ENTERPRISE nvNas
		VARIABLES {nvTrapN0}
		DESCRIPTION
"Probable Cause
  The Link Control Protocol (LCP) has gone down.

Probable Effect
  The link is not configured and is not available for higher-level
  protocols such as IPCP (Internet Protocol Control Protocol).

Recommended Action
  Refer PPP statfile pppstat.
"
		::= 14849

nvTrapPppIpcpOnLcpUp TRAP-TYPE
                ENTERPRISE nvNas
		VARIABLES {nvTrapN0, nvTrapN1}
		DESCRIPTION
"Probable Cause
  The IP Control Protocol (IPCP) has gone up.

Probable Effect
  The Network Layer Protocol is selected and datagrams can be
  sent.

Recommended Action
  The PPP link is now available for datagram traffic.
"
		::= 14850

nvPppIpcpOnLcpDown TRAP-TYPE
                ENTERPRISE nvNas
		VARIABLES {nvTrapN0, nvTrapN1}
		DESCRIPTION
"Probable Cause
  The IP Control Protocol (IPCP) has gone down.

Probable Effect
  The Network Layer Protocol is not selected and datagrams
  can not be sent.

Recommended Action
  Refer PPP statfile pppstat.
"
		::= 14851
--
-- ISDN PRI Traps
--

nvTrapPriDataLayerUp TRAP-TYPE
                ENTERPRISE nvNas
                VARIABLES {nvPristatIndex}
                DESCRIPTION
"Probable Cause
 ISDN Data Layer Up PRI is  functional on the DLI

Probable Effect
 Data Channel responding.

Recommended Action
 Unit is ready to receive ISDN calls
"
                ::= 15136

nvTrapPriDataLayerDn TRAP-TYPE
                ENTERPRISE nvNas
                VARIABLES {nvPristatIndex}
                DESCRIPTION
"Probable Cause
 ISDN Data Layer Down PRI is Not functional on the DLI

Probable Effect
 Data Channel not responding bchannel calls will fail

Recommended Action
 Test the DLI and check associated Config in CDLI and PRICONF
"
                ::= 15137


--
--  Multi link PPP traps
--

nvTrapPppLcpNetworkPhase TRAP-TYPE
               ENTERPRISE nvNas
               VARIABLES {nvTrapS0}
                DESCRIPTION
"Probable Cause
 The LCP protocol has entered the network phase on the PPP link

Probable Effect
 Network layer protocols such as IPCP can now exchange packets on the link

Recommended Action
 None
"
                ::= 15500
		
nvTrapPppLcpNetworkdown TRAP-TYPE
               ENTERPRISE nvNas
               VARIABLES {nvTrapS0}
                DESCRIPTION
"Probable Cause
 The LCP protocol is down on the network phase on the PPP link
Probable Effect
 Network layer protocols such as IPCP can not exchange packets on the link
Recommended Action
"
                ::= 15501

nvTrapPppMpLinkAdded TRAP-TYPE
               ENTERPRISE nvNas
               VARIABLES {nvTrapS0}
                DESCRIPTION
"Probable Cause
 A PPP link has been added to a multilink bundle

Probable Effect
 Greater bandwidth is available on the bundle

Recommended Action
 None required.  Informational only
"
                ::= 15504

nvTrapPppMpLinkDropped TRAP-TYPE
               ENTERPRISE nvNas
               VARIABLES {nvTrapS0}
                DESCRIPTION
"Probable Cause
 A PPP link has been dropped from a multilink bundle

Probable Effect
 The bandwidth for the bundle has been reduced. If this was the
 last link in the bundle the bundle will be closed

Recommended Action
 None required, informational only
"
                ::= 15505

-- DSPM MODULE 

nvTrapDSPMFailedModemThresh1 TRAP-TYPE
               ENTERPRISE nvNas
               VARIABLES {nvTrapN0}
                DESCRIPTION
"Probable Cause
 Number of Modem failures has reached the configured threshold one

Probable Effect
	Modem failure results in failed calls 

Recommended Action
 check modem hardware/configuration
"
                ::= 16896

nvTrapDSPMFailedModemThresh2 TRAP-TYPE
               ENTERPRISE nvNas
               VARIABLES {nvTrapN0}
                DESCRIPTION
"Probable Cause
 Number of Modem failures has reached the configured threshold two

Probable Effect
	Modem failure results in failed calls 

Recommended Action
 check modem hardware/configuration
"
                ::= 16897

nvTrapDSPMFailedModemThresh3 TRAP-TYPE
               ENTERPRISE nvNas
               VARIABLES {nvTrapN0}
                DESCRIPTION
"Probable Cause
 Number of Modem failures has reached the configured threshold three

Probable Effect
	Modem failure results in failed calls 

Recommended Action
check modem hardware/configuration
"
                ::= 16898

nvTrapDSPRFailed TRAP-TYPE
               ENTERPRISE nvNas
               VARIABLES {nvTrapN0}
                DESCRIPTION
"Probable Cause
 DSPR has failed.

Probable Effect
	DSPR card has failed -- hardware resources failure 

Recommended Action
 Replace the DSPR card
"

                ::= 16899

-- ISDNP MODULE 

nvTrapISDNFailedCalls TRAP-TYPE
               ENTERPRISE nvNas
               VARIABLES {nvTrapN0}
                DESCRIPTION
"Probable Cause
 Number of ISDN calls failure have reached the configured threshold

Probable Effect
	ISDN failure -- results in failed ISDN calls 

Recommended Action
 check the ISDN IO cards/service provider/hardware 
"
                ::= 16640

-- FRAMER MODULE Base number 69

nvTrapFRAMERFailed TRAP-TYPE
               ENTERPRISE nvNas
               VARIABLES {nvTrapN0}
                DESCRIPTION
"Probable Cause
	FRAMER card failure  

Probable Effect
	FRAMER card failure -- system failure 

Recommended Action
	replace the framer card
"
                ::= 17664

-- DLI MODULE Base number 70

nvTrapQDLIFailed TRAP-TYPE
               ENTERPRISE nvNas
               VARIABLES {nvTrapN0}
                DESCRIPTION
"Probable Cause
	QDLI card has failed   

Probable Effect
	QDLI card has failed

Recommended Action
 None required, informational only
"
                ::= 17920

nvTrapRemovedCard TRAP-TYPE
               ENTERPRISE nvNas
               VARIABLES {nvTrapS0,nvTrapN0}
                DESCRIPTION
"Probable Cause
        a card has been deleted in the indicated slot

Probable Effect
        a card has been deleted -- hotswap

Recommended Action
 None required, informational only
"
                ::= 17940

nvTrapCardInserted TRAP-TYPE
               ENTERPRISE nvNas
               VARIABLES {nvTrapS0,nvTrapN0}
                DESCRIPTION
"Probable Cause
        a card has been inserted in the indicated slot
          
Probable Effect
        a card has been inserted -- hotswap
          
Recommended Action
 None required, informational only
"
                ::= 17950
		
END
