-- *------------------------------------------------------------------
-- * ALTIGA-FTP-STATS-MIB.my:  FTP Statistics MIB.
-- *
-- * Altiga Networks was acquired by Cisco Systems on March 29, 2000
-- *
-- * Copyright (c) 2002 by Cisco Systems, Inc.
-- * All rights reserved.
-- *
-- *------------------------------------------------------------------

ALTIGA-FTP-STATS-MIB DEFINITIONS ::= BEGIN

   IMPORTS
      MODULE-IDENTITY, OBJECT-TYPE, Counter32, Gauge32
         FROM SNMPv2-SMI
      OBJECT-GROUP, MODULE-COMPLIANCE
         FROM SNMPv2-CONF
      alStatsFtp, alFtpGroup
         FROM ALTIGA-MIB
      alFtpMibModule
         FROM ALTIGA-GLOBAL-REG;

   altigaFtpStatsMibModule MODULE-IDENTITY
      LAST-UPDATED   "200209051300Z"
      ORGANIZATION   "Cisco Systems, Inc."
      CONTACT-INFO
         "Cisco Systems
          170 W Tasman Drive
          San Jose, CA  95134
          USA

          Tel: +1 800 553-NETS
          E-mail: cs-cvpn3000@cisco.com"

      DESCRIPTION
         "The Altiga FTP Statistics MIB models counters and objects
          that are of management interest for FTP.
         
          Acronyms
          The following acronyms are used in this document:

            FTP:        File Transfer Protocol

            MIB:        Management Information Base

         "

        REVISION "200209051300Z"
        DESCRIPTION
                "Added module compliance."

        REVISION "200207100000Z"
        DESCRIPTION
                "Updated with new header"

      ::= { alFtpMibModule 2 }

-- +++++++++++++++++++++++++++++++++++++++++++++++++++++++
-- MIB Objects
-- +++++++++++++++++++++++++++++++++++++++++++++++++++++++

alStatsFtpServerGlobal	OBJECT IDENTIFIER ::= { alStatsFtp 1 }
alStatsFtpClientGlobal	OBJECT IDENTIFIER ::= { alStatsFtp 2 }

alFtpClientStatsMaxSess		OBJECT-TYPE
	SYNTAX			Gauge32
	MAX-ACCESS		read-only
	STATUS			current
	DESCRIPTION
	       "The current maximum number of FTP client sessions."
	::= { alStatsFtpClientGlobal 1 }

alFtpClientStatsTotalSess		OBJECT-TYPE
	SYNTAX			Counter32
	MAX-ACCESS		read-only
	STATUS			current
	DESCRIPTION
	       "The total number of FTP client sessions since boot."
	::= { alStatsFtpClientGlobal 2 }

alFtpClientStatsGoodConns		OBJECT-TYPE
	SYNTAX			Counter32
	MAX-ACCESS		read-only
	STATUS			current
	DESCRIPTION
	       "The total number of successful FTP client connections
                since boot."
	::= { alStatsFtpClientGlobal 3 }

alFtpClientStatsBadConns		OBJECT-TYPE
	SYNTAX			Counter32
	MAX-ACCESS		read-only
	STATUS			current
	DESCRIPTION
	       "The total number of unsuccessful FTP client connections
                since boot."
	::= { alStatsFtpClientGlobal 4 }

alFtpClientStatsGoodDataConns		OBJECT-TYPE
	SYNTAX			Counter32
	MAX-ACCESS		read-only
	STATUS			current
	DESCRIPTION
	       "The total number of successful FTP client data-socket
                connections since boot."
	::= { alStatsFtpClientGlobal 5 }

alFtpClientStatsBadDataConns	OBJECT-TYPE
	SYNTAX			Counter32
	MAX-ACCESS		read-only
	STATUS			current
	DESCRIPTION
	       "The total number of unsuccessful FTP client data-socket
                connections since boot."
	::= { alStatsFtpClientGlobal 6 }

alFtpClientStatsGoodFileXfers	OBJECT-TYPE
	SYNTAX			Counter32
	MAX-ACCESS		read-only
	STATUS			current
	DESCRIPTION
	       "The number of successful FTP client file transfers
                since boot."
	::= { alStatsFtpClientGlobal 7 }

alFtpClientStatsBadFileXfers	OBJECT-TYPE
	SYNTAX			Counter32
	MAX-ACCESS		read-only
	STATUS			current
	DESCRIPTION
	       "The numner of unsuccessful FTP client file transfers
                since boot."
	::= { alStatsFtpClientGlobal 8 }

alFtpClientStatsAsciiXfers		OBJECT-TYPE
	SYNTAX			Counter32
	MAX-ACCESS		read-only
	STATUS			current
	DESCRIPTION
	       "The total number of FTP client ASCII mode transfers
                since boot."
	::= { alStatsFtpClientGlobal 9 }

alFtpClientStatsBinaryXfers		OBJECT-TYPE
	SYNTAX			Counter32
	MAX-ACCESS		read-only
	STATUS			current
	DESCRIPTION
	       "The total number of FTP client BINARY mode transfers
                since boot."
	::= { alStatsFtpClientGlobal 10 }

alFtpClientStatsOctetsXmit		OBJECT-TYPE
	SYNTAX			Counter32
	MAX-ACCESS		read-only
	STATUS			current
	DESCRIPTION
	       "The total number bytes transmitted by the FTP client
                since boot."
	::= { alStatsFtpClientGlobal 11 }

alFtpClientStatsOctetsRecv		OBJECT-TYPE
	SYNTAX			Counter32
	MAX-ACCESS		read-only
	STATUS			current
	DESCRIPTION
	       "The total number bytes received by the FTP client
                since boot."
	::= { alStatsFtpClientGlobal 12 }

alFtpClientStatsTimeouts		OBJECT-TYPE
	SYNTAX			Counter32
	MAX-ACCESS		read-only
	STATUS			current
	DESCRIPTION
	       "The total number of FTP client command/response timeouts
                since boot."
	::= { alStatsFtpClientGlobal 13 }

altigaFtpStatsMibConformance OBJECT IDENTIFIER ::= { altigaFtpStatsMibModule 1 }
altigaFtpStatsMibCompliances OBJECT IDENTIFIER ::= { altigaFtpStatsMibConformance 1 }

altigaFtpStatsMibCompliance MODULE-COMPLIANCE
   STATUS         current
   DESCRIPTION
      "The compliance statement for agents which 
       implement the Altiga FTP Statistics MIB."
   MODULE
   MANDATORY-GROUPS { 
      altigaFtpStatsGroup
   }
   ::= { altigaFtpStatsMibCompliances 1 }

altigaFtpStatsGroup OBJECT-GROUP
	OBJECTS
	{
		alFtpClientStatsMaxSess,
		alFtpClientStatsTotalSess,
		alFtpClientStatsGoodConns,
		alFtpClientStatsBadConns,
		alFtpClientStatsGoodDataConns,
		alFtpClientStatsBadDataConns,
		alFtpClientStatsGoodFileXfers,
		alFtpClientStatsBadFileXfers,
		alFtpClientStatsAsciiXfers,
		alFtpClientStatsBinaryXfers,
		alFtpClientStatsOctetsXmit,
		alFtpClientStatsOctetsRecv,
		alFtpClientStatsTimeouts
	}
	STATUS 	current
	DESCRIPTION
	       "The objects for Ftp statistics."
	::= { alFtpGroup 2 }

END
