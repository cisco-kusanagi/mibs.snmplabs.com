AISYSCFGTEMP-MIB DEFINITIONS ::= BEGIN

IMPORTS
    MODULE-IDENTITY, NOTIFICATION-TYPE, OBJECT-TYPE,
    Integer32,
    enterprises
					FROM SNMPv2-SMI
    DisplayString
					FROM SNMPv2-TC;

    aii OBJECT IDENTIFIER ::= {enterprises 539}
    aiSysCfg OBJECT IDENTIFIER ::= {aii 32}

aiSysCfgTemp MODULE-IDENTITY
    LAST-UPDATED "200104301700Z"
    ORGANIZATION "Applied Innovation Inc."
    CONTACT-INFO
"		Engineering MIB Administrator
		Postal: Applied Innovation Inc.
			5800 Innovation Drive
			Dublin, Ohio 43017-3271

		Tel:	614-798-2000
		Fax:	614-798-1770
		Email:	snmp@aiinet.com"
    DESCRIPTION
	"MIB module for Temperature Probes."
    REVISION "200104301700Z"
    DESCRIPTION "The initial revision of this module."
    ::= { aiSysCfg 5 }

-- Object definitions (Using "aiSCTemp" prefix)

aiSCTempTrapInfo OBJECT IDENTIFIER ::= { aiSysCfgTemp 0 }

aiSCTempTrapFail NOTIFICATION-TYPE
    OBJECTS	{ aiSCTempProbeIndex,
		  aiSCTempProbeTempCelsius }
    STATUS      current
    DESCRIPTION
	"Trap sent when a temperature probe reads a value outside its
	operational range."
    ::= { aiSCTempTrapInfo 1 }

aiSCTempTrapOk NOTIFICATION-TYPE
    OBJECTS	{ aiSCTempProbeIndex,
		  aiSCTempProbeTempCelsius }
    STATUS      current
    DESCRIPTION
	"Trap sent when a temperature probe reverts to its operational
	range from a failure mode."
    ::= { aiSCTempTrapInfo 2 }

aiSCTempAgregateStatus OBJECT-TYPE
    SYNTAX	INTEGER {okay(1), trouble(2)}
    MAX-ACCESS	read-only
    STATUS	current
    DESCRIPTION
	"Aggregate status of the temperature probes in the system."
    ::= { aiSysCfgTemp 1 }

aiSCTempProbeTable OBJECT-TYPE
    SYNTAX	SEQUENCE OF AiSCTempProbeEntry
    MAX-ACCESS	not-accessible
    STATUS	current
    DESCRIPTION
	"A table of information on each temperature probe in the
	system."
    ::= { aiSysCfgTemp 2 }

aiSCTempProbeEntry OBJECT-TYPE
    SYNTAX	AiSCTempProbeEntry
    MAX-ACCESS	not-accessible
    STATUS	current
    DESCRIPTION
	""
    INDEX { aiSCTempProbeIndex }
    ::= { aiSCTempProbeTable 1 }

AiSCTempProbeEntry ::=
    SEQUENCE {
	aiSCTempProbeIndex		Integer32,
	aiSCTempProbeDescription	DisplayString,
	aiSCTempProbeStatus		INTEGER,
	aiSCTempProbeLocation		INTEGER,
	aiSCTempProbeLowThreshCelsius	INTEGER,
	aiSCTempProbeHighThreshCelsius	INTEGER,
	aiSCTempProbeTempCelsius	INTEGER
    }

aiSCTempProbeIndex OBJECT-TYPE
    SYNTAX	Integer32 (1..2147483647)
    MAX-ACCESS	read-only
    STATUS	current
    DESCRIPTION
	"Self referential index into this table."
    ::= { aiSCTempProbeEntry 1 }

aiSCTempProbeDescription OBJECT-TYPE
    SYNTAX	DisplayString (SIZE (0..255))
    MAX-ACCESS	read-only
    STATUS	current
    DESCRIPTION
	"Description of the temperature probe to which this table
	entry refers."
    ::= { aiSCTempProbeEntry 2 }

aiSCTempProbeStatus OBJECT-TYPE
    SYNTAX	INTEGER { available(1), unavailable(2) }
    MAX-ACCESS	read-only
    STATUS	current
    DESCRIPTION
	"The state of this temperature probe.  available(1) indicates
	that the value returned in aiSCTempCelsius is valid."
    ::= { aiSCTempProbeEntry 3 }

aiSCTempProbeLocation OBJECT-TYPE
    SYNTAX	INTEGER { internal(1), external(2) }
    MAX-ACCESS	read-only
    STATUS	current
    DESCRIPTION
	"The location of this temperature probe.  It is either
	available or unavailable."
    ::= { aiSCTempProbeEntry 4 }

aiSCTempProbeLowThreshCelsius OBJECT-TYPE
    SYNTAX	INTEGER
    UNITS	"degrees Celsius"
    MAX-ACCESS	read-write
    STATUS	current
    DESCRIPTION
	"The lower threshold for this temperature probe (Celsius).
	When the temp drops below this value, an SNMP trap is sent."
    ::= { aiSCTempProbeEntry 5 }

aiSCTempProbeHighThreshCelsius OBJECT-TYPE
    SYNTAX	INTEGER
    UNITS	"degrees Celsius"
    MAX-ACCESS	read-write
    STATUS	current
    DESCRIPTION
	"The upper threshold for this temperature probe (Celsius).
	When the temp rises above this value, an SNMP trap is sent."
    ::= { aiSCTempProbeEntry 6 }

aiSCTempProbeTempCelsius OBJECT-TYPE
    SYNTAX	INTEGER
    UNITS	"degrees Celsius"
    MAX-ACCESS	read-only
    STATUS	current
    DESCRIPTION
	"The current temperature of this probe (Celsius)."
    ::= { aiSCTempProbeEntry 7 }

END
