-- extracted from draft-ietf-ipsec-flow-monitoring-mib-00.txt
-- at Sat Nov 20 07:06:56 1999

 IPsecT1-MIB DEFINITIONS ::= BEGIN

    IMPORTS
       MODULE-IDENTITY, OBJECT-TYPE, NOTIFICATION-TYPE,
       Counter32, Counter64, Gauge32, Integer32, enterprises
         FROM SNMPv2-SMI
       TEXTUAL-CONVENTION, DisplayString, TimeStamp, TimeInterval, TruthValue
         FROM SNMPv2-TC
       MODULE-COMPLIANCE, OBJECT-GROUP, NOTIFICATION-GROUP
         FROM SNMPv2-CONF;

    ipsecMIB MODULE-IDENTITY
       LAST-UPDATED "9911040000Z"
       ORGANIZATION "Tivoli Systems and Cisco Systems"
       CONTACT-INFO
          "Tivoli Systems
           Research Triangle Park, NC

           Cisco Systems
           San Jose, CA"
       DESCRIPTION
          "This is the MIB Module for objects to
           manage the IP Security Protocol."
       ::= { enterprises ibm(2) ibmProd(6) tivoliNma(168)
                                           iPsecMgmt(1)
                                           iPsecMgmtT1(1) 1 }

 -- ----------------------------------------------------------------------------
 -- Local Textual Conventions
 -- ----------------------------------------------------------------------------
    IPSIpAddress ::= TEXTUAL-CONVENTION
       STATUS     current
       DESCRIPTION
          "An IP V4 or V6 Address."
       SYNTAX  OCTET STRING(SIZE(4 | 16)) -- IP V4 or V6 Address

    IkePeerType  ::= TEXTUAL-CONVENTION
       STATUS     current
       DESCRIPTION
          "The type of ipsec Phase-1 IKE peer identity.  The IKE peer may be
           indentified by:
           1. an IP address, or
           2. a host name."
       SYNTAX INTEGER {
                 ipAddrPeer(1),
                 namePeer(2)
              }

    IkeNegoMode  ::= TEXTUAL-CONVENTION
       STATUS     current
       DESCRIPTION
          "The ipsec Phase-1 IKE negotiation mode."
       SYNTAX INTEGER {
                 main(1),
                 aggressive(2)
              }

    IkeHashAlgo   ::= TEXTUAL-CONVENTION
       STATUS     current
       DESCRIPTION
          "The hash algorithm used in ipsec Phase-1 IKE negotiations."
       SYNTAX INTEGER {
                 none(1),
                 md5(2),
                 sha(3)
              }

    IkeAuthMethod ::= TEXTUAL-CONVENTION
       STATUS     current
       DESCRIPTION
          "The authentication method used in ipsec Phase-1 IKE
           negotiations."
       SYNTAX INTEGER {
                 none(1),
                 preSharedKey(2),
                 rsaSig(3),
                 rsaEncrypt(4),
                 revPublicKey(5)
              }

    DiffHellmanGrp ::= TEXTUAL-CONVENTION
       STATUS     current
       DESCRIPTION
          "The Diffie Hellman Group used in negotiations."
       SYNTAX INTEGER {
                 none(1),
                 dhGroup1(2),
                 dhGroup2(3)
              }

    KeyType    ::= TEXTUAL-CONVENTION
       STATUS     current
       DESCRIPTION
          "The type of key used by an ipsec Phase-2 Tunnel."
       SYNTAX INTEGER{
                ike(1),
                manual(2)
              }

    EncapMode  ::= TEXTUAL-CONVENTION
       STATUS     current
       DESCRIPTION
          "The encapsulation mode used by an ipsec Phase-2 Tunnel."
       SYNTAX INTEGER{
                tunnel(1),
                transport(2)

              }

    EncryptAlgo   ::= TEXTUAL-CONVENTION
       STATUS     current
       DESCRIPTION
          "The encryption algorithm used in negotiations."
       SYNTAX INTEGER {
                 none(1),
                 des(2),
                 des3(3)
              }

    AuthAlgo      ::= TEXTUAL-CONVENTION
       STATUS     current
       DESCRIPTION
          "The authentication algorithm used by a
           security association of an ipsec Phase-2 Tunnel."
       SYNTAX INTEGER{
                 none(1),
                 hmacMd5(2),
                 hmacSha(3)
              }

    CompAlgo      ::= TEXTUAL-CONVENTION
       STATUS     current
       DESCRIPTION
          "The compression algorithm used by a
           security association of an ipsec Phase-2 Tunnel."
       SYNTAX INTEGER{
                 none(1),
                 ldf(2)
              }

    EndPtType     ::= TEXTUAL-CONVENTION
       STATUS     current
       DESCRIPTION
          "The type of identity use to specify an ipsec End Point."
       SYNTAX INTEGER {
                 singleIpAddr(1),
                 ipAddrRange(2),
                 ipSubnet(3)
              }

    TunnelStatus  ::= TEXTUAL-CONVENTION
       STATUS     current
       DESCRIPTION
          "The status of a Tunnel.  Objects of this type may
           be used to bring the tunnel down by setting
           value of this object to destroy(2).  Objects of this
           type cannot be used to create a Tunnel."
       SYNTAX INTEGER {
                 active(1),
                 destroy(2)
              }

    TrapStatus    ::= TEXTUAL-CONVENTION
       STATUS     current
       DESCRIPTION
          "The administrative status for sending a TRAP."
       SYNTAX INTEGER {
                 enabled(1),
                 disabled(2)
              }

 -- ----------------------------------------------------------------------------
 -- ipsec MIB Object Groups
 --
 -- This MIB module contains the following groups:
 -- 1) ipsec Levels Group
 -- 2) ipsec Phase-1 Group
 -- 3) ipsec Phase-2 Group
 -- 4) ipsec History Group
 -- 5) ipsec Failure Group
 -- 6) ipsec TRAP Control Group
 -- ----------------------------------------------------------------------------

    ipsecMIBObjects         OBJECT IDENTIFIER  ::= {ipsecMIB 1}

    ipsecLevels             OBJECT IDENTIFIER  ::= { ipsecMIBObjects 1 }
    ipsecPhaseOne           OBJECT IDENTIFIER  ::= { ipsecMIBObjects 2 }
    ipsecPhaseTwo           OBJECT IDENTIFIER  ::= { ipsecMIBObjects 3 }
    ipsecHistory            OBJECT IDENTIFIER  ::= { ipsecMIBObjects 4 }
    ipsecFailures           OBJECT IDENTIFIER  ::= { ipsecMIBObjects 5 }
    ipsecTrapCntl           OBJECT IDENTIFIER  ::= { ipsecMIBObjects 6 }

 -- ----------------------------------------------------------------------------
 -- ----------------------------------------------------------------------------
 -- ----------------------------------------------------------------------------
 -- ipsec Levels Group
 --
 -- This group consists of a:
 -- 1) ipsec MIB Level
 -- ----------------------------------------------------------------------------
 -- ----------------------------------------------------------------------------
 -- ----------------------------------------------------------------------------
    ipsecMibLevel OBJECT-TYPE
       SYNTAX Integer32
       MAX-ACCESS read-only
       STATUS current
       DESCRIPTION
          "The level of the ipsec MIB."
       ::= { ipsecLevels 1 }

 -- ----------------------------------------------------------------------------
 -- ----------------------------------------------------------------------------
 -- ----------------------------------------------------------------------------
 -- The ipsec Phase-1 Internet Key Exchange (IKE) Group
 --
 -- This group consists of:
 -- 1) ipsec Phase-1 Global Statistics
 -- 2) ipsec Phase-1 Peer Table
 -- 3) ipsec Phase-1 Tunnel Table
 -- 4) ipsec Phase-1 Correlation Table
 -- ----------------------------------------------------------------------------
 -- ----------------------------------------------------------------------------
 -- ----------------------------------------------------------------------------

 -- ----------------------------------------------------------------------------
 -- The ipsec Phase-1 Global Statistics
 -- ----------------------------------------------------------------------------
    ikeGlobalStats  OBJECT IDENTIFIER  ::= { ipsecPhaseOne 1 }

    ikeGlobalActiveTunnels OBJECT-TYPE
       SYNTAX Gauge32
       MAX-ACCESS read-only
       STATUS current
       DESCRIPTION
          "The number of currently active ipsec Phase-1 IKE Tunnels."
       ::= { ikeGlobalStats 1 }

    ikeGlobalPreviousTunnels OBJECT-TYPE
       SYNTAX Counter32
       MAX-ACCESS read-only
       STATUS current
       DESCRIPTION
          "The total number of previously active ipsec Phase-1 IKE Tunnels."
       ::= { ikeGlobalStats 2 }

    ikeGlobalInOctets OBJECT-TYPE
       SYNTAX Counter32
       MAX-ACCESS read-only
       STATUS current
       DESCRIPTION
          "The total number of octets received by all currently
           and previously active ipsec Phase-1 IKE Tunnels."
       ::= { ikeGlobalStats 3 }

    ikeGlobalInPkts OBJECT-TYPE
       SYNTAX Counter32
       MAX-ACCESS read-only
       STATUS current
       DESCRIPTION
          "The total number of packets received by all currently
           and previously active ipsec Phase-1 IKE Tunnels."
       ::= { ikeGlobalStats 4 }

    ikeGlobalInDropPkts OBJECT-TYPE
       SYNTAX Counter32
       MAX-ACCESS read-only
       STATUS current
       DESCRIPTION
          "The total number of packets which were dropped during
           receive processing by all currently and previously
           active ipsec Phase-1 IKE Tunnels."
       ::= { ikeGlobalStats 5 }

    ikeGlobalInNotifys OBJECT-TYPE
       SYNTAX Counter32
       MAX-ACCESS read-only
       STATUS current
       DESCRIPTION
          "The total number of notifys received by all currently
           and previously active ipsec Phase-1 IKE Tunnels."
       ::= { ikeGlobalStats 6 }

    ikeGlobalInP2Exchgs OBJECT-TYPE
       SYNTAX Counter32
       MAX-ACCESS read-only
       STATUS current
       DESCRIPTION
          "The total number of ipsec Phase-2 exchanges received
           by all currently and previously active ipsec Phase-1
           IKE Tunnels."
       ::= { ikeGlobalStats 7 }

    ikeGlobalInP2ExchgInvalids OBJECT-TYPE
       SYNTAX Counter32
       MAX-ACCESS read-only
       STATUS current
       DESCRIPTION
          "The total number of ipsec Phase-2 exchanges which were
           received and found to be invalid by all currently and
           previously active ipsec Phase-1 IKE Tunnels."
       ::= { ikeGlobalStats 8 }

    ikeGlobalInP2ExchgRejects OBJECT-TYPE
       SYNTAX Counter32
       MAX-ACCESS read-only
       STATUS current
       DESCRIPTION
          "The total number of ipsec Phase-2 exchanges which were
           received and rejected by all currently and
           previously active ipsec Phase-1 IKE Tunnels."
       ::= { ikeGlobalStats 9 }

    ikeGlobalInP2SaDelRequests OBJECT-TYPE
       SYNTAX Counter32
       MAX-ACCESS read-only
       STATUS current
       DESCRIPTION
          "The total number of ipsec Phase-2 security association
           delete requests received by all currently and previously
           active and ipsec Phase-1 IKE Tunnels."
       ::= { ikeGlobalStats 10 }

    ikeGlobalOutOctets OBJECT-TYPE
       SYNTAX Counter32
       MAX-ACCESS read-only
       STATUS current
       DESCRIPTION
          "The total number of octets sent by all currently
           and previously active and ipsec Phase-1 IKE Tunnels."
       ::= { ikeGlobalStats 11 }

    ikeGlobalOutPkts OBJECT-TYPE
       SYNTAX Counter32
       MAX-ACCESS read-only
       STATUS current
       DESCRIPTION
          "The total number of packets sent by all currently
           and previously active and ipsec Phase-1 IKE Tunnels."
       ::= { ikeGlobalStats 12 }

    ikeGlobalOutDropPkts OBJECT-TYPE
       SYNTAX Counter32
       MAX-ACCESS read-only
       STATUS current
       DESCRIPTION
          "The total number of packets which were dropped during
           send processing by all currently and previously
           active ipsec Phase-1 IKE Tunnels."
       ::= { ikeGlobalStats 13 }

    ikeGlobalOutNotifys OBJECT-TYPE
       SYNTAX Counter32
       MAX-ACCESS read-only
       STATUS current
       DESCRIPTION
          "The total number of notifys sent by all currently
           and previously active ipsec Phase-1 IKE Tunnels."
       ::= { ikeGlobalStats 14 }

    ikeGlobalOutP2Exchgs OBJECT-TYPE
       SYNTAX Counter32
       MAX-ACCESS read-only
       STATUS current
       DESCRIPTION
          "The total number of ipsec Phase-2 exchanges which were
           sent by all currently and previously active and ipsec
           Phase-1 IKE Tunnels."
       ::= { ikeGlobalStats 15 }

    ikeGlobalOutP2ExchgInvalids OBJECT-TYPE
       SYNTAX Counter32
       MAX-ACCESS read-only
       STATUS current
       DESCRIPTION
          "The total number of ipsec Phase-2 exchanges which were
           sent and found to be invalid by all currently and
           previously active ipsec Phase-1 IKE Tunnels."
       ::= { ikeGlobalStats 16 }

    ikeGlobalOutP2ExchgRejects OBJECT-TYPE
       SYNTAX Counter32
       MAX-ACCESS read-only
       STATUS current
       DESCRIPTION
          "The total number of ipsec Phase-2 exchanges which were
           sent and rejected by all currently and
           previously active ipsec Phase-1 IKE Tunnels."
       ::= { ikeGlobalStats 17 }

    ikeGlobalOutP2SaDelRequests OBJECT-TYPE
       SYNTAX Counter32
       MAX-ACCESS read-only
       STATUS current
       DESCRIPTION
          "The total number of ipsec Phase-2 security association
           delete requests sent by all currently and previously
           active ipsec Phase-1 IKE Tunnels."
       ::= { ikeGlobalStats 18 }

    ikeGlobalInitTunnels OBJECT-TYPE
       SYNTAX Counter32
       MAX-ACCESS read-only
       STATUS current
       DESCRIPTION
          "The total number of ipsec Phase-1 IKE Tunnels which were
           locally initiated."
       ::= { ikeGlobalStats 19 }

    ikeGlobalInitTunnelFails OBJECT-TYPE
       SYNTAX Counter32
       MAX-ACCESS read-only
       STATUS current
       DESCRIPTION
          "The total number of ipsec Phase-1 IKE Tunnels which were
           locally initiated and failed to activate."
       ::= { ikeGlobalStats 20 }

    ikeGlobalRespTunnelFails OBJECT-TYPE
       SYNTAX Counter32
       MAX-ACCESS read-only
       STATUS current
       DESCRIPTION
          "The total number of ipsec Phase-1 IKE Tunnels which were
           remotely initiated and failed to activate."
       ::= { ikeGlobalStats 21 }

    ikeGlobalSysCapFails OBJECT-TYPE
       SYNTAX Counter32
       MAX-ACCESS read-only
       STATUS current
       DESCRIPTION
          "The total number of system capcity failures which occurred
           during processing of all current and previously active and
           ipsec Phase-1 IKE Tunnels."
       ::= { ikeGlobalStats 22 }

    ikeGlobalAuthFails OBJECT-TYPE
       SYNTAX Counter32
       MAX-ACCESS read-only
       STATUS current
       DESCRIPTION
          "The total number of authentications which ended
           in failure by all current and previous ipsec Phase-1
           IKE Tunnels."
       ::= { ikeGlobalStats 23 }

    ikeGlobalDecryptFails OBJECT-TYPE
       SYNTAX Counter32
       MAX-ACCESS read-only
       STATUS current
       DESCRIPTION
          "The total number of decryptions which ended
           in failure by all current and previous ipsec Phase-1
           IKE Tunnels."
       ::= { ikeGlobalStats 24 }

    ikeGlobalHashValidFails OBJECT-TYPE
       SYNTAX Counter32
       MAX-ACCESS read-only
       STATUS current
       DESCRIPTION
          "The total number of hash validations which ended
           in failure by all current and previous ipsec Phase-1
           IKE Tunnels."
       ::= { ikeGlobalStats 25 }

    ikeGlobalNoSaFails OBJECT-TYPE
       SYNTAX Counter32
       MAX-ACCESS read-only
       STATUS current
       DESCRIPTION
          "The total number of non-existent Security Assocication
           in failures which occurred during processing of all current
           and previous ipsec Phase-1 IKE Tunnels."
       ::= { ikeGlobalStats 26 }

 -- ----------------------------------------------------------------------------
 -- The ipsec Phase-1 Internet Key Exchange Peer Table
 -- ----------------------------------------------------------------------------
    ikePeerTable OBJECT-TYPE
       SYNTAX SEQUENCE OF IkePeerEntry
       MAX-ACCESS not-accessible
       STATUS current
       DESCRIPTION
          "The ipsec Phase-1 Internet Key Exchange Peer Table.
           There is one entry in this table for each ipsec
           Phase-1 IKE peer association which is currently
           associated with an active ipsec Phase-2 Tunnel.
           The ipsec Phase-1 IKE Tunnel associated with this
           ipsec Phase-1 IKE peer association may or may not
           be currently active."
      ::= { ipsecPhaseOne 2 }

    ikePeerEntry OBJECT-TYPE
       SYNTAX IkePeerEntry
       MAX-ACCESS not-accessible
       STATUS current
       DESCRIPTION
             "Each entry contains the attributes associated with
              an ipsec Phase-1 IKE peer association."
       INDEX { ikePeerLocalType,
               ikePeerLocalValue,
               ikePeerRemoteType,
               ikePeerRemoteValue,
               ikePeerIntIndex }
       ::= { ikePeerTable 1}

    IkePeerEntry ::= SEQUENCE {
       ikePeerLocalType                IkePeerType,
       ikePeerLocalValue               DisplayString,
       ikePeerRemoteType               IkePeerType,
       ikePeerRemoteValue              DisplayString,
       ikePeerIntIndex                 Integer32,
       ikePeerLocalAddr                IPSIpAddress,
       ikePeerRemoteAddr               IPSIpAddress,
       ikePeerActiveTime               TimeInterval,
       ikePeerActiveTunnelIndex        Integer32
    }

    ikePeerLocalType OBJECT-TYPE
       SYNTAX IkePeerType
       MAX-ACCESS not-accessible
       STATUS current
       DESCRIPTION
          "The type of local peer identity.  The local peer may be
           indentified by:
           1. an IP address, or
           2. a host name."
       ::= { ikePeerEntry 1 }

    ikePeerLocalValue OBJECT-TYPE
       SYNTAX DisplayString
       MAX-ACCESS not-accessible
       STATUS current
       DESCRIPTION
          "The value of the local peer identity.

           If the local peer type is an IP Address, then this
           is the IP Address used to identify the local peer.

           If the local peer type is a host name, then this is
           the host name used to identify the local peer."
       ::= { ikePeerEntry 2 }

    ikePeerRemoteType OBJECT-TYPE
       SYNTAX IkePeerType
       MAX-ACCESS not-accessible
       STATUS current
       DESCRIPTION
          "The type of remote peer identity.  The remote peer may be
           indentified by:
           1. an IP address, or
           2. a host name."
       ::= { ikePeerEntry 3 }

    ikePeerRemoteValue OBJECT-TYPE
       SYNTAX DisplayString
       MAX-ACCESS not-accessible
       STATUS current
       DESCRIPTION
          "The value of the remote peer identity.

           If the remote peer type is an IP Address, then this
           is the IP Address used to identify the remote peer.

           If the remote peer type is a host name, then this is
           the host name used to identify the remote peer."
       ::= { ikePeerEntry 4 }

    ikePeerIntIndex OBJECT-TYPE
       SYNTAX Integer32
       MAX-ACCESS not-accessible
       STATUS current
       DESCRIPTION
          "The internal index of the local-remote peer association.
           This internal index is used to uniquely identify
           multiple associations between the local and remote peer."
       ::= { ikePeerEntry 5 }

    ikePeerLocalAddr OBJECT-TYPE
       SYNTAX IPSIpAddress
       MAX-ACCESS read-only
       STATUS current
       DESCRIPTION
          "The IP address of the local peer."
       ::= { ikePeerEntry 6 }

    ikePeerRemoteAddr OBJECT-TYPE
       SYNTAX IPSIpAddress
       MAX-ACCESS read-only
       STATUS current
       DESCRIPTION
          "The IP address of the remote peer."
       ::= { ikePeerEntry 7 }

    ikePeerActiveTime OBJECT-TYPE
       SYNTAX TimeInterval
       MAX-ACCESS read-only
       STATUS current
       DESCRIPTION
          "The length of time that the peer association has
           existed in hundredths of a second."
       ::= { ikePeerEntry 8 }

    ikePeerActiveTunnelIndex OBJECT-TYPE
       SYNTAX Integer32
       MAX-ACCESS read-only
       STATUS current
       DESCRIPTION
          "The index of the active ipsec Phase-1 IKE Tunnel
           (ikeTunIndex in the ikeTunnelTable) for this peer
           association.  If an ipsec Phase-1 IKE Tunnel is
           not currently active, then the value of this
           object will be zero."
       ::= { ikePeerEntry 9 }

 -- ----------------------------------------------------------------------------
 -- The ipsec Phase-1 Internet Key Exchange Tunnel Table
 -- ----------------------------------------------------------------------------
    ikeTunnelTable OBJECT-TYPE
       SYNTAX SEQUENCE OF IkeTunnelEntry
       MAX-ACCESS not-accessible
       STATUS current
       DESCRIPTION
          "The ipsec Phase-1 Internet Key Exchange Tunnel Table.
           There is one entry in this table for each active ipsec
           Phase-1 IKE Tunnel."
      ::= { ipsecPhaseOne 3 }

    ikeTunnelEntry OBJECT-TYPE
       SYNTAX IkeTunnelEntry
       MAX-ACCESS not-accessible
       STATUS current
       DESCRIPTION
             "Each entry contains the attributes associated with
              an active ipsec Phase-1 IKE Tunnel."
       INDEX { ikeTunIndex }
       ::= { ikeTunnelTable 1}

    IkeTunnelEntry ::= SEQUENCE {
       ikeTunIndex                 Integer32,
       ikeTunLocalType             IkePeerType,
       ikeTunLocalValue            DisplayString,
       ikeTunLocalAddr             IPSIpAddress,
       ikeTunLocalName             DisplayString,
       ikeTunRemoteType            IkePeerType,
       ikeTunRemoteValue           DisplayString,
       ikeTunRemoteAddr            IPSIpAddress,
       ikeTunRemoteName            DisplayString,
       ikeTunNegoMode              IkeNegoMode,
       ikeTunDiffHellmanGrp        DiffHellmanGrp,
       ikeTunEncryptAlgo           EncryptAlgo,
       ikeTunHashAlgo              IkeHashAlgo,
       ikeTunAuthMethod            IkeAuthMethod,
       ikeTunLifeTime              Integer32,
       ikeTunActiveTime            TimeInterval,
       ikeTunSaRefreshThreshold    Integer32,
       ikeTunTotalRefreshes        Counter32,
       ikeTunInOctets              Counter32,
       ikeTunInPkts                Counter32,
       ikeTunInDropPkts            Counter32,
       ikeTunInNotifys             Counter32,
       ikeTunInP2Exchgs            Counter32,
       ikeTunInP2ExchgInvalids     Counter32,
       ikeTunInP2ExchgRejects      Counter32,
       ikeTunInP2SaDelRequests     Counter32,
       ikeTunOutOctets             Counter32,
       ikeTunOutPkts               Counter32,
       ikeTunOutDropPkts           Counter32,
       ikeTunOutNotifys            Counter32,
       ikeTunOutP2Exchgs           Counter32,
       ikeTunOutP2ExchgInvalids    Counter32,
       ikeTunOutP2ExchgRejects     Counter32,
       ikeTunOutP2SaDelRequests    Counter32,
       ikeTunStatus                TunnelStatus
    }

    ikeTunIndex OBJECT-TYPE
       SYNTAX Integer32
       MAX-ACCESS not-accessible
       STATUS current
       DESCRIPTION
          "The index of the ipsec Phase-1 IKE Tunnel Table.
           The value of the index is a number which begins at one and
           is incremented with each tunnel that is created. The value
           of this object will wrap at 2,147,483,647."
       ::= { ikeTunnelEntry 1 }

    ikeTunLocalType OBJECT-TYPE
       SYNTAX IkePeerType
       MAX-ACCESS read-only
       STATUS current
       DESCRIPTION
          "The type of local peer identity.  The local peer may be
           indentified by:
           1. an IP address, or
           2. a host name."
       ::= { ikeTunnelEntry 2 }

    ikeTunLocalValue OBJECT-TYPE
       SYNTAX DisplayString
       MAX-ACCESS read-only
       STATUS current
       DESCRIPTION
          "The value of the local peer identity.

           If the local peer type is an IP Address, then this
           is the IP Address used to identify the local peer.

           If the local peer type is a host name, then this is
           the host name used to identify the local peer."
       ::= { ikeTunnelEntry 3 }

    ikeTunLocalAddr OBJECT-TYPE
       SYNTAX IPSIpAddress
       MAX-ACCESS read-only
       STATUS current
       DESCRIPTION
          "The IP address of the local endpoint for the ipsec
           Phase-1 IKE Tunnel."
       ::= { ikeTunnelEntry 4 }

    ikeTunLocalName OBJECT-TYPE
       SYNTAX DisplayString
       MAX-ACCESS read-only
       STATUS current
       DESCRIPTION
          "The DNS name of the local IP address for the ipsec Phase-1
           IKE Tunnel. If the DNS name associated with the local
           tunnel endpoint is not known, then the value of this
           object will be a NULL string."
       ::= { ikeTunnelEntry 5 }

    ikeTunRemoteType OBJECT-TYPE
       SYNTAX IkePeerType
       MAX-ACCESS read-only
       STATUS current
       DESCRIPTION
          "The type of remote peer identity.  The remote peer may be
           indentified by:
           1. an IP address, or
           2. a host name."
       ::= { ikeTunnelEntry 6 }

    ikeTunRemoteValue OBJECT-TYPE
       SYNTAX DisplayString
       MAX-ACCESS read-only
       STATUS current
       DESCRIPTION
          "The value of the remote peer identity.

           If the remote peer type is an IP Address, then this
           is the IP Address used to identify the remote peer.

           If the remote peer type is a host name, then this is
           the host name used to identify the remote peer."
       ::= { ikeTunnelEntry 7 }

    ikeTunRemoteAddr OBJECT-TYPE
       SYNTAX IPSIpAddress
       MAX-ACCESS read-only
       STATUS current
       DESCRIPTION
          "The IP address of the remote endpoint for the ipsec
           Phase-1 IKE Tunnel."
       ::= { ikeTunnelEntry 8 }

    ikeTunRemoteName OBJECT-TYPE
       SYNTAX DisplayString
       MAX-ACCESS read-only
       STATUS current
       DESCRIPTION
          "The DNS name of the remote IP address of ipsec Phase-1
           IKE Tunnel. If the DNS name associated with the remote
           tunnel endpoint is not known, then the value of this
           object will be a NULL string."
       ::= { ikeTunnelEntry 9 }

    ikeTunNegoMode OBJECT-TYPE
       SYNTAX IkeNegoMode
       MAX-ACCESS read-only
       STATUS current
       DESCRIPTION
          "The negotiation mode of the ipsec Phase-1 IKE Tunnel."
       ::= { ikeTunnelEntry 10 }

    ikeTunDiffHellmanGrp OBJECT-TYPE
       SYNTAX DiffHellmanGrp
       MAX-ACCESS read-only
       STATUS current
       DESCRIPTION
          "The Diffie Hellman Group used in ipsec Phase-1 IKE
           negotiations."
       ::= { ikeTunnelEntry 11 }

    ikeTunEncryptAlgo OBJECT-TYPE
       SYNTAX EncryptAlgo
       MAX-ACCESS read-only
       STATUS current
       DESCRIPTION
          "The encryption algorithm used in ipsec Phase-1 IKE
           negotiations."
       ::= { ikeTunnelEntry 12 }

    ikeTunHashAlgo OBJECT-TYPE
       SYNTAX IkeHashAlgo
       MAX-ACCESS read-only
       STATUS current
       DESCRIPTION
          "The hash algorithm used in ipsec Phase-1 IKE
           negotiations."
       ::= { ikeTunnelEntry 13 }

    ikeTunAuthMethod OBJECT-TYPE
       SYNTAX IkeAuthMethod
       MAX-ACCESS read-only
       STATUS current
       DESCRIPTION
          "The authentication method used in ipsec Phase-1 IKE
           negotiations."
       ::= { ikeTunnelEntry 14 }

    ikeTunLifeTime OBJECT-TYPE
       SYNTAX Integer32
       MAX-ACCESS read-only
       STATUS current
       DESCRIPTION
          "The negotiated LifeTime of the ipsec Phase-1 IKE Tunnel
           in seconds."
       ::= { ikeTunnelEntry 15 }

    ikeTunActiveTime OBJECT-TYPE
       SYNTAX TimeInterval
       MAX-ACCESS read-only
       STATUS current
       DESCRIPTION
          "The length of time the ipsec Phase-1 IKE tunnel has been
           active in hundredths of seconds."
       ::= { ikeTunnelEntry 16 }

    ikeTunSaRefreshThreshold OBJECT-TYPE
       SYNTAX Integer32
       MAX-ACCESS read-only
       STATUS current
       DESCRIPTION
          "The security assoication refresh threshold in seconds."
       ::= { ikeTunnelEntry 17 }

    ikeTunTotalRefreshes OBJECT-TYPE
       SYNTAX Counter32
       MAX-ACCESS read-only
       STATUS current
       DESCRIPTION
          "The total number of security associations refreshes performed."
       ::= { ikeTunnelEntry 18 }

    ikeTunInOctets OBJECT-TYPE
       SYNTAX Counter32
       MAX-ACCESS read-only
       STATUS current
       DESCRIPTION
          "The total number of octets received by this ipsec Phase-1
           IKE Tunnel."
       ::= { ikeTunnelEntry 19 }

    ikeTunInPkts OBJECT-TYPE
       SYNTAX Counter32
       MAX-ACCESS read-only
       STATUS current
       DESCRIPTION
          "The total number of packets received by this ipsec Phase-1
           IKE Tunnel."
       ::= { ikeTunnelEntry 20 }

    ikeTunInDropPkts OBJECT-TYPE
       SYNTAX Counter32
       MAX-ACCESS read-only
       STATUS current
       DESCRIPTION
          "The total number of packets dropped by this ipsec Phase-1
           IKE Tunnel during receive processing."
       ::= { ikeTunnelEntry 21 }

    ikeTunInNotifys OBJECT-TYPE
       SYNTAX Counter32
       MAX-ACCESS read-only
       STATUS current
       DESCRIPTION
          "The total number of notifys received by this ipsec Phase-1
           IKE Tunnel."
       ::= { ikeTunnelEntry 22 }

    ikeTunInP2Exchgs OBJECT-TYPE
       SYNTAX Counter32
       MAX-ACCESS read-only
       STATUS current
       DESCRIPTION
          "The total number of ipsec Phase-2 exchanges received by
           this ipsec Phase-1 IKE Tunnel."
       ::= { ikeTunnelEntry 23 }

    ikeTunInP2ExchgInvalids OBJECT-TYPE
       SYNTAX Counter32
       MAX-ACCESS read-only
       STATUS current
       DESCRIPTION
          "The total number of ipsec Phase-2 exchanges received and
           found to be invalid by this ipsec Phase-1 IKE Tunnel."
       ::= { ikeTunnelEntry 24 }

    ikeTunInP2ExchgRejects OBJECT-TYPE
       SYNTAX Counter32
       MAX-ACCESS read-only
       STATUS current
       DESCRIPTION
          "The total number of ipsec Phase-2 exchanges received and
           rejected by this ipsec Phase-1 IKE Tunnel."
       ::= { ikeTunnelEntry 25 }

    ikeTunInP2SaDelRequests OBJECT-TYPE
       SYNTAX Counter32
       MAX-ACCESS read-only
       STATUS current
       DESCRIPTION
          "The total number of ipsec Phase-2 security association
           delete requests received by this ipsec Phase-1 IKE Tunnel."
       ::= { ikeTunnelEntry 26 }

    ikeTunOutOctets OBJECT-TYPE
       SYNTAX Counter32
       MAX-ACCESS read-only
       STATUS current
       DESCRIPTION
          "The total number of octets sent by this ipsec Phase-1
           IKE Tunnel."
       ::= { ikeTunnelEntry 27 }

    ikeTunOutPkts OBJECT-TYPE
       SYNTAX Counter32
       MAX-ACCESS read-only
       STATUS current
       DESCRIPTION
          "The total number of packets sent by this ipsec Phase-1
           IKE Tunnel."
       ::= { ikeTunnelEntry 28 }

    ikeTunOutDropPkts OBJECT-TYPE
       SYNTAX Counter32
       MAX-ACCESS read-only
       STATUS current
       DESCRIPTION
          "The total number of packets dropped by this ipsec Phase-1
           IKE Tunnel during send processing."
       ::= { ikeTunnelEntry 29 }

    ikeTunOutNotifys OBJECT-TYPE
       SYNTAX Counter32
       MAX-ACCESS read-only
       STATUS current
       DESCRIPTION
          "The total number of notifys sent by this ipsec Phase-1
           IKE Tunnel."
       ::= { ikeTunnelEntry 30 }

    ikeTunOutP2Exchgs OBJECT-TYPE
       SYNTAX Counter32
       MAX-ACCESS read-only
       STATUS current
       DESCRIPTION
          "The total number of ipsec Phase-2 exchanges sent by
           this ipsec Phase-1 IKE Tunnel."
       ::= { ikeTunnelEntry 31 }

    ikeTunOutP2ExchgInvalids OBJECT-TYPE
       SYNTAX Counter32
       MAX-ACCESS read-only
       STATUS current
       DESCRIPTION
          "The total number of ipsec Phase-2 exchanges sent and
           found to be invalid by this ipsec Phase-1 IKE Tunnel."
       ::= { ikeTunnelEntry 32 }

    ikeTunOutP2ExchgRejects OBJECT-TYPE
       SYNTAX Counter32
       MAX-ACCESS read-only
       STATUS current
       DESCRIPTION
          "The total number of ipsec Phase-2 exchanges sent and
           rejected by this ipsec Phase-1 IKE Tunnel."
       ::= { ikeTunnelEntry 33 }

    ikeTunOutP2SaDelRequests OBJECT-TYPE
       SYNTAX Counter32
       MAX-ACCESS read-only
       STATUS current
       DESCRIPTION
          "The total number of ipsec Phase-2 security association
           delete requests sent by this ipsec Phase-1 IKE Tunnel."
       ::= { ikeTunnelEntry 34 }

    ikeTunStatus OBJECT-TYPE
       SYNTAX TunnelStatus
       MAX-ACCESS read-write
       STATUS current
       DESCRIPTION
          "The status of the MIB table row.

           This object can be used to bring the tunnel down by setting
           value of this object to destroy(2).

           This object cannot be used to create a MIB table row."
       ::= { ikeTunnelEntry 35 }

 -- ----------------------------------------------------------------------------
 -- The Internet Key Exchange Peer Association to Phase-2 Tunnel
 -- Correlation Table
 -- ----------------------------------------------------------------------------
    ikePeerCorrTable OBJECT-TYPE
       SYNTAX SEQUENCE OF IkePeerCorrEntry
       MAX-ACCESS not-accessible
       STATUS current
       DESCRIPTION
          "The ipsec Phase-1 Internet Key Exchange Peer Association to
           ipsec Phase-2 Tunnel Correlation Table.
           There is one entry in this table for each active ipsec
           Phase-2 Tunnel."
      ::= { ipsecPhaseOne 4 }

    ikePeerCorrEntry OBJECT-TYPE
       SYNTAX IkePeerCorrEntry
       MAX-ACCESS not-accessible
       STATUS current
       DESCRIPTION
             "Each entry contains the attributes of an an ipsec Phase-1
              IKE Peer Association to ipsec Phase-2 Tunnel Correlation."
       INDEX { ikePeerCorrLocalType,
               ikePeerCorrLocalValue,
               ikePeerCorrRemoteType,
               ikePeerCorrRemoteValue,
               ikePeerCorrIntIndex,
               ikePeerCorrSeqNum  }
       ::= { ikePeerCorrTable 1}

    IkePeerCorrEntry ::= SEQUENCE {
       ikePeerCorrLocalType                IkePeerType,
       ikePeerCorrLocalValue               DisplayString,
       ikePeerCorrRemoteType               IkePeerType,
       ikePeerCorrRemoteValue              DisplayString,
       ikePeerCorrIntIndex                 Integer32,
       ikePeerCorrSeqNum                   Integer32,
       ikePeerCorripsecTunIndex            Integer32
    }

    ikePeerCorrLocalType OBJECT-TYPE
       SYNTAX IkePeerType
       MAX-ACCESS not-accessible
       STATUS current
       DESCRIPTION
          "The type of local peer identity.  The local peer may be
           indentified by:
           1. an IP address, or
           2. a host name."
       ::= { ikePeerCorrEntry 1 }

    ikePeerCorrLocalValue OBJECT-TYPE
       SYNTAX DisplayString
       MAX-ACCESS not-accessible
       STATUS current
       DESCRIPTION
          "The value of the local peer identity.

           If the local peer type is an IP Address, then this
           is the IP Address used to identify the local peer.

           If the local peer type is a host name, then this is
           the host name used to identify the local peer."
       ::= { ikePeerCorrEntry 2 }

    ikePeerCorrRemoteType OBJECT-TYPE
       SYNTAX IkePeerType
       MAX-ACCESS not-accessible
       STATUS current
       DESCRIPTION
          "The type of remote peer identity.  The remote peer may be
           indentified by:
           1. an IP address, or
           2. a host name."
       ::= { ikePeerCorrEntry 3 }

    ikePeerCorrRemoteValue OBJECT-TYPE
       SYNTAX DisplayString
       MAX-ACCESS not-accessible
       STATUS current
       DESCRIPTION
          "The value of the remote peer identity.

           If the remote peer type is an IP Address, then this
           is the IP Address used to identify the remote peer.

           If the remote peer type is a host name, then this is
           the host name used to identify the remote peer."
       ::= { ikePeerCorrEntry 4 }

    ikePeerCorrIntIndex OBJECT-TYPE
       SYNTAX Integer32
       MAX-ACCESS not-accessible
       STATUS current
       DESCRIPTION
          "The internal index of the local-remote peer association.
           This internal index is used to uniquely identify
           multiple associations between the local and remote peer."
       ::= { ikePeerCorrEntry 5 }

    ikePeerCorrSeqNum   OBJECT-TYPE
       SYNTAX Integer32
       MAX-ACCESS not-accessible
       STATUS current
       DESCRIPTION
          "The sequence number of the local-remote peer association.
           This sequence number is used to uniquely identify
           multiple instances of an unique association between
           the local and remote peer."
       ::= { ikePeerCorrEntry 6 }

    ikePeerCorripsecTunIndex OBJECT-TYPE
       SYNTAX Integer32
       MAX-ACCESS read-only
       STATUS current
       DESCRIPTION
          "The index of the active ipsec Phase-2 Tunnel
           (ipsecTunIndex in the ipsecTunnelTable) for this
           ipsec Phase-1 IKE Peer Association."
       ::= { ikePeerCorrEntry 7 }

 -- -------------------------------------------------------------------------
 -- ----------------------------------------------------------------------------
 -- ----------------------------------------------------------------------------
 -- ipsec Phase-2 Group
 --
 -- This group consists of:
 -- 1) ipsec Phase-2 Global Statistics
 -- 2) ipsec Phase-2 Tunnel Table
 -- 3) ipsec Phase-2 Endpoint Table
 -- 4) ipsec Phase-2 Security Protection Index Table
 -- 4) ipsec Phase-2 Security Protection Index Objects
 -- -------------------------------------------------------------------------
 -- ----------------------------------------------------------------------------
 -- ----------------------------------------------------------------------------

 -- ----------------------------------------------------------------------------
 -- The ipsec Phase-2 Global Tunnel Statistics
 -- ----------------------------------------------------------------------------
    ipsecGlobalStats          OBJECT IDENTIFIER ::= { ipsecPhaseTwo 1 }

    ipsecGlobalActiveTunnels OBJECT-TYPE
       SYNTAX Gauge32
       MAX-ACCESS read-only
       STATUS current
       DESCRIPTION
          "The total number of currently active ipsec Phase-2 Tunnels."
       ::= { ipsecGlobalStats 1 }

    ipsecGlobalPreviousTunnels OBJECT-TYPE
       SYNTAX Counter32
       MAX-ACCESS read-only
       STATUS current
       DESCRIPTION
          "The total number of previously active ipsec Phase-2 Tunnels."
       ::= { ipsecGlobalStats 2 }

    ipsecGlobalInOctets OBJECT-TYPE
       SYNTAX Counter32
       MAX-ACCESS read-only
       STATUS current
       DESCRIPTION
          "The total number of octets received by all current and previous
           ipsec Phase-2 Tunnels.  This value is accumulated
           BEFORE determining whether or not the packet should be
           decompressed.  See also ipsecGlobalInOctWraps for the
           number of times this counter has wrapped."
       ::= { ipsecGlobalStats 3 }

    ipsecGlobalHcInOctets OBJECT-TYPE
       SYNTAX Counter64
       MAX-ACCESS read-only
       STATUS current
       DESCRIPTION
          "A high capacity count of the total number of octets received
           by all current and previous ipsec Phase-2 Tunnels.
           This value is accumulated BEFORE determining whether or
           not the packet should be decompressed."
       ::= { ipsecGlobalStats 4 }

    ipsecGlobalInOctWraps OBJECT-TYPE
       SYNTAX Counter32
       MAX-ACCESS read-only
       STATUS current
       DESCRIPTION
          "The number of times the global octets received counter
           (ipsecGlobalInOctets) has wrapped."
       ::= { ipsecGlobalStats 5 }

    ipsecGlobalInDecompOctets OBJECT-TYPE
       SYNTAX Counter32
       MAX-ACCESS read-only
       STATUS current
       DESCRIPTION
          "The total number of decompressed octets received by all
           current and previous ipsec Phase-2 Tunnels.  This value is
           accumulated AFTER the packet is decompressed. If compression
           is not being used, this value will match the value of
           ipsecGlobalInOctets. See also ipsecGlobalInDecompOctWraps
           for the number of times this counter has wrapped."
       ::= { ipsecGlobalStats 6 }

    ipsecGlobalHcInDecompOctets OBJECT-TYPE
       SYNTAX Counter64
       MAX-ACCESS read-only
       STATUS current
       DESCRIPTION
          "A high capacity count of the total number of decompressed
           octets received by all current and previous ipsec Phase-2 Tunnels.
           This value is accumulated AFTER the packet is decompressed.
           If compression is not being used, this value will match the
           value of ipsecGlobalHcInOctets."
       ::= { ipsecGlobalStats 7 }

    ipsecGlobalInDecompOctWraps OBJECT-TYPE
       SYNTAX Counter32
       MAX-ACCESS read-only
       STATUS current
       DESCRIPTION
          "The number of times the global decompressed octets received counter
           (ipsecGlobalInDecompOctets) has wrapped."
       ::= { ipsecGlobalStats 8 }

    ipsecGlobalInPkts OBJECT-TYPE
       SYNTAX Counter32
       MAX-ACCESS read-only
       STATUS current
       DESCRIPTION
          "The total number of packets received by all current and previous
           ipsec Phase-2 Tunnels."
       ::= { ipsecGlobalStats 9 }

    ipsecGlobalInDrops OBJECT-TYPE
       SYNTAX Counter32
       MAX-ACCESS read-only
       STATUS current
       DESCRIPTION
          "The total number of packets dropped during receive processing
           by all current and previous ipsec Phase-2 Tunnels. This count does
           NOT include packets dropped due to Anti-Replay processing."
       ::= { ipsecGlobalStats 10 }

    ipsecGlobalInReplayDrops OBJECT-TYPE
       SYNTAX Counter32
       MAX-ACCESS read-only
       STATUS current
       DESCRIPTION
          "The total number of packets dropped during receive processing
           due to Anti-Replay processing by all current and previous ipsec
           Phase-2 Tunnels."
       ::= { ipsecGlobalStats 11 }

    ipsecGlobalInAuths OBJECT-TYPE
       SYNTAX Counter32
       MAX-ACCESS read-only
       STATUS current
       DESCRIPTION
          "The total number of inbound authentication's performed
           by all current and previous ipsec Phase-2 Tunnels."
       ::= { ipsecGlobalStats 12 }

    ipsecGlobalInAuthFails OBJECT-TYPE
       SYNTAX Counter32
       MAX-ACCESS read-only
       STATUS current
       DESCRIPTION
          "The total number of inbound authentication's which ended in failure
           by all current and previous ipsec Phase-2 Tunnels."
       ::= { ipsecGlobalStats 13 }

    ipsecGlobalInDecrypts OBJECT-TYPE
       SYNTAX Counter32
       MAX-ACCESS read-only
       STATUS current
       DESCRIPTION
          "The total number of inbound decryption's performed
           by all current and previous ipsec Phase-2 Tunnels."
       ::= { ipsecGlobalStats 14 }

    ipsecGlobalInDecryptFails OBJECT-TYPE
       SYNTAX Counter32
       MAX-ACCESS read-only
       STATUS current
       DESCRIPTION
          "The total number of inbound decryption's which ended in failure
           by all current and previous ipsec Phase-2 Tunnels."
       ::= { ipsecGlobalStats 15 }

    ipsecGlobalOutOctets OBJECT-TYPE
       SYNTAX Counter32
       MAX-ACCESS read-only
       STATUS current
       DESCRIPTION
          "The total number of octets sent by all current and previous
           ipsec Phase-2 Tunnels.  This value is accumulated
           AFTER determining whether or not the packet should be
           compressed.  See also ipsecGlobalOutOctWraps for the
           number of times this counter has wrapped."
       ::= { ipsecGlobalStats 16 }

    ipsecGlobalHcOutOctets OBJECT-TYPE
       SYNTAX Counter64
       MAX-ACCESS read-only
       STATUS current
       DESCRIPTION
          "A high capacity count of the total number of octets
           sent by all current and previous ipsec Phase-2 Tunnels.
           This value is accumulated AFTER determining whether or
           not the packet should be compressed."
       ::= { ipsecGlobalStats 17 }

    ipsecGlobalOutOctWraps OBJECT-TYPE
       SYNTAX Counter32
       MAX-ACCESS read-only
       STATUS current
       DESCRIPTION
          "The number of times the global octets sent counter
           (ipsecGlobalOutOctets) has wrapped."
       ::= { ipsecGlobalStats 18 }

    ipsecGlobalOutUncompOctets OBJECT-TYPE
       SYNTAX Counter32
       MAX-ACCESS read-only
       STATUS current
       DESCRIPTION
          "The total number of uncompressed octets sent by all current
           and previous ipsec Phase-2 Tunnels.  This value is accumulated BEFORE
           the packet is compressed. If compression is not being
           used, this value will match the value of ipsecGlobalOutOctets.
           See also ipsecGlobalOutDecompOctWraps for the number of times
           this counter has wrapped."
       ::= { ipsecGlobalStats 19 }

    ipsecGlobalHcOutUncompOctets OBJECT-TYPE
       SYNTAX Counter64
       MAX-ACCESS read-only
       STATUS current
       DESCRIPTION
          "A high capacity count of the total number of uncompressed
           octets sent by all current and previous ipsec Phase-2 Tunnels.
           This value is accumulated BEFORE the packet is compressed.
           If compression is not being used, this value will match the
           value of ipsecGlobalHcOutOctets."
       ::= { ipsecGlobalStats 20 }

    ipsecGlobalOutUncompOctWraps OBJECT-TYPE
       SYNTAX Counter32
       MAX-ACCESS read-only
       STATUS current
       DESCRIPTION
          "The number of times the global uncompressed octets sent counter
           (ipsecGlobalInUncompOctets) has wrapped."
       ::= { ipsecGlobalStats 21 }

    ipsecGlobalOutPkts OBJECT-TYPE
       SYNTAX Counter32
       MAX-ACCESS read-only
       STATUS current
       DESCRIPTION
          "The total number of packets sent by all current and previous
           ipsec Phase-2 Tunnels."
       ::= { ipsecGlobalStats 22 }

    ipsecGlobalOutDrops OBJECT-TYPE
       SYNTAX Counter32
       MAX-ACCESS read-only
       STATUS current
       DESCRIPTION
          "The total number of packets dropped during send processing
           by all current and previous ipsec Phase-2 Tunnels."
       ::= { ipsecGlobalStats 23 }

    ipsecGlobalOutAuths OBJECT-TYPE
       SYNTAX Counter32
       MAX-ACCESS read-only
       STATUS current
       DESCRIPTION
          "The total number of outbound authentication's performed
           by all current and previous ipsec Phase-2 Tunnels."
       ::= { ipsecGlobalStats 24 }

    ipsecGlobalOutAuthFails OBJECT-TYPE
       SYNTAX Counter32
       MAX-ACCESS read-only
       STATUS current
       DESCRIPTION
          "The total number of outbound authentication's which ended in failure
           by all current and previous ipsec Phase-2 Tunnels."
       ::= { ipsecGlobalStats 25 }

    ipsecGlobalOutEncrypts OBJECT-TYPE
       SYNTAX Counter32
       MAX-ACCESS read-only
       STATUS current
       DESCRIPTION
          "The total number of outbound encryption's performed
           by all current and previous ipsec Phase-2 Tunnels."
       ::= { ipsecGlobalStats 26 }

    ipsecGlobalOutEncryptFails OBJECT-TYPE
       SYNTAX Counter32
       MAX-ACCESS read-only
       STATUS current
       DESCRIPTION
          "The total number of outbound encryption's which ended in failure
           by all current and previous ipsec Phase-2 Tunnels."
       ::= { ipsecGlobalStats 27 }

    ipsecGlobalProtocolUseFails OBJECT-TYPE
       SYNTAX Counter32
       MAX-ACCESS read-only
       STATUS current
       DESCRIPTION
          "The total number of protocol use failures which occurred
           during processing of all current and previously active and
           ipsec Phase-2 Tunnels."
       ::= { ikeGlobalStats 28 }

    ipsecGlobalNoSaFails OBJECT-TYPE
       SYNTAX Counter32
       MAX-ACCESS read-only
       STATUS current
       DESCRIPTION
          "The total number of non-existent Security Assocication
           in failures which occurred during processing of all current
           and previous ipsec Phase-2 Tunnels."
       ::= { ikeGlobalStats 29 }

    ipsecGlobalSysCapFails OBJECT-TYPE
       SYNTAX Counter32
       MAX-ACCESS read-only
       STATUS current
       DESCRIPTION
          "The total number of system capcity failures which occurred
           during processing of all current and previously active and
           ipsec Phase-2 Tunnels."
       ::= { ikeGlobalStats 30 }

 -- ----------------------------------------------------------------------------
 -- The ipsec Phase-2 Tunnel Table
 -- ----------------------------------------------------------------------------
    ipsecTunnelTable OBJECT-TYPE
       SYNTAX SEQUENCE OF IPsecTunnelEntry
       MAX-ACCESS not-accessible
       STATUS current
       DESCRIPTION
          "The ipsec Phase-2 Tunnel Table.  There is one entry in
           this table for each active ipsec Phase-2 Tunnel."
       ::= { ipsecPhaseTwo 2 }

    ipsecTunnelEntry OBJECT-TYPE
       SYNTAX IPsecTunnelEntry
       MAX-ACCESS not-accessible
       STATUS current
       DESCRIPTION
          "Each entry contains the attributes associated with
           an active ipsec Phase-2 Tunnel."
       INDEX { ipsecTunIndex }
       ::= { ipsecTunnelTable 1 }

    IPsecTunnelEntry ::= SEQUENCE {
       ipsecTunIndex                Integer32,
       ipsecTunIkeTunnelIndex       Integer32,
       ipsecTunIkeTunnelAlive       TruthValue,
       ipsecTunLocalAddr            IPSIpAddress,
       ipsecTunRemoteAddr           IPSIpAddress,
       ipsecTunKeyType              KeyType,
       ipsecTunEncapMode            EncapMode,
       ipsecTunLifeSize             Integer32,
       ipsecTunLifeTime             Integer32,
       ipsecTunActiveTime           TimeInterval,
       ipsecTunSaLifeSizeThreshold  Integer32,
       ipsecTunSaLifeTimeThreshold  Integer32,
       ipsecTunTotalRefreshes       Counter32,
       ipsecTunExpiredSaInstances   Counter32,
       ipsecTunCurrentSaInstances   Gauge32,
       ipsecTunInSaDiffHellmanGrp   DiffHellmanGrp,
       ipsecTunInSaEncryptAlgo      EncryptAlgo,
       ipsecTunInSaAhAuthAlgo       AuthAlgo,
       ipsecTunInSaEspAuthAlgo      AuthAlgo,
       ipsecTunInSaDecompAlgo       CompAlgo,
       ipsecTunOutSaDiffHellmanGrp  DiffHellmanGrp,
       ipsecTunOutSaEncryptAlgo     EncryptAlgo,
       ipsecTunOutSaAhAuthAlgo      AuthAlgo,
       ipsecTunOutSaEspAuthAlgo     AuthAlgo,
       ipsecTunOutSaCompAlgo        CompAlgo,
       ipsecTunInOctets             Counter32,
       ipsecTunHcInOctets           Counter64,
       ipsecTunInOctWraps           Counter32,
       ipsecTunInDecompOctets       Counter32,
       ipsecTunHcInDecompOctets     Counter64,
       ipsecTunInDecompOctWraps     Counter32,
       ipsecTunInPkts               Counter32,
       ipsecTunInDropPkts           Counter32,
       ipsecTunInReplayDropPkts     Counter32,
       ipsecTunInAuths              Counter32,
       ipsecTunInAuthFails          Counter32,
       ipsecTunInDecrypts           Counter32,
       ipsecTunInDecryptFails       Counter32,
       ipsecTunOutOctets            Counter32,
       ipsecTunHcOutOctets          Counter64,
       ipsecTunOutOctWraps          Counter32,
       ipsecTunOutUncompOctets      Counter32,
       ipsecTunHcOutUncompOctets    Counter64,
       ipsecTunOutUncompOctWraps    Counter32,
       ipsecTunOutPkts              Counter32,
       ipsecTunOutDropPkts          Counter32,
       ipsecTunOutAuths             Counter32,
       ipsecTunOutAuthFails         Counter32,
       ipsecTunOutEncrypts          Counter32,
       ipsecTunOutEncryptFails      Counter32,
       ipsecTunStatus               TunnelStatus
    }

    ipsecTunIndex OBJECT-TYPE
       SYNTAX Integer32
       MAX-ACCESS not-accessible
       STATUS current
       DESCRIPTION
          "The index of the ipsec Phase-2 Tunnel Table.
           The value of the index is a number which begins at one and
           is incremented with each tunnel that is created. The value
           of this object will wrap at 2,147,483,647."
       ::= { ipsecTunnelEntry 1 }

    ipsecTunIkeTunnelIndex OBJECT-TYPE
       SYNTAX Integer32
       MAX-ACCESS read-only
       STATUS current
       DESCRIPTION
          "The index of the associated ipsec Phase-1 IKE Tunnel.
           (ikeTunIndex in the ikeTunnelTable)"
       ::= { ipsecTunnelEntry 2 }

    ipsecTunIkeTunnelAlive OBJECT-TYPE
       SYNTAX TruthValue
       MAX-ACCESS read-only
       STATUS current
       DESCRIPTION
          "An indicator which specifies whether or not the
           ipsec Phase-1 IKE Tunnel currently exists."
       ::= { ipsecTunnelEntry 3 }

    ipsecTunLocalAddr OBJECT-TYPE
       SYNTAX IPSIpAddress
       MAX-ACCESS read-only
       STATUS current
       DESCRIPTION
          "The IP address of the local endpoint for the ipsec
           Phase-2 Tunnel."
       ::= { ipsecTunnelEntry 4 }

    ipsecTunRemoteAddr OBJECT-TYPE
       SYNTAX IPSIpAddress
       MAX-ACCESS read-only
       STATUS current
       DESCRIPTION
          "The IP address of the remote endpoint for the ipsec
           Phase-2 Tunnel."
       ::= { ipsecTunnelEntry 5 }

    ipsecTunKeyType OBJECT-TYPE
       SYNTAX KeyType
       MAX-ACCESS read-only
       STATUS current
       DESCRIPTION
          "The type of key used by the ipsec Phase-2 Tunnel."
       ::= { ipsecTunnelEntry 6 }

    ipsecTunEncapMode OBJECT-TYPE
       SYNTAX EncapMode
       MAX-ACCESS read-only
       STATUS current
       DESCRIPTION
          "The encapsulation mode used by the ipsec Phase-2 Tunnel."
       ::= { ipsecTunnelEntry 7 }

    ipsecTunLifeSize OBJECT-TYPE
       SYNTAX Integer32
       MAX-ACCESS read-only
       STATUS current
       DESCRIPTION
          "The negotiated LifeSize of the ipsec Phase-2 Tunnel in
           kilobytes."
       ::= { ipsecTunnelEntry 8 }

    ipsecTunLifeTime OBJECT-TYPE
       SYNTAX Integer32
       MAX-ACCESS read-only
       STATUS current
       DESCRIPTION
          "The negotiated LifeTime of the ipsec Phase-2 Tunnel in
           seconds."
       ::= { ipsecTunnelEntry 9 }

    ipsecTunActiveTime OBJECT-TYPE
       SYNTAX TimeInterval
       MAX-ACCESS read-only
       STATUS current
       DESCRIPTION
          "The length of time the ipsec Phase-2 Tunnel has been
           active in hundredths of seconds."
       ::= { ipsecTunnelEntry 10 }

    ipsecTunSaLifeSizeThreshold OBJECT-TYPE
       SYNTAX Integer32
       MAX-ACCESS read-only
       STATUS current
       DESCRIPTION
          "The security association LifeSize refresh threshold in kilobytes."
       ::= { ipsecTunnelEntry 11 }

    ipsecTunSaLifeTimeThreshold OBJECT-TYPE
       SYNTAX Integer32
       MAX-ACCESS read-only
       STATUS current
       DESCRIPTION
          "The security association LifeTime refresh threshold in seconds."
       ::= { ipsecTunnelEntry 12 }

    ipsecTunTotalRefreshes OBJECT-TYPE
       SYNTAX Counter32
       MAX-ACCESS read-only
       STATUS current
       DESCRIPTION
          "The total number of security association refreshes performed."
       ::= { ipsecTunnelEntry 13 }

    ipsecTunExpiredSaInstances OBJECT-TYPE
       SYNTAX Counter32
       MAX-ACCESS read-only
       STATUS current
       DESCRIPTION
          "The total number of security associations which have expired."
       ::= { ipsecTunnelEntry 14 }

    ipsecTunCurrentSaInstances OBJECT-TYPE
       SYNTAX Gauge32
       MAX-ACCESS read-only
       STATUS current
       DESCRIPTION
          "The number of security associations which are currently
           active or expiring."
       ::= { ipsecTunnelEntry 15 }

    ipsecTunInSaDiffHellmanGrp OBJECT-TYPE
      SYNTAX DiffHellmanGrp
       MAX-ACCESS read-only
       STATUS current
       DESCRIPTION
          "The Diffie Hellman Group used by the inbound security
           association of the ipsec Phase-2 Tunnel."
       ::= { ipsecTunnelEntry 16 }

    ipsecTunInSaEncryptAlgo OBJECT-TYPE
       SYNTAX EncryptAlgo
       MAX-ACCESS read-only
       STATUS current
       DESCRIPTION
          "The encryption algorithm used by the inbound security
           association of the ipsec Phase-2 Tunnel."
       ::= { ipsecTunnelEntry 17 }

    ipsecTunInSaAhAuthAlgo OBJECT-TYPE
       SYNTAX AuthAlgo
       MAX-ACCESS read-only
       STATUS current
       DESCRIPTION
          "The authentication algorithm used by the inbound
           authentication header (AH) security association of
           the ipsec Phase-2 Tunnel."
       ::= { ipsecTunnelEntry 18 }

    ipsecTunInSaEspAuthAlgo OBJECT-TYPE
       SYNTAX AuthAlgo
       MAX-ACCESS read-only
       STATUS current
       DESCRIPTION
          "The authentication algorithm used by the inbound
           ecapsulation security protocol (ESP) security association of
           the ipsec Phase-2 Tunnel."
       ::= { ipsecTunnelEntry 19 }

    ipsecTunInSaDecompAlgo OBJECT-TYPE
       SYNTAX CompAlgo
       MAX-ACCESS read-only
       STATUS current
       DESCRIPTION
          "The decompression algorithm used by the inbound
           security association of the ipsec Phase-2 Tunnel."
       ::= { ipsecTunnelEntry 20 }

    ipsecTunOutSaDiffHellmanGrp OBJECT-TYPE
       SYNTAX DiffHellmanGrp
       MAX-ACCESS read-only
       STATUS current
       DESCRIPTION
          "The Diffie Hellman Group used by the outbound security
           association of the ipsec Phase-2 Tunnel."
       ::= { ipsecTunnelEntry 21 }

    ipsecTunOutSaEncryptAlgo OBJECT-TYPE
       SYNTAX EncryptAlgo
       MAX-ACCESS read-only
       STATUS current
       DESCRIPTION
          "The encryption algorithm used by the outbound security
           association of the ipsec Phase-2 Tunnel."
       ::= { ipsecTunnelEntry 22 }

    ipsecTunOutSaAhAuthAlgo OBJECT-TYPE
       SYNTAX AuthAlgo
       MAX-ACCESS read-only
       STATUS current
       DESCRIPTION
          "The authentication algorithm used by the outbound
           authentication header (AH) security association of
           the ipsec Phase-2 Tunnel."
       ::= { ipsecTunnelEntry 23 }

    ipsecTunOutSaEspAuthAlgo OBJECT-TYPE
       SYNTAX AuthAlgo
       MAX-ACCESS read-only
       STATUS current
       DESCRIPTION
          "The authentication algorithm used by the inbound
           ecapsulation security protocol (ESP) security association of
           the ipsec Phase-2 Tunnel."
       ::= { ipsecTunnelEntry 24 }

    ipsecTunOutSaCompAlgo OBJECT-TYPE
       SYNTAX CompAlgo
       MAX-ACCESS read-only
       STATUS current
       DESCRIPTION
          "The compression algorithm used by the inbound
           security association of the ipsec Phase-2 Tunnel."
       ::= { ipsecTunnelEntry 25 }

    ipsecTunInOctets OBJECT-TYPE
       SYNTAX Counter32
       MAX-ACCESS read-only
       STATUS current
       DESCRIPTION
          "The total number of octets received by this ipsec
           Phase-2 Tunnel.  This value is accumulated
           BEFORE determining whether or not the packet should be
           decompressed.  See also ipsecTunInOctWraps for the
           number of times this counter has wrapped."
       ::= { ipsecTunnelEntry 26 }

    ipsecTunHcInOctets OBJECT-TYPE
       SYNTAX Counter64
       MAX-ACCESS read-only
       STATUS current
       DESCRIPTION
          "A high capacity count of the total number of octets
           received by this ipsec Phase-2 Tunnel.  This value is
           accumulated BEFORE determining whether or not the packet
           should be decompressed."
       ::= { ipsecTunnelEntry 27 }

    ipsecTunInOctWraps OBJECT-TYPE
       SYNTAX Counter32
       MAX-ACCESS read-only
       STATUS current
       DESCRIPTION
          "The number of times the octets received counter
           (ipsecTunInOctets) has wrapped."
       ::= { ipsecTunnelEntry 28 }

    ipsecTunInDecompOctets OBJECT-TYPE
       SYNTAX Counter32
       MAX-ACCESS read-only
       STATUS current
       DESCRIPTION
          "The total number of decompressed octets received by this
           ipsec Phase-2 Tunnel.  This value is accumulated AFTER
           the packet is decompressed. If compression is not being
           used, this value will match the value of ipsecTunInOctets.
           See also ipsecTunInDecompOctWraps for the number of times
           this counter has wrapped."
       ::= { ipsecTunnelEntry 29 }

    ipsecTunHcInDecompOctets OBJECT-TYPE
       SYNTAX Counter64
       MAX-ACCESS read-only
       STATUS current
       DESCRIPTION
          "A high capacity count of the total number of decompressed
           octets received by this ipsec Phase-2 Tunnel.  This value
           is accumulated AFTER the packet is decompressed. If
           compression is not being used, this value will match the
           value of ipsecTunHcInOctets."
       ::= { ipsecTunnelEntry 30 }

    ipsecTunInDecompOctWraps OBJECT-TYPE
       SYNTAX Counter32
       MAX-ACCESS read-only
       STATUS current
       DESCRIPTION
          "The number of times the decompressed octets received counter
           (ipsecTunInDecompOctets) has wrapped."
       ::= { ipsecTunnelEntry 31 }

    ipsecTunInPkts OBJECT-TYPE
       SYNTAX Counter32
       MAX-ACCESS read-only
       STATUS current
       DESCRIPTION
          "The total number of packets received by this ipsec Phase-2 Tunnel."
       ::= { ipsecTunnelEntry 32 }

    ipsecTunInDropPkts OBJECT-TYPE
       SYNTAX Counter32
       MAX-ACCESS read-only
       STATUS current
       DESCRIPTION
          "The total number of packets dropped during receive processing
           by this ipsec Phase-2 Tunnel. This count does NOT include
           packets dropped due to Anti-Replay processing."
       ::= { ipsecTunnelEntry 33 }

    ipsecTunInReplayDropPkts OBJECT-TYPE
       SYNTAX Counter32
       MAX-ACCESS read-only
       STATUS current
       DESCRIPTION
          "The total number of packets dropped during receive processing
           due to Anti-Replay processing by this ipsec Phase-2 Tunnel."
       ::= { ipsecTunnelEntry 34 }

    ipsecTunInAuths OBJECT-TYPE
       SYNTAX Counter32
       MAX-ACCESS read-only
       STATUS current
       DESCRIPTION
          "The total number of inbound authentication's performed
           by this ipsec Phase-2 Tunnel."
       ::= { ipsecTunnelEntry 35 }

    ipsecTunInAuthFails OBJECT-TYPE
       SYNTAX Counter32
       MAX-ACCESS read-only
       STATUS current
       DESCRIPTION
          "The total number of inbound authentication's which ended in
           failure by this ipsec Phase-2 Tunnel ."
       ::= { ipsecTunnelEntry 36 }

    ipsecTunInDecrypts OBJECT-TYPE
       SYNTAX Counter32
       MAX-ACCESS read-only
       STATUS current
       DESCRIPTION
          "The total number of inbound decryption's performed
           by this ipsec Phase-2 Tunnel."
       ::= { ipsecTunnelEntry 37 }

    ipsecTunInDecryptFails OBJECT-TYPE
       SYNTAX Counter32
       MAX-ACCESS read-only
       STATUS current
       DESCRIPTION
          "The total number of inbound decryption's which ended in failure
           by this ipsec Phase-2 Tunnel."
       ::= { ipsecTunnelEntry 38 }

    ipsecTunOutOctets OBJECT-TYPE
       SYNTAX Counter32
       MAX-ACCESS read-only
       STATUS current
       DESCRIPTION
          "The total number of octets sent by this ipsec
           Phase-2 Tunnel.  This value is accumulated
           AFTER determining whether or not the packet should be
           compressed.  See also ipsecTunOutOctWraps for the
           number of times this counter has wrapped."
       ::= { ipsecTunnelEntry 39 }

    ipsecTunHcOutOctets OBJECT-TYPE
       SYNTAX Counter64
       MAX-ACCESS read-only
       STATUS current
       DESCRIPTION
          "A high capacity count of the total number of octets
           sent by this ipsec Phase-2 Tunnel.  This value is
           accumulated AFTER determining whether or not the packet
           should be compressed."
       ::= { ipsecTunnelEntry 40 }

    ipsecTunOutOctWraps OBJECT-TYPE
       SYNTAX Counter32
       MAX-ACCESS read-only
       STATUS current
       DESCRIPTION
          "The number of times the octets sent counter
           (ipsecTunOutOctets) has wrapped."
       ::= { ipsecTunnelEntry 41 }

    ipsecTunOutUncompOctets OBJECT-TYPE
       SYNTAX Counter32
       MAX-ACCESS read-only
       STATUS current
       DESCRIPTION
          "The total number of uncompressed octets sent by this
           ipsec Phase-2 Tunnel.  This value is accumulated BEFORE
           the packet is compressed. If compression is not being
           used, this value will match the value of ipsecTunOutOctets.
           See also ipsecTunOutDecompOctWraps for the number of times
           this counter has wrapped."
       ::= { ipsecTunnelEntry 42 }

    ipsecTunHcOutUncompOctets OBJECT-TYPE
       SYNTAX Counter64
       MAX-ACCESS read-only
       STATUS current
       DESCRIPTION
          "A high capacity count of the total number of uncompressed
           octets sent by this ipsec Phase-2 Tunnel.  This value is
           accumulated BEFORE the packet is compressed. If compression
           is not being used, this value will match the value of
           ipsecTunHcOutOctets."
       ::= { ipsecTunnelEntry 43 }

    ipsecTunOutUncompOctWraps OBJECT-TYPE
       SYNTAX Counter32
       MAX-ACCESS read-only
       STATUS current
       DESCRIPTION
          "The number of times the uncompressed octets sent counter
           (ipsecTunInUncompOctets) has wrapped."
       ::= { ipsecTunnelEntry 44 }

    ipsecTunOutPkts OBJECT-TYPE
       SYNTAX Counter32
       MAX-ACCESS read-only
       STATUS current
       DESCRIPTION
          "The total number of packets sent by this ipsec Phase-2 Tunnel."
       ::= { ipsecTunnelEntry 45 }

    ipsecTunOutDropPkts OBJECT-TYPE
       SYNTAX Counter32
       MAX-ACCESS read-only
       STATUS current
       DESCRIPTION
          "The total number of packets dropped during send processing
           by this ipsec Phase-2 Tunnel."
       ::= { ipsecTunnelEntry 46 }

    ipsecTunOutAuths OBJECT-TYPE
       SYNTAX Counter32
       MAX-ACCESS read-only
       STATUS current
       DESCRIPTION
          "The total number of outbound authentication's performed
           by this ipsec Phase-2 Tunnel."
       ::= { ipsecTunnelEntry 47 }

    ipsecTunOutAuthFails OBJECT-TYPE
       SYNTAX Counter32
       MAX-ACCESS read-only
       STATUS current
       DESCRIPTION
          "The total number of outbound authentication's which ended in
           failure by this ipsec Phase-2 Tunnel."
       ::= { ipsecTunnelEntry 48 }

    ipsecTunOutEncrypts OBJECT-TYPE
       SYNTAX Counter32
       MAX-ACCESS read-only
       STATUS current
       DESCRIPTION
          "The total number of outbound encryption's performed
           by this ipsec Phase-2 Tunnel."
       ::= { ipsecTunnelEntry 49 }

    ipsecTunOutEncryptFails OBJECT-TYPE
       SYNTAX Counter32
       MAX-ACCESS read-only
       STATUS current
       DESCRIPTION
          "The total number of outbound encryption's which ended in failure
           by this ipsec Phase-2 Tunnel."
       ::= { ipsecTunnelEntry 50 }

    ipsecTunStatus OBJECT-TYPE
       SYNTAX TunnelStatus
       MAX-ACCESS read-write
       STATUS current
       DESCRIPTION
          "The status of the MIB table row.

           This object can be used to bring the tunnel down
           by setting value of this object to destroy(2).

           This object cannot be used to create a MIB table row."
       ::= { ipsecTunnelEntry 51 }

 -- ----------------------------------------------------------------------------
 -- The ipsec Phase-2 Tunnel Endpoint Table
 -- ----------------------------------------------------------------------------
    ipsecEndPtTable OBJECT-TYPE
       SYNTAX SEQUENCE OF IPsecEndPtEntry
       MAX-ACCESS not-accessible
       STATUS current
       DESCRIPTION
          "The ipsec Phase-2 Tunnel Endpoint Table. This table contains
           an entry for each active endpoint associated with an ipsec
           Phase-2 Tunnel."
       ::= { ipsecPhaseTwo 3 }

    ipsecEndPtEntry OBJECT-TYPE
       SYNTAX IPsecEndPtEntry
       MAX-ACCESS not-accessible
       STATUS current
       DESCRIPTION
          "An ipsec Phase-2 Tunnel Endpoint entry."
       INDEX { ipsecTunIndex,  -- from ipsecTunnelTable
               ipsecEndPtIndex  }
       ::= { ipsecEndPtTable 1 }

    IPsecEndPtEntry ::= SEQUENCE {
       ipsecEndPtIndex                Integer32,
       ipsecEndPtLocalName            DisplayString,
       ipsecEndPtLocalType            EndPtType,
       ipsecEndPtLocalAddr1           IPSIpAddress,
       ipsecEndPtLocalAddr2           IPSIpAddress,
       ipsecEndPtLocalProtocol        Integer32,
       ipsecEndPtLocalPort            Integer32,
       ipsecEndPtRemoteName           DisplayString,
       ipsecEndPtRemoteType           EndPtType,
       ipsecEndPtRemoteAddr1          IPSIpAddress,
       ipsecEndPtRemoteAddr2          IPSIpAddress,
       ipsecEndPtRemoteProtocol       Integer32,
       ipsecEndPtRemotePort           Integer32
    }

    ipsecEndPtIndex OBJECT-TYPE
       SYNTAX Integer32
       MAX-ACCESS not-accessible
       STATUS current
       DESCRIPTION
          "The number of the Endpoint associated with the
           ipsec Phase-2 Tunnel Table.  The value of this
           index is a number which begins at one and is incremented
           with each Endpoint associated with an ipsec Phase-2 Tunnel.
           The value of this object will wrap at 2,147,483,647."
       ::= { ipsecEndPtEntry 1 }

    ipsecEndPtLocalName OBJECT-TYPE
       SYNTAX DisplayString
       MAX-ACCESS read-only
       STATUS current
       DESCRIPTION
          "The DNS name of the local Endpoint."
       ::= { ipsecEndPtEntry 2 }

    ipsecEndPtLocalType OBJECT-TYPE
       SYNTAX EndPtType
       MAX-ACCESS read-only
       STATUS current
       DESCRIPTION
          "The type of identity for the local Endpoint.
           Possible values are:
           1) a single IP address, or
           2) an IP address range, or
           3) an IP subnet."
       ::= { ipsecEndPtEntry 3 }

    ipsecEndPtLocalAddr1 OBJECT-TYPE
       SYNTAX IPSIpAddress
       MAX-ACCESS read-only
       STATUS current
       DESCRIPTION
         "The local Endpoint's first IP address specification.

          If the local Endpoint type is single IP address, then this
          is the value of the IP address.

          If the local Endpoint type is IP subnet, then this
          is the value of the subnet.

          If the local Endpoint type is IP address range, then this
          is the value of beginning IP address of the range."
       ::= { ipsecEndPtEntry 4 }

    ipsecEndPtLocalAddr2 OBJECT-TYPE
       SYNTAX IPSIpAddress
       MAX-ACCESS read-only
       STATUS current
       DESCRIPTION
         "The local Endpoint's second IP address specification.

          If the local Endpoint type is single IP address, then this
          is the value of the IP address.

          If the local Endpoint type is IP subnet, then this
          is the value of the subnet mask.

          If the local Endpoint type is IP address range, then this
          is the value of ending IP address of the range."
       ::= { ipsecEndPtEntry 5 }

    ipsecEndPtLocalProtocol OBJECT-TYPE
       SYNTAX Integer32(1..255)
       MAX-ACCESS read-only
       STATUS current
       DESCRIPTION
          "The protocol number of the local Endpoint's traffic."
       ::= { ipsecEndPtEntry 6 }

    ipsecEndPtLocalPort OBJECT-TYPE
       SYNTAX Integer32(0..65535)
       MAX-ACCESS read-only
       STATUS current
       DESCRIPTION
          "The port number of the local Endpoint's traffic."
       ::= { ipsecEndPtEntry 7 }

    ipsecEndPtRemoteName OBJECT-TYPE
       SYNTAX DisplayString
       MAX-ACCESS read-only
       STATUS current
       DESCRIPTION
          "The DNS name of the remote Endpoint."
       ::= { ipsecEndPtEntry 8 }

    ipsecEndPtRemoteType OBJECT-TYPE
       SYNTAX EndPtType
       MAX-ACCESS read-only
       STATUS current
       DESCRIPTION
          "The type of identity for the remote Endpoint.
           Possible values are:
           1) a single IP address, or
           2) an IP address range, or
           3) an IP subnet."
       ::= { ipsecEndPtEntry 9 }

    ipsecEndPtRemoteAddr1 OBJECT-TYPE
       SYNTAX IPSIpAddress
       MAX-ACCESS read-only
       STATUS current
       DESCRIPTION
         "The remote Endpoint's first IP address specification.

          If the remote Endpoint type is single IP address, then this
          is the value of the IP address.

          If the remote Endpoint type is IP subnet, then this
          is the value of the subnet.

          If the remote Endpoint type is IP address range, then this
          is the value of beginning IP address of the range."
       ::= { ipsecEndPtEntry 10 }

    ipsecEndPtRemoteAddr2 OBJECT-TYPE
       SYNTAX IPSIpAddress
       MAX-ACCESS read-only
       STATUS current
       DESCRIPTION
         "The remote Endpoint's second IP address specification.

          If the remote Endpoint type is single IP address, then this
          is the value of the IP address.

          If the remote Endpoint type is IP subnet, then this
          is the value of the subnet mask.

          If the remote Endpoint type is IP address range, then this
          is the value of ending IP address of the range."
       ::= { ipsecEndPtEntry 11 }

    ipsecEndPtRemoteProtocol OBJECT-TYPE
       SYNTAX Integer32(1..255)
       MAX-ACCESS read-only
       STATUS current
       DESCRIPTION
          "The protocol number of the remote Endpoint's traffic."
       ::= { ipsecEndPtEntry 12 }

    ipsecEndPtRemotePort OBJECT-TYPE
       SYNTAX Integer32(0..65535)
       MAX-ACCESS read-only
       STATUS current
       DESCRIPTION
          "The port number of the remote Endpoint's traffic."
       ::= { ipsecEndPtEntry 13 }

 -- ----------------------------------------------------------------------------
 -- The ipsec Phase-2 Security Protection Index Table
 -- ----------------------------------------------------------------------------
    ipsecSpiTable OBJECT-TYPE
       SYNTAX SEQUENCE OF IPsecSpiEntry
       MAX-ACCESS not-accessible
       STATUS current
       DESCRIPTION
          "The ipsec Phase-2 Security Protection Index Table.  This table
           contains an entry for each active and expiring security
           association."
       ::= { ipsecPhaseTwo 4 }

    ipsecSpiEntry OBJECT-TYPE
       SYNTAX IPsecSpiEntry
       MAX-ACCESS not-accessible
       STATUS current
       DESCRIPTION
          "Each entry contains the attributes associated with
           active and expiring ipsec Phase-2 security associations."
       INDEX { ipsecTunIndex,  -- from ipsecTunnelTable
               ipsecSpiIndex  }
       ::= { ipsecSpiTable 1 }

    IPsecSpiEntry ::= SEQUENCE {
       ipsecSpiIndex                Integer32,
       ipsecSpiDirection            INTEGER,
       ipsecSpiValue                Integer32,
       ipsecSpiProtocol             INTEGER,
       ipsecSpiStatus               INTEGER
    }

    ipsecSpiIndex OBJECT-TYPE
       SYNTAX Integer32
       MAX-ACCESS not-accessible
       STATUS current
       DESCRIPTION
          "The number of the SPI associated with the Phase-2 Tunnel Table.
           The value of this index is a number which begins at one and
           is incremented with each SPI associated with an ipsec Phase-2
           Tunnel.  The value of this object will wrap at 2,147,483,647."
       ::= { ipsecSpiEntry 1 }

    ipsecSpiDirection OBJECT-TYPE
       SYNTAX INTEGER{
                 in(1),
                 out(2)
              }
       MAX-ACCESS read-only
       STATUS current
       DESCRIPTION
          "The direction of the SPI."
       ::= { ipsecSpiEntry 2 }

    ipsecSpiValue OBJECT-TYPE
       SYNTAX Integer32
       MAX-ACCESS read-only
       STATUS current
       DESCRIPTION
          "The value of the SPI."
       ::= { ipsecSpiEntry 3 }

    ipsecSpiProtocol OBJECT-TYPE
       SYNTAX INTEGER{
                 ah(1),
                 esp(2),
                 ipcomp(3)
              }
       MAX-ACCESS read-only
       STATUS current
       DESCRIPTION
          "The protocol of the SPI."
       ::= { ipsecSpiEntry 4 }

    ipsecSpiStatus OBJECT-TYPE
       SYNTAX INTEGER{
                 active(1),
                 expiring(2)
              }
       MAX-ACCESS read-only
       STATUS current
       DESCRIPTION
          "The status of the SPI."
       ::= { ipsecSpiEntry 5 }

 -- ----------------------------------------------------------------------------
 -- ----------------------------------------------------------------------------
 -- ----------------------------------------------------------------------------
 -- The ipsec History Group
 --
 -- This group consists of a:
 -- 1) ipsec History Global Objects
 -- 2) ipsec Phase-1 History Objects
 -- 3) ipsec Phase-2 History Objects
 -- ----------------------------------------------------------------------------
 -- ----------------------------------------------------------------------------
 -- ----------------------------------------------------------------------------
    ipsecHistGlobal           OBJECT IDENTIFIER ::= { ipsecHistory 1 }
    ipsecHistPhaseOne         OBJECT IDENTIFIER ::= { ipsecHistory 2 }
    ipsecHistPhaseTwo         OBJECT IDENTIFIER ::= { ipsecHistory 3 }

 -- ----------------------------------------------------------------------------
 -- ipsec History Global Control Objects
 -- ----------------------------------------------------------------------------
    ipsecHistGlobalCntl OBJECT IDENTIFIER    ::= { ipsecHistGlobal 1 }

    ipsecHistTableSize  OBJECT-TYPE
       SYNTAX Integer32
       MAX-ACCESS read-write
       STATUS current
       DESCRIPTION
          "The window size of the ipsec Phase-1 and Phase-2
           History Tables.

           The ipsec Phase-1 and Phase-2 History Tables are
           implemented as a sliding window in which only the
           last n entries are maintained.  This object is used
           specify the number of entries which will be maintained
           in the ipsec Phase-1 and Phase-2 History Tables.

           When modified by an SNMP SET request, the device will
           set the value of this object as close as possible to
           the requested value based on the implementation and
           available resources."
       ::= { ipsecHistGlobalCntl 1 }

 -- ----------------------------------------------------------------------------
 -- The ipsec Phase-1 Tunnel History Table
 -- ----------------------------------------------------------------------------
    ikeTunnelHistTable OBJECT-TYPE
       SYNTAX SEQUENCE OF IkeTunnelHistEntry
       MAX-ACCESS not-accessible
       STATUS current
       DESCRIPTION
          "The ipsec Phase-1 Internet Key Exchange Tunnel History Table.
           This table is implemented as a sliding window in which only the
           last n entries are maintained.  The maximum number of entries
           is specified by the ipsecHistTableSize object."
      ::= { ipsecHistPhaseOne 1 }

    ikeTunnelHistEntry OBJECT-TYPE
       SYNTAX IkeTunnelHistEntry
       MAX-ACCESS not-accessible
       STATUS current
       DESCRIPTION
             "Each entry contains the attributes associated with
              a previously active ipsec Phase-1 IKE Tunnel."
       INDEX { ikeTunHistIndex }
       ::= { ikeTunnelHistTable 1}

    IkeTunnelHistEntry ::= SEQUENCE {
       ikeTunHistIndex                 Integer32,
       ikeTunHistTermReason            INTEGER,
       ikeTunHistActiveIndex           Integer32,
       ikeTunHistPeerLocalType         IkePeerType,
       ikeTunHistPeerLocalValue        DisplayString,
       ikeTunHistPeerIntIndex          Integer32,
       ikeTunHistPeerRemoteType        IkePeerType,
       ikeTunHistPeerRemoteValue       DisplayString,
       ikeTunHistLocalAddr             IPSIpAddress,
       ikeTunHistLocalName             DisplayString,
       ikeTunHistRemoteAddr            IPSIpAddress,
       ikeTunHistRemoteName            DisplayString,
       ikeTunHistNegoMode              IkeNegoMode,
       ikeTunHistDiffHellmanGrp        DiffHellmanGrp,
       ikeTunHistEncryptAlgo           EncryptAlgo,
       ikeTunHistHashAlgo              IkeHashAlgo,
       ikeTunHistAuthMethod            IkeAuthMethod,
       ikeTunHistLifeTime              Integer32,
       ikeTunHistStartTime             TimeStamp,
       ikeTunHistActiveTime            TimeInterval,
       ikeTunHistTotalRefreshes        Counter32,
       ikeTunHistTotalSas              Counter32,
       ikeTunHistInOctets              Counter32,
       ikeTunHistInPkts                Counter32,
       ikeTunHistInDropPkts            Counter32,
       ikeTunHistInNotifys             Counter32,
       ikeTunHistInP2Exchgs            Counter32,
       ikeTunHistInP2ExchgInvalids     Counter32,
       ikeTunHistInP2ExchgRejects      Counter32,
       ikeTunHistInP2SaDelRequests     Counter32,
       ikeTunHistOutOctets             Counter32,
       ikeTunHistOutPkts               Counter32,
       ikeTunHistOutDropPkts           Counter32,
       ikeTunHistOutNotifys            Counter32,
       ikeTunHistOutP2Exchgs           Counter32,
       ikeTunHistOutP2ExchgInvalids    Counter32,
       ikeTunHistOutP2ExchgRejects     Counter32,
       ikeTunHistOutP2SaDelRequests    Counter32
    }

    ikeTunHistIndex OBJECT-TYPE
       SYNTAX Integer32
       MAX-ACCESS not-accessible
       STATUS current
       DESCRIPTION
          "The index of the ipsec Phase-1 IKE Tunnel History Table.
           The value of the index is a number which begins at one and
           is incremented with each tunnel that ends. The value
           of this object will wrap at 2,147,483,647."
       ::= { ikeTunnelHistEntry 1 }

    ikeTunHistTermReason  OBJECT-TYPE
       SYNTAX INTEGER {
                 other(1),
                 normal(2),
                 operRequest(3),
                 peerDelRequest(4),
                 peerLost(5),
                 seqNumRollOver(6),
                 localFailure(7)
              }
       MAX-ACCESS read-only
       STATUS current
       DESCRIPTION
          "The reason the ipsec Phase-1 IKE Tunnel was terminated.
           Possible reasons include:
           1 = other
           2 = normal termination
           3 = operator request
           4 = peer delete request was received
           5 = contact with peer was lost
           6 = sequence number rolled over
           7 = local failure occurred."
       ::= { ikeTunnelHistEntry 2 }

    ikeTunHistActiveIndex OBJECT-TYPE
       SYNTAX Integer32
       MAX-ACCESS read-only
       STATUS current
       DESCRIPTION
          "The index of the previously active ipsec Phase-1 IKE Tunnel."
       ::= { ikeTunnelHistEntry 3 }

    ikeTunHistPeerLocalType OBJECT-TYPE
       SYNTAX IkePeerType
       MAX-ACCESS read-only
       STATUS current
       DESCRIPTION
          "The type of local peer identity.  The local peer may be
           indentified by:
           1. an IP address, or
           2. a host name."
       ::= { ikeTunnelHistEntry 4 }

    ikeTunHistPeerLocalValue OBJECT-TYPE
       SYNTAX DisplayString
       MAX-ACCESS read-only
       STATUS current
       DESCRIPTION
          "The value of the local peer identity.

           If the local peer type is an IP Address, then this
           is the IP Address used to identify the local peer.
           If the local peer type is a host name, then this is
           the host name used to identify the local peer."
       ::= { ikeTunnelHistEntry 5 }

    ikeTunHistPeerIntIndex OBJECT-TYPE
       SYNTAX Integer32
       MAX-ACCESS read-only
       STATUS current
       DESCRIPTION
          "The internal index of the local-remote peer association.
           This internal index is used to uniquely identify
           multiple associations between the local and remote peer."
       ::= { ikeTunnelHistEntry 6 }

    ikeTunHistPeerRemoteType OBJECT-TYPE
       SYNTAX IkePeerType
       MAX-ACCESS read-only
       STATUS current
       DESCRIPTION
          "The type of remote peer identity.  The remote peer may be
           indentified by:
           1. an IP address, or
           2. a host name."
       ::= { ikeTunnelHistEntry 7 }

    ikeTunHistPeerRemoteValue OBJECT-TYPE
       SYNTAX DisplayString
       MAX-ACCESS read-only
       STATUS current
       DESCRIPTION
          "The value of the remote peer identity.

           If the remote peer type is an IP Address, then this
           is the IP Address used to identify the remote peer.

           If the remote peer type is a host name, then this is
           the host name used to identify the remote peer."
       ::= { ikeTunnelHistEntry 8 }

    ikeTunHistLocalAddr OBJECT-TYPE
       SYNTAX IPSIpAddress
       MAX-ACCESS read-only
       STATUS current
       DESCRIPTION
          "The IP address of the local endpoint for the ipsec
           Phase-1 IKE Tunnel."
       ::= { ikeTunnelHistEntry 9 }

    ikeTunHistLocalName OBJECT-TYPE
       SYNTAX DisplayString
       MAX-ACCESS read-only
       STATUS current
       DESCRIPTION
          "The DNS name of the local IP address for the ipsec Phase-1
           IKE Tunnel. If the DNS name associated with the local
           tunnel endpoint is not known, then the value of this
           object will be a NULL string."
       ::= { ikeTunnelHistEntry 10 }

    ikeTunHistRemoteAddr OBJECT-TYPE
       SYNTAX IPSIpAddress
       MAX-ACCESS read-only
       STATUS current
       DESCRIPTION
          "The IP address of the remote endpoint for the ipsec
           Phase-1 IKE Tunnel."
       ::= { ikeTunnelHistEntry 11 }

    ikeTunHistRemoteName OBJECT-TYPE
       SYNTAX DisplayString
       MAX-ACCESS read-only
       STATUS current
       DESCRIPTION
          "The DNS name of the remote IP address of ipsec Phase-1
           IKE Tunnel. If the DNS name associated with the remote
           tunnel endpoint is not known, then the value of this
           object will be a NULL string."
       ::= { ikeTunnelHistEntry 12 }

    ikeTunHistNegoMode OBJECT-TYPE
       SYNTAX IkeNegoMode
       MAX-ACCESS read-only
       STATUS current
       DESCRIPTION
          "The negotiation mode of the ipsec Phase-1 IKE Tunnel."
       ::= { ikeTunnelHistEntry 13 }

    ikeTunHistDiffHellmanGrp OBJECT-TYPE
       SYNTAX DiffHellmanGrp
       MAX-ACCESS read-only
       STATUS current
       DESCRIPTION
          "The Diffie Hellman Group used in ipsec Phase-1 IKE
           negotiations."
       ::= { ikeTunnelHistEntry 14 }

    ikeTunHistEncryptAlgo OBJECT-TYPE
       SYNTAX EncryptAlgo
       MAX-ACCESS read-only
       STATUS current
       DESCRIPTION
          "The encryption algorithm used in ipsec Phase-1 IKE
           negotiations."
       ::= { ikeTunnelHistEntry 15 }

    ikeTunHistHashAlgo OBJECT-TYPE
       SYNTAX IkeHashAlgo
       MAX-ACCESS read-only
       STATUS current
       DESCRIPTION
          "The hash algorithm used in ipsec Phase-1 IKE
           negotiations."
       ::= { ikeTunnelHistEntry 16 }

    ikeTunHistAuthMethod OBJECT-TYPE
       SYNTAX IkeAuthMethod
       MAX-ACCESS read-only
       STATUS current
       DESCRIPTION
          "The authentication method used in ipsec Phase-1 IKE
           negotiations."
       ::= { ikeTunnelHistEntry 17 }

    ikeTunHistLifeTime OBJECT-TYPE
       SYNTAX Integer32
       MAX-ACCESS read-only
       STATUS current
       DESCRIPTION
          "The negotiated LifeTime of the ipsec Phase-1 IKE Tunnel
           in seconds."
       ::= { ikeTunnelHistEntry 18 }

    ikeTunHistStartTime OBJECT-TYPE
       SYNTAX TimeStamp
       MAX-ACCESS read-only
       STATUS current
       DESCRIPTION
          "The time when the ipsec Phase-1 IKE tunnel was started
           in hundredths of seconds."
       ::= { ikeTunnelHistEntry 19 }

    ikeTunHistActiveTime OBJECT-TYPE
       SYNTAX TimeInterval
       MAX-ACCESS read-only
       STATUS current
       DESCRIPTION
          "The length of time the ipsec Phase-1 IKE tunnel was been
           active in hundredths of seconds."
       ::= { ikeTunnelHistEntry 20 }

    ikeTunHistTotalRefreshes OBJECT-TYPE
       SYNTAX Counter32
       MAX-ACCESS read-only
       STATUS current
       DESCRIPTION
          "The total number of security associations refreshes performed."
       ::= { ikeTunnelHistEntry 21 }

    ikeTunHistTotalSas       OBJECT-TYPE
       SYNTAX Counter32
       MAX-ACCESS read-only
       STATUS current
       DESCRIPTION
          "The total number of security associations used during the
           life of the ipsec Phase-1 IKE Tunnel."
       ::= { ikeTunnelHistEntry 22 }


    ikeTunHistInOctets OBJECT-TYPE
       SYNTAX Counter32
       MAX-ACCESS read-only
       STATUS current
       DESCRIPTION
          "The total number of octets received by this ipsec Phase-1
           IKE Tunnel."
       ::= { ikeTunnelHistEntry 23 }

    ikeTunHistInPkts OBJECT-TYPE
       SYNTAX Counter32
       MAX-ACCESS read-only
       STATUS current
       DESCRIPTION
          "The total number of packets received by this ipsec Phase-1
           IKE Tunnel."
       ::= { ikeTunnelHistEntry 24 }

    ikeTunHistInDropPkts OBJECT-TYPE
       SYNTAX Counter32
       MAX-ACCESS read-only
       STATUS current
       DESCRIPTION
          "The total number of packets dropped by this ipsec Phase-1
           IKE Tunnel during receive processing."
       ::= { ikeTunnelHistEntry 25 }

    ikeTunHistInNotifys OBJECT-TYPE
       SYNTAX Counter32
       MAX-ACCESS read-only
       STATUS current
       DESCRIPTION
          "The total number of nsotifys received by this ipsec Phase-1
           IKE Tunnel."
       ::= { ikeTunnelHistEntry 26 }

    ikeTunHistInP2Exchgs OBJECT-TYPE
       SYNTAX Counter32
       MAX-ACCESS read-only
       STATUS current
       DESCRIPTION
          "The total number of ipsec Phase-2 exchanges received by
           this ipsec Phase-1 IKE Tunnel."
       ::= { ikeTunnelHistEntry 27 }

    ikeTunHistInP2ExchgInvalids OBJECT-TYPE
       SYNTAX Counter32
       MAX-ACCESS read-only
       STATUS current
       DESCRIPTION
          "The total number of ipsec Phase-2 exchanges received and
           found to be invalid by this ipsec Phase-1 IKE Tunnel."
       ::= { ikeTunnelHistEntry 28 }

    ikeTunHistInP2ExchgRejects OBJECT-TYPE
       SYNTAX Counter32
       MAX-ACCESS read-only
       STATUS current
       DESCRIPTION
          "The total number of ipsec Phase-2 exchanges received and
           rejected by this ipsec Phase-1 IKE Tunnel."
       ::= { ikeTunnelHistEntry 29 }

    ikeTunHistInP2SaDelRequests OBJECT-TYPE
       SYNTAX Counter32
       MAX-ACCESS read-only
       STATUS current
       DESCRIPTION
          "The total number of ipsec Phase-2 security association
           delete requests received by this ipsec Phase-1 IKE Tunnel."
       ::= { ikeTunnelHistEntry 30 }

    ikeTunHistOutOctets OBJECT-TYPE
       SYNTAX Counter32
       MAX-ACCESS read-only
       STATUS current
       DESCRIPTION
          "The total number of octets sent by this ipsec Phase-1
           IKE Tunnel."
       ::= { ikeTunnelHistEntry 31 }

    ikeTunHistOutPkts OBJECT-TYPE
       SYNTAX Counter32
       MAX-ACCESS read-only
       STATUS current
       DESCRIPTION
          "The total number of packets sent by this ipsec Phase-1
           IKE Tunnel."
       ::= { ikeTunnelHistEntry 32 }

    ikeTunHistOutDropPkts OBJECT-TYPE
       SYNTAX Counter32
       MAX-ACCESS read-only
       STATUS current
       DESCRIPTION
          "The total number of packets dropped by this ipsec Phase-1
           IKE Tunnel during send processing."
       ::= { ikeTunnelHistEntry 33 }

    ikeTunHistOutNotifys OBJECT-TYPE
       SYNTAX Counter32
       MAX-ACCESS read-only
       STATUS current
       DESCRIPTION
          "The total number of notifys sent by this ipsec Phase-1
           IKE Tunnel."
       ::= { ikeTunnelHistEntry 34 }

    ikeTunHistOutP2Exchgs OBJECT-TYPE
       SYNTAX Counter32
       MAX-ACCESS read-only
       STATUS current
       DESCRIPTION
          "The total number of ipsec Phase-2 exchanges sent by
           this ipsec Phase-1 IKE Tunnel."
       ::= { ikeTunnelHistEntry 35 }

    ikeTunHistOutP2ExchgInvalids OBJECT-TYPE
       SYNTAX Counter32
       MAX-ACCESS read-only
       STATUS current
       DESCRIPTION
          "The total number of ipsec Phase-2 exchanges sent and
           found to be invalid by this ipsec Phase-1 IKE Tunnel."
       ::= { ikeTunnelHistEntry 36 }

    ikeTunHistOutP2ExchgRejects OBJECT-TYPE
       SYNTAX Counter32
       MAX-ACCESS read-only
       STATUS current
       DESCRIPTION
          "The total number of ipsec Phase-2 exchanges sent and
           rejected by this ipsec Phase-1 IKE Tunnel."
       ::= { ikeTunnelHistEntry 37 }

    ikeTunHistOutP2SaDelRequests OBJECT-TYPE
       SYNTAX Counter32
       MAX-ACCESS read-only
       STATUS current
       DESCRIPTION
          "The total number of ipsec Phase-2 security association
           delete requests sent by this ipsec Phase-1 IKE Tunnel."
       ::= { ikeTunnelHistEntry 38 }

 -- ----------------------------------------------------------------------------
 -- The ipsec Phase-2 Tunnel History Table
 -- ----------------------------------------------------------------------------
    ipsecTunnelHistTable OBJECT-TYPE
       SYNTAX SEQUENCE OF IPsecTunnelHistEntry
       MAX-ACCESS not-accessible
       STATUS current
       DESCRIPTION
          "The ipsec Phase-2 Tunnel History Table.
           This table is implemented as a sliding window in which only the
           last n entries are maintained.  The maximum number of entries
           is specified by the ipsecHistTableSize object."
       ::= { ipsecHistPhaseTwo 1 }

    ipsecTunnelHistEntry OBJECT-TYPE
       SYNTAX IPsecTunnelHistEntry
       MAX-ACCESS not-accessible
       STATUS current
       DESCRIPTION
          "Each entry contains the attributes associated with
           a previously active ipsec Phase-2 Tunnel."
       INDEX { ipsecTunHistIndex }
       ::= { ipsecTunnelHistTable 1 }

    IPsecTunnelHistEntry ::= SEQUENCE {
       ipsecTunHistIndex                Integer32,
       ipsecTunHistTermReason           INTEGER,
       ipsecTunHistActiveIndex          Integer32,
       ipsecTunHistIkeTunnelIndex       Integer32,
       ipsecTunHistLocalAddr            IPSIpAddress,
       ipsecTunHistRemoteAddr           IPSIpAddress,
       ipsecTunHistKeyType              KeyType,
       ipsecTunHistEncapMode            EncapMode,
       ipsecTunHistLifeSize             Integer32,
       ipsecTunHistLifeTime             Integer32,
       ipsecTunHistStartTime            TimeStamp,
       ipsecTunHistActiveTime           TimeInterval,
       ipsecTunHistTotalRefreshes       Counter32,
       ipsecTunHistTotalSas             Counter32,
       ipsecTunHistInSaDiffHellmanGrp   DiffHellmanGrp,
       ipsecTunHistInSaEncryptAlgo      EncryptAlgo,
       ipsecTunHistInSaAhAuthAlgo       AuthAlgo,
       ipsecTunHistInSaEspAuthAlgo      AuthAlgo,
       ipsecTunHistInSaDecompAlgo       CompAlgo,
       ipsecTunHistOutSaDiffHellmanGrp  DiffHellmanGrp,
       ipsecTunHistOutSaEncryptAlgo     EncryptAlgo,
       ipsecTunHistOutSaAhAuthAlgo      AuthAlgo,
       ipsecTunHistOutSaEspAuthAlgo     AuthAlgo,
       ipsecTunHistOutSaCompAlgo        CompAlgo,
       ipsecTunHistInOctets             Counter32,
       ipsecTunHistHcInOctets           Counter64,
       ipsecTunHistInOctWraps           Counter32,
       ipsecTunHistInDecompOctets       Counter32,
       ipsecTunHistHcInDecompOctets     Counter64,
       ipsecTunHistInDecompOctWraps     Counter32,
       ipsecTunHistInPkts               Counter32,
       ipsecTunHistInReplayDropPkts     Counter32,
       ipsecTunHistInDropPkts           Counter32,
       ipsecTunHistInAuths              Counter32,
       ipsecTunHistInAuthFails          Counter32,
       ipsecTunHistInDecrypts           Counter32,
       ipsecTunHistInDecryptFails       Counter32,
       ipsecTunHistOutOctets            Counter32,
       ipsecTunHistHcOutOctets          Counter64,
       ipsecTunHistOutOctWraps          Counter32,
       ipsecTunHistOutUncompOctets      Counter32,
       ipsecTunHistHcOutUncompOctets    Counter64,
       ipsecTunHistOutUncompOctWraps    Counter32,
       ipsecTunHistOutPkts              Counter32,
       ipsecTunHistOutDropPkts          Counter32,
       ipsecTunHistOutAuths             Counter32,
       ipsecTunHistOutAuthFails         Counter32,
       ipsecTunHistOutEncrypts          Counter32,
       ipsecTunHistOutEncryptFails      Counter32
    }

    ipsecTunHistIndex OBJECT-TYPE
       SYNTAX Integer32
       MAX-ACCESS not-accessible
       STATUS current
       DESCRIPTION
          "The index of the ipsec Phase-2 Tunnel History Table.
           The value of the index is a number which begins at one and
           is incremented with each tunnel that ends. The value
           of this object will wrap at 2,147,483,647."
       ::= { ipsecTunnelHistEntry 1 }

    ipsecTunHistTermReason  OBJECT-TYPE
       SYNTAX INTEGER {
                 other(1),
                 normal(2),
                 operRequest(3),
                 peerDelRequest(4),
                 peerLost(5),
                 seqNumRollOver(6)
              }
       MAX-ACCESS read-only
       STATUS current
       DESCRIPTION
          "The reason the ipsec Phase-2 Tunnel was terminated.
           Possible reasons include:
           1 = other
           2 = normal termination
           3 = operator request
           4 = peer delete request was received
           5 = contact with peer was lost
           6 = local failure occurred
           7 = sequence number rolled over."
       ::= { ipsecTunnelHistEntry 2 }

    ipsecTunHistActiveIndex OBJECT-TYPE
       SYNTAX Integer32
       MAX-ACCESS read-only
       STATUS current
       DESCRIPTION
          "The index of the previously active ipsec Phase-2 Tunnel."
       ::= { ipsecTunnelHistEntry 3 }

    ipsecTunHistIkeTunnelIndex OBJECT-TYPE
       SYNTAX Integer32
       MAX-ACCESS read-only
       STATUS current
       DESCRIPTION
          "The index of the associated ipsec Phase-1 Tunnel
           (ikeTunIndex in the ikeTunnelTable)."
       ::= { ipsecTunnelHistEntry 4 }

    ipsecTunHistLocalAddr OBJECT-TYPE
       SYNTAX IPSIpAddress
       MAX-ACCESS read-only
       STATUS current
       DESCRIPTION
          "The IP address of the local endpoint for the ipsec
           Phase-2 Tunnel."
       ::= { ipsecTunnelHistEntry 5 }

    ipsecTunHistRemoteAddr OBJECT-TYPE
       SYNTAX IPSIpAddress
       MAX-ACCESS read-only
       STATUS current
       DESCRIPTION
          "The IP address of the remote endpoint for the ipsec
           Phase-2 Tunnel."
       ::= { ipsecTunnelHistEntry 6 }

    ipsecTunHistKeyType OBJECT-TYPE
       SYNTAX KeyType
       MAX-ACCESS read-only
       STATUS current
       DESCRIPTION
          "The type of key used by the ipsec Phase-2 Tunnel."
       ::= { ipsecTunnelHistEntry 7 }

    ipsecTunHistEncapMode OBJECT-TYPE
       SYNTAX EncapMode
       MAX-ACCESS read-only
       STATUS current
       DESCRIPTION
          "The encapsulation mode used by the ipsec Phase-2 Tunnel."
       ::= { ipsecTunnelHistEntry 8 }

    ipsecTunHistLifeSize OBJECT-TYPE
       SYNTAX Integer32
       MAX-ACCESS read-only
       STATUS current
       DESCRIPTION
          "The negotiated LifeSize of the ipsec Phase-2 Tunnel in
           kilobytes."
       ::= { ipsecTunnelHistEntry 9 }

    ipsecTunHistLifeTime OBJECT-TYPE
       SYNTAX Integer32
       MAX-ACCESS read-only
       STATUS current
       DESCRIPTION
          "The negotiated LifeTime of the ipsec Phase-2 Tunnel in
           seconds."
       ::= { ipsecTunnelHistEntry 10 }

    ipsecTunHistStartTime OBJECT-TYPE
       SYNTAX TimeStamp
       MAX-ACCESS read-only
       STATUS current
       DESCRIPTION
          "The time when the ipsec Phase-2 Tunnel was started
           in hundredths of seconds."
       ::= { ipsecTunnelHistEntry 11 }

    ipsecTunHistActiveTime OBJECT-TYPE
       SYNTAX TimeInterval
       MAX-ACCESS read-only
       STATUS current
       DESCRIPTION
          "The length of time the ipsec Phase-2 Tunnel has been
           active in hundredths of seconds."
       ::= { ipsecTunnelHistEntry 12 }

    ipsecTunHistTotalRefreshes OBJECT-TYPE
       SYNTAX Counter32
       MAX-ACCESS read-only
       STATUS current
       DESCRIPTION
          "The total number of security association refreshes performed."
       ::= { ipsecTunnelHistEntry 13 }

    ipsecTunHistTotalSas OBJECT-TYPE
       SYNTAX Counter32
       MAX-ACCESS read-only
       STATUS current
       DESCRIPTION
          "The total number of security associations used during the
           life of the ipsec Phase-2 Tunnel."
       ::= { ipsecTunnelHistEntry 14 }

    ipsecTunHistInSaDiffHellmanGrp OBJECT-TYPE
       SYNTAX DiffHellmanGrp
       MAX-ACCESS read-only
       STATUS current
       DESCRIPTION
          "The Diffie Hellman Group used by the inbound security
           association of the ipsec Phase-2 Tunnel."
       ::= { ipsecTunnelHistEntry 15 }

    ipsecTunHistInSaEncryptAlgo OBJECT-TYPE
       SYNTAX EncryptAlgo
       MAX-ACCESS read-only
       STATUS current
       DESCRIPTION
          "The encryption algorithm used by the inbound security
           association of the ipsec Phase-2 Tunnel."
       ::= { ipsecTunnelHistEntry 16 }

    ipsecTunHistInSaAhAuthAlgo OBJECT-TYPE
       SYNTAX AuthAlgo
       MAX-ACCESS read-only
       STATUS current
       DESCRIPTION
          "The authentication algorithm used by the inbound
           authentication header (AH) security association of
           the ipsec Phase-2 Tunnel."
       ::= { ipsecTunnelHistEntry 17 }

    ipsecTunHistInSaEspAuthAlgo OBJECT-TYPE
       SYNTAX AuthAlgo
       MAX-ACCESS read-only
       STATUS current
       DESCRIPTION
          "The authentication algorithm used by the inbound
           ecapsulation security protocol (ESP) security association of
           the ipsec Phase-2 Tunnel."
       ::= { ipsecTunnelHistEntry 18 }

    ipsecTunHistInSaDecompAlgo OBJECT-TYPE
       SYNTAX CompAlgo
       MAX-ACCESS read-only
       STATUS current
       DESCRIPTION
          "The decompression algorithm used by the inbound
           security association of the ipsec Phase-2 Tunnel."
       ::= { ipsecTunnelHistEntry 19 }

    ipsecTunHistOutSaDiffHellmanGrp OBJECT-TYPE
       SYNTAX DiffHellmanGrp
       MAX-ACCESS read-only
       STATUS current
       DESCRIPTION
          "The Diffie Hellman Group used by the outbound security
           association of the ipsec Phase-2 Tunnel."
       ::= { ipsecTunnelHistEntry 20 }

    ipsecTunHistOutSaEncryptAlgo OBJECT-TYPE
       SYNTAX EncryptAlgo
       MAX-ACCESS read-only
       STATUS current
       DESCRIPTION
          "The encryption algorithm used by the outbound security
           association of the ipsec Phase-2 Tunnel."
       ::= { ipsecTunnelHistEntry 21 }

    ipsecTunHistOutSaAhAuthAlgo OBJECT-TYPE
       SYNTAX AuthAlgo
       MAX-ACCESS read-only
       STATUS current
       DESCRIPTION
          "The authentication algorithm used by the outbound
           authentication header (AH) security association of
           the ipsec Phase-2 Tunnel."
       ::= { ipsecTunnelHistEntry 22 }

    ipsecTunHistOutSaEspAuthAlgo OBJECT-TYPE
       SYNTAX AuthAlgo
       MAX-ACCESS read-only
       STATUS current
       DESCRIPTION
          "The authentication algorithm used by the inbound
           ecapsulation security protocol (ESP) security association of
           the ipsec Phase-2 Tunnel."
       ::= { ipsecTunnelHistEntry 23 }

    ipsecTunHistOutSaCompAlgo OBJECT-TYPE
       SYNTAX CompAlgo
       MAX-ACCESS read-only
       STATUS current
       DESCRIPTION
          "The compression algorithm used by the inbound
           security association of the ipsec Phase-2 Tunnel."
       ::= { ipsecTunnelHistEntry 24 }

    ipsecTunHistInOctets OBJECT-TYPE
       SYNTAX Counter32
       MAX-ACCESS read-only
       STATUS current
       DESCRIPTION
          "The total number of octets received by this ipsec
           Phase-2 Tunnel.  This value is accumulated
           BEFORE determining whether or not the packet should be
           decompressed.  See also ipsecTunInOctWraps for the
           number of times this counter has wrapped."
       ::= { ipsecTunnelHistEntry 25 }

    ipsecTunHistHcInOctets OBJECT-TYPE
       SYNTAX Counter64
       MAX-ACCESS read-only
       STATUS current
       DESCRIPTION
          "A high capacity count of the total number of octets
           received by this ipsec Phase-2 Tunnel.  This value is
           accumulated BEFORE determining whether or not the packet
           should be decompressed."
       ::= { ipsecTunnelHistEntry 26 }

    ipsecTunHistInOctWraps OBJECT-TYPE
       SYNTAX Counter32
       MAX-ACCESS read-only
       STATUS current
       DESCRIPTION
          "The number of times the octets received counter
           (ipsecTunInOctets) has wrapped."
       ::= { ipsecTunnelHistEntry 27 }

    ipsecTunHistInDecompOctets OBJECT-TYPE
       SYNTAX Counter32
       MAX-ACCESS read-only
       STATUS current
       DESCRIPTION
          "The total number of decompressed octets received by this
           ipsec Phase-2 Tunnel.  This value is accumulated AFTER
           the packet is decompressed. If compression is not being
           used, this value will match the value of ipsecTunInOctets.
           See also ipsecTunInDecompOctWraps for the number of times
           this counter has wrapped."
       ::= { ipsecTunnelHistEntry 28 }

    ipsecTunHistHcInDecompOctets OBJECT-TYPE
       SYNTAX Counter64
       MAX-ACCESS read-only
       STATUS current
       DESCRIPTION
          "A high capacity count of the total number of decompressed
           octets received by this ipsec Phase-2 Tunnel.  This value
           is accumulated AFTER the packet is decompressed. If
           compression is not being used, this value will match the
           value of ipsecTunHcInOctets."
       ::= { ipsecTunnelHistEntry 29 }

    ipsecTunHistInDecompOctWraps OBJECT-TYPE
       SYNTAX Counter32
       MAX-ACCESS read-only
       STATUS current
       DESCRIPTION
          "The number of times the decompressed octets received counter
           (ipsecTunInDecompOctets) has wrapped."
       ::= { ipsecTunnelHistEntry 30 }

    ipsecTunHistInPkts OBJECT-TYPE
       SYNTAX Counter32
       MAX-ACCESS read-only
       STATUS current
       DESCRIPTION
          "The total number of packets received by this ipsec Phase-2 Tunnel."
       ::= { ipsecTunnelHistEntry 31 }

    ipsecTunHistInDropPkts OBJECT-TYPE
       SYNTAX Counter32
       MAX-ACCESS read-only
       STATUS current
       DESCRIPTION
          "The total number of packets dropped during receive processing
           by this ipsec Phase-2 Tunnel. This count does NOT include packets
           dropped due to Anti-Replay processing."
       ::= { ipsecTunnelHistEntry 32 }

    ipsecTunHistInReplayDropPkts OBJECT-TYPE
       SYNTAX Counter32
       MAX-ACCESS read-only
       STATUS current
       DESCRIPTION
          "The total number of packets dropped during receive processing
           due to Anti-Replay processing by this ipsec Phase-2 Tunnel."
       ::= { ipsecTunnelHistEntry 33 }

    ipsecTunHistInAuths OBJECT-TYPE
       SYNTAX Counter32
       MAX-ACCESS read-only
       STATUS current
       DESCRIPTION
          "The total number of inbound authentication's performed
           by this ipsec Phase-2 Tunnel."
       ::= { ipsecTunnelHistEntry 34 }

    ipsecTunHistInAuthFails OBJECT-TYPE
       SYNTAX Counter32
       MAX-ACCESS read-only
       STATUS current
       DESCRIPTION
          "The total number of inbound authentication's which ended in
           failure by this ipsec Phase-2 Tunnel ."
       ::= { ipsecTunnelHistEntry 35 }

    ipsecTunHistInDecrypts OBJECT-TYPE
       SYNTAX Counter32
       MAX-ACCESS read-only
       STATUS current
       DESCRIPTION
          "The total number of inbound decryption's performed
           by this ipsec Phase-2 Tunnel."
       ::= { ipsecTunnelHistEntry 36 }

    ipsecTunHistInDecryptFails OBJECT-TYPE
       SYNTAX Counter32
       MAX-ACCESS read-only
       STATUS current
       DESCRIPTION
          "The total number of inbound decryption's which ended in failure
           by this ipsec Phase-2 Tunnel."
       ::= { ipsecTunnelHistEntry 37 }

    ipsecTunHistOutOctets OBJECT-TYPE
       SYNTAX Counter32
       MAX-ACCESS read-only
       STATUS current
       DESCRIPTION
          "The total number of octets sent by this ipsec
           Phase-2 Tunnel.  This value is accumulated
           AFTER determining whether or not the packet should be
           compressed.  See also ipsecTunOutOctWraps for the
           number of times this counter has wrapped."
       ::= { ipsecTunnelHistEntry 38 }

    ipsecTunHistHcOutOctets OBJECT-TYPE
       SYNTAX Counter64
       MAX-ACCESS read-only
       STATUS current
       DESCRIPTION
          "A high capacity count of the total number of octets
           sent by this ipsec Phase-2 Tunnel.  This value is accumulated
           AFTER determining whether or not the packet should be
           compressed."
       ::= { ipsecTunnelHistEntry 39 }

    ipsecTunHistOutOctWraps OBJECT-TYPE
       SYNTAX Counter32
       MAX-ACCESS read-only
       STATUS current
       DESCRIPTION
          "The number of times the octets sent counter
           (ipsecTunOutOctets) has wrapped."
       ::= { ipsecTunnelHistEntry 40 }

    ipsecTunHistOutUncompOctets OBJECT-TYPE
       SYNTAX Counter32
       MAX-ACCESS read-only
       STATUS current
       DESCRIPTION
          "The total number of uncompressed octets sent by this
           ipsec Phase-2 Tunnel.  This value is accumulated BEFORE
           the packet is compressed. If compression is not being
           used, this value will match the value of ipsecTunOutOctets.
           See also ipsecTunOutDecompOctWraps for the number of times
           this counter has wrapped."
       ::= { ipsecTunnelHistEntry 41 }

    ipsecTunHistHcOutUncompOctets OBJECT-TYPE
       SYNTAX Counter64
       MAX-ACCESS read-only
       STATUS current
       DESCRIPTION
          "A high capacity count of the total number of uncompressed
           octets sent by this ipsec Phase-2 Tunnel.  This value is
           accumulated BEFORE the packet is compressed. If compression
           is not being used, this value will match the value of
           ipsecTunHcOutOctets."
       ::= { ipsecTunnelHistEntry 42 }

    ipsecTunHistOutUncompOctWraps OBJECT-TYPE
       SYNTAX Counter32
       MAX-ACCESS read-only
       STATUS current
       DESCRIPTION
          "The number of times the uncompressed octets sent counter
           (ipsecTunInUncompOctets) has wrapped."
       ::= { ipsecTunnelHistEntry 43 }

    ipsecTunHistOutPkts OBJECT-TYPE
       SYNTAX Counter32
       MAX-ACCESS read-only
       STATUS current
       DESCRIPTION
          "The total number of packets sent by this ipsec Phase-2 Tunnel."
       ::= { ipsecTunnelHistEntry 44 }

    ipsecTunHistOutDropPkts OBJECT-TYPE
       SYNTAX Counter32
       MAX-ACCESS read-only
       STATUS current
       DESCRIPTION
          "The total number of packets dropped during send processing
           by this ipsec Phase-2 Tunnel."
       ::= { ipsecTunnelHistEntry 45 }

    ipsecTunHistOutAuths OBJECT-TYPE
       SYNTAX Counter32
       MAX-ACCESS read-only
       STATUS current
       DESCRIPTION
          "The total number of outbound authentication's performed
           by this ipsec Phase-2 Tunnel."
       ::= { ipsecTunnelHistEntry 46 }

    ipsecTunHistOutAuthFails OBJECT-TYPE
       SYNTAX Counter32
       MAX-ACCESS read-only
       STATUS current
       DESCRIPTION
          "The total number of outbound authentication's which ended in
           failure by this ipsec Phase-2 Tunnel."
       ::= { ipsecTunnelHistEntry 47 }

    ipsecTunHistOutEncrypts OBJECT-TYPE
       SYNTAX Counter32
       MAX-ACCESS read-only
       STATUS current
       DESCRIPTION
          "The total number of outbound encryption's performed
           by this ipsec Phase-2 Tunnel."
       ::= { ipsecTunnelHistEntry 48 }

    ipsecTunHistOutEncryptFails OBJECT-TYPE
       SYNTAX Counter32
       MAX-ACCESS read-only
       STATUS current
       DESCRIPTION
          "The total number of outbound encryption's which ended in failure
           by this ipsec Phase-2 Tunnel."
       ::= { ipsecTunnelHistEntry 49 }

 -- ----------------------------------------------------------------------------
 -- The ipsec Phase-2 Tunnel Endpoint History Table
 -- ----------------------------------------------------------------------------
    ipsecEndPtHistTable OBJECT-TYPE
       SYNTAX SEQUENCE OF IPsecEndPtHistEntry
       MAX-ACCESS not-accessible
       STATUS current
       DESCRIPTION
          "The ipsec Phase-2 Tunnel Endpoint History Table.
           This table is implemented as a sliding window in which only the
           last n entries are maintained.  The maximum number of entries
           is specified by the ipsecHistTableSize object."
       ::= { ipsecHistPhaseTwo 2 }

    ipsecEndPtHistEntry OBJECT-TYPE
       SYNTAX IPsecEndPtHistEntry
       MAX-ACCESS not-accessible
       STATUS current
       DESCRIPTION
          "Each entry contains the attributes associated with
           a previously active ipsec Phase-2 Tunnel Endpoint."
       INDEX { ipsecEndPtHistIndex }
       ::= { ipsecEndPtHistTable 1 }

    IPsecEndPtHistEntry ::= SEQUENCE {
       ipsecEndPtHistIndex                Integer32,
       ipsecEndPtHistTunIndex             Integer32,
       ipsecEndPtHistActiveIndex          Integer32,
       ipsecEndPtHistLocalName            DisplayString,
       ipsecEndPtHistLocalType            EndPtType,
       ipsecEndPtHistLocalAddr1           IPSIpAddress,
       ipsecEndPtHistLocalAddr2           IPSIpAddress,
       ipsecEndPtHistLocalProtocol        Integer32,
       ipsecEndPtHistLocalPort            Integer32,
       ipsecEndPtHistRemoteName           DisplayString,
       ipsecEndPtHistRemoteType           EndPtType,
       ipsecEndPtHistRemoteAddr1          IPSIpAddress,
       ipsecEndPtHistRemoteAddr2          IPSIpAddress,
       ipsecEndPtHistRemoteProtocol       Integer32,
       ipsecEndPtHistRemotePort           Integer32
    }

    ipsecEndPtHistIndex OBJECT-TYPE
       SYNTAX Integer32
       MAX-ACCESS not-accessible
       STATUS current
       DESCRIPTION
          "The number of the previously active Endpoint associated
           with a ipsec Phase-2 Tunnel Table.  The value of this
           index is a number which begins at one and is incremented
           with each Endpoint associated with an ipsec Phase-2 Tunnel.
           The value of this object will wrap at 2,147,483,647."
       ::= { ipsecEndPtHistEntry 1 }

    ipsecEndPtHistTunIndex OBJECT-TYPE
       SYNTAX Integer32
       MAX-ACCESS read-only
       STATUS current
       DESCRIPTION
          "The index  of the previously active ipsec Phase-2 Tunnel Table."
       ::= { ipsecEndPtHistEntry 2 }

    ipsecEndPtHistActiveIndex OBJECT-TYPE
       SYNTAX Integer32
       MAX-ACCESS read-only
       STATUS current
       DESCRIPTION
          "The index  of the previously active Endpoint."
       ::= { ipsecEndPtHistEntry 3 }

    ipsecEndPtHistLocalName OBJECT-TYPE
       SYNTAX DisplayString
       MAX-ACCESS read-only
       STATUS current
       DESCRIPTION
          "The DNS name of the local Endpoint."
       ::= { ipsecEndPtHistEntry 4 }

    ipsecEndPtHistLocalType OBJECT-TYPE
       SYNTAX INTEGER {
                 singleIpAddr(1),
                 ipAddrRange(2),
                 ipSubnet(3)
              }
       MAX-ACCESS read-only
       STATUS current
       DESCRIPTION
          "The type of identity for the local Endpoint.
           Possible values are:
           1) a single IP address, or
           2) an IP address range, or
           3) an IP subnet."
       ::= { ipsecEndPtHistEntry 5 }

    ipsecEndPtHistLocalAddr1 OBJECT-TYPE
       SYNTAX IPSIpAddress
       MAX-ACCESS read-only
       STATUS current
       DESCRIPTION
         "The local Endpoint's first IP address specification.

          If the local Endpoint type is single IP address, then this
          is the value of the IP address.

          If the local Endpoint type is IP subnet, then this
          is the value of the subnet.

          If the local Endpoint type is IP address range, then this
          is the value of beginning IP address of the range."
       ::= { ipsecEndPtHistEntry 6 }

    ipsecEndPtHistLocalAddr2 OBJECT-TYPE
       SYNTAX IPSIpAddress
       MAX-ACCESS read-only
       STATUS current
       DESCRIPTION
         "The local Endpoint's second IP address specification.

          If the local Endpoint type is single IP address, then this
          is the value of the IP address.

          If the local Endpoint type is IP subnet, then this
          is the value of the subnet mask.

          If the local Endpoint type is IP address range, then this
          is the value of ending IP address of the range."
       ::= { ipsecEndPtHistEntry 7 }

    ipsecEndPtHistLocalProtocol OBJECT-TYPE
       SYNTAX Integer32(1..255)
       MAX-ACCESS read-only
       STATUS current
       DESCRIPTION
          "The protocol number of the local Endpoint's traffic."
       ::= { ipsecEndPtHistEntry 8 }

    ipsecEndPtHistLocalPort OBJECT-TYPE
       SYNTAX Integer32(0..65535)
       MAX-ACCESS read-only
       STATUS current
       DESCRIPTION
          "The port number of the local Endpoint's traffic."
       ::= { ipsecEndPtHistEntry 9 }

    ipsecEndPtHistRemoteName OBJECT-TYPE
       SYNTAX DisplayString
       MAX-ACCESS read-only
       STATUS current
       DESCRIPTION
          "The DNS name of the remote Endpoint."
       ::= { ipsecEndPtHistEntry 10 }

    ipsecEndPtHistRemoteType OBJECT-TYPE
       SYNTAX INTEGER {
                 singleIpAddr(1),
                 ipAddrRange(2),
                 ipSubnet(3)
              }
       MAX-ACCESS read-only
       STATUS current
       DESCRIPTION
          "The type of identity for the remote Endpoint.
           Possible values are:
           1) a single IP address, or
           2) an IP address range, or
           3) an IP subnet."
       ::= { ipsecEndPtHistEntry 11 }

    ipsecEndPtHistRemoteAddr1 OBJECT-TYPE
       SYNTAX IPSIpAddress
       MAX-ACCESS read-only
       STATUS current
       DESCRIPTION
         "The remote Endpoint's first IP address specification.

          If the remote Endpoint type is single IP address, then this
          is the value of the IP address.

          If the remote Endpoint type is IP subnet, then this
          is the value of the subnet.

          If the remote Endpoint type is IP address range, then this
          is the value of beginning IP address of the range."
       ::= { ipsecEndPtHistEntry 12 }

    ipsecEndPtHistRemoteAddr2 OBJECT-TYPE
       SYNTAX IPSIpAddress
       MAX-ACCESS read-only
       STATUS current
       DESCRIPTION
         "The remote Endpoint's second IP address specification.

          If the remote Endpoint type is single IP address, then this
          is the value of the IP address.

          If the remote Endpoint type is IP subnet, then this
          is the value of the subnet mask.

          If the remote Endpoint type is IP address range, then this
          is the value of ending IP address of the range."
       ::= { ipsecEndPtHistEntry 13 }

    ipsecEndPtHistRemoteProtocol OBJECT-TYPE
       SYNTAX Integer32(1..255)
       MAX-ACCESS read-only
       STATUS current
       DESCRIPTION
          "The protocol number of the remote Endpoint's traffic."
       ::= { ipsecEndPtHistEntry 14 }

    ipsecEndPtHistRemotePort OBJECT-TYPE
       SYNTAX Integer32(0..65535)
       MAX-ACCESS read-only
       STATUS current
       DESCRIPTION
          "The port number of the remote Endpoint's traffic."
       ::= { ipsecEndPtHistEntry 15 }

 -- start here
 -- -------------------------------------------------------------------------
 -- The ipsec Failure Group
 --
 -- This group consists of a:
 -- 1) ipsec Failure Global Objects
 -- 2) ipsec Phase-1 Tunnel Failure Table
 -- 3) ipsec Phase-2 Tunnel Failure Table
 -- -------------------------------------------------------------------------
    ipsecFailGlobal         OBJECT IDENTIFIER ::= { ipsecFailures 1 }
    ipsecFailPhaseOne       OBJECT IDENTIFIER ::= { ipsecFailures 2 }
    ipsecFailPhaseTwo       OBJECT IDENTIFIER ::= { ipsecFailures 3 }

 -- ----------------------------------------------------------------------------
 -- The ipsec Failure Global Control Objects
 -- ----------------------------------------------------------------------------
    ipsecFailGlobalCntl  OBJECT IDENTIFIER    ::= { ipsecFailGlobal 1 }
    ipsecFailTableSize  OBJECT-TYPE
       SYNTAX Integer32
       MAX-ACCESS read-write
       STATUS current
       DESCRIPTION
          "The window size of the ipsec Phase-1 and Phase-2
           Failure Tables.

           The ipsec Phase-1 and Phase-2 Failure Tables are
           implemented as a sliding window in which only the
           last n entries are maintained.  This object is used
           specify the number of entries which will be maintained
           in the ipsec Phase-1 and Phase-2 Failure Tables.

           When modified by an SNMP SET request, the device will
           set the value of this object as close as possible to
           the requested value based on the implementation and
           available resources."
       ::= { ipsecFailGlobalCntl 1 }

 -- ----------------------------------------------------------------------------
 -- The ipsec Phase-1 Failure Table
 -- ----------------------------------------------------------------------------
    ikeFailTable OBJECT-TYPE
       SYNTAX SEQUENCE OF IkeFailEntry
       MAX-ACCESS not-accessible
       STATUS current
       DESCRIPTION
          "The ipsec Phase-1 Failure Table.
           This table is implemented as a sliding window in which only the
           last n entries are maintained.  The maximum number of entries
           is specified by the ipsecFailTableSize object."
       ::= { ipsecFailPhaseOne 1 }

    ikeFailEntry OBJECT-TYPE
       SYNTAX IkeFailEntry
       MAX-ACCESS not-accessible
       STATUS current
       DESCRIPTION
             "Each entry contains the attributes associated with
              an ipsec Phase-1 failure."
       INDEX { ikeFailIndex }
       ::= { ikeFailTable 1 }

    IkeFailEntry ::= SEQUENCE {
       ikeFailIndex                Integer32,
       ikeFailReason               INTEGER,
       ikeFailTime                 TimeStamp,
       ikeFailLocalType            IkePeerType,
       ikeFailLocalValue           DisplayString,
       ikeFailRemoteType           IkePeerType,
       ikeFailRemoteValue          DisplayString,
       ikeFailLocalAddr            IPSIpAddress,
       ikeFailRemoteAddr           IPSIpAddress
    }

    ikeFailIndex OBJECT-TYPE
       SYNTAX Integer32
       MAX-ACCESS not-accessible
       STATUS current
       DESCRIPTION
          "The ipsec Phase-1 Failure Table index.
           The value of the index is a number which begins at one and
           is incremented with each ipsec Phase-1 failure. The value
           of this object will wrap at 2,147,483,647."
       ::= { ikeFailEntry 1 }

    ikeFailReason OBJECT-TYPE
       SYNTAX INTEGER{
                other(1),
                peerDelRequest(2),
                peerLost(3),
                localFailure(4),
                seqNumRollOver(5),
                authFailure(6),
                hashValidation(7),
                encryptFailure(8),
                internalError(9),
                sysCapExceeded(10),
                proposalFailure(11),
                peerCertUnavailable(12),
                peerCertNotValid(13),
                localCertExpired(14),
                crlFailure(15),
                peerEncodingError(16),
                nonExistentSa(17),
                operRequest(18)
              }
       MAX-ACCESS read-only
       STATUS current
       DESCRIPTION
          "The reason for the failure.  Possible reasons include:
            1 = other
            2 = peer delete request was received
            3 = contact with peer was lost
            4 = local failure occurred
            5 = sequence number rolled over
            6 = authentication failure
            7 = hash validation failure
            8 = encryption failure
            9 = internal error occurred
           10 = system capacity failure
           11 = proposal failure
           12 = peer's certificate is unavailable
           13 = peer's certificate was found invalid
           14 = local certificate expired
           15 = certificate revoke list (crl) failure
           16 = peer encoding error
           17 = non-existent security association
           18 = operator requested termination."
       ::= { ikeFailEntry 2 }

    ikeFailTime OBJECT-TYPE
       SYNTAX TimeStamp
       MAX-ACCESS read-only
       STATUS current
       DESCRIPTION
          "The time of the failure in hundredths of seconds."
       ::= { ikeFailEntry 3 }

    ikeFailLocalType OBJECT-TYPE
       SYNTAX IkePeerType
       MAX-ACCESS read-only
       STATUS current
       DESCRIPTION
          "The type of local peer identity.  The local peer may be
           indentified by:
           1. an IP address, or
           2. a host name."
       ::= { ikeFailEntry 4 }

    ikeFailLocalValue OBJECT-TYPE
       SYNTAX DisplayString
       MAX-ACCESS read-only
       STATUS current
       DESCRIPTION
          "The value of the local peer identity.

           If the local peer type is an IP Address, then this
           is the IP Address used to identify the local peer.

           If the local peer type is a host name, then this is
           the host name used to identify the local peer."
       ::= { ikeFailEntry 5 }

    ikeFailRemoteType OBJECT-TYPE
       SYNTAX IkePeerType
       MAX-ACCESS read-only
       STATUS current
       DESCRIPTION
          "The type of remote peer identity.  The remote peer may be
           indentified by:
           1. an IP address, or
           2. a host name."
       ::= { ikeFailEntry 6 }

    ikeFailRemoteValue OBJECT-TYPE
       SYNTAX DisplayString
       MAX-ACCESS read-only
       STATUS current
       DESCRIPTION
          "The value of the remote peer identity.

           If the remote peer type is an IP Address, then this
           is the IP Address used to identify the remote peer.

           If the remote peer type is a host name, then this is
           the host name used to identify the remote peer."
       ::= { ikeFailEntry 7 }

    ikeFailLocalAddr OBJECT-TYPE
       SYNTAX IPSIpAddress
       MAX-ACCESS read-only
       STATUS current
       DESCRIPTION
          "The IP address of the local peer."
       ::= { ikeFailEntry 8 }

    ikeFailRemoteAddr OBJECT-TYPE
       SYNTAX IPSIpAddress
       MAX-ACCESS read-only
       STATUS current
       DESCRIPTION
          "The IP address of the remote peer."
       ::= { ikeFailEntry 9 }

 -- ----------------------------------------------------------------------------
 -- The ipsec Phase-2 Failure Table
 -- ----------------------------------------------------------------------------
    ipsecFailTable OBJECT-TYPE
       SYNTAX SEQUENCE OF IPsecFailEntry
       MAX-ACCESS not-accessible
       STATUS current
       DESCRIPTION
          "The ipsec Phase-2 Failure Table.
           This table is implemented as a sliding window in which only the
           last n entries are maintained.  The maximum number of entries
           is specified by the ipsecFailTableSize object."
       ::= { ipsecFailPhaseTwo 1 }

    ipsecFailEntry OBJECT-TYPE
       SYNTAX IPsecFailEntry
       MAX-ACCESS not-accessible
       STATUS current
       DESCRIPTION
          "Each entry contains the attributes associated with
           an ipsec Phase-1 failure."
       INDEX { ipsecFailIndex }
       ::= { ipsecFailTable 1 }

    IPsecFailEntry ::= SEQUENCE {
       ipsecFailIndex                Integer32,
       ipsecFailReason               INTEGER,
       ipsecFailTime                 TimeStamp,
       ipsecFailTunnelIndex          Integer32,
       ipsecFailSaSpi                Integer32,
       ipsecFailPktSrcAddr           IPSIpAddress,
       ipsecFailPktDstAddr           IPSIpAddress
    }

    ipsecFailIndex OBJECT-TYPE
       SYNTAX Integer32
       MAX-ACCESS not-accessible
       STATUS current
       DESCRIPTION
          "The ipsec Phase-2 Failure Table index.
           The value of the index is a number which begins at one and
           is incremented with each ipsec Phase-1 failure. The value
           of this object will wrap at 2,147,483,647."
       ::= { ipsecFailEntry 1 }

    ipsecFailReason OBJECT-TYPE
       SYNTAX INTEGER{
                other(1),
                internalError(2),
                peerEncodingError(3),
                proposalFailure(4),
                protocolUseFail(5),
                nonExistentSa(6),
                decryptFailure(7),
                encryptFailure(8),
                inAuthFailure(9),
                outAuthFailure(10),
                compression(11),
                sysCapExceeded(12),
                peerDelRequest(13),
                peerLost(14),
                seqNumRollOver(15),
                operRequest(16)
              }
       MAX-ACCESS read-only
       STATUS current
       DESCRIPTION
          "The reason for the failure.  Possible reasons include:
            1 = other
            2 = internal error occurred
            3 = peer encoding error
            4 = proposal failure
            5 = protocol use failure
            6 = non-existent security association
            7 = decryption failure
            8 = encryption failure
            9 = inbound authentication failure
           10 = outbound authentication failure
           11 = compression failure
           12 = system capacity failure
           13 = peer delete request was received
           14 = contact with peer was lost
           15 = sequence number rolled over
           16 = operator requested termination."
       ::= { ipsecFailEntry 2 }

    ipsecFailTime OBJECT-TYPE
       SYNTAX TimeStamp
       MAX-ACCESS read-only
       STATUS current
       DESCRIPTION
          "The time of the failure in hundredths of seconds."
       ::= { ipsecFailEntry 3 }

    ipsecFailTunnelIndex OBJECT-TYPE
       SYNTAX Integer32(0..65535)
       MAX-ACCESS read-only
       STATUS current
       DESCRIPTION
          "The Phase-2 Tunnel index (ipsecTunIndex)."
       ::= { ipsecFailEntry 4 }

    ipsecFailSaSpi  OBJECT-TYPE
       SYNTAX Integer32
       MAX-ACCESS read-only
       STATUS current
       DESCRIPTION
          "The security association SPI value."
       ::= { ipsecFailEntry 5 }

    ipsecFailPktSrcAddr  OBJECT-TYPE
       SYNTAX IPSIpAddress
       MAX-ACCESS read-only
       STATUS current
       DESCRIPTION
          "The packet's source IP address."
       ::= { ipsecFailEntry 6 }

    ipsecFailPktDstAddr  OBJECT-TYPE
       SYNTAX IPSIpAddress
       MAX-ACCESS read-only
       STATUS current
       DESCRIPTION
          "The packet's destination IP address."
       ::= { ipsecFailEntry 7 }

 -- ----------------------------------------------------------------------------
 -- The ipsec TRAP Control Group
 --
 -- This group of objects controls the sending of ipsec TRAPs.
 -- ----------------------------------------------------------------------------
    ipsecTrapCntlIkeTunnelStart OBJECT-TYPE
       SYNTAX TrapStatus
       MAX-ACCESS read-write
       STATUS current
       DESCRIPTION
          "This object defines the administrative state of sending the
           ipsec IKE Phase-1 Tunnel Start TRAP "
       DEFVAL { disabled }
       ::= { ipsecTrapCntl 1 }

    ipsecTrapCntlIkeTunnelStop OBJECT-TYPE
       SYNTAX TrapStatus
       MAX-ACCESS read-write
       STATUS current
       DESCRIPTION
          "This object defines the administrative state of sending the
           ipsec IKE Phase-1 Tunnel Stop TRAP "
       DEFVAL { disabled }
       ::= { ipsecTrapCntl 2 }

    ipsecTrapCntlIkeSysFailure OBJECT-TYPE
       SYNTAX TrapStatus
       MAX-ACCESS read-write
       STATUS current
       DESCRIPTION
          "This object defines the administrative state of sending the
           ipsec IKE Phase-1 System Failure TRAP "
       DEFVAL { disabled }
       ::= { ipsecTrapCntl 3 }

    ipsecTrapCntlIkeCertCrlFailure OBJECT-TYPE
       SYNTAX TrapStatus
       MAX-ACCESS read-write
       STATUS current
       DESCRIPTION
          "This object defines the administrative state of sending the
           ipsec IKE Phase-1 Certificate/CRL Failure TRAP "
       DEFVAL { disabled }
       ::= { ipsecTrapCntl 4 }

    ipsecTrapCntlIkeProtocolFailure OBJECT-TYPE
       SYNTAX TrapStatus
       MAX-ACCESS read-write
       STATUS current
       DESCRIPTION
          "This object defines the administrative state of sending the
           ipsec IKE Phase-1 Protocol Failure TRAP "
       DEFVAL { disabled }
       ::= { ipsecTrapCntl 5 }

    ipsecTrapCntlIkeNoSa OBJECT-TYPE
       SYNTAX TrapStatus
       MAX-ACCESS read-write
       STATUS current
       DESCRIPTION
          "This object defines the administrative state of sending the
           ipsec IKE Phase-1 No Security Association TRAP "
       DEFVAL { disabled }
       ::= { ipsecTrapCntl 6 }

    ipsecTrapCntlipsecTunnelStart OBJECT-TYPE
       SYNTAX TrapStatus
       MAX-ACCESS read-write
       STATUS current
       DESCRIPTION
          "This object defines the administrative state of sending the ipsec
           Phase-2 Tunnel Start TRAP "
       DEFVAL { disabled }
       ::= { ipsecTrapCntl 7 }

    ipsecTrapCntlipsecTunnelStop OBJECT-TYPE
       SYNTAX TrapStatus
       MAX-ACCESS read-write
       STATUS current
       DESCRIPTION
          "This object defines the administrative state of sending the ipsec
           Phase-2 Tunnel Stop TRAP "
       DEFVAL { disabled }
       ::= { ipsecTrapCntl 8 }

    ipsecTrapCntlipsecSysFailure OBJECT-TYPE
       SYNTAX TrapStatus
       MAX-ACCESS read-write
       STATUS current
       DESCRIPTION
          "This object defines the administrative state of sending the ipsec
           Phase-2 System Failure TRAP "
       DEFVAL { disabled }
       ::= { ipsecTrapCntl 9 }

    ipsecTrapCntlipsecSetUpFailure OBJECT-TYPE
       SYNTAX TrapStatus
       MAX-ACCESS read-write
       STATUS current
       DESCRIPTION
          "This object defines the administrative state of sending the ipsec
           Phase-2 Set Up Failure TRAP "
       DEFVAL { disabled }
       ::= { ipsecTrapCntl 10 }

    ipsecTrapCntlipsecEarlyTunTerm OBJECT-TYPE
       SYNTAX TrapStatus
       MAX-ACCESS read-write
       STATUS current
       DESCRIPTION
          "This object defines the administrative state of sending the ipsec
           Phase-2 Earily Tunnel Termination TRAP "
       DEFVAL { disabled }
       ::= { ipsecTrapCntl 11 }

    ipsecTrapCntlipsecProtocolFailure OBJECT-TYPE
       SYNTAX TrapStatus
       MAX-ACCESS read-write
       STATUS current
       DESCRIPTION
          "This object defines the administrative state of sending the ipsec
           Phase-2 Protocol Failure TRAP "
       DEFVAL { disabled }
       ::= { ipsecTrapCntl 12 }

    ipsecTrapCntlipsecNoSa OBJECT-TYPE
       SYNTAX TrapStatus
       MAX-ACCESS read-write
       STATUS current
       DESCRIPTION
          "This object defines the administrative state of sending the ipsec
           Phase-2  No Security Association TRAP "
       DEFVAL { disabled }
       ::= { ipsecTrapCntl 13 }

 -- ----------------------------------------------------------------------------
 -- ipsec Notifications - TRAPs
 -- ----------------------------------------------------------------------------

    ipsecMIBNotifications   OBJECT IDENTIFIER  ::= {ipsecMIB 0}

    ikeTunnelStart NOTIFICATION-TYPE
       OBJECTS {
                 ikePeerLocalType,
                 ikePeerLocalValue,
                 ikePeerLocalAddr,
                 ikePeerRemoteType,
                 ikePeerRemoteValue,
                 ikePeerRemoteAddr,
                 ikePeerIntIndex,
                 ikeTunIndex
               }
       STATUS  current
       DESCRIPTION
          "This notification is generated when an ipsec Phase-1
           IKE Tunnel becomes active."
       ::= { ipsecMIBNotifications 1 }

    ikeTunnelStop NOTIFICATION-TYPE
       OBJECTS {
                 ikePeerLocalType,
                 ikePeerLocalValue,
                 ikePeerLocalAddr,
                 ikePeerRemoteType,
                 ikePeerRemoteValue,
                 ikePeerRemoteAddr,
                 ikePeerIntIndex,
                 ikeTunIndex
               }
       STATUS  current
       DESCRIPTION
          "This notification is generated when an ipsec Phase-1
           IKE Tunnel becomes inactive."
       ::= { ipsecMIBNotifications 2 }

    ikeSysFailure NOTIFICATION-TYPE
       OBJECTS {
                 ikePeerLocalType,
                 ikePeerLocalValue,
                 ikePeerLocalAddr,
                 ikePeerRemoteType,
                 ikePeerRemoteValue,
                 ikePeerRemoteAddr,
                 ikePeerIntIndex
               }
       STATUS  current
       DESCRIPTION
          "This notification is generated when the processing for
           an ipsec Phase-1 IKE Tunnel experiences an internal
           or system capacity error."
       ::= { ipsecMIBNotifications 3 }

    ikeCertCrlFailure NOTIFICATION-TYPE
       OBJECTS {
                 ikePeerLocalType,
                 ikePeerLocalValue,
                 ikePeerLocalAddr,
                 ikePeerRemoteType,
                 ikePeerRemoteValue,
                 ikePeerRemoteAddr,
                 ikePeerIntIndex
               }
       STATUS  current
       DESCRIPTION
          "This notification is generated when the processing for
           an ipsec Phase-1 IKE Tunnel experiences a Certificate
           or a Certificate Revoke List (CRL) related error."
       ::= { ipsecMIBNotifications 4 }

    ikeProtocolFailure NOTIFICATION-TYPE
       OBJECTS {
                 ikePeerLocalType,
                 ikePeerLocalValue,
                 ikePeerLocalAddr,
                 ikePeerRemoteType,
                 ikePeerRemoteValue,
                 ikePeerRemoteAddr,
                 ikePeerIntIndex
               }
       STATUS  current
       DESCRIPTION
          "This notification is generated when the processing for
           an ipsec Phase-1 IKE Tunnel experiences a protocol
           related error."
       ::= { ipsecMIBNotifications 5 }

    ikeNoSa NOTIFICATION-TYPE
       OBJECTS {
                 ikePeerLocalType,
                 ikePeerLocalValue,
                 ikePeerLocalAddr,
                 ikePeerRemoteType,
                 ikePeerRemoteValue,
                 ikePeerRemoteAddr,
                 ikePeerIntIndex
               }
       STATUS  current
       DESCRIPTION
          "This notification is generated when the processing for
           an ipsec Phase-1 IKE Tunnel experiences a non-existent
           security association error."
       ::= { ipsecMIBNotifications 6 }

    ipsecTunnelStart NOTIFICATION-TYPE
       OBJECTS {
                 ipsecTunIndex
               }
       STATUS  current
       DESCRIPTION
          "This notification is generated when an ipsec Phase-2
           Tunnel becomes active."
        ::= { ipsecMIBNotifications 7 }

    ipsecTunnelStop NOTIFICATION-TYPE
       OBJECTS {
                 ipsecTunIndex
               }
       STATUS  current
       DESCRIPTION
          "This notification is generated when an ipsec Phase-2
           Tunnel becomes inactive."
       ::= { ipsecMIBNotifications 8 }

    ipsecSysFailure NOTIFICATION-TYPE
       OBJECTS {
                 ikePeerLocalType,
                 ikePeerLocalValue,
                 ikePeerLocalAddr,
                 ikePeerRemoteType,
                 ikePeerRemoteValue,
                 ikePeerRemoteAddr,
                 ikePeerIntIndex,
                 ipsecTunIndex,
                 ipsecSpiIndex
               }
       STATUS  current
       DESCRIPTION
          "This notification is generated when the processing for
           an ipsec Phase-2 Tunnel experiences an internal
           or system capacity error."
       ::= { ipsecMIBNotifications 9 }

    ipsecSetUpFailure NOTIFICATION-TYPE
       OBJECTS {
                 ikePeerLocalType,
                 ikePeerLocalValue,
                 ikePeerLocalAddr,
                 ikePeerRemoteType,
                 ikePeerRemoteValue,
                 ikePeerRemoteAddr,
                 ikePeerIntIndex
               }
       STATUS  current
       DESCRIPTION
          "This notification is generated when the setup for
           an ipsec Phase-2 Tunnel fails."
       ::= { ipsecMIBNotifications 10 }

    ipsecEarilyTunnelTerm NOTIFICATION-TYPE
       OBJECTS {
                 ipsecTunIndex,
                 ipsecSpiIndex
               }
       STATUS  current
       DESCRIPTION
          "This notification is generated when an an ipsec Phase-2
           Tunnel is terminated earily or before expected."
       ::= { ipsecMIBNotifications 11 }

    ipsecProtocolFailure NOTIFICATION-TYPE
       OBJECTS {
                 ipsecTunIndex,
                 ipsecSpiIndex
               }
       STATUS  current
       DESCRIPTION
          "This notification is generated when the processing for
           an ipsec Phase-2 Tunnel experiences a protocol
           related error."
       ::= { ipsecMIBNotifications 12 }

    ipsecNoSa NOTIFICATION-TYPE
       OBJECTS {
                 ipsecTunIndex,
                 ipsecSpiIndex
               }
       STATUS  current
       DESCRIPTION
          "This notification is generated when the processing for
           an ipsec Phase-2 Tunnel experiences a non-existent
           security association error."
       ::= { ipsecMIBNotifications 13 }

 -- ----------------------------------------------------------------------------
 -- Conformance Information
 -- ----------------------------------------------------------------------------
    ipsecMIBConformance   OBJECT IDENTIFIER ::= { ipsecMIB 2 }

    ipsecMIBGroups        OBJECT IDENTIFIER ::= { ipsecMIBConformance 1 }
    ipsecMIBCompliances   OBJECT IDENTIFIER ::= { ipsecMIBConformance 2 }

 -- ----------------------------------------------------------------------------
 -- Compliance Statements
 -- ----------------------------------------------------------------------------
    ipsecMIBCompliance       MODULE-COMPLIANCE
       STATUS      current
       DESCRIPTION
         "The compliance statement for SNMP entities
          the IP Security Protocol."

       MODULE -- this module
         MANDATORY-GROUPS  { ipsecLevelsGroup,
                             ipsecPhaseOneGroup,
                             ipsecPhaseTwoGroup
                           }

         OBJECT   ikeTunStatus
         MIN-ACCESS read-only
         DESCRIPTION
           "Write access is not required."

         OBJECT   ipsecTunStatus
         MIN-ACCESS read-only
         DESCRIPTION
           "Write access is not required."

         ::= { ipsecMIBCompliances 1 }

 -- ----------------------------------------------------------------------------
 -- Units of Conformance
 -- ----------------------------------------------------------------------------
    ipsecLevelsGroup OBJECT-GROUP
       OBJECTS {
                 ipsecMibLevel
               }
       STATUS current
       DESCRIPTION
          "This group consists of a:
           1) ipsec MIB Level"
       ::= { ipsecMIBGroups 1 }

    ipsecPhaseOneGroup OBJECT-GROUP
       OBJECTS {
                 -- The ipsec Phase-1 Global Statistics
                 ikeGlobalActiveTunnels,
                 ikeGlobalPreviousTunnels,
                 ikeGlobalInOctets,
                 ikeGlobalInPkts,
                 ikeGlobalInDropPkts,
                 ikeGlobalInNotifys,
                 ikeGlobalInP2Exchgs,
                 ikeGlobalInP2ExchgInvalids,
                 ikeGlobalInP2ExchgRejects,
                 ikeGlobalInP2SaDelRequests,
                 ikeGlobalOutOctets,
                 ikeGlobalOutPkts,
                 ikeGlobalOutDropPkts,
                 ikeGlobalOutNotifys,
                 ikeGlobalOutP2Exchgs,
                 ikeGlobalOutP2ExchgInvalids,
                 ikeGlobalOutP2ExchgRejects,
                 ikeGlobalOutP2SaDelRequests,
                 ikeGlobalInitTunnels,
                 ikeGlobalInitTunnelFails,
                 ikeGlobalRespTunnelFails,
                 ikeGlobalSysCapFails,
                 ikeGlobalAuthFails,
                 ikeGlobalDecryptFails,
                 ikeGlobalHashValidFails,
                 ikeGlobalNoSaFails,

                 -- The ipsec Phase-1 Internet Key Exchange Peer Table
                 -- ikePeerLocalType,
                 -- ikePeerLocalValue,
                 -- ikePeerRemoteType,
                 -- ikePeerRemoteValue,
                 -- ikePeerIntIndex,
                 ikePeerLocalAddr,
                 ikePeerRemoteAddr,
                 ikePeerActiveTime,
                 ikePeerActiveTunnelIndex,

                 -- The ipsec Phase-1 Internet Key Exchange Tunnel Table
                 -- ikeTunIndex,
                 ikeTunLocalType,
                 ikeTunLocalValue,
                 ikeTunLocalAddr,
                 ikeTunLocalName,
                 ikeTunRemoteType,
                 ikeTunRemoteValue,
                 ikeTunRemoteAddr,
                 ikeTunRemoteName,
                 ikeTunNegoMode,
                 ikeTunDiffHellmanGrp,
                 ikeTunEncryptAlgo,
                 ikeTunHashAlgo,
                 ikeTunAuthMethod,
                 ikeTunLifeTime,
                 ikeTunActiveTime,
                 ikeTunSaRefreshThreshold,
                 ikeTunTotalRefreshes,
                 ikeTunInOctets,
                 ikeTunInPkts,
                 ikeTunInDropPkts,
                 ikeTunInNotifys,
                 ikeTunInP2Exchgs,
                 ikeTunInP2ExchgInvalids,
                 ikeTunInP2ExchgRejects,
                 ikeTunInP2SaDelRequests,
                 ikeTunOutOctets,
                 ikeTunOutPkts,
                 ikeTunOutDropPkts,
                 ikeTunOutNotifys,
                 ikeTunOutP2Exchgs,
                 ikeTunOutP2ExchgInvalids,
                 ikeTunOutP2ExchgRejects,
                 ikeTunOutP2SaDelRequests,
                 ikeTunStatus,

                 -- The Internet Key Exchange Peer Association to Phase-2 Tunnel
                 -- Correlation Table
                 -- ikePeerCorrLocalType,
                 -- ikePeerCorrLocalValue,
                 -- ikePeerCorrRemoteType,
                 -- ikePeerCorrRemoteValue,
                 -- ikePeerCorrIntIndex,
                 -- ikePeerCorrSeqNum,
                 ikePeerCorripsecTunIndex
               }
       STATUS current
       DESCRIPTION
          "This group consists of:
           1) ipsec Phase-1 Global Objects
           2) ipsec Phase-1 Peer Table
           3) ipsec Phase-1 Tunnel Table
           4) ipsec Phase-1 Correlation Table"
       ::= { ipsecMIBGroups 2 }

    ipsecPhaseTwoGroup OBJECT-GROUP
       OBJECTS {
                 -- The ipsec Phase-2 Global Tunnel Statistics
                 ipsecGlobalActiveTunnels,
                 ipsecGlobalPreviousTunnels,
                 ipsecGlobalInOctets,
                 ipsecGlobalHcInOctets,
                 ipsecGlobalInOctWraps,
                 ipsecGlobalInDecompOctets,
                 ipsecGlobalHcInDecompOctets,
                 ipsecGlobalInDecompOctWraps,
                 ipsecGlobalInPkts,
                 ipsecGlobalInDrops,
                 ipsecGlobalInReplayDrops,
                 ipsecGlobalInAuths,
                 ipsecGlobalInAuthFails,
                 ipsecGlobalInDecrypts,
                 ipsecGlobalInDecryptFails,
                 ipsecGlobalOutOctets,
                 ipsecGlobalHcOutOctets,
                 ipsecGlobalOutOctWraps,
                 ipsecGlobalOutUncompOctets,
                 ipsecGlobalHcOutUncompOctets,
                 ipsecGlobalOutUncompOctWraps,
                 ipsecGlobalOutPkts,
                 ipsecGlobalOutDrops,
                 ipsecGlobalOutAuths,
                 ipsecGlobalOutAuthFails,
                 ipsecGlobalOutEncrypts,
                 ipsecGlobalOutEncryptFails,
                 ipsecGlobalProtocolUseFails,
                 ipsecGlobalNoSaFails,
                 ipsecGlobalSysCapFails,

                 -- The ipsec Phase-2 Tunnel Table
                 -- ipsecTunIndex,
                 ipsecTunIkeTunnelIndex,
                 ipsecTunIkeTunnelAlive,
                 ipsecTunLocalAddr,
                 ipsecTunRemoteAddr,
                 ipsecTunKeyType,
                 ipsecTunEncapMode,
                 ipsecTunLifeSize,
                 ipsecTunLifeTime,
                 ipsecTunActiveTime,
                 ipsecTunSaLifeSizeThreshold,
                 ipsecTunSaLifeTimeThreshold,
                 ipsecTunTotalRefreshes,
                 ipsecTunExpiredSaInstances,
                 ipsecTunCurrentSaInstances,
                 ipsecTunInSaDiffHellmanGrp,
                 ipsecTunInSaEncryptAlgo,
                 ipsecTunInSaAhAuthAlgo,
                 ipsecTunInSaEspAuthAlgo,
                 ipsecTunInSaDecompAlgo,
                 ipsecTunOutSaDiffHellmanGrp,
                 ipsecTunOutSaEncryptAlgo,
                 ipsecTunOutSaAhAuthAlgo,
                 ipsecTunOutSaEspAuthAlgo,
                 ipsecTunOutSaCompAlgo,
                 ipsecTunInOctets,
                 ipsecTunHcInOctets,
                 ipsecTunInOctWraps,
                 ipsecTunInDecompOctets,
                 ipsecTunHcInDecompOctets,
                 ipsecTunInDecompOctWraps,
                 ipsecTunInPkts,
                 ipsecTunInDropPkts,
                 ipsecTunInReplayDropPkts,
                 ipsecTunInAuths,
                 ipsecTunInAuthFails,
                 ipsecTunInDecrypts,
                 ipsecTunInDecryptFails,
                 ipsecTunOutOctets,
                 ipsecTunHcOutOctets,
                 ipsecTunOutOctWraps,
                 ipsecTunOutUncompOctets,
                 ipsecTunHcOutUncompOctets,
                 ipsecTunOutUncompOctWraps,
                 ipsecTunOutPkts,
                 ipsecTunOutDropPkts,
                 ipsecTunOutAuths,
                 ipsecTunOutAuthFails,
                 ipsecTunOutEncrypts,
                 ipsecTunOutEncryptFails,
                 ipsecTunStatus,

                 -- The ipsec Phase-2 Tunnel Endpoint Table
                 -- ipsecEndPtIndex,
                 ipsecEndPtLocalName,
                 ipsecEndPtLocalType,
                 ipsecEndPtLocalAddr1,
                 ipsecEndPtLocalAddr2,
                 ipsecEndPtLocalProtocol,
                 ipsecEndPtLocalPort,
                 ipsecEndPtRemoteName,
                 ipsecEndPtRemoteType,
                 ipsecEndPtRemoteAddr1,
                 ipsecEndPtRemoteAddr2,
                 ipsecEndPtRemoteProtocol,
                 ipsecEndPtRemotePort,

                 -- The ipsec Phase-2 Security Protection Index Table
                 -- ipsecSpiIndex,
                 ipsecSpiDirection,
                 ipsecSpiValue,
                 ipsecSpiProtocol,
                 ipsecSpiStatus
               }
       STATUS current
       DESCRIPTION
          "This group consists of:
           1) ipsec Phase-2 Global Statistics
           2) ipsec Phase-2 Tunnel Table
           3) ipsec Phase-2 Endpoint Table
           4) ipsec Phase-2 Security Protection Index Table"
       ::= { ipsecMIBGroups 3 }

    ipsecHistoryGroup OBJECT-GROUP
       OBJECTS {
                 -- ipsec History Global Control Objects
                 ipsecHistTableSize,

                 -- The ipsec Phase-1 Tunnel History Table
                 -- ikeTunHistIndex,
                 ikeTunHistTermReason,
                 ikeTunHistActiveIndex,
                 ikeTunHistPeerLocalType,
                 ikeTunHistPeerLocalValue,
                 ikeTunHistPeerIntIndex,
                 ikeTunHistPeerRemoteType,
                 ikeTunHistPeerRemoteValue,
                 ikeTunHistLocalAddr,
                 ikeTunHistLocalName,
                 ikeTunHistRemoteAddr,
                 ikeTunHistRemoteName,
                 ikeTunHistNegoMode,
                 ikeTunHistDiffHellmanGrp,
                 ikeTunHistEncryptAlgo,
                 ikeTunHistHashAlgo,
                 ikeTunHistAuthMethod,
                 ikeTunHistLifeTime,
                 ikeTunHistStartTime,
                 ikeTunHistActiveTime,
                 ikeTunHistTotalRefreshes,
                 ikeTunHistTotalSas,
                 ikeTunHistInOctets,
                 ikeTunHistInPkts,
                 ikeTunHistInDropPkts,
                 ikeTunHistInNotifys,
                 ikeTunHistInP2Exchgs,
                 ikeTunHistInP2ExchgInvalids,
                 ikeTunHistInP2ExchgRejects,
                 ikeTunHistInP2SaDelRequests,
                 ikeTunHistOutOctets,
                 ikeTunHistOutPkts,
                 ikeTunHistOutDropPkts,
                 ikeTunHistOutNotifys,
                 ikeTunHistOutP2Exchgs,
                 ikeTunHistOutP2ExchgInvalids,
                 ikeTunHistOutP2ExchgRejects,
                 ikeTunHistOutP2SaDelRequests,

                 -- The ipsec Phase-2 Tunnel History Table
                 -- ipsecTunHistIndex,
                 ipsecTunHistTermReason,
                 ipsecTunHistActiveIndex,
                 ipsecTunHistIkeTunnelIndex,
                 ipsecTunHistLocalAddr,
                 ipsecTunHistRemoteAddr,
                 ipsecTunHistKeyType,
                 ipsecTunHistEncapMode,
                 ipsecTunHistLifeSize,
                 ipsecTunHistLifeTime,
                 ipsecTunHistStartTime,
                 ipsecTunHistActiveTime,
                 ipsecTunHistTotalRefreshes,
                 ipsecTunHistTotalSas,
                 ipsecTunHistInSaDiffHellmanGrp,
                 ipsecTunHistInSaEncryptAlgo,
                 ipsecTunHistInSaAhAuthAlgo,
                 ipsecTunHistInSaEspAuthAlgo,
                 ipsecTunHistInSaDecompAlgo,
                 ipsecTunHistOutSaDiffHellmanGrp,
                 ipsecTunHistOutSaEncryptAlgo,
                 ipsecTunHistOutSaAhAuthAlgo,
                 ipsecTunHistOutSaEspAuthAlgo,
                 ipsecTunHistOutSaCompAlgo,
                 ipsecTunHistInOctets,
                 ipsecTunHistHcInOctets,
                 ipsecTunHistInOctWraps,
                 ipsecTunHistInDecompOctets,
                 ipsecTunHistHcInDecompOctets,
                 ipsecTunHistInDecompOctWraps,
                 ipsecTunHistInPkts,
                 ipsecTunHistInDropPkts,
                 ipsecTunHistInReplayDropPkts,
                 ipsecTunHistInAuths,
                 ipsecTunHistInAuthFails,
                 ipsecTunHistInDecrypts,
                 ipsecTunHistInDecryptFails,
                 ipsecTunHistOutOctets,
                 ipsecTunHistHcOutOctets,
                 ipsecTunHistOutOctWraps,
                 ipsecTunHistOutUncompOctets,
                 ipsecTunHistHcOutUncompOctets,
                 ipsecTunHistOutUncompOctWraps,
                 ipsecTunHistOutPkts,
                 ipsecTunHistOutDropPkts,
                 ipsecTunHistOutAuths,
                 ipsecTunHistOutAuthFails,
                 ipsecTunHistOutEncrypts,
                 ipsecTunHistOutEncryptFails,

                 -- The ipsec Phase-2 End Point History Table
                 -- ipsecEndPtHistIndex,
                 ipsecEndPtHistTunIndex,
                 ipsecEndPtHistActiveIndex,
                 ipsecEndPtHistLocalName,
                 ipsecEndPtHistLocalType,
                 ipsecEndPtHistLocalAddr1,
                 ipsecEndPtHistLocalAddr2,
                 ipsecEndPtHistLocalProtocol,
                 ipsecEndPtHistLocalPort,
                 ipsecEndPtHistRemoteName,
                 ipsecEndPtHistRemoteType,
                 ipsecEndPtHistRemoteAddr1,
                 ipsecEndPtHistRemoteAddr2,
                 ipsecEndPtHistRemoteProtocol,
                 ipsecEndPtHistRemotePort
               }
       STATUS current
       DESCRIPTION
          "This group consists of:
           1) ipsec History Global Objects
           2) ipsec Phase-1 History Objects
           3) ipsec Phase-2 History Objects"
       ::= { ipsecMIBGroups 4 }

    ipsecFailuresGroup OBJECT-GROUP
       OBJECTS {
                 -- The ipsec Failure Global Control Objects
                 ipsecFailTableSize,

                 -- The ipsec Phase-1 Failure Table
                 -- ikeFailIndex,
                 ikeFailReason,
                 ikeFailTime,
                 ikeFailLocalType,
                 ikeFailLocalValue,
                 ikeFailRemoteType,
                 ikeFailRemoteValue,
                 ikeFailLocalAddr,
                 ikeFailRemoteAddr,

                 -- The ipsec Phase-2 Failure Table
                 -- ipsecFailIndex,
                 ipsecFailReason,
                 ipsecFailTime,
                 ipsecFailTunnelIndex,
                 ipsecFailSaSpi,
                 ipsecFailPktSrcAddr,
                 ipsecFailPktDstAddr
               }
       STATUS current
       DESCRIPTION
          "This group consists of:
           1) ipsec Failure Global Objects
           2) ipsec Phase-1 Tunnel Failure Table
           3) ipsec Phase-2 Tunnel Failure Table"
       ::= { ipsecMIBGroups 5 }

    ipsecTrapCntlGroup OBJECT-GROUP
       OBJECTS {
                 ipsecTrapCntlIkeTunnelStart,
                 ipsecTrapCntlIkeTunnelStop,
                 ipsecTrapCntlIkeSysFailure,
                 ipsecTrapCntlIkeCertCrlFailure,
                 ipsecTrapCntlIkeProtocolFailure,
                 ipsecTrapCntlIkeNoSa,
                 ipsecTrapCntlipsecTunnelStart,
                 ipsecTrapCntlipsecTunnelStop,
                 ipsecTrapCntlipsecSysFailure,
                 ipsecTrapCntlipsecSetUpFailure,
                 ipsecTrapCntlipsecEarlyTunTerm,
                 ipsecTrapCntlipsecProtocolFailure,
                 ipsecTrapCntlipsecNoSa
               }
       STATUS current
       DESCRIPTION
          "This group of objects controls the sending of ipsec TRAPs."
       ::= { ipsecMIBGroups 6 }

    ipsecNotificationGroup    NOTIFICATION-GROUP
       NOTIFICATIONS {
                       ikeTunnelStart,
                       ikeTunnelStop,
                       ikeSysFailure,
                       ikeCertCrlFailure,
                       ikeProtocolFailure,
                       ikeNoSa,
                       ipsecTunnelStart,
                       ipsecTunnelStop,
                       ipsecSysFailure,
                       ipsecSetUpFailure,
                       ipsecEarilyTunTerm,
                       ipsecProtocolFailure,
                       ipsecNoSa
                     }
       STATUS current
       DESCRIPTION
          "This group contains the notifications for the ipsec MIB."
       ::= { ipsecMIBGroups 7 }

 END

-- 
--     Copyright (C) The Internet Society (1998).  All Rights Reserved.
-- 
--     This document and translations of it may be copied and furnished to others,
--     and derivative works that comment on or otherwise explain it or assist in its
--     implementation may be prepared, copied, published and distributed, in whole
--     or in part, without restriction of any kind, provided that the above
--     copyright notice and this paragraph are included on all such copies and
--     derivative works.  However, this document itself may not be modified in any
--     way, such as by removing the copyright notice or references to the Internet
--     Society or other Internet organizations, except as needed for the purpose of
--     developing Internet standards in which case the procedures for copyrights
--     defined in the Internet Standards process must be followed, or as required to
--     translate it into languages other than English.
-- 
--     The limited permissions granted above are perpetual and will not be revoked
--     by the Internet Society or its successors or assigns.
-- 
--     This document and the information contained herein is provided on an "AS IS"
--     basis and THE INTERNET SOCIETY AND THE INTERNET ENGINEERING TASK FORCE
--     DISCLAIMS ALL WARRANTIES, EXPRESS OR IMPLIED, INCLUDING BUT NOT LIMITED TO
--     ANY WARRANTY THAT THE USE OF THE INFORMATION HEREIN WILL NOT INFRINGE ANY
--     RIGHTS OR ANY IMPLIED WARRANTIES OF MERCHANTABILITY OR FITNESS FOR A
--     PARTICULAR PURPOSE.
