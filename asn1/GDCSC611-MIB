-- Copyright 1996 General DataComm Ind., Inc. All Rights Reserved.
--
-- Reproduction of this document is authorized on condition that the
-- foregoing copyright notice is included. This General DataComm, GDC,
-- SNMP Management Information Base Specification embodies GDCs'
-- confidential and proprietary intellectual property. GDC retains all
-- title and ownership in the Specification, including any revisions.
--
-- It is GDCs intent to encourage the widespread use of this Specification
-- in connection with the management of GDC's products. GDC grants vendors,
-- end-users, and other interested parties a non-exclusive license to use
-- this Specification in connection with the management of GDC's products.
--
-- This Specification is supplied "AS IS," and GDC makes no warranty,
-- either expressed or implied, as to the use operation, condition, or
-- performance of the Specification.
--
-- Revision History
--
-- Version   Date       Name            Description
-- 1.00A     08-Dec-95	M. Cyr		Initial Revision
-- 1.00B     13-Mar-96	E. Moreno-Leon  Added Major and Minor BER Alarms
-- 1.00C     18-Mar-96  E. Moreno-Leon  Corrected value for DTE data rate

GDCSC611-MIB DEFINITIONS	   ::=	   BEGIN

IMPORTS

	enterprises			FROM RFC1155-SMI
	DisplayString                   FROM RFC1213-MIB
	OBJECT-TYPE                     FROM RFC-1212
	SCinstance                      FROM GDCMACRO-MIB;

gdc          OBJECT IDENTIFIER ::= { enterprises 498 }
bql2	     OBJECT IDENTIFIER ::= { gdc 12 }
bql611	     OBJECT IDENTIFIER ::= { bql2 2 }
bql621	     OBJECT IDENTIFIER ::= { bql2 3 }


-- This is the GDC MIB for SC611 and DC621 objects for ISDN 2B1Q.
--
-- This MIB is only usable when the configuration is software controllable.
--
-- See the GDC MIB requirements document to determine how the standard MIB's
-- are supported.
--
--*****************************************************************************
-- 	SCinstance is defined as the addressing/indexing method of accessing
--	table objects in this MIB. The SCinstance represents the SpectraComm
--	shelf Slot, Line, Drop and interface address.
--	Represented as SLDi, (Slot, Line, Drop, interface).
--	The SC611 and DC621 only supports one loop and one DTE channel.
--
--	SC611			DC621
--      -----                   -----
--      SLDi                    SLDi
--      L=1                     L=1
--      D=0                     D=XX  Depends what is the local unit
--      i=0 or 1                i=0 or 1
--
--*****************************************************************************



--**************************************************************************
--		GDC SC611 and DC621 - MIB VERSION NUMBER
--**************************************************************************

bql611MIBVersion	OBJECT-TYPE
	SYNTAX	DisplayString (SIZE (5))
	ACCESS	read-only
	STATUS  mandatory
	DESCRIPTION
		"The version number of the MIB, to allow products to 
		know which MIB is being supported.  The version number
		will be x.yzT where x is a major revision (1-9), y is a minor
		revision(0-9), z is a typo revision (0-9) and T indicates the
		MIB is still a test revision(A-Z).  When a release is complete
		no T should exist."
	::= { bql611 1 }
--*****************************************************************************
--              GDC SC611 and DC621 -  WHAT ARE YOU TABLE 
--*****************************************************************************
--
-- This table contains network element information indexed by SLDi.
--
-- This table uses SCinstance defined as follows:
--	SC611			DC621
--      -----                   -----
--      SLDi                    SLDi
--      L=1                     L=1
--      D=0                     D=XX Depends what is the local unit
--      i=0                     i=0 
--
--
bql611WhatAreYouTable OBJECT-TYPE
	SYNTAX	SEQUENCE OF Bql611WhatAreYouEntry
	ACCESS  not-accessible
	STATUS  mandatory
	DESCRIPTION
			"The GDC SC611 and DC621 What Are You Table."
	::= { bql611 2 }
bql611WhatAreYouEntry OBJECT-TYPE
	SYNTAX	Bql611WhatAreYouEntry
	ACCESS  not-accessible
	STATUS  mandatory
	DESCRIPTION
			"An entry in the GDC SC611 What Are You table."
	INDEX	{ bql611WhatAreYouIndex }
	::= { bql611WhatAreYouTable 1 }

Bql611WhatAreYouEntry ::=
	SEQUENCE  {
		  bql611WhatAreYouIndex		SCinstance,
		  bql611BaseCardType		INTEGER,
		  bql611OptionCard		INTEGER,
		  bql611DTECardType		INTEGER,
		  bql611CodeRev			DisplayString,
		  bql611AlarmStatus             OCTET STRING
		  }
bql611WhatAreYouIndex OBJECT-TYPE
	SYNTAX  SCinstance
	ACCESS  read-only
	STATUS  mandatory
	DESCRIPTION
	       "This object is the identifier of the SC611/DC621 What Are You table."
	::= { bql611WhatAreYouEntry 1 }

bql611BaseCardType OBJECT-TYPE
	SYNTAX	INTEGER {
			sc611(5),
			dc621(7)
			}
	ACCESS  read-only
	STATUS  mandatory
	DESCRIPTION
		"This function returns the value the Base Card Type."
	::= { bql611WhatAreYouEntry 2 }

bql611OptionCard OBJECT-TYPE
	SYNTAX  INTEGER {
			notInstalled(1),
			installed(2)
			}
	ACCESS  read-only
	STATUS  mandatory
	DESCRIPTION
		"This indicates whether the option card is installed or not
		 on the DC621."
	::= { bql611WhatAreYouEntry 3 }

bql611DTECardType	OBJECT-TYPE
	SYNTAX  INTEGER {
			eia530(1),
			x21(2),
			none(7)
			}
	ACCESS  read-only
	STATUS  mandatory
	DESCRIPTION
		"This object is the DTE plug-in card type. This variable
		 is used for a SC611 or DC621."
	::= { bql611WhatAreYouEntry 4 }

bql611CodeRev OBJECT-TYPE
	SYNTAX  DisplayString (SIZE (4))
	ACCESS  read-only
	STATUS  mandatory
	DESCRIPTION
		"This function returns the firmware code level.
		 Example A-  ,B-  "
	::= { bql611WhatAreYouEntry 5 }

bql611AlarmStatus OBJECT-TYPE
	SYNTAX	  OCTET STRING (SIZE (1..255))
	ACCESS	  read-only
	STATUS	  mandatory
	DESCRIPTION
		"The current alarms of the unit without the alarm masks."
	::= { bql611WhatAreYouEntry 6 }

--*****************************************************************************
-- 		CONFIGURATION TABLE
--*****************************************************************************
--
-- This table contains the network element's configuration information indexed by
-- SLDi and channel.
--
-- This table uses SCinstance defined as follows:
--	SC611			DC621
--      -----                   -----
--      SLDi                    SLDi
--      L=1                     L=1
--      D=0                     D=XX Depends what is the local unit
--      i=1                     i=1 

bql611ConfigTable OBJECT-TYPE
	SYNTAX	SEQUENCE OF Bql611ConfigEntry
	ACCESS  not-accessible
	STATUS  mandatory
	DESCRIPTION
		"The GDC SC611, DC621 2B1Q configuration table."
	::= { bql611 3 }
bql611ConfigEntry OBJECT-TYPE
	SYNTAX	Bql611ConfigEntry
	ACCESS  not-accessible
	STATUS  mandatory
	DESCRIPTION
		"A listing of GDC 2B1Q SC611/DC621 options."
	INDEX	{ bql611ConfigIndex }
	::= { bql611ConfigTable 1 }

Bql611ConfigEntry ::=
	SEQUENCE        {
			bql611ConfigIndex		SCinstance,
			bql611DteRate			INTEGER,
			bql611RateAdaption		INTEGER,
			bql611DteOperation		INTEGER,
			bql611TxClkSource		INTEGER,
			bql611WordLength		INTEGER,
			bql611OverSpeed			INTEGER,
			bql611RTS			INTEGER,
			bql611RTSCTSDelay		INTEGER,
			bql611DCD			INTEGER,
			bql611RDL			INTEGER,
			bql611RDLMethod			INTEGER,
			bql611RDLTimeout		INTEGER,
			bql611TestPattern		INTEGER
			}

bql611ConfigIndex OBJECT-TYPE
	SYNTAX  SCinstance
	ACCESS  read-only
	STATUS  mandatory
	DESCRIPTION
		"A unique index for the Configuration Table."
	::= { bql611ConfigEntry 1 }

bql611DteRate OBJECT-TYPE
	SYNTAX	INTEGER {
			kBps2Dot4(1),
			kBps4Dot8(2),
			kBps9Dot6(3),
			kBps19Dot2(4),
			kBps48(6),
			kBps64(9),
			kBps128(10)
			}
	ACCESS    read-write
	STATUS    mandatory
	DESCRIPTION     "Object to select the DTE rate for the SC611 or DC621."
	::= { bql611ConfigEntry 2 }

bql611RateAdaption OBJECT-TYPE
	SYNTAX	INTEGER {
			x50Div3(1),
			x50Div2(2)
			}
	ACCESS    read-write
	STATUS    mandatory
	DESCRIPTION     "Object to select the DTE Rate Adaption for the SC611 or DC621."
	::= { bql611ConfigEntry 3 }

bql611DteOperation OBJECT-TYPE
	SYNTAX	INTEGER {
			sync(1),
			async(2)
			}
	ACCESS    read-write
	STATUS    mandatory
	DESCRIPTION     "Object to select the DTE Operation for the SC611 or DC621."
	::= { bql611ConfigEntry 4 }

bql611TxClkSource OBJECT-TYPE
	SYNTAX	INTEGER {
			internal(1),
			external(2)
			}
	ACCESS    read-write
	STATUS    mandatory
	DESCRIPTION     "Object to select the Transmit Clock Source for the SC611 ONLY."
	::= { bql611ConfigEntry 5 }

bql611WordLength OBJECT-TYPE
	SYNTAX	INTEGER {
			bitWord8(1),
			bitWord9(2),
			bitWord10(3),
			bitWord11(4)
			}
	ACCESS    read-write
	STATUS    mandatory
	DESCRIPTION     "Object to select the Word Length for the SC611 or DC621 when selected
			 for async mode."
	::= { bql611ConfigEntry 6 }

bql611OverSpeed OBJECT-TYPE
	SYNTAX	INTEGER {
			onePercent(1),
			twoPointThreePercent(2)
			}
	ACCESS    read-write
	STATUS    mandatory
	DESCRIPTION     "Object to select the Over Speed for the SC611 or DC621."
	::= { bql611ConfigEntry 7 }

bql611RTS  OBJECT-TYPE
	SYNTAX	INTEGER {
			normal(1),
			force(2)
			}
	ACCESS    read-write
	STATUS    mandatory
	DESCRIPTION     "Object to select RTS for SC611 and DC621 only."
	::= { bql611ConfigEntry 8 }

bql611RTSCTSDelay OBJECT-TYPE
	SYNTAX	INTEGER {
			noDelay(1),
			delay(2)
			}
	ACCESS    read-write
	STATUS    mandatory
	DESCRIPTION     "Object to select RTS CTS Delay for SC611 and DC621."
	::= { bql611ConfigEntry 9 }

bql611DCD OBJECT-TYPE
	SYNTAX	INTEGER {
			normal(1),
			inBandRTS(2)
			}
	ACCESS    read-write
	STATUS    mandatory
	DESCRIPTION     "Object to select DCD  for SC611 and DC621."
	::= { bql611ConfigEntry 10 }

bql611RDL OBJECT-TYPE
	SYNTAX	INTEGER {
			enable(1),
			disable(2)
			}
	ACCESS    read-write
	STATUS    mandatory
	DESCRIPTION     "Object to select the RDL respond for SC611 and DC621."
	::= { bql611ConfigEntry 11 }

bql611RDLMethod OBJECT-TYPE
	SYNTAX	INTEGER {
			v54(1),
			eocorpn127(2)
			}
	ACCESS    read-write
	STATUS    mandatory
	DESCRIPTION     "Object to select RDL Method for SC611 and DC621.
			 SC611 Valid Choices         DC621 Valid Choices
                       ===================         ===================
			 V54                         V54
                         EOC                         PN127"
	::= { bql611ConfigEntry 12 }

bql611RDLTimeout OBJECT-TYPE
	SYNTAX	INTEGER {
			none(1),
			minutes10(2)
			}
	ACCESS    read-write
	STATUS    mandatory
	DESCRIPTION     "Object to select RDL Timeout for SC611 or DC621."
	::= { bql611ConfigEntry 13 }


bql611TestPattern OBJECT-TYPE
	SYNTAX	INTEGER {
			pattern2047(1),
			pattern511(2)
			}
	ACCESS    read-write
	STATUS    mandatory
	DESCRIPTION     "Object to Test Pattern for SC611 and DC621."
	::= { bql611ConfigEntry 14 }
--*****************************************************************************
--                    DIAGNOSTICS TABLE
--*****************************************************************************
--
-- This table contains the network element's diagnostic test information indexed by
-- SLDi and channel.
--
-- This table uses SCinstance defined as follows:
--	SC611			DC621
--      -----                   -----
--      SLDi                    SLDi
--      L=1                     L=1
--      D=0                     D=XX Depends what is the local unit
--      i=1                     i=1 

bql611DiagnosticTable OBJECT-TYPE
	SYNTAX	SEQUENCE OF Bql611DiagnosticEntry
	ACCESS    not-accessible
	STATUS    mandatory
	DESCRIPTION
			"The GDC SC611/DC621 diagnostics table."
	::= { bql611 4 }

bql611DiagnosticEntry OBJECT-TYPE
	SYNTAX	  Bql611DiagnosticEntry
	ACCESS    not-accessible
	STATUS    mandatory
	DESCRIPTION
			"A listing of GDC SC611/DC621 diagnostic tests"
	INDEX	   { bql611DiagnosticIndex }
	::= { bql611DiagnosticTable 1 }

Bql611DiagnosticEntry	::=
	SEQUENCE        {
			bql611DiagnosticIndex		SCinstance,
			bql611DiagnosticTest		INTEGER,
			bql611DiagnosticActive 		INTEGER,
			bql611DiagnosticResults		INTEGER,
			bql611DiagnosticResetErrorCount INTEGER
			}

bql611DiagnosticIndex OBJECT-TYPE
	SYNTAX    SCinstance
	ACCESS    read-only
	STATUS    mandatory
	DESCRIPTION
			"A unique index for the Diagnostic Table."
	::= { bql611DiagnosticEntry 1 }

bql611DiagnosticTest OBJECT-TYPE
	SYNTAX  INTEGER (0..63)
	ACCESS	  read-write
	STATUS    mandatory
	DESCRIPTION
			"This function selects or reads the test.
			 0  = no test currently operating
			 1  = remote loopback test
			 2  = channel loopback test
			 4  = data loopback test 
			 8  = selftest
			 16 = line loopback test
			 32 = terminate test

			 All other values are test combinations such as
			 9 = selftest and remote loopback."

	::= { bql611DiagnosticEntry 2 }

bql611DiagnosticActive OBJECT-TYPE
	SYNTAX  INTEGER {
			notActive (1),
			active (2)
			}
	ACCESS    read-only
	STATUS    mandatory
	DESCRIPTION
			"This function represents the test condition."
	::= { bql611DiagnosticEntry 3 }

bql611DiagnosticResults OBJECT-TYPE
	SYNTAX  INTEGER (0..16383)
	ACCESS    read-only
	STATUS    mandatory
	DESCRIPTION
			"This function reads the self test results in
			 bit errors."
	::= { bql611DiagnosticEntry 4 }


bql611DiagnosticResetErrorCount OBJECT-TYPE
	SYNTAX	INTEGER {
			normal(1),
			reset(2)
			}
	ACCESS    read-write
	STATUS    mandatory
	DESCRIPTION     "Object to reset selftest error count during diagnostic
			 self testing for SC611 and DC621."
	::= {  bql611DiagnosticEntry 5 }

--********************************************************************************
--	ALARMS SC611 2B1Q - INDIVIDUALLY IDENTIFIED FOR THE CONTROLLER
--********************************************************************************

bql611Alarm  OBJECT IDENTIFIER ::= { bql2 9 }

bql611AlarmData OBJECT IDENTIFIER ::= { bql611Alarm 1 }

-- no response alarm (this is a SCM generated alarm)
bql611NoResponseAlm OBJECT IDENTIFIER     			::= { bql611AlarmData 1 }

-- no diagnostic receive error alarm (this is a SCM generated alarm)
bql611DiagRxErrAlm OBJECT IDENTIFIER      			::= { bql611AlarmData 2 }

-- power up alarm
bql611PowerUpAlm OBJECT IDENTIFIER        			::= { bql611AlarmData 3 }

-- out of sync alarm
bql611OutofSyncAlm OBJECT IDENTIFIER    			::= { bql611AlarmData 4 }

-- tx clock out of tolerance
bql611TxClkOutOfToleranceAlm OBJECT IDENTIFIER			::= { bql611AlarmData 5 }

-- external transmit clock absent
bql611ExtClkAbsentAlm OBJECT IDENTIFIER				::= { bql611AlarmData 6 }

-- sealing current no continuity
bql611SealingCurrentNoContinuityAlm OBJECT IDENTIFIER     	::= { bql611AlarmData 7 }

-- dtr not present alarm
bql611DtrNotPresentAlm OBJECT IDENTIFIER   		  	::= { bql611AlarmData 8 }

-- Major BER alarm
bql611MajorAlarmBERAlm OBJECT IDENTIFIER  			::= { bql611AlarmData 9 }

-- Minor BER alarm
bql611MinorAlarmBERAlm OBJECT IDENTIFIER   	         	::= { bql611AlarmData 10 }

-- ALARM                             Maskable   Valid interfaces   Threshold
-- =========================================================================
-- bql611NoResponseAlm                   no         unit            	no
-- bql611DiagRxErrAlm                    no         unit            	no
-- bql611PowerUpAlm                      no         unit            	no
-- bql611OutofSyncAlm              	 yes        loop 1              no
-- bql611TxClkOutOfToleranceAlm  	 yes        loop 1  		no
-- bql611ExtClkAbsentAlm  		 yes        loop 1 		no
-- bql611SealingCurrentNoContinuityAlm   yes        loop 1 		no
-- bql611DtrNotPresentAlm		 yes	    loop 1		no
-- bql611MajorAlarmBERAlm		 yes        loop 1		yes
-- bql611MinorAlarmBERAlm                yes        loop 1 		yes


--********************************************************************************
--	ALARMS DC621 2B1Q - INDIVIDUALLY IDENTIFIED FOR THE CONTROLLER
--********************************************************************************

bql621Alarm  OBJECT IDENTIFIER ::= { bql2 11 }

bql621AlarmData OBJECT IDENTIFIER ::= { bql621Alarm 1 }

-- no response alarm (this is a SCM generated alarm)
bql621NoResponseAlm OBJECT IDENTIFIER     			::= { bql621AlarmData 1 }

-- no diagnostic receive error alarm (this is a SCM generated alarm)
bql621DiagRxErrAlm OBJECT IDENTIFIER      			::= { bql621AlarmData 2 }

-- power up alarm
bql621PowerUpAlm OBJECT IDENTIFIER        			::= { bql621AlarmData 3 }

-- dtr not present alarm
bql621DtrNotPresentAlm OBJECT IDENTIFIER   			::= { bql621AlarmData 4 }

-- Major BER alarm
bql621MajorAlarmBERAlm OBJECT IDENTIFIER  			::= { bql621AlarmData 5 }

-- Minor BER alarm
bql621MinorAlarmBERAlm OBJECT IDENTIFIER    			::= { bql621AlarmData 6 }

-- ALARM                             Maskable   Valid interfaces   Threshold
-- =========================================================================
-- bql621NoResponseAlm              no         unit            	no
-- bql621DiagRxErrAlm               no         unit            	no
-- bql621PowerUpAlm                 no         unit            	no
-- bql621DtrNotPresentAlm	    yes	       loop 1     	no
-- bql621MajorAlarmBERAlm	    yes        loop 1   	yes
-- bql621MinorAlarmBERAlm           yes        loop 1    	yes


--*****************************************************************************
--       Alarm Config  Table FOR SC621 and DC611.
--*****************************************************************************

bql611AlarmConfigTable OBJECT-TYPE
     SYNTAX SEQUENCE OF Bql611AlarmConfigEntry
     ACCESS not-accessible
     STATUS mandatory
     DESCRIPTION
	 "The bql611AlarmConfigTable contains entries that configure alarm
	 reporting.  The structure of the table is such that alarm
	 configuration is supported on a unit and interface basis, and
	 then on an alarm type basis within the interface.  For
	 simplicity sake alarms, be they unit or interface
	 related, are represented in one table."
     ::= { bql611Alarm 2 }

bql611AlarmConfigEntry OBJECT-TYPE
     SYNTAX Bql611AlarmConfigEntry
     ACCESS not-accessible
     STATUS mandatory
     DESCRIPTION
	 "An entry in the bql611AlarmConfigTable table."
     INDEX { bql611AlarmConfigIndex, bql611AlarmConfigIdentifier }
     ::= { bql611AlarmConfigTable 1 }

Bql611AlarmConfigEntry ::=
     SEQUENCE {
	 	bql611AlarmConfigIndex
	     	SCinstance,
	 	bql611AlarmConfigIdentifier
	     	OBJECT IDENTIFIER,
	 	bql611AlarmThreshold
	     	INTEGER
	     }

bql611AlarmConfigIndex OBJECT-TYPE
     SYNTAX SCinstance
     ACCESS read-only
     STATUS mandatory
     DESCRIPTION
	 "The index value which uniquely identifies the interface to
	 which this entry is applicable."
     ::= { bql611AlarmConfigEntry 1 }

bql611AlarmConfigIdentifier OBJECT-TYPE
     SYNTAX OBJECT IDENTIFIER
     ACCESS read-only
     STATUS mandatory
     DESCRIPTION
	 "The unique alarm identifier assigned to this alarm type.
	 The format of this identifier is an OBJECT IDENTIFIER that has
	 the following format: {iso(1) org(3) dod(6) internet(1)
	 private(4) enterprises(1) gdc(498) xxx(x) alarm(z) yyy(y) 
	 where xxx(x) is the administratively assigned family object 
	 identifier (z) is the object identifier for alarms in the family
	 defined MIB and yyy(y) is the administratively assigned alarm 
	 type identifier for this alarm."
     ::= { bql611AlarmConfigEntry 2 }


bql611AlarmThreshold OBJECT-TYPE
    SYNTAX INTEGER {
			thres10E03(1),
			thres10E04(2),
			thres10E05(3),
			thres10E06(4)
		}
	ACCESS  read-write
	STATUS  mandatory
	DESCRIPTION
		"This function sets/reads the Major or Minor BER alarm threshold criteria for a SC611 or DC621."
    ::= { bql611AlarmConfigEntry 3 }


--*****************************************************************************
--		      CONTROL TABLE FOR 2B1Q SC611 and DC621
--*****************************************************************************
--
-- This table contains the SC611 and DC621 control functions indexed by
-- SLDi.
--
-- This table uses SCinstance defined as follows:
--	SC611			DC621
--      -----                   -----
--      SLDi                    SLDi
--      L=1                     L=1
--      D=0                     D=XX Depends what is the local unit
--      i=0                     i=0 

bql611ControlTable OBJECT-TYPE
	SYNTAX	SEQUENCE OF Bql611ControlEntry
	ACCESS  not-accessible
	STATUS  mandatory
	DESCRIPTION
			"The GDC SC611 and DC621 Control Table."
	::= { bql611 5 }

bql611ControlEntry OBJECT-TYPE
	SYNTAX	Bql611ControlEntry
	ACCESS  not-accessible
	STATUS  mandatory
	DESCRIPTION
			"An entry in the GDC SC611/DC621 Control table."
	INDEX	{ bql611ControlIndex }
	::= { bql611ControlTable 1 }

Bql611ControlEntry ::=
	SEQUENCE {
		  bql611ControlIndex	SCinstance,
		  bql611SoftReset	INTEGER,
		  bql611EraseConfig	INTEGER,
		  bql611FrontPanel	INTEGER,
		  bql611LEDStatus	OCTET STRING,
		  bql621LEDStatus       OCTET STRING
		  }

bql611ControlIndex OBJECT-TYPE
	SYNTAX  SCinstance
	ACCESS  read-only
	STATUS  mandatory
	DESCRIPTION
	       "This object is the identifier of the SC611/DC621 Control table."
	::= { bql611ControlEntry 1 }

bql611SoftReset OBJECT-TYPE
	SYNTAX  INTEGER  {
			 normal(1),
			 reset(2)
			 }
        ACCESS  read-write
	STATUS  mandatory
	DESCRIPTION
                "Forces a soft reset on the network element.
                 The reset selection is write only. The normal
                 selection is read only."
	::= { bql611ControlEntry 2 }

bql611EraseConfig OBJECT-TYPE
	SYNTAX  INTEGER  {
			 normal(1),
			 erase(2)
			 }
      ACCESS  read-write
	STATUS  mandatory
	DESCRIPTION
		"Forces an erase of the stored configuration in the
                 network element. The erase selection is write only.
                 The normal selection is read only."
	::= { bql611ControlEntry 3 }

bql611FrontPanel OBJECT-TYPE
	SYNTAX  INTEGER {
		enable(1),
			disable(2)
			}
	ACCESS    read-write
	STATUS    mandatory
	DESCRIPTION
			"Object used to enable or disable the units front panel
			 switches."
	::= { bql611ControlEntry 4 }

bql611LEDStatus OBJECT-TYPE
	SYNTAX	OCTET STRING (SIZE (3))
	ACCESS  read-only
	STATUS  mandatory
	DESCRIPTION
			"The GDC SC611 front panel LED Status.
			 A value of 1 means on, 0 is off.
			 byte 1 bit 7 (1.7) - not used
			 1.6 - not used
			 1.5 - not used
			 1.4 - test mode
			 1.3 - alarm transitions
			 1.2 - self test
			 1.1 - line loopback
			 1.0 - remote loopback

			 2.7 - not used
			 2.6 - not used
			 2.5 - not used
			 2.4 - not used
			 2.3 - send data transitions
			 2.2 - receive data transitions
			 2.1 - request to send
			 2.0 - data carrier detect

			 3.7 - not used
			 3.6 - not used
			 3.5 - not used
			 3.4 - not used
			 3.3 - not used
			 3.2 - not used
			 3.1 - not used
			 3.0 - not used"
	::= { bql611ControlEntry 5 }

bql621LEDStatus OBJECT-TYPE
	SYNTAX	OCTET STRING (SIZE (3))
	ACCESS  read-only
	STATUS  mandatory
	DESCRIPTION
			"The GDC DC621 front panel LED Status.
			 A value of 1 means on, 0 is off.
			 byte 1 bit 7 (1.7) - not used
			 1.6 - test mode
			 1.5 - sync 
			 1.4 - request to send
			 1.3 - clear to send
			 1.2 - carrier 
			 1.1 - send data transitions
			 1.0 - receive data transitions

			 2.7 - not used
			 2.6 - not used
			 2.5 - not used
			 2.4 - not used
			 2.3 - not used
			 2.2 - not used
			 2.1 - not used
			 2.0 - not used

			 3.7 - not used
			 3.6 - not used
			 3.5 - not used
			 3.4 - not used
			 3.3 - not used
			 3.2 - not used
			 3.1 - not used
			 3.0 - not used"
	::= { bql611ControlEntry 6 }

--*****************************************************************************
--           STATISTICS TABLE - CURRENT 15 MINUTE INTERVAL TABLE
--*****************************************************************************
--
-- The SC611/DC621 current table contains various statistics being
-- collected for the current 15 minute interval.
-- It is indexed by SLDi.
--
-- This table uses SCinstance defined as follows:
--	SC611			DC621
--      -----                   -----
--      SLDi                    SLDi
--      L=1                     L=1
--      D=0                     D=XX Depends what is the local unit
--      i=1                     i=1 

bql611CurrentTable OBJECT-TYPE
             SYNTAX  SEQUENCE OF Bql611CurrentEntry
             ACCESS  not-accessible
             STATUS  mandatory
             DESCRIPTION
                "The SC611/DC621 Current table."
            ::= { bql611 6 }

bql611CurrentEntry OBJECT-TYPE
             SYNTAX  Bql611CurrentEntry
             ACCESS  not-accessible
             STATUS  mandatory
             DESCRIPTION
                "An entry in the SC611/DC621 Current table."
            INDEX   { bql611CurrentIndex }
            ::= { bql611CurrentTable 1 }

Bql611CurrentEntry ::=
         SEQUENCE {
                  bql611CurrentIndex	SCinstance,
                  bql611CurrentStats    OCTET STRING
		  }

bql611CurrentIndex OBJECT-TYPE
             SYNTAX  SCinstance
             ACCESS  read-only
             STATUS  mandatory
             DESCRIPTION
                "The index value which uniquely identifies  the
                SC611 interface to which this entry
		is applicable."
            ::= { bql611CurrentEntry 1 }

bql611CurrentStats OBJECT-TYPE
             SYNTAX  OCTET STRING (SIZE (12))
             ACCESS  read-only
             STATUS  mandatory
             DESCRIPTION
                "The number of Errored Seconds, Severely Errored Seconds &
		 Unavailable Errored Seconds  encountered  by
                an ISDN interface in the current 15 minute interval."
            ::= { bql611CurrentEntry 2 }

--*****************************************************************************
--           STATISTICS TABLE - 15 MINUTE INTERVAL TABLE
--*****************************************************************************
--
-- The SC611/DC621 Interval Table contains various statistics
-- collected by each ISDN Interface over the previous 24 hours of
-- operation.  The past 24 hours are broken into 96 completed
-- 15 minute intervals. This table is indexed by SLDi and Interval Number.
--
-- This table uses SCinstance defined as follows:
--	SC611			DC621
--      -----                   -----
--      SLDi                    SLDi
--      L=1                     L=1
--      D=0                     D=XX Depends what is the local unit
--      i=1                     i=1 
--
-- and Interval Number is a number between 1 and 96.
-- Where 1 is the most recently completed 15 minute
-- interval and 96 is the least recently completed 15 minute interval.
--

bql611IntervalTable OBJECT-TYPE
             SYNTAX  SEQUENCE OF Bql611IntervalEntry
             ACCESS  not-accessible
             STATUS  mandatory
             DESCRIPTION
                "The SC611/DC621 Interval table."
            ::= { bql611 8 }

bql611IntervalEntry OBJECT-TYPE
             SYNTAX  Bql611IntervalEntry
             ACCESS  not-accessible
            STATUS  mandatory
            DESCRIPTION
                "An entry in the SC611/DC621 Interval table."
            INDEX   { bql611IntervalIndex, bql611IntervalNumber }
            ::= { bql611IntervalTable 1 }

Bql611IntervalEntry ::=
         SEQUENCE {
                  bql611IntervalIndex	SCinstance,
                  bql611IntervalNumber	INTEGER,
                  bql611IntervalStats	OCTET STRING
		  }

bql611IntervalIndex OBJECT-TYPE
             SYNTAX  SCinstance
             ACCESS  read-only
             STATUS  mandatory
             DESCRIPTION
                "The index value which uniquely identifies  the
                ISDN  interface  to which this entry is applicable."
            ::= { bql611IntervalEntry 1 }

bql611IntervalNumber OBJECT-TYPE
             SYNTAX  INTEGER (1..96)
             ACCESS  read-only
             STATUS  mandatory
             DESCRIPTION
                "A number between 1 and 96, where 1 is the most
                recently completed 15 minute interval and 96 is
                the least recently completed 15 minute  inter-
                val   (assuming   that  all  96  intervals  are
                valid)."
            ::= { bql611IntervalEntry 2 }

bql611IntervalStats OBJECT-TYPE
             SYNTAX  OCTET STRING (SIZE (12))
             ACCESS  read-only
             STATUS  mandatory
             DESCRIPTION
                "The number of Errored Seconds, Severely Errored Seconds and
		 Unavailable Errored Seconds  encountered by a DS1  interface in one of the 
		 previous 96, individual 15 minute, intervals."
            ::= { bql611IntervalEntry 3 }

--*****************************************************************************
--           STATISTICS TABLE - TOTAL OF INTERVALS TABLE
--*****************************************************************************
--
-- The SC611/DC621 Total Table contains the cumulative sum of the
-- various statistics for the 24 hour period preceding the
-- current interval. It is indexed by SLDi.
--
-- This table uses SCinstance defined as follows:
--	SC611			DC621
--      -----                   -----
--      SLDi                    SLDi
--      L=1                     L=1
--      D=0                     D=XX Depends what is the local unit
--      i=1                     i=1 

bql611TotalTable OBJECT-TYPE
             SYNTAX  SEQUENCE OF Bql611TotalEntry
             ACCESS  not-accessible
             STATUS  mandatory
             DESCRIPTION
                "The SC611/DC621 Total table.  24 hour interval."
            ::= { bql611 9 }

bql611TotalEntry OBJECT-TYPE
             SYNTAX  Bql611TotalEntry
             ACCESS  not-accessible
             STATUS  mandatory
             DESCRIPTION
                "An entry in the SC611/DC621 Total table."
            INDEX   { bql611TotalIndex }
            ::= { bql611TotalTable 1 }

Bql611TotalEntry ::=
         SEQUENCE {
                  bql611TotalIndex	SCinstance,
                  bql611TotalStats	OCTET STRING
                  }

bql611TotalIndex OBJECT-TYPE
             SYNTAX  SCinstance
             ACCESS  read-only
             STATUS  mandatory
             DESCRIPTION
                "The index value which uniquely identifies  the
                ISDN interface  to which this entry is applicable."
            ::= { bql611TotalEntry 1 }

bql611TotalStats OBJECT-TYPE
             SYNTAX  OCTET STRING (SIZE(12))
             ACCESS  read-only
             STATUS  mandatory
             DESCRIPTION
                "The number of Errored Seconds,Severely Errored Seconds & Unavailable Errored
		 Seconds  encountered  by  an ISDN interface in the previous 24 hour interval."
            ::= { bql611TotalEntry 2 }

--*****************************************************************************
--            LOOP Performance Interval Maintenance Table FOR SC611 and DC621
--*****************************************************************************
--
-- This table uses SCinstance defined as follows:
--	SC611			DC621
--      -----                   -----
--      SLDi                    SLDi
--      L=1                     L=1
--      D=0                     D=XX Depends what is the local unit
--      i=1                     i=1 
--

bql611IntervalMaintenanceTable OBJECT-TYPE
     	SYNTAX SEQUENCE OF Bql611IntervalMaintenanceEntry
     	ACCESS not-accessible
     	STATUS mandatory
    	DESCRIPTION
     		"The SC611, DC621 Loop Interval  Maintenance table. "
         ::= { bql611 10 }
bql611IntervalMaintenanceEntry OBJECT-TYPE
 	SYNTAX Bql611IntervalMaintenanceEntry
     	ACCESS not-accessible
     	STATUS mandatory
     	DESCRIPTION
     		"The SC611, DC621 Interval Maintenance table entry. "
     	INDEX { bql611IntervalMaintenanceIndex }
     	::= { bql611IntervalMaintenanceTable 1 }
 
Bql611IntervalMaintenanceEntry ::= 
     	SEQUENCE {
     	    	 bql611IntervalMaintenanceIndex SCinstance,
         	 bql611ResetIntervals           INTEGER,
		 bql611NumberofValidIntervals   INTEGER,
		 bql611ResetMajorAlarm		INTEGER,
		 bql611ResetMinorAlarm		INTEGER
     		 }
 

bql611IntervalMaintenanceIndex OBJECT-TYPE
     	SYNTAX SCinstance
     	ACCESS read-only
     	STATUS mandatory
     	DESCRIPTION
     		"The index value which uniquely identifies the interface to
     		which this entry is applicable.  This has the form of a
     		SCinstance which defines the slot, line, drop, and interface,
     		which in this case is a Loop interface."
     	::= { bql611IntervalMaintenanceEntry 1 }  
bql611ResetIntervals OBJECT-TYPE
     	SYNTAX INTEGER {
     		       norm(1),
     		       reset(2)	
     		       }
     	ACCESS read-write 
     	STATUS mandatory
        DESCRIPTION " This variable is used to reset Loop performance intervals.
 		      When it is set to reset, the Loop performance tables are
 		      reset to zero."
     	::= { bql611IntervalMaintenanceEntry 2 }

bql611NumberofValidIntervals OBJECT-TYPE
     	SYNTAX INTEGER (0..96)
     	ACCESS read-only 
     	STATUS mandatory
        DESCRIPTION " This variable is used to read the number of intervals collected.
		      Each interval is an increment of 15 minutes."
     	::= { bql611IntervalMaintenanceEntry 3 }

bql611ResetMajorAlarm	OBJECT-TYPE
	SYNTAX	INTEGER {
			reset(1),
			norm(2)
			}
     	ACCESS read-write 
     	STATUS mandatory
         DESCRIPTION " This variable is used to reset alarm per Loop basis."
     	::= { bql611IntervalMaintenanceEntry 4 }
 
bql611ResetMinorAlarm	OBJECT-TYPE
	SYNTAX	INTEGER {
			reset(1),
			norm(2)
			}
     	ACCESS read-write 
     	STATUS mandatory
         DESCRIPTION " This variable is used to reset alarm per Loop basis."
     	::= { bql611IntervalMaintenanceEntry 5 }

END
