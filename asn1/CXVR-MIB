CXVR-MIB DEFINITIONS ::= BEGIN

--#CURRENT_VERSION 2

IMPORTS
	Counter                 FROM RFC1155-SMI
	OBJECT-TYPE             FROM RFC-1212
	DisplayString           FROM RFC1213-MIB
	cxVR, Alias             FROM CXProduct-SMI;

-- This module uses the extended OBJECT-TYPE macro as defined in RFC 1212.
-- This is the MIB module for the Voice Routing objects.

--  The VR Registration Table


vrRegTable                      OBJECT-TYPE
		SYNTAX  SEQUENCE OF VrRegEntry
		ACCESS  not-accessible
		STATUS  mandatory
		DESCRIPTION
"The Voice Routing group table."
		::= { cxVR 10 }


vrRegEntry                      OBJECT-TYPE
		SYNTAX  VrRegEntry
		ACCESS  not-accessible
		STATUS  mandatory
		DESCRIPTION
"An entry in the Voice Routing Group Table."
		INDEX { vrRegDialNo }
		::= { vrRegTable 1 }

VrRegEntry      ::=
		SEQUENCE {
-- Parameters
			vrRegDialNo                     INTEGER,
-- Status
			vrRegState                      INTEGER,
			vrRegVceStationId               DisplayString,
			vrRegVceSoftId                  DisplayString,
			vrRegSlotNo                     INTEGER,
			vrRegHuntChannel                DisplayString
-- Statistics
			}


vrRegDialNo                     OBJECT-TYPE
	SYNTAX  INTEGER(0..9999999)
		ACCESS  read-only
		STATUS  mandatory
		DESCRIPTION
"This is the table index."
		::= { vrRegEntry 10 }

 vrRegState                     OBJECT-TYPE
	SYNTAX  INTEGER {       vrOk (1),
				vrAgedOut (2),
				vrTableFull (3),
				vrMemallocFail (4)
			}
		ACCESS  read-only
		STATUS  mandatory
		DESCRIPTION
"Current registration state. 

Options:
vrOk (1):

vrAgedOut (2):

vrTableFull (3):

vrMemallocFail (4):

Default Value: None "

		::= { vrRegEntry  11 }
 
vrRegVceStationId               OBJECT-TYPE
	SYNTAX  DisplayString(SIZE(0..15))
		ACCESS  read-only
		STATUS  mandatory
		DESCRIPTION
"Displays the Station ID name.

Range of Values: From 0 to 15 "

		::= { vrRegEntry  12 }

vrRegVceSoftId                  OBJECT-TYPE
	SYNTAX  DisplayString(SIZE(0..15))
		ACCESS  read-only
		STATUS  mandatory
		DESCRIPTION
"Displays the VCE software ID name.

Range of Values: From 0 to 15 alphanumeric characters."
		::= { vrRegEntry  13 }

vrRegSlotNo                     OBJECT-TYPE
	SYNTAX  INTEGER
		ACCESS  read-only
		STATUS  mandatory
		DESCRIPTION
"This parameter displays the slot number in which the VCE CPU resides.

Range of Values: From 1 to 16 

Default Value:  None"

		::= { vrRegEntry  14 }

vrRegHuntChannel                OBJECT-TYPE
	SYNTAX  DisplayString (SIZE(0..8))
		ACCESS  read-only
		STATUS  mandatory
		DESCRIPTION
"The string that represents the Hunt Channel number in 32 bits wide bit 
map in hexadecimal format.

Range of Values: From 0 to 8 "

		::= { vrRegEntry  15 }


--  The VR Configuration Group


vrConfigGroup                   OBJECT IDENTIFIER ::= { cxVR 20 }

vrConfigNodeId                  OBJECT-TYPE
		SYNTAX  DisplayString(SIZE(0..31))
		ACCESS  read-write
		STATUS  mandatory
		DESCRIPTION
"Allows you to create a unique name for the frame relay node.

Range of Values: Up to 32 characters

Default Value: VoiveRouting"

		DEFVAL { "VoiceRouting" }
		::= { vrConfigGroup 1 }

vrConfigSoftId                  OBJECT-TYPE
		SYNTAX  DisplayString(SIZE(0..3))
		ACCESS  read-only
		STATUS  mandatory
		DESCRIPTION
"Displays the software version number. "

		::= { vrConfigGroup 2 }

vrConfigNoOfSysRouteSupported   OBJECT-TYPE
		SYNTAX  INTEGER (1..1024)
		ACCESS  read-write
		STATUS  mandatory
		DESCRIPTION
"Maximum number of routing definitions that can be supported in the 
VR table.
 
Range of Values: From 1 to 1024
 
Default Value: 1"

		DEFVAL { 1 }
		::= { vrConfigGroup 3 }

vrConfigNoOfDigitSupported      OBJECT-TYPE
		SYNTAX  INTEGER { dig5(5),
				  dig7(7)
				}
		ACCESS  read-write
		STATUS  mandatory
		DESCRIPTION
"The maximum number of digits to be used for dial extension numbers over 
the entire network.

Options:
dig5 (5): The maximum number is five digits.

dig7 (7): The maximum number is seven digits. (FOR FUTURE USE ONLY).

Default Value: dig5 (5)"

		DEFVAL { dig5 }
		::= { vrConfigGroup 4 }

vrConfigMaxBufferPoolSize       OBJECT-TYPE
		SYNTAX  INTEGER
		ACCESS  read-write
		STATUS  mandatory
		DESCRIPTION
"Maximum number of OS buffers that can be queued at any time in the 
VR fifos. 

Range of Values: From 0 to 1000

Note: Zero (0) means that Voice/Fax packets are routed immediately (never 
queued).

Default Values: 0 "

		DEFVAL { 0 }
		::= { vrConfigGroup 5 }

vrConfigFastSwitchingOption     OBJECT-TYPE
		SYNTAX  INTEGER { vrprtysmall(1),
				  vrprtyroute(2)
				}
		ACCESS  read-write
		STATUS  mandatory
		DESCRIPTION
"This object refers to Dial Digit Packing for transmission of the extension 
numbers.  The digits can be sent either 2 bytes or 4 bytes long.

Options:
vrprtysmall (1):  The priority (using 2 bytes) is to minimize the amount of 
bandwidth used.  This option is more CPU intensive, and slower.

vrprtyroute (2):  The priority (using 4 bytes) is speed. This option will 
minimize CPU usage but will require more bandwidth.

Default Value: vrprtysmall (1)"
 
		DEFVAL { vrprtysmall }
		::= { vrConfigGroup 6 }

vrConfigStatsSamplingPeriod     OBJECT-TYPE
		SYNTAX  INTEGER (0..3600)
		ACCESS  read-write
		STATUS  mandatory
		DESCRIPTION
"This parameter allows you to set the polling interval (in seconds) for 
statistics.

Range of Values: From 0 to 3600

Default Value: 15"

		DEFVAL { 15 }
		::= { vrConfigGroup 7 }

vrConfigControl                 OBJECT-TYPE
		SYNTAX  INTEGER {vrcfgidle(1),
				 vrcfgrte(2),
				 vrcfgreg(3)
				}        
		ACCESS  read-write
		STATUS  mandatory
		DESCRIPTION
"This object allows you to control the statistics in the VRSR table 
and the entries in the VR register table. 

Options:   
vrcfgidle(1): Control is turned off

vrcfgrte(2): This option clears the statistics in the VRSR table.

vrcfgreg(3): This options ages out the voice routing register of local
extensions.

Default Value: vrcfgidle (1)"

		DEFVAL { vrcfgidle }
		::= { vrConfigGroup 8 }

   --#STARTING_VERSION 2

vrConfigOptimization                 OBJECT-TYPE
		SYNTAX  INTEGER {vroptdisabled(1),
				 vroptenabled(2),
				 vroptbwmgt(3)
				}        
		ACCESS  read-write
		STATUS  mandatory
		DESCRIPTION
"This object allows you to enable and disable the optimization in the Voice, 
VR and FR modules. 

Options:   
vroptdisabled(1): Optimization code is turned off. This option enables
backwards compatibility with older versions of VR software. This option will
be removed in future releases. 

vroptenabled(2):  Optimization code is turned on. This enables VR, Voice
application module and Frame Relay Multiprotocol Encapsulation to use less
bandwidth. this option will be removed in the future releases.

vroptbwmgt(3): Optimization code is turned on plus enhancement for bandwidth
management. This option is similar to option 2, in addition to when Bandwidth
Management is enabled and there is no more bandwidth left on the link, then
by chosing this option, it will stop any new voice call establishement. This
is the default value and is the recommended value to use.


Default Value: vroptbwmgt (3)"

		DEFVAL { vroptbwmgt }
   --#STARTING_VERSION 2
		::= { vrConfigGroup 9 }


vrMibLevel OBJECT-TYPE
   SYNTAX  INTEGER
   ACCESS  read-only
   STATUS  mandatory
   DESCRIPTION
"Used to determine current MIB module release supported
by the agent. Object is in decimal."
   DEFVAL { 0 }
   --#STARTING_VERSION 1
   ::= { vrConfigGroup 20 }


				    
-- The Voice Routing Statistics Group

-- The VR statistics group contains general statistics about the Voice 

-- Routing scheme.


vrStatGroup                     OBJECT IDENTIFIER ::= { cxVR 30 }

 vrStatInitState                        OBJECT-TYPE
		SYNTAX  INTEGER {       vrDead (1),
						vrUnrecoverableError (2),
						vrTablesBuilt (3),
						vrConfigRead (4),
						vrInitialized (10)
				}
		ACCESS  read-only
		STATUS  mandatory
		DESCRIPTION
 "VR module initialisation state.
 
 Options:
 vrDead (1):
 
 vrUnrecoverableError (2):
 
 vrTablesBuilt (3):
 
 vrConfigRead (4):
 
 vrInitialized (10)"

		::= { vrStatGroup 30 }

vrStatLongestMuxPassInMs        OBJECT-TYPE
		SYNTAX  Counter
		ACCESS  read-only
		STATUS  mandatory
		DESCRIPTION
"Longest time recorded yet for a same multiplexing pass. Relevant only if 
pool is different from zero."
		::= { vrStatGroup 50 }

vrStatNbPacketsForwardedPerSec OBJECT-TYPE
		SYNTAX  Counter
		ACCESS  read-only
		STATUS  mandatory
		DESCRIPTION
"No. of packets per second forwarded by VR during the last sampling period"
		::= { vrStatGroup 51 }

vrStatNbRoutingConflicts        OBJECT-TYPE
		SYNTAX  Counter
		ACCESS  read-only
		STATUS  mandatory
		DESCRIPTION
"No.of times a routing conflict has been detected when adding a routing 
entry."
		::= { vrStatGroup 52 }

vrStatRegOverallNumber          OBJECT-TYPE
		SYNTAX  Counter
		ACCESS  read-only
		STATUS  mandatory
		DESCRIPTION
"Current number of local registration blocks."
		::= { vrStatGroup 60 }

vrStatRegNotOwner               OBJECT-TYPE
		SYNTAX  Counter
		ACCESS  read-only
		STATUS  mandatory
		DESCRIPTION
"Dial number not registered or refreshed because the requester is not 
owner of it."
		::= { vrStatGroup 61 }

vrStatRegInvalidDialNumber      OBJECT-TYPE
		SYNTAX  Counter
		ACCESS  read-only
		STATUS  mandatory
		DESCRIPTION
"The dial number is invalid and cannot be registered."
		::= { vrStatGroup 62 }

vrStatRegFormatError            OBJECT-TYPE
		SYNTAX  Counter
		ACCESS  read-only
		STATUS  mandatory
		DESCRIPTION
"Dial number not registered or refreshed because of a format error in 
the request."
		::= { vrStatGroup 63 }

vrStatNbVceMsgRx                OBJECT-TYPE
		SYNTAX  Counter
		ACCESS  read-only
		STATUS  mandatory
		DESCRIPTION
"Number of messages received from the VCE module."
		::= { vrStatGroup 75 }

vrStatNbVceMsgTx                OBJECT-TYPE
		SYNTAX  Counter
		ACCESS  read-only
		STATUS  mandatory
		DESCRIPTION
"Number of messages transmitted from the VCE module."
		::= { vrStatGroup 76 }

vrStatNbBusMsgRx                OBJECT-TYPE
		SYNTAX  Counter
		ACCESS  read-only
		STATUS  mandatory
		DESCRIPTION
"Number of messages received from the TBC module."
		::= { vrStatGroup 77 }

vrStatNbBusMsgTx                OBJECT-TYPE
		SYNTAX  Counter
		ACCESS  read-only
		STATUS  mandatory
		DESCRIPTION
"Number of messages transmitted from the TBC module."
		::= { vrStatGroup 78 }

vrStatNbWanMsgRx                OBJECT-TYPE
		SYNTAX  Counter
		ACCESS  read-only
		STATUS  mandatory
		DESCRIPTION
"Number of messages received from the WAN."
		::= { vrStatGroup 79 }

vrStatNbWanMsgTx                OBJECT-TYPE
		SYNTAX  Counter
		ACCESS  read-only
		STATUS  mandatory
		DESCRIPTION
"Number of messages transmitted from the WAN."
		::= { vrStatGroup 80 }

vrStatNbOutboundQueueFull       OBJECT-TYPE
		SYNTAX  Counter
		ACCESS  read-only
		STATUS  mandatory
		DESCRIPTION
"Number of times the buffer queue has been exceeded. (Irrelevant 
if pool is set to zero.)"
		::= { vrStatGroup 81 }

vrStatNbOverallForwards         OBJECT-TYPE
		SYNTAX  Counter
		ACCESS  read-only
		STATUS  mandatory
		DESCRIPTION
"Number of overall packets (voice + other applications) forwarded."
		::= { vrStatGroup 90 }

vrStatNbOverallDiscards         OBJECT-TYPE
		SYNTAX  Counter
		ACCESS  read-only
		STATUS  mandatory
		DESCRIPTION
"Number of overall packets (voice + other applications) discarded."
		::= { vrStatGroup 91 }

vrStatNbDeadEnds                OBJECT-TYPE
		SYNTAX  Counter
		ACCESS  read-only
		STATUS  mandatory
		DESCRIPTION
"Number of times the routing process did not find any routing definition 
block for a specific dial number. This also increments the alldsc object."
		::= { vrStatGroup 92 }

vrStatError                     OBJECT-TYPE
		SYNTAX  Counter
		ACCESS  read-only
		STATUS  mandatory
		DESCRIPTION
"Sum of many counters under vrStat.error.xxx, vrStat.ianIfError, etc."
		::= { vrStatGroup 93 }

vrStatFieldsAddress             OBJECT-TYPE
		SYNTAX  DisplayString (SIZE(0..10))
		ACCESS  read-only
		STATUS  mandatory
		DESCRIPTION
"vrStat starting address.
 
 Range of Values: From 0 to 10"

		::= { vrStatGroup 94 }

vrStatIamUnxFieldAddress        OBJECT-TYPE
		SYNTAX  DisplayString (SIZE(0..10))
		ACCESS  read-only
		STATUS  mandatory
		DESCRIPTION
"IAM unexpected event table address.

Range of Values: From 0 to 10"
		::= { vrStatGroup 95 }

--  The Voice Routing System Routes Table


vrSrTable                       OBJECT-TYPE
		SYNTAX  SEQUENCE OF VrSrEntry
		ACCESS  not-accessible
		STATUS  mandatory
		DESCRIPTION
"The Voice Routing System Routes table."
		::= { cxVR 40 }


vrSrEntry                       OBJECT-TYPE
		SYNTAX  VrSrEntry
		ACCESS  not-accessible
		STATUS  mandatory
		DESCRIPTION
"An entry in the Voice Routing System Routes Table."
		INDEX { vrSrIndex }
		::= { vrSrTable 1 }


VrSrEntry       ::=
		SEQUENCE {
-- Parameters
			vrSrIndex                       INTEGER,
			vrSrRowStatus                   INTEGER,
			vrSrDestAlias                   Alias,
			vrSrSubRef                      INTEGER,
			vrSrBandwidth           	INTEGER,
			vrSrBwIndex	       		INTEGER,
-- Status
			vrSrStatus                      INTEGER,
			vrSrConStatus                   INTEGER,
			vrSrFailStatus                  INTEGER,
-- Statistics
			vrSrNbLinkDown                  Counter,
			vrSrNbResetFrameRx              Counter,
			vrSrNbOutboundFrame             Counter,
			vrSrNbInboundFrame              Counter,
			vrSrNbOutboundBw                Counter,
			vrSrNbInboundBw                 Counter,
			vrSrBwUsed                      Counter,
			vrSrNbCalls                     Counter,
			vrSrNbPktDropped                Counter
		}

 vrSrIndex                      OBJECT-TYPE
		SYNTAX  INTEGER (1..1024)
		ACCESS  read-only
		STATUS  mandatory
		DESCRIPTION
"System route index.

Range of Values: From 1 to 1024"

		::= { vrSrEntry 1 }

vrSrRowStatus                   OBJECT-TYPE
		SYNTAX  INTEGER {
					invalid         (1),
					valid           (2)
					}
		ACCESS  read-write
		STATUS  mandatory
		DESCRIPTION
"Indicates whether this specific entry is configured within the MIB.  
Entries (rows) may be created by setting this object value to 'valid', 
or deleted by changing this object value to 'invalid'.

Options: 
invalid (1): Entries can be deleted

valid (2): Entries can be created"

		::= { vrSrEntry 2 }

vrSrDestAlias                   OBJECT-TYPE
		SYNTAX  Alias
		ACCESS  read-write
		STATUS  mandatory
		DESCRIPTION
"Destination string."

		DEFVAL { "" }
		::= { vrSrEntry 3 }

vrSrSubRef                      OBJECT-TYPE
		SYNTAX  INTEGER (1..31)
		ACCESS  read-write
		STATUS  mandatory
		DESCRIPTION
"Sub-reference number for multi-protocol encapsulation.

Range of Values: From 1 to 31

Default Value: 1"

		DEFVAL { 1 }
		::= { vrSrEntry 10 }

vrSrBandwidth			OBJECT-TYPE
		SYNTAX	INTEGER (0..65535)
		ACCESS	read-write
		STATUS	mandatory
		DESCRIPTION
"Maximum Bandwidth allowed for the FR Link in Kbps.
Note: If set to zero (0) bandwidth management is disabled"
		DEFVAL { 0 }
		::= { vrSrEntry 20 }

vrSrBwIndex			OBJECT-TYPE
		SYNTAX	INTEGER (0..32)
		ACCESS	read-write
		STATUS	mandatory
		DESCRIPTION
"The index for bandwidth that corresponds to the vrBwEntry"
   --#STARTING_VERSION 1
		DEFVAL { 0 }
		::= { vrSrEntry 21 }


vrSrStatus                      OBJECT-TYPE
		SYNTAX  INTEGER {       vrSrDown (1),
					vrSrInFlowCtl (2),
					vrSrUp (3)
				}
		ACCESS  read-only
		STATUS  mandatory
		DESCRIPTION
"Current VR system route status.

Options:
vrSrDown (1):

vrSrInFlowCtl (2):

vrSrUp (3):"

		::= { vrSrEntry 30 }

vrSrConStatus                   OBJECT-TYPE
		SYNTAX  INTEGER {       vrNotConfigured (1),
						vrClose (2),
						vrWaitForQuery (3),
						vrWaitForOpenConf (4),
						vrOpen (5)
				}
		ACCESS  read-only
		STATUS  mandatory
		DESCRIPTION
 "Current status of the connection establishment through IAM.
 
 Options: 
 vrNotConfigured (1):
 
 vrClose (2):
 
 vrWaitForQuery (3):
 
 vrWaitForOpenConf (4):
 
 vrOpen (5):"
		::= { vrSrEntry 31 }

vrSrFailStatus                  OBJECT-TYPE
		SYNTAX  INTEGER {       vrNoFailure (1),
						vrInternalError (2),
						vrLocalMemFail (3),
						vrRemMemFail (4),
						vrRemNoAcces (5),
						vrRemPvcDown (6),
						
						vrRemPvcBusy (7),
						vrLocalFcnFailure (8),
						vrRemFcnFailure (9),
						vrLocalDsnFailure (10),
						vrRemAliasNotFound (11),
						vrNoPvcService (12),
						vrOpenReqTimeout (13),
						vrAdjaReset (14),
						vrUnsupportedSR (15)
				}
		ACCESS  read-only
		STATUS  mandatory
		DESCRIPTION
"Current fail status of the connection establishment through IAM.
 
Options:
vrNoFailure (1):
 
vrInternalError (2):
 
vrLocalMemFail (3):
 
vrRemMemFail (4):

vrRemNoAcces (5):

vrRemPvcDown (6):

vrRemPvcBusy (7):

vrLocalFcnFailure (8):

vrRemFcnFailure (9):

vrLocalDsnFailure (10):

vrRemAliasNotFound (11):

vrNoPvcService (12):

vrOpenReqTimeout (13):

vrAdjaReset (14):

vrUnsupportedSR (15):"

		::= { vrSrEntry 32 }

vrSrNbLinkDown          OBJECT-TYPE
		SYNTAX  Counter
		ACCESS  read-only
		STATUS  mandatory
		DESCRIPTION
"The number of times that the system route has received a 'LINK_DOWN' 
with no route available notification."
		::= { vrSrEntry 50 }

vrSrNbResetFrameRx              OBJECT-TYPE
		SYNTAX  Counter
		ACCESS  read-only
		STATUS  mandatory
		DESCRIPTION
"Number of reset frames received."
		::= { vrSrEntry 51 }

vrSrNbOutboundFrame     OBJECT-TYPE
		SYNTAX  Counter
		ACCESS  read-only
		STATUS  mandatory
		DESCRIPTION
"Number of outbound frames (Voice/FAX, signaling and VR applications)."
		::= { vrSrEntry 52 }

vrSrNbInboundFrame              OBJECT-TYPE
		SYNTAX  Counter
		ACCESS  read-only
		STATUS  mandatory
		DESCRIPTION
"Number of inbound frames (Voice/FAX, signaling and VR applications)."
		::= { vrSrEntry 53 }

vrSrNbOutboundBw                OBJECT-TYPE
		SYNTAX  Counter
		ACCESS  read-only
		STATUS  mandatory
		DESCRIPTION
"Outbound WAN bandwidth required in BPS; this figure include the DLCI, 
the proprietary header for encapsulation (if used) and the CRC. The refresh 
period of that object depends on the stsmp object int the vrConfig group."
		::= { vrSrEntry 54 }

vrSrNbInboundBw         OBJECT-TYPE
		SYNTAX  Counter
		ACCESS  read-only
		STATUS  mandatory
		DESCRIPTION
"Inbound WAN bandwidth required in BPS; this figure include the DLCI, the 
proprietary header for encapsulation (if used) and the CRC. The refresh 
period of that object depends on the stsmp object int the vrConfig group."
		::= { vrSrEntry 55 }

vrSrBwUsed         OBJECT-TYPE
		SYNTAX  Counter
		ACCESS  read-only
		STATUS  mandatory
		DESCRIPTION
"The bandwidth utilized in kilo BPS. This value is shown only if the
bandwith management for this Source Route is enabled."
   --#STARTING_VERSION 1
		::= { vrSrEntry 56 }

vrSrNbCalls         OBJECT-TYPE
		SYNTAX  Counter
		ACCESS  read-only
		STATUS  mandatory
		DESCRIPTION
"The number of outstanding voice calls on this Vr Source Route. This value
is shown only if the bandwith management for this Source Route is enabled."
   --#STARTING_VERSION 1
		::= { vrSrEntry 57 }

vrSrNbPktDropped     OBJECT-TYPE
		SYNTAX  Counter
		ACCESS  read-only
		STATUS  mandatory
		DESCRIPTION
"The number of packets discarded due to Bandwidth management. When the
 bandwidth utilized on this VR Source Route reaches to its maximum bandwidth
 allowance, then this value represents the number of Voice packets discarded
 due to this fact."
   --#STARTING_VERSION 2
		::= { vrSrEntry 58 }

--  The Voice Routing Table


vrRouteTable                    OBJECT-TYPE
		SYNTAX  SEQUENCE OF VrRouteEntry
		ACCESS  not-accessible
		STATUS  mandatory
		DESCRIPTION
"The Voice Routing table."
		::= { cxVR 50 }


vrRouteEntry                    OBJECT-TYPE
		SYNTAX  VrRouteEntry
		ACCESS  not-accessible
		STATUS  mandatory
		DESCRIPTION
"An entry in the Voice Routing Table."
		INDEX { vrRouteDialNo }
		::= { vrRouteTable 1 }


VrRouteEntry    ::=
		SEQUENCE {
-- Parameters
			vrRouteDialNo                   INTEGER,
			vrRouteRowStatus                INTEGER,

			vrRouteMask                     INTEGER,
			vrRouteSrNumber         INTEGER,
-- Status
--
-- Statistics
			vrRouteForwardedPkt             Counter
		}

 vrRouteDialNo                  OBJECT-TYPE
		SYNTAX  INTEGER (0..9999999)
		ACCESS  read-only
		STATUS  mandatory
		DESCRIPTION
"Table index."
		::= { vrRouteEntry 1 }

vrRouteRowStatus                        OBJECT-TYPE
		SYNTAX  INTEGER {
					invalid         (1),
					valid           (2)
					}
		ACCESS  read-write
		STATUS  mandatory
		DESCRIPTION
"Indicates whether this specific entry is configured within the MIB.  
Entries (rows) may be created by setting this object value to 'valid', 
or deleted by changing this object value to 'invalid'.

Options:
invalid (1): Entries can be deleted

valid (2): Entries can be created "

		::= { vrRouteEntry 2 }

vrRouteMask             OBJECT-TYPE
		SYNTAX  INTEGER (0..1111111)
		ACCESS  read-write
		STATUS  mandatory
		DESCRIPTION
"The selection of the mask will dictate which of the digits will be read.
A zero (0) means that the digit in that position will not be read. A one (1) 
means that the digit in that position will be read. 

Range of Values:
0000000

1000000

1100000

1110000

1111000

1111100

1111110

1111111

Default Value: 1111111"

		DEFVAL { 1111111 }
		::= { vrRouteEntry 10 }

vrRouteSrNumber         OBJECT-TYPE
		SYNTAX  INTEGER (1..1024)
		ACCESS  read-write
		STATUS  mandatory
		DESCRIPTION
"VR system route number to use for the outbound traffic.

Range of Values: From 1 to 1024"

		::= { vrRouteEntry 11 }

vrRouteForwardedPkt             OBJECT-TYPE
		SYNTAX  Counter
		ACCESS  read-only
		STATUS  mandatory
		DESCRIPTION
"The number of voice packets forwarded over the WAN."
		::= { vrRouteEntry 50 }



--  The Voice Routing Ping Group


vrPingGroup                     OBJECT IDENTIFIER ::= { cxVR 60 }

vrPingDialNo                    OBJECT-TYPE
		SYNTAX  INTEGER (0..9999999)
		ACCESS  read-write
		STATUS  mandatory
		DESCRIPTION
"Dial number to ping.

Range of Values: From 0 to 9999999"

		::= { vrPingGroup 1 }

vrPingNbToBeSent                        OBJECT-TYPE
		SYNTAX  INTEGER (0..4000000)
		ACCESS  read-write
		STATUS  mandatory
		DESCRIPTION
"Number of pings to send after the trigger. (4,000,000 would mean one packet 
sent every 24 ms for 24 hours). 0 means stop the current ping session.

Range of Values: From 0 to 4,000,000

Default Value: 1"

		DEFVAL { 1 }
		::= { vrPingGroup 2 }

vrPingGapsInMs                  OBJECT-TYPE
		SYNTAX  INTEGER (0..1000)
		ACCESS  read-write
		STATUS  mandatory
		DESCRIPTION
"The interval in milliseconds between ping frames.

Range of Values: From 0 to 1000

Default Value: 24"

		DEFVAL { 24 }
		::= { vrPingGroup 3 }

vrPingMaxHopCount               OBJECT-TYPE
		SYNTAX  INTEGER (1..256)
		ACCESS  read-write
		STATUS  mandatory
		DESCRIPTION
"Maximum Hop count allowed.

Range of Values: From 1 to 256

Default Value: 16"

		DEFVAL { 16 }
		::= { vrPingGroup 4 }

vrPingProbeReturnAddress        OBJECT-TYPE
		SYNTAX  INTEGER (0..9999999)
		ACCESS  read-write
		STATUS  mandatory
		DESCRIPTION
"Probe (i.e. ping/trace/search) return dial number.

Range of Values: From 0 to 9999999

Default Value: 9999999"

		DEFVAL { 9999999 }
		::= { vrPingGroup 5 }

vrPingTriggerSend               OBJECT-TYPE
		SYNTAX  INTEGER {       vrIdle (1),
						vrSend (2)
				}
		ACCESS  read-write
		STATUS  mandatory
		DESCRIPTION
"Trigger the pings to be sent.

Options:
vrIdle (1): No pings are sent

vrSend (2): The counter is set to zero and pings will be sent"

		DEFVAL { vrIdle }
		::= { vrPingGroup 6 }

vrPingNbReplyRx         OBJECT-TYPE
		SYNTAX  Counter
		ACCESS  read-only
		STATUS  mandatory
		DESCRIPTION
"Count the number of ping replies received"

		::= { vrPingGroup 30 }

vrPingFormatError               OBJECT-TYPE
		SYNTAX  Counter
		ACCESS  read-only
		STATUS  mandatory
		DESCRIPTION
"Count the number of non-recognizable ping replies."
		::= { vrPingGroup 31 }

vrPingNbVrNodesCrossedForward   OBJECT-TYPE
		SYNTAX  Counter
		ACCESS  read-only
		STATUS  mandatory
		DESCRIPTION
"The number of nodes hopped outbound (forward). When compared to the 
number of hops inbound (backward) the difference can help trace the 
path."
		::= { vrPingGroup 32 }

vrPingNbVrNodesCrossedBackward OBJECT-TYPE
		SYNTAX  Counter
		ACCESS  read-only
		STATUS  mandatory
		DESCRIPTION
"The number of nodes hopped inbound (Backward). When compared to the 
 number of hops outbound (forward) the difference can help trace the 
 path."
		::= { vrPingGroup 33 }

vrPingLastRoundTripInMs         OBJECT-TYPE
		SYNTAX  Counter
		ACCESS  read-only
		STATUS  mandatory
		DESCRIPTION
"The time in milliseconds that the ping took for its last round-trip."
		::= { vrPingGroup 34 }

vrPingLastSequenceNumberRx      OBJECT-TYPE
		SYNTAX  Counter
		ACCESS  read-only
		STATUS  mandatory
		DESCRIPTION
"The sequence number of the last ping received."
		::= { vrPingGroup 35 }

vrPingSequenceError             OBJECT-TYPE
		SYNTAX  Counter
		ACCESS  read-only
		STATUS  mandatory
		DESCRIPTION
"The sequence number of the last error received. Not available if the 
number of pings is set to one."
		::= { vrPingGroup 36 }

vrPingMinRoundTripInMs          OBJECT-TYPE
		SYNTAX  Counter
		ACCESS  read-only
		STATUS  mandatory
		DESCRIPTION
"The Minimum round trip time in milliseconds. This is not applicable if 
pinging is set to one (1)."
		::= { vrPingGroup 37 }

vrPingMaxRoundTripInMs          OBJECT-TYPE
		SYNTAX  Counter
		ACCESS  read-only
		STATUS  mandatory
		DESCRIPTION
"the Maximum round trip time in milliseconds. this is not applicable if
pinging is set to one (1)."
		::= { vrPingGroup 38 }

vrPingRemStatus                 OBJECT-TYPE
	SYNTAX  INTEGER {       vrOk (1),
				vrUnknown (5)
				}
		ACCESS  read-only
		STATUS  mandatory
		DESCRIPTION
"The ping returns the status of the remote node.

Options:
vrOk (1): The remote is OK

vrUnknown (5): Status unknown, there is no response."

		::= { vrPingGroup 39 }

vrPingRemVrNodeId               OBJECT-TYPE
		SYNTAX  DisplayString(SIZE(0..31))
		ACCESS  read-only
		STATUS  mandatory
		DESCRIPTION
"Displays the remote node ID. 

Range of Values: From 0 to 31"

		::= { vrPingGroup 40 }

vrPingRemVceStationId           OBJECT-TYPE
		SYNTAX  DisplayString(SIZE(0..15))
		ACCESS  read-only
		STATUS  mandatory
		DESCRIPTION
"Displays the remote VCE station ID.

Range of Values: from 0 to 15"

		::= { vrPingGroup 41 }

vrPingRemVrSoftId               OBJECT-TYPE
		SYNTAX  DisplayString(SIZE(0..3))
		ACCESS  read-only
		STATUS  mandatory
		DESCRIPTION
"Displays the remote VR software version number.

Range of Values: From 0 to 3"

		::= { vrPingGroup 42 }

vrPingRemVceSoftId              OBJECT-TYPE
		SYNTAX  DisplayString(SIZE(0..15))
		ACCESS  read-only
		STATUS  mandatory
		DESCRIPTION
"Displays the remote VCE software version number."

		::= { vrPingGroup 43 }

vrPingRemSlotIndex              OBJECT-TYPE
		SYNTAX  INTEGER (1..16)
		ACCESS  read-only
		STATUS  mandatory
		DESCRIPTION
"The remote VCE slot number of the registered number"
		::= { vrPingGroup 44 }

vrPingRemHuntChannel            OBJECT-TYPE
		SYNTAX  DisplayString(SIZE(0..8))
		ACCESS  read-only
		STATUS  mandatory
		DESCRIPTION
"Displays the remote hunt channel number.
 
Range of Values: From 0 to 8"

		::= { vrPingGroup 45 }

vrPingRemNbForwardedPacket      OBJECT-TYPE
		SYNTAX  Counter
		ACCESS  read-only
		STATUS  mandatory
		DESCRIPTION
"Number of forwarded packets using that route definition block."
		::= { vrPingGroup 46 }

vrPingRemNbRestart              OBJECT-TYPE
		SYNTAX  Counter
		ACCESS  read-only
		STATUS  mandatory
		DESCRIPTION
"No of times the attached VCE has restarted."
		::= { vrPingGroup 47 }



--  The Voice Global bandwidth management Group

vrBwTable                       OBJECT-TYPE
		SYNTAX  SEQUENCE OF VrBwEntry
		ACCESS  not-accessible
		STATUS  mandatory
		DESCRIPTION
"The Voice Routing Bandwidth Management table."
   --#STARTING_VERSION  1
		::= { cxVR 70 }


vrBwEntry                       OBJECT-TYPE
		SYNTAX  VrBwEntry
		ACCESS  not-accessible
		STATUS  mandatory
		DESCRIPTION
"An entry in the Voice Routing Bandwidth Management Table."
		INDEX { vrBwIndex }
		::= { vrBwTable 1 }


VrBwEntry       ::=
		SEQUENCE {
-- Parameters
			vrBwIndex                       INTEGER,
			vrBwRowStatus                   INTEGER,
			vrBwBandwidthCfg		INTEGER,
-- Statistics
			vrBwBandwidthUsed               INTEGER,
			vrBwNbCalls                     INTEGER,
			vrBwNbPktDropped                Counter
		}

 vrBwIndex                      OBJECT-TYPE
		SYNTAX  INTEGER (1..32)
		ACCESS  read-only
		STATUS  mandatory
		DESCRIPTION
"Total bandwidth index.

Range of Values: From 1 to 32"

		::= { vrBwEntry 1 }

vrBwRowStatus                   OBJECT-TYPE
		SYNTAX  INTEGER {
					invalid         (1),
					valid           (2)
					}
		ACCESS  read-write
		STATUS  mandatory
		DESCRIPTION
"Indicates whether this specific entry is configured within the MIB.  
Entries (rows) may be created by setting this object value to 'valid', 
or deleted by changing this object value to 'invalid'.

Options: 
invalid (1): Entries can be deleted

valid (2): Entries can be created"

		::= { vrBwEntry 2 }


vrBwBandwidthCfg                    OBJECT-TYPE
		SYNTAX  INTEGER (0.. 65535)
		ACCESS  read-write
		STATUS  mandatory
		DESCRIPTION
"Maximum Bandwidth allowed for the FR Link in Kbps.
Note: If set to zero (0) bandwidth management is disabled

Default: 0 (disabled)

Range of Values: From 0 to 65535"

		DEFVAL { 0 }
		::= { vrBwEntry 3 }

vrBwBandwidthUsed                    OBJECT-TYPE
		SYNTAX  INTEGER (0.. 65535)
		ACCESS  read-only
		STATUS  mandatory
		DESCRIPTION
"Total bandwidth used on  the FR Link in Kbps.

Range of Values: From 0 to 65535"

		::= { vrBwEntry 10 }

vrBwNbCalls                     OBJECT-TYPE
		SYNTAX  INTEGER (0.. 65535)
		ACCESS  read-only
		STATUS  mandatory
		DESCRIPTION
"Total number of outstanding Voice sessions on that FR Link

Range of Values: From 0 to 65535"

		::= { vrBwEntry 11 }

vrBwNbPktDropped               OBJECT-TYPE
		SYNTAX  Counter
		ACCESS  read-only
		STATUS  mandatory
		DESCRIPTION
"The number of packets discarded due to Bandwidth management. When the
 bandwidth utilized on this VR Global Bandwidth management entry reaches to
 its maximum bandwidth allowance, then this value represents the number of
 Voice packets discarded due to this fact."

   --#STARTING_VERSION 2

		::= { vrBwEntry 12 }

END
