-- *****************************************************************
--
-- STN-L2TP.mib:  
--      Spring Tide Networks L2TP MIB file.
--
--
--      Copyright (c) 1999, 2000 by Spring Tide Networks, Inc.
--                      ALL RIGHTS RESERVED       
--
-- *****************************************************************
   
    STN-L2TP-MIB DEFINITIONS ::= BEGIN

    IMPORTS
        MODULE-IDENTITY, OBJECT-TYPE
            FROM SNMPv2-SMI

        DisplayString
            FROM SNMPv2-TC

        MODULE-COMPLIANCE
            FROM SNMPv2-CONF

	    StnDomainMapType
            FROM SPRING-TIDE-NETWORKS-TC

        l2tp
            FROM L2TP-MIB;


    stnL2tp    MODULE-IDENTITY
        LAST-UPDATED    "0002160000Z"
        ORGANIZATION    "Spring Tide Networks, Inc."
        CONTACT-INFO
                "
                Spring Tide Networks, Inc.
                Customer Service
                Postal: 3 Clock Tower Place
                        Maynard, MA 01754
                Tel:    1 888-786-4357
                Email:  stncs@springtidenet.com
                "
       DESCRIPTION
          "The MIB module that describes managed objects of
           general use by the Layer 2 Transport Protocol."
       ::= { l2tp 10 }

    --
    -- Top Level STN L2TP MIB Objects
    --
    stnL2tpObjects         OBJECT IDENTIFIER  ::= { stnL2tp 1 }
    stnL2tpMibConformance  OBJECT IDENTIFIER  ::= { stnL2tp 2 }
    stnL2tpTraps           OBJECT IDENTIFIER  ::= { stnL2tp 3 }


    --
    --      The L2TP Domain Mapping Table
    --

    stnL2tpDomainMapTable OBJECT-TYPE
	    SYNTAX          SEQUENCE OF StnL2tpDomainMapTableEntry
	    MAX-ACCESS      not-accessible
	    STATUS          current
	    DESCRIPTION	"This table provides a mapping between L2TP Domain
			        identifiers and hostnames or IP-ATM information"
	    ::= { stnL2tpObjects 10 }

    stnL2tpDomainMapTableEntry OBJECT-TYPE
	    SYNTAX          StnL2tpDomainMapTableEntry
	    MAX-ACCESS      not-accessible
	    STATUS          current
	    DESCRIPTION	"An entry within the STN L2TP Map Table."
	    INDEX		{ stnL2tpDomainMapIdentifier }
	    ::= { stnL2tpDomainMapTable 1 }

    StnL2tpDomainMapTableEntry ::= SEQUENCE {
	    stnL2tpDomainMapIdentifier	DisplayString,
        stnL2tpDomainMapHostName	DisplayString,
        stnL2tpDomainMapType		StnDomainMapType,
        stnL2tpDomainMapTypeInfo	DisplayString
    }

    stnL2tpDomainMapIdentifier OBJECT-TYPE
	    SYNTAX          DisplayString
	    MAX-ACCESS      not-accessible
	    STATUS          current
	    DESCRIPTION     "L2TP Domain Identifier."
	    ::= { stnL2tpDomainMapTableEntry 1 }

    stnL2tpDomainMapHostName OBJECT-TYPE
	    SYNTAX          DisplayString
	    MAX-ACCESS      read-only
	    STATUS          current
	    DESCRIPTION	"The hostname that maps to the L2TP Domain Identifier."
	    ::= { stnL2tpDomainMapTableEntry 2 }

    stnL2tpDomainMapType OBJECT-TYPE
	    SYNTAX		StnDomainMapType
	    MAX-ACCESS	read-only
	    STATUS		current
	    DESCRIPTION     "Identifiers whether the L2TP Domain maps to an IP 
			     subnet or an ATM circuit."
	    ::= { stnL2tpDomainMapTableEntry 3 }

    stnL2tpDomainMapTypeInfo OBJECT-TYPE
	    SYNTAX		DisplayString
	    MAX-ACCESS	read-only
	    STATUS		current
	    DESCRIPTION	"Provides either IP or ATM specific display info."
	    ::= { stnL2tpDomainMapTableEntry 4 }


END
