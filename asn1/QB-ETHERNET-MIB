--
--	Quantum Bridge qbEthernetMIB Management Information Base
--	Version 1.0.0
--	January 12, 2001
--
--	Quantum Bridge Corporation
--	Two Tech Drive
--	Andover, MA 01810
--	(978) 983-2617
--
--------------------------------------------------------------------------------------
--				
--  01/15/2001 - mvaysman    	Added 24-port card objects
--
----------------------------------------------------------------------------------------
--
	QB-ETHERNET-MIB DEFINITIONS ::= BEGIN

	IMPORTS
	TEXTUAL-CONVENTION FROM SNMPv2-TC
	MODULE-IDENTITY, OBJECT-TYPE, Counter32
		FROM SNMPv2-SMI
	MODULE-COMPLIANCE, OBJECT-GROUP
		FROM SNMPv2-CONF
	dot3StatsEntry
		FROM EtherLike-MIB
	MacAddress
	        FROM BRIDGE-MIB
       QbAtmAal5EncapsType
		FROM QB-DWS-MIB  
       qbMibs
            FROM QUANTUMBRIDGE-REG
       ;

	qbEthernetMIB MODULE-IDENTITY
	LAST-UPDATED "0110222155Z" -- January 11, 2001
	ORGANIZATION "Quanrtum Bridge Inc."
	CONTACT-INFO
		"mvaysman@quantumbridge.com"
	DESCRIPTION
		"This module defines proprietary objects that extend those in
		IETF's the Ethernet-Like Interface MIB."
	::= { qbMibs 5 }
      
    -- added support for loopback - wjf 11/17/2000
	-- ================================================================
	-- Top-level organization of the MIB
	-- ================================================================

	qbDot3Objects        OBJECT IDENTIFIER ::= { qbEthernetMIB 1 }
	qbDot3Conformance    OBJECT IDENTIFIER ::= { qbEthernetMIB 2 } 
                                                           
                                                           
    -- ================================================================
    -- Textual Conventions
    -- ================================================================
    
    
	QbDot3LoopbackType ::= TEXTUAL-CONVENTION
		STATUS          current
   		DESCRIPTION	"The type of loopback available on Quantum Bridge 802.3
   				(ethernet) interfaces."
    		SYNTAX          INTEGER {
					qbDot3LoopbackNoLoop(1),
					qbDot3LoopbackLineLoop(2),
					qbDot3LoopbackPayloadLoop(3)
					}

	-- ================================================================
	-- Object Definitions
	-- ================================================================

	--
	-- Quantum Brige Ethernet Config Table	
	--

    qbDot3ConfigTable OBJECT-TYPE
	SYNTAX      SEQUENCE OF QbDot3ConfigEntry
	MAX-ACCESS  not-accessible
	STATUS      current
	DESCRIPTION
		"Quantum Bridge proprietary configuration parameters for ethernet-like
		interfaces."
    ::= { qbDot3Objects 2 }

    qbDot3ConfigEntry OBJECT-TYPE
	SYNTAX      QbDot3ConfigEntry
	MAX-ACCESS  not-accessible
	STATUS      current
	DESCRIPTION
		"Quantum Bridge proprietary configuration parameters for single
		ethernet-like interface."
	AUGMENTS    { dot3StatsEntry }
	::= { qbDot3ConfigTable 1 }

	QbDot3ConfigEntry ::= SEQUENCE {
	   qbDot3ConfigSpeed                INTEGER,
	   qbDot3ConfigDuplexMode           INTEGER,
	   qbDot3ConfigEncapsType	    QbAtmAal5EncapsType,
	   qbDot3ConfigRouterAddress        MacAddress,
	   qbDot3ConfigLoopback		    QbDot3LoopbackType,
	   qbDot3ConfigEnetAdminMode	    OBJECT IDENTIFIER,
	   qbDot3ConfigEnetType		    OBJECT IDENTIFIER,
	   qbDot3ConfigEnetNegMode	    INTEGER
	}

    qbDot3ConfigSpeed OBJECT-TYPE
	SYNTAX      INTEGER {
		            mbps10(1), 
			    mbps100(2),
			    auto(3)
			}	
	MAX-ACCESS  read-write
	STATUS      deprecated
	DESCRIPTION
		"The configured speed of the interface. This may be set by the
		administrator or may be the result of auto-negotiation."
	DEFVAL      { auto }
	::= { qbDot3ConfigEntry 1 }

    qbDot3ConfigDuplexMode OBJECT-TYPE
         SYNTAX      INTEGER {
		                full(1), 
				half(2),
				auto(3)
				}
	MAX-ACCESS  read-write
	STATUS      deprecated
	DESCRIPTION
		"The configured mode of the interface."
	DEFVAL      { auto }
	::= { qbDot3ConfigEntry 2 }

    qbDot3ConfigEncapsType OBJECT-TYPE
	SYNTAX      QbAtmAal5EncapsType
        MAX-ACCESS  read-write
        STATUS      current
        DESCRIPTION
		"The type of data encapsulation used over
		the AAL5 SSCS layer. The definitions reference
		RFC 1483 Multiprotocol Encapsulation
		over ATM AAL5 and to the ATM Forum
		LAN Emulation specification."
	DEFVAL  { qbRoutedEncapsNoHdrNoFcs }
   ::= { qbDot3ConfigEntry 3 }

   qbDot3ConfigRouterAddress OBJECT-TYPE	
              SYNTAX  MacAddress
              MAX-ACCESS  read-write
              STATUS  current
              DESCRIPTION
                      "The MAC address of the router that connects to
		       the IOT Ethnernet port. Note that this object
		       is relevant for IOT ports only"  
    ::= { qbDot3ConfigEntry 4 }

   qbDot3ConfigLoopback OBJECT-TYPE	
              SYNTAX  QbDot3LoopbackType
              MAX-ACCESS  read-write
              STATUS  current
              DESCRIPTION
                      "The loopback configuration of this interface. If used in a 
                      set it will cause the agent to place the interface in the 
                      desired loopback mode. When read, it will return the interface's
                      curretn loopback configuration." 
    ::= { qbDot3ConfigEntry 5 }

    qbDot3ConfigEnetAdminMode OBJECT-TYPE
          SYNTAX      OBJECT IDENTIFIER
          MAX-ACCESS  read-write
          STATUS      current
          DESCRIPTION 
		      "This object identifies the default
                      administrative baseband MAU type, to be used in
                      conjunction with the operational MAU type
                      denoted by ifMauType. For a detailed description
		      see ifMauDefaultType in RFC2668."
          REFERENCE   "[IEEE 802.3 Std], 30.5.1.1.1, aMAUID, and
                      22.2.4.1.4."
          ::= { qbDot3ConfigEntry  6 }

  qbDot3ConfigEnetType	 OBJECT-TYPE
          SYNTAX      OBJECT IDENTIFIER
          MAX-ACCESS  read-only
          STATUS      current
          DESCRIPTION 
		      "This object identifies the MAU type.
		      For a detailed description
		      see ifMauType in RFC2668."
          REFERENCE   "[IEEE 802.3 Std], 30.5.1.1.1, a MAUID, and
                      22.2.4.1.4."
          ::= { qbDot3ConfigEntry  7 }

  qbDot3ConfigEnetNegMode	 OBJECT-TYPE
          SYNTAX      INTEGER {
		    enable(1),
		    disable(2)
	  }
          MAX-ACCESS  read-write
          STATUS      current
          DESCRIPTION 
		      "This object is used to enable and disable
		      auto-negotiation on a given port."
          ::= { qbDot3ConfigEntry  8 }

	-- ================================================================
	-- Conformance Information
	-- ================================================================

	qbDot3Compliances    OBJECT IDENTIFIER ::= { qbDot3Conformance 1 }
	qbDot3Groups         OBJECT IDENTIFIER ::= { qbDot3Conformance 2 }

	--
	-- Compliance Statements
	--

    qbDot3Compliance MODULE-COMPLIANCE
	STATUS      current
	DESCRIPTION
		"The compliance statement for all agents that support this
		MIB. A compliant agent implements all objects defined
		in this MIB."
        MODULE  -- this module
        MANDATORY-GROUPS {
			 qbDot3Group
			 }
	::= { qbDot3Compliances 1 }

	--
	-- Object Groups
	--

   qbDot3Group OBJECT-GROUP
	OBJECTS {
	        qbDot3ConfigSpeed,
		qbDot3ConfigDuplexMode,
		qbDot3ConfigEncapsType,
		qbDot3ConfigRouterAddress,
		qbDot3ConfigLoopback,
		qbDot3ConfigEnetAdminMode,
		qbDot3ConfigEnetType,
		qbDot3ConfigEnetNegMode
	    }
	STATUS      current
	DESCRIPTION
		"The set of all accessible objects in this MIB."
	::= { qbDot3Groups 1 }

   END
