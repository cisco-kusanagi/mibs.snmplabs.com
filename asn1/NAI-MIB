NAI-MIB DEFINITIONS ::= BEGIN

IMPORTS
        enterprises, TimeTicks                                
        FROM RFC1155-SMI
        OBJECT-TYPE                        
        FROM RFC-1212
        TRAP-TYPE                          
        FROM RFC-1215
        DisplayString
        FROM RFC1213-MIB;
 
nai                             OBJECT IDENTIFIER ::= { enterprises 3401 }
naiStandardTrap                 OBJECT IDENTIFIER ::= { nai 1 }

naiTrapAgent OBJECT-TYPE
	SYNTAX          DisplayString (SIZE(0..8))
	ACCESS          read-only
	STATUS          mandatory
	DESCRIPTION     
          "The name of the agent that generated the trap."
	::= { naiStandardTrap 1 }

naiTrapAgentVersion OBJECT-TYPE
        SYNTAX          DisplayString (SIZE(0..8))
        ACCESS          read-only
        STATUS          mandatory
        DESCRIPTION
          "The version of the agent that generated the trap."
        ::= { naiStandardTrap 2 }

naiTrapSeverity OBJECT-TYPE
        SYNTAX          INTEGER
        {
                inform(1),
                warning(2),
                minor(3),
                major(4),
                critical(5)
        }
        ACCESS          read-only
        STATUS          mandatory
        DESCRIPTION
          "Additional information delivered with alarm messages and indicated the critical, 
          Major, Minor, Warning and informational.  Advanced management applications can make 
          use of this information to better evaluate the severity of the situation. This 
          variable is only intended for use with traps; no meaning should be assumed by a 
          Manager to the value retrieved through a Get operation on this object."
        ::= { naiStandardTrap 3 }

naiTrapDescription OBJECT-TYPE
        SYNTAX          DisplayString (SIZE(0..300))
--        SYNTAX          OCTET STRING
        ACCESS          read-only
        STATUS          mandatory
        DESCRIPTION     
          "The alarm description."
        ::= { naiStandardTrap 4 }

naiTrapAlarmSourceAddress OBJECT-TYPE
        SYNTAX          OCTET STRING
        ACCESS          read-only
        STATUS          mandatory
        DESCRIPTION
          "This information identifies the piece of equipment which is casuing the alarm.
           If the information is not available, then this field can be left blank."
        ::= { naiStandardTrap 5 }

naiTrapAlarmSourceDNSName OBJECT-TYPE
        SYNTAX          OCTET STRING
        ACCESS          read-only
        STATUS          mandatory
        DESCRIPTION     
          "The fully qualified DNS name of the piece of equipment which is casuing the            alarm.This can contain the name of the machine that sent the trap, if DNS name
           is not available."
        ::= { naiStandardTrap 6 }

naiTrapGMTTime OBJECT-TYPE
        SYNTAX          TimeTicks
        ACCESS          read-only
        STATUS          mandatory
        DESCRIPTION     
          "The time that the condition or event occurred which caused
          generation of this alarm.  This value is given in seconds since
          00:00:00 Greenwich mean time (GMT) January 1, 1970."
        ::= { naiStandardTrap 7 }

naiTrapLocalTime OBJECT-TYPE
        SYNTAX          TimeTicks
        ACCESS          read-only
        STATUS          mandatory
        DESCRIPTION
          "The time that the condition or event occurred which caused
          generation of this alarm.  This value is given in seconds since
          00:00:00 Local time January 1, 1970."
        ::= { naiStandardTrap 8 }

naiTrapURL OBJECT-TYPE
        SYNTAX          OCTET STRING
        ACCESS          read-only
        STATUS          mandatory
        DESCRIPTION     
          "A fully qualified URL link to an HTML page/FTP file for more information about the alarm."
        ::= { naiStandardTrap 9 }


naiTrapPseudoID OBJECT-TYPE
        SYNTAX          INTEGER
        ACCESS          read-only
        STATUS          optional
        DESCRIPTION     
          "This information identifies the pseudo-Id of the trap being sent.
          If the information is not available, then this field can be left blank."
        ::= { naiStandardTrap 10 }


END
