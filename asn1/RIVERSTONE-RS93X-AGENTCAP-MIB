-- RS Firmware Agent Capabilities macro

-- #include "rfc2665.inc"
-- #include "rfc2668.inc"
-- #include "rfc2011.inc"
-- #include "rfc2096.inc"
-- #include "rfc2012.inc"
-- #include "rfc2013.inc"
-- #include "rfc1850a.inc"
-- #include "rfc1850b.inc"
-- #include "rfc1724.inc"
-- #include "rfc1657.inc"
-- #include "rfc1493.inc"
-- #include "rfc2674a.inc"
-- #include "rfc2674b.inc"
-- #include "rfc2115.inc"
-- #include "rfc1471.inc"
-- #include "rfc1472.inc"
-- #include "rfc1473.inc"
-- #include "rfc2495.inc"
-- #include "rfc2496.inc"
-- #include "rfc1595.inc"
-- #include "rfc1695.inc"
-- #include "rfc2618.inc"
-- #include "rfc1757.inc"
-- #include "rfc2021.inc"
-- #include "rfc2670.inc"


-- draft and enterprise mibs
-- #include "ctron-ssr-smi.txt"
-- #include "rstone-smi-mib.txt"
-- #include "DOCS-BPI-MIB.txt"
-- #include "VRRP-MIB.txt"
-- #include "CTRON-LFAP-MIB.txt"
-- #include "ctron-ssr-policy.txt"
-- #include "ctron-ssr-config.txt"
-- #include "ctron-ssr-hardware.txt"
-- #include "ctron-ssr-service-status.txt"
-- #include "ctron-ssr-capacity.txt"
-- #include "CISCO-SRP-MIB.txt"


RIVERSTONE-RS93X-AGENTCAP-MIB DEFINITIONS ::= BEGIN

IMPORTS
    MODULE-IDENTITY, Integer32, Unsigned32
       FROM SNMPv2-SMI
    DisplayString
       FROM SNMPv2-TC
    AGENT-CAPABILITIES
       FROM  SNMPv2-CONF
    InetAddress
       FROM INET-ADDRESS-MIB
    riverstoneAgentCapabilities 
       FROM RIVERSTONE-SMI-MIB;

rstoneRs93xAgentCapabilityMIB MODULE-IDENTITY
   LAST-UPDATED "200211250000Z"  -- November 25, 2002
   ORGANIZATION "Riverstone Networks, Inc"
   CONTACT-INFO
	"Riverstone Networks, Inc
	 5200 Great America Parkway
	 Santa Clara CA USA 95054
	 PHONE:+1 408.878.6500
	 EMAIL: nms-eng@riverstonenet.com
	 WEB: http://www.riverstonenet.com"

   DESCRIPTION
     "This module defines agent capabilities for Riverstone RS RapidOS 
     Software Product version 9.3.x."


    REVISION     "200211150000Z"
    DESCRIPTION
         "Created agent capabilities mib for version 9.3.x of 
          Riverstone RS RapidOS software product. For agent capabilities of 
		  older versions of RapidOS, refer to rstone-rs-agent-cap-mib.txt and
          ssr-agent-capabilities mib"
        ::= { riverstoneAgentCapabilities 93 }


-- this branch is for device specific agent information descriptions via AGENT-CAPABILITIES macro

rsCapability OBJECT IDENTIFIER ::= {  rstoneRs93xAgentCapabilityMIB 1 }

 rs93x AGENT-CAPABILITIES 
  PRODUCT-RELEASE 
     "9.3.x"
  STATUS  current
  DESCRIPTION
     "Firmware Release 9.3.x for Riverstone  RS RapidOS product line.
      This firmware version supports the following new features - 
      Layer 2 VPLS based on Lasserre-Compella draft, 
      RFC 2549 MPLS-BGP VPN support, ATM VC support for Martini VLL, and 
      HRT enhancements. New hardware includes ES 10170 with Gen5 GE and 
      Gen 4 FE blades, CM5 for RS 8000,
      OC3 and OC48 PoS/MPLS blades for RS 38000, PoS/MPLS blade for RS 3000,
      and FE Gen5 blades for RS 38000, RS 8000 and RS 3000.

      Changes in Existing MIB Modules include:
          DISMAN-PING-MIB
      New MIB modules include:
          RIVERSTONE-MPLS-MIB
          RIVERSTONE-QUEUE-MIB
          RIVERSTONE-VLAN-EXTENSIONS-MIB (introduced in release 9.1.0.1)

      "
  REFERENCE 
     "http://www.riverstonenet.com/products"

     -- RFC 1907
     SUPPORTS SNMPv2-MIB
     INCLUDES { 
         systemGroup,
         snmpGroup, 
         snmpBasicNotificationsGroup,
         --  snmpSetGroup is not implemented, but is needed for SNMPv2-MIB compliance
         -- non mandatory groups
         snmpCommunityGroup,
         -- deprecated/obsolete support
         snmpObsoleteGroup
     }

     -- ********************* ************ ************ *************** ***
     -- RFC 2358
     SUPPORTS EtherLike-MIB
     INCLUDES { 
         etherStats100MbsGroup
     }

     -- ********************* ************ ************ *************** ***
     -- RFC 2233
     SUPPORTS IF-MIB
     INCLUDES { 
         ifGeneralInformationGroup, 
         ifStackGroup2,
         ifCounterDiscontinuityGroup,
         -- non mandatory groups
         ifFixedLengthGroup,
         ifHCFixedLengthGroup,
         ifPacketGroup,
         ifHCPacketGroup,
         ifVHCPacketGroup,
         ifRcvAddressGroup,
         -- deprecated/obsolete support
         ifOldObjectsGroup
     }
     VARIATION ifAlias
     ACCESS read-only
     DESCRIPTION "ifAlias is guarenteed to be unique across reboots. It takes the form Type : instance info
      for example: ifAlias.49 = IP interface: to-sc-BGPfeed or ifAlias.42 = VLAN: test1 or 
      ifAlias.35 = Physical port: et.14.5"

     VARIATION ifAdminStatus
     ACCESS read-only
     DESCRIPTION "For ifTypes corresponding to VLANs this object is read only."

     VARIATION ifLinkUpDownTrapEnable
     ACCESS read-only
     DESCRIPTION "For all ifTypes where ifConnectorPresent is not TRUE."

     VARIATION ifStackStatus
     ACCESS read-only
     DESCRIPTION "Command line interface(CLI) is used to change relationships."

     -- ********************* ************ ************ *************** ***
     -- RFC 2011
     SUPPORTS IP-MIB
     INCLUDES { 
         ipGroup,
         icmpGroup
     }
     VARIATION ipDefaultTTL
     ACCESS read-only
     DESCRIPTION "Command line interface(CLI) is used to change default ttl."

     -- ********************* ************ ************ *************** ***
     -- RFC 2096
     SUPPORTS IP-FORWARD-MIB
     INCLUDES { 
         ipForwardCidrRouteGroup
     }
     VARIATION ipCidrRouteIfIndex
     ACCESS read-only
     DESCRIPTION "Command line interface(CLI) is used to update Forwarding Information Base/FIB."

     VARIATION ipCidrRouteType
     ACCESS read-only
     DESCRIPTION "Command line interface(CLI) is used to update Forwarding Information Base/FIB."

     VARIATION ipCidrRouteInfo
     ACCESS read-only
     DESCRIPTION "Command line interface(CLI) is used to update Forwarding Information Base/FIB."

     VARIATION ipCidrRouteNextHopAS
     ACCESS read-only
     DESCRIPTION "Command line interface(CLI) is used to update Forwarding Information Base/FIB."

     VARIATION ipCidrRouteMetric1
     ACCESS read-only
     DESCRIPTION "Command line interface(CLI) is used to update Forwarding Information Base/FIB."

     VARIATION ipCidrRouteMetric2
     ACCESS read-only
     DESCRIPTION "Command line interface(CLI) is used to update Forwarding Information Base/FIB."

     VARIATION ipCidrRouteMetric3
     ACCESS read-only
     DESCRIPTION "Command line interface(CLI) is used to update Forwarding Information Base/FIB."

     VARIATION ipCidrRouteMetric4
     ACCESS read-only
     DESCRIPTION "Command line interface(CLI) is used to update Forwarding Information Base/FIB."

     VARIATION ipCidrRouteMetric5
     ACCESS read-only
     DESCRIPTION "Command line interface(CLI) is used to update Forwarding Information Base/FIB."

     VARIATION ipCidrRouteStatus
     ACCESS read-only
     DESCRIPTION "Command line interface(CLI) is used to update Forwarding Information Base/FIB."

     -- ********************* ************ ************ *************** ***
     -- RFC 2013
     SUPPORTS UDP-MIB
     INCLUDES { 
         udpGroup         
     }

     -- ********************* ************ ************ *************** ***
     -- RFC 2012
     SUPPORTS TCP-MIB
     INCLUDES { 
         tcpGroup         
     }
     VARIATION tcpConnState
     ACCESS read-only
     DESCRIPTION "Command line interface(CLI) is used to kill tcp sessions."

     -- ********************* ************ ************ *************** ***
     --  RFC 1657 
--     SUPPORTS BGP4-MIB
--     INCLUDES { 
--         This is an smiv1 mib, all objects read only. Specify in device config file to enable this mib.
--     }

     -- ********************* ************ ************ *************** ***
     -- RFC 1850    
     -- Specify in device config file to enable this mib.
     SUPPORTS OSPF-MIB
     INCLUDES { 
         ospfBasicGroup,
         ospfAreaGroup,
         ospfStubAreaGroup,
         ospfIfGroup,
         ospfIfMetricGroup,
         ospfVirtIfGroup,
         ospfNbrGroup,
         ospfVirtNbrGroup,
         ospfAreaAggregateGroup
     }
     VARIATION ospfRouterId
     ACCESS read-only
     DESCRIPTION "Command line interface(CLI) is used to set router id."

     VARIATION ospfAdminStat
     ACCESS read-only
     DESCRIPTION "Command line interface(CLI) is used to set ospf state."

     VARIATION ospfTOSSupport
     ACCESS read-only
     DESCRIPTION "Command line interface(CLI) is used to set ospf TOS support."

     VARIATION ospfExtLsdbLimit
     ACCESS read-only
     DESCRIPTION "Command line interface(CLI) is used to set ospf Lsdb Limit."

     VARIATION ospfMulticastExtensions
     ACCESS read-only
     DESCRIPTION "Command line interface(CLI) is used to set ospf multicast extensions."

     VARIATION ospfExitOverflowInterval
     ACCESS read-only
     DESCRIPTION "Command line interface(CLI) is used to set ospf exit overflow interval."

     VARIATION ospfDemandExtensions
     ACCESS read-only
     DESCRIPTION "Command line interface(CLI) is used to set ospf demand extensions."

     VARIATION ospfAuthType
     ACCESS read-only
     DESCRIPTION "Command line interface(CLI) is used to set ospf authorisation types."

     VARIATION ospfImportAsExtern
     ACCESS read-only
     DESCRIPTION "Command line interface(CLI) is used to set ospf Import AS external routes."

     VARIATION ospfAreaSummary
     ACCESS read-only
     DESCRIPTION "Command line interface(CLI) is used to set ospf area summary importation."

     VARIATION ospfAreaStatus
     ACCESS read-only
     DESCRIPTION "Command line interface(CLI) is used to create & delete ospf areas."

     VARIATION ospfStubMetric
     ACCESS read-only
     DESCRIPTION "Command line interface(CLI) is used to set ospf area stub metric."

     VARIATION ospfStubStatus
     ACCESS read-only
     DESCRIPTION "Command line interface(CLI) is used to create & delete stub areas."

     VARIATION ospfStubMetricType
     ACCESS read-only
     DESCRIPTION "Command line interface(CLI) is used to set ospf stub metric type."

     VARIATION ospfAreaRangeMask
     ACCESS read-only
     DESCRIPTION "Command line interface(CLI) is used to set ospf area range mask."

     VARIATION ospfAreaRangeStatus
     ACCESS read-only
     DESCRIPTION "Command line interface(CLI) is used to create & delete ranges."

     VARIATION ospfAreaRangeEffect
     ACCESS read-only
     DESCRIPTION "Command line interface(CLI) is used to set area range effect."

     VARIATION ospfHostMetric
     ACCESS read-only
     DESCRIPTION "Command line interface(CLI) is used to set host metric."

     VARIATION ospfHostStatus
     ACCESS read-only
     DESCRIPTION "Command line interface(CLI) is used to create & delete hosts."

     VARIATION ospfIfAreaId
     ACCESS read-only
     DESCRIPTION "Command line interface(CLI) is used to set Interface area id."

     VARIATION ospfIfType
     ACCESS read-only
     DESCRIPTION "Command line interface(CLI) is used to set Interface type."

     VARIATION ospfIfAdminStat
     ACCESS read-only
     DESCRIPTION "Command line interface(CLI) is used to set Interface admin status."

     VARIATION ospfIfRtrPriority
     ACCESS read-only
     DESCRIPTION "Command line interface(CLI) is used to set interface router priority."

     VARIATION ospfIfTransitDelay
     ACCESS read-only
     DESCRIPTION "Command line interface(CLI) is used to set interface transit delay."

     VARIATION ospfIfRetransInterval
     ACCESS read-only
     DESCRIPTION "Command line interface(CLI) is used to set interface retransmission interval."

     VARIATION ospfIfHelloInterval
     ACCESS read-only
     DESCRIPTION "Command line interface(CLI) is used to set hello interval."

     VARIATION ospfIfRtrDeadInterval
     ACCESS read-only
     DESCRIPTION "Command line interface(CLI) is used to set dead interval."

     VARIATION ospfIfPollInterval
     ACCESS read-only
     DESCRIPTION "Command line interface(CLI) is used to set poll interval."

     VARIATION ospfIfAuthKey
     ACCESS read-only
     DESCRIPTION "Command line interface(CLI) is used to set interface auth key."

     VARIATION ospfIfStatus
     ACCESS read-only
     DESCRIPTION "Command line interface(CLI) is used to create & delete interfaces."

     VARIATION ospfIfMulticastForwarding
     ACCESS read-only
     DESCRIPTION "Command line interface(CLI) is used to set multicast fwd."

     VARIATION ospfIfDemand
     ACCESS read-only
     DESCRIPTION "Command line interface(CLI) is used to set this attribute."

     VARIATION ospfIfAuthType
     ACCESS read-only
     DESCRIPTION "Command line interface(CLI) is used to set this feature."

     VARIATION ospfIfMetricValue
     ACCESS read-only
     DESCRIPTION "Command line interface(CLI) is used to set this feature."

     VARIATION ospfVirtIfTransitDelay
     ACCESS read-only
     DESCRIPTION "Command line interface(CLI) is used to set this feature."

     VARIATION ospfVirtIfRetransInterval
     ACCESS read-only
     DESCRIPTION "Command line interface(CLI) is used to set this feature."

     VARIATION ospfVirtIfHelloInterval
     ACCESS read-only
     DESCRIPTION "Command line interface(CLI) is used to set this feature."

     VARIATION ospfVirtIfRtrDeadInterval
     ACCESS read-only
     DESCRIPTION "Command line interface(CLI) is used to set this feature."

     VARIATION ospfVirtIfAuthKey
     ACCESS read-only
     DESCRIPTION "Command line interface(CLI) is used to set this feature."

     VARIATION ospfVirtIfStatus
     ACCESS read-only
     DESCRIPTION "Command line interface(CLI) is used to set this feature."

     VARIATION ospfVirtIfAuthType
     ACCESS read-only
     DESCRIPTION "Command line interface(CLI) is used to set this feature."

     VARIATION ospfNbrPriority
     ACCESS read-only
     DESCRIPTION "Command line interface(CLI) is used to set this feature."

     VARIATION ospfNbmaNbrStatus
     ACCESS read-only
     DESCRIPTION "Command line interface(CLI) is used to set this feature."

     VARIATION ospfAreaAggregateStatus
     ACCESS read-only
     DESCRIPTION "Command line interface(CLI) is used to set this feature."

     VARIATION ospfAreaAggregateEffect
     ACCESS read-only
     DESCRIPTION "Command line interface(CLI) is used to set this feature."

     SUPPORTS OSPF-TRAP-MIB
     INCLUDES { 
         ospfTrapControlGroup
     }

     -- ********************* ************ ************ *************** ***
     -- RFC 1724
     -- Specify in device config file to enable this mib.
     SUPPORTS RIPv2-MIB
     INCLUDES { 
         rip2GlobalGroup,
         rip2IfStatGroup,
         rip2IfConfGroup,
         rip2PeerGroup
     }
     VARIATION rip2IfStatStatus
     ACCESS read-only
     DESCRIPTION "Command line interface(CLI) is used to set this feature."
   
     VARIATION rip2IfConfDomain
     ACCESS read-only
     DESCRIPTION "Command line interface(CLI) is used to set this feature."

     VARIATION rip2IfConfAuthType
     ACCESS read-only
     DESCRIPTION "Command line interface(CLI) is used to set this feature."

     VARIATION rip2IfConfAuthKey
     ACCESS read-only
     DESCRIPTION "Command line interface(CLI) is used to set this feature."

     VARIATION rip2IfConfSend
     ACCESS read-only
     DESCRIPTION "Command line interface(CLI) is used to set this feature."

     VARIATION rip2IfConfReceive
     ACCESS read-only
     DESCRIPTION "Command line interface(CLI) is used to set this feature."

     VARIATION rip2IfConfDefaultMetric
     ACCESS read-only
     DESCRIPTION "Command line interface(CLI) is used to set this feature."

     VARIATION rip2IfConfStatus
     ACCESS read-only
     DESCRIPTION "Command line interface(CLI) is used to set this feature."

     VARIATION rip2IfConfSrcAddress
     ACCESS read-only
     DESCRIPTION "Command line interface(CLI) is used to set this feature."

     -- ********************* ************ ************ *************** ***
     -- RFC 1493
--    SUPPORTS BRIDGE-MIB
--    INCLUDES { 
--       smiv1 mib
--    }

     -- ********************* ************ ************ *************** ***
     -- RFC 2674
     -- Updated 09/20/00

     SUPPORTS Q-BRIDGE-MIB
     INCLUDES {
        qBridgeBaseGroup,
        qBridgeVlanGroup,
        qBridgeVlanStaticGroup,
        qBridgePortGroup,
        qBridgeFdbUnicastGroup,
        qBridgeFdbMulticastGroup
     }     

     --qBridgeStaticVlanTable
     --Implicit Vlans are not accounted by SNMP.
     --Only 10 Non Active rows can be present in the temp table . If the user
     --tries to create more than 10 Non Active rows, BAD_VALUE will be returned.
     --Vlan name has to be specified when creating a vlan, apart from the vlan id.
     --This is a limitation of the RS family (RFC does not ask for the vlan name.)

     VARIATION dot1qVlanStaticUntaggedPorts
     ACCESS read-only 
     DESCRIPTION "No hardware support"

     VARIATION dot1qVlanStaticEgressPorts
     ACCESS read-write
     DESCRIPTION "Apart from permanent entries , non permanent entries ( 
	        in the active config and not in the startup config) will 
	        also be displayed."

     

     VARIATION dot1qPvid
     ACCESS read-write
     DESCRIPTION  "For Trunk-Port, PVID cannot be set. Trunk ports can be in 
	         more than one vlan (apart from being in default vlan). 
	         Get reports the default vlan ID."

     VARIATION dot1qPortGvrpStatus
     ACCESS read-only
     DESCRIPTION  "CLI is used to set this"

     VARIATION dot1qTpVlanPortInFrames
     DESCRIPTION "For this object to exist, per-VLAN statistics must first be 
                  enabled through the CLI for each port to be monitored.  

                  SmartTRUNKs are currently not supported."

     VARIATION dot1qTpVlanPortOutFrames
     DESCRIPTION "For this object to exist, per-VLAN statistics must first be 
                  enabled through the CLI for each port to be monitored.  

                  SmartTRUNKs are currently not supported.

                  When an egress port is oversubscribed, the value of this
                  object may be larger than the actual value, since the RS
                  platform cannot account for packets dropped internally 
                  at this level of granularity."

     VARIATION dot1qTpVlanPortInDiscards
     DESCRIPTION "The RS platform does not support the collection of this
                  statistic."

     VARIATION dot1qTpVlanPortInOverflowFrames
     DESCRIPTION "For this object to exist, per-VLAN statistics must first be 
                  enabled through the CLI for each port to be monitored.  

                  SmartTRUNKs are currently not supported."

     VARIATION dot1qTpVlanPortOutOverflowFrames
     DESCRIPTION "For this object to exist, per-VLAN statistics must first be 
                  enabled through the CLI for each port to be monitored.  

                  SmartTRUNKs are currently not supported.

                  When an egress port is oversubscribed, the value of this
                  object may be larger than the actual value, since the RS
                  platform cannot account for packets dropped internally 
                  at this level of granularity."

     VARIATION dot1qTpVlanPortInOverflowDiscards
     DESCRIPTION "The RS platform does not support the collection of this
                  statistic."

     VARIATION dot1qTpVlanPortHCInFrames
     DESCRIPTION "For this object to exist, per-VLAN statistics must first be 
                  enabled through the CLI for each port to be monitored.  

                  SmartTRUNKs are currently not supported."

     VARIATION dot1qTpVlanPortHCOutFrames
     DESCRIPTION "For this object to exist, per-VLAN statistics must first be 
                  enabled through the CLI for each port to be monitored.  

                  SmartTRUNKs are currently not supported.

                  When an egress port is oversubscribed, the value of this
                  object may be larger than the actual value, since the RS
                  platform cannot account for packets dropped internally 
                  at this level of granularity."

     VARIATION dot1qTpVlanPortHCInDiscards
     DESCRIPTION "The RS platform does not support the collection of this
                  statistic."

     VARIATION dot1qConstraintSetDefault
     DESCRIPTION  "This object is not supported."

     VARIATION dot1qConstraintTypeDefault
     DESCRIPTION  "This object is not supported."

     -- ********************* ************ ************ *************** ***
        -- RFC 2674
        -- Update 09/26/00

        SUPPORTS P-BRIDGE-MIB
        INCLUDES {
            pBridgeExtCapGroup,
            pBridgeDevicePriorityGroup,
            pBridgeDefaultPriorityGroup,
            pBridgePriorityGroup,
	        pBridgePortGarpGroup
        }

-- pBridgeExtCapGroup: dot1dDeviceCapabilities :: 
-- dot1dExtendedFilteringServices ,dot1qConfigurablePvidTagging ,
-- dot1qSVLCapable,dot1qHybridCapable  not supported.


     VARIATION dot1dTrafficClassesEnabled
     ACCESS read-only
     DESCRIPTION "This is not settable through SNMP. However this can be
                  set using CLI by mapping all 1p priority levels to the
	        same traffic class."


-- pBridgeDefaultPriorityGroup: dot1dPortDefaultUserPriority If the user 
--			  configures default priority on a port and later
--			  configures a priority for a MAC / VLAN pair
--			  using CLI, CLI would report a conflict.

--			  When this variable is set through snmp, the 
--			  name used for the qos command would be 
--			  "snmp-priority-#portnum". This would be the 
--			  case, even if a priority was configured 
--			  through the cli (using qos set l2 command)
--			  with a different name (say priority-#portnum),
--			  and then modified through snmp.


     VARIATION dot1dPortNumTrafficClasses
     ACCESS read-only
     DESCRIPTION "This value is not settable. Setting this value is optional		        only."


     VARIATION dot1dGmrpStatus
     ACCESS read-only
     DESCRIPTION "Not supported in this release."


     VARIATION dot1dPortGarpJoinTime
     ACCESS read-only
     DESCRIPTION "This is not settable."


     VARIATION dot1dPortGarpLeaveTime
     ACCESS read-only
     DESCRIPTION "This is not settable."


     VARIATION dot1dPortGarpLeaveAllTime
     ACCESS read-only
     DESCRIPTION "This is not settable."

     -- ********************* ************ ************ *************** ***
     -- RFC 2115
     SUPPORTS FRAME-RELAY-DTE-MIB
     INCLUDES { 
       frPortGroup, 
       frCircuitGroup,
       frErrGroup,
       frTrapGroup
     }
     VARIATION frDlcmiState
     ACCESS read-only
     DESCRIPTION "Command line interface(CLI) is used to set this feature."

     VARIATION frDlcmiAddress
     ACCESS read-only
     DESCRIPTION "Command line interface(CLI) is used to set this feature."

     VARIATION frDlcmiAddressLen
     ACCESS read-only
     DESCRIPTION "Command line interface(CLI) is used to set this feature."

     VARIATION frDlcmiPollingInterval
     ACCESS read-only
     DESCRIPTION "Command line interface(CLI) is used to set this feature."
     
     VARIATION frDlcmiFullEnquiryInterval
     ACCESS read-only
     DESCRIPTION "Command line interface(CLI) is used to set this feature."

     VARIATION frDlcmiErrorThreshold
     ACCESS read-only
     DESCRIPTION "Command line interface(CLI) is used to set this feature."

     VARIATION frDlcmiMonitoredEvents
     ACCESS read-only
     DESCRIPTION "Command line interface(CLI) is used to set this feature."

     VARIATION frDlcmiMaxSupportedVCs
     ACCESS read-only
     DESCRIPTION "Command line interface(CLI) is used to set this feature."

     VARIATION frDlcmiMulticast
     ACCESS read-only
     DESCRIPTION "Command line interface(CLI) is used to set this feature."

     VARIATION frDlcmiRowStatus
     ACCESS read-only
     DESCRIPTION "Command line interface(CLI) is used to create & delete dlcmi's."

     VARIATION frCircuitState
     ACCESS read-only
     DESCRIPTION "Command line interface(CLI) is used to set this feature."

     VARIATION frCircuitCommittedBurst
     ACCESS read-only
     DESCRIPTION "Command line interface(CLI) is used to set this feature."

     VARIATION frCircuitExcessBurst
     ACCESS read-only
     DESCRIPTION "Command line interface(CLI) is used to set this feature."

     VARIATION frCircuitThroughput
     ACCESS read-only
     DESCRIPTION "Command line interface(CLI) is used to set this feature."

     VARIATION frCircuitMulticast
     ACCESS read-only
     DESCRIPTION "Command line interface(CLI) is used to set this feature."

     VARIATION frCircuitLogicalIfIndex
     ACCESS read-only
     DESCRIPTION "Command line interface(CLI) is used to set this feature."

     VARIATION frCircuitRowStatus
     ACCESS read-only
     DESCRIPTION "Command line interface(CLI) is used to set this feature."

     -- ********************* ************ ************ *************** ***
       -- RFC 1471
--     SUPPORTS PPP-LCP-MIB
--     INCLUDES { 
--       smiv1 mib - read only 
--     }

     -- ********************* ************ ************ *************** ***
       -- RFC 1472
--     SUPPORTS PPP-SEC-MIB
--     INCLUDES { 
--      smiv1 mib - read only
--     }

     -- ********************* ************ ************ *************** ***
       -- RFC 1473
--     SUPPORTS PPP-IP-NCP-MIB
--     INCLUDES { 
--       smiv1 mib - read only
--     }

     -- ********************* ************ ************ *************** ***
       -- RFC 1474
--     SUPPORTS PPP-BRIDGE-NCP-MIB
--     INCLUDES { 
--       smiv1 mib - read only
--     }

     -- ********************* ************ ************ *************** ***
	 -- RFC 2494
	 SUPPORTS DS0-MIB
	 INCLUDES {
		ds0ConfigGroup
	 }

     -- ********************* ************ ************ *************** ***
	 -- RFC 2494
	 SUPPORTS DS0BUNDLE-MIB
	 INCLUDES {
		ds0BundleConfigGroup
	 }

     -- ********************* ************ ************ *************** ***
     -- RFC 2495
     SUPPORTS DS1-MIB
     INCLUDES { 
        ds1NearEndConfigGroup,
        ds1NearEndStatisticsGroup,
		ds1NearEndOptionalConfigGroup,
		ds1ChanMappingGroup 
     }
     VARIATION dsx1LineType
     ACCESS read-only
     DESCRIPTION "Command line interface(CLI) is used to set this feature."

     VARIATION dsx1LineCoding
     ACCESS read-only
     DESCRIPTION "Command line interface(CLI) is used to set this feature."

     VARIATION dsx1SendCode
     ACCESS read-only
     DESCRIPTION "Command line interface(CLI) is used to set this feature."

     VARIATION dsx1CircuitIdentifier
     ACCESS read-only
     DESCRIPTION "Command line interface(CLI) is used to set this feature."

     VARIATION dsx1LoopbackConfig
     ACCESS read-only
     DESCRIPTION "Command line interface(CLI) is used to set this feature."

     VARIATION dsx1SignalMode
     ACCESS read-only
     DESCRIPTION "Command line interface(CLI) is used to set this feature."

     VARIATION dsx1TransmitClockSource
     ACCESS read-only
     DESCRIPTION "Command line interface(CLI) is used to set this feature."

     VARIATION dsx1Fdl
     ACCESS read-only
     DESCRIPTION "Command line interface(CLI) is used to set this feature."

     VARIATION dsx1LineLength
     ACCESS read-only
     DESCRIPTION "Command line interface(CLI) is used to set this feature."

     VARIATION dsx1LineStatusChangeTrapEnable
     ACCESS read-only
     DESCRIPTION "Command line interface(CLI) is used to set this feature."

     VARIATION dsx1Channelization
     ACCESS read-only
     DESCRIPTION "Command line interface(CLI) is used to set this feature."

     -- ********************* ************ ************ *************** ***
     -- RFC 2496
     SUPPORTS DS3-MIB
     INCLUDES { 
        ds3NearEndConfigGroup,
        ds3NearEndStatisticsGroup,
		ds3NearEndOptionalConfigGroup 
     }

     VARIATION dsx3LineType
     ACCESS read-only
     DESCRIPTION "Command line interface(CLI) is used to set this feature."

     VARIATION dsx3LineCoding
     ACCESS read-only
     DESCRIPTION "Command line interface(CLI) is used to set this feature."

     VARIATION dsx3SendCode
     ACCESS read-only
     DESCRIPTION "Command line interface(CLI) is used to set this feature."

     VARIATION dsx3CircuitIdentifier
     ACCESS read-only
     DESCRIPTION "Command line interface(CLI) is used to set this feature."

     VARIATION dsx3LoopbackConfig
     ACCESS read-only
     DESCRIPTION "Command line interface(CLI) is used to set this feature."

     VARIATION dsx3TransmitClockSource
     ACCESS read-only
     DESCRIPTION "Command line interface(CLI) is used to set this feature."

     VARIATION dsx3LineLength
     ACCESS read-only
     DESCRIPTION "Command line interface(CLI) is used to set this feature."

     VARIATION dsx3LineStatusChangeTrapEnable
     ACCESS read-only
     DESCRIPTION "Command line interface(CLI) is used to set this feature."

     VARIATION dsx3Channelization
     ACCESS read-only
     DESCRIPTION "Command line interface(CLI) is used to set this feature."

     VARIATION dsx3Ds1ForRemoteLoop
     ACCESS read-only
     DESCRIPTION "Command line interface(CLI) is used to set this feature."

     -- ********************* ************ ************ *************** ***
     -- RFC 2558
     SUPPORTS SONET-MIB
     INCLUDES { 
        sonetMediumStuff2, 
        sonetSectionStuff2,
        sonetLineStuff2,
        sonetFarEndLineStuff2,
        sonetPathStuff2,
        sonetFarEndPathStuff2
     }

     VARIATION sonetMediumType
     ACCESS read-write 
     DESCRIPTION "This object is settable."

     VARIATION sonetMediumLineCoding
     ACCESS read-only 
     DESCRIPTION "This object is not settable."

     VARIATION sonetMediumLineType
     ACCESS read-only 
     DESCRIPTION "This object is not settable."

     VARIATION sonetMediumCircuitIdentifier
     ACCESS read-write 
     DESCRIPTION "This object is settable."

     VARIATION sonetMediumInvalidIntervals
     ACCESS read-only
     DESCRIPTION "This object is not up to spec because of two
	 reasons. One this object would not be less than 
	 sonetMediumValidIntervals at any time. Two, an interval
	 cannot be both valid and invalid. This object would start
	 as the number of intervals that are unavailable. An 
	 unavailable interval is an interval that has not finished its
	 15 minute collection of data. It is also an interval that has
	 finished its 15 minutes collection, but no data exist. 
	 The object would decrement if the interval becomes available 
	 and if there is valid data. The sum of this object and 
	 sonetMediumValidIntervals would always be the number of 
	 intervals that are requested to be kept."

     VARIATION sonetMediumLoopbackConfig
     ACCESS read-write 
     DESCRIPTION "This object is settable."

     VARIATION sonetSESthresholdSet
     ACCESS read-only 
     DESCRIPTION "This object is not settable."

     VARIATION sonetPathCurrentWidth
     ACCESS read-only 
     DESCRIPTION "This object is not settable."

     -- The performance monitoring stats don't work for ATM OC3 in 9.1.

     -- ********************* ************ ************ *************** ***
     -- RFC 2515
     SUPPORTS ATM-MIB
     INCLUDES { 
        atmInterfaceConfGroup2,
        atmTrafficDescrGroup2,
	atmVpcTerminationGroup2,
        atmVclCrossConnectGroup,
	atmVcPvcCrossConnectGroup,
        aal5VccGroup
     }    

     VARIATION atmInterfaceMaxVpcs
     ACCESS read-only 
     DESCRIPTION "This object is not settable"

     VARIATION atmInterfaceMaxVccs
     ACCESS read-only
     DESCRIPTION "This object is not settable"

     VARIATION atmInterfaceMaxActiveVpiBits
     ACCESS read-only
     DESCRIPTION "This object is not settable"
     
     VARIATION atmInterfaceMaxActiveVciBits
     ACCESS read-only
     DESCRIPTION "This object is not settable"

     VARIATION atmInterfaceIlmiVpi
     ACCESS not-implemented
     DESCRIPTION "Device does not support Ilmi"

     VARIATION atmInterfaceIlmiVci
     ACCESS not-implemented
     DESCRIPTION "Device does not support Ilmi"

     VARIATION atmInterfaceMyNeighborIpAddress
     ACCESS not-implemented
     DESCRIPTION "Firmware does not support this"

     VARIATION atmInterfaceMyNeighborIfName
     ACCESS not-implemented
     DESCRIPTION "Firmware does not support this"

     VARIATION atmTrafficDescrParam1
     ACCESS read-only
     DESCRIPTION "Command line interface(CLI) is used to set this feature"

     VARIATION atmTrafficDescrParam2
     ACCESS read-only
     DESCRIPTION "Command line interface(CLI) is used to set this feature"
     
     VARIATION atmTrafficDescrParam3
     ACCESS read-only
     DESCRIPTION "Command line interface(CLI) is used to set this feature"

     VARIATION atmTrafficDescrParam4
     ACCESS read-only
     DESCRIPTION "Command line interface(CLI) is used to set this feature"

     VARIATION atmTrafficDescrParam5
     ACCESS read-only
     DESCRIPTION "Command line interface(CLI) is used to set this feature"

     VARIATION atmTrafficQoSClass
     ACCESS read-only
     DESCRIPTION "Command line interface(CLI) is used to set this feature"

     VARIATION atmTrafficDescrRowStatus
     ACCESS not-implemented
     DESCRIPTION "Table is read-only"

     VARIATION atmVclAdminStatus
     ACCESS read-only
     DESCRIPTION "Command line interface(CLI) is used to set this feature"

     VARIATION atmVclReceiveTrafficDescrIndex
     ACCESS read-only
     DESCRIPTION "Memory address is used as the index, CLI is used to set this"

     VARIATION atmVclTransmitTrafficDescrIndex
     ACCESS read-only
     DESCRIPTION "Memory address is used as the index, CLI is used to set this"
        
     VARIATION atmVccAalType
     ACCESS read-only
     DESCRIPTION "This object is not settable"

     VARIATION atmVclRowStatus
     ACCESS read-only
     DESCRIPTION "This object is not settable"

     -- ********************* ************ ************ *************** ***
     -- RFC 2618
     SUPPORTS RADIUS-AUTH-CLIENT-MIB
     INCLUDES { 
          radiusAuthClientMIBGroup
     }

     -- ********************* ************ ************ *************** ***
     -- RFC 1757/2819
       SUPPORTS RMON-MIB
       INCLUDES { 
         
         rmonEtherStatsGroup,
         rmonHistoryControlGroup,
         rmonEthernetHistoryGroup,
         rmonAlarmGroup,
         rmonHostGroup,   -- requires flow bridging hardware mode enabled
         rmonHostTopNGroup, 
         rmonMatrixGroup, -- requires flow bridging hardware mode enabled
         rmonFilterGroup,
         rmonPacketCaptureGroup,
         rmonEventGroup,
         rmonNotificationGroup
       }

     -- ********************* ************ ************ *************** ***
     -- RFC 2021
     SUPPORTS RMON2-MIB
     INCLUDES { 
        protocolDirectoryGroup,
        protocolDistributionGroup,
        addressMapGroup,
        nlHostGroup,
        nlMatrixGroup,
        alHostGroup,
        alMatrixGroup,
        usrHistoryGroup,
        probeInformationGroup,
        probeConfigurationGroup,
        rmon1EthernetEnhancementGroup
        -- rmon1EnhancementGroup supported except for filterProtocolDirDataLocalIndex,
        --  filterProtocolDirLocalIndex
     }
     VARIATION filterProtocolDirDataLocalIndex
     ACCESS not-implemented
     DESCRIPTION "Feature not available in this firmware version "

     VARIATION filterProtocolDirLocalIndex
     ACCESS not-implemented
     DESCRIPTION "Feature not available in this firmware version "

     -- NOTE: Sets to this mib are not persistent. RMON configuration
     -- may be done via CLI for persistence
     -- ********************* ************ ************ *************** ***
     -- From ietf vrrp mib RFC 2787 
     SUPPORTS VRRP-MIB
     INCLUDES { 
        vrrpOperGroup,
        vrrpStatsGroup,
        vrrpTrapGroup,
        vrrpNotificationGroup
     }
     VARIATION vrrpOperAdminState
     ACCESS read-only
     DESCRIPTION "Command line interface(CLI) is used to set this feature."

     VARIATION vrrpOperPriority
     ACCESS read-only
     DESCRIPTION "Command line interface(CLI) is used to set this feature."

     VARIATION vrrpOperPrimaryIpAddr
     ACCESS read-only
     DESCRIPTION "Command line interface(CLI) is used to set this feature."

     VARIATION vrrpOperAuthType
     ACCESS read-only
     DESCRIPTION "Command line interface(CLI) is used to set this feature."

     VARIATION vrrpOperAuthKey
     ACCESS read-only
     DESCRIPTION "Command line interface(CLI) is used to set this feature."

     VARIATION vrrpOperAdvertisementInterval
     ACCESS read-only
     DESCRIPTION "Command line interface(CLI) is used to set this feature."

     VARIATION vrrpOperPreemptMode
     ACCESS read-only
     DESCRIPTION "Command line interface(CLI) is used to set this feature."

     VARIATION vrrpOperProtocol
     ACCESS read-only
     DESCRIPTION "Command line interface(CLI) is used to set this feature."

     VARIATION vrrpOperRowStatus
     ACCESS read-only
     DESCRIPTION "Command line interface(CLI) is used to set this feature."

     VARIATION vrrpAssoIpAddrRowStatus
     ACCESS read-only
     DESCRIPTION "Command line interface(CLI) is used to set this feature."

     VARIATION vrrpStatsPacketLengthErrors
     ACCESS not-implemented
     DESCRIPTION "Current VRRP code is not supporting this statistic"

     -- this section has been commented out because smilint gives some
     -- strange errors. But the fact remains that vrrpTrapAuthFailure
     -- notification is not supported in RapidOS

     -- VARIATION vrrpTrapAuthFailure
     -- ACCESS not-implemented
     -- DESCRIPTION "TrapAuthFailure not implemented"
 
     -- ********************* ************ ************ *************** ***

     SUPPORTS CTRON-LFAP-MIB
     INCLUDES { 
        lfapConfGroupV40
     }

     -- ********************* ************ ************ *************** ***

     SUPPORTS CTRON-SSR-POLICY-MIB
     INCLUDES { 
         polGroupV11        
     }

     -- ********************* ************ ************ *************** ***

     SUPPORTS CTRON-SSR-CONFIG-MIB
     INCLUDES { 
         configGroup20
     }

     
     -- ********************* ************ ************ *************** ***

     SUPPORTS CTRON-SSR-HARDWARE-MIB
     INCLUDES { 
         hwConfGroupV30
     }

     -- ********************* ************ ************ *************** ***

     SUPPORTS CTRON-SSR-SERVICE-STATUS-MIB
     INCLUDES { 
         ssConfGroupV11
     }

     -- ********************* ************ ************ *************** ***

     SUPPORTS CTRON-SSR-CAPACITY-MIB
     INCLUDES { 
         capConfGroupV10
     }

     -- ********************* ************ ************ *************** ***

	 SUPPORTS DOCS-IF-MIB
	 INCLUDES {
         docsIfBasicGroup, 
		 docsIfCmtsGroup
	 }

	 VARIATION docsIfQosProfMaxTxBurst
	 ACCESS read-write
	 DESCRIPTION "This variable returns the value in bits/second rather than
	 mini-slots because this is the expected type by Cablelabs."

     -- ********************* ************ ************ *************** ***

     SUPPORTS DOCS-BPI-MIB
     INCLUDES {
	     docsBpiCmtsGroup
	 }

     VARIATION docsBpiCmtsDefaultAuthLifetime
     ACCESS read-write
     DESCRIPTION "For testing purposes, this variable has an increased
     numeric range from 1 to 6048000."

     VARIATION docsBpiCmtsDefaultTEKLifetime
     ACCESS read-write
     DESCRIPTION "For testing purposes, this variable has an increased
     numeric range from 1 to 604800."

     VARIATION docsBpiCmtsAuthCmLifetime
     ACCESS read-write
     DESCRIPTION "For testing purposes, this variable has an increased
     numeric range from 1 to 6048000."

     VARIATION docsBpiCmtsAuthCmGraceTime
     ACCESS read-write
     DESCRIPTION "For testing purposes, this variable has an increased
     numeric range from 1 to 1800."

     VARIATION docsBpiCmtsTEKLifetime
     ACCESS read-write
     DESCRIPTION "For testing purposes, this variable has an increased
     numeric range from 1 to 604800."

     VARIATION docsBpiCmtsTEKGraceTime
     ACCESS read-write
     DESCRIPTION "For testing purposes, this variable has an increased
     numeric range from 1 to 1800."

     -- ********************* ************ ************ *************** ***

     SUPPORTS RIVERSTONE-STP-MIB
     INCLUDES {
	     rsStpBaseGroup
	 }

     VARIATION rsStpStatus
	 ACCESS not-implemented
	 DESCRIPTION "STP cannot be disabled globally on RS devices"

    -- ********************* ************ ************ *************** ***

     -- IEEE 802.3ad , LAG MIB
     SUPPORTS LAG-MIB
     INCLUDES {
        dot3adAggGroup,
        dot3adAggPortGroup,
        dot3adTablesLastChangedGroup,
        dot3adAggPortListGroup,  
        dot3adAggPortStatsGroup,
        dot3adAggPortDebugGroup
     }

     VARIATION dot3adAggPartnerSystemPriority
     ACCESS read-only 
     DESCRIPTION "This object is not aggregator specific"
     
     VARIATION dot3adAggCollectorMaxDelay
     ACCESS read-only 
     DESCRIPTION "This object is not settable"
  
     VARIATION dot3adAggPortPartnerAdminSystemPriority
     ACCESS read-only 
     DESCRIPTION "This object is not settable"
  
     VARIATION dot3adAggPortPartnerAdminSystemID
     ACCESS read-only 
     DESCRIPTION "This object is not settable"
  
     VARIATION dot3adAggPortPartnerAdminKey
     ACCESS read-only 
     DESCRIPTION "This object is not settable"
  
     VARIATION dot3adAggPortPartnerAdminPort
     ACCESS read-only 
     DESCRIPTION "This object is not settable"
  
     VARIATION dot3adAggPortPartnerAdminPortPriority
     ACCESS read-only 
     DESCRIPTION "This object is not settable"
  
  
     VARIATION dot3adTablesLastChanged
     ACCESS not-implemented
     DESCRIPTION "Firmware does not support this"
  
     VARIATION dot3adAggPortDebugRxState
     ACCESS not-implemented
     DESCRIPTION "Firmware does not support this"
  
     VARIATION dot3adAggPortDebugLastRxTime
     ACCESS not-implemented
     DESCRIPTION "Firmware does not support this"
  
     VARIATION dot3adAggPortDebugMuxState
     ACCESS not-implemented
     DESCRIPTION "Firmware does not support this"
  
     VARIATION dot3adAggPortDebugMuxReason
     ACCESS not-implemented
     DESCRIPTION "Firmware does not support this"
  
     VARIATION dot3adAggPortDebugActorChurnState
     ACCESS not-implemented
     DESCRIPTION "Firmware does not support this"
  
     VARIATION dot3adAggPortDebugPartnerChurnState
     ACCESS not-implemented
     DESCRIPTION "Firmware does not support this"
  
     VARIATION dot3adAggPortDebugActorChurnCount
     ACCESS not-implemented
     DESCRIPTION "Firmware does not support this"
  
     VARIATION dot3adAggPortDebugPartnerChurnCount
     ACCESS not-implemented
     DESCRIPTION "Firmware does not support this"
  
     VARIATION dot3adAggPortDebugActorSyncTransitionCount
     ACCESS not-implemented
     DESCRIPTION "Firmware does not support this"
  
     VARIATION dot3adAggPortDebugPartnerSyncTransitionCount
     ACCESS not-implemented
     DESCRIPTION "Firmware does not support this"
  
     VARIATION dot3adAggPortDebugActorChangeCount
     ACCESS not-implemented
     DESCRIPTION "Firmware does not support this"
  
     VARIATION dot3adAggPortDebugPartnerChangeCount
     ACCESS not-implemented
     DESCRIPTION "Firmware does not support this"

    -- ********************* ************ ************ *************** ***
 
     SUPPORTS CISCO-BGP-POLICY-ACCOUNTING-MIB
     INCLUDES {
        cbpAcctTableGroup
     }
 
     -- ********************* ************ ************ *************** ***

     SUPPORTS CISCO-SRP-MIB
     INCLUDES {
        srpIfGroup,
        srpMACSideGroup,
        srpRingTopologyMapGroup,
        srpMACCountersGroup,
        srpRingCountersCurrentGroup,
        srpRingCountersIntervalGroup,
        srpHostCountersCurrentGroup,
        srpHostCountersIntervalGroup,
        srpErrorsCountersCurrentGroup,
        srpErrorsCountersIntervalGroup,
        srpErrCntCurrGroup,
        srpErrCntIntGroup,
        srpNotificationsGroup
     }

     VARIATION srpPriorityThreshold
     ACCESS read-only
     DESCRIPTION "Use CLI to set this object"
 
     VARIATION srpIpsLockedOut
     ACCESS read-only
     DESCRIPTION "This object is not supported"
 
     VARIATION srpIpsWaitToRestoreTimer
     ACCESS read-only
     DESCRIPTION "Use CLI to set this object"
 
     VARIATION srpMACIpsMgmtRequestedMode
     ACCESS read-only
     DESCRIPTION "Use CLI to set this object"
 
     VARIATION srpMACClockSourceMode
     ACCESS read-only
     DESCRIPTION "Use CLI to set this object"
 
     VARIATION srpMACTopologyTimer
     ACCESS read-only
     DESCRIPTION "Use CLI to set this object"
 
     VARIATION srpMACCountPktsBySourceFlag
     ACCESS read-only
     DESCRIPTION "Use CLI to set this deprecated object"
 
     VARIATION srpMACCountPktsBySourceAddress
     ACCESS read-only
     DESCRIPTION "Use CLI to set this deprecated object"
 
     VARIATION srpMACCountPktsByDestinationFlag
     ACCESS read-only
     DESCRIPTION "This deprecated object is not supported"
 
     VARIATION srpMACCountPktsByDestAddress
     ACCESS read-only
     DESCRIPTION "This deprecated object is not supported"
 
     VARIATION srpMACRejectPktsBySourceFlag
     ACCESS read-only
     DESCRIPTION "Use CLI to set this deprecated object"
 
     VARIATION srpMACRejectPktsBySourceAddress
     ACCESS read-only
     DESCRIPTION "Use CLI to set this deprecated object"
 
     VARIATION srpMACRejectPktsByDestFlag
     ACCESS read-only
     DESCRIPTION "This deprecated object is not supported"
 
     VARIATION srpMACRejectPktsByDestAddress
     ACCESS read-only
     DESCRIPTION "This deprecated object is not supported"
 
     -- ********************* ************ ************ *************** ***
 
     SUPPORTS RIVERSTONE-ATM-MIB
     INCLUDES {
        rsAtmFdbBaseGroup 
     }
 
     -- ********************* ************ ************ *************** ***
     
     SUPPORTS DISMAN-SCHEDULE-MIB
     INCLUDES {
        schedGroup,
        schedCalendarGroup,
        schedNotificationsGroup
     }
 
     -- ********************* ************ ************ *************** ***

     SUPPORTS ENTITY-MIB
     INCLUDES {
         entityPhysicalGroup,
         entityMappingGroup,
	 entityGeneralGroup,
	 entityNotificationsGroup,
	 entityPhysical2Group,
	 entityLogical2Group
     }

     VARIATION entLastChangeTime
     ACCESS read-only
     DESCRIPTION 
	 "This object would always be zero unless the notification
	  entConfigChange is enabled."

     VARIATION entPhysicalSerialNum
     ACCESS read-only
     DESCRIPTION 
	 "This object is readable in 9.1. The user can use the CLI to 
	  set this object."

     VARIATION entPhysicalAlias
     ACCESS read-only
     DESCRIPTION 
	 "This object does not return any meaninful value, and
	  it is currently not settable."

     VARIATION entPhysicalAssetID
     ACCESS read-only
     DESCRIPTION
	 "This object does not return any meaninful value, and
	  it is currently not settable."

     VARIATION entLPPhysicalIndex
     ACCESS not-implemented
     DESCRIPTION 
	 "This object is not implemented even though entLogical2Group
	  is implemented."

     VARIATION entAliasLogicalIndexOrZero
     ACCESS read-only
     DESCRIPTION 
	 "This object would always be zero even though entLogical2Group
	  is implemented."

     VARIATION entLogicalTAddress
     ACCESS not-implemented
     DESCRIPTION 
	 "This is not implemented. A meaningless value is returned."

     VARIATION entLogicalTDomain
     ACCESS not-implemented
     DESCRIPTION 
	 "This is not implemented. A meaningless value is returned."

     -- ********************* ************ ************ *************** ***

     SUPPORTS RADIUS-ACC-CLIENT-MIB
     INCLUDES {
        radiusAccClientMIBGroup
     }
 
     -- ********************* ************ ************ *************** ***

     SUPPORTS RIVERSTONE-RL-MIB
     INCLUDES {
        rsRateLimitGroup1, --perFlow and aggregate rate limiting
        rsRateLimitGroup2, --port based rate limiting
        rsRateLimitGroup4  --software flow aggregate, and time select objes
     }

     VARIATION rsTBMeterApplyMasterAdminStatus
     ACCESS read-write
     DESCRIPTION 
	 "Does not support SET"

     VARIATION rsPortRLMasterAdminStatus
     ACCESS read-write
     DESCRIPTION 
	 "Does not support SET"
 
     VARIATION rsPortRLCount
     ACCESS read-only
     DESCRIPTION 
	 "Counts rows whose rowStatus is 'active'"

     VARIATION rsTBMeterCount
     ACCESS read-only
     DESCRIPTION 
	 "Counts rows whose rowStatus is 'active'"

     VARIATION rsTBMeterApplyCount
     ACCESS read-only
     DESCRIPTION 
	 "Counts rows whose rowStatus is 'active'"
    
     VARIATION rsTBMeterApplyCount
     ACCESS read-only
     DESCRIPTION 
	 "Counts rows whose rowStatus is 'active'"
   
     VARIATION rsTBMeterApplyOwner
     ACCESS read-create
     DESCRIPTION 
	 "Not implemented"

     VARIATION rsPortRLOwner
     ACCESS read-create
     DESCRIPTION 
	 "Not implemented"
    
     -- ********************* ************ ************ *************** ***

     SUPPORTS RIVERSTONE-IMAGE-MIB
     INCLUDES {
        rsImageMibAddDeleteChooseGroup,
	rsImageMibListGroup,
	rsImageMibStatusAndErrorGroup
	}

     -- ********************* ************ ************ *************** ***

     SUPPORTS RIVERSTONE-SNMP-MIB
     INCLUDES {
        rsSnmpBaseGroup 
     }
 
     -- ********************* ************ ************ *************** ***

     SUPPORTS RIVERSTONE-LFAP-MIB
     INCLUDES {
        rsLfapAgentStateGroup,
	rsLfapAgentCfgGroup,

	rsLfapServerStaticGroup,
	rsLfapStatsGroup
     }

     VARIATION rsLfapPollInterval
     ACCESS read-only
     DESCRIPTION 
	 "This is not settable."

     VARIATION rsLfapBatchSize
     ACCESS read-only
     DESCRIPTION 
	 "This is not settable."

     VARIATION rsLfapBatchInterval
     ACCESS read-only
     DESCRIPTION 
	 "This is not settable."

     VARIATION rsLfapLostContactInterval
     ACCESS read-only
     DESCRIPTION 
	 "This is not settable."

     VARIATION rsLfapServerRetryInterval
     ACCESS read-only
     DESCRIPTION 
	 "This is not settable."

     VARIATION rsLfapMaxTxQueueSize
     ACCESS read-only
     DESCRIPTION 
	 "This is not settable."

     VARIATION rsLfapTaskPriority
     ACCESS read-only
     DESCRIPTION 
	 "This is not settable."

     VARIATION rsRunLfapSelfTest
     ACCESS read-only
     DESCRIPTION 
	 "This is not settable."
 
     -- ********************* ************ ************ *************** ***

--     SUPPORTS RIVERSTONE-TRAP-MIB
--     INCLUDES {
--     }
 
     -- ********************* ************ ************ *************** ***

     SUPPORTS DOCS-CABLE-DEVICE-MIB
     INCLUDES {
        docsDevEventGroup 
     }
 
     -- ********************* ************ ************ *************** ***

     SUPPORTS DOCS-CABLE-DEVICE-TRAP-MIB
     INCLUDES {
        docsDevCmtsTrapControlGroup, 
        docsDevCmtsNotificationGroup 
     }
 
     -- ********************* ************ ************ *************** ***

     SUPPORTS DOCS-BPI2-MIB
     INCLUDES {
        docsBpi2CmtsGroup
     }
 
   VARIATION docsBpi2CmtsDefaultAuthLifetime
   ACCESS read-write
   DESCRIPTION "For testing purposes, this variable has increased numeric
   range from 1 to 6048000."
 
   -- relaxation on mandatory range
   VARIATION    docsBpi2CmtsDefaultTEKLifetime
        SYNTAX    Integer32 (1800..604800)
        DESCRIPTION
        "The refined range corresponds to the minimum and maximum
        values in operational networks, according to Appendix A.2 in
        [7]."
 
   -- relaxation on mandatory range
   VARIATION    docsBpi2CmtsAuthCmLifetime
        SYNTAX    Integer32 (86400..6048000)
        DESCRIPTION
        "The refined range corresponds to the minimum and maximum
        values in operational networks, according to Appendix A.2 in
        [7]."
 
   -- relaxation on mandatory range
   VARIATION    docsBpi2CmtsTEKLifetime
        SYNTAX    Integer32 (1800..604800)
        DESCRIPTION
        "The refined range corresponds to the minimum and maximum
        values in operational networks, according to Appendix A.2 in
        [7]."
 
   -- relaxation on IP addressing
   VARIATION    docsBpi2CmIpMulticastAddressType
 
 
          -- SYNTAX InetAddressType { ipv4(1) }
          DESCRIPTION
          "An implementation is only required to support IPv4
           addresses."
 
   -- relaxation on IP addressing
   VARIATION    docsBpi2CmIpMulticastAddress
          SYNTAX  InetAddress (SIZE(4))
          DESCRIPTION
          "An implementation is only required to support IPv4
           addresses."
 
   -- relaxation on IP addressing
   VARIATION    docsBpi2CmtsIpMulticastAddressType
          -- SYNTAX InetAddressType { ipv4(1) }
          DESCRIPTION
          "An implementation is only required to support IPv4
           addresses."
 
   -- relaxation on IP addressing
   VARIATION    docsBpi2CmtsIpMulticastAddress
          SYNTAX  InetAddress (SIZE(4))
          DESCRIPTION
          "An implementation is only required to support IPv4
           addresses."
 
   -- relaxation on IP addressing
   VARIATION    docsBpi2CmtsIpMulticastMaskType
          -- SYNTAX InetAddressType { ipv4(1) }
          DESCRIPTION
          "An implementation is only required to support IPv4
           addresses."
 
   -- relaxation on IP addressing
   VARIATION    docsBpi2CmtsIpMulticastMask
          SYNTAX  InetAddress (SIZE(4))
          DESCRIPTION
          "An implementation is only required to support IPv4
           addresses."

     -- ********************* ************ ************ *************** ***

     SUPPORTS DOCS-IF-EXT-MIB
     INCLUDES {
           docsIfExtGroup,
           docsIfDocsisVersionGroup
     }
 
     -- ********************* ************ ************ *************** ***

     SUPPORTS DOCS-QOS-MIB
     INCLUDES {
       docsQosCmtsGroup,
       docsQosParamSetGroup,
       docsQosServiceClassGroup
     }
 
     -- ********************* ************ ************ *************** ***

     SUPPORTS DOCS-SUBMGT-MIB
     INCLUDES {
           docsSubMgtGroup
     }
 
     -- ********************* ************ ************ *************** ***
     
     SUPPORTS DISMAN-PING-MIB
     INCLUDES {
         pingGroup,
         pingTimeStampGroup,
         pingNotificationsGroup
     }

     VARIATION pingCtlTargetAddressType
     ACCESS read-create
     DESCRIPTION "pingCtlTargetAddressType must be set together with 
		  pingCtlTargetAddress in the same set request PDU."

     VARIATION pingCtlTargetAddress
     ACCESS read-create
     DESCRIPTION "pingCtlTargetAddress must be set together with 
		  pingCtlTargetAddressType in the same set request PDU."

     VARIATION pingCtlMaxRows
     SYNTAX Unsigned32 (1..4294967295)
     ACCESS read-create
     DESCRIPTION "pingCtlMaxRows cannot be 0."
 
     VARIATION pingCtlStorageType
     ACCESS read-create
     DESCRIPTION "Only values of volatile(2) and nonVolatile(3) are permitted.
                  volatile(2) corresponds with the active configuration, and 
                  nonVolatile(3) corresponds with the startup configuration."

     VARIATION pingCtlSourceAddressType
     ACCESS read-create
     DESCRIPTION "pingCtlSourceAddressType must be set together with 
		  pingCtlSourceAddress in the same set request PDU."

     VARIATION pingCtlSourceAddress
     ACCESS read-create
     DESCRIPTION "pingCtlSourceAddress must be set together with 
		  pingCtlSourceAddressType in the same set request PDU."
 
     VARIATION pingCtlIfIndex
     ACCESS read-only
     DESCRIPTION "The RS platform does not support this object.  It will
                  always return 0."

     -- ********************* ************ ************ *************** ***
     
     SUPPORTS DISMAN-TRACEROUTE-MIB
     INCLUDES {
           traceRouteGroup,
           traceRouteTimeStampGroup,
           traceRouteNotificationsGroup,
           traceRouteHopsTableGroup
     }
 
     VARIATION traceRouteCtlTargetAddressType
     ACCESS read-create
     DESCRIPTION "traceRouteCtlTargetAddressType must be set together with 
		  traceRouteCtlTargetAddress in the same set request PDU."

     VARIATION traceRouteCtlTargetAddress
     ACCESS read-create
     DESCRIPTION "traceRouteCtlTargetAddress must be set together with 
		  traceRouteCtlTargetAddressType in the same set request PDU."
 
     VARIATION traceRouteCtlSourceAddressType
     ACCESS read-create
     DESCRIPTION "traceRouteCtlSourceAddressType must be set together with 
		  traceRouteCtlSourceAddress in the same set request PDU."

     VARIATION traceRouteCtlSourceAddress
     ACCESS read-create
     DESCRIPTION "traceRouteCtlSourceAddress must be set together with 
		  traceRouteCtlSourceAddressType in the same set request PDU."
 
     VARIATION traceRouteCtlIfIndex
     ACCESS read-only
     DESCRIPTION "The RS platform does not support this object.  It will
                  always return 0."

     VARIATION traceRouteCtlStorageType
     ACCESS read-create
     DESCRIPTION "Only values of volatile(2) and nonVolatile(3) are permitted.
                  volatile(2) corresponds with the active configuration, and 
                  nonVolatile(3) corresponds with the startup configuration."

     -- ********************* ************ ************ *************** ***

     SUPPORTS MPLS-LSR-MIB
     INCLUDES {
           mplsInSegmentGroup,
           mplsOutSegmentGroup,
           mplsXCGroup,
           mplsInterfaceGroup,
           mplsPerfGroup,
           mplsHCInSegmentPerfGroup,
           mplsHCOutSegmentPerfGroup,
           mplsTrafficParamGroup,
           mplsLabelStackGroup,
           mplsLsrNotificationGroup
     }
 
     VARIATION mplsInterfaceFailedLabelLookup
     ACCESS read-only
     DESCRIPTION "The RS platform does not support this object.  It will
                  always return 0."

     VARIATION mplsInterfaceOutFragments
     ACCESS read-only
     DESCRIPTION "The RS platform does not support this object.  It will
                  always return 0."

     VARIATION mplsInSegmentOwner
     ACCESS read-only
     DESCRIPTION "This object is implemented as readOnly."

     VARIATION mplsInSegmentTrafficParamPtr
     ACCESS read-only
     DESCRIPTION "This object is implemented as readOnly."

     VARIATION mplsInSegmentRowStatus
     ACCESS read-only
     DESCRIPTION "This object is implemented as readOnly."

     VARIATION mplsInSegmentStorageType
     ACCESS read-only
     DESCRIPTION "This object is implemented as readOnly."

     VARIATION mplsInSegmentErrors
     ACCESS read-only
     DESCRIPTION "The RS platform does not support this object.  It will
                  always return 0."

     VARIATION mplsOutSegmentOwner
     ACCESS read-only
     DESCRIPTION "This object is implemented as readOnly."

     VARIATION mplsOutSegmentTrafficParamPtr
     ACCESS read-only
     DESCRIPTION "This object is implemented as readOnly."

     VARIATION mplsOutSegmentErrors
     ACCESS read-only
     DESCRIPTION "The RS platform does not support this object.  It will
                  always return 0."

     VARIATION mplsXCLspId
     ACCESS read-only
     DESCRIPTION "This object is implemented as readOnly."

     VARIATION mplsXCOwner
     ACCESS read-only
     DESCRIPTION "This object is implemented as readOnly."

     VARIATION mplsLabelStackLabel
     ACCESS read-only
     DESCRIPTION "This object is implemented as readOnly."

     VARIATION mplsLabelStackRowStatus
     ACCESS read-only
     DESCRIPTION "This object is implemented as readOnly."

     VARIATION mplsLabelStackStorageType
     ACCESS read-only
     DESCRIPTION "This object is implemented as readOnly."

     VARIATION mplsTrafficParamMaxRate
     ACCESS read-only
     DESCRIPTION "This object is implemented as readOnly."

     VARIATION mplsTrafficParamMaxBurstSize
     ACCESS read-only
     DESCRIPTION "This object is implemented as readOnly."

     VARIATION mplsTrafficParamRowStatus
     ACCESS read-only
     DESCRIPTION "This object is implemented as readOnly."

     VARIATION mplsTrafficParamStorageType
     ACCESS read-only
     DESCRIPTION "This object is implemented as readOnly."

     -- ********************* ************ ************ *************** ***

--     SUPPORTS ISIS-MIB
--     INCLUDES {

        --TBD: Current draft v0.4 does not have a conformance section
        --This section will be updated as soon as we move to the new draft
        --The tables supported in the current versions(all are read only).
        --1.  isisSysEntry,
        --2.  isisManAreaAddrTable,
        --3.  isisAreaAddrTable
        --4.  isisSysProtSuppTable,
        --5.  isisCircTable,
        --6.  isisCircLevelEntry,
        --7.  isisPacketCountEntry,
        --8.  isisISAdjEntry,
        --9.  isisISAdjAreaAddrEntry,
        --10. isisISAdjIPAddrTable
        --11. isisISAdjProtSuppTable

--     }
 
     -- ********************* ************ ************ *************** ***

     SUPPORTS IGMP-STD-MIB
     INCLUDES {
           igmpBaseMIBGroup,
           igmpRouterMIBGroup,
           igmpV2RouterMIBGroup
     }
 
     -- ********************* ************ ************ *************** ***

     SUPPORTS RIVERSTONE-INVENTORY-MIB
     INCLUDES {
           rsChassisGroup,
           rsModuleGroup,
           rsEnvGroup
     }
 
     -- ********************* ************ ************ *************** ***

     SUPPORTS NOTIFICATION-LOG-MIB
     INCLUDES {
           notificationLogConfigGroup,
           notificationLogStatsGroup,
           notificationLogLogGroup
     }

     -- ********************* ************ ************ *************** ***

     SUPPORTS RIVERSTONE-CONFIG-MIB
     INCLUDES {
           rsConfigGroup,
           rsChangeLogGroup,
           rsConfigNotificationGroup,
           rsConfigNotificationControlGroup,
           rsBootInfoGroup 
     }

     VARIATION rsCfgHostAddressType
     ACCESS read-create
     DESCRIPTION 
	 "We support only ipv4 type."
     
     VARIATION rsCfgHostAddress
     SYNTAX  InetAddress (SIZE(4))
     ACCESS read-create
     DESCRIPTION 
	 "We support only ipv4 type.  So, the length of the address is
          restricted to 4."
     
     VARIATION rsCfgFileName
     SYNTAX  DisplayString (SIZE(255))
     ACCESS read-create
     DESCRIPTION 
	 "We support only strings of length 255 or less."
     
     VARIATION rsCfgFileTransferProtocol
     ACCESS read-create
     DESCRIPTION 
	 "We support only TFTP as the file transfer protocol."
     
     VARIATION rsCfgMaxActiveChangeLines
     SYNTAX  Integer32 (100..1000)
     ACCESS read-write
     DESCRIPTION 
	 "We support only the value to be between 100 and 1000."
     
     VARIATION rsCfgMaxActiveChangeLinesPerSession
     SYNTAX  Integer32 (0..100)
     ACCESS read-write
     DESCRIPTION 
	 "We support only values between 0 and 100.  This variable
          cannot be set when the tracking is enabled.  You will have
          to disable and then set this value."
     
     VARIATION rsCfgMaxActiveChangeSessions
     SYNTAX  Integer32 (10..2000)
     ACCESS read-write
     DESCRIPTION 
	 "We support only values between 10 and 2000.  This variable
          cannot be set when the tracking is enabled.  You will have
          to disable and then set this value."
     
 
     -- ********************* ************ ************ *************** ***

     SUPPORTS RIVERSTONE-DHCP-MIB
     INCLUDES {
           rsDhcpGroup1
     }

     -- ********************* ************ ************ *************** ***

     -- Draft #17
     SUPPORTS ATM2-MIB
     INCLUDES { 
          atmHostGroup -- We support only 4 objects and only 1 group.
     }

     VARIATION atmAal5VclInPkts
     ACCESS read-only
     DESCRIPTION 
	 "For ATM OC3, this stat would always return 0 because of
	  hardware limitations."

     VARIATION atmVclAddrType
     ACCESS read-only
     DESCRIPTION "Not supported."

     VARIATION atmVclAddrRowStatus
     ACCESS read-only
     DESCRIPTION "Not supported."

     VARIATION atmAddrVclAddrType
     ACCESS read-only
     DESCRIPTION "Not supported."

     VARIATION atmVclGenSigDescrIndex
     ACCESS read-only
     DESCRIPTION "Not supported."

     VARIATION atmSigDescrParamAalType
     ACCESS read-only
     DESCRIPTION "Not supported."

     VARIATION atmSigDescrParamAalSscsType
     ACCESS read-only
     DESCRIPTION "Not supported."

     VARIATION atmSigDescrParamBhliType
     ACCESS read-only
     DESCRIPTION "Not supported."

     VARIATION atmSigDescrParamBhliInfo
     ACCESS read-only
     DESCRIPTION "Not supported."

     VARIATION atmSigDescrParamBbcConnConf
     ACCESS read-only
     DESCRIPTION "Not supported."

     VARIATION atmSigDescrParamBlliLayer2
     ACCESS read-only
     DESCRIPTION "Not supported."

     VARIATION atmSigDescrParamBlliLayer3
     ACCESS read-only
     DESCRIPTION "Not supported."

     VARIATION atmSigDescrParamBlliPktSize
     ACCESS read-only
     DESCRIPTION "Not supported."

     VARIATION atmSigDescrParamBlliSnapId
     ACCESS read-only
     DESCRIPTION "Not supported."

     VARIATION atmSigDescrParamBlliOuiPid
     ACCESS read-only
     DESCRIPTION "Not supported."

     VARIATION atmSigDescrParamRowStatus
     ACCESS read-only
     DESCRIPTION "Not supported."


     SUPPORTS RIVERSTONE-VLAN-EXTENSIONS-MIB
     INCLUDES {
         rsPortVlanStatsGroup,
         rsPortVlanStatsOverflowGroup,
         rsPortVlanHCStatsGroup
     }


     SUPPORTS RIVERSTONE-MPLS-MIB
     INCLUDES { 
         rsMPLSLSRExtensionGroup,
         rsMPLSNotificationGroup,
         rsMPLSNotificationControlGroup
     }


     SUPPORTS RIVERSTONE-QUEUE-MIB
     INCLUDES { 
         rsQueuePropertiesGroup,
         rsQueueStatsGroup
     }

     -- ********************* ************ ************ *************** ***

     -- ********************* ************ ************ *************** ***
   ::= { rsCapability 9 }

END
