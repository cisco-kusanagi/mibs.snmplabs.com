-- extracted from draft-ietf-disman-alarm-mib-18.txt
-- at Thu Feb 12 06:16:55 2004

   IANA-ITU-ALARM-TC DEFINITIONS ::= BEGIN

   IMPORTS
      MODULE-IDENTITY, mib-2       FROM SNMPv2-SMI
      TEXTUAL-CONVENTION           FROM SNMPv2-TC;

    ianaItuAlarmNumbers MODULE-IDENTITY
        LAST-UPDATED "200402090000Z"
        ORGANIZATION "IANA"
        CONTACT-INFO
            "Postal:    Internet Assigned Numbers Authority
                        Internet Corporation for Assigned Names
                        and Numbers
                        4676 Admiralty Way, Suite 330
                        Marina del Rey, CA 90292-6601
                        USA

            Tel:    +1  310-823-9358
            E-Mail: iana@iana.org"
        DESCRIPTION
            "The MIB module defines the ITU Alarm
            textual convention for objects expected to require
            regular extension.

            Copyright (C) The Internet Society (2004).  The
            initial version of this MIB module was published
            in RFC xxxx. For full legal notices see the RFC
            itself. Supplementary information may be available on:
                 http://www.ietf.org/copyrights/ianamib.html"
         REVISION    "200402090000Z"
         DESCRIPTION
             "Initial version, published as RFC yyyy."
             -- RFC-Editor assigns yyyy
        ::= { mib-2 XX } -- to be assigned by IANA


   IANAItuProbableCause ::= TEXTUAL-CONVENTION
       STATUS current
       DESCRIPTION
           "ITU-T probable cause values. Duplicate values defined in
            X.733 are appended with X733 to ensure syntactic uniqueness.
            Probable cause value 0 is reserved for special purposes.

            The Internet Assigned Number Authority (IANA) is responsible
            for the assignment of the enumerations in this TC.
            IANAItuProbableCause value of 0 is reserved for special
            purposes and MUST NOT be assigned.

            Values of IANAItuProbableCause in the range 1 to 1023 are
            reserved for causes that correspond to ITU-T probable cause.

            All other requests for new causes will be handled on a
            first-come, first served basis and will be assigned
            enumeration values starting with 1025.

            Request should  come in the form of well-formed
            SMI [RFC2578] for enumeration names that are unique and
            sufficiently descriptive.

            While some effort will be taken to ensure that new probable
            causes do not conceptually duplicate existing probable
            causes it is acknowledged that the existence of conceptual
            duplicates in the starting probable cause list is an known
            industry reality.

            To aid IANA in the administration of probable cause names
            and values, the OPS Area Director will appoint one or more
            experts to help review requests.

            See http://www.iana.org"
       REFERENCE
           "ITU Recommendation M.3100, 'Generic Network Information
               Model', 1995
            ITU Recommendation X.733, 'Information Technology - Open
               Systems Interconnection - System Management: Alarm
               Reporting Function', 1992
            ITU Recommendation X.736, 'Information Technology - Open
               Systems Interconnection - System Management: Security
               Alarm Reporting Function', 1992"

       SYNTAX         INTEGER
               {
               -- The following probable causes were defined in M.3100
                aIS  (1),
                callSetUpFailure  (2),
                degradedSignal  (3),
                farEndReceiverFailure  (4),
                framingError  (5),
                lossOfFrame (6),
                lossOfPointer  (7),
                lossOfSignal  (8),
                payloadTypeMismatch (9),
                transmissionError (10),
                remoteAlarmInterface (11),
                excessiveBER  (12),
                pathTraceMismatch  (13),
                unavailable  (14),
                signalLabelMismatch (15),
                lossOfMultiFrame (16),
                receiveFailure (17),
                transmitFailure (18),
                modulationFailure (19),
                demodulationFailure (20),
                broadcastChannelFailure (21),
                connectionEstablishmentError (22),
                invalidMessageReceived (23),
                localNodeTransmissionError (24),
                remoteNodeTransmissionError (25),
                routingFailure (26),

    --Values 27-50 are reserved for communications alarm related
    --probable causes
    -- The following are used with equipment alarm.

                backplaneFailure (51),
                dataSetProblem  (52),
                equipmentIdentifierDuplication  (53),
                externalIFDeviceProblem  (54),
                lineCardProblem (55),
                multiplexerProblem  (56),
                nEIdentifierDuplication  (57),
                powerProblem  (58),
                processorProblem  (59),
                protectionPathFailure  (60),
                receiverFailure  (61),
                replaceableUnitMissing  (62),
                replaceableUnitTypeMismatch (63),
                synchronizationSourceMismatch  (64),
                terminalProblem   (65),
                timingProblem   (66),
                transmitterFailure  (67),
                trunkCardProblem  (68),
                replaceableUnitProblem  (69),
                realTimeClockFailure (70),
    --An equipment alarm to be issued if the system detects that the
    --real time clock has failed
                antennaFailure (71),
                batteryChargingFailure (72),
                diskFailure (73),
                frequencyHoppingFailure (74),
                iODeviceError (75),
                lossOfSynchronisation (76),
                lossOfRedundancy (77),
                powerSupplyFailure (78),
                signalQualityEvaluationFailure (79),
                tranceiverFailure (80),
                protectionMechanismFailure (81),
                protectingResourceFailure (82),
    -- Values 83-100 are reserved for equipment alarm related probable
    -- causes
    -- The following are used with environmental alarm.
                airCompressorFailure  (101),
                airConditioningFailure  (102),
                airDryerFailure   (103),
                batteryDischarging  (104),
                batteryFailure   (105),
                commercialPowerFailure  (106),
                coolingFanFailure  (107),
                engineFailure  (108),
                fireDetectorFailure  (109),
                fuseFailure  (110),
                generatorFailure  (111),
                lowBatteryThreshold (112),
                pumpFailure  (113),
                rectifierFailure  (114),
                rectifierHighVoltage  (115),
                rectifierLowFVoltage  (116),
                ventilationsSystemFailure  (117),
                enclosureDoorOpen  (118),
                explosiveGas  (119),
                fire (120),
                flood   (121),
                highHumidity  (122),
                highTemperature  (123),
                highWind  (124),
                iceBuildUp  (125),
                intrusionDetection  (126),
                lowFuel  (127),
                lowHumidity  (128),
                lowCablePressure  (129),
                lowTemperatue  (130),
                lowWater  (131),
                smoke  (132),
                toxicGas  (133),
                coolingSystemFailure (134),
                externalEquipmentFailure (135),
                externalPointFailure (136),
    -- Values 137-150 are reserved for environmental alarm related
    -- probable causes
    -- The following are used with Processing error alarm.
                storageCapacityProblem (151),
                memoryMismatch  (152),
                corruptData  (153),
                outOfCPUCycles   (154),
                sfwrEnvironmentProblem  (155),
                sfwrDownloadFailure  (156),
                lossOfRealTimel (157),
    --A processing error alarm to be issued after the system has
    --reinitialised. This will indicate
    --to the management systems that the view they have of the managed
    --system may no longer
    --be valid. Usage example: The managed
    --system issues this alarm after a reinitialization with severity
    --warning to inform the
    --management system about the event. No clearing notification will
    --be sent.
                applicationSubsystemFailure (158),
                configurationOrCustomisationError (159),
                databaseInconsistency (160),
                fileError (161),
                outOfMemory (162),
                softwareError (163),
                timeoutExpired (164),
                underlayingResourceUnavailable (165),
                versionMismatch (166),
    --Values 168-200 are reserved for processing error alarm related
    -- probable causes.
                bandwidthReduced (201),
                congestion (202),
                excessiveErrorRate (203),
                excessiveResponseTime (204),
                excessiveRetransmissionRate (205),
                reducedLoggingCapability (206),
                systemResourcesOverload (207 ),
                -- The following were defined X.733
                adapterError (500),
                applicationSubsystemFailture (501),
                bandwidthReducedX733 (502),
                callEstablishmentError (503),
                communicationsProtocolError (504),
                communicationsSubsystemFailure (505),
                configurationOrCustomizationError (506),
                congestionX733 (507),
                coruptData (508),
                cpuCyclesLimitExceeded (509),
                dataSetOrModemError (510),
                degradedSignalX733 (511),
                dteDceInterfaceError (512),
                enclosureDoorOpenX733 (513),
                equipmentMalfunction (514),
                excessiveVibration (515),
                fileErrorX733 (516),
                fireDetected (517),
                framingErrorX733 (518),
                heatingVentCoolingSystemProblem (519),
                humidityUnacceptable (520),
                inputOutputDeviceError (521),
                inputDeviceError (522),
                lanError (523),
                leakDetected (524),
                localNodeTransmissionErrorX733 (525),
                lossOfFrameX733 (526),
                lossOfSignalX733 (527),
                materialSupplyExhausted (528),
                multiplexerProblemX733 (529),
                outOfMemoryX733 (530),
                ouputDeviceError (531),
                performanceDegraded (532),
                powerProblems (533),
                pressureUnacceptable (534),
                processorProblems (535),
                pumpFailureX733 (536),
                queueSizeExceeded (537),
                receiveFailureX733 (538),
                receiverFailureX733 (539),
                remoteNodeTransmissionErrorX733 (540),
                resourceAtOrNearingCapacity (541),
                responseTimeExecessive (542),
                retransmissionRateExcessive (543),
                softwareErrorX733 (544),
                softwareProgramAbnormallyTerminated (545),
                softwareProgramError (546),
                storageCapacityProblemX733 (547),
                temperatureUnacceptable (548),
                thresholdCrossed (549),
                timingProblemX733 (550),
                toxicLeakDetected (551),
                transmitFailureX733 (552),
                transmiterFailure (553),
                underlyingResourceUnavailable (554),
                versionMismatchX733 (555),
                -- The following are defined in X.736
                authenticationFailure (600),
                breachOfConfidentiality (601),
                cableTamper (602),
                delayedInformation (603),
                denialOfService (604),
                duplicateInformation (605),
                informationMissing (606),
                informationModificationDetected (607),
                informationOutOfSequence (608),
                keyExpired (609),
                nonRepudiationFailure (610),
                outOfHoursActivity (611),
                outOfService (612),
                proceduralError (613),
                unauthorizedAccessAttempt (614),
                unexpectedInformation (615),

                other (1024)
                }

   IANAItuEventType ::= TEXTUAL-CONVENTION
       STATUS current
       DESCRIPTION
               "The ITU event Type values.

               The Internet Assigned Number Authority (IANA) is
               responsible for the assignment of the enumerations
               in this TC.

               Request should  come in the form of well-formed
               SMI [RFC2578] for enumeration names that are unique
               and sufficiently descriptive.

               See http://www.iana.org "
       REFERENCE
              "ITU Recommendation X.736, 'Information Technology - Open
               Systems Interconnection - System Management: Security
               Alarm Reporting Function', 1992"
       SYNTAX         INTEGER
              {
              other (1),
              communicationsAlarm (2),
              qualityOfServiceAlarm (3),
              processingErrorAlarm (4),
              equipmentAlarm (5),
              environmentalAlarm (6),
              integrityViolation (7),
              operationalViolation (8),
              physicalViolation (9),
              securityServiceOrMechanismViolation (10),
              timeDomainViolation (11)
              }

   END

-- 
--   Copyright (C) The Internet Society (2004). All Rights Reserved.
-- 
--   This document and translations of it may be copied and furnished to
--   others, and derivative works that comment on or otherwise explain it
--   or assist in its implementation may be prepared, copied, published
--   and distributed, in whole or in part, without restriction of any kind,
--   provided that the above copyright notice and this paragraph are
--   included on all such copies and derivative works.  However, this
--   document itself may not be modified in any way, such as by removing
--   the copyright notice or references to the Internet Society or other
--   Internet organizations, except as needed for the  purpose of
--   developing Internet standards in which case the procedures for
--   copyrights defined in the Internet Standards process must be followed,
--   or as required to translate it into languages other than English.
-- 
--   The limited permissions granted above are perpetual and will not be
--   revoked by the Internet Society or its successors or assigns.
-- 
--   This document and the information contained herein is provided on an
--   "AS IS" basis and THE INTERNET SOCIETY AND THE INTERNET ENGINEERING
--   TASK FORCE DISCLAIMS ALL WARRANTIES, EXPRESS OR IMPLIED, INCLUDING BUT
--   NOT LIMITED TO ANY WARRANTY THAT THE USE OF THE INFORMATION HEREIN
--   WILL NOT INFRINGE ANY RIGHTS OR ANY IMPLIED WARRANTIES OF
--   MERCHANTABILITY OR FITNESS FOR A PARTICULAR PURPOSE.
