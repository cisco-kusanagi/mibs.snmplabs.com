-- *********************************************************************
-- CISCO-UNIFIED-COMPUTING-ETHER-MIB.my
-- 
-- MIB representation of the Cisco Unified Computing System
-- ETHER management information model package
-- 
-- Created January 2016 by Charles Bullis
-- 
-- Copyright (c) 2005-2016 Cisco Systems, Inc. All rights reserved.
-- 
-- *********************************************************************

CISCO-UNIFIED-COMPUTING-ETHER-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoUnifiedComputingMIBObjects,
    CucsManagedObjectId,
    CucsManagedObjectDn
        FROM CISCO-UNIFIED-COMPUTING-MIB
    CucsConditionRemoteInvRslt,
    CucsEquipmentChassisConfigState,
    CucsEquipmentXcvrType,
    CucsEtherCIoEpIfType,
    CucsEtherCloudType,
    CucsEtherErrStatsHistThresholded,
    CucsEtherErrStatsThresholded,
    CucsEtherExternalEpAdminState,
    CucsEtherExternalEpLocale,
    CucsEtherExternalPcAdminState,
    CucsEtherExternalPcLocale,
    CucsEtherFcoeInterfaceStatsHistThresholded,
    CucsEtherFcoeInterfaceStatsThresholded,
    CucsEtherIntFIoEpType,
    CucsEtherInternalPcLocale,
    CucsEtherLossStatsHistThresholded,
    CucsEtherLossStatsThresholded,
    CucsEtherNiErrStatsHistThresholded,
    CucsEtherNiErrStatsThresholded,
    CucsEtherPIoEpIfType,
    CucsEtherPIoFsmCurrentFsm,
    CucsEtherPIoFsmStageName,
    CucsEtherPauseStatsHistThresholded,
    CucsEtherPauseStatsThresholded,
    CucsEtherRxStatsHistThresholded,
    CucsEtherRxStatsThresholded,
    CucsEtherSatelliteConnectionDisc,
    CucsEtherServerIntFIoAdminState,
    CucsEtherServerIntFIoFsmCurrentFsm,
    CucsEtherServerIntFIoFsmStageName,
    CucsEtherServerIntFIoFsmTaskItem,
    CucsEtherServerIntFIoIfRole,
    CucsEtherServerIntFIoLocale,
    CucsEtherServerIntFIoPcEpIfRole,
    CucsEtherServerIntFIoPcEpPortId,
    CucsEtherServerIntFIoPcIfRole,
    CucsEtherServerIntFIoPcPortId,
    CucsEtherServerIntFIoPcTransport,
    CucsEtherServerIntFIoPcType,
    CucsEtherServerIntFIoTransport,
    CucsEtherServerIntFIoType,
    CucsEtherSwitchIntFIoAck,
    CucsEtherSwitchIntFIoIfRole,
    CucsEtherSwitchIntFIoLocale,
    CucsEtherSwitchIntFIoPcEpIfRole,
    CucsEtherSwitchIntFIoPcEpPortId,
    CucsEtherSwitchIntFIoPcIfRole,
    CucsEtherSwitchIntFIoPcMulticastHwHash,
    CucsEtherSwitchIntFIoPcPortId,
    CucsEtherSwitchIntFIoPcTransport,
    CucsEtherSwitchIntFIoPcType,
    CucsEtherSwitchIntFIoTransport,
    CucsEtherSwitchIntFIoType,
    CucsEtherTxStatsHistThresholded,
    CucsEtherTxStatsThresholded,
    CucsFabricAdminState,
    CucsFabricMembershipStatus,
    CucsFsmCompletion,
    CucsFsmFlags,
    CucsFsmFsmStageStatus,
    CucsFsmLifecycle,
    CucsLicenseState,
    CucsNetworkConnectionType,
    CucsNetworkLocale,
    CucsNetworkPhysEpIfType,
    CucsNetworkPortOperState,
    CucsNetworkPortRole,
    CucsNetworkSwitchId,
    CucsNetworkTransport,
    CucsPortEncap,
    CucsPortEthSpeed,
    CucsPortMode
        FROM CISCO-UNIFIED-COMPUTING-TC-MIB;

cucsEtherObjects MODULE-IDENTITY
    LAST-UPDATED    "201601180000Z"
    ORGANIZATION    "Cisco Systems Inc."
    CONTACT-INFO
        "Cisco Systems
        Customer Service
        
        Postal: 170 W Tasman Drive
        San Jose, CA  95134
        USA
        
        Tel: +1 800 553 -NETS
        
        E-mail: cs-san@cisco.com, cs-lan-switch-snmp@cisco.com"
    DESCRIPTION
        "MIB representation of the Cisco Unified Computing System
        ETHER management information model package"
    ::= { ciscoUnifiedComputingMIBObjects 16 }

cucsEtherErrStatsTable OBJECT-TYPE
    SYNTAX           SEQUENCE OF CucsEtherErrStatsEntry
    MAX-ACCESS       not-accessible
    STATUS           current
    DESCRIPTION
        "Cisco UCS ether:ErrStats managed object table"
    ::= { cucsEtherObjects 1 }

cucsEtherErrStatsEntry OBJECT-TYPE
    SYNTAX           CucsEtherErrStatsEntry
    MAX-ACCESS       not-accessible
    STATUS           current
    DESCRIPTION
        "Entry for the cucsEtherErrStatsTable table."
    INDEX { cucsEtherErrStatsInstanceId }
    ::= { cucsEtherErrStatsTable 1 }

CucsEtherErrStatsEntry ::= SEQUENCE {
    cucsEtherErrStatsInstanceId                                      CucsManagedObjectId,
    cucsEtherErrStatsDn                                              CucsManagedObjectDn,
    cucsEtherErrStatsRn                                              SnmpAdminString,
    cucsEtherErrStatsAlign                                           Unsigned64,
    cucsEtherErrStatsAlignDelta                                      Counter64,
    cucsEtherErrStatsAlignDeltaAvg                                   Unsigned64,
    cucsEtherErrStatsAlignDeltaMax                                   Unsigned64,
    cucsEtherErrStatsAlignDeltaMin                                   Unsigned64,
    cucsEtherErrStatsDeferredTx                                      Unsigned64,
    cucsEtherErrStatsDeferredTxDelta                                 Counter64,
    cucsEtherErrStatsDeferredTxDeltaAvg                              Unsigned64,
    cucsEtherErrStatsDeferredTxDeltaMax                              Unsigned64,
    cucsEtherErrStatsDeferredTxDeltaMin                              Unsigned64,
    cucsEtherErrStatsFcs                                             Unsigned64,
    cucsEtherErrStatsFcsDelta                                        Counter64,
    cucsEtherErrStatsFcsDeltaAvg                                     Unsigned64,
    cucsEtherErrStatsFcsDeltaMax                                     Unsigned64,
    cucsEtherErrStatsFcsDeltaMin                                     Unsigned64,
    cucsEtherErrStatsIntMacRx                                        Unsigned64,
    cucsEtherErrStatsIntMacRxDelta                                   Counter64,
    cucsEtherErrStatsIntMacRxDeltaAvg                                Unsigned64,
    cucsEtherErrStatsIntMacRxDeltaMax                                Unsigned64,
    cucsEtherErrStatsIntMacRxDeltaMin                                Unsigned64,
    cucsEtherErrStatsIntMacTx                                        Unsigned64,
    cucsEtherErrStatsIntMacTxDelta                                   Counter64,
    cucsEtherErrStatsIntMacTxDeltaAvg                                Unsigned64,
    cucsEtherErrStatsIntMacTxDeltaMax                                Unsigned64,
    cucsEtherErrStatsIntMacTxDeltaMin                                Unsigned64,
    cucsEtherErrStatsIntervals                                       Gauge32,
    cucsEtherErrStatsOutDiscard                                      Unsigned64,
    cucsEtherErrStatsOutDiscardDelta                                 Counter64,
    cucsEtherErrStatsOutDiscardDeltaAvg                              Unsigned64,
    cucsEtherErrStatsOutDiscardDeltaMax                              Unsigned64,
    cucsEtherErrStatsOutDiscardDeltaMin                              Unsigned64,
    cucsEtherErrStatsRcv                                             Unsigned64,
    cucsEtherErrStatsRcvDelta                                        Counter64,
    cucsEtherErrStatsRcvDeltaAvg                                     Unsigned64,
    cucsEtherErrStatsRcvDeltaMax                                     Unsigned64,
    cucsEtherErrStatsRcvDeltaMin                                     Unsigned64,
    cucsEtherErrStatsSuspect                                         TruthValue,
    cucsEtherErrStatsThresholded                                     CucsEtherErrStatsThresholded,
    cucsEtherErrStatsTimeCollected                                   DateAndTime,
    cucsEtherErrStatsUnderSize                                       Unsigned64,
    cucsEtherErrStatsUnderSizeDelta                                  Counter64,
    cucsEtherErrStatsUnderSizeDeltaAvg                               Unsigned64,
    cucsEtherErrStatsUnderSizeDeltaMax                               Unsigned64,
    cucsEtherErrStatsUnderSizeDeltaMin                               Unsigned64,
    cucsEtherErrStatsUpdate                                          Gauge32,
    cucsEtherErrStatsXmit                                            Unsigned64,
    cucsEtherErrStatsXmitDelta                                       Counter64,
    cucsEtherErrStatsXmitDeltaAvg                                    Unsigned64,
    cucsEtherErrStatsXmitDeltaMax                                    Unsigned64,
    cucsEtherErrStatsXmitDeltaMin                                    Unsigned64
}

cucsEtherErrStatsInstanceId OBJECT-TYPE
    SYNTAX       CucsManagedObjectId
    MAX-ACCESS   not-accessible
    STATUS       current
    DESCRIPTION
        "Instance identifier of the managed object."
    ::= { cucsEtherErrStatsEntry 1 }

cucsEtherErrStatsDn OBJECT-TYPE
    SYNTAX       CucsManagedObjectDn
    MAX-ACCESS   read-only
    STATUS       current
    DESCRIPTION
        "Cisco UCS ether:ErrStats:dn managed object property"
    ::= { cucsEtherErrStatsEntry 2 }

cucsEtherErrStatsRn OBJECT-TYPE
    SYNTAX       SnmpAdminString
    MAX-ACCESS   read-only
    STATUS       current
    DESCRIPTION
        "Cisco UCS ether:ErrStats:rn managed object property"
    ::= { cucsEtherErrStatsEntry 3 }

cucsEtherErrStatsAlign OBJECT-TYPE
    SYNTAX       Unsigned64
    MAX-ACCESS   read-only
    STATUS       current
    DESCRIPTION
        "Cisco UCS ether:ErrStats:align managed object property"
    ::= { cucsEtherErrStatsEntry 4 }

cucsEtherErrStatsAlignDelta OBJECT-TYPE
    SYNTAX       Counter64
    MAX-ACCESS   read-only
    STATUS       current
    DESCRIPTION
        "Cisco UCS ether:ErrStats:alignDelta managed object property"
    ::= { cucsEtherErrStatsEntry 5 }

cucsEtherErrStatsAlignDeltaAvg OBJECT-TYPE
    SYNTAX       Unsigned64
    MAX-ACCESS   read-only
    STATUS       current
    DESCRIPTION
        "Cisco UCS ether:ErrStats:alignDeltaAvg managed object property"
    ::= { cucsEtherErrStatsEntry 6 }

cucsEtherErrStatsAlignDeltaMax OBJECT-TYPE
    SYNTAX       Unsigned64
    MAX-ACCESS   read-only
    STATUS       current
    DESCRIPTION
        "Cisco UCS ether:ErrStats:alignDeltaMax managed object property"
    ::= { cucsEtherErrStatsEntry 7 }

cucsEtherErrStatsAlignDeltaMin OBJECT-TYPE
    SYNTAX       Unsigned64
    MAX-ACCESS   read-only
    STATUS       current
    DESCRIPTION
        "Cisco UCS ether:ErrStats:alignDeltaMin managed object property"
    ::= { cucsEtherErrStatsEntry 8 }

cucsEtherErrStatsDeferredTx OBJECT-TYPE
    SYNTAX       Unsigned64
    MAX-ACCESS   read-only
    STATUS       current
    DESCRIPTION
        "Cisco UCS ether:ErrStats:deferredTx managed object property"
    ::= { cucsEtherErrStatsEntry 9 }

cucsEtherErrStatsDeferredTxDelta OBJECT-TYPE
    SYNTAX       Counter64
    MAX-ACCESS   read-only
    STATUS       current
    DESCRIPTION
        "Cisco UCS ether:ErrStats:deferredTxDelta managed object property"
    ::= { cucsEtherErrStatsEntry 10 }

cucsEtherErrStatsDeferredTxDeltaAvg OBJECT-TYPE
    SYNTAX       Unsigned64
    MAX-ACCESS   read-only
    STATUS       current
    DESCRIPTION
        "Cisco UCS ether:ErrStats:deferredTxDeltaAvg managed
        object property"
    ::= { cucsEtherErrStatsEntry 11 }

cucsEtherErrStatsDeferredTxDeltaMax OBJECT-TYPE
    SYNTAX       Unsigned64
    MAX-ACCESS   read-only
    STATUS       current
    DESCRIPTION
        "Cisco UCS ether:ErrStats:deferredTxDeltaMax managed
        object property"
    ::= { cucsEtherErrStatsEntry 12 }

cucsEtherErrStatsDeferredTxDeltaMin OBJECT-TYPE
    SYNTAX       Unsigned64
    MAX-ACCESS   read-only
    STATUS       current
    DESCRIPTION
        "Cisco UCS ether:ErrStats:deferredTxDeltaMin managed
        object property"
    ::= { cucsEtherErrStatsEntry 13 }

cucsEtherErrStatsFcs OBJECT-TYPE
    SYNTAX       Unsigned64
    MAX-ACCESS   read-only
    STATUS       current
    DESCRIPTION
        "Cisco UCS ether:ErrStats:fcs managed object property"
    ::= { cucsEtherErrStatsEntry 14 }

cucsEtherErrStatsFcsDelta OBJECT-TYPE
    SYNTAX       Counter64
    MAX-ACCESS   read-only
    STATUS       current
    DESCRIPTION
        "Cisco UCS ether:ErrStats:fcsDelta managed object property"
    ::= { cucsEtherErrStatsEntry 15 }

cucsEtherErrStatsFcsDeltaAvg OBJECT-TYPE
    SYNTAX       Unsigned64
    MAX-ACCESS   read-only
    STATUS       current
    DESCRIPTION
        "Cisco UCS ether:ErrStats:fcsDeltaAvg managed object property"
    ::= { cucsEtherErrStatsEntry 16 }

cucsEtherErrStatsFcsDeltaMax OBJECT-TYPE
    SYNTAX       Unsigned64
    MAX-ACCESS   read-only
    STATUS       current
    DESCRIPTION
        "Cisco UCS ether:ErrStats:fcsDeltaMax managed object property"
    ::= { cucsEtherErrStatsEntry 17 }

cucsEtherErrStatsFcsDeltaMin OBJECT-TYPE
    SYNTAX       Unsigned64
    MAX-ACCESS   read-only
    STATUS       current
    DESCRIPTION
        "Cisco UCS ether:ErrStats:fcsDeltaMin managed object property"
    ::= { cucsEtherErrStatsEntry 18 }

cucsEtherErrStatsIntMacRx OBJECT-TYPE
    SYNTAX       Unsigned64
    MAX-ACCESS   read-only
    STATUS       current
    DESCRIPTION
        "Cisco UCS ether:ErrStats:intMacRx managed object property"
    ::= { cucsEtherErrStatsEntry 19 }

cucsEtherErrStatsIntMacRxDelta OBJECT-TYPE
    SYNTAX       Counter64
    MAX-ACCESS   read-only
    STATUS       current
    DESCRIPTION
        "Cisco UCS ether:ErrStats:intMacRxDelta managed object property"
    ::= { cucsEtherErrStatsEntry 20 }

cucsEtherErrStatsIntMacRxDeltaAvg OBJECT-TYPE
    SYNTAX       Unsigned64
    MAX-ACCESS   read-only
    STATUS       current
    DESCRIPTION
        "Cisco UCS ether:ErrStats:intMacRxDeltaAvg managed
        object property"
    ::= { cucsEtherErrStatsEntry 21 }

cucsEtherErrStatsIntMacRxDeltaMax OBJECT-TYPE
    SYNTAX       Unsigned64
    MAX-ACCESS   read-only
    STATUS       current
    DESCRIPTION
        "Cisco UCS ether:ErrStats:intMacRxDeltaMax managed
        object property"
    ::= { cucsEtherErrStatsEntry 22 }

cucsEtherErrStatsIntMacRxDeltaMin OBJECT-TYPE
    SYNTAX       Unsigned64
    MAX-ACCESS   read-only
    STATUS       current
    DESCRIPTION
        "Cisco UCS ether:ErrStats:intMacRxDeltaMin managed
        object property"
    ::= { cucsEtherErrStatsEntry 23 }

cucsEtherErrStatsIntMacTx OBJECT-TYPE
    SYNTAX       Unsigned64
    MAX-ACCESS   read-only
    STATUS       current
    DESCRIPTION
        "Cisco UCS ether:ErrStats:intMacTx managed object property"
    ::= { cucsEtherErrStatsEntry 24 }

cucsEtherErrStatsIntMacTxDelta OBJECT-TYPE
    SYNTAX       Counter64
    MAX-ACCESS   read-only
    STATUS       current
    DESCRIPTION
        "Cisco UCS ether:ErrStats:intMacTxDelta managed object property"
    ::= { cucsEtherErrStatsEntry 25 }

cucsEtherErrStatsIntMacTxDeltaAvg OBJECT-TYPE
    SYNTAX       Unsigned64
    MAX-ACCESS   read-only
    STATUS       current
    DESCRIPTION
        "Cisco UCS ether:ErrStats:intMacTxDeltaAvg managed
        object property"
    ::= { cucsEtherErrStatsEntry 26 }

cucsEtherErrStatsIntMacTxDeltaMax OBJECT-TYPE
    SYNTAX       Unsigned64
    MAX-ACCESS   read-only
    STATUS       current
    DESCRIPTION
        "Cisco UCS ether:ErrStats:intMacTxDeltaMax managed
        object property"
    ::= { cucsEtherErrStatsEntry 27 }

cucsEtherErrStatsIntMacTxDeltaMin OBJECT-TYPE
    SYNTAX       Unsigned64
    MAX-ACCESS   read-only
    STATUS       current
    DESCRIPTION
        "Cisco UCS ether:ErrStats:intMacTxDeltaMin managed
        object property"
    ::= { cucsEtherErrStatsEntry 28 }

cucsEtherErrStatsIntervals OBJECT-TYPE
    SYNTAX       Gauge32
    MAX-ACCESS   read-only
    STATUS       current
    DESCRIPTION
        "Cisco UCS ether:ErrStats:intervals managed object property"
    ::= { cucsEtherErrStatsEntry 29 }

cucsEtherErrStatsOutDiscard OBJECT-TYPE
    SYNTAX       Unsigned64
    MAX-ACCESS   read-only
    STATUS       current
    DESCRIPTION
        "Cisco UCS ether:ErrStats:outDiscard managed object property"
    ::= { cucsEtherErrStatsEntry 30 }

cucsEtherErrStatsOutDiscardDelta OBJECT-TYPE
    SYNTAX       Counter64
    MAX-ACCESS   read-only
    STATUS       current
    DESCRIPTION
        "Cisco UCS ether:ErrStats:outDiscardDelta managed object property"
    ::= { cucsEtherErrStatsEntry 31 }

cucsEtherErrStatsOutDiscardDeltaAvg OBJECT-TYPE
    SYNTAX       Unsigned64
    MAX-ACCESS   read-only
    STATUS       current
    DESCRIPTION
        "Cisco UCS ether:ErrStats:outDiscardDeltaAvg managed
        object property"
    ::= { cucsEtherErrStatsEntry 32 }

cucsEtherErrStatsOutDiscardDeltaMax OBJECT-TYPE
    SYNTAX       Unsigned64
    MAX-ACCESS   read-only
    STATUS       current
    DESCRIPTION
        "Cisco UCS ether:ErrStats:outDiscardDeltaMax managed
        object property"
    ::= { cucsEtherErrStatsEntry 33 }

cucsEtherErrStatsOutDiscardDeltaMin OBJECT-TYPE
    SYNTAX       Unsigned64
    MAX-ACCESS   read-only
    STATUS       current
    DESCRIPTION
        "Cisco UCS ether:ErrStats:outDiscardDeltaMin managed
        object property"
    ::= { cucsEtherErrStatsEntry 34 }

cucsEtherErrStatsRcv OBJECT-TYPE
    SYNTAX       Unsigned64
    MAX-ACCESS   read-only
    STATUS       current
    DESCRIPTION
        "Cisco UCS ether:ErrStats:rcv managed object property"
    ::= { cucsEtherErrStatsEntry 35 }

cucsEtherErrStatsRcvDelta OBJECT-TYPE
    SYNTAX       Counter64
    MAX-ACCESS   read-only
    STATUS       current
    DESCRIPTION
        "Cisco UCS ether:ErrStats:rcvDelta managed object property"
    ::= { cucsEtherErrStatsEntry 36 }

cucsEtherErrStatsRcvDeltaAvg OBJECT-TYPE
    SYNTAX       Unsigned64
    MAX-ACCESS   read-only
    STATUS       current
    DESCRIPTION
        "Cisco UCS ether:ErrStats:rcvDeltaAvg managed object property"
    ::= { cucsEtherErrStatsEntry 37 }

cucsEtherErrStatsRcvDeltaMax OBJECT-TYPE
    SYNTAX       Unsigned64
    MAX-ACCESS   read-only
    STATUS       current
    DESCRIPTION
        "Cisco UCS ether:ErrStats:rcvDeltaMax managed object property"
    ::= { cucsEtherErrStatsEntry 38 }

cucsEtherErrStatsRcvDeltaMin OBJECT-TYPE
    SYNTAX       Unsigned64
    MAX-ACCESS   read-only
    STATUS       current
    DESCRIPTION
        "Cisco UCS ether:ErrStats:rcvDeltaMin managed object property"
    ::= { cucsEtherErrStatsEntry 39 }

cucsEtherErrStatsSuspect OBJECT-TYPE
    SYNTAX       TruthValue
    MAX-ACCESS   read-only
    STATUS       current
    DESCRIPTION
        "Cisco UCS ether:ErrStats:suspect managed object property"
    ::= { cucsEtherErrStatsEntry 40 }

cucsEtherErrStatsThresholded OBJECT-TYPE
    SYNTAX       CucsEtherErrStatsThresholded
    MAX-ACCESS   read-only
    STATUS       current
    DESCRIPTION
        "Cisco UCS ether:ErrStats:thresholded managed object property"
    ::= { cucsEtherErrStatsEntry 41 }

cucsEtherErrStatsTimeCollected OBJECT-TYPE
    SYNTAX       DateAndTime
    MAX-ACCESS   read-only
    STATUS       current
    DESCRIPTION
        "Cisco UCS ether:ErrStats:timeCollected managed object property"
    ::= { cucsEtherErrStatsEntry 42 }

cucsEtherErrStatsUnderSize OBJECT-TYPE
    SYNTAX       Unsigned64
    MAX-ACCESS   read-only
    STATUS       current
    DESCRIPTION
        "Cisco UCS ether:ErrStats:underSize managed object property"
    ::= { cucsEtherErrStatsEntry 43 }

cucsEtherErrStatsUnderSizeDelta OBJECT-TYPE
    SYNTAX       Counter64
    MAX-ACCESS   read-only
    STATUS       current
    DESCRIPTION
        "Cisco UCS ether:ErrStats:underSizeDelta managed object property"
    ::= { cucsEtherErrStatsEntry 44 }

cucsEtherErrStatsUnderSizeDeltaAvg OBJECT-TYPE
    SYNTAX       Unsigned64
    MAX-ACCESS   read-only
    STATUS       current
    DESCRIPTION
        "Cisco UCS ether:ErrStats:underSizeDeltaAvg managed
        object property"
    ::= { cucsEtherErrStatsEntry 45 }

cucsEtherErrStatsUnderSizeDeltaMax OBJECT-TYPE
    SYNTAX       Unsigned64
    MAX-ACCESS   read-only
    STATUS       current
    DESCRIPTION
        "Cisco UCS ether:ErrStats:underSizeDeltaMax managed
        object property"
    ::= { cucsEtherErrStatsEntry 46 }

cucsEtherErrStatsUnderSizeDeltaMin OBJECT-TYPE
    SYNTAX       Unsigned64
    MAX-ACCESS   read-only
    STATUS       current
    DESCRIPTION
        "Cisco UCS ether:ErrStats:underSizeDeltaMin managed
        object property"
    ::= { cucsEtherErrStatsEntry 47 }

cucsEtherErrStatsUpdate OBJECT-TYPE
    SYNTAX       Gauge32
    MAX-ACCESS   read-only
    STATUS       current
    DESCRIPTION
        "Cisco UCS ether:ErrStats:update managed object property"
    ::= { cucsEtherErrStatsEntry 48 }

cucsEtherErrStatsXmit OBJECT-TYPE
    SYNTAX       Unsigned64
    MAX-ACCESS   read-only
    STATUS       current
    DESCRIPTION
        "Cisco UCS ether:ErrStats:xmit managed object property"
    ::= { cucsEtherErrStatsEntry 49 }

cucsEtherErrStatsXmitDelta OBJECT-TYPE
    SYNTAX       Counter64
    MAX-ACCESS   read-only
    STATUS       current
    DESCRIPTION
        "Cisco UCS ether:ErrStats:xmitDelta managed object property"
    ::= { cucsEtherErrStatsEntry 50 }

cucsEtherErrStatsXmitDeltaAvg OBJECT-TYPE
    SYNTAX       Unsigned64
    MAX-ACCESS   read-only
    STATUS       current
    DESCRIPTION
        "Cisco UCS ether:ErrStats:xmitDeltaAvg managed object property"
    ::= { cucsEtherErrStatsEntry 51 }

cucsEtherErrStatsXmitDeltaMax OBJECT-TYPE
    SYNTAX       Unsigned64
    MAX-ACCESS   read-only
    STATUS       current
    DESCRIPTION
        "Cisco UCS ether:ErrStats:xmitDeltaMax managed object property"
    ::= { cucsEtherErrStatsEntry 52 }

cucsEtherErrStatsXmitDeltaMin OBJECT-TYPE
    SYNTAX       Unsigned64
    MAX-ACCESS   read-only
    STATUS       current
    DESCRIPTION
        "Cisco UCS ether:ErrStats:xmitDeltaMin managed object property"
    ::= { cucsEtherErrStatsEntry 53 }

cucsEtherErrStatsHistTable OBJECT-TYPE
    SYNTAX           SEQUENCE OF CucsEtherErrStatsHistEntry
    MAX-ACCESS       not-accessible
    STATUS           current
    DESCRIPTION
        "Cisco UCS ether:ErrStatsHist managed object table"
    ::= { cucsEtherObjects 2 }

cucsEtherErrStatsHistEntry OBJECT-TYPE
    SYNTAX           CucsEtherErrStatsHistEntry
    MAX-ACCESS       not-accessible
    STATUS           current
    DESCRIPTION
        "Entry for the cucsEtherErrStatsHistTable table."
    INDEX { cucsEtherErrStatsHistInstanceId }
    ::= { cucsEtherErrStatsHistTable 1 }

CucsEtherErrStatsHistEntry ::= SEQUENCE {
    cucsEtherErrStatsHistInstanceId                                  CucsManagedObjectId,
    cucsEtherErrStatsHistDn                                          CucsManagedObjectDn,
    cucsEtherErrStatsHistRn                                          SnmpAdminString,
    cucsEtherErrStatsHistAlign                                       Unsigned64,
    cucsEtherErrStatsHistAlignDelta                                  Unsigned64,
    cucsEtherErrStatsHistAlignDeltaAvg                               Unsigned64,
    cucsEtherErrStatsHistAlignDeltaMax                               Unsigned64,
    cucsEtherErrStatsHistAlignDeltaMin                               Unsigned64,
    cucsEtherErrStatsHistDeferredTx                                  Unsigned64,
    cucsEtherErrStatsHistDeferredTxDelta                             Unsigned64,
    cucsEtherErrStatsHistDeferredTxDeltaAvg                          Unsigned64,
    cucsEtherErrStatsHistDeferredTxDeltaMax                          Unsigned64,
    cucsEtherErrStatsHistDeferredTxDeltaMin                          Unsigned64,
    cucsEtherErrStatsHistFcs                                         Unsigned64,
    cucsEtherErrStatsHistFcsDelta                                    Unsigned64,
    cucsEtherErrStatsHistFcsDeltaAvg                                 Unsigned64,
    cucsEtherErrStatsHistFcsDeltaMax                                 Unsigned64,
    cucsEtherErrStatsHistFcsDeltaMin                                 Unsigned64,
    cucsEtherErrStatsHistId                                          Unsigned64,
    cucsEtherErrStatsHistIntMacRx                                    Unsigned64,
    cucsEtherErrStatsHistIntMacRxDelta                               Unsigned64,
    cucsEtherErrStatsHistIntMacRxDeltaAvg                            Unsigned64,
    cucsEtherErrStatsHistIntMacRxDeltaMax                            Unsigned64,
    cucsEtherErrStatsHistIntMacRxDeltaMin                            Unsigned64,
    cucsEtherErrStatsHistIntMacTx                                    Unsigned64,
    cucsEtherErrStatsHistIntMacTxDelta                               Unsigned64,
    cucsEtherErrStatsHistIntMacTxDeltaAvg                            Unsigned64,
    cucsEtherErrStatsHistIntMacTxDeltaMax                            Unsigned64,
    cucsEtherErrStatsHistIntMacTxDeltaMin                            Unsigned64,
    cucsEtherErrStatsHistMostRecent                                  TruthValue,
    cucsEtherErrStatsHistOutDiscard                                  Unsigned64,
    cucsEtherErrStatsHistOutDiscardDelta                             Unsigned64,
    cucsEtherErrStatsHistOutDiscardDeltaAvg                          Unsigned64,
    cucsEtherErrStatsHistOutDiscardDeltaMax                          Unsigned64,
    cucsEtherErrStatsHistOutDiscardDeltaMin                          Unsigned64,
    cucsEtherErrStatsHistRcv                                         Unsigned64,
    cucsEtherErrStatsHistRcvDelta                                    Unsigned64,
    cucsEtherErrStatsHistRcvDeltaAvg                                 Unsigned64,
    cucsEtherErrStatsHistRcvDeltaMax                                 Unsigned64,
    cucsEtherErrStatsHistRcvDeltaMin                                 Unsigned64,
    cucsEtherErrStatsHistSuspect                                     TruthValue,
    cucsEtherErrStatsHistThresholded                                 CucsEtherErrStatsHistThresholded,
    cucsEtherErrStatsHistTimeCollected                               DateAndTime,
    cucsEtherErrStatsHistUnderSize                                   Unsigned64,
    cucsEtherErrStatsHistUnderSizeDelta                              Unsigned64,
    cucsEtherErrStatsHistUnderSizeDeltaAvg                           Unsigned64,
    cucsEtherErrStatsHistUnderSizeDeltaMax                           Unsigned64,
    cucsEtherErrStatsHistUnderSizeDeltaMin                           Unsigned64,
    cucsEtherErrStatsHistXmit                                        Unsigned64,
    cucsEtherErrStatsHistXmitDelta                                   Unsigned64,
    cucsEtherErrStatsHistXmitDeltaAvg                                Unsigned64,
    cucsEtherErrStatsHistXmitDeltaMax                                Unsigned64,
    cucsEtherErrStatsHistXmitDeltaMin                                Unsigned64
}

cucsEtherErrStatsHistInstanceId OBJECT-TYPE
    SYNTAX       CucsManagedObjectId
    MAX-ACCESS   not-accessible
    STATUS       current
    DESCRIPTION
        "Instance identifier of the managed object."
    ::= { cucsEtherErrStatsHistEntry 1 }

cucsEtherErrStatsHistDn OBJECT-TYPE
    SYNTAX       CucsManagedObjectDn
    MAX-ACCESS   read-only
    STATUS       current
    DESCRIPTION
        "Cisco UCS ether:ErrStatsHist:dn managed object property"
    ::= { cucsEtherErrStatsHistEntry 2 }

cucsEtherErrStatsHistRn OBJECT-TYPE
    SYNTAX       SnmpAdminString
    MAX-ACCESS   read-only
    STATUS       current
    DESCRIPTION
        "Cisco UCS ether:ErrStatsHist:rn managed object property"
    ::= { cucsEtherErrStatsHistEntry 3 }

cucsEtherErrStatsHistAlign OBJECT-TYPE
    SYNTAX       Unsigned64
    MAX-ACCESS   read-only
    STATUS       current
    DESCRIPTION
        "Cisco UCS ether:ErrStatsHist:align managed object property"
    ::= { cucsEtherErrStatsHistEntry 4 }

cucsEtherErrStatsHistAlignDelta OBJECT-TYPE
    SYNTAX       Unsigned64
    MAX-ACCESS   read-only
    STATUS       current
    DESCRIPTION
        "Cisco UCS ether:ErrStatsHist:alignDelta managed object property"
    ::= { cucsEtherErrStatsHistEntry 5 }

cucsEtherErrStatsHistAlignDeltaAvg OBJECT-TYPE
    SYNTAX       Unsigned64
    MAX-ACCESS   read-only
    STATUS       current
    DESCRIPTION
        "Cisco UCS ether:ErrStatsHist:alignDeltaAvg managed
        object property"
    ::= { cucsEtherErrStatsHistEntry 6 }

cucsEtherErrStatsHistAlignDeltaMax OBJECT-TYPE
    SYNTAX       Unsigned64
    MAX-ACCESS   read-only
    STATUS       current
    DESCRIPTION
        "Cisco UCS ether:ErrStatsHist:alignDeltaMax managed
        object property"
    ::= { cucsEtherErrStatsHistEntry 7 }

cucsEtherErrStatsHistAlignDeltaMin OBJECT-TYPE
    SYNTAX       Unsigned64
    MAX-ACCESS   read-only
    STATUS       current
    DESCRIPTION
        "Cisco UCS ether:ErrStatsHist:alignDeltaMin managed
        object property"
    ::= { cucsEtherErrStatsHistEntry 8 }

cucsEtherErrStatsHistDeferredTx OBJECT-TYPE
    SYNTAX       Unsigned64
    MAX-ACCESS   read-only
    STATUS       current
    DESCRIPTION
        "Cisco UCS ether:ErrStatsHist:deferredTx managed object property"
    ::= { cucsEtherErrStatsHistEntry 9 }

cucsEtherErrStatsHistDeferredTxDelta OBJECT-TYPE
    SYNTAX       Unsigned64
    MAX-ACCESS   read-only
    STATUS       current
    DESCRIPTION
        "Cisco UCS ether:ErrStatsHist:deferredTxDelta managed
        object property"
    ::= { cucsEtherErrStatsHistEntry 10 }

cucsEtherErrStatsHistDeferredTxDeltaAvg OBJECT-TYPE
    SYNTAX       Unsigned64
    MAX-ACCESS   read-only
    STATUS       current
    DESCRIPTION
        "Cisco UCS ether:ErrStatsHist:deferredTxDeltaAvg
        managed object property"
    ::= { cucsEtherErrStatsHistEntry 11 }

cucsEtherErrStatsHistDeferredTxDeltaMax OBJECT-TYPE
    SYNTAX       Unsigned64
    MAX-ACCESS   read-only
    STATUS       current
    DESCRIPTION
        "Cisco UCS ether:ErrStatsHist:deferredTxDeltaMax
        managed object property"
    ::= { cucsEtherErrStatsHistEntry 12 }

cucsEtherErrStatsHistDeferredTxDeltaMin OBJECT-TYPE
    SYNTAX       Unsigned64
    MAX-ACCESS   read-only
    STATUS       current
    DESCRIPTION
        "Cisco UCS ether:ErrStatsHist:deferredTxDeltaMin
        managed object property"
    ::= { cucsEtherErrStatsHistEntry 13 }

cucsEtherErrStatsHistFcs OBJECT-TYPE
    SYNTAX       Unsigned64
    MAX-ACCESS   read-only
    STATUS       current
    DESCRIPTION
        "Cisco UCS ether:ErrStatsHist:fcs managed object property"
    ::= { cucsEtherErrStatsHistEntry 14 }

cucsEtherErrStatsHistFcsDelta OBJECT-TYPE
    SYNTAX       Unsigned64
    MAX-ACCESS   read-only
    STATUS       current
    DESCRIPTION
        "Cisco UCS ether:ErrStatsHist:fcsDelta managed object property"
    ::= { cucsEtherErrStatsHistEntry 15 }

cucsEtherErrStatsHistFcsDeltaAvg OBJECT-TYPE
    SYNTAX       Unsigned64
    MAX-ACCESS   read-only
    STATUS       current
    DESCRIPTION
        "Cisco UCS ether:ErrStatsHist:fcsDeltaAvg managed object property"
    ::= { cucsEtherErrStatsHistEntry 16 }

cucsEtherErrStatsHistFcsDeltaMax OBJECT-TYPE
    SYNTAX       Unsigned64
    MAX-ACCESS   read-only
    STATUS       current
    DESCRIPTION
        "Cisco UCS ether:ErrStatsHist:fcsDeltaMax managed object property"
    ::= { cucsEtherErrStatsHistEntry 17 }

cucsEtherErrStatsHistFcsDeltaMin OBJECT-TYPE
    SYNTAX       Unsigned64
    MAX-ACCESS   read-only
    STATUS       current
    DESCRIPTION
        "Cisco UCS ether:ErrStatsHist:fcsDeltaMin managed object property"
    ::= { cucsEtherErrStatsHistEntry 18 }

cucsEtherErrStatsHistId OBJECT-TYPE
    SYNTAX       Unsigned64
    MAX-ACCESS   read-only
    STATUS       current
    DESCRIPTION
        "Cisco UCS ether:ErrStatsHist:id managed object property"
    ::= { cucsEtherErrStatsHistEntry 19 }

cucsEtherErrStatsHistIntMacRx OBJECT-TYPE
    SYNTAX       Unsigned64
    MAX-ACCESS   read-only
    STATUS       current
    DESCRIPTION
        "Cisco UCS ether:ErrStatsHist:intMacRx managed object property"
    ::= { cucsEtherErrStatsHistEntry 20 }

cucsEtherErrStatsHistIntMacRxDelta OBJECT-TYPE
    SYNTAX       Unsigned64
    MAX-ACCESS   read-only
    STATUS       current
    DESCRIPTION
        "Cisco UCS ether:ErrStatsHist:intMacRxDelta managed
        object property"
    ::= { cucsEtherErrStatsHistEntry 21 }

cucsEtherErrStatsHistIntMacRxDeltaAvg OBJECT-TYPE
    SYNTAX       Unsigned64
    MAX-ACCESS   read-only
    STATUS       current
    DESCRIPTION
        "Cisco UCS ether:ErrStatsHist:intMacRxDeltaAvg
        managed object property"
    ::= { cucsEtherErrStatsHistEntry 22 }

cucsEtherErrStatsHistIntMacRxDeltaMax OBJECT-TYPE
    SYNTAX       Unsigned64
    MAX-ACCESS   read-only
    STATUS       current
    DESCRIPTION
        "Cisco UCS ether:ErrStatsHist:intMacRxDeltaMax
        managed object property"
    ::= { cucsEtherErrStatsHistEntry 23 }

cucsEtherErrStatsHistIntMacRxDeltaMin OBJECT-TYPE
    SYNTAX       Unsigned64
    MAX-ACCESS   read-only
    STATUS       current
    DESCRIPTION
        "Cisco UCS ether:ErrStatsHist:intMacRxDeltaMin
        managed object property"
    ::= { cucsEtherErrStatsHistEntry 24 }

cucsEtherErrStatsHistIntMacTx OBJECT-TYPE
    SYNTAX       Unsigned64
    MAX-ACCESS   read-only
    STATUS       current
    DESCRIPTION
        "Cisco UCS ether:ErrStatsHist:intMacTx managed object property"
    ::= { cucsEtherErrStatsHistEntry 25 }

cucsEtherErrStatsHistIntMacTxDelta OBJECT-TYPE
    SYNTAX       Unsigned64
    MAX-ACCESS   read-only
    STATUS       current
    DESCRIPTION
        "Cisco UCS ether:ErrStatsHist:intMacTxDelta managed
        object property"
    ::= { cucsEtherErrStatsHistEntry 26 }

cucsEtherErrStatsHistIntMacTxDeltaAvg OBJECT-TYPE
    SYNTAX       Unsigned64
    MAX-ACCESS   read-only
    STATUS       current
    DESCRIPTION
        "Cisco UCS ether:ErrStatsHist:intMacTxDeltaAvg
        managed object property"
    ::= { cucsEtherErrStatsHistEntry 27 }

cucsEtherErrStatsHistIntMacTxDeltaMax OBJECT-TYPE
    SYNTAX       Unsigned64
    MAX-ACCESS   read-only
    STATUS       current
    DESCRIPTION
        "Cisco UCS ether:ErrStatsHist:intMacTxDeltaMax
        managed object property"
    ::= { cucsEtherErrStatsHistEntry 28 }

cucsEtherErrStatsHistIntMacTxDeltaMin OBJECT-TYPE
    SYNTAX       Unsigned64
    MAX-ACCESS   read-only
    STATUS       current
    DESCRIPTION
        "Cisco UCS ether:ErrStatsHist:intMacTxDeltaMin
        managed object property"
    ::= { cucsEtherErrStatsHistEntry 29 }

cucsEtherErrStatsHistMostRecent OBJECT-TYPE
    SYNTAX       TruthValue
    MAX-ACCESS   read-only
    STATUS       current
    DESCRIPTION
        "Cisco UCS ether:ErrStatsHist:mostRecent managed object property"
    ::= { cucsEtherErrStatsHistEntry 30 }

cucsEtherErrStatsHistOutDiscard OBJECT-TYPE
    SYNTAX       Unsigned64
    MAX-ACCESS   read-only
    STATUS       current
    DESCRIPTION
        "Cisco UCS ether:ErrStatsHist:outDiscard managed object property"
    ::= { cucsEtherErrStatsHistEntry 31 }

cucsEtherErrStatsHistOutDiscardDelta OBJECT-TYPE
    SYNTAX       Unsigned64
    MAX-ACCESS   read-only
    STATUS       current
    DESCRIPTION
        "Cisco UCS ether:ErrStatsHist:outDiscardDelta managed
        object property"
    ::= { cucsEtherErrStatsHistEntry 32 }

cucsEtherErrStatsHistOutDiscardDeltaAvg OBJECT-TYPE
    SYNTAX       Unsigned64
    MAX-ACCESS   read-only
    STATUS       current
    DESCRIPTION
        "Cisco UCS ether:ErrStatsHist:outDiscardDeltaAvg
        managed object property"
    ::= { cucsEtherErrStatsHistEntry 33 }

cucsEtherErrStatsHistOutDiscardDeltaMax OBJECT-TYPE
    SYNTAX       Unsigned64
    MAX-ACCESS   read-only
    STATUS       current
    DESCRIPTION
        "Cisco UCS ether:ErrStatsHist:outDiscardDeltaMax
        managed object property"
    ::= { cucsEtherErrStatsHistEntry 34 }

cucsEtherErrStatsHistOutDiscardDeltaMin OBJECT-TYPE
    SYNTAX       Unsigned64
    MAX-ACCESS   read-only
    STATUS       current
    DESCRIPTION
        "Cisco UCS ether:ErrStatsHist:outDiscardDeltaMin
        managed object property"
    ::= { cucsEtherErrStatsHistEntry 35 }

cucsEtherErrStatsHistRcv OBJECT-TYPE
    SYNTAX       Unsigned64
    MAX-ACCESS   read-only
    STATUS       current
    DESCRIPTION
        "Cisco UCS ether:ErrStatsHist:rcv managed object property"
    ::= { cucsEtherErrStatsHistEntry 36 }

cucsEtherErrStatsHistRcvDelta OBJECT-TYPE
    SYNTAX       Unsigned64
    MAX-ACCESS   read-only
    STATUS       current
    DESCRIPTION
        "Cisco UCS ether:ErrStatsHist:rcvDelta managed object property"
    ::= { cucsEtherErrStatsHistEntry 37 }

cucsEtherErrStatsHistRcvDeltaAvg OBJECT-TYPE
    SYNTAX       Unsigned64
    MAX-ACCESS   read-only
    STATUS       current
    DESCRIPTION
        "Cisco UCS ether:ErrStatsHist:rcvDeltaAvg managed object property"
    ::= { cucsEtherErrStatsHistEntry 38 }

cucsEtherErrStatsHistRcvDeltaMax OBJECT-TYPE
    SYNTAX       Unsigned64
    MAX-ACCESS   read-only
    STATUS       current
    DESCRIPTION
        "Cisco UCS ether:ErrStatsHist:rcvDeltaMax managed object property"
    ::= { cucsEtherErrStatsHistEntry 39 }

cucsEtherErrStatsHistRcvDeltaMin OBJECT-TYPE
    SYNTAX       Unsigned64
    MAX-ACCESS   read-only
    STATUS       current
    DESCRIPTION
        "Cisco UCS ether:ErrStatsHist:rcvDeltaMin managed object property"
    ::= { cucsEtherErrStatsHistEntry 40 }

cucsEtherErrStatsHistSuspect OBJECT-TYPE
    SYNTAX       TruthValue
    MAX-ACCESS   read-only
    STATUS       current
    DESCRIPTION
        "Cisco UCS ether:ErrStatsHist:suspect managed object property"
    ::= { cucsEtherErrStatsHistEntry 41 }

cucsEtherErrStatsHistThresholded OBJECT-TYPE
    SYNTAX       CucsEtherErrStatsHistThresholded
    MAX-ACCESS   read-only
    STATUS       current
    DESCRIPTION
        "Cisco UCS ether:ErrStatsHist:thresholded managed object property"
    ::= { cucsEtherErrStatsHistEntry 42 }

cucsEtherErrStatsHistTimeCollected OBJECT-TYPE
    SYNTAX       DateAndTime
    MAX-ACCESS   read-only
    STATUS       current
    DESCRIPTION
        "Cisco UCS ether:ErrStatsHist:timeCollected managed
        object property"
    ::= { cucsEtherErrStatsHistEntry 43 }

cucsEtherErrStatsHistUnderSize OBJECT-TYPE
    SYNTAX       Unsigned64
    MAX-ACCESS   read-only
    STATUS       current
    DESCRIPTION
        "Cisco UCS ether:ErrStatsHist:underSize managed object property"
    ::= { cucsEtherErrStatsHistEntry 44 }

cucsEtherErrStatsHistUnderSizeDelta OBJECT-TYPE
    SYNTAX       Unsigned64
    MAX-ACCESS   read-only
    STATUS       current
    DESCRIPTION
        "Cisco UCS ether:ErrStatsHist:underSizeDelta managed
        object property"
    ::= { cucsEtherErrStatsHistEntry 45 }

cucsEtherErrStatsHistUnderSizeDeltaAvg OBJECT-TYPE
    SYNTAX       Unsigned64
    MAX-ACCESS   read-only
    STATUS       current
    DESCRIPTION
        "Cisco UCS ether:ErrStatsHist:underSizeDeltaAvg
        managed object property"
    ::= { cucsEtherErrStatsHistEntry 46 }

cucsEtherErrStatsHistUnderSizeDeltaMax OBJECT-TYPE
    SYNTAX       Unsigned64
    MAX-ACCESS   read-only
    STATUS       current
    DESCRIPTION
        "Cisco UCS ether:ErrStatsHist:underSizeDeltaMax
        managed object property"
    ::= { cucsEtherErrStatsHistEntry 47 }

cucsEtherErrStatsHistUnderSizeDeltaMin OBJECT-TYPE
    SYNTAX       Unsigned64
    MAX-ACCESS   read-only
    STATUS       current
    DESCRIPTION
        "Cisco UCS ether:ErrStatsHist:underSizeDeltaMin
        managed object property"
    ::= { cucsEtherErrStatsHistEntry 48 }

cucsEtherErrStatsHistXmit OBJECT-TYPE
    SYNTAX       Unsigned64
    MAX-ACCESS   read-only
    STATUS       current
    DESCRIPTION
        "Cisco UCS ether:ErrStatsHist:xmit managed object property"
    ::= { cucsEtherErrStatsHistEntry 49 }

cucsEtherErrStatsHistXmitDelta OBJECT-TYPE
    SYNTAX       Unsigned64
    MAX-ACCESS   read-only
    STATUS       current
    DESCRIPTION
        "Cisco UCS ether:ErrStatsHist:xmitDelta managed object property"
    ::= { cucsEtherErrStatsHistEntry 50 }

cucsEtherErrStatsHistXmitDeltaAvg OBJECT-TYPE
    SYNTAX       Unsigned64
    MAX-ACCESS   read-only
    STATUS       current
    DESCRIPTION
        "Cisco UCS ether:ErrStatsHist:xmitDeltaAvg managed
        object property"
    ::= { cucsEtherErrStatsHistEntry 51 }

cucsEtherErrStatsHistXmitDeltaMax OBJECT-TYPE
    SYNTAX       Unsigned64
    MAX-ACCESS   read-only
    STATUS       current
    DESCRIPTION
        "Cisco UCS ether:ErrStatsHist:xmitDeltaMax managed
        object property"
    ::= { cucsEtherErrStatsHistEntry 52 }

cucsEtherErrStatsHistXmitDeltaMin OBJECT-TYPE
    SYNTAX       Unsigned64
    MAX-ACCESS   read-only
    STATUS       current
    DESCRIPTION
        "Cisco UCS ether:ErrStatsHist:xmitDeltaMin managed
        object property"
    ::= { cucsEtherErrStatsHistEntry 53 }

cucsEtherFcoeInterfaceStatsTable OBJECT-TYPE
    SYNTAX           SEQUENCE OF CucsEtherFcoeInterfaceStatsEntry
    MAX-ACCESS       not-accessible
    STATUS           current
    DESCRIPTION
        "Cisco UCS ether:FcoeInterfaceStats managed object table"
    ::= { cucsEtherObjects 23 }

cucsEtherFcoeInterfaceStatsEntry OBJECT-TYPE
    SYNTAX           CucsEtherFcoeInterfaceStatsEntry
    MAX-ACCESS       not-accessible
    STATUS           current
    DESCRIPTION
        "Entry for the cucsEtherFcoeInterfaceStatsTable table."
    INDEX { cucsEtherFcoeInterfaceStatsInstanceId }
    ::= { cucsEtherFcoeInterfaceStatsTable 1 }

CucsEtherFcoeInterfaceStatsEntry ::= SEQUENCE {
    cucsEtherFcoeInterfaceStatsInstanceId                            CucsManagedObjectId,
    cucsEtherFcoeInterfaceStatsDn                                    CucsManagedObjectDn,
    cucsEtherFcoeInterfaceStatsRn                                    SnmpAdminString,
    cucsEtherFcoeInterfaceStatsBytesRx                               Unsigned64,
    cucsEtherFcoeInterfaceStatsBytesRxDelta                          Counter64,
    cucsEtherFcoeInterfaceStatsBytesRxDeltaAvg                       Unsigned64,
    cucsEtherFcoeInterfaceStatsBytesRxDeltaMax                       Unsigned64,
    cucsEtherFcoeInterfaceStatsBytesRxDeltaMin                       Unsigned64,
    cucsEtherFcoeInterfaceStatsBytesTx                               Unsigned64,
    cucsEtherFcoeInterfaceStatsBytesTxDelta                          Counter64,
    cucsEtherFcoeInterfaceStatsBytesTxDeltaAvg                       Unsigned64,
    cucsEtherFcoeInterfaceStatsBytesTxDeltaMax                       Unsigned64,
    cucsEtherFcoeInterfaceStatsBytesTxDeltaMin                       Unsigned64,
    cucsEtherFcoeInterfaceStatsDroppedRx                             Unsigned64,
    cucsEtherFcoeInterfaceStatsDroppedRxDelta                        Counter64,
    cucsEtherFcoeInterfaceStatsDroppedRxDeltaAvg                     Unsigned64,
    cucsEtherFcoeInterfaceStatsDroppedRxDeltaMax                     Unsigned64,
    cucsEtherFcoeInterfaceStatsDroppedRxDeltaMin                     Unsigned64,
    cucsEtherFcoeInterfaceStatsDroppedTx                             Unsigned64,
    cucsEtherFcoeInterfaceStatsDroppedTxDelta                        Counter64,
    cucsEtherFcoeInterfaceStatsDroppedTxDeltaAvg                     Unsigned64,
    cucsEtherFcoeInterfaceStatsDroppedTxDeltaMax                     Unsigned64,
    cucsEtherFcoeInterfaceStatsDroppedTxDeltaMin                     Unsigned64,
    cucsEtherFcoeInterfaceStatsErrorsRx                              Unsigned64,
    cucsEtherFcoeInterfaceStatsErrorsRxDelta                         Counter64,
    cucsEtherFcoeInterfaceStatsErrorsRxDeltaAvg                      Unsigned64,
    cucsEtherFcoeInterfaceStatsErrorsRxDeltaMax                      Unsigned64,
    cucsEtherFcoeInterfaceStatsErrorsRxDeltaMin                      Unsigned64,
    cucsEtherFcoeInterfaceStatsErrorsTx                              Unsigned64,
    cucsEtherFcoeInterfaceStatsErrorsTxDelta                         Counter64,
    cucsEtherFcoeInterfaceStatsErrorsTxDeltaAvg                      Unsigned64,
    cucsEtherFcoeInterfaceStatsErrorsTxDeltaMax                      Unsigned64,
    cucsEtherFcoeInterfaceStatsErrorsTxDeltaMin                      Unsigned64,
    cucsEtherFcoeInterfaceStatsIntervals                             Gauge32,
    cucsEtherFcoeInterfaceStatsPacketsRx                             Unsigned64,
    cucsEtherFcoeInterfaceStatsPacketsRxDelta                        Counter64,
    cucsEtherFcoeInterfaceStatsPacketsRxDeltaAvg                     Unsigned64,
    cucsEtherFcoeInterfaceStatsPacketsRxDeltaMax                     Unsigned64,
    cucsEtherFcoeInterfaceStatsPacketsRxDeltaMin                     Unsigned64,
    cucsEtherFcoeInterfaceStatsPacketsTx                             Unsigned64,
    cucsEtherFcoeInterfaceStatsPacketsTxDelta                        Counter64,
    cucsEtherFcoeInterfaceStatsPacketsTxDeltaAvg                     Unsigned64,
    cucsEtherFcoeInterfaceStatsPacketsTxDeltaMax                     Unsigned64,
    cucsEtherFcoeInterfaceStatsPacketsTxDeltaMin                     Unsigned64,
    cucsEtherFcoeInterfaceStatsSuspect                               TruthValue,
    cucsEtherFcoeInterfaceStatsThresholded                           CucsEtherFcoeInterfaceStatsThresholded,
    cucsEtherFcoeInterfaceStatsTimeCollected                         DateAndTime,
    cucsEtherFcoeInterfaceStatsUpdate                                Gauge32
}

cucsEtherFcoeInterfaceStatsInstanceId OBJECT-TYPE
    SYNTAX       CucsManagedObjectId
    MAX-ACCESS   not-accessible
    STATUS       current
    DESCRIPTION
        "Instance identifier of the managed object."
    ::= { cucsEtherFcoeInterfaceStatsEntry 1 }

cucsEtherFcoeInterfaceStatsDn OBJECT-TYPE
    SYNTAX       CucsManagedObjectDn
    MAX-ACCESS   read-only
    STATUS       current
    DESCRIPTION
        "Cisco UCS ether:FcoeInterfaceStats:dn managed object property"
    ::= { cucsEtherFcoeInterfaceStatsEntry 2 }

cucsEtherFcoeInterfaceStatsRn OBJECT-TYPE
    SYNTAX       SnmpAdminString
    MAX-ACCESS   read-only
    STATUS       current
    DESCRIPTION
        "Cisco UCS ether:FcoeInterfaceStats:rn managed object property"
    ::= { cucsEtherFcoeInterfaceStatsEntry 3 }

cucsEtherFcoeInterfaceStatsBytesRx OBJECT-TYPE
    SYNTAX       Unsigned64
    MAX-ACCESS   read-only
    STATUS       current
    DESCRIPTION
        "Cisco UCS ether:FcoeInterfaceStats:bytesRx managed
        object property"
    ::= { cucsEtherFcoeInterfaceStatsEntry 4 }

cucsEtherFcoeInterfaceStatsBytesRxDelta OBJECT-TYPE
    SYNTAX       Counter64
    MAX-ACCESS   read-only
    STATUS       current
    DESCRIPTION
        "Cisco UCS ether:FcoeInterfaceStats:bytesRxDelta
        managed object property"
    ::= { cucsEtherFcoeInterfaceStatsEntry 5 }

cucsEtherFcoeInterfaceStatsBytesRxDeltaAvg OBJECT-TYPE
    SYNTAX       Unsigned64
    MAX-ACCESS   read-only
    STATUS       current
    DESCRIPTION
        "Cisco UCS ether:FcoeInterfaceStats:bytesRxDeltaAvg
        managed object property"
    ::= { cucsEtherFcoeInterfaceStatsEntry 6 }

cucsEtherFcoeInterfaceStatsBytesRxDeltaMax OBJECT-TYPE
    SYNTAX       Unsigned64
    MAX-ACCESS   read-only
    STATUS       current
    DESCRIPTION
        "Cisco UCS ether:FcoeInterfaceStats:bytesRxDeltaMax
        managed object property"
    ::= { cucsEtherFcoeInterfaceStatsEntry 7 }

cucsEtherFcoeInterfaceStatsBytesRxDeltaMin OBJECT-TYPE
    SYNTAX       Unsigned64
    MAX-ACCESS   read-only
    STATUS       current
    DESCRIPTION
        "Cisco UCS ether:FcoeInterfaceStats:bytesRxDeltaMin
        managed object property"
    ::= { cucsEtherFcoeInterfaceStatsEntry 8 }

cucsEtherFcoeInterfaceStatsBytesTx OBJECT-TYPE
    SYNTAX       Unsigned64
    MAX-ACCESS   read-only
    STATUS       current
    DESCRIPTION
        "Cisco UCS ether:FcoeInterfaceStats:bytesTx managed
        object property"
    ::= { cucsEtherFcoeInterfaceStatsEntry 9 }

cucsEtherFcoeInterfaceStatsBytesTxDelta OBJECT-TYPE
    SYNTAX       Counter64
    MAX-ACCESS   read-only
    STATUS       current
    DESCRIPTION
        "Cisco UCS ether:FcoeInterfaceStats:bytesTxDelta
        managed object property"
    ::= { cucsEtherFcoeInterfaceStatsEntry 10 }

cucsEtherFcoeInterfaceStatsBytesTxDeltaAvg OBJECT-TYPE
    SYNTAX       Unsigned64
    MAX-ACCESS   read-only
    STATUS       current
    DESCRIPTION
        "Cisco UCS ether:FcoeInterfaceStats:bytesTxDeltaAvg
        managed object property"
    ::= { cucsEtherFcoeInterfaceStatsEntry 11 }

cucsEtherFcoeInterfaceStatsBytesTxDeltaMax OBJECT-TYPE
    SYNTAX       Unsigned64
    MAX-ACCESS   read-only
    STATUS       current
    DESCRIPTION
        "Cisco UCS ether:FcoeInterfaceStats:bytesTxDeltaMax
        managed object property"
    ::= { cucsEtherFcoeInterfaceStatsEntry 12 }

cucsEtherFcoeInterfaceStatsBytesTxDeltaMin OBJECT-TYPE
    SYNTAX       Unsigned64
    MAX-ACCESS   read-only
    STATUS       current
    DESCRIPTION
        "Cisco UCS ether:FcoeInterfaceStats:bytesTxDeltaMin
        managed object property"
    ::= { cucsEtherFcoeInterfaceStatsEntry 13 }

cucsEtherFcoeInterfaceStatsDroppedRx OBJECT-TYPE
    SYNTAX       Unsigned64
    MAX-ACCESS   read-only
    STATUS       current
    DESCRIPTION
        "Cisco UCS ether:FcoeInterfaceStats:droppedRx managed
        object property"
    ::= { cucsEtherFcoeInterfaceStatsEntry 14 }

cucsEtherFcoeInterfaceStatsDroppedRxDelta OBJECT-TYPE
    SYNTAX       Counter64
    MAX-ACCESS   read-only
    STATUS       current
    DESCRIPTION
        "Cisco UCS ether:FcoeInterfaceStats:droppedRxDelta
        managed object property"
    ::= { cucsEtherFcoeInterfaceStatsEntry 15 }

cucsEtherFcoeInterfaceStatsDroppedRxDeltaAvg OBJECT-TYPE
    SYNTAX       Unsigned64
    MAX-ACCESS   read-only
    STATUS       current
    DESCRIPTION
        "Cisco UCS ether:FcoeInterfaceStats:droppedRxDeltaAvg
        managed object property"
    ::= { cucsEtherFcoeInterfaceStatsEntry 16 }

cucsEtherFcoeInterfaceStatsDroppedRxDeltaMax OBJECT-TYPE
    SYNTAX       Unsigned64
    MAX-ACCESS   read-only
    STATUS       current
    DESCRIPTION
        "Cisco UCS ether:FcoeInterfaceStats:droppedRxDeltaMax
        managed object property"
    ::= { cucsEtherFcoeInterfaceStatsEntry 17 }

cucsEtherFcoeInterfaceStatsDroppedRxDeltaMin OBJECT-TYPE
    SYNTAX       Unsigned64
    MAX-ACCESS   read-only
    STATUS       current
    DESCRIPTION
        "Cisco UCS ether:FcoeInterfaceStats:droppedRxDeltaMin
        managed object property"
    ::= { cucsEtherFcoeInterfaceStatsEntry 18 }

cucsEtherFcoeInterfaceStatsDroppedTx OBJECT-TYPE
    SYNTAX       Unsigned64
    MAX-ACCESS   read-only
    STATUS       current
    DESCRIPTION
        "Cisco UCS ether:FcoeInterfaceStats:droppedTx managed
        object property"
    ::= { cucsEtherFcoeInterfaceStatsEntry 19 }

cucsEtherFcoeInterfaceStatsDroppedTxDelta OBJECT-TYPE
    SYNTAX       Counter64
    MAX-ACCESS   read-only
    STATUS       current
    DESCRIPTION
        "Cisco UCS ether:FcoeInterfaceStats:droppedTxDelta
        managed object property"
    ::= { cucsEtherFcoeInterfaceStatsEntry 20 }

cucsEtherFcoeInterfaceStatsDroppedTxDeltaAvg OBJECT-TYPE
    SYNTAX       Unsigned64
    MAX-ACCESS   read-only
    STATUS       current
    DESCRIPTION
        "Cisco UCS ether:FcoeInterfaceStats:droppedTxDeltaAvg
        managed object property"
    ::= { cucsEtherFcoeInterfaceStatsEntry 21 }

cucsEtherFcoeInterfaceStatsDroppedTxDeltaMax OBJECT-TYPE
    SYNTAX       Unsigned64
    MAX-ACCESS   read-only
    STATUS       current
    DESCRIPTION
        "Cisco UCS ether:FcoeInterfaceStats:droppedTxDeltaMax
        managed object property"
    ::= { cucsEtherFcoeInterfaceStatsEntry 22 }

cucsEtherFcoeInterfaceStatsDroppedTxDeltaMin OBJECT-TYPE
    SYNTAX       Unsigned64
    MAX-ACCESS   read-only
    STATUS       current
    DESCRIPTION
        "Cisco UCS ether:FcoeInterfaceStats:droppedTxDeltaMin
        managed object property"
    ::= { cucsEtherFcoeInterfaceStatsEntry 23 }

cucsEtherFcoeInterfaceStatsErrorsRx OBJECT-TYPE
    SYNTAX       Unsigned64
    MAX-ACCESS   read-only
    STATUS       current
    DESCRIPTION
        "Cisco UCS ether:FcoeInterfaceStats:errorsRx managed
        object property"
    ::= { cucsEtherFcoeInterfaceStatsEntry 24 }

cucsEtherFcoeInterfaceStatsErrorsRxDelta OBJECT-TYPE
    SYNTAX       Counter64
    MAX-ACCESS   read-only
    STATUS       current
    DESCRIPTION
        "Cisco UCS ether:FcoeInterfaceStats:errorsRxDelta
        managed object property"
    ::= { cucsEtherFcoeInterfaceStatsEntry 25 }

cucsEtherFcoeInterfaceStatsErrorsRxDeltaAvg OBJECT-TYPE
    SYNTAX       Unsigned64
    MAX-ACCESS   read-only
    STATUS       current
    DESCRIPTION
        "Cisco UCS ether:FcoeInterfaceStats:errorsRxDeltaAvg
        managed object property"
    ::= { cucsEtherFcoeInterfaceStatsEntry 26 }

cucsEtherFcoeInterfaceStatsErrorsRxDeltaMax OBJECT-TYPE
    SYNTAX       Unsigned64
    MAX-ACCESS   read-only
    STATUS       current
    DESCRIPTION
        "Cisco UCS ether:FcoeInterfaceStats:errorsRxDeltaMax
        managed object property"
    ::= { cucsEtherFcoeInterfaceStatsEntry 27 }

cucsEtherFcoeInterfaceStatsErrorsRxDeltaMin OBJECT-TYPE
    SYNTAX       Unsigned64
    MAX-ACCESS   read-only
    STATUS       current
    DESCRIPTION
        "Cisco UCS ether:FcoeInterfaceStats:errorsRxDeltaMin
        managed object property"
    ::= { cucsEtherFcoeInterfaceStatsEntry 28 }

cucsEtherFcoeInterfaceStatsErrorsTx OBJECT-TYPE
    SYNTAX       Unsigned64
    MAX-ACCESS   read-only
    STATUS       current
    DESCRIPTION
        "Cisco UCS ether:FcoeInterfaceStats:errorsTx managed
        object property"
    ::= { cucsEtherFcoeInterfaceStatsEntry 29 }

cucsEtherFcoeInterfaceStatsErrorsTxDelta OBJECT-TYPE
    SYNTAX       Counter64
    MAX-ACCESS   read-only
    STATUS       current
    DESCRIPTION
        "Cisco UCS ether:FcoeInterfaceStats:errorsTxDelta
        managed object property"
    ::= { cucsEtherFcoeInterfaceStatsEntry 30 }

cucsEtherFcoeInterfaceStatsErrorsTxDeltaAvg OBJECT-TYPE
    SYNTAX       Unsigned64
    MAX-ACCESS   read-only
    STATUS       current
    DESCRIPTION
        "Cisco UCS ether:FcoeInterfaceStats:errorsTxDeltaAvg
        managed object property"
    ::= { cucsEtherFcoeInterfaceStatsEntry 31 }

cucsEtherFcoeInterfaceStatsErrorsTxDeltaMax OBJECT-TYPE
    SYNTAX       Unsigned64
    MAX-ACCESS   read-only
    STATUS       current
    DESCRIPTION
        "Cisco UCS ether:FcoeInterfaceStats:errorsTxDeltaMax
        managed object property"
    ::= { cucsEtherFcoeInterfaceStatsEntry 32 }

cucsEtherFcoeInterfaceStatsErrorsTxDeltaMin OBJECT-TYPE
    SYNTAX       Unsigned64
    MAX-ACCESS   read-only
    STATUS       current
    DESCRIPTION
        "Cisco UCS ether:FcoeInterfaceStats:errorsTxDeltaMin
        managed object property"
    ::= { cucsEtherFcoeInterfaceStatsEntry 33 }

cucsEtherFcoeInterfaceStatsIntervals OBJECT-TYPE
    SYNTAX       Gauge32
    MAX-ACCESS   read-only
    STATUS       current
    DESCRIPTION
        "Cisco UCS ether:FcoeInterfaceStats:intervals managed
        object property"
    ::= { cucsEtherFcoeInterfaceStatsEntry 34 }

cucsEtherFcoeInterfaceStatsPacketsRx OBJECT-TYPE
    SYNTAX       Unsigned64
    MAX-ACCESS   read-only
    STATUS       current
    DESCRIPTION
        "Cisco UCS ether:FcoeInterfaceStats:packetsRx managed
        object property"
    ::= { cucsEtherFcoeInterfaceStatsEntry 35 }

cucsEtherFcoeInterfaceStatsPacketsRxDelta OBJECT-TYPE
    SYNTAX       Counter64
    MAX-ACCESS   read-only
    STATUS       current
    DESCRIPTION
        "Cisco UCS ether:FcoeInterfaceStats:packetsRxDelta
        managed object property"
    ::= { cucsEtherFcoeInterfaceStatsEntry 36 }

cucsEtherFcoeInterfaceStatsPacketsRxDeltaAvg OBJECT-TYPE
    SYNTAX       Unsigned64
    MAX-ACCESS   read-only
    STATUS       current
    DESCRIPTION
        "Cisco UCS ether:FcoeInterfaceStats:packetsRxDeltaAvg
        managed object property"
    ::= { cucsEtherFcoeInterfaceStatsEntry 37 }

cucsEtherFcoeInterfaceStatsPacketsRxDeltaMax OBJECT-TYPE
    SYNTAX       Unsigned64
    MAX-ACCESS   read-only
    STATUS       current
    DESCRIPTION
        "Cisco UCS ether:FcoeInterfaceStats:packetsRxDeltaMax
        managed object property"
    ::= { cucsEtherFcoeInterfaceStatsEntry 38 }

cucsEtherFcoeInterfaceStatsPacketsRxDeltaMin OBJECT-TYPE
    SYNTAX       Unsigned64
    MAX-ACCESS   read-only
    STATUS       current
    DESCRIPTION
        "Cisco UCS ether:FcoeInterfaceStats:packetsRxDeltaMin
        managed object property"
    ::= { cucsEtherFcoeInterfaceStatsEntry 39 }

cucsEtherFcoeInterfaceStatsPacketsTx OBJECT-TYPE
    SYNTAX       Unsigned64
    MAX-ACCESS   read-only
    STATUS       current
    DESCRIPTION
        "Cisco UCS ether:FcoeInterfaceStats:packetsTx managed
        object property"
    ::= { cucsEtherFcoeInterfaceStatsEntry 40 }

cucsEtherFcoeInterfaceStatsPacketsTxDelta OBJECT-TYPE
    SYNTAX       Counter64
    MAX-ACCESS   read-only
    STATUS       current
    DESCRIPTION
        "Cisco UCS ether:FcoeInterfaceStats:packetsTxDelta
        managed object property"
    ::= { cucsEtherFcoeInterfaceStatsEntry 41 }

cucsEtherFcoeInterfaceStatsPacketsTxDeltaAvg OBJECT-TYPE
    SYNTAX       Unsigned64
    MAX-ACCESS   read-only
    STATUS       current
    DESCRIPTION
        "Cisco UCS ether:FcoeInterfaceStats:packetsTxDeltaAvg
        managed object property"
    ::= { cucsEtherFcoeInterfaceStatsEntry 42 }

cucsEtherFcoeInterfaceStatsPacketsTxDeltaMax OBJECT-TYPE
    SYNTAX       Unsigned64
    MAX-ACCESS   read-only
    STATUS       current
    DESCRIPTION
        "Cisco UCS ether:FcoeInterfaceStats:packetsTxDeltaMax
        managed object property"
    ::= { cucsEtherFcoeInterfaceStatsEntry 43 }

cucsEtherFcoeInterfaceStatsPacketsTxDeltaMin OBJECT-TYPE
    SYNTAX       Unsigned64
    MAX-ACCESS   read-only
    STATUS       current
    DESCRIPTION
        "Cisco UCS ether:FcoeInterfaceStats:packetsTxDeltaMin
        managed object property"
    ::= { cucsEtherFcoeInterfaceStatsEntry 44 }

cucsEtherFcoeInterfaceStatsSuspect OBJECT-TYPE
    SYNTAX       TruthValue
    MAX-ACCESS   read-only
    STATUS       current
    DESCRIPTION
        "Cisco UCS ether:FcoeInterfaceStats:suspect managed
        object property"
    ::= { cucsEtherFcoeInterfaceStatsEntry 45 }

cucsEtherFcoeInterfaceStatsThresholded OBJECT-TYPE
    SYNTAX       CucsEtherFcoeInterfaceStatsThresholded
    MAX-ACCESS   read-only
    STATUS       current
    DESCRIPTION
        "Cisco UCS ether:FcoeInterfaceStats:thresholded
        managed object property"
    ::= { cucsEtherFcoeInterfaceStatsEntry 46 }

cucsEtherFcoeInterfaceStatsTimeCollected OBJECT-TYPE
    SYNTAX       DateAndTime
    MAX-ACCESS   read-only
    STATUS       current
    DESCRIPTION
        "Cisco UCS ether:FcoeInterfaceStats:timeCollected
        managed object property"
    ::= { cucsEtherFcoeInterfaceStatsEntry 47 }

cucsEtherFcoeInterfaceStatsUpdate OBJECT-TYPE
    SYNTAX       Gauge32
    MAX-ACCESS   read-only
    STATUS       current
    DESCRIPTION
        "Cisco UCS ether:FcoeInterfaceStats:update managed
        object property"
    ::= { cucsEtherFcoeInterfaceStatsEntry 48 }

cucsEtherFcoeInterfaceStatsHistTable OBJECT-TYPE
    SYNTAX           SEQUENCE OF CucsEtherFcoeInterfaceStatsHistEntry
    MAX-ACCESS       not-accessible
    STATUS           current
    DESCRIPTION
        "Cisco UCS ether:FcoeInterfaceStatsHist managed object table"
    ::= { cucsEtherObjects 24 }

cucsEtherFcoeInterfaceStatsHistEntry OBJECT-TYPE
    SYNTAX           CucsEtherFcoeInterfaceStatsHistEntry
    MAX-ACCESS       not-accessible
    STATUS           current
    DESCRIPTION
        "Entry for the cucsEtherFcoeInterfaceStatsHistTable table."
    INDEX { cucsEtherFcoeInterfaceStatsHistInstanceId }
    ::= { cucsEtherFcoeInterfaceStatsHistTable 1 }

CucsEtherFcoeInterfaceStatsHistEntry ::= SEQUENCE {
    cucsEtherFcoeInterfaceStatsHistInstanceId                        CucsManagedObjectId,
    cucsEtherFcoeInterfaceStatsHistDn                                CucsManagedObjectDn,
    cucsEtherFcoeInterfaceStatsHistRn                                SnmpAdminString,
    cucsEtherFcoeInterfaceStatsHistBytesRx                           Unsigned64,
    cucsEtherFcoeInterfaceStatsHistBytesRxDelta                      Unsigned64,
    cucsEtherFcoeInterfaceStatsHistBytesRxDeltaAvg                   Unsigned64,
    cucsEtherFcoeInterfaceStatsHistBytesRxDeltaMax                   Unsigned64,
    cucsEtherFcoeInterfaceStatsHistBytesRxDeltaMin                   Unsigned64,
    cucsEtherFcoeInterfaceStatsHistBytesTx                           Unsigned64,
    cucsEtherFcoeInterfaceStatsHistBytesTxDelta                      Unsigned64,
    cucsEtherFcoeInterfaceStatsHistBytesTxDeltaAvg                   Unsigned64,
    cucsEtherFcoeInterfaceStatsHistBytesTxDeltaMax                   Unsigned64,
    cucsEtherFcoeInterfaceStatsHistBytesTxDeltaMin                   Unsigned64,
    cucsEtherFcoeInterfaceStatsHistDroppedRx                         Unsigned64,
    cucsEtherFcoeInterfaceStatsHistDroppedRxDelta                    Unsigned64,
    cucsEtherFcoeInterfaceStatsHistDroppedRxDeltaAvg                 Unsigned64,
    cucsEtherFcoeInterfaceStatsHistDroppedRxDeltaMax                 Unsigned64,
    cucsEtherFcoeInterfaceStatsHistDroppedRxDeltaMin                 Unsigned64,
    cucsEtherFcoeInterfaceStatsHistDroppedTx                         Unsigned64,
    cucsEtherFcoeInterfaceStatsHistDroppedTxDelta                    Unsigned64,
    cucsEtherFcoeInterfaceStatsHistDroppedTxDeltaAvg                 Unsigned64,
    cucsEtherFcoeInterfaceStatsHistDroppedTxDeltaMax                 Unsigned64,
    cucsEtherFcoeInterfaceStatsHistDroppedTxDeltaMin                 Unsigned64,
    cucsEtherFcoeInterfaceStatsHistErrorsRx                          Unsigned64,
    cucsEtherFcoeInterfaceStatsHistErrorsRxDelta                     Unsigned64,
    cucsEtherFcoeInterfaceStatsHistErrorsRxDeltaAvg                  Unsigned64,
    cucsEtherFcoeInterfaceStatsHistErrorsRxDeltaMax                  Unsigned64,
    cucsEtherFcoeInterfaceStatsHistErrorsRxDeltaMin                  Unsigned64,
    cucsEtherFcoeInterfaceStatsHistErrorsTx                          Unsigned64,
    cucsEtherFcoeInterfaceStatsHistErrorsTxDelta                     Unsigned64,
    cucsEtherFcoeInterfaceStatsHistErrorsTxDeltaAvg                  Unsigned64,
    cucsEtherFcoeInterfaceStatsHistErrorsTxDeltaMax                  Unsigned64,
    cucsEtherFcoeInterfaceStatsHistErrorsTxDeltaMin                  Unsigned64,
    cucsEtherFcoeInterfaceStatsHistId                                Unsigned64,
    cucsEtherFcoeInterfaceStatsHistMostRecent                        TruthValue,
    cucsEtherFcoeInterfaceStatsHistPacketsRx                         Unsigned64,
    cucsEtherFcoeInterfaceStatsHistPacketsRxDelta                    Unsigned64,
    cucsEtherFcoeInterfaceStatsHistPacketsRxDeltaAvg                 Unsigned64,
    cucsEtherFcoeInterfaceStatsHistPacketsRxDeltaMax                 Unsigned64,
    cucsEtherFcoeInterfaceStatsHistPacketsRxDeltaMin                 Unsigned64,
    cucsEtherFcoeInterfaceStatsHistPacketsTx                         Unsigned64,
    cucsEtherFcoeInterfaceStatsHistPacketsTxDelta                    Unsigned64,
    cucsEtherFcoeInterfaceStatsHistPacketsTxDeltaAvg                 Unsigned64,
    cucsEtherFcoeInterfaceStatsHistPacketsTxDeltaMax                 Unsigned64,
    cucsEtherFcoeInterfaceStatsHistPacketsTxDeltaMin                 Unsigned64,
    cucsEtherFcoeInterfaceStatsHistSuspect                           TruthValue,
    cucsEtherFcoeInterfaceStatsHistThresholded                       CucsEtherFcoeInterfaceStatsHistThresholded,
    cucsEtherFcoeInterfaceStatsHistTimeCollected                     DateAndTime
}

cucsEtherFcoeInterfaceStatsHistInstanceId OBJECT-TYPE
    SYNTAX       CucsManagedObjectId
    MAX-ACCESS   not-accessible
    STATUS       current
    DESCRIPTION
        "Instance identifier of the managed object."
    ::= { cucsEtherFcoeInterfaceStatsHistEntry 1 }

cucsEtherFcoeInterfaceStatsHistDn OBJECT-TYPE
    SYNTAX       CucsManagedObjectDn
    MAX-ACCESS   read-only
    STATUS       current
    DESCRIPTION
        "Cisco UCS ether:FcoeInterfaceStatsHist:dn managed
        object property"
    ::= { cucsEtherFcoeInterfaceStatsHistEntry 2 }

cucsEtherFcoeInterfaceStatsHistRn OBJECT-TYPE
    SYNTAX       SnmpAdminString
    MAX-ACCESS   read-only
    STATUS       current
    DESCRIPTION
        "Cisco UCS ether:FcoeInterfaceStatsHist:rn managed
        object property"
    ::= { cucsEtherFcoeInterfaceStatsHistEntry 3 }

cucsEtherFcoeInterfaceStatsHistBytesRx OBJECT-TYPE
    SYNTAX       Unsigned64
    MAX-ACCESS   read-only
    STATUS       current
    DESCRIPTION
        "Cisco UCS ether:FcoeInterfaceStatsHist:bytesRx
        managed object property"
    ::= { cucsEtherFcoeInterfaceStatsHistEntry 4 }

cucsEtherFcoeInterfaceStatsHistBytesRxDelta OBJECT-TYPE
    SYNTAX       Unsigned64
    MAX-ACCESS   read-only
    STATUS       current
    DESCRIPTION
        "Cisco UCS ether:FcoeInterfaceStatsHist:bytesRxDelta
        managed object property"
    ::= { cucsEtherFcoeInterfaceStatsHistEntry 5 }

cucsEtherFcoeInterfaceStatsHistBytesRxDeltaAvg OBJECT-TYPE
    SYNTAX       Unsigned64
    MAX-ACCESS   read-only
    STATUS       current
    DESCRIPTION
        "Cisco UCS ether:FcoeInterfaceStatsHist:bytesRxDeltaAvg
        managed object property"
    ::= { cucsEtherFcoeInterfaceStatsHistEntry 6 }

cucsEtherFcoeInterfaceStatsHistBytesRxDeltaMax OBJECT-TYPE
    SYNTAX       Unsigned64
    MAX-ACCESS   read-only
    STATUS       current
    DESCRIPTION
        "Cisco UCS ether:FcoeInterfaceStatsHist:bytesRxDeltaMax
        managed object property"
    ::= { cucsEtherFcoeInterfaceStatsHistEntry 7 }

cucsEtherFcoeInterfaceStatsHistBytesRxDeltaMin OBJECT-TYPE
    SYNTAX       Unsigned64
    MAX-ACCESS   read-only
    STATUS       current
    DESCRIPTION
        "Cisco UCS ether:FcoeInterfaceStatsHist:bytesRxDeltaMin
        managed object property"
    ::= { cucsEtherFcoeInterfaceStatsHistEntry 8 }

cucsEtherFcoeInterfaceStatsHistBytesTx OBJECT-TYPE
    SYNTAX       Unsigned64
    MAX-ACCESS   read-only
    STATUS       current
    DESCRIPTION
        "Cisco UCS ether:FcoeInterfaceStatsHist:bytesTx
        managed object property"
    ::= { cucsEtherFcoeInterfaceStatsHistEntry 9 }

cucsEtherFcoeInterfaceStatsHistBytesTxDelta OBJECT-TYPE
    SYNTAX       Unsigned64
    MAX-ACCESS   read-only
    STATUS       current
    DESCRIPTION
        "Cisco UCS ether:FcoeInterfaceStatsHist:bytesTxDelta
        managed object property"
    ::= { cucsEtherFcoeInterfaceStatsHistEntry 10 }

cucsEtherFcoeInterfaceStatsHistBytesTxDeltaAvg OBJECT-TYPE
    SYNTAX       Unsigned64
    MAX-ACCESS   read-only
    STATUS       current
    DESCRIPTION
        "Cisco UCS ether:FcoeInterfaceStatsHist:bytesTxDeltaAvg
        managed object property"
    ::= { cucsEtherFcoeInterfaceStatsHistEntry 11 }

cucsEtherFcoeInterfaceStatsHistBytesTxDeltaMax OBJECT-TYPE
    SYNTAX       Unsigned64
    MAX-ACCESS   read-only
    STATUS       current
    DESCRIPTION
        "Cisco UCS ether:FcoeInterfaceStatsHist:bytesTxDeltaMax
        managed object property"
    ::= { cucsEtherFcoeInterfaceStatsHistEntry 12 }

cucsEtherFcoeInterfaceStatsHistBytesTxDeltaMin OBJECT-TYPE
    SYNTAX       Unsigned64
    MAX-ACCESS   read-only
    STATUS       current
    DESCRIPTION
        "Cisco UCS ether:FcoeInterfaceStatsHist:bytesTxDeltaMin
        managed object property"
    ::= { cucsEtherFcoeInterfaceStatsHistEntry 13 }

cucsEtherFcoeInterfaceStatsHistDroppedRx OBJECT-TYPE
    SYNTAX       Unsigned64
    MAX-ACCESS   read-only
    STATUS       current
    DESCRIPTION
        "Cisco UCS ether:FcoeInterfaceStatsHist:droppedRx
        managed object property"
    ::= { cucsEtherFcoeInterfaceStatsHistEntry 14 }

cucsEtherFcoeInterfaceStatsHistDroppedRxDelta OBJECT-TYPE
    SYNTAX       Unsigned64
    MAX-ACCESS   read-only
    STATUS       current
    DESCRIPTION
        "Cisco UCS ether:FcoeInterfaceStatsHist:droppedRxDelta
        managed object property"
    ::= { cucsEtherFcoeInterfaceStatsHistEntry 15 }

cucsEtherFcoeInterfaceStatsHistDroppedRxDeltaAvg OBJECT-TYPE
    SYNTAX       Unsigned64
    MAX-ACCESS   read-only
    STATUS       current
    DESCRIPTION
        "Cisco UCS ether:FcoeInterfaceStatsHist:droppedRxDeltaAvg
        managed object property"
    ::= { cucsEtherFcoeInterfaceStatsHistEntry 16 }

cucsEtherFcoeInterfaceStatsHistDroppedRxDeltaMax OBJECT-TYPE
    SYNTAX       Unsigned64
    MAX-ACCESS   read-only
    STATUS       current
    DESCRIPTION
        "Cisco UCS ether:FcoeInterfaceStatsHist:droppedRxDeltaMax
        managed object property"
    ::= { cucsEtherFcoeInterfaceStatsHistEntry 17 }

cucsEtherFcoeInterfaceStatsHistDroppedRxDeltaMin OBJECT-TYPE
    SYNTAX       Unsigned64
    MAX-ACCESS   read-only
    STATUS       current
    DESCRIPTION
        "Cisco UCS ether:FcoeInterfaceStatsHist:droppedRxDeltaMin
        managed object property"
    ::= { cucsEtherFcoeInterfaceStatsHistEntry 18 }

cucsEtherFcoeInterfaceStatsHistDroppedTx OBJECT-TYPE
    SYNTAX       Unsigned64
    MAX-ACCESS   read-only
    STATUS       current
    DESCRIPTION
        "Cisco UCS ether:FcoeInterfaceStatsHist:droppedTx
        managed object property"
    ::= { cucsEtherFcoeInterfaceStatsHistEntry 19 }

cucsEtherFcoeInterfaceStatsHistDroppedTxDelta OBJECT-TYPE
    SYNTAX       Unsigned64
    MAX-ACCESS   read-only
    STATUS       current
    DESCRIPTION
        "Cisco UCS ether:FcoeInterfaceStatsHist:droppedTxDelta
        managed object property"
    ::= { cucsEtherFcoeInterfaceStatsHistEntry 20 }

cucsEtherFcoeInterfaceStatsHistDroppedTxDeltaAvg OBJECT-TYPE
    SYNTAX       Unsigned64
    MAX-ACCESS   read-only
    STATUS       current
    DESCRIPTION
        "Cisco UCS ether:FcoeInterfaceStatsHist:droppedTxDeltaAvg
        managed object property"
    ::= { cucsEtherFcoeInterfaceStatsHistEntry 21 }

cucsEtherFcoeInterfaceStatsHistDroppedTxDeltaMax OBJECT-TYPE
    SYNTAX       Unsigned64
    MAX-ACCESS   read-only
    STATUS       current
    DESCRIPTION
        "Cisco UCS ether:FcoeInterfaceStatsHist:droppedTxDeltaMax
        managed object property"
    ::= { cucsEtherFcoeInterfaceStatsHistEntry 22 }

cucsEtherFcoeInterfaceStatsHistDroppedTxDeltaMin OBJECT-TYPE
    SYNTAX       Unsigned64
    MAX-ACCESS   read-only
    STATUS       current
    DESCRIPTION
        "Cisco UCS ether:FcoeInterfaceStatsHist:droppedTxDeltaMin
        managed object property"
    ::= { cucsEtherFcoeInterfaceStatsHistEntry 23 }

cucsEtherFcoeInterfaceStatsHistErrorsRx OBJECT-TYPE
    SYNTAX       Unsigned64
    MAX-ACCESS   read-only
    STATUS       current
    DESCRIPTION
        "Cisco UCS ether:FcoeInterfaceStatsHist:errorsRx
        managed object property"
    ::= { cucsEtherFcoeInterfaceStatsHistEntry 24 }

cucsEtherFcoeInterfaceStatsHistErrorsRxDelta OBJECT-TYPE
    SYNTAX       Unsigned64
    MAX-ACCESS   read-only
    STATUS       current
    DESCRIPTION
        "Cisco UCS ether:FcoeInterfaceStatsHist:errorsRxDelta
        managed object property"
    ::= { cucsEtherFcoeInterfaceStatsHistEntry 25 }

cucsEtherFcoeInterfaceStatsHistErrorsRxDeltaAvg OBJECT-TYPE
    SYNTAX       Unsigned64
    MAX-ACCESS   read-only
    STATUS       current
    DESCRIPTION
        "Cisco UCS ether:FcoeInterfaceStatsHist:errorsRxDeltaAvg
        managed object property"
    ::= { cucsEtherFcoeInterfaceStatsHistEntry 26 }

cucsEtherFcoeInterfaceStatsHistErrorsRxDeltaMax OBJECT-TYPE
    SYNTAX       Unsigned64
    MAX-ACCESS   read-only
    STATUS       current
    DESCRIPTION
        "Cisco UCS ether:FcoeInterfaceStatsHist:errorsRxDeltaMax
        managed object property"
    ::= { cucsEtherFcoeInterfaceStatsHistEntry 27 }

cucsEtherFcoeInterfaceStatsHistErrorsRxDeltaMin OBJECT-TYPE
    SYNTAX       Unsigned64
    MAX-ACCESS   read-only
    STATUS       current
    DESCRIPTION
        "Cisco UCS ether:FcoeInterfaceStatsHist:errorsRxDeltaMin
        managed object property"
    ::= { cucsEtherFcoeInterfaceStatsHistEntry 28 }

cucsEtherFcoeInterfaceStatsHistErrorsTx OBJECT-TYPE
    SYNTAX       Unsigned64
    MAX-ACCESS   read-only
    STATUS       current
    DESCRIPTION
        "Cisco UCS ether:FcoeInterfaceStatsHist:errorsTx
        managed object property"
    ::= { cucsEtherFcoeInterfaceStatsHistEntry 29 }

cucsEtherFcoeInterfaceStatsHistErrorsTxDelta OBJECT-TYPE
    SYNTAX       Unsigned64
    MAX-ACCESS   read-only
    STATUS       current
    DESCRIPTION
        "Cisco UCS ether:FcoeInterfaceStatsHist:errorsTxDelta
        managed object property"
    ::= { cucsEtherFcoeInterfaceStatsHistEntry 30 }

cucsEtherFcoeInterfaceStatsHistErrorsTxDeltaAvg OBJECT-TYPE
    SYNTAX       Unsigned64
    MAX-ACCESS   read-only
    STATUS       current
    DESCRIPTION
        "Cisco UCS ether:FcoeInterfaceStatsHist:errorsTxDeltaAvg
        managed object property"
    ::= { cucsEtherFcoeInterfaceStatsHistEntry 31 }

cucsEtherFcoeInterfaceStatsHistErrorsTxDeltaMax OBJECT-TYPE
    SYNTAX       Unsigned64
    MAX-ACCESS   read-only
    STATUS       current
    DESCRIPTION
        "Cisco UCS ether:FcoeInterfaceStatsHist:errorsTxDeltaMax
        managed object property"
    ::= { cucsEtherFcoeInterfaceStatsHistEntry 32 }

cucsEtherFcoeInterfaceStatsHistErrorsTxDeltaMin OBJECT-TYPE
    SYNTAX       Unsigned64
    MAX-ACCESS   read-only
    STATUS       current
    DESCRIPTION
        "Cisco UCS ether:FcoeInterfaceStatsHist:errorsTxDeltaMin
        managed object property"
    ::= { cucsEtherFcoeInterfaceStatsHistEntry 33 }

cucsEtherFcoeInterfaceStatsHistId OBJECT-TYPE
    SYNTAX       Unsigned64
    MAX-ACCESS   read-only
    STATUS       current
    DESCRIPTION
        "Cisco UCS ether:FcoeInterfaceStatsHist:id managed
        object property"
    ::= { cucsEtherFcoeInterfaceStatsHistEntry 34 }

cucsEtherFcoeInterfaceStatsHistMostRecent OBJECT-TYPE
    SYNTAX       TruthValue
    MAX-ACCESS   read-only
    STATUS       current
    DESCRIPTION
        "Cisco UCS ether:FcoeInterfaceStatsHist:mostRecent
        managed object property"
    ::= { cucsEtherFcoeInterfaceStatsHistEntry 35 }

cucsEtherFcoeInterfaceStatsHistPacketsRx OBJECT-TYPE
    SYNTAX       Unsigned64
    MAX-ACCESS   read-only
    STATUS       current
    DESCRIPTION
        "Cisco UCS ether:FcoeInterfaceStatsHist:packetsRx
        managed object property"
    ::= { cucsEtherFcoeInterfaceStatsHistEntry 36 }

cucsEtherFcoeInterfaceStatsHistPacketsRxDelta OBJECT-TYPE
    SYNTAX       Unsigned64
    MAX-ACCESS   read-only
    STATUS       current
    DESCRIPTION
        "Cisco UCS ether:FcoeInterfaceStatsHist:packetsRxDelta
        managed object property"
    ::= { cucsEtherFcoeInterfaceStatsHistEntry 37 }

cucsEtherFcoeInterfaceStatsHistPacketsRxDeltaAvg OBJECT-TYPE
    SYNTAX       Unsigned64
    MAX-ACCESS   read-only
    STATUS       current
    DESCRIPTION
        "Cisco UCS ether:FcoeInterfaceStatsHist:packetsRxDeltaAvg
        managed object property"
    ::= { cucsEtherFcoeInterfaceStatsHistEntry 38 }

cucsEtherFcoeInterfaceStatsHistPacketsRxDeltaMax OBJECT-TYPE
    SYNTAX       Unsigned64
    MAX-ACCESS   read-only
    STATUS       current
    DESCRIPTION
        "Cisco UCS ether:FcoeInterfaceStatsHist:packetsRxDeltaMax
        managed object property"
    ::= { cucsEtherFcoeInterfaceStatsHistEntry 39 }

cucsEtherFcoeInterfaceStatsHistPacketsRxDeltaMin OBJECT-TYPE
    SYNTAX       Unsigned64
    MAX-ACCESS   read-only
    STATUS       current
    DESCRIPTION
        "Cisco UCS ether:FcoeInterfaceStatsHist:packetsRxDeltaMin
        managed object property"
    ::= { cucsEtherFcoeInterfaceStatsHistEntry 40 }

cucsEtherFcoeInterfaceStatsHistPacketsTx OBJECT-TYPE
    SYNTAX       Unsigned64
    MAX-ACCESS   read-only
    STATUS       current
    DESCRIPTION
        "Cisco UCS ether:FcoeInterfaceStatsHist:packetsTx
        managed object property"
    ::= { cucsEtherFcoeInterfaceStatsHistEntry 41 }

cucsEtherFcoeInterfaceStatsHistPacketsTxDelta OBJECT-TYPE
    SYNTAX       Unsigned64
    MAX-ACCESS   read-only
    STATUS       current
    DESCRIPTION
        "Cisco UCS ether:FcoeInterfaceStatsHist:packetsTxDelta
        managed object property"
    ::= { cucsEtherFcoeInterfaceStatsHistEntry 42 }

cucsEtherFcoeInterfaceStatsHistPacketsTxDeltaAvg OBJECT-TYPE
    SYNTAX       Unsigned64
    MAX-ACCESS   read-only
    STATUS       current
    DESCRIPTION
        "Cisco UCS ether:FcoeInterfaceStatsHist:packetsTxDeltaAvg
        managed object property"
    ::= { cucsEtherFcoeInterfaceStatsHistEntry 43 }

cucsEtherFcoeInterfaceStatsHistPacketsTxDeltaMax OBJECT-TYPE
    SYNTAX       Unsigned64
    MAX-ACCESS   read-only
    STATUS       current
    DESCRIPTION
        "Cisco UCS ether:FcoeInterfaceStatsHist:packetsTxDeltaMax
        managed object property"
    ::= { cucsEtherFcoeInterfaceStatsHistEntry 44 }

cucsEtherFcoeInterfaceStatsHistPacketsTxDeltaMin OBJECT-TYPE
    SYNTAX       Unsigned64
    MAX-ACCESS   read-only
    STATUS       current
    DESCRIPTION
        "Cisco UCS ether:FcoeInterfaceStatsHist:packetsTxDeltaMin
        managed object property"
    ::= { cucsEtherFcoeInterfaceStatsHistEntry 45 }

cucsEtherFcoeInterfaceStatsHistSuspect OBJECT-TYPE
    SYNTAX       TruthValue
    MAX-ACCESS   read-only
    STATUS       current
    DESCRIPTION
        "Cisco UCS ether:FcoeInterfaceStatsHist:suspect
        managed object property"
    ::= { cucsEtherFcoeInterfaceStatsHistEntry 46 }

cucsEtherFcoeInterfaceStatsHistThresholded OBJECT-TYPE
    SYNTAX       CucsEtherFcoeInterfaceStatsHistThresholded
    MAX-ACCESS   read-only
    STATUS       current
    DESCRIPTION
        "Cisco UCS ether:FcoeInterfaceStatsHist:thresholded
        managed object property"
    ::= { cucsEtherFcoeInterfaceStatsHistEntry 47 }

cucsEtherFcoeInterfaceStatsHistTimeCollected OBJECT-TYPE
    SYNTAX       DateAndTime
    MAX-ACCESS   read-only
    STATUS       current
    DESCRIPTION
        "Cisco UCS ether:FcoeInterfaceStatsHist:timeCollected
        managed object property"
    ::= { cucsEtherFcoeInterfaceStatsHistEntry 48 }

cucsEtherLossStatsTable OBJECT-TYPE
    SYNTAX           SEQUENCE OF CucsEtherLossStatsEntry
    MAX-ACCESS       not-accessible
    STATUS           current
    DESCRIPTION
        "Cisco UCS ether:LossStats managed object table"
    ::= { cucsEtherObjects 3 }

cucsEtherLossStatsEntry OBJECT-TYPE
    SYNTAX           CucsEtherLossStatsEntry
    MAX-ACCESS       not-accessible
    STATUS           current
    DESCRIPTION
        "Entry for the cucsEtherLossStatsTable table."
    INDEX { cucsEtherLossStatsInstanceId }
    ::= { cucsEtherLossStatsTable 1 }

CucsEtherLossStatsEntry ::= SEQUENCE {
    cucsEtherLossStatsInstanceId                                     CucsManagedObjectId,
    cucsEtherLossStatsDn                                             CucsManagedObjectDn,
    cucsEtherLossStatsRn                                             SnmpAdminString,
    cucsEtherLossStatsSQETest                                        Unsigned64,
    cucsEtherLossStatsSQETestDelta                                   Counter64,
    cucsEtherLossStatsSQETestDeltaAvg                                Unsigned64,
    cucsEtherLossStatsSQETestDeltaMax                                Unsigned64,
    cucsEtherLossStatsSQETestDeltaMin                                Unsigned64,
    cucsEtherLossStatsCarrierSense                                   Unsigned64,
    cucsEtherLossStatsCarrierSenseDelta                              Counter64,
    cucsEtherLossStatsCarrierSenseDeltaAvg                           Unsigned64,
    cucsEtherLossStatsCarrierSenseDeltaMax                           Unsigned64,
    cucsEtherLossStatsCarrierSenseDeltaMin                           Unsigned64,
    cucsEtherLossStatsExcessCollision                                Unsigned64,
    cucsEtherLossStatsExcessCollisionDelta                           Counter64,
    cucsEtherLossStatsExcessCollisionDeltaAvg                        Unsigned64,
    cucsEtherLossStatsExcessCollisionDeltaMax                        Unsigned64,
    cucsEtherLossStatsExcessCollisionDeltaMin                        Unsigned64,
    cucsEtherLossStatsGiants                                         Unsigned64,
    cucsEtherLossStatsGiantsDelta                                    Counter64,
    cucsEtherLossStatsGiantsDeltaAvg                                 Unsigned64,
    cucsEtherLossStatsGiantsDeltaMax                                 Unsigned64,
    cucsEtherLossStatsGiantsDeltaMin                                 Unsigned64,
    cucsEtherLossStatsIntervals                                      Gauge32,
    cucsEtherLossStatsLateCollision                                  Unsigned64,
    cucsEtherLossStatsLateCollisionDelta                             Counter64,
    cucsEtherLossStatsLateCollisionDeltaAvg                          Unsigned64,
    cucsEtherLossStatsLateCollisionDeltaMax                          Unsigned64,
    cucsEtherLossStatsLateCollisionDeltaMin                          Unsigned64,
    cucsEtherLossStatsMultiCollision                                 Unsigned64,
    cucsEtherLossStatsMultiCollisionDelta                            Counter64,
    cucsEtherLossStatsMultiCollisionDeltaAvg                         Unsigned64,
    cucsEtherLossStatsMultiCollisionDeltaMax                         Unsigned64,
    cucsEtherLossStatsMultiCollisionDeltaMin                         Unsigned64,
    cucsEtherLossStatsSingleCollision                                Unsigned64,
    cucsEtherLossStatsSingleCollisionDelta                           Counter64,
    cucsEtherLossStatsSingleCollisionDeltaAvg                        Unsigned64,
    cucsEtherLossStatsSingleCollisionDeltaMax                        Unsigned64,
    cucsEtherLossStatsSingleCollisionDeltaMin                        Unsigned64,
    cucsEtherLossStatsSuspect                                        TruthValue,
    cucsEtherLossStatsSymbol                                         Unsigned64,
    cucsEtherLossStatsSymbolDelta                                    Counter64,
    cucsEtherLossStatsSymbolDeltaAvg                                 Unsigned64,
    cucsEtherLossStatsSymbolDeltaMax                                 Unsigned64,
    cucsEtherLossStatsSymbolDeltaMin                                 Unsigned64,
    cucsEtherLossStatsThresholded                                    CucsEtherLossStatsThresholded,
    cucsEtherLossStatsTimeCollected                                  DateAndTime,
    cucsEtherLossStatsUpdate                                         Gauge32
}

cucsEtherLossStatsInstanceId OBJECT-TYPE
    SYNTAX       CucsManagedObjectId
    MAX-ACCESS   not-accessible
    STATUS       current
    DESCRIPTION
        "Instance identifier of the managed object."
    ::= { cucsEtherLossStatsEntry 1 }

cucsEtherLossStatsDn OBJECT-TYPE
    SYNTAX       CucsManagedObjectDn
    MAX-ACCESS   read-only
    STATUS       current
    DESCRIPTION
        "Cisco UCS ether:LossStats:dn managed object property"
    ::= { cucsEtherLossStatsEntry 2 }

cucsEtherLossStatsRn OBJECT-TYPE
    SYNTAX       SnmpAdminString
    MAX-ACCESS   read-only
    STATUS       current
    DESCRIPTION
        "Cisco UCS ether:LossStats:rn managed object property"
    ::= { cucsEtherLossStatsEntry 3 }

cucsEtherLossStatsSQETest OBJECT-TYPE
    SYNTAX       Unsigned64
    MAX-ACCESS   read-only
    STATUS       current
    DESCRIPTION
        "Cisco UCS ether:LossStats:SQETest managed object property"
    ::= { cucsEtherLossStatsEntry 4 }

cucsEtherLossStatsSQETestDelta OBJECT-TYPE
    SYNTAX       Counter64
    MAX-ACCESS   read-only
    STATUS       current
    DESCRIPTION
        "Cisco UCS ether:LossStats:SQETestDelta managed object property"
    ::= { cucsEtherLossStatsEntry 5 }

cucsEtherLossStatsSQETestDeltaAvg OBJECT-TYPE
    SYNTAX       Unsigned64
    MAX-ACCESS   read-only
    STATUS       current
    DESCRIPTION
        "Cisco UCS ether:LossStats:SQETestDeltaAvg managed
        object property"
    ::= { cucsEtherLossStatsEntry 6 }

cucsEtherLossStatsSQETestDeltaMax OBJECT-TYPE
    SYNTAX       Unsigned64
    MAX-ACCESS   read-only
    STATUS       current
    DESCRIPTION
        "Cisco UCS ether:LossStats:SQETestDeltaMax managed
        object property"
    ::= { cucsEtherLossStatsEntry 7 }

cucsEtherLossStatsSQETestDeltaMin OBJECT-TYPE
    SYNTAX       Unsigned64
    MAX-ACCESS   read-only
    STATUS       current
    DESCRIPTION
        "Cisco UCS ether:LossStats:SQETestDeltaMin managed
        object property"
    ::= { cucsEtherLossStatsEntry 8 }

cucsEtherLossStatsCarrierSense OBJECT-TYPE
    SYNTAX       Unsigned64
    MAX-ACCESS   read-only
    STATUS       current
    DESCRIPTION
        "Cisco UCS ether:LossStats:carrierSense managed object property"
    ::= { cucsEtherLossStatsEntry 9 }

cucsEtherLossStatsCarrierSenseDelta OBJECT-TYPE
    SYNTAX       Counter64
    MAX-ACCESS   read-only
    STATUS       current
    DESCRIPTION
        "Cisco UCS ether:LossStats:carrierSenseDelta managed
        object property"
    ::= { cucsEtherLossStatsEntry 10 }

cucsEtherLossStatsCarrierSenseDeltaAvg OBJECT-TYPE
    SYNTAX       Unsigned64
    MAX-ACCESS   read-only
    STATUS       current
    DESCRIPTION
        "Cisco UCS ether:LossStats:carrierSenseDeltaAvg
        managed object property"
    ::= { cucsEtherLossStatsEntry 11 }

cucsEtherLossStatsCarrierSenseDeltaMax OBJECT-TYPE
    SYNTAX       Unsigned64
    MAX-ACCESS   read-only
    STATUS       current
    DESCRIPTION
        "Cisco UCS ether:LossStats:carrierSenseDeltaMax
        managed object property"
    ::= { cucsEtherLossStatsEntry 12 }

cucsEtherLossStatsCarrierSenseDeltaMin OBJECT-TYPE
    SYNTAX       Unsigned64
    MAX-ACCESS   read-only
    STATUS       current
    DESCRIPTION
        "Cisco UCS ether:LossStats:carrierSenseDeltaMin
        managed object property"
    ::= { cucsEtherLossStatsEntry 13 }

cucsEtherLossStatsExcessCollision OBJECT-TYPE
    SYNTAX       Unsigned64
    MAX-ACCESS   read-only
    STATUS       current
    DESCRIPTION
        "Cisco UCS ether:LossStats:excessCollision managed
        object property"
    ::= { cucsEtherLossStatsEntry 14 }

cucsEtherLossStatsExcessCollisionDelta OBJECT-TYPE
    SYNTAX       Counter64
    MAX-ACCESS   read-only
    STATUS       current
    DESCRIPTION
        "Cisco UCS ether:LossStats:excessCollisionDelta
        managed object property"
    ::= { cucsEtherLossStatsEntry 15 }

cucsEtherLossStatsExcessCollisionDeltaAvg OBJECT-TYPE
    SYNTAX       Unsigned64
    MAX-ACCESS   read-only
    STATUS       current
    DESCRIPTION
        "Cisco UCS ether:LossStats:excessCollisionDeltaAvg
        managed object property"
    ::= { cucsEtherLossStatsEntry 16 }

cucsEtherLossStatsExcessCollisionDeltaMax OBJECT-TYPE
    SYNTAX       Unsigned64
    MAX-ACCESS   read-only
    STATUS       current
    DESCRIPTION
        "Cisco UCS ether:LossStats:excessCollisionDeltaMax
        managed object property"
    ::= { cucsEtherLossStatsEntry 17 }

cucsEtherLossStatsExcessCollisionDeltaMin OBJECT-TYPE
    SYNTAX       Unsigned64
    MAX-ACCESS   read-only
    STATUS       current
    DESCRIPTION
        "Cisco UCS ether:LossStats:excessCollisionDeltaMin
        managed object property"
    ::= { cucsEtherLossStatsEntry 18 }

cucsEtherLossStatsGiants OBJECT-TYPE
    SYNTAX       Unsigned64
    MAX-ACCESS   read-only
    STATUS       current
    DESCRIPTION
        "Cisco UCS ether:LossStats:giants managed object property"
    ::= { cucsEtherLossStatsEntry 19 }

cucsEtherLossStatsGiantsDelta OBJECT-TYPE
    SYNTAX       Counter64
    MAX-ACCESS   read-only
    STATUS       current
    DESCRIPTION
        "Cisco UCS ether:LossStats:giantsDelta managed object property"
    ::= { cucsEtherLossStatsEntry 20 }

cucsEtherLossStatsGiantsDeltaAvg OBJECT-TYPE
    SYNTAX       Unsigned64
    MAX-ACCESS   read-only
    STATUS       current
    DESCRIPTION
        "Cisco UCS ether:LossStats:giantsDeltaAvg managed object property"
    ::= { cucsEtherLossStatsEntry 21 }

cucsEtherLossStatsGiantsDeltaMax OBJECT-TYPE
    SYNTAX       Unsigned64
    MAX-ACCESS   read-only
    STATUS       current
    DESCRIPTION
        "Cisco UCS ether:LossStats:giantsDeltaMax managed object property"
    ::= { cucsEtherLossStatsEntry 22 }

cucsEtherLossStatsGiantsDeltaMin OBJECT-TYPE
    SYNTAX       Unsigned64
    MAX-ACCESS   read-only
    STATUS       current
    DESCRIPTION
        "Cisco UCS ether:LossStats:giantsDeltaMin managed object property"
    ::= { cucsEtherLossStatsEntry 23 }

cucsEtherLossStatsIntervals OBJECT-TYPE
    SYNTAX       Gauge32
    MAX-ACCESS   read-only
    STATUS       current
    DESCRIPTION
        "Cisco UCS ether:LossStats:intervals managed object property"
    ::= { cucsEtherLossStatsEntry 24 }

cucsEtherLossStatsLateCollision OBJECT-TYPE
    SYNTAX       Unsigned64
    MAX-ACCESS   read-only
    STATUS       current
    DESCRIPTION
        "Cisco UCS ether:LossStats:lateCollision managed object property"
    ::= { cucsEtherLossStatsEntry 25 }

cucsEtherLossStatsLateCollisionDelta OBJECT-TYPE
    SYNTAX       Counter64
    MAX-ACCESS   read-only
    STATUS       current
    DESCRIPTION
        "Cisco UCS ether:LossStats:lateCollisionDelta managed
        object property"
    ::= { cucsEtherLossStatsEntry 26 }

cucsEtherLossStatsLateCollisionDeltaAvg OBJECT-TYPE
    SYNTAX       Unsigned64
    MAX-ACCESS   read-only
    STATUS       current
    DESCRIPTION
        "Cisco UCS ether:LossStats:lateCollisionDeltaAvg
        managed object property"
    ::= { cucsEtherLossStatsEntry 27 }

cucsEtherLossStatsLateCollisionDeltaMax OBJECT-TYPE
    SYNTAX       Unsigned64
    MAX-ACCESS   read-only
    STATUS       current
    DESCRIPTION
        "Cisco UCS ether:LossStats:lateCollisionDeltaMax
        managed object property"
    ::= { cucsEtherLossStatsEntry 28 }

cucsEtherLossStatsLateCollisionDeltaMin OBJECT-TYPE
    SYNTAX       Unsigned64
    MAX-ACCESS   read-only
    STATUS       current
    DESCRIPTION
        "Cisco UCS ether:LossStats:lateCollisionDeltaMin
        managed object property"
    ::= { cucsEtherLossStatsEntry 29 }

cucsEtherLossStatsMultiCollision OBJECT-TYPE
    SYNTAX       Unsigned64
    MAX-ACCESS   read-only
    STATUS       current
    DESCRIPTION
        "Cisco UCS ether:LossStats:multiCollision managed object property"
    ::= { cucsEtherLossStatsEntry 30 }

cucsEtherLossStatsMultiCollisionDelta OBJECT-TYPE
    SYNTAX       Counter64
    MAX-ACCESS   read-only
    STATUS       current
    DESCRIPTION
        "Cisco UCS ether:LossStats:multiCollisionDelta
        managed object property"
    ::= { cucsEtherLossStatsEntry 31 }

cucsEtherLossStatsMultiCollisionDeltaAvg OBJECT-TYPE
    SYNTAX       Unsigned64
    MAX-ACCESS   read-only
    STATUS       current
    DESCRIPTION
        "Cisco UCS ether:LossStats:multiCollisionDeltaAvg
        managed object property"
    ::= { cucsEtherLossStatsEntry 32 }

cucsEtherLossStatsMultiCollisionDeltaMax OBJECT-TYPE
    SYNTAX       Unsigned64
    MAX-ACCESS   read-only
    STATUS       current
    DESCRIPTION
        "Cisco UCS ether:LossStats:multiCollisionDeltaMax
        managed object property"
    ::= { cucsEtherLossStatsEntry 33 }

cucsEtherLossStatsMultiCollisionDeltaMin OBJECT-TYPE
    SYNTAX       Unsigned64
    MAX-ACCESS   read-only
    STATUS       current
    DESCRIPTION
        "Cisco UCS ether:LossStats:multiCollisionDeltaMin
        managed object property"
    ::= { cucsEtherLossStatsEntry 34 }

cucsEtherLossStatsSingleCollision OBJECT-TYPE
    SYNTAX       Unsigned64
    MAX-ACCESS   read-only
    STATUS       current
    DESCRIPTION
        "Cisco UCS ether:LossStats:singleCollision managed
        object property"
    ::= { cucsEtherLossStatsEntry 35 }

cucsEtherLossStatsSingleCollisionDelta OBJECT-TYPE
    SYNTAX       Counter64
    MAX-ACCESS   read-only
    STATUS       current
    DESCRIPTION
        "Cisco UCS ether:LossStats:singleCollisionDelta
        managed object property"
    ::= { cucsEtherLossStatsEntry 36 }

cucsEtherLossStatsSingleCollisionDeltaAvg OBJECT-TYPE
    SYNTAX       Unsigned64
    MAX-ACCESS   read-only
    STATUS       current
    DESCRIPTION
        "Cisco UCS ether:LossStats:singleCollisionDeltaAvg
        managed object property"
    ::= { cucsEtherLossStatsEntry 37 }

cucsEtherLossStatsSingleCollisionDeltaMax OBJECT-TYPE
    SYNTAX       Unsigned64
    MAX-ACCESS   read-only
    STATUS       current
    DESCRIPTION
        "Cisco UCS ether:LossStats:singleCollisionDeltaMax
        managed object property"
    ::= { cucsEtherLossStatsEntry 38 }

cucsEtherLossStatsSingleCollisionDeltaMin OBJECT-TYPE
    SYNTAX       Unsigned64
    MAX-ACCESS   read-only
    STATUS       current
    DESCRIPTION
        "Cisco UCS ether:LossStats:singleCollisionDeltaMin
        managed object property"
    ::= { cucsEtherLossStatsEntry 39 }

cucsEtherLossStatsSuspect OBJECT-TYPE
    SYNTAX       TruthValue
    MAX-ACCESS   read-only
    STATUS       current
    DESCRIPTION
        "Cisco UCS ether:LossStats:suspect managed object property"
    ::= { cucsEtherLossStatsEntry 40 }

cucsEtherLossStatsSymbol OBJECT-TYPE
    SYNTAX       Unsigned64
    MAX-ACCESS   read-only
    STATUS       current
    DESCRIPTION
        "Cisco UCS ether:LossStats:symbol managed object property"
    ::= { cucsEtherLossStatsEntry 41 }

cucsEtherLossStatsSymbolDelta OBJECT-TYPE
    SYNTAX       Counter64
    MAX-ACCESS   read-only
    STATUS       current
    DESCRIPTION
        "Cisco UCS ether:LossStats:symbolDelta managed object property"
    ::= { cucsEtherLossStatsEntry 42 }

cucsEtherLossStatsSymbolDeltaAvg OBJECT-TYPE
    SYNTAX       Unsigned64
    MAX-ACCESS   read-only
    STATUS       current
    DESCRIPTION
        "Cisco UCS ether:LossStats:symbolDeltaAvg managed object property"
    ::= { cucsEtherLossStatsEntry 43 }

cucsEtherLossStatsSymbolDeltaMax OBJECT-TYPE
    SYNTAX       Unsigned64
    MAX-ACCESS   read-only
    STATUS       current
    DESCRIPTION
        "Cisco UCS ether:LossStats:symbolDeltaMax managed object property"
    ::= { cucsEtherLossStatsEntry 44 }

cucsEtherLossStatsSymbolDeltaMin OBJECT-TYPE
    SYNTAX       Unsigned64
    MAX-ACCESS   read-only
    STATUS       current
    DESCRIPTION
        "Cisco UCS ether:LossStats:symbolDeltaMin managed object property"
    ::= { cucsEtherLossStatsEntry 45 }

cucsEtherLossStatsThresholded OBJECT-TYPE
    SYNTAX       CucsEtherLossStatsThresholded
    MAX-ACCESS   read-only
    STATUS       current
    DESCRIPTION
        "Cisco UCS ether:LossStats:thresholded managed object property"
    ::= { cucsEtherLossStatsEntry 46 }

cucsEtherLossStatsTimeCollected OBJECT-TYPE
    SYNTAX       DateAndTime
    MAX-ACCESS   read-only
    STATUS       current
    DESCRIPTION
        "Cisco UCS ether:LossStats:timeCollected managed object property"
    ::= { cucsEtherLossStatsEntry 47 }

cucsEtherLossStatsUpdate OBJECT-TYPE
    SYNTAX       Gauge32
    MAX-ACCESS   read-only
    STATUS       current
    DESCRIPTION
        "Cisco UCS ether:LossStats:update managed object property"
    ::= { cucsEtherLossStatsEntry 48 }

cucsEtherLossStatsHistTable OBJECT-TYPE
    SYNTAX           SEQUENCE OF CucsEtherLossStatsHistEntry
    MAX-ACCESS       not-accessible
    STATUS           current
    DESCRIPTION
        "Cisco UCS ether:LossStatsHist managed object table"
    ::= { cucsEtherObjects 4 }

cucsEtherLossStatsHistEntry OBJECT-TYPE
    SYNTAX           CucsEtherLossStatsHistEntry
    MAX-ACCESS       not-accessible
    STATUS           current
    DESCRIPTION
        "Entry for the cucsEtherLossStatsHistTable table."
    INDEX { cucsEtherLossStatsHistInstanceId }
    ::= { cucsEtherLossStatsHistTable 1 }

CucsEtherLossStatsHistEntry ::= SEQUENCE {
    cucsEtherLossStatsHistInstanceId                                 CucsManagedObjectId,
    cucsEtherLossStatsHistDn                                         CucsManagedObjectDn,
    cucsEtherLossStatsHistRn                                         SnmpAdminString,
    cucsEtherLossStatsHistSQETest                                    Unsigned64,
    cucsEtherLossStatsHistSQETestDelta                               Unsigned64,
    cucsEtherLossStatsHistSQETestDeltaAvg                            Unsigned64,
    cucsEtherLossStatsHistSQETestDeltaMax                            Unsigned64,
    cucsEtherLossStatsHistSQETestDeltaMin                            Unsigned64,
    cucsEtherLossStatsHistCarrierSense                               Unsigned64,
    cucsEtherLossStatsHistCarrierSenseDelta                          Unsigned64,
    cucsEtherLossStatsHistCarrierSenseDeltaAvg                       Unsigned64,
    cucsEtherLossStatsHistCarrierSenseDeltaMax                       Unsigned64,
    cucsEtherLossStatsHistCarrierSenseDeltaMin                       Unsigned64,
    cucsEtherLossStatsHistExcessCollision                            Unsigned64,
    cucsEtherLossStatsHistExcessCollisionDelta                       Unsigned64,
    cucsEtherLossStatsHistExcessCollisionDeltaAvg                    Unsigned64,
    cucsEtherLossStatsHistExcessCollisionDeltaMax                    Unsigned64,
    cucsEtherLossStatsHistExcessCollisionDeltaMin                    Unsigned64,
    cucsEtherLossStatsHistGiants                                     Unsigned64,
    cucsEtherLossStatsHistGiantsDelta                                Unsigned64,
    cucsEtherLossStatsHistGiantsDeltaAvg                             Unsigned64,
    cucsEtherLossStatsHistGiantsDeltaMax                             Unsigned64,
    cucsEtherLossStatsHistGiantsDeltaMin                             Unsigned64,
    cucsEtherLossStatsHistId                                         Unsigned64,
    cucsEtherLossStatsHistLateCollision                              Unsigned64,
    cucsEtherLossStatsHistLateCollisionDelta                         Unsigned64,
    cucsEtherLossStatsHistLateCollisionDeltaAvg                      Unsigned64,
    cucsEtherLossStatsHistLateCollisionDeltaMax                      Unsigned64,
    cucsEtherLossStatsHistLateCollisionDeltaMin                      Unsigned64,
    cucsEtherLossStatsHistMostRecent                                 TruthValue,
    cucsEtherLossStatsHistMultiCollision                             Unsigned64,
    cucsEtherLossStatsHistMultiCollisionDelta                        Unsigned64,
    cucsEtherLossStatsHistMultiCollisionDeltaAvg                     Unsigned64,
    cucsEtherLossStatsHistMultiCollisionDeltaMax                     Unsigned64,
    cucsEtherLossStatsHistMultiCollisionDeltaMin                     Unsigned64,
    cucsEtherLossStatsHistSingleCollision                            Unsigned64,
    cucsEtherLossStatsHistSingleCollisionDelta                       Unsigned64,
    cucsEtherLossStatsHistSingleCollisionDeltaAvg                    Unsigned64,
    cucsEtherLossStatsHistSingleCollisionDeltaMax                    Unsigned64,
    cucsEtherLossStatsHistSingleCollisionDeltaMin                    Unsigned64,
    cucsEtherLossStatsHistSuspect                                    TruthValue,
    cucsEtherLossStatsHistSymbol                                     Unsigned64,
    cucsEtherLossStatsHistSymbolDelta                                Unsigned64,
    cucsEtherLossStatsHistSymbolDeltaAvg                             Unsigned64,
    cucsEtherLossStatsHistSymbolDeltaMax                             Unsigned64,
    cucsEtherLossStatsHistSymbolDeltaMin                             Unsigned64,
    cucsEtherLossStatsHistThresholded                                CucsEtherLossStatsHistThresholded,
    cucsEtherLossStatsHistTimeCollected                              DateAndTime
}

cucsEtherLossStatsHistInstanceId OBJECT-TYPE
    SYNTAX       CucsManagedObjectId
    MAX-ACCESS   not-accessible
    STATUS       current
    DESCRIPTION
        "Instance identifier of the managed object."
    ::= { cucsEtherLossStatsHistEntry 1 }

cucsEtherLossStatsHistDn OBJECT-TYPE
    SYNTAX       CucsManagedObjectDn
    MAX-ACCESS   read-only
    STATUS       current
    DESCRIPTION
        "Cisco UCS ether:LossStatsHist:dn managed object property"
    ::= { cucsEtherLossStatsHistEntry 2 }

cucsEtherLossStatsHistRn OBJECT-TYPE
    SYNTAX       SnmpAdminString
    MAX-ACCESS   read-only
    STATUS       current
    DESCRIPTION
        "Cisco UCS ether:LossStatsHist:rn managed object property"
    ::= { cucsEtherLossStatsHistEntry 3 }

cucsEtherLossStatsHistSQETest OBJECT-TYPE
    SYNTAX       Unsigned64
    MAX-ACCESS   read-only
    STATUS       current
    DESCRIPTION
        "Cisco UCS ether:LossStatsHist:SQETest managed object property"
    ::= { cucsEtherLossStatsHistEntry 4 }

cucsEtherLossStatsHistSQETestDelta OBJECT-TYPE
    SYNTAX       Unsigned64
    MAX-ACCESS   read-only
    STATUS       current
    DESCRIPTION
        "Cisco UCS ether:LossStatsHist:SQETestDelta managed
        object property"
    ::= { cucsEtherLossStatsHistEntry 5 }

cucsEtherLossStatsHistSQETestDeltaAvg OBJECT-TYPE
    SYNTAX       Unsigned64
    MAX-ACCESS   read-only
    STATUS       current
    DESCRIPTION
        "Cisco UCS ether:LossStatsHist:SQETestDeltaAvg
        managed object property"
    ::= { cucsEtherLossStatsHistEntry 6 }

cucsEtherLossStatsHistSQETestDeltaMax OBJECT-TYPE
    SYNTAX       Unsigned64
    MAX-ACCESS   read-only
    STATUS       current
    DESCRIPTION
        "Cisco UCS ether:LossStatsHist:SQETestDeltaMax
        managed object property"
    ::= { cucsEtherLossStatsHistEntry 7 }

cucsEtherLossStatsHistSQETestDeltaMin OBJECT-TYPE
    SYNTAX       Unsigned64
    MAX-ACCESS   read-only
    STATUS       current
    DESCRIPTION
        "Cisco UCS ether:LossStatsHist:SQETestDeltaMin
        managed object property"
    ::= { cucsEtherLossStatsHistEntry 8 }

cucsEtherLossStatsHistCarrierSense OBJECT-TYPE
    SYNTAX       Unsigned64
    MAX-ACCESS   read-only
    STATUS       current
    DESCRIPTION
        "Cisco UCS ether:LossStatsHist:carrierSense managed
        object property"
    ::= { cucsEtherLossStatsHistEntry 9 }

cucsEtherLossStatsHistCarrierSenseDelta OBJECT-TYPE
    SYNTAX       Unsigned64
    MAX-ACCESS   read-only
    STATUS       current
    DESCRIPTION
        "Cisco UCS ether:LossStatsHist:carrierSenseDelta
        managed object property"
    ::= { cucsEtherLossStatsHistEntry 10 }

cucsEtherLossStatsHistCarrierSenseDeltaAvg OBJECT-TYPE
    SYNTAX       Unsigned64
    MAX-ACCESS   read-only
    STATUS       current
    DESCRIPTION
        "Cisco UCS ether:LossStatsHist:carrierSenseDeltaAvg
        managed object property"
    ::= { cucsEtherLossStatsHistEntry 11 }

cucsEtherLossStatsHistCarrierSenseDeltaMax OBJECT-TYPE
    SYNTAX       Unsigned64
    MAX-ACCESS   read-only
    STATUS       current
    DESCRIPTION
        "Cisco UCS ether:LossStatsHist:carrierSenseDeltaMax
        managed object property"
    ::= { cucsEtherLossStatsHistEntry 12 }

cucsEtherLossStatsHistCarrierSenseDeltaMin OBJECT-TYPE
    SYNTAX       Unsigned64
    MAX-ACCESS   read-only
    STATUS       current
    DESCRIPTION
        "Cisco UCS ether:LossStatsHist:carrierSenseDeltaMin
        managed object property"
    ::= { cucsEtherLossStatsHistEntry 13 }

cucsEtherLossStatsHistExcessCollision OBJECT-TYPE
    SYNTAX       Unsigned64
    MAX-ACCESS   read-only
    STATUS       current
    DESCRIPTION
        "Cisco UCS ether:LossStatsHist:excessCollision
        managed object property"
    ::= { cucsEtherLossStatsHistEntry 14 }

cucsEtherLossStatsHistExcessCollisionDelta OBJECT-TYPE
    SYNTAX       Unsigned64
    MAX-ACCESS   read-only
    STATUS       current
    DESCRIPTION
        "Cisco UCS ether:LossStatsHist:excessCollisionDelta
        managed object property"
    ::= { cucsEtherLossStatsHistEntry 15 }

cucsEtherLossStatsHistExcessCollisionDeltaAvg OBJECT-TYPE
    SYNTAX       Unsigned64
    MAX-ACCESS   read-only
    STATUS       current
    DESCRIPTION
        "Cisco UCS ether:LossStatsHist:excessCollisionDeltaAvg
        managed object property"
    ::= { cucsEtherLossStatsHistEntry 16 }

cucsEtherLossStatsHistExcessCollisionDeltaMax OBJECT-TYPE
    SYNTAX       Unsigned64
    MAX-ACCESS   read-only
    STATUS       current
    DESCRIPTION
        "Cisco UCS ether:LossStatsHist:excessCollisionDeltaMax
        managed object property"
    ::= { cucsEtherLossStatsHistEntry 17 }

cucsEtherLossStatsHistExcessCollisionDeltaMin OBJECT-TYPE
    SYNTAX       Unsigned64
    MAX-ACCESS   read-only
    STATUS       current
    DESCRIPTION
        "Cisco UCS ether:LossStatsHist:excessCollisionDeltaMin
        managed object property"
    ::= { cucsEtherLossStatsHistEntry 18 }

cucsEtherLossStatsHistGiants OBJECT-TYPE
    SYNTAX       Unsigned64
    MAX-ACCESS   read-only
    STATUS       current
    DESCRIPTION
        "Cisco UCS ether:LossStatsHist:giants managed object property"
    ::= { cucsEtherLossStatsHistEntry 19 }

cucsEtherLossStatsHistGiantsDelta OBJECT-TYPE
    SYNTAX       Unsigned64
    MAX-ACCESS   read-only
    STATUS       current
    DESCRIPTION
        "Cisco UCS ether:LossStatsHist:giantsDelta managed
        object property"
    ::= { cucsEtherLossStatsHistEntry 20 }

cucsEtherLossStatsHistGiantsDeltaAvg OBJECT-TYPE
    SYNTAX       Unsigned64
    MAX-ACCESS   read-only
    STATUS       current
    DESCRIPTION
        "Cisco UCS ether:LossStatsHist:giantsDeltaAvg managed
        object property"
    ::= { cucsEtherLossStatsHistEntry 21 }

cucsEtherLossStatsHistGiantsDeltaMax OBJECT-TYPE
    SYNTAX       Unsigned64
    MAX-ACCESS   read-only
    STATUS       current
    DESCRIPTION
        "Cisco UCS ether:LossStatsHist:giantsDeltaMax managed
        object property"
    ::= { cucsEtherLossStatsHistEntry 22 }

cucsEtherLossStatsHistGiantsDeltaMin OBJECT-TYPE
    SYNTAX       Unsigned64
    MAX-ACCESS   read-only
    STATUS       current
    DESCRIPTION
        "Cisco UCS ether:LossStatsHist:giantsDeltaMin managed
        object property"
    ::= { cucsEtherLossStatsHistEntry 23 }

cucsEtherLossStatsHistId OBJECT-TYPE
    SYNTAX       Unsigned64
    MAX-ACCESS   read-only
    STATUS       current
    DESCRIPTION
        "Cisco UCS ether:LossStatsHist:id managed object property"
    ::= { cucsEtherLossStatsHistEntry 24 }

cucsEtherLossStatsHistLateCollision OBJECT-TYPE
    SYNTAX       Unsigned64
    MAX-ACCESS   read-only
    STATUS       current
    DESCRIPTION
        "Cisco UCS ether:LossStatsHist:lateCollision managed
        object property"
    ::= { cucsEtherLossStatsHistEntry 25 }

cucsEtherLossStatsHistLateCollisionDelta OBJECT-TYPE
    SYNTAX       Unsigned64
    MAX-ACCESS   read-only
    STATUS       current
    DESCRIPTION
        "Cisco UCS ether:LossStatsHist:lateCollisionDelta
        managed object property"
    ::= { cucsEtherLossStatsHistEntry 26 }

cucsEtherLossStatsHistLateCollisionDeltaAvg OBJECT-TYPE
    SYNTAX       Unsigned64
    MAX-ACCESS   read-only
    STATUS       current
    DESCRIPTION
        "Cisco UCS ether:LossStatsHist:lateCollisionDeltaAvg
        managed object property"
    ::= { cucsEtherLossStatsHistEntry 27 }

cucsEtherLossStatsHistLateCollisionDeltaMax OBJECT-TYPE
    SYNTAX       Unsigned64
    MAX-ACCESS   read-only
    STATUS       current
    DESCRIPTION
        "Cisco UCS ether:LossStatsHist:lateCollisionDeltaMax
        managed object property"
    ::= { cucsEtherLossStatsHistEntry 28 }

cucsEtherLossStatsHistLateCollisionDeltaMin OBJECT-TYPE
    SYNTAX       Unsigned64
    MAX-ACCESS   read-only
    STATUS       current
    DESCRIPTION
        "Cisco UCS ether:LossStatsHist:lateCollisionDeltaMin
        managed object property"
    ::= { cucsEtherLossStatsHistEntry 29 }

cucsEtherLossStatsHistMostRecent OBJECT-TYPE
    SYNTAX       TruthValue
    MAX-ACCESS   read-only
    STATUS       current
    DESCRIPTION
        "Cisco UCS ether:LossStatsHist:mostRecent managed object property"
    ::= { cucsEtherLossStatsHistEntry 30 }

cucsEtherLossStatsHistMultiCollision OBJECT-TYPE
    SYNTAX       Unsigned64
    MAX-ACCESS   read-only
    STATUS       current
    DESCRIPTION
        "Cisco UCS ether:LossStatsHist:multiCollision managed
        object property"
    ::= { cucsEtherLossStatsHistEntry 31 }

cucsEtherLossStatsHistMultiCollisionDelta OBJECT-TYPE
    SYNTAX       Unsigned64
    MAX-ACCESS   read-only
    STATUS       current
    DESCRIPTION
        "Cisco UCS ether:LossStatsHist:multiCollisionDelta
        managed object property"
    ::= { cucsEtherLossStatsHistEntry 32 }

cucsEtherLossStatsHistMultiCollisionDeltaAvg OBJECT-TYPE
    SYNTAX       Unsigned64
    MAX-ACCESS   read-only
    STATUS       current
    DESCRIPTION
        "Cisco UCS ether:LossStatsHist:multiCollisionDeltaAvg
        managed object property"
    ::= { cucsEtherLossStatsHistEntry 33 }

cucsEtherLossStatsHistMultiCollisionDeltaMax OBJECT-TYPE
    SYNTAX       Unsigned64
    MAX-ACCESS   read-only
    STATUS       current
    DESCRIPTION
        "Cisco UCS ether:LossStatsHist:multiCollisionDeltaMax
        managed object property"
    ::= { cucsEtherLossStatsHistEntry 34 }

cucsEtherLossStatsHistMultiCollisionDeltaMin OBJECT-TYPE
    SYNTAX       Unsigned64
    MAX-ACCESS   read-only
    STATUS       current
    DESCRIPTION
        "Cisco UCS ether:LossStatsHist:multiCollisionDeltaMin
        managed object property"
    ::= { cucsEtherLossStatsHistEntry 35 }

cucsEtherLossStatsHistSingleCollision OBJECT-TYPE
    SYNTAX       Unsigned64
    MAX-ACCESS   read-only
    STATUS       current
    DESCRIPTION
        "Cisco UCS ether:LossStatsHist:singleCollision
        managed object property"
    ::= { cucsEtherLossStatsHistEntry 36 }

cucsEtherLossStatsHistSingleCollisionDelta OBJECT-TYPE
    SYNTAX       Unsigned64
    MAX-ACCESS   read-only
    STATUS       current
    DESCRIPTION
        "Cisco UCS ether:LossStatsHist:singleCollisionDelta
        managed object property"
    ::= { cucsEtherLossStatsHistEntry 37 }

cucsEtherLossStatsHistSingleCollisionDeltaAvg OBJECT-TYPE
    SYNTAX       Unsigned64
    MAX-ACCESS   read-only
    STATUS       current
    DESCRIPTION
        "Cisco UCS ether:LossStatsHist:singleCollisionDeltaAvg
        managed object property"
    ::= { cucsEtherLossStatsHistEntry 38 }

cucsEtherLossStatsHistSingleCollisionDeltaMax OBJECT-TYPE
    SYNTAX       Unsigned64
    MAX-ACCESS   read-only
    STATUS       current
    DESCRIPTION
        "Cisco UCS ether:LossStatsHist:singleCollisionDeltaMax
        managed object property"
    ::= { cucsEtherLossStatsHistEntry 39 }

cucsEtherLossStatsHistSingleCollisionDeltaMin OBJECT-TYPE
    SYNTAX       Unsigned64
    MAX-ACCESS   read-only
    STATUS       current
    DESCRIPTION
        "Cisco UCS ether:LossStatsHist:singleCollisionDeltaMin
        managed object property"
    ::= { cucsEtherLossStatsHistEntry 40 }

cucsEtherLossStatsHistSuspect OBJECT-TYPE
    SYNTAX       TruthValue
    MAX-ACCESS   read-only
    STATUS       current
    DESCRIPTION
        "Cisco UCS ether:LossStatsHist:suspect managed object property"
    ::= { cucsEtherLossStatsHistEntry 41 }

cucsEtherLossStatsHistSymbol OBJECT-TYPE
    SYNTAX       Unsigned64
    MAX-ACCESS   read-only
    STATUS       current
    DESCRIPTION
        "Cisco UCS ether:LossStatsHist:symbol managed object property"
    ::= { cucsEtherLossStatsHistEntry 42 }

cucsEtherLossStatsHistSymbolDelta OBJECT-TYPE
    SYNTAX       Unsigned64
    MAX-ACCESS   read-only
    STATUS       current
    DESCRIPTION
        "Cisco UCS ether:LossStatsHist:symbolDelta managed
        object property"
    ::= { cucsEtherLossStatsHistEntry 43 }

cucsEtherLossStatsHistSymbolDeltaAvg OBJECT-TYPE
    SYNTAX       Unsigned64
    MAX-ACCESS   read-only
    STATUS       current
    DESCRIPTION
        "Cisco UCS ether:LossStatsHist:symbolDeltaAvg managed
        object property"
    ::= { cucsEtherLossStatsHistEntry 44 }

cucsEtherLossStatsHistSymbolDeltaMax OBJECT-TYPE
    SYNTAX       Unsigned64
    MAX-ACCESS   read-only
    STATUS       current
    DESCRIPTION
        "Cisco UCS ether:LossStatsHist:symbolDeltaMax managed
        object property"
    ::= { cucsEtherLossStatsHistEntry 45 }

cucsEtherLossStatsHistSymbolDeltaMin OBJECT-TYPE
    SYNTAX       Unsigned64
    MAX-ACCESS   read-only
    STATUS       current
    DESCRIPTION
        "Cisco UCS ether:LossStatsHist:symbolDeltaMin managed
        object property"
    ::= { cucsEtherLossStatsHistEntry 46 }

cucsEtherLossStatsHistThresholded OBJECT-TYPE
    SYNTAX       CucsEtherLossStatsHistThresholded
    MAX-ACCESS   read-only
    STATUS       current
    DESCRIPTION
        "Cisco UCS ether:LossStatsHist:thresholded managed
        object property"
    ::= { cucsEtherLossStatsHistEntry 47 }

cucsEtherLossStatsHistTimeCollected OBJECT-TYPE
    SYNTAX       DateAndTime
    MAX-ACCESS   read-only
    STATUS       current
    DESCRIPTION
        "Cisco UCS ether:LossStatsHist:timeCollected managed
        object property"
    ::= { cucsEtherLossStatsHistEntry 48 }

cucsEtherNiErrStatsTable OBJECT-TYPE
    SYNTAX           SEQUENCE OF CucsEtherNiErrStatsEntry
    MAX-ACCESS       not-accessible
    STATUS           current
    DESCRIPTION
        "Cisco UCS ether:NiErrStats managed object table"
    ::= { cucsEtherObjects 30 }

cucsEtherNiErrStatsEntry OBJECT-TYPE
    SYNTAX           CucsEtherNiErrStatsEntry
    MAX-ACCESS       not-accessible
    STATUS           current
    DESCRIPTION
        "Entry for the cucsEtherNiErrStatsTable table."
    INDEX { cucsEtherNiErrStatsInstanceId }
    ::= { cucsEtherNiErrStatsTable 1 }

CucsEtherNiErrStatsEntry ::= SEQUENCE {
    cucsEtherNiErrStatsInstanceId                                    CucsManagedObjectId,
    cucsEtherNiErrStatsDn                                            CucsManagedObjectDn,
    cucsEtherNiErrStatsRn                                            SnmpAdminString,
    cucsEtherNiErrStatsCrc                                           Unsigned64,
    cucsEtherNiErrStatsCrcDelta                                      Counter64,
    cucsEtherNiErrStatsCrcDeltaAvg                                   Unsigned64,
    cucsEtherNiErrStatsCrcDeltaMax                                   Unsigned64,
    cucsEtherNiErrStatsCrcDeltaMin                                   Unsigned64,
    cucsEtherNiErrStatsFrameTx                                       Unsigned64,
    cucsEtherNiErrStatsFrameTxDelta                                  Counter64,
    cucsEtherNiErrStatsFrameTxDeltaAvg                               Unsigned64,
    cucsEtherNiErrStatsFrameTxDeltaMax                               Unsigned64,
    cucsEtherNiErrStatsFrameTxDeltaMin                               Unsigned64,
    cucsEtherNiErrStatsInRange                                       Unsigned64,
    cucsEtherNiErrStatsInRangeDelta                                  Counter64,
    cucsEtherNiErrStatsInRangeDeltaAvg                               Unsigned64,
    cucsEtherNiErrStatsInRangeDeltaMax                               Unsigned64,
    cucsEtherNiErrStatsInRangeDeltaMin                               Unsigned64,
    cucsEtherNiErrStatsIntervals                                     Gauge32,
    cucsEtherNiErrStatsSuspect                                       TruthValue,
    cucsEtherNiErrStatsThresholded                                   CucsEtherNiErrStatsThresholded,
    cucsEtherNiErrStatsTimeCollected                                 DateAndTime,
    cucsEtherNiErrStatsTooLong                                       Unsigned64,
    cucsEtherNiErrStatsTooLongDelta                                  Counter64,
    cucsEtherNiErrStatsTooLongDeltaAvg                               Unsigned64,
    cucsEtherNiErrStatsTooLongDeltaMax                               Unsigned64,
    cucsEtherNiErrStatsTooLongDeltaMin                               Unsigned64,
    cucsEtherNiErrStatsTooShort                                      Unsigned64,
    cucsEtherNiErrStatsTooShortDelta                                 Counter64,
    cucsEtherNiErrStatsTooShortDeltaAvg                              Unsigned64,
    cucsEtherNiErrStatsTooShortDeltaMax                              Unsigned64,
    cucsEtherNiErrStatsTooShortDeltaMin                              Unsigned64,
    cucsEtherNiErrStatsUpdate                                        Gauge32
}

cucsEtherNiErrStatsInstanceId OBJECT-TYPE
    SYNTAX       CucsManagedObjectId
    MAX-ACCESS   not-accessible
    STATUS       current
    DESCRIPTION
        "Instance identifier of the managed object."
    ::= { cucsEtherNiErrStatsEntry 1 }

cucsEtherNiErrStatsDn OBJECT-TYPE
    SYNTAX       CucsManagedObjectDn
    MAX-ACCESS   read-only
    STATUS       current
    DESCRIPTION
        "Cisco UCS ether:NiErrStats:dn managed object property"
    ::= { cucsEtherNiErrStatsEntry 2 }

cucsEtherNiErrStatsRn OBJECT-TYPE
    SYNTAX       SnmpAdminString
    MAX-ACCESS   read-only
    STATUS       current
    DESCRIPTION
        "Cisco UCS ether:NiErrStats:rn managed object property"
    ::= { cucsEtherNiErrStatsEntry 3 }

cucsEtherNiErrStatsCrc OBJECT-TYPE
    SYNTAX       Unsigned64
    MAX-ACCESS   read-only
    STATUS       current
    DESCRIPTION
        "Cisco UCS ether:NiErrStats:crc managed object property"
    ::= { cucsEtherNiErrStatsEntry 4 }

cucsEtherNiErrStatsCrcDelta OBJECT-TYPE
    SYNTAX       Counter64
    MAX-ACCESS   read-only
    STATUS       current
    DESCRIPTION
        "Cisco UCS ether:NiErrStats:crcDelta managed object property"
    ::= { cucsEtherNiErrStatsEntry 5 }

cucsEtherNiErrStatsCrcDeltaAvg OBJECT-TYPE
    SYNTAX       Unsigned64
    MAX-ACCESS   read-only
    STATUS       current
    DESCRIPTION
        "Cisco UCS ether:NiErrStats:crcDeltaAvg managed object property"
    ::= { cucsEtherNiErrStatsEntry 6 }

cucsEtherNiErrStatsCrcDeltaMax OBJECT-TYPE
    SYNTAX       Unsigned64
    MAX-ACCESS   read-only
    STATUS       current
    DESCRIPTION
        "Cisco UCS ether:NiErrStats:crcDeltaMax managed object property"
    ::= { cucsEtherNiErrStatsEntry 7 }

cucsEtherNiErrStatsCrcDeltaMin OBJECT-TYPE
    SYNTAX       Unsigned64
    MAX-ACCESS   read-only
    STATUS       current
    DESCRIPTION
        "Cisco UCS ether:NiErrStats:crcDeltaMin managed object property"
    ::= { cucsEtherNiErrStatsEntry 8 }

cucsEtherNiErrStatsFrameTx OBJECT-TYPE
    SYNTAX       Unsigned64
    MAX-ACCESS   read-only
    STATUS       current
    DESCRIPTION
        "Cisco UCS ether:NiErrStats:frameTx managed object property"
    ::= { cucsEtherNiErrStatsEntry 9 }

cucsEtherNiErrStatsFrameTxDelta OBJECT-TYPE
    SYNTAX       Counter64
    MAX-ACCESS   read-only
    STATUS       current
    DESCRIPTION
        "Cisco UCS ether:NiErrStats:frameTxDelta managed object property"
    ::= { cucsEtherNiErrStatsEntry 10 }

cucsEtherNiErrStatsFrameTxDeltaAvg OBJECT-TYPE
    SYNTAX       Unsigned64
    MAX-ACCESS   read-only
    STATUS       current
    DESCRIPTION
        "Cisco UCS ether:NiErrStats:frameTxDeltaAvg managed
        object property"
    ::= { cucsEtherNiErrStatsEntry 11 }

cucsEtherNiErrStatsFrameTxDeltaMax OBJECT-TYPE
    SYNTAX       Unsigned64
    MAX-ACCESS   read-only
    STATUS       current
    DESCRIPTION
        "Cisco UCS ether:NiErrStats:frameTxDeltaMax managed
        object property"
    ::= { cucsEtherNiErrStatsEntry 12 }

cucsEtherNiErrStatsFrameTxDeltaMin OBJECT-TYPE
    SYNTAX       Unsigned64
    MAX-ACCESS   read-only
    STATUS       current
    DESCRIPTION
        "Cisco UCS ether:NiErrStats:frameTxDeltaMin managed
        object property"
    ::= { cucsEtherNiErrStatsEntry 13 }

cucsEtherNiErrStatsInRange OBJECT-TYPE
    SYNTAX       Unsigned64
    MAX-ACCESS   read-only
    STATUS       current
    DESCRIPTION
        "Cisco UCS ether:NiErrStats:inRange managed object property"
    ::= { cucsEtherNiErrStatsEntry 14 }

cucsEtherNiErrStatsInRangeDelta OBJECT-TYPE
    SYNTAX       Counter64
    MAX-ACCESS   read-only
    STATUS       current
    DESCRIPTION
        "Cisco UCS ether:NiErrStats:inRangeDelta managed object property"
    ::= { cucsEtherNiErrStatsEntry 15 }

cucsEtherNiErrStatsInRangeDeltaAvg OBJECT-TYPE
    SYNTAX       Unsigned64
    MAX-ACCESS   read-only
    STATUS       current
    DESCRIPTION
        "Cisco UCS ether:NiErrStats:inRangeDeltaAvg managed
        object property"
    ::= { cucsEtherNiErrStatsEntry 16 }

cucsEtherNiErrStatsInRangeDeltaMax OBJECT-TYPE
    SYNTAX       Unsigned64
    MAX-ACCESS   read-only
    STATUS       current
    DESCRIPTION
        "Cisco UCS ether:NiErrStats:inRangeDeltaMax managed
        object property"
    ::= { cucsEtherNiErrStatsEntry 17 }

cucsEtherNiErrStatsInRangeDeltaMin OBJECT-TYPE
    SYNTAX       Unsigned64
    MAX-ACCESS   read-only
    STATUS       current
    DESCRIPTION
        "Cisco UCS ether:NiErrStats:inRangeDeltaMin managed
        object property"
    ::= { cucsEtherNiErrStatsEntry 18 }

cucsEtherNiErrStatsIntervals OBJECT-TYPE
    SYNTAX       Gauge32
    MAX-ACCESS   read-only
    STATUS       current
    DESCRIPTION
        "Cisco UCS ether:NiErrStats:intervals managed object property"
    ::= { cucsEtherNiErrStatsEntry 19 }

cucsEtherNiErrStatsSuspect OBJECT-TYPE
    SYNTAX       TruthValue
    MAX-ACCESS   read-only
    STATUS       current
    DESCRIPTION
        "Cisco UCS ether:NiErrStats:suspect managed object property"
    ::= { cucsEtherNiErrStatsEntry 20 }

cucsEtherNiErrStatsThresholded OBJECT-TYPE
    SYNTAX       CucsEtherNiErrStatsThresholded
    MAX-ACCESS   read-only
    STATUS       current
    DESCRIPTION
        "Cisco UCS ether:NiErrStats:thresholded managed object property"
    ::= { cucsEtherNiErrStatsEntry 21 }

cucsEtherNiErrStatsTimeCollected OBJECT-TYPE
    SYNTAX       DateAndTime
    MAX-ACCESS   read-only
    STATUS       current
    DESCRIPTION
        "Cisco UCS ether:NiErrStats:timeCollected managed object property"
    ::= { cucsEtherNiErrStatsEntry 22 }

cucsEtherNiErrStatsTooLong OBJECT-TYPE
    SYNTAX       Unsigned64
    MAX-ACCESS   read-only
    STATUS       current
    DESCRIPTION
        "Cisco UCS ether:NiErrStats:tooLong managed object property"
    ::= { cucsEtherNiErrStatsEntry 23 }

cucsEtherNiErrStatsTooLongDelta OBJECT-TYPE
    SYNTAX       Counter64
    MAX-ACCESS   read-only
    STATUS       current
    DESCRIPTION
        "Cisco UCS ether:NiErrStats:tooLongDelta managed object property"
    ::= { cucsEtherNiErrStatsEntry 24 }

cucsEtherNiErrStatsTooLongDeltaAvg OBJECT-TYPE
    SYNTAX       Unsigned64
    MAX-ACCESS   read-only
    STATUS       current
    DESCRIPTION
        "Cisco UCS ether:NiErrStats:tooLongDeltaAvg managed
        object property"
    ::= { cucsEtherNiErrStatsEntry 25 }

cucsEtherNiErrStatsTooLongDeltaMax OBJECT-TYPE
    SYNTAX       Unsigned64
    MAX-ACCESS   read-only
    STATUS       current
    DESCRIPTION
        "Cisco UCS ether:NiErrStats:tooLongDeltaMax managed
        object property"
    ::= { cucsEtherNiErrStatsEntry 26 }

cucsEtherNiErrStatsTooLongDeltaMin OBJECT-TYPE
    SYNTAX       Unsigned64
    MAX-ACCESS   read-only
    STATUS       current
    DESCRIPTION
        "Cisco UCS ether:NiErrStats:tooLongDeltaMin managed
        object property"
    ::= { cucsEtherNiErrStatsEntry 27 }

cucsEtherNiErrStatsTooShort OBJECT-TYPE
    SYNTAX       Unsigned64
    MAX-ACCESS   read-only
    STATUS       current
    DESCRIPTION
        "Cisco UCS ether:NiErrStats:tooShort managed object property"
    ::= { cucsEtherNiErrStatsEntry 28 }

cucsEtherNiErrStatsTooShortDelta OBJECT-TYPE
    SYNTAX       Counter64
    MAX-ACCESS   read-only
    STATUS       current
    DESCRIPTION
        "Cisco UCS ether:NiErrStats:tooShortDelta managed object property"
    ::= { cucsEtherNiErrStatsEntry 29 }

cucsEtherNiErrStatsTooShortDeltaAvg OBJECT-TYPE
    SYNTAX       Unsigned64
    MAX-ACCESS   read-only
    STATUS       current
    DESCRIPTION
        "Cisco UCS ether:NiErrStats:tooShortDeltaAvg managed
        object property"
    ::= { cucsEtherNiErrStatsEntry 30 }

cucsEtherNiErrStatsTooShortDeltaMax OBJECT-TYPE
    SYNTAX       Unsigned64
    MAX-ACCESS   read-only
    STATUS       current
    DESCRIPTION
        "Cisco UCS ether:NiErrStats:tooShortDeltaMax managed
        object property"
    ::= { cucsEtherNiErrStatsEntry 31 }

cucsEtherNiErrStatsTooShortDeltaMin OBJECT-TYPE
    SYNTAX       Unsigned64
    MAX-ACCESS   read-only
    STATUS       current
    DESCRIPTION
        "Cisco UCS ether:NiErrStats:tooShortDeltaMin managed
        object property"
    ::= { cucsEtherNiErrStatsEntry 32 }

cucsEtherNiErrStatsUpdate OBJECT-TYPE
    SYNTAX       Gauge32
    MAX-ACCESS   read-only
    STATUS       current
    DESCRIPTION
        "Cisco UCS ether:NiErrStats:update managed object property"
    ::= { cucsEtherNiErrStatsEntry 33 }

cucsEtherNiErrStatsHistTable OBJECT-TYPE
    SYNTAX           SEQUENCE OF CucsEtherNiErrStatsHistEntry
    MAX-ACCESS       not-accessible
    STATUS           current
    DESCRIPTION
        "Cisco UCS ether:NiErrStatsHist managed object table"
    ::= { cucsEtherObjects 31 }

cucsEtherNiErrStatsHistEntry OBJECT-TYPE
    SYNTAX           CucsEtherNiErrStatsHistEntry
    MAX-ACCESS       not-accessible
    STATUS           current
    DESCRIPTION
        "Entry for the cucsEtherNiErrStatsHistTable table."
    INDEX { cucsEtherNiErrStatsHistInstanceId }
    ::= { cucsEtherNiErrStatsHistTable 1 }

CucsEtherNiErrStatsHistEntry ::= SEQUENCE {
    cucsEtherNiErrStatsHistInstanceId                                CucsManagedObjectId,
    cucsEtherNiErrStatsHistDn                                        CucsManagedObjectDn,
    cucsEtherNiErrStatsHistRn                                        SnmpAdminString,
    cucsEtherNiErrStatsHistCrc                                       Unsigned64,
    cucsEtherNiErrStatsHistCrcDelta                                  Unsigned64,
    cucsEtherNiErrStatsHistCrcDeltaAvg                               Unsigned64,
    cucsEtherNiErrStatsHistCrcDeltaMax                               Unsigned64,
    cucsEtherNiErrStatsHistCrcDeltaMin                               Unsigned64,
    cucsEtherNiErrStatsHistFrameTx                                   Unsigned64,
    cucsEtherNiErrStatsHistFrameTxDelta                              Unsigned64,
    cucsEtherNiErrStatsHistFrameTxDeltaAvg                           Unsigned64,
    cucsEtherNiErrStatsHistFrameTxDeltaMax                           Unsigned64,
    cucsEtherNiErrStatsHistFrameTxDeltaMin                           Unsigned64,
    cucsEtherNiErrStatsHistId                                        Unsigned64,
    cucsEtherNiErrStatsHistInRange                                   Unsigned64,
    cucsEtherNiErrStatsHistInRangeDelta                              Unsigned64,
    cucsEtherNiErrStatsHistInRangeDeltaAvg                           Unsigned64,
    cucsEtherNiErrStatsHistInRangeDeltaMax                           Unsigned64,
    cucsEtherNiErrStatsHistInRangeDeltaMin                           Unsigned64,
    cucsEtherNiErrStatsHistMostRecent                                TruthValue,
    cucsEtherNiErrStatsHistSuspect                                   TruthValue,
    cucsEtherNiErrStatsHistThresholded                               CucsEtherNiErrStatsHistThresholded,
    cucsEtherNiErrStatsHistTimeCollected                             DateAndTime,
    cucsEtherNiErrStatsHistTooLong                                   Unsigned64,
    cucsEtherNiErrStatsHistTooLongDelta                              Unsigned64,
    cucsEtherNiErrStatsHistTooLongDeltaAvg                           Unsigned64,
    cucsEtherNiErrStatsHistTooLongDeltaMax                           Unsigned64,
    cucsEtherNiErrStatsHistTooLongDeltaMin                           Unsigned64,
    cucsEtherNiErrStatsHistTooShort                                  Unsigned64,
    cucsEtherNiErrStatsHistTooShortDelta                             Unsigned64,
    cucsEtherNiErrStatsHistTooShortDeltaAvg                          Unsigned64,
    cucsEtherNiErrStatsHistTooShortDeltaMax                          Unsigned64,
    cucsEtherNiErrStatsHistTooShortDeltaMin                          Unsigned64
}

cucsEtherNiErrStatsHistInstanceId OBJECT-TYPE
    SYNTAX       CucsManagedObjectId
    MAX-ACCESS   not-accessible
    STATUS       current
    DESCRIPTION
        "Instance identifier of the managed object."
    ::= { cucsEtherNiErrStatsHistEntry 1 }

cucsEtherNiErrStatsHistDn OBJECT-TYPE
    SYNTAX       CucsManagedObjectDn
    MAX-ACCESS   read-only
    STATUS       current
    DESCRIPTION
        "Cisco UCS ether:NiErrStatsHist:dn managed object property"
    ::= { cucsEtherNiErrStatsHistEntry 2 }

cucsEtherNiErrStatsHistRn OBJECT-TYPE
    SYNTAX       SnmpAdminString
    MAX-ACCESS   read-only
    STATUS       current
    DESCRIPTION
        "Cisco UCS ether:NiErrStatsHist:rn managed object property"
    ::= { cucsEtherNiErrStatsHistEntry 3 }

cucsEtherNiErrStatsHistCrc OBJECT-TYPE
    SYNTAX       Unsigned64
    MAX-ACCESS   read-only
    STATUS       current
    DESCRIPTION
        "Cisco UCS ether:NiErrStatsHist:crc managed object property"
    ::= { cucsEtherNiErrStatsHistEntry 4 }

cucsEtherNiErrStatsHistCrcDelta OBJECT-TYPE
    SYNTAX       Unsigned64
    MAX-ACCESS   read-only
    STATUS       current
    DESCRIPTION
        "Cisco UCS ether:NiErrStatsHist:crcDelta managed object property"
    ::= { cucsEtherNiErrStatsHistEntry 5 }

cucsEtherNiErrStatsHistCrcDeltaAvg OBJECT-TYPE
    SYNTAX       Unsigned64
    MAX-ACCESS   read-only
    STATUS       current
    DESCRIPTION
        "Cisco UCS ether:NiErrStatsHist:crcDeltaAvg managed
        object property"
    ::= { cucsEtherNiErrStatsHistEntry 6 }

cucsEtherNiErrStatsHistCrcDeltaMax OBJECT-TYPE
    SYNTAX       Unsigned64
    MAX-ACCESS   read-only
    STATUS       current
    DESCRIPTION
        "Cisco UCS ether:NiErrStatsHist:crcDeltaMax managed
        object property"
    ::= { cucsEtherNiErrStatsHistEntry 7 }

cucsEtherNiErrStatsHistCrcDeltaMin OBJECT-TYPE
    SYNTAX       Unsigned64
    MAX-ACCESS   read-only
    STATUS       current
    DESCRIPTION
        "Cisco UCS ether:NiErrStatsHist:crcDeltaMin managed
        object property"
    ::= { cucsEtherNiErrStatsHistEntry 8 }

cucsEtherNiErrStatsHistFrameTx OBJECT-TYPE
    SYNTAX       Unsigned64
    MAX-ACCESS   read-only
    STATUS       current
    DESCRIPTION
        "Cisco UCS ether:NiErrStatsHist:frameTx managed object property"
    ::= { cucsEtherNiErrStatsHistEntry 9 }

cucsEtherNiErrStatsHistFrameTxDelta OBJECT-TYPE
    SYNTAX       Unsigned64
    MAX-ACCESS   read-only
    STATUS       current
    DESCRIPTION
        "Cisco UCS ether:NiErrStatsHist:frameTxDelta managed
        object property"
    ::= { cucsEtherNiErrStatsHistEntry 10 }

cucsEtherNiErrStatsHistFrameTxDeltaAvg OBJECT-TYPE
    SYNTAX       Unsigned64
    MAX-ACCESS   read-only
    STATUS       current
    DESCRIPTION
        "Cisco UCS ether:NiErrStatsHist:frameTxDeltaAvg
        managed object property"
    ::= { cucsEtherNiErrStatsHistEntry 11 }

cucsEtherNiErrStatsHistFrameTxDeltaMax OBJECT-TYPE
    SYNTAX       Unsigned64
    MAX-ACCESS   read-only
    STATUS       current
    DESCRIPTION
        "Cisco UCS ether:NiErrStatsHist:frameTxDeltaMax
        managed object property"
    ::= { cucsEtherNiErrStatsHistEntry 12 }

cucsEtherNiErrStatsHistFrameTxDeltaMin OBJECT-TYPE
    SYNTAX       Unsigned64
    MAX-ACCESS   read-only
    STATUS       current
    DESCRIPTION
        "Cisco UCS ether:NiErrStatsHist:frameTxDeltaMin
        managed object property"
    ::= { cucsEtherNiErrStatsHistEntry 13 }

cucsEtherNiErrStatsHistId OBJECT-TYPE
    SYNTAX       Unsigned64
    MAX-ACCESS   read-only
    STATUS       current
    DESCRIPTION
        "Cisco UCS ether:NiErrStatsHist:id managed object property"
    ::= { cucsEtherNiErrStatsHistEntry 14 }

cucsEtherNiErrStatsHistInRange OBJECT-TYPE
    SYNTAX       Unsigned64
    MAX-ACCESS   read-only
    STATUS       current
    DESCRIPTION
        "Cisco UCS ether:NiErrStatsHist:inRange managed object property"
    ::= { cucsEtherNiErrStatsHistEntry 15 }

cucsEtherNiErrStatsHistInRangeDelta OBJECT-TYPE
    SYNTAX       Unsigned64
    MAX-ACCESS   read-only
    STATUS       current
    DESCRIPTION
        "Cisco UCS ether:NiErrStatsHist:inRangeDelta managed
        object property"
    ::= { cucsEtherNiErrStatsHistEntry 16 }

cucsEtherNiErrStatsHistInRangeDeltaAvg OBJECT-TYPE
    SYNTAX       Unsigned64
    MAX-ACCESS   read-only
    STATUS       current
    DESCRIPTION
        "Cisco UCS ether:NiErrStatsHist:inRangeDeltaAvg
        managed object property"
    ::= { cucsEtherNiErrStatsHistEntry 17 }

cucsEtherNiErrStatsHistInRangeDeltaMax OBJECT-TYPE
    SYNTAX       Unsigned64
    MAX-ACCESS   read-only
    STATUS       current
    DESCRIPTION
        "Cisco UCS ether:NiErrStatsHist:inRangeDeltaMax
        managed object property"
    ::= { cucsEtherNiErrStatsHistEntry 18 }

cucsEtherNiErrStatsHistInRangeDeltaMin OBJECT-TYPE
    SYNTAX       Unsigned64
    MAX-ACCESS   read-only
    STATUS       current
    DESCRIPTION
        "Cisco UCS ether:NiErrStatsHist:inRangeDeltaMin
        managed object property"
    ::= { cucsEtherNiErrStatsHistEntry 19 }

cucsEtherNiErrStatsHistMostRecent OBJECT-TYPE
    SYNTAX       TruthValue
    MAX-ACCESS   read-only
    STATUS       current
    DESCRIPTION
        "Cisco UCS ether:NiErrStatsHist:mostRecent managed
        object property"
    ::= { cucsEtherNiErrStatsHistEntry 20 }

cucsEtherNiErrStatsHistSuspect OBJECT-TYPE
    SYNTAX       TruthValue
    MAX-ACCESS   read-only
    STATUS       current
    DESCRIPTION
        "Cisco UCS ether:NiErrStatsHist:suspect managed object property"
    ::= { cucsEtherNiErrStatsHistEntry 21 }

cucsEtherNiErrStatsHistThresholded OBJECT-TYPE
    SYNTAX       CucsEtherNiErrStatsHistThresholded
    MAX-ACCESS   read-only
    STATUS       current
    DESCRIPTION
        "Cisco UCS ether:NiErrStatsHist:thresholded managed
        object property"
    ::= { cucsEtherNiErrStatsHistEntry 22 }

cucsEtherNiErrStatsHistTimeCollected OBJECT-TYPE
    SYNTAX       DateAndTime
    MAX-ACCESS   read-only
    STATUS       current
    DESCRIPTION
        "Cisco UCS ether:NiErrStatsHist:timeCollected managed
        object property"
    ::= { cucsEtherNiErrStatsHistEntry 23 }

cucsEtherNiErrStatsHistTooLong OBJECT-TYPE
    SYNTAX       Unsigned64
    MAX-ACCESS   read-only
    STATUS       current
    DESCRIPTION
        "Cisco UCS ether:NiErrStatsHist:tooLong managed object property"
    ::= { cucsEtherNiErrStatsHistEntry 24 }

cucsEtherNiErrStatsHistTooLongDelta OBJECT-TYPE
    SYNTAX       Unsigned64
    MAX-ACCESS   read-only
    STATUS       current
    DESCRIPTION
        "Cisco UCS ether:NiErrStatsHist:tooLongDelta managed
        object property"
    ::= { cucsEtherNiErrStatsHistEntry 25 }

cucsEtherNiErrStatsHistTooLongDeltaAvg OBJECT-TYPE
    SYNTAX       Unsigned64
    MAX-ACCESS   read-only
    STATUS       current
    DESCRIPTION
        "Cisco UCS ether:NiErrStatsHist:tooLongDeltaAvg
        managed object property"
    ::= { cucsEtherNiErrStatsHistEntry 26 }

cucsEtherNiErrStatsHistTooLongDeltaMax OBJECT-TYPE
    SYNTAX       Unsigned64
    MAX-ACCESS   read-only
    STATUS       current
    DESCRIPTION
        "Cisco UCS ether:NiErrStatsHist:tooLongDeltaMax
        managed object property"
    ::= { cucsEtherNiErrStatsHistEntry 27 }

cucsEtherNiErrStatsHistTooLongDeltaMin OBJECT-TYPE
    SYNTAX       Unsigned64
    MAX-ACCESS   read-only
    STATUS       current
    DESCRIPTION
        "Cisco UCS ether:NiErrStatsHist:tooLongDeltaMin
        managed object property"
    ::= { cucsEtherNiErrStatsHistEntry 28 }

cucsEtherNiErrStatsHistTooShort OBJECT-TYPE
    SYNTAX       Unsigned64
    MAX-ACCESS   read-only
    STATUS       current
    DESCRIPTION
        "Cisco UCS ether:NiErrStatsHist:tooShort managed object property"
    ::= { cucsEtherNiErrStatsHistEntry 29 }

cucsEtherNiErrStatsHistTooShortDelta OBJECT-TYPE
    SYNTAX       Unsigned64
    MAX-ACCESS   read-only
    STATUS       current
    DESCRIPTION
        "Cisco UCS ether:NiErrStatsHist:tooShortDelta managed
        object property"
    ::= { cucsEtherNiErrStatsHistEntry 30 }

cucsEtherNiErrStatsHistTooShortDeltaAvg OBJECT-TYPE
    SYNTAX       Unsigned64
    MAX-ACCESS   read-only
    STATUS       current
    DESCRIPTION
        "Cisco UCS ether:NiErrStatsHist:tooShortDeltaAvg
        managed object property"
    ::= { cucsEtherNiErrStatsHistEntry 31 }

cucsEtherNiErrStatsHistTooShortDeltaMax OBJECT-TYPE
    SYNTAX       Unsigned64
    MAX-ACCESS   read-only
    STATUS       current
    DESCRIPTION
        "Cisco UCS ether:NiErrStatsHist:tooShortDeltaMax
        managed object property"
    ::= { cucsEtherNiErrStatsHistEntry 32 }

cucsEtherNiErrStatsHistTooShortDeltaMin OBJECT-TYPE
    SYNTAX       Unsigned64
    MAX-ACCESS   read-only
    STATUS       current
    DESCRIPTION
        "Cisco UCS ether:NiErrStatsHist:tooShortDeltaMin
        managed object property"
    ::= { cucsEtherNiErrStatsHistEntry 33 }

cucsEtherNicIfConfigTable OBJECT-TYPE
    SYNTAX           SEQUENCE OF CucsEtherNicIfConfigEntry
    MAX-ACCESS       not-accessible
    STATUS           current
    DESCRIPTION
        "Cisco UCS ether:NicIfConfig managed object table"
    ::= { cucsEtherObjects 5 }

cucsEtherNicIfConfigEntry OBJECT-TYPE
    SYNTAX           CucsEtherNicIfConfigEntry
    MAX-ACCESS       not-accessible
    STATUS           current
    DESCRIPTION
        "Entry for the cucsEtherNicIfConfigTable table."
    INDEX { cucsEtherNicIfConfigInstanceId }
    ::= { cucsEtherNicIfConfigTable 1 }

CucsEtherNicIfConfigEntry ::= SEQUENCE {
    cucsEtherNicIfConfigInstanceId                                   CucsManagedObjectId,
    cucsEtherNicIfConfigDn                                           CucsManagedObjectDn,
    cucsEtherNicIfConfigRn                                           SnmpAdminString
}

cucsEtherNicIfConfigInstanceId OBJECT-TYPE
    SYNTAX       CucsManagedObjectId
    MAX-ACCESS   not-accessible
    STATUS       current
    DESCRIPTION
        "Instance identifier of the managed object."
    ::= { cucsEtherNicIfConfigEntry 1 }

cucsEtherNicIfConfigDn OBJECT-TYPE
    SYNTAX       CucsManagedObjectDn
    MAX-ACCESS   read-only
    STATUS       current
    DESCRIPTION
        "Cisco UCS ether:NicIfConfig:dn managed object property"
    ::= { cucsEtherNicIfConfigEntry 2 }

cucsEtherNicIfConfigRn OBJECT-TYPE
    SYNTAX       SnmpAdminString
    MAX-ACCESS   read-only
    STATUS       current
    DESCRIPTION
        "Cisco UCS ether:NicIfConfig:rn managed object property"
    ::= { cucsEtherNicIfConfigEntry 3 }

cucsEtherPIoTable OBJECT-TYPE
    SYNTAX           SEQUENCE OF CucsEtherPIoEntry
    MAX-ACCESS       not-accessible
    STATUS           current
    DESCRIPTION
        "Cisco UCS ether:PIo managed object table"
    ::= { cucsEtherObjects 6 }

cucsEtherPIoEntry OBJECT-TYPE
    SYNTAX           CucsEtherPIoEntry
    MAX-ACCESS       not-accessible
    STATUS           current
    DESCRIPTION
        "Entry for the cucsEtherPIoTable table."
    INDEX { cucsEtherPIoInstanceId }
    ::= { cucsEtherPIoTable 1 }

CucsEtherPIoEntry ::= SEQUENCE {
    cucsEtherPIoInstanceId                                           CucsManagedObjectId,
    cucsEtherPIoDn                                                   CucsManagedObjectDn,
    cucsEtherPIoRn                                                   SnmpAdminString,
    cucsEtherPIoAdminState                                           CucsFabricAdminState,
    cucsEtherPIoChassisId                                            Gauge32,
    cucsEtherPIoEncap                                                CucsPortEncap,
    cucsEtherPIoEpDn                                                 SnmpAdminString,
    cucsEtherPIoFltAggr                                              Unsigned64,
    cucsEtherPIoIfRole                                               CucsNetworkPortRole,
    cucsEtherPIoIfType                                               CucsNetworkPhysEpIfType,
    cucsEtherPIoLocale                                               CucsNetworkLocale,
    cucsEtherPIoMac                                                  MacAddress,
    cucsEtherPIoMode                                                 CucsPortMode,
    cucsEtherPIoModel                                                SnmpAdminString,
    cucsEtherPIoName                                                 SnmpAdminString,
    cucsEtherPIoOperSpeed                                            CucsPortEthSpeed,
    cucsEtherPIoOperState                                            CucsNetworkPortOperState,
    cucsEtherPIoPeerDn                                               SnmpAdminString,
    cucsEtherPIoPeerPortId                                           Gauge32,
    cucsEtherPIoPeerSlotId                                           Gauge32,
    cucsEtherPIoPortId                                               Gauge32,
    cucsEtherPIoRevision                                             SnmpAdminString,
    cucsEtherPIoSerial                                               SnmpAdminString,
    cucsEtherPIoSlotId                                               Gauge32,
    cucsEtherPIoStateQual                                            SnmpAdminString,
    cucsEtherPIoSwitchId                                             CucsNetworkSwitchId,
    cucsEtherPIoTransport                                            CucsNetworkTransport,
    cucsEtherPIoTs                                                   DateAndTime,
    cucsEtherPIoType                                                 CucsNetworkConnectionType,
    cucsEtherPIoUsrLbl                                               SnmpAdminString,
    cucsEtherPIoVendor                                               SnmpAdminString,
    cucsEtherPIoFsmDescr                                             SnmpAdminString,
    cucsEtherPIoFsmPrev                                              SnmpAdminString,
    cucsEtherPIoFsmProgr                                             Gauge32,
    cucsEtherPIoFsmRmtInvErrCode                                     Gauge32,
    cucsEtherPIoFsmRmtInvErrDescr                                    SnmpAdminString,
    cucsEtherPIoFsmRmtInvRslt                                        CucsConditionRemoteInvRslt,
    cucsEtherPIoFsmStageDescr                                        SnmpAdminString,
    cucsEtherPIoFsmStamp                                             DateAndTime,
    cucsEtherPIoFsmStatus                                            SnmpAdminString,
    cucsEtherPIoFsmTry                                               Gauge32,
    cucsEtherPIoLicGP                                                Unsigned64,
    cucsEtherPIoLicState                                             CucsLicenseState,
    cucsEtherPIoXcvrType                                             CucsEquipmentXcvrType,
    cucsEtherPIoPeerChassisId                                        Gauge32,
    cucsEtherPIoAdminTransport                                       CucsNetworkTransport,
    cucsEtherPIoLc                                                   CucsFsmLifecycle,
    cucsEtherPIoUnifiedPort                                          TruthValue,
    cucsEtherPIoIsPortChannelMember                                  TruthValue,
    cucsEtherPIoAggrPortId                                           Gauge32,
    cucsEtherPIoPeerAggrPortId                                       Gauge32,
    cucsEtherPIoNonCR4                                               TruthValue
}

cucsEtherPIoInstanceId OBJECT-TYPE
    SYNTAX       CucsManagedObjectId
    MAX-ACCESS   not-accessible
    STATUS       current
    DESCRIPTION
        "Instance identifier of the managed object."
    ::= { cucsEtherPIoEntry 1 }

cucsEtherPIoDn OBJECT-TYPE
    SYNTAX       CucsManagedObjectDn
    MAX-ACCESS   read-only
    STATUS       current
    DESCRIPTION
        "Cisco UCS ether:PIo:dn managed object property"
    ::= { cucsEtherPIoEntry 2 }

cucsEtherPIoRn OBJECT-TYPE
    SYNTAX       SnmpAdminString
    MAX-ACCESS   read-only
    STATUS       current
    DESCRIPTION
        "Cisco UCS ether:PIo:rn managed object property"
    ::= { cucsEtherPIoEntry 3 }

cucsEtherPIoAdminState OBJECT-TYPE
    SYNTAX       CucsFabricAdminState
    MAX-ACCESS   read-only
    STATUS       current
    DESCRIPTION
        "Cisco UCS ether:PIo:adminState managed object property"
    ::= { cucsEtherPIoEntry 4 }

cucsEtherPIoChassisId OBJECT-TYPE
    SYNTAX       Gauge32
    MAX-ACCESS   read-only
    STATUS       current
    DESCRIPTION
        "Cisco UCS ether:PIo:chassisId managed object property"
    ::= { cucsEtherPIoEntry 5 }

cucsEtherPIoEncap OBJECT-TYPE
    SYNTAX       CucsPortEncap
    MAX-ACCESS   read-only
    STATUS       current
    DESCRIPTION
        "Cisco UCS ether:PIo:encap managed object property"
    ::= { cucsEtherPIoEntry 6 }

cucsEtherPIoEpDn OBJECT-TYPE
    SYNTAX       SnmpAdminString
    MAX-ACCESS   read-only
    STATUS       current
    DESCRIPTION
        "Cisco UCS ether:PIo:epDn managed object property"
    ::= { cucsEtherPIoEntry 7 }

cucsEtherPIoFltAggr OBJECT-TYPE
    SYNTAX       Unsigned64
    MAX-ACCESS   read-only
    STATUS       current
    DESCRIPTION
        "Cisco UCS ether:PIo:fltAggr managed object property"
    ::= { cucsEtherPIoEntry 8 }

cucsEtherPIoIfRole OBJECT-TYPE
    SYNTAX       CucsNetworkPortRole
    MAX-ACCESS   read-only
    STATUS       current
    DESCRIPTION
        "Cisco UCS ether:PIo:ifRole managed object property"
    ::= { cucsEtherPIoEntry 9 }

cucsEtherPIoIfType OBJECT-TYPE
    SYNTAX       CucsNetworkPhysEpIfType
    MAX-ACCESS   read-only
    STATUS       current
    DESCRIPTION
        "Cisco UCS ether:PIo:ifType managed object property"
    ::= { cucsEtherPIoEntry 10 }

cucsEtherPIoLocale OBJECT-TYPE
    SYNTAX       CucsNetworkLocale
    MAX-ACCESS   read-only
    STATUS       current
    DESCRIPTION
        "Cisco UCS ether:PIo:locale managed object property"
    ::= { cucsEtherPIoEntry 11 }

cucsEtherPIoMac OBJECT-TYPE
    SYNTAX       MacAddress
    MAX-ACCESS   read-only
    STATUS       current
    DESCRIPTION
        "Cisco UCS ether:PIo:mac managed object property"
    ::= { cucsEtherPIoEntry 12 }

cucsEtherPIoMode OBJECT-TYPE
    SYNTAX       CucsPortMode
    MAX-ACCESS   read-only
    STATUS       current
    DESCRIPTION
        "Cisco UCS ether:PIo:mode managed object property"
    ::= { cucsEtherPIoEntry 13 }

cucsEtherPIoModel OBJECT-TYPE
    SYNTAX       SnmpAdminString
    MAX-ACCESS   read-only
    STATUS       current
    DESCRIPTION
        "Cisco UCS ether:PIo:model managed object property"
    ::= { cucsEtherPIoEntry 14 }

cucsEtherPIoName OBJECT-TYPE
    SYNTAX       SnmpAdminString
    MAX-ACCESS   read-only
    STATUS       current
    DESCRIPTION
        "Cisco UCS ether:PIo:name managed object property"
    ::= { cucsEtherPIoEntry 15 }

cucsEtherPIoOperSpeed OBJECT-TYPE
    SYNTAX       CucsPortEthSpeed
    MAX-ACCESS   read-only
    STATUS       current
    DESCRIPTION
        "Cisco UCS ether:PIo:operSpeed managed object property"
    ::= { cucsEtherPIoEntry 16 }

cucsEtherPIoOperState OBJECT-TYPE
    SYNTAX       CucsNetworkPortOperState
    MAX-ACCESS   read-only
    STATUS       current
    DESCRIPTION
        "Cisco UCS ether:PIo:operState managed object property"
    ::= { cucsEtherPIoEntry 17 }

cucsEtherPIoPeerDn OBJECT-TYPE
    SYNTAX       SnmpAdminString
    MAX-ACCESS   read-only
    STATUS       current
    DESCRIPTION
        "Cisco UCS ether:PIo:peerDn managed object property"
    ::= { cucsEtherPIoEntry 18 }

cucsEtherPIoPeerPortId OBJECT-TYPE
    SYNTAX       Gauge32
    MAX-ACCESS   read-only
    STATUS       current
    DESCRIPTION
        "Cisco UCS ether:PIo:peerPortId managed object property"
    ::= { cucsEtherPIoEntry 19 }

cucsEtherPIoPeerSlotId OBJECT-TYPE
    SYNTAX       Gauge32
    MAX-ACCESS   read-only
    STATUS       current
    DESCRIPTION
        "Cisco UCS ether:PIo:peerSlotId managed object property"
    ::= { cucsEtherPIoEntry 20 }

cucsEtherPIoPortId OBJECT-TYPE
    SYNTAX       Gauge32
    MAX-ACCESS   read-only
    STATUS       current
    DESCRIPTION
        "Cisco UCS ether:PIo:portId managed object property"
    ::= { cucsEtherPIoEntry 21 }

cucsEtherPIoRevision OBJECT-TYPE
    SYNTAX       SnmpAdminString
    MAX-ACCESS   read-only
    STATUS       current
    DESCRIPTION
        "Cisco UCS ether:PIo:revision managed object property"
    ::= { cucsEtherPIoEntry 22 }

cucsEtherPIoSerial OBJECT-TYPE
    SYNTAX       SnmpAdminString
    MAX-ACCESS   read-only
    STATUS       current
    DESCRIPTION
        "Cisco UCS ether:PIo:serial managed object property"
    ::= { cucsEtherPIoEntry 23 }

cucsEtherPIoSlotId OBJECT-TYPE
    SYNTAX       Gauge32
    MAX-ACCESS   read-only
    STATUS       current
    DESCRIPTION
        "Cisco UCS ether:PIo:slotId managed object property"
    ::= { cucsEtherPIoEntry 24 }

cucsEtherPIoStateQual OBJECT-TYPE
    SYNTAX       SnmpAdminString
    MAX-ACCESS   read-only
    STATUS       current
    DESCRIPTION
        "Cisco UCS ether:PIo:stateQual managed object property"
    ::= { cucsEtherPIoEntry 25 }

cucsEtherPIoSwitchId OBJECT-TYPE
    SYNTAX       CucsNetworkSwitchId
    MAX-ACCESS   read-only
    STATUS       current
    DESCRIPTION
        "Cisco UCS ether:PIo:switchId managed object property"
    ::= { cucsEtherPIoEntry 26 }

cucsEtherPIoTransport OBJECT-TYPE
    SYNTAX       CucsNetworkTransport
    MAX-ACCESS   read-only
    STATUS       current
    DESCRIPTION
        "Cisco UCS ether:PIo:transport managed object property"
    ::= { cucsEtherPIoEntry 27 }

cucsEtherPIoTs OBJECT-TYPE
    SYNTAX       DateAndTime
    MAX-ACCESS   read-only
    STATUS       current
    DESCRIPTION
        "Cisco UCS ether:PIo:ts managed object property"
    ::= { cucsEtherPIoEntry 28 }

cucsEtherPIoType OBJECT-TYPE
    SYNTAX       CucsNetworkConnectionType
    MAX-ACCESS   read-only
    STATUS       current
    DESCRIPTION
        "Cisco UCS ether:PIo:type managed object property"
    ::= { cucsEtherPIoEntry 29 }

cucsEtherPIoUsrLbl OBJECT-TYPE
    SYNTAX       SnmpAdminString
    MAX-ACCESS   read-only
    STATUS       current
    DESCRIPTION
        "Cisco UCS ether:PIo:usrLbl managed object property"
    ::= { cucsEtherPIoEntry 30 }

cucsEtherPIoVendor OBJECT-TYPE
    SYNTAX       SnmpAdminString
    MAX-ACCESS   read-only
    STATUS       current
    DESCRIPTION
        "Cisco UCS ether:PIo:vendor managed object property"
    ::= { cucsEtherPIoEntry 31 }

cucsEtherPIoFsmDescr OBJECT-TYPE
    SYNTAX       SnmpAdminString
    MAX-ACCESS   read-only
    STATUS       current
    DESCRIPTION
        "Cisco UCS ether:PIo:fsmDescr managed object property"
    ::= { cucsEtherPIoEntry 32 }

cucsEtherPIoFsmPrev OBJECT-TYPE
    SYNTAX       SnmpAdminString
    MAX-ACCESS   read-only
    STATUS       current
    DESCRIPTION
        "Cisco UCS ether:PIo:fsmPrev managed object property"
    ::= { cucsEtherPIoEntry 33 }

cucsEtherPIoFsmProgr OBJECT-TYPE
    SYNTAX       Gauge32
    MAX-ACCESS   read-only
    STATUS       current
    DESCRIPTION
        "Cisco UCS ether:PIo:fsmProgr managed object property"
    ::= { cucsEtherPIoEntry 34 }

cucsEtherPIoFsmRmtInvErrCode OBJECT-TYPE
    SYNTAX       Gauge32
    MAX-ACCESS   read-only
    STATUS       current
    DESCRIPTION
        "Cisco UCS ether:PIo:fsmRmtInvErrCode managed object property"
    ::= { cucsEtherPIoEntry 35 }

cucsEtherPIoFsmRmtInvErrDescr OBJECT-TYPE
    SYNTAX       SnmpAdminString
    MAX-ACCESS   read-only
    STATUS       current
    DESCRIPTION
        "Cisco UCS ether:PIo:fsmRmtInvErrDescr managed object property"
    ::= { cucsEtherPIoEntry 36 }

cucsEtherPIoFsmRmtInvRslt OBJECT-TYPE
    SYNTAX       CucsConditionRemoteInvRslt
    MAX-ACCESS   read-only
    STATUS       current
    DESCRIPTION
        "Cisco UCS ether:PIo:fsmRmtInvRslt managed object property"
    ::= { cucsEtherPIoEntry 37 }

cucsEtherPIoFsmStageDescr OBJECT-TYPE
    SYNTAX       SnmpAdminString
    MAX-ACCESS   read-only
    STATUS       current
    DESCRIPTION
        "Cisco UCS ether:PIo:fsmStageDescr managed object property"
    ::= { cucsEtherPIoEntry 38 }

cucsEtherPIoFsmStamp OBJECT-TYPE
    SYNTAX       DateAndTime
    MAX-ACCESS   read-only
    STATUS       current
    DESCRIPTION
        "Cisco UCS ether:PIo:fsmStamp managed object property"
    ::= { cucsEtherPIoEntry 39 }

cucsEtherPIoFsmStatus OBJECT-TYPE
    SYNTAX       SnmpAdminString
    MAX-ACCESS   read-only
    STATUS       current
    DESCRIPTION
        "Cisco UCS ether:PIo:fsmStatus managed object property"
    ::= { cucsEtherPIoEntry 40 }

cucsEtherPIoFsmTry OBJECT-TYPE
    SYNTAX       Gauge32
    MAX-ACCESS   read-only
    STATUS       current
    DESCRIPTION
        "Cisco UCS ether:PIo:fsmTry managed object property"
    ::= { cucsEtherPIoEntry 41 }

cucsEtherPIoLicGP OBJECT-TYPE
    SYNTAX       Unsigned64
    MAX-ACCESS   read-only
    STATUS       current
    DESCRIPTION
        "Cisco UCS ether:PIo:licGP managed object property"
    ::= { cucsEtherPIoEntry 42 }

cucsEtherPIoLicState OBJECT-TYPE
    SYNTAX       CucsLicenseState
    MAX-ACCESS   read-only
    STATUS       current
    DESCRIPTION
        "Cisco UCS ether:PIo:licState managed object property"
    ::= { cucsEtherPIoEntry 43 }

cucsEtherPIoXcvrType OBJECT-TYPE
    SYNTAX       CucsEquipmentXcvrType
    MAX-ACCESS   read-only
    STATUS       current
    DESCRIPTION
        "Cisco UCS ether:PIo:xcvrType managed object property"
    ::= { cucsEtherPIoEntry 44 }

cucsEtherPIoPeerChassisId OBJECT-TYPE
    SYNTAX       Gauge32
    MAX-ACCESS   read-only
    STATUS       current
    DESCRIPTION
        "Cisco UCS ether:PIo:peerChassisId managed object property"
    ::= { cucsEtherPIoEntry 45 }

cucsEtherPIoAdminTransport OBJECT-TYPE
    SYNTAX       CucsNetworkTransport
    MAX-ACCESS   read-only
    STATUS       current
    DESCRIPTION
        "Cisco UCS ether:PIo:adminTransport managed object property"
    ::= { cucsEtherPIoEntry 46 }

cucsEtherPIoLc OBJECT-TYPE
    SYNTAX       CucsFsmLifecycle
    MAX-ACCESS   read-only
    STATUS       current
    DESCRIPTION
        "Cisco UCS ether:PIo:lc managed object property"
    ::= { cucsEtherPIoEntry 47 }

cucsEtherPIoUnifiedPort OBJECT-TYPE
    SYNTAX       TruthValue
    MAX-ACCESS   read-only
    STATUS       current
    DESCRIPTION
        "Cisco UCS ether:PIo:unifiedPort managed object property"
    ::= { cucsEtherPIoEntry 48 }

cucsEtherPIoIsPortChannelMember OBJECT-TYPE
    SYNTAX       TruthValue
    MAX-ACCESS   read-only
    STATUS       current
    DESCRIPTION
        "Cisco UCS ether:PIo:isPortChannelMember managed object property"
    ::= { cucsEtherPIoEntry 49 }

cucsEtherPIoAggrPortId OBJECT-TYPE
    SYNTAX       Gauge32
    MAX-ACCESS   read-only
    STATUS       current
    DESCRIPTION
        "Cisco UCS ether:PIo:aggrPortId managed object property"
    ::= { cucsEtherPIoEntry 50 }

cucsEtherPIoPeerAggrPortId OBJECT-TYPE
    SYNTAX       Gauge32
    MAX-ACCESS   read-only
    STATUS       current
    DESCRIPTION
        "Cisco UCS ether:PIo:peerAggrPortId managed object property"
    ::= { cucsEtherPIoEntry 51 }

cucsEtherPIoNonCR4 OBJECT-TYPE
    SYNTAX       TruthValue
    MAX-ACCESS   read-only
    STATUS       current
    DESCRIPTION
        "Cisco UCS ether:PIo:nonCR4 managed object property"
    ::= { cucsEtherPIoEntry 52 }

cucsEtherPIoEndPointTable OBJECT-TYPE
    SYNTAX           SEQUENCE OF CucsEtherPIoEndPointEntry
    MAX-ACCESS       not-accessible
    STATUS           current
    DESCRIPTION
        "Cisco UCS ether:PIoEndPoint managed object table"
    ::= { cucsEtherObjects 25 }

cucsEtherPIoEndPointEntry OBJECT-TYPE
    SYNTAX           CucsEtherPIoEndPointEntry
    MAX-ACCESS       not-accessible
    STATUS           current
    DESCRIPTION
        "Entry for the cucsEtherPIoEndPointTable table."
    INDEX { cucsEtherPIoEndPointInstanceId }
    ::= { cucsEtherPIoEndPointTable 1 }

CucsEtherPIoEndPointEntry ::= SEQUENCE {
    cucsEtherPIoEndPointInstanceId                                   CucsManagedObjectId,
    cucsEtherPIoEndPointDn                                           CucsManagedObjectDn,
    cucsEtherPIoEndPointRn                                           SnmpAdminString,
    cucsEtherPIoEndPointEndPointDn                                   SnmpAdminString,
    cucsEtherPIoEndPointEpCloudType                                  CucsEtherCloudType,
    cucsEtherPIoEndPointUsrLbl                                       SnmpAdminString
}

cucsEtherPIoEndPointInstanceId OBJECT-TYPE
    SYNTAX       CucsManagedObjectId
    MAX-ACCESS   not-accessible
    STATUS       current
    DESCRIPTION
        "Instance identifier of the managed object."
    ::= { cucsEtherPIoEndPointEntry 1 }

cucsEtherPIoEndPointDn OBJECT-TYPE
    SYNTAX       CucsManagedObjectDn
    MAX-ACCESS   read-only
    STATUS       current
    DESCRIPTION
        "Cisco UCS ether:PIoEndPoint:dn managed object property"
    ::= { cucsEtherPIoEndPointEntry 2 }

cucsEtherPIoEndPointRn OBJECT-TYPE
    SYNTAX       SnmpAdminString
    MAX-ACCESS   read-only
    STATUS       current
    DESCRIPTION
        "Cisco UCS ether:PIoEndPoint:rn managed object property"
    ::= { cucsEtherPIoEndPointEntry 3 }

cucsEtherPIoEndPointEndPointDn OBJECT-TYPE
    SYNTAX       SnmpAdminString
    MAX-ACCESS   read-only
    STATUS       current
    DESCRIPTION
        "Cisco UCS ether:PIoEndPoint:EndPointDn managed object property"
    ::= { cucsEtherPIoEndPointEntry 4 }

cucsEtherPIoEndPointEpCloudType OBJECT-TYPE
    SYNTAX       CucsEtherCloudType
    MAX-ACCESS   read-only
    STATUS       current
    DESCRIPTION
        "Cisco UCS ether:PIoEndPoint:epCloudType managed object property"
    ::= { cucsEtherPIoEndPointEntry 5 }

cucsEtherPIoEndPointUsrLbl OBJECT-TYPE
    SYNTAX       SnmpAdminString
    MAX-ACCESS   read-only
    STATUS       current
    DESCRIPTION
        "Cisco UCS ether:PIoEndPoint:usrLbl managed object property"
    ::= { cucsEtherPIoEndPointEntry 6 }

cucsEtherPIoFsmTable OBJECT-TYPE
    SYNTAX           SEQUENCE OF CucsEtherPIoFsmEntry
    MAX-ACCESS       not-accessible
    STATUS           current
    DESCRIPTION
        "Cisco UCS ether:PIoFsm managed object table"
    ::= { cucsEtherObjects 26 }

cucsEtherPIoFsmEntry OBJECT-TYPE
    SYNTAX           CucsEtherPIoFsmEntry
    MAX-ACCESS       not-accessible
    STATUS           current
    DESCRIPTION
        "Entry for the cucsEtherPIoFsmTable table."
    INDEX { cucsEtherPIoFsmInstanceId }
    ::= { cucsEtherPIoFsmTable 1 }

CucsEtherPIoFsmEntry ::= SEQUENCE {
    cucsEtherPIoFsmInstanceId                                        CucsManagedObjectId,
    cucsEtherPIoFsmDn                                                CucsManagedObjectDn,
    cucsEtherPIoFsmRn                                                SnmpAdminString,
    cucsEtherPIoFsmCompletionTime                                    DateAndTime,
    cucsEtherPIoFsmCurrentFsm                                        CucsEtherPIoFsmCurrentFsm,
    cucsEtherPIoFsmDescrData                                         SnmpAdminString,
    cucsEtherPIoFsmFsmStatus                                         CucsFsmFsmStageStatus,
    cucsEtherPIoFsmProgress                                          Gauge32,
    cucsEtherPIoFsmRmtErrCode                                        Gauge32,
    cucsEtherPIoFsmRmtErrDescr                                       SnmpAdminString,
    cucsEtherPIoFsmRmtRslt                                           CucsConditionRemoteInvRslt
}

cucsEtherPIoFsmInstanceId OBJECT-TYPE
    SYNTAX       CucsManagedObjectId
    MAX-ACCESS   not-accessible
    STATUS       current
    DESCRIPTION
        "Instance identifier of the managed object."
    ::= { cucsEtherPIoFsmEntry 1 }

cucsEtherPIoFsmDn OBJECT-TYPE
    SYNTAX       CucsManagedObjectDn
    MAX-ACCESS   read-only
    STATUS       current
    DESCRIPTION
        "Cisco UCS ether:PIoFsm:dn managed object property"
    ::= { cucsEtherPIoFsmEntry 2 }

cucsEtherPIoFsmRn OBJECT-TYPE
    SYNTAX       SnmpAdminString
    MAX-ACCESS   read-only
    STATUS       current
    DESCRIPTION
        "Cisco UCS ether:PIoFsm:rn managed object property"
    ::= { cucsEtherPIoFsmEntry 3 }

cucsEtherPIoFsmCompletionTime OBJECT-TYPE
    SYNTAX       DateAndTime
    MAX-ACCESS   read-only
    STATUS       current
    DESCRIPTION
        "Cisco UCS ether:PIoFsm:completionTime managed object property"
    ::= { cucsEtherPIoFsmEntry 4 }

cucsEtherPIoFsmCurrentFsm OBJECT-TYPE
    SYNTAX       CucsEtherPIoFsmCurrentFsm
    MAX-ACCESS   read-only
    STATUS       current
    DESCRIPTION
        "Cisco UCS ether:PIoFsm:currentFsm managed object property"
    ::= { cucsEtherPIoFsmEntry 5 }

cucsEtherPIoFsmDescrData OBJECT-TYPE
    SYNTAX       SnmpAdminString
    MAX-ACCESS   read-only
    STATUS       current
    DESCRIPTION
        "Cisco UCS ether:PIoFsm:descr managed object property"
    ::= { cucsEtherPIoFsmEntry 6 }

cucsEtherPIoFsmFsmStatus OBJECT-TYPE
    SYNTAX       CucsFsmFsmStageStatus
    MAX-ACCESS   read-only
    STATUS       current
    DESCRIPTION
        "Cisco UCS ether:PIoFsm:fsmStatus managed object property"
    ::= { cucsEtherPIoFsmEntry 7 }

cucsEtherPIoFsmProgress OBJECT-TYPE
    SYNTAX       Gauge32
    MAX-ACCESS   read-only
    STATUS       current
    DESCRIPTION
        "Cisco UCS ether:PIoFsm:progress managed object property"
    ::= { cucsEtherPIoFsmEntry 8 }

cucsEtherPIoFsmRmtErrCode OBJECT-TYPE
    SYNTAX       Gauge32
    MAX-ACCESS   read-only
    STATUS       current
    DESCRIPTION
        "Cisco UCS ether:PIoFsm:rmtErrCode managed object property"
    ::= { cucsEtherPIoFsmEntry 9 }

cucsEtherPIoFsmRmtErrDescr OBJECT-TYPE
    SYNTAX       SnmpAdminString
    MAX-ACCESS   read-only
    STATUS       current
    DESCRIPTION
        "Cisco UCS ether:PIoFsm:rmtErrDescr managed object property"
    ::= { cucsEtherPIoFsmEntry 10 }

cucsEtherPIoFsmRmtRslt OBJECT-TYPE
    SYNTAX       CucsConditionRemoteInvRslt
    MAX-ACCESS   read-only
    STATUS       current
    DESCRIPTION
        "Cisco UCS ether:PIoFsm:rmtRslt managed object property"
    ::= { cucsEtherPIoFsmEntry 11 }

cucsEtherPIoFsmStageTable OBJECT-TYPE
    SYNTAX           SEQUENCE OF CucsEtherPIoFsmStageEntry
    MAX-ACCESS       not-accessible
    STATUS           current
    DESCRIPTION
        "Cisco UCS ether:PIoFsmStage managed object table"
    ::= { cucsEtherObjects 27 }

cucsEtherPIoFsmStageEntry OBJECT-TYPE
    SYNTAX           CucsEtherPIoFsmStageEntry
    MAX-ACCESS       not-accessible
    STATUS           current
    DESCRIPTION
        "Entry for the cucsEtherPIoFsmStageTable table."
    INDEX { cucsEtherPIoFsmStageInstanceId }
    ::= { cucsEtherPIoFsmStageTable 1 }

CucsEtherPIoFsmStageEntry ::= SEQUENCE {
    cucsEtherPIoFsmStageInstanceId                                   CucsManagedObjectId,
    cucsEtherPIoFsmStageDn                                           CucsManagedObjectDn,
    cucsEtherPIoFsmStageRn                                           SnmpAdminString,
    cucsEtherPIoFsmStageDescrData                                    SnmpAdminString,
    cucsEtherPIoFsmStageLastUpdateTime                               DateAndTime,
    cucsEtherPIoFsmStageName                                         CucsEtherPIoFsmStageName,
    cucsEtherPIoFsmStageOrder                                        Gauge32,
    cucsEtherPIoFsmStageRetry                                        Gauge32,
    cucsEtherPIoFsmStageStageStatus                                  CucsFsmFsmStageStatus
}

cucsEtherPIoFsmStageInstanceId OBJECT-TYPE
    SYNTAX       CucsManagedObjectId
    MAX-ACCESS   not-accessible
    STATUS       current
    DESCRIPTION
        "Instance identifier of the managed object."
    ::= { cucsEtherPIoFsmStageEntry 1 }

cucsEtherPIoFsmStageDn OBJECT-TYPE
    SYNTAX       CucsManagedObjectDn
    MAX-ACCESS   read-only
    STATUS       current
    DESCRIPTION
        "Cisco UCS ether:PIoFsmStage:dn managed object property"
    ::= { cucsEtherPIoFsmStageEntry 2 }

cucsEtherPIoFsmStageRn OBJECT-TYPE
    SYNTAX       SnmpAdminString
    MAX-ACCESS   read-only
    STATUS       current
    DESCRIPTION
        "Cisco UCS ether:PIoFsmStage:rn managed object property"
    ::= { cucsEtherPIoFsmStageEntry 3 }

cucsEtherPIoFsmStageDescrData OBJECT-TYPE
    SYNTAX       SnmpAdminString
    MAX-ACCESS   read-only
    STATUS       current
    DESCRIPTION
        "Cisco UCS ether:PIoFsmStage:descr managed object property"
    ::= { cucsEtherPIoFsmStageEntry 4 }

cucsEtherPIoFsmStageLastUpdateTime OBJECT-TYPE
    SYNTAX       DateAndTime
    MAX-ACCESS   read-only
    STATUS       current
    DESCRIPTION
        "Cisco UCS ether:PIoFsmStage:lastUpdateTime managed
        object property"
    ::= { cucsEtherPIoFsmStageEntry 5 }

cucsEtherPIoFsmStageName OBJECT-TYPE
    SYNTAX       CucsEtherPIoFsmStageName
    MAX-ACCESS   read-only
    STATUS       current
    DESCRIPTION
        "Cisco UCS ether:PIoFsmStage:name managed object property"
    ::= { cucsEtherPIoFsmStageEntry 6 }

cucsEtherPIoFsmStageOrder OBJECT-TYPE
    SYNTAX       Gauge32
    MAX-ACCESS   read-only
    STATUS       current
    DESCRIPTION
        "Cisco UCS ether:PIoFsmStage:order managed object property"
    ::= { cucsEtherPIoFsmStageEntry 7 }

cucsEtherPIoFsmStageRetry OBJECT-TYPE
    SYNTAX       Gauge32
    MAX-ACCESS   read-only
    STATUS       current
    DESCRIPTION
        "Cisco UCS ether:PIoFsmStage:retry managed object property"
    ::= { cucsEtherPIoFsmStageEntry 8 }

cucsEtherPIoFsmStageStageStatus OBJECT-TYPE
    SYNTAX       CucsFsmFsmStageStatus
    MAX-ACCESS   read-only
    STATUS       current
    DESCRIPTION
        "Cisco UCS ether:PIoFsmStage:stageStatus managed object property"
    ::= { cucsEtherPIoFsmStageEntry 9 }

cucsEtherPauseStatsTable OBJECT-TYPE
    SYNTAX           SEQUENCE OF CucsEtherPauseStatsEntry
    MAX-ACCESS       not-accessible
    STATUS           current
    DESCRIPTION
        "Cisco UCS ether:PauseStats managed object table"
    ::= { cucsEtherObjects 7 }

cucsEtherPauseStatsEntry OBJECT-TYPE
    SYNTAX           CucsEtherPauseStatsEntry
    MAX-ACCESS       not-accessible
    STATUS           current
    DESCRIPTION
        "Entry for the cucsEtherPauseStatsTable table."
    INDEX { cucsEtherPauseStatsInstanceId }
    ::= { cucsEtherPauseStatsTable 1 }

CucsEtherPauseStatsEntry ::= SEQUENCE {
    cucsEtherPauseStatsInstanceId                                    CucsManagedObjectId,
    cucsEtherPauseStatsDn                                            CucsManagedObjectDn,
    cucsEtherPauseStatsRn                                            SnmpAdminString,
    cucsEtherPauseStatsIntervals                                     Gauge32,
    cucsEtherPauseStatsRecvPause                                     Unsigned64,
    cucsEtherPauseStatsRecvPauseDelta                                Counter64,
    cucsEtherPauseStatsRecvPauseDeltaAvg                             Unsigned64,
    cucsEtherPauseStatsRecvPauseDeltaMax                             Unsigned64,
    cucsEtherPauseStatsRecvPauseDeltaMin                             Unsigned64,
    cucsEtherPauseStatsResets                                        Unsigned64,
    cucsEtherPauseStatsResetsDelta                                   Counter64,
    cucsEtherPauseStatsResetsDeltaAvg                                Unsigned64,
    cucsEtherPauseStatsResetsDeltaMax                                Unsigned64,
    cucsEtherPauseStatsResetsDeltaMin                                Unsigned64,
    cucsEtherPauseStatsSuspect                                       TruthValue,
    cucsEtherPauseStatsThresholded                                   CucsEtherPauseStatsThresholded,
    cucsEtherPauseStatsTimeCollected                                 DateAndTime,
    cucsEtherPauseStatsUpdate                                        Gauge32,
    cucsEtherPauseStatsXmitPause                                     Unsigned64,
    cucsEtherPauseStatsXmitPauseDelta                                Counter64,
    cucsEtherPauseStatsXmitPauseDeltaAvg                             Unsigned64,
    cucsEtherPauseStatsXmitPauseDeltaMax                             Unsigned64,
    cucsEtherPauseStatsXmitPauseDeltaMin                             Unsigned64
}

cucsEtherPauseStatsInstanceId OBJECT-TYPE
    SYNTAX       CucsManagedObjectId
    MAX-ACCESS   not-accessible
    STATUS       current
    DESCRIPTION
        "Instance identifier of the managed object."
    ::= { cucsEtherPauseStatsEntry 1 }

cucsEtherPauseStatsDn OBJECT-TYPE
    SYNTAX       CucsManagedObjectDn
    MAX-ACCESS   read-only
    STATUS       current
    DESCRIPTION
        "Cisco UCS ether:PauseStats:dn managed object property"
    ::= { cucsEtherPauseStatsEntry 2 }

cucsEtherPauseStatsRn OBJECT-TYPE
    SYNTAX       SnmpAdminString
    MAX-ACCESS   read-only
    STATUS       current
    DESCRIPTION
        "Cisco UCS ether:PauseStats:rn managed object property"
    ::= { cucsEtherPauseStatsEntry 3 }

cucsEtherPauseStatsIntervals OBJECT-TYPE
    SYNTAX       Gauge32
    MAX-ACCESS   read-only
    STATUS       current
    DESCRIPTION
        "Cisco UCS ether:PauseStats:intervals managed object property"
    ::= { cucsEtherPauseStatsEntry 4 }

cucsEtherPauseStatsRecvPause OBJECT-TYPE
    SYNTAX       Unsigned64
    MAX-ACCESS   read-only
    STATUS       current
    DESCRIPTION
        "Cisco UCS ether:PauseStats:recvPause managed object property"
    ::= { cucsEtherPauseStatsEntry 5 }

cucsEtherPauseStatsRecvPauseDelta OBJECT-TYPE
    SYNTAX       Counter64
    MAX-ACCESS   read-only
    STATUS       current
    DESCRIPTION
        "Cisco UCS ether:PauseStats:recvPauseDelta managed
        object property"
    ::= { cucsEtherPauseStatsEntry 6 }

cucsEtherPauseStatsRecvPauseDeltaAvg OBJECT-TYPE
    SYNTAX       Unsigned64
    MAX-ACCESS   read-only
    STATUS       current
    DESCRIPTION
        "Cisco UCS ether:PauseStats:recvPauseDeltaAvg managed
        object property"
    ::= { cucsEtherPauseStatsEntry 7 }

cucsEtherPauseStatsRecvPauseDeltaMax OBJECT-TYPE
    SYNTAX       Unsigned64
    MAX-ACCESS   read-only
    STATUS       current
    DESCRIPTION
        "Cisco UCS ether:PauseStats:recvPauseDeltaMax managed
        object property"
    ::= { cucsEtherPauseStatsEntry 8 }

cucsEtherPauseStatsRecvPauseDeltaMin OBJECT-TYPE
    SYNTAX       Unsigned64
    MAX-ACCESS   read-only
    STATUS       current
    DESCRIPTION
        "Cisco UCS ether:PauseStats:recvPauseDeltaMin managed
        object property"
    ::= { cucsEtherPauseStatsEntry 9 }

cucsEtherPauseStatsResets OBJECT-TYPE
    SYNTAX       Unsigned64
    MAX-ACCESS   read-only
    STATUS       current
    DESCRIPTION
        "Cisco UCS ether:PauseStats:resets managed object property"
    ::= { cucsEtherPauseStatsEntry 10 }

cucsEtherPauseStatsResetsDelta OBJECT-TYPE
    SYNTAX       Counter64
    MAX-ACCESS   read-only
    STATUS       current
    DESCRIPTION
        "Cisco UCS ether:PauseStats:resetsDelta managed object property"
    ::= { cucsEtherPauseStatsEntry 11 }

cucsEtherPauseStatsResetsDeltaAvg OBJECT-TYPE
    SYNTAX       Unsigned64
    MAX-ACCESS   read-only
    STATUS       current
    DESCRIPTION
        "Cisco UCS ether:PauseStats:resetsDeltaAvg managed
        object property"
    ::= { cucsEtherPauseStatsEntry 12 }

cucsEtherPauseStatsResetsDeltaMax OBJECT-TYPE
    SYNTAX       Unsigned64
    MAX-ACCESS   read-only
    STATUS       current
    DESCRIPTION
        "Cisco UCS ether:PauseStats:resetsDeltaMax managed
        object property"
    ::= { cucsEtherPauseStatsEntry 13 }

cucsEtherPauseStatsResetsDeltaMin OBJECT-TYPE
    SYNTAX       Unsigned64
    MAX-ACCESS   read-only
    STATUS       current
    DESCRIPTION
        "Cisco UCS ether:PauseStats:resetsDeltaMin managed
        object property"
    ::= { cucsEtherPauseStatsEntry 14 }

cucsEtherPauseStatsSuspect OBJECT-TYPE
    SYNTAX       TruthValue
    MAX-ACCESS   read-only
    STATUS       current
    DESCRIPTION
        "Cisco UCS ether:PauseStats:suspect managed object property"
    ::= { cucsEtherPauseStatsEntry 15 }

cucsEtherPauseStatsThresholded OBJECT-TYPE
    SYNTAX       CucsEtherPauseStatsThresholded
    MAX-ACCESS   read-only
    STATUS       current
    DESCRIPTION
        "Cisco UCS ether:PauseStats:thresholded managed object property"
    ::= { cucsEtherPauseStatsEntry 16 }

cucsEtherPauseStatsTimeCollected OBJECT-TYPE
    SYNTAX       DateAndTime
    MAX-ACCESS   read-only
    STATUS       current
    DESCRIPTION
        "Cisco UCS ether:PauseStats:timeCollected managed object property"
    ::= { cucsEtherPauseStatsEntry 17 }

cucsEtherPauseStatsUpdate OBJECT-TYPE
    SYNTAX       Gauge32
    MAX-ACCESS   read-only
    STATUS       current
    DESCRIPTION
        "Cisco UCS ether:PauseStats:update managed object property"
    ::= { cucsEtherPauseStatsEntry 18 }

cucsEtherPauseStatsXmitPause OBJECT-TYPE
    SYNTAX       Unsigned64
    MAX-ACCESS   read-only
    STATUS       current
    DESCRIPTION
        "Cisco UCS ether:PauseStats:xmitPause managed object property"
    ::= { cucsEtherPauseStatsEntry 19 }

cucsEtherPauseStatsXmitPauseDelta OBJECT-TYPE
    SYNTAX       Counter64
    MAX-ACCESS   read-only
    STATUS       current
    DESCRIPTION
        "Cisco UCS ether:PauseStats:xmitPauseDelta managed
        object property"
    ::= { cucsEtherPauseStatsEntry 20 }

cucsEtherPauseStatsXmitPauseDeltaAvg OBJECT-TYPE
    SYNTAX       Unsigned64
    MAX-ACCESS   read-only
    STATUS       current
    DESCRIPTION
        "Cisco UCS ether:PauseStats:xmitPauseDeltaAvg managed
        object property"
    ::= { cucsEtherPauseStatsEntry 21 }

cucsEtherPauseStatsXmitPauseDeltaMax OBJECT-TYPE
    SYNTAX       Unsigned64
    MAX-ACCESS   read-only
    STATUS       current
    DESCRIPTION
        "Cisco UCS ether:PauseStats:xmitPauseDeltaMax managed
        object property"
    ::= { cucsEtherPauseStatsEntry 22 }

cucsEtherPauseStatsXmitPauseDeltaMin OBJECT-TYPE
    SYNTAX       Unsigned64
    MAX-ACCESS   read-only
    STATUS       current
    DESCRIPTION
        "Cisco UCS ether:PauseStats:xmitPauseDeltaMin managed
        object property"
    ::= { cucsEtherPauseStatsEntry 23 }

cucsEtherPauseStatsHistTable OBJECT-TYPE
    SYNTAX           SEQUENCE OF CucsEtherPauseStatsHistEntry
    MAX-ACCESS       not-accessible
    STATUS           current
    DESCRIPTION
        "Cisco UCS ether:PauseStatsHist managed object table"
    ::= { cucsEtherObjects 8 }

cucsEtherPauseStatsHistEntry OBJECT-TYPE
    SYNTAX           CucsEtherPauseStatsHistEntry
    MAX-ACCESS       not-accessible
    STATUS           current
    DESCRIPTION
        "Entry for the cucsEtherPauseStatsHistTable table."
    INDEX { cucsEtherPauseStatsHistInstanceId }
    ::= { cucsEtherPauseStatsHistTable 1 }

CucsEtherPauseStatsHistEntry ::= SEQUENCE {
    cucsEtherPauseStatsHistInstanceId                                CucsManagedObjectId,
    cucsEtherPauseStatsHistDn                                        CucsManagedObjectDn,
    cucsEtherPauseStatsHistRn                                        SnmpAdminString,
    cucsEtherPauseStatsHistId                                        Unsigned64,
    cucsEtherPauseStatsHistMostRecent                                TruthValue,
    cucsEtherPauseStatsHistRecvPause                                 Unsigned64,
    cucsEtherPauseStatsHistRecvPauseDelta                            Unsigned64,
    cucsEtherPauseStatsHistRecvPauseDeltaAvg                         Unsigned64,
    cucsEtherPauseStatsHistRecvPauseDeltaMax                         Unsigned64,
    cucsEtherPauseStatsHistRecvPauseDeltaMin                         Unsigned64,
    cucsEtherPauseStatsHistResets                                    Unsigned64,
    cucsEtherPauseStatsHistResetsDelta                               Unsigned64,
    cucsEtherPauseStatsHistResetsDeltaAvg                            Unsigned64,
    cucsEtherPauseStatsHistResetsDeltaMax                            Unsigned64,
    cucsEtherPauseStatsHistResetsDeltaMin                            Unsigned64,
    cucsEtherPauseStatsHistSuspect                                   TruthValue,
    cucsEtherPauseStatsHistThresholded                               CucsEtherPauseStatsHistThresholded,
    cucsEtherPauseStatsHistTimeCollected                             DateAndTime,
    cucsEtherPauseStatsHistXmitPause                                 Unsigned64,
    cucsEtherPauseStatsHistXmitPauseDelta                            Unsigned64,
    cucsEtherPauseStatsHistXmitPauseDeltaAvg                         Unsigned64,
    cucsEtherPauseStatsHistXmitPauseDeltaMax                         Unsigned64,
    cucsEtherPauseStatsHistXmitPauseDeltaMin                         Unsigned64
}

cucsEtherPauseStatsHistInstanceId OBJECT-TYPE
    SYNTAX       CucsManagedObjectId
    MAX-ACCESS   not-accessible
    STATUS       current
    DESCRIPTION
        "Instance identifier of the managed object."
    ::= { cucsEtherPauseStatsHistEntry 1 }

cucsEtherPauseStatsHistDn OBJECT-TYPE
    SYNTAX       CucsManagedObjectDn
    MAX-ACCESS   read-only
    STATUS       current
    DESCRIPTION
        "Cisco UCS ether:PauseStatsHist:dn managed object property"
    ::= { cucsEtherPauseStatsHistEntry 2 }

cucsEtherPauseStatsHistRn OBJECT-TYPE
    SYNTAX       SnmpAdminString
    MAX-ACCESS   read-only
    STATUS       current
    DESCRIPTION
        "Cisco UCS ether:PauseStatsHist:rn managed object property"
    ::= { cucsEtherPauseStatsHistEntry 3 }

cucsEtherPauseStatsHistId OBJECT-TYPE
    SYNTAX       Unsigned64
    MAX-ACCESS   read-only
    STATUS       current
    DESCRIPTION
        "Cisco UCS ether:PauseStatsHist:id managed object property"
    ::= { cucsEtherPauseStatsHistEntry 4 }

cucsEtherPauseStatsHistMostRecent OBJECT-TYPE
    SYNTAX       TruthValue
    MAX-ACCESS   read-only
    STATUS       current
    DESCRIPTION
        "Cisco UCS ether:PauseStatsHist:mostRecent managed
        object property"
    ::= { cucsEtherPauseStatsHistEntry 5 }

cucsEtherPauseStatsHistRecvPause OBJECT-TYPE
    SYNTAX       Unsigned64
    MAX-ACCESS   read-only
    STATUS       current
    DESCRIPTION
        "Cisco UCS ether:PauseStatsHist:recvPause managed object property"
    ::= { cucsEtherPauseStatsHistEntry 6 }

cucsEtherPauseStatsHistRecvPauseDelta OBJECT-TYPE
    SYNTAX       Unsigned64
    MAX-ACCESS   read-only
    STATUS       current
    DESCRIPTION
        "Cisco UCS ether:PauseStatsHist:recvPauseDelta
        managed object property"
    ::= { cucsEtherPauseStatsHistEntry 7 }

cucsEtherPauseStatsHistRecvPauseDeltaAvg OBJECT-TYPE
    SYNTAX       Unsigned64
    MAX-ACCESS   read-only
    STATUS       current
    DESCRIPTION
        "Cisco UCS ether:PauseStatsHist:recvPauseDeltaAvg
        managed object property"
    ::= { cucsEtherPauseStatsHistEntry 8 }

cucsEtherPauseStatsHistRecvPauseDeltaMax OBJECT-TYPE
    SYNTAX       Unsigned64
    MAX-ACCESS   read-only
    STATUS       current
    DESCRIPTION
        "Cisco UCS ether:PauseStatsHist:recvPauseDeltaMax
        managed object property"
    ::= { cucsEtherPauseStatsHistEntry 9 }

cucsEtherPauseStatsHistRecvPauseDeltaMin OBJECT-TYPE
    SYNTAX       Unsigned64
    MAX-ACCESS   read-only
    STATUS       current
    DESCRIPTION
        "Cisco UCS ether:PauseStatsHist:recvPauseDeltaMin
        managed object property"
    ::= { cucsEtherPauseStatsHistEntry 10 }

cucsEtherPauseStatsHistResets OBJECT-TYPE
    SYNTAX       Unsigned64
    MAX-ACCESS   read-only
    STATUS       current
    DESCRIPTION
        "Cisco UCS ether:PauseStatsHist:resets managed object property"
    ::= { cucsEtherPauseStatsHistEntry 11 }

cucsEtherPauseStatsHistResetsDelta OBJECT-TYPE
    SYNTAX       Unsigned64
    MAX-ACCESS   read-only
    STATUS       current
    DESCRIPTION
        "Cisco UCS ether:PauseStatsHist:resetsDelta managed
        object property"
    ::= { cucsEtherPauseStatsHistEntry 12 }

cucsEtherPauseStatsHistResetsDeltaAvg OBJECT-TYPE
    SYNTAX       Unsigned64
    MAX-ACCESS   read-only
    STATUS       current
    DESCRIPTION
        "Cisco UCS ether:PauseStatsHist:resetsDeltaAvg
        managed object property"
    ::= { cucsEtherPauseStatsHistEntry 13 }

cucsEtherPauseStatsHistResetsDeltaMax OBJECT-TYPE
    SYNTAX       Unsigned64
    MAX-ACCESS   read-only
    STATUS       current
    DESCRIPTION
        "Cisco UCS ether:PauseStatsHist:resetsDeltaMax
        managed object property"
    ::= { cucsEtherPauseStatsHistEntry 14 }

cucsEtherPauseStatsHistResetsDeltaMin OBJECT-TYPE
    SYNTAX       Unsigned64
    MAX-ACCESS   read-only
    STATUS       current
    DESCRIPTION
        "Cisco UCS ether:PauseStatsHist:resetsDeltaMin
        managed object property"
    ::= { cucsEtherPauseStatsHistEntry 15 }

cucsEtherPauseStatsHistSuspect OBJECT-TYPE
    SYNTAX       TruthValue
    MAX-ACCESS   read-only
    STATUS       current
    DESCRIPTION
        "Cisco UCS ether:PauseStatsHist:suspect managed object property"
    ::= { cucsEtherPauseStatsHistEntry 16 }

cucsEtherPauseStatsHistThresholded OBJECT-TYPE
    SYNTAX       CucsEtherPauseStatsHistThresholded
    MAX-ACCESS   read-only
    STATUS       current
    DESCRIPTION
        "Cisco UCS ether:PauseStatsHist:thresholded managed
        object property"
    ::= { cucsEtherPauseStatsHistEntry 17 }

cucsEtherPauseStatsHistTimeCollected OBJECT-TYPE
    SYNTAX       DateAndTime
    MAX-ACCESS   read-only
    STATUS       current
    DESCRIPTION
        "Cisco UCS ether:PauseStatsHist:timeCollected managed
        object property"
    ::= { cucsEtherPauseStatsHistEntry 18 }

cucsEtherPauseStatsHistXmitPause OBJECT-TYPE
    SYNTAX       Unsigned64
    MAX-ACCESS   read-only
    STATUS       current
    DESCRIPTION
        "Cisco UCS ether:PauseStatsHist:xmitPause managed object property"
    ::= { cucsEtherPauseStatsHistEntry 19 }

cucsEtherPauseStatsHistXmitPauseDelta OBJECT-TYPE
    SYNTAX       Unsigned64
    MAX-ACCESS   read-only
    STATUS       current
    DESCRIPTION
        "Cisco UCS ether:PauseStatsHist:xmitPauseDelta
        managed object property"
    ::= { cucsEtherPauseStatsHistEntry 20 }

cucsEtherPauseStatsHistXmitPauseDeltaAvg OBJECT-TYPE
    SYNTAX       Unsigned64
    MAX-ACCESS   read-only
    STATUS       current
    DESCRIPTION
        "Cisco UCS ether:PauseStatsHist:xmitPauseDeltaAvg
        managed object property"
    ::= { cucsEtherPauseStatsHistEntry 21 }

cucsEtherPauseStatsHistXmitPauseDeltaMax OBJECT-TYPE
    SYNTAX       Unsigned64
    MAX-ACCESS   read-only
    STATUS       current
    DESCRIPTION
        "Cisco UCS ether:PauseStatsHist:xmitPauseDeltaMax
        managed object property"
    ::= { cucsEtherPauseStatsHistEntry 22 }

cucsEtherPauseStatsHistXmitPauseDeltaMin OBJECT-TYPE
    SYNTAX       Unsigned64
    MAX-ACCESS   read-only
    STATUS       current
    DESCRIPTION
        "Cisco UCS ether:PauseStatsHist:xmitPauseDeltaMin
        managed object property"
    ::= { cucsEtherPauseStatsHistEntry 23 }

cucsEtherPortChanIdElemTable OBJECT-TYPE
    SYNTAX           SEQUENCE OF CucsEtherPortChanIdElemEntry
    MAX-ACCESS       not-accessible
    STATUS           current
    DESCRIPTION
        "Cisco UCS ether:PortChanIdElem managed object table"
    ::= { cucsEtherObjects 16 }

cucsEtherPortChanIdElemEntry OBJECT-TYPE
    SYNTAX           CucsEtherPortChanIdElemEntry
    MAX-ACCESS       not-accessible
    STATUS           current
    DESCRIPTION
        "Entry for the cucsEtherPortChanIdElemTable table."
    INDEX { cucsEtherPortChanIdElemInstanceId }
    ::= { cucsEtherPortChanIdElemTable 1 }

CucsEtherPortChanIdElemEntry ::= SEQUENCE {
    cucsEtherPortChanIdElemInstanceId                                CucsManagedObjectId,
    cucsEtherPortChanIdElemDn                                        CucsManagedObjectDn,
    cucsEtherPortChanIdElemRn                                        SnmpAdminString,
    cucsEtherPortChanIdElemId                                        Gauge32,
    cucsEtherPortChanIdElemAssignedToDn                              SnmpAdminString,
    cucsEtherPortChanIdElemPrevAssignedToDn                          SnmpAdminString
}

cucsEtherPortChanIdElemInstanceId OBJECT-TYPE
    SYNTAX       CucsManagedObjectId
    MAX-ACCESS   not-accessible
    STATUS       current
    DESCRIPTION
        "Instance identifier of the managed object."
    ::= { cucsEtherPortChanIdElemEntry 1 }

cucsEtherPortChanIdElemDn OBJECT-TYPE
    SYNTAX       CucsManagedObjectDn
    MAX-ACCESS   read-only
    STATUS       current
    DESCRIPTION
        "Cisco UCS ether:PortChanIdElem:dn managed object property"
    ::= { cucsEtherPortChanIdElemEntry 2 }

cucsEtherPortChanIdElemRn OBJECT-TYPE
    SYNTAX       SnmpAdminString
    MAX-ACCESS   read-only
    STATUS       current
    DESCRIPTION
        "Cisco UCS ether:PortChanIdElem:rn managed object property"
    ::= { cucsEtherPortChanIdElemEntry 3 }

cucsEtherPortChanIdElemId OBJECT-TYPE
    SYNTAX       Gauge32
    MAX-ACCESS   read-only
    STATUS       current
    DESCRIPTION
        "Cisco UCS ether:PortChanIdElem:id managed object property"
    ::= { cucsEtherPortChanIdElemEntry 4 }

cucsEtherPortChanIdElemAssignedToDn OBJECT-TYPE
    SYNTAX       SnmpAdminString
    MAX-ACCESS   read-only
    STATUS       current
    DESCRIPTION
        "Cisco UCS ether:PortChanIdElem:assignedToDn managed
        object property"
    ::= { cucsEtherPortChanIdElemEntry 5 }

cucsEtherPortChanIdElemPrevAssignedToDn OBJECT-TYPE
    SYNTAX       SnmpAdminString
    MAX-ACCESS   read-only
    STATUS       current
    DESCRIPTION
        "Cisco UCS ether:PortChanIdElem:prevAssignedToDn
        managed object property"
    ::= { cucsEtherPortChanIdElemEntry 6 }

cucsEtherPortChanIdUniverseTable OBJECT-TYPE
    SYNTAX           SEQUENCE OF CucsEtherPortChanIdUniverseEntry
    MAX-ACCESS       not-accessible
    STATUS           current
    DESCRIPTION
        "Cisco UCS ether:PortChanIdUniverse managed object table"
    ::= { cucsEtherObjects 17 }

cucsEtherPortChanIdUniverseEntry OBJECT-TYPE
    SYNTAX           CucsEtherPortChanIdUniverseEntry
    MAX-ACCESS       not-accessible
    STATUS           current
    DESCRIPTION
        "Entry for the cucsEtherPortChanIdUniverseTable table."
    INDEX { cucsEtherPortChanIdUniverseInstanceId }
    ::= { cucsEtherPortChanIdUniverseTable 1 }

CucsEtherPortChanIdUniverseEntry ::= SEQUENCE {
    cucsEtherPortChanIdUniverseInstanceId                            CucsManagedObjectId,
    cucsEtherPortChanIdUniverseDn                                    CucsManagedObjectDn,
    cucsEtherPortChanIdUniverseRn                                    SnmpAdminString
}

cucsEtherPortChanIdUniverseInstanceId OBJECT-TYPE
    SYNTAX       CucsManagedObjectId
    MAX-ACCESS   not-accessible
    STATUS       current
    DESCRIPTION
        "Instance identifier of the managed object."
    ::= { cucsEtherPortChanIdUniverseEntry 1 }

cucsEtherPortChanIdUniverseDn OBJECT-TYPE
    SYNTAX       CucsManagedObjectDn
    MAX-ACCESS   read-only
    STATUS       current
    DESCRIPTION
        "Cisco UCS ether:PortChanIdUniverse:dn managed object property"
    ::= { cucsEtherPortChanIdUniverseEntry 2 }

cucsEtherPortChanIdUniverseRn OBJECT-TYPE
    SYNTAX       SnmpAdminString
    MAX-ACCESS   read-only
    STATUS       current
    DESCRIPTION
        "Cisco UCS ether:PortChanIdUniverse:rn managed object property"
    ::= { cucsEtherPortChanIdUniverseEntry 3 }

cucsEtherRxStatsTable OBJECT-TYPE
    SYNTAX           SEQUENCE OF CucsEtherRxStatsEntry
    MAX-ACCESS       not-accessible
    STATUS           current
    DESCRIPTION
        "Cisco UCS ether:RxStats managed object table"
    ::= { cucsEtherObjects 9 }

cucsEtherRxStatsEntry OBJECT-TYPE
    SYNTAX           CucsEtherRxStatsEntry
    MAX-ACCESS       not-accessible
    STATUS           current
    DESCRIPTION
        "Entry for the cucsEtherRxStatsTable table."
    INDEX { cucsEtherRxStatsInstanceId }
    ::= { cucsEtherRxStatsTable 1 }

CucsEtherRxStatsEntry ::= SEQUENCE {
    cucsEtherRxStatsInstanceId                                       CucsManagedObjectId,
    cucsEtherRxStatsDn                                               CucsManagedObjectDn,
    cucsEtherRxStatsRn                                               SnmpAdminString,
    cucsEtherRxStatsBroadcastPackets                                 Unsigned64,
    cucsEtherRxStatsBroadcastPacketsDelta                            Counter64,
    cucsEtherRxStatsBroadcastPacketsDeltaAvg                         Unsigned64,
    cucsEtherRxStatsBroadcastPacketsDeltaMax                         Unsigned64,
    cucsEtherRxStatsBroadcastPacketsDeltaMin                         Unsigned64,
    cucsEtherRxStatsIntervals                                        Gauge32,
    cucsEtherRxStatsJumboPackets                                     Unsigned64,
    cucsEtherRxStatsJumboPacketsDelta                                Counter64,
    cucsEtherRxStatsJumboPacketsDeltaAvg                             Unsigned64,
    cucsEtherRxStatsJumboPacketsDeltaMax                             Unsigned64,
    cucsEtherRxStatsJumboPacketsDeltaMin                             Unsigned64,
    cucsEtherRxStatsMulticastPackets                                 Unsigned64,
    cucsEtherRxStatsMulticastPacketsDelta                            Counter64,
    cucsEtherRxStatsMulticastPacketsDeltaAvg                         Unsigned64,
    cucsEtherRxStatsMulticastPacketsDeltaMax                         Unsigned64,
    cucsEtherRxStatsMulticastPacketsDeltaMin                         Unsigned64,
    cucsEtherRxStatsSuspect                                          TruthValue,
    cucsEtherRxStatsThresholded                                      CucsEtherRxStatsThresholded,
    cucsEtherRxStatsTimeCollected                                    DateAndTime,
    cucsEtherRxStatsTotalBytes                                       Unsigned64,
    cucsEtherRxStatsTotalBytesDelta                                  Counter64,
    cucsEtherRxStatsTotalBytesDeltaAvg                               Unsigned64,
    cucsEtherRxStatsTotalBytesDeltaMax                               Unsigned64,
    cucsEtherRxStatsTotalBytesDeltaMin                               Unsigned64,
    cucsEtherRxStatsTotalPackets                                     Unsigned64,
    cucsEtherRxStatsTotalPacketsDelta                                Counter64,
    cucsEtherRxStatsTotalPacketsDeltaAvg                             Unsigned64,
    cucsEtherRxStatsTotalPacketsDeltaMax                             Unsigned64,
    cucsEtherRxStatsTotalPacketsDeltaMin                             Unsigned64,
    cucsEtherRxStatsUnicastPackets                                   Unsigned64,
    cucsEtherRxStatsUnicastPacketsDelta                              Counter64,
    cucsEtherRxStatsUnicastPacketsDeltaAvg                           Unsigned64,
    cucsEtherRxStatsUnicastPacketsDeltaMax                           Unsigned64,
    cucsEtherRxStatsUnicastPacketsDeltaMin                           Unsigned64,
    cucsEtherRxStatsUpdate                                           Gauge32
}

cucsEtherRxStatsInstanceId OBJECT-TYPE
    SYNTAX       CucsManagedObjectId
    MAX-ACCESS   not-accessible
    STATUS       current
    DESCRIPTION
        "Instance identifier of the managed object."
    ::= { cucsEtherRxStatsEntry 1 }

cucsEtherRxStatsDn OBJECT-TYPE
    SYNTAX       CucsManagedObjectDn
    MAX-ACCESS   read-only
    STATUS       current
    DESCRIPTION
        "Cisco UCS ether:RxStats:dn managed object property"
    ::= { cucsEtherRxStatsEntry 2 }

cucsEtherRxStatsRn OBJECT-TYPE
    SYNTAX       SnmpAdminString
    MAX-ACCESS   read-only
    STATUS       current
    DESCRIPTION
        "Cisco UCS ether:RxStats:rn managed object property"
    ::= { cucsEtherRxStatsEntry 3 }

cucsEtherRxStatsBroadcastPackets OBJECT-TYPE
    SYNTAX       Unsigned64
    MAX-ACCESS   read-only
    STATUS       current
    DESCRIPTION
        "Cisco UCS ether:RxStats:broadcastPackets managed object property"
    ::= { cucsEtherRxStatsEntry 4 }

cucsEtherRxStatsBroadcastPacketsDelta OBJECT-TYPE
    SYNTAX       Counter64
    MAX-ACCESS   read-only
    STATUS       current
    DESCRIPTION
        "Cisco UCS ether:RxStats:broadcastPacketsDelta
        managed object property"
    ::= { cucsEtherRxStatsEntry 5 }

cucsEtherRxStatsBroadcastPacketsDeltaAvg OBJECT-TYPE
    SYNTAX       Unsigned64
    MAX-ACCESS   read-only
    STATUS       current
    DESCRIPTION
        "Cisco UCS ether:RxStats:broadcastPacketsDeltaAvg
        managed object property"
    ::= { cucsEtherRxStatsEntry 6 }

cucsEtherRxStatsBroadcastPacketsDeltaMax OBJECT-TYPE
    SYNTAX       Unsigned64
    MAX-ACCESS   read-only
    STATUS       current
    DESCRIPTION
        "Cisco UCS ether:RxStats:broadcastPacketsDeltaMax
        managed object property"
    ::= { cucsEtherRxStatsEntry 7 }

cucsEtherRxStatsBroadcastPacketsDeltaMin OBJECT-TYPE
    SYNTAX       Unsigned64
    MAX-ACCESS   read-only
    STATUS       current
    DESCRIPTION
        "Cisco UCS ether:RxStats:broadcastPacketsDeltaMin
        managed object property"
    ::= { cucsEtherRxStatsEntry 8 }

cucsEtherRxStatsIntervals OBJECT-TYPE
    SYNTAX       Gauge32
    MAX-ACCESS   read-only
    STATUS       current
    DESCRIPTION
        "Cisco UCS ether:RxStats:intervals managed object property"
    ::= { cucsEtherRxStatsEntry 9 }

cucsEtherRxStatsJumboPackets OBJECT-TYPE
    SYNTAX       Unsigned64
    MAX-ACCESS   read-only
    STATUS       current
    DESCRIPTION
        "Cisco UCS ether:RxStats:jumboPackets managed object property"
    ::= { cucsEtherRxStatsEntry 10 }

cucsEtherRxStatsJumboPacketsDelta OBJECT-TYPE
    SYNTAX       Counter64
    MAX-ACCESS   read-only
    STATUS       current
    DESCRIPTION
        "Cisco UCS ether:RxStats:jumboPacketsDelta managed
        object property"
    ::= { cucsEtherRxStatsEntry 11 }

cucsEtherRxStatsJumboPacketsDeltaAvg OBJECT-TYPE
    SYNTAX       Unsigned64
    MAX-ACCESS   read-only
    STATUS       current
    DESCRIPTION
        "Cisco UCS ether:RxStats:jumboPacketsDeltaAvg managed
        object property"
    ::= { cucsEtherRxStatsEntry 12 }

cucsEtherRxStatsJumboPacketsDeltaMax OBJECT-TYPE
    SYNTAX       Unsigned64
    MAX-ACCESS   read-only
    STATUS       current
    DESCRIPTION
        "Cisco UCS ether:RxStats:jumboPacketsDeltaMax managed
        object property"
    ::= { cucsEtherRxStatsEntry 13 }

cucsEtherRxStatsJumboPacketsDeltaMin OBJECT-TYPE
    SYNTAX       Unsigned64
    MAX-ACCESS   read-only
    STATUS       current
    DESCRIPTION
        "Cisco UCS ether:RxStats:jumboPacketsDeltaMin managed
        object property"
    ::= { cucsEtherRxStatsEntry 14 }

cucsEtherRxStatsMulticastPackets OBJECT-TYPE
    SYNTAX       Unsigned64
    MAX-ACCESS   read-only
    STATUS       current
    DESCRIPTION
        "Cisco UCS ether:RxStats:multicastPackets managed object property"
    ::= { cucsEtherRxStatsEntry 15 }

cucsEtherRxStatsMulticastPacketsDelta OBJECT-TYPE
    SYNTAX       Counter64
    MAX-ACCESS   read-only
    STATUS       current
    DESCRIPTION
        "Cisco UCS ether:RxStats:multicastPacketsDelta
        managed object property"
    ::= { cucsEtherRxStatsEntry 16 }

cucsEtherRxStatsMulticastPacketsDeltaAvg OBJECT-TYPE
    SYNTAX       Unsigned64
    MAX-ACCESS   read-only
    STATUS       current
    DESCRIPTION
        "Cisco UCS ether:RxStats:multicastPacketsDeltaAvg
        managed object property"
    ::= { cucsEtherRxStatsEntry 17 }

cucsEtherRxStatsMulticastPacketsDeltaMax OBJECT-TYPE
    SYNTAX       Unsigned64
    MAX-ACCESS   read-only
    STATUS       current
    DESCRIPTION
        "Cisco UCS ether:RxStats:multicastPacketsDeltaMax
        managed object property"
    ::= { cucsEtherRxStatsEntry 18 }

cucsEtherRxStatsMulticastPacketsDeltaMin OBJECT-TYPE
    SYNTAX       Unsigned64
    MAX-ACCESS   read-only
    STATUS       current
    DESCRIPTION
        "Cisco UCS ether:RxStats:multicastPacketsDeltaMin
        managed object property"
    ::= { cucsEtherRxStatsEntry 19 }

cucsEtherRxStatsSuspect OBJECT-TYPE
    SYNTAX       TruthValue
    MAX-ACCESS   read-only
    STATUS       current
    DESCRIPTION
        "Cisco UCS ether:RxStats:suspect managed object property"
    ::= { cucsEtherRxStatsEntry 20 }

cucsEtherRxStatsThresholded OBJECT-TYPE
    SYNTAX       CucsEtherRxStatsThresholded
    MAX-ACCESS   read-only
    STATUS       current
    DESCRIPTION
        "Cisco UCS ether:RxStats:thresholded managed object property"
    ::= { cucsEtherRxStatsEntry 21 }

cucsEtherRxStatsTimeCollected OBJECT-TYPE
    SYNTAX       DateAndTime
    MAX-ACCESS   read-only
    STATUS       current
    DESCRIPTION
        "Cisco UCS ether:RxStats:timeCollected managed object property"
    ::= { cucsEtherRxStatsEntry 22 }

cucsEtherRxStatsTotalBytes OBJECT-TYPE
    SYNTAX       Unsigned64
    MAX-ACCESS   read-only
    STATUS       current
    DESCRIPTION
        "Cisco UCS ether:RxStats:totalBytes managed object property"
    ::= { cucsEtherRxStatsEntry 23 }

cucsEtherRxStatsTotalBytesDelta OBJECT-TYPE
    SYNTAX       Counter64
    MAX-ACCESS   read-only
    STATUS       current
    DESCRIPTION
        "Cisco UCS ether:RxStats:totalBytesDelta managed object property"
    ::= { cucsEtherRxStatsEntry 24 }

cucsEtherRxStatsTotalBytesDeltaAvg OBJECT-TYPE
    SYNTAX       Unsigned64
    MAX-ACCESS   read-only
    STATUS       current
    DESCRIPTION
        "Cisco UCS ether:RxStats:totalBytesDeltaAvg managed
        object property"
    ::= { cucsEtherRxStatsEntry 25 }

cucsEtherRxStatsTotalBytesDeltaMax OBJECT-TYPE
    SYNTAX       Unsigned64
    MAX-ACCESS   read-only
    STATUS       current
    DESCRIPTION
        "Cisco UCS ether:RxStats:totalBytesDeltaMax managed
        object property"
    ::= { cucsEtherRxStatsEntry 26 }

cucsEtherRxStatsTotalBytesDeltaMin OBJECT-TYPE
    SYNTAX       Unsigned64
    MAX-ACCESS   read-only
    STATUS       current
    DESCRIPTION
        "Cisco UCS ether:RxStats:totalBytesDeltaMin managed
        object property"
    ::= { cucsEtherRxStatsEntry 27 }

cucsEtherRxStatsTotalPackets OBJECT-TYPE
    SYNTAX       Unsigned64
    MAX-ACCESS   read-only
    STATUS       current
    DESCRIPTION
        "Cisco UCS ether:RxStats:totalPackets managed object property"
    ::= { cucsEtherRxStatsEntry 28 }

cucsEtherRxStatsTotalPacketsDelta OBJECT-TYPE
    SYNTAX       Counter64
    MAX-ACCESS   read-only
    STATUS       current
    DESCRIPTION
        "Cisco UCS ether:RxStats:totalPacketsDelta managed
        object property"
    ::= { cucsEtherRxStatsEntry 29 }

cucsEtherRxStatsTotalPacketsDeltaAvg OBJECT-TYPE
    SYNTAX       Unsigned64
    MAX-ACCESS   read-only
    STATUS       current
    DESCRIPTION
        "Cisco UCS ether:RxStats:totalPacketsDeltaAvg managed
        object property"
    ::= { cucsEtherRxStatsEntry 30 }

cucsEtherRxStatsTotalPacketsDeltaMax OBJECT-TYPE
    SYNTAX       Unsigned64
    MAX-ACCESS   read-only
    STATUS       current
    DESCRIPTION
        "Cisco UCS ether:RxStats:totalPacketsDeltaMax managed
        object property"
    ::= { cucsEtherRxStatsEntry 31 }

cucsEtherRxStatsTotalPacketsDeltaMin OBJECT-TYPE
    SYNTAX       Unsigned64
    MAX-ACCESS   read-only
    STATUS       current
    DESCRIPTION
        "Cisco UCS ether:RxStats:totalPacketsDeltaMin managed
        object property"
    ::= { cucsEtherRxStatsEntry 32 }

cucsEtherRxStatsUnicastPackets OBJECT-TYPE
    SYNTAX       Unsigned64
    MAX-ACCESS   read-only
    STATUS       current
    DESCRIPTION
        "Cisco UCS ether:RxStats:unicastPackets managed object property"
    ::= { cucsEtherRxStatsEntry 33 }

cucsEtherRxStatsUnicastPacketsDelta OBJECT-TYPE
    SYNTAX       Counter64
    MAX-ACCESS   read-only
    STATUS       current
    DESCRIPTION
        "Cisco UCS ether:RxStats:unicastPacketsDelta managed
        object property"
    ::= { cucsEtherRxStatsEntry 34 }

cucsEtherRxStatsUnicastPacketsDeltaAvg OBJECT-TYPE
    SYNTAX       Unsigned64
    MAX-ACCESS   read-only
    STATUS       current
    DESCRIPTION
        "Cisco UCS ether:RxStats:unicastPacketsDeltaAvg
        managed object property"
    ::= { cucsEtherRxStatsEntry 35 }

cucsEtherRxStatsUnicastPacketsDeltaMax OBJECT-TYPE
    SYNTAX       Unsigned64
    MAX-ACCESS   read-only
    STATUS       current
    DESCRIPTION
        "Cisco UCS ether:RxStats:unicastPacketsDeltaMax
        managed object property"
    ::= { cucsEtherRxStatsEntry 36 }

cucsEtherRxStatsUnicastPacketsDeltaMin OBJECT-TYPE
    SYNTAX       Unsigned64
    MAX-ACCESS   read-only
    STATUS       current
    DESCRIPTION
        "Cisco UCS ether:RxStats:unicastPacketsDeltaMin
        managed object property"
    ::= { cucsEtherRxStatsEntry 37 }

cucsEtherRxStatsUpdate OBJECT-TYPE
    SYNTAX       Gauge32
    MAX-ACCESS   read-only
    STATUS       current
    DESCRIPTION
        "Cisco UCS ether:RxStats:update managed object property"
    ::= { cucsEtherRxStatsEntry 38 }

cucsEtherRxStatsHistTable OBJECT-TYPE
    SYNTAX           SEQUENCE OF CucsEtherRxStatsHistEntry
    MAX-ACCESS       not-accessible
    STATUS           current
    DESCRIPTION
        "Cisco UCS ether:RxStatsHist managed object table"
    ::= { cucsEtherObjects 10 }

cucsEtherRxStatsHistEntry OBJECT-TYPE
    SYNTAX           CucsEtherRxStatsHistEntry
    MAX-ACCESS       not-accessible
    STATUS           current
    DESCRIPTION
        "Entry for the cucsEtherRxStatsHistTable table."
    INDEX { cucsEtherRxStatsHistInstanceId }
    ::= { cucsEtherRxStatsHistTable 1 }

CucsEtherRxStatsHistEntry ::= SEQUENCE {
    cucsEtherRxStatsHistInstanceId                                   CucsManagedObjectId,
    cucsEtherRxStatsHistDn                                           CucsManagedObjectDn,
    cucsEtherRxStatsHistRn                                           SnmpAdminString,
    cucsEtherRxStatsHistBroadcastPackets                             Unsigned64,
    cucsEtherRxStatsHistBroadcastPacketsDelta                        Unsigned64,
    cucsEtherRxStatsHistBroadcastPacketsDeltaAvg                     Unsigned64,
    cucsEtherRxStatsHistBroadcastPacketsDeltaMax                     Unsigned64,
    cucsEtherRxStatsHistBroadcastPacketsDeltaMin                     Unsigned64,
    cucsEtherRxStatsHistId                                           Unsigned64,
    cucsEtherRxStatsHistJumboPackets                                 Unsigned64,
    cucsEtherRxStatsHistJumboPacketsDelta                            Unsigned64,
    cucsEtherRxStatsHistJumboPacketsDeltaAvg                         Unsigned64,
    cucsEtherRxStatsHistJumboPacketsDeltaMax                         Unsigned64,
    cucsEtherRxStatsHistJumboPacketsDeltaMin                         Unsigned64,
    cucsEtherRxStatsHistMostRecent                                   TruthValue,
    cucsEtherRxStatsHistMulticastPackets                             Unsigned64,
    cucsEtherRxStatsHistMulticastPacketsDelta                        Unsigned64,
    cucsEtherRxStatsHistMulticastPacketsDeltaAvg                     Unsigned64,
    cucsEtherRxStatsHistMulticastPacketsDeltaMax                     Unsigned64,
    cucsEtherRxStatsHistMulticastPacketsDeltaMin                     Unsigned64,
    cucsEtherRxStatsHistSuspect                                      TruthValue,
    cucsEtherRxStatsHistThresholded                                  CucsEtherRxStatsHistThresholded,
    cucsEtherRxStatsHistTimeCollected                                DateAndTime,
    cucsEtherRxStatsHistTotalBytes                                   Unsigned64,
    cucsEtherRxStatsHistTotalBytesDelta                              Unsigned64,
    cucsEtherRxStatsHistTotalBytesDeltaAvg                           Unsigned64,
    cucsEtherRxStatsHistTotalBytesDeltaMax                           Unsigned64,
    cucsEtherRxStatsHistTotalBytesDeltaMin                           Unsigned64,
    cucsEtherRxStatsHistTotalPackets                                 Unsigned64,
    cucsEtherRxStatsHistTotalPacketsDelta                            Unsigned64,
    cucsEtherRxStatsHistTotalPacketsDeltaAvg                         Unsigned64,
    cucsEtherRxStatsHistTotalPacketsDeltaMax                         Unsigned64,
    cucsEtherRxStatsHistTotalPacketsDeltaMin                         Unsigned64,
    cucsEtherRxStatsHistUnicastPackets                               Unsigned64,
    cucsEtherRxStatsHistUnicastPacketsDelta                          Unsigned64,
    cucsEtherRxStatsHistUnicastPacketsDeltaAvg                       Unsigned64,
    cucsEtherRxStatsHistUnicastPacketsDeltaMax                       Unsigned64,
    cucsEtherRxStatsHistUnicastPacketsDeltaMin                       Unsigned64
}

cucsEtherRxStatsHistInstanceId OBJECT-TYPE
    SYNTAX       CucsManagedObjectId
    MAX-ACCESS   not-accessible
    STATUS       current
    DESCRIPTION
        "Instance identifier of the managed object."
    ::= { cucsEtherRxStatsHistEntry 1 }

cucsEtherRxStatsHistDn OBJECT-TYPE
    SYNTAX       CucsManagedObjectDn
    MAX-ACCESS   read-only
    STATUS       current
    DESCRIPTION
        "Cisco UCS ether:RxStatsHist:dn managed object property"
    ::= { cucsEtherRxStatsHistEntry 2 }

cucsEtherRxStatsHistRn OBJECT-TYPE
    SYNTAX       SnmpAdminString
    MAX-ACCESS   read-only
    STATUS       current
    DESCRIPTION
        "Cisco UCS ether:RxStatsHist:rn managed object property"
    ::= { cucsEtherRxStatsHistEntry 3 }

cucsEtherRxStatsHistBroadcastPackets OBJECT-TYPE
    SYNTAX       Unsigned64
    MAX-ACCESS   read-only
    STATUS       current
    DESCRIPTION
        "Cisco UCS ether:RxStatsHist:broadcastPackets managed
        object property"
    ::= { cucsEtherRxStatsHistEntry 4 }

cucsEtherRxStatsHistBroadcastPacketsDelta OBJECT-TYPE
    SYNTAX       Unsigned64
    MAX-ACCESS   read-only
    STATUS       current
    DESCRIPTION
        "Cisco UCS ether:RxStatsHist:broadcastPacketsDelta
        managed object property"
    ::= { cucsEtherRxStatsHistEntry 5 }

cucsEtherRxStatsHistBroadcastPacketsDeltaAvg OBJECT-TYPE
    SYNTAX       Unsigned64
    MAX-ACCESS   read-only
    STATUS       current
    DESCRIPTION
        "Cisco UCS ether:RxStatsHist:broadcastPacketsDeltaAvg
        managed object property"
    ::= { cucsEtherRxStatsHistEntry 6 }

cucsEtherRxStatsHistBroadcastPacketsDeltaMax OBJECT-TYPE
    SYNTAX       Unsigned64
    MAX-ACCESS   read-only
    STATUS       current
    DESCRIPTION
        "Cisco UCS ether:RxStatsHist:broadcastPacketsDeltaMax
        managed object property"
    ::= { cucsEtherRxStatsHistEntry 7 }

cucsEtherRxStatsHistBroadcastPacketsDeltaMin OBJECT-TYPE
    SYNTAX       Unsigned64
    MAX-ACCESS   read-only
    STATUS       current
    DESCRIPTION
        "Cisco UCS ether:RxStatsHist:broadcastPacketsDeltaMin
        managed object property"
    ::= { cucsEtherRxStatsHistEntry 8 }

cucsEtherRxStatsHistId OBJECT-TYPE
    SYNTAX       Unsigned64
    MAX-ACCESS   read-only
    STATUS       current
    DESCRIPTION
        "Cisco UCS ether:RxStatsHist:id managed object property"
    ::= { cucsEtherRxStatsHistEntry 9 }

cucsEtherRxStatsHistJumboPackets OBJECT-TYPE
    SYNTAX       Unsigned64
    MAX-ACCESS   read-only
    STATUS       current
    DESCRIPTION
        "Cisco UCS ether:RxStatsHist:jumboPackets managed object property"
    ::= { cucsEtherRxStatsHistEntry 10 }

cucsEtherRxStatsHistJumboPacketsDelta OBJECT-TYPE
    SYNTAX       Unsigned64
    MAX-ACCESS   read-only
    STATUS       current
    DESCRIPTION
        "Cisco UCS ether:RxStatsHist:jumboPacketsDelta
        managed object property"
    ::= { cucsEtherRxStatsHistEntry 11 }

cucsEtherRxStatsHistJumboPacketsDeltaAvg OBJECT-TYPE
    SYNTAX       Unsigned64
    MAX-ACCESS   read-only
    STATUS       current
    DESCRIPTION
        "Cisco UCS ether:RxStatsHist:jumboPacketsDeltaAvg
        managed object property"
    ::= { cucsEtherRxStatsHistEntry 12 }

cucsEtherRxStatsHistJumboPacketsDeltaMax OBJECT-TYPE
    SYNTAX       Unsigned64
    MAX-ACCESS   read-only
    STATUS       current
    DESCRIPTION
        "Cisco UCS ether:RxStatsHist:jumboPacketsDeltaMax
        managed object property"
    ::= { cucsEtherRxStatsHistEntry 13 }

cucsEtherRxStatsHistJumboPacketsDeltaMin OBJECT-TYPE
    SYNTAX       Unsigned64
    MAX-ACCESS   read-only
    STATUS       current
    DESCRIPTION
        "Cisco UCS ether:RxStatsHist:jumboPacketsDeltaMin
        managed object property"
    ::= { cucsEtherRxStatsHistEntry 14 }

cucsEtherRxStatsHistMostRecent OBJECT-TYPE
    SYNTAX       TruthValue
    MAX-ACCESS   read-only
    STATUS       current
    DESCRIPTION
        "Cisco UCS ether:RxStatsHist:mostRecent managed object property"
    ::= { cucsEtherRxStatsHistEntry 15 }

cucsEtherRxStatsHistMulticastPackets OBJECT-TYPE
    SYNTAX       Unsigned64
    MAX-ACCESS   read-only
    STATUS       current
    DESCRIPTION
        "Cisco UCS ether:RxStatsHist:multicastPackets managed
        object property"
    ::= { cucsEtherRxStatsHistEntry 16 }

cucsEtherRxStatsHistMulticastPacketsDelta OBJECT-TYPE
    SYNTAX       Unsigned64
    MAX-ACCESS   read-only
    STATUS       current
    DESCRIPTION
        "Cisco UCS ether:RxStatsHist:multicastPacketsDelta
        managed object property"
    ::= { cucsEtherRxStatsHistEntry 17 }

cucsEtherRxStatsHistMulticastPacketsDeltaAvg OBJECT-TYPE
    SYNTAX       Unsigned64
    MAX-ACCESS   read-only
    STATUS       current
    DESCRIPTION
        "Cisco UCS ether:RxStatsHist:multicastPacketsDeltaAvg
        managed object property"
    ::= { cucsEtherRxStatsHistEntry 18 }

cucsEtherRxStatsHistMulticastPacketsDeltaMax OBJECT-TYPE
    SYNTAX       Unsigned64
    MAX-ACCESS   read-only
    STATUS       current
    DESCRIPTION
        "Cisco UCS ether:RxStatsHist:multicastPacketsDeltaMax
        managed object property"
    ::= { cucsEtherRxStatsHistEntry 19 }

cucsEtherRxStatsHistMulticastPacketsDeltaMin OBJECT-TYPE
    SYNTAX       Unsigned64
    MAX-ACCESS   read-only
    STATUS       current
    DESCRIPTION
        "Cisco UCS ether:RxStatsHist:multicastPacketsDeltaMin
        managed object property"
    ::= { cucsEtherRxStatsHistEntry 20 }

cucsEtherRxStatsHistSuspect OBJECT-TYPE
    SYNTAX       TruthValue
    MAX-ACCESS   read-only
    STATUS       current
    DESCRIPTION
        "Cisco UCS ether:RxStatsHist:suspect managed object property"
    ::= { cucsEtherRxStatsHistEntry 21 }

cucsEtherRxStatsHistThresholded OBJECT-TYPE
    SYNTAX       CucsEtherRxStatsHistThresholded
    MAX-ACCESS   read-only
    STATUS       current
    DESCRIPTION
        "Cisco UCS ether:RxStatsHist:thresholded managed object property"
    ::= { cucsEtherRxStatsHistEntry 22 }

cucsEtherRxStatsHistTimeCollected OBJECT-TYPE
    SYNTAX       DateAndTime
    MAX-ACCESS   read-only
    STATUS       current
    DESCRIPTION
        "Cisco UCS ether:RxStatsHist:timeCollected managed
        object property"
    ::= { cucsEtherRxStatsHistEntry 23 }

cucsEtherRxStatsHistTotalBytes OBJECT-TYPE
    SYNTAX       Unsigned64
    MAX-ACCESS   read-only
    STATUS       current
    DESCRIPTION
        "Cisco UCS ether:RxStatsHist:totalBytes managed object property"
    ::= { cucsEtherRxStatsHistEntry 24 }

cucsEtherRxStatsHistTotalBytesDelta OBJECT-TYPE
    SYNTAX       Unsigned64
    MAX-ACCESS   read-only
    STATUS       current
    DESCRIPTION
        "Cisco UCS ether:RxStatsHist:totalBytesDelta managed
        object property"
    ::= { cucsEtherRxStatsHistEntry 25 }

cucsEtherRxStatsHistTotalBytesDeltaAvg OBJECT-TYPE
    SYNTAX       Unsigned64
    MAX-ACCESS   read-only
    STATUS       current
    DESCRIPTION
        "Cisco UCS ether:RxStatsHist:totalBytesDeltaAvg
        managed object property"
    ::= { cucsEtherRxStatsHistEntry 26 }

cucsEtherRxStatsHistTotalBytesDeltaMax OBJECT-TYPE
    SYNTAX       Unsigned64
    MAX-ACCESS   read-only
    STATUS       current
    DESCRIPTION
        "Cisco UCS ether:RxStatsHist:totalBytesDeltaMax
        managed object property"
    ::= { cucsEtherRxStatsHistEntry 27 }

cucsEtherRxStatsHistTotalBytesDeltaMin OBJECT-TYPE
    SYNTAX       Unsigned64
    MAX-ACCESS   read-only
    STATUS       current
    DESCRIPTION
        "Cisco UCS ether:RxStatsHist:totalBytesDeltaMin
        managed object property"
    ::= { cucsEtherRxStatsHistEntry 28 }

cucsEtherRxStatsHistTotalPackets OBJECT-TYPE
    SYNTAX       Unsigned64
    MAX-ACCESS   read-only
    STATUS       current
    DESCRIPTION
        "Cisco UCS ether:RxStatsHist:totalPackets managed object property"
    ::= { cucsEtherRxStatsHistEntry 29 }

cucsEtherRxStatsHistTotalPacketsDelta OBJECT-TYPE
    SYNTAX       Unsigned64
    MAX-ACCESS   read-only
    STATUS       current
    DESCRIPTION
        "Cisco UCS ether:RxStatsHist:totalPacketsDelta
        managed object property"
    ::= { cucsEtherRxStatsHistEntry 30 }

cucsEtherRxStatsHistTotalPacketsDeltaAvg OBJECT-TYPE
    SYNTAX       Unsigned64
    MAX-ACCESS   read-only
    STATUS       current
    DESCRIPTION
        "Cisco UCS ether:RxStatsHist:totalPacketsDeltaAvg
        managed object property"
    ::= { cucsEtherRxStatsHistEntry 31 }

cucsEtherRxStatsHistTotalPacketsDeltaMax OBJECT-TYPE
    SYNTAX       Unsigned64
    MAX-ACCESS   read-only
    STATUS       current
    DESCRIPTION
        "Cisco UCS ether:RxStatsHist:totalPacketsDeltaMax
        managed object property"
    ::= { cucsEtherRxStatsHistEntry 32 }

cucsEtherRxStatsHistTotalPacketsDeltaMin OBJECT-TYPE
    SYNTAX       Unsigned64
    MAX-ACCESS   read-only
    STATUS       current
    DESCRIPTION
        "Cisco UCS ether:RxStatsHist:totalPacketsDeltaMin
        managed object property"
    ::= { cucsEtherRxStatsHistEntry 33 }

cucsEtherRxStatsHistUnicastPackets OBJECT-TYPE
    SYNTAX       Unsigned64
    MAX-ACCESS   read-only
    STATUS       current
    DESCRIPTION
        "Cisco UCS ether:RxStatsHist:unicastPackets managed
        object property"
    ::= { cucsEtherRxStatsHistEntry 34 }

cucsEtherRxStatsHistUnicastPacketsDelta OBJECT-TYPE
    SYNTAX       Unsigned64
    MAX-ACCESS   read-only
    STATUS       current
    DESCRIPTION
        "Cisco UCS ether:RxStatsHist:unicastPacketsDelta
        managed object property"
    ::= { cucsEtherRxStatsHistEntry 35 }

cucsEtherRxStatsHistUnicastPacketsDeltaAvg OBJECT-TYPE
    SYNTAX       Unsigned64
    MAX-ACCESS   read-only
    STATUS       current
    DESCRIPTION
        "Cisco UCS ether:RxStatsHist:unicastPacketsDeltaAvg
        managed object property"
    ::= { cucsEtherRxStatsHistEntry 36 }

cucsEtherRxStatsHistUnicastPacketsDeltaMax OBJECT-TYPE
    SYNTAX       Unsigned64
    MAX-ACCESS   read-only
    STATUS       current
    DESCRIPTION
        "Cisco UCS ether:RxStatsHist:unicastPacketsDeltaMax
        managed object property"
    ::= { cucsEtherRxStatsHistEntry 37 }

cucsEtherRxStatsHistUnicastPacketsDeltaMin OBJECT-TYPE
    SYNTAX       Unsigned64
    MAX-ACCESS   read-only
    STATUS       current
    DESCRIPTION
        "Cisco UCS ether:RxStatsHist:unicastPacketsDeltaMin
        managed object property"
    ::= { cucsEtherRxStatsHistEntry 38 }

cucsEtherServerIntFIoTable OBJECT-TYPE
    SYNTAX           SEQUENCE OF CucsEtherServerIntFIoEntry
    MAX-ACCESS       not-accessible
    STATUS           current
    DESCRIPTION
        "Cisco UCS ether:ServerIntFIo managed object table"
    ::= { cucsEtherObjects 11 }

cucsEtherServerIntFIoEntry OBJECT-TYPE
    SYNTAX           CucsEtherServerIntFIoEntry
    MAX-ACCESS       not-accessible
    STATUS           current
    DESCRIPTION
        "Entry for the cucsEtherServerIntFIoTable table."
    INDEX { cucsEtherServerIntFIoInstanceId }
    ::= { cucsEtherServerIntFIoTable 1 }

CucsEtherServerIntFIoEntry ::= SEQUENCE {
    cucsEtherServerIntFIoInstanceId                                  CucsManagedObjectId,
    cucsEtherServerIntFIoDn                                          CucsManagedObjectDn,
    cucsEtherServerIntFIoRn                                          SnmpAdminString,
    cucsEtherServerIntFIoAdminState                                  CucsEtherServerIntFIoAdminState,
    cucsEtherServerIntFIoChassisId                                   Gauge32,
    cucsEtherServerIntFIoEncap                                       CucsPortEncap,
    cucsEtherServerIntFIoEpDn                                        SnmpAdminString,
    cucsEtherServerIntFIoFltAggr                                     Unsigned64,
    cucsEtherServerIntFIoIfRole                                      CucsEtherServerIntFIoIfRole,
    cucsEtherServerIntFIoIfType                                      CucsNetworkPhysEpIfType,
    cucsEtherServerIntFIoLocale                                      CucsEtherServerIntFIoLocale,
    cucsEtherServerIntFIoMode                                        CucsPortMode,
    cucsEtherServerIntFIoModel                                       SnmpAdminString,
    cucsEtherServerIntFIoName                                        SnmpAdminString,
    cucsEtherServerIntFIoOperBorderPortId                            Gauge32,
    cucsEtherServerIntFIoOperBorderSlotId                            Gauge32,
    cucsEtherServerIntFIoOperState                                   CucsNetworkPortOperState,
    cucsEtherServerIntFIoPeerDn                                      SnmpAdminString,
    cucsEtherServerIntFIoPeerPortId                                  Gauge32,
    cucsEtherServerIntFIoPeerSlotId                                  Gauge32,
    cucsEtherServerIntFIoPortId                                      Gauge32,
    cucsEtherServerIntFIoRevision                                    SnmpAdminString,
    cucsEtherServerIntFIoSerial                                      SnmpAdminString,
    cucsEtherServerIntFIoSlotId                                      Gauge32,
    cucsEtherServerIntFIoStateQual                                   SnmpAdminString,
    cucsEtherServerIntFIoSwitchId                                    CucsNetworkSwitchId,
    cucsEtherServerIntFIoTransport                                   CucsEtherServerIntFIoTransport,
    cucsEtherServerIntFIoTs                                          DateAndTime,
    cucsEtherServerIntFIoType                                        CucsEtherServerIntFIoType,
    cucsEtherServerIntFIoVendor                                      SnmpAdminString,
    cucsEtherServerIntFIoMac                                         MacAddress,
    cucsEtherServerIntFIoPeerChassisId                               Gauge32,
    cucsEtherServerIntFIoXcvrType                                    CucsEquipmentXcvrType,
    cucsEtherServerIntFIoAdminSpeed                                  CucsPortEthSpeed,
    cucsEtherServerIntFIoFsmDescr                                    SnmpAdminString,
    cucsEtherServerIntFIoFsmPrev                                     SnmpAdminString,
    cucsEtherServerIntFIoFsmProgr                                    Gauge32,
    cucsEtherServerIntFIoFsmRmtInvErrCode                            Gauge32,
    cucsEtherServerIntFIoFsmRmtInvErrDescr                           SnmpAdminString,
    cucsEtherServerIntFIoFsmRmtInvRslt                               CucsConditionRemoteInvRslt,
    cucsEtherServerIntFIoFsmStageDescr                               SnmpAdminString,
    cucsEtherServerIntFIoFsmStamp                                    DateAndTime,
    cucsEtherServerIntFIoFsmStatus                                   SnmpAdminString,
    cucsEtherServerIntFIoFsmTry                                      Gauge32,
    cucsEtherServerIntFIoNsSize                                      Gauge32,
    cucsEtherServerIntFIoPeerEncap                                   Gauge32,
    cucsEtherServerIntFIoAggrPortId                                  Gauge32,
    cucsEtherServerIntFIoPeerAggrPortId                              Gauge32,
    cucsEtherServerIntFIoMacAddr                                     MacAddress,
    cucsEtherServerIntFIoOperBorderAggrPortId                        Gauge32
}

cucsEtherServerIntFIoInstanceId OBJECT-TYPE
    SYNTAX       CucsManagedObjectId
    MAX-ACCESS   not-accessible
    STATUS       current
    DESCRIPTION
        "Instance identifier of the managed object."
    ::= { cucsEtherServerIntFIoEntry 1 }

cucsEtherServerIntFIoDn OBJECT-TYPE
    SYNTAX       CucsManagedObjectDn
    MAX-ACCESS   read-only
    STATUS       current
    DESCRIPTION
        "Cisco UCS ether:ServerIntFIo:dn managed object property"
    ::= { cucsEtherServerIntFIoEntry 2 }

cucsEtherServerIntFIoRn OBJECT-TYPE
    SYNTAX       SnmpAdminString
    MAX-ACCESS   read-only
    STATUS       current
    DESCRIPTION
        "Cisco UCS ether:ServerIntFIo:rn managed object property"
    ::= { cucsEtherServerIntFIoEntry 3 }

cucsEtherServerIntFIoAdminState OBJECT-TYPE
    SYNTAX       CucsEtherServerIntFIoAdminState
    MAX-ACCESS   read-only
    STATUS       current
    DESCRIPTION
        "Cisco UCS ether:ServerIntFIo:adminState managed object property"
    ::= { cucsEtherServerIntFIoEntry 4 }

cucsEtherServerIntFIoChassisId OBJECT-TYPE
    SYNTAX       Gauge32
    MAX-ACCESS   read-only
    STATUS       current
    DESCRIPTION
        "Cisco UCS ether:ServerIntFIo:chassisId managed object property"
    ::= { cucsEtherServerIntFIoEntry 5 }

cucsEtherServerIntFIoEncap OBJECT-TYPE
    SYNTAX       CucsPortEncap
    MAX-ACCESS   read-only
    STATUS       current
    DESCRIPTION
        "Cisco UCS ether:ServerIntFIo:encap managed object property"
    ::= { cucsEtherServerIntFIoEntry 6 }

cucsEtherServerIntFIoEpDn OBJECT-TYPE
    SYNTAX       SnmpAdminString
    MAX-ACCESS   read-only
    STATUS       current
    DESCRIPTION
        "Cisco UCS ether:ServerIntFIo:epDn managed object property"
    ::= { cucsEtherServerIntFIoEntry 7 }

cucsEtherServerIntFIoFltAggr OBJECT-TYPE
    SYNTAX       Unsigned64
    MAX-ACCESS   read-only
    STATUS       current
    DESCRIPTION
        "Cisco UCS ether:ServerIntFIo:fltAggr managed object property"
    ::= { cucsEtherServerIntFIoEntry 8 }

cucsEtherServerIntFIoIfRole OBJECT-TYPE
    SYNTAX       CucsEtherServerIntFIoIfRole
    MAX-ACCESS   read-only
    STATUS       current
    DESCRIPTION
        "Cisco UCS ether:ServerIntFIo:ifRole managed object property"
    ::= { cucsEtherServerIntFIoEntry 9 }

cucsEtherServerIntFIoIfType OBJECT-TYPE
    SYNTAX       CucsNetworkPhysEpIfType
    MAX-ACCESS   read-only
    STATUS       current
    DESCRIPTION
        "Cisco UCS ether:ServerIntFIo:ifType managed object property"
    ::= { cucsEtherServerIntFIoEntry 10 }

cucsEtherServerIntFIoLocale OBJECT-TYPE
    SYNTAX       CucsEtherServerIntFIoLocale
    MAX-ACCESS   read-only
    STATUS       current
    DESCRIPTION
        "Cisco UCS ether:ServerIntFIo:locale managed object property"
    ::= { cucsEtherServerIntFIoEntry 11 }

cucsEtherServerIntFIoMode OBJECT-TYPE
    SYNTAX       CucsPortMode
    MAX-ACCESS   read-only
    STATUS       current
    DESCRIPTION
        "Cisco UCS ether:ServerIntFIo:mode managed object property"
    ::= { cucsEtherServerIntFIoEntry 12 }

cucsEtherServerIntFIoModel OBJECT-TYPE
    SYNTAX       SnmpAdminString
    MAX-ACCESS   read-only
    STATUS       current
    DESCRIPTION
        "Cisco UCS ether:ServerIntFIo:model managed object property"
    ::= { cucsEtherServerIntFIoEntry 13 }

cucsEtherServerIntFIoName OBJECT-TYPE
    SYNTAX       SnmpAdminString
    MAX-ACCESS   read-only
    STATUS       current
    DESCRIPTION
        "Cisco UCS ether:ServerIntFIo:name managed object property"
    ::= { cucsEtherServerIntFIoEntry 14 }

cucsEtherServerIntFIoOperBorderPortId OBJECT-TYPE
    SYNTAX       Gauge32
    MAX-ACCESS   read-only
    STATUS       current
    DESCRIPTION
        "Cisco UCS ether:ServerIntFIo:operBorderPortId
        managed object property"
    ::= { cucsEtherServerIntFIoEntry 15 }

cucsEtherServerIntFIoOperBorderSlotId OBJECT-TYPE
    SYNTAX       Gauge32
    MAX-ACCESS   read-only
    STATUS       current
    DESCRIPTION
        "Cisco UCS ether:ServerIntFIo:operBorderSlotId
        managed object property"
    ::= { cucsEtherServerIntFIoEntry 16 }

cucsEtherServerIntFIoOperState OBJECT-TYPE
    SYNTAX       CucsNetworkPortOperState
    MAX-ACCESS   read-only
    STATUS       current
    DESCRIPTION
        "Cisco UCS ether:ServerIntFIo:operState managed object property"
    ::= { cucsEtherServerIntFIoEntry 17 }

cucsEtherServerIntFIoPeerDn OBJECT-TYPE
    SYNTAX       SnmpAdminString
    MAX-ACCESS   read-only
    STATUS       current
    DESCRIPTION
        "Cisco UCS ether:ServerIntFIo:peerDn managed object property"
    ::= { cucsEtherServerIntFIoEntry 18 }

cucsEtherServerIntFIoPeerPortId OBJECT-TYPE
    SYNTAX       Gauge32
    MAX-ACCESS   read-only
    STATUS       current
    DESCRIPTION
        "Cisco UCS ether:ServerIntFIo:peerPortId managed object property"
    ::= { cucsEtherServerIntFIoEntry 19 }

cucsEtherServerIntFIoPeerSlotId OBJECT-TYPE
    SYNTAX       Gauge32
    MAX-ACCESS   read-only
    STATUS       current
    DESCRIPTION
        "Cisco UCS ether:ServerIntFIo:peerSlotId managed object property"
    ::= { cucsEtherServerIntFIoEntry 20 }

cucsEtherServerIntFIoPortId OBJECT-TYPE
    SYNTAX       Gauge32
    MAX-ACCESS   read-only
    STATUS       current
    DESCRIPTION
        "Cisco UCS ether:ServerIntFIo:portId managed object property"
    ::= { cucsEtherServerIntFIoEntry 21 }

cucsEtherServerIntFIoRevision OBJECT-TYPE
    SYNTAX       SnmpAdminString
    MAX-ACCESS   read-only
    STATUS       current
    DESCRIPTION
        "Cisco UCS ether:ServerIntFIo:revision managed object property"
    ::= { cucsEtherServerIntFIoEntry 22 }

cucsEtherServerIntFIoSerial OBJECT-TYPE
    SYNTAX       SnmpAdminString
    MAX-ACCESS   read-only
    STATUS       current
    DESCRIPTION
        "Cisco UCS ether:ServerIntFIo:serial managed object property"
    ::= { cucsEtherServerIntFIoEntry 23 }

cucsEtherServerIntFIoSlotId OBJECT-TYPE
    SYNTAX       Gauge32
    MAX-ACCESS   read-only
    STATUS       current
    DESCRIPTION
        "Cisco UCS ether:ServerIntFIo:slotId managed object property"
    ::= { cucsEtherServerIntFIoEntry 24 }

cucsEtherServerIntFIoStateQual OBJECT-TYPE
    SYNTAX       SnmpAdminString
    MAX-ACCESS   read-only
    STATUS       current
    DESCRIPTION
        "Cisco UCS ether:ServerIntFIo:stateQual managed object property"
    ::= { cucsEtherServerIntFIoEntry 25 }

cucsEtherServerIntFIoSwitchId OBJECT-TYPE
    SYNTAX       CucsNetworkSwitchId
    MAX-ACCESS   read-only
    STATUS       current
    DESCRIPTION
        "Cisco UCS ether:ServerIntFIo:switchId managed object property"
    ::= { cucsEtherServerIntFIoEntry 26 }

cucsEtherServerIntFIoTransport OBJECT-TYPE
    SYNTAX       CucsEtherServerIntFIoTransport
    MAX-ACCESS   read-only
    STATUS       current
    DESCRIPTION
        "Cisco UCS ether:ServerIntFIo:transport managed object property"
    ::= { cucsEtherServerIntFIoEntry 27 }

cucsEtherServerIntFIoTs OBJECT-TYPE
    SYNTAX       DateAndTime
    MAX-ACCESS   read-only
    STATUS       current
    DESCRIPTION
        "Cisco UCS ether:ServerIntFIo:ts managed object property"
    ::= { cucsEtherServerIntFIoEntry 28 }

cucsEtherServerIntFIoType OBJECT-TYPE
    SYNTAX       CucsEtherServerIntFIoType
    MAX-ACCESS   read-only
    STATUS       current
    DESCRIPTION
        "Cisco UCS ether:ServerIntFIo:type managed object property"
    ::= { cucsEtherServerIntFIoEntry 29 }

cucsEtherServerIntFIoVendor OBJECT-TYPE
    SYNTAX       SnmpAdminString
    MAX-ACCESS   read-only
    STATUS       current
    DESCRIPTION
        "Cisco UCS ether:ServerIntFIo:vendor managed object property"
    ::= { cucsEtherServerIntFIoEntry 30 }

cucsEtherServerIntFIoMac OBJECT-TYPE
    SYNTAX       MacAddress
    MAX-ACCESS   read-only
    STATUS       current
    DESCRIPTION
        "Cisco UCS ether:ServerIntFIo:mac managed object property"
    ::= { cucsEtherServerIntFIoEntry 31 }

cucsEtherServerIntFIoPeerChassisId OBJECT-TYPE
    SYNTAX       Gauge32
    MAX-ACCESS   read-only
    STATUS       current
    DESCRIPTION
        "Cisco UCS ether:ServerIntFIo:peerChassisId managed
        object property"
    ::= { cucsEtherServerIntFIoEntry 32 }

cucsEtherServerIntFIoXcvrType OBJECT-TYPE
    SYNTAX       CucsEquipmentXcvrType
    MAX-ACCESS   read-only
    STATUS       current
    DESCRIPTION
        "Cisco UCS ether:ServerIntFIo:xcvrType managed object property"
    ::= { cucsEtherServerIntFIoEntry 33 }

cucsEtherServerIntFIoAdminSpeed OBJECT-TYPE
    SYNTAX       CucsPortEthSpeed
    MAX-ACCESS   read-only
    STATUS       current
    DESCRIPTION
        "Cisco UCS ether:ServerIntFIo:adminSpeed managed object property"
    ::= { cucsEtherServerIntFIoEntry 34 }

cucsEtherServerIntFIoFsmDescr OBJECT-TYPE
    SYNTAX       SnmpAdminString
    MAX-ACCESS   read-only
    STATUS       current
    DESCRIPTION
        "Cisco UCS ether:ServerIntFIo:fsmDescr managed object property"
    ::= { cucsEtherServerIntFIoEntry 35 }

cucsEtherServerIntFIoFsmPrev OBJECT-TYPE
    SYNTAX       SnmpAdminString
    MAX-ACCESS   read-only
    STATUS       current
    DESCRIPTION
        "Cisco UCS ether:ServerIntFIo:fsmPrev managed object property"
    ::= { cucsEtherServerIntFIoEntry 36 }

cucsEtherServerIntFIoFsmProgr OBJECT-TYPE
    SYNTAX       Gauge32
    MAX-ACCESS   read-only
    STATUS       current
    DESCRIPTION
        "Cisco UCS ether:ServerIntFIo:fsmProgr managed object property"
    ::= { cucsEtherServerIntFIoEntry 37 }

cucsEtherServerIntFIoFsmRmtInvErrCode OBJECT-TYPE
    SYNTAX       Gauge32
    MAX-ACCESS   read-only
    STATUS       current
    DESCRIPTION
        "Cisco UCS ether:ServerIntFIo:fsmRmtInvErrCode
        managed object property"
    ::= { cucsEtherServerIntFIoEntry 38 }

cucsEtherServerIntFIoFsmRmtInvErrDescr OBJECT-TYPE
    SYNTAX       SnmpAdminString
    MAX-ACCESS   read-only
    STATUS       current
    DESCRIPTION
        "Cisco UCS ether:ServerIntFIo:fsmRmtInvErrDescr
        managed object property"
    ::= { cucsEtherServerIntFIoEntry 39 }

cucsEtherServerIntFIoFsmRmtInvRslt OBJECT-TYPE
    SYNTAX       CucsConditionRemoteInvRslt
    MAX-ACCESS   read-only
    STATUS       current
    DESCRIPTION
        "Cisco UCS ether:ServerIntFIo:fsmRmtInvRslt managed
        object property"
    ::= { cucsEtherServerIntFIoEntry 40 }

cucsEtherServerIntFIoFsmStageDescr OBJECT-TYPE
    SYNTAX       SnmpAdminString
    MAX-ACCESS   read-only
    STATUS       current
    DESCRIPTION
        "Cisco UCS ether:ServerIntFIo:fsmStageDescr managed
        object property"
    ::= { cucsEtherServerIntFIoEntry 41 }

cucsEtherServerIntFIoFsmStamp OBJECT-TYPE
    SYNTAX       DateAndTime
    MAX-ACCESS   read-only
    STATUS       current
    DESCRIPTION
        "Cisco UCS ether:ServerIntFIo:fsmStamp managed object property"
    ::= { cucsEtherServerIntFIoEntry 42 }

cucsEtherServerIntFIoFsmStatus OBJECT-TYPE
    SYNTAX       SnmpAdminString
    MAX-ACCESS   read-only
    STATUS       current
    DESCRIPTION
        "Cisco UCS ether:ServerIntFIo:fsmStatus managed object property"
    ::= { cucsEtherServerIntFIoEntry 43 }

cucsEtherServerIntFIoFsmTry OBJECT-TYPE
    SYNTAX       Gauge32
    MAX-ACCESS   read-only
    STATUS       current
    DESCRIPTION
        "Cisco UCS ether:ServerIntFIo:fsmTry managed object property"
    ::= { cucsEtherServerIntFIoEntry 44 }

cucsEtherServerIntFIoNsSize OBJECT-TYPE
    SYNTAX       Gauge32
    MAX-ACCESS   read-only
    STATUS       current
    DESCRIPTION
        "Cisco UCS ether:ServerIntFIo:nsSize managed object property"
    ::= { cucsEtherServerIntFIoEntry 45 }

cucsEtherServerIntFIoPeerEncap OBJECT-TYPE
    SYNTAX       Gauge32
    MAX-ACCESS   read-only
    STATUS       current
    DESCRIPTION
        "Cisco UCS ether:ServerIntFIo:peerEncap managed object property"
    ::= { cucsEtherServerIntFIoEntry 46 }

cucsEtherServerIntFIoAggrPortId OBJECT-TYPE
    SYNTAX       Gauge32
    MAX-ACCESS   read-only
    STATUS       current
    DESCRIPTION
        "Cisco UCS ether:ServerIntFIo:aggrPortId managed object property"
    ::= { cucsEtherServerIntFIoEntry 47 }

cucsEtherServerIntFIoPeerAggrPortId OBJECT-TYPE
    SYNTAX       Gauge32
    MAX-ACCESS   read-only
    STATUS       current
    DESCRIPTION
        "Cisco UCS ether:ServerIntFIo:peerAggrPortId managed
        object property"
    ::= { cucsEtherServerIntFIoEntry 48 }

cucsEtherServerIntFIoMacAddr OBJECT-TYPE
    SYNTAX       MacAddress
    MAX-ACCESS   read-only
    STATUS       current
    DESCRIPTION
        "Cisco UCS ether:ServerIntFIo:macAddr managed object property"
    ::= { cucsEtherServerIntFIoEntry 49 }

cucsEtherServerIntFIoOperBorderAggrPortId OBJECT-TYPE
    SYNTAX       Gauge32
    MAX-ACCESS   read-only
    STATUS       current
    DESCRIPTION
        "Cisco UCS ether:ServerIntFIo:operBorderAggrPortId
        managed object property"
    ::= { cucsEtherServerIntFIoEntry 50 }

cucsEtherServerIntFIoFsmTable OBJECT-TYPE
    SYNTAX           SEQUENCE OF CucsEtherServerIntFIoFsmEntry
    MAX-ACCESS       not-accessible
    STATUS           current
    DESCRIPTION
        "Cisco UCS ether:ServerIntFIoFsm managed object table"
    ::= { cucsEtherObjects 28 }

cucsEtherServerIntFIoFsmEntry OBJECT-TYPE
    SYNTAX           CucsEtherServerIntFIoFsmEntry
    MAX-ACCESS       not-accessible
    STATUS           current
    DESCRIPTION
        "Entry for the cucsEtherServerIntFIoFsmTable table."
    INDEX { cucsEtherServerIntFIoFsmInstanceId }
    ::= { cucsEtherServerIntFIoFsmTable 1 }

CucsEtherServerIntFIoFsmEntry ::= SEQUENCE {
    cucsEtherServerIntFIoFsmInstanceId                               CucsManagedObjectId,
    cucsEtherServerIntFIoFsmDn                                       CucsManagedObjectDn,
    cucsEtherServerIntFIoFsmRn                                       SnmpAdminString,
    cucsEtherServerIntFIoFsmCompletionTime                           DateAndTime,
    cucsEtherServerIntFIoFsmCurrentFsm                               CucsEtherServerIntFIoFsmCurrentFsm,
    cucsEtherServerIntFIoFsmDescrData                                SnmpAdminString,
    cucsEtherServerIntFIoFsmFsmStatus                                CucsFsmFsmStageStatus,
    cucsEtherServerIntFIoFsmProgress                                 Gauge32,
    cucsEtherServerIntFIoFsmRmtErrCode                               Gauge32,
    cucsEtherServerIntFIoFsmRmtErrDescr                              SnmpAdminString,
    cucsEtherServerIntFIoFsmRmtRslt                                  CucsConditionRemoteInvRslt
}

cucsEtherServerIntFIoFsmInstanceId OBJECT-TYPE
    SYNTAX       CucsManagedObjectId
    MAX-ACCESS   not-accessible
    STATUS       current
    DESCRIPTION
        "Instance identifier of the managed object."
    ::= { cucsEtherServerIntFIoFsmEntry 1 }

cucsEtherServerIntFIoFsmDn OBJECT-TYPE
    SYNTAX       CucsManagedObjectDn
    MAX-ACCESS   read-only
    STATUS       current
    DESCRIPTION
        "Cisco UCS ether:ServerIntFIoFsm:dn managed object property"
    ::= { cucsEtherServerIntFIoFsmEntry 2 }

cucsEtherServerIntFIoFsmRn OBJECT-TYPE
    SYNTAX       SnmpAdminString
    MAX-ACCESS   read-only
    STATUS       current
    DESCRIPTION
        "Cisco UCS ether:ServerIntFIoFsm:rn managed object property"
    ::= { cucsEtherServerIntFIoFsmEntry 3 }

cucsEtherServerIntFIoFsmCompletionTime OBJECT-TYPE
    SYNTAX       DateAndTime
    MAX-ACCESS   read-only
    STATUS       current
    DESCRIPTION
        "Cisco UCS ether:ServerIntFIoFsm:completionTime
        managed object property"
    ::= { cucsEtherServerIntFIoFsmEntry 4 }

cucsEtherServerIntFIoFsmCurrentFsm OBJECT-TYPE
    SYNTAX       CucsEtherServerIntFIoFsmCurrentFsm
    MAX-ACCESS   read-only
    STATUS       current
    DESCRIPTION
        "Cisco UCS ether:ServerIntFIoFsm:currentFsm managed
        object property"
    ::= { cucsEtherServerIntFIoFsmEntry 5 }

cucsEtherServerIntFIoFsmDescrData OBJECT-TYPE
    SYNTAX       SnmpAdminString
    MAX-ACCESS   read-only
    STATUS       current
    DESCRIPTION
        "Cisco UCS ether:ServerIntFIoFsm:descr managed object property"
    ::= { cucsEtherServerIntFIoFsmEntry 6 }

cucsEtherServerIntFIoFsmFsmStatus OBJECT-TYPE
    SYNTAX       CucsFsmFsmStageStatus
    MAX-ACCESS   read-only
    STATUS       current
    DESCRIPTION
        "Cisco UCS ether:ServerIntFIoFsm:fsmStatus managed
        object property"
    ::= { cucsEtherServerIntFIoFsmEntry 7 }

cucsEtherServerIntFIoFsmProgress OBJECT-TYPE
    SYNTAX       Gauge32
    MAX-ACCESS   read-only
    STATUS       current
    DESCRIPTION
        "Cisco UCS ether:ServerIntFIoFsm:progress managed object property"
    ::= { cucsEtherServerIntFIoFsmEntry 8 }

cucsEtherServerIntFIoFsmRmtErrCode OBJECT-TYPE
    SYNTAX       Gauge32
    MAX-ACCESS   read-only
    STATUS       current
    DESCRIPTION
        "Cisco UCS ether:ServerIntFIoFsm:rmtErrCode managed
        object property"
    ::= { cucsEtherServerIntFIoFsmEntry 9 }

cucsEtherServerIntFIoFsmRmtErrDescr OBJECT-TYPE
    SYNTAX       SnmpAdminString
    MAX-ACCESS   read-only
    STATUS       current
    DESCRIPTION
        "Cisco UCS ether:ServerIntFIoFsm:rmtErrDescr managed
        object property"
    ::= { cucsEtherServerIntFIoFsmEntry 10 }

cucsEtherServerIntFIoFsmRmtRslt OBJECT-TYPE
    SYNTAX       CucsConditionRemoteInvRslt
    MAX-ACCESS   read-only
    STATUS       current
    DESCRIPTION
        "Cisco UCS ether:ServerIntFIoFsm:rmtRslt managed object property"
    ::= { cucsEtherServerIntFIoFsmEntry 11 }

cucsEtherServerIntFIoFsmStageTable OBJECT-TYPE
    SYNTAX           SEQUENCE OF CucsEtherServerIntFIoFsmStageEntry
    MAX-ACCESS       not-accessible
    STATUS           current
    DESCRIPTION
        "Cisco UCS ether:ServerIntFIoFsmStage managed object table"
    ::= { cucsEtherObjects 29 }

cucsEtherServerIntFIoFsmStageEntry OBJECT-TYPE
    SYNTAX           CucsEtherServerIntFIoFsmStageEntry
    MAX-ACCESS       not-accessible
    STATUS           current
    DESCRIPTION
        "Entry for the cucsEtherServerIntFIoFsmStageTable table."
    INDEX { cucsEtherServerIntFIoFsmStageInstanceId }
    ::= { cucsEtherServerIntFIoFsmStageTable 1 }

CucsEtherServerIntFIoFsmStageEntry ::= SEQUENCE {
    cucsEtherServerIntFIoFsmStageInstanceId                          CucsManagedObjectId,
    cucsEtherServerIntFIoFsmStageDn                                  CucsManagedObjectDn,
    cucsEtherServerIntFIoFsmStageRn                                  SnmpAdminString,
    cucsEtherServerIntFIoFsmStageDescrData                           SnmpAdminString,
    cucsEtherServerIntFIoFsmStageLastUpdateTime                      DateAndTime,
    cucsEtherServerIntFIoFsmStageName                                CucsEtherServerIntFIoFsmStageName,
    cucsEtherServerIntFIoFsmStageOrder                               Gauge32,
    cucsEtherServerIntFIoFsmStageRetry                               Gauge32,
    cucsEtherServerIntFIoFsmStageStageStatus                         CucsFsmFsmStageStatus
}

cucsEtherServerIntFIoFsmStageInstanceId OBJECT-TYPE
    SYNTAX       CucsManagedObjectId
    MAX-ACCESS   not-accessible
    STATUS       current
    DESCRIPTION
        "Instance identifier of the managed object."
    ::= { cucsEtherServerIntFIoFsmStageEntry 1 }

cucsEtherServerIntFIoFsmStageDn OBJECT-TYPE
    SYNTAX       CucsManagedObjectDn
    MAX-ACCESS   read-only
    STATUS       current
    DESCRIPTION
        "Cisco UCS ether:ServerIntFIoFsmStage:dn managed object property"
    ::= { cucsEtherServerIntFIoFsmStageEntry 2 }

cucsEtherServerIntFIoFsmStageRn OBJECT-TYPE
    SYNTAX       SnmpAdminString
    MAX-ACCESS   read-only
    STATUS       current
    DESCRIPTION
        "Cisco UCS ether:ServerIntFIoFsmStage:rn managed object property"
    ::= { cucsEtherServerIntFIoFsmStageEntry 3 }

cucsEtherServerIntFIoFsmStageDescrData OBJECT-TYPE
    SYNTAX       SnmpAdminString
    MAX-ACCESS   read-only
    STATUS       current
    DESCRIPTION
        "Cisco UCS ether:ServerIntFIoFsmStage:descr managed
        object property"
    ::= { cucsEtherServerIntFIoFsmStageEntry 4 }

cucsEtherServerIntFIoFsmStageLastUpdateTime OBJECT-TYPE
    SYNTAX       DateAndTime
    MAX-ACCESS   read-only
    STATUS       current
    DESCRIPTION
        "Cisco UCS ether:ServerIntFIoFsmStage:lastUpdateTime
        managed object property"
    ::= { cucsEtherServerIntFIoFsmStageEntry 5 }

cucsEtherServerIntFIoFsmStageName OBJECT-TYPE
    SYNTAX       CucsEtherServerIntFIoFsmStageName
    MAX-ACCESS   read-only
    STATUS       current
    DESCRIPTION
        "Cisco UCS ether:ServerIntFIoFsmStage:name managed
        object property"
    ::= { cucsEtherServerIntFIoFsmStageEntry 6 }

cucsEtherServerIntFIoFsmStageOrder OBJECT-TYPE
    SYNTAX       Gauge32
    MAX-ACCESS   read-only
    STATUS       current
    DESCRIPTION
        "Cisco UCS ether:ServerIntFIoFsmStage:order managed
        object property"
    ::= { cucsEtherServerIntFIoFsmStageEntry 7 }

cucsEtherServerIntFIoFsmStageRetry OBJECT-TYPE
    SYNTAX       Gauge32
    MAX-ACCESS   read-only
    STATUS       current
    DESCRIPTION
        "Cisco UCS ether:ServerIntFIoFsmStage:retry managed
        object property"
    ::= { cucsEtherServerIntFIoFsmStageEntry 8 }

cucsEtherServerIntFIoFsmStageStageStatus OBJECT-TYPE
    SYNTAX       CucsFsmFsmStageStatus
    MAX-ACCESS   read-only
    STATUS       current
    DESCRIPTION
        "Cisco UCS ether:ServerIntFIoFsmStage:stageStatus
        managed object property"
    ::= { cucsEtherServerIntFIoFsmStageEntry 9 }

cucsEtherServerIntFIoFsmTaskTable OBJECT-TYPE
    SYNTAX           SEQUENCE OF CucsEtherServerIntFIoFsmTaskEntry
    MAX-ACCESS       not-accessible
    STATUS           current
    DESCRIPTION
        "Cisco UCS ether:ServerIntFIoFsmTask managed object table"
    ::= { cucsEtherObjects 22 }

cucsEtherServerIntFIoFsmTaskEntry OBJECT-TYPE
    SYNTAX           CucsEtherServerIntFIoFsmTaskEntry
    MAX-ACCESS       not-accessible
    STATUS           current
    DESCRIPTION
        "Entry for the cucsEtherServerIntFIoFsmTaskTable table."
    INDEX { cucsEtherServerIntFIoFsmTaskInstanceId }
    ::= { cucsEtherServerIntFIoFsmTaskTable 1 }

CucsEtherServerIntFIoFsmTaskEntry ::= SEQUENCE {
    cucsEtherServerIntFIoFsmTaskInstanceId                           CucsManagedObjectId,
    cucsEtherServerIntFIoFsmTaskDn                                   CucsManagedObjectDn,
    cucsEtherServerIntFIoFsmTaskRn                                   SnmpAdminString,
    cucsEtherServerIntFIoFsmTaskCompletion                           CucsFsmCompletion,
    cucsEtherServerIntFIoFsmTaskFlags                                CucsFsmFlags,
    cucsEtherServerIntFIoFsmTaskItem                                 CucsEtherServerIntFIoFsmTaskItem,
    cucsEtherServerIntFIoFsmTaskSeqId                                Gauge32
}

cucsEtherServerIntFIoFsmTaskInstanceId OBJECT-TYPE
    SYNTAX       CucsManagedObjectId
    MAX-ACCESS   not-accessible
    STATUS       current
    DESCRIPTION
        "Instance identifier of the managed object."
    ::= { cucsEtherServerIntFIoFsmTaskEntry 1 }

cucsEtherServerIntFIoFsmTaskDn OBJECT-TYPE
    SYNTAX       CucsManagedObjectDn
    MAX-ACCESS   read-only
    STATUS       current
    DESCRIPTION
        "Cisco UCS ether:ServerIntFIoFsmTask:dn managed object property"
    ::= { cucsEtherServerIntFIoFsmTaskEntry 2 }

cucsEtherServerIntFIoFsmTaskRn OBJECT-TYPE
    SYNTAX       SnmpAdminString
    MAX-ACCESS   read-only
    STATUS       current
    DESCRIPTION
        "Cisco UCS ether:ServerIntFIoFsmTask:rn managed object property"
    ::= { cucsEtherServerIntFIoFsmTaskEntry 3 }

cucsEtherServerIntFIoFsmTaskCompletion OBJECT-TYPE
    SYNTAX       CucsFsmCompletion
    MAX-ACCESS   read-only
    STATUS       current
    DESCRIPTION
        "Cisco UCS ether:ServerIntFIoFsmTask:completion
        managed object property"
    ::= { cucsEtherServerIntFIoFsmTaskEntry 4 }

cucsEtherServerIntFIoFsmTaskFlags OBJECT-TYPE
    SYNTAX       CucsFsmFlags
    MAX-ACCESS   read-only
    STATUS       current
    DESCRIPTION
        "Cisco UCS ether:ServerIntFIoFsmTask:flags managed
        object property"
    ::= { cucsEtherServerIntFIoFsmTaskEntry 5 }

cucsEtherServerIntFIoFsmTaskItem OBJECT-TYPE
    SYNTAX       CucsEtherServerIntFIoFsmTaskItem
    MAX-ACCESS   read-only
    STATUS       current
    DESCRIPTION
        "Cisco UCS ether:ServerIntFIoFsmTask:item managed object property"
    ::= { cucsEtherServerIntFIoFsmTaskEntry 6 }

cucsEtherServerIntFIoFsmTaskSeqId OBJECT-TYPE
    SYNTAX       Gauge32
    MAX-ACCESS   read-only
    STATUS       current
    DESCRIPTION
        "Cisco UCS ether:ServerIntFIoFsmTask:seqId managed
        object property"
    ::= { cucsEtherServerIntFIoFsmTaskEntry 7 }

cucsEtherServerIntFIoPcTable OBJECT-TYPE
    SYNTAX           SEQUENCE OF CucsEtherServerIntFIoPcEntry
    MAX-ACCESS       not-accessible
    STATUS           current
    DESCRIPTION
        "Cisco UCS ether:ServerIntFIoPc managed object table"
    ::= { cucsEtherObjects 18 }

cucsEtherServerIntFIoPcEntry OBJECT-TYPE
    SYNTAX           CucsEtherServerIntFIoPcEntry
    MAX-ACCESS       not-accessible
    STATUS           current
    DESCRIPTION
        "Entry for the cucsEtherServerIntFIoPcTable table."
    INDEX { cucsEtherServerIntFIoPcInstanceId }
    ::= { cucsEtherServerIntFIoPcTable 1 }

CucsEtherServerIntFIoPcEntry ::= SEQUENCE {
    cucsEtherServerIntFIoPcInstanceId                                CucsManagedObjectId,
    cucsEtherServerIntFIoPcDn                                        CucsManagedObjectDn,
    cucsEtherServerIntFIoPcRn                                        SnmpAdminString,
    cucsEtherServerIntFIoPcChassisId                                 Gauge32,
    cucsEtherServerIntFIoPcEpDn                                      SnmpAdminString,
    cucsEtherServerIntFIoPcFltAggr                                   Unsigned64,
    cucsEtherServerIntFIoPcIfRole                                    CucsEtherServerIntFIoPcIfRole,
    cucsEtherServerIntFIoPcIfType                                    CucsEtherCIoEpIfType,
    cucsEtherServerIntFIoPcLocale                                    CucsEtherInternalPcLocale,
    cucsEtherServerIntFIoPcName                                      SnmpAdminString,
    cucsEtherServerIntFIoPcOperSpeed                                 CucsPortEthSpeed,
    cucsEtherServerIntFIoPcOperState                                 CucsNetworkPortOperState,
    cucsEtherServerIntFIoPcPeerDn                                    SnmpAdminString,
    cucsEtherServerIntFIoPcPortId                                    CucsEtherServerIntFIoPcPortId,
    cucsEtherServerIntFIoPcStateQual                                 SnmpAdminString,
    cucsEtherServerIntFIoPcSwitchId                                  CucsNetworkSwitchId,
    cucsEtherServerIntFIoPcTransport                                 CucsEtherServerIntFIoPcTransport,
    cucsEtherServerIntFIoPcType                                      CucsEtherServerIntFIoPcType
}

cucsEtherServerIntFIoPcInstanceId OBJECT-TYPE
    SYNTAX       CucsManagedObjectId
    MAX-ACCESS   not-accessible
    STATUS       current
    DESCRIPTION
        "Instance identifier of the managed object."
    ::= { cucsEtherServerIntFIoPcEntry 1 }

cucsEtherServerIntFIoPcDn OBJECT-TYPE
    SYNTAX       CucsManagedObjectDn
    MAX-ACCESS   read-only
    STATUS       current
    DESCRIPTION
        "Cisco UCS ether:ServerIntFIoPc:dn managed object property"
    ::= { cucsEtherServerIntFIoPcEntry 2 }

cucsEtherServerIntFIoPcRn OBJECT-TYPE
    SYNTAX       SnmpAdminString
    MAX-ACCESS   read-only
    STATUS       current
    DESCRIPTION
        "Cisco UCS ether:ServerIntFIoPc:rn managed object property"
    ::= { cucsEtherServerIntFIoPcEntry 3 }

cucsEtherServerIntFIoPcChassisId OBJECT-TYPE
    SYNTAX       Gauge32
    MAX-ACCESS   read-only
    STATUS       current
    DESCRIPTION
        "Cisco UCS ether:ServerIntFIoPc:chassisId managed object property"
    ::= { cucsEtherServerIntFIoPcEntry 4 }

cucsEtherServerIntFIoPcEpDn OBJECT-TYPE
    SYNTAX       SnmpAdminString
    MAX-ACCESS   read-only
    STATUS       current
    DESCRIPTION
        "Cisco UCS ether:ServerIntFIoPc:epDn managed object property"
    ::= { cucsEtherServerIntFIoPcEntry 5 }

cucsEtherServerIntFIoPcFltAggr OBJECT-TYPE
    SYNTAX       Unsigned64
    MAX-ACCESS   read-only
    STATUS       current
    DESCRIPTION
        "Cisco UCS ether:ServerIntFIoPc:fltAggr managed object property"
    ::= { cucsEtherServerIntFIoPcEntry 6 }

cucsEtherServerIntFIoPcIfRole OBJECT-TYPE
    SYNTAX       CucsEtherServerIntFIoPcIfRole
    MAX-ACCESS   read-only
    STATUS       current
    DESCRIPTION
        "Cisco UCS ether:ServerIntFIoPc:ifRole managed object property"
    ::= { cucsEtherServerIntFIoPcEntry 7 }

cucsEtherServerIntFIoPcIfType OBJECT-TYPE
    SYNTAX       CucsEtherCIoEpIfType
    MAX-ACCESS   read-only
    STATUS       current
    DESCRIPTION
        "Cisco UCS ether:ServerIntFIoPc:ifType managed object property"
    ::= { cucsEtherServerIntFIoPcEntry 8 }

cucsEtherServerIntFIoPcLocale OBJECT-TYPE
    SYNTAX       CucsEtherInternalPcLocale
    MAX-ACCESS   read-only
    STATUS       current
    DESCRIPTION
        "Cisco UCS ether:ServerIntFIoPc:locale managed object property"
    ::= { cucsEtherServerIntFIoPcEntry 9 }

cucsEtherServerIntFIoPcName OBJECT-TYPE
    SYNTAX       SnmpAdminString
    MAX-ACCESS   read-only
    STATUS       current
    DESCRIPTION
        "Cisco UCS ether:ServerIntFIoPc:name managed object property"
    ::= { cucsEtherServerIntFIoPcEntry 10 }

cucsEtherServerIntFIoPcOperSpeed OBJECT-TYPE
    SYNTAX       CucsPortEthSpeed
    MAX-ACCESS   read-only
    STATUS       current
    DESCRIPTION
        "Cisco UCS ether:ServerIntFIoPc:operSpeed managed object property"
    ::= { cucsEtherServerIntFIoPcEntry 11 }

cucsEtherServerIntFIoPcOperState OBJECT-TYPE
    SYNTAX       CucsNetworkPortOperState
    MAX-ACCESS   read-only
    STATUS       current
    DESCRIPTION
        "Cisco UCS ether:ServerIntFIoPc:operState managed object property"
    ::= { cucsEtherServerIntFIoPcEntry 12 }

cucsEtherServerIntFIoPcPeerDn OBJECT-TYPE
    SYNTAX       SnmpAdminString
    MAX-ACCESS   read-only
    STATUS       current
    DESCRIPTION
        "Cisco UCS ether:ServerIntFIoPc:peerDn managed object property"
    ::= { cucsEtherServerIntFIoPcEntry 13 }

cucsEtherServerIntFIoPcPortId OBJECT-TYPE
    SYNTAX       CucsEtherServerIntFIoPcPortId
    MAX-ACCESS   read-only
    STATUS       current
    DESCRIPTION
        "Cisco UCS ether:ServerIntFIoPc:portId managed object property"
    ::= { cucsEtherServerIntFIoPcEntry 14 }

cucsEtherServerIntFIoPcStateQual OBJECT-TYPE
    SYNTAX       SnmpAdminString
    MAX-ACCESS   read-only
    STATUS       current
    DESCRIPTION
        "Cisco UCS ether:ServerIntFIoPc:stateQual managed object property"
    ::= { cucsEtherServerIntFIoPcEntry 15 }

cucsEtherServerIntFIoPcSwitchId OBJECT-TYPE
    SYNTAX       CucsNetworkSwitchId
    MAX-ACCESS   read-only
    STATUS       current
    DESCRIPTION
        "Cisco UCS ether:ServerIntFIoPc:switchId managed object property"
    ::= { cucsEtherServerIntFIoPcEntry 16 }

cucsEtherServerIntFIoPcTransport OBJECT-TYPE
    SYNTAX       CucsEtherServerIntFIoPcTransport
    MAX-ACCESS   read-only
    STATUS       current
    DESCRIPTION
        "Cisco UCS ether:ServerIntFIoPc:transport managed object property"
    ::= { cucsEtherServerIntFIoPcEntry 17 }

cucsEtherServerIntFIoPcType OBJECT-TYPE
    SYNTAX       CucsEtherServerIntFIoPcType
    MAX-ACCESS   read-only
    STATUS       current
    DESCRIPTION
        "Cisco UCS ether:ServerIntFIoPc:type managed object property"
    ::= { cucsEtherServerIntFIoPcEntry 18 }

cucsEtherServerIntFIoPcEpTable OBJECT-TYPE
    SYNTAX           SEQUENCE OF CucsEtherServerIntFIoPcEpEntry
    MAX-ACCESS       not-accessible
    STATUS           current
    DESCRIPTION
        "Cisco UCS ether:ServerIntFIoPcEp managed object table"
    ::= { cucsEtherObjects 19 }

cucsEtherServerIntFIoPcEpEntry OBJECT-TYPE
    SYNTAX           CucsEtherServerIntFIoPcEpEntry
    MAX-ACCESS       not-accessible
    STATUS           current
    DESCRIPTION
        "Entry for the cucsEtherServerIntFIoPcEpTable table."
    INDEX { cucsEtherServerIntFIoPcEpInstanceId }
    ::= { cucsEtherServerIntFIoPcEpTable 1 }

CucsEtherServerIntFIoPcEpEntry ::= SEQUENCE {
    cucsEtherServerIntFIoPcEpInstanceId                              CucsManagedObjectId,
    cucsEtherServerIntFIoPcEpDnData                                  CucsManagedObjectDn,
    cucsEtherServerIntFIoPcEpRn                                      SnmpAdminString,
    cucsEtherServerIntFIoPcEpAdminState                              CucsEtherExternalEpAdminState,
    cucsEtherServerIntFIoPcEpChassisId                               Gauge32,
    cucsEtherServerIntFIoPcEpEpDn                                    SnmpAdminString,
    cucsEtherServerIntFIoPcEpIfRole                                  CucsEtherServerIntFIoPcEpIfRole,
    cucsEtherServerIntFIoPcEpIfType                                  CucsEtherPIoEpIfType,
    cucsEtherServerIntFIoPcEpLocale                                  CucsEtherExternalEpLocale,
    cucsEtherServerIntFIoPcEpMembership                              CucsFabricMembershipStatus,
    cucsEtherServerIntFIoPcEpName                                    SnmpAdminString,
    cucsEtherServerIntFIoPcEpPeerChassisId                           Gauge32,
    cucsEtherServerIntFIoPcEpPeerDn                                  SnmpAdminString,
    cucsEtherServerIntFIoPcEpPeerPortId                              Gauge32,
    cucsEtherServerIntFIoPcEpPeerSlotId                              Gauge32,
    cucsEtherServerIntFIoPcEpPortId                                  CucsEtherServerIntFIoPcEpPortId,
    cucsEtherServerIntFIoPcEpSlotId                                  Gauge32,
    cucsEtherServerIntFIoPcEpSwitchId                                CucsNetworkSwitchId,
    cucsEtherServerIntFIoPcEpTransport                               CucsNetworkTransport,
    cucsEtherServerIntFIoPcEpType                                    CucsEtherIntFIoEpType,
    cucsEtherServerIntFIoPcEpAggrPortId                              Gauge32,
    cucsEtherServerIntFIoPcEpPeerAggrPortId                          Gauge32
}

cucsEtherServerIntFIoPcEpInstanceId OBJECT-TYPE
    SYNTAX       CucsManagedObjectId
    MAX-ACCESS   not-accessible
    STATUS       current
    DESCRIPTION
        "Instance identifier of the managed object."
    ::= { cucsEtherServerIntFIoPcEpEntry 1 }

cucsEtherServerIntFIoPcEpDnData OBJECT-TYPE
    SYNTAX       CucsManagedObjectDn
    MAX-ACCESS   read-only
    STATUS       current
    DESCRIPTION
        "Cisco UCS ether:ServerIntFIoPcEp:dn managed object property"
    ::= { cucsEtherServerIntFIoPcEpEntry 2 }

cucsEtherServerIntFIoPcEpRn OBJECT-TYPE
    SYNTAX       SnmpAdminString
    MAX-ACCESS   read-only
    STATUS       current
    DESCRIPTION
        "Cisco UCS ether:ServerIntFIoPcEp:rn managed object property"
    ::= { cucsEtherServerIntFIoPcEpEntry 3 }

cucsEtherServerIntFIoPcEpAdminState OBJECT-TYPE
    SYNTAX       CucsEtherExternalEpAdminState
    MAX-ACCESS   read-only
    STATUS       current
    DESCRIPTION
        "Cisco UCS ether:ServerIntFIoPcEp:adminState managed
        object property"
    ::= { cucsEtherServerIntFIoPcEpEntry 4 }

cucsEtherServerIntFIoPcEpChassisId OBJECT-TYPE
    SYNTAX       Gauge32
    MAX-ACCESS   read-only
    STATUS       current
    DESCRIPTION
        "Cisco UCS ether:ServerIntFIoPcEp:chassisId managed
        object property"
    ::= { cucsEtherServerIntFIoPcEpEntry 5 }

cucsEtherServerIntFIoPcEpEpDn OBJECT-TYPE
    SYNTAX       SnmpAdminString
    MAX-ACCESS   read-only
    STATUS       current
    DESCRIPTION
        "Cisco UCS ether:ServerIntFIoPcEp:epDn managed object property"
    ::= { cucsEtherServerIntFIoPcEpEntry 6 }

cucsEtherServerIntFIoPcEpIfRole OBJECT-TYPE
    SYNTAX       CucsEtherServerIntFIoPcEpIfRole
    MAX-ACCESS   read-only
    STATUS       current
    DESCRIPTION
        "Cisco UCS ether:ServerIntFIoPcEp:ifRole managed object property"
    ::= { cucsEtherServerIntFIoPcEpEntry 7 }

cucsEtherServerIntFIoPcEpIfType OBJECT-TYPE
    SYNTAX       CucsEtherPIoEpIfType
    MAX-ACCESS   read-only
    STATUS       current
    DESCRIPTION
        "Cisco UCS ether:ServerIntFIoPcEp:ifType managed object property"
    ::= { cucsEtherServerIntFIoPcEpEntry 8 }

cucsEtherServerIntFIoPcEpLocale OBJECT-TYPE
    SYNTAX       CucsEtherExternalEpLocale
    MAX-ACCESS   read-only
    STATUS       current
    DESCRIPTION
        "Cisco UCS ether:ServerIntFIoPcEp:locale managed object property"
    ::= { cucsEtherServerIntFIoPcEpEntry 9 }

cucsEtherServerIntFIoPcEpMembership OBJECT-TYPE
    SYNTAX       CucsFabricMembershipStatus
    MAX-ACCESS   read-only
    STATUS       current
    DESCRIPTION
        "Cisco UCS ether:ServerIntFIoPcEp:membership managed
        object property"
    ::= { cucsEtherServerIntFIoPcEpEntry 10 }

cucsEtherServerIntFIoPcEpName OBJECT-TYPE
    SYNTAX       SnmpAdminString
    MAX-ACCESS   read-only
    STATUS       current
    DESCRIPTION
        "Cisco UCS ether:ServerIntFIoPcEp:name managed object property"
    ::= { cucsEtherServerIntFIoPcEpEntry 11 }

cucsEtherServerIntFIoPcEpPeerChassisId OBJECT-TYPE
    SYNTAX       Gauge32
    MAX-ACCESS   read-only
    STATUS       current
    DESCRIPTION
        "Cisco UCS ether:ServerIntFIoPcEp:peerChassisId
        managed object property"
    ::= { cucsEtherServerIntFIoPcEpEntry 12 }

cucsEtherServerIntFIoPcEpPeerDn OBJECT-TYPE
    SYNTAX       SnmpAdminString
    MAX-ACCESS   read-only
    STATUS       current
    DESCRIPTION
        "Cisco UCS ether:ServerIntFIoPcEp:peerDn managed object property"
    ::= { cucsEtherServerIntFIoPcEpEntry 13 }

cucsEtherServerIntFIoPcEpPeerPortId OBJECT-TYPE
    SYNTAX       Gauge32
    MAX-ACCESS   read-only
    STATUS       current
    DESCRIPTION
        "Cisco UCS ether:ServerIntFIoPcEp:peerPortId managed
        object property"
    ::= { cucsEtherServerIntFIoPcEpEntry 14 }

cucsEtherServerIntFIoPcEpPeerSlotId OBJECT-TYPE
    SYNTAX       Gauge32
    MAX-ACCESS   read-only
    STATUS       current
    DESCRIPTION
        "Cisco UCS ether:ServerIntFIoPcEp:peerSlotId managed
        object property"
    ::= { cucsEtherServerIntFIoPcEpEntry 15 }

cucsEtherServerIntFIoPcEpPortId OBJECT-TYPE
    SYNTAX       CucsEtherServerIntFIoPcEpPortId
    MAX-ACCESS   read-only
    STATUS       current
    DESCRIPTION
        "Cisco UCS ether:ServerIntFIoPcEp:portId managed object property"
    ::= { cucsEtherServerIntFIoPcEpEntry 16 }

cucsEtherServerIntFIoPcEpSlotId OBJECT-TYPE
    SYNTAX       Gauge32
    MAX-ACCESS   read-only
    STATUS       current
    DESCRIPTION
        "Cisco UCS ether:ServerIntFIoPcEp:slotId managed object property"
    ::= { cucsEtherServerIntFIoPcEpEntry 17 }

cucsEtherServerIntFIoPcEpSwitchId OBJECT-TYPE
    SYNTAX       CucsNetworkSwitchId
    MAX-ACCESS   read-only
    STATUS       current
    DESCRIPTION
        "Cisco UCS ether:ServerIntFIoPcEp:switchId managed
        object property"
    ::= { cucsEtherServerIntFIoPcEpEntry 18 }

cucsEtherServerIntFIoPcEpTransport OBJECT-TYPE
    SYNTAX       CucsNetworkTransport
    MAX-ACCESS   read-only
    STATUS       current
    DESCRIPTION
        "Cisco UCS ether:ServerIntFIoPcEp:transport managed
        object property"
    ::= { cucsEtherServerIntFIoPcEpEntry 19 }

cucsEtherServerIntFIoPcEpType OBJECT-TYPE
    SYNTAX       CucsEtherIntFIoEpType
    MAX-ACCESS   read-only
    STATUS       current
    DESCRIPTION
        "Cisco UCS ether:ServerIntFIoPcEp:type managed object property"
    ::= { cucsEtherServerIntFIoPcEpEntry 20 }

cucsEtherServerIntFIoPcEpAggrPortId OBJECT-TYPE
    SYNTAX       Gauge32
    MAX-ACCESS   read-only
    STATUS       current
    DESCRIPTION
        "Cisco UCS ether:ServerIntFIoPcEp:aggrPortId managed
        object property"
    ::= { cucsEtherServerIntFIoPcEpEntry 21 }

cucsEtherServerIntFIoPcEpPeerAggrPortId OBJECT-TYPE
    SYNTAX       Gauge32
    MAX-ACCESS   read-only
    STATUS       current
    DESCRIPTION
        "Cisco UCS ether:ServerIntFIoPcEp:peerAggrPortId
        managed object property"
    ::= { cucsEtherServerIntFIoPcEpEntry 22 }

cucsEtherSwIfConfigTable OBJECT-TYPE
    SYNTAX           SEQUENCE OF CucsEtherSwIfConfigEntry
    MAX-ACCESS       not-accessible
    STATUS           current
    DESCRIPTION
        "Cisco UCS ether:SwIfConfig managed object table"
    ::= { cucsEtherObjects 12 }

cucsEtherSwIfConfigEntry OBJECT-TYPE
    SYNTAX           CucsEtherSwIfConfigEntry
    MAX-ACCESS       not-accessible
    STATUS           current
    DESCRIPTION
        "Entry for the cucsEtherSwIfConfigTable table."
    INDEX { cucsEtherSwIfConfigInstanceId }
    ::= { cucsEtherSwIfConfigTable 1 }

CucsEtherSwIfConfigEntry ::= SEQUENCE {
    cucsEtherSwIfConfigInstanceId                                    CucsManagedObjectId,
    cucsEtherSwIfConfigDn                                            CucsManagedObjectDn,
    cucsEtherSwIfConfigRn                                            SnmpAdminString
}

cucsEtherSwIfConfigInstanceId OBJECT-TYPE
    SYNTAX       CucsManagedObjectId
    MAX-ACCESS   not-accessible
    STATUS       current
    DESCRIPTION
        "Instance identifier of the managed object."
    ::= { cucsEtherSwIfConfigEntry 1 }

cucsEtherSwIfConfigDn OBJECT-TYPE
    SYNTAX       CucsManagedObjectDn
    MAX-ACCESS   read-only
    STATUS       current
    DESCRIPTION
        "Cisco UCS ether:SwIfConfig:dn managed object property"
    ::= { cucsEtherSwIfConfigEntry 2 }

cucsEtherSwIfConfigRn OBJECT-TYPE
    SYNTAX       SnmpAdminString
    MAX-ACCESS   read-only
    STATUS       current
    DESCRIPTION
        "Cisco UCS ether:SwIfConfig:rn managed object property"
    ::= { cucsEtherSwIfConfigEntry 3 }

cucsEtherSwitchIntFIoTable OBJECT-TYPE
    SYNTAX           SEQUENCE OF CucsEtherSwitchIntFIoEntry
    MAX-ACCESS       not-accessible
    STATUS           current
    DESCRIPTION
        "Cisco UCS ether:SwitchIntFIo managed object table"
    ::= { cucsEtherObjects 13 }

cucsEtherSwitchIntFIoEntry OBJECT-TYPE
    SYNTAX           CucsEtherSwitchIntFIoEntry
    MAX-ACCESS       not-accessible
    STATUS           current
    DESCRIPTION
        "Entry for the cucsEtherSwitchIntFIoTable table."
    INDEX { cucsEtherSwitchIntFIoInstanceId }
    ::= { cucsEtherSwitchIntFIoTable 1 }

CucsEtherSwitchIntFIoEntry ::= SEQUENCE {
    cucsEtherSwitchIntFIoInstanceId                                  CucsManagedObjectId,
    cucsEtherSwitchIntFIoDn                                          CucsManagedObjectDn,
    cucsEtherSwitchIntFIoRn                                          SnmpAdminString,
    cucsEtherSwitchIntFIoAck                                         CucsEtherSwitchIntFIoAck,
    cucsEtherSwitchIntFIoAdminState                                  CucsFabricAdminState,
    cucsEtherSwitchIntFIoChassisId                                   Gauge32,
    cucsEtherSwitchIntFIoDiscovery                                   CucsEtherSatelliteConnectionDisc,
    cucsEtherSwitchIntFIoEncap                                       CucsPortEncap,
    cucsEtherSwitchIntFIoEpDn                                        SnmpAdminString,
    cucsEtherSwitchIntFIoFltAggr                                     Unsigned64,
    cucsEtherSwitchIntFIoIfRole                                      CucsEtherSwitchIntFIoIfRole,
    cucsEtherSwitchIntFIoIfType                                      CucsNetworkPhysEpIfType,
    cucsEtherSwitchIntFIoLocale                                      CucsEtherSwitchIntFIoLocale,
    cucsEtherSwitchIntFIoMode                                        CucsPortMode,
    cucsEtherSwitchIntFIoModel                                       SnmpAdminString,
    cucsEtherSwitchIntFIoName                                        SnmpAdminString,
    cucsEtherSwitchIntFIoOperState                                   CucsNetworkPortOperState,
    cucsEtherSwitchIntFIoPeerDn                                      SnmpAdminString,
    cucsEtherSwitchIntFIoPeerPortId                                  Gauge32,
    cucsEtherSwitchIntFIoPeerSlotId                                  Gauge32,
    cucsEtherSwitchIntFIoPortId                                      Gauge32,
    cucsEtherSwitchIntFIoRevision                                    SnmpAdminString,
    cucsEtherSwitchIntFIoSerial                                      SnmpAdminString,
    cucsEtherSwitchIntFIoSlotId                                      Gauge32,
    cucsEtherSwitchIntFIoStateQual                                   SnmpAdminString,
    cucsEtherSwitchIntFIoSwitchId                                    CucsNetworkSwitchId,
    cucsEtherSwitchIntFIoTransport                                   CucsEtherSwitchIntFIoTransport,
    cucsEtherSwitchIntFIoTs                                          DateAndTime,
    cucsEtherSwitchIntFIoType                                        CucsEtherSwitchIntFIoType,
    cucsEtherSwitchIntFIoVendor                                      SnmpAdminString,
    cucsEtherSwitchIntFIoPeerChassisId                               Gauge32,
    cucsEtherSwitchIntFIoXcvrType                                    CucsEquipmentXcvrType,
    cucsEtherSwitchIntFIoDelFeTs                                     Unsigned64,
    cucsEtherSwitchIntFIoNewFeTs                                     Unsigned64,
    cucsEtherSwitchIntFIoAggrPortId                                  Gauge32,
    cucsEtherSwitchIntFIoPeerAggrPortId                              Gauge32,
    cucsEtherSwitchIntFIoMacAddr                                     MacAddress
}

cucsEtherSwitchIntFIoInstanceId OBJECT-TYPE
    SYNTAX       CucsManagedObjectId
    MAX-ACCESS   not-accessible
    STATUS       current
    DESCRIPTION
        "Instance identifier of the managed object."
    ::= { cucsEtherSwitchIntFIoEntry 1 }

cucsEtherSwitchIntFIoDn OBJECT-TYPE
    SYNTAX       CucsManagedObjectDn
    MAX-ACCESS   read-only
    STATUS       current
    DESCRIPTION
        "Cisco UCS ether:SwitchIntFIo:dn managed object property"
    ::= { cucsEtherSwitchIntFIoEntry 2 }

cucsEtherSwitchIntFIoRn OBJECT-TYPE
    SYNTAX       SnmpAdminString
    MAX-ACCESS   read-only
    STATUS       current
    DESCRIPTION
        "Cisco UCS ether:SwitchIntFIo:rn managed object property"
    ::= { cucsEtherSwitchIntFIoEntry 3 }

cucsEtherSwitchIntFIoAck OBJECT-TYPE
    SYNTAX       CucsEtherSwitchIntFIoAck
    MAX-ACCESS   read-only
    STATUS       current
    DESCRIPTION
        "Cisco UCS ether:SwitchIntFIo:ack managed object property"
    ::= { cucsEtherSwitchIntFIoEntry 4 }

cucsEtherSwitchIntFIoAdminState OBJECT-TYPE
    SYNTAX       CucsFabricAdminState
    MAX-ACCESS   read-only
    STATUS       current
    DESCRIPTION
        "Cisco UCS ether:SwitchIntFIo:adminState managed object property"
    ::= { cucsEtherSwitchIntFIoEntry 5 }

cucsEtherSwitchIntFIoChassisId OBJECT-TYPE
    SYNTAX       Gauge32
    MAX-ACCESS   read-only
    STATUS       current
    DESCRIPTION
        "Cisco UCS ether:SwitchIntFIo:chassisId managed object property"
    ::= { cucsEtherSwitchIntFIoEntry 6 }

cucsEtherSwitchIntFIoDiscovery OBJECT-TYPE
    SYNTAX       CucsEtherSatelliteConnectionDisc
    MAX-ACCESS   read-only
    STATUS       current
    DESCRIPTION
        "Cisco UCS ether:SwitchIntFIo:discovery managed object property"
    ::= { cucsEtherSwitchIntFIoEntry 7 }

cucsEtherSwitchIntFIoEncap OBJECT-TYPE
    SYNTAX       CucsPortEncap
    MAX-ACCESS   read-only
    STATUS       current
    DESCRIPTION
        "Cisco UCS ether:SwitchIntFIo:encap managed object property"
    ::= { cucsEtherSwitchIntFIoEntry 8 }

cucsEtherSwitchIntFIoEpDn OBJECT-TYPE
    SYNTAX       SnmpAdminString
    MAX-ACCESS   read-only
    STATUS       current
    DESCRIPTION
        "Cisco UCS ether:SwitchIntFIo:epDn managed object property"
    ::= { cucsEtherSwitchIntFIoEntry 9 }

cucsEtherSwitchIntFIoFltAggr OBJECT-TYPE
    SYNTAX       Unsigned64
    MAX-ACCESS   read-only
    STATUS       current
    DESCRIPTION
        "Cisco UCS ether:SwitchIntFIo:fltAggr managed object property"
    ::= { cucsEtherSwitchIntFIoEntry 10 }

cucsEtherSwitchIntFIoIfRole OBJECT-TYPE
    SYNTAX       CucsEtherSwitchIntFIoIfRole
    MAX-ACCESS   read-only
    STATUS       current
    DESCRIPTION
        "Cisco UCS ether:SwitchIntFIo:ifRole managed object property"
    ::= { cucsEtherSwitchIntFIoEntry 11 }

cucsEtherSwitchIntFIoIfType OBJECT-TYPE
    SYNTAX       CucsNetworkPhysEpIfType
    MAX-ACCESS   read-only
    STATUS       current
    DESCRIPTION
        "Cisco UCS ether:SwitchIntFIo:ifType managed object property"
    ::= { cucsEtherSwitchIntFIoEntry 12 }

cucsEtherSwitchIntFIoLocale OBJECT-TYPE
    SYNTAX       CucsEtherSwitchIntFIoLocale
    MAX-ACCESS   read-only
    STATUS       current
    DESCRIPTION
        "Cisco UCS ether:SwitchIntFIo:locale managed object property"
    ::= { cucsEtherSwitchIntFIoEntry 13 }

cucsEtherSwitchIntFIoMode OBJECT-TYPE
    SYNTAX       CucsPortMode
    MAX-ACCESS   read-only
    STATUS       current
    DESCRIPTION
        "Cisco UCS ether:SwitchIntFIo:mode managed object property"
    ::= { cucsEtherSwitchIntFIoEntry 14 }

cucsEtherSwitchIntFIoModel OBJECT-TYPE
    SYNTAX       SnmpAdminString
    MAX-ACCESS   read-only
    STATUS       current
    DESCRIPTION
        "Cisco UCS ether:SwitchIntFIo:model managed object property"
    ::= { cucsEtherSwitchIntFIoEntry 15 }

cucsEtherSwitchIntFIoName OBJECT-TYPE
    SYNTAX       SnmpAdminString
    MAX-ACCESS   read-only
    STATUS       current
    DESCRIPTION
        "Cisco UCS ether:SwitchIntFIo:name managed object property"
    ::= { cucsEtherSwitchIntFIoEntry 16 }

cucsEtherSwitchIntFIoOperState OBJECT-TYPE
    SYNTAX       CucsNetworkPortOperState
    MAX-ACCESS   read-only
    STATUS       current
    DESCRIPTION
        "Cisco UCS ether:SwitchIntFIo:operState managed object property"
    ::= { cucsEtherSwitchIntFIoEntry 17 }

cucsEtherSwitchIntFIoPeerDn OBJECT-TYPE
    SYNTAX       SnmpAdminString
    MAX-ACCESS   read-only
    STATUS       current
    DESCRIPTION
        "Cisco UCS ether:SwitchIntFIo:peerDn managed object property"
    ::= { cucsEtherSwitchIntFIoEntry 18 }

cucsEtherSwitchIntFIoPeerPortId OBJECT-TYPE
    SYNTAX       Gauge32
    MAX-ACCESS   read-only
    STATUS       current
    DESCRIPTION
        "Cisco UCS ether:SwitchIntFIo:peerPortId managed object property"
    ::= { cucsEtherSwitchIntFIoEntry 19 }

cucsEtherSwitchIntFIoPeerSlotId OBJECT-TYPE
    SYNTAX       Gauge32
    MAX-ACCESS   read-only
    STATUS       current
    DESCRIPTION
        "Cisco UCS ether:SwitchIntFIo:peerSlotId managed object property"
    ::= { cucsEtherSwitchIntFIoEntry 20 }

cucsEtherSwitchIntFIoPortId OBJECT-TYPE
    SYNTAX       Gauge32
    MAX-ACCESS   read-only
    STATUS       current
    DESCRIPTION
        "Cisco UCS ether:SwitchIntFIo:portId managed object property"
    ::= { cucsEtherSwitchIntFIoEntry 21 }

cucsEtherSwitchIntFIoRevision OBJECT-TYPE
    SYNTAX       SnmpAdminString
    MAX-ACCESS   read-only
    STATUS       current
    DESCRIPTION
        "Cisco UCS ether:SwitchIntFIo:revision managed object property"
    ::= { cucsEtherSwitchIntFIoEntry 22 }

cucsEtherSwitchIntFIoSerial OBJECT-TYPE
    SYNTAX       SnmpAdminString
    MAX-ACCESS   read-only
    STATUS       current
    DESCRIPTION
        "Cisco UCS ether:SwitchIntFIo:serial managed object property"
    ::= { cucsEtherSwitchIntFIoEntry 23 }

cucsEtherSwitchIntFIoSlotId OBJECT-TYPE
    SYNTAX       Gauge32
    MAX-ACCESS   read-only
    STATUS       current
    DESCRIPTION
        "Cisco UCS ether:SwitchIntFIo:slotId managed object property"
    ::= { cucsEtherSwitchIntFIoEntry 24 }

cucsEtherSwitchIntFIoStateQual OBJECT-TYPE
    SYNTAX       SnmpAdminString
    MAX-ACCESS   read-only
    STATUS       current
    DESCRIPTION
        "Cisco UCS ether:SwitchIntFIo:stateQual managed object property"
    ::= { cucsEtherSwitchIntFIoEntry 25 }

cucsEtherSwitchIntFIoSwitchId OBJECT-TYPE
    SYNTAX       CucsNetworkSwitchId
    MAX-ACCESS   read-only
    STATUS       current
    DESCRIPTION
        "Cisco UCS ether:SwitchIntFIo:switchId managed object property"
    ::= { cucsEtherSwitchIntFIoEntry 26 }

cucsEtherSwitchIntFIoTransport OBJECT-TYPE
    SYNTAX       CucsEtherSwitchIntFIoTransport
    MAX-ACCESS   read-only
    STATUS       current
    DESCRIPTION
        "Cisco UCS ether:SwitchIntFIo:transport managed object property"
    ::= { cucsEtherSwitchIntFIoEntry 27 }

cucsEtherSwitchIntFIoTs OBJECT-TYPE
    SYNTAX       DateAndTime
    MAX-ACCESS   read-only
    STATUS       current
    DESCRIPTION
        "Cisco UCS ether:SwitchIntFIo:ts managed object property"
    ::= { cucsEtherSwitchIntFIoEntry 28 }

cucsEtherSwitchIntFIoType OBJECT-TYPE
    SYNTAX       CucsEtherSwitchIntFIoType
    MAX-ACCESS   read-only
    STATUS       current
    DESCRIPTION
        "Cisco UCS ether:SwitchIntFIo:type managed object property"
    ::= { cucsEtherSwitchIntFIoEntry 29 }

cucsEtherSwitchIntFIoVendor OBJECT-TYPE
    SYNTAX       SnmpAdminString
    MAX-ACCESS   read-only
    STATUS       current
    DESCRIPTION
        "Cisco UCS ether:SwitchIntFIo:vendor managed object property"
    ::= { cucsEtherSwitchIntFIoEntry 30 }

cucsEtherSwitchIntFIoPeerChassisId OBJECT-TYPE
    SYNTAX       Gauge32
    MAX-ACCESS   read-only
    STATUS       current
    DESCRIPTION
        "Cisco UCS ether:SwitchIntFIo:peerChassisId managed
        object property"
    ::= { cucsEtherSwitchIntFIoEntry 31 }

cucsEtherSwitchIntFIoXcvrType OBJECT-TYPE
    SYNTAX       CucsEquipmentXcvrType
    MAX-ACCESS   read-only
    STATUS       current
    DESCRIPTION
        "Cisco UCS ether:SwitchIntFIo:xcvrType managed object property"
    ::= { cucsEtherSwitchIntFIoEntry 32 }

cucsEtherSwitchIntFIoDelFeTs OBJECT-TYPE
    SYNTAX       Unsigned64
    MAX-ACCESS   read-only
    STATUS       current
    DESCRIPTION
        "Cisco UCS ether:SwitchIntFIo:delFeTs managed object property"
    ::= { cucsEtherSwitchIntFIoEntry 33 }

cucsEtherSwitchIntFIoNewFeTs OBJECT-TYPE
    SYNTAX       Unsigned64
    MAX-ACCESS   read-only
    STATUS       current
    DESCRIPTION
        "Cisco UCS ether:SwitchIntFIo:newFeTs managed object property"
    ::= { cucsEtherSwitchIntFIoEntry 34 }

cucsEtherSwitchIntFIoAggrPortId OBJECT-TYPE
    SYNTAX       Gauge32
    MAX-ACCESS   read-only
    STATUS       current
    DESCRIPTION
        "Cisco UCS ether:SwitchIntFIo:aggrPortId managed object property"
    ::= { cucsEtherSwitchIntFIoEntry 35 }

cucsEtherSwitchIntFIoPeerAggrPortId OBJECT-TYPE
    SYNTAX       Gauge32
    MAX-ACCESS   read-only
    STATUS       current
    DESCRIPTION
        "Cisco UCS ether:SwitchIntFIo:peerAggrPortId managed
        object property"
    ::= { cucsEtherSwitchIntFIoEntry 36 }

cucsEtherSwitchIntFIoMacAddr OBJECT-TYPE
    SYNTAX       MacAddress
    MAX-ACCESS   read-only
    STATUS       current
    DESCRIPTION
        "Cisco UCS ether:SwitchIntFIo:macAddr managed object property"
    ::= { cucsEtherSwitchIntFIoEntry 37 }

cucsEtherSwitchIntFIoPcTable OBJECT-TYPE
    SYNTAX           SEQUENCE OF CucsEtherSwitchIntFIoPcEntry
    MAX-ACCESS       not-accessible
    STATUS           current
    DESCRIPTION
        "Cisco UCS ether:SwitchIntFIoPc managed object table"
    ::= { cucsEtherObjects 20 }

cucsEtherSwitchIntFIoPcEntry OBJECT-TYPE
    SYNTAX           CucsEtherSwitchIntFIoPcEntry
    MAX-ACCESS       not-accessible
    STATUS           current
    DESCRIPTION
        "Entry for the cucsEtherSwitchIntFIoPcTable table."
    INDEX { cucsEtherSwitchIntFIoPcInstanceId }
    ::= { cucsEtherSwitchIntFIoPcTable 1 }

CucsEtherSwitchIntFIoPcEntry ::= SEQUENCE {
    cucsEtherSwitchIntFIoPcInstanceId                                CucsManagedObjectId,
    cucsEtherSwitchIntFIoPcDn                                        CucsManagedObjectDn,
    cucsEtherSwitchIntFIoPcRn                                        SnmpAdminString,
    cucsEtherSwitchIntFIoPcAdminState                                CucsEtherExternalPcAdminState,
    cucsEtherSwitchIntFIoPcChassisId                                 Gauge32,
    cucsEtherSwitchIntFIoPcEpDn                                      SnmpAdminString,
    cucsEtherSwitchIntFIoPcFltAggr                                   Unsigned64,
    cucsEtherSwitchIntFIoPcIfRole                                    CucsEtherSwitchIntFIoPcIfRole,
    cucsEtherSwitchIntFIoPcIfType                                    CucsEtherCIoEpIfType,
    cucsEtherSwitchIntFIoPcLocale                                    CucsEtherExternalPcLocale,
    cucsEtherSwitchIntFIoPcName                                      SnmpAdminString,
    cucsEtherSwitchIntFIoPcOperSpeed                                 CucsPortEthSpeed,
    cucsEtherSwitchIntFIoPcOperState                                 CucsNetworkPortOperState,
    cucsEtherSwitchIntFIoPcPeerDn                                    SnmpAdminString,
    cucsEtherSwitchIntFIoPcPortId                                    CucsEtherSwitchIntFIoPcPortId,
    cucsEtherSwitchIntFIoPcStateQual                                 SnmpAdminString,
    cucsEtherSwitchIntFIoPcSwitchId                                  CucsNetworkSwitchId,
    cucsEtherSwitchIntFIoPcTransport                                 CucsEtherSwitchIntFIoPcTransport,
    cucsEtherSwitchIntFIoPcType                                      CucsEtherSwitchIntFIoPcType,
    cucsEtherSwitchIntFIoPcMulticastHwHash                           CucsEtherSwitchIntFIoPcMulticastHwHash
}

cucsEtherSwitchIntFIoPcInstanceId OBJECT-TYPE
    SYNTAX       CucsManagedObjectId
    MAX-ACCESS   not-accessible
    STATUS       current
    DESCRIPTION
        "Instance identifier of the managed object."
    ::= { cucsEtherSwitchIntFIoPcEntry 1 }

cucsEtherSwitchIntFIoPcDn OBJECT-TYPE
    SYNTAX       CucsManagedObjectDn
    MAX-ACCESS   read-only
    STATUS       current
    DESCRIPTION
        "Cisco UCS ether:SwitchIntFIoPc:dn managed object property"
    ::= { cucsEtherSwitchIntFIoPcEntry 2 }

cucsEtherSwitchIntFIoPcRn OBJECT-TYPE
    SYNTAX       SnmpAdminString
    MAX-ACCESS   read-only
    STATUS       current
    DESCRIPTION
        "Cisco UCS ether:SwitchIntFIoPc:rn managed object property"
    ::= { cucsEtherSwitchIntFIoPcEntry 3 }

cucsEtherSwitchIntFIoPcAdminState OBJECT-TYPE
    SYNTAX       CucsEtherExternalPcAdminState
    MAX-ACCESS   read-only
    STATUS       current
    DESCRIPTION
        "Cisco UCS ether:SwitchIntFIoPc:adminState managed
        object property"
    ::= { cucsEtherSwitchIntFIoPcEntry 4 }

cucsEtherSwitchIntFIoPcChassisId OBJECT-TYPE
    SYNTAX       Gauge32
    MAX-ACCESS   read-only
    STATUS       current
    DESCRIPTION
        "Cisco UCS ether:SwitchIntFIoPc:chassisId managed object property"
    ::= { cucsEtherSwitchIntFIoPcEntry 5 }

cucsEtherSwitchIntFIoPcEpDn OBJECT-TYPE
    SYNTAX       SnmpAdminString
    MAX-ACCESS   read-only
    STATUS       current
    DESCRIPTION
        "Cisco UCS ether:SwitchIntFIoPc:epDn managed object property"
    ::= { cucsEtherSwitchIntFIoPcEntry 6 }

cucsEtherSwitchIntFIoPcFltAggr OBJECT-TYPE
    SYNTAX       Unsigned64
    MAX-ACCESS   read-only
    STATUS       current
    DESCRIPTION
        "Cisco UCS ether:SwitchIntFIoPc:fltAggr managed object property"
    ::= { cucsEtherSwitchIntFIoPcEntry 7 }

cucsEtherSwitchIntFIoPcIfRole OBJECT-TYPE
    SYNTAX       CucsEtherSwitchIntFIoPcIfRole
    MAX-ACCESS   read-only
    STATUS       current
    DESCRIPTION
        "Cisco UCS ether:SwitchIntFIoPc:ifRole managed object property"
    ::= { cucsEtherSwitchIntFIoPcEntry 8 }

cucsEtherSwitchIntFIoPcIfType OBJECT-TYPE
    SYNTAX       CucsEtherCIoEpIfType
    MAX-ACCESS   read-only
    STATUS       current
    DESCRIPTION
        "Cisco UCS ether:SwitchIntFIoPc:ifType managed object property"
    ::= { cucsEtherSwitchIntFIoPcEntry 9 }

cucsEtherSwitchIntFIoPcLocale OBJECT-TYPE
    SYNTAX       CucsEtherExternalPcLocale
    MAX-ACCESS   read-only
    STATUS       current
    DESCRIPTION
        "Cisco UCS ether:SwitchIntFIoPc:locale managed object property"
    ::= { cucsEtherSwitchIntFIoPcEntry 10 }

cucsEtherSwitchIntFIoPcName OBJECT-TYPE
    SYNTAX       SnmpAdminString
    MAX-ACCESS   read-only
    STATUS       current
    DESCRIPTION
        "Cisco UCS ether:SwitchIntFIoPc:name managed object property"
    ::= { cucsEtherSwitchIntFIoPcEntry 11 }

cucsEtherSwitchIntFIoPcOperSpeed OBJECT-TYPE
    SYNTAX       CucsPortEthSpeed
    MAX-ACCESS   read-only
    STATUS       current
    DESCRIPTION
        "Cisco UCS ether:SwitchIntFIoPc:operSpeed managed object property"
    ::= { cucsEtherSwitchIntFIoPcEntry 12 }

cucsEtherSwitchIntFIoPcOperState OBJECT-TYPE
    SYNTAX       CucsNetworkPortOperState
    MAX-ACCESS   read-only
    STATUS       current
    DESCRIPTION
        "Cisco UCS ether:SwitchIntFIoPc:operState managed object property"
    ::= { cucsEtherSwitchIntFIoPcEntry 13 }

cucsEtherSwitchIntFIoPcPeerDn OBJECT-TYPE
    SYNTAX       SnmpAdminString
    MAX-ACCESS   read-only
    STATUS       current
    DESCRIPTION
        "Cisco UCS ether:SwitchIntFIoPc:peerDn managed object property"
    ::= { cucsEtherSwitchIntFIoPcEntry 14 }

cucsEtherSwitchIntFIoPcPortId OBJECT-TYPE
    SYNTAX       CucsEtherSwitchIntFIoPcPortId
    MAX-ACCESS   read-only
    STATUS       current
    DESCRIPTION
        "Cisco UCS ether:SwitchIntFIoPc:portId managed object property"
    ::= { cucsEtherSwitchIntFIoPcEntry 15 }

cucsEtherSwitchIntFIoPcStateQual OBJECT-TYPE
    SYNTAX       SnmpAdminString
    MAX-ACCESS   read-only
    STATUS       current
    DESCRIPTION
        "Cisco UCS ether:SwitchIntFIoPc:stateQual managed object property"
    ::= { cucsEtherSwitchIntFIoPcEntry 16 }

cucsEtherSwitchIntFIoPcSwitchId OBJECT-TYPE
    SYNTAX       CucsNetworkSwitchId
    MAX-ACCESS   read-only
    STATUS       current
    DESCRIPTION
        "Cisco UCS ether:SwitchIntFIoPc:switchId managed object property"
    ::= { cucsEtherSwitchIntFIoPcEntry 17 }

cucsEtherSwitchIntFIoPcTransport OBJECT-TYPE
    SYNTAX       CucsEtherSwitchIntFIoPcTransport
    MAX-ACCESS   read-only
    STATUS       current
    DESCRIPTION
        "Cisco UCS ether:SwitchIntFIoPc:transport managed object property"
    ::= { cucsEtherSwitchIntFIoPcEntry 18 }

cucsEtherSwitchIntFIoPcType OBJECT-TYPE
    SYNTAX       CucsEtherSwitchIntFIoPcType
    MAX-ACCESS   read-only
    STATUS       current
    DESCRIPTION
        "Cisco UCS ether:SwitchIntFIoPc:type managed object property"
    ::= { cucsEtherSwitchIntFIoPcEntry 19 }

cucsEtherSwitchIntFIoPcMulticastHwHash OBJECT-TYPE
    SYNTAX       CucsEtherSwitchIntFIoPcMulticastHwHash
    MAX-ACCESS   read-only
    STATUS       current
    DESCRIPTION
        "Cisco UCS ether:SwitchIntFIoPc:multicastHwHash
        managed object property"
    ::= { cucsEtherSwitchIntFIoPcEntry 20 }

cucsEtherSwitchIntFIoPcEpTable OBJECT-TYPE
    SYNTAX           SEQUENCE OF CucsEtherSwitchIntFIoPcEpEntry
    MAX-ACCESS       not-accessible
    STATUS           current
    DESCRIPTION
        "Cisco UCS ether:SwitchIntFIoPcEp managed object table"
    ::= { cucsEtherObjects 21 }

cucsEtherSwitchIntFIoPcEpEntry OBJECT-TYPE
    SYNTAX           CucsEtherSwitchIntFIoPcEpEntry
    MAX-ACCESS       not-accessible
    STATUS           current
    DESCRIPTION
        "Entry for the cucsEtherSwitchIntFIoPcEpTable table."
    INDEX { cucsEtherSwitchIntFIoPcEpInstanceId }
    ::= { cucsEtherSwitchIntFIoPcEpTable 1 }

CucsEtherSwitchIntFIoPcEpEntry ::= SEQUENCE {
    cucsEtherSwitchIntFIoPcEpInstanceId                              CucsManagedObjectId,
    cucsEtherSwitchIntFIoPcEpDnData                                  CucsManagedObjectDn,
    cucsEtherSwitchIntFIoPcEpRn                                      SnmpAdminString,
    cucsEtherSwitchIntFIoPcEpAdminState                              CucsEtherExternalEpAdminState,
    cucsEtherSwitchIntFIoPcEpChassisId                               Gauge32,
    cucsEtherSwitchIntFIoPcEpEpDn                                    SnmpAdminString,
    cucsEtherSwitchIntFIoPcEpIfRole                                  CucsEtherSwitchIntFIoPcEpIfRole,
    cucsEtherSwitchIntFIoPcEpIfType                                  CucsEtherPIoEpIfType,
    cucsEtherSwitchIntFIoPcEpLocale                                  CucsEtherExternalEpLocale,
    cucsEtherSwitchIntFIoPcEpMembership                              CucsFabricMembershipStatus,
    cucsEtherSwitchIntFIoPcEpName                                    SnmpAdminString,
    cucsEtherSwitchIntFIoPcEpPeerChassisId                           Gauge32,
    cucsEtherSwitchIntFIoPcEpPeerDn                                  SnmpAdminString,
    cucsEtherSwitchIntFIoPcEpPeerPortId                              Gauge32,
    cucsEtherSwitchIntFIoPcEpPeerSlotId                              Gauge32,
    cucsEtherSwitchIntFIoPcEpPortId                                  CucsEtherSwitchIntFIoPcEpPortId,
    cucsEtherSwitchIntFIoPcEpSlotId                                  Gauge32,
    cucsEtherSwitchIntFIoPcEpStatusChangeTs                          DateAndTime,
    cucsEtherSwitchIntFIoPcEpSwitchId                                CucsNetworkSwitchId,
    cucsEtherSwitchIntFIoPcEpTransport                               CucsNetworkTransport,
    cucsEtherSwitchIntFIoPcEpType                                    CucsEtherIntFIoEpType,
    cucsEtherSwitchIntFIoPcEpAckState                                CucsEquipmentChassisConfigState,
    cucsEtherSwitchIntFIoPcEpAggrPortId                              Gauge32,
    cucsEtherSwitchIntFIoPcEpPeerAggrPortId                          Gauge32
}

cucsEtherSwitchIntFIoPcEpInstanceId OBJECT-TYPE
    SYNTAX       CucsManagedObjectId
    MAX-ACCESS   not-accessible
    STATUS       current
    DESCRIPTION
        "Instance identifier of the managed object."
    ::= { cucsEtherSwitchIntFIoPcEpEntry 1 }

cucsEtherSwitchIntFIoPcEpDnData OBJECT-TYPE
    SYNTAX       CucsManagedObjectDn
    MAX-ACCESS   read-only
    STATUS       current
    DESCRIPTION
        "Cisco UCS ether:SwitchIntFIoPcEp:dn managed object property"
    ::= { cucsEtherSwitchIntFIoPcEpEntry 2 }

cucsEtherSwitchIntFIoPcEpRn OBJECT-TYPE
    SYNTAX       SnmpAdminString
    MAX-ACCESS   read-only
    STATUS       current
    DESCRIPTION
        "Cisco UCS ether:SwitchIntFIoPcEp:rn managed object property"
    ::= { cucsEtherSwitchIntFIoPcEpEntry 3 }

cucsEtherSwitchIntFIoPcEpAdminState OBJECT-TYPE
    SYNTAX       CucsEtherExternalEpAdminState
    MAX-ACCESS   read-only
    STATUS       current
    DESCRIPTION
        "Cisco UCS ether:SwitchIntFIoPcEp:adminState managed
        object property"
    ::= { cucsEtherSwitchIntFIoPcEpEntry 4 }

cucsEtherSwitchIntFIoPcEpChassisId OBJECT-TYPE
    SYNTAX       Gauge32
    MAX-ACCESS   read-only
    STATUS       current
    DESCRIPTION
        "Cisco UCS ether:SwitchIntFIoPcEp:chassisId managed
        object property"
    ::= { cucsEtherSwitchIntFIoPcEpEntry 5 }

cucsEtherSwitchIntFIoPcEpEpDn OBJECT-TYPE
    SYNTAX       SnmpAdminString
    MAX-ACCESS   read-only
    STATUS       current
    DESCRIPTION
        "Cisco UCS ether:SwitchIntFIoPcEp:epDn managed object property"
    ::= { cucsEtherSwitchIntFIoPcEpEntry 6 }

cucsEtherSwitchIntFIoPcEpIfRole OBJECT-TYPE
    SYNTAX       CucsEtherSwitchIntFIoPcEpIfRole
    MAX-ACCESS   read-only
    STATUS       current
    DESCRIPTION
        "Cisco UCS ether:SwitchIntFIoPcEp:ifRole managed object property"
    ::= { cucsEtherSwitchIntFIoPcEpEntry 7 }

cucsEtherSwitchIntFIoPcEpIfType OBJECT-TYPE
    SYNTAX       CucsEtherPIoEpIfType
    MAX-ACCESS   read-only
    STATUS       current
    DESCRIPTION
        "Cisco UCS ether:SwitchIntFIoPcEp:ifType managed object property"
    ::= { cucsEtherSwitchIntFIoPcEpEntry 8 }

cucsEtherSwitchIntFIoPcEpLocale OBJECT-TYPE
    SYNTAX       CucsEtherExternalEpLocale
    MAX-ACCESS   read-only
    STATUS       current
    DESCRIPTION
        "Cisco UCS ether:SwitchIntFIoPcEp:locale managed object property"
    ::= { cucsEtherSwitchIntFIoPcEpEntry 9 }

cucsEtherSwitchIntFIoPcEpMembership OBJECT-TYPE
    SYNTAX       CucsFabricMembershipStatus
    MAX-ACCESS   read-only
    STATUS       current
    DESCRIPTION
        "Cisco UCS ether:SwitchIntFIoPcEp:membership managed
        object property"
    ::= { cucsEtherSwitchIntFIoPcEpEntry 10 }

cucsEtherSwitchIntFIoPcEpName OBJECT-TYPE
    SYNTAX       SnmpAdminString
    MAX-ACCESS   read-only
    STATUS       current
    DESCRIPTION
        "Cisco UCS ether:SwitchIntFIoPcEp:name managed object property"
    ::= { cucsEtherSwitchIntFIoPcEpEntry 11 }

cucsEtherSwitchIntFIoPcEpPeerChassisId OBJECT-TYPE
    SYNTAX       Gauge32
    MAX-ACCESS   read-only
    STATUS       current
    DESCRIPTION
        "Cisco UCS ether:SwitchIntFIoPcEp:peerChassisId
        managed object property"
    ::= { cucsEtherSwitchIntFIoPcEpEntry 12 }

cucsEtherSwitchIntFIoPcEpPeerDn OBJECT-TYPE
    SYNTAX       SnmpAdminString
    MAX-ACCESS   read-only
    STATUS       current
    DESCRIPTION
        "Cisco UCS ether:SwitchIntFIoPcEp:peerDn managed object property"
    ::= { cucsEtherSwitchIntFIoPcEpEntry 13 }

cucsEtherSwitchIntFIoPcEpPeerPortId OBJECT-TYPE
    SYNTAX       Gauge32
    MAX-ACCESS   read-only
    STATUS       current
    DESCRIPTION
        "Cisco UCS ether:SwitchIntFIoPcEp:peerPortId managed
        object property"
    ::= { cucsEtherSwitchIntFIoPcEpEntry 14 }

cucsEtherSwitchIntFIoPcEpPeerSlotId OBJECT-TYPE
    SYNTAX       Gauge32
    MAX-ACCESS   read-only
    STATUS       current
    DESCRIPTION
        "Cisco UCS ether:SwitchIntFIoPcEp:peerSlotId managed
        object property"
    ::= { cucsEtherSwitchIntFIoPcEpEntry 15 }

cucsEtherSwitchIntFIoPcEpPortId OBJECT-TYPE
    SYNTAX       CucsEtherSwitchIntFIoPcEpPortId
    MAX-ACCESS   read-only
    STATUS       current
    DESCRIPTION
        "Cisco UCS ether:SwitchIntFIoPcEp:portId managed object property"
    ::= { cucsEtherSwitchIntFIoPcEpEntry 16 }

cucsEtherSwitchIntFIoPcEpSlotId OBJECT-TYPE
    SYNTAX       Gauge32
    MAX-ACCESS   read-only
    STATUS       current
    DESCRIPTION
        "Cisco UCS ether:SwitchIntFIoPcEp:slotId managed object property"
    ::= { cucsEtherSwitchIntFIoPcEpEntry 17 }

cucsEtherSwitchIntFIoPcEpStatusChangeTs OBJECT-TYPE
    SYNTAX       DateAndTime
    MAX-ACCESS   read-only
    STATUS       current
    DESCRIPTION
        "Cisco UCS ether:SwitchIntFIoPcEp:statusChangeTs
        managed object property"
    ::= { cucsEtherSwitchIntFIoPcEpEntry 18 }

cucsEtherSwitchIntFIoPcEpSwitchId OBJECT-TYPE
    SYNTAX       CucsNetworkSwitchId
    MAX-ACCESS   read-only
    STATUS       current
    DESCRIPTION
        "Cisco UCS ether:SwitchIntFIoPcEp:switchId managed
        object property"
    ::= { cucsEtherSwitchIntFIoPcEpEntry 19 }

cucsEtherSwitchIntFIoPcEpTransport OBJECT-TYPE
    SYNTAX       CucsNetworkTransport
    MAX-ACCESS   read-only
    STATUS       current
    DESCRIPTION
        "Cisco UCS ether:SwitchIntFIoPcEp:transport managed
        object property"
    ::= { cucsEtherSwitchIntFIoPcEpEntry 20 }

cucsEtherSwitchIntFIoPcEpType OBJECT-TYPE
    SYNTAX       CucsEtherIntFIoEpType
    MAX-ACCESS   read-only
    STATUS       current
    DESCRIPTION
        "Cisco UCS ether:SwitchIntFIoPcEp:type managed object property"
    ::= { cucsEtherSwitchIntFIoPcEpEntry 21 }

cucsEtherSwitchIntFIoPcEpAckState OBJECT-TYPE
    SYNTAX       CucsEquipmentChassisConfigState
    MAX-ACCESS   read-only
    STATUS       current
    DESCRIPTION
        "Cisco UCS ether:SwitchIntFIoPcEp:ackState managed
        object property"
    ::= { cucsEtherSwitchIntFIoPcEpEntry 22 }

cucsEtherSwitchIntFIoPcEpAggrPortId OBJECT-TYPE
    SYNTAX       Gauge32
    MAX-ACCESS   read-only
    STATUS       current
    DESCRIPTION
        "Cisco UCS ether:SwitchIntFIoPcEp:aggrPortId managed
        object property"
    ::= { cucsEtherSwitchIntFIoPcEpEntry 23 }

cucsEtherSwitchIntFIoPcEpPeerAggrPortId OBJECT-TYPE
    SYNTAX       Gauge32
    MAX-ACCESS   read-only
    STATUS       current
    DESCRIPTION
        "Cisco UCS ether:SwitchIntFIoPcEp:peerAggrPortId
        managed object property"
    ::= { cucsEtherSwitchIntFIoPcEpEntry 24 }

cucsEtherTxStatsTable OBJECT-TYPE
    SYNTAX           SEQUENCE OF CucsEtherTxStatsEntry
    MAX-ACCESS       not-accessible
    STATUS           current
    DESCRIPTION
        "Cisco UCS ether:TxStats managed object table"
    ::= { cucsEtherObjects 14 }

cucsEtherTxStatsEntry OBJECT-TYPE
    SYNTAX           CucsEtherTxStatsEntry
    MAX-ACCESS       not-accessible
    STATUS           current
    DESCRIPTION
        "Entry for the cucsEtherTxStatsTable table."
    INDEX { cucsEtherTxStatsInstanceId }
    ::= { cucsEtherTxStatsTable 1 }

CucsEtherTxStatsEntry ::= SEQUENCE {
    cucsEtherTxStatsInstanceId                                       CucsManagedObjectId,
    cucsEtherTxStatsDn                                               CucsManagedObjectDn,
    cucsEtherTxStatsRn                                               SnmpAdminString,
    cucsEtherTxStatsBroadcastPackets                                 Unsigned64,
    cucsEtherTxStatsBroadcastPacketsDelta                            Counter64,
    cucsEtherTxStatsBroadcastPacketsDeltaAvg                         Unsigned64,
    cucsEtherTxStatsBroadcastPacketsDeltaMax                         Unsigned64,
    cucsEtherTxStatsBroadcastPacketsDeltaMin                         Unsigned64,
    cucsEtherTxStatsIntervals                                        Gauge32,
    cucsEtherTxStatsJumboPackets                                     Unsigned64,
    cucsEtherTxStatsJumboPacketsDelta                                Counter64,
    cucsEtherTxStatsJumboPacketsDeltaAvg                             Unsigned64,
    cucsEtherTxStatsJumboPacketsDeltaMax                             Unsigned64,
    cucsEtherTxStatsJumboPacketsDeltaMin                             Unsigned64,
    cucsEtherTxStatsMulticastPackets                                 Unsigned64,
    cucsEtherTxStatsMulticastPacketsDelta                            Counter64,
    cucsEtherTxStatsMulticastPacketsDeltaAvg                         Unsigned64,
    cucsEtherTxStatsMulticastPacketsDeltaMax                         Unsigned64,
    cucsEtherTxStatsMulticastPacketsDeltaMin                         Unsigned64,
    cucsEtherTxStatsSuspect                                          TruthValue,
    cucsEtherTxStatsThresholded                                      CucsEtherTxStatsThresholded,
    cucsEtherTxStatsTimeCollected                                    DateAndTime,
    cucsEtherTxStatsTotalBytes                                       Unsigned64,
    cucsEtherTxStatsTotalBytesDelta                                  Counter64,
    cucsEtherTxStatsTotalBytesDeltaAvg                               Unsigned64,
    cucsEtherTxStatsTotalBytesDeltaMax                               Unsigned64,
    cucsEtherTxStatsTotalBytesDeltaMin                               Unsigned64,
    cucsEtherTxStatsTotalPackets                                     Unsigned64,
    cucsEtherTxStatsTotalPacketsDelta                                Counter64,
    cucsEtherTxStatsTotalPacketsDeltaAvg                             Unsigned64,
    cucsEtherTxStatsTotalPacketsDeltaMax                             Unsigned64,
    cucsEtherTxStatsTotalPacketsDeltaMin                             Unsigned64,
    cucsEtherTxStatsUnicastPackets                                   Unsigned64,
    cucsEtherTxStatsUnicastPacketsDelta                              Counter64,
    cucsEtherTxStatsUnicastPacketsDeltaAvg                           Unsigned64,
    cucsEtherTxStatsUnicastPacketsDeltaMax                           Unsigned64,
    cucsEtherTxStatsUnicastPacketsDeltaMin                           Unsigned64,
    cucsEtherTxStatsUpdate                                           Gauge32
}

cucsEtherTxStatsInstanceId OBJECT-TYPE
    SYNTAX       CucsManagedObjectId
    MAX-ACCESS   not-accessible
    STATUS       current
    DESCRIPTION
        "Instance identifier of the managed object."
    ::= { cucsEtherTxStatsEntry 1 }

cucsEtherTxStatsDn OBJECT-TYPE
    SYNTAX       CucsManagedObjectDn
    MAX-ACCESS   read-only
    STATUS       current
    DESCRIPTION
        "Cisco UCS ether:TxStats:dn managed object property"
    ::= { cucsEtherTxStatsEntry 2 }

cucsEtherTxStatsRn OBJECT-TYPE
    SYNTAX       SnmpAdminString
    MAX-ACCESS   read-only
    STATUS       current
    DESCRIPTION
        "Cisco UCS ether:TxStats:rn managed object property"
    ::= { cucsEtherTxStatsEntry 3 }

cucsEtherTxStatsBroadcastPackets OBJECT-TYPE
    SYNTAX       Unsigned64
    MAX-ACCESS   read-only
    STATUS       current
    DESCRIPTION
        "Cisco UCS ether:TxStats:broadcastPackets managed object property"
    ::= { cucsEtherTxStatsEntry 4 }

cucsEtherTxStatsBroadcastPacketsDelta OBJECT-TYPE
    SYNTAX       Counter64
    MAX-ACCESS   read-only
    STATUS       current
    DESCRIPTION
        "Cisco UCS ether:TxStats:broadcastPacketsDelta
        managed object property"
    ::= { cucsEtherTxStatsEntry 5 }

cucsEtherTxStatsBroadcastPacketsDeltaAvg OBJECT-TYPE
    SYNTAX       Unsigned64
    MAX-ACCESS   read-only
    STATUS       current
    DESCRIPTION
        "Cisco UCS ether:TxStats:broadcastPacketsDeltaAvg
        managed object property"
    ::= { cucsEtherTxStatsEntry 6 }

cucsEtherTxStatsBroadcastPacketsDeltaMax OBJECT-TYPE
    SYNTAX       Unsigned64
    MAX-ACCESS   read-only
    STATUS       current
    DESCRIPTION
        "Cisco UCS ether:TxStats:broadcastPacketsDeltaMax
        managed object property"
    ::= { cucsEtherTxStatsEntry 7 }

cucsEtherTxStatsBroadcastPacketsDeltaMin OBJECT-TYPE
    SYNTAX       Unsigned64
    MAX-ACCESS   read-only
    STATUS       current
    DESCRIPTION
        "Cisco UCS ether:TxStats:broadcastPacketsDeltaMin
        managed object property"
    ::= { cucsEtherTxStatsEntry 8 }

cucsEtherTxStatsIntervals OBJECT-TYPE
    SYNTAX       Gauge32
    MAX-ACCESS   read-only
    STATUS       current
    DESCRIPTION
        "Cisco UCS ether:TxStats:intervals managed object property"
    ::= { cucsEtherTxStatsEntry 9 }

cucsEtherTxStatsJumboPackets OBJECT-TYPE
    SYNTAX       Unsigned64
    MAX-ACCESS   read-only
    STATUS       current
    DESCRIPTION
        "Cisco UCS ether:TxStats:jumboPackets managed object property"
    ::= { cucsEtherTxStatsEntry 10 }

cucsEtherTxStatsJumboPacketsDelta OBJECT-TYPE
    SYNTAX       Counter64
    MAX-ACCESS   read-only
    STATUS       current
    DESCRIPTION
        "Cisco UCS ether:TxStats:jumboPacketsDelta managed
        object property"
    ::= { cucsEtherTxStatsEntry 11 }

cucsEtherTxStatsJumboPacketsDeltaAvg OBJECT-TYPE
    SYNTAX       Unsigned64
    MAX-ACCESS   read-only
    STATUS       current
    DESCRIPTION
        "Cisco UCS ether:TxStats:jumboPacketsDeltaAvg managed
        object property"
    ::= { cucsEtherTxStatsEntry 12 }

cucsEtherTxStatsJumboPacketsDeltaMax OBJECT-TYPE
    SYNTAX       Unsigned64
    MAX-ACCESS   read-only
    STATUS       current
    DESCRIPTION
        "Cisco UCS ether:TxStats:jumboPacketsDeltaMax managed
        object property"
    ::= { cucsEtherTxStatsEntry 13 }

cucsEtherTxStatsJumboPacketsDeltaMin OBJECT-TYPE
    SYNTAX       Unsigned64
    MAX-ACCESS   read-only
    STATUS       current
    DESCRIPTION
        "Cisco UCS ether:TxStats:jumboPacketsDeltaMin managed
        object property"
    ::= { cucsEtherTxStatsEntry 14 }

cucsEtherTxStatsMulticastPackets OBJECT-TYPE
    SYNTAX       Unsigned64
    MAX-ACCESS   read-only
    STATUS       current
    DESCRIPTION
        "Cisco UCS ether:TxStats:multicastPackets managed object property"
    ::= { cucsEtherTxStatsEntry 15 }

cucsEtherTxStatsMulticastPacketsDelta OBJECT-TYPE
    SYNTAX       Counter64
    MAX-ACCESS   read-only
    STATUS       current
    DESCRIPTION
        "Cisco UCS ether:TxStats:multicastPacketsDelta
        managed object property"
    ::= { cucsEtherTxStatsEntry 16 }

cucsEtherTxStatsMulticastPacketsDeltaAvg OBJECT-TYPE
    SYNTAX       Unsigned64
    MAX-ACCESS   read-only
    STATUS       current
    DESCRIPTION
        "Cisco UCS ether:TxStats:multicastPacketsDeltaAvg
        managed object property"
    ::= { cucsEtherTxStatsEntry 17 }

cucsEtherTxStatsMulticastPacketsDeltaMax OBJECT-TYPE
    SYNTAX       Unsigned64
    MAX-ACCESS   read-only
    STATUS       current
    DESCRIPTION
        "Cisco UCS ether:TxStats:multicastPacketsDeltaMax
        managed object property"
    ::= { cucsEtherTxStatsEntry 18 }

cucsEtherTxStatsMulticastPacketsDeltaMin OBJECT-TYPE
    SYNTAX       Unsigned64
    MAX-ACCESS   read-only
    STATUS       current
    DESCRIPTION
        "Cisco UCS ether:TxStats:multicastPacketsDeltaMin
        managed object property"
    ::= { cucsEtherTxStatsEntry 19 }

cucsEtherTxStatsSuspect OBJECT-TYPE
    SYNTAX       TruthValue
    MAX-ACCESS   read-only
    STATUS       current
    DESCRIPTION
        "Cisco UCS ether:TxStats:suspect managed object property"
    ::= { cucsEtherTxStatsEntry 20 }

cucsEtherTxStatsThresholded OBJECT-TYPE
    SYNTAX       CucsEtherTxStatsThresholded
    MAX-ACCESS   read-only
    STATUS       current
    DESCRIPTION
        "Cisco UCS ether:TxStats:thresholded managed object property"
    ::= { cucsEtherTxStatsEntry 21 }

cucsEtherTxStatsTimeCollected OBJECT-TYPE
    SYNTAX       DateAndTime
    MAX-ACCESS   read-only
    STATUS       current
    DESCRIPTION
        "Cisco UCS ether:TxStats:timeCollected managed object property"
    ::= { cucsEtherTxStatsEntry 22 }

cucsEtherTxStatsTotalBytes OBJECT-TYPE
    SYNTAX       Unsigned64
    MAX-ACCESS   read-only
    STATUS       current
    DESCRIPTION
        "Cisco UCS ether:TxStats:totalBytes managed object property"
    ::= { cucsEtherTxStatsEntry 23 }

cucsEtherTxStatsTotalBytesDelta OBJECT-TYPE
    SYNTAX       Counter64
    MAX-ACCESS   read-only
    STATUS       current
    DESCRIPTION
        "Cisco UCS ether:TxStats:totalBytesDelta managed object property"
    ::= { cucsEtherTxStatsEntry 24 }

cucsEtherTxStatsTotalBytesDeltaAvg OBJECT-TYPE
    SYNTAX       Unsigned64
    MAX-ACCESS   read-only
    STATUS       current
    DESCRIPTION
        "Cisco UCS ether:TxStats:totalBytesDeltaAvg managed
        object property"
    ::= { cucsEtherTxStatsEntry 25 }

cucsEtherTxStatsTotalBytesDeltaMax OBJECT-TYPE
    SYNTAX       Unsigned64
    MAX-ACCESS   read-only
    STATUS       current
    DESCRIPTION
        "Cisco UCS ether:TxStats:totalBytesDeltaMax managed
        object property"
    ::= { cucsEtherTxStatsEntry 26 }

cucsEtherTxStatsTotalBytesDeltaMin OBJECT-TYPE
    SYNTAX       Unsigned64
    MAX-ACCESS   read-only
    STATUS       current
    DESCRIPTION
        "Cisco UCS ether:TxStats:totalBytesDeltaMin managed
        object property"
    ::= { cucsEtherTxStatsEntry 27 }

cucsEtherTxStatsTotalPackets OBJECT-TYPE
    SYNTAX       Unsigned64
    MAX-ACCESS   read-only
    STATUS       current
    DESCRIPTION
        "Cisco UCS ether:TxStats:totalPackets managed object property"
    ::= { cucsEtherTxStatsEntry 28 }

cucsEtherTxStatsTotalPacketsDelta OBJECT-TYPE
    SYNTAX       Counter64
    MAX-ACCESS   read-only
    STATUS       current
    DESCRIPTION
        "Cisco UCS ether:TxStats:totalPacketsDelta managed
        object property"
    ::= { cucsEtherTxStatsEntry 29 }

cucsEtherTxStatsTotalPacketsDeltaAvg OBJECT-TYPE
    SYNTAX       Unsigned64
    MAX-ACCESS   read-only
    STATUS       current
    DESCRIPTION
        "Cisco UCS ether:TxStats:totalPacketsDeltaAvg managed
        object property"
    ::= { cucsEtherTxStatsEntry 30 }

cucsEtherTxStatsTotalPacketsDeltaMax OBJECT-TYPE
    SYNTAX       Unsigned64
    MAX-ACCESS   read-only
    STATUS       current
    DESCRIPTION
        "Cisco UCS ether:TxStats:totalPacketsDeltaMax managed
        object property"
    ::= { cucsEtherTxStatsEntry 31 }

cucsEtherTxStatsTotalPacketsDeltaMin OBJECT-TYPE
    SYNTAX       Unsigned64
    MAX-ACCESS   read-only
    STATUS       current
    DESCRIPTION
        "Cisco UCS ether:TxStats:totalPacketsDeltaMin managed
        object property"
    ::= { cucsEtherTxStatsEntry 32 }

cucsEtherTxStatsUnicastPackets OBJECT-TYPE
    SYNTAX       Unsigned64
    MAX-ACCESS   read-only
    STATUS       current
    DESCRIPTION
        "Cisco UCS ether:TxStats:unicastPackets managed object property"
    ::= { cucsEtherTxStatsEntry 33 }

cucsEtherTxStatsUnicastPacketsDelta OBJECT-TYPE
    SYNTAX       Counter64
    MAX-ACCESS   read-only
    STATUS       current
    DESCRIPTION
        "Cisco UCS ether:TxStats:unicastPacketsDelta managed
        object property"
    ::= { cucsEtherTxStatsEntry 34 }

cucsEtherTxStatsUnicastPacketsDeltaAvg OBJECT-TYPE
    SYNTAX       Unsigned64
    MAX-ACCESS   read-only
    STATUS       current
    DESCRIPTION
        "Cisco UCS ether:TxStats:unicastPacketsDeltaAvg
        managed object property"
    ::= { cucsEtherTxStatsEntry 35 }

cucsEtherTxStatsUnicastPacketsDeltaMax OBJECT-TYPE
    SYNTAX       Unsigned64
    MAX-ACCESS   read-only
    STATUS       current
    DESCRIPTION
        "Cisco UCS ether:TxStats:unicastPacketsDeltaMax
        managed object property"
    ::= { cucsEtherTxStatsEntry 36 }

cucsEtherTxStatsUnicastPacketsDeltaMin OBJECT-TYPE
    SYNTAX       Unsigned64
    MAX-ACCESS   read-only
    STATUS       current
    DESCRIPTION
        "Cisco UCS ether:TxStats:unicastPacketsDeltaMin
        managed object property"
    ::= { cucsEtherTxStatsEntry 37 }

cucsEtherTxStatsUpdate OBJECT-TYPE
    SYNTAX       Gauge32
    MAX-ACCESS   read-only
    STATUS       current
    DESCRIPTION
        "Cisco UCS ether:TxStats:update managed object property"
    ::= { cucsEtherTxStatsEntry 38 }

cucsEtherTxStatsHistTable OBJECT-TYPE
    SYNTAX           SEQUENCE OF CucsEtherTxStatsHistEntry
    MAX-ACCESS       not-accessible
    STATUS           current
    DESCRIPTION
        "Cisco UCS ether:TxStatsHist managed object table"
    ::= { cucsEtherObjects 15 }

cucsEtherTxStatsHistEntry OBJECT-TYPE
    SYNTAX           CucsEtherTxStatsHistEntry
    MAX-ACCESS       not-accessible
    STATUS           current
    DESCRIPTION
        "Entry for the cucsEtherTxStatsHistTable table."
    INDEX { cucsEtherTxStatsHistInstanceId }
    ::= { cucsEtherTxStatsHistTable 1 }

CucsEtherTxStatsHistEntry ::= SEQUENCE {
    cucsEtherTxStatsHistInstanceId                                   CucsManagedObjectId,
    cucsEtherTxStatsHistDn                                           CucsManagedObjectDn,
    cucsEtherTxStatsHistRn                                           SnmpAdminString,
    cucsEtherTxStatsHistBroadcastPackets                             Unsigned64,
    cucsEtherTxStatsHistBroadcastPacketsDelta                        Unsigned64,
    cucsEtherTxStatsHistBroadcastPacketsDeltaAvg                     Unsigned64,
    cucsEtherTxStatsHistBroadcastPacketsDeltaMax                     Unsigned64,
    cucsEtherTxStatsHistBroadcastPacketsDeltaMin                     Unsigned64,
    cucsEtherTxStatsHistId                                           Unsigned64,
    cucsEtherTxStatsHistJumboPackets                                 Unsigned64,
    cucsEtherTxStatsHistJumboPacketsDelta                            Unsigned64,
    cucsEtherTxStatsHistJumboPacketsDeltaAvg                         Unsigned64,
    cucsEtherTxStatsHistJumboPacketsDeltaMax                         Unsigned64,
    cucsEtherTxStatsHistJumboPacketsDeltaMin                         Unsigned64,
    cucsEtherTxStatsHistMostRecent                                   TruthValue,
    cucsEtherTxStatsHistMulticastPackets                             Unsigned64,
    cucsEtherTxStatsHistMulticastPacketsDelta                        Unsigned64,
    cucsEtherTxStatsHistMulticastPacketsDeltaAvg                     Unsigned64,
    cucsEtherTxStatsHistMulticastPacketsDeltaMax                     Unsigned64,
    cucsEtherTxStatsHistMulticastPacketsDeltaMin                     Unsigned64,
    cucsEtherTxStatsHistSuspect                                      TruthValue,
    cucsEtherTxStatsHistThresholded                                  CucsEtherTxStatsHistThresholded,
    cucsEtherTxStatsHistTimeCollected                                DateAndTime,
    cucsEtherTxStatsHistTotalBytes                                   Unsigned64,
    cucsEtherTxStatsHistTotalBytesDelta                              Unsigned64,
    cucsEtherTxStatsHistTotalBytesDeltaAvg                           Unsigned64,
    cucsEtherTxStatsHistTotalBytesDeltaMax                           Unsigned64,
    cucsEtherTxStatsHistTotalBytesDeltaMin                           Unsigned64,
    cucsEtherTxStatsHistTotalPackets                                 Unsigned64,
    cucsEtherTxStatsHistTotalPacketsDelta                            Unsigned64,
    cucsEtherTxStatsHistTotalPacketsDeltaAvg                         Unsigned64,
    cucsEtherTxStatsHistTotalPacketsDeltaMax                         Unsigned64,
    cucsEtherTxStatsHistTotalPacketsDeltaMin                         Unsigned64,
    cucsEtherTxStatsHistUnicastPackets                               Unsigned64,
    cucsEtherTxStatsHistUnicastPacketsDelta                          Unsigned64,
    cucsEtherTxStatsHistUnicastPacketsDeltaAvg                       Unsigned64,
    cucsEtherTxStatsHistUnicastPacketsDeltaMax                       Unsigned64,
    cucsEtherTxStatsHistUnicastPacketsDeltaMin                       Unsigned64
}

cucsEtherTxStatsHistInstanceId OBJECT-TYPE
    SYNTAX       CucsManagedObjectId
    MAX-ACCESS   not-accessible
    STATUS       current
    DESCRIPTION
        "Instance identifier of the managed object."
    ::= { cucsEtherTxStatsHistEntry 1 }

cucsEtherTxStatsHistDn OBJECT-TYPE
    SYNTAX       CucsManagedObjectDn
    MAX-ACCESS   read-only
    STATUS       current
    DESCRIPTION
        "Cisco UCS ether:TxStatsHist:dn managed object property"
    ::= { cucsEtherTxStatsHistEntry 2 }

cucsEtherTxStatsHistRn OBJECT-TYPE
    SYNTAX       SnmpAdminString
    MAX-ACCESS   read-only
    STATUS       current
    DESCRIPTION
        "Cisco UCS ether:TxStatsHist:rn managed object property"
    ::= { cucsEtherTxStatsHistEntry 3 }

cucsEtherTxStatsHistBroadcastPackets OBJECT-TYPE
    SYNTAX       Unsigned64
    MAX-ACCESS   read-only
    STATUS       current
    DESCRIPTION
        "Cisco UCS ether:TxStatsHist:broadcastPackets managed
        object property"
    ::= { cucsEtherTxStatsHistEntry 4 }

cucsEtherTxStatsHistBroadcastPacketsDelta OBJECT-TYPE
    SYNTAX       Unsigned64
    MAX-ACCESS   read-only
    STATUS       current
    DESCRIPTION
        "Cisco UCS ether:TxStatsHist:broadcastPacketsDelta
        managed object property"
    ::= { cucsEtherTxStatsHistEntry 5 }

cucsEtherTxStatsHistBroadcastPacketsDeltaAvg OBJECT-TYPE
    SYNTAX       Unsigned64
    MAX-ACCESS   read-only
    STATUS       current
    DESCRIPTION
        "Cisco UCS ether:TxStatsHist:broadcastPacketsDeltaAvg
        managed object property"
    ::= { cucsEtherTxStatsHistEntry 6 }

cucsEtherTxStatsHistBroadcastPacketsDeltaMax OBJECT-TYPE
    SYNTAX       Unsigned64
    MAX-ACCESS   read-only
    STATUS       current
    DESCRIPTION
        "Cisco UCS ether:TxStatsHist:broadcastPacketsDeltaMax
        managed object property"
    ::= { cucsEtherTxStatsHistEntry 7 }

cucsEtherTxStatsHistBroadcastPacketsDeltaMin OBJECT-TYPE
    SYNTAX       Unsigned64
    MAX-ACCESS   read-only
    STATUS       current
    DESCRIPTION
        "Cisco UCS ether:TxStatsHist:broadcastPacketsDeltaMin
        managed object property"
    ::= { cucsEtherTxStatsHistEntry 8 }

cucsEtherTxStatsHistId OBJECT-TYPE
    SYNTAX       Unsigned64
    MAX-ACCESS   read-only
    STATUS       current
    DESCRIPTION
        "Cisco UCS ether:TxStatsHist:id managed object property"
    ::= { cucsEtherTxStatsHistEntry 9 }

cucsEtherTxStatsHistJumboPackets OBJECT-TYPE
    SYNTAX       Unsigned64
    MAX-ACCESS   read-only
    STATUS       current
    DESCRIPTION
        "Cisco UCS ether:TxStatsHist:jumboPackets managed object property"
    ::= { cucsEtherTxStatsHistEntry 10 }

cucsEtherTxStatsHistJumboPacketsDelta OBJECT-TYPE
    SYNTAX       Unsigned64
    MAX-ACCESS   read-only
    STATUS       current
    DESCRIPTION
        "Cisco UCS ether:TxStatsHist:jumboPacketsDelta
        managed object property"
    ::= { cucsEtherTxStatsHistEntry 11 }

cucsEtherTxStatsHistJumboPacketsDeltaAvg OBJECT-TYPE
    SYNTAX       Unsigned64
    MAX-ACCESS   read-only
    STATUS       current
    DESCRIPTION
        "Cisco UCS ether:TxStatsHist:jumboPacketsDeltaAvg
        managed object property"
    ::= { cucsEtherTxStatsHistEntry 12 }

cucsEtherTxStatsHistJumboPacketsDeltaMax OBJECT-TYPE
    SYNTAX       Unsigned64
    MAX-ACCESS   read-only
    STATUS       current
    DESCRIPTION
        "Cisco UCS ether:TxStatsHist:jumboPacketsDeltaMax
        managed object property"
    ::= { cucsEtherTxStatsHistEntry 13 }

cucsEtherTxStatsHistJumboPacketsDeltaMin OBJECT-TYPE
    SYNTAX       Unsigned64
    MAX-ACCESS   read-only
    STATUS       current
    DESCRIPTION
        "Cisco UCS ether:TxStatsHist:jumboPacketsDeltaMin
        managed object property"
    ::= { cucsEtherTxStatsHistEntry 14 }

cucsEtherTxStatsHistMostRecent OBJECT-TYPE
    SYNTAX       TruthValue
    MAX-ACCESS   read-only
    STATUS       current
    DESCRIPTION
        "Cisco UCS ether:TxStatsHist:mostRecent managed object property"
    ::= { cucsEtherTxStatsHistEntry 15 }

cucsEtherTxStatsHistMulticastPackets OBJECT-TYPE
    SYNTAX       Unsigned64
    MAX-ACCESS   read-only
    STATUS       current
    DESCRIPTION
        "Cisco UCS ether:TxStatsHist:multicastPackets managed
        object property"
    ::= { cucsEtherTxStatsHistEntry 16 }

cucsEtherTxStatsHistMulticastPacketsDelta OBJECT-TYPE
    SYNTAX       Unsigned64
    MAX-ACCESS   read-only
    STATUS       current
    DESCRIPTION
        "Cisco UCS ether:TxStatsHist:multicastPacketsDelta
        managed object property"
    ::= { cucsEtherTxStatsHistEntry 17 }

cucsEtherTxStatsHistMulticastPacketsDeltaAvg OBJECT-TYPE
    SYNTAX       Unsigned64
    MAX-ACCESS   read-only
    STATUS       current
    DESCRIPTION
        "Cisco UCS ether:TxStatsHist:multicastPacketsDeltaAvg
        managed object property"
    ::= { cucsEtherTxStatsHistEntry 18 }

cucsEtherTxStatsHistMulticastPacketsDeltaMax OBJECT-TYPE
    SYNTAX       Unsigned64
    MAX-ACCESS   read-only
    STATUS       current
    DESCRIPTION
        "Cisco UCS ether:TxStatsHist:multicastPacketsDeltaMax
        managed object property"
    ::= { cucsEtherTxStatsHistEntry 19 }

cucsEtherTxStatsHistMulticastPacketsDeltaMin OBJECT-TYPE
    SYNTAX       Unsigned64
    MAX-ACCESS   read-only
    STATUS       current
    DESCRIPTION
        "Cisco UCS ether:TxStatsHist:multicastPacketsDeltaMin
        managed object property"
    ::= { cucsEtherTxStatsHistEntry 20 }

cucsEtherTxStatsHistSuspect OBJECT-TYPE
    SYNTAX       TruthValue
    MAX-ACCESS   read-only
    STATUS       current
    DESCRIPTION
        "Cisco UCS ether:TxStatsHist:suspect managed object property"
    ::= { cucsEtherTxStatsHistEntry 21 }

cucsEtherTxStatsHistThresholded OBJECT-TYPE
    SYNTAX       CucsEtherTxStatsHistThresholded
    MAX-ACCESS   read-only
    STATUS       current
    DESCRIPTION
        "Cisco UCS ether:TxStatsHist:thresholded managed object property"
    ::= { cucsEtherTxStatsHistEntry 22 }

cucsEtherTxStatsHistTimeCollected OBJECT-TYPE
    SYNTAX       DateAndTime
    MAX-ACCESS   read-only
    STATUS       current
    DESCRIPTION
        "Cisco UCS ether:TxStatsHist:timeCollected managed
        object property"
    ::= { cucsEtherTxStatsHistEntry 23 }

cucsEtherTxStatsHistTotalBytes OBJECT-TYPE
    SYNTAX       Unsigned64
    MAX-ACCESS   read-only
    STATUS       current
    DESCRIPTION
        "Cisco UCS ether:TxStatsHist:totalBytes managed object property"
    ::= { cucsEtherTxStatsHistEntry 24 }

cucsEtherTxStatsHistTotalBytesDelta OBJECT-TYPE
    SYNTAX       Unsigned64
    MAX-ACCESS   read-only
    STATUS       current
    DESCRIPTION
        "Cisco UCS ether:TxStatsHist:totalBytesDelta managed
        object property"
    ::= { cucsEtherTxStatsHistEntry 25 }

cucsEtherTxStatsHistTotalBytesDeltaAvg OBJECT-TYPE
    SYNTAX       Unsigned64
    MAX-ACCESS   read-only
    STATUS       current
    DESCRIPTION
        "Cisco UCS ether:TxStatsHist:totalBytesDeltaAvg
        managed object property"
    ::= { cucsEtherTxStatsHistEntry 26 }

cucsEtherTxStatsHistTotalBytesDeltaMax OBJECT-TYPE
    SYNTAX       Unsigned64
    MAX-ACCESS   read-only
    STATUS       current
    DESCRIPTION
        "Cisco UCS ether:TxStatsHist:totalBytesDeltaMax
        managed object property"
    ::= { cucsEtherTxStatsHistEntry 27 }

cucsEtherTxStatsHistTotalBytesDeltaMin OBJECT-TYPE
    SYNTAX       Unsigned64
    MAX-ACCESS   read-only
    STATUS       current
    DESCRIPTION
        "Cisco UCS ether:TxStatsHist:totalBytesDeltaMin
        managed object property"
    ::= { cucsEtherTxStatsHistEntry 28 }

cucsEtherTxStatsHistTotalPackets OBJECT-TYPE
    SYNTAX       Unsigned64
    MAX-ACCESS   read-only
    STATUS       current
    DESCRIPTION
        "Cisco UCS ether:TxStatsHist:totalPackets managed object property"
    ::= { cucsEtherTxStatsHistEntry 29 }

cucsEtherTxStatsHistTotalPacketsDelta OBJECT-TYPE
    SYNTAX       Unsigned64
    MAX-ACCESS   read-only
    STATUS       current
    DESCRIPTION
        "Cisco UCS ether:TxStatsHist:totalPacketsDelta
        managed object property"
    ::= { cucsEtherTxStatsHistEntry 30 }

cucsEtherTxStatsHistTotalPacketsDeltaAvg OBJECT-TYPE
    SYNTAX       Unsigned64
    MAX-ACCESS   read-only
    STATUS       current
    DESCRIPTION
        "Cisco UCS ether:TxStatsHist:totalPacketsDeltaAvg
        managed object property"
    ::= { cucsEtherTxStatsHistEntry 31 }

cucsEtherTxStatsHistTotalPacketsDeltaMax OBJECT-TYPE
    SYNTAX       Unsigned64
    MAX-ACCESS   read-only
    STATUS       current
    DESCRIPTION
        "Cisco UCS ether:TxStatsHist:totalPacketsDeltaMax
        managed object property"
    ::= { cucsEtherTxStatsHistEntry 32 }

cucsEtherTxStatsHistTotalPacketsDeltaMin OBJECT-TYPE
    SYNTAX       Unsigned64
    MAX-ACCESS   read-only
    STATUS       current
    DESCRIPTION
        "Cisco UCS ether:TxStatsHist:totalPacketsDeltaMin
        managed object property"
    ::= { cucsEtherTxStatsHistEntry 33 }

cucsEtherTxStatsHistUnicastPackets OBJECT-TYPE
    SYNTAX       Unsigned64
    MAX-ACCESS   read-only
    STATUS       current
    DESCRIPTION
        "Cisco UCS ether:TxStatsHist:unicastPackets managed
        object property"
    ::= { cucsEtherTxStatsHistEntry 34 }

cucsEtherTxStatsHistUnicastPacketsDelta OBJECT-TYPE
    SYNTAX       Unsigned64
    MAX-ACCESS   read-only
    STATUS       current
    DESCRIPTION
        "Cisco UCS ether:TxStatsHist:unicastPacketsDelta
        managed object property"
    ::= { cucsEtherTxStatsHistEntry 35 }

cucsEtherTxStatsHistUnicastPacketsDeltaAvg OBJECT-TYPE
    SYNTAX       Unsigned64
    MAX-ACCESS   read-only
    STATUS       current
    DESCRIPTION
        "Cisco UCS ether:TxStatsHist:unicastPacketsDeltaAvg
        managed object property"
    ::= { cucsEtherTxStatsHistEntry 36 }

cucsEtherTxStatsHistUnicastPacketsDeltaMax OBJECT-TYPE
    SYNTAX       Unsigned64
    MAX-ACCESS   read-only
    STATUS       current
    DESCRIPTION
        "Cisco UCS ether:TxStatsHist:unicastPacketsDeltaMax
        managed object property"
    ::= { cucsEtherTxStatsHistEntry 37 }

cucsEtherTxStatsHistUnicastPacketsDeltaMin OBJECT-TYPE
    SYNTAX       Unsigned64
    MAX-ACCESS   read-only
    STATUS       current
    DESCRIPTION
        "Cisco UCS ether:TxStatsHist:unicastPacketsDeltaMin
        managed object property"
    ::= { cucsEtherTxStatsHistEntry 38 }

END
