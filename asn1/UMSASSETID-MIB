UMSASSETID-MIB DEFINITIONS ::= BEGIN

IMPORTS
   OBJECT-TYPE
      FROM RFC-1212

   TRAP-TYPE
      FROM RFC-1215

   ibmpsgAssetID,
   Boolean, Uint8, Sint8, Uint16, Sint16, Uint32,
   Sint32, Uint64, Sint64, Real32, Real64, String, Datetime
      FROM UMS-MIB;

iBMPSGSerialNumberInformationTable OBJECT-TYPE
   SYNTAX         SEQUENCE OF IBMPSGSerialNumberInformationEntry
   ACCESS         not-accessible
   STATUS         mandatory
   DESCRIPTION    "The IBMPSG_Serial_Number_Information class contains serial numbers for each of the major hardware components in an IBM PC."
   REFERENCE      "IBMPSG_Serial_Number_Information"
::= { ibmpsgAssetID 1 }

iBMPSGSerialNumberInformationEntry OBJECT-TYPE
   SYNTAX         IBMPSGSerialNumberInformationEntry
   ACCESS         not-accessible
   STATUS         mandatory
   DESCRIPTION    ""
   INDEX          { iBMPSGSerialNumberInformationKeyIndex }
::= { iBMPSGSerialNumberInformationTable 1 }

IBMPSGSerialNumberInformationEntry ::= SEQUENCE
{
   iBMPSGSerialNumberInformationKeyIndex String,
   iBMPSGSerialNumberInformationName String,
   iBMPSGSerialNumberInformationSerialNumber String,
   iBMPSGSerialNumberInformationManufacturer String,
   iBMPSGSerialNumberInformationModel String,
   iBMPSGSerialNumberInformationVersion String,
   iBMPSGSerialNumberInformationOtherIdentifyingInfo String
}

iBMPSGSerialNumberInformationKeyIndex OBJECT-TYPE
   SYNTAX         String
   ACCESS         read-write
   STATUS         mandatory
   DESCRIPTION    ""
   REFERENCE      "IBMPSG_Serial_Number_Information.KeyIndex"
::= { iBMPSGSerialNumberInformationEntry 1 }

iBMPSGSerialNumberInformationName OBJECT-TYPE
   SYNTAX         String
   ACCESS         read-write
   STATUS         mandatory
   DESCRIPTION    "Name of the Asset"
   REFERENCE      "IBMPSG_Serial_Number_Information.Name"
::= { iBMPSGSerialNumberInformationEntry 2 }

iBMPSGSerialNumberInformationSerialNumber OBJECT-TYPE
   SYNTAX         String
   ACCESS         read-write
   STATUS         mandatory
   DESCRIPTION    "Serial Number of the Asset"
   REFERENCE      "IBMPSG_Serial_Number_Information.SerialNumber"
::= { iBMPSGSerialNumberInformationEntry 3 }

iBMPSGSerialNumberInformationManufacturer OBJECT-TYPE
   SYNTAX         String
   ACCESS         read-write
   STATUS         mandatory
   DESCRIPTION    ""
   REFERENCE      "IBMPSG_Serial_Number_Information.Manufacturer"
::= { iBMPSGSerialNumberInformationEntry 4 }

iBMPSGSerialNumberInformationModel OBJECT-TYPE
   SYNTAX         String
   ACCESS         read-write
   STATUS         mandatory
   DESCRIPTION    ""
   REFERENCE      "IBMPSG_Serial_Number_Information.Model"
::= { iBMPSGSerialNumberInformationEntry 5 }

iBMPSGSerialNumberInformationVersion OBJECT-TYPE
   SYNTAX         String
   ACCESS         read-write
   STATUS         mandatory
   DESCRIPTION    ""
   REFERENCE      "IBMPSG_Serial_Number_Information.Version"
::= { iBMPSGSerialNumberInformationEntry 6 }

iBMPSGSerialNumberInformationOtherIdentifyingInfo OBJECT-TYPE
   SYNTAX         String
   ACCESS         read-write
   STATUS         mandatory
   DESCRIPTION    ""
   REFERENCE      "IBMPSG_Serial_Number_Information.OtherIdentifyingInfo"
::= { iBMPSGSerialNumberInformationEntry 7 }

iBMPSGComputerSystemTable OBJECT-TYPE
   SYNTAX         SEQUENCE OF IBMPSGComputerSystemEntry
   ACCESS         not-accessible
   STATUS         mandatory
   DESCRIPTION    "The IBMPSG_ComputerSystem class represents an IBM managed PC."
   REFERENCE      "IBMPSG_ComputerSystem"
::= { ibmpsgAssetID 2 }

iBMPSGComputerSystemEntry OBJECT-TYPE
   SYNTAX         IBMPSGComputerSystemEntry
   ACCESS         not-accessible
   STATUS         mandatory
   DESCRIPTION    ""
   INDEX          { iBMPSGComputerSystemKeyIndex }
::= { iBMPSGComputerSystemTable 1 }

IBMPSGComputerSystemEntry ::= SEQUENCE
{
   iBMPSGComputerSystemKeyIndex String,   
   iBMPSGComputerSystemName String,
   iBMPSGComputerSystemModel String,
   iBMPSGComputerSystemPrimaryOwnerContact String,
   iBMPSGComputerSystemStatus String
}

iBMPSGComputerSystemKeyIndex OBJECT-TYPE
   SYNTAX         String
   ACCESS         read-write
   STATUS         mandatory
   DESCRIPTION    ""
   REFERENCE      "IBMPSG_ComputerSystem.KeyIndex"
::= { iBMPSGComputerSystemEntry 1 }

iBMPSGComputerSystemName OBJECT-TYPE
   SYNTAX         String
   ACCESS         read-write
   STATUS         mandatory
   DESCRIPTION    ""
   REFERENCE      "IBMPSG_ComputerSystem.Name"
::= { iBMPSGComputerSystemEntry 2 }

iBMPSGComputerSystemModel OBJECT-TYPE
   SYNTAX         String
   ACCESS         read-write
   STATUS         mandatory
   DESCRIPTION    ""
   REFERENCE      "IBMPSG_ComputerSystem.Model"
::= { iBMPSGComputerSystemEntry 3 }

iBMPSGComputerSystemPrimaryOwnerContact OBJECT-TYPE
   SYNTAX         String
   ACCESS         read-write
   STATUS         mandatory
   DESCRIPTION    ""
   REFERENCE      "IBMPSG_ComputerSystem.PrimaryOwnerContact"
::= { iBMPSGComputerSystemEntry 4 }

iBMPSGComputerSystemStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "IBMPSG_ComputerSystem.Status"
::= { iBMPSGComputerSystemEntry 5 }

iBMPSGComputerSystemDetailsTable OBJECT-TYPE
   SYNTAX         SEQUENCE OF IBMPSGComputerSystemDetailsEntry
   ACCESS         not-accessible
   STATUS         mandatory
   DESCRIPTION    "The IBMPSG_ComputerSystemDetails class contains extended information about an IBM managed PC."
   REFERENCE      "IBMPSG_ComputerSystemDetails"
::= { ibmpsgAssetID 3 }

iBMPSGComputerSystemDetailsEntry OBJECT-TYPE
   SYNTAX         IBMPSGComputerSystemDetailsEntry
   ACCESS         not-accessible
   STATUS         mandatory
   DESCRIPTION    ""
   INDEX          { iBMPSGComputerSystemDetailsKeyIndex }
::= { iBMPSGComputerSystemDetailsTable 1 }

IBMPSGComputerSystemDetailsEntry ::= SEQUENCE
{
   iBMPSGComputerSystemDetailsKeyIndex String,   
   iBMPSGComputerSystemDetailsName String,
   iBMPSGComputerSystemDetailsSystemUUID String,
   iBMPSGComputerSystemDetailsAssetNumber String,
   iBMPSGComputerSystemDetailsAssetIdTag String,
   iBMPSGComputerSystemDetailsLastInventoried Datetime,
   iBMPSGComputerSystemDetailsPurchaseDate Datetime,
   iBMPSGComputerSystemDetailsModel String,
   iBMPSGComputerSystemDetailsProductName String,
   iBMPSGComputerSystemDetailsSerialNumber String,
   iBMPSGComputerSystemDetailsPersonalizedLabel1 String,
   iBMPSGComputerSystemDetailsPersonalizedData1 String,
   iBMPSGComputerSystemDetailsPersonalizedLabel2 String,
   iBMPSGComputerSystemDetailsPersonalizedData2 String,
   iBMPSGComputerSystemDetailsPersonalizedLabel3 String,
   iBMPSGComputerSystemDetailsPersonalizedData3 String,
   iBMPSGComputerSystemDetailsPersonalizedLabel4 String,
   iBMPSGComputerSystemDetailsPersonalizedData4 String,
   iBMPSGComputerSystemDetailsPersonalizedLabel5 String,
   iBMPSGComputerSystemDetailsPersonalizedData5 String,
   iBMPSGComputerSystemDetailsPrimaryOwnerName String,
   iBMPSGComputerSystemDetailsPrimaryOwnerPhone String,
   iBMPSGComputerSystemDetailsPrimaryOwnerDepartment String,
   iBMPSGComputerSystemDetailsPrimaryOwnerPosition String,
   iBMPSGComputerSystemDetailsSystemLocation String,
   iBMPSGComputerSystemDetailsAssetIDStringArea Uint32,
   iBMPSGComputerSystemDetailsLocalDateTime Datetime,
   iBMPSGComputerSystemDetailsLCCMProfile String,
   iBMPSGComputerSystemDetailsLCCMUpdateTime Datetime
}

iBMPSGComputerSystemDetailsKeyIndex OBJECT-TYPE
   SYNTAX         String
   ACCESS         read-write
   STATUS         mandatory
   DESCRIPTION    ""
   REFERENCE      "IBMPSG_ComputerSystemDetails.KeyIndex"
::= { iBMPSGComputerSystemDetailsEntry 1 }

iBMPSGComputerSystemDetailsName OBJECT-TYPE
   SYNTAX         String
   ACCESS         read-write
   STATUS         mandatory
   DESCRIPTION    ""
   REFERENCE      "IBMPSG_ComputerSystemDetails.Name"
::= { iBMPSGComputerSystemDetailsEntry 2 }

iBMPSGComputerSystemDetailsSystemUUID OBJECT-TYPE
   SYNTAX         String
   ACCESS         read-write
   STATUS         mandatory
   DESCRIPTION    "Universally unique system identifier as defined in the PC97 and the SMBIOS specifications."
   REFERENCE      "IBMPSG_ComputerSystemDetails.SystemUUID"
::= { iBMPSGComputerSystemDetailsEntry 3 }

iBMPSGComputerSystemDetailsAssetNumber OBJECT-TYPE
   SYNTAX         String
   ACCESS         read-write
   STATUS         mandatory
   DESCRIPTION    "A unique identifier assigned to this asset."
   REFERENCE      "IBMPSG_ComputerSystemDetails.AssetNumber"
::= { iBMPSGComputerSystemDetailsEntry 4 }

iBMPSGComputerSystemDetailsAssetIdTag OBJECT-TYPE
   SYNTAX         String
   ACCESS         read-write
   STATUS         mandatory
   DESCRIPTION    "A unique identifier transmitted when a system with AssetID enters an RF field."
   REFERENCE      "IBMPSG_ComputerSystemDetails.AssetIdTag"
::= { iBMPSGComputerSystemDetailsEntry 5 }

iBMPSGComputerSystemDetailsLastInventoried OBJECT-TYPE
   SYNTAX         Datetime
   ACCESS         read-write
   STATUS         mandatory
   DESCRIPTION    "Date when the system was last counted."
   REFERENCE      "IBMPSG_ComputerSystemDetails.LastInventoried"
::= { iBMPSGComputerSystemDetailsEntry 6 }

iBMPSGComputerSystemDetailsPurchaseDate OBJECT-TYPE
   SYNTAX         Datetime
   ACCESS         read-write
   STATUS         mandatory
   DESCRIPTION    "Date on which this asset was purchased."
   REFERENCE      "IBMPSG_ComputerSystemDetails.PurchaseDate"
::= { iBMPSGComputerSystemDetailsEntry 7 }

iBMPSGComputerSystemDetailsModel OBJECT-TYPE
   SYNTAX         String
   ACCESS         read-write
   STATUS         mandatory
   DESCRIPTION    "Serial number of this system."
   REFERENCE      "IBMPSG_ComputerSystemDetails.Model"
::= { iBMPSGComputerSystemDetailsEntry 8 }

iBMPSGComputerSystemDetailsProductName OBJECT-TYPE
   SYNTAX         String
   ACCESS         read-write
   STATUS         mandatory
   DESCRIPTION    "Serial number of this system."
   REFERENCE      "IBMPSG_ComputerSystemDetails.ProductName"
::= { iBMPSGComputerSystemDetailsEntry 9 }

iBMPSGComputerSystemDetailsSerialNumber OBJECT-TYPE
   SYNTAX         String
   ACCESS         read-write
   STATUS         mandatory
   DESCRIPTION    "Serial number of this system."
   REFERENCE      "IBMPSG_ComputerSystemDetails.SerialNumber"
::= { iBMPSGComputerSystemDetailsEntry 10 }

iBMPSGComputerSystemDetailsPersonalizedLabel1 OBJECT-TYPE
   SYNTAX         String
   ACCESS         read-write
   STATUS         mandatory
   DESCRIPTION    "Used to personalize information about this computer system."
   REFERENCE      "IBMPSG_ComputerSystemDetails.PersonalizedLabel1"
::= { iBMPSGComputerSystemDetailsEntry 11 }

iBMPSGComputerSystemDetailsPersonalizedData1 OBJECT-TYPE
   SYNTAX         String
   ACCESS         read-write
   STATUS         mandatory
   DESCRIPTION    "Used to personalize information about this computer system."
   REFERENCE      "IBMPSG_ComputerSystemDetails.PersonalizedData1"
::= { iBMPSGComputerSystemDetailsEntry 12 }

iBMPSGComputerSystemDetailsPersonalizedLabel2 OBJECT-TYPE
   SYNTAX         String
   ACCESS         read-write
   STATUS         mandatory
   DESCRIPTION    "Used to personalize information about this computer system."
   REFERENCE      "IBMPSG_ComputerSystemDetails.PersonalizedLabel2"
::= { iBMPSGComputerSystemDetailsEntry 13 }

iBMPSGComputerSystemDetailsPersonalizedData2 OBJECT-TYPE
   SYNTAX         String
   ACCESS         read-write
   STATUS         mandatory
   DESCRIPTION    "Used to personalize information about this computer system."
   REFERENCE      "IBMPSG_ComputerSystemDetails.PersonalizedData2"
::= { iBMPSGComputerSystemDetailsEntry 14 }

iBMPSGComputerSystemDetailsPersonalizedLabel3 OBJECT-TYPE
   SYNTAX         String
   ACCESS         read-write
   STATUS         mandatory
   DESCRIPTION    "Used to personalize information about this computer system."
   REFERENCE      "IBMPSG_ComputerSystemDetails.PersonalizedLabel3"
::= { iBMPSGComputerSystemDetailsEntry 15 }

iBMPSGComputerSystemDetailsPersonalizedData3 OBJECT-TYPE
   SYNTAX         String
   ACCESS         read-write
   STATUS         mandatory
   DESCRIPTION    "Used to personalize information about this computer system."
   REFERENCE      "IBMPSG_ComputerSystemDetails.PersonalizedData3"
::= { iBMPSGComputerSystemDetailsEntry 16 }

iBMPSGComputerSystemDetailsPersonalizedLabel4 OBJECT-TYPE
   SYNTAX         String
   ACCESS         read-write
   STATUS         mandatory
   DESCRIPTION    "Used to personalize information about this computer system."
   REFERENCE      "IBMPSG_ComputerSystemDetails.PersonalizedLabel4"
::= { iBMPSGComputerSystemDetailsEntry 17 }

iBMPSGComputerSystemDetailsPersonalizedData4 OBJECT-TYPE
   SYNTAX         String
   ACCESS         read-write
   STATUS         mandatory
   DESCRIPTION    "Used to personalize information about this computer system."
   REFERENCE      "IBMPSG_ComputerSystemDetails.PersonalizedData4"
::= { iBMPSGComputerSystemDetailsEntry 18 }

iBMPSGComputerSystemDetailsPersonalizedLabel5 OBJECT-TYPE
   SYNTAX         String
   ACCESS         read-write
   STATUS         mandatory
   DESCRIPTION    "Used to personalize information about this computer system"
   REFERENCE      "IBMPSG_ComputerSystemDetails.PersonalizedLabel5"
::= { iBMPSGComputerSystemDetailsEntry 19 }

iBMPSGComputerSystemDetailsPersonalizedData5 OBJECT-TYPE
   SYNTAX         String
   ACCESS         read-write
   STATUS         mandatory
   DESCRIPTION    "Used to personalize information about this computer system"
   REFERENCE      "IBMPSG_ComputerSystemDetails.PersonalizedData5"
::= { iBMPSGComputerSystemDetailsEntry 20 }

iBMPSGComputerSystemDetailsPrimaryOwnerName OBJECT-TYPE
   SYNTAX         String
   ACCESS         read-write
   STATUS         mandatory
   DESCRIPTION    ""
   REFERENCE      "IBMPSG_ComputerSystemDetails.PrimaryOwnerName"
::= { iBMPSGComputerSystemDetailsEntry 21 }

iBMPSGComputerSystemDetailsPrimaryOwnerPhone OBJECT-TYPE
   SYNTAX         String
   ACCESS         read-write
   STATUS         mandatory
   DESCRIPTION    ""
   REFERENCE      "IBMPSG_ComputerSystemDetails.PrimaryOwnerPhone"
::= { iBMPSGComputerSystemDetailsEntry 22 }

iBMPSGComputerSystemDetailsPrimaryOwnerDepartment OBJECT-TYPE
   SYNTAX         String
   ACCESS         read-write
   STATUS         mandatory
   DESCRIPTION    ""
   REFERENCE      "IBMPSG_ComputerSystemDetails.PrimaryOwnerDepartment"
::= { iBMPSGComputerSystemDetailsEntry 23 }

iBMPSGComputerSystemDetailsPrimaryOwnerPosition OBJECT-TYPE
   SYNTAX         String
   ACCESS         read-write
   STATUS         mandatory
   DESCRIPTION    ""
   REFERENCE      "IBMPSG_ComputerSystemDetails.PrimaryOwnerPosition"
::= { iBMPSGComputerSystemDetailsEntry 24 }

iBMPSGComputerSystemDetailsSystemLocation OBJECT-TYPE
   SYNTAX         String
   ACCESS         read-write
   STATUS         mandatory
   DESCRIPTION    ""
   REFERENCE      "IBMPSG_ComputerSystemDetails.SystemLocation"
::= { iBMPSGComputerSystemDetailsEntry 25 }

iBMPSGComputerSystemDetailsAssetIDStringArea OBJECT-TYPE
   SYNTAX         Uint32
   ACCESS         read-write
   STATUS         mandatory
   DESCRIPTION    "The available String Area in bytes in the RF-ID EEPROM."
   REFERENCE      "IBMPSG_ComputerSystemDetails.AssetIDStringArea"
::= { iBMPSGComputerSystemDetailsEntry 26 }

iBMPSGComputerSystemDetailsLocalDateTime OBJECT-TYPE
   SYNTAX         Datetime
   ACCESS         read-write
   STATUS         mandatory
   DESCRIPTION    "Writable version of the OperatingSystem's notion of the local date and time of day."
   REFERENCE      "IBMPSG_ComputerSystemDetails.LocalDateTime"
::= { iBMPSGComputerSystemDetailsEntry 27 }

iBMPSGComputerSystemDetailsLCCMProfile OBJECT-TYPE
   SYNTAX         String
   ACCESS         read-write
   STATUS         mandatory
   DESCRIPTION    "LCCM Profile name describing the operating system image installed on this system"
   REFERENCE      "IBMPSG_ComputerSystemDetails.LCCMProfile"
::= { iBMPSGComputerSystemDetailsEntry 28 }

iBMPSGComputerSystemDetailsLCCMUpdateTime OBJECT-TYPE
   SYNTAX         Datetime
   ACCESS         read-write
   STATUS         mandatory
   DESCRIPTION    "Date that the hard drive image was last updated by LCCM"
   REFERENCE      "IBMPSG_ComputerSystemDetails.LCCMUpdateTime"
::= { iBMPSGComputerSystemDetailsEntry 29 }

iBMPSGLeaseTable OBJECT-TYPE
   SYNTAX         SEQUENCE OF IBMPSGLeaseEntry
   ACCESS         not-accessible
   STATUS         mandatory
   DESCRIPTION    "The IBMPSG_Lease class contains leasing information about the computer system."
   REFERENCE      "IBMPSG_Lease"
::= { ibmpsgAssetID 4 }

iBMPSGLeaseEntry OBJECT-TYPE
   SYNTAX         IBMPSGLeaseEntry
   ACCESS         not-accessible
   STATUS         mandatory
   DESCRIPTION    ""
   INDEX          { iBMPSGLeaseKeyIndex }
::= { iBMPSGLeaseTable 1 }

IBMPSGLeaseEntry ::= SEQUENCE
{
   iBMPSGLeaseKeyIndex String,   
   iBMPSGLeaseName String,
   iBMPSGLeaseLessor String,
   iBMPSGLeaseBuyout Uint32,
   iBMPSGLeaseLRF Uint8,
   iBMPSGLeaseLeaseStartDate Datetime,
   iBMPSGLeaseLeaseEndDate Datetime,
   iBMPSGLeaseFMV Uint32,
   iBMPSGLeaseLeaseTerm Uint8,
   iBMPSGLeaseLeasePayment String
}

iBMPSGLeaseKeyIndex OBJECT-TYPE
   SYNTAX         String
   ACCESS         read-write
   STATUS         mandatory
   DESCRIPTION    ""
   REFERENCE      "IBMPSG_Lease.KeyIndex"
::= { iBMPSGLeaseEntry 1 }

iBMPSGLeaseName OBJECT-TYPE
   SYNTAX         String
   ACCESS         read-write
   STATUS         mandatory
   DESCRIPTION    "The name of this lease."
   REFERENCE      "IBMPSG_Lease.Name"
::= { iBMPSGLeaseEntry 2 }

iBMPSGLeaseLessor OBJECT-TYPE
   SYNTAX         String
   ACCESS         read-write
   STATUS         mandatory
   DESCRIPTION    "The name of the owner of the leased property."
   REFERENCE      "IBMPSG_Lease.Lessor"
::= { iBMPSGLeaseEntry 3 }

iBMPSGLeaseBuyout OBJECT-TYPE
   SYNTAX         Uint32
   ACCESS         read-write
   STATUS         mandatory
   DESCRIPTION    "Amount of money required to purchase the leased property at the end of the lease term."
   REFERENCE      "IBMPSG_Lease.Buyout"
::= { iBMPSGLeaseEntry 4 }

iBMPSGLeaseLRF OBJECT-TYPE
   SYNTAX         Uint8
   ACCESS         read-write
   STATUS         mandatory
   DESCRIPTION    "Lease Rate Factor.  This is a percentage that when multiplied by the cost gives the periodic lease payment amount."
   REFERENCE      "IBMPSG_Lease.LRF"
::= { iBMPSGLeaseEntry 5 }

iBMPSGLeaseLeaseStartDate OBJECT-TYPE
   SYNTAX         Datetime
   ACCESS         read-write
   STATUS         mandatory
   DESCRIPTION    "Start date of the lease agreement."
   REFERENCE      "IBMPSG_Lease.LeaseStartDate"
::= { iBMPSGLeaseEntry 6 }

iBMPSGLeaseLeaseEndDate OBJECT-TYPE
   SYNTAX         Datetime
   ACCESS         read-write
   STATUS         mandatory
   DESCRIPTION    "Lease end date."
   REFERENCE      "IBMPSG_Lease.LeaseEndDate"
::= { iBMPSGLeaseEntry 7 }

iBMPSGLeaseFMV OBJECT-TYPE
   SYNTAX         Uint32
   ACCESS         read-write
   STATUS         mandatory
   DESCRIPTION    "Residual value / Fair Market Value (FMV) of system.  The price a willing buyer will pay a willing seller for leased property on an as is, where is basis with both under no compulsion to either buy or sell."
   REFERENCE      "IBMPSG_Lease.FMV"
::= { iBMPSGLeaseEntry 8 }

iBMPSGLeaseLeaseTerm OBJECT-TYPE
   SYNTAX         Uint8
   ACCESS         read-write
   STATUS         mandatory
   DESCRIPTION    "Length of the lease agreement in months."
   REFERENCE      "IBMPSG_Lease.LeaseTerm"
::= { iBMPSGLeaseEntry 9 }

iBMPSGLeaseLeasePayment OBJECT-TYPE
   SYNTAX         String
   ACCESS         read-write
   STATUS         mandatory
   DESCRIPTION    "Lease payment (rent)."
   REFERENCE      "IBMPSG_Lease.LeasePayment"
::= { iBMPSGLeaseEntry 10 }

iBMPSGWarrantyTable OBJECT-TYPE
   SYNTAX         SEQUENCE OF IBMPSGWarrantyEntry
   ACCESS         not-accessible
   STATUS         mandatory
   DESCRIPTION    "The IBMPSG_Warranty class contains warranty information about the Computer System."
   REFERENCE      "IBMPSG_Warranty"
::= { ibmpsgAssetID 5 }

iBMPSGWarrantyEntry OBJECT-TYPE
   SYNTAX         IBMPSGWarrantyEntry
   ACCESS         not-accessible
   STATUS         mandatory
   DESCRIPTION    ""
   INDEX          { iBMPSGWarrantyKeyIndex }
::= { iBMPSGWarrantyTable 1 }

IBMPSGWarrantyEntry ::= SEQUENCE
{
   iBMPSGWarrantyKeyIndex String,   
   iBMPSGWarrantyName String,
   iBMPSGWarrantyWarrantyDuration Uint8,
   iBMPSGWarrantyWarrantyDurationUnit Uint8,
   iBMPSGWarrantyWarrantyEndDate Datetime,
   iBMPSGWarrantyWarrantyCost String
}

iBMPSGWarrantyKeyIndex OBJECT-TYPE
   SYNTAX         String
   ACCESS         read-write
   STATUS         mandatory
   DESCRIPTION    ""
   REFERENCE      "IBMPSG_Warranty.KeyIndex"
::= { iBMPSGWarrantyEntry 1 }

iBMPSGWarrantyName OBJECT-TYPE
   SYNTAX         String
   ACCESS         read-write
   STATUS         mandatory
   DESCRIPTION    "The name of this warranty."
   REFERENCE      "IBMPSG_Warranty.Name"
::= { iBMPSGWarrantyEntry 2 }

iBMPSGWarrantyWarrantyDuration OBJECT-TYPE
   SYNTAX         Uint8
   ACCESS         read-write
   STATUS         mandatory
   DESCRIPTION    "Time period of warranty (start date to end date)."
   REFERENCE      "IBMPSG_Warranty.WarrantyDuration"
::= { iBMPSGWarrantyEntry 3 }

iBMPSGWarrantyWarrantyDurationUnit OBJECT-TYPE
   SYNTAX         Uint8
   ACCESS         read-write
   STATUS         mandatory
   DESCRIPTION    "The time unit for the warranty duration."
   REFERENCE      "IBMPSG_Warranty.WarrantyDurationUnit"
::= { iBMPSGWarrantyEntry 4 }

iBMPSGWarrantyWarrantyEndDate OBJECT-TYPE
   SYNTAX         Datetime
   ACCESS         read-write
   STATUS         mandatory
   DESCRIPTION    "Date on which the warranty expires."
   REFERENCE      "IBMPSG_Warranty.WarrantyEndDate"
::= { iBMPSGWarrantyEntry 5 }

iBMPSGWarrantyWarrantyCost OBJECT-TYPE
   SYNTAX         String
   ACCESS         read-write
   STATUS         mandatory
   DESCRIPTION    "Cost of the extended warranty"
   REFERENCE      "IBMPSG_Warranty.WarrantyCost"
::= { iBMPSGWarrantyEntry 6 }



iBMPSGFRUTable OBJECT-TYPE
   SYNTAX         SEQUENCE OF IBMPSGFRUEntry
   ACCESS         not-accessible
   STATUS         mandatory
   DESCRIPTION    "The IBMPSG_FRU class contains FRU information about the Computer System."
   REFERENCE      "IBMPSG_FRU"
::= { ibmpsgAssetID 6 }

iBMPSGFRUEntry OBJECT-TYPE
   SYNTAX         IBMPSGFRUEntry
   ACCESS         not-accessible
   STATUS         mandatory
   DESCRIPTION    ""
   INDEX          { iBMPSGFRUKeyIndex }
::= { iBMPSGFRUTable 1 }

IBMPSGFRUEntry ::= SEQUENCE
{
   iBMPSGFRUKeyIndex String,   
   iBMPSGFRUName String,
   iBMPSGFRUFRUNumber String,
   iBMPSGFRUIdentifyingNumber String,
   iBMPSGFRUVendor String,
   iBMPSGFRURevisionLevel String,
   iBMPSGFRUDescription String
}

iBMPSGFRUKeyIndex OBJECT-TYPE
   SYNTAX         String
   ACCESS         read-write
   STATUS         mandatory
   DESCRIPTION    ""
   REFERENCE      "IBMPSG_FRU.KeyIndex"
::= { iBMPSGFRUEntry 1 }

iBMPSGFRUName OBJECT-TYPE
   SYNTAX         String
   ACCESS         read-write
   STATUS         mandatory
   DESCRIPTION    "FRU name."
   REFERENCE      "IBMPSG_FRU.Name"
::= { iBMPSGFRUEntry 2 }

iBMPSGFRUFRUNumber OBJECT-TYPE
   SYNTAX         String
   ACCESS         read-write
   STATUS         mandatory
   DESCRIPTION    "FRU ordering information."
   REFERENCE      "IBMPSG_FRU.FRUNumber"
::= { iBMPSGFRUEntry 3 }

iBMPSGFRUIdentifyingNumber OBJECT-TYPE
   SYNTAX         String
   ACCESS         read-write
   STATUS         mandatory
   DESCRIPTION    "FRU identification such as a serial number on software or a die number on a hardware chip."
   REFERENCE      "IBMPSG_FRU.IdentifyingNumber"
::= { iBMPSGFRUEntry 4 }

iBMPSGFRUVendor OBJECT-TYPE
   SYNTAX         String
   ACCESS         read-write
   STATUS         mandatory
   DESCRIPTION    "The name of the FRU's supplier."
   REFERENCE      "IBMPSG_FRU.Vendor"
::= { iBMPSGFRUEntry 5 }

iBMPSGFRURevisionLevel OBJECT-TYPE
   SYNTAX         String
   ACCESS         read-write
   STATUS         mandatory
   DESCRIPTION    "The FRU's revision level."
   REFERENCE      "IBMPSG_FRU.RevisionLevel"
::= { iBMPSGFRUEntry 6 }

iBMPSGFRUDescription OBJECT-TYPE
   SYNTAX         String
   ACCESS         read-write
   STATUS         mandatory
   DESCRIPTION    "A textual description of the FRU."
   REFERENCE      "IBMPSG_FRU.Description"
::= { iBMPSGFRUEntry 7 }

END
