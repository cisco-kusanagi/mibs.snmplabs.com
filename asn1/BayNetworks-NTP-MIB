--NTP mib file
--BayNetworks-NTP-MIB definitions

BayNetworks-NTP-MIB DEFINITIONS ::= BEGIN


    IMPORTS

      IpAddress, Counter, Gauge, TimeTicks
        FROM RFC1155-SMI
      OBJECT-TYPE
        FROM RFC-1212
    wfNtpGroup	
        FROM Wellfleet-COMMON-MIB;  



 	wfNtpEntryTable OBJECT-TYPE
	SYNTAX SEQUENCE OF WfNtpEntry
	ACCESS not-accessible
	STATUS mandatory
	DESCRIPTION 
		"NTP base entry table. 
		"
	::= {wfNtpGroup 1}
	
	wfNtpEntry OBJECT-TYPE
	 	SYNTAX  WfNtpEntry
	        ACCESS  not-accessible
        	STATUS  mandatory
        	DESCRIPTION
                "An  NTP base entry description"
        INDEX   { wfNtpIndex}

        ::= { wfNtpEntryTable 1 }
 
    WfNtpEntry ::= SEQUENCE {
		wfNtpIndex
		INTEGER,
		wfNtpDelete
		INTEGER,
		wfNtpDisable
		INTEGER,
		wfNtpMode
		INTEGER,
		wfNtpDebugFlag
		Gauge,
		wfNtpState
		INTEGER,
		wfNtpVersion
		INTEGER,
		wfNtpStratum
		INTEGER,
		wfNtpRootDelay
		INTEGER,
		wfNtpReferenceId
		IpAddress,
		wfNtpClockPrec
		INTEGER,
		wfNtpLeapHappened
		INTEGER,
		wfNtpLeapTime
		TimeTicks,
                wfNtpUpdateTimer
                INTEGER
	    }


	wfNtpIndex OBJECT-TYPE
	     	SYNTAX INTEGER
		ACCESS read-only
		STATUS mandatory
	DESCRIPTION
		" Index of this entry. Index could only be one"
	::= { wfNtpEntry 1}	
	wfNtpDelete OBJECT-TYPE
		SYNTAX INTEGER{
			created(1),
			deleted(2)
			}
		ACCESS read-write
		STATUS mandatory
        DESCRIPTION
                "Create/Delete parameter. Default is created.
                Users perform a set operation on this
                object in order to create/delete NTP."
        DEFVAL	{ created }
        ::= { wfNtpEntry 2 }
	
	wfNtpDisable OBJECT-TYPE
		SYNTAX INTEGER {
			enabled(1),
			disabled(2)
			}
   		ACCESS read-write
		STATUS mandatory
	DESCRIPTION
		"Enable/Disable NTP"
	DEFVAL	{ enabled }
        ::= { wfNtpEntry 3 }

	wfNtpMode OBJECT-TYPE
		SYNTAX INTEGER {
			client(1),
			bclient(2),
			mclient(3)
			}
   		ACCESS read-write
		STATUS mandatory
	DESCRIPTION
		"Enable/Disable NTP"
	DEFVAL	{ client }
        ::= { wfNtpEntry 4 }

	wfNtpDebugFlag OBJECT-TYPE
		SYNTAX Gauge
		ACCESS read-write
		STATUS mandatory
		DESCRIPTION
			"Flag for setting debug level"
		
	::= { wfNtpEntry 5 } 

    	wfNtpState OBJECT-TYPE
        	SYNTAX	INTEGER {
 		    up(1),
    		    down(2),
    		    init(3),
    		    notpresent(4)    		
    		}
        	ACCESS	read-only
        	STATUS	mandatory
        DESCRIPTION
                "The current state of NTP."
        DEFVAL	{ notpresent }
        ::= { wfNtpEntry 6 }
	
	wfNtpVersion OBJECT-TYPE
		SYNTAX INTEGER
		ACCESS read-only
		STATUS mandatory
		DESCRIPTION
			"The NTP version on the Router NTP client/server
			 software"
		
	::= { wfNtpEntry 7 } 
						
	wfNtpStratum OBJECT-TYPE
		SYNTAX INTEGER (0..15)
	        ACCESS read-only
		STATUS mandatory
		DESCRIPTION
			"Router NTP client software stratum"
	::= {wfNtpEntry 8 }

	wfNtpRootDelay OBJECT-TYPE
		SYNTAX INTEGER
		ACCESS read-only
		STATUS mandatory
		DESCRIPTION
			"Delay from  synchronization server
			 this could be another secondary server or
			 primary server in seconds"
	::= {wfNtpEntry 9 }

	wfNtpReferenceId OBJECT-TYPE
		SYNTAX IpAddress
		ACCESS read-only
		STATUS mandatory
		DESCRIPTION "Reference ID of time synchronozition source "
	::={wfNtpEntry 10}

	

	wfNtpClockPrec OBJECT-TYPE
		SYNTAX INTEGER
		ACCESS read-only
		STATUS mandatory
		DESCRIPTION "  An 8 bit number indicating the precision 
			       of the router clock in seconds to the nearest
			       power of two.
			    "	
	::={wfNtpEntry 11}  

	wfNtpLeapHappened OBJECT-TYPE
		SYNTAX INTEGER{
			yes(1),
			no(2)
			}
		ACCESS read-only
		STATUS mandatory
		DESCRIPTION "Flag indicating whether leap occurred or not 
			     leap: a leap second is added / subtracted from the 
			     last second of a particular day for e.g. the time  
                             of a particular day will end with 23:59:60 instead
			     of 23:59:59. This is done to conform with Universal 
			     Standard Time conventions"
	 ::={wfNtpEntry 12}

	wfNtpLeapTime OBJECT-TYPE	
		SYNTAX TimeTicks
		ACCESS read-only
		STATUS mandatory
		DESCRIPTION "Next leap adjustment in 1/100 second"
	 ::={wfNtpEntry 13}

        wfNtpUpdateTimer OBJECT-TYPE
                SYNTAX INTEGER
                ACCESS read-write
                STATUS mandatory
                DESCRIPTION "Number of seconds in powers of 2 between NTP polls."
         ::={wfNtpEntry 14}


 	wfNtpAccessTable OBJECT-TYPE
	SYNTAX SEQUENCE OF WfNtpAccessEntry
	ACCESS not-accessible
	STATUS mandatory
	DESCRIPTION 
		"List of peers we restrict/prefer time synchronization
		 based on source IP address or the source subnet
		"
	::= {wfNtpGroup 2}
	
	wfNtpAccessEntry OBJECT-TYPE
	 	SYNTAX  WfNtpAccessEntry
	        ACCESS  not-accessible
        	STATUS  mandatory
        	DESCRIPTION
                "An  access control entry description"
        INDEX   { wfNtpAccessIpAddr }

        ::= { wfNtpAccessTable 1 }
 
    WfNtpAccessEntry ::= SEQUENCE {
            wfNtpAccessDelete
                INTEGER,
	    wfNtpAccessFilterType
		INTEGER,
            wfNtpAccessIpAddr
                IpAddress,
            wfNtpAccessIpMask
                IpAddress
	    }

    	wfNtpAccessDelete OBJECT-TYPE
	SYNTAX INTEGER {
		created(1),
		deleted(2)
		}	
	
	ACCESS  read-write
        STATUS  mandatory
        DESCRIPTION
                "Create/Delete parameter. Default is created.
                Users perform a set operation on this
                object in order to create/delete an NTP access control record"
        DEFVAL  { created }	
        ::= {wfNtpAccessEntry 1}
	
	wfNtpAccessFilterType OBJECT-TYPE  
	SYNTAX INTEGER {
		restrict(1),
		prefer(2)
		}	
	 ACCESS  read-write
        STATUS  mandatory
        DESCRIPTION
                "Could be restrict or prefer"
	DEFVAL {restrict}
        ::= {wfNtpAccessEntry 2}
	
	wfNtpAccessIpAddr OBJECT-TYPE
	SYNTAX IpAddress
	 ACCESS  read-only
        STATUS  mandatory
        DESCRIPTION
                "Source Ip address of Peer the rule applies to"
        ::= {wfNtpAccessEntry 3}

	wfNtpAccessIpMask OBJECT-TYPE
	SYNTAX   IpAddress
	 ACCESS  read-write
        STATUS  mandatory
        DESCRIPTION
                "Mask of subnet if rule applies to peers from 
		a specific subnet"
        ::= {wfNtpAccessEntry 4}	 
	


	wfNtpPeerTable OBJECT-TYPE
        SYNTAX  SEQUENCE OF WfNtpPeerEntry
        ACCESS  not-accessible
        STATUS  mandatory
        DESCRIPTION
                "The list of configured NTP peers"
        ::= { wfNtpGroup 3 }
 
    wfNtpPeerEntry OBJECT-TYPE
        SYNTAX  WfNtpPeerEntry
        ACCESS  not-accessible
        STATUS  mandatory
        DESCRIPTION
                "An NTP peer  description"
        INDEX   { wfNtpPeerIpAddress }
                  
        ::= { wfNtpPeerTable 1 }
 
    WfNtpPeerEntry ::= SEQUENCE {
		wfNtpPeerDelete
		INTEGER,
		wfNtpPeerState
		Gauge,
		wfNtpCfgPeerMode
		INTEGER,
		wfNtpPeerMode 
		INTEGER,
		wfNtpPeerHostMode
		INTEGER,   
		wfNtpPeerIpAddress
		IpAddress,
		wfNtpSourceIpAddress
		IpAddress,
		wfNtpPeerPref
		INTEGER,
		wfNtpPeerRefId
		IpAddress,
		wfNtpPeerVersion
		INTEGER,
		wfNtpPeerPrecision
		INTEGER,
		wfNtpPeerStratum
		INTEGER,
		wfNtpPeerRootDelay
		INTEGER,
		wfNtpPeerDispersion
		Gauge,
		wfNtpPeerOffset
		Gauge,
		wfNtpPeerPolls
		Counter,
		wfNtpPeerFrameReceives
		Counter

	}

	wfNtpPeerDelete OBJECT-TYPE
        SYNTAX  INTEGER {
		created(1),
                deleted(2)
                }

        ACCESS  read-write
        STATUS  mandatory
        DESCRIPTION
                "Create/Delete parameter. Default is created.
                Users perform a set operation on this
                object in order to create/delete an IP interface."
	 DEFVAL  { created } 
     	 ::= { wfNtpPeerEntry 1 }

	wfNtpPeerState OBJECT-TYPE
        SYNTAX  Gauge
        ACCESS  read-only
        STATUS  mandatory
        DESCRIPTION
                "State of peer "
        ::= { wfNtpPeerEntry 2 }
	

	wfNtpCfgPeerMode OBJECT-TYPE
	SYNTAX  INTEGER {
		server(1),
		peer(2)
		}
        ACCESS  read-write
        STATUS  mandatory
        DESCRIPTION
                "The configured as peer or server"
	DEFVAL {server}
	::= { wfNtpPeerEntry 3 }

	wfNtpPeerMode OBJECT-TYPE
        SYNTAX  INTEGER {
		symmetrica(1),
		symmetricp(2),
		client(3),
		server(4),
		broadcast(5),
		ntpctrl(6)
		}
        ACCESS  read-only
        STATUS  mandatory
        DESCRIPTION
                "The mode peer of operation"
        ::= { wfNtpPeerEntry 4 }

	
	wfNtpPeerHostMode OBJECT-TYPE
        SYNTAX  INTEGER {
		symmetrica(1),
		symmetricp (2),
		client(3),
		server(4),
		broadcast(5),
		ntpctrl(6)
		}
        ACCESS  read-write
        STATUS  mandatory
        DESCRIPTION
                "Router NTP mode"
	DEFVAL {client}	
        ::= { wfNtpPeerEntry 5 }


	wfNtpPeerIpAddress OBJECT-TYPE
        SYNTAX  IpAddress
        ACCESS  read-only
        STATUS  mandatory
        DESCRIPTION
                "Source IP address of Peer"
        ::= { wfNtpPeerEntry 6 }

	wfNtpSourceIpAddress OBJECT-TYPE
        SYNTAX  IpAddress
        ACCESS  read-write
        STATUS  mandatory
        DESCRIPTION
                "Source IP address of Peer"
        ::= { wfNtpPeerEntry 7 }
	
	wfNtpPeerPref OBJECT-TYPE
	SYNTAX  INTEGER{
		yes(1),
		no(2)
		}
        ACCESS  read-write
        STATUS  mandatory
        DESCRIPTION
                "Peer Preference: Preference assigned to this peer. Will override 
		 NTP peer selection algorithm if greater than default value"
	DEFVAL {no}
        ::= { wfNtpPeerEntry 8 }
	
	
	wfNtpPeerRefId OBJECT-TYPE
        SYNTAX  IpAddress 
        ACCESS  read-only
        STATUS  mandatory
        DESCRIPTION
                "Peer Reference clock IP address"
        ::= { wfNtpPeerEntry 9 }
	

	wfNtpPeerVersion OBJECT-TYPE
        SYNTAX  INTEGER 
        ACCESS  read-only
        STATUS  mandatory
        DESCRIPTION
                "Peers NTP version number"
	DEFVAL{3}
        ::= { wfNtpPeerEntry 10 }

	wfNtpPeerPrecision OBJECT-TYPE
        SYNTAX  INTEGER 
        ACCESS  read-only
        STATUS  mandatory
        DESCRIPTION
                "Peers clock precision"
        ::= { wfNtpPeerEntry 11 }

	wfNtpPeerStratum OBJECT-TYPE
        SYNTAX  INTEGER(0 .. 15) 
        ACCESS  read-only
        STATUS  mandatory
        DESCRIPTION
                "Peer stratum"
        ::= { wfNtpPeerEntry 12 }

	wfNtpPeerRootDelay OBJECT-TYPE
        SYNTAX  INTEGER 
        ACCESS  read-only
        STATUS  mandatory
        DESCRIPTION
                "Delay from syncronization clock in seconds"
        ::= { wfNtpPeerEntry 13 }

	wfNtpPeerDispersion OBJECT-TYPE
        SYNTAX  Gauge
        ACCESS  read-only
        STATUS  mandatory
        DESCRIPTION
                "Peer clock dispersion"
        ::= { wfNtpPeerEntry 14 }

	wfNtpPeerOffset OBJECT-TYPE
        SYNTAX  Gauge
        ACCESS  read-only
        STATUS  mandatory
        DESCRIPTION
                "Peer clock offset"
        ::= { wfNtpPeerEntry 15 }

	wfNtpPeerPolls OBJECT-TYPE
        SYNTAX  Counter 
        ACCESS  read-only
        STATUS  mandatory
        DESCRIPTION
                "Number of times this peer has been polled"
        ::= { wfNtpPeerEntry 16 }
	
	wfNtpPeerFrameReceives OBJECT-TYPE
	SYNTAX  Counter  
        ACCESS  read-only
        STATUS  mandatory
        DESCRIPTION
                "Number of times this peer has been polled"
        ::= { wfNtpPeerEntry 17 }

END  -- BayNetworks-NTP-MIB
