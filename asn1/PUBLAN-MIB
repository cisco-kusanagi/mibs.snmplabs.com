PUBLAN-MIB 

--FORCE-INCLUDE <stdio.h>

DEFINITIONS ::= BEGIN

IMPORTS
	mgmt, private, enterprises,
		NetworkAddress, IpAddress, Counter, Gauge,
	        TimeTicks
            FROM RFC1155-SMI

        OBJECT-TYPE
            FROM RFC-1212

       TRAP-TYPE
	    FROM RFC-1215;


	DisplayString ::=
              OCTET STRING
          -- This data type is used to model textual information taken
          -- from the NVT ASCII character set.  By convention, objects
          -- with this syntax are declared as having
          --
          --      SIZE (0..255)

        PhysAddress ::=
              OCTET STRING
          -- This data type is used to model media addresses.  For many
          -- types of media, this will be in a binary representation.
          -- For example, an ethernet address would be represented as
          -- a string of 6 octets.


       -- defining the enterprise OID for publan
       
       lucent	OBJECT IDENTIFIER ::= { enterprises 1751 }

       lucent-MIB OBJECT IDENTIFIER ::= { lucent 2 }

       publan   OBJECT IDENTIFIER ::= { lucent-MIB 51 }

       pubStation OBJECT IDENTIFIER ::= { publan 1 }

       pubClient OBJECT IDENTIFIER ::= { publan 2 }


       -- The various groups in this agent

       publanInterface OBJECT IDENTIFIER ::= { publan 3 }

       publanSNMPSetup OBJECT IDENTIFIER ::= { publan 4 }

       publanPPPSetup  OBJECT IDENTIFIER ::= { publan 5 }

       publanAgent OBJECT IDENTIFIER ::= { publan 6 } 

       radius OBJECT IDENTIFIER ::= { publan 7 }

       publanShimECPSetup  OBJECT IDENTIFIER ::= { publan 8 }

       pubStationTraps OBJECT IDENTIFIER ::= { publan 15 }

       -- The sub-groups of publanInterface

       publanPHY OBJECT IDENTIFIER ::= { publanInterface 2 }

       publanDriver OBJECT IDENTIFIER ::= { publanInterface 4 }

	-- The publanPHY sub-group of publanInterface

	pliSystemName	OBJECT-TYPE
	    SYNTAX DisplayString
            ACCESS read-write
	    STATUS mandatory
	    DESCRIPTION
		"The sysName of the PubStation. This may be used for 
		diagnostic purposes. This name will be the same as the
		sysName of the system group of MIB II"
            ::= { publanPHY 1 }

	pliNetworkName	OBJECT-TYPE
	    SYNTAX DisplayString
	    ACCESS read-write
	    STATUS mandatory
	    DESCRIPTION
		"The network name of this interface"
	    ::= { publanPHY 2 }

	pliMACAddress	OBJECT-TYPE
	    SYNTAX PhysAddress
	    ACCESS read-only
	    STATUS mandatory
	    DESCRIPTION
		"The MAC address of this PubStation."
	    ::= { publanPHY 3 }

	pliMediumReservation 	OBJECT-TYPE
	    SYNTAX INTEGER(0..2347)
	    ACCESS read-write
	    STATUS mandatory
	    DESCRIPTION
		"The medium reservation value. The range is 0 - 2347.
	         Default is 2347 - means disabled.
		 Medium reservation specifies the number of octets in
		 a message above which a RTS/CTS handshake is performed."
            ::= { publanPHY 4 }

	pliTransmitRate	OBJECT-TYPE
	    SYNTAX INTEGER (1..3)
		   --{
            --Commented this out 1,
		    --Commented this out 2,
		    -- Commented this out 3
		   --}
            ACCESS read-write
	    STATUS mandatory
            DESCRIPTION
		"The transmit rate of this interface."
            ::= { publanPHY 5 }
        
	pliOperatingFrequency OBJECT-TYPE
	    SYNTAX INTEGER(1..14)
            ACCESS read-write
            STATUS mandatory
	    DESCRIPTION
	        "The RF channel that the PubStation is working on."
            ::= { publanPHY 6 }

	pliAPDensity	OBJECT-TYPE
	    SYNTAX INTEGER (1..3)
	           --{
	    	     -- Commented this out 1,
	    	     -- Commented this out 2,
	    	     -- Commented this out 3
	           --}
            ACCESS read-write
	    STATUS mandatory
            DESCRIPTION
		"The AP density in the region."
	    ::= { publanPHY 7 }

	pliClosedSystem 	OBJECT-TYPE
	    SYNTAX INTEGER (1..2)
	    --{
	      -- Commented this out 1,
	      -- Commented this out 2
	    --}
	    ACCESS read-only
	    STATUS mandatory
	    DESCRIPTION
		"This flag identifies whether the PubStation will accept 
		associate requests from PubClients having a network name 
		of 'ANY'. The PubStation should always be a closed station
		and such requests should always be rejected. This flag is 
		provided for diagnostic purposes."
            ::= { publanPHY 8 }            
            
 	pliAllowedDataRates OBJECT-TYPE
	    SYNTAX INTEGER
            ACCESS read-only
            STATUS mandatory
	    DESCRIPTION
	        "this identifies the allowed data rates of the Wavelan Card"
            ::= { publanPHY 9 }
           

	-- The publanDriver sub-group of publanInterface

	pliDriverName	OBJECT-TYPE
	    SYNTAX DisplayString
	    ACCESS read-only
	    STATUS mandatory
	    DESCRIPTION
	        "The driver name."
            ::= { publanDriver 1 }

	pliDriverVersion	OBJECT-TYPE
	    SYNTAX DisplayString
	    ACCESS read-only
	    STATUS mandatory
	    DESCRIPTION
	        "The driver's version number. This is a text string
	        including the major and minor release number, and, 
	        optionally, the patch level:  'mm.nn.pp', where
                    mm = major release number
                    nn = point release number
                    pp = optional patch number."
	    ::= { publanDriver 2 }

	-- The publanSNMPSetup specific management objects start here

	psSNMPReadPassword	OBJECT-TYPE
	    SYNTAX DisplayString
	    ACCESS write-only
	    STATUS mandatory
	    DESCRIPTION
	        "The password for reading object values from the agent."
	    ::= { publanSNMPSetup 1 }

	psSNMPReadWritePassword	 OBJECT-TYPE
	    SYNTAX DisplayString
	    ACCESS write-only
	    STATUS mandatory
	    DESCRIPTION
	        "The password for reading and modifying object values 
	        from the agent."
            ::= { publanSNMPSetup 2 }

	psSNMPTrapHostIPAddress	  OBJECT-TYPE
	    SYNTAX IpAddress
	    ACCESS read-write
	    STATUS mandatory
	    DESCRIPTION
	        "The IP address of the host to which traps should be sent."
	    ::= { publanSNMPSetup 3 }

	psSNMPTrapHostPassword	OBJECT-TYPE
	    SYNTAX DisplayString
	    ACCESS read-write
	    STATUS mandatory
	    DESCRIPTION
	        "The password sent with the trap to enable the management
	        station to ignore unsolicited traps."
	    ::= { publanSNMPSetup 4 }

	psSNMPManagerCount	OBJECT-TYPE
	    SYNTAX INTEGER
	    ACCESS read-only
	    STATUS mandatory
	    DESCRIPTION
	        "The number of management stations that have been 
	        authorised to manage this PubStation."
	    ::= { publanSNMPSetup 5 }

	psSNMPAccessTable OBJECT-TYPE
	    SYNTAX SEQUENCE OF PsSNMPAccessTableEntry
	    ACCESS not-accessible
	    STATUS mandatory
	    DESCRIPTION
		"The table containing the information about the
		managers authorised to manage this PubStation."
            ::= { publanSNMPSetup 6 }
	
	psSNMPAccessTableEntry OBJECT-TYPE
	    SYNTAX PsSNMPAccessTableEntry
	    ACCESS not-accessible
	    STATUS mandatory
	    DESCRIPTION
	        "The entry in the SNMP access table. Described
	        next."
            INDEX { psSNMPManagerIndex }
            ::= { psSNMPAccessTable 1 }

	PsSNMPAccessTableEntry ::=
	    SEQUENCE
	    {
	      index INTEGER,
	      managerIPAddress IpAddress,
	      managerIPMask  IpAddress,
	      managerStatus  INTEGER
	    }
	  

	index	OBJECT-TYPE
	    SYNTAX INTEGER
	    ACCESS not-accessible
	    STATUS mandatory
	    DESCRIPTION
	        "Management station identification number.
	        Is the index for the table."
	    ::= { psSNMPAccessTableEntry 1 }


	managerIPAddress	OBJECT-TYPE
	    SYNTAX IpAddress
	    ACCESS read-write
	    STATUS mandatory
	    DESCRIPTION
	        "IP address of the management station."
	    ::= { psSNMPAccessTableEntry 2 }


	managerIPMask	OBJECT-TYPE
	    SYNTAX IpAddress
	    ACCESS read-write
	    STATUS mandatory
	    DESCRIPTION
		"The IP subnet  mask. Used to grant access to a complete 
		subnet."
            ::= { psSNMPAccessTableEntry 3 }


	managerStatus	OBJECT-TYPE
	    SYNTAX INTEGER
		   {
		     enable(1),
		     --disable(2)
		     delete(2)
		   }
            ACCESS read-write
	    STATUS mandatory
	    DESCRIPTION
	        "Whether the manager is enabled or disabled.
		Used to delete the unwanted entries."
            ::= { psSNMPAccessTableEntry 4 }

	psSNMPInBadManagers OBJECT-TYPE
	    SYNTAX Counter
	    ACCESS read-only
	    STATUS mandatory
	    DESCRIPTION
	        "The no of attempts to manage this PubStation
		 by unauthorised managers."
	    ::= { publanSNMPSetup 7 }

	-- The publanPPPSetup specific management objects start here

	psPPPIPAddressAssignmentType  OBJECT-TYPE 
	    SYNTAX INTEGER (1..3)
		   --{
		    -- apm(1),
		    -- dhcp(2),
		    -- radius(3)
		   --}
            ACCESS read-write
	    STATUS mandatory
	    DESCRIPTION
                "This identifies whether the IP addresses assigned 
		 to the PubClients are obtained through APM (address 
		 pool manager), through DHCP or through the RADIUS 
		 server."
            ::= { publanPPPSetup 1 }

	psPPPStartIPAddress  OBJECT-TYPE
	    SYNTAX IpAddress
	    ACCESS read-write
	    STATUS mandatory
	    DESCRIPTION
		"The start IP address that the PPP can use for 
		assignment to clients."
            ::= { publanPPPSetup 2 }

	psPPPEndIPAddress  OBJECT-TYPE
	    SYNTAX IpAddress
	    ACCESS read-write
	    STATUS mandatory
	    DESCRIPTION
	        "The last IP address that the PPP can use for 
		assignment to clients. Combined with the 
		psPPPStartIPAddress, this specifies the range of 
		addresses to be used."
	    ::= { publanPPPSetup 3 }

	psPPPNoOfMACIPMappingEntries  OBJECT-TYPE
	    SYNTAX INTEGER
	    ACCESS read-only
	    STATUS mandatory
	    DESCRIPTION
	      "The number of static mapping entries."
	    ::= { publanPPPSetup 4 }

	psPPPMACIPMappingTable  OBJECT-TYPE
	    SYNTAX SEQUENCE OF PsPPPMACIPMappingTableEntry
	    ACCESS not-accessible
	    STATUS mandatory
	    DESCRIPTION
		"This table contains the static mapping of
		MAC addresses to IP addresses."
		::= { publanPPPSetup 5 }
        
	psPPPMACIPMappingTableEntry  OBJECT-TYPE
	    SYNTAX PsPPPMACIPMappingTableEntry
	    ACCESS not-accessible
	    STATUS mandatory
            DESCRIPTION
		"The entry of the psPPPMACIPMappingTable.
		Described below."
            INDEX { psPPPMACIPTableIndex }
            ::= { psPPPMACIPMappingTable 1 }

	PsPPPMACIPMappingTableEntry  ::=
	     SEQUENCE
	     {
	       index2 INTEGER,
	       macaddress PhysAddress,
	       ipAddress IpAddress,
	       comment   DisplayString,
	       entrystatus INTEGER
	     }

	index3  OBJECT-TYPE
	    SYNTAX INTEGER
	    ACCESS not-accessible
	    STATUS mandatory
	    DESCRIPTION
	        " This is the index for the mappping table."
	    ::= { psPPPMACIPMappingTableEntry 1 }

	macaddress OBJECT-TYPE
	    SYNTAX PhysAddress
	    ACCESS read-write
	    STATUS mandatory
	    DESCRIPTION
	        "This is the MAC address."
	    ::= { psPPPMACIPMappingTableEntry 2 }

	ipAddress  OBJECT-TYPE
	    SYNTAX  IpAddress
	    ACCESS read-write
	    STATUS mandatory
	    DESCRIPTION
	        "The IP address corresponding to the MAC address."
            ::= { psPPPMACIPMappingTableEntry 3 }

	comment   OBJECT-TYPE
	    SYNTAX  DisplayString
	    ACCESS read-write
	    STATUS mandatory
	    DESCRIPTION
	        "The comment for thi entry, maybe the PC's owner."
            ::= { psPPPMACIPMappingTableEntry 4 }


	entrystatus	OBJECT-TYPE
	    SYNTAX INTEGER
		   {
		     enable(1),
		     --disable(2)
		     delete(2)
		   }
            ACCESS write-only
	    STATUS mandatory
	    DESCRIPTION
	        "Whether the entry is enabled or disabled.
		Used to delete the unwanted entries."
            ::= { psPPPMACIPMappingTableEntry 5 }


	psPPPKeepAliveInterval  OBJECT-TYPE
	    SYNTAX INTEGER
	    ACCESS read-write
	    STATUS mandatory
	    DESCRIPTION
	        "The keep alive interval to be notified to the PPP 
	        layer."
	    ::= { publanPPPSetup 6 }

	psPPPNoOfKeepAliveTimeouts  OBJECT-TYPE
	    SYNTAX INTEGER
	    ACCESS read-write
	    STATUS mandatory
	    DESCRIPTION
	        "The maximum number of timeouts before the session 
	        is torn down."
            ::= { publanPPPSetup 7 }

	psPPPDNSIPAddress  OBJECT-TYPE
	    SYNTAX IpAddress
	    ACCESS read-write
	    STATUS mandatory
	    DESCRIPTION
	        "The IP address of the DNS server in the network."
            ::= { publanPPPSetup 8 }

		psPPPIPRangeTable  OBJECT-TYPE
	    SYNTAX SEQUENCE OF PsPPPIPRangeTableEntry
	    ACCESS not-accessible
	    STATUS mandatory
	    DESCRIPTION
		"This table contains the static mapping of
		MAC addresses to IP addresses."
		::= { publanPPPSetup 20 }
        
	psPPPIPRangeTableEntry  OBJECT-TYPE
	    SYNTAX PsPPPIPRangeTableEntry
	    ACCESS not-accessible
	    STATUS mandatory
            DESCRIPTION
		"The entry of the psPPPIPRangeTable.
		Described below."
            INDEX { psPPPIPRangeTableIndex }
            ::= { psPPPIPRangeTable 1 }

	PsPPPIPRangeTableEntry  ::=
	     SEQUENCE
	     {
	       psPPPIPRangeTableIndex INTEGER,
	       poolStartIPAddress IpAddress,
	       poolEndIPAddress IpAddress,
	       numOfIPAddresss INTEGER,
	       --Comments DisplayString,
	       status INTEGER
	     }

	psPPPIPRangeTableIndex  OBJECT-TYPE
	    SYNTAX INTEGER
	    ACCESS not-accessible
	    STATUS mandatory
	    DESCRIPTION
	        " This is the index for the IP range table."
	    ::= { psPPPIPRangeTableEntry 1 }

	poolStartIPAddress OBJECT-TYPE
	    SYNTAX IpAddress
	    ACCESS read-write
	    STATUS mandatory
	    DESCRIPTION
	        "This is the staring IP address of this range."
	    ::= { psPPPIPRangeTableEntry 2 }

	 poolEndIPAddress OBJECT-TYPE
	    SYNTAX IpAddress
	    ACCESS read-write
	    STATUS mandatory
	    DESCRIPTION
	        "This is the ending IP address of this range."
	    ::= { psPPPIPRangeTableEntry 3 }

	numOfIPAddresss OBJECT-TYPE
	    SYNTAX INTEGER
	    ACCESS read-write
	    STATUS mandatory
	    DESCRIPTION
	        "This is the withd of the range (no of addresses)."
	    ::= { psPPPIPRangeTableEntry 4 }

	comments OBJECT-TYPE
	    SYNTAX DisplayString
	    ACCESS read-write
	    STATUS mandatory
	    DESCRIPTION
	        "Comment on the entry that is added"
	    ::= { psPPPIPRangeTableEntry 6 }


	status   OBJECT-TYPE
	    SYNTAX  INTEGER
	    {
	      enable(1), 
	      --disable(2),	
	      delete(3)
	    }  
	    ACCESS read-write
	    STATUS mandatory
	    DESCRIPTION
	        "The status of the entry, whether to be used or not
		 used. Setting this to delete will remove this entry."
            ::= { psPPPIPRangeTableEntry 5 }




	-- The publan agent specific management objects start here

	psVersion   OBJECT-TYPE
	    SYNTAX DisplayString
	    ACCESS read-only
	    STATUS mandatory
	    DESCRIPTION
		"The version of the PubStation software currently execuing.
		 Would be text string including the major and minor release 
		 number, and, optionally, the patch level:  'mm.nn.pp', where
                    mm = major release number
                    nn = point release number
                    pp = optional patch number."
            ::= { publanAgent 1 }

	psIPAddress   OBJECT-TYPE
	    SYNTAX IpAddress
	    ACCESS read-write
	    STATUS mandatory
	    DESCRIPTION
	        "The IP address to be assigned to the PubStation (to 
	        change from factory fitted IP address)."
	    ::= { publanAgent 2 }

	psSubnetMask   OBJECT-TYPE
	    SYNTAX IpAddress
	    ACCESS read-write
	    STATUS mandatory
	    DESCRIPTION
		"The subnet mask of the PubStation."
            ::= { publanAgent 3 }

	psDefaultGateway   OBJECT-TYPE
	    SYNTAX IpAddress
	    ACCESS read-write
	    STATUS mandatory
	    DESCRIPTION
	        "The default gateway for the PubStation."
	    ::= { publanAgent 4 }

	psIPAddressType   OBJECT-TYPE
	    SYNTAX  INTEGER    (1..2)
	    ACCESS read-write
	    STATUS mandatory
	    DESCRIPTION
		"This can be DHCP or static. The IP address of the
		PubStation will be assigned based on this."
            ::= { publanAgent 5 }

	psAdministrativeState   OBJECT-TYPE
	    SYNTAX  INTEGER (1..2)
		ACCESS read-write
	    STATUS mandatory
	    DESCRIPTION
		"The administrative state of the substation, can 
		be Up or Down."
            ::= { publanAgent 6 }


	psTFTPIPAddress   OBJECT-TYPE
	    SYNTAX IpAddress
	    ACCESS read-write
	    STATUS mandatory
	    DESCRIPTION
	        "The IP address of the TFTP server."
	    ::= { publanAgent 7 }


	psTFTPFilename   OBJECT-TYPE
	    SYNTAX DisplayString
	    ACCESS read-write
	    STATUS mandatory
	    DESCRIPTION
		"The filename of the image in the TFTP server."
            ::= { publanAgent 8 }

	psTFTPOperation   OBJECT-TYPE
	    SYNTAX INTEGER  (1..2)
		ACCESS write-only
	    STATUS mandatory
	    DESCRIPTION 
		"The operation  to be done, can be upload or download."
            ::= { publanAgent 9 }

	psReboot	OBJECT-TYPE
	    SYNTAX INTEGER
	    ACCESS write-only
	    STATUS mandatory
	    DESCRIPTION
		"This variable must be set to reboot the PubStation. The 
		 value is the number of seconds to wait to do a reboot."
            ::= { publanAgent 10 }

	--- RADIUS-CLIENT-MIB DEFINITIONS ::= BEGIN
	
	 -- radius OBJECT IDENTIFIER
	 --    DESCRIPTION
	 --       "The OID assigned to RADIUS MIB work by the IANA."
	 --       "The OID assigned to RADIUS MIB work by PubLAN."
	 --  ::= { publan 5 }
	 -- Moving this up to the common section

	 radiusClientMIB OBJECT IDENTIFIER
	 --    DESCRIPTION
	 --        "The MIB module for RADIUS Client Management."
	    ::=  { radius 2 }

	 radiusClientMIBObjects OBJECT IDENTIFIER ::=  { radiusClientMIB 1 }

	 radiusClient OBJECT IDENTIFIER ::=  { radiusClientMIBObjects 1 }

	 radiusClientInvalidServerAddresses OBJECT-TYPE
	     SYNTAX Counter
	     ACCESS read-only
	     STATUS mandatory
	     DESCRIPTION
	         "The total number of RADIUS Access-Response messages 
		 received from unknown addresses since client start-up"
	     ::=  { radiusClient 1 }

	 radiusServerTable OBJECT-TYPE
	     SYNTAX SEQUENCE OF RadiusServerEntry
	     ACCESS not-accessible
	     STATUS mandatory
	     DESCRIPTION
	         "The (conceptual) table listing the RADIUS servers with
	          which the client shares a secret."
	     ::=  { radiusClient 2 }

	 radiusServerEntry OBJECT-TYPE
	     SYNTAX RadiusServerEntry
	     ACCESS not-accessible
	     STATUS mandatory
	     DESCRIPTION
	         "An entry (conceptual row) representing a RADIUS server
	          with which the client shares a secret."
	     INDEX {radiusServerIndex}
	     ::=  { radiusServerTable 1 }

	 RadiusServerEntry ::= SEQUENCE {
	     index    INTEGER,
	     type    INTEGER,
	     --Type    DisplayString,
	     serverIPAddress    IpAddress,
	     destPortAuth    INTEGER,
	     destPortAcct    INTEGER,
	     accessRequests    Counter,
	     accessRetransmissions    Counter,
	     accessAccepts    Counter,
	     accessChallenges    Counter,
	     malformedAccessResponses    Counter,
	     authenticationBadAuthenticators    Counter,
	     accessRejects    Counter,
	     timeouts    Counter,
	     accountingRequests    Counter,
	     accountingRetransmissions    Counter,
	     accountingResponses    Counter,
	     accountingBadAuthenticators    Counter,
	     sharedSecret    DisplayString,
	     enabled    INTEGER,
	     responseTime    INTEGER,
	     maximumRetransmission    INTEGER
	     }

	 index4 OBJECT-TYPE
	     SYNTAX INTEGER
	     ACCESS not-accessible
	     STATUS mandatory
	     DESCRIPTION
	         "The RADIUS server with whom the client interacts."
	     ::=  { radiusServerEntry 1 }

	  type OBJECT-TYPE
	     SYNTAX INTEGER { auth (1),
	                      acct (2),
	                      --both (3)
	                      auth-and-acct (3)
	                    }
	     --SYNTAX DisplayString 
	     ACCESS read-only
	     STATUS mandatory
	     DESCRIPTION
	         "The RADIUS server type (Authentication or Accounting or Both).
	          For creating a server entry Server Type should be set"
	     --DEFVAL { "auth-and-acct" }     
	     ::=  { radiusServerEntry 2 }
	     

	 serverIPAddress OBJECT-TYPE
	     SYNTAX IpAddress
	     ACCESS read-write
	     STATUS mandatory
	     DESCRIPTION
	         "The IP address of the RADIUS server
	          referred to in this table entry."
	     ::=  { radiusServerEntry 3 }

	 destPortAuth OBJECT-TYPE
	     SYNTAX INTEGER
	     ACCESS read-write
	     STATUS mandatory
	     DESCRIPTION
	         " The Authentication port of the RADIUS Server."
	     ::=  { radiusServerEntry 4 }

	 destPortAcct OBJECT-TYPE
	     SYNTAX INTEGER
	     ACCESS read-write
	     STATUS mandatory
	     DESCRIPTION
	         " The Accounting port of the RADIUS Server."
	     ::=  { radiusServerEntry 5 }

	 accessRequests OBJECT-TYPE
	     SYNTAX Counter
	     ACCESS read-only
	     STATUS mandatory
	     DESCRIPTION
	         "The total number of RADIUS Access-Request messages sent
	          since client start-up"
	     ::=  { radiusServerEntry 6 }

	 accessRetransmissions OBJECT-TYPE
	     SYNTAX Counter
	     ACCESS read-only
	     STATUS mandatory
	     DESCRIPTION
	         "The total number of RADIUS Access-Request messages retransmitted
	      since client start-up"
	     ::=  { radiusServerEntry 7 }

	 accessAccepts OBJECT-TYPE
	     SYNTAX Counter
	     ACCESS read-only
	     STATUS mandatory
	     DESCRIPTION
	         "The total number of RADIUS Access-Accept messages received
	          since client start-up"
	     ::=  { radiusServerEntry 8 }

	 accessChallenges OBJECT-TYPE
	     SYNTAX Counter
	     ACCESS read-only
	     STATUS mandatory
	     DESCRIPTION
	         "The total number of RADIUS Access-Challenge messages received
	          since client start-up"
	     ::=  { radiusServerEntry 9 }

	 malformedAccessResponses OBJECT-TYPE
	     SYNTAX Counter
	     ACCESS read-only
	     STATUS mandatory
	     DESCRIPTION
	         "The total number of malformed RADIUS Access-Response messages 
		  received since client start-up"
	     ::=  { radiusServerEntry 10 }

	 authenticationBadAuthenticators OBJECT-TYPE
	     SYNTAX Counter
	     ACCESS read-only
	     STATUS mandatory
	     DESCRIPTION
	         "The total number of RADIUS Access-Response messages 
		  containing invalid authenticators received since client 
		  start-up"
	     ::=  { radiusServerEntry 11 }

	accessRejects OBJECT-TYPE
	     SYNTAX Counter
	     ACCESS read-only
	     STATUS mandatory
	     DESCRIPTION
	         "The total number of RADIUS Access-Reject messages sent 
		  since client start-up"
	     ::=  { radiusServerEntry 12 }

	timeouts OBJECT-TYPE
	     SYNTAX Counter
	     ACCESS read-only
	     STATUS mandatory
	     DESCRIPTION
	         "The total number of timeouts since client startup"
	     ::=  { radiusServerEntry 13 }

	accountingRequests OBJECT-TYPE
	     SYNTAX Counter
	     ACCESS read-only
	     STATUS mandatory
	     DESCRIPTION
	         "The total number of RADIUS Accounting-Request messages sent
	          since client start-up"
	     ::=  { radiusServerEntry 14 }

	accountingRetransmissions OBJECT-TYPE
	     SYNTAX Counter
	     ACCESS read-only
	     STATUS mandatory
	     DESCRIPTION
	         "The total number of RADIUS Accounting-Request messages 
		  retransmitted since client start-up"
	     ::=  { radiusServerEntry 15 }

	accountingResponses OBJECT-TYPE
	     SYNTAX Counter
	     ACCESS read-only
	     STATUS mandatory
	     DESCRIPTION
	         "The total number of RADIUS Accounting-Response messages 
		  received since client start-up"
	     ::=  { radiusServerEntry 16 }

	accountingBadAuthenticators OBJECT-TYPE
	     SYNTAX Counter
	     ACCESS read-only
	     STATUS mandatory
	     DESCRIPTION
	         "The total number of RADIUS Accounting-Response messages which
	          contained invalid  authenticators received since client 
		  start-up"
	     ::=  { radiusServerEntry 17 }

	sharedSecret OBJECT-TYPE
	     SYNTAX DisplayString
	     ACCESS read-write
	     STATUS mandatory
	     DESCRIPTION
	         "The secret string which is shared between Server and Client"
	     ::=  { radiusServerEntry 18 }

	enabled OBJECT-TYPE
	     SYNTAX INTEGER   
	     {
		     enable(1),
		     disable(2),
		     delete(3)
		   }
	     ACCESS read-write
	     STATUS mandatory
	     DESCRIPTION
	         "Flag to tell whether the server is active or Inactive"
	     ::=  { radiusServerEntry 19 }

	responseTime OBJECT-TYPE
	     SYNTAX INTEGER
         {
	      one-sec(1),
	      two-secs(2),
	      three-secs(3),
	      four-secs(4),
	      five-secs(5),
	      six-secs(6),
	      seven-secs(7),
	      eight-secs(8),
	      nine-secs(9),
	      ten-secs(10)
	     }
	     ACCESS read-write
	     STATUS mandatory
	     DESCRIPTION
	         "The maximum time within which the server has to respond for a
	          request from the client"
	     ::=  { radiusServerEntry 20 }

	maximumRetransmission OBJECT-TYPE
	     SYNTAX INTEGER
	     {
	      one(1),
	      two(2),
	      three(3),
	      four(4)
	   	 }
	     ACCESS read-write
	     STATUS mandatory
	     DESCRIPTION
	         "The allowed maximum no. of trials to be tried by a client 
		  to get response from the server for a request"
	     ::=  { radiusServerEntry 21 }

	 -- conformance information

	 radiusClientMIBConformance OBJECT IDENTIFIER 
	     ::=  { radiusClientMIB 2 }

	 radiusClientMIBCompliances OBJECT IDENTIFIER
	     ::=  { radiusClientMIBConformance 1 }

	 radiusClientMIBGroups OBJECT IDENTIFIER
	     ::=  { radiusClientMIBConformance 2 }


	 -- PubStation ECP Information

        psShimECPRetransmissionCount OBJECT-TYPE
            SYNTAX INTEGER
            ACCESS read-write
            STATUS mandatory
            DESCRIPTION
                "The number of retransmissions when responses are not
                 received with the timeout period."
            ::= { publanShimECPSetup 1 }

        psShimECPRepeatResponseCount  OBJECT-TYPE
            SYNTAX INTEGER
            ACCESS read-write
            STATUS mandatory
            DESCRIPTION
                "The number of time the transmitted response can be
                 retransmitted."
            ::= { publanShimECPSetup 2 }

        psShimECPRetransmissionTimeout  OBJECT-TYPE
            SYNTAX INTEGER
            ACCESS read-write
            STATUS mandatory
            DESCRIPTION
                "The timeout interval for a response to be received."
            ::= { publanShimECPSetup 3 }

	 -- PubStation Trap Information

	 pubStationTrapVariables OBJECT IDENTIFIER
	     ::= { pubStationTraps 1 }

	 pubStationMacAddress OBJECT-TYPE
	     SYNTAX PhysAddress
	     ACCESS not-accessible
	     STATUS mandatory
	     DESCRIPTION
	       "The MAC address that is sent with the traps to
		identify which PubStation has the problem "
             ::= { pubStationTrapVariables 1 }

	 pubStationFlashRelatedTraps OBJECT IDENTIFIER
	     ::= { pubStationTraps 2 }

	 pubStationFlashNotPresent TRAP-TYPE
	     ENTERPRISE pubStationFlashRelatedTraps
	     DESCRIPTION
	       "This trap is sent when the FLASH is missing."
	     ::= 1

	 pubStationFlashEmpty TRAP-TYPE
	     ENTERPRISE pubStationFlashRelatedTraps
	     DESCRIPTION
	       "This trap is sent when the FLASH is empty."
	     ::= 2

	 pubStationFlashCorrupted TRAP-TYPE
	     ENTERPRISE pubStationFlashRelatedTraps
	     DESCRIPTION
	       "This trap is sent when the data in the FLASH is corrupted."
	     ::= 3

	 pubStationConfigurationRelatedTraps OBJECT IDENTIFIER
	     ::= { pubStationTraps 3 }

	 pubStationInvalidKey TRAP-TYPE
	     ENTERPRISE pubStationConfigurationRelatedTraps
	     DESCRIPTION
	       "This trap is sent when an invalid key is detected at the
		PubStation."
	     ::= 1

	 pubStationAPMNotConfigured TRAP-TYPE
	     ENTERPRISE pubStationConfigurationRelatedTraps
	     DESCRIPTION
	       "This trap is sent when the APM information is not 
		 configured in the PubStation."
	     ::= 2

	 pubStationIncompatibleWavelanCard TRAP-TYPE
	     ENTERPRISE pubStationConfigurationRelatedTraps
	     DESCRIPTION
	       "This trap is sent when the wavelan card plugged
		in the PubStation is not compatible with the firmware
		versions supported."
	     ::= 3

END
