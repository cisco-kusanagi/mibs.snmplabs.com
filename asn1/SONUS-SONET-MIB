--
-- This SMIv2 module has been generated by smidump 0.2-cvs. Do not edit.
--

SONUS-SONET-MIB DEFINITIONS ::= BEGIN

IMPORTS
    ifIndex
        FROM IF-MIB
    PerfCurrentCount, PerfIntervalCount
        FROM PerfHist-TC-MIB
    Integer32, MODULE-IDENTITY, NOTIFICATION-TYPE, OBJECT-TYPE
        FROM SNMPv2-SMI
    DisplayString, RowStatus, TruthValue
        FROM SNMPv2-TC
    sonusEventClass, sonusEventDescription, sonusEventLevel, 
    sonusPortIndex, sonusShelfIndex, sonusSlotIndex
        FROM SONUS-COMMON-MIB
    sonusCircuitMIBs
        FROM SONUS-SMI
    SonusAdminAction, SonusAdminState, SonusName, SonusServiceState, 
    SonusShelfIndex, SonusSlotIndex
        FROM SONUS-TC;

sonusSonetMIB MODULE-IDENTITY
    LAST-UPDATED    "200102030000Z"
    ORGANIZATION    
            "Sonus Networks, Inc."
    CONTACT-INFO    
            "   Customer Support    
             Sonus Networks, Inc,
             5 carlisle Road
             Westford, MA 01886
             USA
             
             Tel: 978-692-8999
             Fax: 978-392-9118
             E-mail: cs.snmp@sonusnet.com"
    DESCRIPTION     
            "The MIB Module for Sonus SONET/SDH extensions."
    ::= { sonusCircuitMIBs 3 }


sonusSonetObjects OBJECT IDENTIFIER
    ::= { sonusSonetMIB 1 }

sonusSonetPortAdmn OBJECT IDENTIFIER
    ::= { sonusSonetObjects 1 }

sonusSonetPortAdmnTable OBJECT-TYPE
    SYNTAX          SEQUENCE OF SonusSonetPortAdmnEntry
    MAX-ACCESS      not-accessible
    STATUS          current
    DESCRIPTION     
            "The Sonus SONET Port Admn Table."
    ::= { sonusSonetPortAdmn 1 }

sonusSonetPortAdmnEntry OBJECT-TYPE
    SYNTAX          SonusSonetPortAdmnEntry
    MAX-ACCESS      not-accessible
    STATUS          current
    DESCRIPTION     
            "An entry in the Sonus SONET Port Admn table."
    INDEX           { sonusSonetPortAdmnIfIndex }
    ::= { sonusSonetPortAdmnTable 1 }

SonusSonetPortAdmnEntry ::=
    SEQUENCE {
        sonusSonetPortAdmnIfIndex       Integer32,
        sonusSonetPortAdmnShelfIndex    SonusShelfIndex,
        sonusSonetPortAdmnSlotIndex     SonusSlotIndex,
        sonusSonetPortAdmnPortIndex     Integer32,
        sonusSonetPortAdmnRowStatus     RowStatus,
        sonusSonetPortAdmnName          SonusName,
        sonusSonetPortAdmnState         SonusAdminState,
        sonusSonetPortAdmnMode          SonusServiceState,
        sonusSonetPortAdmnAction        SonusAdminAction,
        sonusSonetPortAdmnTimeout       Integer32,
        sonusSonetPortAdmnStatAction    INTEGER,
        sonusSonetPortAdmnLaserState    INTEGER,
        sonusSonetPortAdmn24hTimeElapsed Integer32,
        sonusSonetPortAdmnOperStatus    INTEGER,
        sonusSonetPortAdmnDs3ModeOverride SonusAdminState,
        sonusSonetPortAdmnStsXmtScramble SonusAdminState,
        sonusSonetPortAdmnStsRcvDescramble  SonusAdminState,
        sonusSonetPortAdmnAtmXmtScramble SonusAdminState,
        sonusSonetPortAdmnAtmRcvDescramble  SonusAdminState
    }

sonusSonetPortAdmnIfIndex OBJECT-TYPE
    SYNTAX          Integer32
    MAX-ACCESS      not-accessible
    STATUS          current
    DESCRIPTION     
            "The ifIndex assigned to this port when it was created.
             This will not change until the port is deleted."
    ::= { sonusSonetPortAdmnEntry 1 }

sonusSonetPortAdmnShelfIndex OBJECT-TYPE
    SYNTAX          SonusShelfIndex
    MAX-ACCESS      read-write
    STATUS          current
    DESCRIPTION     
            "Shelf index for this table."
    ::= { sonusSonetPortAdmnEntry 2 }

sonusSonetPortAdmnSlotIndex OBJECT-TYPE
    SYNTAX          SonusSlotIndex
    MAX-ACCESS      read-write
    STATUS          current
    DESCRIPTION     
            "Slot index for this table."
    ::= { sonusSonetPortAdmnEntry 3 }

sonusSonetPortAdmnPortIndex OBJECT-TYPE
    SYNTAX          Integer32 (1..4)
    MAX-ACCESS      read-write
    STATUS          current
    DESCRIPTION     
            "OC3 port index for this table."
    ::= { sonusSonetPortAdmnEntry 4 }

sonusSonetPortAdmnRowStatus OBJECT-TYPE
    SYNTAX          RowStatus
    MAX-ACCESS      read-write
    STATUS          current
    DESCRIPTION     
            "This object is used to create, delete, or modify a row in this table."
    ::= { sonusSonetPortAdmnEntry 5 }

sonusSonetPortAdmnName OBJECT-TYPE
    SYNTAX          SonusName
    MAX-ACCESS      read-write
    STATUS          current
    DESCRIPTION     
            "Name of this STS3"
    ::= { sonusSonetPortAdmnEntry 6 }

sonusSonetPortAdmnState OBJECT-TYPE
    SYNTAX          SonusAdminState
    MAX-ACCESS      read-write
    STATUS          current
    DESCRIPTION     
            "State of STS3, Enabled/Disabled"
    DEFVAL          { disabled }
    ::= { sonusSonetPortAdmnEntry 7 }

sonusSonetPortAdmnMode OBJECT-TYPE
    SYNTAX          SonusServiceState
    MAX-ACCESS      read-write
    STATUS          current
    DESCRIPTION     
            "SONET port entries are created with a mode of outOfService. A
             SONET port which is outOfService has had all active calls
             terminated. A SOENT port must be outOfService in order to change
             its state to disabled."
    DEFVAL          { outOfService }
    ::= { sonusSonetPortAdmnEntry 8 }

sonusSonetPortAdmnAction OBJECT-TYPE
    SYNTAX          SonusAdminAction
    MAX-ACCESS      read-write
    STATUS          current
    DESCRIPTION     
            "The type of action to perform when a SONET port is taken out of 
             service. The SONET port can be dried up, or it can be forced
             out of service."
    DEFVAL          { dryUp }
    ::= { sonusSonetPortAdmnEntry 9 }

sonusSonetPortAdmnTimeout OBJECT-TYPE
    SYNTAX          Integer32 (0..1440)
    MAX-ACCESS      read-write
    STATUS          current
    DESCRIPTION     
            "The Dryup Timeout specifies the maximum amount of time to wait for
             all active calls to terminate on a SONET port before the port
             		 should be taken out-of-service."
    DEFVAL          { 5 }
    ::= { sonusSonetPortAdmnEntry 10 }

sonusSonetPortAdmnStatAction OBJECT-TYPE
    SYNTAX          INTEGER { init15MinuteNearEnd(1), 
                        init15MinuteFarEnd(2), init24HourNearEnd(4), 
                        init24HourFarEnd(8) }
    MAX-ACCESS      read-write
    STATUS          current
    DESCRIPTION     
            "Initialize Performance Monitoring Statistics. A PM initialization
             action initiates one request for the action. Requests to initialize
             more than one group of statistics can be accomplished by OR-ing the 
             appropriate bits (e.g., to initialize all 15 minute PM statistics, 
             set bits 1 and 2). Reading this variable always returns zero."
    ::= { sonusSonetPortAdmnEntry 11 }

sonusSonetPortAdmnLaserState OBJECT-TYPE
    SYNTAX          INTEGER { on(1), off(2) }
    MAX-ACCESS      read-write
    STATUS          current
    DESCRIPTION     
            "Controls whether the fiber-optic laser is On or Off."
    DEFVAL          { on }
    ::= { sonusSonetPortAdmnEntry 12 }

sonusSonetPortAdmn24hTimeElapsed OBJECT-TYPE
    SYNTAX          Integer32 (0..86400)
    MAX-ACCESS      read-only
    STATUS          current
    DESCRIPTION     
            "The number of seconds, including partial seconds,
             that have elapsed since the beginning of the current
             24 hour measurement period."
    ::= { sonusSonetPortAdmnEntry 13 }

sonusSonetPortAdmnOperStatus OBJECT-TYPE
    SYNTAX          INTEGER { enabledInService(1), 
                        enabledOutOfService(2), enabledDown(3), 
                        dryingUp(4), disabled(5), up(6), down(7) }
    MAX-ACCESS      read-only
    STATUS          current
    DESCRIPTION     
            "The actual status of the Sonet interface. Interface is 
             Up if it is administratively in service and there are no
             line failures or hardware failures. Interface is Down if
             it is administratively in service and there are line
             failures or hardware failures, or if it is administratively
             out of service. Interface is DryingUp if it is administratively
             out of service and is drying up (no new	calls, still carrying
             in-progress calls). OTHER VALUES ARE NO LONGER SUPPORTED"
    ::= { sonusSonetPortAdmnEntry 14 }

sonusSonetPortAdmnDs3ModeOverride OBJECT-TYPE
    SYNTAX          SonusAdminState
    MAX-ACCESS      read-write
    STATUS          current
    DESCRIPTION     
            "This flag controls whether the mode and state of the Paths
             carried in an OC3 are modified when the mode and state of
             the OC3 is modified. If this flag is set to Enabled, the Path
             state and mode are not changed when the OC3 mode and state
             are changed."
    DEFVAL          { disabled }
    ::= { sonusSonetPortAdmnEntry 15 }

sonusSonetPortAdmnStsXmtScramble OBJECT-TYPE
    SYNTAX          SonusAdminState
    MAX-ACCESS      read-write
    STATUS          current
    DESCRIPTION     
            "Controls whether the transmitted STS-N data stream is scrambled.
             If this flag is set to Enabled, the data is scrambled."
    DEFVAL          { enabled }
    ::= { sonusSonetPortAdmnEntry 16 }

sonusSonetPortAdmnStsRcvDescramble OBJECT-TYPE
    SYNTAX          SonusAdminState
    MAX-ACCESS      read-write
    STATUS          current
    DESCRIPTION     
            "Controls whether the received STS-N data stream is descrambled.
             If this flag is set to Enabled, the data is descrambled."
    DEFVAL          { enabled }
    ::= { sonusSonetPortAdmnEntry 17 }

sonusSonetPortAdmnAtmXmtScramble OBJECT-TYPE
    SYNTAX          SonusAdminState
    MAX-ACCESS      read-write
    STATUS          current
    DESCRIPTION     
            "Controls whether the transmitted ATM payload data is scrambled.
             If this flag is set to Enabled, the data is scrambled. This
             object only pertains to interfaces carrying ATM."
    DEFVAL          { enabled }
    ::= { sonusSonetPortAdmnEntry 18 }

sonusSonetPortAdmnAtmRcvDescramble OBJECT-TYPE
    SYNTAX          SonusAdminState
    MAX-ACCESS      read-write
    STATUS          current
    DESCRIPTION     
            "Controls whether the received ATM payload data is descrambled.
             If this flag is set to Enabled, the data is descrambled. This
             object only pertains to interfaces carrying ATM."
    DEFVAL          { enabled }
    ::= { sonusSonetPortAdmnEntry 19 }

sonusSonetSection OBJECT IDENTIFIER
    ::= { sonusSonetObjects 2 }

sonusSonetSectionThresholdTable OBJECT-TYPE
    SYNTAX          SEQUENCE OF SonusSonetSectionThresholdEntry
    MAX-ACCESS      not-accessible
    STATUS          current
    DESCRIPTION     
            "The Sonus SONET Section Threshold Table. This table adds objects
             to set the Performance Monitoring thresholds for generating a
             Threshold Crossing Alert."
    ::= { sonusSonetSection 1 }

sonusSonetSectionThresholdEntry OBJECT-TYPE
    SYNTAX          SonusSonetSectionThresholdEntry
    MAX-ACCESS      not-accessible
    STATUS          current
    DESCRIPTION     
            "An entry in the Sonus SONET Section Threshold table."
    INDEX           { sonusSonetSectionThresholdIfIndex }
    ::= { sonusSonetSectionThresholdTable 1 }

SonusSonetSectionThresholdEntry ::=
    SEQUENCE {
        sonusSonetSectionThresholdIfIndex Integer32,
        sonusSonetSectionThreshold15mCVs Integer32,
        sonusSonetSectionThreshold15mESs Integer32,
        sonusSonetSectionThreshold15mSESs Integer32,
        sonusSonetSectionThreshold15mSEFSs  Integer32,
        sonusSonetSectionThreshold24hCVs Integer32,
        sonusSonetSectionThreshold24hESs Integer32,
        sonusSonetSectionThreshold24hSESs Integer32,
        sonusSonetSectionThreshold24hSEFSs  Integer32
    }

sonusSonetSectionThresholdIfIndex OBJECT-TYPE
    SYNTAX          Integer32
    MAX-ACCESS      not-accessible
    STATUS          current
    DESCRIPTION     
            "The ifIndex assigned to this port when it was created.
             This will not change until the port is deleted."
    ::= { sonusSonetSectionThresholdEntry 1 }

sonusSonetSectionThreshold15mCVs OBJECT-TYPE
    SYNTAX          Integer32 (0..16383)
    MAX-ACCESS      read-write
    STATUS          current
    DESCRIPTION     
            "Threshold for 15 minute interval Section layer Coding Violations."
    ::= { sonusSonetSectionThresholdEntry 2 }

sonusSonetSectionThreshold15mESs OBJECT-TYPE
    SYNTAX          Integer32 (0..16383)
    MAX-ACCESS      read-write
    STATUS          current
    DESCRIPTION     
            "Threshold for 15 minute interval Section layer Errored Seconds."
    ::= { sonusSonetSectionThresholdEntry 3 }

sonusSonetSectionThreshold15mSESs OBJECT-TYPE
    SYNTAX          Integer32 (0..900)
    MAX-ACCESS      read-write
    STATUS          current
    DESCRIPTION     
            "Threshold for 15 minute interval Section layer Severely Errored
             Seconds."
    ::= { sonusSonetSectionThresholdEntry 4 }

sonusSonetSectionThreshold15mSEFSs OBJECT-TYPE
    SYNTAX          Integer32 (0..900)
    MAX-ACCESS      read-write
    STATUS          current
    DESCRIPTION     
            "Threshold for 15 minute interval Section layer Severely Errored
             Frame Seconds."
    ::= { sonusSonetSectionThresholdEntry 5 }

sonusSonetSectionThreshold24hCVs OBJECT-TYPE
    SYNTAX          Integer32 (0..1048575)
    MAX-ACCESS      read-write
    STATUS          current
    DESCRIPTION     
            "Threshold for 24 hour interval Section layer Coding Violations."
    ::= { sonusSonetSectionThresholdEntry 6 }

sonusSonetSectionThreshold24hESs OBJECT-TYPE
    SYNTAX          Integer32 (0..65535)
    MAX-ACCESS      read-write
    STATUS          current
    DESCRIPTION     
            "Threshold for 24 hour interval Section layer Errored Seconds."
    ::= { sonusSonetSectionThresholdEntry 7 }

sonusSonetSectionThreshold24hSESs OBJECT-TYPE
    SYNTAX          Integer32 (0..65535)
    MAX-ACCESS      read-write
    STATUS          current
    DESCRIPTION     
            "Threshold for 24 hour interval Section layer Severely Errored
             Seconds."
    ::= { sonusSonetSectionThresholdEntry 8 }

sonusSonetSectionThreshold24hSEFSs OBJECT-TYPE
    SYNTAX          Integer32 (0..65535)
    MAX-ACCESS      read-write
    STATUS          current
    DESCRIPTION     
            "Threshold for 24 hour interval Section layer Severely Errored
             Frame Seconds."
    ::= { sonusSonetSectionThresholdEntry 9 }

sonusSonetSectionCurrentTable OBJECT-TYPE
    SYNTAX          SEQUENCE OF SonusSonetSectionCurrentEntry
    MAX-ACCESS      not-accessible
    STATUS          current
    DESCRIPTION     
            "The Sonus SONET Section Current table."
    ::= { sonusSonetSection 2 }

sonusSonetSectionCurrentEntry OBJECT-TYPE
    SYNTAX          SonusSonetSectionCurrentEntry
    MAX-ACCESS      not-accessible
    STATUS          current
    DESCRIPTION     
            "An entry in the Sonus SONET Section Current table."
    INDEX           { sonusSonetSectionCurrentIfIndex }
    ::= { sonusSonetSectionCurrentTable 1 }

SonusSonetSectionCurrentEntry ::=
    SEQUENCE {
        sonusSonetSectionCurrentIfIndex Integer32,
        sonusSonetSectionCurrentStatus  Integer32,
        sonusSonetSectionCurrentESs     PerfCurrentCount,
        sonusSonetSectionCurrentSESs    PerfCurrentCount,
        sonusSonetSectionCurrentSEFSs   PerfCurrentCount,
        sonusSonetSectionCurrentCVs     PerfCurrentCount
    }

sonusSonetSectionCurrentIfIndex OBJECT-TYPE
    SYNTAX          Integer32
    MAX-ACCESS      not-accessible
    STATUS          current
    DESCRIPTION     
            "The ifIndex assigned to this port when it was created.
             This will not change until the port is deleted."
    ::= { sonusSonetSectionCurrentEntry 1 }

sonusSonetSectionCurrentStatus OBJECT-TYPE
    SYNTAX          Integer32 (1..6)
    MAX-ACCESS      read-only
    STATUS          current
    DESCRIPTION     
            "This variable indicates the status of the interface. It is
             a bit map represented as a sum, therefore, it can represent
             multiple defects simultaneously. The sonetSectionNoDefect
             should be set if and only if no other flag is set.
             
             The various bit positions are:
             1   sonetSectionNoDefect
             2   sonetSectionLOS
             4   sonetSectionLOF"
    ::= { sonusSonetSectionCurrentEntry 2 }

sonusSonetSectionCurrentESs OBJECT-TYPE
    SYNTAX          PerfCurrentCount
    MAX-ACCESS      read-only
    STATUS          current
    DESCRIPTION     
            "The counter associated with the number of Errored Seconds
             encountered by a SONET/SDH Section in the current 24 hour
             interval."
    ::= { sonusSonetSectionCurrentEntry 3 }

sonusSonetSectionCurrentSESs OBJECT-TYPE
    SYNTAX          PerfCurrentCount
    MAX-ACCESS      read-only
    STATUS          current
    DESCRIPTION     
            "The counter associated with the number of Severely Errored
             Seconds encountered by a SONET/SDH Section in the current 
             24 hour interval."
    ::= { sonusSonetSectionCurrentEntry 4 }

sonusSonetSectionCurrentSEFSs OBJECT-TYPE
    SYNTAX          PerfCurrentCount
    MAX-ACCESS      read-only
    STATUS          current
    DESCRIPTION     
            "The counter associated with the number of Severely Errored
             Framing Seconds encountered by a SONET/SDH Section in the
             current 24 hour interval."
    ::= { sonusSonetSectionCurrentEntry 5 }

sonusSonetSectionCurrentCVs OBJECT-TYPE
    SYNTAX          PerfCurrentCount
    MAX-ACCESS      read-only
    STATUS          current
    DESCRIPTION     
            "The counter associated with the number of Coding Violations
             encountered by a SONET/SDH Section in the current 24 hour
             	 interval."
    ::= { sonusSonetSectionCurrentEntry 6 }

sonusSonetSectionIntervalTable OBJECT-TYPE
    SYNTAX          SEQUENCE OF SonusSonetSectionIntervalEntry
    MAX-ACCESS      not-accessible
    STATUS          current
    DESCRIPTION     
            "The Sonus SONET Section Interval table."
    ::= { sonusSonetSection 3 }

sonusSonetSectionIntervalEntry OBJECT-TYPE
    SYNTAX          SonusSonetSectionIntervalEntry
    MAX-ACCESS      not-accessible
    STATUS          current
    DESCRIPTION     
            "An entry in the Sonus SONET Section Interval table."
    INDEX           { sonusSonetSectionIntervalIfIndex, 
                      sonusSonetSectionIntervalNumber }
    ::= { sonusSonetSectionIntervalTable 1 }

SonusSonetSectionIntervalEntry ::=
    SEQUENCE {
        sonusSonetSectionIntervalIfIndex Integer32,
        sonusSonetSectionIntervalNumber Integer32,
        sonusSonetSectionIntervalESs    PerfCurrentCount,
        sonusSonetSectionIntervalSESs   PerfCurrentCount,
        sonusSonetSectionIntervalSEFSs  PerfCurrentCount,
        sonusSonetSectionIntervalCVs    PerfCurrentCount,
        sonusSonetSectionIntervalValidData  TruthValue
    }

sonusSonetSectionIntervalIfIndex OBJECT-TYPE
    SYNTAX          Integer32
    MAX-ACCESS      not-accessible
    STATUS          current
    DESCRIPTION     
            "The ifIndex assigned to this port when it was created.
             This will not change until the port is deleted."
    ::= { sonusSonetSectionIntervalEntry 1 }

sonusSonetSectionIntervalNumber OBJECT-TYPE
    SYNTAX          Integer32 (1)
    MAX-ACCESS      not-accessible
    STATUS          current
    DESCRIPTION     
            "The number 1 identifies the most recently completed 24 hour
             interval. In the future if more 24 hour intervals are supported,
             the interval identified by N is the interval immediately
             preceding the one identified by N-1."
    ::= { sonusSonetSectionIntervalEntry 2 }

sonusSonetSectionIntervalESs OBJECT-TYPE
    SYNTAX          PerfCurrentCount
    MAX-ACCESS      read-only
    STATUS          current
    DESCRIPTION     
            "The counter associated with the number of Errored Seconds
             encountered by a SONET/SDH Section in the previous 24 hour
             interval."
    ::= { sonusSonetSectionIntervalEntry 3 }

sonusSonetSectionIntervalSESs OBJECT-TYPE
    SYNTAX          PerfCurrentCount
    MAX-ACCESS      read-only
    STATUS          current
    DESCRIPTION     
            "The counter associated with the number of Severely Errored
             Seconds encountered by a SONET/SDH Section in the previous 
             24 hour interval."
    ::= { sonusSonetSectionIntervalEntry 4 }

sonusSonetSectionIntervalSEFSs OBJECT-TYPE
    SYNTAX          PerfCurrentCount
    MAX-ACCESS      read-only
    STATUS          current
    DESCRIPTION     
            "The counter associated with the number of Severely Errored
             Framing Seconds encountered by a SONET/SDH Section in the
             previous 24 hour interval."
    ::= { sonusSonetSectionIntervalEntry 5 }

sonusSonetSectionIntervalCVs OBJECT-TYPE
    SYNTAX          PerfCurrentCount
    MAX-ACCESS      read-only
    STATUS          current
    DESCRIPTION     
            "The counter associated with the number of Coding Violations
             encountered by a SONET/SDH Section in the previous 24 hour
             	 interval."
    ::= { sonusSonetSectionIntervalEntry 6 }

sonusSonetSectionIntervalValidData OBJECT-TYPE
    SYNTAX          TruthValue
    MAX-ACCESS      read-only
    STATUS          current
    DESCRIPTION     
            "This variable indicates if the data for this interval is valid."
    ::= { sonusSonetSectionIntervalEntry 7 }

sonusSonetLine OBJECT IDENTIFIER
    ::= { sonusSonetObjects 3 }

sonusSonetLineThresholdTable OBJECT-TYPE
    SYNTAX          SEQUENCE OF SonusSonetLineThresholdEntry
    MAX-ACCESS      not-accessible
    STATUS          current
    DESCRIPTION     
            "The Sonus SONET Line Threshold Table. This table adds objects
             to set the Performance Monitoring thresholds for generating a
             Threshold Crossing Alert."
    ::= { sonusSonetLine 1 }

sonusSonetLineThresholdEntry OBJECT-TYPE
    SYNTAX          SonusSonetLineThresholdEntry
    MAX-ACCESS      not-accessible
    STATUS          current
    DESCRIPTION     
            "An entry in the Sonus SONET Line Threshold table."
    INDEX           { sonusSonetLineThresholdIfIndex }
    ::= { sonusSonetLineThresholdTable 1 }

SonusSonetLineThresholdEntry ::=
    SEQUENCE {
        sonusSonetLineThresholdIfIndex  Integer32,
        sonusSonetLineThreshold15mCVs   Integer32,
        sonusSonetLineThreshold15mESs   Integer32,
        sonusSonetLineThreshold15mSESs  Integer32,
        sonusSonetLineThreshold15mUASs  Integer32,
        sonusSonetLineThreshold24hCVs   Integer32,
        sonusSonetLineThreshold24hESs   Integer32,
        sonusSonetLineThreshold24hSESs  Integer32,
        sonusSonetLineThreshold24hUASs  Integer32
    }

sonusSonetLineThresholdIfIndex OBJECT-TYPE
    SYNTAX          Integer32
    MAX-ACCESS      not-accessible
    STATUS          current
    DESCRIPTION     
            "The ifIndex assigned to this port when it was created.
             This will not change until the port is deleted."
    ::= { sonusSonetLineThresholdEntry 1 }

sonusSonetLineThreshold15mCVs OBJECT-TYPE
    SYNTAX          Integer32 (0..16383)
    MAX-ACCESS      read-write
    STATUS          current
    DESCRIPTION     
            "Threshold for 15 minute interval Line layer Coding Violations."
    ::= { sonusSonetLineThresholdEntry 2 }

sonusSonetLineThreshold15mESs OBJECT-TYPE
    SYNTAX          Integer32 (0..900)
    MAX-ACCESS      read-write
    STATUS          current
    DESCRIPTION     
            "Threshold for 15 minute interval Line layer Errored Seconds."
    ::= { sonusSonetLineThresholdEntry 3 }

sonusSonetLineThreshold15mSESs OBJECT-TYPE
    SYNTAX          Integer32 (0..900)
    MAX-ACCESS      read-write
    STATUS          current
    DESCRIPTION     
            "Threshold for 15 minute interval Line layer Severely Errored
             Seconds."
    ::= { sonusSonetLineThresholdEntry 4 }

sonusSonetLineThreshold15mUASs OBJECT-TYPE
    SYNTAX          Integer32 (0..900)
    MAX-ACCESS      read-write
    STATUS          current
    DESCRIPTION     
            "Threshold for 15 minute interval Line layer Unavailable Seconds."
    ::= { sonusSonetLineThresholdEntry 5 }

sonusSonetLineThreshold24hCVs OBJECT-TYPE
    SYNTAX          Integer32 (0..1048575)
    MAX-ACCESS      read-write
    STATUS          current
    DESCRIPTION     
            "Threshold for 24 hour interval Line layer Coding Violations."
    ::= { sonusSonetLineThresholdEntry 6 }

sonusSonetLineThreshold24hESs OBJECT-TYPE
    SYNTAX          Integer32 (0..65535)
    MAX-ACCESS      read-write
    STATUS          current
    DESCRIPTION     
            "Threshold for 24 hour interval Line layer Errored Seconds."
    ::= { sonusSonetLineThresholdEntry 7 }

sonusSonetLineThreshold24hSESs OBJECT-TYPE
    SYNTAX          Integer32 (0..65535)
    MAX-ACCESS      read-write
    STATUS          current
    DESCRIPTION     
            "Threshold for 24 hour interval Line layer Severely Errored
             Seconds."
    ::= { sonusSonetLineThresholdEntry 8 }

sonusSonetLineThreshold24hUASs OBJECT-TYPE
    SYNTAX          Integer32 (0..65535)
    MAX-ACCESS      read-write
    STATUS          current
    DESCRIPTION     
            "Threshold for 24 hour interval Line layer Unavailable Seconds."
    ::= { sonusSonetLineThresholdEntry 9 }

sonusSonetLineCurrentTable OBJECT-TYPE
    SYNTAX          SEQUENCE OF SonusSonetLineCurrentEntry
    MAX-ACCESS      not-accessible
    STATUS          current
    DESCRIPTION     
            "The Sonus SONET Line Current table."
    ::= { sonusSonetLine 2 }

sonusSonetLineCurrentEntry OBJECT-TYPE
    SYNTAX          SonusSonetLineCurrentEntry
    MAX-ACCESS      not-accessible
    STATUS          current
    DESCRIPTION     
            "An entry in the Sonus SONET Line Current table."
    INDEX           { sonusSonetLineCurrentIfIndex }
    ::= { sonusSonetLineCurrentTable 1 }

SonusSonetLineCurrentEntry ::=
    SEQUENCE {
        sonusSonetLineCurrentIfIndex    Integer32,
        sonusSonetLineCurrentStatus     Integer32,
        sonusSonetLineCurrentESs        PerfCurrentCount,
        sonusSonetLineCurrentSESs       PerfCurrentCount,
        sonusSonetLineCurrentUASs       PerfCurrentCount,
        sonusSonetLineCurrentCVs        PerfCurrentCount,
        sonusSonetLineCurrentFCs        PerfCurrentCount
    }

sonusSonetLineCurrentIfIndex OBJECT-TYPE
    SYNTAX          Integer32
    MAX-ACCESS      not-accessible
    STATUS          current
    DESCRIPTION     
            "The ifIndex assigned to this port when it was created.
             This will not change until the port is deleted."
    ::= { sonusSonetLineCurrentEntry 1 }

sonusSonetLineCurrentStatus OBJECT-TYPE
    SYNTAX          Integer32 (1..6)
    MAX-ACCESS      read-only
    STATUS          current
    DESCRIPTION     
            "This variable indicates the status of the interface. It is
             a bit map represented as a sum, therefore, it can represent
             multiple defects simultaneously. The sonetLineNoDefect
             should be set if and only if no other flag is set.
             
             The various bit positions are:
             1   sonetSectionNoDefect
             2   sonetLineAIS
             4   sonetLineRDI"
    ::= { sonusSonetLineCurrentEntry 2 }

sonusSonetLineCurrentESs OBJECT-TYPE
    SYNTAX          PerfCurrentCount
    MAX-ACCESS      read-only
    STATUS          current
    DESCRIPTION     
            "The counter associated with the number of Errored Seconds
             encountered by a SONET/SDH Line in the current 24 hour
             interval."
    ::= { sonusSonetLineCurrentEntry 3 }

sonusSonetLineCurrentSESs OBJECT-TYPE
    SYNTAX          PerfCurrentCount
    MAX-ACCESS      read-only
    STATUS          current
    DESCRIPTION     
            "The counter associated with the number of Severely Errored
             Seconds encountered by a SONET/SDH Line in the current 
             24 hour interval."
    ::= { sonusSonetLineCurrentEntry 4 }

sonusSonetLineCurrentUASs OBJECT-TYPE
    SYNTAX          PerfCurrentCount
    MAX-ACCESS      read-only
    STATUS          current
    DESCRIPTION     
            "The counter associated with the number of Unavailable
             Seconds encountered by a SONET/SDH Line in the current
             24 hour interval."
    ::= { sonusSonetLineCurrentEntry 5 }

sonusSonetLineCurrentCVs OBJECT-TYPE
    SYNTAX          PerfCurrentCount
    MAX-ACCESS      read-only
    STATUS          current
    DESCRIPTION     
            "The counter associated with the number of Coding Violations
             encountered by a SONET/SDH Line in the current 24 hour
             	 interval."
    ::= { sonusSonetLineCurrentEntry 6 }

sonusSonetLineCurrentFCs OBJECT-TYPE
    SYNTAX          PerfCurrentCount
    MAX-ACCESS      read-only
    STATUS          current
    DESCRIPTION     
            "The counter associated with the number of Failures encountered
             by a SONET/SDH Line in the current 24 hour interval."
    ::= { sonusSonetLineCurrentEntry 7 }

sonusSonetLineIntervalTable OBJECT-TYPE
    SYNTAX          SEQUENCE OF SonusSonetLineIntervalEntry
    MAX-ACCESS      not-accessible
    STATUS          current
    DESCRIPTION     
            "The Sonus SONET Line Interval table."
    ::= { sonusSonetLine 3 }

sonusSonetLineIntervalEntry OBJECT-TYPE
    SYNTAX          SonusSonetLineIntervalEntry
    MAX-ACCESS      not-accessible
    STATUS          current
    DESCRIPTION     
            "An entry in the Sonus SONET Line Interval table."
    INDEX           { sonusSonetLineIntervalIfIndex, 
                      sonusSonetLineIntervalNumber }
    ::= { sonusSonetLineIntervalTable 1 }

SonusSonetLineIntervalEntry ::=
    SEQUENCE {
        sonusSonetLineIntervalIfIndex   Integer32,
        sonusSonetLineIntervalNumber    Integer32,
        sonusSonetLineIntervalESs       PerfIntervalCount,
        sonusSonetLineIntervalSESs      PerfIntervalCount,
        sonusSonetLineIntervalUASs      PerfIntervalCount,
        sonusSonetLineIntervalCVs       PerfIntervalCount,
        sonusSonetLineIntervalFCs       PerfIntervalCount,
        sonusSonetLineIntervalValidData TruthValue
    }

sonusSonetLineIntervalIfIndex OBJECT-TYPE
    SYNTAX          Integer32
    MAX-ACCESS      not-accessible
    STATUS          current
    DESCRIPTION     
            "The ifIndex assigned to this port when it was created.
             This will not change until the port is deleted."
    ::= { sonusSonetLineIntervalEntry 1 }

sonusSonetLineIntervalNumber OBJECT-TYPE
    SYNTAX          Integer32 (1)
    MAX-ACCESS      not-accessible
    STATUS          current
    DESCRIPTION     
            "The number 1 identifies the most recently completed 24 hour
             interval. In the future if more 24 hour intervals are supported,
             the interval identified by N is the interval immediately
             preceding the one identified by N-1."
    ::= { sonusSonetLineIntervalEntry 2 }

sonusSonetLineIntervalESs OBJECT-TYPE
    SYNTAX          PerfIntervalCount
    MAX-ACCESS      read-only
    STATUS          current
    DESCRIPTION     
            "The counter associated with the number of Errored Seconds
             encountered by a SONET/SDH Line in the previous 24 hour
             interval."
    ::= { sonusSonetLineIntervalEntry 3 }

sonusSonetLineIntervalSESs OBJECT-TYPE
    SYNTAX          PerfIntervalCount
    MAX-ACCESS      read-only
    STATUS          current
    DESCRIPTION     
            "The counter associated with the number of Severely Errored
             Seconds encountered by a SONET/SDH Line in the previous 
             24 hour interval."
    ::= { sonusSonetLineIntervalEntry 4 }

sonusSonetLineIntervalUASs OBJECT-TYPE
    SYNTAX          PerfIntervalCount
    MAX-ACCESS      read-only
    STATUS          current
    DESCRIPTION     
            "The counter associated with the number of Unavailable
             Seconds encountered by a SONET/SDH Line in the previous
             24 hour interval."
    ::= { sonusSonetLineIntervalEntry 5 }

sonusSonetLineIntervalCVs OBJECT-TYPE
    SYNTAX          PerfIntervalCount
    MAX-ACCESS      read-only
    STATUS          current
    DESCRIPTION     
            "The counter associated with the number of Coding Violations
             encountered by a SONET/SDH Line in the previous 24 hour
             	 interval."
    ::= { sonusSonetLineIntervalEntry 6 }

sonusSonetLineIntervalFCs OBJECT-TYPE
    SYNTAX          PerfIntervalCount
    MAX-ACCESS      read-only
    STATUS          current
    DESCRIPTION     
            "The counter associated with the number of Failures encountered
             by a SONET/SDH Line in the previous 24 hour interval."
    ::= { sonusSonetLineIntervalEntry 7 }

sonusSonetLineIntervalValidData OBJECT-TYPE
    SYNTAX          TruthValue
    MAX-ACCESS      read-only
    STATUS          current
    DESCRIPTION     
            "This variable indicates if the data for this interval is valid."
    ::= { sonusSonetLineIntervalEntry 8 }

sonusSonetFarEndLineCurrentTable OBJECT-TYPE
    SYNTAX          SEQUENCE OF SonusSonetFarEndLineCurrentEntry
    MAX-ACCESS      not-accessible
    STATUS          current
    DESCRIPTION     
            "The Sonus SONET Far End Line Current table."
    ::= { sonusSonetLine 4 }

sonusSonetFarEndLineCurrentEntry OBJECT-TYPE
    SYNTAX          SonusSonetFarEndLineCurrentEntry
    MAX-ACCESS      not-accessible
    STATUS          current
    DESCRIPTION     
            "An entry in the Sonus SONET Far End Line Current table."
    INDEX           { sonusSonetFarEndLineCurrentIfIndex }
    ::= { sonusSonetFarEndLineCurrentTable 1 }

SonusSonetFarEndLineCurrentEntry ::=
    SEQUENCE {
        sonusSonetFarEndLineCurrentIfIndex  Integer32,
        sonusSonetFarEndLineCurrentESs  PerfCurrentCount,
        sonusSonetFarEndLineCurrentSESs PerfCurrentCount,
        sonusSonetFarEndLineCurrentUASs PerfCurrentCount,
        sonusSonetFarEndLineCurrentCVs  PerfCurrentCount,
        sonusSonetFarEndLineCurrentFCs  PerfCurrentCount
    }

sonusSonetFarEndLineCurrentIfIndex OBJECT-TYPE
    SYNTAX          Integer32
    MAX-ACCESS      not-accessible
    STATUS          current
    DESCRIPTION     
            "The ifIndex assigned to this port when it was created.
             This will not change until the port is deleted."
    ::= { sonusSonetFarEndLineCurrentEntry 1 }

sonusSonetFarEndLineCurrentESs OBJECT-TYPE
    SYNTAX          PerfCurrentCount
    MAX-ACCESS      read-only
    STATUS          current
    DESCRIPTION     
            "The counter associated with the number of Far End Errored
             Seconds encountered by a SONET/SDH Line in the current
             24 hour interval."
    ::= { sonusSonetFarEndLineCurrentEntry 2 }

sonusSonetFarEndLineCurrentSESs OBJECT-TYPE
    SYNTAX          PerfCurrentCount
    MAX-ACCESS      read-only
    STATUS          current
    DESCRIPTION     
            "The counter associated with the number of Far End Severely
             Errored Seconds encountered by a SONET/SDH Line in the
             current 24 hour interval."
    ::= { sonusSonetFarEndLineCurrentEntry 3 }

sonusSonetFarEndLineCurrentUASs OBJECT-TYPE
    SYNTAX          PerfCurrentCount
    MAX-ACCESS      read-only
    STATUS          current
    DESCRIPTION     
            "The counter associated with the number of Far End 
             Unavailable Seconds encountered by a SONET/SDH Line in the
             current 24 hour interval."
    ::= { sonusSonetFarEndLineCurrentEntry 4 }

sonusSonetFarEndLineCurrentCVs OBJECT-TYPE
    SYNTAX          PerfCurrentCount
    MAX-ACCESS      read-only
    STATUS          current
    DESCRIPTION     
            "The counter associated with the number of Far End Coding
             Violations encountered by a SONET/SDH Line in the current
             	 24 hour interval."
    ::= { sonusSonetFarEndLineCurrentEntry 5 }

sonusSonetFarEndLineCurrentFCs OBJECT-TYPE
    SYNTAX          PerfCurrentCount
    MAX-ACCESS      read-only
    STATUS          current
    DESCRIPTION     
            "The counter associated with the number of Far End Failures
             encountered by a SONET/SDH Line in the current 24 hour
             interval."
    ::= { sonusSonetFarEndLineCurrentEntry 6 }

sonusSonetFarEndLineIntervalTable OBJECT-TYPE
    SYNTAX          SEQUENCE OF SonusSonetFarEndLineIntervalEntry
    MAX-ACCESS      not-accessible
    STATUS          current
    DESCRIPTION     
            "The Sonus SONET Far End Line Interval table."
    ::= { sonusSonetLine 5 }

sonusSonetFarEndLineIntervalEntry OBJECT-TYPE
    SYNTAX          SonusSonetFarEndLineIntervalEntry
    MAX-ACCESS      not-accessible
    STATUS          current
    DESCRIPTION     
            "An entry in the Sonus SONET Far End Line Interval table."
    INDEX           { sonusSonetFarEndLineIntervalIfIndex, 
                      sonusSonetFarEndLineIntervalNumber }
    ::= { sonusSonetFarEndLineIntervalTable 1 }

SonusSonetFarEndLineIntervalEntry ::=
    SEQUENCE {
        sonusSonetFarEndLineIntervalIfIndex   Integer32,
        sonusSonetFarEndLineIntervalNumber  Integer32,
        sonusSonetFarEndLineIntervalESs PerfIntervalCount,
        sonusSonetFarEndLineIntervalSESs PerfIntervalCount,
        sonusSonetFarEndLineIntervalUASs PerfIntervalCount,
        sonusSonetFarEndLineIntervalCVs PerfIntervalCount,
        sonusSonetFarEndLineIntervalFCs PerfIntervalCount,
        sonusSonetFarEndLineIntervalValidData     TruthValue
    }

sonusSonetFarEndLineIntervalIfIndex OBJECT-TYPE
    SYNTAX          Integer32
    MAX-ACCESS      not-accessible
    STATUS          current
    DESCRIPTION     
            "The ifIndex assigned to this port when it was created.
             This will not change until the port is deleted."
    ::= { sonusSonetFarEndLineIntervalEntry 1 }

sonusSonetFarEndLineIntervalNumber OBJECT-TYPE
    SYNTAX          Integer32 (1)
    MAX-ACCESS      not-accessible
    STATUS          current
    DESCRIPTION     
            "The number 1 identifies the most recently completed 24 hour
             interval. In the future if more 24 hour intervals are supported,
             the interval identified by N is the interval immediately
             preceding the one identified by N-1."
    ::= { sonusSonetFarEndLineIntervalEntry 2 }

sonusSonetFarEndLineIntervalESs OBJECT-TYPE
    SYNTAX          PerfIntervalCount
    MAX-ACCESS      read-only
    STATUS          current
    DESCRIPTION     
            "The counter associated with the number of Far End Errored
             Seconds encountered by a SONET/SDH Line in the current
             24 hour interval."
    ::= { sonusSonetFarEndLineIntervalEntry 3 }

sonusSonetFarEndLineIntervalSESs OBJECT-TYPE
    SYNTAX          PerfIntervalCount
    MAX-ACCESS      read-only
    STATUS          current
    DESCRIPTION     
            "The counter associated with the number of Far End Severely
             Errored Seconds encountered by a SONET/SDH Line in the
             current 24 hour interval."
    ::= { sonusSonetFarEndLineIntervalEntry 4 }

sonusSonetFarEndLineIntervalUASs OBJECT-TYPE
    SYNTAX          PerfIntervalCount
    MAX-ACCESS      read-only
    STATUS          current
    DESCRIPTION     
            "The counter associated with the number of Far End 
             Unavailable Seconds encountered by a SONET/SDH Line in the
             current 24 hour interval."
    ::= { sonusSonetFarEndLineIntervalEntry 5 }

sonusSonetFarEndLineIntervalCVs OBJECT-TYPE
    SYNTAX          PerfIntervalCount
    MAX-ACCESS      read-only
    STATUS          current
    DESCRIPTION     
            "The counter associated with the number of Far End Coding
             Violations encountered by a SONET/SDH Line in the current
             	 24 hour interval."
    ::= { sonusSonetFarEndLineIntervalEntry 6 }

sonusSonetFarEndLineIntervalFCs OBJECT-TYPE
    SYNTAX          PerfIntervalCount
    MAX-ACCESS      read-only
    STATUS          current
    DESCRIPTION     
            "The counter associated with the number of Far End Failures
             encountered by a SONET/SDH Line in the current 24 hour
             interval."
    ::= { sonusSonetFarEndLineIntervalEntry 7 }

sonusSonetFarEndLineIntervalValidData OBJECT-TYPE
    SYNTAX          TruthValue
    MAX-ACCESS      read-only
    STATUS          current
    DESCRIPTION     
            "This variable indicates if the data for this interval is valid."
    ::= { sonusSonetFarEndLineIntervalEntry 8 }

sonusSonetLineFailureCurrentTable OBJECT-TYPE
    SYNTAX          SEQUENCE OF SonusSonetLineFailureCurrentEntry
    MAX-ACCESS      not-accessible
    STATUS          current
    DESCRIPTION     
            "The Sonus SONET Line Failure Current table."
    ::= { sonusSonetLine 6 }

sonusSonetLineFailureCurrentEntry OBJECT-TYPE
    SYNTAX          SonusSonetLineFailureCurrentEntry
    MAX-ACCESS      not-accessible
    STATUS          current
    DESCRIPTION     
            "An entry in the Sonus SONET Line Failure Current table."
    INDEX           { sonusSonetLineFailureCurrentIfIndex }
    ::= { sonusSonetLineFailureCurrentTable 1 }

SonusSonetLineFailureCurrentEntry ::=
    SEQUENCE {
        sonusSonetLineFailureCurrentIfIndex   Integer32,
        sonusSonetLineFailureCurrentFCs PerfCurrentCount
    }

sonusSonetLineFailureCurrentIfIndex OBJECT-TYPE
    SYNTAX          Integer32
    MAX-ACCESS      not-accessible
    STATUS          current
    DESCRIPTION     
            "The ifIndex assigned to this port when it was created.
             This will not change until the port is deleted."
    ::= { sonusSonetLineFailureCurrentEntry 1 }

sonusSonetLineFailureCurrentFCs OBJECT-TYPE
    SYNTAX          PerfCurrentCount
    MAX-ACCESS      read-only
    STATUS          current
    DESCRIPTION     
            "The counter associated with the number of Failures encountered
             by a SONET/SDH Line in the current 15 minute interval."
    ::= { sonusSonetLineFailureCurrentEntry 2 }

sonusSonetLineFailureIntervalTable OBJECT-TYPE
    SYNTAX          SEQUENCE OF SonusSonetLineFailureIntervalEntry
    MAX-ACCESS      not-accessible
    STATUS          current
    DESCRIPTION     
            "The Sonus SONET Line Failure Interval table."
    ::= { sonusSonetLine 7 }

sonusSonetLineFailureIntervalEntry OBJECT-TYPE
    SYNTAX          SonusSonetLineFailureIntervalEntry
    MAX-ACCESS      not-accessible
    STATUS          current
    DESCRIPTION     
            "An entry in the Sonus SONET Line Failure Interval table."
    INDEX           { sonusSonetLineFailureIntervalIfIndex, 
                      sonusSonetLineFailureIntervalNumber }
    ::= { sonusSonetLineFailureIntervalTable 1 }

SonusSonetLineFailureIntervalEntry ::=
    SEQUENCE {
        sonusSonetLineFailureIntervalIfIndex    Integer32,
        sonusSonetLineFailureIntervalNumber   Integer32,
        sonusSonetLineFailureIntervalFCs PerfCurrentCount
    }

sonusSonetLineFailureIntervalIfIndex OBJECT-TYPE
    SYNTAX          Integer32
    MAX-ACCESS      not-accessible
    STATUS          current
    DESCRIPTION     
            "The ifIndex assigned to this port when it was created.
             This will not change until the port is deleted."
    ::= { sonusSonetLineFailureIntervalEntry 1 }

sonusSonetLineFailureIntervalNumber OBJECT-TYPE
    SYNTAX          Integer32
    MAX-ACCESS      not-accessible
    STATUS          current
    DESCRIPTION     
            "A number between 1 and 32, which identifies the interval
             for which the set of statistics is available. The number 1
             identifies the most recently completed interval, and the
             interval identified by N is the interval immediately
             preceding the one identified by N-1."
    ::= { sonusSonetLineFailureIntervalEntry 2 }

sonusSonetLineFailureIntervalFCs OBJECT-TYPE
    SYNTAX          PerfCurrentCount
    MAX-ACCESS      read-only
    STATUS          current
    DESCRIPTION     
            "The counter associated with the number of Failures encountered
             by a SONET/SDH Line in the current 15 minute interval."
    ::= { sonusSonetLineFailureIntervalEntry 3 }

sonusSonetFarEndLineFailureCurrentTable OBJECT-TYPE
    SYNTAX          SEQUENCE OF SonusSonetFarEndLineFailureCurrentEntry
    MAX-ACCESS      not-accessible
    STATUS          current
    DESCRIPTION     
            "The Sonus SONET Far End Line Failure Current table."
    ::= { sonusSonetLine 8 }

sonusSonetFarEndLineFailureCurrentEntry OBJECT-TYPE
    SYNTAX          SonusSonetFarEndLineFailureCurrentEntry
    MAX-ACCESS      not-accessible
    STATUS          current
    DESCRIPTION     
            "An entry in the Sonus SONET Far End Line Failure Current table."
    INDEX           { sonusSonetFarEndLineFailureCurrentIfIndex }
    ::= { sonusSonetFarEndLineFailureCurrentTable 1 }

SonusSonetFarEndLineFailureCurrentEntry ::=
    SEQUENCE {
        sonusSonetFarEndLineFailureCurrentIfIndex         Integer32,
        sonusSonetFarEndLineFailureCurrentFCs     PerfCurrentCount
    }

sonusSonetFarEndLineFailureCurrentIfIndex OBJECT-TYPE
    SYNTAX          Integer32
    MAX-ACCESS      not-accessible
    STATUS          current
    DESCRIPTION     
            "The ifIndex assigned to this port when it was created.
             This will not change until the port is deleted."
    ::= { sonusSonetFarEndLineFailureCurrentEntry 1 }

sonusSonetFarEndLineFailureCurrentFCs OBJECT-TYPE
    SYNTAX          PerfCurrentCount
    MAX-ACCESS      read-only
    STATUS          current
    DESCRIPTION     
            "The counter associated with the number of Failures encountered
             by a SONET/SDH Line in the current 15 minute interval."
    ::= { sonusSonetFarEndLineFailureCurrentEntry 2 }

sonusSonetFarEndLineFailureIntervalTable OBJECT-TYPE
    SYNTAX          SEQUENCE OF SonusSonetFarEndLineFailureIntervalEntry
    MAX-ACCESS      not-accessible
    STATUS          current
    DESCRIPTION     
            "The Sonus SONET Far End Line Failure Interval table."
    ::= { sonusSonetLine 9 }

sonusSonetFarEndLineFailureIntervalEntry OBJECT-TYPE
    SYNTAX          SonusSonetFarEndLineFailureIntervalEntry
    MAX-ACCESS      not-accessible
    STATUS          current
    DESCRIPTION     
            "An entry in the Sonus SONET Far End Line Failure Interval table."
    INDEX           { sonusSonetFarEndLineFailureIntervalIfIndex, 
                      sonusSonetFarEndLineFailureIntervalNumber }
    ::= { sonusSonetFarEndLineFailureIntervalTable 1 }

SonusSonetFarEndLineFailureIntervalEntry ::=
    SEQUENCE {
        sonusSonetFarEndLineFailureIntervalIfIndex          Integer32,
        sonusSonetFarEndLineFailureIntervalNumber         Integer32,
        sonusSonetFarEndLineFailureIntervalFCs      PerfCurrentCount
    }

sonusSonetFarEndLineFailureIntervalIfIndex OBJECT-TYPE
    SYNTAX          Integer32
    MAX-ACCESS      not-accessible
    STATUS          current
    DESCRIPTION     
            "The ifIndex assigned to this port when it was created.
             This will not change until the port is deleted."
    ::= { sonusSonetFarEndLineFailureIntervalEntry 1 }

sonusSonetFarEndLineFailureIntervalNumber OBJECT-TYPE
    SYNTAX          Integer32
    MAX-ACCESS      not-accessible
    STATUS          current
    DESCRIPTION     
            "A number between 1 and 32, which identifies the interval
             for which the set of statistics is available. The number 1
             identifies the most recently completed interval, and the
             interval identified by N is the interval immediately
             preceding the one identified by N-1."
    ::= { sonusSonetFarEndLineFailureIntervalEntry 2 }

sonusSonetFarEndLineFailureIntervalFCs OBJECT-TYPE
    SYNTAX          PerfCurrentCount
    MAX-ACCESS      read-only
    STATUS          current
    DESCRIPTION     
            "The counter associated with the number of Failures encountered
             by a SONET/SDH Line in the current 15 minute interval."
    ::= { sonusSonetFarEndLineFailureIntervalEntry 3 }

sonusSonetLayer OBJECT IDENTIFIER
    ::= { sonusSonetObjects 4 }

sonusSonetLayerTable OBJECT-TYPE
    SYNTAX          SEQUENCE OF SonusSonetLayerEntry
    MAX-ACCESS      not-accessible
    STATUS          current
    DESCRIPTION     
            "The SONET layer table.  This table maps SONET Interface ifIndex
             to a shelf, slot, and port."
    ::= { sonusSonetLayer 1 }

sonusSonetLayerEntry OBJECT-TYPE
    SYNTAX          SonusSonetLayerEntry
    MAX-ACCESS      not-accessible
    STATUS          current
    DESCRIPTION     
            "An entry in the SONET layer table. This entry 
             maps the ifIndex of the SONET Interface to a shelf, slot
             and port.  A row is added to this table when a SONET
             port is created."
    INDEX           { sonusSonetLayerShelfIndex, 
                      sonusSonetLayerSlotIndex, sonusSonetLayerPortIndex }
    ::= { sonusSonetLayerTable 1 }

SonusSonetLayerEntry ::=
    SEQUENCE {
        sonusSonetLayerShelfIndex       SonusShelfIndex,
        sonusSonetLayerSlotIndex        SonusSlotIndex,
        sonusSonetLayerPortIndex        Integer32,
        sonusSonetLayerIfIndex          Integer32,
        sonusSonetLayerRowStatus        RowStatus
    }

sonusSonetLayerShelfIndex OBJECT-TYPE
    SYNTAX          SonusShelfIndex
    MAX-ACCESS      not-accessible
    STATUS          current
    DESCRIPTION     
            "Shelf index for this table."
    ::= { sonusSonetLayerEntry 1 }

sonusSonetLayerSlotIndex OBJECT-TYPE
    SYNTAX          SonusSlotIndex
    MAX-ACCESS      not-accessible
    STATUS          current
    DESCRIPTION     
            "Slot index for this table."
    ::= { sonusSonetLayerEntry 2 }

sonusSonetLayerPortIndex OBJECT-TYPE
    SYNTAX          Integer32
    MAX-ACCESS      not-accessible
    STATUS          current
    DESCRIPTION     
            "Port index for this table."
    ::= { sonusSonetLayerEntry 3 }

sonusSonetLayerIfIndex OBJECT-TYPE
    SYNTAX          Integer32
    MAX-ACCESS      read-only
    STATUS          current
    DESCRIPTION     
            "The ifIndex assigned to this shelf, slot, and port when the 
             SONET Interface was created."
    ::= { sonusSonetLayerEntry 4 }

sonusSonetLayerRowStatus OBJECT-TYPE
    SYNTAX          RowStatus
    MAX-ACCESS      read-create
    STATUS          current
    DESCRIPTION     
            "This object is used to create, delete,
             or modify a row in this table."
    ::= { sonusSonetLayerEntry 5 }

sonusSonetObjectsPath OBJECT IDENTIFIER
    ::= { sonusSonetMIB 2 }

sonusSonetPathAdmn OBJECT IDENTIFIER
    ::= { sonusSonetObjectsPath 1 }

sonusSonetPathAdmnTable OBJECT-TYPE
    SYNTAX          SEQUENCE OF SonusSonetPathAdmnEntry
    MAX-ACCESS      not-accessible
    STATUS          current
    DESCRIPTION     
            "The Sonus SONET Path Admn Table."
    ::= { sonusSonetPathAdmn 1 }

sonusSonetPathAdmnEntry OBJECT-TYPE
    SYNTAX          SonusSonetPathAdmnEntry
    MAX-ACCESS      not-accessible
    STATUS          current
    DESCRIPTION     
            "An entry in the Sonus SONET Path Admn table."
    INDEX           { sonusSonetPathAdmnIfIndex }
    ::= { sonusSonetPathAdmnTable 1 }

SonusSonetPathAdmnEntry ::=
    SEQUENCE {
        sonusSonetPathAdmnIfIndex       Integer32,
        sonusSonetPathAdmnShelfIndex    SonusShelfIndex,
        sonusSonetPathAdmnSlotIndex     SonusSlotIndex,
        sonusSonetPathAdmnPortIndex     Integer32,
        sonusSonetPathAdmnPathIndex     Integer32,
        sonusSonetPathAdmnRowStatus     RowStatus,
        sonusSonetPathAdmnState         SonusAdminState,
        sonusSonetPathAdmnMode          SonusServiceState,
        sonusSonetPathAdmnAction        SonusAdminAction,
        sonusSonetPathAdmnTimeout       Integer32,
        sonusSonetPathAdmnStatAction    INTEGER,
        sonusSonetPathAdmnRDIMode       INTEGER,
        sonusSonetPathAdmnTraceState    SonusAdminState,
        sonusSonetPathAdmnTraceExpMsg   DisplayString,
        sonusSonetPathAdmnTraceXmtMsg   DisplayString,
        sonusSonetPathAdmnTraceRcvMsg   DisplayString,
        sonusSonetPathAdmnOperStatus    INTEGER,
        sonusSonetPathAdmnDs3ModeOverride SonusAdminState
    }

sonusSonetPathAdmnIfIndex OBJECT-TYPE
    SYNTAX          Integer32
    MAX-ACCESS      not-accessible
    STATUS          current
    DESCRIPTION     
            "The ifIndex assigned to this path when it was created.
             This will not change until the path is deleted."
    ::= { sonusSonetPathAdmnEntry 1 }

sonusSonetPathAdmnShelfIndex OBJECT-TYPE
    SYNTAX          SonusShelfIndex
    MAX-ACCESS      read-write
    STATUS          current
    DESCRIPTION     
            "Shelf index for this table."
    ::= { sonusSonetPathAdmnEntry 2 }

sonusSonetPathAdmnSlotIndex OBJECT-TYPE
    SYNTAX          SonusSlotIndex
    MAX-ACCESS      read-write
    STATUS          current
    DESCRIPTION     
            "Slot index for this table."
    ::= { sonusSonetPathAdmnEntry 3 }

sonusSonetPathAdmnPortIndex OBJECT-TYPE
    SYNTAX          Integer32 (1..4)
    MAX-ACCESS      read-write
    STATUS          current
    DESCRIPTION     
            "OC3 port index for this table."
    ::= { sonusSonetPathAdmnEntry 4 }

sonusSonetPathAdmnPathIndex OBJECT-TYPE
    SYNTAX          Integer32 (1..3)
    MAX-ACCESS      read-only
    STATUS          current
    DESCRIPTION     
            "STS1 path index for this table."
    ::= { sonusSonetPathAdmnEntry 5 }

sonusSonetPathAdmnRowStatus OBJECT-TYPE
    SYNTAX          RowStatus
    MAX-ACCESS      read-write
    STATUS          current
    DESCRIPTION     
            "This object is used to create, delete, or modify a row in this table."
    ::= { sonusSonetPathAdmnEntry 6 }

sonusSonetPathAdmnState OBJECT-TYPE
    SYNTAX          SonusAdminState
    MAX-ACCESS      read-write
    STATUS          current
    DESCRIPTION     
            "State of STS1, Enabled/Disabled"
    DEFVAL          { disabled }
    ::= { sonusSonetPathAdmnEntry 7 }

sonusSonetPathAdmnMode OBJECT-TYPE
    SYNTAX          SonusServiceState
    MAX-ACCESS      read-write
    STATUS          current
    DESCRIPTION     
            "STS1 in-service/out-of-service."
    DEFVAL          { outOfService }
    ::= { sonusSonetPathAdmnEntry 8 }

sonusSonetPathAdmnAction OBJECT-TYPE
    SYNTAX          SonusAdminAction
    MAX-ACCESS      read-write
    STATUS          current
    DESCRIPTION     
            "The type of action to perform when a SONET path is taken out of 
             service. The SONET path can be dried up, or it can be forced
             out of service."
    DEFVAL          { dryUp }
    ::= { sonusSonetPathAdmnEntry 9 }

sonusSonetPathAdmnTimeout OBJECT-TYPE
    SYNTAX          Integer32 (0..1440)
    MAX-ACCESS      read-write
    STATUS          current
    DESCRIPTION     
            "The Dryup Timeout specifies the maximum amount of time to wait for
             all active calls to terminate on a SONET path before the path
             		 should be taken out-of-service."
    DEFVAL          { 5 }
    ::= { sonusSonetPathAdmnEntry 10 }

sonusSonetPathAdmnStatAction OBJECT-TYPE
    SYNTAX          INTEGER { init15MinuteNearEnd(1), 
                        init15MinuteFarEnd(2), init24HourNearEnd(4), 
                        init24HourFarEnd(8) }
    MAX-ACCESS      read-write
    STATUS          current
    DESCRIPTION     
            "Initialize Performance Monitoring Statistics.  A PM initialization
             action initiates one request for the action.  Requests to initialize
             more than one group of statistics can be accomplished by OR-ing the 
             appropriate bits (e.g., to initialize all 15 minute PM statistics, 
             set bits 1 and 2). Reading this variable always returns zero."
    ::= { sonusSonetPathAdmnEntry 11 }

sonusSonetPathAdmnRDIMode OBJECT-TYPE
    SYNTAX          INTEGER { normal(1), enhanced(2) }
    MAX-ACCESS      read-write
    STATUS          current
    DESCRIPTION     
            "The desired type of SONET port Path Remote Defect Indication to
             use.
             		 (1) normal - Use one-bit RDI-P signalling using bit 5 of G1.
             		 (2) enhanced - Use three-bit RDI-P (ERDI-P) using bits 5-7 of G1."
    DEFVAL          { enhanced }
    ::= { sonusSonetPathAdmnEntry 12 }

sonusSonetPathAdmnTraceState OBJECT-TYPE
    SYNTAX          SonusAdminState
    MAX-ACCESS      read-write
    STATUS          current
    DESCRIPTION     
            "The desired state of SONET Path Trace.
             (1) enabled - Enables the generation of SONET Path Trace Messages
             in the J1 bytes of the STS Path overhead, and enables the reception and
             checking of received Path Trace Messages with the Expected Path Trace
             Message.
             (2) disabled - Transmits all zero's in the J1 bytes of the STS Path
             overhead, and disables  the reception and checking of received
             Path Trace Messages with the Expected Path Trace Message."
    DEFVAL          { disabled }
    ::= { sonusSonetPathAdmnEntry 13 }

sonusSonetPathAdmnTraceExpMsg OBJECT-TYPE
    SYNTAX          DisplayString (SIZE(0..61))
    MAX-ACCESS      read-write
    STATUS          current
    DESCRIPTION     
            "The expected path trace string to be received on the SONET port in the
             J1 bytes of the STS Path overhead."
    ::= { sonusSonetPathAdmnEntry 14 }

sonusSonetPathAdmnTraceXmtMsg OBJECT-TYPE
    SYNTAX          DisplayString (SIZE(0..61))
    MAX-ACCESS      read-write
    STATUS          current
    DESCRIPTION     
            "The path trace string to be transmitted on the SONET port in the J1
             bytes of the STS Path overhead."
    ::= { sonusSonetPathAdmnEntry 15 }

sonusSonetPathAdmnTraceRcvMsg OBJECT-TYPE
    SYNTAX          DisplayString (SIZE(0..61))
    MAX-ACCESS      read-only
    STATUS          current
    DESCRIPTION     
            "The path trace string received on the SONET port in the J1
             bytes of the STS Path overhead."
    ::= { sonusSonetPathAdmnEntry 16 }

sonusSonetPathAdmnOperStatus OBJECT-TYPE
    SYNTAX          INTEGER { enabledInService(1), 
                        enabledOutOfService(2), enabledDown(3), 
                        dryingUp(4), disabled(5), up(6), down(7) }
    MAX-ACCESS      read-only
    STATUS          current
    DESCRIPTION     
            "The actual status of the Sonet path. Path is 
             Up if it is administratively in service and there are no
             line failures or hardware failures. Path is Down if
             it is administratively in service and there are line
             failures or hardware failures, or if it is administratively
             out of service. Path is DryingUp if it is administratively
             out of service and is drying up (no new	calls, still carrying
             in-progress calls) THE OTHER VALUES ARE NO LONGER SUPPORTED."
    ::= { sonusSonetPathAdmnEntry 17 }

sonusSonetPathAdmnDs3ModeOverride OBJECT-TYPE
    SYNTAX          SonusAdminState
    MAX-ACCESS      read-write
    STATUS          current
    DESCRIPTION     
            "This flag controls whether the mode and state of the DS3
             carried in the Path are modified when the mode and state of
             the Path is modified. If this flag is set to Enabled, the DS3
             state and mode are not changed when the Path mode and state
             are changed."
    DEFVAL          { disabled }
    ::= { sonusSonetPathAdmnEntry 18 }

sonusSonetPath OBJECT IDENTIFIER
    ::= { sonusSonetObjectsPath 2 }

sonusSonetPathThresholdTable OBJECT-TYPE
    SYNTAX          SEQUENCE OF SonusSonetPathThresholdEntry
    MAX-ACCESS      not-accessible
    STATUS          current
    DESCRIPTION     
            "The Sonus SONET Path Threshold Table. This table adds objects to
             set the Performance Monitoring thresholds for generating a
             Threshold Crossing Alert."
    ::= { sonusSonetPath 1 }

sonusSonetPathThresholdEntry OBJECT-TYPE
    SYNTAX          SonusSonetPathThresholdEntry
    MAX-ACCESS      not-accessible
    STATUS          current
    DESCRIPTION     
            "An entry in the Sonus SONET Path Threshold table."
    INDEX           { sonusSonetPathThresholdIfIndex }
    ::= { sonusSonetPathThresholdTable 1 }

SonusSonetPathThresholdEntry ::=
    SEQUENCE {
        sonusSonetPathThresholdIfIndex  Integer32,
        sonusSonetPathThresholdPathIndex Integer32,
        sonusSonetPathThreshold15mCVs   Integer32,
        sonusSonetPathThreshold15mESs   Integer32,
        sonusSonetPathThreshold15mSESs  Integer32,
        sonusSonetPathThreshold15mUASs  Integer32,
        sonusSonetPathThreshold24hCVs   Integer32,
        sonusSonetPathThreshold24hESs   Integer32,
        sonusSonetPathThreshold24hSESs  Integer32,
        sonusSonetPathThreshold24hUASs  Integer32
    }

sonusSonetPathThresholdIfIndex OBJECT-TYPE
    SYNTAX          Integer32
    MAX-ACCESS      not-accessible
    STATUS          current
    DESCRIPTION     
            "The ifIndex assigned to this path when it was created.
             This will not change until the path is deleted."
    ::= { sonusSonetPathThresholdEntry 1 }

sonusSonetPathThresholdPathIndex OBJECT-TYPE
    SYNTAX          Integer32 (1..3)
    MAX-ACCESS      read-only
    STATUS          current
    DESCRIPTION     
            "STS1 path index for this table."
    ::= { sonusSonetPathThresholdEntry 2 }

sonusSonetPathThreshold15mCVs OBJECT-TYPE
    SYNTAX          Integer32 (0..16383)
    MAX-ACCESS      read-write
    STATUS          current
    DESCRIPTION     
            "Threshold for 15 minute interval Path layer Coding Violations."
    ::= { sonusSonetPathThresholdEntry 3 }

sonusSonetPathThreshold15mESs OBJECT-TYPE
    SYNTAX          Integer32 (0..900)
    MAX-ACCESS      read-write
    STATUS          current
    DESCRIPTION     
            "Threshold for 15 minute interval Path layer Errored Seconds."
    ::= { sonusSonetPathThresholdEntry 4 }

sonusSonetPathThreshold15mSESs OBJECT-TYPE
    SYNTAX          Integer32 (0..900)
    MAX-ACCESS      read-write
    STATUS          current
    DESCRIPTION     
            "Threshold for 15 minute interval Path layer Severely Errored
             Seconds."
    ::= { sonusSonetPathThresholdEntry 5 }

sonusSonetPathThreshold15mUASs OBJECT-TYPE
    SYNTAX          Integer32 (0..900)
    MAX-ACCESS      read-write
    STATUS          current
    DESCRIPTION     
            "Threshold for 15 minute interval Path layer Unavailable Seconds."
    ::= { sonusSonetPathThresholdEntry 6 }

sonusSonetPathThreshold24hCVs OBJECT-TYPE
    SYNTAX          Integer32 (0..1048575)
    MAX-ACCESS      read-write
    STATUS          current
    DESCRIPTION     
            "Threshold for 24 hour interval Path layer Coding Violations."
    ::= { sonusSonetPathThresholdEntry 7 }

sonusSonetPathThreshold24hESs OBJECT-TYPE
    SYNTAX          Integer32 (0..65535)
    MAX-ACCESS      read-write
    STATUS          current
    DESCRIPTION     
            "Threshold for 24 hour interval Path layer Errored Seconds."
    ::= { sonusSonetPathThresholdEntry 8 }

sonusSonetPathThreshold24hSESs OBJECT-TYPE
    SYNTAX          Integer32 (0..65535)
    MAX-ACCESS      read-write
    STATUS          current
    DESCRIPTION     
            "Threshold for 24 hour interval Path layer Severely Errored
             Seconds."
    ::= { sonusSonetPathThresholdEntry 9 }

sonusSonetPathThreshold24hUASs OBJECT-TYPE
    SYNTAX          Integer32 (0..65535)
    MAX-ACCESS      read-write
    STATUS          current
    DESCRIPTION     
            "Threshold for 24 hour interval Path layer Unavailable Seconds."
    ::= { sonusSonetPathThresholdEntry 10 }

sonusSonetPathCurrentTable OBJECT-TYPE
    SYNTAX          SEQUENCE OF SonusSonetPathCurrentEntry
    MAX-ACCESS      not-accessible
    STATUS          current
    DESCRIPTION     
            "The Sonus SONET Path Current table."
    ::= { sonusSonetPath 2 }

sonusSonetPathCurrentEntry OBJECT-TYPE
    SYNTAX          SonusSonetPathCurrentEntry
    MAX-ACCESS      not-accessible
    STATUS          current
    DESCRIPTION     
            "An entry in the Sonus SONET Path Current table."
    INDEX           { sonusSonetPathCurrentIfIndex }
    ::= { sonusSonetPathCurrentTable 1 }

SonusSonetPathCurrentEntry ::=
    SEQUENCE {
        sonusSonetPathCurrentIfIndex    Integer32,
        sonusSonetPathCurrentPathIndex  Integer32,
        sonusSonetPathCurrentWidth      INTEGER,
        sonusSonetPathCurrentStatus     Integer32,
        sonusSonetPathCurrentESs        PerfCurrentCount,
        sonusSonetPathCurrentSESs       PerfCurrentCount,
        sonusSonetPathCurrentUASs       PerfCurrentCount,
        sonusSonetPathCurrentCVs        PerfCurrentCount,
        sonusSonetPathCurrentFCs        PerfCurrentCount,
        sonusSonetPathCurrentTraceStatus INTEGER
    }

sonusSonetPathCurrentIfIndex OBJECT-TYPE
    SYNTAX          Integer32
    MAX-ACCESS      not-accessible
    STATUS          current
    DESCRIPTION     
            "The ifIndex assigned to this path when it was created.
             This will not change until the path is deleted."
    ::= { sonusSonetPathCurrentEntry 1 }

sonusSonetPathCurrentPathIndex OBJECT-TYPE
    SYNTAX          Integer32 (1..3)
    MAX-ACCESS      read-only
    STATUS          current
    DESCRIPTION     
            "STS1 path index for this table."
    ::= { sonusSonetPathCurrentEntry 2 }

sonusSonetPathCurrentWidth OBJECT-TYPE
    SYNTAX          INTEGER { sts1(1), sts3cSTM1(2), sts12cSTM4(3), 
                        sts24c(4), sts48cSTM16(5) }
    MAX-ACCESS      read-only
    STATUS          current
    DESCRIPTION     
            "A value that indicates the type of the SONET/SDH Path.
             For SONET, the assigned types are the STS-Nc SPEs,
             where N = 1, 3, 12, 24, and 48. STS-1 is equal to 51.84
             Mbps. For SDH, the assigned types are the STM-Nc VCs,
             where N = 1, 4, and 16."
    ::= { sonusSonetPathCurrentEntry 3 }

sonusSonetPathCurrentStatus OBJECT-TYPE
    SYNTAX          Integer32 (1..62)
    MAX-ACCESS      read-only
    STATUS          current
    DESCRIPTION     
            "This variable indicates the status of the interface. It is
             a bit map represented as a sum, therefore, it can represent
             multiple defects simultaneously. The sonetPathNoDefect
             should be set if and only if no other flag is set.
             
             The various bit positions are:
             1   sonetPathNoDefect
             2   sonetPathSTSLOP
             4   sonetPathSTSAIS
             8   sonetPathSTSRDI
             16  sonetPathUnequiped
             32  sonetPathSignalLabelMismatch"
    ::= { sonusSonetPathCurrentEntry 4 }

sonusSonetPathCurrentESs OBJECT-TYPE
    SYNTAX          PerfCurrentCount
    MAX-ACCESS      read-only
    STATUS          current
    DESCRIPTION     
            "The counter associated with the number of Errored Seconds
             encountered by a SONET/SDH Path in the current 24 hour
             interval."
    ::= { sonusSonetPathCurrentEntry 5 }

sonusSonetPathCurrentSESs OBJECT-TYPE
    SYNTAX          PerfCurrentCount
    MAX-ACCESS      read-only
    STATUS          current
    DESCRIPTION     
            "The counter associated with the number of Severely Errored
             Seconds encountered by a SONET/SDH Path in the current 
             24 hour interval."
    ::= { sonusSonetPathCurrentEntry 6 }

sonusSonetPathCurrentUASs OBJECT-TYPE
    SYNTAX          PerfCurrentCount
    MAX-ACCESS      read-only
    STATUS          current
    DESCRIPTION     
            "The counter associated with the number of Unavailable
             Seconds encountered by a SONET/SDH Path in the current
             24 hour interval."
    ::= { sonusSonetPathCurrentEntry 7 }

sonusSonetPathCurrentCVs OBJECT-TYPE
    SYNTAX          PerfCurrentCount
    MAX-ACCESS      read-only
    STATUS          current
    DESCRIPTION     
            "The counter associated with the number of Coding Violations
             encountered by a SONET/SDH Path in the current 24 hour
             	 interval."
    ::= { sonusSonetPathCurrentEntry 8 }

sonusSonetPathCurrentFCs OBJECT-TYPE
    SYNTAX          PerfCurrentCount
    MAX-ACCESS      read-only
    STATUS          current
    DESCRIPTION     
            "The counter associated with the number of Failures encountered
             by a SONET/SDH Path in the current 24 hour interval."
    ::= { sonusSonetPathCurrentEntry 9 }

sonusSonetPathCurrentTraceStatus OBJECT-TYPE
    SYNTAX          INTEGER { nodefect(1), tracemismatch(2) }
    MAX-ACCESS      read-only
    STATUS          current
    DESCRIPTION     
            "The status of the Trace Mismatch Failure."
    ::= { sonusSonetPathCurrentEntry 10 }

sonusSonetPathIntervalTable OBJECT-TYPE
    SYNTAX          SEQUENCE OF SonusSonetPathIntervalEntry
    MAX-ACCESS      not-accessible
    STATUS          current
    DESCRIPTION     
            "The Sonus SONET Path Interval table."
    ::= { sonusSonetPath 3 }

sonusSonetPathIntervalEntry OBJECT-TYPE
    SYNTAX          SonusSonetPathIntervalEntry
    MAX-ACCESS      not-accessible
    STATUS          current
    DESCRIPTION     
            "An entry in the Sonus SONET Path Interval table."
    INDEX           { sonusSonetPathIntervalIfIndex, 
                      sonusSonetPathIntervalNumber }
    ::= { sonusSonetPathIntervalTable 1 }

SonusSonetPathIntervalEntry ::=
    SEQUENCE {
        sonusSonetPathIntervalIfIndex   Integer32,
        sonusSonetPathIntervalPathIndex Integer32,
        sonusSonetPathIntervalNumber    Integer32,
        sonusSonetPathIntervalESs       PerfIntervalCount,
        sonusSonetPathIntervalSESs      PerfIntervalCount,
        sonusSonetPathIntervalUASs      PerfIntervalCount,
        sonusSonetPathIntervalCVs       PerfIntervalCount,
        sonusSonetPathIntervalFCs       PerfIntervalCount,
        sonusSonetPathIntervalValidData TruthValue
    }

sonusSonetPathIntervalIfIndex OBJECT-TYPE
    SYNTAX          Integer32
    MAX-ACCESS      not-accessible
    STATUS          current
    DESCRIPTION     
            "The ifIndex assigned to this path when it was created.
             This will not change until the path is deleted."
    ::= { sonusSonetPathIntervalEntry 1 }

sonusSonetPathIntervalPathIndex OBJECT-TYPE
    SYNTAX          Integer32 (1..3)
    MAX-ACCESS      read-only
    STATUS          current
    DESCRIPTION     
            "STS1 path index for this table."
    ::= { sonusSonetPathIntervalEntry 2 }

sonusSonetPathIntervalNumber OBJECT-TYPE
    SYNTAX          Integer32 (1)
    MAX-ACCESS      not-accessible
    STATUS          current
    DESCRIPTION     
            "The number 1 identifies the most recently completed 24 hour
             interval. In the future if more 24 hour intervals are supported,
             the interval identified by N is the interval immediately
             preceding the one identified by N-1."
    ::= { sonusSonetPathIntervalEntry 3 }

sonusSonetPathIntervalESs OBJECT-TYPE
    SYNTAX          PerfIntervalCount
    MAX-ACCESS      read-only
    STATUS          current
    DESCRIPTION     
            "The counter associated with the number of Errored Seconds
             encountered by a SONET/SDH Path in the previous 24 hour
             interval."
    ::= { sonusSonetPathIntervalEntry 4 }

sonusSonetPathIntervalSESs OBJECT-TYPE
    SYNTAX          PerfIntervalCount
    MAX-ACCESS      read-only
    STATUS          current
    DESCRIPTION     
            "The counter associated with the number of Severely Errored
             Seconds encountered by a SONET/SDH Path in the previous 
             24 hour interval."
    ::= { sonusSonetPathIntervalEntry 5 }

sonusSonetPathIntervalUASs OBJECT-TYPE
    SYNTAX          PerfIntervalCount
    MAX-ACCESS      read-only
    STATUS          current
    DESCRIPTION     
            "The counter associated with the number of Unavailable
             Seconds encountered by a SONET/SDH Path in the previous
             24 hour interval."
    ::= { sonusSonetPathIntervalEntry 6 }

sonusSonetPathIntervalCVs OBJECT-TYPE
    SYNTAX          PerfIntervalCount
    MAX-ACCESS      read-only
    STATUS          current
    DESCRIPTION     
            "The counter associated with the number of Coding Violations
             encountered by a SONET/SDH Path in the previous 24 hour
             	 interval."
    ::= { sonusSonetPathIntervalEntry 7 }

sonusSonetPathIntervalFCs OBJECT-TYPE
    SYNTAX          PerfIntervalCount
    MAX-ACCESS      read-only
    STATUS          current
    DESCRIPTION     
            "The counter associated with the number of Failures encountered
             by a SONET/SDH Path in the previous 24 hour interval."
    ::= { sonusSonetPathIntervalEntry 8 }

sonusSonetPathIntervalValidData OBJECT-TYPE
    SYNTAX          TruthValue
    MAX-ACCESS      read-only
    STATUS          current
    DESCRIPTION     
            "This variable indicates if the data for this interval is valid."
    ::= { sonusSonetPathIntervalEntry 9 }

sonusSonetFarEndPathCurrentTable OBJECT-TYPE
    SYNTAX          SEQUENCE OF SonusSonetFarEndPathCurrentEntry
    MAX-ACCESS      not-accessible
    STATUS          current
    DESCRIPTION     
            "The Sonus SONET Far End Path Current table."
    ::= { sonusSonetPath 4 }

sonusSonetFarEndPathCurrentEntry OBJECT-TYPE
    SYNTAX          SonusSonetFarEndPathCurrentEntry
    MAX-ACCESS      not-accessible
    STATUS          current
    DESCRIPTION     
            "An entry in the Sonus SONET Far End Path Current table."
    INDEX           { sonusSonetFarEndPathCurrentIfIndex }
    ::= { sonusSonetFarEndPathCurrentTable 1 }

SonusSonetFarEndPathCurrentEntry ::=
    SEQUENCE {
        sonusSonetFarEndPathCurrentIfIndex  Integer32,
        sonusSonetFarEndPathCurrentPathIndex    Integer32,
        sonusSonetFarEndPathCurrentESs  PerfCurrentCount,
        sonusSonetFarEndPathCurrentSESs PerfCurrentCount,
        sonusSonetFarEndPathCurrentUASs PerfCurrentCount,
        sonusSonetFarEndPathCurrentCVs  PerfCurrentCount,
        sonusSonetFarEndPathCurrentFCs  PerfCurrentCount
    }

sonusSonetFarEndPathCurrentIfIndex OBJECT-TYPE
    SYNTAX          Integer32
    MAX-ACCESS      not-accessible
    STATUS          current
    DESCRIPTION     
            "The ifIndex assigned to this path when it was created.
             This will not change until the path is deleted."
    ::= { sonusSonetFarEndPathCurrentEntry 1 }

sonusSonetFarEndPathCurrentPathIndex OBJECT-TYPE
    SYNTAX          Integer32 (1..3)
    MAX-ACCESS      read-only
    STATUS          current
    DESCRIPTION     
            "STS1 path index for this table."
    ::= { sonusSonetFarEndPathCurrentEntry 2 }

sonusSonetFarEndPathCurrentESs OBJECT-TYPE
    SYNTAX          PerfCurrentCount
    MAX-ACCESS      read-only
    STATUS          current
    DESCRIPTION     
            "The counter associated with the number of Far End Errored
             Seconds encountered by a SONET/SDH Path in the current
             24 hour interval."
    ::= { sonusSonetFarEndPathCurrentEntry 3 }

sonusSonetFarEndPathCurrentSESs OBJECT-TYPE
    SYNTAX          PerfCurrentCount
    MAX-ACCESS      read-only
    STATUS          current
    DESCRIPTION     
            "The counter associated with the number of Far End Severely
             Errored Seconds encountered by a SONET/SDH Path in the
             current 24 hour interval."
    ::= { sonusSonetFarEndPathCurrentEntry 4 }

sonusSonetFarEndPathCurrentUASs OBJECT-TYPE
    SYNTAX          PerfCurrentCount
    MAX-ACCESS      read-only
    STATUS          current
    DESCRIPTION     
            "The counter associated with the number of Far End 
             Unavailable Seconds encountered by a SONET/SDH Path in the
             current 24 hour interval."
    ::= { sonusSonetFarEndPathCurrentEntry 5 }

sonusSonetFarEndPathCurrentCVs OBJECT-TYPE
    SYNTAX          PerfCurrentCount
    MAX-ACCESS      read-only
    STATUS          current
    DESCRIPTION     
            "The counter associated with the number of Far End Coding
             Violations encountered by a SONET/SDH Path in the current
             	 24 hour interval."
    ::= { sonusSonetFarEndPathCurrentEntry 6 }

sonusSonetFarEndPathCurrentFCs OBJECT-TYPE
    SYNTAX          PerfCurrentCount
    MAX-ACCESS      read-only
    STATUS          current
    DESCRIPTION     
            "The counter associated with the number of Far End Failures
             encountered by a SONET/SDH Path in the current 24 hour
             interval."
    ::= { sonusSonetFarEndPathCurrentEntry 7 }

sonusSonetFarEndPathIntervalTable OBJECT-TYPE
    SYNTAX          SEQUENCE OF SonusSonetFarEndPathIntervalEntry
    MAX-ACCESS      not-accessible
    STATUS          current
    DESCRIPTION     
            "The Sonus SONET Far End Path Interval table."
    ::= { sonusSonetPath 5 }

sonusSonetFarEndPathIntervalEntry OBJECT-TYPE
    SYNTAX          SonusSonetFarEndPathIntervalEntry
    MAX-ACCESS      not-accessible
    STATUS          current
    DESCRIPTION     
            "An entry in the Sonus SONET Far End Path Interval table."
    INDEX           { sonusSonetFarEndPathIntervalIfIndex, 
                      sonusSonetFarEndPathIntervalNumber }
    ::= { sonusSonetFarEndPathIntervalTable 1 }

SonusSonetFarEndPathIntervalEntry ::=
    SEQUENCE {
        sonusSonetFarEndPathIntervalIfIndex   Integer32,
        sonusSonetFarEndPathIntervalPathIndex     Integer32,
        sonusSonetFarEndPathIntervalNumber  Integer32,
        sonusSonetFarEndPathIntervalESs PerfIntervalCount,
        sonusSonetFarEndPathIntervalSESs PerfIntervalCount,
        sonusSonetFarEndPathIntervalUASs PerfIntervalCount,
        sonusSonetFarEndPathIntervalCVs PerfIntervalCount,
        sonusSonetFarEndPathIntervalFCs PerfIntervalCount,
        sonusSonetFarEndPathIntervalValidData     TruthValue
    }

sonusSonetFarEndPathIntervalIfIndex OBJECT-TYPE
    SYNTAX          Integer32
    MAX-ACCESS      not-accessible
    STATUS          current
    DESCRIPTION     
            "The ifIndex assigned to this path when it was created.
             This will not change until the path is deleted."
    ::= { sonusSonetFarEndPathIntervalEntry 1 }

sonusSonetFarEndPathIntervalPathIndex OBJECT-TYPE
    SYNTAX          Integer32 (1..3)
    MAX-ACCESS      read-only
    STATUS          current
    DESCRIPTION     
            "STS1 path index for this table."
    ::= { sonusSonetFarEndPathIntervalEntry 2 }

sonusSonetFarEndPathIntervalNumber OBJECT-TYPE
    SYNTAX          Integer32 (1)
    MAX-ACCESS      not-accessible
    STATUS          current
    DESCRIPTION     
            "The number 1 identifies the most recently completed 24 hour
             interval. In the future if more 24 hour intervals are supported,
             the interval identified by N is the interval immediately
             preceding the one identified by N-1."
    ::= { sonusSonetFarEndPathIntervalEntry 3 }

sonusSonetFarEndPathIntervalESs OBJECT-TYPE
    SYNTAX          PerfIntervalCount
    MAX-ACCESS      read-only
    STATUS          current
    DESCRIPTION     
            "The counter associated with the number of Far End Errored
             Seconds encountered by a SONET/SDH Path in the current
             24 hour interval."
    ::= { sonusSonetFarEndPathIntervalEntry 4 }

sonusSonetFarEndPathIntervalSESs OBJECT-TYPE
    SYNTAX          PerfIntervalCount
    MAX-ACCESS      read-only
    STATUS          current
    DESCRIPTION     
            "The counter associated with the number of Far End Severely
             Errored Seconds encountered by a SONET/SDH Path in the
             current 24 hour interval."
    ::= { sonusSonetFarEndPathIntervalEntry 5 }

sonusSonetFarEndPathIntervalUASs OBJECT-TYPE
    SYNTAX          PerfIntervalCount
    MAX-ACCESS      read-only
    STATUS          current
    DESCRIPTION     
            "The counter associated with the number of Far End 
             Unavailable Seconds encountered by a SONET/SDH Path in the
             current 24 hour interval."
    ::= { sonusSonetFarEndPathIntervalEntry 6 }

sonusSonetFarEndPathIntervalCVs OBJECT-TYPE
    SYNTAX          PerfIntervalCount
    MAX-ACCESS      read-only
    STATUS          current
    DESCRIPTION     
            "The counter associated with the number of Far End Coding
             Violations encountered by a SONET/SDH Path in the current
             	 24 hour interval."
    ::= { sonusSonetFarEndPathIntervalEntry 7 }

sonusSonetFarEndPathIntervalFCs OBJECT-TYPE
    SYNTAX          PerfIntervalCount
    MAX-ACCESS      read-only
    STATUS          current
    DESCRIPTION     
            "The counter associated with the number of Far End Failures
             encountered by a SONET/SDH Path in the current 24 hour
             interval."
    ::= { sonusSonetFarEndPathIntervalEntry 8 }

sonusSonetFarEndPathIntervalValidData OBJECT-TYPE
    SYNTAX          TruthValue
    MAX-ACCESS      read-only
    STATUS          current
    DESCRIPTION     
            "This variable indicates if the data for this interval is valid."
    ::= { sonusSonetFarEndPathIntervalEntry 9 }

sonusSonetPathFailureCurrentTable OBJECT-TYPE
    SYNTAX          SEQUENCE OF SonusSonetPathFailureCurrentEntry
    MAX-ACCESS      not-accessible
    STATUS          current
    DESCRIPTION     
            "The Sonus SONET Path Failure Current table."
    ::= { sonusSonetPath 6 }

sonusSonetPathFailureCurrentEntry OBJECT-TYPE
    SYNTAX          SonusSonetPathFailureCurrentEntry
    MAX-ACCESS      not-accessible
    STATUS          current
    DESCRIPTION     
            "An entry in the Sonus SONET Path Failure Current table."
    INDEX           { sonusSonetPathFailureCurrentIfIndex }
    ::= { sonusSonetPathFailureCurrentTable 1 }

SonusSonetPathFailureCurrentEntry ::=
    SEQUENCE {
        sonusSonetPathFailureCurrentIfIndex   Integer32,
        sonusSonetPathFailureCurrentPathIndex     Integer32,
        sonusSonetPathFailureCurrentFCs PerfCurrentCount,
        sonusSonetPathFailureCurrentTraceStatus       INTEGER
    }

sonusSonetPathFailureCurrentIfIndex OBJECT-TYPE
    SYNTAX          Integer32
    MAX-ACCESS      not-accessible
    STATUS          current
    DESCRIPTION     
            "The ifIndex assigned to this path when it was created.
             This will not change until the path is deleted."
    ::= { sonusSonetPathFailureCurrentEntry 1 }

sonusSonetPathFailureCurrentPathIndex OBJECT-TYPE
    SYNTAX          Integer32 (1..3)
    MAX-ACCESS      read-only
    STATUS          current
    DESCRIPTION     
            "STS1 path index for this table."
    ::= { sonusSonetPathFailureCurrentEntry 2 }

sonusSonetPathFailureCurrentFCs OBJECT-TYPE
    SYNTAX          PerfCurrentCount
    MAX-ACCESS      read-only
    STATUS          current
    DESCRIPTION     
            "The counter associated with the number of Failures encountered
             by a SONET/SDH Path in the current 15 minute interval."
    ::= { sonusSonetPathFailureCurrentEntry 3 }

sonusSonetPathFailureCurrentTraceStatus OBJECT-TYPE
    SYNTAX          INTEGER { nodefect(1), tracemismatch(2) }
    MAX-ACCESS      read-only
    STATUS          current
    DESCRIPTION     
            "The status of the Trace Mismatch Failure."
    ::= { sonusSonetPathFailureCurrentEntry 4 }

sonusSonetPathFailureIntervalTable OBJECT-TYPE
    SYNTAX          SEQUENCE OF SonusSonetPathFailureIntervalEntry
    MAX-ACCESS      not-accessible
    STATUS          current
    DESCRIPTION     
            "The Sonus SONET Path Failure Interval table."
    ::= { sonusSonetPath 7 }

sonusSonetPathFailureIntervalEntry OBJECT-TYPE
    SYNTAX          SonusSonetPathFailureIntervalEntry
    MAX-ACCESS      not-accessible
    STATUS          current
    DESCRIPTION     
            "An entry in the Sonus SONET Path Failure Interval table."
    INDEX           { sonusSonetPathFailureIntervalIfIndex, 
                      sonusSonetPathFailureIntervalNumber }
    ::= { sonusSonetPathFailureIntervalTable 1 }

SonusSonetPathFailureIntervalEntry ::=
    SEQUENCE {
        sonusSonetPathFailureIntervalIfIndex    Integer32,
        sonusSonetPathFailureIntervalPathIndex      Integer32,
        sonusSonetPathFailureIntervalNumber   Integer32,
        sonusSonetPathFailureIntervalFCs PerfCurrentCount
    }

sonusSonetPathFailureIntervalIfIndex OBJECT-TYPE
    SYNTAX          Integer32
    MAX-ACCESS      not-accessible
    STATUS          current
    DESCRIPTION     
            "The ifIndex assigned to this path when it was created.
             This will not change until the path is deleted."
    ::= { sonusSonetPathFailureIntervalEntry 1 }

sonusSonetPathFailureIntervalPathIndex OBJECT-TYPE
    SYNTAX          Integer32 (1..3)
    MAX-ACCESS      read-only
    STATUS          current
    DESCRIPTION     
            "STS1 path index for this table."
    ::= { sonusSonetPathFailureIntervalEntry 2 }

sonusSonetPathFailureIntervalNumber OBJECT-TYPE
    SYNTAX          Integer32
    MAX-ACCESS      not-accessible
    STATUS          current
    DESCRIPTION     
            "A number between 1 and 32, which identifies the interval
             for which the set of statistics is available. The number 1
             identifies the most recently completed interval, and the
             interval identified by N is the interval immediately
             preceding the one identified by N-1."
    ::= { sonusSonetPathFailureIntervalEntry 3 }

sonusSonetPathFailureIntervalFCs OBJECT-TYPE
    SYNTAX          PerfCurrentCount
    MAX-ACCESS      read-only
    STATUS          current
    DESCRIPTION     
            "The counter associated with the number of Failures encountered
             by a SONET/SDH Path in the current 15 minute interval."
    ::= { sonusSonetPathFailureIntervalEntry 4 }

sonusSonetFarEndPathFailureCurrentTable OBJECT-TYPE
    SYNTAX          SEQUENCE OF SonusSonetFarEndPathFailureCurrentEntry
    MAX-ACCESS      not-accessible
    STATUS          current
    DESCRIPTION     
            "The Sonus SONET Far End Path Failure Current table."
    ::= { sonusSonetPath 8 }

sonusSonetFarEndPathFailureCurrentEntry OBJECT-TYPE
    SYNTAX          SonusSonetFarEndPathFailureCurrentEntry
    MAX-ACCESS      not-accessible
    STATUS          current
    DESCRIPTION     
            "An entry in the Sonus SONET Far End Path Failure Current table."
    INDEX           { sonusSonetFarEndPathFailureCurrentIfIndex }
    ::= { sonusSonetFarEndPathFailureCurrentTable 1 }

SonusSonetFarEndPathFailureCurrentEntry ::=
    SEQUENCE {
        sonusSonetFarEndPathFailureCurrentIfIndex         Integer32,
        sonusSonetFarEndPathFailureCurrentPathIndex           Integer32,
        sonusSonetFarEndPathFailureCurrentFCs     PerfCurrentCount
    }

sonusSonetFarEndPathFailureCurrentIfIndex OBJECT-TYPE
    SYNTAX          Integer32
    MAX-ACCESS      not-accessible
    STATUS          current
    DESCRIPTION     
            "The ifIndex assigned to this path when it was created.
             This will not change until the path is deleted."
    ::= { sonusSonetFarEndPathFailureCurrentEntry 1 }

sonusSonetFarEndPathFailureCurrentPathIndex OBJECT-TYPE
    SYNTAX          Integer32 (1..3)
    MAX-ACCESS      read-only
    STATUS          current
    DESCRIPTION     
            "STS1 path index for this table."
    ::= { sonusSonetFarEndPathFailureCurrentEntry 2 }

sonusSonetFarEndPathFailureCurrentFCs OBJECT-TYPE
    SYNTAX          PerfCurrentCount
    MAX-ACCESS      read-only
    STATUS          current
    DESCRIPTION     
            "The counter associated with the number of Failures encountered
             by a SONET/SDH Path in the current 15 minute interval."
    ::= { sonusSonetFarEndPathFailureCurrentEntry 3 }

sonusSonetFarEndPathFailureIntervalTable OBJECT-TYPE
    SYNTAX          SEQUENCE OF SonusSonetFarEndPathFailureIntervalEntry
    MAX-ACCESS      not-accessible
    STATUS          current
    DESCRIPTION     
            "The Sonus SONET Far End Path Failure Interval table."
    ::= { sonusSonetPath 9 }

sonusSonetFarEndPathFailureIntervalEntry OBJECT-TYPE
    SYNTAX          SonusSonetFarEndPathFailureIntervalEntry
    MAX-ACCESS      not-accessible
    STATUS          current
    DESCRIPTION     
            "An entry in the Sonus SONET Far End Path Failure Interval table."
    INDEX           { sonusSonetFarEndPathFailureIntervalIfIndex, 
                      sonusSonetFarEndPathFailureIntervalNumber }
    ::= { sonusSonetFarEndPathFailureIntervalTable 1 }

SonusSonetFarEndPathFailureIntervalEntry ::=
    SEQUENCE {
        sonusSonetFarEndPathFailureIntervalIfIndex          Integer32,
        sonusSonetFarEndPathFailureIntervalPathIndex            Integer32,
        sonusSonetFarEndPathFailureIntervalNumber         Integer32,
        sonusSonetFarEndPathFailureIntervalFCs      PerfCurrentCount
    }

sonusSonetFarEndPathFailureIntervalIfIndex OBJECT-TYPE
    SYNTAX          Integer32
    MAX-ACCESS      not-accessible
    STATUS          current
    DESCRIPTION     
            "The ifIndex assigned to this path when it was created.
             This will not change until the path is deleted."
    ::= { sonusSonetFarEndPathFailureIntervalEntry 1 }

sonusSonetFarEndPathFailureIntervalPathIndex OBJECT-TYPE
    SYNTAX          Integer32 (1..3)
    MAX-ACCESS      read-only
    STATUS          current
    DESCRIPTION     
            "STS1 path index for this table."
    ::= { sonusSonetFarEndPathFailureIntervalEntry 2 }

sonusSonetFarEndPathFailureIntervalNumber OBJECT-TYPE
    SYNTAX          Integer32
    MAX-ACCESS      not-accessible
    STATUS          current
    DESCRIPTION     
            "A number between 1 and 32, which identifies the interval
             for which the set of statistics is available. The number 1
             identifies the most recently completed interval, and the
             interval identified by N is the interval immediately
             preceding the one identified by N-1."
    ::= { sonusSonetFarEndPathFailureIntervalEntry 3 }

sonusSonetFarEndPathFailureIntervalFCs OBJECT-TYPE
    SYNTAX          PerfCurrentCount
    MAX-ACCESS      read-only
    STATUS          current
    DESCRIPTION     
            "The counter associated with the number of Failures encountered
             by a SONET/SDH Path in the current 15 minute interval."
    ::= { sonusSonetFarEndPathFailureIntervalEntry 4 }

sonusSonetNextIndex OBJECT-TYPE
    SYNTAX          Integer32
    MAX-ACCESS      read-only
    STATUS          current
    DESCRIPTION     
            "The next valid index to use when creating an entry in
             the sonusSonetTable."
    ::= { sonusSonetMIB 3 }

sonusSonetMIBNotifications OBJECT IDENTIFIER
    ::= { sonusSonetMIB 4 }

sonusSonetMIBNotificationsPrefix OBJECT IDENTIFIER
    ::= { sonusSonetMIBNotifications 0 }

sonusSonetMIBNotificationsObjects OBJECT IDENTIFIER
    ::= { sonusSonetMIBNotifications 1 }

sonusSonetAdminStatus OBJECT-TYPE
    SYNTAX          INTEGER { enabledInService(1), 
                        enabledOutOfService(2), disabled(3), deleted(4), 
                        dryingUp(5) }
    MAX-ACCESS      read-only
    STATUS          current
    DESCRIPTION     
            "The administrative status of a Sonet port. EnabledInService
             means the port configuration is applied and the port is
             available to carry calls. EnabledOutOfService means the port
             configuration is applied and the port is not available to carry
             calls. Disabled means the port configuration is not applied
             and the port is not available to carry calls. DryingUp means
             the port is still carrying in-progress calls but is not available
             for new calls. Value deleted is NO LONGER SUPPORTED."
    ::= { sonusSonetMIBNotificationsObjects 1 }

sonusSonetOperStatus OBJECT-TYPE
    SYNTAX          INTEGER { inService(1), outOfService(2), dryingUp(3), 
                        inServiceDown(4), outOfServiceDown(5), 
                        disabled(6) }
    MAX-ACCESS      read-only
    STATUS          obsolete
    DESCRIPTION     
            "Operational status of the Sonet port. Port is inService 
             if the admin state is enabled and the admin mode is in
             service. Port is outOfService if admin state is enabled,
             admin mode is out of service, and port is no longer
             carrying calls (dried up). Port is dryingUp if admin
             state is enabled, admin mode is out of service, and 
             port is drying up (no new calls, still carrying
             in-progress calls). Port is inServiceDown if admin state
             is enabled, admin mode is in service, but physical link
             is not available due to alarm condition. Port is
             outOfServiceDown if admin state is enabled, admin mode is
             out of service, but physical link is not available due to
             alarm condition. Port is disabled if admin state is
             disabled, admin mode is out of service, and port is no
             longer carrying calls (dried up)."
    ::= { sonusSonetMIBNotificationsObjects 2 }

sonusSonetAlarmStatus OBJECT-TYPE
    SYNTAX          INTEGER { los(1), losClear(2), lof(3), lofClear(4), 
                        lAIS(5), lAISClear(6), lRFI(7), lRFIClear(8), 
                        pAIS(9), pAISClear(10), pRFI(11), pRFIClear(12), 
                        pLOP(13), pLOPClear(14), pUNEQ(15), 
                        pUNEQClear(16), pPLM(17), pPLMClear(18), 
                        pTIM(19), pTIMClear(20) }
    MAX-ACCESS      read-only
    STATUS          current
    DESCRIPTION     
            "Alarm conditions."
    ::= { sonusSonetMIBNotificationsObjects 3 }

sonusSonetThresholdType OBJECT-TYPE
    SYNTAX          INTEGER { sectionNearendCodingViolation15min(1), 
                        sectionNearendErroredSec15min(2), 
                        sectionNearendSeverelyErroredSec15min(3), 
                        sectionNearendSeverelyErroredFrameSec15min(4), 
                        lineNearendCodingViolation15min(5), 
                        lineNearendErroredSec15min(6), 
                        lineNearendSeverelyErroredSec15min(7), 
                        lineNearendUnavailableSec15min(8), 
                        pathNearendCodingViolation15min(9), 
                        pathNearendErroredSec15min(10), 
                        pathNearendSeverelyErroredSec15min(11), 
                        pathNearendUnavailableSec15min(12), 
                        sectionNearendCodingViolation24hr(13), 
                        sectionNearendErroredSec24hr(14), 
                        sectionNearendSeverelyErroredSec24hr(15), 
                        sectionNearendSeverelyErroredFrameSec24hr(16), 
                        lineNearendCodingViolation24hr(17), 
                        lineNearendErroredSec24hr(18), 
                        lineNearendSeverelyErroredSec24hr(19), 
                        lineNearendUnavailableSec24hr(20), 
                        pathNearendCodingViolation24hr(21), 
                        pathNearendErroredSec24hr(22), 
                        pathNearendSeverelyErroredSec24hr(23), 
                        pathNearendUnavailableSec24hr(24), 
                        lineFarendCodingViolation15min(25), 
                        lineFarendErroredSec15min(26), 
                        lineFarendSeverelyErroredSec15min(27), 
                        lineFarendUnavailableSec15min(28), 
                        pathFarendCodingViolation15min(29), 
                        pathFarendErroredSec15min(30), 
                        pathFarendSeverelyErroredSec15min(31), 
                        pathFarendUnavailableSec15min(32), 
                        sectionFarendCodingViolation24hr(33), 
                        sectionFarendErroredSec24hr(34), 
                        sectionFarendSeverelyErroredSec24hr(35), 
                        sectionFarendSeverelyErroredFrameSec24hr(36), 
                        lineFarendCodingViolation24hr(37), 
                        lineFarendErroredSec24hr(38), 
                        lineFarendSeverelyErroredSec24hr(39), 
                        lineFarendUnavailableSec24hr(40), 
                        pathFarendCodingViolation24hr(41), 
                        pathFarendErroredSec24hr(42), 
                        pathFarendSeverelyErroredSec24hr(43), 
                        pathFarendUnavailableSec24hr(44) }
    MAX-ACCESS      read-only
    STATUS          current
    DESCRIPTION     
            "Threshold crossing types."
    ::= { sonusSonetMIBNotificationsObjects 4 }

sonusPathIndex OBJECT-TYPE
    SYNTAX          Integer32 (1..3)
    MAX-ACCESS      read-only
    STATUS          current
    DESCRIPTION     
            "STS1 path index."
    ::= { sonusSonetMIBNotificationsObjects 5 }

sonusSonetOutOfServiceReason OBJECT-TYPE
    SYNTAX          INTEGER { admin(1), hwFailure(2) }
    MAX-ACCESS      read-only
    STATUS          current
    DESCRIPTION     
            "Reason the Sonet port/path went out of service."
    ::= { sonusSonetMIBNotificationsObjects 6 }

sonusSonetPortAdminStatusNotification NOTIFICATION-TYPE
    OBJECTS         { ifIndex, sonusShelfIndex, sonusSlotIndex, 
                      sonusPortIndex, sonusSonetAdminStatus, 
                      sonusEventDescription, sonusEventClass, 
                      sonusEventLevel }
    STATUS          current
    DESCRIPTION     
            "This trap indicates the Sonet port's administrative status
             has changed due to an operator-initiated command. Possible
             admin status is EnabledInService, EnabledOutOfService,
             Disabled, and DryingUp."
    ::= { sonusSonetMIBNotificationsPrefix 1 }

sonusSonetPortOperStatusNotification NOTIFICATION-TYPE
    OBJECTS         { ifIndex, sonusShelfIndex, sonusSlotIndex, 
                      sonusPortIndex, sonusSonetOperStatus, 
                      sonusEventDescription, sonusEventClass, 
                      sonusEventLevel }
    STATUS          obsolete
    DESCRIPTION     
            "NO LONGER SUPPORTED. This trap indicates the Sonet
             port's operational status
             has changed."
    ::= { sonusSonetMIBNotificationsPrefix 2 }

sonusSonetLineAlarmNotification NOTIFICATION-TYPE
    OBJECTS         { ifIndex, sonusShelfIndex, sonusSlotIndex, 
                      sonusPortIndex, sonusSonetAlarmStatus, 
                      sonusEventDescription, sonusEventClass, 
                      sonusEventLevel }
    STATUS          current
    DESCRIPTION     
            "This trap indicates the line Section/Line-layer alarm
             state of the Sonet port has changed."
    ::= { sonusSonetMIBNotificationsPrefix 3 }

sonusSonetLineThresholdCrossNotification NOTIFICATION-TYPE
    OBJECTS         { ifIndex, sonusShelfIndex, sonusSlotIndex, 
                      sonusPortIndex, sonusSonetThresholdType, 
                      sonusEventDescription, sonusEventClass, 
                      sonusEventLevel }
    STATUS          current
    DESCRIPTION     
            "This trap indicates that a Section/Line-layer performance
             monitoring threshold has been crossed."
    ::= { sonusSonetMIBNotificationsPrefix 4 }

sonusSonetPathAdminStatusNotification NOTIFICATION-TYPE
    OBJECTS         { ifIndex, sonusShelfIndex, sonusSlotIndex, 
                      sonusPortIndex, sonusPathIndex, 
                      sonusSonetAdminStatus, sonusEventDescription, 
                      sonusEventClass, sonusEventLevel }
    STATUS          current
    DESCRIPTION     
            "This trap indicates the Sonet path's administrative status
             has changed due to an operator-initiated command. Possible
             admin status is EnabledInService, EnabledOutOfService,
             Disabled, and DryingUp."
    ::= { sonusSonetMIBNotificationsPrefix 5 }

sonusSonetPathOperStatusNotification NOTIFICATION-TYPE
    OBJECTS         { ifIndex, sonusShelfIndex, sonusSlotIndex, 
                      sonusPortIndex, sonusPathIndex, 
                      sonusSonetOperStatus, sonusEventDescription, 
                      sonusEventClass, sonusEventLevel }
    STATUS          obsolete
    DESCRIPTION     
            "NO LONGER SUPPORTED. This trap indicates the Sonet
             path's operational status has changed."
    ::= { sonusSonetMIBNotificationsPrefix 6 }

sonusSonetPathAlarmNotification NOTIFICATION-TYPE
    OBJECTS         { ifIndex, sonusShelfIndex, sonusSlotIndex, 
                      sonusPortIndex, sonusPathIndex, 
                      sonusSonetAlarmStatus, sonusEventDescription, 
                      sonusEventClass, sonusEventLevel }
    STATUS          current
    DESCRIPTION     
            "This trap indicates the line Path-layer alarm state
             of the Sonet path has changed."
    ::= { sonusSonetMIBNotificationsPrefix 7 }

sonusSonetPathThresholdCrossNotification NOTIFICATION-TYPE
    OBJECTS         { ifIndex, sonusShelfIndex, sonusSlotIndex, 
                      sonusPortIndex, sonusPathIndex, 
                      sonusSonetThresholdType, sonusEventDescription, 
                      sonusEventClass, sonusEventLevel }
    STATUS          current
    DESCRIPTION     
            "This trap indicates that a Path-layer performance
             monitoring threshold has been crossed."
    ::= { sonusSonetMIBNotificationsPrefix 8 }

sonusSonetPortOutOfServiceNotification NOTIFICATION-TYPE
    OBJECTS         { ifIndex, sonusShelfIndex, sonusSlotIndex, 
                      sonusPortIndex, sonusSonetOutOfServiceReason, 
                      sonusEventDescription, sonusEventClass, 
                      sonusEventLevel }
    STATUS          current
    DESCRIPTION     
            "This trap indicates the Sonet port went out of service.
             Reason indicates why the port went out of service. Possible
             reasons include admin or hardware failure."
    ::= { sonusSonetMIBNotificationsPrefix 9 }

sonusSonetPathOutOfServiceNotification NOTIFICATION-TYPE
    OBJECTS         { ifIndex, sonusShelfIndex, sonusSlotIndex, 
                      sonusPortIndex, sonusPathIndex, 
                      sonusSonetOutOfServiceReason, 
                      sonusEventDescription, sonusEventClass, 
                      sonusEventLevel }
    STATUS          current
    DESCRIPTION     
            "This trap indicates the Sonet path went out of service.
             Reason indicates why the port went out of service. Possible
             reasons include admin or hardware failure."
    ::= { sonusSonetMIBNotificationsPrefix 10 }

END -- end of module SONUS-SONET-MIB.
