-- $Id: it-system-mib.mib,v 1.9 2002/01/18 19:08:16 sse Exp $
           ITOUCH-SYSTEM-MIB DEFINITIONS ::= BEGIN

                    IMPORTS
                            Counter, Gauge, TimeTicks,
                            IpAddress
                                    FROM RFC1155-SMI
                            DisplayString, sysLocation
                                    FROM RFC1213-MIB
                            OBJECT-TYPE
                                    FROM RFC-1212
                            TRAP-TYPE
                                    FROM RFC-1215
                            iTouch, AddressType, DateTime,
                            HardwareType, ChassisType, TypedAddress
                                    FROM ITOUCH-MIB;

            xSystem         OBJECT IDENTIFIER ::= { iTouch 1 }

            -- This is a MIB module for all iTouch Communications systems.

            -- Copyright 2000 iTouch Communications, Inc. All Rights Reserved.
            -- Reproduction of this document is authorized on
            -- condition that this copyright notice is included.
            -- This MIB document embodies iTouch Communications, Inc.'s 
            -- proprietary intellectual property.  iTouch Communications, Inc.
            -- retains all title and ownership in this MIB, including any
            -- revisions.
            --
            -- It is iTouch Communications, Inc.'s intent to encourage the
            -- widespread use of this MIB in connection with the management of
            -- iTouch Communications, Inc. products. iTouch Communications,
            -- Inc. grants vendors,end-users, and other interested parties a
            -- non-exclusive license to use this MIB in connection with the
            -- management of iTouch Communications, Inc. products.
            --
            -- This MIB document is supplied "AS IS," and iTouch 
            -- Communications, Inc. makes no warranty, either express or
            -- implied, as to the use operation, condition, or performance of
            -- the MIB.


            -- the System group

            -- Implementation of this group is mandatory for all iTouch
            -- systems.

            sysIdent OBJECT-TYPE
                SYNTAX DisplayString (SIZE (0..50))
                ACCESS read-write
                STATUS mandatory
                DESCRIPTION
                    "An identification string for local and remote 
                    displays.  Corresponds directly to SERVER 
                    IDENTIFICATION and the value labeled 
                    'Identification:' on the SERVER CHARACTERISTICS 
                    display."
                ::= { xSystem 1 }

            sysDefineMode OBJECT-TYPE
                SYNTAX INTEGER { permOnly(1), operAndPerm(2) }
                ACCESS read-write
                STATUS mandatory
                DESCRIPTION
                    "The system's operation with regard to DEFINE 
                    commands.  'permOnly' indicates that DEFINE commands 
                    modify only the permanent data base.  'operAndPerm' 
                    indicates that DEFINE commands modify both 
                    operational and permanent data bases, unless 
                    specifically documented to the contrary.  
                    Corresponds to SERVER CHANGE and the presence of the 
                    label CHANGE in the SERVER CHARACTERISTICS 
                    display."
                ::= { xSystem 2 }

            sysDateTime OBJECT-TYPE
                SYNTAX DateTime
                ACCESS read-write
                STATUS mandatory
                DESCRIPTION
                    "The system's current local date and time.  
                    Corresponds directly to SERVER DATE and SERVER TIME 
                    and the value in various displays."
                ::= { xSystem 3 }

            sysTimeZone OBJECT-TYPE
                SYNTAX OCTET STRING (SIZE (2))
                ACCESS read-write
                STATUS mandatory
                DESCRIPTION
                    "The adjustment to apply to a universal (Greenwich) 
                    time received when down-line loaded, comprising two 
                    octets.  The first octet is the number of hours west 
                    of universal, the second is the number of minutes.  
                    Corresponds directly to SERVER TIMEZONE and the 
                    value labeled 'Timezone:' in the SERVER 
                    CHARACTERISTICS display."
                ::= { xSystem 4 }

            sysLoadSoftware OBJECT-TYPE
                SYNTAX DisplayString (SIZE (0..16))
                ACCESS read-write
                STATUS mandatory
                DESCRIPTION
                    "The software file name to request for down-line 
                    load of the server.  Corresponds directly to SERVER 
                    SOFTWARE, and the value labeled 'Software:' in the 
                    SERVER CHARACTERISTICS display."
                ::= { xSystem 5 }

            sysDump OBJECT-TYPE
                SYNTAX INTEGER { disabled(1), enabled(2) }
                ACCESS read-write
                STATUS mandatory
                DESCRIPTION
                    "Control for dumping the system's memory when the 
                    system crashes.  Corresponds directly to SERVER DUMP 
                    and the presence of 'Dump' under the label 'Enabled 
                    Characteristics' in the SERVER CHARACTERISTICS 
                    display."
                ::= { xSystem 6 }

            sysMaintenancePassword OBJECT-TYPE
                SYNTAX OCTET STRING (SIZE (0..8))
                ACCESS read-write
                STATUS mandatory
                DESCRIPTION
                    "The password a management system must supply to 
                    force the system to reboot or use the system's 
                    remote console via the Maintenance Operation 
                    Protocol (MOP).  Corresponds directly to SERVER 
                    MAINTENANCE PASSWORD.

                    When setting this value, the management system must 
                    supply eight octets, filling with zeros from the 
                    first octet.  That is, the value '1ab42' would be 
                    expressed as '0.0.0.0.0.1.ab.42'.  Setting the value 
                    to zero disables the password check.

                    When returning this value, the agent always returns 
                    a zero length OCTET STRING."
                ::= { xSystem 7 }

            sysLocalName OBJECT-TYPE
                SYNTAX DisplayString (SIZE (1..16))
                ACCESS read-write
                STATUS mandatory
                DESCRIPTION
                    "The system's local name.  Corresponds directly to 
                    SERVER NAME and the value labeled 'Name:' in the 
                    SERVER CHARACTERISTICS display."
                ::= { xSystem 8 }

            sysSoftwareVersionType OBJECT-TYPE
                SYNTAX INTEGER { alpha(1), beta(2),
                                 production(3), special(4) }
                ACCESS read-only
                STATUS mandatory
                DESCRIPTION
                    "The software version variant running in the system.  
                    Corresponds to the letter in the software version in 
                    the SERVER CHARACTERISTICS display.

                    alpha         'A':   alpha test
                    beta          'B':   beta test
                    production    null:  normal, production software
                    special       'S':   special, custom software
                    "
                ::= { xSystem 9 }

            sysSoftwareVersion OBJECT-TYPE
                SYNTAX OCTET STRING (SIZE (4))
                ACCESS read-only
                STATUS mandatory
                DESCRIPTION
                    "The software version running in the system.  In 
                    order, the octets contain major version, minor 
                    version, ECO, and pre-release number.  Corresponds 
                    to the numbers in the software version in the SERVER 
                    CHARACTERISTICS display.

                    For example, the version display for 
                    sysSoftwareVersionType 'production' and 
                    sysSoftwareVersion '2.2.0.0' is 'V2.2'.

                    The version display for sysSoftwareVersionType 
                    'beta' and sysSoftwareVersion '3.1.0.4' is 
                    'V3.1B4'."
                ::= { xSystem 10 }

            sysRomVersion OBJECT-TYPE
                SYNTAX INTEGER
                ACCESS read-only
                STATUS mandatory
                DESCRIPTION
                    "The firmware version of the bootstrap ROM installed 
                    in the system.  Corresponds directly to the value 
                    labeled 'Rom' in the SERVER CHARACTERISTICS 
                    display."
                ::= { xSystem 11 }

            sysHardwareType OBJECT-TYPE
                SYNTAX HardwareType
                ACCESS read-only
                STATUS mandatory
                DESCRIPTION
                    "The type of hardware on which the system is 
                    running.  Corresponds directly to the value labeled 
                    'Hardware Type:' in the UNIT display."
                ::= { xSystem 12 }

            sysHardwareVersion OBJECT-TYPE
                SYNTAX INTEGER
                ACCESS read-only
                STATUS mandatory
                DESCRIPTION
                    "This version of hardware on which the system is 
                    running.  Corresponds directly to part of the value 
                    labeled 'HW' in the SERVER CHARACTERISTICS 
                    display."
                ::= { xSystem 13 }

            sysChassisType OBJECT-TYPE
                SYNTAX ChassisType
                ACCESS read-only
                STATUS mandatory
                DESCRIPTION
                    "The type of chassis in which the system is running.  
                    Corresponds directly to part of the value labeled 
                    'HW' in the SERVER CHARACTERISTICS display."
                ::= { xSystem 14 }

            sysChassisVersion OBJECT-TYPE
                SYNTAX INTEGER
                ACCESS read-only
                STATUS mandatory
                DESCRIPTION
                    "This version of chassis in which the system is 
                    running.  Corresponds directly to part of the value 
                    labeled 'HW' in the SERVER CHARACTERISTICS 
                    display."
                ::= { xSystem 15 }

            sysCrash OBJECT-TYPE
                SYNTAX INTEGER { ready(1), execute(2) }
                ACCESS read-write
                STATUS mandatory
                DESCRIPTION
                    "Control to cause this system to crash.  In response 
                    to a get-request or get-next-request, the agent 
                    always returns 'ready' for this value.  Setting the 
                    value to 'ready' has no effect.  Setting it to 
                    'execute' causes an immediate crash.  Corresponds to 
                    the CRASH command."
            ::= { xSystem 16 }

            sysInitialize OBJECT-TYPE
                SYNTAX INTEGER { ready(1), conditionalExecute(2),
                                 unconditionalExecute(3), cancel(4) }
                ACCESS read-write
                STATUS mandatory
                DESCRIPTION
                    "Control to cause this system to reset its software 
                    to initial load values, typically by reloading.  
                    When executing an initialize command, the system 
                    observes the value of sysInitializeDelay as supplied 
                    anywhere in the same set request with sysInitialize. 
                     If this value is not included in the set request, 
                    the system uses its default value.

                    In response to a get-request or get-next-request, 
                    the agent always returns 'ready' for this value.  

                    Setting the value to 'ready' has no effect.  Setting 
                    it to 'conditionalExecute' causes initialization if 
                    the overall system state is acceptible (such as not 
                    needing to store permanent parameters).  Setting it 
                    to 'unconditionalExecute' causes initialization 
                    regardless of the overall system state.  Setting it 
                    to 'cancel' aborts an initialization that has not 
                    yet started.  According to standard SNMP operation, 
                    if the system is not in a proper state to accept a 
                    given set request for this value, it returns the 
                    standard SNMP error 'badValue'.

                    Corresponds to the INITIALIZE command."
                ::= { xSystem 17 }

            sysInitializeDelay OBJECT-TYPE
                SYNTAX INTEGER (0..32767)
                ACCESS read-write
                STATUS mandatory
                DESCRIPTION
                    "The number of minutes to delay before beginning the 
                    system initialization process as executed with 
                    sysInitialize.

                    This value cannot be set outside a set-request that 
                    contains the value 'execute' for sysInitialize.  If 
                    not included in such a set, the default value is 1.

                    Corresponds to the INITIALIZE command's DELAY 
                    parameter and to the value labeled 'Minutes to 
                    shutdown:' in the SYSTEM STATUS display."
                ::= { xSystem 18 }

            sysZeroAll OBJECT-TYPE
                SYNTAX INTEGER { ready(1), execute(2) }
                ACCESS read-write
                STATUS mandatory
                DESCRIPTION
                    "Control to zero all counters.  In response to a 
                    get-request or get-next-request, the agent always 
                    returns 'ready' for this value.  Setting the value 
                    to 'ready' has no effect.  Setting it to 'execute' 
                    causes all the system's counters to be zeroed.  
                    Corresponds to the ZERO ALL command."
                ::= { xSystem 19 }

            sysZeroBase OBJECT-TYPE
                SYNTAX INTEGER { ready(1), execute(2) }
                ACCESS read-write
                STATUS mandatory
                DESCRIPTION
                    "Control to zero all base counters.  In response to 
                    a get-request or get-next-request, the agent always 
                    returns 'ready' for this value.  Setting the value 
                    to 'ready' has no effect.  Setting it to 'execute' 
                    causes all the system's base counters to be zeroed.  
                    Examples of counters that are zeroed are the SNMP 
                    counters or the counters from the SYSTEM COUNTERS 
                    display.  Examples of counters that are not zeroed 
                    are Ethernet interface counters or port counters.  
                    Corresponds to the ZERO SYSTEM command."
                ::= { xSystem 20 }

            sysZeroBaseTime OBJECT-TYPE
                SYNTAX TimeTicks
                ACCESS read-only
                STATUS mandatory
                DESCRIPTION
                    "The number hundredths of a second since the most 
                    recent zeroing of the base counters, such as through 
                    execution of sysZeroAll or sysZeroBase.  Corresponds 
                    directly to the value labeled 'Seconds Since 
                    Zeroed:' in the SERVER COUNTERS display."
                ::= { xSystem 21 }

            sysLoaderName OBJECT-TYPE
                SYNTAX DisplayString (SIZE (0..40))
                ACCESS read-only
                STATUS mandatory
                DESCRIPTION
                    "The name of the system that provided this system's 
                    running software.  Corresponds directly to the value 
                    labeled 'Primary Host:' in the SERVER STATUS 
                    display."
                ::= { xSystem 22 }

            sysLoaderAddressType OBJECT-TYPE
                SYNTAX AddressType
                ACCESS read-only
                STATUS mandatory
                DESCRIPTION
                    "The type of network address contained in 
                    sysLoaderAddress.  'unknown' means no address has 
                    been defined.  'other' means no other type value 
                    applies.  'local' means there is no address and this 
                    system's software was loaded from local storage.  
                    'ip' is an Internet IP address.  'ethernet' is an 
                    802.3 MAC address.  Corresponds indirectly to the 
                    value labeled 'Load Address:' in the SERVER STATUS 
                    display."
                ::= { xSystem 23 }

            sysLoaderAddress OBJECT-TYPE
                SYNTAX OCTET STRING
                ACCESS read-only
                STATUS mandatory
                DESCRIPTION
                    "The network address of the system that provided 
                    this system's running software.  Corresponds 
                    directly to the value labeled 'Load Address:' in the 
                    SERVER STATUS display."
                ::= { xSystem 24 }

            sysDumperAddressType OBJECT-TYPE
                SYNTAX AddressType
                ACCESS read-only
                STATUS mandatory
                DESCRIPTION
                    "The type of network address contained in 
                    sysDumperAddress.  'unknown' means no address has 
                    been defined.  'other' means no other type value 
                    applies.  'local' means there is no address and this 
                    system's was dumped to local storage.  'ip' is an 
                    Internet IP address.  'ethernet' is an 802.3 MAC 
                    address.  Corresponds indirectly to the value 
                    labeled 'Dump Address:' in the SERVER STATUS 
                    display."
                ::= { xSystem 25 }

            sysDumperAddress OBJECT-TYPE
                SYNTAX OCTET STRING
                ACCESS read-only
                STATUS mandatory
                DESCRIPTION
                    "The network address of the system that most 
                    recently accepted a crash dump from this system.  
                    Corresponds directly to the value labeled 'Dump 
                    Address:' in the SERVER STATUS display."
                ::= { xSystem 26 }

            sysResourceLacks OBJECT-TYPE
                SYNTAX Counter
                ACCESS read-only
                STATUS mandatory
                DESCRIPTION
                    "The number of times a local resource allocation 
                    failed, for example due to lack of dynamic memory.  
                    Corresponds directly to the value labeled 'Resource 
                    Errors:' in the SERVER STATUS display."
                ::= { xSystem 27 }

            sysChassisState OBJECT-TYPE
                SYNTAX INTEGER { notApplicable(1), noFault(2), fault(3),
                                 loop(4) }
                ACCESS read-only
                STATUS mandatory
                DESCRIPTION
                    "For chassis-based systems, the state of the overall 
                    chassis.  'notApplicable' indicates the system is 
                    not chassis based.  'noFault' indicates no current 
                    chassis problem.  'fault' indicates a current 
                    chassis problem such as a card or power supply 
                    failure.  Corresponds directly to the value labeled 
                    'Crate Current State: in the SERVER ALTERNATE STATUS 
                    display."
                ::= { xSystem 28 }

            sysChassisFaultTransitions OBJECT-TYPE
                SYNTAX Counter
                ACCESS read-only
                STATUS mandatory
                DESCRIPTION
                    "The number of times this system has seen 
                    sysChassisState switch from 'noFault' to 'fault' or 
                    from 'fault' to 'noFault'.  Corresponds directly to 
                    the value labeled 'Crate Transition Count: in the 
                    SERVER ALTERNATE STATUS display."
                ::= { xSystem 29 }

            sysResourceNumber OBJECT-TYPE
                SYNTAX INTEGER
                ACCESS read-only
                STATUS mandatory
                DESCRIPTION
                    "The number of resource entries in the Resource 
                    table."
                ::= { xSystem 30 }

            sysFeatureNumber OBJECT-TYPE
                SYNTAX INTEGER
                ACCESS read-only
                STATUS mandatory
                DESCRIPTION
                    "The number of feature entries in the Feature 
                    table."
                ::= { xSystem 31 }

            -- more base objects following tables


            -- the Resource table

            resTable OBJECT-TYPE
                SYNTAX SEQUENCE OF ResEntry
                ACCESS not-accessible
                STATUS mandatory
                DESCRIPTION
                    "A list of resource entries.  The number of entries 
                    is given by the value of sysResourceNumber."
                ::= { xSystem 32 }

            resEntry OBJECT-TYPE
                SYNTAX ResEntry
                ACCESS not-accessible
                STATUS mandatory
                DESCRIPTION
                    "Status values for a system resource."
                INDEX { resType }
                ::= { resTable 1 }

            ResEntry ::=
                SEQUENCE {
                    resType
                        INTEGER,
                    resCurrent
                        Gauge,
                    resWorst
                        Gauge,
                    resAdminMaximum
                        INTEGER,
                    resLacks
                        Counter,
                    resLackTime
                        DateTime,
                    resOperMaximum
                        INTEGER
                }

            resType OBJECT-TYPE
                SYNTAX INTEGER { cpuPercent(1), memoryPercent(2),
                                 process(3), timer(4), packetBuffer(5),
                                 ipcMessage(6), textPool(7),
                                 freeMemory(8), globalMemoryPercent(9),
                                 phivDecnetRouteCache(10),
                                 ipFilterCache(11), ipRouteCache(12),
                                 ipxRouteCache(13), ipPolicyTable(14),
                                 ipFilterTable(15),
                                 phivDecnetPolicyTable(16),
                                 phivDecnetFilterTable(17),
                                 appleRouteCache(18),
                                 appleFilterTable(19),
                                 repeaterPortAccessTable(20),
                                 repeaterPortNameTable(21),
                                 ipxRipTable(22), ipxSapTable(23),
                                 repeaterPortSecurityTable(24),
                                 bridgeFilterTable(25),
                                 bridgeStaticFilters(26),
                                 bridgeSourceFilters(27),
                                 bridgeLearnedFilters(28),
                                 bridgeInactiveFilters(29),
                                 bridgeProtocolFilters(30),
                                 latAnnouncementCompressionTable(31),
                                 packetCompressionTable(32),
                                 ipFragmentTable(33),
                                 repeaterRedundancyTable(34),
                                 repeaterGlobalSecurityTable(35),
				 packetHeaders(36), interfaces(37),
				 circuits(38), ipIgmpTable(39),
				 ipMulticastTable(40), ipRouteTable(41),
				 ipxRipFilterTable(42), ipxSapFilterTable(43)
                               }
                ACCESS read-only
                STATUS mandatory
                DESCRIPTION
                    "Identification of a resource type.  Typically 
                    corresponds directly to a label such as 'Processes:' 
                    in the SERVER ALTERNATE STATUS display."
                ::= { resEntry 1 }

            resCurrent OBJECT-TYPE
                SYNTAX Gauge
                ACCESS read-only
                STATUS mandatory
                DESCRIPTION
                    "The number of resources currently in use on the 
                    system.  Typically corresponds directly to a value 
                    labeled 'Cur' in the SERVER ALTERNATE STATUS 
                    display."
                ::= { resEntry 2 }

            resWorst OBJECT-TYPE
                SYNTAX Gauge
                ACCESS read-only
                STATUS mandatory
                DESCRIPTION
                    "The highest or lowest value of resCurrent since 
                    system initialization.  Typically corresponds 
                    directly to a value labeled 'High' or 'Low' in the 
                    SERVER ALTERNATE STATUS display."
                ::= { resEntry 3 }

            resAdminMaximum OBJECT-TYPE
                SYNTAX INTEGER
                ACCESS read-write
                STATUS mandatory
                DESCRIPTION
                    "The desired maximum possible number of resources in 
                    the system.  In many cases, ACCESS to this object 
                    for a particular resType is read-only.  Typically 
                    corresponds directly to a value labeled 'Max' in the 
                    SERVER ALTERNATE STATUS display for desired, 
                    administrative values.  When the desired change 
                    takes effect is implementation specific, ranging 
                    from immediately to the next system initialization."
                ::= { resEntry 4 }

            resLacks OBJECT-TYPE
                SYNTAX Counter
                ACCESS read-only
                STATUS mandatory
                DESCRIPTION
                    "The number of times since system initialization 
                    that the system could not obtain the resource 
                    because none were available.  Typically corresponds 
                    directly to a value labeled 'Failure' in the SERVER 
                    ALTERNATE STATUS display.

                    If such failures do not apply to the particular 
                    resource, such as 'cpuPercent', the agent returns 
                    zero for this object."
                ::= { resEntry 5 }

            resLackTime OBJECT-TYPE
                SYNTAX DateTime
                ACCESS read-only
                STATUS mandatory
                DESCRIPTION
                    "The local system date and time when resLack last 
                    increased.  Typically corresponds directly to a 
                    value labeled 'Last Occurred' in the SERVER 
                    ALTERNATE STATUS display.

                    If such failures do not apply to the particular 
                    resource, such as 'cpuPercent', the agent returns 
                    all zeroes (unknown) for this object."
            ::= { resEntry 6 }

            resOperMaximum OBJECT-TYPE
                SYNTAX INTEGER
                ACCESS read-only
                STATUS mandatory
                DESCRIPTION
                    "The current maximum possible number of resources in 
                    the system.  Typically corresponds directly to a 
                    value labeled 'Max' in the SERVER ALTERNATE STATUS 
                    display for current operational values.  This value 
                    is based on current or previous value of 
                    resAdminMaximum."
                ::= { resEntry 7 }


            -- the Feature table

            featTable OBJECT-TYPE
                SYNTAX SEQUENCE OF FeatEntry
                ACCESS not-accessible
                STATUS mandatory
                DESCRIPTION
                    "A list of feature entries.  The number of entries 
                    is given by the value of sysFeatureNumber."
                ::= { xSystem 33 }

            featEntry OBJECT-TYPE
                SYNTAX FeatEntry
                ACCESS not-accessible
                STATUS mandatory
                DESCRIPTION
                    "Status values for a system feature."
                INDEX { featType }
                ::= { featTable 1 }

            FeatEntry ::=
                SEQUENCE {
                    featType
                        INTEGER,
                    featStatus
                        INTEGER,
                    featKey
                        DisplayString
                }

            featType OBJECT-TYPE
                SYNTAX INTEGER { help(1), snmp(2), xremote(3),
                                 tn3270(4), menu(5), multisessions(6),
                                 lat(7), eventLog(8),
                                 internetSecurity(9), slip(10),
                                 scriptServer(11), kerberos(12),
                                 telnet(13), rlogin(14), allPorts(15),
                                 xprinter(16), x25(17),
                                 frameRelay(18),
                                 ipMulticastSpecial(19),
                                 changeEthernetAddress(20),
                                 expanded800(21), lpDaemon(22),
                                 ppp(23), unixCommands(24),
                                 arap(25), fingerDaemon(26),
                                 routeDaemon(27), rwhoDaemon(28),
                                 securID(29), apd(30), ipxRouting(31),
                		 ipxFiltering(32), ipFiltering(33), 
                                 kerberos5(34), radius(35), 
                                 enviromentalManager(36), terminalServer(37),
                                 ssh(38), tl1(39) }
                ACCESS read-only
                STATUS mandatory
                DESCRIPTION
                    "Identification of a feature type.  Corresponds to a 
                    SERVER feature keyword."
                ::= { featEntry 1 }

            featStatus OBJECT-TYPE
                SYNTAX INTEGER { disabled(1), enabled(2), locked(3) }
                ACCESS read-write
                STATUS mandatory
                DESCRIPTION
                    "The status of the feature as of the next system 
                    initialization.  Corresponds to the presence of the 
                    feature's lable following the label 'Enabled 
                    Feature(s): in the UNIT display."
                ::= { featEntry 2 }

            featKey OBJECT-TYPE
                SYNTAX DisplayString (SIZE (8))
                ACCESS read-write
                STATUS mandatory
                DESCRIPTION
                    "The key a management system must supply to make a 
                    locked feature available.  When unlocking a feature 
                    and the management system does not supply a value 
                    for featStatus, that object's value is 
                    implementation dependent.

                    When returning this value, the agent always returns 
                    a zero length DisplayString."
                ::= { featEntry 3 }


            -- the Boot Control group

            -- The Boot Control group contains parameters to control
            -- how a system loads and dumps its runtime software and
            -- parameters.  Typically these parameters are kept for
            -- and used by system initialization firmware.

            -- This group is deprecated in favor of the Boot Control
            -- Record table, found later in this MIB.

            xBootControl OBJECT IDENTIFIER ::= { xSystem 34 }

            bootControlLoadInternetFile OBJECT-TYPE
                SYNTAX DisplayString (SIZE (0..64))
                ACCESS read-write
                STATUS deprecated
                DESCRIPTION
                    "The filename to request when loading an image via 
                    TFTP.  Corresponds directly to SERVER INTERNET LOAD 
                    FILE and the value labeled 'Internet Load File:' in 
                    the SERVER BOOT CHARACTERISTICS display."
                ::= { xBootControl 1 }

            bootControlLoadInternetServer OBJECT-TYPE
                SYNTAX IpAddress
                ACCESS read-write
                STATUS deprecated
                DESCRIPTION
                    "The internet address of the server to use when 
                    loading an image via TFTP.  Corresponds directly to 
                    SERVER INTERNET LOAD HOST and the value labeled 
                    'Internet Load Host:' in the SERVER BOOT 
                    CHARACTERISTICS display."
                ::= { xBootControl 2 }

            bootControlLoadInternetGateway OBJECT-TYPE
                SYNTAX IpAddress
                ACCESS read-write
                STATUS deprecated
                DESCRIPTION
                    "The internet address of the gateway to use when 
                    loading an image via TFTP.  Corresponds directly to 
                    SERVER INTERNET LOAD GATEWAY and the value labeled 
                    'Internet Load Gateway:' in the SERVER BOOT 
                    CHARACTERISTICS display."
                ::= { xBootControl 3 }

            bootControlLoadBootpTftp OBJECT-TYPE
                SYNTAX INTEGER { disabled(1), enabled(2) }
                ACCESS read-write
                STATUS deprecated
                DESCRIPTION
                    "Control for loading via the combination of BOOTP 
                    and TFTP.  Corresponds to SERVER LOAD PROTOCOL 
                    BOOTPTFTP and the presence of 'BOOTP/TFTP/' 
                    following the label 'Load Protocols Enabled:' in the 
                    SERVER BOOT CHARACTERISTICS display."
                ::= { xBootControl 4 }

            bootControlLoadTftpDirect OBJECT-TYPE
                SYNTAX INTEGER { disabled(1), enabled(2) }
                ACCESS read-write
                STATUS deprecated
                DESCRIPTION
                    "Control for loading via directed TFTP.  Corresponds 
                    to SERVER LOAD PROTOCOL TFTPDIRECT and the presence 
                    of 'TFTPDIRECT' following the label 'Load Protocols 
                    Enabled:' in the SERVER BOOT CHARACTERISTICS 
                    display."
                ::= { xBootControl 5 }

            bootControlLoadLocal OBJECT-TYPE
                SYNTAX INTEGER { disabled(1), enabled(2) }
                ACCESS read-write
                STATUS deprecated
                DESCRIPTION
                    "Control for loading from a local medium.  
                    Corresponds to SERVER LOAD PROTOCOL LOCAL and the 
                    presence of 'LOCAL' following the label 'Load 
                    Protocols Enabled:' in the SERVER BOOT 
                    CHARACTERISTICS display."
                ::= { xBootControl 6 }

            bootControlLoadMop OBJECT-TYPE
                SYNTAX INTEGER { disabled(1), enabled(2) }
                ACCESS read-write
                STATUS deprecated
                DESCRIPTION
                    "Control for loading via DEC MOP.  Corresponds to 
                    SERVER LOAD PROTOCOL MOP and the presence of 'MOP' 
                    following the label 'Load Protocols Enabled:' in the 
                    SERVER BOOT CHARACTERISTICS display."
                ::= { xBootControl 7 }

            bootControlLoadProprietary OBJECT-TYPE
                SYNTAX INTEGER { disabled(1), enabled(2) }
                ACCESS read-write
                STATUS deprecated
                DESCRIPTION
                    "Control for loading via ITouch-proprietary extended 
                    MOP.  Corresponds to SERVER LOAD PROTOCOL 
                    PROPRIETARY and the presence of 'Proprietary' 
                    following the label 'Load Protocols Enabled:' in the 
                    SERVER BOOT CHARACTERISTICS display."
                ::= { xBootControl 8 }

            bootControlLoadRarpTftp OBJECT-TYPE
                SYNTAX INTEGER { disabled(1), enabled(2) }
                ACCESS read-write
                STATUS deprecated
                DESCRIPTION
                    "Control for loading via the combination of RARP and 
                    TFTP.  Corresponds to SERVER LOAD PROTOCOL RARPTFTP 
                    and the presence of 'RARP/TFTP' following the label 
                    'Load Protocols Enabled:' in the SERVER BOOT 
                    CHARACTERISTICS display."
                ::= { xBootControl 9 }

            bootControlDumpBootpTftp OBJECT-TYPE
                SYNTAX INTEGER { disabled(1), enabled(2) }
                ACCESS read-write
                STATUS deprecated
                DESCRIPTION
                    "Control for dumping via the combination of BOOTP 
                    and TFTP.  Corresponds to SERVER DUMP PROTOCOL 
                    BOOTPTFTP and the presence of 'BOOTP/TFTP' following 
                    the label 'Dump Protocols Enabled:' in the SERVER 
                    BOOT CHARACTERISTICS display."
                ::= { xBootControl 10 }

            bootControlDumpLocal OBJECT-TYPE
                SYNTAX INTEGER { disabled(1), enabled(2) }
                ACCESS read-write
                STATUS deprecated
                DESCRIPTION
                    "Control for dumping to a local medium.  Corresponds 
                    to SERVER DUMP PROTOCOL LOCAL and the presence of 
                    'Local' following the label 'Dump Protocols 
                    Enabled:' in the SERVER BOOT CHARACTERISTICS 
                    display."
                ::= { xBootControl 11 }

            bootControlDumpMop OBJECT-TYPE
                SYNTAX INTEGER { disabled(1), enabled(2) }
                ACCESS read-write
                STATUS deprecated
                DESCRIPTION
                    "Control for dumping via DEC MOP.  Corresponds to 
                    SERVER DUMP PROTOCOL MOP and the presence of 'MOP' 
                    following the label 'Dump Protocols Enabled:' in the 
                    SERVER BOOT CHARACTERISTICS display."
                ::= { xBootControl 12 }

            bootControlDumpProprietary OBJECT-TYPE
                SYNTAX INTEGER { disabled(1), enabled(2) }
                ACCESS read-write
                STATUS deprecated
                DESCRIPTION
                    "Control for dumping via ITouch-proprietary extended 
                    MOP.  Corresponds to SERVER DUMP PROTOCOL 
                    PROPRIETARY and the presence of 'Proprietary' 
                    following the label 'Dump Protocols Enabled:' in the 
                    SERVER BOOT CHARACTERISTICS display."
                ::= { xBootControl 13 }

            bootControlDumpRarpTftp OBJECT-TYPE
                SYNTAX INTEGER { disabled(1), enabled(2) }
                ACCESS read-write
                STATUS deprecated
                DESCRIPTION
                    "Control for dumping via the combination of RARP and 
                    TFTP.  Corresponds to SERVER DUMP PROTOCOL RARPTFTP 
                    and the presence of 'RARP/TFTP' following the label 
                    'Dump Protocols Enabled:' in the SERVER BOOT 
                    CHARACTERISTICS display."
                ::= { xBootControl 14 }

            bootControlParamBootpTftp OBJECT-TYPE
                SYNTAX INTEGER { disabled(1), enabled(2) }
                ACCESS read-write
                STATUS deprecated
                DESCRIPTION
                    "Control for loading parameters via the combination 
                    of BOOTP and TFTP.  Corresponds to SERVER PARAMETER 
                    PROTOCOL MOP and the presence of 'BOOTP/TFTP' 
                    following the label 'Parameter Protocols Enabled:' 
                    in the SERVER BOOT CHARACTERISTICS display."
                ::= { xBootControl 15 }

            bootControlParamLocal OBJECT-TYPE
                SYNTAX INTEGER { disabled(1), enabled(2) }
                ACCESS read-write
                STATUS deprecated
                DESCRIPTION
                    "Control for loading parameters from a local medium.  
                    Corresponds to SERVER PARAMETER PROTOCOL LOCAL and 
                    the presence of 'LOCAL' following the label 
                    'Parameter Protocols Enabled:' in the SERVER BOOT 
                    CHARACTERISTICS display."
                ::= { xBootControl 16 }

            bootControlParamMop OBJECT-TYPE
                SYNTAX INTEGER { disabled(1), enabled(2) }
                ACCESS read-write
                STATUS deprecated
                DESCRIPTION
                    "Control for loading parameters via DEC MOP.  
                    Corresponds to SERVER PARAMETER PROTOCOL MOP and the 
                    presence of 'MOP' following the label 'Parameter 
                    Protocols Enabled:' in the SERVER BOOT 
                    CHARACTERISTICS display."
                ::= { xBootControl 17 }

            bootControlParamProprietary OBJECT-TYPE
                SYNTAX INTEGER { disabled(1), enabled(2) }
                ACCESS read-write
                STATUS deprecated
                DESCRIPTION
                    "Control for loading parameters via 
                    ITouch-proprietary extended MOP.  Corresponds to 
                    SERVER PARAMETER PROTOCOL PROPRIETARY and the 
                    presence of 'Proprietary' following the label 
                    'Parameter Protocols Enabled:' in the SERVER BOOT 
                    CHARACTERISTICS display."
                ::= { xBootControl 18 }

            bootControlParamRarpTftp OBJECT-TYPE
                SYNTAX INTEGER { disabled(1), enabled(2) }
                ACCESS read-write
                STATUS deprecated
                DESCRIPTION
                    "Control for loading parameters via the combination 
                    of RARP and TFTP.  Corresponds to SERVER PARAMETER 
                    PROTOCOL RARPTFTP and the presence of 'RARP/TFTP' 
                    following the label 'Parameter Protocols Enabled:' 
                    in the SERVER BOOT CHARACTERISTICS display."
                ::= { xBootControl 19 }


            -- the System group, basic parameters continued

            sysInstalledMemory OBJECT-TYPE
                SYNTAX Gauge
                ACCESS read-only
                STATUS mandatory
                DESCRIPTION
                    "The total number of bytes of main memory installed 
                    in the system.  Corresponds directly to the value 
                    labeled 'Installed' on the SERVER ALTERNATE STATUS 
                    display.  A value of 0 indicates standard memory for 
                    the particular hardware."
                ::= { xSystem 35 }

            sysTemperatureLevel OBJECT-TYPE
                SYNTAX INTEGER { unknown(1), normal(2), high(3) }
                ACCESS read-only
                STATUS mandatory
                DESCRIPTION
                    "The temperature level of the system.  'unknown' 
                    indicates the system does not support a temperature 
                    sensor.  'normal' indicates a normal temperature 
                    level.  'high' indicates an excessive temperature 
                    level.  Corresponds directly to the value labeled 
                    'Temperature Level:' in the SERVER ALTERNATE STATUS 
                    display."
                ::= { xSystem 36 }

            -- basic parameters continue after boot record table


            -- the Boot Control Record table

            -- The Boot Control Record table contains parameters to
            -- control how a system loads and dumps its runtime
            -- software and parameters.  Typically these parameters
            -- are kept for and used by system initialization firmware.

            -- This table is mandatory for systems that offer runtime
            -- control of these parameters, and empty in systems
            -- that do not.

            bootRecordTable OBJECT-TYPE
                SYNTAX SEQUENCE OF BootRecordEntry
                ACCESS not-accessible
                STATUS mandatory
                DESCRIPTION
                    "A list of boot control records."
                ::= { xSystem 37 }

            bootRecordEntry OBJECT-TYPE
                SYNTAX BootRecordEntry
                ACCESS not-accessible
                 STATUS mandatory
                DESCRIPTION
                    "Values for a boot record."
                INDEX { bootRecordIndex }
                ::= { bootRecordTable 1 }

            BootRecordEntry ::=
                SEQUENCE {
                    bootRecordIndex
                        INTEGER,
                    bootRecordLoadInternetFile
                        DisplayString,
                    bootRecordLoadInternetServer
                        IpAddress,
                    bootRecordLoadInternetGateway
                        IpAddress,
                    bootRecordLoadBootpTftp
                        INTEGER,
                    bootRecordLoadTftpDirect
                        INTEGER,
                    bootRecordLoadLocal
                        INTEGER,
                    bootRecordLoadMop
                        INTEGER,
                    bootRecordLoadProprietary
                        INTEGER,
                    bootRecordLoadRarpTftp
                        INTEGER,
                    bootRecordDumpBootpTftp
                        INTEGER,
                    bootRecordDumpLocal
                        INTEGER,
                    bootRecordDumpMop
                        INTEGER,
                    bootRecordDumpProprietary
                        INTEGER,
                    bootRecordDumpRarpTftp
                        INTEGER,
                    bootRecordParamBootpTftp
                        INTEGER,
                    bootRecordParamLocal
                        INTEGER,
                    bootRecordParamMop
                        INTEGER,
                    bootRecordParamProprietary
                        INTEGER,
                    bootRecordParamRarpTftp
                        INTEGER,
                    bootRecordStatus
                        INTEGER,
                    bootRecordMopFile
                        DisplayString,
                    bootRecordInternetAddress
                        IpAddress,
                    bootRecordParamTftpDirect
                        INTEGER,
                    bootRecordInternetDelimiter 
                        DisplayString 
                }

            bootRecordIndex OBJECT-TYPE
                SYNTAX INTEGER
                ACCESS read-only
                STATUS mandatory
                DESCRIPTION
                    "An index value that uniquely identifies a boot 
                    control record entry, from 1 to the number of 
                    entries for the system."
                ::= { bootRecordEntry 1 }

            bootRecordLoadInternetFile OBJECT-TYPE
                SYNTAX DisplayString (SIZE (0..64))
                ACCESS read-write
                STATUS mandatory
                DESCRIPTION
                    "The filename to request when loading an image via 
                    TFTP.  Corresponds directly to SERVER INTERNET LOAD 
                    FILE and the value labeled 'Internet Load File:' in 
                    the SERVER BOOT CHARACTERISTICS display."
                ::= { bootRecordEntry 2 }

            bootRecordLoadInternetServer OBJECT-TYPE
                SYNTAX IpAddress
                ACCESS read-write
                STATUS mandatory
                DESCRIPTION
                    "The internet address of the server to use when 
                    loading an image via TFTP.  Corresponds directly to 
                    SERVER INTERNET LOAD HOST and the value labeled 
                    'Internet Load Host:' in the SERVER BOOT 
                    CHARACTERISTICS display."
                ::= { bootRecordEntry 3 }

            bootRecordLoadInternetGateway OBJECT-TYPE
                SYNTAX IpAddress
                ACCESS read-write
                STATUS mandatory
                DESCRIPTION
                    "The internet address of the gateway to use when 
                    loading an image via TFTP.  Corresponds directly to 
                    SERVER INTERNET LOAD GATEWAY and the value labeled 
                    'Internet Load Gateway:' in the SERVER BOOT 
                    CHARACTERISTICS display."
                ::= { bootRecordEntry 4 }

            bootRecordLoadBootpTftp OBJECT-TYPE
                SYNTAX INTEGER { disabled(1), enabled(2) }
                ACCESS read-write
                STATUS mandatory
                DESCRIPTION
                    "Control for loading via the combination of BOOTP 
                    and TFTP.  Corresponds to SERVER LOAD PROTOCOL 
                    BOOTPTFTP and the presence of 'BOOTP/TFTP/' 
                    following the label 'Load Protocols Enabled:' in the 
                    SERVER BOOT CHARACTERISTICS display."
                ::= { bootRecordEntry 5 }

            bootRecordLoadTftpDirect OBJECT-TYPE
                SYNTAX INTEGER { disabled(1), enabled(2) }
                ACCESS read-write
                STATUS mandatory
                DESCRIPTION
                    "Control for loading via directed TFTP.  Corresponds 
                    to SERVER LOAD PROTOCOL TFTPDIRECT and the presence 
                    of 'TFTPDIRECT' following the label 'Load Protocols 
                    Enabled:' in the SERVER BOOT CHARACTERISTICS 
                    display."
                ::= { bootRecordEntry 6 }

            bootRecordLoadLocal OBJECT-TYPE
                SYNTAX INTEGER { disabled(1), enabled(2) }
                ACCESS read-write
                STATUS mandatory
                DESCRIPTION
                    "Control for loading from a local medium.  
                    Corresponds to SERVER LOAD PROTOCOL LOCAL and the 
                    presence of 'LOCAL' following the label 'Load 
                    Protocols Enabled:' in the SERVER BOOT 
                    CHARACTERISTICS display."
                ::= { bootRecordEntry 7 }

            bootRecordLoadMop OBJECT-TYPE
                SYNTAX INTEGER { disabled(1), enabled(2) }
                ACCESS read-write
                STATUS mandatory
                DESCRIPTION
                    "Control for loading via DEC MOP.  Corresponds to 
                    SERVER LOAD PROTOCOL MOP and the presence of 'MOP' 
                    following the label 'Load Protocols Enabled:' in the 
                    SERVER BOOT CHARACTERISTICS display."
                ::= { bootRecordEntry 8 }

            bootRecordLoadProprietary OBJECT-TYPE
                SYNTAX INTEGER { disabled(1), enabled(2) }
                ACCESS read-write
                STATUS mandatory
                DESCRIPTION
                    "Control for loading via ITouch-proprietary extended 
                    MOP.  Corresponds to SERVER LOAD PROTOCOL 
                    PROPRIETARY and the presence of 'Proprietary' 
                    following the label 'Load Protocols Enabled:' in the 
                    SERVER BOOT CHARACTERISTICS display."
                ::= { bootRecordEntry 9 }

            bootRecordLoadRarpTftp OBJECT-TYPE
                SYNTAX INTEGER { disabled(1), enabled(2) }
                ACCESS read-write
                STATUS mandatory
                DESCRIPTION
                    "Control for loading via the combination of RARP and 
                    TFTP.  Corresponds to SERVER LOAD PROTOCOL RARPTFTP 
                    and the presence of 'RARP/TFTP' following the label 
                    'Load Protocols Enabled:' in the SERVER BOOT 
                    CHARACTERISTICS display."
                ::= { bootRecordEntry 10 }

            bootRecordDumpBootpTftp OBJECT-TYPE
                SYNTAX INTEGER { disabled(1), enabled(2) }
                ACCESS read-write
                STATUS mandatory
                DESCRIPTION
                    "Control for dumping via the combination of BOOTP 
                    and TFTP.  Corresponds to SERVER DUMP PROTOCOL 
                    BOOTPTFTP and the presence of 'BOOTP/TFTP' following 
                    the label 'Dump Protocols Enabled:' in the SERVER 
                    BOOT CHARACTERISTICS display."
                ::= { bootRecordEntry 11 }

            bootRecordDumpLocal OBJECT-TYPE
                SYNTAX INTEGER { disabled(1), enabled(2) }
                ACCESS read-write
                STATUS mandatory
                DESCRIPTION
                    "Control for dumping to a local medium.  Corresponds 
                    to SERVER DUMP PROTOCOL LOCAL and the presence of 
                    'Local' following the label 'Dump Protocols 
                    Enabled:' in the SERVER BOOT CHARACTERISTICS 
                    display."
                ::= { bootRecordEntry 12 }

            bootRecordDumpMop OBJECT-TYPE
                SYNTAX INTEGER { disabled(1), enabled(2) }
                ACCESS read-write
                STATUS mandatory
                DESCRIPTION
                    "Control for dumping via DEC MOP.  Corresponds to 
                    SERVER DUMP PROTOCOL MOP and the presence of 'MOP' 
                    following the label 'Dump Protocols Enabled:' in the 
                    SERVER BOOT CHARACTERISTICS display."
                ::= { bootRecordEntry 13 }

            bootRecordDumpProprietary OBJECT-TYPE
                SYNTAX INTEGER { disabled(1), enabled(2) }
                ACCESS read-write
                STATUS mandatory
                DESCRIPTION
                    "Control for dumping via ITouch-proprietary extended 
                    MOP.  Corresponds to SERVER DUMP PROTOCOL 
                    PROPRIETARY and the presence of 'Proprietary' 
                    following the label 'Dump Protocols Enabled:' in the 
                    SERVER BOOT CHARACTERISTICS display."
                ::= { bootRecordEntry 14 }

            bootRecordDumpRarpTftp OBJECT-TYPE
                SYNTAX INTEGER { disabled(1), enabled(2) }
                ACCESS read-write
                STATUS mandatory
                DESCRIPTION
                    "Control for dumping via the combination of RARP and 
                    TFTP.  Corresponds to SERVER DUMP PROTOCOL RARPTFTP 
                    and the presence of 'RARP/TFTP' following the label 
                    'Dump Protocols Enabled:' in the SERVER BOOT 
                    CHARACTERISTICS display."
                ::= { bootRecordEntry 15 }

            bootRecordParamBootpTftp OBJECT-TYPE
                SYNTAX INTEGER { disabled(1), enabled(2) }
                ACCESS read-write
                STATUS mandatory
                DESCRIPTION
                    "Control for loading parameters via the combination 
                    of BOOTP and TFTP.  Corresponds to SERVER PARAMETER 
                    PROTOCOL MOP and the presence of 'BOOTP/TFTP' 
                    following the label 'Parameter Protocols Enabled:' 
                    in the SERVER BOOT CHARACTERISTICS display."
                ::= { bootRecordEntry 16 }

            bootRecordParamLocal OBJECT-TYPE
                SYNTAX INTEGER { disabled(1), enabled(2) }
                ACCESS read-write
                STATUS mandatory
                DESCRIPTION
                    "Control for loading parameters from a local medium.  
                    Corresponds to SERVER PARAMETER PROTOCOL LOCAL and 
                    the presence of 'LOCAL' following the label 
                    'Parameter Protocols Enabled:' in the SERVER BOOT 
                    CHARACTERISTICS display."
                ::= { bootRecordEntry 17 }

            bootRecordParamMop OBJECT-TYPE
                SYNTAX INTEGER { disabled(1), enabled(2) }
                ACCESS read-write
                STATUS mandatory
                DESCRIPTION
                    "Control for loading parameters via DEC MOP.  
                    Corresponds to SERVER PARAMETER PROTOCOL MOP and the 
                    presence of 'MOP' following the label 'Parameter 
                    Protocols Enabled:' in the SERVER BOOT 
                    CHARACTERISTICS display."
                ::= { bootRecordEntry 18 }

            bootRecordParamProprietary OBJECT-TYPE
                SYNTAX INTEGER { disabled(1), enabled(2) }
                ACCESS read-write
                STATUS mandatory
                DESCRIPTION
                    "Control for loading parameters via 
                    ITouch-proprietary extended MOP.  Corresponds to 
                    SERVER PARAMETER PROTOCOL PROPRIETARY and the 
                    presence of 'Proprietary' following the label 
                    'Parameter Protocols Enabled:' in the SERVER BOOT 
                    CHARACTERISTICS display."
                ::= { bootRecordEntry 19 }

            bootRecordParamRarpTftp OBJECT-TYPE
                SYNTAX INTEGER { disabled(1), enabled(2) }
                ACCESS read-write
                STATUS mandatory
                DESCRIPTION
                    "Control for loading parameters via the combination 
                    of RARP and TFTP.  Corresponds to SERVER PARAMETER 
                    PROTOCOL RARPTFTP and the presence of 'RARP/TFTP' 
                    following the label 'Parameter Protocols Enabled:' 
                    in the SERVER BOOT CHARACTERISTICS display."
                ::= { bootRecordEntry 20 }

            bootRecordStatus OBJECT-TYPE
                SYNTAX INTEGER { disabled(1), enabled(2) }
                ACCESS read-write
                STATUS mandatory
                DESCRIPTION
               "The status of the entry.  Set to 'disabled' to
               disable the entry."
                ::= { bootRecordEntry 21 }

            bootRecordMopFile OBJECT-TYPE
                SYNTAX DisplayString (SIZE (0..15))
                ACCESS read-write
                STATUS mandatory
                DESCRIPTION
                    "The software file name to request for down-line 
                    load of the server via MOP or XMOP."
                ::= { bootRecordEntry 22 }

            bootRecordInternetAddress OBJECT-TYPE
                SYNTAX IpAddress
                ACCESS read-write
                STATUS mandatory
                DESCRIPTION
                    "The internet address of the system is to use for 
                    itself when loading via TFTP.  The value 0.0.0.0 
                    indicates default action."
                ::= { bootRecordEntry 23 }

            bootRecordParamTftpDirect OBJECT-TYPE
                SYNTAX INTEGER { disabled(1), enabled(2) }
                ACCESS read-write
                STATUS mandatory
                DESCRIPTION
                    "Control for loading parameters via the protocol
                    DTFTP.  Corresponds to SERVER PARAMETER 
                    PROTOCOL DTFTP and the presence of 'DTFTP' 
                    following the label 'Parameter Protocols Enabled:' 
                    in the SERVER BOOT CHARACTERISTICS display."
                ::= { bootRecordEntry 24 }

            bootRecordInternetDelimiter OBJECT-TYPE 
                SYNTAX DisplayString (SIZE (0..1)) 
                ACCESS read-write 
                STATUS mandatory
                DESCRIPTION 
                    "The character separating the load file directory name
                    from the file name." 
                DEFVAL { '00'h }  -- the null string
                ::= { bootRecordEntry 25 }



            -- the System group, basic parameters continued

            sysLastAgentError OBJECT-TYPE
                SYNTAX INTEGER { noError(1), tooBig(2), noSuchName(3),
                                 badValue(4), readOnly(5), genErr(6),
                                 badCommunity(7), badVersion(8), badType(9),
                                 badClient(10) }
                ACCESS read-only
                STATUS mandatory
                DESCRIPTION
                    "The most recent error the agent encountered in 
                    attempting to satisfy an SNMP request.  Reading this 
                    value has the side effect of resetting it to 
                    'noError'."
                ::= { xSystem 38 }

             sysRcpMulticast OBJECT-TYPE
                SYNTAX INTEGER { disabled(1), enabled(2) }
                ACCESS read-write
                STATUS mandatory
                DESCRIPTION
                    "Control for sending of the MOP RCP system identifier
                    message.  Corresponds directly to the presence of 'RCP
                    Multicast' under the label 'Enabled Characteristics'
                    in the SERVER CHARACTERISTICS display."
                ::= { xSystem 40 }

            sysTimeServerAddress OBJECT-TYPE
                SYNTAX TypedAddress
                ACCESS read-only 
                STATUS mandatory 
                DESCRIPTION 
                    "The address of the time server, either an
                     IpAddr or an ethernet address."
                ::= { xSystem 41 }

            sysTimeServerConfiguredAddress OBJECT-TYPE
                SYNTAX TypedAddress
                ACCESS read-write
                STATUS mandatory
                DESCRIPTION
                      "The address of a configured time server (, either an
                          IpAddr or an ethernet address)."
                ::= { xSystem 46 }

            sysTimeServerConfiguredStatus OBJECT-TYPE
                SYNTAX INTEGER { disabled(1), enabled(2), required(3) }
                ACCESS read-write
                STATUS mandatory
                DESCRIPTION
                   "Control whether the sysTimeServerConfiguredAddress is
                    the only time server used to obtain the time (REQUIRED),
                    the first time server used to obtain the time (ENABLED),
                    or not used to obtain the time (DISABLED)."
                DEFVAL { disabled }
                ::= { xSystem 47 }
                 
            sysBootRecordOverrideDefinedAddress OBJECT-TYPE
                SYNTAX INTEGER { enabled(1), disabled(2) }
                ACCESS read-write
                STATUS mandatory
                DESCRIPTION
                   "Control to override the internally defined Internet address
                    with that obtained from the bootp loading protocol."
                DEFVAL { disabled  }
                ::= { xSystem 48 }

            sysBootRecordMessageEnable OBJECT-TYPE
                SYNTAX INTEGER { enabled(1), disabled(2) }
                ACCESS read-write
                STATUS mandatory
                DESCRIPTION
                    "Control to display load status messages during reboot.
                     Corresponds directly to the value labeled 'Status Message:'
                     in the SERVER LOADDUMP display."
                DEFVAL { enabled }
                ::= { xSystem 49 }
 
            sysBootRecordParamDefaults OBJECT-TYPE
                SYNTAX INTEGER { enabled(1), disabled(2) }
                ACCESS read-write
                STATUS mandatory
                DESCRIPTION
                    "Control to use default parameters upon the next reboot
                     after which time this control reverts to disabled. This
                     control only applies to stand-alone devices. Corresponds 
                     directly to the value labeled 'Default Parameters:'
                     in the SERVER LOADDUMP display."
                DEFVAL { disabled  }
                ::= { xSystem 50 }
 
            sysLoginAuthFailureTrapType OBJECT-TYPE
                SYNTAX INTEGER { none(1), loginPassword(2), pap(3),
                                 chap(4), kerberos(5), securId(6),
                                 radius(7), privilegedPassword(8),
                                 limitedPrivilegedPassword(9) }
                ACCESS read-only
                STATUS mandatory
                DESCRIPTION 
                    "Indicates the type of authentication failure which last
                     occurred."   
                
                ::= { xSystem 78 }

             sysLoginAuthTrapIdentity OBJECT-TYPE
                SYNTAX DisplayString (SIZE (0..16))
                ACCESS read-only
                STATUS mandatory
                DESCRIPTION
                    "An identification string for the circuit or port where an
                     authentication failure last occurred."
                ::= { xSystem 81 }

            sysLocalScriptServer OBJECT-TYPE
                SYNTAX INTEGER { disabled(1), enabled(2) }
                ACCESS read-write
                STATUS mandatory
                DESCRIPTION
                    "Control to allow script serving for this system
                     from a script residing in a local flash card."
                DEFVAL { enabled }
                ::= { xSystem 82 }

            sysInReachManagementSecurityStatus OBJECT-TYPE
                SYNTAX INTEGER { disabled(1), enabled(2) }
                ACCESS read-only
                STATUS mandatory
                DESCRIPTION
                    "Indicates whether per port authentication is in use. This
                     includes username, password, privilege level, and list of
                     power outlets controlled by that user, or console
                     connections allowed from that port."
                DEFVAL { disabled }
                ::= { xSystem 83 }

            sysProductName OBJECT-TYPE
                SYNTAX DisplayString
                ACCESS read-only
                STATUS mandatory
                DESCRIPTION
                    "Displays the product name of this system."
                ::= { xSystem 84 }

            sysModemPresent OBJECT-TYPE
                SYNTAX INTEGER { noModem(1), modem(2) }
                ACCESS read-only
                STATUS mandatory
                DESCRIPTION
                    "Indicates whether this system has a built-in 
                     modem."
                ::= { xSystem 85 }

            sysCauseAction  OBJECT-TYPE
                SYNTAX INTEGER { disabled(1), enabled(2) }
                ACCESS read-write
                STATUS mandatory
                DESCRIPTION
                    "A control for toggling the cause action feature.
                     Corresponds directly to the presence of 'Trigger/Action' 
                     under the label 'Enabled Characteristics:' in the SERVER
                     CHARACTERISTICS display. The desired change will not take
                     effect until the next system initialization."
                DEFVAL { disabled }
                ::= { xSystem 86 }                

            sysWebServerConfigAdminStatus  OBJECT-TYPE
                SYNTAX INTEGER { disabled(1), enabled(2) }
                ACCESS read-write
                STATUS mandatory
                DESCRIPTION
                    "A control for bring the web server up or down.
                     Corresponds directly to the presence of 'Web Server'
                     under the label 'Enabled Characteristics:' in the SERVER
                     CHARACTERISTICS display."
                DEFVAL { enabled }
                ::= { xSystem 87 }                

 	sysTl1SourceIdentifier OBJECT-TYPE
		SYNTAX DisplayString (SIZE (0..20))
		ACCESS read-write
		STATUS mandatory
		DESCRIPTION
		    "The source identifier (SID) is the server name used by
                     TL1 to identify the server."
		::= { xSystem 88 }

        sysInitializeDelayParameter OBJECT-TYPE
                SYNTAX INTEGER { ready(1), execute(2) }
                ACCESS read-write
                STATUS mandatory
                DESCRIPTION
                    "Control to begin the system initialization process
                    providing that at least one parameter server is
                    current. Corresponds directly to the INITIALIZE DELAY 
                    PARAMETER command. In response to a get-request or
                    get-next-request, the agent always returns 'ready' for
                    this value."
                ::= { xSystem 89 }


            -- System Traps
            -- resourceLack is deprecated, and replaced by resourceFailure.

            resourceLack TRAP-TYPE
                ENTERPRISE xSystem
                VARIABLES {
                    resType
                    }
                DESCRIPTION
                    "Indication that the system incremented the 
                    corresponding value of resLacks."
                ::= 1

            resourceFailure TRAP-TYPE
                ENTERPRISE iTouch
                VARIABLES {
                    resType,
		    sysLocation
                    }
                DESCRIPTION
                    "Indication that a system resource lack occurred of
                     the type resType."
                ::= 9

            sysLoginAuthenticationFailure TRAP-TYPE
                ENTERPRISE iTouch
                VARIABLES { sysLoginAuthFailureTrapType,
                        sysLoginAuthTrapIdentity }
                DESCRIPTION
                    "Indicates when and where a user attempted and failed to
                     access the system."
                ::= 28


END
