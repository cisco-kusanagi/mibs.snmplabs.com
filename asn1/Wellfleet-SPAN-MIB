Wellfleet-SPAN-MIB DEFINITIONS ::= BEGIN

-- Created by mdl2asn version 3.1
-- Creation date: Wed Aug 30 16:47:49 EDT 1995


    IMPORTS

      Counter
        FROM RFC1155-SMI
      OBJECT-TYPE
        FROM RFC-1212
      wfSpanningTree
        FROM Wellfleet-COMMON-MIB;


    wfBrStp		OBJECT IDENTIFIER ::= { wfSpanningTree 1 }

    wfBrStpBaseDelete OBJECT-TYPE
        SYNTAX	INTEGER {
    		    created(1),
    		    deleted(2)
    		}
        ACCESS	read-write
        STATUS	mandatory
        DESCRIPTION
                "Create/Delete parameter. Default is created.
                Users perform an SNMP SET operation on this
                object in order to create/delete the Spanning
                tree."
        DEFVAL	{ created }
        ::= { wfBrStp 1 }

    wfBrStpBaseEnable OBJECT-TYPE
        SYNTAX	INTEGER {
    		    enabled(1),
    		    disabled(2)
    		}
        ACCESS	read-write
        STATUS	mandatory
        DESCRIPTION
                "Enable/Disable parameter. Default is enabled.
                Users perform an SNMP SET operation on this
                object in order to enable/disable the spanning
                tree."
        DEFVAL	{ enabled }
        ::= { wfBrStp 2 }

    wfBrStpBaseState OBJECT-TYPE
        SYNTAX	INTEGER {
    		    up(1),
    		    down(2),
    		    init(3),
    		    pres(4)
    		}
        ACCESS	read-only
        STATUS	mandatory
        DESCRIPTION
                "The current state of the spanning tree."
        DEFVAL	{ down }
        ::= { wfBrStp 3 }

    wfBrStpProtocolSpecification OBJECT-TYPE
        SYNTAX	INTEGER {
    		    unknown(1),
    		    declb100(2),
    		    ieee8021d(3)
    		}
        ACCESS	read-only
        STATUS	mandatory
        DESCRIPTION
                "The version of the Spanning Tree protocol being
                run."
        DEFVAL	{ ieee8021d }
        ::= { wfBrStp 4 }

    wfBrStpBridgeID OBJECT-TYPE
        SYNTAX	OCTET STRING
        ACCESS	read-write
        STATUS	mandatory
        DESCRIPTION
                "The Spanning Tree Bridge ID assigned to this
                bridge.  It is a 8-octet string.  The first two
                octets make up the bridge priority, and the last
                six are the MAC address of this bridge, which
                is commonly the MAC address of the first port
                on the bridge."
        ::= { wfBrStp 5 }

    wfBrStpTimeSinceTopologyChange OBJECT-TYPE
        SYNTAX	Counter
        ACCESS	read-only
        STATUS	mandatory
        DESCRIPTION
                "The time (in hundredths of a second) since the last
                topology change was detected by the bridge."
        ::= { wfBrStp 6 }

    wfBrStpTopChanges OBJECT-TYPE
        SYNTAX	Counter
        ACCESS	read-only
        STATUS	mandatory
        DESCRIPTION
                "The total number of topology changes detected by
                this bridge since it was last reset or initialized"
        ::= { wfBrStp 7 }

    wfBrStpDesignatedRoot OBJECT-TYPE
        SYNTAX	OCTET STRING
        ACCESS	read-only
        STATUS	mandatory
        DESCRIPTION
                "The bridge ID of the root of the spanning tree as
                determined by the Spanning Tree Protocol as
                executed by the bridge. This value is used as
                the Root Identifier parameter in all Configuration
                Bridge PDUs originated by this node. It is a 8-octet
                string.  The first two octets make up the priority,
                and the last six are the MAC address of the designated
                root bridge."
        ::= { wfBrStp 8 }

    wfBrStpRootCost OBJECT-TYPE
        SYNTAX	INTEGER
        ACCESS	read-only
        STATUS	mandatory
        DESCRIPTION
                "The cost of the path to the root as seen from this
                bridge."
        ::= { wfBrStp 9 }

    wfBrStpRootPort OBJECT-TYPE
        SYNTAX	INTEGER
        ACCESS	read-only
        STATUS	mandatory
        DESCRIPTION
                "The port identifier of the port which offers the
                lowest cost path from this bridge to the root bridge."
        ::= { wfBrStp 10 }

    wfBrStpMaxAge OBJECT-TYPE
        SYNTAX	INTEGER
        ACCESS	read-only
        STATUS	mandatory
        DESCRIPTION
                "The maximum age of the Spanning Tree Protocol
                information learned from the network on any port
                before it is discarded, in hundredths of a second.
                This represents the value actually in use by the
                bridge."
        ::= { wfBrStp 11 }

    wfBrStpHelloTime OBJECT-TYPE
        SYNTAX	INTEGER
        ACCESS	read-only
        STATUS	mandatory
        DESCRIPTION
                "The amount of time between transmission of
                configuration BPDUs by this bridge on any port,
                when it is the root of the spanning tree or
                trying to become so, in hundreths of a second.
                This represents the value actually in use by the bridge."
        ::= { wfBrStp 12 }

    wfBrStpHoldTime OBJECT-TYPE
        SYNTAX	INTEGER {
    		    time(100)
    		}
        ACCESS	read-only
        STATUS	mandatory
        DESCRIPTION
                "The value that determines the interval length during
                which no more than two configuration BPDUs shall be
                transmitted by this bridge, in hundredths of a second."
        DEFVAL	{ time }
        ::= { wfBrStp 13 }

    wfBrStpForwardDelay OBJECT-TYPE
        SYNTAX	INTEGER
        ACCESS	read-only
        STATUS	mandatory
        DESCRIPTION
                "The time, in hundredths of a second, that a port
                on this bridge will stay in a transitional state
                (e.g. LISTENING) before moving to the next state
                (e.g. LEARNING).  This value is also used to age
                all dynamic entries in the Forwarding Database
                when a topology changed has been detected and is
                underway. This represents the value actually in
                use by the bridge."
        ::= { wfBrStp 14 }

    wfBrStpBridgeMaxAge OBJECT-TYPE
        SYNTAX	INTEGER(600..4000)
        ACCESS	read-write
        STATUS	mandatory
        DESCRIPTION
                "The value that all bridges use for MaxAge when
                this bridge acting as the root."
        DEFVAL	{ 2000 }
        ::= { wfBrStp 15 }

    wfBrStpBridgeHelloTime OBJECT-TYPE
        SYNTAX	INTEGER(100..1000)
        ACCESS	read-write
        STATUS	mandatory
        DESCRIPTION
                "The value that all bridges use for HelloTime when
                this bridge acting as the root."
        DEFVAL	{ 200 }
        ::= { wfBrStp 16 }

    wfBrStpBridgeForwardDelay OBJECT-TYPE
        SYNTAX	INTEGER(400..3000)
        ACCESS	read-write
        STATUS	mandatory
        DESCRIPTION
                "The value that all bridges use for ForwardDelay when
                this bridge acting as the root."
        DEFVAL	{ 1500 }
        ::= { wfBrStp 17 }

    wfBrStpBaseTrueConverge OBJECT-TYPE
        SYNTAX  INTEGER {
                    enabled(1),
                    disabled(2)
                }
        ACCESS  read-write
        STATUS  mandatory
        DESCRIPTION
                "Enable/Disable parameter. Default is disabled.
                 Allow spanning tree convergence times to become
                 predictable and accurate to settings specified
                 in user configuration."
        DEFVAL  { disabled }
        ::= { wfBrStp 18 }


    wfBrStpInterfaceTable OBJECT-TYPE
        SYNTAX	SEQUENCE OF WfBrStpInterfaceEntry
        ACCESS	not-accessible
        STATUS	mandatory
        DESCRIPTION
                "inst_id[1] = wfBrStpInterfaceCircuit"
        ::= { wfSpanningTree 2 }

    wfBrStpInterfaceEntry OBJECT-TYPE
        SYNTAX	WfBrStpInterfaceEntry
        ACCESS	not-accessible
        STATUS	mandatory
        DESCRIPTION
                "An entry in wfBrStpInterface."
        INDEX	{ wfBrStpInterfaceCircuit }
        ::= { wfBrStpInterfaceTable 1 }

    WfBrStpInterfaceEntry ::= SEQUENCE {
    	    wfBrStpInterfaceDelete
    		INTEGER,
    	    wfBrStpInterfaceEnable
    		INTEGER,
    	    wfBrStpInterfaceCircuit
    		INTEGER,
    	    wfBrStpInterfacePriority
    		INTEGER,
    	    wfBrStpInterfaceState
    		INTEGER,
    	    wfBrStpInterfaceMultiCastAddr
    		OCTET STRING,
    	    wfBrStpInterfacePathCost
    		INTEGER,
    	    wfBrStpInterfaceDesignatedRoot
    		OCTET STRING,
    	    wfBrStpInterfaceDesignatedCost
    		INTEGER,
    	    wfBrStpInterfaceDesignatedBridge
    		OCTET STRING,
    	    wfBrStpInterfaceDesignatedPort
    		INTEGER,
    	    wfBrStpInterfaceForwardTransitions
    		Counter,
    	    wfBrStpInterfacePktsXmitd
    		Counter,
    	    wfBrStpInterfacePktsRcvd
    		Counter,
    	    wfBrStpInterfaceTranslationDisable
    		INTEGER
        }

    wfBrStpInterfaceDelete OBJECT-TYPE
        SYNTAX	INTEGER {
    		    created(1),
    		    deleted(2)
    		}
        ACCESS	read-write
        STATUS	mandatory
        DESCRIPTION
                "Create/Delete parameter. Default is created.
                Users perform an SNMP SET operation on this
                object in order to create/delete an interface
                for the Spanning Tree."
        DEFVAL	{ created }
        ::= { wfBrStpInterfaceEntry 1 }

    wfBrStpInterfaceEnable OBJECT-TYPE
        SYNTAX	INTEGER {
    		    enabled(1),
    		    disabled(2)
    		}
        ACCESS	read-write
        STATUS	mandatory
        DESCRIPTION
                "Enable/Disable parameter. Default is enabled.
                Users perform an SNMP SET operation on this
                object in order to enable/disable an interface
                for the Spanning Tree."
        DEFVAL	{ enabled }
        ::= { wfBrStpInterfaceEntry 2 }

    wfBrStpInterfaceCircuit OBJECT-TYPE
        SYNTAX	INTEGER
        ACCESS	read-only
        STATUS	mandatory
        DESCRIPTION
                "The circuit number on which this interface is defined."
        ::= { wfBrStpInterfaceEntry 3 }

    wfBrStpInterfacePriority OBJECT-TYPE
        SYNTAX	INTEGER(0..255)
        ACCESS	read-write
        STATUS	mandatory
        DESCRIPTION
                "The value of the priority field which is contained in
                the first octet of the (2 octet long) port ID for this
                circuit. The other octet of the port ID is given by
                wfBrStpInterfaceCircuit."
        DEFVAL	{ 128 }
        ::= { wfBrStpInterfaceEntry 4 }

    wfBrStpInterfaceState OBJECT-TYPE
        SYNTAX	INTEGER {
    		    disabled(1),
    		    blocking(2),
    		    listening(3),
    		    learning(4),
    		    forwarding(5),
    		    broken(6)
    		}
        ACCESS	read-only
        STATUS	mandatory
        DESCRIPTION
                "The current state of the port as defined by the
                application of the Spanning Tree Protocol."
        DEFVAL	{ disabled }
        ::= { wfBrStpInterfaceEntry 5 }

    wfBrStpInterfaceMultiCastAddr OBJECT-TYPE
        SYNTAX	OCTET STRING
        ACCESS	read-only
        STATUS	mandatory
        DESCRIPTION
                "The MAC address used as the destination for all
                BPDU packets generated out this port."
        ::= { wfBrStpInterfaceEntry 6 }

    wfBrStpInterfacePathCost OBJECT-TYPE
        SYNTAX	INTEGER(1..65535)
        ACCESS	read-write
        STATUS	mandatory
        DESCRIPTION
                "The contribution of this port the the root
                path cost of paths toward the spanning tree
                root which include this port."
        DEFVAL	{ 1 }
        ::= { wfBrStpInterfaceEntry 7 }

    wfBrStpInterfaceDesignatedRoot OBJECT-TYPE
        SYNTAX	OCTET STRING
        ACCESS	read-only
        STATUS	mandatory
        DESCRIPTION
                "The unique Bridge Identifier of the Bridge recorded
                as the Root in the Configuration BPDUs transmitted
                by the Designated Bridge for the segment to which this
                port is attached.  Bridge IDs are made up of a
                2-byte priority field, and a 6-byte MAC address."
        ::= { wfBrStpInterfaceEntry 8 }

    wfBrStpInterfaceDesignatedCost OBJECT-TYPE
        SYNTAX	INTEGER
        ACCESS	read-only
        STATUS	mandatory
        DESCRIPTION
                "The path cost of the Designated Port of the
                segment connected to this port. This value
                is compared to the Root Path Cost field in
                received bridge PDUs."
        ::= { wfBrStpInterfaceEntry 9 }

    wfBrStpInterfaceDesignatedBridge OBJECT-TYPE
        SYNTAX	OCTET STRING
        ACCESS	read-only
        STATUS	mandatory
        DESCRIPTION
                "The Bridge Identifier of the bridge which this
                port considers to be the Designated Bridge for
                this port's segment."
        ::= { wfBrStpInterfaceEntry 10 }

    wfBrStpInterfaceDesignatedPort OBJECT-TYPE
        SYNTAX	INTEGER
        ACCESS	read-only
        STATUS	mandatory
        DESCRIPTION
                "The Port Identifier of the port on the Designated
                Bridge for this port's segment."
        ::= { wfBrStpInterfaceEntry 11 }

    wfBrStpInterfaceForwardTransitions OBJECT-TYPE
        SYNTAX	Counter
        ACCESS	read-only
        STATUS	mandatory
        DESCRIPTION
                "The number of times this port has transitioned
                from the Learning State to the Forwarding state."
        ::= { wfBrStpInterfaceEntry 12 }

    wfBrStpInterfacePktsXmitd OBJECT-TYPE
        SYNTAX	Counter
        ACCESS	read-only
        STATUS	mandatory
        DESCRIPTION
                "The number of BPDU packets transmitted out this port"
        ::= { wfBrStpInterfaceEntry 13 }

    wfBrStpInterfacePktsRcvd OBJECT-TYPE
        SYNTAX	Counter
        ACCESS	read-only
        STATUS	mandatory
        DESCRIPTION
                "The number of BPDU packets received on this port"
        ::= { wfBrStpInterfaceEntry 14 }

    wfBrStpInterfaceTranslationDisable OBJECT-TYPE
        SYNTAX	INTEGER {
    		    enabled(1),
    		    disabled(2)
    		}
        ACCESS	read-write
        STATUS	mandatory
        DESCRIPTION
                "Enable/Disable translation bridging parameter. Default is disabled."
        DEFVAL	{ disabled }
        ::= { wfBrStpInterfaceEntry 15 }

    END  -- Wellfleet-SPAN-MIB
