Wellfleet-STATS-MIB DEFINITIONS ::= BEGIN

-- Created by mdl2asn version 3.1
-- Creation date: Wed Aug 30 16:48:24 EDT 1995


    IMPORTS

      Gauge
        FROM RFC1155-SMI
      OBJECT-TYPE
        FROM RFC-1212
      DisplayString
        FROM RFC1213-MIB
      wfStatsDcGroup
        FROM Wellfleet-COMMON-MIB;


    wfStatsDc	OBJECT IDENTIFIER ::= { wfStatsDcGroup 1 }

    wfStatsDcDisable OBJECT-TYPE
        SYNTAX	INTEGER {
    		    enabled(1),
    		    disabled(2)
    		}
        ACCESS	read-write
        STATUS	mandatory
        DESCRIPTION
                "Enable/Disable  Statistical Data Collection."
        DEFVAL	{ disabled }
        ::= { wfStatsDc 1 }

    wfStatsDcVolume OBJECT-TYPE
        SYNTAX	INTEGER(0..14)
        ACCESS	read-write
        STATUS	mandatory
        DESCRIPTION
                "Indicates the file system volume number to which the
                Statistical Data Collection info files will be written.  The volume
                number corresponds to the slot number on which the
                volume resides.  "
        DEFVAL	{ 4 }
        ::= { wfStatsDc 2 }

    wfStatsDcFilePrefix OBJECT-TYPE
        SYNTAX	DisplayString
        ACCESS	read-write
        STATUS	mandatory
        DESCRIPTION
                "The name of statistical data files."
        ::= { wfStatsDc 3 }

    wfStatsDcUpdateInterval OBJECT-TYPE
        SYNTAX	INTEGER(10..2147483647)
        ACCESS	read-write
        STATUS	obsolete
        DESCRIPTION
                "This number specifies the interval (number of minutes)
                for the STATS process to collect and update STATS data."
        DEFVAL	{ 60 }
        ::= { wfStatsDc 4 }

    wfStatsDcStoreInterval OBJECT-TYPE
        SYNTAX	INTEGER(10..2147483647)
        ACCESS	read-write
        STATUS	mandatory
        DESCRIPTION
                "This number specifies the interval (number of minutes)
                for the STATS master process to collect and update STATS
                data from each slot and to write statistical data on to the
                file system. "
        DEFVAL	{ 60 }
        ::= { wfStatsDc 5 }

    wfStatsDcUpdateData OBJECT-TYPE
        SYNTAX	INTEGER
        ACCESS	read-write
        STATUS	obsolete
        DESCRIPTION
                "Setting this attribute to a non-zero value will cause
                an immediate updating of the statistical data.
                Once activated, this attribute should be reset to zero
                to allow subsequent activations. "
        ::= { wfStatsDc 6 }

    wfStatsDcStoreData OBJECT-TYPE
        SYNTAX	INTEGER
        ACCESS	read-write
        STATUS	mandatory
        DESCRIPTION
                "Setting this attribute to a non-zero value will cause
                an immediate writing of the statistical data info to
                a file in SRAM. Once activated, this attribute should
                be reset to zero to allow subsequent activations. "
        ::= { wfStatsDc 7 }

    wfStatsDcSwitchId OBJECT-TYPE
        SYNTAX	DisplayString
        ACCESS	read-write
        STATUS	mandatory
        DESCRIPTION
                "switch id used in the statistical data file to identify BNX. If
                it is not given explicitely, it will be assigned with wfSysName."
        ::= { wfStatsDc 8 }

    wfStatsDcEnableAll OBJECT-TYPE
        SYNTAX	INTEGER {
    		    on(1),
    		    off(2)
    		}
        ACCESS	read-write
        STATUS	mandatory
        DESCRIPTION
                "This attribute, if set, will overwrite individual logical line
                enable/disable setting of statistical data collection."
        DEFVAL	{ off }
        ::= { wfStatsDc 9 }

    wfStatsDcMaxNumFiles OBJECT-TYPE
        SYNTAX	INTEGER(0..144)
        ACCESS	read-write
        STATUS	mandatory
        DESCRIPTION
                "This attribute sets the MAX number of STATS files in an SRAM.
                If this number is reached, before writing the next STATS DC
                file to SRAM, the older STATS DC file will be delete.
                Note: Value 0 has the special meaning that this limitation
                  will not take into effect. The DC file will be written
                  in the round robin manner."
        ::= { wfStatsDc 10 }

    wfStatsDcFrVcDisable OBJECT-TYPE
        SYNTAX	INTEGER {
    		    enabled(1),
    		    disabled(2)
    		}
        ACCESS	read-write
        STATUS	mandatory
        DESCRIPTION
                "When this switch is turned on, the stats data of all VCs of the
                configured circuit will be collected. This is per BNX."
        DEFVAL	{ disabled }
        ::= { wfStatsDc 11 }

    wfStatsDcState OBJECT-TYPE
        SYNTAX	INTEGER {
    		    up(1),
    		    down(2),
    		    init(3),
    		    notpresent(4)
    		}
        ACCESS	read-only
        STATUS	mandatory
        DESCRIPTION
                "current state."
        DEFVAL	{ notpresent }
        ::= { wfStatsDc 12 }

    wfStatsDcHssiFields OBJECT-TYPE
        SYNTAX	Gauge
        ACCESS	read-write
        STATUS	mandatory
        DESCRIPTION
                "************************************************************"
        DEFVAL	{ 4278190080 }
        ::= { wfStatsDc 13 }

    wfStatsDcSyncFields OBJECT-TYPE
        SYNTAX	Gauge
        ACCESS	read-write
        STATUS	mandatory
        DESCRIPTION
                "************************************************************"
        DEFVAL	{ 4278190080 }
        ::= { wfStatsDc 14 }

    wfStatsDcDs1E1Fields OBJECT-TYPE
        SYNTAX	Gauge
        ACCESS	read-write
        STATUS	mandatory
        DESCRIPTION
                "************************************************************"
        DEFVAL	{ 4294836224 }
        ::= { wfStatsDc 15 }

    wfStatsDcFrSwVcFields OBJECT-TYPE
        SYNTAX	Gauge
        ACCESS	read-write
        STATUS	mandatory
        DESCRIPTION
                "************************************************************"
        DEFVAL	{ 4294966272 }
        ::= { wfStatsDc 16 }

    wfStatsDcCctCngcFields OBJECT-TYPE
        SYNTAX	Gauge
        ACCESS	read-write
        STATUS	mandatory
        DESCRIPTION
                "************************************************************"
        DEFVAL	{ 4294901760 }
        ::= { wfStatsDc 17 }

    wfStatsDcFddiFields OBJECT-TYPE
        SYNTAX	OCTET STRING
        ACCESS	read-write
        STATUS	mandatory
        DESCRIPTION
                "************************************************************"
        ::= { wfStatsDc 18 }

    wfStatsDcCctCngcDisable OBJECT-TYPE
        SYNTAX	INTEGER {
    		    enabled(1),
    		    disabled(2)
    		}
        ACCESS	read-write
        STATUS	mandatory
        DESCRIPTION
                "This attribute is to enable.disable frsw cngc data collection"
        DEFVAL	{ disabled }
        ::= { wfStatsDc 19 }

    wfStatsDcLbcFileDisable OBJECT-TYPE
        SYNTAX	INTEGER {
    		    enabled(1),
    		    disabled(2)
    		}
        ACCESS	read-write
        STATUS	mandatory
        DESCRIPTION
                "To enable/disable LBC file write."
        DEFVAL	{ disabled }
        ::= { wfStatsDc 20 }

    wfStatsDcAtmzPhyFields OBJECT-TYPE
        SYNTAX  Gauge
        ACCESS  read-write
        STATUS  mandatory
        DESCRIPTION
                "Selection of Atmz Line Attributes for Data Collection "
        DEFVAL  { 4294967264 }
        ::= { wfStatsDc 21 }


    wfStatsDcMediaTable OBJECT-TYPE
        SYNTAX	SEQUENCE OF WfStatsDcMediaEntry
        ACCESS	not-accessible
        STATUS	mandatory
        DESCRIPTION
                "STATS Generic Media table for Generic media drivers using Line Number in their mib."
        ::= { wfStatsDcGroup 2 }

    wfStatsDcMediaEntry OBJECT-TYPE
        SYNTAX	WfStatsDcMediaEntry
        ACCESS	not-accessible
        STATUS	mandatory
        DESCRIPTION
                "The parameters for Stats."
        INDEX	{ wfStatsDcMediaLineNumber }
        ::= { wfStatsDcMediaTable 1 }

    WfStatsDcMediaEntry ::= SEQUENCE {
    	    wfStatsDcMediaDelete
    		INTEGER,
    	    wfStatsDcMediaLineNumber
    		INTEGER
        }

    wfStatsDcMediaDelete OBJECT-TYPE
        SYNTAX	INTEGER {
    		    created(1),
    		    deleted(2)
    		}
        ACCESS	read-write
        STATUS	mandatory
        DESCRIPTION
                "Indicates status of this entry."
        DEFVAL	{ created }
        ::= { wfStatsDcMediaEntry 1 }

    wfStatsDcMediaLineNumber OBJECT-TYPE
        SYNTAX	INTEGER
        ACCESS	read-only
        STATUS	mandatory
        DESCRIPTION
                "Instance identifier; this indicates which line number
                NOTE: Line number is based on the following scheme:
                     msb   0         00      00      00      0       00      lsb
                           resv.     chan    type    slot    mod     conn"
        ::= { wfStatsDcMediaEntry 2 }

    wfStatsDcLbcTable OBJECT-TYPE
        SYNTAX	SEQUENCE OF WfStatsDcLbcEntry
        ACCESS	not-accessible
        STATUS	mandatory
        DESCRIPTION
                "LBC Entry using line number as its index."
        ::= { wfStatsDcGroup 3 }

    wfStatsDcLbcEntry OBJECT-TYPE
        SYNTAX	WfStatsDcLbcEntry
        ACCESS	not-accessible
        STATUS	mandatory
        DESCRIPTION
                "LBC Entry using line number as its index."
        INDEX	{ wfStatsDcLbcLineNumber }
        ::= { wfStatsDcLbcTable 1 }

    WfStatsDcLbcEntry ::= SEQUENCE {
    	    wfStatsDcLbcDelete
    		INTEGER,
    	    wfStatsDcLbcDisable
    		INTEGER,
    	    wfStatsDcLbcLineNumber
    		INTEGER,
    	    wfStatsDcLbcUpdateInterval
    		INTEGER,
    	    wfStatsDcLbcState
    		INTEGER,
    	    wfStatsDcLbcRxMaxDelta0
    		Gauge,
    	    wfStatsDcLbcTxMaxDelta0
    		Gauge,
    	    wfStatsDcLbcRxMaxDelta1
    		Gauge,
    	    wfStatsDcLbcTxMaxDelta1
    		Gauge,
    	    wfStatsDcLbcRxMaxDelta2
    		Gauge,
    	    wfStatsDcLbcTxMaxDelta2
    		Gauge,
    	    wfStatsDcLbcRxMaxDelta3
    		Gauge,
    	    wfStatsDcLbcTxMaxDelta3
    		Gauge,
    	    wfStatsDcLbcRxMaxDelta4
    		Gauge,
    	    wfStatsDcLbcTxMaxDelta4
    		Gauge,
    	    wfStatsDcLbcRxMaxDelta5
    		Gauge,
    	    wfStatsDcLbcTxMaxDelta5
    		Gauge,
    	    wfStatsDcLbcRxMaxDelta6
    		Gauge,
    	    wfStatsDcLbcTxMaxDelta6
    		Gauge,
    	    wfStatsDcLbcRxMaxDelta7
    		Gauge,
    	    wfStatsDcLbcTxMaxDelta7
    		Gauge,
    	    wfStatsDcLbcRxMaxDelta8
    		Gauge,
    	    wfStatsDcLbcTxMaxDelta8
    		Gauge,
    	    wfStatsDcLbcRxMaxDelta9
    		Gauge,
    	    wfStatsDcLbcTxMaxDelta9
    		Gauge,
    	    wfStatsDcLbcRxMaxDelta10
    		Gauge,
    	    wfStatsDcLbcTxMaxDelta10
    		Gauge,
    	    wfStatsDcLbcRxMaxDelta11
    		Gauge,
    	    wfStatsDcLbcTxMaxDelta11
    		Gauge,
    	    wfStatsDcLbcRxMaxDelta12
    		Gauge,
    	    wfStatsDcLbcTxMaxDelta12
    		Gauge,
    	    wfStatsDcLbcRxMaxDelta13
    		Gauge,
    	    wfStatsDcLbcTxMaxDelta13
    		Gauge,
    	    wfStatsDcLbcRxMaxDelta14
    		Gauge,
    	    wfStatsDcLbcTxMaxDelta14
    		Gauge,
    	    wfStatsDcLbcRxMaxDelta15
    		Gauge,
    	    wfStatsDcLbcTxMaxDelta15
    		Gauge,
    	    wfStatsDcLbcRxMaxDelta16
    		Gauge,
    	    wfStatsDcLbcTxMaxDelta16
    		Gauge,
    	    wfStatsDcLbcRxMaxDelta17
    		Gauge,
    	    wfStatsDcLbcTxMaxDelta17
    		Gauge,
    	    wfStatsDcLbcRxMaxDelta18
    		Gauge,
    	    wfStatsDcLbcTxMaxDelta18
    		Gauge,
    	    wfStatsDcLbcRxMaxDelta19
    		Gauge,
    	    wfStatsDcLbcTxMaxDelta19
    		Gauge,
    	    wfStatsDcLbcRxMaxDelta20
    		Gauge,
    	    wfStatsDcLbcTxMaxDelta20
    		Gauge,
    	    wfStatsDcLbcRxMaxDelta21
    		Gauge,
    	    wfStatsDcLbcTxMaxDelta21
    		Gauge,
    	    wfStatsDcLbcRxMaxDelta22
    		Gauge,
    	    wfStatsDcLbcTxMaxDelta22
    		Gauge,
    	    wfStatsDcLbcRxMaxDelta23
    		Gauge,
    	    wfStatsDcLbcTxMaxDelta23
    		Gauge

        }

   wfStatsDcLbcDelete	OBJECT-TYPE
	SYNTAX  INTEGER {
    		    created(1),
    		    deleted(2)
    		}
	ACCESS	read-write
        STATUS  mandatory
	DESCRIPTION "To create or delete this instance."
	DEFVAL	{ created }
	::= { wfStatsDcLbcEntry 1 }

   wfStatsDcLbcDisable 	OBJECT-TYPE
        SYNTAX  INTEGER {
                    enabled(1),
                    disabled(2)
                }
        ACCESS  read-write
        STATUS  mandatory
        DESCRIPTION "When this switch is turned on, BNX will read
		the configured trunk line's rx/tx counter value at
		a predetermined time frequency."
        DEFVAL  { enabled }
        ::= { wfStatsDcLbcEntry 2 }
	

    wfStatsDcLbcLineNumber OBJECT-TYPE
        SYNTAX	INTEGER
        ACCESS	read-only
        STATUS	mandatory
        DESCRIPTION
                "line number for this line instance"
        ::= { wfStatsDcLbcEntry 3 }

   wfStatsDcLbcUpdateInterval	OBJECT-TYPE
	SYNTAX	INTEGER (1..60)
	ACCESS	read-write
	STATUS	mandatory
	DESCRIPTION "The value must be divisible into 60. In another 
		word, 60/value must be an integer."
	DEFVAL	{ 5 }
	::= { wfStatsDcLbcEntry 4 }

   wfStatsDcLbcState	OBJECT-TYPE
	SYNTAX	INTEGER {
    		    up(1),
    		    down(2),
    		    init(3),
    		    notpresent(4)
		}
	ACCESS	read-only
	STATUS	mandatory
	DESCRIPTION "TBC state "
	DEFVAL	{ notpresent }
	::= { wfStatsDcLbcEntry 5}

   wfStatsDcLbcRxMaxDelta0	OBJECT-TYPE
	SYNTAX	Gauge
	ACCESS	read-only
	STATUS	mandatory
	DESCRIPTION "Maximum number of the rx bytes count for this instance 
		in hour 0."
	DEFVAL 	{ 0 }
	::= { wfStatsDcLbcEntry 6 }

   wfStatsDcLbcTxMaxDelta0	OBJECT-TYPE
	SYNTAX	Gauge
	ACCESS	read-only
	STATUS	mandatory
	DESCRIPTION "Maximum number of the tx bytes count for this instance 
		in hour 0."
	DEFVAL 	{ 0 }
	::= { wfStatsDcLbcEntry 7 }

   wfStatsDcLbcRxMaxDelta1	OBJECT-TYPE
	SYNTAX	Gauge
	ACCESS	read-only
	STATUS	mandatory
	DESCRIPTION "Maximum number of the rx bytes count for this instance 
		in hour 1."
	DEFVAL 	{ 0 }
	::= { wfStatsDcLbcEntry 8 }

   wfStatsDcLbcTxMaxDelta1	OBJECT-TYPE
	SYNTAX	Gauge
	ACCESS	read-only
	STATUS	mandatory
	DESCRIPTION "Maximum number of the tx bytes count for this instance 
		in hour 1."
	DEFVAL 	{ 0 }
	::= { wfStatsDcLbcEntry 9 }

   wfStatsDcLbcRxMaxDelta2	OBJECT-TYPE
	SYNTAX	Gauge
	ACCESS	read-only
	STATUS	mandatory
	DESCRIPTION "Maximum number of the rx bytes count for this instance 
		in hour 2."
	DEFVAL 	{ 0 }
	::= { wfStatsDcLbcEntry 10 }

   wfStatsDcLbcTxMaxDelta2	OBJECT-TYPE
	SYNTAX	Gauge
	ACCESS	read-only
	STATUS	mandatory
	DESCRIPTION "Maximum number of the tx bytes count for this instance 
		in hour 2."
	DEFVAL 	{ 0 }
	::= { wfStatsDcLbcEntry 11 }

   wfStatsDcLbcRxMaxDelta3	OBJECT-TYPE
	SYNTAX	Gauge
	ACCESS	read-only
	STATUS	mandatory
	DESCRIPTION "Maximum number of the rx bytes count for this instance 
		in hour 3."
	DEFVAL 	{ 0 }
	::= { wfStatsDcLbcEntry 12 }

   wfStatsDcLbcTxMaxDelta3	OBJECT-TYPE
	SYNTAX	Gauge
	ACCESS	read-only
	STATUS	mandatory
	DESCRIPTION "Maximum number of the tx bytes count for this instance 
		in hour 3."
	DEFVAL 	{ 0 }
	::= { wfStatsDcLbcEntry 13 }

   wfStatsDcLbcRxMaxDelta4	OBJECT-TYPE
	SYNTAX	Gauge
	ACCESS	read-only
	STATUS	mandatory
	DESCRIPTION "Maximum number of the rx bytes count for this instance 
		in hour 4."
	DEFVAL 	{ 0 }
	::= { wfStatsDcLbcEntry 14 }

   wfStatsDcLbcTxMaxDelta4	OBJECT-TYPE
	SYNTAX	Gauge
	ACCESS	read-only
	STATUS	mandatory
	DESCRIPTION "Maximum number of the tx bytes count for this instance 
		in hour 4."
	DEFVAL 	{ 0 }
	::= { wfStatsDcLbcEntry 15 }

   wfStatsDcLbcRxMaxDelta5	OBJECT-TYPE
	SYNTAX	Gauge
	ACCESS	read-only
	STATUS	mandatory
	DESCRIPTION "Maximum number of the rx bytes count for this instance 
		in hour 5."
	DEFVAL 	{ 0 }
	::= { wfStatsDcLbcEntry 16 }

   wfStatsDcLbcTxMaxDelta5	OBJECT-TYPE
	SYNTAX	Gauge
	ACCESS	read-only
	STATUS	mandatory
	DESCRIPTION "Maximum number of the tx bytes count for this instance 
		in hour 5."
	DEFVAL 	{ 0 }
	::= { wfStatsDcLbcEntry 17 }

   wfStatsDcLbcRxMaxDelta6	OBJECT-TYPE
	SYNTAX	Gauge
	ACCESS	read-only
	STATUS	mandatory
	DESCRIPTION "Maximum number of the rx bytes count for this instance 
		in hour 6."
	DEFVAL 	{ 0 }
	::= { wfStatsDcLbcEntry 18 }

   wfStatsDcLbcTxMaxDelta6	OBJECT-TYPE
	SYNTAX	Gauge
	ACCESS	read-only
	STATUS	mandatory
	DESCRIPTION "Maximum number of the tx bytes count for this instance 
		in hour 6."
	DEFVAL 	{ 0 }
	::= { wfStatsDcLbcEntry 19 }

   wfStatsDcLbcRxMaxDelta7	OBJECT-TYPE
	SYNTAX	Gauge
	ACCESS	read-only
	STATUS	mandatory
	DESCRIPTION "Maximum number of the rx bytes count for this instance 
		in hour 7."
	DEFVAL 	{ 0 }
	::= { wfStatsDcLbcEntry 20 }

   wfStatsDcLbcTxMaxDelta7	OBJECT-TYPE
	SYNTAX	Gauge
	ACCESS	read-only
	STATUS	mandatory
	DESCRIPTION "Maximum number of the tx bytes count for this instance 
		in hour 7."
	DEFVAL 	{ 0 }
	::= { wfStatsDcLbcEntry 21 }

   wfStatsDcLbcRxMaxDelta8	OBJECT-TYPE
	SYNTAX	Gauge
	ACCESS	read-only
	STATUS	mandatory
	DESCRIPTION "Maximum number of the rx bytes count for this instance 
		in hour 8."
	DEFVAL 	{ 0 }
	::= { wfStatsDcLbcEntry 22 }

   wfStatsDcLbcTxMaxDelta8	OBJECT-TYPE
	SYNTAX	Gauge
	ACCESS	read-only
	STATUS	mandatory
	DESCRIPTION "Maximum number of the tx bytes count for this instance 
		in hour 8."
	DEFVAL 	{ 0 }
	::= { wfStatsDcLbcEntry 23 }

   wfStatsDcLbcRxMaxDelta9	OBJECT-TYPE
	SYNTAX	Gauge
	ACCESS	read-only
	STATUS	mandatory
	DESCRIPTION "Maximum number of the rx bytes count for this instance 
		in hour 9."
	DEFVAL 	{ 0 }
	::= { wfStatsDcLbcEntry 24 }

   wfStatsDcLbcTxMaxDelta9	OBJECT-TYPE
	SYNTAX	Gauge
	ACCESS	read-only
	STATUS	mandatory
	DESCRIPTION "Maximum number of the tx bytes count for this instance 
		in hour 9."
	DEFVAL 	{ 0 }
	::= { wfStatsDcLbcEntry 25 }

   wfStatsDcLbcRxMaxDelta10	OBJECT-TYPE
	SYNTAX	Gauge
	ACCESS	read-only
	STATUS	mandatory
	DESCRIPTION "Maximum number of the rx bytes count for this instance 
		in hour 10."
	DEFVAL 	{ 0 }
	::= { wfStatsDcLbcEntry 26 }

   wfStatsDcLbcTxMaxDelta10	OBJECT-TYPE
	SYNTAX	Gauge
	ACCESS	read-only
	STATUS	mandatory
	DESCRIPTION "Maximum number of the tx bytes count for this instance 
		in hour 10."
	DEFVAL 	{ 0 }
	::= { wfStatsDcLbcEntry 27 }

   wfStatsDcLbcRxMaxDelta11	OBJECT-TYPE
	SYNTAX	Gauge
	ACCESS	read-only
	STATUS	mandatory
	DESCRIPTION "Maximum number of the rx bytes count for this instance 
		in hour 11."
	DEFVAL 	{ 0 }
	::= { wfStatsDcLbcEntry 28 }

   wfStatsDcLbcTxMaxDelta11	OBJECT-TYPE
	SYNTAX	Gauge
	ACCESS	read-only
	STATUS	mandatory
	DESCRIPTION "Maximum number of the tx bytes count for this instance 
		in hour 11."
	DEFVAL 	{ 0 }
	::= { wfStatsDcLbcEntry 29 }

   wfStatsDcLbcRxMaxDelta12	OBJECT-TYPE
	SYNTAX	Gauge
	ACCESS	read-only
	STATUS	mandatory
	DESCRIPTION "Maximum number of the rx bytes count for this instance 
		in hour 12."
	DEFVAL 	{ 0 }
	::= { wfStatsDcLbcEntry 30 }

   wfStatsDcLbcTxMaxDelta12	OBJECT-TYPE
	SYNTAX	Gauge
	ACCESS	read-only
	STATUS	mandatory
	DESCRIPTION "Maximum number of the tx bytes count for this instance 
		in hour 12."
	DEFVAL 	{ 0 }
	::= { wfStatsDcLbcEntry 31 }

   wfStatsDcLbcRxMaxDelta13	OBJECT-TYPE
	SYNTAX	Gauge
	ACCESS	read-only
	STATUS	mandatory
	DESCRIPTION "Maximum number of the rx bytes count for this instance 
		in hour 13."
	DEFVAL 	{ 0 }
	::= { wfStatsDcLbcEntry 32 }

   wfStatsDcLbcTxMaxDelta13	OBJECT-TYPE
	SYNTAX	Gauge
	ACCESS	read-only
	STATUS	mandatory
	DESCRIPTION "Maximum number of the tx bytes count for this instance 
		in hour 13."
	DEFVAL 	{ 0 }
	::= { wfStatsDcLbcEntry 33 }

   wfStatsDcLbcRxMaxDelta14	OBJECT-TYPE
	SYNTAX	Gauge
	ACCESS	read-only
	STATUS	mandatory
	DESCRIPTION "Maximum number of the rx bytes count for this instance 
		in hour 14."
	DEFVAL 	{ 0 }
	::= { wfStatsDcLbcEntry 34 }

   wfStatsDcLbcTxMaxDelta14	OBJECT-TYPE
	SYNTAX	Gauge
	ACCESS	read-only
	STATUS	mandatory
	DESCRIPTION "Maximum number of the tx bytes count for this instance 
		in hour 14."
	DEFVAL 	{ 0 }
	::= { wfStatsDcLbcEntry 35 }

   wfStatsDcLbcRxMaxDelta15	OBJECT-TYPE
	SYNTAX	Gauge
	ACCESS	read-only
	STATUS	mandatory
	DESCRIPTION "Maximum number of the rx bytes count for this instance 
		in hour 15."
	DEFVAL 	{ 0 }
	::= { wfStatsDcLbcEntry 36 }

   wfStatsDcLbcTxMaxDelta15	OBJECT-TYPE
	SYNTAX	Gauge
	ACCESS	read-only
	STATUS	mandatory
	DESCRIPTION "Maximum number of the tx bytes count for this instance 
		in hour 15."
	DEFVAL 	{ 0 }
	::= { wfStatsDcLbcEntry 37 }

   wfStatsDcLbcRxMaxDelta16	OBJECT-TYPE
	SYNTAX	Gauge
	ACCESS	read-only
	STATUS	mandatory
	DESCRIPTION "Maximum number of the rx bytes count for this instance 
		in hour 16."
	DEFVAL 	{ 0 }
	::= { wfStatsDcLbcEntry 38 }

   wfStatsDcLbcTxMaxDelta16	OBJECT-TYPE
	SYNTAX	Gauge
	ACCESS	read-only
	STATUS	mandatory
	DESCRIPTION "Maximum number of the tx bytes count for this instance 
		in hour 16."
	DEFVAL 	{ 0 }
	::= { wfStatsDcLbcEntry 39 }

   wfStatsDcLbcRxMaxDelta17	OBJECT-TYPE
	SYNTAX	Gauge
	ACCESS	read-only
	STATUS	mandatory
	DESCRIPTION "Maximum number of the rx bytes count for this instance 
		in hour 17."
	DEFVAL 	{ 0 }
	::= { wfStatsDcLbcEntry 40 }

   wfStatsDcLbcTxMaxDelta17	OBJECT-TYPE
	SYNTAX	Gauge
	ACCESS	read-only
	STATUS	mandatory
	DESCRIPTION "Maximum number of the tx bytes count for this instance 
		in hour 17."
	DEFVAL 	{ 0 }
	::= { wfStatsDcLbcEntry 41 }

   wfStatsDcLbcRxMaxDelta18	OBJECT-TYPE
	SYNTAX	Gauge
	ACCESS	read-only
	STATUS	mandatory
	DESCRIPTION "Maximum number of the rx bytes count for this instance 
		in hour 18."
	DEFVAL 	{ 0 }
	::= { wfStatsDcLbcEntry 42 }

   wfStatsDcLbcTxMaxDelta18	OBJECT-TYPE
	SYNTAX	Gauge
	ACCESS	read-only
	STATUS	mandatory
	DESCRIPTION "Maximum number of the tx bytes count for this instance 
		in hour 18."
	DEFVAL 	{ 0 }
	::= { wfStatsDcLbcEntry 43 }

   wfStatsDcLbcRxMaxDelta19	OBJECT-TYPE
	SYNTAX	Gauge
	ACCESS	read-only
	STATUS	mandatory
	DESCRIPTION "Maximum number of the rx bytes count for this instance 
		in hour 19."
	DEFVAL 	{ 0 }
	::= { wfStatsDcLbcEntry 44 }

   wfStatsDcLbcTxMaxDelta19	OBJECT-TYPE
	SYNTAX	Gauge
	ACCESS	read-only
	STATUS	mandatory
	DESCRIPTION "Maximum number of the tx bytes count for this instance 
		in hour 19."
	DEFVAL 	{ 0 }
	::= { wfStatsDcLbcEntry 45 }

   wfStatsDcLbcRxMaxDelta20	OBJECT-TYPE
	SYNTAX	Gauge
	ACCESS	read-only
	STATUS	mandatory
	DESCRIPTION "Maximum number of the rx bytes count for this instance 
		in hour 20."
	DEFVAL 	{ 0 }
	::= { wfStatsDcLbcEntry 46 }

   wfStatsDcLbcTxMaxDelta20	OBJECT-TYPE
	SYNTAX	Gauge
	ACCESS	read-only
	STATUS	mandatory
	DESCRIPTION "Maximum number of the tx bytes count for this instance 
		in hour 20."
	DEFVAL 	{ 0 }
	::= { wfStatsDcLbcEntry 47 }

   wfStatsDcLbcRxMaxDelta21	OBJECT-TYPE
	SYNTAX	Gauge
	ACCESS	read-only
	STATUS	mandatory
	DESCRIPTION "Maximum number of the rx bytes count for this instance 
		in hour 21."
	DEFVAL 	{ 0 }
	::= { wfStatsDcLbcEntry 48 }

   wfStatsDcLbcTxMaxDelta21	OBJECT-TYPE
	SYNTAX	Gauge
	ACCESS	read-only
	STATUS	mandatory
	DESCRIPTION "Maximum number of the tx bytes count for this instance 
		in hour 21."
	DEFVAL 	{ 0 }
	::= { wfStatsDcLbcEntry 49 }

   wfStatsDcLbcRxMaxDelta22	OBJECT-TYPE
	SYNTAX	Gauge
	ACCESS	read-only
	STATUS	mandatory
	DESCRIPTION "Maximum number of the rx bytes count for this instance 
		in hour 22."
	DEFVAL 	{ 0 }
	::= { wfStatsDcLbcEntry 50 }

   wfStatsDcLbcTxMaxDelta22	OBJECT-TYPE
	SYNTAX	Gauge
	ACCESS	read-only
	STATUS	mandatory
	DESCRIPTION "Maximum number of the tx bytes count for this instance 
		in hour 22."
	DEFVAL 	{ 0 }
	::= { wfStatsDcLbcEntry 51 }

   wfStatsDcLbcRxMaxDelta23	OBJECT-TYPE
	SYNTAX	Gauge
	ACCESS	read-only
	STATUS	mandatory
	DESCRIPTION "Maximum number of the rx bytes count for this instance 
		in hour 23."
	DEFVAL 	{ 0 }
	::= { wfStatsDcLbcEntry 52 }

   wfStatsDcLbcTxMaxDelta23	OBJECT-TYPE
	SYNTAX	Gauge
	ACCESS	read-only
	STATUS	mandatory
	DESCRIPTION "Maximum number of the tx bytes count for this instance 
		in hour 23."
	DEFVAL 	{ 0 }
	::= { wfStatsDcLbcEntry 53 }

    END  -- Wellfleet-STATS-MIB
