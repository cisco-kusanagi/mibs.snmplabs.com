Wellfleet-VCCT-MIB DEFINITIONS ::= BEGIN

-- Created by mdl2asn version 3.1
-- Creation date: Wed Sep  6 16:57:28 EDT 1995
-- Edited by sbasu

    IMPORTS

      OBJECT-TYPE
        FROM RFC-1212
      wfVcctGroup
        FROM Wellfleet-COMMON-MIB;

    wfVcct               OBJECT IDENTIFIER ::= { wfVcctGroup 1 }

    wfVcctDelete OBJECT-TYPE
        SYNTAX  INTEGER {
                    created(1),
                    deleted(2)
                }
        ACCESS  read-write
        STATUS  mandatory
        DESCRIPTION
                "Create/Delete parameter. Default is created.
                User perform an SNMP SET operation on this object
                in order to create/delete VCCT"
        DEFVAL  { created }
        ::= { wfVcct 1 }

    wfVcctDisable OBJECT-TYPE
        SYNTAX  INTEGER {
                    enabled(1),
                    disabled(2)
                }
        ACCESS  read-write
        STATUS  mandatory
        DESCRIPTION
                "Enable/Disable parameter. Default is enabled.
                User perform an SNMP SET operation on this object
                in order to enable/disable VCCT"
        DEFVAL  { enabled }
        ::= { wfVcct 2 }

    wfVcctState OBJECT-TYPE
        SYNTAX  INTEGER {
                    up(1),
                    down(2),
                    init(3),
                    notpresent(4)
                }
        ACCESS  read-only
        STATUS  mandatory
        DESCRIPTION
                "The current state of VCCT subsystem"
        DEFVAL  { down }
        ::= { wfVcct 3 }

    wfVcctTable OBJECT-TYPE
        SYNTAX  SEQUENCE OF WfVcctEntry
        ACCESS  not-accessible
        STATUS  mandatory
        DESCRIPTION
                "Table of Virtual Circuit Config Objects"
        ::= { wfVcctGroup 2 }

    wfVcctEntry OBJECT-TYPE
        SYNTAX  WfVcctEntry
        ACCESS  not-accessible
        STATUS  mandatory
        DESCRIPTION
                "An entry in the Virtual Circuit Config Table"
        INDEX   { wfVcctEntrySlot,
                  wfVcctEntryCct }
        ::= { wfVcctTable 1 }

    WfVcctEntry ::= SEQUENCE {
            wfVcctEntryDelete
                INTEGER,
            wfVcctEntryDisable
                INTEGER,
            wfVcctEntryState
                INTEGER,
            wfVcctEntrySlot
                INTEGER,
            wfVcctEntryCct
                INTEGER,
            wfVcctEntryNumClients
                INTEGER,
            wfVcctEntryServiceType
                INTEGER
    }

    wfVcctEntryDelete OBJECT-TYPE
        SYNTAX  INTEGER {
                    created(1),
                    deleted(2)
                }
        ACCESS  read-write
        STATUS  mandatory
        DESCRIPTION
                "Create/Delete parameter. Default is created.
                User perform an SNMP SET operation on this object
                in order to create/delete the Virtual Circuit gate"
        DEFVAL  { created }
        ::= { wfVcctEntry 1 }

    wfVcctEntryDisable OBJECT-TYPE
        SYNTAX  INTEGER {
                    enabled(1),
                    disabled(2)
                }
        ACCESS  read-write
        STATUS  mandatory
        DESCRIPTION
                "Enable/Disable parameter. Default is enabled.
                User perform an SNMP SET operation on this object
                in order to enable/disable the Virtual Circuit gate"
        DEFVAL  { enabled }
        ::= { wfVcctEntry 2 }

    wfVcctEntryState OBJECT-TYPE
        SYNTAX  INTEGER {
                    coisapwait(1),
                    connectwait(2),
                    connectrspwait(3),
		    connectrcv(4),
		    disconnectrspwait(5)
                }
        ACCESS  read-only
        STATUS  mandatory
        DESCRIPTION
               "Current state of the virtual circuit gate"
        DEFVAL  { coisapwait }
        ::= { wfVcctEntry 3 }

    wfVcctEntrySlot OBJECT-TYPE
        SYNTAX  INTEGER
        ACCESS  read-only
        STATUS  mandatory
        DESCRIPTION
                "Slot that the Virtual Circuit gate is running on"
        ::= { wfVcctEntry 4 }

    wfVcctEntryCct OBJECT-TYPE
        SYNTAX  INTEGER
        ACCESS  read-only
        STATUS  mandatory
        DESCRIPTION
                "Circuit number of this Virtual Circuit gate"
        ::= { wfVcctEntry 5 }

    wfVcctEntryNumClients OBJECT-TYPE
        SYNTAX  INTEGER
        ACCESS  read-only
        STATUS  mandatory
        DESCRIPTION
                "Total number of clients registered on this Virtual
		 Circuit Gate"
        ::= { wfVcctEntry 6 }

    wfVcctEntryServiceType OBJECT-TYPE
        SYNTAX  INTEGER {
		   dlcClientApi(1)
                }
        ACCESS  read-write
        STATUS  mandatory
        DESCRIPTION
                "Type of Service being provided by this Virtual Circuit gate"
        DEFVAL  { dlcClientApi }
        ::= { wfVcctEntry 7 }
   
    END  -- Wellfleet-VCCT-MIB
