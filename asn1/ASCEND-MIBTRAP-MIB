--			Ascend mibtrap MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBTRAP-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibtrapProfile  OBJECT IDENTIFIER ::= { configuration 132}

	-- The mibtrapProfile table
	--
	-- This table contains parameters for the mibtrapProfile profile
	--

    mibtrapProfileTable	OBJECT-TYPE
	SYNTAX		SEQUENCE OF MibtrapProfileEntry
	ACCESS		not-accessible
	STATUS		mandatory
	DESCRIPTION	"A list of mibtrapProfile profile entries."
	::= { mibtrapProfile 1 }

    mibtrapProfileEntry	OBJECT-TYPE
	SYNTAX		MibtrapProfileEntry
	ACCESS		not-accessible
	STATUS		mandatory
	DESCRIPTION	"A mibtrapProfile entry containing objects that
			 maps to the parameters of mibtrapProfile profile."
	INDEX		{ trapProfile-HostName }
	::= { mibtrapProfileTable 1 }

    MibtrapProfileEntry ::=
	SEQUENCE {
	    trapProfile-HostName
		DisplayString,
	    trapProfile-ActiveEnabled
		INTEGER,
	    trapProfile-CommunityName
		DisplayString,
	    trapProfile-HostAddress
		IpAddress,
	    trapProfile-HostPort
		INTEGER,
	    trapProfile-InformTimeOut
		INTEGER,
	    trapProfile-InformRetryCount
		INTEGER,
	    trapProfile-NotifyTagList
		OCTET STRING,
	    trapProfile-TargetParamsName
		OCTET STRING,
	    trapProfile-NotificationLogEnable
		INTEGER,
	    trapProfile-NotificationLogLimit
		INTEGER,
	    trapProfile-AgentAddress
		IpAddress,
	    trapProfile-AlarmEnabled
		INTEGER,
	    trapProfile-SecurityEnabled
		INTEGER,
	    trapProfile-PortEnabled
		INTEGER,
	    trapProfile-SlotEnabled
		INTEGER,
	    trapProfile-ColdstartEnabled
		INTEGER,
	    trapProfile-WarmstartEnabled
		INTEGER,
	    trapProfile-LinkdownEnabled
		INTEGER,
	    trapProfile-LinkupEnabled
		INTEGER,
	    trapProfile-AscendEnabled
		INTEGER,
	    trapProfile-ConsoleEnabled
		INTEGER,
	    trapProfile-UseExceededEnabled
		INTEGER,
	    trapProfile-PasswordEnabled
		INTEGER,
	    trapProfile-FrLinkupEnabled
		INTEGER,
	    trapProfile-FrLinkdownEnabled
		INTEGER,
	    trapProfile-EventOverwriteEnabled
		INTEGER,
	    trapProfile-RadiusChangeEnabled
		INTEGER,
	    trapProfile-McastMonitorEnabled
		INTEGER,
	    trapProfile-LanModemEnabled
		INTEGER,
	    trapProfile-DirdoEnabled
		INTEGER,
	    trapProfile-SlotProfileChangeEnabled
		INTEGER,
	    trapProfile-PowerSupplyEnabled
		INTEGER,
	    trapProfile-MultishelfEnabled
		INTEGER,
	    trapProfile-AuthenticationEnabled
		INTEGER,
	    trapProfile-ConfigChangeEnabled
		INTEGER,
	    trapProfile-SysClockDriftEnabled
		INTEGER,
	    trapProfile-PrimarySdtnEmptyEnabled
		INTEGER,
	    trapProfile-SecondarySdtnEmptyEnabled
		INTEGER,
	    trapProfile-SuspectAccessResourceEnabled
		INTEGER,
	    trapProfile-OspfEnabled
		INTEGER,
	    trapProfile-OspfIfConfigErrorEnabled
		INTEGER,
	    trapProfile-OspfIfAuthFailureEnabled
		INTEGER,
	    trapProfile-OspfIfStateChangeEnabled
		INTEGER,
	    trapProfile-OspfIfRxBadPacket
		INTEGER,
	    trapProfile-OspfTxRetransmitEnabled
		INTEGER,
	    trapProfile-OspfNbrStateChangeEnabled
		INTEGER,
	    trapProfile-OspfVirtIfConfigErrorEnabled
		INTEGER,
	    trapProfile-OspfVirtIfAuthFailureEnabled
		INTEGER,
	    trapProfile-OspfVirtIfStateChangeEnabled
		INTEGER,
	    trapProfile-OspfVirtIfRxBadPacket
		INTEGER,
	    trapProfile-OspfVirtIfTxRetransmitEnabled
		INTEGER,
	    trapProfile-OspfVirtNbrStateChangeEnabled
		INTEGER,
	    trapProfile-OspfOriginateLsaEnabled
		INTEGER,
	    trapProfile-OspfMaxAgeLsaEnabled
		INTEGER,
	    trapProfile-OspfLsdbOverflowEnabled
		INTEGER,
	    trapProfile-OspfApproachingOverflowEnabled
		INTEGER,
	    trapProfile-WatchdogWarningEnabled
		INTEGER,
	    trapProfile-ControllerSwitchoverEnabled
		INTEGER,
	    trapProfile-CallLogServChangeEnabled
		INTEGER,
	    trapProfile-VoipGkChangeEnabled
		INTEGER,
	    trapProfile-WanLineStateChangeEnabled
		INTEGER,
	    trapProfile-CallLogDroppedPktEnabled
		INTEGER,
	    trapProfile-LimSparingEnabled
		INTEGER,
	    trapProfile-InterfaceSparingEnabled
		INTEGER,
	    trapProfile-MegacoLinkStatusEnabled
		INTEGER,
	    trapProfile-SecondaryControllerStateChangeEnabled
		INTEGER,
	    trapProfile-PctfiTrunkStatusChangeEnabled
		INTEGER,
	    trapProfile-NoResourceAvailableEnabled
		INTEGER,
	    trapProfile-DslThreshTrapEnabled
		INTEGER,
	    trapProfile-AtmPvcFailureTrapEnabled
		INTEGER,
	    trapProfile-AtmImaAlarmTrapEnabled
		INTEGER,
	    trapProfile-AscendLinkDownTrapEnabled
		INTEGER,
	    trapProfile-AscendLinkUpTrapEnabled
		INTEGER,
	    trapProfile-SnmpIllegalAccessAttempt
		INTEGER,
	    trapProfile-L2tpTunnelTrapEnabled
		INTEGER,
	    trapProfile-Hdsl2ShdslThresholdTrapsEnabled
		INTEGER,
	    trapProfile-ClockChangeTrapEnabled
		INTEGER,
	    trapProfile-Action-o
		INTEGER
	}

    trapProfile-HostName	OBJECT-TYPE
	SYNTAX	DisplayString
	ACCESS	read-only
	STATUS	mandatory
	DESCRIPTION	"The name of the host to send traps to. When DNS or YP/NIS is supported this name will be used to look up the LAN address when hostAddress is 0."
	::= { mibtrapProfileEntry 1 }

    trapProfile-ActiveEnabled	OBJECT-TYPE
	SYNTAX	INTEGER {
		    no (1),
		    yes (2)
		}
	ACCESS	read-write
	STATUS	mandatory
	DESCRIPTION	"If TRUE, profile is enabled to send traps to this target"
	::= { mibtrapProfileEntry 2 }

    trapProfile-CommunityName	OBJECT-TYPE
	SYNTAX	DisplayString
	ACCESS	read-write
	STATUS	mandatory
	DESCRIPTION	"The community name associated with the SNMP PDU."
	::= { mibtrapProfileEntry 3 }

    trapProfile-HostAddress	OBJECT-TYPE
	SYNTAX	IpAddress
	ACCESS	read-write
	STATUS	mandatory
	DESCRIPTION	"The LAN address of the named host. If 0 the address will be looked up via DNS or YP/NIS when supported."
	::= { mibtrapProfileEntry 4 }

    trapProfile-HostPort	OBJECT-TYPE
	SYNTAX	INTEGER
	ACCESS	read-write
	STATUS	mandatory
	DESCRIPTION	"Port number of the named host. Value 0 is not allowed"
	::= { mibtrapProfileEntry 5 }

    trapProfile-InformTimeOut	OBJECT-TYPE
	SYNTAX	INTEGER
	ACCESS	read-only
	STATUS	mandatory
	DESCRIPTION	"Timeout interval in units of 0.01 seconds after which the Inform PDU is retransmitted on receiving no acknowledgement"
	::= { mibtrapProfileEntry 6 }

    trapProfile-InformRetryCount	OBJECT-TYPE
	SYNTAX	INTEGER
	ACCESS	read-only
	STATUS	mandatory
	DESCRIPTION	"Number of retries attempted when acknowledgement is not received for an Inform PDU"
	::= { mibtrapProfileEntry 7 }

    trapProfile-NotifyTagList	OBJECT-TYPE
	SYNTAX	OCTET STRING
	ACCESS	read-write
	STATUS	mandatory
	DESCRIPTION	"String containing a list of tag values that are used to select target addresses for a particular operation."
	::= { mibtrapProfileEntry 8 }

    trapProfile-TargetParamsName	OBJECT-TYPE
	SYNTAX	OCTET STRING
	ACCESS	read-write
	STATUS	mandatory
	DESCRIPTION	"Index to the row an entry in SNMPV3-TARGET-PARAM table which is used when generating messages to be sent to this host-address"
	::= { mibtrapProfileEntry 9 }

    trapProfile-NotificationLogEnable	OBJECT-TYPE
	SYNTAX	INTEGER {
		    no (1),
		    yes (2)
		}
	ACCESS	read-write
	STATUS	mandatory
	DESCRIPTION	"YES if notifications sent on behalf of this entry needs to be logged. "
	::= { mibtrapProfileEntry 75 }

    trapProfile-NotificationLogLimit	OBJECT-TYPE
	SYNTAX	INTEGER
	ACCESS	read-write
	STATUS	mandatory
	DESCRIPTION	"The maximum number of notification entries that can be held in the notification log."
	::= { mibtrapProfileEntry 76 }

    trapProfile-AgentAddress	OBJECT-TYPE
	SYNTAX	IpAddress
	ACCESS	read-write
	STATUS	mandatory
	DESCRIPTION	"The IP address of the object, generating the SNMP trap."
	::= { mibtrapProfileEntry 10 }

    trapProfile-AlarmEnabled	OBJECT-TYPE
	SYNTAX	INTEGER {
		    no (1),
		    yes (2)
		}
	ACCESS	read-write
	STATUS	mandatory
	DESCRIPTION	"TRUE if alarm class traps are to be sent to the identified host."
	::= { mibtrapProfileEntry 11 }

    trapProfile-SecurityEnabled	OBJECT-TYPE
	SYNTAX	INTEGER {
		    no (1),
		    yes (2)
		}
	ACCESS	read-write
	STATUS	mandatory
	DESCRIPTION	"TRUE if security class traps are to be sent to the identified host."
	::= { mibtrapProfileEntry 12 }

    trapProfile-PortEnabled	OBJECT-TYPE
	SYNTAX	INTEGER {
		    no (1),
		    yes (2)
		}
	ACCESS	read-write
	STATUS	mandatory
	DESCRIPTION	"TRUE if port class traps are to be sent to the identified host."
	::= { mibtrapProfileEntry 13 }

    trapProfile-SlotEnabled	OBJECT-TYPE
	SYNTAX	INTEGER {
		    no (1),
		    yes (2)
		}
	ACCESS	read-write
	STATUS	mandatory
	DESCRIPTION	"TRUE if slot class traps are to be sent to the identified host."
	::= { mibtrapProfileEntry 14 }

    trapProfile-ColdstartEnabled	OBJECT-TYPE
	SYNTAX	INTEGER {
		    no (1),
		    yes (2)
		}
	ACCESS	read-write
	STATUS	mandatory
	DESCRIPTION	"TRUE if cold start trap is enabled."
	::= { mibtrapProfileEntry 15 }

    trapProfile-WarmstartEnabled	OBJECT-TYPE
	SYNTAX	INTEGER {
		    no (1),
		    yes (2)
		}
	ACCESS	read-write
	STATUS	mandatory
	DESCRIPTION	"TRUE if warm start trap is enabled."
	::= { mibtrapProfileEntry 16 }

    trapProfile-LinkdownEnabled	OBJECT-TYPE
	SYNTAX	INTEGER {
		    no (1),
		    yes (2)
		}
	ACCESS	read-write
	STATUS	mandatory
	DESCRIPTION	"TRUE if link down trap is enabled."
	::= { mibtrapProfileEntry 17 }

    trapProfile-LinkupEnabled	OBJECT-TYPE
	SYNTAX	INTEGER {
		    no (1),
		    yes (2)
		}
	ACCESS	read-write
	STATUS	mandatory
	DESCRIPTION	"TRUE if link up trap is enabled."
	::= { mibtrapProfileEntry 18 }

    trapProfile-AscendEnabled	OBJECT-TYPE
	SYNTAX	INTEGER {
		    no (1),
		    yes (2)
		}
	ACCESS	read-write
	STATUS	mandatory
	DESCRIPTION	"TRUE if Ascend trap is enabled."
	::= { mibtrapProfileEntry 19 }

    trapProfile-ConsoleEnabled	OBJECT-TYPE
	SYNTAX	INTEGER {
		    no (1),
		    yes (2)
		}
	ACCESS	read-write
	STATUS	mandatory
	DESCRIPTION	"TRUE if console trap is enabled."
	::= { mibtrapProfileEntry 20 }

    trapProfile-UseExceededEnabled	OBJECT-TYPE
	SYNTAX	INTEGER {
		    no (1),
		    yes (2)
		}
	ACCESS	read-write
	STATUS	mandatory
	DESCRIPTION	"TRUE if use exceeded trap is enabled."
	::= { mibtrapProfileEntry 21 }

    trapProfile-PasswordEnabled	OBJECT-TYPE
	SYNTAX	INTEGER {
		    no (1),
		    yes (2)
		}
	ACCESS	read-write
	STATUS	mandatory
	DESCRIPTION	"TRUE if Telnet password trap is enabled."
	::= { mibtrapProfileEntry 22 }

    trapProfile-FrLinkupEnabled	OBJECT-TYPE
	SYNTAX	INTEGER {
		    no (1),
		    yes (2)
		}
	ACCESS	read-write
	STATUS	mandatory
	DESCRIPTION	"TRUE if FR link up trap is enabled."
	::= { mibtrapProfileEntry 23 }

    trapProfile-FrLinkdownEnabled	OBJECT-TYPE
	SYNTAX	INTEGER {
		    no (1),
		    yes (2)
		}
	ACCESS	read-write
	STATUS	mandatory
	DESCRIPTION	"TRUE if FR Link Down trap is enabled."
	::= { mibtrapProfileEntry 24 }

    trapProfile-EventOverwriteEnabled	OBJECT-TYPE
	SYNTAX	INTEGER {
		    no (1),
		    yes (2)
		}
	ACCESS	read-write
	STATUS	mandatory
	DESCRIPTION	"TRUE if event Overwrite trap is enabled."
	::= { mibtrapProfileEntry 25 }

    trapProfile-RadiusChangeEnabled	OBJECT-TYPE
	SYNTAX	INTEGER {
		    no (1),
		    yes (2)
		}
	ACCESS	read-write
	STATUS	mandatory
	DESCRIPTION	"TRUE if radius change trap is enabled."
	::= { mibtrapProfileEntry 26 }

    trapProfile-McastMonitorEnabled	OBJECT-TYPE
	SYNTAX	INTEGER {
		    no (1),
		    yes (2)
		}
	ACCESS	read-write
	STATUS	mandatory
	DESCRIPTION	"TRUE if multicast monitor trap is enabled."
	::= { mibtrapProfileEntry 27 }

    trapProfile-LanModemEnabled	OBJECT-TYPE
	SYNTAX	INTEGER {
		    no (1),
		    yes (2)
		}
	ACCESS	read-write
	STATUS	mandatory
	DESCRIPTION	"TRUE if lan modem trap is enabled."
	::= { mibtrapProfileEntry 28 }

    trapProfile-DirdoEnabled	OBJECT-TYPE
	SYNTAX	INTEGER {
		    no (1),
		    yes (2)
		}
	ACCESS	read-write
	STATUS	mandatory
	DESCRIPTION	"TRUE if DIRDO trap is enabled."
	::= { mibtrapProfileEntry 29 }

    trapProfile-SlotProfileChangeEnabled	OBJECT-TYPE
	SYNTAX	INTEGER {
		    no (1),
		    yes (2)
		}
	ACCESS	read-write
	STATUS	mandatory
	DESCRIPTION	"TRUE if slot profile change trap is enabled."
	::= { mibtrapProfileEntry 30 }

    trapProfile-PowerSupplyEnabled	OBJECT-TYPE
	SYNTAX	INTEGER {
		    no (1),
		    yes (2)
		}
	ACCESS	read-write
	STATUS	mandatory
	DESCRIPTION	"TRUE if power supply changed trap is enabled."
	::= { mibtrapProfileEntry 31 }

    trapProfile-MultishelfEnabled	OBJECT-TYPE
	SYNTAX	INTEGER {
		    no (1),
		    yes (2)
		}
	ACCESS	read-write
	STATUS	mandatory
	DESCRIPTION	"TRUE if multi-shelf controller state trap is enabled."
	::= { mibtrapProfileEntry 32 }

    trapProfile-AuthenticationEnabled	OBJECT-TYPE
	SYNTAX	INTEGER {
		    no (1),
		    yes (2)
		}
	ACCESS	read-write
	STATUS	mandatory
	DESCRIPTION	"TRUE if SNMP authentication trap is enabled."
	::= { mibtrapProfileEntry 33 }

    trapProfile-ConfigChangeEnabled	OBJECT-TYPE
	SYNTAX	INTEGER {
		    no (1),
		    yes (2)
		}
	ACCESS	read-write
	STATUS	mandatory
	DESCRIPTION	"TRUE if SNMP configuration change trap is enabled."
	::= { mibtrapProfileEntry 34 }

    trapProfile-SysClockDriftEnabled	OBJECT-TYPE
	SYNTAX	INTEGER {
		    no (1),
		    yes (2)
		}
	ACCESS	read-write
	STATUS	mandatory
	DESCRIPTION	"TRUE if system clock drifted trap is enabled."
	::= { mibtrapProfileEntry 35 }

    trapProfile-PrimarySdtnEmptyEnabled	OBJECT-TYPE
	SYNTAX	INTEGER {
		    no (1),
		    yes (2)
		}
	ACCESS	read-write
	STATUS	mandatory
	DESCRIPTION	"TRUE if SDTN Primary List Empty trap is enabled."
	::= { mibtrapProfileEntry 36 }

    trapProfile-SecondarySdtnEmptyEnabled	OBJECT-TYPE
	SYNTAX	INTEGER {
		    no (1),
		    yes (2)
		}
	ACCESS	read-write
	STATUS	mandatory
	DESCRIPTION	"TRUE if SDTN Secondary List Empty trap is enabled."
	::= { mibtrapProfileEntry 37 }

    trapProfile-SuspectAccessResourceEnabled	OBJECT-TYPE
	SYNTAX	INTEGER {
		    no (1),
		    yes (2)
		}
	ACCESS	read-write
	STATUS	mandatory
	DESCRIPTION	"TRUE if suspect access resource trap is enabled."
	::= { mibtrapProfileEntry 38 }

    trapProfile-OspfEnabled	OBJECT-TYPE
	SYNTAX	INTEGER {
		    no (1),
		    yes (2)
		}
	ACCESS	read-write
	STATUS	mandatory
	DESCRIPTION	"TRUE if OSPF traps are to be sent to the identified host."
	::= { mibtrapProfileEntry 39 }

    trapProfile-OspfIfConfigErrorEnabled	OBJECT-TYPE
	SYNTAX	INTEGER {
		    no (1),
		    yes (2)
		}
	ACCESS	read-write
	STATUS	mandatory
	DESCRIPTION	"TRUE if OSPF interface configuration error trap is enabled."
	::= { mibtrapProfileEntry 40 }

    trapProfile-OspfIfAuthFailureEnabled	OBJECT-TYPE
	SYNTAX	INTEGER {
		    no (1),
		    yes (2)
		}
	ACCESS	read-write
	STATUS	mandatory
	DESCRIPTION	"TRUE if OSPF interface authentication failure trap is enabled."
	::= { mibtrapProfileEntry 41 }

    trapProfile-OspfIfStateChangeEnabled	OBJECT-TYPE
	SYNTAX	INTEGER {
		    no (1),
		    yes (2)
		}
	ACCESS	read-write
	STATUS	mandatory
	DESCRIPTION	"TRUE if OSPF interface state change trap is enabled."
	::= { mibtrapProfileEntry 42 }

    trapProfile-OspfIfRxBadPacket	OBJECT-TYPE
	SYNTAX	INTEGER {
		    no (1),
		    yes (2)
		}
	ACCESS	read-write
	STATUS	mandatory
	DESCRIPTION	"TRUE if OSPF interface receive bad packet trap is enabled."
	::= { mibtrapProfileEntry 43 }

    trapProfile-OspfTxRetransmitEnabled	OBJECT-TYPE
	SYNTAX	INTEGER {
		    no (1),
		    yes (2)
		}
	ACCESS	read-write
	STATUS	mandatory
	DESCRIPTION	"TRUE if OSPF retransmit trap is enabled."
	::= { mibtrapProfileEntry 44 }

    trapProfile-OspfNbrStateChangeEnabled	OBJECT-TYPE
	SYNTAX	INTEGER {
		    no (1),
		    yes (2)
		}
	ACCESS	read-write
	STATUS	mandatory
	DESCRIPTION	"TRUE if OSPF neighbor state change trap is enabled."
	::= { mibtrapProfileEntry 45 }

    trapProfile-OspfVirtIfConfigErrorEnabled	OBJECT-TYPE
	SYNTAX	INTEGER {
		    no (1),
		    yes (2)
		}
	ACCESS	read-write
	STATUS	mandatory
	DESCRIPTION	"TRUE if OSPF virtual interface configuration error trap is enabled."
	::= { mibtrapProfileEntry 46 }

    trapProfile-OspfVirtIfAuthFailureEnabled	OBJECT-TYPE
	SYNTAX	INTEGER {
		    no (1),
		    yes (2)
		}
	ACCESS	read-write
	STATUS	mandatory
	DESCRIPTION	"TRUE if OSPF virtual interface authentication failure trap is enabled."
	::= { mibtrapProfileEntry 47 }

    trapProfile-OspfVirtIfStateChangeEnabled	OBJECT-TYPE
	SYNTAX	INTEGER {
		    no (1),
		    yes (2)
		}
	ACCESS	read-write
	STATUS	mandatory
	DESCRIPTION	"TRUE if OSPF virtual interface state change trap is enabled."
	::= { mibtrapProfileEntry 48 }

    trapProfile-OspfVirtIfRxBadPacket	OBJECT-TYPE
	SYNTAX	INTEGER {
		    no (1),
		    yes (2)
		}
	ACCESS	read-write
	STATUS	mandatory
	DESCRIPTION	"TRUE if OSPF virtual interface receive bad packet trap is enabled."
	::= { mibtrapProfileEntry 49 }

    trapProfile-OspfVirtIfTxRetransmitEnabled	OBJECT-TYPE
	SYNTAX	INTEGER {
		    no (1),
		    yes (2)
		}
	ACCESS	read-write
	STATUS	mandatory
	DESCRIPTION	"TRUE if OSPF virtual interface retransmit trap is enabled."
	::= { mibtrapProfileEntry 50 }

    trapProfile-OspfVirtNbrStateChangeEnabled	OBJECT-TYPE
	SYNTAX	INTEGER {
		    no (1),
		    yes (2)
		}
	ACCESS	read-write
	STATUS	mandatory
	DESCRIPTION	"TRUE if OSPF virtual neighbor state change trap is enabled."
	::= { mibtrapProfileEntry 51 }

    trapProfile-OspfOriginateLsaEnabled	OBJECT-TYPE
	SYNTAX	INTEGER {
		    no (1),
		    yes (2)
		}
	ACCESS	read-write
	STATUS	mandatory
	DESCRIPTION	"TRUE if OSPF originate LSA trap is enabled."
	::= { mibtrapProfileEntry 52 }

    trapProfile-OspfMaxAgeLsaEnabled	OBJECT-TYPE
	SYNTAX	INTEGER {
		    no (1),
		    yes (2)
		}
	ACCESS	read-write
	STATUS	mandatory
	DESCRIPTION	"TRUE if OSPF MaxAgeLsa trap is enabled."
	::= { mibtrapProfileEntry 53 }

    trapProfile-OspfLsdbOverflowEnabled	OBJECT-TYPE
	SYNTAX	INTEGER {
		    no (1),
		    yes (2)
		}
	ACCESS	read-write
	STATUS	mandatory
	DESCRIPTION	"TRUE if OSPF LSDB overflow trap is enabled."
	::= { mibtrapProfileEntry 54 }

    trapProfile-OspfApproachingOverflowEnabled	OBJECT-TYPE
	SYNTAX	INTEGER {
		    no (1),
		    yes (2)
		}
	ACCESS	read-write
	STATUS	mandatory
	DESCRIPTION	"TRUE if OSPF LSDB approaching overflow trap is enabled."
	::= { mibtrapProfileEntry 55 }

    trapProfile-WatchdogWarningEnabled	OBJECT-TYPE
	SYNTAX	INTEGER {
		    no (1),
		    yes (2)
		}
	ACCESS	read-write
	STATUS	mandatory
	DESCRIPTION	"TRUE if watchdog warning trap is enabled."
	::= { mibtrapProfileEntry 56 }

    trapProfile-ControllerSwitchoverEnabled	OBJECT-TYPE
	SYNTAX	INTEGER {
		    no (1),
		    yes (2)
		}
	ACCESS	read-write
	STATUS	mandatory
	DESCRIPTION	"TRUE if controller switchover trap is enabled."
	::= { mibtrapProfileEntry 57 }

    trapProfile-CallLogServChangeEnabled	OBJECT-TYPE
	SYNTAX	INTEGER {
		    no (1),
		    yes (2)
		}
	ACCESS	read-write
	STATUS	mandatory
	DESCRIPTION	"TRUE if call logging server change trap is enabled."
	::= { mibtrapProfileEntry 58 }

    trapProfile-VoipGkChangeEnabled	OBJECT-TYPE
	SYNTAX	INTEGER {
		    no (1),
		    yes (2)
		}
	ACCESS	read-write
	STATUS	mandatory
	DESCRIPTION	"TRUE if VOIP gatekeeper change trap is enabled."
	::= { mibtrapProfileEntry 59 }

    trapProfile-WanLineStateChangeEnabled	OBJECT-TYPE
	SYNTAX	INTEGER {
		    no (1),
		    yes (2)
		}
	ACCESS	read-write
	STATUS	mandatory
	DESCRIPTION	"TRUE if WAN line state change trap is enabled."
	::= { mibtrapProfileEntry 60 }

    trapProfile-CallLogDroppedPktEnabled	OBJECT-TYPE
	SYNTAX	INTEGER {
		    no (1),
		    yes (2)
		}
	ACCESS	read-write
	STATUS	mandatory
	DESCRIPTION	"TRUE if call logging dropped packet trap is enabled."
	::= { mibtrapProfileEntry 61 }

    trapProfile-LimSparingEnabled	OBJECT-TYPE
	SYNTAX	INTEGER {
		    no (1),
		    yes (2)
		}
	ACCESS	read-write
	STATUS	mandatory
	DESCRIPTION	"TRUE if LIM sparing trap should to be sent to the identified host."
	::= { mibtrapProfileEntry 62 }

    trapProfile-InterfaceSparingEnabled	OBJECT-TYPE
	SYNTAX	INTEGER {
		    no (1),
		    yes (2)
		}
	ACCESS	read-write
	STATUS	mandatory
	DESCRIPTION	"TRUE if interface (port) sparing trap should to be sent to the identified host."
	::= { mibtrapProfileEntry 63 }

    trapProfile-MegacoLinkStatusEnabled	OBJECT-TYPE
	SYNTAX	INTEGER {
		    no (1),
		    yes (2)
		}
	ACCESS	read-write
	STATUS	mandatory
	DESCRIPTION	"TRUE if the trap that reports changes in the operational status of media gateway control link(s) is enabled."
	::= { mibtrapProfileEntry 64 }

    trapProfile-SecondaryControllerStateChangeEnabled	OBJECT-TYPE
	SYNTAX	INTEGER {
		    no (1),
		    yes (2)
		}
	ACCESS	read-write
	STATUS	mandatory
	DESCRIPTION	"TRUE if cntrReduAvailTrap is enabled."
	::= { mibtrapProfileEntry 65 }

    trapProfile-PctfiTrunkStatusChangeEnabled	OBJECT-TYPE
	SYNTAX	INTEGER {
		    no (1),
		    yes (2)
		}
	ACCESS	read-write
	STATUS	mandatory
	DESCRIPTION	"TRUE if enabledPctfiTrunkStatusChange is enabled."
	::= { mibtrapProfileEntry 66 }

    trapProfile-NoResourceAvailableEnabled	OBJECT-TYPE
	SYNTAX	INTEGER {
		    no (1),
		    yes (2)
		}
	ACCESS	read-write
	STATUS	mandatory
	DESCRIPTION	"TRUE if No Resource Available to answer call is enabled."
	::= { mibtrapProfileEntry 67 }

    trapProfile-DslThreshTrapEnabled	OBJECT-TYPE
	SYNTAX	INTEGER {
		    no (1),
		    yes (2)
		}
	ACCESS	read-write
	STATUS	mandatory
	DESCRIPTION	"TRUE if various DSL threshold traps should be sent to the identified host."
	::= { mibtrapProfileEntry 68 }

    trapProfile-AtmPvcFailureTrapEnabled	OBJECT-TYPE
	SYNTAX	INTEGER {
		    no (1),
		    yes (2)
		}
	ACCESS	read-write
	STATUS	mandatory
	DESCRIPTION	"TRUE if PVC or Soft PVC failure trap should be sent to the identified host."
	::= { mibtrapProfileEntry 69 }

    trapProfile-AtmImaAlarmTrapEnabled	OBJECT-TYPE
	SYNTAX	INTEGER {
		    no (1),
		    yes (2)
		}
	ACCESS	read-write
	STATUS	mandatory
	DESCRIPTION	"TRUE if IMA Alarm trap should be sent to the identified host."
	::= { mibtrapProfileEntry 70 }

    trapProfile-AscendLinkDownTrapEnabled	OBJECT-TYPE
	SYNTAX	INTEGER {
		    no (1),
		    yes (2)
		}
	ACCESS	read-write
	STATUS	mandatory
	DESCRIPTION	"TRUE if the ascend link down trap should be sent to the identified host. This can be enabled only if linkdown-enabled is enabled. This is an alarm class trap."
	::= { mibtrapProfileEntry 71 }

    trapProfile-AscendLinkUpTrapEnabled	OBJECT-TYPE
	SYNTAX	INTEGER {
		    no (1),
		    yes (2)
		}
	ACCESS	read-write
	STATUS	mandatory
	DESCRIPTION	"TRUE if the ascend link up trap should be sent to the identified host. This can be enabled only if linkup-enabled is enabled. This is an alarm class trap."
	::= { mibtrapProfileEntry 72 }

    trapProfile-SnmpIllegalAccessAttempt	OBJECT-TYPE
	SYNTAX	INTEGER {
		    no (1),
		    yes (2)
		}
	ACCESS	read-write
	STATUS	mandatory
	DESCRIPTION	"TRUE if the ascend security alert trap is enabled."
	::= { mibtrapProfileEntry 73 }

    trapProfile-L2tpTunnelTrapEnabled	OBJECT-TYPE
	SYNTAX	INTEGER {
		    no (1),
		    yes (2)
		}
	ACCESS	read-write
	STATUS	mandatory
	DESCRIPTION	"TRUE if L2TP Setup failure and L2TP Tunnel Disconnect trap should be sent to the identified host."
	::= { mibtrapProfileEntry 79 }

    trapProfile-Hdsl2ShdslThresholdTrapsEnabled	OBJECT-TYPE
	SYNTAX	INTEGER {
		    no (1),
		    yes (2)
		}
	ACCESS	read-write
	STATUS	mandatory
	DESCRIPTION	"Set to TRUE to enable HDSL2/SHDSL threshold traps."
	::= { mibtrapProfileEntry 77 }

    trapProfile-ClockChangeTrapEnabled	OBJECT-TYPE
	SYNTAX	INTEGER {
		    no (1),
		    yes (2)
		}
	ACCESS	read-write
	STATUS	mandatory
	DESCRIPTION	"TRUE if clock change trap is enabled."
	::= { mibtrapProfileEntry 78 }

    trapProfile-Action-o	OBJECT-TYPE
	SYNTAX	INTEGER {
		    noAction (1),
		    createProfile (2),
		    deleteProfile (3)
		}
	ACCESS	read-write
	STATUS	mandatory
	DESCRIPTION	""
	::= { mibtrapProfileEntry 74 }

END
