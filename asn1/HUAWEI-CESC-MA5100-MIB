-- -----------------------------------------------------------------------------
--                  HUAWEI MUSA Enterprise MIB   
--                                       Musa CESC MIB 
--      Copyright (c) 1999-2002 HUA WEI TECH CO.,LTD,SHENZHEN.
--      All rights reserved.
--
--  Created by:  Xu Gang
--  Create date: 2000-11-14
--  Modify by: Lai Zhansong
--  Modify date: 2002-11-13
-- -----------------------------------------------------------------------------

HUAWEI-CESC-MA5100-MIB DEFINITIONS ::= BEGIN
IMPORTS
        OBJECT-TYPE    FROM   RFC-1212
             Counter   FROM   RFC1155-SMI
        hwMa5100Mib, hwMusaFrameIndex, hwMusaSlotIndex   FROM HUAWEI-MUSA-MA5100-MIB;

    -- ----------------------------------------------------------------------------
    -- CESC MIB
    -- ----------------------------------------------------------------------------
    hwMusaCescMib    OBJECT IDENTIFIER ::= { hwMa5100Mib 8 }

    -- Board config table for CES with E1 subboard

    hwMusaCescCfgTable   OBJECT-TYPE
    SYNTAX          SEQUENCE OF HwMusaCescCfgEntry
    ACCESS          not-accessible 
    STATUS          mandatory
    DESCRIPTION     "Board config table"
    ::= { hwMusaCescMib 1}

    hwMusaCescCfgEntry   OBJECT-TYPE
    SYNTAX          HwMusaCescCfgEntry
    ACCESS          not-accessible 
    STATUS          mandatory
    DESCRIPTION     "Board config table entry"
    INDEX
    { 
        hwMusaFrameIndex,
        hwMusaSlotIndex
    }
    ::= { hwMusaCescCfgTable 1 }
    
    HwMusaCescCfgEntry ::= SEQUENCE
    {
        hwMusaCescWorkMode        INTEGER,
        hwMusaCesc16MTDMBus0      INTEGER,
        hwMusaCesc16MTDMBus1      INTEGER,
        hwMusaCesc16MTDMBus2      INTEGER,
        hwMusaCesc16MTDMBus3      INTEGER           
    }


    hwMusaCescWorkMode OBJECT-TYPE
    SYNTAX          INTEGER { 
                             tdm-cesc(0),
                             e1-interface(1)
                            }
    ACCESS          read-write
    STATUS          mandatory
    DESCRIPTION     "Working mode of CES board"
    ::= { hwMusaCescCfgEntry 3 }

    hwMusaCesc16MTDMBus0 OBJECT-TYPE
    SYNTAX          INTEGER (0..15)
    ACCESS          read-write
    STATUS          mandatory
    DESCRIPTION     "TDM bus 0 of CES board"
    ::= { hwMusaCescCfgEntry 4 }

    hwMusaCesc16MTDMBus1 OBJECT-TYPE
    SYNTAX          INTEGER (0..15)
    ACCESS          read-write
    STATUS          mandatory
    DESCRIPTION     "TDM bus 1 of CES board"
    ::= { hwMusaCescCfgEntry 5 }

    hwMusaCesc16MTDMBus2 OBJECT-TYPE
    SYNTAX          INTEGER (0..15)
    ACCESS          read-write
    STATUS          mandatory
    DESCRIPTION     "TDM bus 2 of CES board"
    ::= { hwMusaCescCfgEntry 6 }

    hwMusaCesc16MTDMBus3 OBJECT-TYPE
    SYNTAX          INTEGER (0..15)
    ACCESS          read-write
    STATUS          mandatory
    DESCRIPTION     "TDM bus 3 of CES board"
    ::= { hwMusaCescCfgEntry 7 }

    -- Port config table for CES with E1 subboard

    hwMusaCescPortCfgTable OBJECT-TYPE
    SYNTAX          SEQUENCE OF HwMusaCescPortCfgEntry
    ACCESS          not-accessible 
    STATUS          mandatory
    DESCRIPTION     "E1 port config table"
    ::= { hwMusaCescMib 2 }

    hwMusaCescPortCfgEntry   OBJECT-TYPE
    SYNTAX          HwMusaCescPortCfgEntry
    ACCESS          not-accessible 
    STATUS          mandatory
    DESCRIPTION     "E1 port config table entry"
    INDEX {   
        hwMusaFrameIndex,
        hwMusaSlotIndex,
        hwMusaCescPortIndex
        }
    ::= { hwMusaCescPortCfgTable 1 }

    HwMusaCescPortCfgEntry ::= SEQUENCE
    {
    hwMusaCescPortIndex           INTEGER,
    hwMusaCescPortWorkMode        INTEGER,
    hwMusaCescPortClockMode       INTEGER,
    hwMusaCescPortSignalType      INTEGER,
    hwMusaCescPortFrameVerifyMode INTEGER,
    hwMusaCescPortTimeSlotBMP     INTEGER,
    hwMusaCescPortWarningStatus   INTEGER,
    hwMusaCescPortUtopiaStatus    INTEGER,
    hwMusaCescPortLiuStatus       INTEGER,
    hwMusaCescPortBlock           INTEGER
    }

    hwMusaCescPortIndex       OBJECT-TYPE
    SYNTAX              INTEGER(0..15)
    ACCESS              not-accessible
    STATUS              mandatory
    DESCRIPTION       "CES port index"
    ::= { hwMusaCescPortCfgEntry 3 }

    hwMusaCescPortWorkMode      OBJECT-TYPE
    SYNTAX          INTEGER   {
                                uni(0),
                                sdt(1),
                                udt(2),
                                idle(3)
                              }
    ACCESS          read-write
    STATUS          mandatory
    DESCRIPTION     "The working mode of E1 port"
    ::= { hwMusaCescPortCfgEntry 4 }
 
    hwMusaCescPortClockMode     OBJECT-TYPE
    SYNTAX          INTEGER  {                              
                         sys-clk('00'h),        --System CLK          
                         rx-clk('01'h),         --Rx CLK              
                         reco-clk-acm('02'h),   --ACM (Recovered CLK) 
                         reco-clk-srts('03'h)   --SRTS (Recovered CLK)
                             }
    ACCESS          read-write
    STATUS          mandatory 
    DESCRIPTION    "Clock mode of E1 port"
    ::= { hwMusaCescPortCfgEntry 5 }
        
    hwMusaCescPortSignalType   OBJECT-TYPE
    SYNTAX          INTEGER {
                                ccs(0),
                                cas(1)
                                }
    ACCESS          read-write
    STATUS          mandatory
    DESCRIPTION     "Signal type of E1 port"
    ::= { hwMusaCescPortCfgEntry 6 }
    

    hwMusaCescPortFrameVerifyMode OBJECT-TYPE
    SYNTAX           INTEGER {
                              enable-crc4(1),
                              diable-crc4(0)
                             }
    ACCESS           read-write
    STATUS           mandatory
    DESCRIPTION      "Frame verify mode of E1 port"
    ::= { hwMusaCescPortCfgEntry 7 }

    hwMusaCescPortTimeSlotBMP OBJECT-TYPE
    SYNTAX           INTEGER
    ACCESS           read-only
    STATUS           mandatory
    DESCRIPTION      "Timeslot bitmap of E1 port"
    ::= { hwMusaCescPortCfgEntry 8 }

    hwMusaCescPortWarningStatus   OBJECT-TYPE
    SYNTAX           INTEGER
    ACCESS           read-only
    STATUS           mandatory
    DESCRIPTION      "Alarm state of E1 port
                      bit0- LOS
                      bit1- LOF
                      bit2- RRA
                      bit3- LMF
                      bit4- AIS"
    ::= { hwMusaCescPortCfgEntry 9 }

    hwMusaCescPortUtopiaStatus       OBJECT-TYPE
    SYNTAX          INTEGER {normal(1), test(2), idle(3), noinstall(4), failure(5),blocked(6)}
    ACCESS          read-only
    STATUS          mandatory
    DESCRIPTION     "UTOPIA port state( normal(1), test(2), idle(3), noinstall(4), failure(5), blocked(6)"
    ::= { hwMusaCescPortCfgEntry 10 }

    hwMusaCescPortLiuStatus       OBJECT-TYPE
    SYNTAX          INTEGER {normal(1), test(2), idle(3), noinstall(4),failure(5),blocked(6),localtest(11),remotetest(12),tslocal(13)}
    ACCESS          read-only
    STATUS          mandatory
    DESCRIPTION     "LIU port state (normal(1), test(2), idle(3), noinstall(4),failure(5),blocked(6),localtest(11),remotetest(12),tslocal(13)"
    ::= { hwMusaCescPortCfgEntry 11 }
    
    hwMusaCescPortBlock        OBJECT-TYPE     
    SYNTAX              INTEGER{
                                block(0),
                                unblock(1)
                               }
    ACCESS              write-only
    STATUS              mandatory
    DESCRIPTION         "To block or unblock the E1 port"
    ::= { hwMusaCescPortCfgEntry 12 }

    -- Port config table for CES with V35 subboard
    
    hwMusaCescPortV35CfgTable OBJECT-TYPE
    SYNTAX          SEQUENCE OF HwMusaCescPortV35CfgEntry
    ACCESS          not-accessible 
    STATUS          mandatory
    DESCRIPTION     "V35 port config table"
    ::= { hwMusaCescMib 3 }

    hwMusaCescPortV35CfgEntry OBJECT-TYPE
    SYNTAX          HwMusaCescPortV35CfgEntry
    ACCESS          not-accessible
    STATUS          mandatory
    DESCRIPTION     "V35 port config table entry"
    INDEX {
            hwMusaFrameIndex,
            hwMusaSlotIndex,
            hwMusaCescPortIndex
          }
    ::= { hwMusaCescPortV35CfgTable 1 }
    
    HwMusaCescPortV35CfgEntry ::= SEQUENCE
    {
                hwMusaCescPortV35NValue         INTEGER,
                hwMusaCescPortV35ClockMode      INTEGER,
                hwMusaCescPortV35BlockStatus    INTEGER,
                hwMusaCescPortV35ReversePhase   INTEGER,
                hwMusaCescPortV35WarningStatus  INTEGER,
                hwMusaCescPortV35Status         INTEGER
    }

    hwMusaCescPortV35NValue             OBJECT-TYPE
    SYNTAX              INTEGER(0..31)
    ACCESS              read-only
    STATUS              mandatory
    DESCRIPTION         "N value of V35 port"
    ::= { hwMusaCescPortV35CfgEntry 4 }

    hwMusaCescPortV35ClockMode          OBJECT-TYPE     
    SYNTAX              INTEGER {       
                                 dceinter('00'h), --DCE-internal
                                 dceslave('01'h), --DCE-slave
                                 dceouter('02'h), --DCE-external
                                 dteinter('03'h), --DTE-internal
                                 dteslave('04'h), --DTE-slave
                                 dteouter('05'h)  --DTE-external
                                }
    ACCESS              read-write
    STATUS              mandatory
    DESCRIPTION         "Clock mode of V35 port"
    ::= { hwMusaCescPortV35CfgEntry 5 }

    hwMusaCescPortV35BlockStatus        OBJECT-TYPE     
    SYNTAX              INTEGER{
                                block(0),
                                unblock(1)
                               }
    ACCESS              write-only
    STATUS              mandatory
    DESCRIPTION         "To block or unblock the V35 port"
    ::= { hwMusaCescPortV35CfgEntry 6 }

    hwMusaCescPortV35ReversePhase       OBJECT-TYPE     
    SYNTAX              INTEGER {
                                unreversephase(0),
                                reversephase(1)
                                }
    ACCESS              read-write
    STATUS              mandatory
    DESCRIPTION         "Inverse the clock of V35 port"
    ::= { hwMusaCescPortV35CfgEntry 7 }

    hwMusaCescPortV35WarningStatus      OBJECT-TYPE     
    SYNTAX              INTEGER
    ACCESS              read-only
    STATUS              mandatory
    DESCRIPTION         "Alarm state of V35 port"
    ::= { hwMusaCescPortV35CfgEntry 8 }

    hwMusaCescPortV35Status             OBJECT-TYPE
    SYNTAX              INTEGER{
                              normal(1),
                              test(2),
                              idle(3),
                              localtest(4),
                              remotetest(5),
                              block(6)
                               }
    ACCESS              read-only
    STATUS              mandatory
    DESCRIPTION         "Port state of V35"
    ::= { hwMusaCescPortV35CfgEntry 9 }

    -- statistics table of CES SDT channel

    hwMusaCescChnlStatisTable OBJECT-TYPE
    SYNTAX          SEQUENCE OF HwMusaCescChnlStatisEntry
    ACCESS          not-accessible 
    STATUS          mandatory
    DESCRIPTION     "Statistics table of CES SDT channel"
    ::= { hwMusaCescMib 4 }
 
    hwMusaCescChnlStatisEntry OBJECT-TYPE
    SYNTAX          HwMusaCescChnlStatisEntry
    ACCESS          not-accessible
    STATUS          mandatory
    DESCRIPTION     "Statistics table entry of CES SDT channel"
    INDEX {
            hwMusaFrameIndex,
                hwMusaSlotIndex,
                hwMusaCescPortIndex,
            hwMusaCescChnlIndex
           }
    ::= { hwMusaCescChnlStatisTable 1 }

    HwMusaCescChnlStatisEntry ::= SEQUENCE
    {
                hwMusaCescChnlIndex                INTEGER,
                hwMusaCescChnlStatisCounter0       Counter,
                hwMusaCescChnlStatisCounter1       Counter,
                hwMusaCescChnlStatisCounter2       Counter,
                hwMusaCescChnlStatisCounter3       Counter,
                hwMusaCescChnlStatisCounter4       Counter,
                hwMusaCescChnlStatisCounter5       Counter,
                hwMusaCescChnlStatisCounter6       Counter,
                hwMusaCescChnlStatisCounter7       Counter,
                hwMusaCescChnlStatisCounter8       Counter,
                hwMusaCescChnlStatisCounter9       Counter,
                hwMusaCescChnlStatisCounter10      Counter,
                hwMusaCescChnlStatisCounter11      Counter,
                hwMusaCescChnlStatisCounter12      Counter,
                hwMusaCescChnlStatisCounter13      Counter,
                hwMusaCescChnlStatisCounter14      Counter,
                hwMusaCescChnlStatisCounter15      Counter,
                hwMusaCescChnlStatisOper           INTEGER
    }

    hwMusaCescChnlIndex OBJECT-TYPE
    SYNTAX     INTEGER 
    ACCESS     not-accessible
    STATUS     mandatory
    DESCRIPTION "SDT channel Index"
    ::= { hwMusaCescChnlStatisEntry 4 }
     
    hwMusaCescChnlStatisCounter0 OBJECT-TYPE
    SYNTAX    Counter
    ACCESS    read-write
    STATUS    mandatory 
    DESCRIPTION   "Discard cells due to output queue"
    ::= { hwMusaCescChnlStatisEntry 5 }

    hwMusaCescChnlStatisCounter1 OBJECT-TYPE
    SYNTAX    Counter
    ACCESS    read-write
    STATUS    mandatory 
    DESCRIPTION   "not used"
    ::= { hwMusaCescChnlStatisEntry 6 }

    hwMusaCescChnlStatisCounter2 OBJECT-TYPE
    SYNTAX    Counter
    ACCESS    read-write
    STATUS    mandatory 
    DESCRIPTION   "Cells that are passed to framer interface"
    ::= { hwMusaCescChnlStatisEntry 7 }

    hwMusaCescChnlStatisCounter3 OBJECT-TYPE
    SYNTAX    Counter
    ACCESS    read-write
    STATUS    mandatory 
    DESCRIPTION   "Times SDT start of structure changes phase upstream"
    ::= { hwMusaCescChnlStatisEntry 8 }

    hwMusaCescChnlStatisCounter4 OBJECT-TYPE
    SYNTAX    Counter
    ACCESS    read-write
    STATUS    mandatory 
    DESCRIPTION   "Discard downstream cells with invalid SN/SNP"
    ::= { hwMusaCescChnlStatisEntry 9 }

    hwMusaCescChnlStatisCounter5 OBJECT-TYPE
    SYNTAX    Counter
    ACCESS    read-write
    STATUS    mandatory 
    DESCRIPTION   "End of reassembly buffer overflow"
    ::= { hwMusaCescChnlStatisEntry 10 }

    hwMusaCescChnlStatisCounter6 OBJECT-TYPE
    SYNTAX    Counter
    ACCESS    read-write
    STATUS    mandatory 
    DESCRIPTION   "Downstream cells with invalid SN/SNP"
    ::= { hwMusaCescChnlStatisEntry 11 }

    hwMusaCescChnlStatisCounter7 OBJECT-TYPE
    SYNTAX    Counter
    ACCESS    read-write
    STATUS    mandatory 
    DESCRIPTION   "SC out of sequence"
    ::= { hwMusaCescChnlStatisEntry 12 }

    hwMusaCescChnlStatisCounter8 OBJECT-TYPE
    SYNTAX    Counter
    ACCESS    read-write
    STATUS    mandatory 
    DESCRIPTION   "Downstream misinserted cells detected by SC algorithm"
    ::= { hwMusaCescChnlStatisEntry 13 }

    hwMusaCescChnlStatisCounter9 OBJECT-TYPE
    SYNTAX    Counter
    ACCESS    read-write
    STATUS    mandatory 
    DESCRIPTION   "Downstream cells discarded by SC algorithm"
    ::= { hwMusaCescChnlStatisEntry 14 }

    hwMusaCescChnlStatisCounter10 OBJECT-TYPE
    SYNTAX    Counter
    ACCESS    read-write
    STATUS    mandatory 
    DESCRIPTION   "Rejected SDT pointer due to parity error"
    ::= { hwMusaCescChnlStatisEntry 15 }

    hwMusaCescChnlStatisCounter11 OBJECT-TYPE
    SYNTAX    Counter
    ACCESS    read-write
    STATUS    mandatory 
    DESCRIPTION   "SC cycles with no SDT pointer field or more than one pointer field"
    ::= { hwMusaCescChnlStatisEntry 16 }

    hwMusaCescChnlStatisCounter12 OBJECT-TYPE
    SYNTAX    Counter
    ACCESS    read-write
    STATUS    mandatory 
    DESCRIPTION   "End of reassembly buffer underflow"
    ::= { hwMusaCescChnlStatisEntry 17 }

    hwMusaCescChnlStatisCounter13 OBJECT-TYPE
    SYNTAX    Counter
    ACCESS    read-write
    STATUS    mandatory 
    DESCRIPTION   "Insert starvation cells due to reassembly buffer underflow"
    ::= { hwMusaCescChnlStatisEntry 18 }

    hwMusaCescChnlStatisCounter14 OBJECT-TYPE
    SYNTAX    Counter
    ACCESS    read-write
    STATUS    mandatory 
    DESCRIPTION   "Times ATM start of structure out of sync with port start of structure"
    ::= { hwMusaCescChnlStatisEntry 19 }

    hwMusaCescChnlStatisCounter15 OBJECT-TYPE
    SYNTAX    Counter
    ACCESS    read-write
    STATUS    mandatory 
    DESCRIPTION   "Downstream lost cells detected by SC algorithm"
    ::= { hwMusaCescChnlStatisEntry 20 }

    hwMusaCescChnlStatisOper     OBJECT-TYPE
    SYNTAX      INTEGER { del(1) }
    ACCESS      read-write
    STATUS      mandatory
    DESCRIPTION   "Clear CES SDT channel statistics"
    ::= { hwMusaCescChnlStatisEntry 21 }

    -- statistics table of CES UDT/UNI port

    hwMusaCescPortStatisTable OBJECT-TYPE
    SYNTAX          SEQUENCE OF HwMusaCescPortStatisEntry
    ACCESS          not-accessible 
    STATUS          mandatory
    DESCRIPTION     "Statistics table of CES UDT/UNI port(UNI port  only use from counter 0 to counter 4)"
    ::= { hwMusaCescMib 5 }
   
    hwMusaCescPortStatisEntry OBJECT-TYPE
    SYNTAX         HwMusaCescPortStatisEntry
    ACCESS         not-accessible
    STATUS         mandatory
    DESCRIPTION    "Statistics table entry of CES UDT/UNI port" 
    INDEX {
                hwMusaFrameIndex,
                hwMusaSlotIndex,
                hwMusaCescPortIndex           
          } 
   ::= { hwMusaCescPortStatisTable 1 }

    HwMusaCescPortStatisEntry ::= SEQUENCE
    {
         hwMusaCescPortStatisCounter0     Counter,
         hwMusaCescPortStatisCounter1     Counter,
         hwMusaCescPortStatisCounter2     Counter,
         hwMusaCescPortStatisCounter3     Counter,
         hwMusaCescPortStatisCounter4     Counter,
         hwMusaCescPortStatisCounter5     Counter,
         hwMusaCescPortStatisCounter6     Counter,
         hwMusaCescPortStatisCounter7     Counter,
         hwMusaCescPortStatisCounter8     Counter,
         hwMusaCescPortStatisCounter9     Counter,
         hwMusaCescPortStatisCounter10     Counter,
         hwMusaCescPortStatisCounter11     Counter,
         hwMusaCescPortStatisCounter12     Counter,
         hwMusaCescPortStatisCounter13     Counter,
         hwMusaCescPortStatisCounter14     Counter,
         hwMusaCescPortStatisCounter15     Counter,      
         hwMusaCescPortStatisOper         INTEGER
    }
   
    hwMusaCescPortStatisCounter0  OBJECT-TYPE
    SYNTAX       Counter
    ACCESS       read-write
    STATUS       mandatory
    DESCRIPTION  "Discard cells due to output queue"  
    ::= { hwMusaCescPortStatisEntry 4 }

    hwMusaCescPortStatisCounter1  OBJECT-TYPE
    SYNTAX       Counter
    ACCESS       read-write
    STATUS       mandatory
    DESCRIPTION  "Not used (UDT)
                  Received cells with correctable HEC errors (UNI)"  
    ::= { hwMusaCescPortStatisEntry 5 }

    hwMusaCescPortStatisCounter2  OBJECT-TYPE
    SYNTAX       Counter
    ACCESS       read-write
    STATUS       mandatory
    DESCRIPTION  "Cells that are passed to framer interface (UDT) 
                  Received cells with non-correctable HEC errors (UNI)"  
    ::= { hwMusaCescPortStatisEntry 6 }

    hwMusaCescPortStatisCounter3  OBJECT-TYPE
    SYNTAX       Counter
    ACCESS       read-write
    STATUS       mandatory
    DESCRIPTION  "Times SDT start of structure changes phase upstream (UDT)
                  Times cell delineation SYNC state is left (UNI)"  
    ::= { hwMusaCescPortStatisEntry 7 }

    hwMusaCescPortStatisCounter4  OBJECT-TYPE
    SYNTAX       Counter
    ACCESS       read-write
    STATUS       mandatory
    DESCRIPTION  "Discard downstream cells with invalid SN/SNP (UDT)
                  Discard cells due to ATM transmit buffer overflow (UNI)"  
    ::= { hwMusaCescPortStatisEntry 8 }

    hwMusaCescPortStatisCounter5  OBJECT-TYPE
    SYNTAX       Counter
    ACCESS       read-write
    STATUS       mandatory
    DESCRIPTION  "End of reassembly buffer overflow (UDT)"  
    ::= { hwMusaCescPortStatisEntry 9 }

    hwMusaCescPortStatisCounter6  OBJECT-TYPE
    SYNTAX       Counter
    ACCESS       read-write
    STATUS       mandatory
    DESCRIPTION  "Downstream cells with invalid SN/SNP (UDT)"  
    ::= { hwMusaCescPortStatisEntry 10 }

    hwMusaCescPortStatisCounter7  OBJECT-TYPE
    SYNTAX       Counter
    ACCESS       read-write
    STATUS       mandatory
    DESCRIPTION  "SC out of sequence (UDT)"  
    ::= { hwMusaCescPortStatisEntry 11 }

    hwMusaCescPortStatisCounter8  OBJECT-TYPE
    SYNTAX       Counter
    ACCESS       read-write
    STATUS       mandatory
    DESCRIPTION  "Downstream misinserted cells detected by SC algorithm (UDT) "  
    ::= { hwMusaCescPortStatisEntry 12 }

    hwMusaCescPortStatisCounter9  OBJECT-TYPE
    SYNTAX       Counter
    ACCESS       read-write
    STATUS       mandatory
    DESCRIPTION  "Downstream cells discarded by SC algorithm  (UDT)"  
    ::= { hwMusaCescPortStatisEntry 13 }

    hwMusaCescPortStatisCounter10  OBJECT-TYPE
    SYNTAX       Counter
    ACCESS       read-write
    STATUS       mandatory
    DESCRIPTION  "Rejected SDT pointer due to parity error  (UDT)"  
    ::= { hwMusaCescPortStatisEntry 14 }

    hwMusaCescPortStatisCounter11  OBJECT-TYPE
    SYNTAX       Counter
    ACCESS       read-write
    STATUS       mandatory
    DESCRIPTION  "SC cycles with no SDT pointer field or more than one pointer field  (UDT)"  
    ::= { hwMusaCescPortStatisEntry 15 }

    hwMusaCescPortStatisCounter12  OBJECT-TYPE
    SYNTAX       Counter
    ACCESS       read-write
    STATUS       mandatory
    DESCRIPTION  "End of reassembly buffer underflow  (UDT)"  
    ::= { hwMusaCescPortStatisEntry 16 }

    hwMusaCescPortStatisCounter13  OBJECT-TYPE
    SYNTAX       Counter
    ACCESS       read-write
    STATUS       mandatory
    DESCRIPTION  "Insert starvation cells due to reassembly buffer underflow  (UDT)"  
    ::= { hwMusaCescPortStatisEntry 17 }

    hwMusaCescPortStatisCounter14  OBJECT-TYPE
    SYNTAX       Counter
    ACCESS       read-write
    STATUS       mandatory
    DESCRIPTION  "Times ATM start of structure out of sync with port start of structure  (UDT)"  
    ::= { hwMusaCescPortStatisEntry 18 }

    hwMusaCescPortStatisCounter15  OBJECT-TYPE
    SYNTAX       Counter
    ACCESS       read-write
    STATUS       mandatory
    DESCRIPTION  "Downstream lost cells detected by SC algorithm  (UDT)"  
    ::= { hwMusaCescPortStatisEntry 19 }
    
    hwMusaCescPortStatisOper OBJECT-TYPE
    SYNTAX       INTEGER { 
                          del(1)
                          }
    ACCESS       read-write
    STATUS       mandatory
    DESCRIPTION  "Clear CES UNI/UDT port statistics"
    ::= { hwMusaCescPortStatisEntry 20 }

    -- maintenace table of CES port

    hwMusaCescPortMaintTable OBJECT-TYPE
    SYNTAX          SEQUENCE OF HwMusaCescPortMaintEntry
    ACCESS          not-accessible 
    STATUS          mandatory
    DESCRIPTION     "Maintenace table of CES port "
    ::= { hwMusaCescMib 6 }
    
    hwMusaCescPortMaintEntry   OBJECT-TYPE
    SYNTAX         HwMusaCescPortMaintEntry
    ACCESS         not-accessible
    STATUS         mandatory
    DESCRIPTION    "Maintenace table entry of CES port"
    INDEX {
                hwMusaFrameIndex,
                hwMusaSlotIndex,
                hwMusaCescPortIndex                       
          }
    ::= { hwMusaCescPortMaintTable 1 }
    
    HwMusaCescPortMaintEntry ::= SEQUENCE
    {
         hwMusaCescPortMaintLoop    INTEGER,
         hwMusaCescPortMaintOper    INTEGER,
         hwMusaCescSingleTimeslotId INTEGER       
    }
    
    hwMusaCescPortMaintLoop OBJECT-TYPE
    SYNTAX       INTEGER {
                         noloop('00'h),
                         local('01'h),
                         remote('02'h),
                         single-timeslot('04'h)
                         }
    ACCESS       read-write
    STATUS       mandatory
    DESCRIPTION  "The looping test mode of CES port"
    ::= { hwMusaCescPortMaintEntry 4 }

    hwMusaCescPortMaintOper   OBJECT-TYPE
    SYNTAX          INTEGER   {set(0),unset(1)}    
    ACCESS          read-write
    STATUS          mandatory
    DESCRIPTION  "The oprating of looping test mode"
    ::= { hwMusaCescPortMaintEntry 5 }
    
    hwMusaCescSingleTimeslotId   OBJECT-TYPE
    SYNTAX          INTEGER   (1..31)    
    ACCESS          read-write
    STATUS          mandatory
    DESCRIPTION  "The timeslot number of single timeslot looping test (only for SDT port)"
    ::= { hwMusaCescPortMaintEntry 6 }   

 END
