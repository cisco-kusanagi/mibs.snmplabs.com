--**************************************************************************
--                                                                          
--    Copyright 2004 Broadcom Corporation                                   
--    All Rights Reserved                                                   
--    No portions of this material may be reproduced in any form without the
--    written permission of:                                                
--             Broadcom Corporation                                         
--             16251 Laguna Canyon Road                                     
--             Irvine, California  92618                                    
--    All information contained in this document is Broadcom Corporation    
--    company private, proprietary, and trade secret.                       
--                                                                          
--                                                                          
--                                                                          
--**************************************************************************
--    Filename: brcm-http-mgmt.mib
--    Author:   Kevin O'Neal
--    Creation Date: 24-february-2004
--
--**************************************************************************
--    Description:
--
--		private MIB for runtime BFC management
--		
--**************************************************************************
--    Revision History:
--
--**************************************************************************

BRCM-HTTP-MGMT-MIB DEFINITIONS ::= BEGIN

IMPORTS
    MODULE-IDENTITY,
    OBJECT-TYPE,
    IpAddress
        FROM SNMPv2-SMI
    DisplayString,
    TruthValue
        FROM SNMPv2-TC
    cableDataMgmtBase
        FROM BRCM-CABLEDATA-MGMT-MIB;
                
httpMgmt MODULE-IDENTITY
    LAST-UPDATED "200402240000Z"
    ORGANIZATION "Broadcom Corporation"
    CONTACT-INFO
        "	BANANA-CABLEDATA
                (cableData branch of the
                Broadcom Assigned Numbers and Naming Authority)
                Broadcom Corporation

        Postal: 4385 River Green Parkway
                Duluth, GA  30096
                USA

           Tel: +1 770 232-0018

        E-mail: banana-cabledata@broadcom.com"
    DESCRIPTION
        "Broadcom HTTP management MIB"
    REVISION      "200402240000Z"
    DESCRIPTION
            "Initial version of this MIB module."
    ::= { cableDataMgmtBase 3 }
    
httpAdminId OBJECT-TYPE
    SYNTAX      DisplayString
    MAX-ACCESS  read-write
    STATUS      current
    DESCRIPTION
        "Controls and reflects the user name for admin level HTTP priveleges."
    DEFVAL { "" }
    ::= { httpMgmt 1 }

httpAdminPassword OBJECT-TYPE
    SYNTAX      DisplayString
    MAX-ACCESS  read-write
    STATUS      current
    DESCRIPTION
        "Controls and reflects the password for admin level HTTP priveleges."
    DEFVAL { "" }
    ::= { httpMgmt 2 }
    
httpUserId OBJECT-TYPE
    SYNTAX      DisplayString
    MAX-ACCESS  read-write
    STATUS      current
    DESCRIPTION
        "Controls and reflects the user name for user level HTTP priveleges."
    DEFVAL { "" }
    ::= { httpMgmt 3 }

httpUserPassword OBJECT-TYPE
    SYNTAX      DisplayString
    MAX-ACCESS  read-write
    STATUS      current
    DESCRIPTION
        "Controls and reflects the password for user level HTTP priveleges."
    DEFVAL { "" }
    ::= { httpMgmt 4 }

httpIpStackInterfaces OBJECT-TYPE
    SYNTAX      BITS {
                interface1(0),
                interface2(1),
                interface3(2),
                interface4(3),
                interface5(4),
                interface6(5),
                interface7(6),
                interface8(7)
    }
    MAX-ACCESS  read-write
    STATUS      current
    DESCRIPTION
        "Controls and reflects the IP stack interfaces on which an HTTP server
         is active.  By default, the HTTP server is enabled only on the private
         IP stack interface."
    ::= { httpMgmt 5 }

httpAdvancedAccessEnabled OBJECT-TYPE
    SYNTAX      BITS {
                interface1(0),
                interface2(1),
                interface3(2),
                interface4(3),
                interface5(4),
                interface6(5),
                interface7(6),
                interface8(7)
    }
    MAX-ACCESS  read-write
    STATUS      current
    DESCRIPTION
        "Controls and reflects the IP stack interfaces on which advanced
        access is allowed.  By default, advanced access is allowed only on
        remote stack interfaces."
    ::= { httpMgmt 6 }

httpPasswordOfTheDaySeed OBJECT-TYPE
    SYNTAX      DisplayString
    MAX-ACCESS  read-write
    STATUS      current
    DESCRIPTION
        "Controls and reflects the seed used to generate the password of the day."
    DEFVAL { "" }
    ::= { httpMgmt 7 }

END
