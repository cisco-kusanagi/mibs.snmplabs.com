CNTEXT-MIB 

   --FORCE-INCLUDE <mib.h>
   --FORCE-INCLUDE <snmpdefs.h>
   --FORCE-INCLUDE <snmpstat.h>
   --FORCE-INCLUDE "mibproto.h"
 
	DEFINITIONS ::= BEGIN

	IMPORTS
		MODULE-IDENTITY, OBJECT-TYPE, Integer32, IpAddress, Counter32
			FROM SNMPv2-SMI
		DisplayString, RowStatus
			FROM SNMPv2-TC
		cntExt
			FROM APENT-MIB;

--CNTEXT MIB

    apCntExtMib MODULE-IDENTITY
	   LAST-UPDATED "9710092000Z" -- Thu October 9 20:00:00 EST 1997
	   ORGANIZATION "ArrowPoint Communications Inc."
	   CONTACT-INFO
	   "                      
	   Postal:               ArrowPoint Communications Inc.
				                 50 Nagog Park
				                 Acton, Massachusetts 01720
	   Tel:                   +1 978-206-3000  option 1
	   E-Mail:                support@arrowpoint.com"
       DESCRIPTION
	  "The MIB module used to describe the ArrowPoint Communications
	  content rule table"
      ::= { cntExt 1}

apCntRuleOrder OBJECT-TYPE
	SYNTAX		INTEGER {
							hierarchicalFirst(0),
							cacheRuleFirst(1)
						}
	MAX-ACCESS  read-write
	STATUS      current
	DESCRIPTION
			"Affects which ruleset is consulted first when categorizing flows"
	DEFVAL {cacheRuleFirst}
	::= { cntExt 2 }

apCntTable OBJECT-TYPE
	SYNTAX          SEQUENCE OF APCntEntry
	MAX-ACCESS      not-accessible
	STATUS          current
	DESCRIPTION
		"A list of content rule entries."
	::= { cntExt 4 }

apCntEntry OBJECT-TYPE
	SYNTAX          APCntEntry
	MAX-ACCESS      not-accessible
	STATUS          current
	DESCRIPTION
		"A group of information to uniquely identify a content providing 
		service."
	INDEX   { apCntOwner, apCntName }
	--DEFAULT apjam-group apCntInst, apCntName
	--DEFAULT apjam-popup-def apCntInst, Properties, local, Advanced
	--DEFAULT apjam-popup-def apCntInst, Statistics, chart, ContentChartGroup
	--DEFAULT apjam-popup-def apCntInst, Delete, special, apCntStatus
	--DEFAULT apjam-popup-def apCntInst, Reset, special, apCntZeroButton, 1
	--DEFAULT apjam-wizard	Content Rule Wizard, 1, images/arrowlogo.gif, "Content Rules allow acces to the specific content of a website."
	--DEFAULT apjam-wizard	Content Rule Wizard, 2, images/arrowlogo.gif, ""
	--DEFAULT apjam-wizard	Content Rule Wizard, 3, images/arrowlogo.gif, ""
	--DEFAULT apjam-chart-group ContentChartGroup, com.arrowpoint.auto.charts.cntHitsChart, apCntInst
	--DEFAULT apjam-chart-group ContentChartGroup, com.arrowpoint.auto.charts.cntSvcHitsChart, apCntInst
	::= { apCntTable 1 }

APCntEntry ::= SEQUENCE {
		apCntOwner                   DisplayString,
		apCntName                    DisplayString,
		apCntIndex                   Integer32,
		apCntIPAddress               IpAddress,
		apCntIPProtocol              INTEGER,
		apCntPort                    Integer32,
		apCntUrl                     DisplayString,
		apCntSticky                  INTEGER,
		apCntBalance                 INTEGER,
		apCntQOSTag                  Integer32,
		apCntEnable                  INTEGER,
		apCntRedirect                DisplayString,
		apCntDrop                    DisplayString,
		apCntSize                    Integer32,
		apCntPersistence             INTEGER,
		apCntAuthor                  DisplayString,
		apCntSpider                  INTEGER,
		apCntHits                    Counter32,
		apCntRedirects               Counter32,
		apCntDrops                   Counter32,
		apCntRejNoServices           Counter32,
		apCntRejServOverload         Counter32,
		apCntSpoofs                  Counter32,
		apCntNats                    Counter32,
		apCntByteCount               Counter32,
		apCntFrameCount              Counter32,
		apCntZeroButton              Integer32,
		apCntHotListEnabled          INTEGER,
		apCntHotListSize             Integer32,
		apCntHotListThreshold        Integer32,
		apCntHotListType             INTEGER,
		apCntHotListInterval         Integer32,
		apCntFlowTrack               INTEGER,
		apCntWeightMask              DisplayString,
 	    apCntStickyMask              IpAddress,
 	    apCntCookieStartPos          INTEGER,
 	    apCntHeuristicCookieFence    INTEGER,
		apCntEqlName                 DisplayString,
		apCntCacheFalloverType       INTEGER,
		apCntLocalLoadThreshold      INTEGER,
		apCntStatus                  RowStatus,
		apCntRedirectLoadThreshold   INTEGER,
		apCntContentType			 INTEGER,
 	    apCntStickyInactivity          Integer32,
		apCntDNSBalance              INTEGER,
        apCntStickyGroup             Integer32,
		apCntAppTypeBypasses         Counter32,
		apCntNoSvcBypasses           Counter32,
		apCntSvcLoadBypasses         Counter32,
		apCntConnCtBypasses          Counter32,
		apCntUrqlTblName             DisplayString,
        apCntStickyStrPre            DisplayString,
        apCntStickyStrEos            DisplayString,
        apCntStickyStrSkipLen        Integer32,
        apCntStickyStrProcLen        Integer32,
        apCntStickyStrAction         INTEGER,
        apCntStickyStrAsciiConv      INTEGER,
		apCntPrimarySorryServer      DisplayString,
		apCntSecondSorryServer       DisplayString,
		apCntPrimarySorryHits        Counter32,
		apCntSecondSorryHits         Counter32,
        apCntStickySrvrDownFailover  INTEGER,
        apCntStickyStrType           INTEGER,
        apCntParamBypass             INTEGER,	
        apCntAvgLocalLoad            Integer32,
        apCntAvgRemoteLoad           Integer32,
		apCntDqlName                 DisplayString,
		apCntIPAddressRange			 INTEGER,
		apCntTagListName             DisplayString,
		apCntStickyNoCookieAction        INTEGER,
		apCntStickyNoCookieString	 DisplayString,
		apCntStickyCookiePath		 DisplayString,
		apCntStickyCookieExp		 DisplayString,
		apCntStickyCacheExp		 INTEGER,		
		apCntTagWeight                   INTEGER		
-- Port range interface is not exposed. Supported internally.
--		apCntPortRange               INTEGER
}

apCntOwner OBJECT-TYPE
	SYNTAX          DisplayString (SIZE(1..31))
	MAX-ACCESS      read-create
	STATUS          current
	DESCRIPTION     
		"The name of the contents administrative owner."
	--DEFAULT ap-display-name	Owner Name
	--DEFAULT apjam-popup-ref apCntInst, Properties
	--DEFAULT ap-create-requires Yes
	--DEFAULT apjam-noedit-dlg	True
	--DEFAULT apjam-wizard-field 1, choice, apOwnName( ), nodepend
	::= {apCntEntry 1}

apCntName OBJECT-TYPE
	SYNTAX          DisplayString (SIZE(1..31))
	MAX-ACCESS      read-create
	STATUS          current
	DESCRIPTION     
			"The name of the content providing service."
	--DEFAULT ap-display-name	Content Name
	--DEFAULT apjam-popup-ref apCntInst, Properties
	--DEFAULT ap-create-requires Yes
	--DEFAULT apjam-noedit-dlg	True
	--DEFAULT apjam-wizard-field	1, normal
	::= {apCntEntry 2}

apCntIndex OBJECT-TYPE
	SYNTAX          Integer32
	MAX-ACCESS      read-only
	STATUS  		current
	DESCRIPTION     
		"The unique service index assigned to the name by the SCM."
	::= {apCntEntry 3}

apCntIPAddress OBJECT-TYPE
	SYNTAX          IpAddress
	MAX-ACCESS      read-create
	STATUS  		current
	DESCRIPTION     
		"The IP Address the of the content providing service."
	--DEFAULT ap-display-name	IP Address
	--DEFAULT apjam-popup-ref apCntInst, Properties
	--DEFAULT apjam-wizard-field	1, normal
	::= {apCntEntry 4}

apCntIPProtocol OBJECT-TYPE
	SYNTAX          INTEGER {
							any(0),
							tcp (6),
							udp (17)
							}
	MAX-ACCESS      read-create
	STATUS  		current
	DESCRIPTION     
		"The IP Protocol the of the content providing service."
	DEFVAL { any }
	--DEFAULT ap-display-name	Protocol
	--DEFAULT apjam-popup-ref apCntInst, Properties
	--DEFAULT apjam-wizard-field	1, normal
	::= {apCntEntry 5}

apCntPort OBJECT-TYPE
	SYNTAX          Integer32 (0..65535)
	MAX-ACCESS      read-create
	STATUS  		current
	DESCRIPTION     
		"The UDP or TCP port of the content providing service."
    DEFVAL { 0 }
	--DEFAULT ap-display-name	Port
	--DEFAULT apjam-popup-ref apCntInst, Properties
	--DEFAULT apjam-wizard-field	1, normal
	::= {apCntEntry 6}

apCntUrl OBJECT-TYPE
	SYNTAX          DisplayString (SIZE(0..255))
	MAX-ACCESS      read-create
	STATUS          current
	DESCRIPTION     
			"The name of the content providing service."
	--DEFAULT ap-display-name	URL
	--DEFAULT apjam-popup-ref apCntInst, Properties
	--DEFAULT apjam-wizard-field	2, normal
	::= {apCntEntry 7}

apCntSticky OBJECT-TYPE
	SYNTAX          INTEGER {
							none(1),
							ssl(2),
                            cookieurl(3),
                            url(4),
							cookies(5),
                            sticky-srcip-dstport(6),
                            sticky-srcip(7),
							arrowpoint-cookie(8)
							}
	MAX-ACCESS      read-create
	STATUS  		current
	DESCRIPTION     
		"The sticky attribute controls whether source addresses stick to a 
		 server once they go to it initially based on load balancing."
	DEFVAL { none }
	--DEFAULT ap-display-name	Sticky
	--DEFAULT apjam-popup-ref apCntInst, Properties
	--DEFAULT apjam-wizard-field	3, normal
	::= {apCntEntry 8}

apCntBalance OBJECT-TYPE
	SYNTAX          INTEGER {
							roundrobin(1),
							aca(2),
							destip(3),
							srcip(4),
							domain(5),
							url(6),
							leastconn(7),
							weightedrr(8),
							domainhash(9),
							urlhash(10)
							}
	MAX-ACCESS      read-create
	STATUS  		current
	DESCRIPTION     
		"The load distribution algorithm to use for this content."
	DEFVAL { roundrobin }
	--DEFAULT ap-display-name	Balance
	--DEFAULT apjam-popup-ref apCntInst, Properties
	--DEFAULT apjam-wizard-field	3, normal
	::= {apCntEntry 9}

apCntQOSTag OBJECT-TYPE
	SYNTAX          Integer32 (0..7)
	MAX-ACCESS      read-create
	STATUS  		current
	DESCRIPTION     
		"The QOS tag to associate with this content definition."
	DEFVAL { 7 }
	--DEFAULT ap-display-name	QOS Tag
	::= {apCntEntry 10}

apCntEnable  OBJECT-TYPE
	SYNTAX  INTEGER {
					disable(0),
					enable(1)
 					}
	MAX-ACCESS      read-create
	STATUS 			current
	DESCRIPTION     
		"The state of the service, either enable or disabled"
	DEFVAL { disable }
	--DEFAULT ap-display-name	Status
	--DEFAULT apjam-popup-ref apCntInst, Properties
	--DEFAULT apjam-wizard-field	1, normal
	::= {apCntEntry  11}

apCntRedirect OBJECT-TYPE
	SYNTAX          DisplayString (SIZE(0..64))
	MAX-ACCESS      read-create
	STATUS          current
	DESCRIPTION     
			"Where to 302 redirect any requests for this content"
	--DEFAULT ap-display-name	Redirect
	--DEFAULT apjam-popup-ref apCntInst, Properties
	--DEFAULT apjam-wizard-field	2, normal
	::= {apCntEntry 12}

apCntDrop OBJECT-TYPE
	SYNTAX          DisplayString (SIZE(0..64))
	MAX-ACCESS      read-create
	STATUS          current
	DESCRIPTION     
			"Specify that requests for this content receive a 404 message and the txt to include"
	--DEFAULT ap-display-name	Drop
	--DEFAULT apjam-popup-ref apCntInst, Properties
	--DEFAULT apjam-wizard-field	2, normal
	::= {apCntEntry 13}

apCntSize OBJECT-TYPE
	SYNTAX          Integer32 (0..65535)
	MAX-ACCESS      read-create
	STATUS  		obsolete
	DESCRIPTION     
		"This object is obsolete."
	DEFVAL { 4000 }
	--DEFAULT ap-display-name	Size
	--DEFAULT apjam-popup-ref apCntInst, Properties, Advanced
	--DEFAULT apjam-wizard-field	2, normal
	::= {apCntEntry 14}

apCntPersistence  OBJECT-TYPE
	SYNTAX  INTEGER {
					disable(0),
					enable(1)
 					}
	MAX-ACCESS      read-create
	STATUS 			current
	DESCRIPTION     
		"Controls whether each GET is inspected individuallly or else GETs 
		 may be pipelined on a single persistent TCP connection"
	DEFVAL { disable }
	--DEFAULT ap-display-name	Persistence
	--DEFAULT apjam-popup-ref apCntInst, Properties
	--DEFAULT apjam-wizard-field	3, normal
	::= {apCntEntry  15}

apCntAuthor OBJECT-TYPE
	SYNTAX          DisplayString (SIZE(1..16))
	MAX-ACCESS      read-create
	STATUS          current
	DESCRIPTION     
			"The name of the author of this content rule."
	--DEFAULT ap-display-name	Author
	--DEFAULT apjam-popup-ref apCntInst, Properties
	--DEFAULT apjam-wizard-field	2, normal
	::= {apCntEntry 16}

apCntSpider  OBJECT-TYPE
	SYNTAX  INTEGER {
					disable(0),
					enable(1)
 					}
	MAX-ACCESS      read-create
	STATUS 			current
	DESCRIPTION     
		"Controls whether the content will be spidered at rule activation time."
	DEFVAL { disable }
	--DEFAULT ap-display-name	Spider
	--DEFAULT apjam-popup-ref apCntInst, Properties, Advanced
	--DEFAULT apjam-wizard-field	2, normal
	::= {apCntEntry  17}

apCntHits OBJECT-TYPE
	SYNTAX          Counter32
	MAX-ACCESS      read-only
	STATUS  		current
	DESCRIPTION     
		"Number of times user request was detected which invoked this content rule."
	--DEFAULT ap-display-name	Hits
	--DEFAULT apjam-popup-ref apCntInst, Statistics
	--DEFAULT apjam-chart-def cntHitsChart, pie, apCntInst, "Hit Information for Content Rule"
	--DEFAULT apjam-chart-item cntHitsChart, get, green
	::= {apCntEntry 18}

apCntRedirects OBJECT-TYPE
	SYNTAX          Counter32
	MAX-ACCESS      read-only
	STATUS  		current
	DESCRIPTION     
		"Number of times this content rule caused a redirect request."
	--DEFAULT ap-display-name	Redirects
	--DEFAULT apjam-popup-ref apCntInst, Statistics
	--DEFAULT apjam-chart-item cntHitsChart, get, blue
	::= {apCntEntry 19}

apCntDrops OBJECT-TYPE
	SYNTAX          Counter32
	MAX-ACCESS      read-only
	STATUS  		current
	DESCRIPTION     
		"Number of times this content rule was unable to establish a connection."
	--DEFAULT ap-display-name	Drops
	--DEFAULT apjam-popup-ref apCntInst, Statistics
	--DEFAULT apjam-chart-item cntHitsChart, get, orange
	::= {apCntEntry 20}

apCntRejNoServices OBJECT-TYPE
	SYNTAX          Counter32
	MAX-ACCESS      read-only
	STATUS  		current
	DESCRIPTION     
		"Number of times this content rule rejected a connection for want of a service."
	--DEFAULT ap-display-name	Rejects No Services
	--DEFAULT apjam-popup-ref apCntInst, Statistics
	--DEFAULT apjam-chart-item cntHitsChart, get, red
	::= {apCntEntry 21}

apCntRejServOverload OBJECT-TYPE
	SYNTAX          Counter32
	MAX-ACCESS      read-only
	STATUS  		current
	DESCRIPTION     
		"Number of times this content rule rejected a connection because of overload on the designated service(s)."
	--DEFAULT ap-display-name	Reject Services Overload
	--DEFAULT apjam-popup-ref apCntInst, Statistics
	--DEFAULT apjam-chart-item cntHitsChart, get, yellow
	::= {apCntEntry 22}

apCntSpoofs OBJECT-TYPE
	SYNTAX          Counter32
	MAX-ACCESS      read-only
	STATUS  		current
	DESCRIPTION     
		"Number of times a connection was created using this content rule."
	--DEFAULT ap-display-name	Spoof Flows
	--DEFAULT apjam-popup-ref apCntInst, Statistics
	::= {apCntEntry 23}

apCntNats OBJECT-TYPE
	SYNTAX          Counter32
	MAX-ACCESS      read-only
	STATUS  		current
	DESCRIPTION     
		"Number of times network address translation was performed using this content rule."
	--DEFAULT ap-display-name	Nat Flows
	--DEFAULT apjam-popup-ref apCntInst, Statistics
	::= {apCntEntry 24}

apCntByteCount OBJECT-TYPE
	SYNTAX          Counter32
	MAX-ACCESS      read-only
	STATUS  		current
	DESCRIPTION     
		"Total number of bytes passed using this content rule."
	--DEFAULT ap-display-name	Bytes
	--DEFAULT apjam-popup-ref apCntInst, Statistics
	::= {apCntEntry 25}

apCntFrameCount OBJECT-TYPE
	SYNTAX          Counter32
	MAX-ACCESS      read-only
	STATUS  		current
	DESCRIPTION     
		"Total number of frames passed using this content rule."
	--DEFAULT ap-display-name	Frames
	--DEFAULT apjam-popup-ref apCntInst, Statistics
	::= {apCntEntry 26}

apCntZeroButton OBJECT-TYPE
	SYNTAX          Integer32
	MAX-ACCESS      read-create
	STATUS  		current
	DESCRIPTION     
		"Number of time counters for this content rule have been zeroed."
	DEFVAL { 0 }
	::= {apCntEntry 27}

apCntHotListEnabled  OBJECT-TYPE
	SYNTAX  INTEGER {
					disable(0),
					enable(1)
 					}
	MAX-ACCESS      read-create
	STATUS 			current
	DESCRIPTION     
		"Controls whether a hotlist will be maintained for this content rule."
	DEFVAL { disable }
	--DEFAULT ap-display-name	Hot List
	--DEFAULT apjam-popup-ref apCntInst, Properties
	--DEFAULT apjam-wizard-field	2, normal
	::= {apCntEntry  28}

apCntHotListSize OBJECT-TYPE
	SYNTAX          Integer32 (1..100)
	MAX-ACCESS      read-create
	STATUS  		current
	DESCRIPTION     
		"Total number of hotlist entries which will be maintainted for this rule."
	DEFVAL { 10 }
	--DEFAULT ap-display-name	Hot List Size
	--DEFAULT apjam-popup-ref apCntInst, Properties, Advanced
	::= {apCntEntry 29}

apCntHotListThreshold OBJECT-TYPE
	SYNTAX          Integer32 (0..65535)
	MAX-ACCESS      read-create
	STATUS  		current
	DESCRIPTION     
		"The threshold under which an item is not considered hot."
	DEFVAL { 0 }
	--DEFAULT ap-display-name	Hot List Threshold
	--DEFAULT apjam-popup-ref apCntInst, Properties, Advanced
	::= {apCntEntry 30}

apCntHotListType  OBJECT-TYPE
	SYNTAX  INTEGER {
					hitCount(0)
 					}
	MAX-ACCESS      read-create
	STATUS 			current
	DESCRIPTION     
		"Configures how a determination of hotness will be done."
	DEFVAL { hitCount }
	--DEFAULT ap-display-name	Hot List Type
	--DEFAULT apjam-popup-ref apCntInst, Properties, Advanced
	::= {apCntEntry  31}

apCntHotListInterval OBJECT-TYPE
	SYNTAX          Integer32 (1..60)
	MAX-ACCESS      read-create
	STATUS  		current
	DESCRIPTION     
		"The interval in units of minutes used to refreshing the hot list."
	DEFVAL { 1 }
	--DEFAULT ap-display-name	Hot List Interval
	--DEFAULT apjam-popup-ref apCntInst, Properties, Advanced
	::= {apCntEntry 32}

apCntFlowTrack  OBJECT-TYPE
	SYNTAX  INTEGER {
					disable(0),
					enable(1)
 					}
	MAX-ACCESS      read-create
	STATUS 			current
	DESCRIPTION     
		"Controls whether arrowflow reporting will be done for this content 
         rule."
	DEFVAL { disable }
	--DEFAULT ap-display-name	Flow Track
	--DEFAULT apjam-popup-ref apCntInst, Properties
	::= {apCntEntry  33}

apCntWeightMask OBJECT-TYPE
	SYNTAX          DisplayString (SIZE(1..8))
	MAX-ACCESS      read-create
	STATUS 			current
	DESCRIPTION     
		"This object specifies a bitmask used to determine the type of 
		metric to be used for load balancing."
	--DEFAULT ap-display-name	Weight Mask
	--DEFAULT apjam-popup-ref apCntInst, Properties, Advanced
	::= {apCntEntry  34}

apCntStickyMask OBJECT-TYPE
	SYNTAX          IpAddress
	MAX-ACCESS      read-create
	STATUS  		current
	DESCRIPTION     
		"This object specifies the sticky mask used to determine the
		portion of the IP Address which denotes stickness between the
		server and client."
	--DEFAULT ap-display-name	Sticky Mask
	--DEFAULT apjam-popup-ref apCntInst, Properties, Advanced
	::= {apCntEntry 35}

apCntCookieStartPos OBJECT-TYPE
	SYNTAX          INTEGER (1..600)
	MAX-ACCESS      read-create
	STATUS 			current
	DESCRIPTION     
		"This object specifies the start of a cookie."
	DEFVAL { 1 }
	--DEFAULT ap-display-name	Cookie Start Position
	--DEFAULT apjam-popup-ref apCntInst, Properties, Advanced
	::= {apCntEntry 36}

apCntHeuristicCookieFence OBJECT-TYPE
	SYNTAX          INTEGER (1..1000)
	MAX-ACCESS      read-create
	STATUS 			current
	DESCRIPTION     
		"This object specifies the end of a Heuristic Cookie Fence."
	DEFVAL { 100 }
	--DEFAULT ap-display-name	Cookie End Position
	--DEFAULT apjam-popup-ref apCntInst, Properties, Advanced
	::= {apCntEntry 37}

apCntEqlName OBJECT-TYPE
	SYNTAX          DisplayString (SIZE(0..32))
	MAX-ACCESS      read-create
	STATUS          current
	DESCRIPTION     
			"The name of the EQL associated with this content rule"
	--DEFAULT ap-display-name	EQL Name
	--DEFAULT apjam-popup-ref apCntInst, Properties, Advanced
	::= {apCntEntry 38}

apCntCacheFalloverType OBJECT-TYPE
	SYNTAX          INTEGER {
							linear(1)                                      ,
							next(2)                                          ,
							bypass(3)                                     
							}
	MAX-ACCESS      read-create
	STATUS          current
	DESCRIPTION     
			"The type of fallover to use with division balancing"
	DEFVAL { linear }
	--DEFAULT ap-display-name	Cache Fallover Strategy
	--DEFAULT apjam-popup-ref apCntInst, Properties, Advanced
	::= {apCntEntry 39}

apCntLocalLoadThreshold OBJECT-TYPE
	SYNTAX          INTEGER (2..254)
	MAX-ACCESS      read-create
	STATUS 			current
	DESCRIPTION     
		"Redirect services are preferred when all local services exceed this thrreshold."
	DEFVAL { 254 }
	--DEFAULT ap-display-name	Local Load Threshold
	--DEFAULT apjam-popup-ref apCntInst, Properties, Advanced
	::= {apCntEntry 40}

apCntStatus OBJECT-TYPE
	SYNTAX          RowStatus
	MAX-ACCESS      read-create
	STATUS          current
	DESCRIPTION      
		"Status entry for this row "
	::= {apCntEntry 41}

apCntRedirectLoadThreshold OBJECT-TYPE
	SYNTAX          INTEGER (0..255)
	MAX-ACCESS      read-create
	STATUS 			current
	DESCRIPTION     
		"Redirect services are eligible when their load is below this thrreshold."
	DEFVAL { 255 }
	--DEFAULT ap-display-name	Redirect Load Threshold
	--DEFAULT apjam-popup-ref apCntInst, Properties, Advanced
	::= {apCntEntry 42}

apCntContentType OBJECT-TYPE
	SYNTAX          INTEGER {
							http(1),
							ftp-control(2),
							realaudio-control(3),
							ssl(4),
							bypass(5),
							ftp-publish(6)
							}
	MAX-ACCESS      read-create
	STATUS  		current
	DESCRIPTION     
		"The type of flow associated with this rule"
	DEFVAL { http }
	--DEFAULT ap-display-name	Content Type
	::= {apCntEntry 43}

apCntStickyInactivity OBJECT-TYPE
 	SYNTAX          Integer32 (0..65535)
 	MAX-ACCESS      read-create
 	STATUS 			current
 	DESCRIPTION     
 		"The maximun inactivity on a sticky connection (in minutes)"
 	DEFVAL { 0 }
 	::= {apCntEntry 44}

apCntDNSBalance OBJECT-TYPE
	SYNTAX          INTEGER {
							preferlocal(1),
							roundrobin(2),
							useownerdnsbalance(3),
							leastloaded(4)
							}
	MAX-ACCESS      read-create
	STATUS  		current
	DESCRIPTION     
		"The DNS distribution algorithm to use for this content rule."
	DEFVAL { useownerdnsbalance }
	--DEFAULT ap-display-name	DNSBalance
	--DEFAULT apjam-popup-ref apCntInst, Properties
	--DEFAULT apjam-wizard-field	3, normal
	::= {apCntEntry 45}

apCntStickyGroup OBJECT-TYPE
        SYNTAX          Integer32 (0..65535)
        MAX-ACCESS      read-create
        STATUS          current
        DESCRIPTION
                "The sticky group number of a rule, 0 means not being used"
        DEFVAL { 0 }
        ::= {apCntEntry 46}

apCntAppTypeBypasses OBJECT-TYPE
	SYNTAX          Counter32
	MAX-ACCESS      read-only
	STATUS  		current
	DESCRIPTION     
		"Total number of frames bypassed directly by matching this content rule."
	--DEFAULT ap-display-name	AppTypeBypasses
	--DEFAULT apjam-popup-ref apCntInst, Statistics
	--DEFAULT apjam-chart-def cntHitsChart, pie, apCntInst, "App Type Bypass Information for Content Rule"
	--DEFAULT apjam-chart-item cntHitsChart, get, green
	::= {apCntEntry 47}

apCntNoSvcBypasses OBJECT-TYPE
	SYNTAX          Counter32
	MAX-ACCESS      read-only
	STATUS  		current
	DESCRIPTION     
		"Total number of frames bypassed due to no services available on this content rule."
	--DEFAULT ap-display-name	NoSvcBypasses
	--DEFAULT apjam-popup-ref apCntInst, Statistics
	--DEFAULT apjam-chart-def cntHitsChart, pie, apCntInst, "No Service Bypass Information for Content Rule"
	--DEFAULT apjam-chart-item cntHitsChart, get, green
	::= {apCntEntry 48}

apCntSvcLoadBypasses OBJECT-TYPE
	SYNTAX          Counter32
	MAX-ACCESS      read-only
	STATUS  		current
	DESCRIPTION     
		"Total number of frames bypassed due to overloaded services on this content rule."
	--DEFAULT ap-display-name	SvcLoadBypasses
	--DEFAULT apjam-popup-ref apCntInst, Statistics
	--DEFAULT apjam-chart-def cntHitsChart, pie, apCntInst, "Service Load Bypass Information for Content Rule"
	--DEFAULT apjam-chart-item cntHitsChart, get, green
	::= {apCntEntry 49}

apCntConnCtBypasses OBJECT-TYPE
	SYNTAX          Counter32
	MAX-ACCESS      read-only
	STATUS  		current
	DESCRIPTION     
		"Total number of frames bypassed due to connection count on this content rule."
	--DEFAULT ap-display-name	ConnCtBypasses
	--DEFAULT apjam-popup-ref apCntInst, Statistics
	--DEFAULT apjam-chart-def cntHitsChart, pie, apCntInst, "Connection Count Bypass Information for Content Rule"
	--DEFAULT apjam-chart-item cntHitsChart, get, green
	::= {apCntEntry 50}

apCntUrqlTblName OBJECT-TYPE
	SYNTAX          DisplayString (SIZE(0..31))
	MAX-ACCESS      read-create
	STATUS          current
	DESCRIPTION     
			"The name of the URQL table associated with this content rule"
	--DEFAULT ap-display-name	URQL Table Name
	--DEFAULT apjam-popup-ref apCntInst, Properties, Advanced
	::= {apCntEntry 51}

apCntStickyStrPre OBJECT-TYPE
        SYNTAX          DisplayString (SIZE(0..32))
        MAX-ACCESS      read-create
        STATUS          current
        DESCRIPTION
                        "The string prefix for sticky string operation"
        ::= {apCntEntry 52}

apCntStickyStrEos OBJECT-TYPE
        SYNTAX          DisplayString (SIZE(0..5))
        MAX-ACCESS      read-create
        STATUS          current
        DESCRIPTION
                        "The End-Of-String characters"
        ::= {apCntEntry 53}

apCntStickyStrSkipLen OBJECT-TYPE
        SYNTAX          Integer32 (0..64)
        MAX-ACCESS      read-create
        STATUS          current
        DESCRIPTION
                "The number of bytes to be skipped before sticky operation"
        DEFVAL { 0 }
        ::= {apCntEntry 54}

apCntStickyStrProcLen OBJECT-TYPE
        SYNTAX          Integer32 (0..64)
        MAX-ACCESS      read-create
        STATUS          current
        DESCRIPTION
                "The number of bytes to be processed by the string action"
        DEFVAL { 0 }
        ::= {apCntEntry 55}

apCntStickyStrAction OBJECT-TYPE
        SYNTAX          INTEGER {
                                hash-a(1),
                                hash-xor(2),
                                hash-crc32(3),
                                match-service-cookie(4)
                                }
        MAX-ACCESS      read-create
        STATUS          current
        DESCRIPTION
                "The sticky operation to be applied on the sticky cookie/string"
        DEFVAL { match-service-cookie }
        ::= {apCntEntry 56}

apCntStickyStrAsciiConv OBJECT-TYPE
        SYNTAX          INTEGER {
                                enable(1),
                                disable(2)
                                }
        MAX-ACCESS      read-create
        STATUS          current
        DESCRIPTION
                "To convert the escaped ASCII code to its char in sticky string"
        DEFVAL { enable }
        ::= {apCntEntry 57}

apCntPrimarySorryServer OBJECT-TYPE
	SYNTAX          DisplayString (SIZE(0..31))
	MAX-ACCESS      read-create
	STATUS  		current
	DESCRIPTION     
		"The last chance server which will be chosen if all other servers fail"
	--DEFAULT ap-display-name	PrimarySorryServer
	::= {apCntEntry 58}

apCntSecondSorryServer OBJECT-TYPE
	SYNTAX          DisplayString (SIZE(0..31))
	MAX-ACCESS      read-create
	STATUS  		current
	DESCRIPTION     
		"The backup for the primary sorry server"
	--DEFAULT ap-display-name	SecondSorryServer
	::= {apCntEntry 59}

apCntPrimarySorryHits OBJECT-TYPE
	SYNTAX          Counter32
	MAX-ACCESS      read-only
	STATUS  		current
	DESCRIPTION     
		"Total number of hits to the primary sorry server"
	--DEFAULT ap-display-name   PrimarySorryHits
	::= {apCntEntry 60}

apCntSecondSorryHits OBJECT-TYPE
	SYNTAX          Counter32
	MAX-ACCESS      read-only
	STATUS  		current
	DESCRIPTION     
		"Total number of hits to the secondary sorry server"
	--DEFAULT ap-display-name   SecondSorryHits
	::= {apCntEntry 61}

apCntStickySrvrDownFailover OBJECT-TYPE
        SYNTAX          INTEGER {
                                reject(1),
                                redirect(2),
                                balance(3),
                                sticky-srcip(4),
                                sticky-srcip-dstport(5)
                                }
        MAX-ACCESS      read-create
        STATUS          current
        DESCRIPTION
                "The failover mechanism used when sticky server is not active"
        DEFVAL { balance }
        ::= {apCntEntry 62}

apCntStickyStrType OBJECT-TYPE
        SYNTAX          INTEGER {
                                cookieurl(1),
                                url(2),
                                cookies(3)
                                }
        MAX-ACCESS      read-create
        STATUS          current
        DESCRIPTION
                "The type of string that strig criteria applies to"
        DEFVAL { cookieurl }
        ::= {apCntEntry 63}

apCntParamBypass OBJECT-TYPE
        SYNTAX          INTEGER {
                                enable(1),
                                disable(2)
                                }
        MAX-ACCESS      read-create
        STATUS          current
        DESCRIPTION
                "Specifies that content requests which contain the special terminators '?' 
				 or '#' indicating arguments in the request are to bypass transparent 
				 caches and are to be sent directly to the origin server."
        DEFVAL { disable }
        ::= {apCntEntry 64}


apCntAvgLocalLoad OBJECT-TYPE
	SYNTAX          Integer32 (0..255)
	MAX-ACCESS      read-only
	STATUS  		current
	DESCRIPTION     
		"The currently sensed average load for all local services under this rule"
	DEFVAL { 0 }
        ::= {apCntEntry 65}


apCntAvgRemoteLoad OBJECT-TYPE
	SYNTAX          Integer32 (0..255)
	MAX-ACCESS      read-only
	STATUS  		current
	DESCRIPTION     
		"The currently sensed average load for all remote services under this rule"
	DEFVAL { 0 }
        ::= {apCntEntry 66}

apCntDqlName OBJECT-TYPE
	SYNTAX          DisplayString (SIZE(0..31))
	MAX-ACCESS      read-create
	STATUS          current
	DESCRIPTION     
			"The name of the DQL table associated with this content rule"
	--DEFAULT ap-display-name	DQL Name
	--DEFAULT apjam-popup-ref apCntInst, Properties, Advanced
	::= {apCntEntry 67}

apCntIPAddressRange OBJECT-TYPE
	SYNTAX          INTEGER (1..65535)
	MAX-ACCESS      read-create
	STATUS  		current
	DESCRIPTION     
		"The range of IP Addresses of the content providing service."
    DEFVAL { 1 }
	--DEFAULT ap-display-name	IP Address Range
	--DEFAULT apjam-popup-ref apCntInst, Properties
	--DEFAULT apjam-wizard-field	1, normal
	::= {apCntEntry 68}

apCntTagListName OBJECT-TYPE
	SYNTAX          DisplayString (SIZE(0..31))
	MAX-ACCESS      read-create
	STATUS          current
	DESCRIPTION     
			"The name of the tag list to be used with this content rule"
	--DEFAULT ap-display-name	Tag List Name
	--DEFAULT apjam-popup-ref apCntInst, Properties, Advanced
	::= {apCntEntry 69}

apCntStickyNoCookieAction  OBJECT-TYPE
   	SYNTAX		    INTEGER {
	                    loadbalance(1),
	                    reject(2),
                            redirect(3),
                            service(4)
		 	    }
	MAX-ACCESS		read-create
	STATUS			current
	DESCRIPTION
		"The action to be taken when no cookie found with sticky cookie config."
	DEFVAL { loadbalance }
	::= {apCntEntry 70}

apCntStickyNoCookieString OBJECT-TYPE
	SYNTAX			 DisplayString(SIZE(0..64))
        MAX-ACCESS		 read-create
	STATUS			 current
	DESCRIPTION
		"The String used by sticky no cookie redirect action"
	::= {apCntEntry 71}

apCntStickyCookiePath OBJECT-TYPE
	SYNTAX			DisplayString(SIZE(0..99))
	MAX-ACCESS		read-create
	STATUS			current
	DESCRIPTION
		"The value to be used as the Cookie Path Attribute."
	::= {apCntEntry 72}

apCntStickyCookieExp OBJECT-TYPE
	SYNTAX			DisplayString(SIZE(11..11))
	MAX-ACCESS		read-create
	STATUS			current
	DESCRIPTION
		"The value to be used as the Cookie Experation Attribute. Format - dd:hh:mm:ss"
	::= {apCntEntry 73}

apCntStickyCacheExp OBJECT-TYPE
	SYNTAX			INTEGER(0..60)
	MAX-ACCESS		read-create
	STATUS			current
	DESCRIPTION
		"The value used to time out entries in the Cookie Cache."
    DEFVAL { 3 }
	::= {apCntEntry 74}

apCntTagWeight      OBJECT-TYPE
	SYNTAX			INTEGER(0..1024)
	MAX-ACCESS		read-create
	STATUS			current
	DESCRIPTION
		"The weight assigned to the rule using header-field-group."
	DEFVAL { 0 }
	::= {apCntEntry 75}

-- Port range interface is not exposed. Supported internally.
-- apCntPortRange OBJECT-TYPE
--	SYNTAX          INTEGER (0..65535)
--	MAX-ACCESS      read-create
--	STATUS  		current
--	DESCRIPTION     
--		"The range of UDP or TCP ports of the content providing service."
--	DEFVAL { 0 }
--	::= {apCntEntry xx}

apCntAclBypassCt OBJECT-TYPE
	SYNTAX          Counter32
	MAX-ACCESS      read-only
	STATUS          current
	DESCRIPTION
		"Total number of frames bypassed due to ACL restrictions."
	--DEFAULT ap-display-name	AclBypassCt
	--DEFAULT apjam-popup-ref apCntInst, Statistics
	--DEFAULT apjam-chart-def cntHitsChart, pie, apCntInst, "Global ACL Bypass Count"
	--DEFAULT apjam-chart-item cntHitsChart, get, green
	::= { cntExt 5 }

apCntNoRuleBypassCt OBJECT-TYPE
	SYNTAX          Counter32
	MAX-ACCESS      read-only
	STATUS          current
	DESCRIPTION
		"Total number of frames bypassed due to no rule matches."
	--DEFAULT ap-display-name	NoRuleBypassCt
	--DEFAULT apjam-popup-ref apCntInst, Statistics
	--DEFAULT apjam-chart-def cntHitsChart, pie, apCntInst, "Global No Rule Match Bypass Count"
	--DEFAULT apjam-chart-item cntHitsChart, get, green
	::= { cntExt 6 }

apCntCacheMissBypassCt OBJECT-TYPE
	SYNTAX          Counter32
	MAX-ACCESS      read-only
	STATUS          current
	DESCRIPTION
		"Total number of frames bypassed due to returning from a transparent cache."
	--DEFAULT ap-display-name	CacheMissBypassCt
	--DEFAULT apjam-popup-ref apCntInst, Statistics
	--DEFAULT apjam-chart-def cntHitsChart, pie, apCntInst, "Global Transparent Cache Miss Bypass Count"
	--DEFAULT apjam-chart-item cntHitsChart, get, green
	::= { cntExt 7 }

apCntGarbageBypassCt OBJECT-TYPE
	SYNTAX          Counter32
	MAX-ACCESS      read-only
	STATUS          current
	DESCRIPTION
		"Total number of frames bypassed due to unknown info found in the URL."
	--DEFAULT ap-display-name	GarbageBypassCt
	--DEFAULT apjam-popup-ref apCntInst, Statistics
	--DEFAULT apjam-chart-def cntHitsChart, pie, apCntInst, "Global Unknown Info Bypass Count"
	--DEFAULT apjam-chart-item cntHitsChart, get, green
	::= { cntExt 8 }

apCntUrlParamsBypassCt OBJECT-TYPE
	SYNTAX          Counter32
	MAX-ACCESS      read-only
	STATUS          current
	DESCRIPTION
		"Total number of frames bypassed due to paramters found in the URL."
	--DEFAULT ap-display-name	UrlParamsBypassCt
	--DEFAULT apjam-popup-ref apCntInst, Statistics
	--DEFAULT apjam-chart-def cntHitsChart, pie, apCntInst, "Global URL Parameters Bypass Count"
	--DEFAULT apjam-chart-item cntHitsChart, get, green
	::= { cntExt 9 }

apCntBypassConnectionPersistence OBJECT-TYPE
	SYNTAX		INTEGER {
							disable(0),
							enable(1)
						}
	MAX-ACCESS  read-write
	STATUS      current
	DESCRIPTION
			"Affects which ruleset is consulted first when categorizing flows"
	DEFVAL {enable}
	::= { cntExt 10 }

apCntPersistenceResetMethod OBJECT-TYPE
	SYNTAX		INTEGER {
							redirect(0),
							remap(1)
						}
	MAX-ACCESS  read-write
	STATUS      current
	DESCRIPTION
			"Affects which ruleset is consulted first when categorizing flows"
	DEFVAL {redirect}
	::= { cntExt 11 }

END
