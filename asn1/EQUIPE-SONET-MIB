EQUIPE-SONET-MIB DEFINITIONS ::= BEGIN

    --
    -- Equipe SONET MIB
    --

    IMPORTS
	TEXTUAL-CONVENTION FROM SNMPv2-TC
        enterprises    
            FROM RFC1155-SMI
        ifIndex 
            FROM IF-MIB
        Integer32, MODULE-IDENTITY, OBJECT-TYPE, Counter32
            FROM SNMPv2-SMI;

    equipe        OBJECT IDENTIFIER ::= { enterprises 5022 }

    eqSonetMib MODULE-IDENTITY
        LAST-UPDATED "0105060000Z"  -- May 6, 2001
        ORGANIZATION ""
        CONTACT-INFO
            "Jas Parmar
            Equipe Communications
            100 Nagog Park
            Acton MA 01720"
        DESCRIPTION
            "This is the Equipe SONET MIB module."
        ::= { equipe 3 }

    --
    --  Equipe Sonet Textual conventions
    --

    EqSonetApsCfgStatus ::= TEXTUAL-CONVENTION
        STATUS      current
        DESCRIPTION
                "Equipe sonet aps config status values."
        SYNTAX    INTEGER {
                none(1),  
                working(2),
                protecting(3),
                lockoutProtecting(4),
                forcedSwitchWorkingToProtecting(5),
                forcedSwitchProtectingToWorking(6),
                manualSwitchWorkingToProtecting(7),
                manualSwitchProtectingToWorking(8)
       }

    EqSonetApsCfgAction ::= TEXTUAL-CONVENTION
        STATUS      current
        DESCRIPTION
                "Equipe sonet aps config action values."
        SYNTAX    INTEGER {
                other(1),
                clear(2),
                lockoutProtecting(3),
                forcedSwitchWorkingToProtecting(4),
                forcedSwitchProtectingToWorking(5),
                manualSwitchWorkingToProtecting(6),
                manualSwitchProtectingToWorking(7)
       }

    --
    --  Sonet Port APS Config Table.
    --

    eqSonetApsCfgTable OBJECT-TYPE
        SYNTAX      SEQUENCE OF EqSonetApsCfgEntry
        MAX-ACCESS  not-accessible
        STATUS      current
        DESCRIPTION
           "This table contains aps config info for a sonet port."
        ::= { eqSonetMib 1 }
        
    eqSonetApsCfgEntry OBJECT-TYPE
        SYNTAX      EqSonetApsCfgEntry
        MAX-ACCESS  not-accessible
        STATUS      current
        DESCRIPTION
                "A sonet port aps config entry."
        INDEX    { ifIndex }
        ::= { eqSonetApsCfgTable 1 }

    EqSonetApsCfgEntry ::=
        SEQUENCE {
            eqSonetApsCfgStatus        
                    EqSonetApsCfgStatus,
            eqSonetApsCfgAction        
                    EqSonetApsCfgAction,
            eqSonetApsCfgLastAction        
                    EqSonetApsCfgAction,
            eqSonetApsCfgPortActive
                    INTEGER
        }

    eqSonetApsCfgStatus OBJECT-TYPE
        SYNTAX      EqSonetApsCfgStatus
        MAX-ACCESS  read-only
        STATUS      current
        DESCRIPTION
            "The current aps status for this sonet port."
        ::= { eqSonetApsCfgEntry 1 }

    eqSonetApsCfgAction OBJECT-TYPE
        SYNTAX      EqSonetApsCfgAction
        MAX-ACCESS  read-write
        STATUS      current
        DESCRIPTION
            "This object is used to perform an aps action on a sonet port.

             A read on this object always returns the value other(1).

             Setting this object to clear(2) causes the port to revert
             back to default aps configuration.

             Setting this object to lockoutProtecting(3) prevents any
             of the working channels from switching to the protecting
             line.

             Setting this object to forcedSwitchWorkingToProtecting(4) 
             switches the working port to the protecting port. 

             Setting this object to forcedSwitchProtectingToWorking(5) 
             switches the protecting port to the working port. 

             Setting this object to manualSwitchWorkingToProtecting(6) 
             switches the working port to the protecting port. 

             Setting this object to manualSwitchProtectingToWorking(7) 
             switches the protecting port to the working port."
        ::= { eqSonetApsCfgEntry 2 }

    eqSonetApsCfgLastAction OBJECT-TYPE
        SYNTAX      EqSonetApsCfgAction
        MAX-ACCESS  read-only
        STATUS      current
        DESCRIPTION
            "This object indicates the last aps action requested on this
             port." 
        ::= { eqSonetApsCfgEntry 3 }

    eqSonetApsCfgPortActive OBJECT-TYPE
        SYNTAX      INTEGER {
                false(1),
                true(2)
        }
        MAX-ACCESS  read-only
        STATUS      current
        DESCRIPTION
            "This object is used to determine if the sts paths configured
             on this port are currrently actually terminated on this port.  
             This is used to determine if the port is in active or standby 
             mode. A value of false(1) indicates that the sts paths are
             not terminated (standby). A value of true(2) indicates
             that the sts paths are terminated (active)."
        ::= { eqSonetApsCfgEntry 4 }

    --
    --  Sonet Path Table.
    --

    eqSonetPathTable OBJECT-TYPE
        SYNTAX      SEQUENCE OF EqSonetPathEntry
        MAX-ACCESS  not-accessible
        STATUS      current
        DESCRIPTION
           "This table contains config info for a sonet port."
        ::= { eqSonetMib 2 }
        
    eqSonetPathEntry OBJECT-TYPE
        SYNTAX      EqSonetPathEntry
        MAX-ACCESS  not-accessible
        STATUS      current
        DESCRIPTION
                "A sonet path config entry."
        INDEX    { ifIndex }
        ::= { eqSonetPathTable 1 }

    EqSonetPathEntry ::=
        SEQUENCE {
            eqSonetPathActualPort        
                    INTEGER
        }

    eqSonetPathActualPort OBJECT-TYPE
        SYNTAX      INTEGER (1..2147483647)
        MAX-ACCESS  read-only
        STATUS      current
        DESCRIPTION
            "The ifIndex of the sonet port over which this path is
             actually running. Note that this value could be different 
             from the sonet port that the sts path was originally
             configured."
        ::= { eqSonetPathEntry 1 }


    --
    --  Sonet Stats Table.
    --

    eqSonetStatsTable OBJECT-TYPE
        SYNTAX      SEQUENCE OF EqSonetStatsEntry
        MAX-ACCESS  not-accessible
        STATUS      current
        DESCRIPTION
           "This table contains stats for a sonet port."
        ::= { eqSonetMib 3 }
        
    eqSonetStatsEntry OBJECT-TYPE
        SYNTAX      EqSonetStatsEntry
        MAX-ACCESS  not-accessible
        STATUS      current
        DESCRIPTION
                "A sonet port stats entry."
        INDEX    { eqSonetStatsIfIndex }
        ::= { eqSonetStatsTable 1 }

    EqSonetStatsEntry ::=
        SEQUENCE {
            eqSonetStatsIfIndex    
                    INTEGER,
            eqSonetStatsLineFailures        
                    Counter32,
            eqSonetStatsLineApsCount 
                    Counter32,
            eqSonetStatsLineApsSwitchDuration        
                    Counter32,
            eqSonetStatsLineStsPtrAdjustments        
                    Counter32,
            eqSonetStatsPathFailures        
                    Counter32,
            eqSonetStatsTimeElapsed 
                     Integer32
        }

    eqSonetStatsIfIndex OBJECT-TYPE
        SYNTAX      INTEGER (1..2147483647)
        MAX-ACCESS  read-only
        STATUS      current
        DESCRIPTION
            "The ifIndex for the corresponding sonet port."
        ::= { eqSonetStatsEntry 1 }

    eqSonetStatsLineFailures OBJECT-TYPE
        SYNTAX      Counter32 
        MAX-ACCESS  read-only
        STATUS      current
        DESCRIPTION
            "The number of line failure events. A line failure is an
             AIS-L signal received from another NE, or received from 
             the same NE when internally generating an AIS-L signal 
             in the LTE."
        ::= { eqSonetStatsEntry 2 }

    eqSonetStatsLineApsCount OBJECT-TYPE
        SYNTAX      Counter32 
        MAX-ACCESS  read-only
        STATUS      current
        DESCRIPTION
            "The number of times the service has switched from the
             working to the protect line."
        ::= { eqSonetStatsEntry 3 }

    eqSonetStatsLineApsSwitchDuration OBJECT-TYPE
        SYNTAX      Counter32 
        MAX-ACCESS  read-only
        STATUS      current
        DESCRIPTION
            "The number of seconds the service has been carried on 
             the protection line."
        ::= { eqSonetStatsEntry 4 }

    eqSonetStatsLineStsPtrAdjustments OBJECT-TYPE
        SYNTAX      Counter32 
        MAX-ACCESS  read-only
        STATUS      current
        DESCRIPTION
            "The count of STS pointer adjustments created or absorbed
             by an NE due to differences in the frame rates of the 
             incoming and outgoing sonet signal."
        ::= { eqSonetStatsEntry 5 }

    eqSonetStatsPathFailures OBJECT-TYPE
        SYNTAX      Counter32 
        MAX-ACCESS  read-only
        STATUS      current
        DESCRIPTION
            "The number of path failure events. A path failure is an
             AIS-P signal received from another NE, or received from 
             the same NE when internally generating an AIS-P signal 
             in the PTE. A path with support for ERDI-P will increment
             this counter when an UNEQ-P failure is declared."
        ::= { eqSonetStatsEntry 6 }

    eqSonetStatsTimeElapsed OBJECT-TYPE
        SYNTAX      Integer32 (1..900)
        MAX-ACCESS  read-only
        STATUS      current
        DESCRIPTION
            "The number of seconds, including partial seconds,
             that have elapsed since the beginning of the current
             measurement period. If, for some reason, such as an
             adjustment in the system's time-of-day clock, the
             current interval exceeds the maximum value, the
             agent will return the maximum value."
        ::= { eqSonetStatsEntry 7 }
END
