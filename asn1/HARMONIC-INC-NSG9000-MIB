-- File: NSG9000.mib
-- Description: HARMONIC-INC-NSG9000-MIB contains the definition
--              of the MIB tree structure supported by the SNMP Agents
--              for Harmonic Inc Products
-- Created: Oct 23, 2007
-- 

HARMONIC-INC-NSG9000-MIB DEFINITIONS ::= BEGIN
    IMPORTS
        OBJECT-TYPE             FROM RFC-1212
        DisplayString           FROM RFC1213-MIB
        IpAddress,TimeTicks    	FROM RFC1155-SMI
	entPhysicalIndex	FROM ENTITY-MIB
	enterprises             FROM SNMPv2-SMI
	TRAP-TYPE            FROM RFC-1215;

----------------------------
--   harmonicInc   --
----------------------------
    harmonicInc OBJECT IDENTIFIER
        --DEFAULT test-function   test_%n
        --DEFAULT set-function    set_%n
        --DEFAULT get-function    get_%n
        --DEFAULT next-function   next_%p
        --DEFAULT cookie          (char *) 0
        ::= { enterprises 1563 }

-- Harmonic Lightwaves Object Identifier Definition
hOids      		OBJECT IDENTIFIER ::= { harmonicInc 1 }
hObjects   		OBJECT IDENTIFIER ::= { harmonicInc 2 }
hTrapFields   		OBJECT IDENTIFIER ::= { harmonicInc 3 }

hModuleOids		OBJECT IDENTIFIER ::= { hOids 1 }

hSystemOid		OBJECT IDENTIFIER ::= { hModuleOids 1 }
hPlatformOid		OBJECT IDENTIFIER ::= { hModuleOids 2 }
hGbePortOid		OBJECT IDENTIFIER ::= { hModuleOids 3 }
hSlotOid		OBJECT IDENTIFIER ::= { hModuleOids 4 }
hRfModuleOid		OBJECT IDENTIFIER ::= { hModuleOids 5 }
hRfPortOid		OBJECT IDENTIFIER ::= { hModuleOids 6 }
hQamChannelOid		OBJECT IDENTIFIER ::= { hModuleOids 7 }

hSystem        	OBJECT IDENTIFIER ::= { hObjects 1 }

-- System Group

--  hSysLastConfigSignature OBJECT-TYPE 
--    SYNTAX  INTEGER   unsigned 32-bit integer
--    ACCESS  read-write
--    STATUS  mandatory
--    DESCRIPTION
--        "This variable represents the last configuration signature
--        set by management application every time it issues set-request
--        on configuration variables.
--
--        The special value `0' may be set by the agent as a token of
--        either its initial state of operation or its internal data base
--        corruption.
--
--        A manager should periodically check the value of this variable
--        against the manager's own copy. No trap will be sent by the agent
--        when it changes the value."
--    DEFVAL { 0 }
--    ::= { hSystem 1 }


-- hSysMibVersion OBJECT-TYPE 
--    SYNTAX  DisplayString (SIZE(10))
--    ACCESS  read-only
--    STATUS  mandatory
--    DESCRIPTION
--        "The Mib version of the platform in the form `major.minor'."
--    ::= { hSystem 2 }

hTrapTimeLastGenerated  OBJECT-TYPE
    SYNTAX TimeTicks
    ACCESS read-only
    STATUS mandatory
    DESCRIPTION
        "The value of sysUpTime at the time the last trap was
        generated.
        
        This object can be used by the management station to determine
        whether traps were generated since the last poll."
    ::= { hSystem 3 }

hTrapForwardTable  OBJECT-TYPE
    SYNTAX  SEQUENCE OF HTrapForwardEntry
    ACCESS  not-accessible
    STATUS  mandatory
    DESCRIPTION
        "This table contains one row per event (trap) forwarding
        discriminator."
    ::= { hSystem 4 }

hTrapForwardEntry  OBJECT-TYPE
    SYNTAX  HTrapForwardEntry
    ACCESS  not-accessible
    STATUS  mandatory
    DESCRIPTION
        "An entry in the Trap Forwarding Table
        contains information about a particular event forwarding
        discrminator (EFD). Each EFD specifies exactly one
        destination. Its discriminator construct always evaluates
        to TRUE value, i.e. all event reports pass a particualar EFD.
        This is the reason why discriminator construct are omitted."
    INDEX   { hTrapDestAddr }
    ::= { hTrapForwardTable 1 }

HTrapForwardEntry ::= 
    SEQUENCE {
        hTrapDestAddr  IpAddress,
        hTrapDestAddrStatus  INTEGER
    }

hTrapDestAddr  OBJECT-TYPE
    SYNTAX  IpAddress
    ACCESS  read-only
    STATUS  mandatory
    DESCRIPTION
        "The IP address of the network management entity to which traps
        (of the type specified in this table entry) should be sent. The
        value of this object uniquely identifies the trap destination."
    ::= { hTrapForwardEntry 1 }

hTrapDestAddrStatus  OBJECT-TYPE
    SYNTAX  INTEGER {
        active(1),
        createAndGo(4),
        destroy(6)
    }
    ACCESS  read-write
    STATUS  mandatory
    DESCRIPTION
        "The status of the table entry denotes both action and current
        states.

        Set-requests can carry the action values createAndGo(4) and
        destroy(6).

        Get-request always yields the current value active(1).

        In order for a management application to create an entry the
        Set-request with hlpTrapDestAddrStatus(createAndGo) variable
        binding must be sent to the agent. The instance ID part of the
        status variable will indicate the desired ip-address.

        In order for a management application to delete an entry the
        Set-request with hlpTrapDestAddrStatus(destroy) variable
        binding must be sent to the agent.

        Upon creation, the entry moves into active(1) state and stays
        in this state until deletion."
    ::= { hTrapForwardEntry 2 }

-- OID valuse of trap fields

hAlarmStatus   OBJECT IDENTIFIER ::= { hTrapFields 1 }
hAlarmSeverity   OBJECT IDENTIFIER 
	 --"value 6 critical Failure"
	 --"value 4 minor problem"
	 --"value 0 notification"
	 --"values 1,2,3,5 reserved for future uses"
	 ::= { hTrapFields 2 }

hAlarmDesc   OBJECT IDENTIFIER ::= { hTrapFields 3 }

-- OID value assignments for Types of Traps
hTraps		OBJECT IDENTIFIER ::= { hOids 2 }



hPlatformTempFailTrap TRAP-TYPE
	ENTERPRISE hTraps
	VARIABLES	{
		hAlarmStatus,
		hAlarmSeverity,
		hAlarmDesc,
		entPhysicalIndex
 	}
	DESCRIPTION
			 "Temp Failure"
	::= 1
	
hPlatformVoltageFailTrap TRAP-TYPE
	ENTERPRISE hTraps
	VARIABLES	{
		hAlarmStatus,
		hAlarmSeverity,
		hAlarmDesc,
		entPhysicalIndex
 	}
	DESCRIPTION
			 "Voltage Failure"
	::= 2
	
hPlatformFan1FailTrap TRAP-TYPE
	ENTERPRISE hTraps
	VARIABLES	{
		hAlarmStatus,
		hAlarmSeverity,
		hAlarmDesc,
		entPhysicalIndex
 	}
	DESCRIPTION
			 "Fan 1  Failure"
	::= 3	
	
hPlatformFan2FailTrap TRAP-TYPE
	ENTERPRISE hTraps
	VARIABLES	{
		hAlarmStatus,
		hAlarmSeverity,
		hAlarmDesc,
		entPhysicalIndex
 	}
	DESCRIPTION
			 "Fan 2  Failure"
	::= 4	
	
hPlatformFan3FailTrap TRAP-TYPE
	ENTERPRISE hTraps
	VARIABLES	{
		hAlarmStatus,
		hAlarmSeverity,
		hAlarmDesc,
		entPhysicalIndex
 	}
	DESCRIPTION
			 "Fan 3  Failure"
	::= 5	
	
hPlatformFan4FailTrap TRAP-TYPE
	ENTERPRISE hTraps
	VARIABLES	{
		hAlarmStatus,
		hAlarmSeverity,
		hAlarmDesc,
		entPhysicalIndex
 	}
	DESCRIPTION
			 "Fan 4  Failure"
	::= 6	
	
hPlatformPS1VoltageFailTrap TRAP-TYPE
	ENTERPRISE hTraps
	VARIABLES	{
		hAlarmStatus,
		hAlarmSeverity,
		hAlarmDesc,
		entPhysicalIndex
 	}
	DESCRIPTION
			 "Power supply  1  Failure"
	::= 7
	
hPlatformPS2VoltageFailTrap TRAP-TYPE
	ENTERPRISE hTraps
	VARIABLES	{
		hAlarmStatus,
		hAlarmSeverity,
		hAlarmDesc,
		entPhysicalIndex
 	}
	DESCRIPTION
			 "Power supply  2  Failure"
	::= 8		
          
hPlatformR6ConnLossTrap TRAP-TYPE
	ENTERPRISE hTraps
	VARIABLES	{
		hAlarmStatus,
		hAlarmSeverity,
		hAlarmDesc,
		entPhysicalIndex
 	}
	DESCRIPTION
			 "R6 connection lost"
	::= 9


hPlatformD6ConnLossTrap TRAP-TYPE
	ENTERPRISE hTraps
	VARIABLES	{
		hAlarmStatus,
		hAlarmSeverity,
		hAlarmDesc,
		entPhysicalIndex
 	}
	DESCRIPTION
			 "D6 connection lost"
	::= 10

hGbePortLinkDownTrap TRAP-TYPE
	ENTERPRISE hTraps
	VARIABLES	{
		hAlarmStatus,
		hAlarmSeverity,
		hAlarmDesc,
		entPhysicalIndex
 	}
	DESCRIPTION
			 "Gbe port link down"
	::= 11

hRfModuleHwFailTrap TRAP-TYPE
	ENTERPRISE hTraps
	VARIABLES	{
		hAlarmStatus,
		hAlarmSeverity,
		hAlarmDesc,
		entPhysicalIndex
 	}
	DESCRIPTION
			 "Rf module hw failure"
	::= 12

hRfModuleTempFailTrap TRAP-TYPE
	ENTERPRISE hTraps
	VARIABLES	{
		hAlarmStatus,
		hAlarmSeverity,
		hAlarmDesc,
		entPhysicalIndex
 	}
	DESCRIPTION
			 "Rf module temperature  failure"
	::= 13
	
hRfPortHwFailTrap TRAP-TYPE
	ENTERPRISE hTraps
	VARIABLES	{
		hAlarmStatus,
		hAlarmSeverity,
		hAlarmDesc,
		entPhysicalIndex
 	}
	DESCRIPTION
			 "Rf port hw  failure"
	::= 14
	
    
hRfPortTempFailTrap TRAP-TYPE
	ENTERPRISE hTraps
	VARIABLES	{
		hAlarmStatus,
		hAlarmSeverity,
		hAlarmDesc,
		entPhysicalIndex
 	}
	DESCRIPTION
			 "Rf port temperature  failure"
	::= 15
	                 
hQamChanneOverflowTrap TRAP-TYPE
	ENTERPRISE hTraps
	VARIABLES	{
		hAlarmStatus,
		hAlarmSeverity,
		hAlarmDesc,
		entPhysicalIndex
 	}
	DESCRIPTION
			 "Qam channel overflow"
	::= 16

hServicePatMissing TRAP-TYPE
	ENTERPRISE hTraps
	VARIABLES	{
		hAlarmStatus,
		hAlarmSeverity,
		hAlarmDesc,
		entPhysicalIndex
 	}
	DESCRIPTION
			 "Service pat missing"
	::= 17

hServicePmtMissing TRAP-TYPE
	ENTERPRISE hTraps
	VARIABLES	{
		hAlarmStatus,
		hAlarmSeverity,
		hAlarmDesc,
		entPhysicalIndex
 	}
	DESCRIPTION
			 "Service pmt missing"
	::= 18

hSwitchToAlternateSource TRAP-TYPE
	ENTERPRISE hTraps
	VARIABLES	{
		hAlarmStatus,
		hAlarmSeverity,
		hAlarmDesc,
		entPhysicalIndex
 	}
	DESCRIPTION
			 "SDV service switch to alternate source"
	::= 19

hPassThroughSourceFailure TRAP-TYPE
	ENTERPRISE hTraps
	VARIABLES	{
		hAlarmStatus,
		hAlarmSeverity,
		hAlarmDesc,
		entPhysicalIndex
 	}
	DESCRIPTION
			 "Source Failure"
	::= 20

hPidRemuxSourceFailure TRAP-TYPE
	ENTERPRISE hTraps
	VARIABLES	{
		hAlarmStatus,
		hAlarmSeverity,
		hAlarmDesc,
		entPhysicalIndex
 	}
	DESCRIPTION
			 "Source Failure"
	::= 21

hDtiCardMissing TRAP-TYPE
	ENTERPRISE hTraps
	VARIABLES	{
		hAlarmStatus,
		hAlarmSeverity,
		hAlarmDesc,
		entPhysicalIndex
 	}
	DESCRIPTION
			 "DTI Card Missing"
	::= 22

hMcECMMissing TRAP-TYPE
	ENTERPRISE hTraps
	VARIABLES	{
		hAlarmStatus,
		hAlarmSeverity,
		hAlarmDesc,
		entPhysicalIndex
 	}
	DESCRIPTION
			 "ECM Missing"
	::= 23

hMcECMNearingExpiration TRAP-TYPE
	ENTERPRISE hTraps
	VARIABLES	{
		hAlarmStatus,
		hAlarmSeverity,
		hAlarmDesc,
		entPhysicalIndex
 	}
	DESCRIPTION
			 "ECM Nearing Expiration"
	::= 24

hMcECMExpired TRAP-TYPE
	ENTERPRISE hTraps
	VARIABLES	{
		hAlarmStatus,
		hAlarmSeverity,
		hAlarmDesc,
		entPhysicalIndex
 	}
	DESCRIPTION
			 "ECM Expired"
	::= 25

hDtiClientLinkDown TRAP-TYPE
	ENTERPRISE hTraps
	VARIABLES	{
		hAlarmStatus,
		hAlarmSeverity,
		hAlarmDesc,
		entPhysicalIndex
 	}
	DESCRIPTION
			 "DTI Client Link Down"
	::= 26

hDtiClientNotLocked TRAP-TYPE
	ENTERPRISE hTraps
	VARIABLES	{
		hAlarmStatus,
		hAlarmSeverity,
		hAlarmDesc,
		entPhysicalIndex
 	}
	DESCRIPTION
			 "DTI Client Not Locked"
	::= 27


END
