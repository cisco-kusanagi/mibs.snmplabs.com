--
--  Title:  Appian BUFFERS MIB
--
--  Dated:  10/16/00
--  Author: Russell Peterson
--
--  Description:
--
--  The buffers MIB defines buffer management objects for the Appian Communications
--  OSAP platform.
--
--

APPIAN-BUFFERS-MIB DEFINITIONS ::= BEGIN

    IMPORTS

        acOsap, AcAdminStatus, AcNodeId                 FROM APPIAN-SMI-MIB

        MODULE-IDENTITY, OBJECT-TYPE, Unsigned32        FROM SNMPv2-SMI

        DisplayString                                   FROM SNMPv2-TC;


acBuffers
    MODULE-IDENTITY
        LAST-UPDATED    "0010161130Z"
        ORGANIZATION    "Appian Communications, Inc."
        CONTACT-INFO    "Douglas Theriault"
        DESCRIPTION 
                        "Appian Communications OSAP buffers MIB contains the
                        definitions for buffer management related 
                        configuration objects."

        REVISION        "0010161130Z"
        DESCRIPTION     "Initial version of MIB."
        
        ::= { acOsap 10 }

--
-- Start buffers MIB
--

acSwitchBuffStatsTable   OBJECT-TYPE
    SYNTAX  SEQUENCE OF AcSwitchBuffStatsEntry
    MAX-ACCESS  not-accessible
    STATUS  current
    DESCRIPTION
    "This table contains switch buffer statistics.  Switch buffers are used by the
    switch forwarding logic on the services card to enqueue packets."

    ::= { acBuffers 1 }

acSwitchBuffStatsEntry   OBJECT-TYPE
    SYNTAX  AcSwitchBuffStatsEntry
    MAX-ACCESS  not-accessible
    STATUS  current
    DESCRIPTION
    "A row within the switch buffer statistics table."
    
    INDEX   { acSwitchBuffStatsNodeId }

    ::= { acSwitchBuffStatsTable 1 }

    AcSwitchBuffStatsEntry ::=
        SEQUENCE {
            acSwitchBuffStatsNodeId              AcNodeId,
            acSwitchBuffStatsBuffSize            Unsigned32,
            acSwitchBuffStatsTotalBuffs          Unsigned32,
            acSwitchBuffStatsTotalBuffCredits    Unsigned32,
            acSwitchBuffStatsTotalLocalServices  Unsigned32,
            acSwitchBuffStatsTotalRemoteServices Unsigned32,
            acSwitchBuffStatsTotalRemPoolMisses  Unsigned32
        }


acSwitchBuffStatsNodeId OBJECT-TYPE
    SYNTAX      AcNodeId
    MAX-ACCESS  accessible-for-notify
    STATUS      current
    DESCRIPTION
    "The unique node identification number representing a chassis within a
    ring of OSAP's."

    ::= { acSwitchBuffStatsEntry 1 }

acSwitchBuffStatsBuffSize OBJECT-TYPE
    SYNTAX      Unsigned32
    MAX-ACCESS  read-only
    STATUS      current
    DESCRIPTION
    "The size of a switch buffer in bytes (octets)."

    ::= { acSwitchBuffStatsEntry 2 }

acSwitchBuffStatsTotalBuffs OBJECT-TYPE
    SYNTAX      Unsigned32
    MAX-ACCESS  read-only
    STATUS      current
    DESCRIPTION
    "The total number of physical switch buffers available for general use."

    ::= { acSwitchBuffStatsEntry 3 }

acSwitchBuffStatsTotalBuffCredits OBJECT-TYPE
    SYNTAX      Unsigned32
    MAX-ACCESS  read-only
    STATUS      current
    DESCRIPTION
    "The total number of buffer credits available for general use.  The 
    number of buffer credits is a function of acSwitchBuffStatsBuffSize, 
    acSwitchBuffStatsTotalBuffs, and acSwitchBuffCfgOversubRate."

    ::= { acSwitchBuffStatsEntry 4 }

acSwitchBuffStatsTotalLocalServices OBJECT-TYPE
    SYNTAX      Unsigned32
    MAX-ACCESS  read-only
    STATUS      current
    DESCRIPTION
    "The total number of local services configured on this system."

    ::= { acSwitchBuffStatsEntry 5 }

acSwitchBuffStatsTotalRemoteServices OBJECT-TYPE
    SYNTAX      Unsigned32
    MAX-ACCESS  read-only
    STATUS      current
    DESCRIPTION
    "The total number of remote services configured on this system."

    ::= { acSwitchBuffStatsEntry 6 }

acSwitchBuffStatsTotalRemPoolMisses OBJECT-TYPE
    SYNTAX      Unsigned32
    MAX-ACCESS  read-only
    STATUS      current
    DESCRIPTION
    "The total number of remote services that are in the
    acSwitchBuffCfgRemoteServicesBP buffer pool because the buffer
    pool associated with that remote service does not exist or is
    disabled."

    ::= { acSwitchBuffStatsEntry 7 }



acSwitchBuffCfgTable   OBJECT-TYPE
    SYNTAX  SEQUENCE OF AcSwitchBuffCfgEntry
    MAX-ACCESS  not-accessible
    STATUS  current
    DESCRIPTION
    "This table contains switch buffer configuration parameters.  Switch buffers 
    are used by the switch forwarding logic on the services card to 
    enqueue packets."

    ::= { acBuffers 2 }

acSwitchBuffCfgEntry   OBJECT-TYPE
    SYNTAX  AcSwitchBuffCfgEntry
    MAX-ACCESS  not-accessible
    STATUS  current
    DESCRIPTION
    "A row within the switch buffer configuration table."
    
    INDEX   { acSwitchBuffCfgNodeId }

    ::= { acSwitchBuffCfgTable 1 }

    AcSwitchBuffCfgEntry ::=
        SEQUENCE {
            acSwitchBuffCfgNodeId              AcNodeId,
            acSwitchBuffCfgOversubRate         Unsigned32,
            acSwitchBuffCfgMinDefaultBPSize    Unsigned32,
            acSwitchBuffCfgRemoteServicesBP    Unsigned32,
            acSwitchBuffCfgUpBuffCapWeight     Unsigned32,
            acSwitchBuffCfgDownBuffCapWeight   Unsigned32,
            acSwitchBuffCfgLocalBuffCapWeight  Unsigned32,
            acSwitchBuffCfgRemoteBuffCapWeight Unsigned32
        }


acSwitchBuffCfgNodeId OBJECT-TYPE
    SYNTAX      AcNodeId
    MAX-ACCESS  accessible-for-notify
    STATUS      current
    DESCRIPTION
    "The unique node identification number representing a chassis within a
    ring of OSAP's."

    ::= { acSwitchBuffCfgEntry 1 }

acSwitchBuffCfgOversubRate OBJECT-TYPE
    SYNTAX      Unsigned32
    MAX-ACCESS  read-create
    STATUS      current
    DESCRIPTION
    "A percentage indicating how much the system should oversubscribe buffers
    to queues.  By oversubscribing buffers to queues, a statistical gain can
    be achieved with respect to system throughput.  For example, to oversubscribe
    buffer utilization by 50%, set acSwitchBuffCfgOversubRate to 50.  This means
    that if some queues encounter bursty traffic, they will be less likely to
    drop data.  Using oversubscription involves risking that all traffic flows
    do not burst at the same time.  If this were to happen, some high priority
    traffic could be dropped in favor of lower priority traffic.  Since this
    may be undesirable, the default value for this object is 0 (indicating a
    zero percent oversubscription rate).  A setting of 0 implies the total number
    of buffer credits in the system equals the total number of physical buffers."

    DEFVAL {0}

    ::= { acSwitchBuffCfgEntry 2 }

acSwitchBuffCfgMinDefaultBPSize OBJECT-TYPE
    SYNTAX      Unsigned32(0..100)
    MAX-ACCESS  read-create
    STATUS      current
    DESCRIPTION
    "A percentage indicating how much of the total system buffer credits should
    be reserved for the default buffer pool.  Since user defined buffer pools
    take buffers from the default buffer pool, setting 
    acSwitchBuffCfgMinDefaultBPSize to a value greater that 0 ensures that the
    default buffer pool will never have 0 buffer credits.  For example, setting
    acSwitchBuffCfgMinDefaultBPSize to 37 will reserve 37% of the total system
    buffer credits (acSwitchBuffStatsTotalBuffCredits) for the default buffer pool."

    DEFVAL {0}

    ::= { acSwitchBuffCfgEntry 3 }

acSwitchBuffCfgRemoteServicesBP OBJECT-TYPE
    SYNTAX      Unsigned32 (1..131072)
    MAX-ACCESS  read-create
    STATUS      current
    DESCRIPTION
    "A buffer pool associated with remote services.  All remote services on this
    system will share this buffer pool if the buffer pool associated with the
    remote service does not exist or is diabled.  The default buffer pool
    (buffer pool #1) is the default setting for this attribute."

    DEFVAL {1}

    ::= { acSwitchBuffCfgEntry 4 }

acSwitchBuffCfgUpBuffCapWeight OBJECT-TYPE
    SYNTAX      Unsigned32(1..10)
    MAX-ACCESS  read-create
    STATUS      current
    DESCRIPTION
    "The system level buffering capacity weight for upstream traffic.  Upstream traffic
    is defined as traffic that enters the system on an access port and exits the system
    on a trunk.  A value of 1 provides the least amount of buffering capacity while a
    value of 10 provides the most buffering capacity.  This value is relative in that
    the number of buffers actually assigned to hardware queues depends on how many
    services are configured on any given buffer pool."

    DEFVAL {5}

    ::= { acSwitchBuffCfgEntry 5 }

acSwitchBuffCfgDownBuffCapWeight OBJECT-TYPE
    SYNTAX      Unsigned32(1..10)
    MAX-ACCESS  read-create
    STATUS      current
    DESCRIPTION
    "The system level buffering capacity weight for downstream traffic.  Downstream traffic
    is defined as traffic that enters the system on a trunk and exits the system on an
    access port.  A value of 1 provides the least amount of buffering capacity while a
    value of 10 provides the most buffering capacity.  This value is relative in that
    the number of buffers actually assigned to hardware queues depends on how many
    services are configured on any given buffer pool."

    DEFVAL {1}

    ::= { acSwitchBuffCfgEntry 6 }

acSwitchBuffCfgLocalBuffCapWeight OBJECT-TYPE
    SYNTAX      Unsigned32(1..10)
    MAX-ACCESS  read-create
    STATUS      current
    DESCRIPTION
    "The system level buffering capacity weight for local traffic.  Local traffic
    is defined as traffic that enters the system on an access port and exits the system
    on an access port.  Local traffic only exists on systems which have multiple ports
    configured on the same transparent LAN service.  A value of 1 provides the least 
    amount of buffering capacity while a value of 10 provides the most buffering capacity.
    This value is relative in that the number of buffers actually assigned to hardware 
    queues depends on how many services are configured on any given buffer pool."

    DEFVAL {2}

    ::= { acSwitchBuffCfgEntry 7 }

acSwitchBuffCfgRemoteBuffCapWeight OBJECT-TYPE
    SYNTAX      Unsigned32(1..10)
    MAX-ACCESS  read-create
    STATUS      current
    DESCRIPTION
    "The system level buffering capacity weight for remote services traffic.  Remote
    services traffic enters the system on a trunk and exits the system on a trunk.
    A value of 1 provides the least amount of buffering capacity while a value of 10 
    provides the most buffering capacity.  This value is relative in that the number 
    of buffers actually assigned to hardware queues depends on how many services are 
    configured on any given buffer pool."

    DEFVAL {2}

    ::= { acSwitchBuffCfgEntry 8 }


acSwitchBuffPoolTable   OBJECT-TYPE
    SYNTAX  SEQUENCE OF AcSwitchBuffPoolEntry
    MAX-ACCESS  not-accessible
    STATUS  current
    DESCRIPTION
    "This table contains switch logical buffer pool configuration parameters.  
    Switch buffers are used by the switch forwarding logic on the services card to 
    enqueue packets.  Logical switch buffer pools can be assigned/associated with
    OSAP services."

    ::= { acBuffers 3 }

acSwitchBuffPoolEntry   OBJECT-TYPE
    SYNTAX  AcSwitchBuffPoolEntry
    MAX-ACCESS  not-accessible
    STATUS  current
    DESCRIPTION
    "A row within the switch logical buffer pool table."
    
    INDEX   { acSwitchBuffPoolNodeId, acSwitchBuffPoolID }

    ::= { acSwitchBuffPoolTable 1 }

    AcSwitchBuffPoolEntry ::=
        SEQUENCE {
            acSwitchBuffPoolNodeId              AcNodeId,
            acSwitchBuffPoolID                  Unsigned32,
            acSwitchBuffPoolAdminStatus         AcAdminStatus,
            acSwitchBuffPoolName                DisplayString,
            acSwitchBuffPoolCfgBuffCredits      Unsigned32,
            acSwitchBuffPoolActualBuffCredits   Unsigned32,
            acSwitchBuffPoolTotalLocalServices  Unsigned32,
            acSwitchBuffPoolTotalRemoteServices Unsigned32,
            acSwitchBuffPoolResellerId          INTEGER,
            acSwitchBuffPoolResellerName        DisplayString
        }


acSwitchBuffPoolNodeId OBJECT-TYPE
    SYNTAX      AcNodeId
    MAX-ACCESS  accessible-for-notify
    STATUS      current
    DESCRIPTION
    "The unique node identification number representing a chassis within a
    ring of OSAP's."

    ::= { acSwitchBuffPoolEntry 1 }

acSwitchBuffPoolID OBJECT-TYPE
    SYNTAX      Unsigned32 (1..131072)
    MAX-ACCESS  accessible-for-notify
    STATUS      current
    DESCRIPTION
    "The buffer pool identifier.  Also known as the buffer pool number.  Buffer
    pool number 1 is reserved as the default buffer pool (which always exists
    and cannot be deleted or disabled)."

    ::= { acSwitchBuffPoolEntry 2 }

acSwitchBuffPoolAdminStatus  OBJECT-TYPE
    SYNTAX  AcAdminStatus
    MAX-ACCESS read-create
    STATUS  current
    DESCRIPTION
    "Appian Administrative Status attribute used to set the provisioning
    state as either activate(1), inactivate(2) or delete(3).  Refer to
    the Appian-SMI.mib file for additional information.

    Note that the default buffer pool cannot be deleted or disabled."

    DEFVAL { activate }

    ::= { acSwitchBuffPoolEntry 3 }

acSwitchBuffPoolName OBJECT-TYPE
    SYNTAX      DisplayString (SIZE(0..64))
    MAX-ACCESS  read-create
    STATUS      current
    DESCRIPTION
    "A user defined string.  This allows users to assign a descriptive name
    to a buffer pool."

    ::= { acSwitchBuffPoolEntry 4 }

acSwitchBuffPoolCfgBuffCredits OBJECT-TYPE
    SYNTAX      Unsigned32(1..100)
    MAX-ACCESS  read-create
    STATUS      current
    DESCRIPTION
    "Allocate the specified percentage of the total switch buffer
    credits to this buffer pool.  Note that if the request cannot be met, the
    system will allocate as high a percentage as possible and report that value
    in acSwitchBuffPoolActualBuffCredits."

    ::= { acSwitchBuffPoolEntry 5 }

acSwitchBuffPoolActualBuffCredits OBJECT-TYPE
    SYNTAX      Unsigned32(0..100)
    MAX-ACCESS  read-only
    STATUS      current
    DESCRIPTION
    "The actual percentage of the total switch buffer credits allocated to
    this buffer pool."

    ::= { acSwitchBuffPoolEntry 6 }

acSwitchBuffPoolTotalLocalServices OBJECT-TYPE
    SYNTAX      Unsigned32
    MAX-ACCESS  read-only
    STATUS      current
    DESCRIPTION
    "The number of local services associated with this buffer pool."

    ::= { acSwitchBuffPoolEntry 7 }

acSwitchBuffPoolTotalRemoteServices OBJECT-TYPE
    SYNTAX      Unsigned32
    MAX-ACCESS  read-only
    STATUS      current
    DESCRIPTION
    "The number of remote services associated with this buffer pool."

    ::= { acSwitchBuffPoolEntry 8 }

acSwitchBuffPoolResellerId  OBJECT-TYPE
    SYNTAX  INTEGER
    MAX-ACCESS read-create
    STATUS  current
    DESCRIPTION
    "A unique number assigned by the EMS that uniquely identifies the reseller
    which supplies this buffer pool."
    
    ::= { acSwitchBuffPoolEntry 9 }

acSwitchBuffPoolResellerName  OBJECT-TYPE
    SYNTAX  DisplayString (SIZE(0..64))
    MAX-ACCESS read-create
    STATUS  current
    DESCRIPTION
    "An ASCII string which represents the reseller in a readable form. The
    string can be up to 64 characters in length."    

    ::= { acSwitchBuffPoolEntry 10 }

END
