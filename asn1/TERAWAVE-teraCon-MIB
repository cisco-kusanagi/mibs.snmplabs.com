TERAWAVE-teraCon-MIB DEFINITIONS ::= BEGIN
        -- Created by sml2mib compiler 
        IMPORTS

	Counter32 FROM SNMPv2-SMI
 IpAddress, enterprises,  OBJECT-TYPE,  Counter,  Gauge,  TimeTicks
        FROM RFC1155-SMI;

terawave OBJECT IDENTIFIER ::=  { enterprises 4513 }

connections OBJECT IDENTIFIER ::=  { terawave 2 }

     -- NextConTableEntryTable (special)

     -- conTable

conTable OBJECT-TYPE
     SYNTAX SEQUENCE OF ConTableEntryType
     ACCESS not-accessible
     STATUS mandatory
     DESCRIPTION
          " table conTable"
     ::= { connections 1 }

nextConTableEntryIndex OBJECT-TYPE
          SYNTAX Counter32
          ACCESS read-only
          STATUS mandatory
          DESCRIPTION
               " Next index to the table."
     ::= { conTable 1 }
conTableEntry OBJECT-TYPE
          SYNTAX ConTableEntryType
          ACCESS not-accessible
          STATUS mandatory
          DESCRIPTION
               " table entry conTableEntry "
          INDEX {                   circuitCONID }
     ::= { conTable 2 }

ConTableEntryType ::= SEQUENCE {
          circuitCONID   
             Counter32,
          circuitCONName   
             OCTET STRING,
          serviceCONType   
             INTEGER,
          firstCONIfIndex   
             INTEGER,
          secondCONIfIndex   
             INTEGER,
          firstCONVPI   
             INTEGER,
          firstCONVCI   
             INTEGER,
          secondCONVPI   
             INTEGER,
          secondCONVCI   
             INTEGER,
          conVLANNumber   
             INTEGER (0..4094),
          requestedCONBW   
             INTEGER,
          firstInternalVPI   
             INTEGER,
          firstInternalVCI   
             INTEGER,
          secondInternalVPI   
             INTEGER,
          secondInternalVCI   
             INTEGER,
          rowCONTableAction   
             INTEGER,
          conStatus   
             INTEGER,
          conUserId   
             INTEGER,
          conUserConId   
             INTEGER
}

circuitCONID OBJECT-TYPE
          SYNTAX Counter32
          ACCESS read-only
          STATUS mandatory
          DESCRIPTION
               ""
          ::= { conTableEntry 1 }

circuitCONName OBJECT-TYPE
          SYNTAX OCTET STRING
          ACCESS read-write
          STATUS mandatory
          DESCRIPTION
               ""
          ::= { conTableEntry 2 }

serviceCONType OBJECT-TYPE
          SYNTAX INTEGER
                  {
                  tdm-tdm(1),
                  tdm-pvc(2),
                  pvc-pvc(3),
                  lan-pvc(4),
                  lan-lan(5),
                  lan2pvc(6),
                  vlan-trunk(7)
                  }
          ACCESS read-write
          STATUS mandatory
          DESCRIPTION
               ""
          ::= { conTableEntry 3 }

firstCONIfIndex OBJECT-TYPE
          SYNTAX INTEGER
          ACCESS read-write
          STATUS mandatory
          DESCRIPTION
               ""
          ::= { conTableEntry 4 }

secondCONIfIndex OBJECT-TYPE
          SYNTAX INTEGER
          ACCESS read-write
          STATUS mandatory
          DESCRIPTION
               ""
          ::= { conTableEntry 5 }

firstCONVPI OBJECT-TYPE
          SYNTAX INTEGER
          ACCESS read-write
          STATUS mandatory
          DESCRIPTION
               ""
          ::= { conTableEntry 6 }

firstCONVCI OBJECT-TYPE
          SYNTAX INTEGER
          ACCESS read-write
          STATUS mandatory
          DESCRIPTION
               ""
          ::= { conTableEntry 7 }

secondCONVPI OBJECT-TYPE
          SYNTAX INTEGER
          ACCESS read-write
          STATUS mandatory
          DESCRIPTION
               ""
          ::= { conTableEntry 8 }

secondCONVCI OBJECT-TYPE
          SYNTAX INTEGER
          ACCESS read-write
          STATUS mandatory
          DESCRIPTION
               ""
          ::= { conTableEntry 9 }

conVLANNumber OBJECT-TYPE
          SYNTAX INTEGER (0..4094)
          ACCESS read-write
          STATUS mandatory
          DESCRIPTION
               ""
          ::= { conTableEntry 10 }

requestedCONBW OBJECT-TYPE
          SYNTAX INTEGER
                  {
                  atm(1),
                  vlan-c(2),
                  t1(3),
                  e1(4),
                  ds3(5),
                  e3(6),
                  oc3(7),
                  stm1(8),
                  atm-vpi(9)
                  }
          ACCESS read-write
          STATUS mandatory
          DESCRIPTION
               ""
          ::= { conTableEntry 11 }

firstInternalVPI OBJECT-TYPE
          SYNTAX INTEGER
          ACCESS read-only
          STATUS mandatory
          DESCRIPTION
               ""
          ::= { conTableEntry 12 }

firstInternalVCI OBJECT-TYPE
          SYNTAX INTEGER
          ACCESS read-only
          STATUS mandatory
          DESCRIPTION
               ""
          ::= { conTableEntry 13 }

secondInternalVPI OBJECT-TYPE
          SYNTAX INTEGER
          ACCESS read-only
          STATUS mandatory
          DESCRIPTION
               ""
          ::= { conTableEntry 14 }

secondInternalVCI OBJECT-TYPE
          SYNTAX INTEGER
          ACCESS read-only
          STATUS mandatory
          DESCRIPTION
               ""
          ::= { conTableEntry 15 }

rowCONTableAction OBJECT-TYPE
          SYNTAX INTEGER
                  {
                  ok(1),
                  delete(2)
                  }
          ACCESS read-write
          STATUS mandatory
          DESCRIPTION
               ""
          ::= { conTableEntry 16 }

conStatus OBJECT-TYPE
          SYNTAX INTEGER
                  {
                  up(1),
                  down(2)
                  }
          ACCESS read-only
          STATUS mandatory
          DESCRIPTION
               ""
          ::= { conTableEntry 17 }

conUserId OBJECT-TYPE
          SYNTAX INTEGER
          ACCESS read-write
          STATUS mandatory
          DESCRIPTION
               ""
          ::= { conTableEntry 18 }

conUserConId OBJECT-TYPE
          SYNTAX INTEGER
          ACCESS read-write
          STATUS mandatory
          DESCRIPTION
               ""
          ::= { conTableEntry 19 }

     -- circTable

circTable OBJECT-TYPE
     SYNTAX SEQUENCE OF CircTableEntryType
     ACCESS not-accessible
     STATUS mandatory
     DESCRIPTION
          " table circTable"
     ::= { connections 2 }

circTableEntry OBJECT-TYPE
          SYNTAX CircTableEntryType
          ACCESS not-accessible
          STATUS mandatory
          DESCRIPTION
               " table entry circTableEntry "
          INDEX {                   circuitCONID }
     ::= { circTable 1 }

CircTableEntryType ::= SEQUENCE {
          cmFirstInternalVPI   
             INTEGER,
          cmFirstInternalVCI   
             INTEGER,
          cmSecondInternalVPI   
             INTEGER,
          cmSecondInternalVCI   
             INTEGER
}

cmFirstInternalVPI OBJECT-TYPE
          SYNTAX INTEGER
          ACCESS read-write
          STATUS mandatory
          DESCRIPTION
               ""
          ::= { circTableEntry 1 }

cmFirstInternalVCI OBJECT-TYPE
          SYNTAX INTEGER
          ACCESS read-write
          STATUS mandatory
          DESCRIPTION
               ""
          ::= { circTableEntry 2 }

cmSecondInternalVPI OBJECT-TYPE
          SYNTAX INTEGER
          ACCESS read-write
          STATUS mandatory
          DESCRIPTION
               ""
          ::= { circTableEntry 3 }

cmSecondInternalVCI OBJECT-TYPE
          SYNTAX INTEGER
          ACCESS read-write
          STATUS mandatory
          DESCRIPTION
               ""
          ::= { circTableEntry 4 }

bandwidthGroup OBJECT IDENTIFIER ::=  { connections 3 }

     -- bwGroupTableNextTable (special)

     -- bwGroupTable

bwGroupTable OBJECT-TYPE
     SYNTAX SEQUENCE OF BwGroupTableEntryType
     ACCESS not-accessible
     STATUS mandatory
     DESCRIPTION
          " table bwGroupTable"
     ::= { bandwidthGroup 1 }

bwGroupTableNextId OBJECT-TYPE
          SYNTAX INTEGER
          ACCESS read-only
          STATUS mandatory
          DESCRIPTION
               " Next index to the table."
     ::= { bwGroupTable 1 }
bwGroupTableEntry OBJECT-TYPE
          SYNTAX BwGroupTableEntryType
          ACCESS not-accessible
          STATUS mandatory
          DESCRIPTION
               " table entry bwGroupTableEntry "
          INDEX {                   bwGroupId }
     ::= { bwGroupTable 2 }

BwGroupTableEntryType ::= SEQUENCE {
          bwGroupId   
             INTEGER,
          bwGroupName   
             OCTET STRING,
          requestedBandwidth   
             INTEGER,
          maxBandwidth   
             INTEGER,
          bwGroupPorts   
             OCTET STRING,
          bwGroupTableAction   
             INTEGER
}

bwGroupId OBJECT-TYPE
          SYNTAX INTEGER
          ACCESS read-only
          STATUS mandatory
          DESCRIPTION
               ""
          ::= { bwGroupTableEntry 1 }

bwGroupName OBJECT-TYPE
          SYNTAX OCTET STRING
          ACCESS read-write
          STATUS mandatory
          DESCRIPTION
               ""
          ::= { bwGroupTableEntry 2 }

requestedBandwidth OBJECT-TYPE
          SYNTAX INTEGER
          ACCESS read-write
          STATUS mandatory
          DESCRIPTION
               ""
          ::= { bwGroupTableEntry 3 }

maxBandwidth OBJECT-TYPE
          SYNTAX INTEGER
          ACCESS read-write
          STATUS mandatory
          DESCRIPTION
               ""
          ::= { bwGroupTableEntry 4 }

bwGroupPorts OBJECT-TYPE
          SYNTAX OCTET STRING
          ACCESS read-write
          STATUS mandatory
          DESCRIPTION
               ""
          ::= { bwGroupTableEntry 5 }

bwGroupTableAction OBJECT-TYPE
          SYNTAX INTEGER
                  {
                  ok(1),
                  delete(2)
                  }
          ACCESS read-write
          STATUS mandatory
          DESCRIPTION
               ""
          ::= { bwGroupTableEntry 6 }

     -- teraStaticBWTable

teraStaticBWTable OBJECT-TYPE
     SYNTAX SEQUENCE OF TeraStaticBWTableEntryType
     ACCESS not-accessible
     STATUS mandatory
     DESCRIPTION
          " table teraStaticBWTable"
     ::= { connections 4 }

teraStaticBWTableEntry OBJECT-TYPE
          SYNTAX TeraStaticBWTableEntryType
          ACCESS not-accessible
          STATUS mandatory
          DESCRIPTION
               " table entry teraStaticBWTableEntry "
          INDEX {                   teraInstallSlotNumber }
     ::= { teraStaticBWTable 1 }

TeraStaticBWTableEntryType ::= SEQUENCE {
          teraStaticBWTotal   
             INTEGER,
          teraStaticBWcbr   
             INTEGER,
          teraStaticBWaux   
             INTEGER,
          teraStaticBWvbr   
             INTEGER,
          teraStaticAllocBWvbr   
             INTEGER
}

teraStaticBWTotal OBJECT-TYPE
          SYNTAX INTEGER
          ACCESS read-only
          STATUS mandatory
          DESCRIPTION
               ""
          ::= { teraStaticBWTableEntry 1 }

teraStaticBWcbr OBJECT-TYPE
          SYNTAX INTEGER
          ACCESS read-only
          STATUS mandatory
          DESCRIPTION
               ""
          ::= { teraStaticBWTableEntry 2 }

teraStaticBWaux OBJECT-TYPE
          SYNTAX INTEGER
          ACCESS read-only
          STATUS mandatory
          DESCRIPTION
               ""
          ::= { teraStaticBWTableEntry 3 }

teraStaticBWvbr OBJECT-TYPE
          SYNTAX INTEGER
          ACCESS read-only
          STATUS mandatory
          DESCRIPTION
               ""
          ::= { teraStaticBWTableEntry 4 }

teraStaticAllocBWvbr OBJECT-TYPE
          SYNTAX INTEGER
          ACCESS read-only
          STATUS mandatory
          DESCRIPTION
               ""
          ::= { teraStaticBWTableEntry 5 }

     -- teraStaticSplitBWTable

teraStaticSplitBWTable OBJECT-TYPE
     SYNTAX SEQUENCE OF TeraStaticSplitBWTableEntryType
     ACCESS not-accessible
     STATUS mandatory
     DESCRIPTION
          " table teraStaticSplitBWTable"
     ::= { connections 5 }

teraStaticSplitBWTableEntry OBJECT-TYPE
          SYNTAX TeraStaticSplitBWTableEntryType
          ACCESS not-accessible
          STATUS mandatory
          DESCRIPTION
               " table entry teraStaticSplitBWTableEntry "
          INDEX {                   teraInstallSlotNumber,                  teraNEIDxSlotLevel1 }
     ::= { teraStaticSplitBWTable 1 }

TeraStaticSplitBWTableEntryType ::= SEQUENCE {
          teraStaticSplitBWVBRConn   
             INTEGER,
          teraStaticSplitBWCBRConn   
             INTEGER,
          teraStaticSplitBWEffective   
             INTEGER,
          teraStaticSplitBWUnits   
             INTEGER,
          teraStaticSplitBWUnitsBandwidth   
             INTEGER,
          teraStaticSplitBWAllocated   
             INTEGER
}

teraStaticSplitBWVBRConn OBJECT-TYPE
          SYNTAX INTEGER
          ACCESS read-only
          STATUS mandatory
          DESCRIPTION
               ""
          ::= { teraStaticSplitBWTableEntry 1 }

teraStaticSplitBWCBRConn OBJECT-TYPE
          SYNTAX INTEGER
          ACCESS read-only
          STATUS mandatory
          DESCRIPTION
               ""
          ::= { teraStaticSplitBWTableEntry 2 }

teraStaticSplitBWEffective OBJECT-TYPE
          SYNTAX INTEGER
          ACCESS read-only
          STATUS mandatory
          DESCRIPTION
               ""
          ::= { teraStaticSplitBWTableEntry 3 }

teraStaticSplitBWUnits OBJECT-TYPE
          SYNTAX INTEGER
          ACCESS read-only
          STATUS mandatory
          DESCRIPTION
               ""
          ::= { teraStaticSplitBWTableEntry 4 }

teraStaticSplitBWUnitsBandwidth OBJECT-TYPE
          SYNTAX INTEGER
          ACCESS read-only
          STATUS mandatory
          DESCRIPTION
               ""
          ::= { teraStaticSplitBWTableEntry 5 }

teraStaticSplitBWAllocated OBJECT-TYPE
          SYNTAX INTEGER
          ACCESS read-only
          STATUS mandatory
          DESCRIPTION
               ""
          ::= { teraStaticSplitBWTableEntry 6 }

     -- teraCraftCMTable (special)

teraCraftCMTable OBJECT IDENTIFIER ::=  { connections 6 }

teraCraftCMAdminStatus OBJECT-TYPE
          SYNTAX INTEGER
                  {
                  none(0),
                  granted(1),
                  notgranted(2)
                  }
          ACCESS read-write
          STATUS mandatory
          DESCRIPTION
               ""
          ::= { teraCraftCMTable 1 }

teraCraftCMOperStatus OBJECT-TYPE
          SYNTAX INTEGER
                  {
                  on(1),
                  off(2),
                  wait4ack(3)
                  }
          ACCESS read-only
          STATUS mandatory
          DESCRIPTION
               ""
          ::= { teraCraftCMTable 2 }

     -- teraManagementPVCTable

teraManagementPVCTable OBJECT-TYPE
     SYNTAX SEQUENCE OF TeraManagementPVCTableEntryType
     ACCESS not-accessible
     STATUS mandatory
     DESCRIPTION
          " table teraManagementPVCTable"
     ::= { connections 7 }

teraManagementPVCTableEntry OBJECT-TYPE
          SYNTAX TeraManagementPVCTableEntryType
          ACCESS not-accessible
          STATUS mandatory
          DESCRIPTION
               " table entry teraManagementPVCTableEntry "
          INDEX {                   teraManagementPVCNumber }
     ::= { teraManagementPVCTable 1 }

TeraManagementPVCTableEntryType ::= SEQUENCE {
          teraManagementPVCNumber   
             INTEGER (1..10),
          teraManagementPVCAdminStatus   
             INTEGER,
          teraManagementPVCPortIfIndex   
             INTEGER (0..2147483647),
          teraManagementPVCVclVpi   
             INTEGER (0..4095),
          teraManagementPVCVclVci   
             INTEGER (0..4095),
          teraManagementPVCIPAddress   
             IpAddress,
          teraManagementPVCIPNetMask   
             IpAddress,
          teraManagementPVCIPGateway   
             IpAddress,
          teraManagementPVCIPMtu   
             INTEGER (0..2048),
          teraManagementPVCIPEncapsType   
             INTEGER
}

teraManagementPVCNumber OBJECT-TYPE
          SYNTAX INTEGER (1..10)
          ACCESS read-only
          STATUS mandatory
          DESCRIPTION
               ""
          ::= { teraManagementPVCTableEntry 1 }

teraManagementPVCAdminStatus OBJECT-TYPE
          SYNTAX INTEGER
                  {
                  disable(1),
                  enable(2)
                  }
          ACCESS read-write
          STATUS mandatory
          DESCRIPTION
               ""
          ::= { teraManagementPVCTableEntry 2 }

teraManagementPVCPortIfIndex OBJECT-TYPE
          SYNTAX INTEGER (0..2147483647)
          ACCESS read-write
          STATUS mandatory
          DESCRIPTION
               ""
          ::= { teraManagementPVCTableEntry 3 }

teraManagementPVCVclVpi OBJECT-TYPE
          SYNTAX INTEGER (0..4095)
          ACCESS read-write
          STATUS mandatory
          DESCRIPTION
               ""
          ::= { teraManagementPVCTableEntry 4 }

teraManagementPVCVclVci OBJECT-TYPE
          SYNTAX INTEGER (0..4095)
          ACCESS read-write
          STATUS mandatory
          DESCRIPTION
               ""
          ::= { teraManagementPVCTableEntry 5 }

teraManagementPVCIPAddress OBJECT-TYPE
          SYNTAX IpAddress
          ACCESS read-write
          STATUS mandatory
          DESCRIPTION
               ""
          ::= { teraManagementPVCTableEntry 6 }

teraManagementPVCIPNetMask OBJECT-TYPE
          SYNTAX IpAddress
          ACCESS read-write
          STATUS mandatory
          DESCRIPTION
               ""
          ::= { teraManagementPVCTableEntry 7 }

teraManagementPVCIPGateway OBJECT-TYPE
          SYNTAX IpAddress
          ACCESS read-write
          STATUS mandatory
          DESCRIPTION
               ""
          ::= { teraManagementPVCTableEntry 8 }

teraManagementPVCIPMtu OBJECT-TYPE
          SYNTAX INTEGER (0..2048)
          ACCESS read-write
          STATUS mandatory
          DESCRIPTION
               ""
          ::= { teraManagementPVCTableEntry 9 }

teraManagementPVCIPEncapsType OBJECT-TYPE
          SYNTAX INTEGER
                  {
                  llcNone(1),
                  llcRoutedIPv4(2),
                  llcRoutedIPv4AtmArp(3)
                  }
          ACCESS read-write
          STATUS mandatory
          DESCRIPTION
               ""
          ::= { teraManagementPVCTableEntry 10 }

     -- teraONTconTable

teraONTconTable OBJECT-TYPE
     SYNTAX SEQUENCE OF TeraONTconTableEntryType
     ACCESS not-accessible
     STATUS mandatory
     DESCRIPTION
          " table teraONTconTable"
     ::= { connections 8 }

teraONTconTableEntry OBJECT-TYPE
          SYNTAX TeraONTconTableEntryType
          ACCESS not-accessible
          STATUS mandatory
          DESCRIPTION
               " table entry teraONTconTableEntry "
          INDEX {                   teraONTconID }
     ::= { teraONTconTable 1 }

TeraONTconTableEntryType ::= SEQUENCE {
          teraONTconID   
             Counter32,
          teraONTfirstCONIfIndex   
             INTEGER,
          teraONTsecondCONIfIndex   
             INTEGER,
          teraONTfirstCONVPI   
             INTEGER,
          teraONTfirstCONVCI   
             INTEGER,
          teraONTsecondCONVPI   
             INTEGER,
          teraONTsecondCONVCI   
             INTEGER,
          teraONTconVLANNumber   
             INTEGER (0..4094),
          teraONTrequestedCONBW   
             INTEGER,
          teraONTfirstInternalVPI   
             INTEGER,
          teraONTfirstInternalVCI   
             INTEGER,
          teraONTsecondInternalVPI   
             INTEGER,
          teraONTsecondInternalVCI   
             INTEGER,
          teraONTconStatus   
             INTEGER
}

teraONTconID OBJECT-TYPE
          SYNTAX Counter32
          ACCESS read-only
          STATUS mandatory
          DESCRIPTION
               ""
          ::= { teraONTconTableEntry 1 }

teraONTfirstCONIfIndex OBJECT-TYPE
          SYNTAX INTEGER
          ACCESS read-only
          STATUS mandatory
          DESCRIPTION
               ""
          ::= { teraONTconTableEntry 2 }

teraONTsecondCONIfIndex OBJECT-TYPE
          SYNTAX INTEGER
          ACCESS read-only
          STATUS mandatory
          DESCRIPTION
               ""
          ::= { teraONTconTableEntry 3 }

teraONTfirstCONVPI OBJECT-TYPE
          SYNTAX INTEGER
          ACCESS read-only
          STATUS mandatory
          DESCRIPTION
               ""
          ::= { teraONTconTableEntry 4 }

teraONTfirstCONVCI OBJECT-TYPE
          SYNTAX INTEGER
          ACCESS read-only
          STATUS mandatory
          DESCRIPTION
               ""
          ::= { teraONTconTableEntry 5 }

teraONTsecondCONVPI OBJECT-TYPE
          SYNTAX INTEGER
          ACCESS read-only
          STATUS mandatory
          DESCRIPTION
               ""
          ::= { teraONTconTableEntry 6 }

teraONTsecondCONVCI OBJECT-TYPE
          SYNTAX INTEGER
          ACCESS read-only
          STATUS mandatory
          DESCRIPTION
               ""
          ::= { teraONTconTableEntry 7 }

teraONTconVLANNumber OBJECT-TYPE
          SYNTAX INTEGER (0..4094)
          ACCESS read-only
          STATUS mandatory
          DESCRIPTION
               ""
          ::= { teraONTconTableEntry 8 }

teraONTrequestedCONBW OBJECT-TYPE
          SYNTAX INTEGER
                  {
                  atm(1),
                  vlan-c(2),
                  t1(3),
                  e1(4),
                  ds3(5),
                  e3(6),
                  oc3(7),
                  stm1(8),
                  atm-vpi(9)
                  }
          ACCESS read-only
          STATUS mandatory
          DESCRIPTION
               ""
          ::= { teraONTconTableEntry 9 }

teraONTfirstInternalVPI OBJECT-TYPE
          SYNTAX INTEGER
          ACCESS read-only
          STATUS mandatory
          DESCRIPTION
               ""
          ::= { teraONTconTableEntry 10 }

teraONTfirstInternalVCI OBJECT-TYPE
          SYNTAX INTEGER
          ACCESS read-only
          STATUS mandatory
          DESCRIPTION
               ""
          ::= { teraONTconTableEntry 11 }

teraONTsecondInternalVPI OBJECT-TYPE
          SYNTAX INTEGER
          ACCESS read-only
          STATUS mandatory
          DESCRIPTION
               ""
          ::= { teraONTconTableEntry 12 }

teraONTsecondInternalVCI OBJECT-TYPE
          SYNTAX INTEGER
          ACCESS read-only
          STATUS mandatory
          DESCRIPTION
               ""
          ::= { teraONTconTableEntry 13 }

teraONTconStatus OBJECT-TYPE
          SYNTAX INTEGER
                  {
                  up(1),
                  down(2)
                  }
          ACCESS read-only
          STATUS mandatory
          DESCRIPTION
               ""
          ::= { teraONTconTableEntry 14 }

END
