CROSSBEAM-SYSTEMS-MIB DEFINITIONS ::= BEGIN

IMPORTS
   enterprises, MODULE-IDENTITY   FROM SNMPv2-SMI;

crossbeamSystems  OBJECT IDENTIFIER ::= { enterprises 6848 }

cbsProducts      OBJECT IDENTIFIER ::= { crossbeamSystems 1 }
cbsMgmt          OBJECT IDENTIFIER ::= { crossbeamSystems 2 }
cbsMIBs          OBJECT IDENTIFIER ::= { crossbeamSystems 3 }
cbsTraps         OBJECT IDENTIFIER ::= { crossbeamSystems 4 }

crossbeamSystemsMIB MODULE-IDENTITY
   LAST-UPDATED "200203150000Z"     -- 2 March 2001
   ORGANIZATION "Crossbeam Systems, Inc."
   CONTACT-INFO "Email:  mib-admin@crossbeamsys.com
                 Postal: 80 Central Street
                         Boxborough, MA  01719"
   DESCRIPTION  "XOS, Release 9.5: This MIB module defines the objects 
                 used to identify the ProductIDs for Crossbeam Systems 
                 products."

   REVISION     "200305090000Z"     -- 9 May 2003
   DESCRIPTION  "Added new chassis and module types for X45 and
                 X80"

   REVISION     "200203150000Z"     -- 15 March 2002
   DESCRIPTION  "Initial Revision"

   REVISION     "200403100000Z"     -- 10 March 2004
   DESCRIPTION  "Added Product Identifier for C10 Chassis Type"

   REVISION     "200405100000Z"     -- 10 May 2004
   DESCRIPTION  "Added Product Identifier for C30i Chassis Type"

   REVISION     "200407070000Z"     -- 07 July 2004
   DESCRIPTION  "Added Product Identifier for AP8400"

   REVISION     "200508220000Z"     -- 22 Aug 2005
   DESCRIPTION  "Added Product Identifier for C2 and C6"

   REVISION     "200510250000Z"     -- 25 Oct 2005
   DESCRIPTION  "Added Product Identifier for CP8400"

   REVISION     "200602070000Z"     -- 07 Feb 2006
   DESCRIPTION  "Added Product Identifier for C12 and C25"

   REVISION     "201004140000Z"     -- 14 April 2010
   DESCRIPTION  "Revise cbsCPM8650 to cbsCPM9600"

   REVISION     "201006170000Z"     -- 17 June 2010
   DESCRIPTION  "Added new chassis type for X60"

   REVISION     "201008100000Z"     -- 10 Aug 2010
   DESCRIPTION  "Added new chassis types for X20 and X30"

   REVISION     "201008110000Z"     -- 11 August 2010
   DESCRIPTION  "Added new module type APM 9600"

   REVISION     "201010080000Z"     -- 08 Oct 2010
   DESCRIPTION  "Added new module type APM 2030, NPM20 and NPM30"

::= { cbsMIBs 1 }

-- Product Identifiers

cbsX40        OBJECT IDENTIFIER ::= { cbsProducts 1 }
cbsXSeries    OBJECT IDENTIFIER ::= { cbsProducts 2 }
cbsCSeries    OBJECT IDENTIFIER ::= { cbsProducts 3 }


-- Chassis

cbsXChassis   OBJECT IDENTIFIER ::= { cbsXSeries 1 }

cbsX45Chassis OBJECT IDENTIFIER ::= { cbsXChassis 1 }
cbsX80Chassis OBJECT IDENTIFIER ::= { cbsXChassis 2 }
cbsX60Chassis OBJECT IDENTIFIER ::= { cbsXChassis 3 }
cbsX20Chassis OBJECT IDENTIFIER ::= { cbsXChassis 4 }
cbsX30Chassis OBJECT IDENTIFIER ::= { cbsXChassis 5 }

cbsX40Chassis OBJECT IDENTIFIER ::= { cbsX40 1 }

cbsCChassis   OBJECT IDENTIFIER ::= { cbsCSeries 1 }

cbsC30Chassis OBJECT IDENTIFIER ::= { cbsCChassis 1 }

cbsC10Chassis OBJECT IDENTIFIER ::= { cbsCChassis 2 }

cbsC30iChassis OBJECT IDENTIFIER ::= { cbsCChassis 3 }

cbsC2Chassis OBJECT IDENTIFIER ::= { cbsCChassis 4 }

cbsC6Chassis OBJECT IDENTIFIER ::= { cbsCChassis 5 }

cbsC12Chassis OBJECT IDENTIFIER ::= { cbsCChassis 6 }

cbsC25Chassis OBJECT IDENTIFIER ::= { cbsCChassis 7 }

-- X Series Modules

cbsX40Modules OBJECT IDENTIFIER ::= { cbsX40 2 }

cbsCPModules   OBJECT IDENTIFIER ::= { cbsX40Modules 1 }
cbsAPModules   OBJECT IDENTIFIER ::= { cbsX40Modules 2 }
cbsNPModules   OBJECT IDENTIFIER ::= { cbsX40Modules 3 }


-- Control Processor Modules
cbsCPM4100     OBJECT IDENTIFIER ::= { cbsCPModules 1 }
cbsCPM8100     OBJECT IDENTIFIER ::= { cbsCPModules 2 }
cbsCPM8400     OBJECT IDENTIFIER ::= { cbsCPModules 3 }
cbsCPM8600     OBJECT IDENTIFIER ::= { cbsCPModules 4 }
cbsCPM9600     OBJECT IDENTIFIER ::= { cbsCPModules 5 }

-- Application Processor Modules

-- Single P-III 1 GHz 
cbsAPM4100    OBJECT IDENTIFIER ::= { cbsAPModules 1 }

-- Single P-III 1.4 GHz
cbsAPM4200    OBJECT IDENTIFIER ::= { cbsAPModules 2 }

-- Dual P-III 1.4 GHz
cbsAPM4250    OBJECT IDENTIFIER ::= { cbsAPModules 3 }

-- X80 Compatible Application Processor Modules
cbsAPM8200    OBJECT IDENTIFIER ::= { cbsAPModules 4 }
cbsAPM8400    OBJECT IDENTIFIER ::= { cbsAPModules 5 }
cbsAPM8600    OBJECT IDENTIFIER ::= { cbsAPModules 6 }
cbsAPM8650    OBJECT IDENTIFIER ::= { cbsAPModules 7 }
cbsAPM9600    OBJECT IDENTIFIER ::= { cbsAPModules 8 }
cbsAPM2030    OBJECT IDENTIFIER ::= { cbsAPModules 9 }

-- Network Processor Modules

-- Dual Gigabit Ethernet
cbsNPM4100    OBJECT IDENTIFIER ::= { cbsNPModules 1 }

-- Single Gigabit Ethernet/Octal fastethernet
cbsNPM4110    OBJECT IDENTIFIER ::= { cbsNPModules 2 }

-- Octal Gigabit
cbsNPM8200    OBJECT IDENTIFIER ::= { cbsNPModules 3 }

-- 16 port Fastethernet
cbsNPM8210    OBJECT IDENTIFIER ::= { cbsNPModules 4 }

-- 10 Gigabit Ethernet/Dual 10Gigabit Ethernet
cbsNPM8600    OBJECT IDENTIFIER ::= { cbsNPModules 5 }
cbsNPM8650    OBJECT IDENTIFIER ::= { cbsNPModules 6 }
cbsNPM30      OBJECT IDENTIFIER ::= { cbsNPModules 8 }

-- 10 Gigabit Ethernet
cbsNPM8620    OBJECT IDENTIFIER ::= { cbsNPModules 7 }
cbsNPM20    OBJECT IDENTIFIER ::= { cbsNPModules 9 }

END
