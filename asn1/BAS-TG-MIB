BAS-TG-MIB DEFINITIONS ::= BEGIN

IMPORTS
    MODULE-IDENTITY, OBJECT-TYPE, Counter32,
    IpAddress                                                   FROM SNMPv2-SMI
    RowStatus                                                   FROM SNMPv2-TC
    basTrafGen                                                  FROM BAS-MIB;

basTrafGenMIB MODULE-IDENTITY
    LAST-UPDATED "9902031415Z"
    ORGANIZATION "Broadband Access Systems, Inc."
    CONTACT-INFO
        " Tech Support
          Broadband Access Systems, Inc.
          201 Forest Street
          Marlborough, MA 01752
          USA

          508-485-8200
          support@basystems.com"
    DESCRIPTION
        "The MIB module defines the configuration MIB objects
         for Broadband Access Systems, Inc. Traffic Generation
         extensions."
    ::= { basTrafGen 1 }


-- the BAS Traffic Generation table

-- The BAS Traffic Generation table contains BAS proprietaryinformation on
-- the entity's Traffic Generation.

basTrafGenTable OBJECT-TYPE
    SYNTAX      SEQUENCE OF BasTrafGenEntry
    MAX-ACCESS  not-accessible
    STATUS      current
    DESCRIPTION
        "A list of traffic generation entries.  The number of entries
        is given by the value of ifNumber."
    ::= { basTrafGenMIB 1 }

basTrafGenEntry OBJECT-TYPE
    SYNTAX      BasTrafGenEntry
    MAX-ACCESS  not-accessible
    STATUS      current
    DESCRIPTION
        "An entry containing management information applicable
        to a particular traffic generation."
    INDEX {basTrafGenIndex}
    ::= { basTrafGenTable 1 }

BasTrafGenEntry ::=
    SEQUENCE {
        basTrafGenIndex       INTEGER,
        basTrafGenTransport   INTEGER,
        basTrafGenPort        INTEGER,
        basTrafGenStart       INTEGER,
        basTrafGenRate        INTEGER,
        basTrafGenDest        IpAddress,
        basTrafGenSrc         IpAddress,
        basTrafGenIn          Counter32,
        basTrafGenOut         Counter32,
        basTrafGenSeqError    Counter32,
        basTrafGenSize        INTEGER,
        basTrafGenPattern     INTEGER,
        basTrafGenReset       INTEGER,    
        basTrafGenStatus      RowStatus    
    }

basTrafGenIndex OBJECT-TYPE
    SYNTAX      INTEGER
    MAX-ACCESS  read-only
    STATUS      current
    DESCRIPTION
        "Used to create an instance of GenTraff."
    ::= { basTrafGenEntry 1 }

basTrafGenTransport OBJECT-TYPE
    SYNTAX      INTEGER {
                basTrafIp(1),
                basTrafUdp(2),
                basTrafTcp(3)
                }
    MAX-ACCESS  read-create
    STATUS      current
    DESCRIPTION
        "Transport to use."
    DEFVAL {1}
    ::= { basTrafGenEntry 2 }

basTrafGenPort OBJECT-TYPE
    SYNTAX      INTEGER
    MAX-ACCESS  read-create
    STATUS      current
    DESCRIPTION
        "Port to use."
    DEFVAL {99}
    ::= { basTrafGenEntry 3 }

basTrafGenStart OBJECT-TYPE
    SYNTAX      INTEGER {
                basTrafStart(1),
                basTrafStop(2)
                }
    MAX-ACCESS  read-create
    STATUS      current
    DESCRIPTION
        "Stop and start traffic."
    DEFVAL {2}
    ::= { basTrafGenEntry 4 }

basTrafGenRate OBJECT-TYPE
    SYNTAX     INTEGER {
               basTranMax(1),
               basTran1sec(2)
               }
    MAX-ACCESS  read-create
    STATUS      current
    DESCRIPTION
        "Rate of sending max means no delay between transmissions. 1sec means send
        one packet per second."
    DEFVAL {1}
    ::= { basTrafGenEntry 5 }

basTrafGenDest OBJECT-TYPE
    SYNTAX     IpAddress
    MAX-ACCESS  read-create
    STATUS      current
    DESCRIPTION
        "Destination IP address."
    ::= { basTrafGenEntry 6 }

basTrafGenSrc OBJECT-TYPE
    SYNTAX     IpAddress
    MAX-ACCESS  read-create
    STATUS      current
    DESCRIPTION
        "Destination IP address."
    ::= { basTrafGenEntry 7 }

basTrafGenIn OBJECT-TYPE
    SYNTAX     Counter32
    MAX-ACCESS  read-only
    STATUS      current
    DESCRIPTION
        "Received packets."
    ::= { basTrafGenEntry 8 }

basTrafGenOut OBJECT-TYPE
    SYNTAX     Counter32
    MAX-ACCESS  read-only
    STATUS      current
    DESCRIPTION
        "Sent packets."
    ::= { basTrafGenEntry 9 }

basTrafGenSeqError OBJECT-TYPE
    SYNTAX      Counter32
    MAX-ACCESS  read-only
    STATUS      current
    DESCRIPTION
        "Sequence error count."
    ::= { basTrafGenEntry 10 }

basTrafGenSize  OBJECT-TYPE
    SYNTAX      INTEGER
    MAX-ACCESS  read-create
    STATUS      current
    DESCRIPTION
        "Packet size."
    ::= { basTrafGenEntry 11 }

basTrafGenPattern OBJECT-TYPE
    SYNTAX      INTEGER
    MAX-ACCESS  read-create
    STATUS      current
    DESCRIPTION
        "32 bit pattern to send."
    ::= { basTrafGenEntry 12 }

basTrafGenReset OBJECT-TYPE
    SYNTAX      INTEGER
    MAX-ACCESS  read-create
    STATUS      current
    DESCRIPTION
        "Status."
    ::= { basTrafGenEntry 13 }

basTrafGenStatus OBJECT-TYPE
    SYNTAX      RowStatus
    MAX-ACCESS  read-create
    STATUS      current
    DESCRIPTION
        "Status."
    ::= { basTrafGenEntry 14 }

END
