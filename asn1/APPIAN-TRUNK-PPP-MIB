--
--      Title:  Appian PPP/MLPPP Services MIB
--
--      Dated:  11/8/99
--      Author: D. Theriault
--
--      Description:
--
--      This MIB file contains the definitions and support for the Appian
--      Optical Services Access Platform(s).
-- 
--      This MIB is a subsection of the Appian Services MIB (services.mib) and
--      contains the configuration and statistics MIBs for the Point-to-Point
--      and Multi-Link Point-to-Point protocol.
--
--  Notes:
--
--      1.  Now that there will be a multilink flag in the acTrunkTable may
--          want to break out the MLPPP stuff into its own table
--
APPIAN-TRUNK-PPP-MIB  DEFINITIONS ::= BEGIN
    IMPORTS
        acTrunks                                            FROM APPIAN-SMI-MIB
        
        MODULE-IDENTITY, OBJECT-TYPE                        FROM SNMPv2-SMI

        TruthValue                                          FROM SNMPv2-TC;

--
-- Top Level PPP Node
--        
acPppTrunk

    MODULE-IDENTITY
        LAST-UPDATED    "0003200000Z"
        ORGANIZATION    "Appian Communications, Inc."
        CONTACT-INFO    "Gerry Pednault"

        DESCRIPTION     "Appian Communications PPP/MLPPP Services MIB."

        REVISION        "0003200000Z"
        DESCRIPTION     "Appian Initial release."

        ::= { acTrunks 3 }


--
-- PPP Trunk Configuration Table
--
acPppTrunkTable   OBJECT-TYPE
    SYNTAX    SEQUENCE OF AcPppTrunkEntry
    MAX-ACCESS    not-accessible
    STATUS    current
    DESCRIPTION
    "A table containing PPP-link specific configuration information. This
     table is created, with reasonable defaults, whenever the associated 
     acTrunkTable acTrunkProt field is set to 'PPP' or 'MLPPP'. Managment 
     of this record is required only when it is desired to change the 
     reasonable default. "
    
    ::= { acPppTrunk 1 }

acPppTrunkEntry   OBJECT-TYPE
    SYNTAX  AcPppTrunkEntry
    MAX-ACCESS  not-accessible
    STATUS      current
    DESCRIPTION
    "Configuration information about a particular PPP Link."
    
    INDEX { acPppTrunkIndex }
               
    ::= { acPppTrunkTable 1 }

     AcPppTrunkEntry ::= 
        SEQUENCE {
            acPppTrunkIndex                      INTEGER,
            acPppTrunkMru                        INTEGER,
            acPppTrunkMrru                       INTEGER,
            acPppTrunkSeqNum                     INTEGER,
            acPppTrunkMagicNumberEnable          TruthValue,
            acPppTrunkLCPEchoEnable              TruthValue,
            acPppTrunkLCPEchoInterval            INTEGER,
            acPppTrunkMgmtAccess                 TruthValue,
            acPppTrunkIPCPAddressEnable          TruthValue,
            acPppTrunkMaxTerminate               INTEGER,
            acPppTrunkMaxConfigure               INTEGER, 
            acPppTrunkMaxFailure                 INTEGER      
        }


acPppTrunkIndex  OBJECT-TYPE
    SYNTAX  INTEGER (0..2147483647)
    MAX-ACCESS  accessible-for-notify
    STATUS      current
    DESCRIPTION
    "The trunk entry that this PPP / MLPPP configuration is associated."

     ::= { acPppTrunkEntry 1 }


acPppTrunkMru    OBJECT-TYPE
    SYNTAX  INTEGER (64..2048)
    MAX-ACCESS  read-write
    STATUS      deprecated
    DESCRIPTION
    "This attribute has been deprecated - it no longer has an effect."
    DEFVAL      { 1520 } 
    
    ::= { acPppTrunkEntry 2 }

acPppTrunkMrru    OBJECT-TYPE
    SYNTAX  INTEGER (64..2048)
    MAX-ACCESS  read-write
    STATUS      deprecated
    DESCRIPTION
    "This attribute has been deprecated - it no longer has an effect."
    DEFVAL      { 1520 } 
    
    ::= { acPppTrunkEntry 3 }

acPppTrunkSeqNum OBJECT-TYPE
     SYNTAX  INTEGER {
                long(0),
                short(1)
            }
    MAX-ACCESS  read-write
    STATUS      current
    DESCRIPTION
    "Defines the type of multilink sequence number to use. There are two 
    possible sequence number types: long and short. Long sequence numbers 
    are 24 bit values. Short sequence numbers are 12 bit values. The default
    is the PPP standard of long sequence numbers"
    DEFVAL      { long }   

    ::= {acPppTrunkEntry 4 }

acPppTrunkMagicNumberEnable  OBJECT-TYPE
    SYNTAX  TruthValue
    MAX-ACCESS  read-write
    STATUS      current
    DESCRIPTION
    "Enables the inclusion of magic numbers in LCP messages. This, in
    conjunction with LCP echo is useful to detect non-transitory loopback
    conditions. This feature defaults to enabled (True)." 
    DEFVAL     { true } 

    ::= { acPppTrunkEntry 5 }


acPppTrunkLCPEchoEnable  OBJECT-TYPE
    SYNTAX  TruthValue
    MAX-ACCESS  read-write
    STATUS      current
    DESCRIPTION
    "Enables the OSAP initiation of LCP Echo message sequence processing. 
    This attribute also controls link keepalive processing which is based 
    upon LCP echo processing.
    This feature defaults to enabled (True)." 
    DEFVAL      { true } 
    
    ::= { acPppTrunkEntry 6 }

acPppTrunkLCPEchoInterval  OBJECT-TYPE
    SYNTAX  INTEGER (1..3600)
    MAX-ACCESS  read-write
    STATUS      current
    DESCRIPTION
    "Time in seconds between OSAP initiated echo sequences.  The default is 60
    seconds. The range is an integer which is expressed in seconds supporting
    1 second to 1 hour in length. This value has a direct relationship to how
    long it takes to detect a PPP link down condition via keepalive processing.
    The lower this value the quicker a PPP link down condition will be 
    detected. 
    The default for this value is 1"
    DEFVAL      { 1 } 

    ::= { acPppTrunkEntry 7 }

acPppTrunkMgmtAccess    OBJECT-TYPE
    SYNTAX  TruthValue
    MAX-ACCESS  read-write
    STATUS      current
    DESCRIPTION
    "This attribute controls how a PPP trunk starts up. It is used to indicate 
     if this is an inband managment trunk. TRUE indicates the trunk can be
     exclusively used for inband managment. FALSE indicates the trunk is a data
     trunk only. A PPP trunk can not be used for inband managment and data 
     passing at the same time. The default for this attribute is FALSE"
    DEFVAL      { false }

    ::= { acPppTrunkEntry 8 }

acPppTrunkIPCPAddressEnable    OBJECT-TYPE
    SYNTAX  TruthValue
    MAX-ACCESS  read-write
    STATUS      current
    DESCRIPTION
    "This attribute controls if IP address negotiation occurs during the 
    IPCP phase of a PPP trunk startup. If this attribute is set to TRUE the
    IP address negotiation will occur. If this attribute is set to FALSE then
    IP address negotiation will not occur.
    The default for this attribute will be FALSE"
    DEFVAL      { false }

    ::= { acPppTrunkEntry 9 }


acPppTrunkMaxTerminate    OBJECT-TYPE
    SYNTAX  INTEGER
    MAX-ACCESS  read-write
    STATUS      current
    DESCRIPTION 
    "Max-Terminate indicates the number of Terminate-Request packets sent 
    without receiving a Terminate-Ack before assuming that the peer is unable 
    to respond."

    DEFVAL      { 2 }

    ::= { acPppTrunkEntry 10 }


acPppTrunkMaxConfigure    OBJECT-TYPE
    SYNTAX  INTEGER
    MAX-ACCESS  read-write
    STATUS      current
    DESCRIPTION 
    "Max-Configure indicates the number of Configure-Request packets sent
    without receiving a valid Configure-Ack, Configure-Nak or
    Configure-Reject before assuming that the peer is unable to respond."

    DEFVAL      { 10 }

    ::= { acPppTrunkEntry 11 }


acPppTrunkMaxFailure    OBJECT-TYPE
    SYNTAX  INTEGER
    MAX-ACCESS  read-write
    STATUS      current
    DESCRIPTION 
    "Max-Failure indicates the number of Configure-Nak packets sent without 
    sending a Configure-Ack before assuming that configuration is not converging."

    DEFVAL      { 5 }

    ::= { acPppTrunkEntry 12 }


END
